AFFIRMED-SERVICECONSTRUCT-MIB DEFINITIONS ::= BEGIN
IMPORTS
    MODULE-IDENTITY, OBJECT-TYPE,
    Integer32, Unsigned32, Counter32, Counter64,
    Gauge32, IpAddress
        FROM SNMPv2-SMI
    TEXTUAL-CONVENTION, RowStatus, DateAndTime,
    TruthValue
        FROM SNMPv2-TC
;

affirmedServiceconstructMIB MODULE-IDENTITY
    ORGANIZATION "Affirmed Networks, Inc."
    CONTACT-INFO "Affirmed Networks, Inc. 35 Nagog Park, Acton, MA, USA"
    DESCRIPTION ""
    ::= { 1 3 6 1 4 1 37963 10 16 }

ConfdString ::= TEXTUAL-CONVENTION
    DISPLAY-HINT "1t"
    STATUS      current
    DESCRIPTION "xs: and confd: types mapped to strings"
    SYNTAX      OCTET STRING

String ::= TEXTUAL-CONVENTION
    DISPLAY-HINT "1t"
    STATUS      current
    DESCRIPTION "xs:string"
    SYNTAX      OCTET STRING

affirmedServiceconstruct OBJECT IDENTIFIER ::= { affirmedServiceconstructMIB 1 }

affirmedServiceconstructInterface OBJECT IDENTIFIER ::= { affirmedServiceconstruct 1 }

affirmedServiceconstructInterfaceAaaGroup OBJECT IDENTIFIER ::= { affirmedServiceconstructInterface 1 }

affirmedServiceconstructInterfaceAaaGroupDiameter OBJECT IDENTIFIER ::= { affirmedServiceconstructInterfaceAaaGroup 1 }

affirmedServiceconstructInterfaceAaaGroupDiameterStatistics OBJECT IDENTIFIER ::= { affirmedServiceconstructInterfaceAaaGroupDiameter 5 }

affirmedServiceconstructInterfaceAaaGroupDiameterStatisticsChassisLevel OBJECT IDENTIFIER ::= { affirmedServiceconstructInterfaceAaaGroupDiameterStatistics 1 }

affirmedServiceconstructInterfaceAaaGroupDiameterStatisticsChassisLevelPeer OBJECT IDENTIFIER ::= { affirmedServiceconstructInterfaceAaaGroupDiameterStatisticsChassisLevel 1 }

affirmedServiceconstructInterfaceAaaGroupDiameterStatisticsChassisLevelEndhost OBJECT IDENTIFIER ::= { affirmedServiceconstructInterfaceAaaGroupDiameterStatisticsChassisLevel 2 }

affirmedServiceconstructInterfaceAaaGroupGtpp OBJECT IDENTIFIER ::= { affirmedServiceconstructInterfaceAaaGroup 2 }

affirmedServiceconstructInterfaceAaaGroupGtppStatistics OBJECT IDENTIFIER ::= { affirmedServiceconstructInterfaceAaaGroupGtpp 5 }

affirmedServiceconstructInterfaceAaaGroupGtppStatisticsChassisLevel OBJECT IDENTIFIER ::= { affirmedServiceconstructInterfaceAaaGroupGtppStatistics 1 }

affirmedServiceconstructInterfaceAaaGroupGtppStatisticsChassisLevelPeer OBJECT IDENTIFIER ::= { affirmedServiceconstructInterfaceAaaGroupGtppStatisticsChassisLevel 1 }

affirmedServiceconstructInterfaceAaaGroupRadius OBJECT IDENTIFIER ::= { affirmedServiceconstructInterfaceAaaGroup 3 }

affirmedServiceconstructInterfaceAaaGroupRadiusStatus OBJECT IDENTIFIER ::= { affirmedServiceconstructInterfaceAaaGroupRadius 1 }

affirmedServiceconstructInterfaceAaaGroupRadiusStatistics OBJECT IDENTIFIER ::= { affirmedServiceconstructInterfaceAaaGroupRadius 2 }

affirmedServiceconstructInterfaceAaaGroupRadiusStatisticsGridLevel OBJECT IDENTIFIER ::= { affirmedServiceconstructInterfaceAaaGroupRadiusStatistics 1 }

affirmedServiceconstructInterfaceAaaGroupRadiusStatisticsGridLevelProcStats OBJECT IDENTIFIER ::= { affirmedServiceconstructInterfaceAaaGroupRadiusStatisticsGridLevel 1 }

affirmedServiceconstructInterfaceAaaGroupRadiusStatisticsChassisLevel OBJECT IDENTIFIER ::= { affirmedServiceconstructInterfaceAaaGroupRadiusStatistics 2 }

affirmedServiceconstructInterfaceAaaGroupRadiusStatisticsChassisLevelProcStats OBJECT IDENTIFIER ::= { affirmedServiceconstructInterfaceAaaGroupRadiusStatisticsChassisLevel 1 }

affirmedServiceconstructInterfaceAaaGroupRadiusStatisticsSlotLevel OBJECT IDENTIFIER ::= { affirmedServiceconstructInterfaceAaaGroupRadiusStatistics 3 }

affirmedServiceconstructInterfaceAaaGroupRadiusStatisticsSlotLevelProcStats OBJECT IDENTIFIER ::= { affirmedServiceconstructInterfaceAaaGroupRadiusStatisticsSlotLevel 1 }

affirmedServiceconstructInterfaceAaaGroupRadiusServer OBJECT IDENTIFIER ::= { affirmedServiceconstructInterfaceAaaGroup 4 }

affirmedServiceconstructInterfaceAaaGroupRadiusServerStatistics OBJECT IDENTIFIER ::= { affirmedServiceconstructInterfaceAaaGroupRadiusServer 1 }

affirmedServiceconstructInterfaceAaaGroupRadiusServerStatisticsChassisLevel OBJECT IDENTIFIER ::= { affirmedServiceconstructInterfaceAaaGroupRadiusServerStatistics 1 }

affirmedServiceconstructInterfaceAaaGroupRadiusServerStatisticsChassisLevelServerStats OBJECT IDENTIFIER ::= { affirmedServiceconstructInterfaceAaaGroupRadiusServerStatisticsChassisLevel 1 }

affirmedServiceconstructInterfaceIpms OBJECT IDENTIFIER ::= { affirmedServiceconstructInterface 2 }

affirmedServiceconstructInterfaceIpmsStatistics OBJECT IDENTIFIER ::= { affirmedServiceconstructInterfaceIpms 1 }

affirmedServiceconstructInterfaceIpmsStatus OBJECT IDENTIFIER ::= { affirmedServiceconstructInterfaceIpms 2 }

affirmedServiceconstructInterfaceDb-interface OBJECT IDENTIFIER ::= { affirmedServiceconstructInterface 3 }

affirmedServiceconstructInterfaceT8Interface OBJECT IDENTIFIER ::= { affirmedServiceconstructInterface 4 }

affirmedServiceconstructInterfaceT8InterfaceStatistics OBJECT IDENTIFIER ::= { affirmedServiceconstructInterfaceT8Interface 1 }

affirmedServiceconstructInterfaceT8InterfaceStatisticsDebug OBJECT IDENTIFIER ::= { affirmedServiceconstructInterfaceT8InterfaceStatistics 4 }

affirmedServiceconstructInterfaceT8InterfaceStatisticsDebugRestClient OBJECT IDENTIFIER ::= { affirmedServiceconstructInterfaceT8InterfaceStatisticsDebug 1 }

affirmedServiceconstructControlServiceProfile OBJECT IDENTIFIER ::= { affirmedServiceconstruct 4 }

affirmedServiceconstructControlServiceProfileDhcp OBJECT IDENTIFIER ::= { affirmedServiceconstructControlServiceProfile 1 }

affirmedServiceconstructUrlListStats OBJECT IDENTIFIER ::= { affirmedServiceconstruct 2 }

affirmedServiceconstructDeviceDatabaseStats OBJECT IDENTIFIER ::= { affirmedServiceconstruct 9 }

affirmedServiceconstructFilterHashListStats OBJECT IDENTIFIER ::= { affirmedServiceconstruct 8 }

affirmedServiceconstructManifestInterfaceStats OBJECT IDENTIFIER ::= { affirmedServiceconstruct 10 }

affirmedServiceconstructManifestInterfaceStatsStatistics OBJECT IDENTIFIER ::= { affirmedServiceconstructManifestInterfaceStats 1 }

affirmedServiceconstructManifestInterfaceStatsStatisticsClusterLevel OBJECT IDENTIFIER ::= { affirmedServiceconstructManifestInterfaceStatsStatistics 1 }

affirmedServiceconstructRadiusMapping OBJECT IDENTIFIER ::= { affirmedServiceconstruct 5 }

affirmedServiceconstructDhcpMapping OBJECT IDENTIFIER ::= { affirmedServiceconstruct 6 }

affirmedServiceconstructInterfaceAaaGroupDiameterStatisticsChassisLevelPeerInterfaceTypeTable OBJECT-TYPE
    SYNTAX      SEQUENCE OF AffirmedServiceconstructInterfaceAaaGroupDiameterStatisticsChassisLevelPeerInterfaceTypeEntry
    MAX-ACCESS  not-accessible
    STATUS      deprecated
    DESCRIPTION ""
    ::= { affirmedServiceconstructInterfaceAaaGroupDiameterStatisticsChassisLevelPeer 1 }

affirmedServiceconstructInterfaceAaaGroupDiameterStatisticsChassisLevelPeerInterfaceTypeEntry OBJECT-TYPE
    SYNTAX      AffirmedServiceconstructInterfaceAaaGroupDiameterStatisticsChassisLevelPeerInterfaceTypeEntry
    MAX-ACCESS  not-accessible
    STATUS      deprecated
    DESCRIPTION ""
    INDEX { affirmedServiceconstructInterfaceAaaGroupDiameterStatisticsChassisLevelPeerInterfaceTypeIfType, affirmedServiceconstructInterfaceAaaGroupDiameterStatisticsChassisLevelPeerInterfaceTypeNodeName, affirmedServiceconstructInterfaceAaaGroupDiameterStatisticsChassisLevelPeerInterfaceTypePeerName }
        ::= { affirmedServiceconstructInterfaceAaaGroupDiameterStatisticsChassisLevelPeerInterfaceTypeTable 1 }

AffirmedServiceconstructInterfaceAaaGroupDiameterStatisticsChassisLevelPeerInterfaceTypeEntry ::=
    SEQUENCE {
        affirmedServiceconstructInterfaceAaaGroupDiameterStatisticsChassisLevelPeerInterfaceTypeIfType INTEGER,
        affirmedServiceconstructInterfaceAaaGroupDiameterStatisticsChassisLevelPeerInterfaceTypeNodeName String,
        affirmedServiceconstructInterfaceAaaGroupDiameterStatisticsChassisLevelPeerInterfaceTypePeerName String,
        affirmedServiceconstructInterfaceAaaGroupDiameterStatisticsChassisLevelPeerInterfaceTypeChassis Unsigned32,
        affirmedServiceconstructInterfaceAaaGroupDiameterStatisticsChassisLevelPeerInterfaceTypeNumCCRInitialAttempted ConfdString,
        affirmedServiceconstructInterfaceAaaGroupDiameterStatisticsChassisLevelPeerInterfaceTypeNumCCRInitialSuccess ConfdString,
        affirmedServiceconstructInterfaceAaaGroupDiameterStatisticsChassisLevelPeerInterfaceTypeNumCCRInitialFailure ConfdString,
        affirmedServiceconstructInterfaceAaaGroupDiameterStatisticsChassisLevelPeerInterfaceTypeNumCCRInitialTimeout ConfdString,
        affirmedServiceconstructInterfaceAaaGroupDiameterStatisticsChassisLevelPeerInterfaceTypeNumCCAInitialRcvdFirstAttempt ConfdString,
        affirmedServiceconstructInterfaceAaaGroupDiameterStatisticsChassisLevelPeerInterfaceTypeNumCCAInitialRcvdReTx ConfdString,
        affirmedServiceconstructInterfaceAaaGroupDiameterStatisticsChassisLevelPeerInterfaceTypeNumCCRInitialStoredForReplay ConfdString,
        affirmedServiceconstructInterfaceAaaGroupDiameterStatisticsChassisLevelPeerInterfaceTypeNumCCRUpdateAttempted ConfdString,
        affirmedServiceconstructInterfaceAaaGroupDiameterStatisticsChassisLevelPeerInterfaceTypeNumCCRUpdateSuccess ConfdString,
        affirmedServiceconstructInterfaceAaaGroupDiameterStatisticsChassisLevelPeerInterfaceTypeNumCCRUpdateFailure ConfdString,
        affirmedServiceconstructInterfaceAaaGroupDiameterStatisticsChassisLevelPeerInterfaceTypeNumCCRUpdateTimeout ConfdString,
        affirmedServiceconstructInterfaceAaaGroupDiameterStatisticsChassisLevelPeerInterfaceTypeNumCCAUpdateRcvdFirstAttempt ConfdString,
        affirmedServiceconstructInterfaceAaaGroupDiameterStatisticsChassisLevelPeerInterfaceTypeNumCCAUpdateRcvdReTx ConfdString,
        affirmedServiceconstructInterfaceAaaGroupDiameterStatisticsChassisLevelPeerInterfaceTypeNumCCRUpdateStoredForReplay ConfdString,
        affirmedServiceconstructInterfaceAaaGroupDiameterStatisticsChassisLevelPeerInterfaceTypeNumCCRTerminateAttempted ConfdString,
        affirmedServiceconstructInterfaceAaaGroupDiameterStatisticsChassisLevelPeerInterfaceTypeNumCCRTerminateSuccess ConfdString,
        affirmedServiceconstructInterfaceAaaGroupDiameterStatisticsChassisLevelPeerInterfaceTypeNumCCRTerminateFailure ConfdString,
        affirmedServiceconstructInterfaceAaaGroupDiameterStatisticsChassisLevelPeerInterfaceTypeNumCCRTerminateTimeout ConfdString,
        affirmedServiceconstructInterfaceAaaGroupDiameterStatisticsChassisLevelPeerInterfaceTypeNumCCATerminateRcvdFirstAttempt ConfdString,
        affirmedServiceconstructInterfaceAaaGroupDiameterStatisticsChassisLevelPeerInterfaceTypeNumCCATerminateRcvdReTx ConfdString,
        affirmedServiceconstructInterfaceAaaGroupDiameterStatisticsChassisLevelPeerInterfaceTypeNumCCRTerminateStoredForReplay ConfdString,
        affirmedServiceconstructInterfaceAaaGroupDiameterStatisticsChassisLevelPeerInterfaceTypeNumDiameterSessions ConfdString
    }

affirmedServiceconstructInterfaceAaaGroupDiameterStatisticsChassisLevelPeerInterfaceTypeIfType OBJECT-TYPE
    SYNTAX      INTEGER {gx(1),gy(2),gz(3),s6b(4),sta(5),swm(6),flowauth(7),sxab(8),s6t(9),t6a(10),s6m(11),t4(12),sd(15)}
    MAX-ACCESS  not-accessible
    STATUS      current
    DESCRIPTION "Interface Type - enum list"
    ::= { affirmedServiceconstructInterfaceAaaGroupDiameterStatisticsChassisLevelPeerInterfaceTypeEntry 1 }

affirmedServiceconstructInterfaceAaaGroupDiameterStatisticsChassisLevelPeerInterfaceTypeNodeName OBJECT-TYPE
    SYNTAX      String
    MAX-ACCESS  not-accessible
    STATUS      current
    DESCRIPTION "Local Diameter Node Name"
    ::= { affirmedServiceconstructInterfaceAaaGroupDiameterStatisticsChassisLevelPeerInterfaceTypeEntry 2 }

affirmedServiceconstructInterfaceAaaGroupDiameterStatisticsChassisLevelPeerInterfaceTypePeerName OBJECT-TYPE
    SYNTAX      String
    MAX-ACCESS  not-accessible
    STATUS      current
    DESCRIPTION "Peer name"
    ::= { affirmedServiceconstructInterfaceAaaGroupDiameterStatisticsChassisLevelPeerInterfaceTypeEntry 3 }

affirmedServiceconstructInterfaceAaaGroupDiameterStatisticsChassisLevelPeerInterfaceTypeChassis OBJECT-TYPE
    SYNTAX      Unsigned32
    MAX-ACCESS  read-only
    STATUS      deprecated
    DESCRIPTION "chassis ID"
    ::= { affirmedServiceconstructInterfaceAaaGroupDiameterStatisticsChassisLevelPeerInterfaceTypeEntry 4 }

affirmedServiceconstructInterfaceAaaGroupDiameterStatisticsChassisLevelPeerInterfaceTypeNumCCRInitialAttempted OBJECT-TYPE
    SYNTAX      ConfdString
    MAX-ACCESS  read-only
    STATUS      current
    DESCRIPTION "Number of CCR Initial attempts made"
    ::= { affirmedServiceconstructInterfaceAaaGroupDiameterStatisticsChassisLevelPeerInterfaceTypeEntry 5 }

affirmedServiceconstructInterfaceAaaGroupDiameterStatisticsChassisLevelPeerInterfaceTypeNumCCRInitialSuccess OBJECT-TYPE
    SYNTAX      ConfdString
    MAX-ACCESS  read-only
    STATUS      current
    DESCRIPTION "Number of successful CCR Initial attempts"
    ::= { affirmedServiceconstructInterfaceAaaGroupDiameterStatisticsChassisLevelPeerInterfaceTypeEntry 6 }

affirmedServiceconstructInterfaceAaaGroupDiameterStatisticsChassisLevelPeerInterfaceTypeNumCCRInitialFailure OBJECT-TYPE
    SYNTAX      ConfdString
    MAX-ACCESS  read-only
    STATUS      current
    DESCRIPTION "Number of failed CCR Initial attempts"
    ::= { affirmedServiceconstructInterfaceAaaGroupDiameterStatisticsChassisLevelPeerInterfaceTypeEntry 7 }

affirmedServiceconstructInterfaceAaaGroupDiameterStatisticsChassisLevelPeerInterfaceTypeNumCCRInitialTimeout OBJECT-TYPE
    SYNTAX      ConfdString
    MAX-ACCESS  read-only
    STATUS      current
    DESCRIPTION "Number of CCR Initial attempts that timed out"
    ::= { affirmedServiceconstructInterfaceAaaGroupDiameterStatisticsChassisLevelPeerInterfaceTypeEntry 8 }

affirmedServiceconstructInterfaceAaaGroupDiameterStatisticsChassisLevelPeerInterfaceTypeNumCCAInitialRcvdFirstAttempt OBJECT-TYPE
    SYNTAX      ConfdString
    MAX-ACCESS  read-only
    STATUS      current
    DESCRIPTION "Number of CCR Initial requests for which response was received when first transmitted "
    ::= { affirmedServiceconstructInterfaceAaaGroupDiameterStatisticsChassisLevelPeerInterfaceTypeEntry 9 }

affirmedServiceconstructInterfaceAaaGroupDiameterStatisticsChassisLevelPeerInterfaceTypeNumCCAInitialRcvdReTx OBJECT-TYPE
    SYNTAX      ConfdString
    MAX-ACCESS  read-only
    STATUS      current
    DESCRIPTION "Number of CCR Initial Requests for which response was received when message was retransmitted"
    ::= { affirmedServiceconstructInterfaceAaaGroupDiameterStatisticsChassisLevelPeerInterfaceTypeEntry 10 }

affirmedServiceconstructInterfaceAaaGroupDiameterStatisticsChassisLevelPeerInterfaceTypeNumCCRInitialStoredForReplay OBJECT-TYPE
    SYNTAX      ConfdString
    MAX-ACCESS  read-only
    STATUS      current
    DESCRIPTION "Number of CCR Initial Requests stored for replay"
    ::= { affirmedServiceconstructInterfaceAaaGroupDiameterStatisticsChassisLevelPeerInterfaceTypeEntry 11 }

affirmedServiceconstructInterfaceAaaGroupDiameterStatisticsChassisLevelPeerInterfaceTypeNumCCRUpdateAttempted OBJECT-TYPE
    SYNTAX      ConfdString
    MAX-ACCESS  read-only
    STATUS      current
    DESCRIPTION "Number of CCR Update attempts made"
    ::= { affirmedServiceconstructInterfaceAaaGroupDiameterStatisticsChassisLevelPeerInterfaceTypeEntry 12 }

affirmedServiceconstructInterfaceAaaGroupDiameterStatisticsChassisLevelPeerInterfaceTypeNumCCRUpdateSuccess OBJECT-TYPE
    SYNTAX      ConfdString
    MAX-ACCESS  read-only
    STATUS      current
    DESCRIPTION "Number of successful CCR Update attempts"
    ::= { affirmedServiceconstructInterfaceAaaGroupDiameterStatisticsChassisLevelPeerInterfaceTypeEntry 13 }

affirmedServiceconstructInterfaceAaaGroupDiameterStatisticsChassisLevelPeerInterfaceTypeNumCCRUpdateFailure OBJECT-TYPE
    SYNTAX      ConfdString
    MAX-ACCESS  read-only
    STATUS      current
    DESCRIPTION "Number of failed CCR Update attempts"
    ::= { affirmedServiceconstructInterfaceAaaGroupDiameterStatisticsChassisLevelPeerInterfaceTypeEntry 14 }

affirmedServiceconstructInterfaceAaaGroupDiameterStatisticsChassisLevelPeerInterfaceTypeNumCCRUpdateTimeout OBJECT-TYPE
    SYNTAX      ConfdString
    MAX-ACCESS  read-only
    STATUS      current
    DESCRIPTION "Number of CCR Update attempts that timed out"
    ::= { affirmedServiceconstructInterfaceAaaGroupDiameterStatisticsChassisLevelPeerInterfaceTypeEntry 15 }

affirmedServiceconstructInterfaceAaaGroupDiameterStatisticsChassisLevelPeerInterfaceTypeNumCCAUpdateRcvdFirstAttempt OBJECT-TYPE
    SYNTAX      ConfdString
    MAX-ACCESS  read-only
    STATUS      current
    DESCRIPTION "Number of CCA Update requests for which response was received when first transmitted "
    ::= { affirmedServiceconstructInterfaceAaaGroupDiameterStatisticsChassisLevelPeerInterfaceTypeEntry 16 }

affirmedServiceconstructInterfaceAaaGroupDiameterStatisticsChassisLevelPeerInterfaceTypeNumCCAUpdateRcvdReTx OBJECT-TYPE
    SYNTAX      ConfdString
    MAX-ACCESS  read-only
    STATUS      current
    DESCRIPTION "Number of CCR Update Requests for which response was received when message was retransmitted"
    ::= { affirmedServiceconstructInterfaceAaaGroupDiameterStatisticsChassisLevelPeerInterfaceTypeEntry 17 }

affirmedServiceconstructInterfaceAaaGroupDiameterStatisticsChassisLevelPeerInterfaceTypeNumCCRUpdateStoredForReplay OBJECT-TYPE
    SYNTAX      ConfdString
    MAX-ACCESS  read-only
    STATUS      current
    DESCRIPTION "Number of CCR Update Requests stored for replay"
    ::= { affirmedServiceconstructInterfaceAaaGroupDiameterStatisticsChassisLevelPeerInterfaceTypeEntry 18 }

affirmedServiceconstructInterfaceAaaGroupDiameterStatisticsChassisLevelPeerInterfaceTypeNumCCRTerminateAttempted OBJECT-TYPE
    SYNTAX      ConfdString
    MAX-ACCESS  read-only
    STATUS      current
    DESCRIPTION "Number of CCR Terminate attempts made"
    ::= { affirmedServiceconstructInterfaceAaaGroupDiameterStatisticsChassisLevelPeerInterfaceTypeEntry 19 }

affirmedServiceconstructInterfaceAaaGroupDiameterStatisticsChassisLevelPeerInterfaceTypeNumCCRTerminateSuccess OBJECT-TYPE
    SYNTAX      ConfdString
    MAX-ACCESS  read-only
    STATUS      current
    DESCRIPTION "Number of successful CCR Terminate attempts"
    ::= { affirmedServiceconstructInterfaceAaaGroupDiameterStatisticsChassisLevelPeerInterfaceTypeEntry 20 }

affirmedServiceconstructInterfaceAaaGroupDiameterStatisticsChassisLevelPeerInterfaceTypeNumCCRTerminateFailure OBJECT-TYPE
    SYNTAX      ConfdString
    MAX-ACCESS  read-only
    STATUS      current
    DESCRIPTION "Number of failed CCR Terminate attempts"
    ::= { affirmedServiceconstructInterfaceAaaGroupDiameterStatisticsChassisLevelPeerInterfaceTypeEntry 21 }

affirmedServiceconstructInterfaceAaaGroupDiameterStatisticsChassisLevelPeerInterfaceTypeNumCCRTerminateTimeout OBJECT-TYPE
    SYNTAX      ConfdString
    MAX-ACCESS  read-only
    STATUS      current
    DESCRIPTION "Number of CCR Terminate attempts that timed out"
    ::= { affirmedServiceconstructInterfaceAaaGroupDiameterStatisticsChassisLevelPeerInterfaceTypeEntry 22 }

affirmedServiceconstructInterfaceAaaGroupDiameterStatisticsChassisLevelPeerInterfaceTypeNumCCATerminateRcvdFirstAttempt OBJECT-TYPE
    SYNTAX      ConfdString
    MAX-ACCESS  read-only
    STATUS      current
    DESCRIPTION "Number of CCA Terminate requests for which response was received when first transmitted "
    ::= { affirmedServiceconstructInterfaceAaaGroupDiameterStatisticsChassisLevelPeerInterfaceTypeEntry 23 }

affirmedServiceconstructInterfaceAaaGroupDiameterStatisticsChassisLevelPeerInterfaceTypeNumCCATerminateRcvdReTx OBJECT-TYPE
    SYNTAX      ConfdString
    MAX-ACCESS  read-only
    STATUS      current
    DESCRIPTION "Number of CCR Terminate Requests for which response was received when message was retransmitted"
    ::= { affirmedServiceconstructInterfaceAaaGroupDiameterStatisticsChassisLevelPeerInterfaceTypeEntry 24 }

affirmedServiceconstructInterfaceAaaGroupDiameterStatisticsChassisLevelPeerInterfaceTypeNumCCRTerminateStoredForReplay OBJECT-TYPE
    SYNTAX      ConfdString
    MAX-ACCESS  read-only
    STATUS      current
    DESCRIPTION "Number of CCR Terminate Requests stored for replay"
    ::= { affirmedServiceconstructInterfaceAaaGroupDiameterStatisticsChassisLevelPeerInterfaceTypeEntry 25 }

affirmedServiceconstructInterfaceAaaGroupDiameterStatisticsChassisLevelPeerInterfaceTypeNumDiameterSessions OBJECT-TYPE
    SYNTAX      ConfdString
    MAX-ACCESS  read-only
    STATUS      current
    DESCRIPTION "Number of subscribers using the diameter connection"
    ::= { affirmedServiceconstructInterfaceAaaGroupDiameterStatisticsChassisLevelPeerInterfaceTypeEntry 26 }

affirmedServiceconstructInterfaceAaaGroupDiameterStatisticsChassisLevelPeerDiameterInterfaceTypeTable OBJECT-TYPE
    SYNTAX      SEQUENCE OF AffirmedServiceconstructInterfaceAaaGroupDiameterStatisticsChassisLevelPeerDiameterInterfaceTypeEntry
    MAX-ACCESS  not-accessible
    STATUS      current
    DESCRIPTION ""
    ::= { affirmedServiceconstructInterfaceAaaGroupDiameterStatisticsChassisLevelPeer 2 }

affirmedServiceconstructInterfaceAaaGroupDiameterStatisticsChassisLevelPeerDiameterInterfaceTypeEntry OBJECT-TYPE
    SYNTAX      AffirmedServiceconstructInterfaceAaaGroupDiameterStatisticsChassisLevelPeerDiameterInterfaceTypeEntry
    MAX-ACCESS  not-accessible
    STATUS      current
    DESCRIPTION ""
    INDEX { affirmedServiceconstructInterfaceAaaGroupDiameterStatisticsChassisLevelPeerDiameterInterfaceTypeIntfType, affirmedServiceconstructInterfaceAaaGroupDiameterStatisticsChassisLevelPeerDiameterInterfaceTypeNodeName, affirmedServiceconstructInterfaceAaaGroupDiameterStatisticsChassisLevelPeerDiameterInterfaceTypePeerName }
        ::= { affirmedServiceconstructInterfaceAaaGroupDiameterStatisticsChassisLevelPeerDiameterInterfaceTypeTable 1 }

AffirmedServiceconstructInterfaceAaaGroupDiameterStatisticsChassisLevelPeerDiameterInterfaceTypeEntry ::=
    SEQUENCE {
        affirmedServiceconstructInterfaceAaaGroupDiameterStatisticsChassisLevelPeerDiameterInterfaceTypeIntfType String,
        affirmedServiceconstructInterfaceAaaGroupDiameterStatisticsChassisLevelPeerDiameterInterfaceTypeNodeName String,
        affirmedServiceconstructInterfaceAaaGroupDiameterStatisticsChassisLevelPeerDiameterInterfaceTypePeerName String,
        affirmedServiceconstructInterfaceAaaGroupDiameterStatisticsChassisLevelPeerDiameterInterfaceTypeNumCCRInitialAttempted ConfdString,
        affirmedServiceconstructInterfaceAaaGroupDiameterStatisticsChassisLevelPeerDiameterInterfaceTypeNumCCRInitialSuccess ConfdString,
        affirmedServiceconstructInterfaceAaaGroupDiameterStatisticsChassisLevelPeerDiameterInterfaceTypeNumCCRInitialFailure ConfdString,
        affirmedServiceconstructInterfaceAaaGroupDiameterStatisticsChassisLevelPeerDiameterInterfaceTypeNumCCRInitialTimeout ConfdString,
        affirmedServiceconstructInterfaceAaaGroupDiameterStatisticsChassisLevelPeerDiameterInterfaceTypeNumCCAInitialRcvdFirstAttempt ConfdString,
        affirmedServiceconstructInterfaceAaaGroupDiameterStatisticsChassisLevelPeerDiameterInterfaceTypeNumCCAInitialRcvdReTx ConfdString,
        affirmedServiceconstructInterfaceAaaGroupDiameterStatisticsChassisLevelPeerDiameterInterfaceTypeNumCCRInitialStoredForReplay ConfdString,
        affirmedServiceconstructInterfaceAaaGroupDiameterStatisticsChassisLevelPeerDiameterInterfaceTypeNumCCRUpdateAttempted ConfdString,
        affirmedServiceconstructInterfaceAaaGroupDiameterStatisticsChassisLevelPeerDiameterInterfaceTypeNumCCRUpdateSuccess ConfdString,
        affirmedServiceconstructInterfaceAaaGroupDiameterStatisticsChassisLevelPeerDiameterInterfaceTypeNumCCRUpdateFailure ConfdString,
        affirmedServiceconstructInterfaceAaaGroupDiameterStatisticsChassisLevelPeerDiameterInterfaceTypeNumCCRUpdateTimeout ConfdString,
        affirmedServiceconstructInterfaceAaaGroupDiameterStatisticsChassisLevelPeerDiameterInterfaceTypeNumCCAUpdateRcvdFirstAttempt ConfdString,
        affirmedServiceconstructInterfaceAaaGroupDiameterStatisticsChassisLevelPeerDiameterInterfaceTypeNumCCAUpdateRcvdReTx ConfdString,
        affirmedServiceconstructInterfaceAaaGroupDiameterStatisticsChassisLevelPeerDiameterInterfaceTypeNumCCRUpdateStoredForReplay ConfdString,
        affirmedServiceconstructInterfaceAaaGroupDiameterStatisticsChassisLevelPeerDiameterInterfaceTypeNumCCRTerminateAttempted ConfdString,
        affirmedServiceconstructInterfaceAaaGroupDiameterStatisticsChassisLevelPeerDiameterInterfaceTypeNumCCRTerminateSuccess ConfdString,
        affirmedServiceconstructInterfaceAaaGroupDiameterStatisticsChassisLevelPeerDiameterInterfaceTypeNumCCRTerminateFailure ConfdString,
        affirmedServiceconstructInterfaceAaaGroupDiameterStatisticsChassisLevelPeerDiameterInterfaceTypeNumCCRTerminateTimeout ConfdString,
        affirmedServiceconstructInterfaceAaaGroupDiameterStatisticsChassisLevelPeerDiameterInterfaceTypeNumCCATerminateRcvdFirstAttempt ConfdString,
        affirmedServiceconstructInterfaceAaaGroupDiameterStatisticsChassisLevelPeerDiameterInterfaceTypeNumCCATerminateRcvdReTx ConfdString,
        affirmedServiceconstructInterfaceAaaGroupDiameterStatisticsChassisLevelPeerDiameterInterfaceTypeNumCCRTerminateStoredForReplay ConfdString,
        affirmedServiceconstructInterfaceAaaGroupDiameterStatisticsChassisLevelPeerDiameterInterfaceTypeNumDiameterSessions ConfdString,
        affirmedServiceconstructInterfaceAaaGroupDiameterStatisticsChassisLevelPeerDiameterInterfaceTypeNumCCRInitialReplay ConfdString,
        affirmedServiceconstructInterfaceAaaGroupDiameterStatisticsChassisLevelPeerDiameterInterfaceTypeNumCCRInitialReplayReTx ConfdString,
        affirmedServiceconstructInterfaceAaaGroupDiameterStatisticsChassisLevelPeerDiameterInterfaceTypeNumCCRInitialReplaySuccess ConfdString,
        affirmedServiceconstructInterfaceAaaGroupDiameterStatisticsChassisLevelPeerDiameterInterfaceTypeNumCCRInitialReplayFailure ConfdString,
        affirmedServiceconstructInterfaceAaaGroupDiameterStatisticsChassisLevelPeerDiameterInterfaceTypeNumCCRUpdateReplay ConfdString,
        affirmedServiceconstructInterfaceAaaGroupDiameterStatisticsChassisLevelPeerDiameterInterfaceTypeNumCCRUpdateReplayReTx ConfdString,
        affirmedServiceconstructInterfaceAaaGroupDiameterStatisticsChassisLevelPeerDiameterInterfaceTypeNumCCRUpdateReplaySuccess ConfdString,
        affirmedServiceconstructInterfaceAaaGroupDiameterStatisticsChassisLevelPeerDiameterInterfaceTypeNumCCRUpdateReplayFailure ConfdString,
        affirmedServiceconstructInterfaceAaaGroupDiameterStatisticsChassisLevelPeerDiameterInterfaceTypeNumCCRTerminateReplay ConfdString,
        affirmedServiceconstructInterfaceAaaGroupDiameterStatisticsChassisLevelPeerDiameterInterfaceTypeNumCCRTerminateReplayReTx ConfdString,
        affirmedServiceconstructInterfaceAaaGroupDiameterStatisticsChassisLevelPeerDiameterInterfaceTypeNumCCRTerminateReplaySuccess ConfdString,
        affirmedServiceconstructInterfaceAaaGroupDiameterStatisticsChassisLevelPeerDiameterInterfaceTypeNumCCRTerminateReplayFailure ConfdString,
        affirmedServiceconstructInterfaceAaaGroupDiameterStatisticsChassisLevelPeerDiameterInterfaceTypeNumACRStartAttempted ConfdString,
        affirmedServiceconstructInterfaceAaaGroupDiameterStatisticsChassisLevelPeerDiameterInterfaceTypeNumACRStartSuccess ConfdString,
        affirmedServiceconstructInterfaceAaaGroupDiameterStatisticsChassisLevelPeerDiameterInterfaceTypeNumACRStartFailure ConfdString,
        affirmedServiceconstructInterfaceAaaGroupDiameterStatisticsChassisLevelPeerDiameterInterfaceTypeNumACRStartReTx ConfdString,
        affirmedServiceconstructInterfaceAaaGroupDiameterStatisticsChassisLevelPeerDiameterInterfaceTypeNumACRInterimAttempted ConfdString,
        affirmedServiceconstructInterfaceAaaGroupDiameterStatisticsChassisLevelPeerDiameterInterfaceTypeNumACRInterimSuccess ConfdString,
        affirmedServiceconstructInterfaceAaaGroupDiameterStatisticsChassisLevelPeerDiameterInterfaceTypeNumACRInterimFailure ConfdString,
        affirmedServiceconstructInterfaceAaaGroupDiameterStatisticsChassisLevelPeerDiameterInterfaceTypeNumACRInterimReTx ConfdString,
        affirmedServiceconstructInterfaceAaaGroupDiameterStatisticsChassisLevelPeerDiameterInterfaceTypeNumACRStopAttempted ConfdString,
        affirmedServiceconstructInterfaceAaaGroupDiameterStatisticsChassisLevelPeerDiameterInterfaceTypeNumACRStopSuccess ConfdString,
        affirmedServiceconstructInterfaceAaaGroupDiameterStatisticsChassisLevelPeerDiameterInterfaceTypeNumACRStopFailure ConfdString,
        affirmedServiceconstructInterfaceAaaGroupDiameterStatisticsChassisLevelPeerDiameterInterfaceTypeNumACRStopReTx ConfdString,
        affirmedServiceconstructInterfaceAaaGroupDiameterStatisticsChassisLevelPeerDiameterInterfaceTypeNumACREventAttempted ConfdString,
        affirmedServiceconstructInterfaceAaaGroupDiameterStatisticsChassisLevelPeerDiameterInterfaceTypeNumACREventSuccess ConfdString,
        affirmedServiceconstructInterfaceAaaGroupDiameterStatisticsChassisLevelPeerDiameterInterfaceTypeNumACREventFailure ConfdString,
        affirmedServiceconstructInterfaceAaaGroupDiameterStatisticsChassisLevelPeerDiameterInterfaceTypeNumACREventReTx ConfdString,
        affirmedServiceconstructInterfaceAaaGroupDiameterStatisticsChassisLevelPeerDiameterInterfaceTypeNumCCAInitial3xxx ConfdString,
        affirmedServiceconstructInterfaceAaaGroupDiameterStatisticsChassisLevelPeerDiameterInterfaceTypeNumCCRInitialAborted ConfdString,
        affirmedServiceconstructInterfaceAaaGroupDiameterStatisticsChassisLevelPeerDiameterInterfaceTypeNumCCAInitialDelayedSuccess ConfdString,
        affirmedServiceconstructInterfaceAaaGroupDiameterStatisticsChassisLevelPeerDiameterInterfaceTypeNumCCAInitialDelayedFailure ConfdString,
        affirmedServiceconstructInterfaceAaaGroupDiameterStatisticsChassisLevelPeerDiameterInterfaceTypeNumCCAInitialDelayed3xxx ConfdString,
        affirmedServiceconstructInterfaceAaaGroupDiameterStatisticsChassisLevelPeerDiameterInterfaceTypeNumCCAUpdate3xxx ConfdString,
        affirmedServiceconstructInterfaceAaaGroupDiameterStatisticsChassisLevelPeerDiameterInterfaceTypeNumCCRUpdateAborted ConfdString,
        affirmedServiceconstructInterfaceAaaGroupDiameterStatisticsChassisLevelPeerDiameterInterfaceTypeNumCCAUpdateDelayedSuccess ConfdString,
        affirmedServiceconstructInterfaceAaaGroupDiameterStatisticsChassisLevelPeerDiameterInterfaceTypeNumCCAUpdateDelayedFailure ConfdString,
        affirmedServiceconstructInterfaceAaaGroupDiameterStatisticsChassisLevelPeerDiameterInterfaceTypeNumCCAUpdateDelayed3xxx ConfdString,
        affirmedServiceconstructInterfaceAaaGroupDiameterStatisticsChassisLevelPeerDiameterInterfaceTypeNumCCATerminate3xxx ConfdString,
        affirmedServiceconstructInterfaceAaaGroupDiameterStatisticsChassisLevelPeerDiameterInterfaceTypeNumCCRTerminateAborted ConfdString,
        affirmedServiceconstructInterfaceAaaGroupDiameterStatisticsChassisLevelPeerDiameterInterfaceTypeNumCCATerminateDelayedSuccess ConfdString,
        affirmedServiceconstructInterfaceAaaGroupDiameterStatisticsChassisLevelPeerDiameterInterfaceTypeNumCCATerminateDelayedFailure ConfdString,
        affirmedServiceconstructInterfaceAaaGroupDiameterStatisticsChassisLevelPeerDiameterInterfaceTypeNumCCATerminateDelayed3xxx ConfdString,
        affirmedServiceconstructInterfaceAaaGroupDiameterStatisticsChassisLevelPeerDiameterInterfaceTypeNumCCAInitialDroppedBadSeqNum ConfdString,
        affirmedServiceconstructInterfaceAaaGroupDiameterStatisticsChassisLevelPeerDiameterInterfaceTypeNumCCAInitialDroppedNoSession ConfdString,
        affirmedServiceconstructInterfaceAaaGroupDiameterStatisticsChassisLevelPeerDiameterInterfaceTypeNumCCAInitialDroppedNoProc ConfdString,
        affirmedServiceconstructInterfaceAaaGroupDiameterStatisticsChassisLevelPeerDiameterInterfaceTypeNumCCAUpdateDroppedBadSeqNum ConfdString,
        affirmedServiceconstructInterfaceAaaGroupDiameterStatisticsChassisLevelPeerDiameterInterfaceTypeNumCCAUpdateDroppedNoSession ConfdString,
        affirmedServiceconstructInterfaceAaaGroupDiameterStatisticsChassisLevelPeerDiameterInterfaceTypeNumCCAUpdateDroppedNoProc ConfdString,
        affirmedServiceconstructInterfaceAaaGroupDiameterStatisticsChassisLevelPeerDiameterInterfaceTypeNumCCATerminateDroppedBadSeqNum ConfdString,
        affirmedServiceconstructInterfaceAaaGroupDiameterStatisticsChassisLevelPeerDiameterInterfaceTypeNumCCATerminateDroppedNoSession ConfdString,
        affirmedServiceconstructInterfaceAaaGroupDiameterStatisticsChassisLevelPeerDiameterInterfaceTypeNumCCATerminateDroppedNoProc ConfdString,
        affirmedServiceconstructInterfaceAaaGroupDiameterStatisticsChassisLevelPeerDiameterInterfaceTypeNumTimesPeerDeactivated ConfdString,
        affirmedServiceconstructInterfaceAaaGroupDiameterStatisticsChassisLevelPeerDiameterInterfaceTypeNumTimesPeerFlowOffRcvd ConfdString,
        affirmedServiceconstructInterfaceAaaGroupDiameterStatisticsChassisLevelPeerDiameterInterfaceTypeNumAARInitialAttempted ConfdString,
        affirmedServiceconstructInterfaceAaaGroupDiameterStatisticsChassisLevelPeerDiameterInterfaceTypeNumAARInitialSuccess ConfdString,
        affirmedServiceconstructInterfaceAaaGroupDiameterStatisticsChassisLevelPeerDiameterInterfaceTypeNumAARInitialFailure ConfdString,
        affirmedServiceconstructInterfaceAaaGroupDiameterStatisticsChassisLevelPeerDiameterInterfaceTypeNumAARInitialTimeout ConfdString,
        affirmedServiceconstructInterfaceAaaGroupDiameterStatisticsChassisLevelPeerDiameterInterfaceTypeNumAAAInitialRcvdFirstAttempt ConfdString,
        affirmedServiceconstructInterfaceAaaGroupDiameterStatisticsChassisLevelPeerDiameterInterfaceTypeNumAAAInitialRcvdReTx ConfdString,
        affirmedServiceconstructInterfaceAaaGroupDiameterStatisticsChassisLevelPeerDiameterInterfaceTypeNumSTRAttempted ConfdString,
        affirmedServiceconstructInterfaceAaaGroupDiameterStatisticsChassisLevelPeerDiameterInterfaceTypeNumSTRSuccess ConfdString,
        affirmedServiceconstructInterfaceAaaGroupDiameterStatisticsChassisLevelPeerDiameterInterfaceTypeNumSTRFailure ConfdString,
        affirmedServiceconstructInterfaceAaaGroupDiameterStatisticsChassisLevelPeerDiameterInterfaceTypeNumSTRTimeout ConfdString,
        affirmedServiceconstructInterfaceAaaGroupDiameterStatisticsChassisLevelPeerDiameterInterfaceTypeNumSTARcvdFirstAttempt ConfdString,
        affirmedServiceconstructInterfaceAaaGroupDiameterStatisticsChassisLevelPeerDiameterInterfaceTypeNumSTARcvdReTx ConfdString,
        affirmedServiceconstructInterfaceAaaGroupDiameterStatisticsChassisLevelPeerDiameterInterfaceTypeNumHandoffAARAttempted ConfdString,
        affirmedServiceconstructInterfaceAaaGroupDiameterStatisticsChassisLevelPeerDiameterInterfaceTypeNumHandoffAARSuccess ConfdString,
        affirmedServiceconstructInterfaceAaaGroupDiameterStatisticsChassisLevelPeerDiameterInterfaceTypeNumHandoffAARFailure ConfdString,
        affirmedServiceconstructInterfaceAaaGroupDiameterStatisticsChassisLevelPeerDiameterInterfaceTypeNumHandoffAARTimeout ConfdString,
        affirmedServiceconstructInterfaceAaaGroupDiameterStatisticsChassisLevelPeerDiameterInterfaceTypeNumHandoffAAARcvdFirstAttempt ConfdString,
        affirmedServiceconstructInterfaceAaaGroupDiameterStatisticsChassisLevelPeerDiameterInterfaceTypeNumHandoffAAARcvdReTx ConfdString,
        affirmedServiceconstructInterfaceAaaGroupDiameterStatisticsChassisLevelPeerDiameterInterfaceTypeNumRarInitAARAttempted ConfdString,
        affirmedServiceconstructInterfaceAaaGroupDiameterStatisticsChassisLevelPeerDiameterInterfaceTypeNumRarInitAARSuccess ConfdString,
        affirmedServiceconstructInterfaceAaaGroupDiameterStatisticsChassisLevelPeerDiameterInterfaceTypeNumRarInitAARFailure ConfdString,
        affirmedServiceconstructInterfaceAaaGroupDiameterStatisticsChassisLevelPeerDiameterInterfaceTypeNumRarInitAARTimeout ConfdString,
        affirmedServiceconstructInterfaceAaaGroupDiameterStatisticsChassisLevelPeerDiameterInterfaceTypeNumRarInitAAARcvdFirstAttempt ConfdString,
        affirmedServiceconstructInterfaceAaaGroupDiameterStatisticsChassisLevelPeerDiameterInterfaceTypeNumRarInitAAARcvdReTx ConfdString,
        affirmedServiceconstructInterfaceAaaGroupDiameterStatisticsChassisLevelPeerDiameterInterfaceTypeNumDERInitialAttempted ConfdString,
        affirmedServiceconstructInterfaceAaaGroupDiameterStatisticsChassisLevelPeerDiameterInterfaceTypeNumDERInitialSuccess ConfdString,
        affirmedServiceconstructInterfaceAaaGroupDiameterStatisticsChassisLevelPeerDiameterInterfaceTypeNumDERInitialFailure ConfdString,
        affirmedServiceconstructInterfaceAaaGroupDiameterStatisticsChassisLevelPeerDiameterInterfaceTypeNumDERInitialTimeout ConfdString,
        affirmedServiceconstructInterfaceAaaGroupDiameterStatisticsChassisLevelPeerDiameterInterfaceTypeNumDERInitialChallenge ConfdString,
        affirmedServiceconstructInterfaceAaaGroupDiameterStatisticsChassisLevelPeerDiameterInterfaceTypeNumDERInitialNotification ConfdString,
        affirmedServiceconstructInterfaceAaaGroupDiameterStatisticsChassisLevelPeerDiameterInterfaceTypeNumDERReAuthAttempted ConfdString,
        affirmedServiceconstructInterfaceAaaGroupDiameterStatisticsChassisLevelPeerDiameterInterfaceTypeNumDERReAuthSuccess ConfdString,
        affirmedServiceconstructInterfaceAaaGroupDiameterStatisticsChassisLevelPeerDiameterInterfaceTypeNumDERReAuthFailure ConfdString,
        affirmedServiceconstructInterfaceAaaGroupDiameterStatisticsChassisLevelPeerDiameterInterfaceTypeNumDERReAuthTimeout ConfdString,
        affirmedServiceconstructInterfaceAaaGroupDiameterStatisticsChassisLevelPeerDiameterInterfaceTypeNumDERReAuthChallenge ConfdString,
        affirmedServiceconstructInterfaceAaaGroupDiameterStatisticsChassisLevelPeerDiameterInterfaceTypeNumDERReAuthNotification ConfdString,
        affirmedServiceconstructInterfaceAaaGroupDiameterStatisticsChassisLevelPeerDiameterInterfaceTypeNumRarRcvd ConfdString,
        affirmedServiceconstructInterfaceAaaGroupDiameterStatisticsChassisLevelPeerDiameterInterfaceTypeNumRarFailure ConfdString,
        affirmedServiceconstructInterfaceAaaGroupDiameterStatisticsChassisLevelPeerDiameterInterfaceTypeNumAsrRcvd ConfdString,
        affirmedServiceconstructInterfaceAaaGroupDiameterStatisticsChassisLevelPeerDiameterInterfaceTypeNumAsrFailure ConfdString,
        affirmedServiceconstructInterfaceAaaGroupDiameterStatisticsChassisLevelPeerDiameterInterfaceTypeNumRarReceived Unsigned32,
        affirmedServiceconstructInterfaceAaaGroupDiameterStatisticsChassisLevelPeerDiameterInterfaceTypeNumRaaSuccess Unsigned32,
        affirmedServiceconstructInterfaceAaaGroupDiameterStatisticsChassisLevelPeerDiameterInterfaceTypeNumRaaFailures Unsigned32,
        affirmedServiceconstructInterfaceAaaGroupDiameterStatisticsChassisLevelPeerDiameterInterfaceTypeNumRaaFailuresUnknownSession Unsigned32,
        affirmedServiceconstructInterfaceAaaGroupDiameterStatisticsChassisLevelPeerDiameterInterfaceTypeNumRaaFailuresMissingAVP Unsigned32,
        affirmedServiceconstructInterfaceAaaGroupDiameterStatisticsChassisLevelPeerDiameterInterfaceTypeNumRaaFailuresRealmNotServed Unsigned32,
        affirmedServiceconstructInterfaceAaaGroupDiameterStatisticsChassisLevelPeerDiameterInterfaceTypeNumRaaFailuresUnableToDeliver Unsigned32,
        affirmedServiceconstructInterfaceAaaGroupDiameterStatisticsChassisLevelPeerDiameterInterfaceTypeNumRaaFailuresTooBusy Unsigned32,
        affirmedServiceconstructInterfaceAaaGroupDiameterStatisticsChassisLevelPeerDiameterInterfaceTypeNumCCAInitial4xxx ConfdString,
        affirmedServiceconstructInterfaceAaaGroupDiameterStatisticsChassisLevelPeerDiameterInterfaceTypeNumCCAInitial5xxx ConfdString,
        affirmedServiceconstructInterfaceAaaGroupDiameterStatisticsChassisLevelPeerDiameterInterfaceTypeNumCCAUpdate4xxx ConfdString,
        affirmedServiceconstructInterfaceAaaGroupDiameterStatisticsChassisLevelPeerDiameterInterfaceTypeNumCCAUpdate5xxx ConfdString,
        affirmedServiceconstructInterfaceAaaGroupDiameterStatisticsChassisLevelPeerDiameterInterfaceTypeNumCCATerminate4xxx ConfdString,
        affirmedServiceconstructInterfaceAaaGroupDiameterStatisticsChassisLevelPeerDiameterInterfaceTypeNumCCATerminate5xxx ConfdString,
        affirmedServiceconstructInterfaceAaaGroupDiameterStatisticsChassisLevelPeerDiameterInterfaceTypeNumAuthLifetmrInitAARAttmpted ConfdString,
        affirmedServiceconstructInterfaceAaaGroupDiameterStatisticsChassisLevelPeerDiameterInterfaceTypeNumAuthLifetimerInitAARSuccess ConfdString,
        affirmedServiceconstructInterfaceAaaGroupDiameterStatisticsChassisLevelPeerDiameterInterfaceTypeNumAuthLifetimerInitAARFailure ConfdString,
        affirmedServiceconstructInterfaceAaaGroupDiameterStatisticsChassisLevelPeerDiameterInterfaceTypeNumAuthLifetimerInitAARTimeout ConfdString,
        affirmedServiceconstructInterfaceAaaGroupDiameterStatisticsChassisLevelPeerDiameterInterfaceTypeNumAuthLifetmrInitAAARxFirstAt ConfdString,
        affirmedServiceconstructInterfaceAaaGroupDiameterStatisticsChassisLevelPeerDiameterInterfaceTypeNumAuthLifetmrInitAAARxReTx ConfdString,
        affirmedServiceconstructInterfaceAaaGroupDiameterStatisticsChassisLevelPeerDiameterInterfaceTypeNumAuthGraceTmrInitAARAtmpted ConfdString,
        affirmedServiceconstructInterfaceAaaGroupDiameterStatisticsChassisLevelPeerDiameterInterfaceTypeNumAuthGraceTmrInitAARSuccess ConfdString,
        affirmedServiceconstructInterfaceAaaGroupDiameterStatisticsChassisLevelPeerDiameterInterfaceTypeNumAuthGraceTmrInitAARFailure ConfdString,
        affirmedServiceconstructInterfaceAaaGroupDiameterStatisticsChassisLevelPeerDiameterInterfaceTypeNumAuthGraceTmrInitAARTimeout ConfdString,
        affirmedServiceconstructInterfaceAaaGroupDiameterStatisticsChassisLevelPeerDiameterInterfaceTypeNumAuthGraceTmrInitAAARxFstAt ConfdString,
        affirmedServiceconstructInterfaceAaaGroupDiameterStatisticsChassisLevelPeerDiameterInterfaceTypeNumAuthGraceTmrInitAAARxReTx ConfdString,
        affirmedServiceconstructInterfaceAaaGroupDiameterStatisticsChassisLevelPeerDiameterInterfaceTypeNumACRStartTimeout ConfdString,
        affirmedServiceconstructInterfaceAaaGroupDiameterStatisticsChassisLevelPeerDiameterInterfaceTypeNumACRStartAborted ConfdString,
        affirmedServiceconstructInterfaceAaaGroupDiameterStatisticsChassisLevelPeerDiameterInterfaceTypeNumACRStartDelayedSuccess ConfdString,
        affirmedServiceconstructInterfaceAaaGroupDiameterStatisticsChassisLevelPeerDiameterInterfaceTypeNumACRStartDelayedFailure ConfdString,
        affirmedServiceconstructInterfaceAaaGroupDiameterStatisticsChassisLevelPeerDiameterInterfaceTypeNumACRStartDropped ConfdString,
        affirmedServiceconstructInterfaceAaaGroupDiameterStatisticsChassisLevelPeerDiameterInterfaceTypeNumACRStartWriteToDisk ConfdString,
        affirmedServiceconstructInterfaceAaaGroupDiameterStatisticsChassisLevelPeerDiameterInterfaceTypeNumACRInterimTimeout ConfdString,
        affirmedServiceconstructInterfaceAaaGroupDiameterStatisticsChassisLevelPeerDiameterInterfaceTypeNumACRInterimAborted ConfdString,
        affirmedServiceconstructInterfaceAaaGroupDiameterStatisticsChassisLevelPeerDiameterInterfaceTypeNumACRInterimDelayedSuccess ConfdString,
        affirmedServiceconstructInterfaceAaaGroupDiameterStatisticsChassisLevelPeerDiameterInterfaceTypeNumACRInterimDelayedFailure ConfdString,
        affirmedServiceconstructInterfaceAaaGroupDiameterStatisticsChassisLevelPeerDiameterInterfaceTypeNumACRInterimDropped ConfdString,
        affirmedServiceconstructInterfaceAaaGroupDiameterStatisticsChassisLevelPeerDiameterInterfaceTypeNumACRInterimWriteToDisk ConfdString,
        affirmedServiceconstructInterfaceAaaGroupDiameterStatisticsChassisLevelPeerDiameterInterfaceTypeNumACRStopTimeout ConfdString,
        affirmedServiceconstructInterfaceAaaGroupDiameterStatisticsChassisLevelPeerDiameterInterfaceTypeNumACRStopAborted ConfdString,
        affirmedServiceconstructInterfaceAaaGroupDiameterStatisticsChassisLevelPeerDiameterInterfaceTypeNumACRStopDelayedSuccess ConfdString,
        affirmedServiceconstructInterfaceAaaGroupDiameterStatisticsChassisLevelPeerDiameterInterfaceTypeNumACRStopDelayedFailure ConfdString,
        affirmedServiceconstructInterfaceAaaGroupDiameterStatisticsChassisLevelPeerDiameterInterfaceTypeNumACRStopDropped ConfdString,
        affirmedServiceconstructInterfaceAaaGroupDiameterStatisticsChassisLevelPeerDiameterInterfaceTypeNumACRStopWriteToDisk ConfdString,
        affirmedServiceconstructInterfaceAaaGroupDiameterStatisticsChassisLevelPeerDiameterInterfaceTypeNumACREventTimeout ConfdString,
        affirmedServiceconstructInterfaceAaaGroupDiameterStatisticsChassisLevelPeerDiameterInterfaceTypeNumACREventAborted ConfdString,
        affirmedServiceconstructInterfaceAaaGroupDiameterStatisticsChassisLevelPeerDiameterInterfaceTypeNumACREventDelayedSuccess ConfdString,
        affirmedServiceconstructInterfaceAaaGroupDiameterStatisticsChassisLevelPeerDiameterInterfaceTypeNumACREventDelayedFailure ConfdString,
        affirmedServiceconstructInterfaceAaaGroupDiameterStatisticsChassisLevelPeerDiameterInterfaceTypeNumACREventDropped ConfdString,
        affirmedServiceconstructInterfaceAaaGroupDiameterStatisticsChassisLevelPeerDiameterInterfaceTypeNumACREventWriteToDisk ConfdString,
        affirmedServiceconstructInterfaceAaaGroupDiameterStatisticsChassisLevelPeerDiameterInterfaceTypeNumACRWriteToDiskFailure ConfdString,
        affirmedServiceconstructInterfaceAaaGroupDiameterStatisticsChassisLevelPeerDiameterInterfaceTypeNumCCREventTx ConfdString,
        affirmedServiceconstructInterfaceAaaGroupDiameterStatisticsChassisLevelPeerDiameterInterfaceTypeNumCCAEventRx ConfdString,
        affirmedServiceconstructInterfaceAaaGroupDiameterStatisticsChassisLevelPeerDiameterInterfaceTypeNumCCREventTimeout ConfdString,
        affirmedServiceconstructInterfaceAaaGroupDiameterStatisticsChassisLevelPeerDiameterInterfaceTypeNumSTRRetransmission ConfdString,
        affirmedServiceconstructInterfaceAaaGroupDiameterStatisticsChassisLevelPeerDiameterInterfaceTypeNumDERRetransmission ConfdString,
        affirmedServiceconstructInterfaceAaaGroupDiameterStatisticsChassisLevelPeerDiameterInterfaceTypeNumCCAPendingTransaction ConfdString,
        affirmedServiceconstructInterfaceAaaGroupDiameterStatisticsChassisLevelPeerDiameterInterfaceTypeNumRaaPendingTransaction Unsigned32,
        affirmedServiceconstructInterfaceAaaGroupDiameterStatisticsChassisLevelPeerDiameterInterfaceTypeNumSTRDropByPoc ConfdString,
        affirmedServiceconstructInterfaceAaaGroupDiameterStatisticsChassisLevelPeerDiameterInterfaceTypeNumSTRRedirect ConfdString,
        affirmedServiceconstructInterfaceAaaGroupDiameterStatisticsChassisLevelPeerDiameterInterfaceTypeNumRARInitAARDropByPoc ConfdString,
        affirmedServiceconstructInterfaceAaaGroupDiameterStatisticsChassisLevelPeerDiameterInterfaceTypeNumRARInitAARRedirect ConfdString,
        affirmedServiceconstructInterfaceAaaGroupDiameterStatisticsChassisLevelPeerDiameterInterfaceTypeNumDERInitialDropByPoc ConfdString,
        affirmedServiceconstructInterfaceAaaGroupDiameterStatisticsChassisLevelPeerDiameterInterfaceTypeNumDERInitialRedirect ConfdString,
        affirmedServiceconstructInterfaceAaaGroupDiameterStatisticsChassisLevelPeerDiameterInterfaceTypeNumDERReAuthDropByPoc ConfdString,
        affirmedServiceconstructInterfaceAaaGroupDiameterStatisticsChassisLevelPeerDiameterInterfaceTypeNumDERReAuthRedirect ConfdString,
        affirmedServiceconstructInterfaceAaaGroupDiameterStatisticsChassisLevelPeerDiameterInterfaceTypeNumAuthLifetimerInitAARDropByPoc ConfdString,
        affirmedServiceconstructInterfaceAaaGroupDiameterStatisticsChassisLevelPeerDiameterInterfaceTypeNumAuthLifetimerInitAARRedirect ConfdString,
        affirmedServiceconstructInterfaceAaaGroupDiameterStatisticsChassisLevelPeerDiameterInterfaceTypeNumAARAborted ConfdString,
        affirmedServiceconstructInterfaceAaaGroupDiameterStatisticsChassisLevelPeerDiameterInterfaceTypeNumRaaSendFailure Unsigned32,
        affirmedServiceconstructInterfaceAaaGroupDiameterStatisticsChassisLevelPeerDiameterInterfaceTypeNumRaaFailuresAppUnsupported Unsigned32,
        affirmedServiceconstructInterfaceAaaGroupDiameterStatisticsChassisLevelPeerDiameterInterfaceTypeNumRaaFailuresAuthRejected Unsigned32,
        affirmedServiceconstructInterfaceAaaGroupDiameterStatisticsChassisLevelPeerDiameterInterfaceTypeNumCommandUnsupported ConfdString,
        affirmedServiceconstructInterfaceAaaGroupDiameterStatisticsChassisLevelPeerDiameterInterfaceTypeNumUnableToDeliver ConfdString,
        affirmedServiceconstructInterfaceAaaGroupDiameterStatisticsChassisLevelPeerDiameterInterfaceTypeNumRealmNotServed ConfdString,
        affirmedServiceconstructInterfaceAaaGroupDiameterStatisticsChassisLevelPeerDiameterInterfaceTypeNumTooBusy ConfdString,
        affirmedServiceconstructInterfaceAaaGroupDiameterStatisticsChassisLevelPeerDiameterInterfaceTypeNumLoopDetected ConfdString,
        affirmedServiceconstructInterfaceAaaGroupDiameterStatisticsChassisLevelPeerDiameterInterfaceTypeNumRedirectIndication ConfdString,
        affirmedServiceconstructInterfaceAaaGroupDiameterStatisticsChassisLevelPeerDiameterInterfaceTypeNumApplicationUnsupported ConfdString,
        affirmedServiceconstructInterfaceAaaGroupDiameterStatisticsChassisLevelPeerDiameterInterfaceTypeNumInvalidHdrBits ConfdString,
        affirmedServiceconstructInterfaceAaaGroupDiameterStatisticsChassisLevelPeerDiameterInterfaceTypeNumInvalidAvpBits ConfdString,
        affirmedServiceconstructInterfaceAaaGroupDiameterStatisticsChassisLevelPeerDiameterInterfaceTypeNumUnknownPeer ConfdString,
        affirmedServiceconstructInterfaceAaaGroupDiameterStatisticsChassisLevelPeerDiameterInterfaceTypeNumAuthenticationRejected ConfdString,
        affirmedServiceconstructInterfaceAaaGroupDiameterStatisticsChassisLevelPeerDiameterInterfaceTypeNumOutOfSpace ConfdString,
        affirmedServiceconstructInterfaceAaaGroupDiameterStatisticsChassisLevelPeerDiameterInterfaceTypeNumElectionLost ConfdString,
        affirmedServiceconstructInterfaceAaaGroupDiameterStatisticsChassisLevelPeerDiameterInterfaceTypeNumAvpUnsupported ConfdString,
        affirmedServiceconstructInterfaceAaaGroupDiameterStatisticsChassisLevelPeerDiameterInterfaceTypeNumUnknownSessionId ConfdString,
        affirmedServiceconstructInterfaceAaaGroupDiameterStatisticsChassisLevelPeerDiameterInterfaceTypeNumAuthorizationRejected ConfdString,
        affirmedServiceconstructInterfaceAaaGroupDiameterStatisticsChassisLevelPeerDiameterInterfaceTypeNumInvalidAvpValue ConfdString,
        affirmedServiceconstructInterfaceAaaGroupDiameterStatisticsChassisLevelPeerDiameterInterfaceTypeNumMissingAvp ConfdString,
        affirmedServiceconstructInterfaceAaaGroupDiameterStatisticsChassisLevelPeerDiameterInterfaceTypeNumResourcesExceeded ConfdString,
        affirmedServiceconstructInterfaceAaaGroupDiameterStatisticsChassisLevelPeerDiameterInterfaceTypeNumContradictingAvps ConfdString,
        affirmedServiceconstructInterfaceAaaGroupDiameterStatisticsChassisLevelPeerDiameterInterfaceTypeNumAvpNotAllowed ConfdString,
        affirmedServiceconstructInterfaceAaaGroupDiameterStatisticsChassisLevelPeerDiameterInterfaceTypeNumOccursTooManyTimes ConfdString,
        affirmedServiceconstructInterfaceAaaGroupDiameterStatisticsChassisLevelPeerDiameterInterfaceTypeNumNoCommonApplication ConfdString,
        affirmedServiceconstructInterfaceAaaGroupDiameterStatisticsChassisLevelPeerDiameterInterfaceTypeNumUnableToComply ConfdString,
        affirmedServiceconstructInterfaceAaaGroupDiameterStatisticsChassisLevelPeerDiameterInterfaceTypeNumInvalidBitInHdr ConfdString,
        affirmedServiceconstructInterfaceAaaGroupDiameterStatisticsChassisLevelPeerDiameterInterfaceTypeNumInvalidAvpLength ConfdString,
        affirmedServiceconstructInterfaceAaaGroupDiameterStatisticsChassisLevelPeerDiameterInterfaceTypeNumInvalidMessageLength ConfdString,
        affirmedServiceconstructInterfaceAaaGroupDiameterStatisticsChassisLevelPeerDiameterInterfaceTypeNumInvalidAvpBitCombo ConfdString,
        affirmedServiceconstructInterfaceAaaGroupDiameterStatisticsChassisLevelPeerDiameterInterfaceTypeNumNoCommonSecurity ConfdString,
        affirmedServiceconstructInterfaceAaaGroupDiameterStatisticsChassisLevelPeerDiameterInterfaceTypeNumUserUnknown ConfdString,
        affirmedServiceconstructInterfaceAaaGroupDiameterStatisticsChassisLevelPeerDiameterInterfaceTypeNumRoamingNotAllowed ConfdString,
        affirmedServiceconstructInterfaceAaaGroupDiameterStatisticsChassisLevelPeerDiameterInterfaceTypeNumIdentityAlreadyRegistered ConfdString,
        affirmedServiceconstructInterfaceAaaGroupDiameterStatisticsChassisLevelPeerDiameterInterfaceTypeNumOverloadRetryNotAllowed ConfdString,
        affirmedServiceconstructInterfaceAaaGroupDiameterStatisticsChassisLevelPeerDiameterInterfaceTypeNumUnknownEpsSubscription ConfdString,
        affirmedServiceconstructInterfaceAaaGroupDiameterStatisticsChassisLevelPeerDiameterInterfaceTypeNumUserNoNonGppSubscription ConfdString,
        affirmedServiceconstructInterfaceAaaGroupDiameterStatisticsChassisLevelPeerDiameterInterfaceTypeNumUserNoApnSubscription ConfdString,
        affirmedServiceconstructInterfaceAaaGroupDiameterStatisticsChassisLevelPeerDiameterInterfaceTypeNumRatTypeNotAllowed ConfdString,
        affirmedServiceconstructInterfaceAaaGroupDiameterStatisticsChassisLevelPeerDiameterInterfaceTypeNumLateOverlappingRequest ConfdString,
        affirmedServiceconstructInterfaceAaaGroupDiameterStatisticsChassisLevelPeerDiameterInterfaceTypeNumTimedOutRequest ConfdString,
        affirmedServiceconstructInterfaceAaaGroupDiameterStatisticsChassisLevelPeerDiameterInterfaceTypeNumNIRAttempted ConfdString,
        affirmedServiceconstructInterfaceAaaGroupDiameterStatisticsChassisLevelPeerDiameterInterfaceTypeNumNIRSuccess ConfdString,
        affirmedServiceconstructInterfaceAaaGroupDiameterStatisticsChassisLevelPeerDiameterInterfaceTypeNumNIRFailure ConfdString,
        affirmedServiceconstructInterfaceAaaGroupDiameterStatisticsChassisLevelPeerDiameterInterfaceTypeNumNIRTimeout ConfdString,
        affirmedServiceconstructInterfaceAaaGroupDiameterStatisticsChassisLevelPeerDiameterInterfaceTypeNumNIRAborted ConfdString,
        affirmedServiceconstructInterfaceAaaGroupDiameterStatisticsChassisLevelPeerDiameterInterfaceTypeNumNIRcvdFirstAttempt ConfdString,
        affirmedServiceconstructInterfaceAaaGroupDiameterStatisticsChassisLevelPeerDiameterInterfaceTypeNumNIARcvdReTx ConfdString,
        affirmedServiceconstructInterfaceAaaGroupDiameterStatisticsChassisLevelPeerDiameterInterfaceTypeNumNIA3xxx ConfdString,
        affirmedServiceconstructInterfaceAaaGroupDiameterStatisticsChassisLevelPeerDiameterInterfaceTypeNumNIA4xxx ConfdString,
        affirmedServiceconstructInterfaceAaaGroupDiameterStatisticsChassisLevelPeerDiameterInterfaceTypeNumNIA5xxx ConfdString,
        affirmedServiceconstructInterfaceAaaGroupDiameterStatisticsChassisLevelPeerDiameterInterfaceTypeNumNIADelayedSuccess ConfdString,
        affirmedServiceconstructInterfaceAaaGroupDiameterStatisticsChassisLevelPeerDiameterInterfaceTypeNumNIADelayedFailure ConfdString,
        affirmedServiceconstructInterfaceAaaGroupDiameterStatisticsChassisLevelPeerDiameterInterfaceTypeNumNIADelayed3xxx ConfdString,
        affirmedServiceconstructInterfaceAaaGroupDiameterStatisticsChassisLevelPeerDiameterInterfaceTypeNumNIADroppedNoProc ConfdString,
        affirmedServiceconstructInterfaceAaaGroupDiameterStatisticsChassisLevelPeerDiameterInterfaceTypeNumCIRAttempted ConfdString,
        affirmedServiceconstructInterfaceAaaGroupDiameterStatisticsChassisLevelPeerDiameterInterfaceTypeNumCIRSuccess ConfdString,
        affirmedServiceconstructInterfaceAaaGroupDiameterStatisticsChassisLevelPeerDiameterInterfaceTypeNumCIRFailure ConfdString,
        affirmedServiceconstructInterfaceAaaGroupDiameterStatisticsChassisLevelPeerDiameterInterfaceTypeNumCIRTimeout ConfdString,
        affirmedServiceconstructInterfaceAaaGroupDiameterStatisticsChassisLevelPeerDiameterInterfaceTypeNumCIRAborted ConfdString,
        affirmedServiceconstructInterfaceAaaGroupDiameterStatisticsChassisLevelPeerDiameterInterfaceTypeNumCIRcvdFirstAttempt ConfdString,
        affirmedServiceconstructInterfaceAaaGroupDiameterStatisticsChassisLevelPeerDiameterInterfaceTypeNumCIARcvdReTx ConfdString,
        affirmedServiceconstructInterfaceAaaGroupDiameterStatisticsChassisLevelPeerDiameterInterfaceTypeNumCIA3xxx ConfdString,
        affirmedServiceconstructInterfaceAaaGroupDiameterStatisticsChassisLevelPeerDiameterInterfaceTypeNumCIA4xxx ConfdString,
        affirmedServiceconstructInterfaceAaaGroupDiameterStatisticsChassisLevelPeerDiameterInterfaceTypeNumCIA5xxx ConfdString,
        affirmedServiceconstructInterfaceAaaGroupDiameterStatisticsChassisLevelPeerDiameterInterfaceTypeNumCIADelayedSuccess ConfdString,
        affirmedServiceconstructInterfaceAaaGroupDiameterStatisticsChassisLevelPeerDiameterInterfaceTypeNumCIADelayedFailure ConfdString,
        affirmedServiceconstructInterfaceAaaGroupDiameterStatisticsChassisLevelPeerDiameterInterfaceTypeNumCIADelayed3xxx ConfdString,
        affirmedServiceconstructInterfaceAaaGroupDiameterStatisticsChassisLevelPeerDiameterInterfaceTypeNumCIADroppedNoProc ConfdString,
        affirmedServiceconstructInterfaceAaaGroupDiameterStatisticsChassisLevelPeerDiameterInterfaceTypeNumTDRAttempted ConfdString,
        affirmedServiceconstructInterfaceAaaGroupDiameterStatisticsChassisLevelPeerDiameterInterfaceTypeNumTDRSuccess ConfdString,
        affirmedServiceconstructInterfaceAaaGroupDiameterStatisticsChassisLevelPeerDiameterInterfaceTypeNumTDRFailure ConfdString,
        affirmedServiceconstructInterfaceAaaGroupDiameterStatisticsChassisLevelPeerDiameterInterfaceTypeNumTDRTimeout ConfdString,
        affirmedServiceconstructInterfaceAaaGroupDiameterStatisticsChassisLevelPeerDiameterInterfaceTypeNumTDRAborted ConfdString,
        affirmedServiceconstructInterfaceAaaGroupDiameterStatisticsChassisLevelPeerDiameterInterfaceTypeNumTDARcvdFirstAttempt ConfdString,
        affirmedServiceconstructInterfaceAaaGroupDiameterStatisticsChassisLevelPeerDiameterInterfaceTypeNumTDARcvdReTx ConfdString,
        affirmedServiceconstructInterfaceAaaGroupDiameterStatisticsChassisLevelPeerDiameterInterfaceTypeNumTDA3xxx ConfdString,
        affirmedServiceconstructInterfaceAaaGroupDiameterStatisticsChassisLevelPeerDiameterInterfaceTypeNumTDA4xxx ConfdString,
        affirmedServiceconstructInterfaceAaaGroupDiameterStatisticsChassisLevelPeerDiameterInterfaceTypeNumTDA5xxx ConfdString,
        affirmedServiceconstructInterfaceAaaGroupDiameterStatisticsChassisLevelPeerDiameterInterfaceTypeNumTDADroppedNoProc ConfdString,
        affirmedServiceconstructInterfaceAaaGroupDiameterStatisticsChassisLevelPeerDiameterInterfaceTypeNumCmrCReceived ConfdString,
        affirmedServiceconstructInterfaceAaaGroupDiameterStatisticsChassisLevelPeerDiameterInterfaceTypeNumCMACSuccess ConfdString,
        affirmedServiceconstructInterfaceAaaGroupDiameterStatisticsChassisLevelPeerDiameterInterfaceTypeNumCMACFailures ConfdString,
        affirmedServiceconstructInterfaceAaaGroupDiameterStatisticsChassisLevelPeerDiameterInterfaceTypeNumCMACFailuresUnknownSession ConfdString,
        affirmedServiceconstructInterfaceAaaGroupDiameterStatisticsChassisLevelPeerDiameterInterfaceTypeNumCMACFailuresMissingAVP ConfdString,
        affirmedServiceconstructInterfaceAaaGroupDiameterStatisticsChassisLevelPeerDiameterInterfaceTypeNumCmrUReceived ConfdString,
        affirmedServiceconstructInterfaceAaaGroupDiameterStatisticsChassisLevelPeerDiameterInterfaceTypeNumCMAUSuccess ConfdString,
        affirmedServiceconstructInterfaceAaaGroupDiameterStatisticsChassisLevelPeerDiameterInterfaceTypeNumCMAUFailures ConfdString,
        affirmedServiceconstructInterfaceAaaGroupDiameterStatisticsChassisLevelPeerDiameterInterfaceTypeNumCMAUFailuresUnknownSession ConfdString,
        affirmedServiceconstructInterfaceAaaGroupDiameterStatisticsChassisLevelPeerDiameterInterfaceTypeNumCMAUFailuresMissingAVP ConfdString,
        affirmedServiceconstructInterfaceAaaGroupDiameterStatisticsChassisLevelPeerDiameterInterfaceTypeNumCmrRReceived ConfdString,
        affirmedServiceconstructInterfaceAaaGroupDiameterStatisticsChassisLevelPeerDiameterInterfaceTypeNumCMARSuccess ConfdString,
        affirmedServiceconstructInterfaceAaaGroupDiameterStatisticsChassisLevelPeerDiameterInterfaceTypeNumCMARFailures ConfdString,
        affirmedServiceconstructInterfaceAaaGroupDiameterStatisticsChassisLevelPeerDiameterInterfaceTypeNumCMARFailuresUnknownSession ConfdString,
        affirmedServiceconstructInterfaceAaaGroupDiameterStatisticsChassisLevelPeerDiameterInterfaceTypeNumCMARFailuresMissingAVP ConfdString,
        affirmedServiceconstructInterfaceAaaGroupDiameterStatisticsChassisLevelPeerDiameterInterfaceTypeNumCMRRScefInitAttempted ConfdString,
        affirmedServiceconstructInterfaceAaaGroupDiameterStatisticsChassisLevelPeerDiameterInterfaceTypeNumCMRRScefInitSuccess ConfdString,
        affirmedServiceconstructInterfaceAaaGroupDiameterStatisticsChassisLevelPeerDiameterInterfaceTypeNumCMRRScefInitFailure ConfdString,
        affirmedServiceconstructInterfaceAaaGroupDiameterStatisticsChassisLevelPeerDiameterInterfaceTypeNumCMRRScefInitTimeout ConfdString,
        affirmedServiceconstructInterfaceAaaGroupDiameterStatisticsChassisLevelPeerDiameterInterfaceTypeNumCMRRScefInitAborted ConfdString,
        affirmedServiceconstructInterfaceAaaGroupDiameterStatisticsChassisLevelPeerDiameterInterfaceTypeNumCMARScefInitRcvdFirstAttempt ConfdString,
        affirmedServiceconstructInterfaceAaaGroupDiameterStatisticsChassisLevelPeerDiameterInterfaceTypeNumCMARScefInitRcvdReTx ConfdString,
        affirmedServiceconstructInterfaceAaaGroupDiameterStatisticsChassisLevelPeerDiameterInterfaceTypeNumCMARScefInit3xxx ConfdString,
        affirmedServiceconstructInterfaceAaaGroupDiameterStatisticsChassisLevelPeerDiameterInterfaceTypeNumCMARScefInit4xxx ConfdString,
        affirmedServiceconstructInterfaceAaaGroupDiameterStatisticsChassisLevelPeerDiameterInterfaceTypeNumCMARScefInit5xxx ConfdString,
        affirmedServiceconstructInterfaceAaaGroupDiameterStatisticsChassisLevelPeerDiameterInterfaceTypeNumCMARScefInitDroppedNoProc ConfdString,
        affirmedServiceconstructInterfaceAaaGroupDiameterStatisticsChassisLevelPeerDiameterInterfaceTypeNumODRReceived ConfdString,
        affirmedServiceconstructInterfaceAaaGroupDiameterStatisticsChassisLevelPeerDiameterInterfaceTypeNumODASuccess ConfdString,
        affirmedServiceconstructInterfaceAaaGroupDiameterStatisticsChassisLevelPeerDiameterInterfaceTypeNumODAFailures ConfdString,
        affirmedServiceconstructInterfaceAaaGroupDiameterStatisticsChassisLevelPeerDiameterInterfaceTypeNumODAFailuresUnknownSession ConfdString,
        affirmedServiceconstructInterfaceAaaGroupDiameterStatisticsChassisLevelPeerDiameterInterfaceTypeNumODAFailuresMissingAVP ConfdString,
        affirmedServiceconstructInterfaceAaaGroupDiameterStatisticsChassisLevelPeerDiameterInterfaceTypeNumODAFailuresUnableToDeliver ConfdString,
        affirmedServiceconstructInterfaceAaaGroupDiameterStatisticsChassisLevelPeerDiameterInterfaceTypeNumRIRReceived ConfdString,
        affirmedServiceconstructInterfaceAaaGroupDiameterStatisticsChassisLevelPeerDiameterInterfaceTypeNumRIASuccess ConfdString,
        affirmedServiceconstructInterfaceAaaGroupDiameterStatisticsChassisLevelPeerDiameterInterfaceTypeNumRIAFailures ConfdString,
        affirmedServiceconstructInterfaceAaaGroupDiameterStatisticsChassisLevelPeerDiameterInterfaceTypeNumRIAFailuresUnknownScefRefId ConfdString,
        affirmedServiceconstructInterfaceAaaGroupDiameterStatisticsChassisLevelPeerDiameterInterfaceTypeNumRIAFailuresUnknownSession ConfdString,
        affirmedServiceconstructInterfaceAaaGroupDiameterStatisticsChassisLevelPeerDiameterInterfaceTypeNumRIAFailuresMissingAVP ConfdString,
        affirmedServiceconstructInterfaceAaaGroupDiameterStatisticsChassisLevelPeerDiameterInterfaceTypeNumRIAFailuresUnableToDeliver ConfdString,
        affirmedServiceconstructInterfaceAaaGroupDiameterStatisticsChassisLevelPeerDiameterInterfaceTypeNumSIRAttempted ConfdString,
        affirmedServiceconstructInterfaceAaaGroupDiameterStatisticsChassisLevelPeerDiameterInterfaceTypeNumSIRSuccess ConfdString,
        affirmedServiceconstructInterfaceAaaGroupDiameterStatisticsChassisLevelPeerDiameterInterfaceTypeNumSIRFailure ConfdString,
        affirmedServiceconstructInterfaceAaaGroupDiameterStatisticsChassisLevelPeerDiameterInterfaceTypeNumSIRTimeout ConfdString,
        affirmedServiceconstructInterfaceAaaGroupDiameterStatisticsChassisLevelPeerDiameterInterfaceTypeNumSIRAborted ConfdString,
        affirmedServiceconstructInterfaceAaaGroupDiameterStatisticsChassisLevelPeerDiameterInterfaceTypeNumSIRcvdFirstAttempt ConfdString,
        affirmedServiceconstructInterfaceAaaGroupDiameterStatisticsChassisLevelPeerDiameterInterfaceTypeNumSIARcvdReTx ConfdString,
        affirmedServiceconstructInterfaceAaaGroupDiameterStatisticsChassisLevelPeerDiameterInterfaceTypeNumSIA3xxx ConfdString,
        affirmedServiceconstructInterfaceAaaGroupDiameterStatisticsChassisLevelPeerDiameterInterfaceTypeNumSIA4xxx ConfdString,
        affirmedServiceconstructInterfaceAaaGroupDiameterStatisticsChassisLevelPeerDiameterInterfaceTypeNumSIA5xxx ConfdString,
        affirmedServiceconstructInterfaceAaaGroupDiameterStatisticsChassisLevelPeerDiameterInterfaceTypeNumSIADelayedSuccess ConfdString,
        affirmedServiceconstructInterfaceAaaGroupDiameterStatisticsChassisLevelPeerDiameterInterfaceTypeNumSIADelayedFailure ConfdString,
        affirmedServiceconstructInterfaceAaaGroupDiameterStatisticsChassisLevelPeerDiameterInterfaceTypeNumSIADelayed3xxx ConfdString,
        affirmedServiceconstructInterfaceAaaGroupDiameterStatisticsChassisLevelPeerDiameterInterfaceTypeNumSIADroppedNoProc ConfdString,
        affirmedServiceconstructInterfaceAaaGroupDiameterStatisticsChassisLevelPeerDiameterInterfaceTypeNumDTRAttempted ConfdString,
        affirmedServiceconstructInterfaceAaaGroupDiameterStatisticsChassisLevelPeerDiameterInterfaceTypeNumDTRSuccess ConfdString,
        affirmedServiceconstructInterfaceAaaGroupDiameterStatisticsChassisLevelPeerDiameterInterfaceTypeNumDTRFailure ConfdString,
        affirmedServiceconstructInterfaceAaaGroupDiameterStatisticsChassisLevelPeerDiameterInterfaceTypeNumDTRTimeout ConfdString,
        affirmedServiceconstructInterfaceAaaGroupDiameterStatisticsChassisLevelPeerDiameterInterfaceTypeNumDTRAborted ConfdString,
        affirmedServiceconstructInterfaceAaaGroupDiameterStatisticsChassisLevelPeerDiameterInterfaceTypeNumDTRcvdFirstAttempt ConfdString,
        affirmedServiceconstructInterfaceAaaGroupDiameterStatisticsChassisLevelPeerDiameterInterfaceTypeNumDTARcvdReTx ConfdString,
        affirmedServiceconstructInterfaceAaaGroupDiameterStatisticsChassisLevelPeerDiameterInterfaceTypeNumDTA3xxx ConfdString,
        affirmedServiceconstructInterfaceAaaGroupDiameterStatisticsChassisLevelPeerDiameterInterfaceTypeNumDTA4xxx ConfdString,
        affirmedServiceconstructInterfaceAaaGroupDiameterStatisticsChassisLevelPeerDiameterInterfaceTypeNumDTA5xxx ConfdString,
        affirmedServiceconstructInterfaceAaaGroupDiameterStatisticsChassisLevelPeerDiameterInterfaceTypeNumDTADelayedSuccess ConfdString,
        affirmedServiceconstructInterfaceAaaGroupDiameterStatisticsChassisLevelPeerDiameterInterfaceTypeNumDTADelayedFailure ConfdString,
        affirmedServiceconstructInterfaceAaaGroupDiameterStatisticsChassisLevelPeerDiameterInterfaceTypeNumDTADelayed3xxx ConfdString,
        affirmedServiceconstructInterfaceAaaGroupDiameterStatisticsChassisLevelPeerDiameterInterfaceTypeNumDTADroppedNoProc ConfdString,
        affirmedServiceconstructInterfaceAaaGroupDiameterStatisticsChassisLevelPeerDiameterInterfaceTypeNumDTRTriggerAttempted ConfdString,
        affirmedServiceconstructInterfaceAaaGroupDiameterStatisticsChassisLevelPeerDiameterInterfaceTypeNumDTRTriggerSuccess ConfdString,
        affirmedServiceconstructInterfaceAaaGroupDiameterStatisticsChassisLevelPeerDiameterInterfaceTypeNumDTRTriggerFailure ConfdString,
        affirmedServiceconstructInterfaceAaaGroupDiameterStatisticsChassisLevelPeerDiameterInterfaceTypeNumDTRTriggerTimeout ConfdString,
        affirmedServiceconstructInterfaceAaaGroupDiameterStatisticsChassisLevelPeerDiameterInterfaceTypeNumDTRTriggerAborted ConfdString,
        affirmedServiceconstructInterfaceAaaGroupDiameterStatisticsChassisLevelPeerDiameterInterfaceTypeNumDTRTriggercvdFirstAttempt ConfdString,
        affirmedServiceconstructInterfaceAaaGroupDiameterStatisticsChassisLevelPeerDiameterInterfaceTypeNumDTATriggerRcvdReTx ConfdString,
        affirmedServiceconstructInterfaceAaaGroupDiameterStatisticsChassisLevelPeerDiameterInterfaceTypeNumDTATrigger3xxx ConfdString,
        affirmedServiceconstructInterfaceAaaGroupDiameterStatisticsChassisLevelPeerDiameterInterfaceTypeNumDTATrigger4xxx ConfdString,
        affirmedServiceconstructInterfaceAaaGroupDiameterStatisticsChassisLevelPeerDiameterInterfaceTypeNumDTATrigger5xxx ConfdString,
        affirmedServiceconstructInterfaceAaaGroupDiameterStatisticsChassisLevelPeerDiameterInterfaceTypeNumDTATriggerDelayedSuccess ConfdString,
        affirmedServiceconstructInterfaceAaaGroupDiameterStatisticsChassisLevelPeerDiameterInterfaceTypeNumDTATriggerDelayedFailure ConfdString,
        affirmedServiceconstructInterfaceAaaGroupDiameterStatisticsChassisLevelPeerDiameterInterfaceTypeNumDTATriggerDelayed3xxx ConfdString,
        affirmedServiceconstructInterfaceAaaGroupDiameterStatisticsChassisLevelPeerDiameterInterfaceTypeNumDTATriggerDroppedNoProc ConfdString,
        affirmedServiceconstructInterfaceAaaGroupDiameterStatisticsChassisLevelPeerDiameterInterfaceTypeNumDTRRecallAttempted ConfdString,
        affirmedServiceconstructInterfaceAaaGroupDiameterStatisticsChassisLevelPeerDiameterInterfaceTypeNumDTRRecallSuccess ConfdString,
        affirmedServiceconstructInterfaceAaaGroupDiameterStatisticsChassisLevelPeerDiameterInterfaceTypeNumDTRRecallFailure ConfdString,
        affirmedServiceconstructInterfaceAaaGroupDiameterStatisticsChassisLevelPeerDiameterInterfaceTypeNumDTRRecallTimeout ConfdString,
        affirmedServiceconstructInterfaceAaaGroupDiameterStatisticsChassisLevelPeerDiameterInterfaceTypeNumDTRRecallAborted ConfdString,
        affirmedServiceconstructInterfaceAaaGroupDiameterStatisticsChassisLevelPeerDiameterInterfaceTypeNumDTRRecallcvdFirstAttempt ConfdString,
        affirmedServiceconstructInterfaceAaaGroupDiameterStatisticsChassisLevelPeerDiameterInterfaceTypeNumDTARecallRcvdReTx ConfdString,
        affirmedServiceconstructInterfaceAaaGroupDiameterStatisticsChassisLevelPeerDiameterInterfaceTypeNumDTARecall3xxx ConfdString,
        affirmedServiceconstructInterfaceAaaGroupDiameterStatisticsChassisLevelPeerDiameterInterfaceTypeNumDTARecall4xxx ConfdString,
        affirmedServiceconstructInterfaceAaaGroupDiameterStatisticsChassisLevelPeerDiameterInterfaceTypeNumDTARecall5xxx ConfdString,
        affirmedServiceconstructInterfaceAaaGroupDiameterStatisticsChassisLevelPeerDiameterInterfaceTypeNumDTARecallDelayedSuccess ConfdString,
        affirmedServiceconstructInterfaceAaaGroupDiameterStatisticsChassisLevelPeerDiameterInterfaceTypeNumDTARecallDelayedFailure ConfdString,
        affirmedServiceconstructInterfaceAaaGroupDiameterStatisticsChassisLevelPeerDiameterInterfaceTypeNumDTARecallDelayed3xxx ConfdString,
        affirmedServiceconstructInterfaceAaaGroupDiameterStatisticsChassisLevelPeerDiameterInterfaceTypeNumDTARecallDroppedNoProc ConfdString,
        affirmedServiceconstructInterfaceAaaGroupDiameterStatisticsChassisLevelPeerDiameterInterfaceTypeNumDTRReplaceAttempted ConfdString,
        affirmedServiceconstructInterfaceAaaGroupDiameterStatisticsChassisLevelPeerDiameterInterfaceTypeNumDTRReplaceSuccess ConfdString,
        affirmedServiceconstructInterfaceAaaGroupDiameterStatisticsChassisLevelPeerDiameterInterfaceTypeNumDTRReplaceFailure ConfdString,
        affirmedServiceconstructInterfaceAaaGroupDiameterStatisticsChassisLevelPeerDiameterInterfaceTypeNumDTRReplaceTimeout ConfdString,
        affirmedServiceconstructInterfaceAaaGroupDiameterStatisticsChassisLevelPeerDiameterInterfaceTypeNumDTRReplaceAborted ConfdString,
        affirmedServiceconstructInterfaceAaaGroupDiameterStatisticsChassisLevelPeerDiameterInterfaceTypeNumDTRReplacecvdFirstAttempt ConfdString,
        affirmedServiceconstructInterfaceAaaGroupDiameterStatisticsChassisLevelPeerDiameterInterfaceTypeNumDTAReplaceRcvdReTx ConfdString,
        affirmedServiceconstructInterfaceAaaGroupDiameterStatisticsChassisLevelPeerDiameterInterfaceTypeNumDTAReplace3xxx ConfdString,
        affirmedServiceconstructInterfaceAaaGroupDiameterStatisticsChassisLevelPeerDiameterInterfaceTypeNumDTAReplace4xxx ConfdString,
        affirmedServiceconstructInterfaceAaaGroupDiameterStatisticsChassisLevelPeerDiameterInterfaceTypeNumDTAReplace5xxx ConfdString,
        affirmedServiceconstructInterfaceAaaGroupDiameterStatisticsChassisLevelPeerDiameterInterfaceTypeNumDTAReplaceDelayedSuccess ConfdString,
        affirmedServiceconstructInterfaceAaaGroupDiameterStatisticsChassisLevelPeerDiameterInterfaceTypeNumDTAReplaceDelayedFailure ConfdString,
        affirmedServiceconstructInterfaceAaaGroupDiameterStatisticsChassisLevelPeerDiameterInterfaceTypeNumDTAReplaceDelayed3xxx ConfdString,
        affirmedServiceconstructInterfaceAaaGroupDiameterStatisticsChassisLevelPeerDiameterInterfaceTypeNumDTAReplaceDroppedNoProc ConfdString,
        affirmedServiceconstructInterfaceAaaGroupDiameterStatisticsChassisLevelPeerDiameterInterfaceTypeNumDRRReceived ConfdString,
        affirmedServiceconstructInterfaceAaaGroupDiameterStatisticsChassisLevelPeerDiameterInterfaceTypeNumDRASuccess ConfdString,
        affirmedServiceconstructInterfaceAaaGroupDiameterStatisticsChassisLevelPeerDiameterInterfaceTypeNumDRAFailures ConfdString,
        affirmedServiceconstructInterfaceAaaGroupDiameterStatisticsChassisLevelPeerDiameterInterfaceTypeNumDRAFailuresUnknownRefId ConfdString,
        affirmedServiceconstructInterfaceAaaGroupDiameterStatisticsChassisLevelPeerDiameterInterfaceTypeNumDRAFailuresUnknownSession ConfdString,
        affirmedServiceconstructInterfaceAaaGroupDiameterStatisticsChassisLevelPeerDiameterInterfaceTypeNumDRAFailuresMissingAVP ConfdString,
        affirmedServiceconstructInterfaceAaaGroupDiameterStatisticsChassisLevelPeerDiameterInterfaceTypeNumDRAFailuresUnableToDeliver ConfdString,
        affirmedServiceconstructInterfaceAaaGroupDiameterStatisticsChassisLevelPeerDiameterInterfaceTypeNumAuthLifetimerInitAARRetry ConfdString,
        affirmedServiceconstructInterfaceAaaGroupDiameterStatisticsChassisLevelPeerDiameterInterfaceTypeNumAuthGraceTmrInitAARRetry ConfdString,
        affirmedServiceconstructInterfaceAaaGroupDiameterStatisticsChassisLevelPeerDiameterInterfaceTypeNumTsrReceived Unsigned32,
        affirmedServiceconstructInterfaceAaaGroupDiameterStatisticsChassisLevelPeerDiameterInterfaceTypeNumTsaSuccess Unsigned32,
        affirmedServiceconstructInterfaceAaaGroupDiameterStatisticsChassisLevelPeerDiameterInterfaceTypeNumTsaFailures Unsigned32,
        affirmedServiceconstructInterfaceAaaGroupDiameterStatisticsChassisLevelPeerDiameterInterfaceTypeNumAAAInitialDelayedSuccess ConfdString,
        affirmedServiceconstructInterfaceAaaGroupDiameterStatisticsChassisLevelPeerDiameterInterfaceTypeNumAAAInitialDelayedFailure ConfdString,
        affirmedServiceconstructInterfaceAaaGroupDiameterStatisticsChassisLevelPeerDiameterInterfaceTypeNumAAAInitialDelayed3xxx ConfdString,
        affirmedServiceconstructInterfaceAaaGroupDiameterStatisticsChassisLevelPeerDiameterInterfaceTypeNumAARRetry ConfdString,
        affirmedServiceconstructInterfaceAaaGroupDiameterStatisticsChassisLevelPeerDiameterInterfaceTypeNumRarInitiatedAARRetry ConfdString
    }

affirmedServiceconstructInterfaceAaaGroupDiameterStatisticsChassisLevelPeerDiameterInterfaceTypeIntfType OBJECT-TYPE
    SYNTAX      String
    MAX-ACCESS  not-accessible
    STATUS      current
    DESCRIPTION "Diameter Interface Type: GX/GY/GZ/S6B/STA/SWM/S6T/T6A/T4/S6M/SWM/FLOWAUTH/SXAB/SD"
    ::= { affirmedServiceconstructInterfaceAaaGroupDiameterStatisticsChassisLevelPeerDiameterInterfaceTypeEntry 1 }

affirmedServiceconstructInterfaceAaaGroupDiameterStatisticsChassisLevelPeerDiameterInterfaceTypeNodeName OBJECT-TYPE
    SYNTAX      String
    MAX-ACCESS  not-accessible
    STATUS      current
    DESCRIPTION "Local Diameter Node Name"
    ::= { affirmedServiceconstructInterfaceAaaGroupDiameterStatisticsChassisLevelPeerDiameterInterfaceTypeEntry 2 }

affirmedServiceconstructInterfaceAaaGroupDiameterStatisticsChassisLevelPeerDiameterInterfaceTypePeerName OBJECT-TYPE
    SYNTAX      String
    MAX-ACCESS  not-accessible
    STATUS      current
    DESCRIPTION "Peer name"
    ::= { affirmedServiceconstructInterfaceAaaGroupDiameterStatisticsChassisLevelPeerDiameterInterfaceTypeEntry 3 }

affirmedServiceconstructInterfaceAaaGroupDiameterStatisticsChassisLevelPeerDiameterInterfaceTypeNumCCRInitialAttempted OBJECT-TYPE
    SYNTAX      ConfdString
    MAX-ACCESS  read-only
    STATUS      current
    DESCRIPTION "Number of CCR Initial attempts made"
    ::= { affirmedServiceconstructInterfaceAaaGroupDiameterStatisticsChassisLevelPeerDiameterInterfaceTypeEntry 4 }

affirmedServiceconstructInterfaceAaaGroupDiameterStatisticsChassisLevelPeerDiameterInterfaceTypeNumCCRInitialSuccess OBJECT-TYPE
    SYNTAX      ConfdString
    MAX-ACCESS  read-only
    STATUS      current
    DESCRIPTION "Number of successful CCR Initial attempts"
    ::= { affirmedServiceconstructInterfaceAaaGroupDiameterStatisticsChassisLevelPeerDiameterInterfaceTypeEntry 5 }

affirmedServiceconstructInterfaceAaaGroupDiameterStatisticsChassisLevelPeerDiameterInterfaceTypeNumCCRInitialFailure OBJECT-TYPE
    SYNTAX      ConfdString
    MAX-ACCESS  read-only
    STATUS      current
    DESCRIPTION "Number of failed CCR Initial attempts"
    ::= { affirmedServiceconstructInterfaceAaaGroupDiameterStatisticsChassisLevelPeerDiameterInterfaceTypeEntry 6 }

affirmedServiceconstructInterfaceAaaGroupDiameterStatisticsChassisLevelPeerDiameterInterfaceTypeNumCCRInitialTimeout OBJECT-TYPE
    SYNTAX      ConfdString
    MAX-ACCESS  read-only
    STATUS      current
    DESCRIPTION "Number of CCR Initial attempts that timed out"
    ::= { affirmedServiceconstructInterfaceAaaGroupDiameterStatisticsChassisLevelPeerDiameterInterfaceTypeEntry 7 }

affirmedServiceconstructInterfaceAaaGroupDiameterStatisticsChassisLevelPeerDiameterInterfaceTypeNumCCAInitialRcvdFirstAttempt OBJECT-TYPE
    SYNTAX      ConfdString
    MAX-ACCESS  read-only
    STATUS      current
    DESCRIPTION "Number of CCR Initial requests for which response was received when first transmitted "
    ::= { affirmedServiceconstructInterfaceAaaGroupDiameterStatisticsChassisLevelPeerDiameterInterfaceTypeEntry 8 }

affirmedServiceconstructInterfaceAaaGroupDiameterStatisticsChassisLevelPeerDiameterInterfaceTypeNumCCAInitialRcvdReTx OBJECT-TYPE
    SYNTAX      ConfdString
    MAX-ACCESS  read-only
    STATUS      current
    DESCRIPTION "Number of CCR Initial Requests for which response was received when message was retransmitted"
    ::= { affirmedServiceconstructInterfaceAaaGroupDiameterStatisticsChassisLevelPeerDiameterInterfaceTypeEntry 9 }

affirmedServiceconstructInterfaceAaaGroupDiameterStatisticsChassisLevelPeerDiameterInterfaceTypeNumCCRInitialStoredForReplay OBJECT-TYPE
    SYNTAX      ConfdString
    MAX-ACCESS  read-only
    STATUS      current
    DESCRIPTION "Number of CCR Initial Requests stored for replay"
    ::= { affirmedServiceconstructInterfaceAaaGroupDiameterStatisticsChassisLevelPeerDiameterInterfaceTypeEntry 10 }

affirmedServiceconstructInterfaceAaaGroupDiameterStatisticsChassisLevelPeerDiameterInterfaceTypeNumCCRUpdateAttempted OBJECT-TYPE
    SYNTAX      ConfdString
    MAX-ACCESS  read-only
    STATUS      current
    DESCRIPTION "Number of CCR Update attempts made"
    ::= { affirmedServiceconstructInterfaceAaaGroupDiameterStatisticsChassisLevelPeerDiameterInterfaceTypeEntry 11 }

affirmedServiceconstructInterfaceAaaGroupDiameterStatisticsChassisLevelPeerDiameterInterfaceTypeNumCCRUpdateSuccess OBJECT-TYPE
    SYNTAX      ConfdString
    MAX-ACCESS  read-only
    STATUS      current
    DESCRIPTION "Number of successful CCR Update attempts"
    ::= { affirmedServiceconstructInterfaceAaaGroupDiameterStatisticsChassisLevelPeerDiameterInterfaceTypeEntry 12 }

affirmedServiceconstructInterfaceAaaGroupDiameterStatisticsChassisLevelPeerDiameterInterfaceTypeNumCCRUpdateFailure OBJECT-TYPE
    SYNTAX      ConfdString
    MAX-ACCESS  read-only
    STATUS      current
    DESCRIPTION "Number of failed CCR Update attempts"
    ::= { affirmedServiceconstructInterfaceAaaGroupDiameterStatisticsChassisLevelPeerDiameterInterfaceTypeEntry 13 }

affirmedServiceconstructInterfaceAaaGroupDiameterStatisticsChassisLevelPeerDiameterInterfaceTypeNumCCRUpdateTimeout OBJECT-TYPE
    SYNTAX      ConfdString
    MAX-ACCESS  read-only
    STATUS      current
    DESCRIPTION "Number of CCR Update attempts that timed out"
    ::= { affirmedServiceconstructInterfaceAaaGroupDiameterStatisticsChassisLevelPeerDiameterInterfaceTypeEntry 14 }

affirmedServiceconstructInterfaceAaaGroupDiameterStatisticsChassisLevelPeerDiameterInterfaceTypeNumCCAUpdateRcvdFirstAttempt OBJECT-TYPE
    SYNTAX      ConfdString
    MAX-ACCESS  read-only
    STATUS      current
    DESCRIPTION "Number of CCA Update requests for which response was received when first transmitted "
    ::= { affirmedServiceconstructInterfaceAaaGroupDiameterStatisticsChassisLevelPeerDiameterInterfaceTypeEntry 15 }

affirmedServiceconstructInterfaceAaaGroupDiameterStatisticsChassisLevelPeerDiameterInterfaceTypeNumCCAUpdateRcvdReTx OBJECT-TYPE
    SYNTAX      ConfdString
    MAX-ACCESS  read-only
    STATUS      current
    DESCRIPTION "Number of CCR Update Requests for which response was received when message was retransmitted"
    ::= { affirmedServiceconstructInterfaceAaaGroupDiameterStatisticsChassisLevelPeerDiameterInterfaceTypeEntry 16 }

affirmedServiceconstructInterfaceAaaGroupDiameterStatisticsChassisLevelPeerDiameterInterfaceTypeNumCCRUpdateStoredForReplay OBJECT-TYPE
    SYNTAX      ConfdString
    MAX-ACCESS  read-only
    STATUS      current
    DESCRIPTION "Number of CCR Update Requests stored for replay"
    ::= { affirmedServiceconstructInterfaceAaaGroupDiameterStatisticsChassisLevelPeerDiameterInterfaceTypeEntry 17 }

affirmedServiceconstructInterfaceAaaGroupDiameterStatisticsChassisLevelPeerDiameterInterfaceTypeNumCCRTerminateAttempted OBJECT-TYPE
    SYNTAX      ConfdString
    MAX-ACCESS  read-only
    STATUS      current
    DESCRIPTION "Number of CCR Terminate attempts made"
    ::= { affirmedServiceconstructInterfaceAaaGroupDiameterStatisticsChassisLevelPeerDiameterInterfaceTypeEntry 18 }

affirmedServiceconstructInterfaceAaaGroupDiameterStatisticsChassisLevelPeerDiameterInterfaceTypeNumCCRTerminateSuccess OBJECT-TYPE
    SYNTAX      ConfdString
    MAX-ACCESS  read-only
    STATUS      current
    DESCRIPTION "Number of successful CCR Terminate attempts"
    ::= { affirmedServiceconstructInterfaceAaaGroupDiameterStatisticsChassisLevelPeerDiameterInterfaceTypeEntry 19 }

affirmedServiceconstructInterfaceAaaGroupDiameterStatisticsChassisLevelPeerDiameterInterfaceTypeNumCCRTerminateFailure OBJECT-TYPE
    SYNTAX      ConfdString
    MAX-ACCESS  read-only
    STATUS      current
    DESCRIPTION "Number of failed CCR Terminate attempts"
    ::= { affirmedServiceconstructInterfaceAaaGroupDiameterStatisticsChassisLevelPeerDiameterInterfaceTypeEntry 20 }

affirmedServiceconstructInterfaceAaaGroupDiameterStatisticsChassisLevelPeerDiameterInterfaceTypeNumCCRTerminateTimeout OBJECT-TYPE
    SYNTAX      ConfdString
    MAX-ACCESS  read-only
    STATUS      current
    DESCRIPTION "Number of CCR Terminate attempts that timed out"
    ::= { affirmedServiceconstructInterfaceAaaGroupDiameterStatisticsChassisLevelPeerDiameterInterfaceTypeEntry 21 }

affirmedServiceconstructInterfaceAaaGroupDiameterStatisticsChassisLevelPeerDiameterInterfaceTypeNumCCATerminateRcvdFirstAttempt OBJECT-TYPE
    SYNTAX      ConfdString
    MAX-ACCESS  read-only
    STATUS      current
    DESCRIPTION "Number of CCA Terminate requests for which response was received when first transmitted "
    ::= { affirmedServiceconstructInterfaceAaaGroupDiameterStatisticsChassisLevelPeerDiameterInterfaceTypeEntry 22 }

affirmedServiceconstructInterfaceAaaGroupDiameterStatisticsChassisLevelPeerDiameterInterfaceTypeNumCCATerminateRcvdReTx OBJECT-TYPE
    SYNTAX      ConfdString
    MAX-ACCESS  read-only
    STATUS      current
    DESCRIPTION "Number of CCR Terminate Requests for which response was received when message was retransmitted"
    ::= { affirmedServiceconstructInterfaceAaaGroupDiameterStatisticsChassisLevelPeerDiameterInterfaceTypeEntry 23 }

affirmedServiceconstructInterfaceAaaGroupDiameterStatisticsChassisLevelPeerDiameterInterfaceTypeNumCCRTerminateStoredForReplay OBJECT-TYPE
    SYNTAX      ConfdString
    MAX-ACCESS  read-only
    STATUS      current
    DESCRIPTION "Number of CCR Terminate Requests stored for replay"
    ::= { affirmedServiceconstructInterfaceAaaGroupDiameterStatisticsChassisLevelPeerDiameterInterfaceTypeEntry 24 }

affirmedServiceconstructInterfaceAaaGroupDiameterStatisticsChassisLevelPeerDiameterInterfaceTypeNumDiameterSessions OBJECT-TYPE
    SYNTAX      ConfdString
    MAX-ACCESS  read-only
    STATUS      current
    DESCRIPTION "Number of subscribers using the diameter connection"
    ::= { affirmedServiceconstructInterfaceAaaGroupDiameterStatisticsChassisLevelPeerDiameterInterfaceTypeEntry 25 }

affirmedServiceconstructInterfaceAaaGroupDiameterStatisticsChassisLevelPeerDiameterInterfaceTypeNumCCRInitialReplay OBJECT-TYPE
    SYNTAX      ConfdString
    MAX-ACCESS  read-only
    STATUS      current
    DESCRIPTION "Number of CCR Initial Requests that were replayed"
    ::= { affirmedServiceconstructInterfaceAaaGroupDiameterStatisticsChassisLevelPeerDiameterInterfaceTypeEntry 26 }

affirmedServiceconstructInterfaceAaaGroupDiameterStatisticsChassisLevelPeerDiameterInterfaceTypeNumCCRInitialReplayReTx OBJECT-TYPE
    SYNTAX      ConfdString
    MAX-ACCESS  read-only
    STATUS      current
    DESCRIPTION "Number of CCR Initial Requests that were replayed more than once"
    ::= { affirmedServiceconstructInterfaceAaaGroupDiameterStatisticsChassisLevelPeerDiameterInterfaceTypeEntry 27 }

affirmedServiceconstructInterfaceAaaGroupDiameterStatisticsChassisLevelPeerDiameterInterfaceTypeNumCCRInitialReplaySuccess OBJECT-TYPE
    SYNTAX      ConfdString
    MAX-ACCESS  read-only
    STATUS      current
    DESCRIPTION "Number of CCR Initial Requests that were replayed and successful"
    ::= { affirmedServiceconstructInterfaceAaaGroupDiameterStatisticsChassisLevelPeerDiameterInterfaceTypeEntry 28 }

affirmedServiceconstructInterfaceAaaGroupDiameterStatisticsChassisLevelPeerDiameterInterfaceTypeNumCCRInitialReplayFailure OBJECT-TYPE
    SYNTAX      ConfdString
    MAX-ACCESS  read-only
    STATUS      current
    DESCRIPTION "Number of CCR Initial Requests that were replayed and failed"
    ::= { affirmedServiceconstructInterfaceAaaGroupDiameterStatisticsChassisLevelPeerDiameterInterfaceTypeEntry 29 }

affirmedServiceconstructInterfaceAaaGroupDiameterStatisticsChassisLevelPeerDiameterInterfaceTypeNumCCRUpdateReplay OBJECT-TYPE
    SYNTAX      ConfdString
    MAX-ACCESS  read-only
    STATUS      current
    DESCRIPTION "Number of CCR Update Requests that were replayed"
    ::= { affirmedServiceconstructInterfaceAaaGroupDiameterStatisticsChassisLevelPeerDiameterInterfaceTypeEntry 30 }

affirmedServiceconstructInterfaceAaaGroupDiameterStatisticsChassisLevelPeerDiameterInterfaceTypeNumCCRUpdateReplayReTx OBJECT-TYPE
    SYNTAX      ConfdString
    MAX-ACCESS  read-only
    STATUS      current
    DESCRIPTION "Number of CCR Update Requests that were replayed more than once"
    ::= { affirmedServiceconstructInterfaceAaaGroupDiameterStatisticsChassisLevelPeerDiameterInterfaceTypeEntry 31 }

affirmedServiceconstructInterfaceAaaGroupDiameterStatisticsChassisLevelPeerDiameterInterfaceTypeNumCCRUpdateReplaySuccess OBJECT-TYPE
    SYNTAX      ConfdString
    MAX-ACCESS  read-only
    STATUS      current
    DESCRIPTION "Number of CCR Update Requests that were replayed and successful"
    ::= { affirmedServiceconstructInterfaceAaaGroupDiameterStatisticsChassisLevelPeerDiameterInterfaceTypeEntry 32 }

affirmedServiceconstructInterfaceAaaGroupDiameterStatisticsChassisLevelPeerDiameterInterfaceTypeNumCCRUpdateReplayFailure OBJECT-TYPE
    SYNTAX      ConfdString
    MAX-ACCESS  read-only
    STATUS      current
    DESCRIPTION "Number of CCR Update Requests that were replayed and failed"
    ::= { affirmedServiceconstructInterfaceAaaGroupDiameterStatisticsChassisLevelPeerDiameterInterfaceTypeEntry 33 }

affirmedServiceconstructInterfaceAaaGroupDiameterStatisticsChassisLevelPeerDiameterInterfaceTypeNumCCRTerminateReplay OBJECT-TYPE
    SYNTAX      ConfdString
    MAX-ACCESS  read-only
    STATUS      current
    DESCRIPTION "Number of CCR Terminate Requests that were replayed"
    ::= { affirmedServiceconstructInterfaceAaaGroupDiameterStatisticsChassisLevelPeerDiameterInterfaceTypeEntry 34 }

affirmedServiceconstructInterfaceAaaGroupDiameterStatisticsChassisLevelPeerDiameterInterfaceTypeNumCCRTerminateReplayReTx OBJECT-TYPE
    SYNTAX      ConfdString
    MAX-ACCESS  read-only
    STATUS      current
    DESCRIPTION "Number of CCR Terminate Requests that were replayed"
    ::= { affirmedServiceconstructInterfaceAaaGroupDiameterStatisticsChassisLevelPeerDiameterInterfaceTypeEntry 35 }

affirmedServiceconstructInterfaceAaaGroupDiameterStatisticsChassisLevelPeerDiameterInterfaceTypeNumCCRTerminateReplaySuccess OBJECT-TYPE
    SYNTAX      ConfdString
    MAX-ACCESS  read-only
    STATUS      current
    DESCRIPTION "Number of CCR Terminate Requests that were replayed and successful"
    ::= { affirmedServiceconstructInterfaceAaaGroupDiameterStatisticsChassisLevelPeerDiameterInterfaceTypeEntry 36 }

affirmedServiceconstructInterfaceAaaGroupDiameterStatisticsChassisLevelPeerDiameterInterfaceTypeNumCCRTerminateReplayFailure OBJECT-TYPE
    SYNTAX      ConfdString
    MAX-ACCESS  read-only
    STATUS      current
    DESCRIPTION "Number of CCR Terminate Requests that were replayed and failed"
    ::= { affirmedServiceconstructInterfaceAaaGroupDiameterStatisticsChassisLevelPeerDiameterInterfaceTypeEntry 37 }

affirmedServiceconstructInterfaceAaaGroupDiameterStatisticsChassisLevelPeerDiameterInterfaceTypeNumACRStartAttempted OBJECT-TYPE
    SYNTAX      ConfdString
    MAX-ACCESS  read-only
    STATUS      current
    DESCRIPTION "Number of ACR Start Request attempts made"
    ::= { affirmedServiceconstructInterfaceAaaGroupDiameterStatisticsChassisLevelPeerDiameterInterfaceTypeEntry 38 }

affirmedServiceconstructInterfaceAaaGroupDiameterStatisticsChassisLevelPeerDiameterInterfaceTypeNumACRStartSuccess OBJECT-TYPE
    SYNTAX      ConfdString
    MAX-ACCESS  read-only
    STATUS      current
    DESCRIPTION "Number of successful ACR Start Requests"
    ::= { affirmedServiceconstructInterfaceAaaGroupDiameterStatisticsChassisLevelPeerDiameterInterfaceTypeEntry 39 }

affirmedServiceconstructInterfaceAaaGroupDiameterStatisticsChassisLevelPeerDiameterInterfaceTypeNumACRStartFailure OBJECT-TYPE
    SYNTAX      ConfdString
    MAX-ACCESS  read-only
    STATUS      current
    DESCRIPTION "Number of failed ACR Start Requests"
    ::= { affirmedServiceconstructInterfaceAaaGroupDiameterStatisticsChassisLevelPeerDiameterInterfaceTypeEntry 40 }

affirmedServiceconstructInterfaceAaaGroupDiameterStatisticsChassisLevelPeerDiameterInterfaceTypeNumACRStartReTx OBJECT-TYPE
    SYNTAX      ConfdString
    MAX-ACCESS  read-only
    STATUS      current
    DESCRIPTION "Number of retransmitted ACR Start Requests"
    ::= { affirmedServiceconstructInterfaceAaaGroupDiameterStatisticsChassisLevelPeerDiameterInterfaceTypeEntry 41 }

affirmedServiceconstructInterfaceAaaGroupDiameterStatisticsChassisLevelPeerDiameterInterfaceTypeNumACRInterimAttempted OBJECT-TYPE
    SYNTAX      ConfdString
    MAX-ACCESS  read-only
    STATUS      current
    DESCRIPTION "Number of ACR Interim Request attempts made"
    ::= { affirmedServiceconstructInterfaceAaaGroupDiameterStatisticsChassisLevelPeerDiameterInterfaceTypeEntry 42 }

affirmedServiceconstructInterfaceAaaGroupDiameterStatisticsChassisLevelPeerDiameterInterfaceTypeNumACRInterimSuccess OBJECT-TYPE
    SYNTAX      ConfdString
    MAX-ACCESS  read-only
    STATUS      current
    DESCRIPTION "Number of successful ACR Interim Requests"
    ::= { affirmedServiceconstructInterfaceAaaGroupDiameterStatisticsChassisLevelPeerDiameterInterfaceTypeEntry 43 }

affirmedServiceconstructInterfaceAaaGroupDiameterStatisticsChassisLevelPeerDiameterInterfaceTypeNumACRInterimFailure OBJECT-TYPE
    SYNTAX      ConfdString
    MAX-ACCESS  read-only
    STATUS      current
    DESCRIPTION "Number of failed ACR Interim Requests"
    ::= { affirmedServiceconstructInterfaceAaaGroupDiameterStatisticsChassisLevelPeerDiameterInterfaceTypeEntry 44 }

affirmedServiceconstructInterfaceAaaGroupDiameterStatisticsChassisLevelPeerDiameterInterfaceTypeNumACRInterimReTx OBJECT-TYPE
    SYNTAX      ConfdString
    MAX-ACCESS  read-only
    STATUS      current
    DESCRIPTION "Number of retransmitted ACR Interim Requests"
    ::= { affirmedServiceconstructInterfaceAaaGroupDiameterStatisticsChassisLevelPeerDiameterInterfaceTypeEntry 45 }

affirmedServiceconstructInterfaceAaaGroupDiameterStatisticsChassisLevelPeerDiameterInterfaceTypeNumACRStopAttempted OBJECT-TYPE
    SYNTAX      ConfdString
    MAX-ACCESS  read-only
    STATUS      current
    DESCRIPTION "Number of ACR Stop Request attempts made"
    ::= { affirmedServiceconstructInterfaceAaaGroupDiameterStatisticsChassisLevelPeerDiameterInterfaceTypeEntry 46 }

affirmedServiceconstructInterfaceAaaGroupDiameterStatisticsChassisLevelPeerDiameterInterfaceTypeNumACRStopSuccess OBJECT-TYPE
    SYNTAX      ConfdString
    MAX-ACCESS  read-only
    STATUS      current
    DESCRIPTION "Number of successful ACR Stop Requests"
    ::= { affirmedServiceconstructInterfaceAaaGroupDiameterStatisticsChassisLevelPeerDiameterInterfaceTypeEntry 47 }

affirmedServiceconstructInterfaceAaaGroupDiameterStatisticsChassisLevelPeerDiameterInterfaceTypeNumACRStopFailure OBJECT-TYPE
    SYNTAX      ConfdString
    MAX-ACCESS  read-only
    STATUS      current
    DESCRIPTION "Number of failed ACR Stop Requests"
    ::= { affirmedServiceconstructInterfaceAaaGroupDiameterStatisticsChassisLevelPeerDiameterInterfaceTypeEntry 48 }

affirmedServiceconstructInterfaceAaaGroupDiameterStatisticsChassisLevelPeerDiameterInterfaceTypeNumACRStopReTx OBJECT-TYPE
    SYNTAX      ConfdString
    MAX-ACCESS  read-only
    STATUS      current
    DESCRIPTION "Number of retransmitted ACR Stop Requests"
    ::= { affirmedServiceconstructInterfaceAaaGroupDiameterStatisticsChassisLevelPeerDiameterInterfaceTypeEntry 49 }

affirmedServiceconstructInterfaceAaaGroupDiameterStatisticsChassisLevelPeerDiameterInterfaceTypeNumACREventAttempted OBJECT-TYPE
    SYNTAX      ConfdString
    MAX-ACCESS  read-only
    STATUS      current
    DESCRIPTION "Number of ACR Event Request attempts made"
    ::= { affirmedServiceconstructInterfaceAaaGroupDiameterStatisticsChassisLevelPeerDiameterInterfaceTypeEntry 50 }

affirmedServiceconstructInterfaceAaaGroupDiameterStatisticsChassisLevelPeerDiameterInterfaceTypeNumACREventSuccess OBJECT-TYPE
    SYNTAX      ConfdString
    MAX-ACCESS  read-only
    STATUS      current
    DESCRIPTION "Number of successful ACR Event Requests"
    ::= { affirmedServiceconstructInterfaceAaaGroupDiameterStatisticsChassisLevelPeerDiameterInterfaceTypeEntry 51 }

affirmedServiceconstructInterfaceAaaGroupDiameterStatisticsChassisLevelPeerDiameterInterfaceTypeNumACREventFailure OBJECT-TYPE
    SYNTAX      ConfdString
    MAX-ACCESS  read-only
    STATUS      current
    DESCRIPTION "Number of failed ACR Event Requests"
    ::= { affirmedServiceconstructInterfaceAaaGroupDiameterStatisticsChassisLevelPeerDiameterInterfaceTypeEntry 52 }

affirmedServiceconstructInterfaceAaaGroupDiameterStatisticsChassisLevelPeerDiameterInterfaceTypeNumACREventReTx OBJECT-TYPE
    SYNTAX      ConfdString
    MAX-ACCESS  read-only
    STATUS      current
    DESCRIPTION "Number of retransmitted ACR Event Requests"
    ::= { affirmedServiceconstructInterfaceAaaGroupDiameterStatisticsChassisLevelPeerDiameterInterfaceTypeEntry 53 }

affirmedServiceconstructInterfaceAaaGroupDiameterStatisticsChassisLevelPeerDiameterInterfaceTypeNumCCAInitial3xxx OBJECT-TYPE
    SYNTAX      ConfdString
    MAX-ACCESS  read-only
    STATUS      current
    DESCRIPTION "Number of failed CCR Initial attempts due to 3xx error"
    ::= { affirmedServiceconstructInterfaceAaaGroupDiameterStatisticsChassisLevelPeerDiameterInterfaceTypeEntry 54 }

affirmedServiceconstructInterfaceAaaGroupDiameterStatisticsChassisLevelPeerDiameterInterfaceTypeNumCCRInitialAborted OBJECT-TYPE
    SYNTAX      ConfdString
    MAX-ACCESS  read-only
    STATUS      current
    DESCRIPTION "Number of CCR Initial attempts that were aborted due to response received from another peer"
    ::= { affirmedServiceconstructInterfaceAaaGroupDiameterStatisticsChassisLevelPeerDiameterInterfaceTypeEntry 55 }

affirmedServiceconstructInterfaceAaaGroupDiameterStatisticsChassisLevelPeerDiameterInterfaceTypeNumCCAInitialDelayedSuccess OBJECT-TYPE
    SYNTAX      ConfdString
    MAX-ACCESS  read-only
    STATUS      current
    DESCRIPTION "Number of CCA Initial success which were received after the request had been re-transmitted to another server"
    ::= { affirmedServiceconstructInterfaceAaaGroupDiameterStatisticsChassisLevelPeerDiameterInterfaceTypeEntry 56 }

affirmedServiceconstructInterfaceAaaGroupDiameterStatisticsChassisLevelPeerDiameterInterfaceTypeNumCCAInitialDelayedFailure OBJECT-TYPE
    SYNTAX      ConfdString
    MAX-ACCESS  read-only
    STATUS      current
    DESCRIPTION "Number of CCA Initial failures which were received after the request had been re-transmitted to another server"
    ::= { affirmedServiceconstructInterfaceAaaGroupDiameterStatisticsChassisLevelPeerDiameterInterfaceTypeEntry 57 }

affirmedServiceconstructInterfaceAaaGroupDiameterStatisticsChassisLevelPeerDiameterInterfaceTypeNumCCAInitialDelayed3xxx OBJECT-TYPE
    SYNTAX      ConfdString
    MAX-ACCESS  read-only
    STATUS      current
    DESCRIPTION "Number of delayed CCA Initial 3xx error which were received after the request had been re-transmitted to another server"
    ::= { affirmedServiceconstructInterfaceAaaGroupDiameterStatisticsChassisLevelPeerDiameterInterfaceTypeEntry 58 }

affirmedServiceconstructInterfaceAaaGroupDiameterStatisticsChassisLevelPeerDiameterInterfaceTypeNumCCAUpdate3xxx OBJECT-TYPE
    SYNTAX      ConfdString
    MAX-ACCESS  read-only
    STATUS      current
    DESCRIPTION "Number of failed CCR Update attempts due to 3xx error"
    ::= { affirmedServiceconstructInterfaceAaaGroupDiameterStatisticsChassisLevelPeerDiameterInterfaceTypeEntry 59 }

affirmedServiceconstructInterfaceAaaGroupDiameterStatisticsChassisLevelPeerDiameterInterfaceTypeNumCCRUpdateAborted OBJECT-TYPE
    SYNTAX      ConfdString
    MAX-ACCESS  read-only
    STATUS      current
    DESCRIPTION "Number of CCR Update attempts that were aborted due to response received from another peer"
    ::= { affirmedServiceconstructInterfaceAaaGroupDiameterStatisticsChassisLevelPeerDiameterInterfaceTypeEntry 60 }

affirmedServiceconstructInterfaceAaaGroupDiameterStatisticsChassisLevelPeerDiameterInterfaceTypeNumCCAUpdateDelayedSuccess OBJECT-TYPE
    SYNTAX      ConfdString
    MAX-ACCESS  read-only
    STATUS      current
    DESCRIPTION "Number of CCA Update success which were received after the request had been re-transmitted to another server"
    ::= { affirmedServiceconstructInterfaceAaaGroupDiameterStatisticsChassisLevelPeerDiameterInterfaceTypeEntry 61 }

affirmedServiceconstructInterfaceAaaGroupDiameterStatisticsChassisLevelPeerDiameterInterfaceTypeNumCCAUpdateDelayedFailure OBJECT-TYPE
    SYNTAX      ConfdString
    MAX-ACCESS  read-only
    STATUS      current
    DESCRIPTION "Number of CCA Update failures which were received after the request had been re-transmitted to another server"
    ::= { affirmedServiceconstructInterfaceAaaGroupDiameterStatisticsChassisLevelPeerDiameterInterfaceTypeEntry 62 }

affirmedServiceconstructInterfaceAaaGroupDiameterStatisticsChassisLevelPeerDiameterInterfaceTypeNumCCAUpdateDelayed3xxx OBJECT-TYPE
    SYNTAX      ConfdString
    MAX-ACCESS  read-only
    STATUS      current
    DESCRIPTION "Number of CCA Update 3xx errors which were received after the request had been re-transmitted to another server"
    ::= { affirmedServiceconstructInterfaceAaaGroupDiameterStatisticsChassisLevelPeerDiameterInterfaceTypeEntry 63 }

affirmedServiceconstructInterfaceAaaGroupDiameterStatisticsChassisLevelPeerDiameterInterfaceTypeNumCCATerminate3xxx OBJECT-TYPE
    SYNTAX      ConfdString
    MAX-ACCESS  read-only
    STATUS      current
    DESCRIPTION "Number of failed CCR Terminate attempts due to 3xx error"
    ::= { affirmedServiceconstructInterfaceAaaGroupDiameterStatisticsChassisLevelPeerDiameterInterfaceTypeEntry 64 }

affirmedServiceconstructInterfaceAaaGroupDiameterStatisticsChassisLevelPeerDiameterInterfaceTypeNumCCRTerminateAborted OBJECT-TYPE
    SYNTAX      ConfdString
    MAX-ACCESS  read-only
    STATUS      current
    DESCRIPTION "Number of CCR Terminate attempts that were aborted due to response received from another peer"
    ::= { affirmedServiceconstructInterfaceAaaGroupDiameterStatisticsChassisLevelPeerDiameterInterfaceTypeEntry 65 }

affirmedServiceconstructInterfaceAaaGroupDiameterStatisticsChassisLevelPeerDiameterInterfaceTypeNumCCATerminateDelayedSuccess OBJECT-TYPE
    SYNTAX      ConfdString
    MAX-ACCESS  read-only
    STATUS      current
    DESCRIPTION "Number of CCA Terminate success which were received after the request had been re-transmitted to another server"
    ::= { affirmedServiceconstructInterfaceAaaGroupDiameterStatisticsChassisLevelPeerDiameterInterfaceTypeEntry 66 }

affirmedServiceconstructInterfaceAaaGroupDiameterStatisticsChassisLevelPeerDiameterInterfaceTypeNumCCATerminateDelayedFailure OBJECT-TYPE
    SYNTAX      ConfdString
    MAX-ACCESS  read-only
    STATUS      current
    DESCRIPTION "Number of CCA Terminate failures which were received after the request had been re-transmitted to another server"
    ::= { affirmedServiceconstructInterfaceAaaGroupDiameterStatisticsChassisLevelPeerDiameterInterfaceTypeEntry 67 }

affirmedServiceconstructInterfaceAaaGroupDiameterStatisticsChassisLevelPeerDiameterInterfaceTypeNumCCATerminateDelayed3xxx OBJECT-TYPE
    SYNTAX      ConfdString
    MAX-ACCESS  read-only
    STATUS      current
    DESCRIPTION "Number of CCA Terminate 3xx errors which were received after the request had been re-transmitted to another server"
    ::= { affirmedServiceconstructInterfaceAaaGroupDiameterStatisticsChassisLevelPeerDiameterInterfaceTypeEntry 68 }

affirmedServiceconstructInterfaceAaaGroupDiameterStatisticsChassisLevelPeerDiameterInterfaceTypeNumCCAInitialDroppedBadSeqNum OBJECT-TYPE
    SYNTAX      ConfdString
    MAX-ACCESS  read-only
    STATUS      current
    DESCRIPTION "Number of CCA Initial that were dropped due to unexpected sequence number in the response received from peer"
    ::= { affirmedServiceconstructInterfaceAaaGroupDiameterStatisticsChassisLevelPeerDiameterInterfaceTypeEntry 69 }

affirmedServiceconstructInterfaceAaaGroupDiameterStatisticsChassisLevelPeerDiameterInterfaceTypeNumCCAInitialDroppedNoSession OBJECT-TYPE
    SYNTAX      ConfdString
    MAX-ACCESS  read-only
    STATUS      current
    DESCRIPTION "Number of CCA Initial that were dropped due to session not found"
    ::= { affirmedServiceconstructInterfaceAaaGroupDiameterStatisticsChassisLevelPeerDiameterInterfaceTypeEntry 70 }

affirmedServiceconstructInterfaceAaaGroupDiameterStatisticsChassisLevelPeerDiameterInterfaceTypeNumCCAInitialDroppedNoProc OBJECT-TYPE
    SYNTAX      ConfdString
    MAX-ACCESS  read-only
    STATUS      current
    DESCRIPTION "Number of CCA Initial that were dropped due to no matching transaction"
    ::= { affirmedServiceconstructInterfaceAaaGroupDiameterStatisticsChassisLevelPeerDiameterInterfaceTypeEntry 71 }

affirmedServiceconstructInterfaceAaaGroupDiameterStatisticsChassisLevelPeerDiameterInterfaceTypeNumCCAUpdateDroppedBadSeqNum OBJECT-TYPE
    SYNTAX      ConfdString
    MAX-ACCESS  read-only
    STATUS      current
    DESCRIPTION "Number of CCA Update that were dropped due to unexpected sequence number in the response received from peer"
    ::= { affirmedServiceconstructInterfaceAaaGroupDiameterStatisticsChassisLevelPeerDiameterInterfaceTypeEntry 72 }

affirmedServiceconstructInterfaceAaaGroupDiameterStatisticsChassisLevelPeerDiameterInterfaceTypeNumCCAUpdateDroppedNoSession OBJECT-TYPE
    SYNTAX      ConfdString
    MAX-ACCESS  read-only
    STATUS      current
    DESCRIPTION "Number of CCA Update that were dropped due to session not found"
    ::= { affirmedServiceconstructInterfaceAaaGroupDiameterStatisticsChassisLevelPeerDiameterInterfaceTypeEntry 73 }

affirmedServiceconstructInterfaceAaaGroupDiameterStatisticsChassisLevelPeerDiameterInterfaceTypeNumCCAUpdateDroppedNoProc OBJECT-TYPE
    SYNTAX      ConfdString
    MAX-ACCESS  read-only
    STATUS      current
    DESCRIPTION "Number of CCA Update that were dropped due to no matching transaction"
    ::= { affirmedServiceconstructInterfaceAaaGroupDiameterStatisticsChassisLevelPeerDiameterInterfaceTypeEntry 74 }

affirmedServiceconstructInterfaceAaaGroupDiameterStatisticsChassisLevelPeerDiameterInterfaceTypeNumCCATerminateDroppedBadSeqNum OBJECT-TYPE
    SYNTAX      ConfdString
    MAX-ACCESS  read-only
    STATUS      current
    DESCRIPTION "Number of CCA Terminate that were dropped due to unexpected sequence number in the response received from peer"
    ::= { affirmedServiceconstructInterfaceAaaGroupDiameterStatisticsChassisLevelPeerDiameterInterfaceTypeEntry 75 }

affirmedServiceconstructInterfaceAaaGroupDiameterStatisticsChassisLevelPeerDiameterInterfaceTypeNumCCATerminateDroppedNoSession OBJECT-TYPE
    SYNTAX      ConfdString
    MAX-ACCESS  read-only
    STATUS      current
    DESCRIPTION "Number of CCA Terminate that were dropped due to session not found"
    ::= { affirmedServiceconstructInterfaceAaaGroupDiameterStatisticsChassisLevelPeerDiameterInterfaceTypeEntry 76 }

affirmedServiceconstructInterfaceAaaGroupDiameterStatisticsChassisLevelPeerDiameterInterfaceTypeNumCCATerminateDroppedNoProc OBJECT-TYPE
    SYNTAX      ConfdString
    MAX-ACCESS  read-only
    STATUS      current
    DESCRIPTION "Number of CCA Terminate that were dropped due to no matching transaction"
    ::= { affirmedServiceconstructInterfaceAaaGroupDiameterStatisticsChassisLevelPeerDiameterInterfaceTypeEntry 77 }

affirmedServiceconstructInterfaceAaaGroupDiameterStatisticsChassisLevelPeerDiameterInterfaceTypeNumTimesPeerDeactivated OBJECT-TYPE
    SYNTAX      ConfdString
    MAX-ACCESS  read-only
    STATUS      current
    DESCRIPTION "Number of times the peer went down"
    ::= { affirmedServiceconstructInterfaceAaaGroupDiameterStatisticsChassisLevelPeerDiameterInterfaceTypeEntry 78 }

affirmedServiceconstructInterfaceAaaGroupDiameterStatisticsChassisLevelPeerDiameterInterfaceTypeNumTimesPeerFlowOffRcvd OBJECT-TYPE
    SYNTAX      ConfdString
    MAX-ACCESS  read-only
    STATUS      current
    DESCRIPTION "Number of times flow-off received for peer"
    ::= { affirmedServiceconstructInterfaceAaaGroupDiameterStatisticsChassisLevelPeerDiameterInterfaceTypeEntry 79 }

affirmedServiceconstructInterfaceAaaGroupDiameterStatisticsChassisLevelPeerDiameterInterfaceTypeNumAARInitialAttempted OBJECT-TYPE
    SYNTAX      ConfdString
    MAX-ACCESS  read-only
    STATUS      current
    DESCRIPTION "Number of AAR Initial attempts made"
    ::= { affirmedServiceconstructInterfaceAaaGroupDiameterStatisticsChassisLevelPeerDiameterInterfaceTypeEntry 80 }

affirmedServiceconstructInterfaceAaaGroupDiameterStatisticsChassisLevelPeerDiameterInterfaceTypeNumAARInitialSuccess OBJECT-TYPE
    SYNTAX      ConfdString
    MAX-ACCESS  read-only
    STATUS      current
    DESCRIPTION "Number of successful AAR Initial attempts"
    ::= { affirmedServiceconstructInterfaceAaaGroupDiameterStatisticsChassisLevelPeerDiameterInterfaceTypeEntry 81 }

affirmedServiceconstructInterfaceAaaGroupDiameterStatisticsChassisLevelPeerDiameterInterfaceTypeNumAARInitialFailure OBJECT-TYPE
    SYNTAX      ConfdString
    MAX-ACCESS  read-only
    STATUS      current
    DESCRIPTION "Number of failed AAR Initial attempts"
    ::= { affirmedServiceconstructInterfaceAaaGroupDiameterStatisticsChassisLevelPeerDiameterInterfaceTypeEntry 82 }

affirmedServiceconstructInterfaceAaaGroupDiameterStatisticsChassisLevelPeerDiameterInterfaceTypeNumAARInitialTimeout OBJECT-TYPE
    SYNTAX      ConfdString
    MAX-ACCESS  read-only
    STATUS      current
    DESCRIPTION "Number of AAR Initial attempts that timed out"
    ::= { affirmedServiceconstructInterfaceAaaGroupDiameterStatisticsChassisLevelPeerDiameterInterfaceTypeEntry 83 }

affirmedServiceconstructInterfaceAaaGroupDiameterStatisticsChassisLevelPeerDiameterInterfaceTypeNumAAAInitialRcvdFirstAttempt OBJECT-TYPE
    SYNTAX      ConfdString
    MAX-ACCESS  read-only
    STATUS      current
    DESCRIPTION "Number of AAR Initial requests for which response was received when first transmitted "
    ::= { affirmedServiceconstructInterfaceAaaGroupDiameterStatisticsChassisLevelPeerDiameterInterfaceTypeEntry 84 }

affirmedServiceconstructInterfaceAaaGroupDiameterStatisticsChassisLevelPeerDiameterInterfaceTypeNumAAAInitialRcvdReTx OBJECT-TYPE
    SYNTAX      ConfdString
    MAX-ACCESS  read-only
    STATUS      current
    DESCRIPTION "Number of AAR Initial Requests for which response was received when message was retransmitted"
    ::= { affirmedServiceconstructInterfaceAaaGroupDiameterStatisticsChassisLevelPeerDiameterInterfaceTypeEntry 85 }

affirmedServiceconstructInterfaceAaaGroupDiameterStatisticsChassisLevelPeerDiameterInterfaceTypeNumSTRAttempted OBJECT-TYPE
    SYNTAX      ConfdString
    MAX-ACCESS  read-only
    STATUS      current
    DESCRIPTION "Number of STR attempts made"
    ::= { affirmedServiceconstructInterfaceAaaGroupDiameterStatisticsChassisLevelPeerDiameterInterfaceTypeEntry 86 }

affirmedServiceconstructInterfaceAaaGroupDiameterStatisticsChassisLevelPeerDiameterInterfaceTypeNumSTRSuccess OBJECT-TYPE
    SYNTAX      ConfdString
    MAX-ACCESS  read-only
    STATUS      current
    DESCRIPTION "Number of successful STR attempts"
    ::= { affirmedServiceconstructInterfaceAaaGroupDiameterStatisticsChassisLevelPeerDiameterInterfaceTypeEntry 87 }

affirmedServiceconstructInterfaceAaaGroupDiameterStatisticsChassisLevelPeerDiameterInterfaceTypeNumSTRFailure OBJECT-TYPE
    SYNTAX      ConfdString
    MAX-ACCESS  read-only
    STATUS      current
    DESCRIPTION "Number of failed STR attempts"
    ::= { affirmedServiceconstructInterfaceAaaGroupDiameterStatisticsChassisLevelPeerDiameterInterfaceTypeEntry 88 }

affirmedServiceconstructInterfaceAaaGroupDiameterStatisticsChassisLevelPeerDiameterInterfaceTypeNumSTRTimeout OBJECT-TYPE
    SYNTAX      ConfdString
    MAX-ACCESS  read-only
    STATUS      current
    DESCRIPTION "Number of STR attempts that timed out"
    ::= { affirmedServiceconstructInterfaceAaaGroupDiameterStatisticsChassisLevelPeerDiameterInterfaceTypeEntry 89 }

affirmedServiceconstructInterfaceAaaGroupDiameterStatisticsChassisLevelPeerDiameterInterfaceTypeNumSTARcvdFirstAttempt OBJECT-TYPE
    SYNTAX      ConfdString
    MAX-ACCESS  read-only
    STATUS      current
    DESCRIPTION "Number of STR requests for which response was received when first transmitted "
    ::= { affirmedServiceconstructInterfaceAaaGroupDiameterStatisticsChassisLevelPeerDiameterInterfaceTypeEntry 90 }

affirmedServiceconstructInterfaceAaaGroupDiameterStatisticsChassisLevelPeerDiameterInterfaceTypeNumSTARcvdReTx OBJECT-TYPE
    SYNTAX      ConfdString
    MAX-ACCESS  read-only
    STATUS      current
    DESCRIPTION "Number of STR Requests for which response was received when message was retransmitted"
    ::= { affirmedServiceconstructInterfaceAaaGroupDiameterStatisticsChassisLevelPeerDiameterInterfaceTypeEntry 91 }

affirmedServiceconstructInterfaceAaaGroupDiameterStatisticsChassisLevelPeerDiameterInterfaceTypeNumHandoffAARAttempted OBJECT-TYPE
    SYNTAX      ConfdString
    MAX-ACCESS  read-only
    STATUS      current
    DESCRIPTION "Number of Handoff AAR attempts made"
    ::= { affirmedServiceconstructInterfaceAaaGroupDiameterStatisticsChassisLevelPeerDiameterInterfaceTypeEntry 92 }

affirmedServiceconstructInterfaceAaaGroupDiameterStatisticsChassisLevelPeerDiameterInterfaceTypeNumHandoffAARSuccess OBJECT-TYPE
    SYNTAX      ConfdString
    MAX-ACCESS  read-only
    STATUS      current
    DESCRIPTION "Number of successful Handoff AAR attempts"
    ::= { affirmedServiceconstructInterfaceAaaGroupDiameterStatisticsChassisLevelPeerDiameterInterfaceTypeEntry 93 }

affirmedServiceconstructInterfaceAaaGroupDiameterStatisticsChassisLevelPeerDiameterInterfaceTypeNumHandoffAARFailure OBJECT-TYPE
    SYNTAX      ConfdString
    MAX-ACCESS  read-only
    STATUS      current
    DESCRIPTION "Number of failed Handoff AAR attempts"
    ::= { affirmedServiceconstructInterfaceAaaGroupDiameterStatisticsChassisLevelPeerDiameterInterfaceTypeEntry 94 }

affirmedServiceconstructInterfaceAaaGroupDiameterStatisticsChassisLevelPeerDiameterInterfaceTypeNumHandoffAARTimeout OBJECT-TYPE
    SYNTAX      ConfdString
    MAX-ACCESS  read-only
    STATUS      current
    DESCRIPTION "Number of Handoff AAR attempts that timed out"
    ::= { affirmedServiceconstructInterfaceAaaGroupDiameterStatisticsChassisLevelPeerDiameterInterfaceTypeEntry 95 }

affirmedServiceconstructInterfaceAaaGroupDiameterStatisticsChassisLevelPeerDiameterInterfaceTypeNumHandoffAAARcvdFirstAttempt OBJECT-TYPE
    SYNTAX      ConfdString
    MAX-ACCESS  read-only
    STATUS      current
    DESCRIPTION "Number of Handoff AAR requests for which response was received when first transmitted "
    ::= { affirmedServiceconstructInterfaceAaaGroupDiameterStatisticsChassisLevelPeerDiameterInterfaceTypeEntry 96 }

affirmedServiceconstructInterfaceAaaGroupDiameterStatisticsChassisLevelPeerDiameterInterfaceTypeNumHandoffAAARcvdReTx OBJECT-TYPE
    SYNTAX      ConfdString
    MAX-ACCESS  read-only
    STATUS      current
    DESCRIPTION "Number of Handoff AAR Requests for which response was received when message was retransmitted"
    ::= { affirmedServiceconstructInterfaceAaaGroupDiameterStatisticsChassisLevelPeerDiameterInterfaceTypeEntry 97 }

affirmedServiceconstructInterfaceAaaGroupDiameterStatisticsChassisLevelPeerDiameterInterfaceTypeNumRarInitAARAttempted OBJECT-TYPE
    SYNTAX      ConfdString
    MAX-ACCESS  read-only
    STATUS      current
    DESCRIPTION "Number of RAR Initiated AAR attempts made"
    ::= { affirmedServiceconstructInterfaceAaaGroupDiameterStatisticsChassisLevelPeerDiameterInterfaceTypeEntry 98 }

affirmedServiceconstructInterfaceAaaGroupDiameterStatisticsChassisLevelPeerDiameterInterfaceTypeNumRarInitAARSuccess OBJECT-TYPE
    SYNTAX      ConfdString
    MAX-ACCESS  read-only
    STATUS      current
    DESCRIPTION "Number of successful RAR Initiated AAR attempts"
    ::= { affirmedServiceconstructInterfaceAaaGroupDiameterStatisticsChassisLevelPeerDiameterInterfaceTypeEntry 99 }

affirmedServiceconstructInterfaceAaaGroupDiameterStatisticsChassisLevelPeerDiameterInterfaceTypeNumRarInitAARFailure OBJECT-TYPE
    SYNTAX      ConfdString
    MAX-ACCESS  read-only
    STATUS      current
    DESCRIPTION "Number of failed RAR Initiated AAR failures"
    ::= { affirmedServiceconstructInterfaceAaaGroupDiameterStatisticsChassisLevelPeerDiameterInterfaceTypeEntry 100 }

affirmedServiceconstructInterfaceAaaGroupDiameterStatisticsChassisLevelPeerDiameterInterfaceTypeNumRarInitAARTimeout OBJECT-TYPE
    SYNTAX      ConfdString
    MAX-ACCESS  read-only
    STATUS      current
    DESCRIPTION "Number of RAR Initiated AAR attempts that timed out"
    ::= { affirmedServiceconstructInterfaceAaaGroupDiameterStatisticsChassisLevelPeerDiameterInterfaceTypeEntry 101 }

affirmedServiceconstructInterfaceAaaGroupDiameterStatisticsChassisLevelPeerDiameterInterfaceTypeNumRarInitAAARcvdFirstAttempt OBJECT-TYPE
    SYNTAX      ConfdString
    MAX-ACCESS  read-only
    STATUS      current
    DESCRIPTION "Number of RAR Initiated AAR requests for which response was received when first transmitted "
    ::= { affirmedServiceconstructInterfaceAaaGroupDiameterStatisticsChassisLevelPeerDiameterInterfaceTypeEntry 102 }

affirmedServiceconstructInterfaceAaaGroupDiameterStatisticsChassisLevelPeerDiameterInterfaceTypeNumRarInitAAARcvdReTx OBJECT-TYPE
    SYNTAX      ConfdString
    MAX-ACCESS  read-only
    STATUS      current
    DESCRIPTION "Number of RAR Initiated AAR Requests for which response was received when message was retransmitted"
    ::= { affirmedServiceconstructInterfaceAaaGroupDiameterStatisticsChassisLevelPeerDiameterInterfaceTypeEntry 103 }

affirmedServiceconstructInterfaceAaaGroupDiameterStatisticsChassisLevelPeerDiameterInterfaceTypeNumDERInitialAttempted OBJECT-TYPE
    SYNTAX      ConfdString
    MAX-ACCESS  read-only
    STATUS      current
    DESCRIPTION "Number of initial authentication DER attempts"
    ::= { affirmedServiceconstructInterfaceAaaGroupDiameterStatisticsChassisLevelPeerDiameterInterfaceTypeEntry 104 }

affirmedServiceconstructInterfaceAaaGroupDiameterStatisticsChassisLevelPeerDiameterInterfaceTypeNumDERInitialSuccess OBJECT-TYPE
    SYNTAX      ConfdString
    MAX-ACCESS  read-only
    STATUS      current
    DESCRIPTION "Number of initial authentication DER that succeeded"
    ::= { affirmedServiceconstructInterfaceAaaGroupDiameterStatisticsChassisLevelPeerDiameterInterfaceTypeEntry 105 }

affirmedServiceconstructInterfaceAaaGroupDiameterStatisticsChassisLevelPeerDiameterInterfaceTypeNumDERInitialFailure OBJECT-TYPE
    SYNTAX      ConfdString
    MAX-ACCESS  read-only
    STATUS      current
    DESCRIPTION "Number of initial authentication DER attempts that failed"
    ::= { affirmedServiceconstructInterfaceAaaGroupDiameterStatisticsChassisLevelPeerDiameterInterfaceTypeEntry 106 }

affirmedServiceconstructInterfaceAaaGroupDiameterStatisticsChassisLevelPeerDiameterInterfaceTypeNumDERInitialTimeout OBJECT-TYPE
    SYNTAX      ConfdString
    MAX-ACCESS  read-only
    STATUS      current
    DESCRIPTION "Number of initial authentication DER attempts that timed out"
    ::= { affirmedServiceconstructInterfaceAaaGroupDiameterStatisticsChassisLevelPeerDiameterInterfaceTypeEntry 107 }

affirmedServiceconstructInterfaceAaaGroupDiameterStatisticsChassisLevelPeerDiameterInterfaceTypeNumDERInitialChallenge OBJECT-TYPE
    SYNTAX      ConfdString
    MAX-ACCESS  read-only
    STATUS      current
    DESCRIPTION "Number of initial authentication DER requests sent with challenge "
    ::= { affirmedServiceconstructInterfaceAaaGroupDiameterStatisticsChassisLevelPeerDiameterInterfaceTypeEntry 108 }

affirmedServiceconstructInterfaceAaaGroupDiameterStatisticsChassisLevelPeerDiameterInterfaceTypeNumDERInitialNotification OBJECT-TYPE
    SYNTAX      ConfdString
    MAX-ACCESS  read-only
    STATUS      current
    DESCRIPTION "Number of initial authentication DER requests sent with notification"
    ::= { affirmedServiceconstructInterfaceAaaGroupDiameterStatisticsChassisLevelPeerDiameterInterfaceTypeEntry 109 }

affirmedServiceconstructInterfaceAaaGroupDiameterStatisticsChassisLevelPeerDiameterInterfaceTypeNumDERReAuthAttempted OBJECT-TYPE
    SYNTAX      ConfdString
    MAX-ACCESS  read-only
    STATUS      current
    DESCRIPTION "Number of re-authentication DER attempts made"
    ::= { affirmedServiceconstructInterfaceAaaGroupDiameterStatisticsChassisLevelPeerDiameterInterfaceTypeEntry 110 }

affirmedServiceconstructInterfaceAaaGroupDiameterStatisticsChassisLevelPeerDiameterInterfaceTypeNumDERReAuthSuccess OBJECT-TYPE
    SYNTAX      ConfdString
    MAX-ACCESS  read-only
    STATUS      current
    DESCRIPTION "Number of re-authentication DER attempts that succeeded"
    ::= { affirmedServiceconstructInterfaceAaaGroupDiameterStatisticsChassisLevelPeerDiameterInterfaceTypeEntry 111 }

affirmedServiceconstructInterfaceAaaGroupDiameterStatisticsChassisLevelPeerDiameterInterfaceTypeNumDERReAuthFailure OBJECT-TYPE
    SYNTAX      ConfdString
    MAX-ACCESS  read-only
    STATUS      current
    DESCRIPTION "Number of re-authentication DER attempts that failed"
    ::= { affirmedServiceconstructInterfaceAaaGroupDiameterStatisticsChassisLevelPeerDiameterInterfaceTypeEntry 112 }

affirmedServiceconstructInterfaceAaaGroupDiameterStatisticsChassisLevelPeerDiameterInterfaceTypeNumDERReAuthTimeout OBJECT-TYPE
    SYNTAX      ConfdString
    MAX-ACCESS  read-only
    STATUS      current
    DESCRIPTION "Number of re-authentication DER attempts that timed out"
    ::= { affirmedServiceconstructInterfaceAaaGroupDiameterStatisticsChassisLevelPeerDiameterInterfaceTypeEntry 113 }

affirmedServiceconstructInterfaceAaaGroupDiameterStatisticsChassisLevelPeerDiameterInterfaceTypeNumDERReAuthChallenge OBJECT-TYPE
    SYNTAX      ConfdString
    MAX-ACCESS  read-only
    STATUS      current
    DESCRIPTION "Number of re-authentication DER attempts sent with Challenges"
    ::= { affirmedServiceconstructInterfaceAaaGroupDiameterStatisticsChassisLevelPeerDiameterInterfaceTypeEntry 114 }

affirmedServiceconstructInterfaceAaaGroupDiameterStatisticsChassisLevelPeerDiameterInterfaceTypeNumDERReAuthNotification OBJECT-TYPE
    SYNTAX      ConfdString
    MAX-ACCESS  read-only
    STATUS      current
    DESCRIPTION "Number of re-authentication DER attempts sent with Notification"
    ::= { affirmedServiceconstructInterfaceAaaGroupDiameterStatisticsChassisLevelPeerDiameterInterfaceTypeEntry 115 }

affirmedServiceconstructInterfaceAaaGroupDiameterStatisticsChassisLevelPeerDiameterInterfaceTypeNumRarRcvd OBJECT-TYPE
    SYNTAX      ConfdString
    MAX-ACCESS  read-only
    STATUS      current
    DESCRIPTION "Number of Diameter RAR request received"
    ::= { affirmedServiceconstructInterfaceAaaGroupDiameterStatisticsChassisLevelPeerDiameterInterfaceTypeEntry 116 }

affirmedServiceconstructInterfaceAaaGroupDiameterStatisticsChassisLevelPeerDiameterInterfaceTypeNumRarFailure OBJECT-TYPE
    SYNTAX      ConfdString
    MAX-ACCESS  read-only
    STATUS      current
    DESCRIPTION "Number of Diameter RAR failed as sessions no longer exist"
    ::= { affirmedServiceconstructInterfaceAaaGroupDiameterStatisticsChassisLevelPeerDiameterInterfaceTypeEntry 117 }

affirmedServiceconstructInterfaceAaaGroupDiameterStatisticsChassisLevelPeerDiameterInterfaceTypeNumAsrRcvd OBJECT-TYPE
    SYNTAX      ConfdString
    MAX-ACCESS  read-only
    STATUS      current
    DESCRIPTION "Number of Diameter ASR request received"
    ::= { affirmedServiceconstructInterfaceAaaGroupDiameterStatisticsChassisLevelPeerDiameterInterfaceTypeEntry 118 }

affirmedServiceconstructInterfaceAaaGroupDiameterStatisticsChassisLevelPeerDiameterInterfaceTypeNumAsrFailure OBJECT-TYPE
    SYNTAX      ConfdString
    MAX-ACCESS  read-only
    STATUS      current
    DESCRIPTION "Number of Diameter ASR failed as sessions no longer exist"
    ::= { affirmedServiceconstructInterfaceAaaGroupDiameterStatisticsChassisLevelPeerDiameterInterfaceTypeEntry 119 }

affirmedServiceconstructInterfaceAaaGroupDiameterStatisticsChassisLevelPeerDiameterInterfaceTypeNumRarReceived OBJECT-TYPE
    SYNTAX      Unsigned32
    MAX-ACCESS  read-only
    STATUS      current
    DESCRIPTION "Number of RAR messages received from peer"
    ::= { affirmedServiceconstructInterfaceAaaGroupDiameterStatisticsChassisLevelPeerDiameterInterfaceTypeEntry 120 }

affirmedServiceconstructInterfaceAaaGroupDiameterStatisticsChassisLevelPeerDiameterInterfaceTypeNumRaaSuccess OBJECT-TYPE
    SYNTAX      Unsigned32
    MAX-ACCESS  read-only
    STATUS      current
    DESCRIPTION "Number of RAA success messages sent to peer"
    ::= { affirmedServiceconstructInterfaceAaaGroupDiameterStatisticsChassisLevelPeerDiameterInterfaceTypeEntry 121 }

affirmedServiceconstructInterfaceAaaGroupDiameterStatisticsChassisLevelPeerDiameterInterfaceTypeNumRaaFailures OBJECT-TYPE
    SYNTAX      Unsigned32
    MAX-ACCESS  read-only
    STATUS      current
    DESCRIPTION "Number of RAA failure messages sent to peer"
    ::= { affirmedServiceconstructInterfaceAaaGroupDiameterStatisticsChassisLevelPeerDiameterInterfaceTypeEntry 122 }

affirmedServiceconstructInterfaceAaaGroupDiameterStatisticsChassisLevelPeerDiameterInterfaceTypeNumRaaFailuresUnknownSession OBJECT-TYPE
    SYNTAX      Unsigned32
    MAX-ACCESS  read-only
    STATUS      current
    DESCRIPTION "Number of RAA failure messages due to unknown session sent to peer"
    ::= { affirmedServiceconstructInterfaceAaaGroupDiameterStatisticsChassisLevelPeerDiameterInterfaceTypeEntry 123 }

affirmedServiceconstructInterfaceAaaGroupDiameterStatisticsChassisLevelPeerDiameterInterfaceTypeNumRaaFailuresMissingAVP OBJECT-TYPE
    SYNTAX      Unsigned32
    MAX-ACCESS  read-only
    STATUS      current
    DESCRIPTION "Number of RAA failure messages due to missing AVPs sent to peer"
    ::= { affirmedServiceconstructInterfaceAaaGroupDiameterStatisticsChassisLevelPeerDiameterInterfaceTypeEntry 124 }

affirmedServiceconstructInterfaceAaaGroupDiameterStatisticsChassisLevelPeerDiameterInterfaceTypeNumRaaFailuresRealmNotServed OBJECT-TYPE
    SYNTAX      Unsigned32
    MAX-ACCESS  read-only
    STATUS      current
    DESCRIPTION "Number of RAA failure messages sent to peer due to Destination Realm in RAR not being recognized"
    ::= { affirmedServiceconstructInterfaceAaaGroupDiameterStatisticsChassisLevelPeerDiameterInterfaceTypeEntry 125 }

affirmedServiceconstructInterfaceAaaGroupDiameterStatisticsChassisLevelPeerDiameterInterfaceTypeNumRaaFailuresUnableToDeliver OBJECT-TYPE
    SYNTAX      Unsigned32
    MAX-ACCESS  read-only
    STATUS      current
    DESCRIPTION "Number of RAA failure messages sent to peer due to Destination Host in RAR not being found"
    ::= { affirmedServiceconstructInterfaceAaaGroupDiameterStatisticsChassisLevelPeerDiameterInterfaceTypeEntry 126 }

affirmedServiceconstructInterfaceAaaGroupDiameterStatisticsChassisLevelPeerDiameterInterfaceTypeNumRaaFailuresTooBusy OBJECT-TYPE
    SYNTAX      Unsigned32
    MAX-ACCESS  read-only
    STATUS      current
    DESCRIPTION "Number of RAA failure messages sent to peer due to Gateway too busy to process RAR"
    ::= { affirmedServiceconstructInterfaceAaaGroupDiameterStatisticsChassisLevelPeerDiameterInterfaceTypeEntry 127 }

affirmedServiceconstructInterfaceAaaGroupDiameterStatisticsChassisLevelPeerDiameterInterfaceTypeNumCCAInitial4xxx OBJECT-TYPE
    SYNTAX      ConfdString
    MAX-ACCESS  read-only
    STATUS      current
    DESCRIPTION "Number of CCA Initial received with 4xx errors"
    ::= { affirmedServiceconstructInterfaceAaaGroupDiameterStatisticsChassisLevelPeerDiameterInterfaceTypeEntry 128 }

affirmedServiceconstructInterfaceAaaGroupDiameterStatisticsChassisLevelPeerDiameterInterfaceTypeNumCCAInitial5xxx OBJECT-TYPE
    SYNTAX      ConfdString
    MAX-ACCESS  read-only
    STATUS      current
    DESCRIPTION "Number of failed CCA Initial received with 5xx error"
    ::= { affirmedServiceconstructInterfaceAaaGroupDiameterStatisticsChassisLevelPeerDiameterInterfaceTypeEntry 129 }

affirmedServiceconstructInterfaceAaaGroupDiameterStatisticsChassisLevelPeerDiameterInterfaceTypeNumCCAUpdate4xxx OBJECT-TYPE
    SYNTAX      ConfdString
    MAX-ACCESS  read-only
    STATUS      current
    DESCRIPTION "Number of failed CCA Update received with 4xx error"
    ::= { affirmedServiceconstructInterfaceAaaGroupDiameterStatisticsChassisLevelPeerDiameterInterfaceTypeEntry 130 }

affirmedServiceconstructInterfaceAaaGroupDiameterStatisticsChassisLevelPeerDiameterInterfaceTypeNumCCAUpdate5xxx OBJECT-TYPE
    SYNTAX      ConfdString
    MAX-ACCESS  read-only
    STATUS      current
    DESCRIPTION "Number of failed CCA Update received with 5xx error"
    ::= { affirmedServiceconstructInterfaceAaaGroupDiameterStatisticsChassisLevelPeerDiameterInterfaceTypeEntry 131 }

affirmedServiceconstructInterfaceAaaGroupDiameterStatisticsChassisLevelPeerDiameterInterfaceTypeNumCCATerminate4xxx OBJECT-TYPE
    SYNTAX      ConfdString
    MAX-ACCESS  read-only
    STATUS      current
    DESCRIPTION "Number of failed CCA Terminate received with 4xx error"
    ::= { affirmedServiceconstructInterfaceAaaGroupDiameterStatisticsChassisLevelPeerDiameterInterfaceTypeEntry 132 }

affirmedServiceconstructInterfaceAaaGroupDiameterStatisticsChassisLevelPeerDiameterInterfaceTypeNumCCATerminate5xxx OBJECT-TYPE
    SYNTAX      ConfdString
    MAX-ACCESS  read-only
    STATUS      current
    DESCRIPTION "Number of failed CCA Terminate received with 5xx error"
    ::= { affirmedServiceconstructInterfaceAaaGroupDiameterStatisticsChassisLevelPeerDiameterInterfaceTypeEntry 133 }

affirmedServiceconstructInterfaceAaaGroupDiameterStatisticsChassisLevelPeerDiameterInterfaceTypeNumAuthLifetmrInitAARAttmpted OBJECT-TYPE
    SYNTAX      ConfdString
    MAX-ACCESS  read-only
    STATUS      current
    DESCRIPTION "Number of Authorization-Lifetime timer Initiated AAR attempts made"
    ::= { affirmedServiceconstructInterfaceAaaGroupDiameterStatisticsChassisLevelPeerDiameterInterfaceTypeEntry 134 }

affirmedServiceconstructInterfaceAaaGroupDiameterStatisticsChassisLevelPeerDiameterInterfaceTypeNumAuthLifetimerInitAARSuccess OBJECT-TYPE
    SYNTAX      ConfdString
    MAX-ACCESS  read-only
    STATUS      current
    DESCRIPTION "Number of Authorization-Lifetime timer Initiated AAR success"
    ::= { affirmedServiceconstructInterfaceAaaGroupDiameterStatisticsChassisLevelPeerDiameterInterfaceTypeEntry 135 }

affirmedServiceconstructInterfaceAaaGroupDiameterStatisticsChassisLevelPeerDiameterInterfaceTypeNumAuthLifetimerInitAARFailure OBJECT-TYPE
    SYNTAX      ConfdString
    MAX-ACCESS  read-only
    STATUS      current
    DESCRIPTION "Number of Authorization-Lifetime timer Initiated AAR failure"
    ::= { affirmedServiceconstructInterfaceAaaGroupDiameterStatisticsChassisLevelPeerDiameterInterfaceTypeEntry 136 }

affirmedServiceconstructInterfaceAaaGroupDiameterStatisticsChassisLevelPeerDiameterInterfaceTypeNumAuthLifetimerInitAARTimeout OBJECT-TYPE
    SYNTAX      ConfdString
    MAX-ACCESS  read-only
    STATUS      current
    DESCRIPTION "Number of Authorization-Lifetime timer Initiated AAR attempts that timed out"
    ::= { affirmedServiceconstructInterfaceAaaGroupDiameterStatisticsChassisLevelPeerDiameterInterfaceTypeEntry 137 }

affirmedServiceconstructInterfaceAaaGroupDiameterStatisticsChassisLevelPeerDiameterInterfaceTypeNumAuthLifetmrInitAAARxFirstAt OBJECT-TYPE
    SYNTAX      ConfdString
    MAX-ACCESS  read-only
    STATUS      current
    DESCRIPTION "Number of Authorization-Lifetime timer Initiated AAR requests for which response was received when first transmitted "
    ::= { affirmedServiceconstructInterfaceAaaGroupDiameterStatisticsChassisLevelPeerDiameterInterfaceTypeEntry 138 }

affirmedServiceconstructInterfaceAaaGroupDiameterStatisticsChassisLevelPeerDiameterInterfaceTypeNumAuthLifetmrInitAAARxReTx OBJECT-TYPE
    SYNTAX      ConfdString
    MAX-ACCESS  read-only
    STATUS      current
    DESCRIPTION "Number of Authorization-Lifetime timer Initiated AAR Requests for which response was received when message was retransmitted"
    ::= { affirmedServiceconstructInterfaceAaaGroupDiameterStatisticsChassisLevelPeerDiameterInterfaceTypeEntry 139 }

affirmedServiceconstructInterfaceAaaGroupDiameterStatisticsChassisLevelPeerDiameterInterfaceTypeNumAuthGraceTmrInitAARAtmpted OBJECT-TYPE
    SYNTAX      ConfdString
    MAX-ACCESS  read-only
    STATUS      current
    DESCRIPTION "Number of Auth-Grace-Period timer Initiated AAR attempts made"
    ::= { affirmedServiceconstructInterfaceAaaGroupDiameterStatisticsChassisLevelPeerDiameterInterfaceTypeEntry 140 }

affirmedServiceconstructInterfaceAaaGroupDiameterStatisticsChassisLevelPeerDiameterInterfaceTypeNumAuthGraceTmrInitAARSuccess OBJECT-TYPE
    SYNTAX      ConfdString
    MAX-ACCESS  read-only
    STATUS      current
    DESCRIPTION "Number of Auth-Grace-Period timer Initiated AAR success"
    ::= { affirmedServiceconstructInterfaceAaaGroupDiameterStatisticsChassisLevelPeerDiameterInterfaceTypeEntry 141 }

affirmedServiceconstructInterfaceAaaGroupDiameterStatisticsChassisLevelPeerDiameterInterfaceTypeNumAuthGraceTmrInitAARFailure OBJECT-TYPE
    SYNTAX      ConfdString
    MAX-ACCESS  read-only
    STATUS      current
    DESCRIPTION "Number of Auth-Grace-Period timer Initiated AAR failure"
    ::= { affirmedServiceconstructInterfaceAaaGroupDiameterStatisticsChassisLevelPeerDiameterInterfaceTypeEntry 142 }

affirmedServiceconstructInterfaceAaaGroupDiameterStatisticsChassisLevelPeerDiameterInterfaceTypeNumAuthGraceTmrInitAARTimeout OBJECT-TYPE
    SYNTAX      ConfdString
    MAX-ACCESS  read-only
    STATUS      current
    DESCRIPTION "Number of Auth-Grace-Period timer Initiated AAR attempts that timed out"
    ::= { affirmedServiceconstructInterfaceAaaGroupDiameterStatisticsChassisLevelPeerDiameterInterfaceTypeEntry 143 }

affirmedServiceconstructInterfaceAaaGroupDiameterStatisticsChassisLevelPeerDiameterInterfaceTypeNumAuthGraceTmrInitAAARxFstAt OBJECT-TYPE
    SYNTAX      ConfdString
    MAX-ACCESS  read-only
    STATUS      current
    DESCRIPTION "Number of Auth-Grace-Period timer Initiated AAR requests for which response was received when first transmitted "
    ::= { affirmedServiceconstructInterfaceAaaGroupDiameterStatisticsChassisLevelPeerDiameterInterfaceTypeEntry 144 }

affirmedServiceconstructInterfaceAaaGroupDiameterStatisticsChassisLevelPeerDiameterInterfaceTypeNumAuthGraceTmrInitAAARxReTx OBJECT-TYPE
    SYNTAX      ConfdString
    MAX-ACCESS  read-only
    STATUS      current
    DESCRIPTION "Number of Auth-Grace-Period timer Initiated AAR Requests for which response was received when message was retransmitted"
    ::= { affirmedServiceconstructInterfaceAaaGroupDiameterStatisticsChassisLevelPeerDiameterInterfaceTypeEntry 145 }

affirmedServiceconstructInterfaceAaaGroupDiameterStatisticsChassisLevelPeerDiameterInterfaceTypeNumACRStartTimeout OBJECT-TYPE
    SYNTAX      ConfdString
    MAX-ACCESS  read-only
    STATUS      current
    DESCRIPTION "Number of ACR Start Timeouts"
    ::= { affirmedServiceconstructInterfaceAaaGroupDiameterStatisticsChassisLevelPeerDiameterInterfaceTypeEntry 146 }

affirmedServiceconstructInterfaceAaaGroupDiameterStatisticsChassisLevelPeerDiameterInterfaceTypeNumACRStartAborted OBJECT-TYPE
    SYNTAX      ConfdString
    MAX-ACCESS  read-only
    STATUS      current
    DESCRIPTION "Number of ACR Start Requests Aborted due to response received from another peer"
    ::= { affirmedServiceconstructInterfaceAaaGroupDiameterStatisticsChassisLevelPeerDiameterInterfaceTypeEntry 147 }

affirmedServiceconstructInterfaceAaaGroupDiameterStatisticsChassisLevelPeerDiameterInterfaceTypeNumACRStartDelayedSuccess OBJECT-TYPE
    SYNTAX      ConfdString
    MAX-ACCESS  read-only
    STATUS      current
    DESCRIPTION "Number of ACR Start Success Responses received late - transaction was completed or the request was sent to a different server"
    ::= { affirmedServiceconstructInterfaceAaaGroupDiameterStatisticsChassisLevelPeerDiameterInterfaceTypeEntry 148 }

affirmedServiceconstructInterfaceAaaGroupDiameterStatisticsChassisLevelPeerDiameterInterfaceTypeNumACRStartDelayedFailure OBJECT-TYPE
    SYNTAX      ConfdString
    MAX-ACCESS  read-only
    STATUS      current
    DESCRIPTION "Number of ACR Start Failure Responses received late - transaction was completed or the request was sent to a different server"
    ::= { affirmedServiceconstructInterfaceAaaGroupDiameterStatisticsChassisLevelPeerDiameterInterfaceTypeEntry 149 }

affirmedServiceconstructInterfaceAaaGroupDiameterStatisticsChassisLevelPeerDiameterInterfaceTypeNumACRStartDropped OBJECT-TYPE
    SYNTAX      ConfdString
    MAX-ACCESS  read-only
    STATUS      current
    DESCRIPTION "Number of ACR Start Requests Droppedr"
    ::= { affirmedServiceconstructInterfaceAaaGroupDiameterStatisticsChassisLevelPeerDiameterInterfaceTypeEntry 150 }

affirmedServiceconstructInterfaceAaaGroupDiameterStatisticsChassisLevelPeerDiameterInterfaceTypeNumACRStartWriteToDisk OBJECT-TYPE
    SYNTAX      ConfdString
    MAX-ACCESS  read-only
    STATUS      current
    DESCRIPTION "Number of ACR Start write to disk after failed to send to OFCS Server"
    ::= { affirmedServiceconstructInterfaceAaaGroupDiameterStatisticsChassisLevelPeerDiameterInterfaceTypeEntry 151 }

affirmedServiceconstructInterfaceAaaGroupDiameterStatisticsChassisLevelPeerDiameterInterfaceTypeNumACRInterimTimeout OBJECT-TYPE
    SYNTAX      ConfdString
    MAX-ACCESS  read-only
    STATUS      current
    DESCRIPTION "Number of ACR Interim Timeouts"
    ::= { affirmedServiceconstructInterfaceAaaGroupDiameterStatisticsChassisLevelPeerDiameterInterfaceTypeEntry 152 }

affirmedServiceconstructInterfaceAaaGroupDiameterStatisticsChassisLevelPeerDiameterInterfaceTypeNumACRInterimAborted OBJECT-TYPE
    SYNTAX      ConfdString
    MAX-ACCESS  read-only
    STATUS      current
    DESCRIPTION "Number of ACR Interim Requests Aborted due to response received from another peer"
    ::= { affirmedServiceconstructInterfaceAaaGroupDiameterStatisticsChassisLevelPeerDiameterInterfaceTypeEntry 153 }

affirmedServiceconstructInterfaceAaaGroupDiameterStatisticsChassisLevelPeerDiameterInterfaceTypeNumACRInterimDelayedSuccess OBJECT-TYPE
    SYNTAX      ConfdString
    MAX-ACCESS  read-only
    STATUS      current
    DESCRIPTION "Number of ACR Interim Success Responses received late - transaction was completed or the request was sent to a different server"
    ::= { affirmedServiceconstructInterfaceAaaGroupDiameterStatisticsChassisLevelPeerDiameterInterfaceTypeEntry 154 }

affirmedServiceconstructInterfaceAaaGroupDiameterStatisticsChassisLevelPeerDiameterInterfaceTypeNumACRInterimDelayedFailure OBJECT-TYPE
    SYNTAX      ConfdString
    MAX-ACCESS  read-only
    STATUS      current
    DESCRIPTION "Number of ACR Interim Failure Responses received late - transaction was completed or the request was sent to a different server"
    ::= { affirmedServiceconstructInterfaceAaaGroupDiameterStatisticsChassisLevelPeerDiameterInterfaceTypeEntry 155 }

affirmedServiceconstructInterfaceAaaGroupDiameterStatisticsChassisLevelPeerDiameterInterfaceTypeNumACRInterimDropped OBJECT-TYPE
    SYNTAX      ConfdString
    MAX-ACCESS  read-only
    STATUS      current
    DESCRIPTION "Number of ACR Interim Requests Droppedr"
    ::= { affirmedServiceconstructInterfaceAaaGroupDiameterStatisticsChassisLevelPeerDiameterInterfaceTypeEntry 156 }

affirmedServiceconstructInterfaceAaaGroupDiameterStatisticsChassisLevelPeerDiameterInterfaceTypeNumACRInterimWriteToDisk OBJECT-TYPE
    SYNTAX      ConfdString
    MAX-ACCESS  read-only
    STATUS      current
    DESCRIPTION "Number of ACR Interim write to disk after failed to send to OFCS Server"
    ::= { affirmedServiceconstructInterfaceAaaGroupDiameterStatisticsChassisLevelPeerDiameterInterfaceTypeEntry 157 }

affirmedServiceconstructInterfaceAaaGroupDiameterStatisticsChassisLevelPeerDiameterInterfaceTypeNumACRStopTimeout OBJECT-TYPE
    SYNTAX      ConfdString
    MAX-ACCESS  read-only
    STATUS      current
    DESCRIPTION "Number of ACR Stop Timeouts"
    ::= { affirmedServiceconstructInterfaceAaaGroupDiameterStatisticsChassisLevelPeerDiameterInterfaceTypeEntry 158 }

affirmedServiceconstructInterfaceAaaGroupDiameterStatisticsChassisLevelPeerDiameterInterfaceTypeNumACRStopAborted OBJECT-TYPE
    SYNTAX      ConfdString
    MAX-ACCESS  read-only
    STATUS      current
    DESCRIPTION "Number of ACR Stop Requests Aborted due to response received from another peer"
    ::= { affirmedServiceconstructInterfaceAaaGroupDiameterStatisticsChassisLevelPeerDiameterInterfaceTypeEntry 159 }

affirmedServiceconstructInterfaceAaaGroupDiameterStatisticsChassisLevelPeerDiameterInterfaceTypeNumACRStopDelayedSuccess OBJECT-TYPE
    SYNTAX      ConfdString
    MAX-ACCESS  read-only
    STATUS      current
    DESCRIPTION "Number of ACR Stop Success Responses received late - transaction was completed or the request was sent to a different server"
    ::= { affirmedServiceconstructInterfaceAaaGroupDiameterStatisticsChassisLevelPeerDiameterInterfaceTypeEntry 160 }

affirmedServiceconstructInterfaceAaaGroupDiameterStatisticsChassisLevelPeerDiameterInterfaceTypeNumACRStopDelayedFailure OBJECT-TYPE
    SYNTAX      ConfdString
    MAX-ACCESS  read-only
    STATUS      current
    DESCRIPTION "Number of ACR Stop Failure Responses received late - transaction was completed or the request was sent to a different server"
    ::= { affirmedServiceconstructInterfaceAaaGroupDiameterStatisticsChassisLevelPeerDiameterInterfaceTypeEntry 161 }

affirmedServiceconstructInterfaceAaaGroupDiameterStatisticsChassisLevelPeerDiameterInterfaceTypeNumACRStopDropped OBJECT-TYPE
    SYNTAX      ConfdString
    MAX-ACCESS  read-only
    STATUS      current
    DESCRIPTION "Number of ACR Stop Requests Droppedr"
    ::= { affirmedServiceconstructInterfaceAaaGroupDiameterStatisticsChassisLevelPeerDiameterInterfaceTypeEntry 162 }

affirmedServiceconstructInterfaceAaaGroupDiameterStatisticsChassisLevelPeerDiameterInterfaceTypeNumACRStopWriteToDisk OBJECT-TYPE
    SYNTAX      ConfdString
    MAX-ACCESS  read-only
    STATUS      current
    DESCRIPTION "Number of ACR Stop write to disk after failed to send to OFCS Server"
    ::= { affirmedServiceconstructInterfaceAaaGroupDiameterStatisticsChassisLevelPeerDiameterInterfaceTypeEntry 163 }

affirmedServiceconstructInterfaceAaaGroupDiameterStatisticsChassisLevelPeerDiameterInterfaceTypeNumACREventTimeout OBJECT-TYPE
    SYNTAX      ConfdString
    MAX-ACCESS  read-only
    STATUS      current
    DESCRIPTION "Number of ACR Event Timeouts"
    ::= { affirmedServiceconstructInterfaceAaaGroupDiameterStatisticsChassisLevelPeerDiameterInterfaceTypeEntry 164 }

affirmedServiceconstructInterfaceAaaGroupDiameterStatisticsChassisLevelPeerDiameterInterfaceTypeNumACREventAborted OBJECT-TYPE
    SYNTAX      ConfdString
    MAX-ACCESS  read-only
    STATUS      current
    DESCRIPTION "Number of ACR Event Requests Aborted due to response received from another peer"
    ::= { affirmedServiceconstructInterfaceAaaGroupDiameterStatisticsChassisLevelPeerDiameterInterfaceTypeEntry 165 }

affirmedServiceconstructInterfaceAaaGroupDiameterStatisticsChassisLevelPeerDiameterInterfaceTypeNumACREventDelayedSuccess OBJECT-TYPE
    SYNTAX      ConfdString
    MAX-ACCESS  read-only
    STATUS      current
    DESCRIPTION "Number of ACR Event Success Responses received late - transaction was completed or the request was sent to a different server"
    ::= { affirmedServiceconstructInterfaceAaaGroupDiameterStatisticsChassisLevelPeerDiameterInterfaceTypeEntry 166 }

affirmedServiceconstructInterfaceAaaGroupDiameterStatisticsChassisLevelPeerDiameterInterfaceTypeNumACREventDelayedFailure OBJECT-TYPE
    SYNTAX      ConfdString
    MAX-ACCESS  read-only
    STATUS      current
    DESCRIPTION "Number of ACR Event Failure Responses received late - transaction was completed or the request was sent to a different server"
    ::= { affirmedServiceconstructInterfaceAaaGroupDiameterStatisticsChassisLevelPeerDiameterInterfaceTypeEntry 167 }

affirmedServiceconstructInterfaceAaaGroupDiameterStatisticsChassisLevelPeerDiameterInterfaceTypeNumACREventDropped OBJECT-TYPE
    SYNTAX      ConfdString
    MAX-ACCESS  read-only
    STATUS      current
    DESCRIPTION "Number of ACR Event Requests Droppedr"
    ::= { affirmedServiceconstructInterfaceAaaGroupDiameterStatisticsChassisLevelPeerDiameterInterfaceTypeEntry 168 }

affirmedServiceconstructInterfaceAaaGroupDiameterStatisticsChassisLevelPeerDiameterInterfaceTypeNumACREventWriteToDisk OBJECT-TYPE
    SYNTAX      ConfdString
    MAX-ACCESS  read-only
    STATUS      current
    DESCRIPTION "Number of ACR Event write to disk after failed to send to OFCS Server"
    ::= { affirmedServiceconstructInterfaceAaaGroupDiameterStatisticsChassisLevelPeerDiameterInterfaceTypeEntry 169 }

affirmedServiceconstructInterfaceAaaGroupDiameterStatisticsChassisLevelPeerDiameterInterfaceTypeNumACRWriteToDiskFailure OBJECT-TYPE
    SYNTAX      ConfdString
    MAX-ACCESS  read-only
    STATUS      current
    DESCRIPTION "Number of ACR write to disk Failure"
    ::= { affirmedServiceconstructInterfaceAaaGroupDiameterStatisticsChassisLevelPeerDiameterInterfaceTypeEntry 170 }

affirmedServiceconstructInterfaceAaaGroupDiameterStatisticsChassisLevelPeerDiameterInterfaceTypeNumCCREventTx OBJECT-TYPE
    SYNTAX      ConfdString
    MAX-ACCESS  read-only
    STATUS      current
    DESCRIPTION "Number of CCR Event-Request has been transmitted"
    ::= { affirmedServiceconstructInterfaceAaaGroupDiameterStatisticsChassisLevelPeerDiameterInterfaceTypeEntry 171 }

affirmedServiceconstructInterfaceAaaGroupDiameterStatisticsChassisLevelPeerDiameterInterfaceTypeNumCCAEventRx OBJECT-TYPE
    SYNTAX      ConfdString
    MAX-ACCESS  read-only
    STATUS      current
    DESCRIPTION "Number of CCA Event-Request has been received"
    ::= { affirmedServiceconstructInterfaceAaaGroupDiameterStatisticsChassisLevelPeerDiameterInterfaceTypeEntry 172 }

affirmedServiceconstructInterfaceAaaGroupDiameterStatisticsChassisLevelPeerDiameterInterfaceTypeNumCCREventTimeout OBJECT-TYPE
    SYNTAX      ConfdString
    MAX-ACCESS  read-only
    STATUS      current
    DESCRIPTION "Number of CCR Event-Request has been timed out"
    ::= { affirmedServiceconstructInterfaceAaaGroupDiameterStatisticsChassisLevelPeerDiameterInterfaceTypeEntry 173 }

affirmedServiceconstructInterfaceAaaGroupDiameterStatisticsChassisLevelPeerDiameterInterfaceTypeNumSTRRetransmission OBJECT-TYPE
    SYNTAX      ConfdString
    MAX-ACCESS  read-only
    STATUS      current
    DESCRIPTION "Number of STR retransmits"
    ::= { affirmedServiceconstructInterfaceAaaGroupDiameterStatisticsChassisLevelPeerDiameterInterfaceTypeEntry 174 }

affirmedServiceconstructInterfaceAaaGroupDiameterStatisticsChassisLevelPeerDiameterInterfaceTypeNumDERRetransmission OBJECT-TYPE
    SYNTAX      ConfdString
    MAX-ACCESS  read-only
    STATUS      current
    DESCRIPTION "Number of initial authentication DER retransmits"
    ::= { affirmedServiceconstructInterfaceAaaGroupDiameterStatisticsChassisLevelPeerDiameterInterfaceTypeEntry 175 }

affirmedServiceconstructInterfaceAaaGroupDiameterStatisticsChassisLevelPeerDiameterInterfaceTypeNumCCAPendingTransaction OBJECT-TYPE
    SYNTAX      ConfdString
    MAX-ACCESS  read-only
    STATUS      current
    DESCRIPTION "Number of CCA Received with Experimental Result Code Pending Transaction"
    ::= { affirmedServiceconstructInterfaceAaaGroupDiameterStatisticsChassisLevelPeerDiameterInterfaceTypeEntry 176 }

affirmedServiceconstructInterfaceAaaGroupDiameterStatisticsChassisLevelPeerDiameterInterfaceTypeNumRaaPendingTransaction OBJECT-TYPE
    SYNTAX      Unsigned32
    MAX-ACCESS  read-only
    STATUS      current
    DESCRIPTION "Number of RAA with Experimental Result Code Pending Transaction"
    ::= { affirmedServiceconstructInterfaceAaaGroupDiameterStatisticsChassisLevelPeerDiameterInterfaceTypeEntry 177 }

affirmedServiceconstructInterfaceAaaGroupDiameterStatisticsChassisLevelPeerDiameterInterfaceTypeNumSTRDropByPoc OBJECT-TYPE
    SYNTAX      ConfdString
    MAX-ACCESS  read-only
    STATUS      current
    DESCRIPTION "Number of STR Requests are not sent as a result of peer overload control"
    ::= { affirmedServiceconstructInterfaceAaaGroupDiameterStatisticsChassisLevelPeerDiameterInterfaceTypeEntry 178 }

affirmedServiceconstructInterfaceAaaGroupDiameterStatisticsChassisLevelPeerDiameterInterfaceTypeNumSTRRedirect OBJECT-TYPE
    SYNTAX      ConfdString
    MAX-ACCESS  read-only
    STATUS      current
    DESCRIPTION "Number of STR Requests are redirected"
    ::= { affirmedServiceconstructInterfaceAaaGroupDiameterStatisticsChassisLevelPeerDiameterInterfaceTypeEntry 179 }

affirmedServiceconstructInterfaceAaaGroupDiameterStatisticsChassisLevelPeerDiameterInterfaceTypeNumRARInitAARDropByPoc OBJECT-TYPE
    SYNTAX      ConfdString
    MAX-ACCESS  read-only
    STATUS      current
    DESCRIPTION "Number of RAR Initiated AAR Requests are not sent as a result of peer overload control"
    ::= { affirmedServiceconstructInterfaceAaaGroupDiameterStatisticsChassisLevelPeerDiameterInterfaceTypeEntry 180 }

affirmedServiceconstructInterfaceAaaGroupDiameterStatisticsChassisLevelPeerDiameterInterfaceTypeNumRARInitAARRedirect OBJECT-TYPE
    SYNTAX      ConfdString
    MAX-ACCESS  read-only
    STATUS      current
    DESCRIPTION "Number of RAR Initiated AAR Requests are redirected"
    ::= { affirmedServiceconstructInterfaceAaaGroupDiameterStatisticsChassisLevelPeerDiameterInterfaceTypeEntry 181 }

affirmedServiceconstructInterfaceAaaGroupDiameterStatisticsChassisLevelPeerDiameterInterfaceTypeNumDERInitialDropByPoc OBJECT-TYPE
    SYNTAX      ConfdString
    MAX-ACCESS  read-only
    STATUS      current
    DESCRIPTION "Number of initial authentication DER requests are not sent as a result of peer overload control"
    ::= { affirmedServiceconstructInterfaceAaaGroupDiameterStatisticsChassisLevelPeerDiameterInterfaceTypeEntry 182 }

affirmedServiceconstructInterfaceAaaGroupDiameterStatisticsChassisLevelPeerDiameterInterfaceTypeNumDERInitialRedirect OBJECT-TYPE
    SYNTAX      ConfdString
    MAX-ACCESS  read-only
    STATUS      current
    DESCRIPTION "Number of initial authentication DER requests are redirected"
    ::= { affirmedServiceconstructInterfaceAaaGroupDiameterStatisticsChassisLevelPeerDiameterInterfaceTypeEntry 183 }

affirmedServiceconstructInterfaceAaaGroupDiameterStatisticsChassisLevelPeerDiameterInterfaceTypeNumDERReAuthDropByPoc OBJECT-TYPE
    SYNTAX      ConfdString
    MAX-ACCESS  read-only
    STATUS      current
    DESCRIPTION "Number of re-authentication DER requests are not sent as a result of peer overload control"
    ::= { affirmedServiceconstructInterfaceAaaGroupDiameterStatisticsChassisLevelPeerDiameterInterfaceTypeEntry 184 }

affirmedServiceconstructInterfaceAaaGroupDiameterStatisticsChassisLevelPeerDiameterInterfaceTypeNumDERReAuthRedirect OBJECT-TYPE
    SYNTAX      ConfdString
    MAX-ACCESS  read-only
    STATUS      current
    DESCRIPTION "Number of r-authentication DER requests are redirected"
    ::= { affirmedServiceconstructInterfaceAaaGroupDiameterStatisticsChassisLevelPeerDiameterInterfaceTypeEntry 185 }

affirmedServiceconstructInterfaceAaaGroupDiameterStatisticsChassisLevelPeerDiameterInterfaceTypeNumAuthLifetimerInitAARDropByPoc OBJECT-TYPE
    SYNTAX      ConfdString
    MAX-ACCESS  read-only
    STATUS      current
    DESCRIPTION "Number of Authorization-Lifetime timer Initiated AAR Requests are not sent as a result of peer overload control"
    ::= { affirmedServiceconstructInterfaceAaaGroupDiameterStatisticsChassisLevelPeerDiameterInterfaceTypeEntry 186 }

affirmedServiceconstructInterfaceAaaGroupDiameterStatisticsChassisLevelPeerDiameterInterfaceTypeNumAuthLifetimerInitAARRedirect OBJECT-TYPE
    SYNTAX      ConfdString
    MAX-ACCESS  read-only
    STATUS      current
    DESCRIPTION "Number of Authorization-Lifetime timer Initiated AAR Requests are redirected"
    ::= { affirmedServiceconstructInterfaceAaaGroupDiameterStatisticsChassisLevelPeerDiameterInterfaceTypeEntry 187 }

affirmedServiceconstructInterfaceAaaGroupDiameterStatisticsChassisLevelPeerDiameterInterfaceTypeNumAARAborted OBJECT-TYPE
    SYNTAX      ConfdString
    MAX-ACCESS  read-only
    STATUS      current
    DESCRIPTION "Number of AAR attempts that were aborted due to response received from another peer"
    ::= { affirmedServiceconstructInterfaceAaaGroupDiameterStatisticsChassisLevelPeerDiameterInterfaceTypeEntry 188 }

affirmedServiceconstructInterfaceAaaGroupDiameterStatisticsChassisLevelPeerDiameterInterfaceTypeNumRaaSendFailure OBJECT-TYPE
    SYNTAX      Unsigned32
    MAX-ACCESS  read-only
    STATUS      current
    DESCRIPTION "Number of RAA messages failed to send to peer"
    ::= { affirmedServiceconstructInterfaceAaaGroupDiameterStatisticsChassisLevelPeerDiameterInterfaceTypeEntry 189 }

affirmedServiceconstructInterfaceAaaGroupDiameterStatisticsChassisLevelPeerDiameterInterfaceTypeNumRaaFailuresAppUnsupported OBJECT-TYPE
    SYNTAX      Unsigned32
    MAX-ACCESS  read-only
    STATUS      current
    DESCRIPTION "Number of RAA failure messages due to unknown application ID sent to peer"
    ::= { affirmedServiceconstructInterfaceAaaGroupDiameterStatisticsChassisLevelPeerDiameterInterfaceTypeEntry 190 }

affirmedServiceconstructInterfaceAaaGroupDiameterStatisticsChassisLevelPeerDiameterInterfaceTypeNumRaaFailuresAuthRejected OBJECT-TYPE
    SYNTAX      Unsigned32
    MAX-ACCESS  read-only
    STATUS      current
    DESCRIPTION "Number of RAA failure messages due to authentication rejection sent to peer"
    ::= { affirmedServiceconstructInterfaceAaaGroupDiameterStatisticsChassisLevelPeerDiameterInterfaceTypeEntry 191 }

affirmedServiceconstructInterfaceAaaGroupDiameterStatisticsChassisLevelPeerDiameterInterfaceTypeNumCommandUnsupported OBJECT-TYPE
    SYNTAX      ConfdString
    MAX-ACCESS  read-only
    STATUS      current
    DESCRIPTION "Number of received response with result code 3001"
    ::= { affirmedServiceconstructInterfaceAaaGroupDiameterStatisticsChassisLevelPeerDiameterInterfaceTypeEntry 192 }

affirmedServiceconstructInterfaceAaaGroupDiameterStatisticsChassisLevelPeerDiameterInterfaceTypeNumUnableToDeliver OBJECT-TYPE
    SYNTAX      ConfdString
    MAX-ACCESS  read-only
    STATUS      current
    DESCRIPTION "Number of received response with result code 3002"
    ::= { affirmedServiceconstructInterfaceAaaGroupDiameterStatisticsChassisLevelPeerDiameterInterfaceTypeEntry 193 }

affirmedServiceconstructInterfaceAaaGroupDiameterStatisticsChassisLevelPeerDiameterInterfaceTypeNumRealmNotServed OBJECT-TYPE
    SYNTAX      ConfdString
    MAX-ACCESS  read-only
    STATUS      current
    DESCRIPTION "Number of received response with result code 3003"
    ::= { affirmedServiceconstructInterfaceAaaGroupDiameterStatisticsChassisLevelPeerDiameterInterfaceTypeEntry 194 }

affirmedServiceconstructInterfaceAaaGroupDiameterStatisticsChassisLevelPeerDiameterInterfaceTypeNumTooBusy OBJECT-TYPE
    SYNTAX      ConfdString
    MAX-ACCESS  read-only
    STATUS      current
    DESCRIPTION "Number of received response with result code 3004"
    ::= { affirmedServiceconstructInterfaceAaaGroupDiameterStatisticsChassisLevelPeerDiameterInterfaceTypeEntry 195 }

affirmedServiceconstructInterfaceAaaGroupDiameterStatisticsChassisLevelPeerDiameterInterfaceTypeNumLoopDetected OBJECT-TYPE
    SYNTAX      ConfdString
    MAX-ACCESS  read-only
    STATUS      current
    DESCRIPTION "Number of received response with result code 3005"
    ::= { affirmedServiceconstructInterfaceAaaGroupDiameterStatisticsChassisLevelPeerDiameterInterfaceTypeEntry 196 }

affirmedServiceconstructInterfaceAaaGroupDiameterStatisticsChassisLevelPeerDiameterInterfaceTypeNumRedirectIndication OBJECT-TYPE
    SYNTAX      ConfdString
    MAX-ACCESS  read-only
    STATUS      current
    DESCRIPTION "Number of received response with result code 3006"
    ::= { affirmedServiceconstructInterfaceAaaGroupDiameterStatisticsChassisLevelPeerDiameterInterfaceTypeEntry 197 }

affirmedServiceconstructInterfaceAaaGroupDiameterStatisticsChassisLevelPeerDiameterInterfaceTypeNumApplicationUnsupported OBJECT-TYPE
    SYNTAX      ConfdString
    MAX-ACCESS  read-only
    STATUS      current
    DESCRIPTION "Number of received response with result code 3007"
    ::= { affirmedServiceconstructInterfaceAaaGroupDiameterStatisticsChassisLevelPeerDiameterInterfaceTypeEntry 198 }

affirmedServiceconstructInterfaceAaaGroupDiameterStatisticsChassisLevelPeerDiameterInterfaceTypeNumInvalidHdrBits OBJECT-TYPE
    SYNTAX      ConfdString
    MAX-ACCESS  read-only
    STATUS      current
    DESCRIPTION "Number of received response with result code 3008"
    ::= { affirmedServiceconstructInterfaceAaaGroupDiameterStatisticsChassisLevelPeerDiameterInterfaceTypeEntry 199 }

affirmedServiceconstructInterfaceAaaGroupDiameterStatisticsChassisLevelPeerDiameterInterfaceTypeNumInvalidAvpBits OBJECT-TYPE
    SYNTAX      ConfdString
    MAX-ACCESS  read-only
    STATUS      current
    DESCRIPTION "Number of received response with result code 3009"
    ::= { affirmedServiceconstructInterfaceAaaGroupDiameterStatisticsChassisLevelPeerDiameterInterfaceTypeEntry 200 }

affirmedServiceconstructInterfaceAaaGroupDiameterStatisticsChassisLevelPeerDiameterInterfaceTypeNumUnknownPeer OBJECT-TYPE
    SYNTAX      ConfdString
    MAX-ACCESS  read-only
    STATUS      current
    DESCRIPTION "Number of received response with result code 3010"
    ::= { affirmedServiceconstructInterfaceAaaGroupDiameterStatisticsChassisLevelPeerDiameterInterfaceTypeEntry 201 }

affirmedServiceconstructInterfaceAaaGroupDiameterStatisticsChassisLevelPeerDiameterInterfaceTypeNumAuthenticationRejected OBJECT-TYPE
    SYNTAX      ConfdString
    MAX-ACCESS  read-only
    STATUS      current
    DESCRIPTION "Number of received response with result code 4001"
    ::= { affirmedServiceconstructInterfaceAaaGroupDiameterStatisticsChassisLevelPeerDiameterInterfaceTypeEntry 202 }

affirmedServiceconstructInterfaceAaaGroupDiameterStatisticsChassisLevelPeerDiameterInterfaceTypeNumOutOfSpace OBJECT-TYPE
    SYNTAX      ConfdString
    MAX-ACCESS  read-only
    STATUS      current
    DESCRIPTION "Number of received response with result code 4002"
    ::= { affirmedServiceconstructInterfaceAaaGroupDiameterStatisticsChassisLevelPeerDiameterInterfaceTypeEntry 203 }

affirmedServiceconstructInterfaceAaaGroupDiameterStatisticsChassisLevelPeerDiameterInterfaceTypeNumElectionLost OBJECT-TYPE
    SYNTAX      ConfdString
    MAX-ACCESS  read-only
    STATUS      current
    DESCRIPTION "Number of received response with result code 4003"
    ::= { affirmedServiceconstructInterfaceAaaGroupDiameterStatisticsChassisLevelPeerDiameterInterfaceTypeEntry 204 }

affirmedServiceconstructInterfaceAaaGroupDiameterStatisticsChassisLevelPeerDiameterInterfaceTypeNumAvpUnsupported OBJECT-TYPE
    SYNTAX      ConfdString
    MAX-ACCESS  read-only
    STATUS      current
    DESCRIPTION "Total number of received replies with result code 5001"
    ::= { affirmedServiceconstructInterfaceAaaGroupDiameterStatisticsChassisLevelPeerDiameterInterfaceTypeEntry 205 }

affirmedServiceconstructInterfaceAaaGroupDiameterStatisticsChassisLevelPeerDiameterInterfaceTypeNumUnknownSessionId OBJECT-TYPE
    SYNTAX      ConfdString
    MAX-ACCESS  read-only
    STATUS      current
    DESCRIPTION "Total number of received replies with result code 5002"
    ::= { affirmedServiceconstructInterfaceAaaGroupDiameterStatisticsChassisLevelPeerDiameterInterfaceTypeEntry 206 }

affirmedServiceconstructInterfaceAaaGroupDiameterStatisticsChassisLevelPeerDiameterInterfaceTypeNumAuthorizationRejected OBJECT-TYPE
    SYNTAX      ConfdString
    MAX-ACCESS  read-only
    STATUS      current
    DESCRIPTION "Number of received response with result code 5003"
    ::= { affirmedServiceconstructInterfaceAaaGroupDiameterStatisticsChassisLevelPeerDiameterInterfaceTypeEntry 207 }

affirmedServiceconstructInterfaceAaaGroupDiameterStatisticsChassisLevelPeerDiameterInterfaceTypeNumInvalidAvpValue OBJECT-TYPE
    SYNTAX      ConfdString
    MAX-ACCESS  read-only
    STATUS      current
    DESCRIPTION "Number of received response with result code 5004"
    ::= { affirmedServiceconstructInterfaceAaaGroupDiameterStatisticsChassisLevelPeerDiameterInterfaceTypeEntry 208 }

affirmedServiceconstructInterfaceAaaGroupDiameterStatisticsChassisLevelPeerDiameterInterfaceTypeNumMissingAvp OBJECT-TYPE
    SYNTAX      ConfdString
    MAX-ACCESS  read-only
    STATUS      current
    DESCRIPTION "Number of received response with result code 5005"
    ::= { affirmedServiceconstructInterfaceAaaGroupDiameterStatisticsChassisLevelPeerDiameterInterfaceTypeEntry 209 }

affirmedServiceconstructInterfaceAaaGroupDiameterStatisticsChassisLevelPeerDiameterInterfaceTypeNumResourcesExceeded OBJECT-TYPE
    SYNTAX      ConfdString
    MAX-ACCESS  read-only
    STATUS      current
    DESCRIPTION "Total number of receivd replies with result code 5006"
    ::= { affirmedServiceconstructInterfaceAaaGroupDiameterStatisticsChassisLevelPeerDiameterInterfaceTypeEntry 210 }

affirmedServiceconstructInterfaceAaaGroupDiameterStatisticsChassisLevelPeerDiameterInterfaceTypeNumContradictingAvps OBJECT-TYPE
    SYNTAX      ConfdString
    MAX-ACCESS  read-only
    STATUS      current
    DESCRIPTION "Total number of receivd replies with result code 5007"
    ::= { affirmedServiceconstructInterfaceAaaGroupDiameterStatisticsChassisLevelPeerDiameterInterfaceTypeEntry 211 }

affirmedServiceconstructInterfaceAaaGroupDiameterStatisticsChassisLevelPeerDiameterInterfaceTypeNumAvpNotAllowed OBJECT-TYPE
    SYNTAX      ConfdString
    MAX-ACCESS  read-only
    STATUS      current
    DESCRIPTION "Total number of received replies with result code 5008"
    ::= { affirmedServiceconstructInterfaceAaaGroupDiameterStatisticsChassisLevelPeerDiameterInterfaceTypeEntry 212 }

affirmedServiceconstructInterfaceAaaGroupDiameterStatisticsChassisLevelPeerDiameterInterfaceTypeNumOccursTooManyTimes OBJECT-TYPE
    SYNTAX      ConfdString
    MAX-ACCESS  read-only
    STATUS      current
    DESCRIPTION "Total number of received replies with result code 5009"
    ::= { affirmedServiceconstructInterfaceAaaGroupDiameterStatisticsChassisLevelPeerDiameterInterfaceTypeEntry 213 }

affirmedServiceconstructInterfaceAaaGroupDiameterStatisticsChassisLevelPeerDiameterInterfaceTypeNumNoCommonApplication OBJECT-TYPE
    SYNTAX      ConfdString
    MAX-ACCESS  read-only
    STATUS      current
    DESCRIPTION "Total number of received replies with result code 5010"
    ::= { affirmedServiceconstructInterfaceAaaGroupDiameterStatisticsChassisLevelPeerDiameterInterfaceTypeEntry 214 }

affirmedServiceconstructInterfaceAaaGroupDiameterStatisticsChassisLevelPeerDiameterInterfaceTypeNumUnableToComply OBJECT-TYPE
    SYNTAX      ConfdString
    MAX-ACCESS  read-only
    STATUS      current
    DESCRIPTION "Total number of received replies with result code 5012"
    ::= { affirmedServiceconstructInterfaceAaaGroupDiameterStatisticsChassisLevelPeerDiameterInterfaceTypeEntry 215 }

affirmedServiceconstructInterfaceAaaGroupDiameterStatisticsChassisLevelPeerDiameterInterfaceTypeNumInvalidBitInHdr OBJECT-TYPE
    SYNTAX      ConfdString
    MAX-ACCESS  read-only
    STATUS      current
    DESCRIPTION "Total number of received replies with result code 5013"
    ::= { affirmedServiceconstructInterfaceAaaGroupDiameterStatisticsChassisLevelPeerDiameterInterfaceTypeEntry 216 }

affirmedServiceconstructInterfaceAaaGroupDiameterStatisticsChassisLevelPeerDiameterInterfaceTypeNumInvalidAvpLength OBJECT-TYPE
    SYNTAX      ConfdString
    MAX-ACCESS  read-only
    STATUS      current
    DESCRIPTION "Total number of received replies with result code 5014"
    ::= { affirmedServiceconstructInterfaceAaaGroupDiameterStatisticsChassisLevelPeerDiameterInterfaceTypeEntry 217 }

affirmedServiceconstructInterfaceAaaGroupDiameterStatisticsChassisLevelPeerDiameterInterfaceTypeNumInvalidMessageLength OBJECT-TYPE
    SYNTAX      ConfdString
    MAX-ACCESS  read-only
    STATUS      current
    DESCRIPTION "Total number of received replies with result code 5015"
    ::= { affirmedServiceconstructInterfaceAaaGroupDiameterStatisticsChassisLevelPeerDiameterInterfaceTypeEntry 218 }

affirmedServiceconstructInterfaceAaaGroupDiameterStatisticsChassisLevelPeerDiameterInterfaceTypeNumInvalidAvpBitCombo OBJECT-TYPE
    SYNTAX      ConfdString
    MAX-ACCESS  read-only
    STATUS      current
    DESCRIPTION "Total number of received replies with result code 5016"
    ::= { affirmedServiceconstructInterfaceAaaGroupDiameterStatisticsChassisLevelPeerDiameterInterfaceTypeEntry 219 }

affirmedServiceconstructInterfaceAaaGroupDiameterStatisticsChassisLevelPeerDiameterInterfaceTypeNumNoCommonSecurity OBJECT-TYPE
    SYNTAX      ConfdString
    MAX-ACCESS  read-only
    STATUS      current
    DESCRIPTION "Total number of received replies with result code 5017"
    ::= { affirmedServiceconstructInterfaceAaaGroupDiameterStatisticsChassisLevelPeerDiameterInterfaceTypeEntry 220 }

affirmedServiceconstructInterfaceAaaGroupDiameterStatisticsChassisLevelPeerDiameterInterfaceTypeNumUserUnknown OBJECT-TYPE
    SYNTAX      ConfdString
    MAX-ACCESS  read-only
    STATUS      current
    DESCRIPTION "Number of received response with experiment-result code 5001"
    ::= { affirmedServiceconstructInterfaceAaaGroupDiameterStatisticsChassisLevelPeerDiameterInterfaceTypeEntry 221 }

affirmedServiceconstructInterfaceAaaGroupDiameterStatisticsChassisLevelPeerDiameterInterfaceTypeNumRoamingNotAllowed OBJECT-TYPE
    SYNTAX      ConfdString
    MAX-ACCESS  read-only
    STATUS      current
    DESCRIPTION "Total number of received replies with experiment-result code 5004"
    ::= { affirmedServiceconstructInterfaceAaaGroupDiameterStatisticsChassisLevelPeerDiameterInterfaceTypeEntry 222 }

affirmedServiceconstructInterfaceAaaGroupDiameterStatisticsChassisLevelPeerDiameterInterfaceTypeNumIdentityAlreadyRegistered OBJECT-TYPE
    SYNTAX      ConfdString
    MAX-ACCESS  read-only
    STATUS      current
    DESCRIPTION "Total number of received replies with experiment-result code 5005"
    ::= { affirmedServiceconstructInterfaceAaaGroupDiameterStatisticsChassisLevelPeerDiameterInterfaceTypeEntry 223 }

affirmedServiceconstructInterfaceAaaGroupDiameterStatisticsChassisLevelPeerDiameterInterfaceTypeNumOverloadRetryNotAllowed OBJECT-TYPE
    SYNTAX      ConfdString
    MAX-ACCESS  read-only
    STATUS      current
    DESCRIPTION "Total number of received replies with experiment-result code 5198"
    ::= { affirmedServiceconstructInterfaceAaaGroupDiameterStatisticsChassisLevelPeerDiameterInterfaceTypeEntry 224 }

affirmedServiceconstructInterfaceAaaGroupDiameterStatisticsChassisLevelPeerDiameterInterfaceTypeNumUnknownEpsSubscription OBJECT-TYPE
    SYNTAX      ConfdString
    MAX-ACCESS  read-only
    STATUS      current
    DESCRIPTION "Total number of received replies with experiment-result code 5420"
    ::= { affirmedServiceconstructInterfaceAaaGroupDiameterStatisticsChassisLevelPeerDiameterInterfaceTypeEntry 225 }

affirmedServiceconstructInterfaceAaaGroupDiameterStatisticsChassisLevelPeerDiameterInterfaceTypeNumUserNoNonGppSubscription OBJECT-TYPE
    SYNTAX      ConfdString
    MAX-ACCESS  read-only
    STATUS      current
    DESCRIPTION "Total number of received replies with experiment-result code 5450"
    ::= { affirmedServiceconstructInterfaceAaaGroupDiameterStatisticsChassisLevelPeerDiameterInterfaceTypeEntry 226 }

affirmedServiceconstructInterfaceAaaGroupDiameterStatisticsChassisLevelPeerDiameterInterfaceTypeNumUserNoApnSubscription OBJECT-TYPE
    SYNTAX      ConfdString
    MAX-ACCESS  read-only
    STATUS      current
    DESCRIPTION "Total number of received replies with experiment-result code 5451"
    ::= { affirmedServiceconstructInterfaceAaaGroupDiameterStatisticsChassisLevelPeerDiameterInterfaceTypeEntry 227 }

affirmedServiceconstructInterfaceAaaGroupDiameterStatisticsChassisLevelPeerDiameterInterfaceTypeNumRatTypeNotAllowed OBJECT-TYPE
    SYNTAX      ConfdString
    MAX-ACCESS  read-only
    STATUS      current
    DESCRIPTION "Total number of received replies with experiment-result code 5452"
    ::= { affirmedServiceconstructInterfaceAaaGroupDiameterStatisticsChassisLevelPeerDiameterInterfaceTypeEntry 228 }

affirmedServiceconstructInterfaceAaaGroupDiameterStatisticsChassisLevelPeerDiameterInterfaceTypeNumLateOverlappingRequest OBJECT-TYPE
    SYNTAX      ConfdString
    MAX-ACCESS  read-only
    STATUS      current
    DESCRIPTION "Total number of received replies with experiment-result code 5453"
    ::= { affirmedServiceconstructInterfaceAaaGroupDiameterStatisticsChassisLevelPeerDiameterInterfaceTypeEntry 229 }

affirmedServiceconstructInterfaceAaaGroupDiameterStatisticsChassisLevelPeerDiameterInterfaceTypeNumTimedOutRequest OBJECT-TYPE
    SYNTAX      ConfdString
    MAX-ACCESS  read-only
    STATUS      current
    DESCRIPTION "Total number of received replies with experiment-result code 5454"
    ::= { affirmedServiceconstructInterfaceAaaGroupDiameterStatisticsChassisLevelPeerDiameterInterfaceTypeEntry 230 }

affirmedServiceconstructInterfaceAaaGroupDiameterStatisticsChassisLevelPeerDiameterInterfaceTypeNumNIRAttempted OBJECT-TYPE
    SYNTAX      ConfdString
    MAX-ACCESS  read-only
    STATUS      current
    DESCRIPTION "Number of NIR attempts made"
    ::= { affirmedServiceconstructInterfaceAaaGroupDiameterStatisticsChassisLevelPeerDiameterInterfaceTypeEntry 231 }

affirmedServiceconstructInterfaceAaaGroupDiameterStatisticsChassisLevelPeerDiameterInterfaceTypeNumNIRSuccess OBJECT-TYPE
    SYNTAX      ConfdString
    MAX-ACCESS  read-only
    STATUS      current
    DESCRIPTION "Number of NIR success responses received"
    ::= { affirmedServiceconstructInterfaceAaaGroupDiameterStatisticsChassisLevelPeerDiameterInterfaceTypeEntry 232 }

affirmedServiceconstructInterfaceAaaGroupDiameterStatisticsChassisLevelPeerDiameterInterfaceTypeNumNIRFailure OBJECT-TYPE
    SYNTAX      ConfdString
    MAX-ACCESS  read-only
    STATUS      current
    DESCRIPTION "Number of NIR failure responses received"
    ::= { affirmedServiceconstructInterfaceAaaGroupDiameterStatisticsChassisLevelPeerDiameterInterfaceTypeEntry 233 }

affirmedServiceconstructInterfaceAaaGroupDiameterStatisticsChassisLevelPeerDiameterInterfaceTypeNumNIRTimeout OBJECT-TYPE
    SYNTAX      ConfdString
    MAX-ACCESS  read-only
    STATUS      current
    DESCRIPTION "Number of NIR attempts timed out "
    ::= { affirmedServiceconstructInterfaceAaaGroupDiameterStatisticsChassisLevelPeerDiameterInterfaceTypeEntry 234 }

affirmedServiceconstructInterfaceAaaGroupDiameterStatisticsChassisLevelPeerDiameterInterfaceTypeNumNIRAborted OBJECT-TYPE
    SYNTAX      ConfdString
    MAX-ACCESS  read-only
    STATUS      current
    DESCRIPTION "Number of NIR attempts aborted"
    ::= { affirmedServiceconstructInterfaceAaaGroupDiameterStatisticsChassisLevelPeerDiameterInterfaceTypeEntry 235 }

affirmedServiceconstructInterfaceAaaGroupDiameterStatisticsChassisLevelPeerDiameterInterfaceTypeNumNIRcvdFirstAttempt OBJECT-TYPE
    SYNTAX      ConfdString
    MAX-ACCESS  read-only
    STATUS      current
    DESCRIPTION "Number of NIA received to the initial NIR request"
    ::= { affirmedServiceconstructInterfaceAaaGroupDiameterStatisticsChassisLevelPeerDiameterInterfaceTypeEntry 236 }

affirmedServiceconstructInterfaceAaaGroupDiameterStatisticsChassisLevelPeerDiameterInterfaceTypeNumNIARcvdReTx OBJECT-TYPE
    SYNTAX      ConfdString
    MAX-ACCESS  read-only
    STATUS      current
    DESCRIPTION "Number of NIA received to the retransmitted NIR request"
    ::= { affirmedServiceconstructInterfaceAaaGroupDiameterStatisticsChassisLevelPeerDiameterInterfaceTypeEntry 237 }

affirmedServiceconstructInterfaceAaaGroupDiameterStatisticsChassisLevelPeerDiameterInterfaceTypeNumNIA3xxx OBJECT-TYPE
    SYNTAX      ConfdString
    MAX-ACCESS  read-only
    STATUS      current
    DESCRIPTION "Number of NIA received with 3xxx result code"
    ::= { affirmedServiceconstructInterfaceAaaGroupDiameterStatisticsChassisLevelPeerDiameterInterfaceTypeEntry 238 }

affirmedServiceconstructInterfaceAaaGroupDiameterStatisticsChassisLevelPeerDiameterInterfaceTypeNumNIA4xxx OBJECT-TYPE
    SYNTAX      ConfdString
    MAX-ACCESS  read-only
    STATUS      current
    DESCRIPTION "Number of NIA received with 4xxx result code"
    ::= { affirmedServiceconstructInterfaceAaaGroupDiameterStatisticsChassisLevelPeerDiameterInterfaceTypeEntry 239 }

affirmedServiceconstructInterfaceAaaGroupDiameterStatisticsChassisLevelPeerDiameterInterfaceTypeNumNIA5xxx OBJECT-TYPE
    SYNTAX      ConfdString
    MAX-ACCESS  read-only
    STATUS      current
    DESCRIPTION "Number of NIA received with 5xxx result code"
    ::= { affirmedServiceconstructInterfaceAaaGroupDiameterStatisticsChassisLevelPeerDiameterInterfaceTypeEntry 240 }

affirmedServiceconstructInterfaceAaaGroupDiameterStatisticsChassisLevelPeerDiameterInterfaceTypeNumNIADelayedSuccess OBJECT-TYPE
    SYNTAX      ConfdString
    MAX-ACCESS  read-only
    STATUS      current
    DESCRIPTION "Number of NIA success received after the request had been re-transmitted to another server"
    ::= { affirmedServiceconstructInterfaceAaaGroupDiameterStatisticsChassisLevelPeerDiameterInterfaceTypeEntry 241 }

affirmedServiceconstructInterfaceAaaGroupDiameterStatisticsChassisLevelPeerDiameterInterfaceTypeNumNIADelayedFailure OBJECT-TYPE
    SYNTAX      ConfdString
    MAX-ACCESS  read-only
    STATUS      current
    DESCRIPTION "Number of NIA failures received after the request had been re-transmitted to another server"
    ::= { affirmedServiceconstructInterfaceAaaGroupDiameterStatisticsChassisLevelPeerDiameterInterfaceTypeEntry 242 }

affirmedServiceconstructInterfaceAaaGroupDiameterStatisticsChassisLevelPeerDiameterInterfaceTypeNumNIADelayed3xxx OBJECT-TYPE
    SYNTAX      ConfdString
    MAX-ACCESS  read-only
    STATUS      current
    DESCRIPTION "Number of NIA received with 3xxx result code after the request had been re-transmitted to another server"
    ::= { affirmedServiceconstructInterfaceAaaGroupDiameterStatisticsChassisLevelPeerDiameterInterfaceTypeEntry 243 }

affirmedServiceconstructInterfaceAaaGroupDiameterStatisticsChassisLevelPeerDiameterInterfaceTypeNumNIADroppedNoProc OBJECT-TYPE
    SYNTAX      ConfdString
    MAX-ACCESS  read-only
    STATUS      current
    DESCRIPTION "Number of NIA dropped due to no matching transaction identifier"
    ::= { affirmedServiceconstructInterfaceAaaGroupDiameterStatisticsChassisLevelPeerDiameterInterfaceTypeEntry 244 }

affirmedServiceconstructInterfaceAaaGroupDiameterStatisticsChassisLevelPeerDiameterInterfaceTypeNumCIRAttempted OBJECT-TYPE
    SYNTAX      ConfdString
    MAX-ACCESS  read-only
    STATUS      current
    DESCRIPTION "Number of CIR attempts made"
    ::= { affirmedServiceconstructInterfaceAaaGroupDiameterStatisticsChassisLevelPeerDiameterInterfaceTypeEntry 245 }

affirmedServiceconstructInterfaceAaaGroupDiameterStatisticsChassisLevelPeerDiameterInterfaceTypeNumCIRSuccess OBJECT-TYPE
    SYNTAX      ConfdString
    MAX-ACCESS  read-only
    STATUS      current
    DESCRIPTION "Number of CIR success responses received"
    ::= { affirmedServiceconstructInterfaceAaaGroupDiameterStatisticsChassisLevelPeerDiameterInterfaceTypeEntry 246 }

affirmedServiceconstructInterfaceAaaGroupDiameterStatisticsChassisLevelPeerDiameterInterfaceTypeNumCIRFailure OBJECT-TYPE
    SYNTAX      ConfdString
    MAX-ACCESS  read-only
    STATUS      current
    DESCRIPTION "Number of CIR failure responses received"
    ::= { affirmedServiceconstructInterfaceAaaGroupDiameterStatisticsChassisLevelPeerDiameterInterfaceTypeEntry 247 }

affirmedServiceconstructInterfaceAaaGroupDiameterStatisticsChassisLevelPeerDiameterInterfaceTypeNumCIRTimeout OBJECT-TYPE
    SYNTAX      ConfdString
    MAX-ACCESS  read-only
    STATUS      current
    DESCRIPTION "Number of CIR attempts timed out"
    ::= { affirmedServiceconstructInterfaceAaaGroupDiameterStatisticsChassisLevelPeerDiameterInterfaceTypeEntry 248 }

affirmedServiceconstructInterfaceAaaGroupDiameterStatisticsChassisLevelPeerDiameterInterfaceTypeNumCIRAborted OBJECT-TYPE
    SYNTAX      ConfdString
    MAX-ACCESS  read-only
    STATUS      current
    DESCRIPTION "Number of CIR attempts aborted"
    ::= { affirmedServiceconstructInterfaceAaaGroupDiameterStatisticsChassisLevelPeerDiameterInterfaceTypeEntry 249 }

affirmedServiceconstructInterfaceAaaGroupDiameterStatisticsChassisLevelPeerDiameterInterfaceTypeNumCIRcvdFirstAttempt OBJECT-TYPE
    SYNTAX      ConfdString
    MAX-ACCESS  read-only
    STATUS      current
    DESCRIPTION "Number of CIA received to the initial CIR request"
    ::= { affirmedServiceconstructInterfaceAaaGroupDiameterStatisticsChassisLevelPeerDiameterInterfaceTypeEntry 250 }

affirmedServiceconstructInterfaceAaaGroupDiameterStatisticsChassisLevelPeerDiameterInterfaceTypeNumCIARcvdReTx OBJECT-TYPE
    SYNTAX      ConfdString
    MAX-ACCESS  read-only
    STATUS      current
    DESCRIPTION "Number of CIA received to the retransmitted CIR request"
    ::= { affirmedServiceconstructInterfaceAaaGroupDiameterStatisticsChassisLevelPeerDiameterInterfaceTypeEntry 251 }

affirmedServiceconstructInterfaceAaaGroupDiameterStatisticsChassisLevelPeerDiameterInterfaceTypeNumCIA3xxx OBJECT-TYPE
    SYNTAX      ConfdString
    MAX-ACCESS  read-only
    STATUS      current
    DESCRIPTION "Number of CIA received with 3xxx result code"
    ::= { affirmedServiceconstructInterfaceAaaGroupDiameterStatisticsChassisLevelPeerDiameterInterfaceTypeEntry 252 }

affirmedServiceconstructInterfaceAaaGroupDiameterStatisticsChassisLevelPeerDiameterInterfaceTypeNumCIA4xxx OBJECT-TYPE
    SYNTAX      ConfdString
    MAX-ACCESS  read-only
    STATUS      current
    DESCRIPTION "Number of CIA received with 4xxx result code"
    ::= { affirmedServiceconstructInterfaceAaaGroupDiameterStatisticsChassisLevelPeerDiameterInterfaceTypeEntry 253 }

affirmedServiceconstructInterfaceAaaGroupDiameterStatisticsChassisLevelPeerDiameterInterfaceTypeNumCIA5xxx OBJECT-TYPE
    SYNTAX      ConfdString
    MAX-ACCESS  read-only
    STATUS      current
    DESCRIPTION "Number of CIA received with 5xxx result code"
    ::= { affirmedServiceconstructInterfaceAaaGroupDiameterStatisticsChassisLevelPeerDiameterInterfaceTypeEntry 254 }

affirmedServiceconstructInterfaceAaaGroupDiameterStatisticsChassisLevelPeerDiameterInterfaceTypeNumCIADelayedSuccess OBJECT-TYPE
    SYNTAX      ConfdString
    MAX-ACCESS  read-only
    STATUS      current
    DESCRIPTION "Number of CIA success received after the request had been re-transmitted to another server"
    ::= { affirmedServiceconstructInterfaceAaaGroupDiameterStatisticsChassisLevelPeerDiameterInterfaceTypeEntry 255 }

affirmedServiceconstructInterfaceAaaGroupDiameterStatisticsChassisLevelPeerDiameterInterfaceTypeNumCIADelayedFailure OBJECT-TYPE
    SYNTAX      ConfdString
    MAX-ACCESS  read-only
    STATUS      current
    DESCRIPTION "Number of CIA failures received after the request had been re-transmitted to another server"
    ::= { affirmedServiceconstructInterfaceAaaGroupDiameterStatisticsChassisLevelPeerDiameterInterfaceTypeEntry 256 }

affirmedServiceconstructInterfaceAaaGroupDiameterStatisticsChassisLevelPeerDiameterInterfaceTypeNumCIADelayed3xxx OBJECT-TYPE
    SYNTAX      ConfdString
    MAX-ACCESS  read-only
    STATUS      current
    DESCRIPTION "Number of CIA received with 3xxx result code after the request had been re-transmitted to another server"
    ::= { affirmedServiceconstructInterfaceAaaGroupDiameterStatisticsChassisLevelPeerDiameterInterfaceTypeEntry 257 }

affirmedServiceconstructInterfaceAaaGroupDiameterStatisticsChassisLevelPeerDiameterInterfaceTypeNumCIADroppedNoProc OBJECT-TYPE
    SYNTAX      ConfdString
    MAX-ACCESS  read-only
    STATUS      current
    DESCRIPTION "Number of CIA dropped due to no matching transaction identifier"
    ::= { affirmedServiceconstructInterfaceAaaGroupDiameterStatisticsChassisLevelPeerDiameterInterfaceTypeEntry 258 }

affirmedServiceconstructInterfaceAaaGroupDiameterStatisticsChassisLevelPeerDiameterInterfaceTypeNumTDRAttempted OBJECT-TYPE
    SYNTAX      ConfdString
    MAX-ACCESS  read-only
    STATUS      current
    DESCRIPTION "Number of TDR attempts made"
    ::= { affirmedServiceconstructInterfaceAaaGroupDiameterStatisticsChassisLevelPeerDiameterInterfaceTypeEntry 259 }

affirmedServiceconstructInterfaceAaaGroupDiameterStatisticsChassisLevelPeerDiameterInterfaceTypeNumTDRSuccess OBJECT-TYPE
    SYNTAX      ConfdString
    MAX-ACCESS  read-only
    STATUS      current
    DESCRIPTION "Number of TDR success responses received"
    ::= { affirmedServiceconstructInterfaceAaaGroupDiameterStatisticsChassisLevelPeerDiameterInterfaceTypeEntry 260 }

affirmedServiceconstructInterfaceAaaGroupDiameterStatisticsChassisLevelPeerDiameterInterfaceTypeNumTDRFailure OBJECT-TYPE
    SYNTAX      ConfdString
    MAX-ACCESS  read-only
    STATUS      current
    DESCRIPTION "Number of TDR failure responses received"
    ::= { affirmedServiceconstructInterfaceAaaGroupDiameterStatisticsChassisLevelPeerDiameterInterfaceTypeEntry 261 }

affirmedServiceconstructInterfaceAaaGroupDiameterStatisticsChassisLevelPeerDiameterInterfaceTypeNumTDRTimeout OBJECT-TYPE
    SYNTAX      ConfdString
    MAX-ACCESS  read-only
    STATUS      current
    DESCRIPTION "Number of TDR attempts timed out"
    ::= { affirmedServiceconstructInterfaceAaaGroupDiameterStatisticsChassisLevelPeerDiameterInterfaceTypeEntry 262 }

affirmedServiceconstructInterfaceAaaGroupDiameterStatisticsChassisLevelPeerDiameterInterfaceTypeNumTDRAborted OBJECT-TYPE
    SYNTAX      ConfdString
    MAX-ACCESS  read-only
    STATUS      current
    DESCRIPTION "Number of TDR attempts aborted"
    ::= { affirmedServiceconstructInterfaceAaaGroupDiameterStatisticsChassisLevelPeerDiameterInterfaceTypeEntry 263 }

affirmedServiceconstructInterfaceAaaGroupDiameterStatisticsChassisLevelPeerDiameterInterfaceTypeNumTDARcvdFirstAttempt OBJECT-TYPE
    SYNTAX      ConfdString
    MAX-ACCESS  read-only
    STATUS      current
    DESCRIPTION "Number of TDA received to the initial request"
    ::= { affirmedServiceconstructInterfaceAaaGroupDiameterStatisticsChassisLevelPeerDiameterInterfaceTypeEntry 264 }

affirmedServiceconstructInterfaceAaaGroupDiameterStatisticsChassisLevelPeerDiameterInterfaceTypeNumTDARcvdReTx OBJECT-TYPE
    SYNTAX      ConfdString
    MAX-ACCESS  read-only
    STATUS      current
    DESCRIPTION "Number of TDA received to the retransmitted TDR request"
    ::= { affirmedServiceconstructInterfaceAaaGroupDiameterStatisticsChassisLevelPeerDiameterInterfaceTypeEntry 265 }

affirmedServiceconstructInterfaceAaaGroupDiameterStatisticsChassisLevelPeerDiameterInterfaceTypeNumTDA3xxx OBJECT-TYPE
    SYNTAX      ConfdString
    MAX-ACCESS  read-only
    STATUS      current
    DESCRIPTION "Number of TDA received with 3xxx result code"
    ::= { affirmedServiceconstructInterfaceAaaGroupDiameterStatisticsChassisLevelPeerDiameterInterfaceTypeEntry 266 }

affirmedServiceconstructInterfaceAaaGroupDiameterStatisticsChassisLevelPeerDiameterInterfaceTypeNumTDA4xxx OBJECT-TYPE
    SYNTAX      ConfdString
    MAX-ACCESS  read-only
    STATUS      current
    DESCRIPTION "Number of TDA received with 4xxx result code"
    ::= { affirmedServiceconstructInterfaceAaaGroupDiameterStatisticsChassisLevelPeerDiameterInterfaceTypeEntry 267 }

affirmedServiceconstructInterfaceAaaGroupDiameterStatisticsChassisLevelPeerDiameterInterfaceTypeNumTDA5xxx OBJECT-TYPE
    SYNTAX      ConfdString
    MAX-ACCESS  read-only
    STATUS      current
    DESCRIPTION "Number of TDA received with 5xxx result code"
    ::= { affirmedServiceconstructInterfaceAaaGroupDiameterStatisticsChassisLevelPeerDiameterInterfaceTypeEntry 268 }

affirmedServiceconstructInterfaceAaaGroupDiameterStatisticsChassisLevelPeerDiameterInterfaceTypeNumTDADroppedNoProc OBJECT-TYPE
    SYNTAX      ConfdString
    MAX-ACCESS  read-only
    STATUS      current
    DESCRIPTION "Number of TDA dropped due to no matching transaction"
    ::= { affirmedServiceconstructInterfaceAaaGroupDiameterStatisticsChassisLevelPeerDiameterInterfaceTypeEntry 269 }

affirmedServiceconstructInterfaceAaaGroupDiameterStatisticsChassisLevelPeerDiameterInterfaceTypeNumCmrCReceived OBJECT-TYPE
    SYNTAX      ConfdString
    MAX-ACCESS  read-only
    STATUS      current
    DESCRIPTION "Number of CMR connection establishment requests received"
    ::= { affirmedServiceconstructInterfaceAaaGroupDiameterStatisticsChassisLevelPeerDiameterInterfaceTypeEntry 270 }

affirmedServiceconstructInterfaceAaaGroupDiameterStatisticsChassisLevelPeerDiameterInterfaceTypeNumCMACSuccess OBJECT-TYPE
    SYNTAX      ConfdString
    MAX-ACCESS  read-only
    STATUS      current
    DESCRIPTION "Number of CMR connection establishment success responses sent"
    ::= { affirmedServiceconstructInterfaceAaaGroupDiameterStatisticsChassisLevelPeerDiameterInterfaceTypeEntry 271 }

affirmedServiceconstructInterfaceAaaGroupDiameterStatisticsChassisLevelPeerDiameterInterfaceTypeNumCMACFailures OBJECT-TYPE
    SYNTAX      ConfdString
    MAX-ACCESS  read-only
    STATUS      current
    DESCRIPTION "Number of CMR connection establishment failure responses sent"
    ::= { affirmedServiceconstructInterfaceAaaGroupDiameterStatisticsChassisLevelPeerDiameterInterfaceTypeEntry 272 }

affirmedServiceconstructInterfaceAaaGroupDiameterStatisticsChassisLevelPeerDiameterInterfaceTypeNumCMACFailuresUnknownSession OBJECT-TYPE
    SYNTAX      ConfdString
    MAX-ACCESS  read-only
    STATUS      current
    DESCRIPTION "Number of CMR connection establishment failures due to unknown session"
    ::= { affirmedServiceconstructInterfaceAaaGroupDiameterStatisticsChassisLevelPeerDiameterInterfaceTypeEntry 273 }

affirmedServiceconstructInterfaceAaaGroupDiameterStatisticsChassisLevelPeerDiameterInterfaceTypeNumCMACFailuresMissingAVP OBJECT-TYPE
    SYNTAX      ConfdString
    MAX-ACCESS  read-only
    STATUS      current
    DESCRIPTION "Number of CMR connection establishment failures due to missing AVPs"
    ::= { affirmedServiceconstructInterfaceAaaGroupDiameterStatisticsChassisLevelPeerDiameterInterfaceTypeEntry 274 }

affirmedServiceconstructInterfaceAaaGroupDiameterStatisticsChassisLevelPeerDiameterInterfaceTypeNumCmrUReceived OBJECT-TYPE
    SYNTAX      ConfdString
    MAX-ACCESS  read-only
    STATUS      current
    DESCRIPTION "Number of CMR connection update requests received"
    ::= { affirmedServiceconstructInterfaceAaaGroupDiameterStatisticsChassisLevelPeerDiameterInterfaceTypeEntry 275 }

affirmedServiceconstructInterfaceAaaGroupDiameterStatisticsChassisLevelPeerDiameterInterfaceTypeNumCMAUSuccess OBJECT-TYPE
    SYNTAX      ConfdString
    MAX-ACCESS  read-only
    STATUS      current
    DESCRIPTION "Number of CMR connection update success responses sent"
    ::= { affirmedServiceconstructInterfaceAaaGroupDiameterStatisticsChassisLevelPeerDiameterInterfaceTypeEntry 276 }

affirmedServiceconstructInterfaceAaaGroupDiameterStatisticsChassisLevelPeerDiameterInterfaceTypeNumCMAUFailures OBJECT-TYPE
    SYNTAX      ConfdString
    MAX-ACCESS  read-only
    STATUS      current
    DESCRIPTION "Number of CMR connection update failure responses sent"
    ::= { affirmedServiceconstructInterfaceAaaGroupDiameterStatisticsChassisLevelPeerDiameterInterfaceTypeEntry 277 }

affirmedServiceconstructInterfaceAaaGroupDiameterStatisticsChassisLevelPeerDiameterInterfaceTypeNumCMAUFailuresUnknownSession OBJECT-TYPE
    SYNTAX      ConfdString
    MAX-ACCESS  read-only
    STATUS      current
    DESCRIPTION "Number of CMR connection update failures due to unknown session"
    ::= { affirmedServiceconstructInterfaceAaaGroupDiameterStatisticsChassisLevelPeerDiameterInterfaceTypeEntry 278 }

affirmedServiceconstructInterfaceAaaGroupDiameterStatisticsChassisLevelPeerDiameterInterfaceTypeNumCMAUFailuresMissingAVP OBJECT-TYPE
    SYNTAX      ConfdString
    MAX-ACCESS  read-only
    STATUS      current
    DESCRIPTION "Number of CMR connection update failures due to missing AVPs"
    ::= { affirmedServiceconstructInterfaceAaaGroupDiameterStatisticsChassisLevelPeerDiameterInterfaceTypeEntry 279 }

affirmedServiceconstructInterfaceAaaGroupDiameterStatisticsChassisLevelPeerDiameterInterfaceTypeNumCmrRReceived OBJECT-TYPE
    SYNTAX      ConfdString
    MAX-ACCESS  read-only
    STATUS      current
    DESCRIPTION "Number of CMR connection release requests received"
    ::= { affirmedServiceconstructInterfaceAaaGroupDiameterStatisticsChassisLevelPeerDiameterInterfaceTypeEntry 280 }

affirmedServiceconstructInterfaceAaaGroupDiameterStatisticsChassisLevelPeerDiameterInterfaceTypeNumCMARSuccess OBJECT-TYPE
    SYNTAX      ConfdString
    MAX-ACCESS  read-only
    STATUS      current
    DESCRIPTION "Number of CMR connection release success responses sent"
    ::= { affirmedServiceconstructInterfaceAaaGroupDiameterStatisticsChassisLevelPeerDiameterInterfaceTypeEntry 281 }

affirmedServiceconstructInterfaceAaaGroupDiameterStatisticsChassisLevelPeerDiameterInterfaceTypeNumCMARFailures OBJECT-TYPE
    SYNTAX      ConfdString
    MAX-ACCESS  read-only
    STATUS      current
    DESCRIPTION "Number of CMR connection release failure responses sent"
    ::= { affirmedServiceconstructInterfaceAaaGroupDiameterStatisticsChassisLevelPeerDiameterInterfaceTypeEntry 282 }

affirmedServiceconstructInterfaceAaaGroupDiameterStatisticsChassisLevelPeerDiameterInterfaceTypeNumCMARFailuresUnknownSession OBJECT-TYPE
    SYNTAX      ConfdString
    MAX-ACCESS  read-only
    STATUS      current
    DESCRIPTION "Number of CMR connection release failures due to unknown session"
    ::= { affirmedServiceconstructInterfaceAaaGroupDiameterStatisticsChassisLevelPeerDiameterInterfaceTypeEntry 283 }

affirmedServiceconstructInterfaceAaaGroupDiameterStatisticsChassisLevelPeerDiameterInterfaceTypeNumCMARFailuresMissingAVP OBJECT-TYPE
    SYNTAX      ConfdString
    MAX-ACCESS  read-only
    STATUS      current
    DESCRIPTION "Number of CMR connection release failures due to missing AVPs"
    ::= { affirmedServiceconstructInterfaceAaaGroupDiameterStatisticsChassisLevelPeerDiameterInterfaceTypeEntry 284 }

affirmedServiceconstructInterfaceAaaGroupDiameterStatisticsChassisLevelPeerDiameterInterfaceTypeNumCMRRScefInitAttempted OBJECT-TYPE
    SYNTAX      ConfdString
    MAX-ACCESS  read-only
    STATUS      current
    DESCRIPTION "Number of CMR connection release attempts made"
    ::= { affirmedServiceconstructInterfaceAaaGroupDiameterStatisticsChassisLevelPeerDiameterInterfaceTypeEntry 285 }

affirmedServiceconstructInterfaceAaaGroupDiameterStatisticsChassisLevelPeerDiameterInterfaceTypeNumCMRRScefInitSuccess OBJECT-TYPE
    SYNTAX      ConfdString
    MAX-ACCESS  read-only
    STATUS      current
    DESCRIPTION "Number of CMR connection release success responses received"
    ::= { affirmedServiceconstructInterfaceAaaGroupDiameterStatisticsChassisLevelPeerDiameterInterfaceTypeEntry 286 }

affirmedServiceconstructInterfaceAaaGroupDiameterStatisticsChassisLevelPeerDiameterInterfaceTypeNumCMRRScefInitFailure OBJECT-TYPE
    SYNTAX      ConfdString
    MAX-ACCESS  read-only
    STATUS      current
    DESCRIPTION "Number of CMR connection release failure responses received"
    ::= { affirmedServiceconstructInterfaceAaaGroupDiameterStatisticsChassisLevelPeerDiameterInterfaceTypeEntry 287 }

affirmedServiceconstructInterfaceAaaGroupDiameterStatisticsChassisLevelPeerDiameterInterfaceTypeNumCMRRScefInitTimeout OBJECT-TYPE
    SYNTAX      ConfdString
    MAX-ACCESS  read-only
    STATUS      current
    DESCRIPTION "Number of CMR connection release attempts timed out"
    ::= { affirmedServiceconstructInterfaceAaaGroupDiameterStatisticsChassisLevelPeerDiameterInterfaceTypeEntry 288 }

affirmedServiceconstructInterfaceAaaGroupDiameterStatisticsChassisLevelPeerDiameterInterfaceTypeNumCMRRScefInitAborted OBJECT-TYPE
    SYNTAX      ConfdString
    MAX-ACCESS  read-only
    STATUS      current
    DESCRIPTION "Number of CMR connection release attempts aborted"
    ::= { affirmedServiceconstructInterfaceAaaGroupDiameterStatisticsChassisLevelPeerDiameterInterfaceTypeEntry 289 }

affirmedServiceconstructInterfaceAaaGroupDiameterStatisticsChassisLevelPeerDiameterInterfaceTypeNumCMARScefInitRcvdFirstAttempt OBJECT-TYPE
    SYNTAX      ConfdString
    MAX-ACCESS  read-only
    STATUS      current
    DESCRIPTION "Number of CMR connection release responses received to the initial request"
    ::= { affirmedServiceconstructInterfaceAaaGroupDiameterStatisticsChassisLevelPeerDiameterInterfaceTypeEntry 290 }

affirmedServiceconstructInterfaceAaaGroupDiameterStatisticsChassisLevelPeerDiameterInterfaceTypeNumCMARScefInitRcvdReTx OBJECT-TYPE
    SYNTAX      ConfdString
    MAX-ACCESS  read-only
    STATUS      current
    DESCRIPTION "Number of CMR connection release responses received to the retransmitted request"
    ::= { affirmedServiceconstructInterfaceAaaGroupDiameterStatisticsChassisLevelPeerDiameterInterfaceTypeEntry 291 }

affirmedServiceconstructInterfaceAaaGroupDiameterStatisticsChassisLevelPeerDiameterInterfaceTypeNumCMARScefInit3xxx OBJECT-TYPE
    SYNTAX      ConfdString
    MAX-ACCESS  read-only
    STATUS      current
    DESCRIPTION "Number of CMR connection release responses received with 3xxx result code"
    ::= { affirmedServiceconstructInterfaceAaaGroupDiameterStatisticsChassisLevelPeerDiameterInterfaceTypeEntry 292 }

affirmedServiceconstructInterfaceAaaGroupDiameterStatisticsChassisLevelPeerDiameterInterfaceTypeNumCMARScefInit4xxx OBJECT-TYPE
    SYNTAX      ConfdString
    MAX-ACCESS  read-only
    STATUS      current
    DESCRIPTION "Number of CMR Connection Release responses received with 4xxx result code"
    ::= { affirmedServiceconstructInterfaceAaaGroupDiameterStatisticsChassisLevelPeerDiameterInterfaceTypeEntry 293 }

affirmedServiceconstructInterfaceAaaGroupDiameterStatisticsChassisLevelPeerDiameterInterfaceTypeNumCMARScefInit5xxx OBJECT-TYPE
    SYNTAX      ConfdString
    MAX-ACCESS  read-only
    STATUS      current
    DESCRIPTION "Number of CMR Connection Release responses received with 5xxx result code"
    ::= { affirmedServiceconstructInterfaceAaaGroupDiameterStatisticsChassisLevelPeerDiameterInterfaceTypeEntry 294 }

affirmedServiceconstructInterfaceAaaGroupDiameterStatisticsChassisLevelPeerDiameterInterfaceTypeNumCMARScefInitDroppedNoProc OBJECT-TYPE
    SYNTAX      ConfdString
    MAX-ACCESS  read-only
    STATUS      current
    DESCRIPTION "Number of CMR connection release answers dropped due to no matching transaction"
    ::= { affirmedServiceconstructInterfaceAaaGroupDiameterStatisticsChassisLevelPeerDiameterInterfaceTypeEntry 295 }

affirmedServiceconstructInterfaceAaaGroupDiameterStatisticsChassisLevelPeerDiameterInterfaceTypeNumODRReceived OBJECT-TYPE
    SYNTAX      ConfdString
    MAX-ACCESS  read-only
    STATUS      current
    DESCRIPTION "Number of ODR messages received"
    ::= { affirmedServiceconstructInterfaceAaaGroupDiameterStatisticsChassisLevelPeerDiameterInterfaceTypeEntry 296 }

affirmedServiceconstructInterfaceAaaGroupDiameterStatisticsChassisLevelPeerDiameterInterfaceTypeNumODASuccess OBJECT-TYPE
    SYNTAX      ConfdString
    MAX-ACCESS  read-only
    STATUS      current
    DESCRIPTION "Number of ODR success responses sent"
    ::= { affirmedServiceconstructInterfaceAaaGroupDiameterStatisticsChassisLevelPeerDiameterInterfaceTypeEntry 297 }

affirmedServiceconstructInterfaceAaaGroupDiameterStatisticsChassisLevelPeerDiameterInterfaceTypeNumODAFailures OBJECT-TYPE
    SYNTAX      ConfdString
    MAX-ACCESS  read-only
    STATUS      current
    DESCRIPTION "Number of ODR failure responses sent"
    ::= { affirmedServiceconstructInterfaceAaaGroupDiameterStatisticsChassisLevelPeerDiameterInterfaceTypeEntry 298 }

affirmedServiceconstructInterfaceAaaGroupDiameterStatisticsChassisLevelPeerDiameterInterfaceTypeNumODAFailuresUnknownSession OBJECT-TYPE
    SYNTAX      ConfdString
    MAX-ACCESS  read-only
    STATUS      current
    DESCRIPTION "Number of ODR failures due to unknown session"
    ::= { affirmedServiceconstructInterfaceAaaGroupDiameterStatisticsChassisLevelPeerDiameterInterfaceTypeEntry 299 }

affirmedServiceconstructInterfaceAaaGroupDiameterStatisticsChassisLevelPeerDiameterInterfaceTypeNumODAFailuresMissingAVP OBJECT-TYPE
    SYNTAX      ConfdString
    MAX-ACCESS  read-only
    STATUS      current
    DESCRIPTION "Number of ODR failures due to missing AVPs"
    ::= { affirmedServiceconstructInterfaceAaaGroupDiameterStatisticsChassisLevelPeerDiameterInterfaceTypeEntry 300 }

affirmedServiceconstructInterfaceAaaGroupDiameterStatisticsChassisLevelPeerDiameterInterfaceTypeNumODAFailuresUnableToDeliver OBJECT-TYPE
    SYNTAX      ConfdString
    MAX-ACCESS  read-only
    STATUS      current
    DESCRIPTION "Number of ODR failures due to Destination Host in ODR not being found"
    ::= { affirmedServiceconstructInterfaceAaaGroupDiameterStatisticsChassisLevelPeerDiameterInterfaceTypeEntry 301 }

affirmedServiceconstructInterfaceAaaGroupDiameterStatisticsChassisLevelPeerDiameterInterfaceTypeNumRIRReceived OBJECT-TYPE
    SYNTAX      ConfdString
    MAX-ACCESS  read-only
    STATUS      current
    DESCRIPTION "Number of RIR messages received"
    ::= { affirmedServiceconstructInterfaceAaaGroupDiameterStatisticsChassisLevelPeerDiameterInterfaceTypeEntry 302 }

affirmedServiceconstructInterfaceAaaGroupDiameterStatisticsChassisLevelPeerDiameterInterfaceTypeNumRIASuccess OBJECT-TYPE
    SYNTAX      ConfdString
    MAX-ACCESS  read-only
    STATUS      current
    DESCRIPTION "Number of RIR success responses sent"
    ::= { affirmedServiceconstructInterfaceAaaGroupDiameterStatisticsChassisLevelPeerDiameterInterfaceTypeEntry 303 }

affirmedServiceconstructInterfaceAaaGroupDiameterStatisticsChassisLevelPeerDiameterInterfaceTypeNumRIAFailures OBJECT-TYPE
    SYNTAX      ConfdString
    MAX-ACCESS  read-only
    STATUS      current
    DESCRIPTION "Number of RIR failure responses sent"
    ::= { affirmedServiceconstructInterfaceAaaGroupDiameterStatisticsChassisLevelPeerDiameterInterfaceTypeEntry 304 }

affirmedServiceconstructInterfaceAaaGroupDiameterStatisticsChassisLevelPeerDiameterInterfaceTypeNumRIAFailuresUnknownScefRefId OBJECT-TYPE
    SYNTAX      ConfdString
    MAX-ACCESS  read-only
    STATUS      current
    DESCRIPTION "Number of RIR failures due to unknown SCEF Reference Identifier"
    ::= { affirmedServiceconstructInterfaceAaaGroupDiameterStatisticsChassisLevelPeerDiameterInterfaceTypeEntry 305 }

affirmedServiceconstructInterfaceAaaGroupDiameterStatisticsChassisLevelPeerDiameterInterfaceTypeNumRIAFailuresUnknownSession OBJECT-TYPE
    SYNTAX      ConfdString
    MAX-ACCESS  read-only
    STATUS      current
    DESCRIPTION "Number of RIR failures due to context not found"
    ::= { affirmedServiceconstructInterfaceAaaGroupDiameterStatisticsChassisLevelPeerDiameterInterfaceTypeEntry 306 }

affirmedServiceconstructInterfaceAaaGroupDiameterStatisticsChassisLevelPeerDiameterInterfaceTypeNumRIAFailuresMissingAVP OBJECT-TYPE
    SYNTAX      ConfdString
    MAX-ACCESS  read-only
    STATUS      current
    DESCRIPTION "Number of RIR failures due to missing AVPs"
    ::= { affirmedServiceconstructInterfaceAaaGroupDiameterStatisticsChassisLevelPeerDiameterInterfaceTypeEntry 307 }

affirmedServiceconstructInterfaceAaaGroupDiameterStatisticsChassisLevelPeerDiameterInterfaceTypeNumRIAFailuresUnableToDeliver OBJECT-TYPE
    SYNTAX      ConfdString
    MAX-ACCESS  read-only
    STATUS      current
    DESCRIPTION "Number of RIR failures due to Destination Host in RIR not being found"
    ::= { affirmedServiceconstructInterfaceAaaGroupDiameterStatisticsChassisLevelPeerDiameterInterfaceTypeEntry 308 }

affirmedServiceconstructInterfaceAaaGroupDiameterStatisticsChassisLevelPeerDiameterInterfaceTypeNumSIRAttempted OBJECT-TYPE
    SYNTAX      ConfdString
    MAX-ACCESS  read-only
    STATUS      current
    DESCRIPTION "Number of SIR attempts made"
    ::= { affirmedServiceconstructInterfaceAaaGroupDiameterStatisticsChassisLevelPeerDiameterInterfaceTypeEntry 309 }

affirmedServiceconstructInterfaceAaaGroupDiameterStatisticsChassisLevelPeerDiameterInterfaceTypeNumSIRSuccess OBJECT-TYPE
    SYNTAX      ConfdString
    MAX-ACCESS  read-only
    STATUS      current
    DESCRIPTION "Number of SIR success responses received"
    ::= { affirmedServiceconstructInterfaceAaaGroupDiameterStatisticsChassisLevelPeerDiameterInterfaceTypeEntry 310 }

affirmedServiceconstructInterfaceAaaGroupDiameterStatisticsChassisLevelPeerDiameterInterfaceTypeNumSIRFailure OBJECT-TYPE
    SYNTAX      ConfdString
    MAX-ACCESS  read-only
    STATUS      current
    DESCRIPTION "Number of SIR failure responses received"
    ::= { affirmedServiceconstructInterfaceAaaGroupDiameterStatisticsChassisLevelPeerDiameterInterfaceTypeEntry 311 }

affirmedServiceconstructInterfaceAaaGroupDiameterStatisticsChassisLevelPeerDiameterInterfaceTypeNumSIRTimeout OBJECT-TYPE
    SYNTAX      ConfdString
    MAX-ACCESS  read-only
    STATUS      current
    DESCRIPTION "Number of SIR attempts timed out"
    ::= { affirmedServiceconstructInterfaceAaaGroupDiameterStatisticsChassisLevelPeerDiameterInterfaceTypeEntry 312 }

affirmedServiceconstructInterfaceAaaGroupDiameterStatisticsChassisLevelPeerDiameterInterfaceTypeNumSIRAborted OBJECT-TYPE
    SYNTAX      ConfdString
    MAX-ACCESS  read-only
    STATUS      current
    DESCRIPTION "Number of SIR attempts aborted"
    ::= { affirmedServiceconstructInterfaceAaaGroupDiameterStatisticsChassisLevelPeerDiameterInterfaceTypeEntry 313 }

affirmedServiceconstructInterfaceAaaGroupDiameterStatisticsChassisLevelPeerDiameterInterfaceTypeNumSIRcvdFirstAttempt OBJECT-TYPE
    SYNTAX      ConfdString
    MAX-ACCESS  read-only
    STATUS      current
    DESCRIPTION "Number of SIA received to the initial SIR request"
    ::= { affirmedServiceconstructInterfaceAaaGroupDiameterStatisticsChassisLevelPeerDiameterInterfaceTypeEntry 314 }

affirmedServiceconstructInterfaceAaaGroupDiameterStatisticsChassisLevelPeerDiameterInterfaceTypeNumSIARcvdReTx OBJECT-TYPE
    SYNTAX      ConfdString
    MAX-ACCESS  read-only
    STATUS      current
    DESCRIPTION "Number of SIA received to the retransmitted SIR request"
    ::= { affirmedServiceconstructInterfaceAaaGroupDiameterStatisticsChassisLevelPeerDiameterInterfaceTypeEntry 315 }

affirmedServiceconstructInterfaceAaaGroupDiameterStatisticsChassisLevelPeerDiameterInterfaceTypeNumSIA3xxx OBJECT-TYPE
    SYNTAX      ConfdString
    MAX-ACCESS  read-only
    STATUS      current
    DESCRIPTION "Number of SIA received with 3xxx result code"
    ::= { affirmedServiceconstructInterfaceAaaGroupDiameterStatisticsChassisLevelPeerDiameterInterfaceTypeEntry 316 }

affirmedServiceconstructInterfaceAaaGroupDiameterStatisticsChassisLevelPeerDiameterInterfaceTypeNumSIA4xxx OBJECT-TYPE
    SYNTAX      ConfdString
    MAX-ACCESS  read-only
    STATUS      current
    DESCRIPTION "Number of SIA received with 4xxx result code"
    ::= { affirmedServiceconstructInterfaceAaaGroupDiameterStatisticsChassisLevelPeerDiameterInterfaceTypeEntry 317 }

affirmedServiceconstructInterfaceAaaGroupDiameterStatisticsChassisLevelPeerDiameterInterfaceTypeNumSIA5xxx OBJECT-TYPE
    SYNTAX      ConfdString
    MAX-ACCESS  read-only
    STATUS      current
    DESCRIPTION "Number of SIA received with 5xxx result code"
    ::= { affirmedServiceconstructInterfaceAaaGroupDiameterStatisticsChassisLevelPeerDiameterInterfaceTypeEntry 318 }

affirmedServiceconstructInterfaceAaaGroupDiameterStatisticsChassisLevelPeerDiameterInterfaceTypeNumSIADelayedSuccess OBJECT-TYPE
    SYNTAX      ConfdString
    MAX-ACCESS  read-only
    STATUS      current
    DESCRIPTION "Number of SIA success received after the request had been re-transmitted to another server"
    ::= { affirmedServiceconstructInterfaceAaaGroupDiameterStatisticsChassisLevelPeerDiameterInterfaceTypeEntry 319 }

affirmedServiceconstructInterfaceAaaGroupDiameterStatisticsChassisLevelPeerDiameterInterfaceTypeNumSIADelayedFailure OBJECT-TYPE
    SYNTAX      ConfdString
    MAX-ACCESS  read-only
    STATUS      current
    DESCRIPTION "Number of SIA failures received after the request had been re-transmitted to another server"
    ::= { affirmedServiceconstructInterfaceAaaGroupDiameterStatisticsChassisLevelPeerDiameterInterfaceTypeEntry 320 }

affirmedServiceconstructInterfaceAaaGroupDiameterStatisticsChassisLevelPeerDiameterInterfaceTypeNumSIADelayed3xxx OBJECT-TYPE
    SYNTAX      ConfdString
    MAX-ACCESS  read-only
    STATUS      current
    DESCRIPTION "Number of SIA received with 3xxx result code after the request had been re-transmitted to another server"
    ::= { affirmedServiceconstructInterfaceAaaGroupDiameterStatisticsChassisLevelPeerDiameterInterfaceTypeEntry 321 }

affirmedServiceconstructInterfaceAaaGroupDiameterStatisticsChassisLevelPeerDiameterInterfaceTypeNumSIADroppedNoProc OBJECT-TYPE
    SYNTAX      ConfdString
    MAX-ACCESS  read-only
    STATUS      current
    DESCRIPTION "Number of SIA dropped due to no matching transaction identifier"
    ::= { affirmedServiceconstructInterfaceAaaGroupDiameterStatisticsChassisLevelPeerDiameterInterfaceTypeEntry 322 }

affirmedServiceconstructInterfaceAaaGroupDiameterStatisticsChassisLevelPeerDiameterInterfaceTypeNumDTRAttempted OBJECT-TYPE
    SYNTAX      ConfdString
    MAX-ACCESS  read-only
    STATUS      current
    DESCRIPTION "Number of DTR attempts made"
    ::= { affirmedServiceconstructInterfaceAaaGroupDiameterStatisticsChassisLevelPeerDiameterInterfaceTypeEntry 323 }

affirmedServiceconstructInterfaceAaaGroupDiameterStatisticsChassisLevelPeerDiameterInterfaceTypeNumDTRSuccess OBJECT-TYPE
    SYNTAX      ConfdString
    MAX-ACCESS  read-only
    STATUS      current
    DESCRIPTION "Number of DTR success responses received"
    ::= { affirmedServiceconstructInterfaceAaaGroupDiameterStatisticsChassisLevelPeerDiameterInterfaceTypeEntry 324 }

affirmedServiceconstructInterfaceAaaGroupDiameterStatisticsChassisLevelPeerDiameterInterfaceTypeNumDTRFailure OBJECT-TYPE
    SYNTAX      ConfdString
    MAX-ACCESS  read-only
    STATUS      current
    DESCRIPTION "Number of DTR failure responses received"
    ::= { affirmedServiceconstructInterfaceAaaGroupDiameterStatisticsChassisLevelPeerDiameterInterfaceTypeEntry 325 }

affirmedServiceconstructInterfaceAaaGroupDiameterStatisticsChassisLevelPeerDiameterInterfaceTypeNumDTRTimeout OBJECT-TYPE
    SYNTAX      ConfdString
    MAX-ACCESS  read-only
    STATUS      current
    DESCRIPTION "Number of DTR attempts timed out"
    ::= { affirmedServiceconstructInterfaceAaaGroupDiameterStatisticsChassisLevelPeerDiameterInterfaceTypeEntry 326 }

affirmedServiceconstructInterfaceAaaGroupDiameterStatisticsChassisLevelPeerDiameterInterfaceTypeNumDTRAborted OBJECT-TYPE
    SYNTAX      ConfdString
    MAX-ACCESS  read-only
    STATUS      current
    DESCRIPTION "Number of DTR attempts aborted"
    ::= { affirmedServiceconstructInterfaceAaaGroupDiameterStatisticsChassisLevelPeerDiameterInterfaceTypeEntry 327 }

affirmedServiceconstructInterfaceAaaGroupDiameterStatisticsChassisLevelPeerDiameterInterfaceTypeNumDTRcvdFirstAttempt OBJECT-TYPE
    SYNTAX      ConfdString
    MAX-ACCESS  read-only
    STATUS      current
    DESCRIPTION "Number of DTA received to the initial DTR request"
    ::= { affirmedServiceconstructInterfaceAaaGroupDiameterStatisticsChassisLevelPeerDiameterInterfaceTypeEntry 328 }

affirmedServiceconstructInterfaceAaaGroupDiameterStatisticsChassisLevelPeerDiameterInterfaceTypeNumDTARcvdReTx OBJECT-TYPE
    SYNTAX      ConfdString
    MAX-ACCESS  read-only
    STATUS      current
    DESCRIPTION "Number of DTA received to the retransmitted DTR request"
    ::= { affirmedServiceconstructInterfaceAaaGroupDiameterStatisticsChassisLevelPeerDiameterInterfaceTypeEntry 329 }

affirmedServiceconstructInterfaceAaaGroupDiameterStatisticsChassisLevelPeerDiameterInterfaceTypeNumDTA3xxx OBJECT-TYPE
    SYNTAX      ConfdString
    MAX-ACCESS  read-only
    STATUS      current
    DESCRIPTION "Number of DTA received with 3xxx result code"
    ::= { affirmedServiceconstructInterfaceAaaGroupDiameterStatisticsChassisLevelPeerDiameterInterfaceTypeEntry 330 }

affirmedServiceconstructInterfaceAaaGroupDiameterStatisticsChassisLevelPeerDiameterInterfaceTypeNumDTA4xxx OBJECT-TYPE
    SYNTAX      ConfdString
    MAX-ACCESS  read-only
    STATUS      current
    DESCRIPTION "Number of DTA received with 4xxx result code"
    ::= { affirmedServiceconstructInterfaceAaaGroupDiameterStatisticsChassisLevelPeerDiameterInterfaceTypeEntry 331 }

affirmedServiceconstructInterfaceAaaGroupDiameterStatisticsChassisLevelPeerDiameterInterfaceTypeNumDTA5xxx OBJECT-TYPE
    SYNTAX      ConfdString
    MAX-ACCESS  read-only
    STATUS      current
    DESCRIPTION "Number of DTA received with 5xxx result code"
    ::= { affirmedServiceconstructInterfaceAaaGroupDiameterStatisticsChassisLevelPeerDiameterInterfaceTypeEntry 332 }

affirmedServiceconstructInterfaceAaaGroupDiameterStatisticsChassisLevelPeerDiameterInterfaceTypeNumDTADelayedSuccess OBJECT-TYPE
    SYNTAX      ConfdString
    MAX-ACCESS  read-only
    STATUS      current
    DESCRIPTION "Number of DTA success received after the request had been re-transmitted to another server"
    ::= { affirmedServiceconstructInterfaceAaaGroupDiameterStatisticsChassisLevelPeerDiameterInterfaceTypeEntry 333 }

affirmedServiceconstructInterfaceAaaGroupDiameterStatisticsChassisLevelPeerDiameterInterfaceTypeNumDTADelayedFailure OBJECT-TYPE
    SYNTAX      ConfdString
    MAX-ACCESS  read-only
    STATUS      current
    DESCRIPTION "Number of DTA failures received after the request had been re-transmitted to another server"
    ::= { affirmedServiceconstructInterfaceAaaGroupDiameterStatisticsChassisLevelPeerDiameterInterfaceTypeEntry 334 }

affirmedServiceconstructInterfaceAaaGroupDiameterStatisticsChassisLevelPeerDiameterInterfaceTypeNumDTADelayed3xxx OBJECT-TYPE
    SYNTAX      ConfdString
    MAX-ACCESS  read-only
    STATUS      current
    DESCRIPTION "Number of DTA received with 3xxx result code after the request had been re-transmitted to another server"
    ::= { affirmedServiceconstructInterfaceAaaGroupDiameterStatisticsChassisLevelPeerDiameterInterfaceTypeEntry 335 }

affirmedServiceconstructInterfaceAaaGroupDiameterStatisticsChassisLevelPeerDiameterInterfaceTypeNumDTADroppedNoProc OBJECT-TYPE
    SYNTAX      ConfdString
    MAX-ACCESS  read-only
    STATUS      current
    DESCRIPTION "Number of DTA dropped due to no matching transaction identifier"
    ::= { affirmedServiceconstructInterfaceAaaGroupDiameterStatisticsChassisLevelPeerDiameterInterfaceTypeEntry 336 }

affirmedServiceconstructInterfaceAaaGroupDiameterStatisticsChassisLevelPeerDiameterInterfaceTypeNumDTRTriggerAttempted OBJECT-TYPE
    SYNTAX      ConfdString
    MAX-ACCESS  read-only
    STATUS      current
    DESCRIPTION "Number of DTR trigger attempts made"
    ::= { affirmedServiceconstructInterfaceAaaGroupDiameterStatisticsChassisLevelPeerDiameterInterfaceTypeEntry 337 }

affirmedServiceconstructInterfaceAaaGroupDiameterStatisticsChassisLevelPeerDiameterInterfaceTypeNumDTRTriggerSuccess OBJECT-TYPE
    SYNTAX      ConfdString
    MAX-ACCESS  read-only
    STATUS      current
    DESCRIPTION "Number of DTR trigger success responses received"
    ::= { affirmedServiceconstructInterfaceAaaGroupDiameterStatisticsChassisLevelPeerDiameterInterfaceTypeEntry 338 }

affirmedServiceconstructInterfaceAaaGroupDiameterStatisticsChassisLevelPeerDiameterInterfaceTypeNumDTRTriggerFailure OBJECT-TYPE
    SYNTAX      ConfdString
    MAX-ACCESS  read-only
    STATUS      current
    DESCRIPTION "Number of DTR trigger failure responses received"
    ::= { affirmedServiceconstructInterfaceAaaGroupDiameterStatisticsChassisLevelPeerDiameterInterfaceTypeEntry 339 }

affirmedServiceconstructInterfaceAaaGroupDiameterStatisticsChassisLevelPeerDiameterInterfaceTypeNumDTRTriggerTimeout OBJECT-TYPE
    SYNTAX      ConfdString
    MAX-ACCESS  read-only
    STATUS      current
    DESCRIPTION "Number of DTR trigger attempts timed out"
    ::= { affirmedServiceconstructInterfaceAaaGroupDiameterStatisticsChassisLevelPeerDiameterInterfaceTypeEntry 340 }

affirmedServiceconstructInterfaceAaaGroupDiameterStatisticsChassisLevelPeerDiameterInterfaceTypeNumDTRTriggerAborted OBJECT-TYPE
    SYNTAX      ConfdString
    MAX-ACCESS  read-only
    STATUS      current
    DESCRIPTION "Number of DTR trigger attempts aborted"
    ::= { affirmedServiceconstructInterfaceAaaGroupDiameterStatisticsChassisLevelPeerDiameterInterfaceTypeEntry 341 }

affirmedServiceconstructInterfaceAaaGroupDiameterStatisticsChassisLevelPeerDiameterInterfaceTypeNumDTRTriggercvdFirstAttempt OBJECT-TYPE
    SYNTAX      ConfdString
    MAX-ACCESS  read-only
    STATUS      current
    DESCRIPTION "Number of DTA received to the initial DTR trigger request"
    ::= { affirmedServiceconstructInterfaceAaaGroupDiameterStatisticsChassisLevelPeerDiameterInterfaceTypeEntry 342 }

affirmedServiceconstructInterfaceAaaGroupDiameterStatisticsChassisLevelPeerDiameterInterfaceTypeNumDTATriggerRcvdReTx OBJECT-TYPE
    SYNTAX      ConfdString
    MAX-ACCESS  read-only
    STATUS      current
    DESCRIPTION "Number of DTA received to the retransmitted DTR trigger request"
    ::= { affirmedServiceconstructInterfaceAaaGroupDiameterStatisticsChassisLevelPeerDiameterInterfaceTypeEntry 343 }

affirmedServiceconstructInterfaceAaaGroupDiameterStatisticsChassisLevelPeerDiameterInterfaceTypeNumDTATrigger3xxx OBJECT-TYPE
    SYNTAX      ConfdString
    MAX-ACCESS  read-only
    STATUS      current
    DESCRIPTION "Number of DTA received for the trigger action with 3xxx result code"
    ::= { affirmedServiceconstructInterfaceAaaGroupDiameterStatisticsChassisLevelPeerDiameterInterfaceTypeEntry 344 }

affirmedServiceconstructInterfaceAaaGroupDiameterStatisticsChassisLevelPeerDiameterInterfaceTypeNumDTATrigger4xxx OBJECT-TYPE
    SYNTAX      ConfdString
    MAX-ACCESS  read-only
    STATUS      current
    DESCRIPTION "Number of DTA received for the trigger action with 4xxx result code"
    ::= { affirmedServiceconstructInterfaceAaaGroupDiameterStatisticsChassisLevelPeerDiameterInterfaceTypeEntry 345 }

affirmedServiceconstructInterfaceAaaGroupDiameterStatisticsChassisLevelPeerDiameterInterfaceTypeNumDTATrigger5xxx OBJECT-TYPE
    SYNTAX      ConfdString
    MAX-ACCESS  read-only
    STATUS      current
    DESCRIPTION "Number of DTA received for the trigger action with 5xxx result code"
    ::= { affirmedServiceconstructInterfaceAaaGroupDiameterStatisticsChassisLevelPeerDiameterInterfaceTypeEntry 346 }

affirmedServiceconstructInterfaceAaaGroupDiameterStatisticsChassisLevelPeerDiameterInterfaceTypeNumDTATriggerDelayedSuccess OBJECT-TYPE
    SYNTAX      ConfdString
    MAX-ACCESS  read-only
    STATUS      current
    DESCRIPTION "Number of DTA success received for the trigger action after the request had been re-transmitted to another server"
    ::= { affirmedServiceconstructInterfaceAaaGroupDiameterStatisticsChassisLevelPeerDiameterInterfaceTypeEntry 347 }

affirmedServiceconstructInterfaceAaaGroupDiameterStatisticsChassisLevelPeerDiameterInterfaceTypeNumDTATriggerDelayedFailure OBJECT-TYPE
    SYNTAX      ConfdString
    MAX-ACCESS  read-only
    STATUS      current
    DESCRIPTION "Number of DTA failures received for the trigger action after the request had been re-transmitted to another server"
    ::= { affirmedServiceconstructInterfaceAaaGroupDiameterStatisticsChassisLevelPeerDiameterInterfaceTypeEntry 348 }

affirmedServiceconstructInterfaceAaaGroupDiameterStatisticsChassisLevelPeerDiameterInterfaceTypeNumDTATriggerDelayed3xxx OBJECT-TYPE
    SYNTAX      ConfdString
    MAX-ACCESS  read-only
    STATUS      current
    DESCRIPTION "Number of DTA received with 3xxx result code for the trigger action after the request had been re-transmitted to another server"
    ::= { affirmedServiceconstructInterfaceAaaGroupDiameterStatisticsChassisLevelPeerDiameterInterfaceTypeEntry 349 }

affirmedServiceconstructInterfaceAaaGroupDiameterStatisticsChassisLevelPeerDiameterInterfaceTypeNumDTATriggerDroppedNoProc OBJECT-TYPE
    SYNTAX      ConfdString
    MAX-ACCESS  read-only
    STATUS      current
    DESCRIPTION "Number of DTA for the trigger action dropped due to no matching transaction identifier"
    ::= { affirmedServiceconstructInterfaceAaaGroupDiameterStatisticsChassisLevelPeerDiameterInterfaceTypeEntry 350 }

affirmedServiceconstructInterfaceAaaGroupDiameterStatisticsChassisLevelPeerDiameterInterfaceTypeNumDTRRecallAttempted OBJECT-TYPE
    SYNTAX      ConfdString
    MAX-ACCESS  read-only
    STATUS      current
    DESCRIPTION "Number of DTR recall attempts made"
    ::= { affirmedServiceconstructInterfaceAaaGroupDiameterStatisticsChassisLevelPeerDiameterInterfaceTypeEntry 351 }

affirmedServiceconstructInterfaceAaaGroupDiameterStatisticsChassisLevelPeerDiameterInterfaceTypeNumDTRRecallSuccess OBJECT-TYPE
    SYNTAX      ConfdString
    MAX-ACCESS  read-only
    STATUS      current
    DESCRIPTION "Number of DTR recall success responses received"
    ::= { affirmedServiceconstructInterfaceAaaGroupDiameterStatisticsChassisLevelPeerDiameterInterfaceTypeEntry 352 }

affirmedServiceconstructInterfaceAaaGroupDiameterStatisticsChassisLevelPeerDiameterInterfaceTypeNumDTRRecallFailure OBJECT-TYPE
    SYNTAX      ConfdString
    MAX-ACCESS  read-only
    STATUS      current
    DESCRIPTION "Number of DTR recall failure responses received"
    ::= { affirmedServiceconstructInterfaceAaaGroupDiameterStatisticsChassisLevelPeerDiameterInterfaceTypeEntry 353 }

affirmedServiceconstructInterfaceAaaGroupDiameterStatisticsChassisLevelPeerDiameterInterfaceTypeNumDTRRecallTimeout OBJECT-TYPE
    SYNTAX      ConfdString
    MAX-ACCESS  read-only
    STATUS      current
    DESCRIPTION "Number of DTR recall attempts timed out"
    ::= { affirmedServiceconstructInterfaceAaaGroupDiameterStatisticsChassisLevelPeerDiameterInterfaceTypeEntry 354 }

affirmedServiceconstructInterfaceAaaGroupDiameterStatisticsChassisLevelPeerDiameterInterfaceTypeNumDTRRecallAborted OBJECT-TYPE
    SYNTAX      ConfdString
    MAX-ACCESS  read-only
    STATUS      current
    DESCRIPTION "Number of DTR recall attempts aborted"
    ::= { affirmedServiceconstructInterfaceAaaGroupDiameterStatisticsChassisLevelPeerDiameterInterfaceTypeEntry 355 }

affirmedServiceconstructInterfaceAaaGroupDiameterStatisticsChassisLevelPeerDiameterInterfaceTypeNumDTRRecallcvdFirstAttempt OBJECT-TYPE
    SYNTAX      ConfdString
    MAX-ACCESS  read-only
    STATUS      current
    DESCRIPTION "Number of DTA received to the initial DTR recall request"
    ::= { affirmedServiceconstructInterfaceAaaGroupDiameterStatisticsChassisLevelPeerDiameterInterfaceTypeEntry 356 }

affirmedServiceconstructInterfaceAaaGroupDiameterStatisticsChassisLevelPeerDiameterInterfaceTypeNumDTARecallRcvdReTx OBJECT-TYPE
    SYNTAX      ConfdString
    MAX-ACCESS  read-only
    STATUS      current
    DESCRIPTION "Number of DTA received to the retransmitted DTR recall request"
    ::= { affirmedServiceconstructInterfaceAaaGroupDiameterStatisticsChassisLevelPeerDiameterInterfaceTypeEntry 357 }

affirmedServiceconstructInterfaceAaaGroupDiameterStatisticsChassisLevelPeerDiameterInterfaceTypeNumDTARecall3xxx OBJECT-TYPE
    SYNTAX      ConfdString
    MAX-ACCESS  read-only
    STATUS      current
    DESCRIPTION "Number of DTA received for the recall action with 3xxx result code"
    ::= { affirmedServiceconstructInterfaceAaaGroupDiameterStatisticsChassisLevelPeerDiameterInterfaceTypeEntry 358 }

affirmedServiceconstructInterfaceAaaGroupDiameterStatisticsChassisLevelPeerDiameterInterfaceTypeNumDTARecall4xxx OBJECT-TYPE
    SYNTAX      ConfdString
    MAX-ACCESS  read-only
    STATUS      current
    DESCRIPTION "Number of DTA received for the recall action with 4xxx result code"
    ::= { affirmedServiceconstructInterfaceAaaGroupDiameterStatisticsChassisLevelPeerDiameterInterfaceTypeEntry 359 }

affirmedServiceconstructInterfaceAaaGroupDiameterStatisticsChassisLevelPeerDiameterInterfaceTypeNumDTARecall5xxx OBJECT-TYPE
    SYNTAX      ConfdString
    MAX-ACCESS  read-only
    STATUS      current
    DESCRIPTION "Number of DTA received for the recall action with 5xxx result code"
    ::= { affirmedServiceconstructInterfaceAaaGroupDiameterStatisticsChassisLevelPeerDiameterInterfaceTypeEntry 360 }

affirmedServiceconstructInterfaceAaaGroupDiameterStatisticsChassisLevelPeerDiameterInterfaceTypeNumDTARecallDelayedSuccess OBJECT-TYPE
    SYNTAX      ConfdString
    MAX-ACCESS  read-only
    STATUS      current
    DESCRIPTION "Number of DTA success received for the recall action after the request had been re-transmitted to another server"
    ::= { affirmedServiceconstructInterfaceAaaGroupDiameterStatisticsChassisLevelPeerDiameterInterfaceTypeEntry 361 }

affirmedServiceconstructInterfaceAaaGroupDiameterStatisticsChassisLevelPeerDiameterInterfaceTypeNumDTARecallDelayedFailure OBJECT-TYPE
    SYNTAX      ConfdString
    MAX-ACCESS  read-only
    STATUS      current
    DESCRIPTION "Number of DTA failures received for the recall action after the request had been re-transmitted to another server"
    ::= { affirmedServiceconstructInterfaceAaaGroupDiameterStatisticsChassisLevelPeerDiameterInterfaceTypeEntry 362 }

affirmedServiceconstructInterfaceAaaGroupDiameterStatisticsChassisLevelPeerDiameterInterfaceTypeNumDTARecallDelayed3xxx OBJECT-TYPE
    SYNTAX      ConfdString
    MAX-ACCESS  read-only
    STATUS      current
    DESCRIPTION "Number of DTA received with 3xxx result code for the recall action after the request had been re-transmitted to another server"
    ::= { affirmedServiceconstructInterfaceAaaGroupDiameterStatisticsChassisLevelPeerDiameterInterfaceTypeEntry 363 }

affirmedServiceconstructInterfaceAaaGroupDiameterStatisticsChassisLevelPeerDiameterInterfaceTypeNumDTARecallDroppedNoProc OBJECT-TYPE
    SYNTAX      ConfdString
    MAX-ACCESS  read-only
    STATUS      current
    DESCRIPTION "Number of DTA for the recall action dropped due to no matching transaction identifier"
    ::= { affirmedServiceconstructInterfaceAaaGroupDiameterStatisticsChassisLevelPeerDiameterInterfaceTypeEntry 364 }

affirmedServiceconstructInterfaceAaaGroupDiameterStatisticsChassisLevelPeerDiameterInterfaceTypeNumDTRReplaceAttempted OBJECT-TYPE
    SYNTAX      ConfdString
    MAX-ACCESS  read-only
    STATUS      current
    DESCRIPTION "Number of DTR replace attempts made"
    ::= { affirmedServiceconstructInterfaceAaaGroupDiameterStatisticsChassisLevelPeerDiameterInterfaceTypeEntry 365 }

affirmedServiceconstructInterfaceAaaGroupDiameterStatisticsChassisLevelPeerDiameterInterfaceTypeNumDTRReplaceSuccess OBJECT-TYPE
    SYNTAX      ConfdString
    MAX-ACCESS  read-only
    STATUS      current
    DESCRIPTION "Number of DTR replace success responses received"
    ::= { affirmedServiceconstructInterfaceAaaGroupDiameterStatisticsChassisLevelPeerDiameterInterfaceTypeEntry 366 }

affirmedServiceconstructInterfaceAaaGroupDiameterStatisticsChassisLevelPeerDiameterInterfaceTypeNumDTRReplaceFailure OBJECT-TYPE
    SYNTAX      ConfdString
    MAX-ACCESS  read-only
    STATUS      current
    DESCRIPTION "Number of DTR replace failure responses received"
    ::= { affirmedServiceconstructInterfaceAaaGroupDiameterStatisticsChassisLevelPeerDiameterInterfaceTypeEntry 367 }

affirmedServiceconstructInterfaceAaaGroupDiameterStatisticsChassisLevelPeerDiameterInterfaceTypeNumDTRReplaceTimeout OBJECT-TYPE
    SYNTAX      ConfdString
    MAX-ACCESS  read-only
    STATUS      current
    DESCRIPTION "Number of DTR replace attempts timed out"
    ::= { affirmedServiceconstructInterfaceAaaGroupDiameterStatisticsChassisLevelPeerDiameterInterfaceTypeEntry 368 }

affirmedServiceconstructInterfaceAaaGroupDiameterStatisticsChassisLevelPeerDiameterInterfaceTypeNumDTRReplaceAborted OBJECT-TYPE
    SYNTAX      ConfdString
    MAX-ACCESS  read-only
    STATUS      current
    DESCRIPTION "Number of DTR replace attempts aborted"
    ::= { affirmedServiceconstructInterfaceAaaGroupDiameterStatisticsChassisLevelPeerDiameterInterfaceTypeEntry 369 }

affirmedServiceconstructInterfaceAaaGroupDiameterStatisticsChassisLevelPeerDiameterInterfaceTypeNumDTRReplacecvdFirstAttempt OBJECT-TYPE
    SYNTAX      ConfdString
    MAX-ACCESS  read-only
    STATUS      current
    DESCRIPTION "Number of DTA received to the initial DTR replace request"
    ::= { affirmedServiceconstructInterfaceAaaGroupDiameterStatisticsChassisLevelPeerDiameterInterfaceTypeEntry 370 }

affirmedServiceconstructInterfaceAaaGroupDiameterStatisticsChassisLevelPeerDiameterInterfaceTypeNumDTAReplaceRcvdReTx OBJECT-TYPE
    SYNTAX      ConfdString
    MAX-ACCESS  read-only
    STATUS      current
    DESCRIPTION "Number of DTA received to the retransmitted DTR replace request"
    ::= { affirmedServiceconstructInterfaceAaaGroupDiameterStatisticsChassisLevelPeerDiameterInterfaceTypeEntry 371 }

affirmedServiceconstructInterfaceAaaGroupDiameterStatisticsChassisLevelPeerDiameterInterfaceTypeNumDTAReplace3xxx OBJECT-TYPE
    SYNTAX      ConfdString
    MAX-ACCESS  read-only
    STATUS      current
    DESCRIPTION "Number of DTA received for the replace action with 3xxx result code"
    ::= { affirmedServiceconstructInterfaceAaaGroupDiameterStatisticsChassisLevelPeerDiameterInterfaceTypeEntry 372 }

affirmedServiceconstructInterfaceAaaGroupDiameterStatisticsChassisLevelPeerDiameterInterfaceTypeNumDTAReplace4xxx OBJECT-TYPE
    SYNTAX      ConfdString
    MAX-ACCESS  read-only
    STATUS      current
    DESCRIPTION "Number of DTA received for the replace action with 4xxx result code"
    ::= { affirmedServiceconstructInterfaceAaaGroupDiameterStatisticsChassisLevelPeerDiameterInterfaceTypeEntry 373 }

affirmedServiceconstructInterfaceAaaGroupDiameterStatisticsChassisLevelPeerDiameterInterfaceTypeNumDTAReplace5xxx OBJECT-TYPE
    SYNTAX      ConfdString
    MAX-ACCESS  read-only
    STATUS      current
    DESCRIPTION "Number of DTA received for the replace action with 5xxx result code"
    ::= { affirmedServiceconstructInterfaceAaaGroupDiameterStatisticsChassisLevelPeerDiameterInterfaceTypeEntry 374 }

affirmedServiceconstructInterfaceAaaGroupDiameterStatisticsChassisLevelPeerDiameterInterfaceTypeNumDTAReplaceDelayedSuccess OBJECT-TYPE
    SYNTAX      ConfdString
    MAX-ACCESS  read-only
    STATUS      current
    DESCRIPTION "Number of DTA success received for the replace action after the request had been re-transmitted to another server"
    ::= { affirmedServiceconstructInterfaceAaaGroupDiameterStatisticsChassisLevelPeerDiameterInterfaceTypeEntry 375 }

affirmedServiceconstructInterfaceAaaGroupDiameterStatisticsChassisLevelPeerDiameterInterfaceTypeNumDTAReplaceDelayedFailure OBJECT-TYPE
    SYNTAX      ConfdString
    MAX-ACCESS  read-only
    STATUS      current
    DESCRIPTION "Number of DTA failures received for the replace action after the request had been re-transmitted to another server"
    ::= { affirmedServiceconstructInterfaceAaaGroupDiameterStatisticsChassisLevelPeerDiameterInterfaceTypeEntry 376 }

affirmedServiceconstructInterfaceAaaGroupDiameterStatisticsChassisLevelPeerDiameterInterfaceTypeNumDTAReplaceDelayed3xxx OBJECT-TYPE
    SYNTAX      ConfdString
    MAX-ACCESS  read-only
    STATUS      current
    DESCRIPTION "Number of DTA received with 3xxx result code for the replace action after the request had been re-transmitted to another server"
    ::= { affirmedServiceconstructInterfaceAaaGroupDiameterStatisticsChassisLevelPeerDiameterInterfaceTypeEntry 377 }

affirmedServiceconstructInterfaceAaaGroupDiameterStatisticsChassisLevelPeerDiameterInterfaceTypeNumDTAReplaceDroppedNoProc OBJECT-TYPE
    SYNTAX      ConfdString
    MAX-ACCESS  read-only
    STATUS      current
    DESCRIPTION "Number of DTA for the replace action dropped due to no matching transaction identifier"
    ::= { affirmedServiceconstructInterfaceAaaGroupDiameterStatisticsChassisLevelPeerDiameterInterfaceTypeEntry 378 }

affirmedServiceconstructInterfaceAaaGroupDiameterStatisticsChassisLevelPeerDiameterInterfaceTypeNumDRRReceived OBJECT-TYPE
    SYNTAX      ConfdString
    MAX-ACCESS  read-only
    STATUS      current
    DESCRIPTION "Number of DRR messages received"
    ::= { affirmedServiceconstructInterfaceAaaGroupDiameterStatisticsChassisLevelPeerDiameterInterfaceTypeEntry 379 }

affirmedServiceconstructInterfaceAaaGroupDiameterStatisticsChassisLevelPeerDiameterInterfaceTypeNumDRASuccess OBJECT-TYPE
    SYNTAX      ConfdString
    MAX-ACCESS  read-only
    STATUS      current
    DESCRIPTION "Number of DRR success responses sent"
    ::= { affirmedServiceconstructInterfaceAaaGroupDiameterStatisticsChassisLevelPeerDiameterInterfaceTypeEntry 380 }

affirmedServiceconstructInterfaceAaaGroupDiameterStatisticsChassisLevelPeerDiameterInterfaceTypeNumDRAFailures OBJECT-TYPE
    SYNTAX      ConfdString
    MAX-ACCESS  read-only
    STATUS      current
    DESCRIPTION "Number of DRR failure responses sent"
    ::= { affirmedServiceconstructInterfaceAaaGroupDiameterStatisticsChassisLevelPeerDiameterInterfaceTypeEntry 381 }

affirmedServiceconstructInterfaceAaaGroupDiameterStatisticsChassisLevelPeerDiameterInterfaceTypeNumDRAFailuresUnknownRefId OBJECT-TYPE
    SYNTAX      ConfdString
    MAX-ACCESS  read-only
    STATUS      current
    DESCRIPTION "Number of DRR failures due to unknown Reference Identifier"
    ::= { affirmedServiceconstructInterfaceAaaGroupDiameterStatisticsChassisLevelPeerDiameterInterfaceTypeEntry 382 }

affirmedServiceconstructInterfaceAaaGroupDiameterStatisticsChassisLevelPeerDiameterInterfaceTypeNumDRAFailuresUnknownSession OBJECT-TYPE
    SYNTAX      ConfdString
    MAX-ACCESS  read-only
    STATUS      current
    DESCRIPTION "Number of DRR failures due to context not found"
    ::= { affirmedServiceconstructInterfaceAaaGroupDiameterStatisticsChassisLevelPeerDiameterInterfaceTypeEntry 383 }

affirmedServiceconstructInterfaceAaaGroupDiameterStatisticsChassisLevelPeerDiameterInterfaceTypeNumDRAFailuresMissingAVP OBJECT-TYPE
    SYNTAX      ConfdString
    MAX-ACCESS  read-only
    STATUS      current
    DESCRIPTION "Number of DRR failures due to missing AVPs"
    ::= { affirmedServiceconstructInterfaceAaaGroupDiameterStatisticsChassisLevelPeerDiameterInterfaceTypeEntry 384 }

affirmedServiceconstructInterfaceAaaGroupDiameterStatisticsChassisLevelPeerDiameterInterfaceTypeNumDRAFailuresUnableToDeliver OBJECT-TYPE
    SYNTAX      ConfdString
    MAX-ACCESS  read-only
    STATUS      current
    DESCRIPTION "Number of DRR failures due to Destination Host in DRR not being found"
    ::= { affirmedServiceconstructInterfaceAaaGroupDiameterStatisticsChassisLevelPeerDiameterInterfaceTypeEntry 385 }

affirmedServiceconstructInterfaceAaaGroupDiameterStatisticsChassisLevelPeerDiameterInterfaceTypeNumAuthLifetimerInitAARRetry OBJECT-TYPE
    SYNTAX      ConfdString
    MAX-ACCESS  read-only
    STATUS      current
    DESCRIPTION "Number of Authorization-Lifetime AAR retransmits"
    ::= { affirmedServiceconstructInterfaceAaaGroupDiameterStatisticsChassisLevelPeerDiameterInterfaceTypeEntry 386 }

affirmedServiceconstructInterfaceAaaGroupDiameterStatisticsChassisLevelPeerDiameterInterfaceTypeNumAuthGraceTmrInitAARRetry OBJECT-TYPE
    SYNTAX      ConfdString
    MAX-ACCESS  read-only
    STATUS      current
    DESCRIPTION "Number of Auth-Grace-Period AAR retransmits"
    ::= { affirmedServiceconstructInterfaceAaaGroupDiameterStatisticsChassisLevelPeerDiameterInterfaceTypeEntry 387 }

affirmedServiceconstructInterfaceAaaGroupDiameterStatisticsChassisLevelPeerDiameterInterfaceTypeNumTsrReceived OBJECT-TYPE
    SYNTAX      Unsigned32
    MAX-ACCESS  read-only
    STATUS      current
    DESCRIPTION "Number of TSR messages received from peer"
    ::= { affirmedServiceconstructInterfaceAaaGroupDiameterStatisticsChassisLevelPeerDiameterInterfaceTypeEntry 388 }

affirmedServiceconstructInterfaceAaaGroupDiameterStatisticsChassisLevelPeerDiameterInterfaceTypeNumTsaSuccess OBJECT-TYPE
    SYNTAX      Unsigned32
    MAX-ACCESS  read-only
    STATUS      current
    DESCRIPTION "Number of TSA success messages sent to peer"
    ::= { affirmedServiceconstructInterfaceAaaGroupDiameterStatisticsChassisLevelPeerDiameterInterfaceTypeEntry 389 }

affirmedServiceconstructInterfaceAaaGroupDiameterStatisticsChassisLevelPeerDiameterInterfaceTypeNumTsaFailures OBJECT-TYPE
    SYNTAX      Unsigned32
    MAX-ACCESS  read-only
    STATUS      current
    DESCRIPTION "Number of TSA failures"
    ::= { affirmedServiceconstructInterfaceAaaGroupDiameterStatisticsChassisLevelPeerDiameterInterfaceTypeEntry 390 }

affirmedServiceconstructInterfaceAaaGroupDiameterStatisticsChassisLevelPeerDiameterInterfaceTypeNumAAAInitialDelayedSuccess OBJECT-TYPE
    SYNTAX      ConfdString
    MAX-ACCESS  read-only
    STATUS      current
    DESCRIPTION "Number of AAA Initial success which were received after the request had been re-transmitted to another server"
    ::= { affirmedServiceconstructInterfaceAaaGroupDiameterStatisticsChassisLevelPeerDiameterInterfaceTypeEntry 391 }

affirmedServiceconstructInterfaceAaaGroupDiameterStatisticsChassisLevelPeerDiameterInterfaceTypeNumAAAInitialDelayedFailure OBJECT-TYPE
    SYNTAX      ConfdString
    MAX-ACCESS  read-only
    STATUS      current
    DESCRIPTION "Number of AAA Initial failures which were received after the request had been re-transmitted to another server"
    ::= { affirmedServiceconstructInterfaceAaaGroupDiameterStatisticsChassisLevelPeerDiameterInterfaceTypeEntry 392 }

affirmedServiceconstructInterfaceAaaGroupDiameterStatisticsChassisLevelPeerDiameterInterfaceTypeNumAAAInitialDelayed3xxx OBJECT-TYPE
    SYNTAX      ConfdString
    MAX-ACCESS  read-only
    STATUS      current
    DESCRIPTION "Number of delayed AAA Initial 3xxx error which were received after the request had been re-transmitted to another server"
    ::= { affirmedServiceconstructInterfaceAaaGroupDiameterStatisticsChassisLevelPeerDiameterInterfaceTypeEntry 393 }

affirmedServiceconstructInterfaceAaaGroupDiameterStatisticsChassisLevelPeerDiameterInterfaceTypeNumAARRetry OBJECT-TYPE
    SYNTAX      ConfdString
    MAX-ACCESS  read-only
    STATUS      current
    DESCRIPTION "Number of AAR retransmits"
    ::= { affirmedServiceconstructInterfaceAaaGroupDiameterStatisticsChassisLevelPeerDiameterInterfaceTypeEntry 394 }

affirmedServiceconstructInterfaceAaaGroupDiameterStatisticsChassisLevelPeerDiameterInterfaceTypeNumRarInitiatedAARRetry OBJECT-TYPE
    SYNTAX      ConfdString
    MAX-ACCESS  read-only
    STATUS      current
    DESCRIPTION "Number of RAR initiated AAR retransmits"
    ::= { affirmedServiceconstructInterfaceAaaGroupDiameterStatisticsChassisLevelPeerDiameterInterfaceTypeEntry 395 }

affirmedServiceconstructInterfaceAaaGroupDiameterStatisticsChassisLevelPeerResultCodeStatisticsTable OBJECT-TYPE
    SYNTAX      SEQUENCE OF AffirmedServiceconstructInterfaceAaaGroupDiameterStatisticsChassisLevelPeerResultCodeStatisticsEntry
    MAX-ACCESS  not-accessible
    STATUS      current
    DESCRIPTION ""
    ::= { affirmedServiceconstructInterfaceAaaGroupDiameterStatisticsChassisLevelPeer 3 }

affirmedServiceconstructInterfaceAaaGroupDiameterStatisticsChassisLevelPeerResultCodeStatisticsEntry OBJECT-TYPE
    SYNTAX      AffirmedServiceconstructInterfaceAaaGroupDiameterStatisticsChassisLevelPeerResultCodeStatisticsEntry
    MAX-ACCESS  not-accessible
    STATUS      current
    DESCRIPTION ""
    INDEX { affirmedServiceconstructInterfaceAaaGroupDiameterStatisticsChassisLevelPeerResultCodeStatisticsIntfType, affirmedServiceconstructInterfaceAaaGroupDiameterStatisticsChassisLevelPeerResultCodeStatisticsNodeName, affirmedServiceconstructInterfaceAaaGroupDiameterStatisticsChassisLevelPeerResultCodeStatisticsPeerName, affirmedServiceconstructInterfaceAaaGroupDiameterStatisticsChassisLevelPeerResultCodeStatisticsResultCode }
        ::= { affirmedServiceconstructInterfaceAaaGroupDiameterStatisticsChassisLevelPeerResultCodeStatisticsTable 1 }

AffirmedServiceconstructInterfaceAaaGroupDiameterStatisticsChassisLevelPeerResultCodeStatisticsEntry ::=
    SEQUENCE {
        affirmedServiceconstructInterfaceAaaGroupDiameterStatisticsChassisLevelPeerResultCodeStatisticsIntfType String,
        affirmedServiceconstructInterfaceAaaGroupDiameterStatisticsChassisLevelPeerResultCodeStatisticsNodeName String,
        affirmedServiceconstructInterfaceAaaGroupDiameterStatisticsChassisLevelPeerResultCodeStatisticsPeerName String,
        affirmedServiceconstructInterfaceAaaGroupDiameterStatisticsChassisLevelPeerResultCodeStatisticsResultCode String,
        affirmedServiceconstructInterfaceAaaGroupDiameterStatisticsChassisLevelPeerResultCodeStatisticsNumInitialResponse ConfdString,
        affirmedServiceconstructInterfaceAaaGroupDiameterStatisticsChassisLevelPeerResultCodeStatisticsNumUpdateResponse ConfdString,
        affirmedServiceconstructInterfaceAaaGroupDiameterStatisticsChassisLevelPeerResultCodeStatisticsNumTerminateResponse ConfdString
    }

affirmedServiceconstructInterfaceAaaGroupDiameterStatisticsChassisLevelPeerResultCodeStatisticsIntfType OBJECT-TYPE
    SYNTAX      String
    MAX-ACCESS  not-accessible
    STATUS      current
    DESCRIPTION "Diameter Interface Type: GX/GY"
    ::= { affirmedServiceconstructInterfaceAaaGroupDiameterStatisticsChassisLevelPeerResultCodeStatisticsEntry 1 }

affirmedServiceconstructInterfaceAaaGroupDiameterStatisticsChassisLevelPeerResultCodeStatisticsNodeName OBJECT-TYPE
    SYNTAX      String
    MAX-ACCESS  not-accessible
    STATUS      current
    DESCRIPTION "Local Diameter Server Node Name"
    ::= { affirmedServiceconstructInterfaceAaaGroupDiameterStatisticsChassisLevelPeerResultCodeStatisticsEntry 2 }

affirmedServiceconstructInterfaceAaaGroupDiameterStatisticsChassisLevelPeerResultCodeStatisticsPeerName OBJECT-TYPE
    SYNTAX      String
    MAX-ACCESS  not-accessible
    STATUS      current
    DESCRIPTION "Peer name"
    ::= { affirmedServiceconstructInterfaceAaaGroupDiameterStatisticsChassisLevelPeerResultCodeStatisticsEntry 3 }

affirmedServiceconstructInterfaceAaaGroupDiameterStatisticsChassisLevelPeerResultCodeStatisticsResultCode OBJECT-TYPE
    SYNTAX      String
    MAX-ACCESS  not-accessible
    STATUS      current
    DESCRIPTION "Result Code"
    ::= { affirmedServiceconstructInterfaceAaaGroupDiameterStatisticsChassisLevelPeerResultCodeStatisticsEntry 4 }

affirmedServiceconstructInterfaceAaaGroupDiameterStatisticsChassisLevelPeerResultCodeStatisticsNumInitialResponse OBJECT-TYPE
    SYNTAX      ConfdString
    MAX-ACCESS  read-only
    STATUS      current
    DESCRIPTION "Total number of Inital Response Received with the result code "
    ::= { affirmedServiceconstructInterfaceAaaGroupDiameterStatisticsChassisLevelPeerResultCodeStatisticsEntry 5 }

affirmedServiceconstructInterfaceAaaGroupDiameterStatisticsChassisLevelPeerResultCodeStatisticsNumUpdateResponse OBJECT-TYPE
    SYNTAX      ConfdString
    MAX-ACCESS  read-only
    STATUS      current
    DESCRIPTION "Total number of Update Response Received with the result code "
    ::= { affirmedServiceconstructInterfaceAaaGroupDiameterStatisticsChassisLevelPeerResultCodeStatisticsEntry 6 }

affirmedServiceconstructInterfaceAaaGroupDiameterStatisticsChassisLevelPeerResultCodeStatisticsNumTerminateResponse OBJECT-TYPE
    SYNTAX      ConfdString
    MAX-ACCESS  read-only
    STATUS      current
    DESCRIPTION "Total number of Terminate Response Received with the result code "
    ::= { affirmedServiceconstructInterfaceAaaGroupDiameterStatisticsChassisLevelPeerResultCodeStatisticsEntry 7 }

affirmedServiceconstructInterfaceAaaGroupDiameterStatisticsChassisLevelEndhostIntfTypeTable OBJECT-TYPE
    SYNTAX      SEQUENCE OF AffirmedServiceconstructInterfaceAaaGroupDiameterStatisticsChassisLevelEndhostIntfTypeEntry
    MAX-ACCESS  not-accessible
    STATUS      current
    DESCRIPTION ""
    ::= { affirmedServiceconstructInterfaceAaaGroupDiameterStatisticsChassisLevelEndhost 1 }

affirmedServiceconstructInterfaceAaaGroupDiameterStatisticsChassisLevelEndhostIntfTypeEntry OBJECT-TYPE
    SYNTAX      AffirmedServiceconstructInterfaceAaaGroupDiameterStatisticsChassisLevelEndhostIntfTypeEntry
    MAX-ACCESS  not-accessible
    STATUS      current
    DESCRIPTION ""
    INDEX { affirmedServiceconstructInterfaceAaaGroupDiameterStatisticsChassisLevelEndhostIntfTypeIntfType, affirmedServiceconstructInterfaceAaaGroupDiameterStatisticsChassisLevelEndhostIntfTypeNodeName, affirmedServiceconstructInterfaceAaaGroupDiameterStatisticsChassisLevelEndhostIntfTypeDraName, affirmedServiceconstructInterfaceAaaGroupDiameterStatisticsChassisLevelEndhostIntfTypeEndHostName }
        ::= { affirmedServiceconstructInterfaceAaaGroupDiameterStatisticsChassisLevelEndhostIntfTypeTable 1 }

AffirmedServiceconstructInterfaceAaaGroupDiameterStatisticsChassisLevelEndhostIntfTypeEntry ::=
    SEQUENCE {
        affirmedServiceconstructInterfaceAaaGroupDiameterStatisticsChassisLevelEndhostIntfTypeIntfType String,
        affirmedServiceconstructInterfaceAaaGroupDiameterStatisticsChassisLevelEndhostIntfTypeNodeName String,
        affirmedServiceconstructInterfaceAaaGroupDiameterStatisticsChassisLevelEndhostIntfTypeDraName String,
        affirmedServiceconstructInterfaceAaaGroupDiameterStatisticsChassisLevelEndhostIntfTypeEndHostName String,
        affirmedServiceconstructInterfaceAaaGroupDiameterStatisticsChassisLevelEndhostIntfTypeNumCCRInitialAttempted ConfdString,
        affirmedServiceconstructInterfaceAaaGroupDiameterStatisticsChassisLevelEndhostIntfTypeNumCCRInitialSuccess ConfdString,
        affirmedServiceconstructInterfaceAaaGroupDiameterStatisticsChassisLevelEndhostIntfTypeNumCCRInitialFailure ConfdString,
        affirmedServiceconstructInterfaceAaaGroupDiameterStatisticsChassisLevelEndhostIntfTypeNumCCAInitial3xxx ConfdString,
        affirmedServiceconstructInterfaceAaaGroupDiameterStatisticsChassisLevelEndhostIntfTypeNumCCAInitial4xxx ConfdString,
        affirmedServiceconstructInterfaceAaaGroupDiameterStatisticsChassisLevelEndhostIntfTypeNumCCAInitial5xxx ConfdString,
        affirmedServiceconstructInterfaceAaaGroupDiameterStatisticsChassisLevelEndhostIntfTypeNumCCRInitialTimeout ConfdString,
        affirmedServiceconstructInterfaceAaaGroupDiameterStatisticsChassisLevelEndhostIntfTypeNumCCRInitialAborted ConfdString,
        affirmedServiceconstructInterfaceAaaGroupDiameterStatisticsChassisLevelEndhostIntfTypeNumCCAInitialDelayedSuccess ConfdString,
        affirmedServiceconstructInterfaceAaaGroupDiameterStatisticsChassisLevelEndhostIntfTypeNumCCAInitialDelayedFailure ConfdString,
        affirmedServiceconstructInterfaceAaaGroupDiameterStatisticsChassisLevelEndhostIntfTypeNumCCAInitialDelayed3xxx ConfdString,
        affirmedServiceconstructInterfaceAaaGroupDiameterStatisticsChassisLevelEndhostIntfTypeNumCCAInitialRcvdFirstAttempt ConfdString,
        affirmedServiceconstructInterfaceAaaGroupDiameterStatisticsChassisLevelEndhostIntfTypeNumCCAInitialRcvdReTx ConfdString,
        affirmedServiceconstructInterfaceAaaGroupDiameterStatisticsChassisLevelEndhostIntfTypeNumCCRUpdateAttempted ConfdString,
        affirmedServiceconstructInterfaceAaaGroupDiameterStatisticsChassisLevelEndhostIntfTypeNumCCRUpdateSuccess ConfdString,
        affirmedServiceconstructInterfaceAaaGroupDiameterStatisticsChassisLevelEndhostIntfTypeNumCCRUpdateFailure ConfdString,
        affirmedServiceconstructInterfaceAaaGroupDiameterStatisticsChassisLevelEndhostIntfTypeNumCCAUpdate3xxx ConfdString,
        affirmedServiceconstructInterfaceAaaGroupDiameterStatisticsChassisLevelEndhostIntfTypeNumCCAUpdate4xxx ConfdString,
        affirmedServiceconstructInterfaceAaaGroupDiameterStatisticsChassisLevelEndhostIntfTypeNumCCAUpdate5xxx ConfdString,
        affirmedServiceconstructInterfaceAaaGroupDiameterStatisticsChassisLevelEndhostIntfTypeNumCCRUpdateTimeout ConfdString,
        affirmedServiceconstructInterfaceAaaGroupDiameterStatisticsChassisLevelEndhostIntfTypeNumCCRUpdateAborted ConfdString,
        affirmedServiceconstructInterfaceAaaGroupDiameterStatisticsChassisLevelEndhostIntfTypeNumCCAUpdateDelayedSuccess ConfdString,
        affirmedServiceconstructInterfaceAaaGroupDiameterStatisticsChassisLevelEndhostIntfTypeNumCCAUpdateDelayedFailure ConfdString,
        affirmedServiceconstructInterfaceAaaGroupDiameterStatisticsChassisLevelEndhostIntfTypeNumCCAUpdateDelayed3xxx ConfdString,
        affirmedServiceconstructInterfaceAaaGroupDiameterStatisticsChassisLevelEndhostIntfTypeNumCCAUpdateRcvdFirstAttempt ConfdString,
        affirmedServiceconstructInterfaceAaaGroupDiameterStatisticsChassisLevelEndhostIntfTypeNumCCAUpdateRcvdReTx ConfdString,
        affirmedServiceconstructInterfaceAaaGroupDiameterStatisticsChassisLevelEndhostIntfTypeNumCCRTerminateAttempted ConfdString,
        affirmedServiceconstructInterfaceAaaGroupDiameterStatisticsChassisLevelEndhostIntfTypeNumCCRTerminateSuccess ConfdString,
        affirmedServiceconstructInterfaceAaaGroupDiameterStatisticsChassisLevelEndhostIntfTypeNumCCRTerminateFailure ConfdString,
        affirmedServiceconstructInterfaceAaaGroupDiameterStatisticsChassisLevelEndhostIntfTypeNumCCATerminate3xxx ConfdString,
        affirmedServiceconstructInterfaceAaaGroupDiameterStatisticsChassisLevelEndhostIntfTypeNumCCATerminate4xxx ConfdString,
        affirmedServiceconstructInterfaceAaaGroupDiameterStatisticsChassisLevelEndhostIntfTypeNumCCATerminate5xxx ConfdString,
        affirmedServiceconstructInterfaceAaaGroupDiameterStatisticsChassisLevelEndhostIntfTypeNumCCRTerminateTimeout ConfdString,
        affirmedServiceconstructInterfaceAaaGroupDiameterStatisticsChassisLevelEndhostIntfTypeNumCCRTerminateAborted ConfdString,
        affirmedServiceconstructInterfaceAaaGroupDiameterStatisticsChassisLevelEndhostIntfTypeNumCCATerminateDelayedSuccess ConfdString,
        affirmedServiceconstructInterfaceAaaGroupDiameterStatisticsChassisLevelEndhostIntfTypeNumCCATerminateDelayedFailure ConfdString,
        affirmedServiceconstructInterfaceAaaGroupDiameterStatisticsChassisLevelEndhostIntfTypeNumCCATerminateDelayed3xxx ConfdString,
        affirmedServiceconstructInterfaceAaaGroupDiameterStatisticsChassisLevelEndhostIntfTypeNumCCATerminateRcvdFirstAttempt ConfdString,
        affirmedServiceconstructInterfaceAaaGroupDiameterStatisticsChassisLevelEndhostIntfTypeNumCCATerminateRcvdReTx ConfdString,
        affirmedServiceconstructInterfaceAaaGroupDiameterStatisticsChassisLevelEndhostIntfTypeNumCCRTerminateStoredForReplay ConfdString,
        affirmedServiceconstructInterfaceAaaGroupDiameterStatisticsChassisLevelEndhostIntfTypeNumDiameterSessions ConfdString,
        affirmedServiceconstructInterfaceAaaGroupDiameterStatisticsChassisLevelEndhostIntfTypeNumCCRTerminateReplay ConfdString,
        affirmedServiceconstructInterfaceAaaGroupDiameterStatisticsChassisLevelEndhostIntfTypeNumCCRTerminateReplayReTx ConfdString,
        affirmedServiceconstructInterfaceAaaGroupDiameterStatisticsChassisLevelEndhostIntfTypeNumCCRTerminateReplaySuccess ConfdString,
        affirmedServiceconstructInterfaceAaaGroupDiameterStatisticsChassisLevelEndhostIntfTypeNumCCRTerminateReplayFailure ConfdString,
        affirmedServiceconstructInterfaceAaaGroupDiameterStatisticsChassisLevelEndhostIntfTypeNumACRStartAttempted ConfdString,
        affirmedServiceconstructInterfaceAaaGroupDiameterStatisticsChassisLevelEndhostIntfTypeNumACRStartReTx ConfdString,
        affirmedServiceconstructInterfaceAaaGroupDiameterStatisticsChassisLevelEndhostIntfTypeNumACRStartSuccess ConfdString,
        affirmedServiceconstructInterfaceAaaGroupDiameterStatisticsChassisLevelEndhostIntfTypeNumACRStartFailure ConfdString,
        affirmedServiceconstructInterfaceAaaGroupDiameterStatisticsChassisLevelEndhostIntfTypeNumACRStartTimeout ConfdString,
        affirmedServiceconstructInterfaceAaaGroupDiameterStatisticsChassisLevelEndhostIntfTypeNumACRStartAborted ConfdString,
        affirmedServiceconstructInterfaceAaaGroupDiameterStatisticsChassisLevelEndhostIntfTypeNumACRStartDelayedSuccess ConfdString,
        affirmedServiceconstructInterfaceAaaGroupDiameterStatisticsChassisLevelEndhostIntfTypeNumACRStartDelayedFailure ConfdString,
        affirmedServiceconstructInterfaceAaaGroupDiameterStatisticsChassisLevelEndhostIntfTypeNumACRStartDropped ConfdString,
        affirmedServiceconstructInterfaceAaaGroupDiameterStatisticsChassisLevelEndhostIntfTypeNumACRStartWriteToDisk ConfdString,
        affirmedServiceconstructInterfaceAaaGroupDiameterStatisticsChassisLevelEndhostIntfTypeNumACRInterimAttempted ConfdString,
        affirmedServiceconstructInterfaceAaaGroupDiameterStatisticsChassisLevelEndhostIntfTypeNumACRInterimReTx ConfdString,
        affirmedServiceconstructInterfaceAaaGroupDiameterStatisticsChassisLevelEndhostIntfTypeNumACRInterimSuccess ConfdString,
        affirmedServiceconstructInterfaceAaaGroupDiameterStatisticsChassisLevelEndhostIntfTypeNumACRInterimFailure ConfdString,
        affirmedServiceconstructInterfaceAaaGroupDiameterStatisticsChassisLevelEndhostIntfTypeNumACRInterimTimeout ConfdString,
        affirmedServiceconstructInterfaceAaaGroupDiameterStatisticsChassisLevelEndhostIntfTypeNumACRInterimAborted ConfdString,
        affirmedServiceconstructInterfaceAaaGroupDiameterStatisticsChassisLevelEndhostIntfTypeNumACRInterimDelayedSuccess ConfdString,
        affirmedServiceconstructInterfaceAaaGroupDiameterStatisticsChassisLevelEndhostIntfTypeNumACRInterimDelayedFailure ConfdString,
        affirmedServiceconstructInterfaceAaaGroupDiameterStatisticsChassisLevelEndhostIntfTypeNumACRInterimDropped ConfdString,
        affirmedServiceconstructInterfaceAaaGroupDiameterStatisticsChassisLevelEndhostIntfTypeNumACRInterimWriteToDisk ConfdString,
        affirmedServiceconstructInterfaceAaaGroupDiameterStatisticsChassisLevelEndhostIntfTypeNumACRStopAttempted ConfdString,
        affirmedServiceconstructInterfaceAaaGroupDiameterStatisticsChassisLevelEndhostIntfTypeNumACRStopReTx ConfdString,
        affirmedServiceconstructInterfaceAaaGroupDiameterStatisticsChassisLevelEndhostIntfTypeNumACRStopSuccess ConfdString,
        affirmedServiceconstructInterfaceAaaGroupDiameterStatisticsChassisLevelEndhostIntfTypeNumACRStopFailure ConfdString,
        affirmedServiceconstructInterfaceAaaGroupDiameterStatisticsChassisLevelEndhostIntfTypeNumACRStopTimeout ConfdString,
        affirmedServiceconstructInterfaceAaaGroupDiameterStatisticsChassisLevelEndhostIntfTypeNumACRStopAborted ConfdString,
        affirmedServiceconstructInterfaceAaaGroupDiameterStatisticsChassisLevelEndhostIntfTypeNumACRStopDelayedSuccess ConfdString,
        affirmedServiceconstructInterfaceAaaGroupDiameterStatisticsChassisLevelEndhostIntfTypeNumACRStopDelayedFailure ConfdString,
        affirmedServiceconstructInterfaceAaaGroupDiameterStatisticsChassisLevelEndhostIntfTypeNumACRStopDropped ConfdString,
        affirmedServiceconstructInterfaceAaaGroupDiameterStatisticsChassisLevelEndhostIntfTypeNumACRStopWriteToDisk ConfdString,
        affirmedServiceconstructInterfaceAaaGroupDiameterStatisticsChassisLevelEndhostIntfTypeNumACREventAttempted ConfdString,
        affirmedServiceconstructInterfaceAaaGroupDiameterStatisticsChassisLevelEndhostIntfTypeNumACREventReTx ConfdString,
        affirmedServiceconstructInterfaceAaaGroupDiameterStatisticsChassisLevelEndhostIntfTypeNumACREventSuccess ConfdString,
        affirmedServiceconstructInterfaceAaaGroupDiameterStatisticsChassisLevelEndhostIntfTypeNumACREventFailure ConfdString,
        affirmedServiceconstructInterfaceAaaGroupDiameterStatisticsChassisLevelEndhostIntfTypeNumACREventTimeout ConfdString,
        affirmedServiceconstructInterfaceAaaGroupDiameterStatisticsChassisLevelEndhostIntfTypeNumACREventAborted ConfdString,
        affirmedServiceconstructInterfaceAaaGroupDiameterStatisticsChassisLevelEndhostIntfTypeNumACREventDelayedSuccess ConfdString,
        affirmedServiceconstructInterfaceAaaGroupDiameterStatisticsChassisLevelEndhostIntfTypeNumACREventDelayedFailure ConfdString,
        affirmedServiceconstructInterfaceAaaGroupDiameterStatisticsChassisLevelEndhostIntfTypeNumACREventDropped ConfdString,
        affirmedServiceconstructInterfaceAaaGroupDiameterStatisticsChassisLevelEndhostIntfTypeNumACREventWriteToDisk ConfdString,
        affirmedServiceconstructInterfaceAaaGroupDiameterStatisticsChassisLevelEndhostIntfTypeNumACRWriteToDiskFailure ConfdString,
        affirmedServiceconstructInterfaceAaaGroupDiameterStatisticsChassisLevelEndhostIntfTypeNumAARInitialAttempted ConfdString,
        affirmedServiceconstructInterfaceAaaGroupDiameterStatisticsChassisLevelEndhostIntfTypeNumAARInitialSuccess ConfdString,
        affirmedServiceconstructInterfaceAaaGroupDiameterStatisticsChassisLevelEndhostIntfTypeNumAARInitialFailure ConfdString,
        affirmedServiceconstructInterfaceAaaGroupDiameterStatisticsChassisLevelEndhostIntfTypeNumAARInitialTimeout ConfdString,
        affirmedServiceconstructInterfaceAaaGroupDiameterStatisticsChassisLevelEndhostIntfTypeNumAARAborted ConfdString,
        affirmedServiceconstructInterfaceAaaGroupDiameterStatisticsChassisLevelEndhostIntfTypeNumAAAInitialRcvdFirstAttempt ConfdString,
        affirmedServiceconstructInterfaceAaaGroupDiameterStatisticsChassisLevelEndhostIntfTypeNumAAAInitialRcvdReTx ConfdString,
        affirmedServiceconstructInterfaceAaaGroupDiameterStatisticsChassisLevelEndhostIntfTypeNumSTRAttempted ConfdString,
        affirmedServiceconstructInterfaceAaaGroupDiameterStatisticsChassisLevelEndhostIntfTypeNumSTRRetransmission ConfdString,
        affirmedServiceconstructInterfaceAaaGroupDiameterStatisticsChassisLevelEndhostIntfTypeNumSTRSuccess ConfdString,
        affirmedServiceconstructInterfaceAaaGroupDiameterStatisticsChassisLevelEndhostIntfTypeNumSTRFailure ConfdString,
        affirmedServiceconstructInterfaceAaaGroupDiameterStatisticsChassisLevelEndhostIntfTypeNumSTRTimeout ConfdString,
        affirmedServiceconstructInterfaceAaaGroupDiameterStatisticsChassisLevelEndhostIntfTypeNumSTARcvdFirstAttempt ConfdString,
        affirmedServiceconstructInterfaceAaaGroupDiameterStatisticsChassisLevelEndhostIntfTypeNumSTARcvdReTx ConfdString,
        affirmedServiceconstructInterfaceAaaGroupDiameterStatisticsChassisLevelEndhostIntfTypeNumSTRDropByPoc ConfdString,
        affirmedServiceconstructInterfaceAaaGroupDiameterStatisticsChassisLevelEndhostIntfTypeNumSTRRedirect ConfdString,
        affirmedServiceconstructInterfaceAaaGroupDiameterStatisticsChassisLevelEndhostIntfTypeNumHandoffAARAttempted ConfdString,
        affirmedServiceconstructInterfaceAaaGroupDiameterStatisticsChassisLevelEndhostIntfTypeNumHandoffAARSuccess ConfdString,
        affirmedServiceconstructInterfaceAaaGroupDiameterStatisticsChassisLevelEndhostIntfTypeNumHandoffAARFailure ConfdString,
        affirmedServiceconstructInterfaceAaaGroupDiameterStatisticsChassisLevelEndhostIntfTypeNumHandoffAARTimeout ConfdString,
        affirmedServiceconstructInterfaceAaaGroupDiameterStatisticsChassisLevelEndhostIntfTypeNumHandoffAAARcvdFirstAttempt ConfdString,
        affirmedServiceconstructInterfaceAaaGroupDiameterStatisticsChassisLevelEndhostIntfTypeNumHandoffAAARcvdReTx ConfdString,
        affirmedServiceconstructInterfaceAaaGroupDiameterStatisticsChassisLevelEndhostIntfTypeNumRarInitAARAttempted ConfdString,
        affirmedServiceconstructInterfaceAaaGroupDiameterStatisticsChassisLevelEndhostIntfTypeNumRarInitAARSuccess ConfdString,
        affirmedServiceconstructInterfaceAaaGroupDiameterStatisticsChassisLevelEndhostIntfTypeNumRarInitAARFailure ConfdString,
        affirmedServiceconstructInterfaceAaaGroupDiameterStatisticsChassisLevelEndhostIntfTypeNumRarInitAARTimeout ConfdString,
        affirmedServiceconstructInterfaceAaaGroupDiameterStatisticsChassisLevelEndhostIntfTypeNumRarInitAAARcvdFirstAttempt ConfdString,
        affirmedServiceconstructInterfaceAaaGroupDiameterStatisticsChassisLevelEndhostIntfTypeNumRarInitAAARcvdReTx ConfdString,
        affirmedServiceconstructInterfaceAaaGroupDiameterStatisticsChassisLevelEndhostIntfTypeNumRARInitAARDropByPoc ConfdString,
        affirmedServiceconstructInterfaceAaaGroupDiameterStatisticsChassisLevelEndhostIntfTypeNumRARInitAARRedirect ConfdString,
        affirmedServiceconstructInterfaceAaaGroupDiameterStatisticsChassisLevelEndhostIntfTypeNumDERInitialAttempted ConfdString,
        affirmedServiceconstructInterfaceAaaGroupDiameterStatisticsChassisLevelEndhostIntfTypeNumDERRetransmission ConfdString,
        affirmedServiceconstructInterfaceAaaGroupDiameterStatisticsChassisLevelEndhostIntfTypeNumDERInitialSuccess ConfdString,
        affirmedServiceconstructInterfaceAaaGroupDiameterStatisticsChassisLevelEndhostIntfTypeNumDERInitialFailure ConfdString,
        affirmedServiceconstructInterfaceAaaGroupDiameterStatisticsChassisLevelEndhostIntfTypeNumDERInitialTimeout ConfdString,
        affirmedServiceconstructInterfaceAaaGroupDiameterStatisticsChassisLevelEndhostIntfTypeNumDERInitialChallenge ConfdString,
        affirmedServiceconstructInterfaceAaaGroupDiameterStatisticsChassisLevelEndhostIntfTypeNumDERInitialNotification ConfdString,
        affirmedServiceconstructInterfaceAaaGroupDiameterStatisticsChassisLevelEndhostIntfTypeNumDERInitialDropByPoc ConfdString,
        affirmedServiceconstructInterfaceAaaGroupDiameterStatisticsChassisLevelEndhostIntfTypeNumDERInitialRedirect ConfdString,
        affirmedServiceconstructInterfaceAaaGroupDiameterStatisticsChassisLevelEndhostIntfTypeNumDERReAuthAttempted ConfdString,
        affirmedServiceconstructInterfaceAaaGroupDiameterStatisticsChassisLevelEndhostIntfTypeNumDERReAuthSuccess ConfdString,
        affirmedServiceconstructInterfaceAaaGroupDiameterStatisticsChassisLevelEndhostIntfTypeNumDERReAuthFailure ConfdString,
        affirmedServiceconstructInterfaceAaaGroupDiameterStatisticsChassisLevelEndhostIntfTypeNumDERReAuthTimeout ConfdString,
        affirmedServiceconstructInterfaceAaaGroupDiameterStatisticsChassisLevelEndhostIntfTypeNumDERReAuthChallenge ConfdString,
        affirmedServiceconstructInterfaceAaaGroupDiameterStatisticsChassisLevelEndhostIntfTypeNumDERReAuthNotification ConfdString,
        affirmedServiceconstructInterfaceAaaGroupDiameterStatisticsChassisLevelEndhostIntfTypeNumDERReAuthDropByPoc ConfdString,
        affirmedServiceconstructInterfaceAaaGroupDiameterStatisticsChassisLevelEndhostIntfTypeNumDERReAuthRedirect ConfdString,
        affirmedServiceconstructInterfaceAaaGroupDiameterStatisticsChassisLevelEndhostIntfTypeNumRarRcvd ConfdString,
        affirmedServiceconstructInterfaceAaaGroupDiameterStatisticsChassisLevelEndhostIntfTypeNumRarFailure ConfdString,
        affirmedServiceconstructInterfaceAaaGroupDiameterStatisticsChassisLevelEndhostIntfTypeNumAsrRcvd ConfdString,
        affirmedServiceconstructInterfaceAaaGroupDiameterStatisticsChassisLevelEndhostIntfTypeNumAsrFailure ConfdString,
        affirmedServiceconstructInterfaceAaaGroupDiameterStatisticsChassisLevelEndhostIntfTypeNumCCAInitialDroppedBadSeqNum ConfdString,
        affirmedServiceconstructInterfaceAaaGroupDiameterStatisticsChassisLevelEndhostIntfTypeNumCCAInitialDroppedNoSession ConfdString,
        affirmedServiceconstructInterfaceAaaGroupDiameterStatisticsChassisLevelEndhostIntfTypeNumCCAInitialDroppedNoProc ConfdString,
        affirmedServiceconstructInterfaceAaaGroupDiameterStatisticsChassisLevelEndhostIntfTypeNumCCAUpdateDroppedBadSeqNum ConfdString,
        affirmedServiceconstructInterfaceAaaGroupDiameterStatisticsChassisLevelEndhostIntfTypeNumCCAUpdateDroppedNoSession ConfdString,
        affirmedServiceconstructInterfaceAaaGroupDiameterStatisticsChassisLevelEndhostIntfTypeNumCCAUpdateDroppedNoProc ConfdString,
        affirmedServiceconstructInterfaceAaaGroupDiameterStatisticsChassisLevelEndhostIntfTypeNumCCATerminateDroppedBadSeqNum ConfdString,
        affirmedServiceconstructInterfaceAaaGroupDiameterStatisticsChassisLevelEndhostIntfTypeNumCCATerminateDroppedNoSession ConfdString,
        affirmedServiceconstructInterfaceAaaGroupDiameterStatisticsChassisLevelEndhostIntfTypeNumCCATerminateDroppedNoProc ConfdString,
        affirmedServiceconstructInterfaceAaaGroupDiameterStatisticsChassisLevelEndhostIntfTypeNumCCAPendingTransaction ConfdString,
        affirmedServiceconstructInterfaceAaaGroupDiameterStatisticsChassisLevelEndhostIntfTypeNumRarReceived Unsigned32,
        affirmedServiceconstructInterfaceAaaGroupDiameterStatisticsChassisLevelEndhostIntfTypeNumRaaSuccess Unsigned32,
        affirmedServiceconstructInterfaceAaaGroupDiameterStatisticsChassisLevelEndhostIntfTypeNumRaaSendFailure Unsigned32,
        affirmedServiceconstructInterfaceAaaGroupDiameterStatisticsChassisLevelEndhostIntfTypeNumRaaFailures Unsigned32,
        affirmedServiceconstructInterfaceAaaGroupDiameterStatisticsChassisLevelEndhostIntfTypeNumRaaFailuresUnknownSession Unsigned32,
        affirmedServiceconstructInterfaceAaaGroupDiameterStatisticsChassisLevelEndhostIntfTypeNumRaaFailuresMissingAVP Unsigned32,
        affirmedServiceconstructInterfaceAaaGroupDiameterStatisticsChassisLevelEndhostIntfTypeNumRaaFailuresAuthRejected Unsigned32,
        affirmedServiceconstructInterfaceAaaGroupDiameterStatisticsChassisLevelEndhostIntfTypeNumRaaFailuresAppUnsupported Unsigned32,
        affirmedServiceconstructInterfaceAaaGroupDiameterStatisticsChassisLevelEndhostIntfTypeNumRaaFailuresRealmNotServed Unsigned32,
        affirmedServiceconstructInterfaceAaaGroupDiameterStatisticsChassisLevelEndhostIntfTypeNumRaaFailuresUnableToDeliver Unsigned32,
        affirmedServiceconstructInterfaceAaaGroupDiameterStatisticsChassisLevelEndhostIntfTypeNumRaaFailuresTooBusy Unsigned32,
        affirmedServiceconstructInterfaceAaaGroupDiameterStatisticsChassisLevelEndhostIntfTypeNumRaaPendingTransaction Unsigned32,
        affirmedServiceconstructInterfaceAaaGroupDiameterStatisticsChassisLevelEndhostIntfTypeNumTimesPeerDeactivated ConfdString,
        affirmedServiceconstructInterfaceAaaGroupDiameterStatisticsChassisLevelEndhostIntfTypeNumTimesPeerFlowOffRcvd ConfdString,
        affirmedServiceconstructInterfaceAaaGroupDiameterStatisticsChassisLevelEndhostIntfTypeNumAuthLifetmrInitAARAttmpted ConfdString,
        affirmedServiceconstructInterfaceAaaGroupDiameterStatisticsChassisLevelEndhostIntfTypeNumAuthLifetimerInitAARSuccess ConfdString,
        affirmedServiceconstructInterfaceAaaGroupDiameterStatisticsChassisLevelEndhostIntfTypeNumAuthLifetimerInitAARFailure ConfdString,
        affirmedServiceconstructInterfaceAaaGroupDiameterStatisticsChassisLevelEndhostIntfTypeNumAuthLifetimerInitAARTimeout ConfdString,
        affirmedServiceconstructInterfaceAaaGroupDiameterStatisticsChassisLevelEndhostIntfTypeNumAuthLifetmrInitAAARxFirstAt ConfdString,
        affirmedServiceconstructInterfaceAaaGroupDiameterStatisticsChassisLevelEndhostIntfTypeNumAuthLifetmrInitAAARxReTx ConfdString,
        affirmedServiceconstructInterfaceAaaGroupDiameterStatisticsChassisLevelEndhostIntfTypeNumAuthLifetimerInitAARDropByPoc ConfdString,
        affirmedServiceconstructInterfaceAaaGroupDiameterStatisticsChassisLevelEndhostIntfTypeNumAuthLifetimerInitAARRedirect ConfdString,
        affirmedServiceconstructInterfaceAaaGroupDiameterStatisticsChassisLevelEndhostIntfTypeNumAuthLifetimerInitAARRetry ConfdString,
        affirmedServiceconstructInterfaceAaaGroupDiameterStatisticsChassisLevelEndhostIntfTypeNumAuthGraceTmrInitAARAtmpted ConfdString,
        affirmedServiceconstructInterfaceAaaGroupDiameterStatisticsChassisLevelEndhostIntfTypeNumAuthGraceTmrInitAARSuccess ConfdString,
        affirmedServiceconstructInterfaceAaaGroupDiameterStatisticsChassisLevelEndhostIntfTypeNumAuthGraceTmrInitAARFailure ConfdString,
        affirmedServiceconstructInterfaceAaaGroupDiameterStatisticsChassisLevelEndhostIntfTypeNumAuthGraceTmrInitAARTimeout ConfdString,
        affirmedServiceconstructInterfaceAaaGroupDiameterStatisticsChassisLevelEndhostIntfTypeNumAuthGraceTmrInitAAARxFstAt ConfdString,
        affirmedServiceconstructInterfaceAaaGroupDiameterStatisticsChassisLevelEndhostIntfTypeNumAuthGraceTmrInitAAARxReTx ConfdString,
        affirmedServiceconstructInterfaceAaaGroupDiameterStatisticsChassisLevelEndhostIntfTypeNumAuthGraceTmrInitAARRetry ConfdString,
        affirmedServiceconstructInterfaceAaaGroupDiameterStatisticsChassisLevelEndhostIntfTypeNumCCREventTx ConfdString,
        affirmedServiceconstructInterfaceAaaGroupDiameterStatisticsChassisLevelEndhostIntfTypeNumCCAEventRx ConfdString,
        affirmedServiceconstructInterfaceAaaGroupDiameterStatisticsChassisLevelEndhostIntfTypeNumCCREventTimeout ConfdString,
        affirmedServiceconstructInterfaceAaaGroupDiameterStatisticsChassisLevelEndhostIntfTypeNumNIRAttempted ConfdString,
        affirmedServiceconstructInterfaceAaaGroupDiameterStatisticsChassisLevelEndhostIntfTypeNumNIRSuccess ConfdString,
        affirmedServiceconstructInterfaceAaaGroupDiameterStatisticsChassisLevelEndhostIntfTypeNumNIRFailure ConfdString,
        affirmedServiceconstructInterfaceAaaGroupDiameterStatisticsChassisLevelEndhostIntfTypeNumNIRTimeout ConfdString,
        affirmedServiceconstructInterfaceAaaGroupDiameterStatisticsChassisLevelEndhostIntfTypeNumNIRAborted ConfdString,
        affirmedServiceconstructInterfaceAaaGroupDiameterStatisticsChassisLevelEndhostIntfTypeNumNIRcvdFirstAttempt ConfdString,
        affirmedServiceconstructInterfaceAaaGroupDiameterStatisticsChassisLevelEndhostIntfTypeNumNIARcvdReTx ConfdString,
        affirmedServiceconstructInterfaceAaaGroupDiameterStatisticsChassisLevelEndhostIntfTypeNumNIA3xxx ConfdString,
        affirmedServiceconstructInterfaceAaaGroupDiameterStatisticsChassisLevelEndhostIntfTypeNumNIA4xxx ConfdString,
        affirmedServiceconstructInterfaceAaaGroupDiameterStatisticsChassisLevelEndhostIntfTypeNumNIA5xxx ConfdString,
        affirmedServiceconstructInterfaceAaaGroupDiameterStatisticsChassisLevelEndhostIntfTypeNumNIADelayedSuccess ConfdString,
        affirmedServiceconstructInterfaceAaaGroupDiameterStatisticsChassisLevelEndhostIntfTypeNumNIADelayedFailure ConfdString,
        affirmedServiceconstructInterfaceAaaGroupDiameterStatisticsChassisLevelEndhostIntfTypeNumNIADelayed3xxx ConfdString,
        affirmedServiceconstructInterfaceAaaGroupDiameterStatisticsChassisLevelEndhostIntfTypeNumNIADroppedNoProc ConfdString,
        affirmedServiceconstructInterfaceAaaGroupDiameterStatisticsChassisLevelEndhostIntfTypeNumCIRAttempted ConfdString,
        affirmedServiceconstructInterfaceAaaGroupDiameterStatisticsChassisLevelEndhostIntfTypeNumCIRSuccess ConfdString,
        affirmedServiceconstructInterfaceAaaGroupDiameterStatisticsChassisLevelEndhostIntfTypeNumCIRFailure ConfdString,
        affirmedServiceconstructInterfaceAaaGroupDiameterStatisticsChassisLevelEndhostIntfTypeNumCIRTimeout ConfdString,
        affirmedServiceconstructInterfaceAaaGroupDiameterStatisticsChassisLevelEndhostIntfTypeNumCIRAborted ConfdString,
        affirmedServiceconstructInterfaceAaaGroupDiameterStatisticsChassisLevelEndhostIntfTypeNumCIRcvdFirstAttempt ConfdString,
        affirmedServiceconstructInterfaceAaaGroupDiameterStatisticsChassisLevelEndhostIntfTypeNumCIARcvdReTx ConfdString,
        affirmedServiceconstructInterfaceAaaGroupDiameterStatisticsChassisLevelEndhostIntfTypeNumCIA3xxx ConfdString,
        affirmedServiceconstructInterfaceAaaGroupDiameterStatisticsChassisLevelEndhostIntfTypeNumCIA4xxx ConfdString,
        affirmedServiceconstructInterfaceAaaGroupDiameterStatisticsChassisLevelEndhostIntfTypeNumCIA5xxx ConfdString,
        affirmedServiceconstructInterfaceAaaGroupDiameterStatisticsChassisLevelEndhostIntfTypeNumCIADelayedSuccess ConfdString,
        affirmedServiceconstructInterfaceAaaGroupDiameterStatisticsChassisLevelEndhostIntfTypeNumCIADelayedFailure ConfdString,
        affirmedServiceconstructInterfaceAaaGroupDiameterStatisticsChassisLevelEndhostIntfTypeNumCIADelayed3xxx ConfdString,
        affirmedServiceconstructInterfaceAaaGroupDiameterStatisticsChassisLevelEndhostIntfTypeNumCIADroppedNoProc ConfdString,
        affirmedServiceconstructInterfaceAaaGroupDiameterStatisticsChassisLevelEndhostIntfTypeNumTDRAttempted ConfdString,
        affirmedServiceconstructInterfaceAaaGroupDiameterStatisticsChassisLevelEndhostIntfTypeNumTDRSuccess ConfdString,
        affirmedServiceconstructInterfaceAaaGroupDiameterStatisticsChassisLevelEndhostIntfTypeNumTDRFailure ConfdString,
        affirmedServiceconstructInterfaceAaaGroupDiameterStatisticsChassisLevelEndhostIntfTypeNumTDRTimeout ConfdString,
        affirmedServiceconstructInterfaceAaaGroupDiameterStatisticsChassisLevelEndhostIntfTypeNumTDRAborted ConfdString,
        affirmedServiceconstructInterfaceAaaGroupDiameterStatisticsChassisLevelEndhostIntfTypeNumTDARcvdFirstAttempt ConfdString,
        affirmedServiceconstructInterfaceAaaGroupDiameterStatisticsChassisLevelEndhostIntfTypeNumTDARcvdReTx ConfdString,
        affirmedServiceconstructInterfaceAaaGroupDiameterStatisticsChassisLevelEndhostIntfTypeNumTDA3xxx ConfdString,
        affirmedServiceconstructInterfaceAaaGroupDiameterStatisticsChassisLevelEndhostIntfTypeNumTDA4xxx ConfdString,
        affirmedServiceconstructInterfaceAaaGroupDiameterStatisticsChassisLevelEndhostIntfTypeNumTDA5xxx ConfdString,
        affirmedServiceconstructInterfaceAaaGroupDiameterStatisticsChassisLevelEndhostIntfTypeNumTDADroppedNoProc ConfdString,
        affirmedServiceconstructInterfaceAaaGroupDiameterStatisticsChassisLevelEndhostIntfTypeNumCmrCReceived ConfdString,
        affirmedServiceconstructInterfaceAaaGroupDiameterStatisticsChassisLevelEndhostIntfTypeNumCMACSuccess ConfdString,
        affirmedServiceconstructInterfaceAaaGroupDiameterStatisticsChassisLevelEndhostIntfTypeNumCMACFailures ConfdString,
        affirmedServiceconstructInterfaceAaaGroupDiameterStatisticsChassisLevelEndhostIntfTypeNumCMACFailuresUnknownSession ConfdString,
        affirmedServiceconstructInterfaceAaaGroupDiameterStatisticsChassisLevelEndhostIntfTypeNumCMACFailuresMissingAVP ConfdString,
        affirmedServiceconstructInterfaceAaaGroupDiameterStatisticsChassisLevelEndhostIntfTypeNumCmrUReceived ConfdString,
        affirmedServiceconstructInterfaceAaaGroupDiameterStatisticsChassisLevelEndhostIntfTypeNumCMAUSuccess ConfdString,
        affirmedServiceconstructInterfaceAaaGroupDiameterStatisticsChassisLevelEndhostIntfTypeNumCMAUFailures ConfdString,
        affirmedServiceconstructInterfaceAaaGroupDiameterStatisticsChassisLevelEndhostIntfTypeNumCMAUFailuresUnknownSession ConfdString,
        affirmedServiceconstructInterfaceAaaGroupDiameterStatisticsChassisLevelEndhostIntfTypeNumCMAUFailuresMissingAVP ConfdString,
        affirmedServiceconstructInterfaceAaaGroupDiameterStatisticsChassisLevelEndhostIntfTypeNumCmrRReceived ConfdString,
        affirmedServiceconstructInterfaceAaaGroupDiameterStatisticsChassisLevelEndhostIntfTypeNumCMARSuccess ConfdString,
        affirmedServiceconstructInterfaceAaaGroupDiameterStatisticsChassisLevelEndhostIntfTypeNumCMARFailures ConfdString,
        affirmedServiceconstructInterfaceAaaGroupDiameterStatisticsChassisLevelEndhostIntfTypeNumCMARFailuresUnknownSession ConfdString,
        affirmedServiceconstructInterfaceAaaGroupDiameterStatisticsChassisLevelEndhostIntfTypeNumCMARFailuresMissingAVP ConfdString,
        affirmedServiceconstructInterfaceAaaGroupDiameterStatisticsChassisLevelEndhostIntfTypeNumCMRRScefInitAttempted ConfdString,
        affirmedServiceconstructInterfaceAaaGroupDiameterStatisticsChassisLevelEndhostIntfTypeNumCMRRScefInitSuccess ConfdString,
        affirmedServiceconstructInterfaceAaaGroupDiameterStatisticsChassisLevelEndhostIntfTypeNumCMRRScefInitFailure ConfdString,
        affirmedServiceconstructInterfaceAaaGroupDiameterStatisticsChassisLevelEndhostIntfTypeNumCMRRScefInitTimeout ConfdString,
        affirmedServiceconstructInterfaceAaaGroupDiameterStatisticsChassisLevelEndhostIntfTypeNumCMRRScefInitAborted ConfdString,
        affirmedServiceconstructInterfaceAaaGroupDiameterStatisticsChassisLevelEndhostIntfTypeNumCMARScefInitRcvdFirstAttempt ConfdString,
        affirmedServiceconstructInterfaceAaaGroupDiameterStatisticsChassisLevelEndhostIntfTypeNumCMARScefInitRcvdReTx ConfdString,
        affirmedServiceconstructInterfaceAaaGroupDiameterStatisticsChassisLevelEndhostIntfTypeNumCMARScefInit3xxx ConfdString,
        affirmedServiceconstructInterfaceAaaGroupDiameterStatisticsChassisLevelEndhostIntfTypeNumCMARScefInit4xxx ConfdString,
        affirmedServiceconstructInterfaceAaaGroupDiameterStatisticsChassisLevelEndhostIntfTypeNumCMARScefInit5xxx ConfdString,
        affirmedServiceconstructInterfaceAaaGroupDiameterStatisticsChassisLevelEndhostIntfTypeNumCMARScefInitDroppedNoProc ConfdString,
        affirmedServiceconstructInterfaceAaaGroupDiameterStatisticsChassisLevelEndhostIntfTypeNumODRReceived ConfdString,
        affirmedServiceconstructInterfaceAaaGroupDiameterStatisticsChassisLevelEndhostIntfTypeNumODASuccess ConfdString,
        affirmedServiceconstructInterfaceAaaGroupDiameterStatisticsChassisLevelEndhostIntfTypeNumODAFailures ConfdString,
        affirmedServiceconstructInterfaceAaaGroupDiameterStatisticsChassisLevelEndhostIntfTypeNumODAFailuresUnknownSession ConfdString,
        affirmedServiceconstructInterfaceAaaGroupDiameterStatisticsChassisLevelEndhostIntfTypeNumODAFailuresMissingAVP ConfdString,
        affirmedServiceconstructInterfaceAaaGroupDiameterStatisticsChassisLevelEndhostIntfTypeNumODAFailuresUnableToDeliver ConfdString,
        affirmedServiceconstructInterfaceAaaGroupDiameterStatisticsChassisLevelEndhostIntfTypeNumRIRReceived ConfdString,
        affirmedServiceconstructInterfaceAaaGroupDiameterStatisticsChassisLevelEndhostIntfTypeNumRIASuccess ConfdString,
        affirmedServiceconstructInterfaceAaaGroupDiameterStatisticsChassisLevelEndhostIntfTypeNumRIAFailures ConfdString,
        affirmedServiceconstructInterfaceAaaGroupDiameterStatisticsChassisLevelEndhostIntfTypeNumRIAFailuresUnknownScefRefId ConfdString,
        affirmedServiceconstructInterfaceAaaGroupDiameterStatisticsChassisLevelEndhostIntfTypeNumRIAFailuresUnknownSession ConfdString,
        affirmedServiceconstructInterfaceAaaGroupDiameterStatisticsChassisLevelEndhostIntfTypeNumRIAFailuresMissingAVP ConfdString,
        affirmedServiceconstructInterfaceAaaGroupDiameterStatisticsChassisLevelEndhostIntfTypeNumRIAFailuresUnableToDeliver ConfdString,
        affirmedServiceconstructInterfaceAaaGroupDiameterStatisticsChassisLevelEndhostIntfTypeNumSIRAttempted ConfdString,
        affirmedServiceconstructInterfaceAaaGroupDiameterStatisticsChassisLevelEndhostIntfTypeNumSIRSuccess ConfdString,
        affirmedServiceconstructInterfaceAaaGroupDiameterStatisticsChassisLevelEndhostIntfTypeNumSIRFailure ConfdString,
        affirmedServiceconstructInterfaceAaaGroupDiameterStatisticsChassisLevelEndhostIntfTypeNumSIRTimeout ConfdString,
        affirmedServiceconstructInterfaceAaaGroupDiameterStatisticsChassisLevelEndhostIntfTypeNumSIRAborted ConfdString,
        affirmedServiceconstructInterfaceAaaGroupDiameterStatisticsChassisLevelEndhostIntfTypeNumSIRcvdFirstAttempt ConfdString,
        affirmedServiceconstructInterfaceAaaGroupDiameterStatisticsChassisLevelEndhostIntfTypeNumSIARcvdReTx ConfdString,
        affirmedServiceconstructInterfaceAaaGroupDiameterStatisticsChassisLevelEndhostIntfTypeNumSIA3xxx ConfdString,
        affirmedServiceconstructInterfaceAaaGroupDiameterStatisticsChassisLevelEndhostIntfTypeNumSIA4xxx ConfdString,
        affirmedServiceconstructInterfaceAaaGroupDiameterStatisticsChassisLevelEndhostIntfTypeNumSIA5xxx ConfdString,
        affirmedServiceconstructInterfaceAaaGroupDiameterStatisticsChassisLevelEndhostIntfTypeNumSIADelayedSuccess ConfdString,
        affirmedServiceconstructInterfaceAaaGroupDiameterStatisticsChassisLevelEndhostIntfTypeNumSIADelayedFailure ConfdString,
        affirmedServiceconstructInterfaceAaaGroupDiameterStatisticsChassisLevelEndhostIntfTypeNumSIADelayed3xxx ConfdString,
        affirmedServiceconstructInterfaceAaaGroupDiameterStatisticsChassisLevelEndhostIntfTypeNumSIADroppedNoProc ConfdString,
        affirmedServiceconstructInterfaceAaaGroupDiameterStatisticsChassisLevelEndhostIntfTypeNumDTRAttempted ConfdString,
        affirmedServiceconstructInterfaceAaaGroupDiameterStatisticsChassisLevelEndhostIntfTypeNumDTRSuccess ConfdString,
        affirmedServiceconstructInterfaceAaaGroupDiameterStatisticsChassisLevelEndhostIntfTypeNumDTRFailure ConfdString,
        affirmedServiceconstructInterfaceAaaGroupDiameterStatisticsChassisLevelEndhostIntfTypeNumDTRTimeout ConfdString,
        affirmedServiceconstructInterfaceAaaGroupDiameterStatisticsChassisLevelEndhostIntfTypeNumDTRAborted ConfdString,
        affirmedServiceconstructInterfaceAaaGroupDiameterStatisticsChassisLevelEndhostIntfTypeNumDTRcvdFirstAttempt ConfdString,
        affirmedServiceconstructInterfaceAaaGroupDiameterStatisticsChassisLevelEndhostIntfTypeNumDTARcvdReTx ConfdString,
        affirmedServiceconstructInterfaceAaaGroupDiameterStatisticsChassisLevelEndhostIntfTypeNumDTA3xxx ConfdString,
        affirmedServiceconstructInterfaceAaaGroupDiameterStatisticsChassisLevelEndhostIntfTypeNumDTA4xxx ConfdString,
        affirmedServiceconstructInterfaceAaaGroupDiameterStatisticsChassisLevelEndhostIntfTypeNumDTA5xxx ConfdString,
        affirmedServiceconstructInterfaceAaaGroupDiameterStatisticsChassisLevelEndhostIntfTypeNumDTADelayedSuccess ConfdString,
        affirmedServiceconstructInterfaceAaaGroupDiameterStatisticsChassisLevelEndhostIntfTypeNumDTADelayedFailure ConfdString,
        affirmedServiceconstructInterfaceAaaGroupDiameterStatisticsChassisLevelEndhostIntfTypeNumDTADelayed3xxx ConfdString,
        affirmedServiceconstructInterfaceAaaGroupDiameterStatisticsChassisLevelEndhostIntfTypeNumDTADroppedNoProc ConfdString,
        affirmedServiceconstructInterfaceAaaGroupDiameterStatisticsChassisLevelEndhostIntfTypeNumDTRTriggerAttempted ConfdString,
        affirmedServiceconstructInterfaceAaaGroupDiameterStatisticsChassisLevelEndhostIntfTypeNumDTRTriggerSuccess ConfdString,
        affirmedServiceconstructInterfaceAaaGroupDiameterStatisticsChassisLevelEndhostIntfTypeNumDTRTriggerFailure ConfdString,
        affirmedServiceconstructInterfaceAaaGroupDiameterStatisticsChassisLevelEndhostIntfTypeNumDTRTriggerTimeout ConfdString,
        affirmedServiceconstructInterfaceAaaGroupDiameterStatisticsChassisLevelEndhostIntfTypeNumDTRTriggerAborted ConfdString,
        affirmedServiceconstructInterfaceAaaGroupDiameterStatisticsChassisLevelEndhostIntfTypeNumDTRTriggercvdFirstAttempt ConfdString,
        affirmedServiceconstructInterfaceAaaGroupDiameterStatisticsChassisLevelEndhostIntfTypeNumDTATriggerRcvdReTx ConfdString,
        affirmedServiceconstructInterfaceAaaGroupDiameterStatisticsChassisLevelEndhostIntfTypeNumDTATrigger3xxx ConfdString,
        affirmedServiceconstructInterfaceAaaGroupDiameterStatisticsChassisLevelEndhostIntfTypeNumDTATrigger4xxx ConfdString,
        affirmedServiceconstructInterfaceAaaGroupDiameterStatisticsChassisLevelEndhostIntfTypeNumDTATrigger5xxx ConfdString,
        affirmedServiceconstructInterfaceAaaGroupDiameterStatisticsChassisLevelEndhostIntfTypeNumDTATriggerDelayedSuccess ConfdString,
        affirmedServiceconstructInterfaceAaaGroupDiameterStatisticsChassisLevelEndhostIntfTypeNumDTATriggerDelayedFailure ConfdString,
        affirmedServiceconstructInterfaceAaaGroupDiameterStatisticsChassisLevelEndhostIntfTypeNumDTATriggerDelayed3xxx ConfdString,
        affirmedServiceconstructInterfaceAaaGroupDiameterStatisticsChassisLevelEndhostIntfTypeNumDTATriggerDroppedNoProc ConfdString,
        affirmedServiceconstructInterfaceAaaGroupDiameterStatisticsChassisLevelEndhostIntfTypeNumDTRRecallAttempted ConfdString,
        affirmedServiceconstructInterfaceAaaGroupDiameterStatisticsChassisLevelEndhostIntfTypeNumDTRRecallSuccess ConfdString,
        affirmedServiceconstructInterfaceAaaGroupDiameterStatisticsChassisLevelEndhostIntfTypeNumDTRRecallFailure ConfdString,
        affirmedServiceconstructInterfaceAaaGroupDiameterStatisticsChassisLevelEndhostIntfTypeNumDTRRecallTimeout ConfdString,
        affirmedServiceconstructInterfaceAaaGroupDiameterStatisticsChassisLevelEndhostIntfTypeNumDTRRecallAborted ConfdString,
        affirmedServiceconstructInterfaceAaaGroupDiameterStatisticsChassisLevelEndhostIntfTypeNumDTRRecallcvdFirstAttempt ConfdString,
        affirmedServiceconstructInterfaceAaaGroupDiameterStatisticsChassisLevelEndhostIntfTypeNumDTARecallRcvdReTx ConfdString,
        affirmedServiceconstructInterfaceAaaGroupDiameterStatisticsChassisLevelEndhostIntfTypeNumDTARecall3xxx ConfdString,
        affirmedServiceconstructInterfaceAaaGroupDiameterStatisticsChassisLevelEndhostIntfTypeNumDTARecall4xxx ConfdString,
        affirmedServiceconstructInterfaceAaaGroupDiameterStatisticsChassisLevelEndhostIntfTypeNumDTARecall5xxx ConfdString,
        affirmedServiceconstructInterfaceAaaGroupDiameterStatisticsChassisLevelEndhostIntfTypeNumDTARecallDelayedSuccess ConfdString,
        affirmedServiceconstructInterfaceAaaGroupDiameterStatisticsChassisLevelEndhostIntfTypeNumDTARecallDelayedFailure ConfdString,
        affirmedServiceconstructInterfaceAaaGroupDiameterStatisticsChassisLevelEndhostIntfTypeNumDTARecallDelayed3xxx ConfdString,
        affirmedServiceconstructInterfaceAaaGroupDiameterStatisticsChassisLevelEndhostIntfTypeNumDTARecallDroppedNoProc ConfdString,
        affirmedServiceconstructInterfaceAaaGroupDiameterStatisticsChassisLevelEndhostIntfTypeNumDTRReplaceAttempted ConfdString,
        affirmedServiceconstructInterfaceAaaGroupDiameterStatisticsChassisLevelEndhostIntfTypeNumDTRReplaceSuccess ConfdString,
        affirmedServiceconstructInterfaceAaaGroupDiameterStatisticsChassisLevelEndhostIntfTypeNumDTRReplaceFailure ConfdString,
        affirmedServiceconstructInterfaceAaaGroupDiameterStatisticsChassisLevelEndhostIntfTypeNumDTRReplaceTimeout ConfdString,
        affirmedServiceconstructInterfaceAaaGroupDiameterStatisticsChassisLevelEndhostIntfTypeNumDTRReplaceAborted ConfdString,
        affirmedServiceconstructInterfaceAaaGroupDiameterStatisticsChassisLevelEndhostIntfTypeNumDTRReplacecvdFirstAttempt ConfdString,
        affirmedServiceconstructInterfaceAaaGroupDiameterStatisticsChassisLevelEndhostIntfTypeNumDTAReplaceRcvdReTx ConfdString,
        affirmedServiceconstructInterfaceAaaGroupDiameterStatisticsChassisLevelEndhostIntfTypeNumDTAReplace3xxx ConfdString,
        affirmedServiceconstructInterfaceAaaGroupDiameterStatisticsChassisLevelEndhostIntfTypeNumDTAReplace4xxx ConfdString,
        affirmedServiceconstructInterfaceAaaGroupDiameterStatisticsChassisLevelEndhostIntfTypeNumDTAReplace5xxx ConfdString,
        affirmedServiceconstructInterfaceAaaGroupDiameterStatisticsChassisLevelEndhostIntfTypeNumDTAReplaceDelayedSuccess ConfdString,
        affirmedServiceconstructInterfaceAaaGroupDiameterStatisticsChassisLevelEndhostIntfTypeNumDTAReplaceDelayedFailure ConfdString,
        affirmedServiceconstructInterfaceAaaGroupDiameterStatisticsChassisLevelEndhostIntfTypeNumDTAReplaceDelayed3xxx ConfdString,
        affirmedServiceconstructInterfaceAaaGroupDiameterStatisticsChassisLevelEndhostIntfTypeNumDTAReplaceDroppedNoProc ConfdString,
        affirmedServiceconstructInterfaceAaaGroupDiameterStatisticsChassisLevelEndhostIntfTypeNumDRRReceived ConfdString,
        affirmedServiceconstructInterfaceAaaGroupDiameterStatisticsChassisLevelEndhostIntfTypeNumDRASuccess ConfdString,
        affirmedServiceconstructInterfaceAaaGroupDiameterStatisticsChassisLevelEndhostIntfTypeNumDRAFailures ConfdString,
        affirmedServiceconstructInterfaceAaaGroupDiameterStatisticsChassisLevelEndhostIntfTypeNumDRAFailuresUnknownRefId ConfdString,
        affirmedServiceconstructInterfaceAaaGroupDiameterStatisticsChassisLevelEndhostIntfTypeNumDRAFailuresUnknownSession ConfdString,
        affirmedServiceconstructInterfaceAaaGroupDiameterStatisticsChassisLevelEndhostIntfTypeNumDRAFailuresMissingAVP ConfdString,
        affirmedServiceconstructInterfaceAaaGroupDiameterStatisticsChassisLevelEndhostIntfTypeNumDRAFailuresUnableToDeliver ConfdString,
        affirmedServiceconstructInterfaceAaaGroupDiameterStatisticsChassisLevelEndhostIntfTypeNumTsrReceived Unsigned32,
        affirmedServiceconstructInterfaceAaaGroupDiameterStatisticsChassisLevelEndhostIntfTypeNumTsaSuccess Unsigned32,
        affirmedServiceconstructInterfaceAaaGroupDiameterStatisticsChassisLevelEndhostIntfTypeNumTsaFailures Unsigned32,
        affirmedServiceconstructInterfaceAaaGroupDiameterStatisticsChassisLevelEndhostIntfTypeNumAAAInitialDelayedSuccess ConfdString,
        affirmedServiceconstructInterfaceAaaGroupDiameterStatisticsChassisLevelEndhostIntfTypeNumAAAInitialDelayedFailure ConfdString,
        affirmedServiceconstructInterfaceAaaGroupDiameterStatisticsChassisLevelEndhostIntfTypeNumAAAInitialDelayed3xxx ConfdString,
        affirmedServiceconstructInterfaceAaaGroupDiameterStatisticsChassisLevelEndhostIntfTypeNumCommandUnsupported ConfdString,
        affirmedServiceconstructInterfaceAaaGroupDiameterStatisticsChassisLevelEndhostIntfTypeNumUnableToDeliver ConfdString,
        affirmedServiceconstructInterfaceAaaGroupDiameterStatisticsChassisLevelEndhostIntfTypeNumRealmNotServed ConfdString,
        affirmedServiceconstructInterfaceAaaGroupDiameterStatisticsChassisLevelEndhostIntfTypeNumTooBusy ConfdString,
        affirmedServiceconstructInterfaceAaaGroupDiameterStatisticsChassisLevelEndhostIntfTypeNumLoopDetected ConfdString,
        affirmedServiceconstructInterfaceAaaGroupDiameterStatisticsChassisLevelEndhostIntfTypeNumRedirectIndication ConfdString,
        affirmedServiceconstructInterfaceAaaGroupDiameterStatisticsChassisLevelEndhostIntfTypeNumApplicationUnsupported ConfdString,
        affirmedServiceconstructInterfaceAaaGroupDiameterStatisticsChassisLevelEndhostIntfTypeNumInvalidHdrBits ConfdString,
        affirmedServiceconstructInterfaceAaaGroupDiameterStatisticsChassisLevelEndhostIntfTypeNumInvalidAvpBits ConfdString,
        affirmedServiceconstructInterfaceAaaGroupDiameterStatisticsChassisLevelEndhostIntfTypeNumUnknownPeer ConfdString,
        affirmedServiceconstructInterfaceAaaGroupDiameterStatisticsChassisLevelEndhostIntfTypeNumAuthenticationRejected ConfdString,
        affirmedServiceconstructInterfaceAaaGroupDiameterStatisticsChassisLevelEndhostIntfTypeNumOutOfSpace ConfdString,
        affirmedServiceconstructInterfaceAaaGroupDiameterStatisticsChassisLevelEndhostIntfTypeNumElectionLost ConfdString,
        affirmedServiceconstructInterfaceAaaGroupDiameterStatisticsChassisLevelEndhostIntfTypeNumAvpUnsupported ConfdString,
        affirmedServiceconstructInterfaceAaaGroupDiameterStatisticsChassisLevelEndhostIntfTypeNumUnknownSessionId ConfdString,
        affirmedServiceconstructInterfaceAaaGroupDiameterStatisticsChassisLevelEndhostIntfTypeNumAuthorizationRejected ConfdString,
        affirmedServiceconstructInterfaceAaaGroupDiameterStatisticsChassisLevelEndhostIntfTypeNumInvalidAvpValue ConfdString,
        affirmedServiceconstructInterfaceAaaGroupDiameterStatisticsChassisLevelEndhostIntfTypeNumMissingAvp ConfdString,
        affirmedServiceconstructInterfaceAaaGroupDiameterStatisticsChassisLevelEndhostIntfTypeNumResourcesExceeded ConfdString,
        affirmedServiceconstructInterfaceAaaGroupDiameterStatisticsChassisLevelEndhostIntfTypeNumContradictingAvps ConfdString,
        affirmedServiceconstructInterfaceAaaGroupDiameterStatisticsChassisLevelEndhostIntfTypeNumAvpNotAllowed ConfdString,
        affirmedServiceconstructInterfaceAaaGroupDiameterStatisticsChassisLevelEndhostIntfTypeNumOccursTooManyTimes ConfdString,
        affirmedServiceconstructInterfaceAaaGroupDiameterStatisticsChassisLevelEndhostIntfTypeNumNoCommonApplication ConfdString,
        affirmedServiceconstructInterfaceAaaGroupDiameterStatisticsChassisLevelEndhostIntfTypeNumUnableToComply ConfdString,
        affirmedServiceconstructInterfaceAaaGroupDiameterStatisticsChassisLevelEndhostIntfTypeNumInvalidBitInHdr ConfdString,
        affirmedServiceconstructInterfaceAaaGroupDiameterStatisticsChassisLevelEndhostIntfTypeNumInvalidAvpLength ConfdString,
        affirmedServiceconstructInterfaceAaaGroupDiameterStatisticsChassisLevelEndhostIntfTypeNumInvalidMessageLength ConfdString,
        affirmedServiceconstructInterfaceAaaGroupDiameterStatisticsChassisLevelEndhostIntfTypeNumInvalidAvpBitCombo ConfdString,
        affirmedServiceconstructInterfaceAaaGroupDiameterStatisticsChassisLevelEndhostIntfTypeNumNoCommonSecurity ConfdString,
        affirmedServiceconstructInterfaceAaaGroupDiameterStatisticsChassisLevelEndhostIntfTypeNumUserUnknown ConfdString,
        affirmedServiceconstructInterfaceAaaGroupDiameterStatisticsChassisLevelEndhostIntfTypeNumRoamingNotAllowed ConfdString,
        affirmedServiceconstructInterfaceAaaGroupDiameterStatisticsChassisLevelEndhostIntfTypeNumIdentityAlreadyRegistered ConfdString,
        affirmedServiceconstructInterfaceAaaGroupDiameterStatisticsChassisLevelEndhostIntfTypeNumOverloadRetryNotAllowed ConfdString,
        affirmedServiceconstructInterfaceAaaGroupDiameterStatisticsChassisLevelEndhostIntfTypeNumUnknownEpsSubscription ConfdString,
        affirmedServiceconstructInterfaceAaaGroupDiameterStatisticsChassisLevelEndhostIntfTypeNumUserNoNonGppSubscription ConfdString,
        affirmedServiceconstructInterfaceAaaGroupDiameterStatisticsChassisLevelEndhostIntfTypeNumUserNoApnSubscription ConfdString,
        affirmedServiceconstructInterfaceAaaGroupDiameterStatisticsChassisLevelEndhostIntfTypeNumRatTypeNotAllowed ConfdString,
        affirmedServiceconstructInterfaceAaaGroupDiameterStatisticsChassisLevelEndhostIntfTypeNumLateOverlappingRequest ConfdString,
        affirmedServiceconstructInterfaceAaaGroupDiameterStatisticsChassisLevelEndhostIntfTypeNumTimedOutRequest ConfdString
    }

affirmedServiceconstructInterfaceAaaGroupDiameterStatisticsChassisLevelEndhostIntfTypeIntfType OBJECT-TYPE
    SYNTAX      String
    MAX-ACCESS  not-accessible
    STATUS      current
    DESCRIPTION "Diameter Interface Type: GX/GY/GZ/S6B/STA/SWM/S6T/T6A/T4/S6M/SWM/FLOWAUTH/SXAB/SD"
    ::= { affirmedServiceconstructInterfaceAaaGroupDiameterStatisticsChassisLevelEndhostIntfTypeEntry 1 }

affirmedServiceconstructInterfaceAaaGroupDiameterStatisticsChassisLevelEndhostIntfTypeNodeName OBJECT-TYPE
    SYNTAX      String
    MAX-ACCESS  not-accessible
    STATUS      current
    DESCRIPTION "Local Diameter Node Name"
    ::= { affirmedServiceconstructInterfaceAaaGroupDiameterStatisticsChassisLevelEndhostIntfTypeEntry 2 }

affirmedServiceconstructInterfaceAaaGroupDiameterStatisticsChassisLevelEndhostIntfTypeDraName OBJECT-TYPE
    SYNTAX      String
    MAX-ACCESS  not-accessible
    STATUS      current
    DESCRIPTION "DRA name"
    ::= { affirmedServiceconstructInterfaceAaaGroupDiameterStatisticsChassisLevelEndhostIntfTypeEntry 3 }

affirmedServiceconstructInterfaceAaaGroupDiameterStatisticsChassisLevelEndhostIntfTypeEndHostName OBJECT-TYPE
    SYNTAX      String
    MAX-ACCESS  not-accessible
    STATUS      current
    DESCRIPTION "End Host name"
    ::= { affirmedServiceconstructInterfaceAaaGroupDiameterStatisticsChassisLevelEndhostIntfTypeEntry 4 }

affirmedServiceconstructInterfaceAaaGroupDiameterStatisticsChassisLevelEndhostIntfTypeNumCCRInitialAttempted OBJECT-TYPE
    SYNTAX      ConfdString
    MAX-ACCESS  read-only
    STATUS      current
    DESCRIPTION "Number of CCR Initial attempts made"
    ::= { affirmedServiceconstructInterfaceAaaGroupDiameterStatisticsChassisLevelEndhostIntfTypeEntry 5 }

affirmedServiceconstructInterfaceAaaGroupDiameterStatisticsChassisLevelEndhostIntfTypeNumCCRInitialSuccess OBJECT-TYPE
    SYNTAX      ConfdString
    MAX-ACCESS  read-only
    STATUS      current
    DESCRIPTION "Number of successful CCR Initial attempts"
    ::= { affirmedServiceconstructInterfaceAaaGroupDiameterStatisticsChassisLevelEndhostIntfTypeEntry 6 }

affirmedServiceconstructInterfaceAaaGroupDiameterStatisticsChassisLevelEndhostIntfTypeNumCCRInitialFailure OBJECT-TYPE
    SYNTAX      ConfdString
    MAX-ACCESS  read-only
    STATUS      current
    DESCRIPTION "Number of failed CCR Initial attempts"
    ::= { affirmedServiceconstructInterfaceAaaGroupDiameterStatisticsChassisLevelEndhostIntfTypeEntry 7 }

affirmedServiceconstructInterfaceAaaGroupDiameterStatisticsChassisLevelEndhostIntfTypeNumCCAInitial3xxx OBJECT-TYPE
    SYNTAX      ConfdString
    MAX-ACCESS  read-only
    STATUS      current
    DESCRIPTION "Number of failed CCR Initial attempts due to 3xx error"
    ::= { affirmedServiceconstructInterfaceAaaGroupDiameterStatisticsChassisLevelEndhostIntfTypeEntry 8 }

affirmedServiceconstructInterfaceAaaGroupDiameterStatisticsChassisLevelEndhostIntfTypeNumCCAInitial4xxx OBJECT-TYPE
    SYNTAX      ConfdString
    MAX-ACCESS  read-only
    STATUS      current
    DESCRIPTION "Number of CCA Initial received with 4xx errors"
    ::= { affirmedServiceconstructInterfaceAaaGroupDiameterStatisticsChassisLevelEndhostIntfTypeEntry 9 }

affirmedServiceconstructInterfaceAaaGroupDiameterStatisticsChassisLevelEndhostIntfTypeNumCCAInitial5xxx OBJECT-TYPE
    SYNTAX      ConfdString
    MAX-ACCESS  read-only
    STATUS      current
    DESCRIPTION "Number of failed CCA Initial received with 5xx error"
    ::= { affirmedServiceconstructInterfaceAaaGroupDiameterStatisticsChassisLevelEndhostIntfTypeEntry 10 }

affirmedServiceconstructInterfaceAaaGroupDiameterStatisticsChassisLevelEndhostIntfTypeNumCCRInitialTimeout OBJECT-TYPE
    SYNTAX      ConfdString
    MAX-ACCESS  read-only
    STATUS      current
    DESCRIPTION "Number of CCR Initial attempts that timed out"
    ::= { affirmedServiceconstructInterfaceAaaGroupDiameterStatisticsChassisLevelEndhostIntfTypeEntry 11 }

affirmedServiceconstructInterfaceAaaGroupDiameterStatisticsChassisLevelEndhostIntfTypeNumCCRInitialAborted OBJECT-TYPE
    SYNTAX      ConfdString
    MAX-ACCESS  read-only
    STATUS      current
    DESCRIPTION "Number of CCR Initial attempts that were aborted due to response received from another peer"
    ::= { affirmedServiceconstructInterfaceAaaGroupDiameterStatisticsChassisLevelEndhostIntfTypeEntry 12 }

affirmedServiceconstructInterfaceAaaGroupDiameterStatisticsChassisLevelEndhostIntfTypeNumCCAInitialDelayedSuccess OBJECT-TYPE
    SYNTAX      ConfdString
    MAX-ACCESS  read-only
    STATUS      current
    DESCRIPTION "Number of CCA Initial success which were received after the request had been re-transmitted to another server"
    ::= { affirmedServiceconstructInterfaceAaaGroupDiameterStatisticsChassisLevelEndhostIntfTypeEntry 13 }

affirmedServiceconstructInterfaceAaaGroupDiameterStatisticsChassisLevelEndhostIntfTypeNumCCAInitialDelayedFailure OBJECT-TYPE
    SYNTAX      ConfdString
    MAX-ACCESS  read-only
    STATUS      current
    DESCRIPTION "Number of CCA Initial failures which were received after the request had been re-transmitted to another server"
    ::= { affirmedServiceconstructInterfaceAaaGroupDiameterStatisticsChassisLevelEndhostIntfTypeEntry 14 }

affirmedServiceconstructInterfaceAaaGroupDiameterStatisticsChassisLevelEndhostIntfTypeNumCCAInitialDelayed3xxx OBJECT-TYPE
    SYNTAX      ConfdString
    MAX-ACCESS  read-only
    STATUS      current
    DESCRIPTION "Number of delayed CCA Initial 3xx error which were received after the request had been re-transmitted to another server"
    ::= { affirmedServiceconstructInterfaceAaaGroupDiameterStatisticsChassisLevelEndhostIntfTypeEntry 15 }

affirmedServiceconstructInterfaceAaaGroupDiameterStatisticsChassisLevelEndhostIntfTypeNumCCAInitialRcvdFirstAttempt OBJECT-TYPE
    SYNTAX      ConfdString
    MAX-ACCESS  read-only
    STATUS      current
    DESCRIPTION "Number of CCR Initial requests for which response was received when first transmitted "
    ::= { affirmedServiceconstructInterfaceAaaGroupDiameterStatisticsChassisLevelEndhostIntfTypeEntry 16 }

affirmedServiceconstructInterfaceAaaGroupDiameterStatisticsChassisLevelEndhostIntfTypeNumCCAInitialRcvdReTx OBJECT-TYPE
    SYNTAX      ConfdString
    MAX-ACCESS  read-only
    STATUS      current
    DESCRIPTION "Number of CCR Initial Requests for which response was received when message was retransmitted"
    ::= { affirmedServiceconstructInterfaceAaaGroupDiameterStatisticsChassisLevelEndhostIntfTypeEntry 17 }

affirmedServiceconstructInterfaceAaaGroupDiameterStatisticsChassisLevelEndhostIntfTypeNumCCRUpdateAttempted OBJECT-TYPE
    SYNTAX      ConfdString
    MAX-ACCESS  read-only
    STATUS      current
    DESCRIPTION "Number of CCR Update attempts made"
    ::= { affirmedServiceconstructInterfaceAaaGroupDiameterStatisticsChassisLevelEndhostIntfTypeEntry 18 }

affirmedServiceconstructInterfaceAaaGroupDiameterStatisticsChassisLevelEndhostIntfTypeNumCCRUpdateSuccess OBJECT-TYPE
    SYNTAX      ConfdString
    MAX-ACCESS  read-only
    STATUS      current
    DESCRIPTION "Number of successful CCR Update attempts"
    ::= { affirmedServiceconstructInterfaceAaaGroupDiameterStatisticsChassisLevelEndhostIntfTypeEntry 19 }

affirmedServiceconstructInterfaceAaaGroupDiameterStatisticsChassisLevelEndhostIntfTypeNumCCRUpdateFailure OBJECT-TYPE
    SYNTAX      ConfdString
    MAX-ACCESS  read-only
    STATUS      current
    DESCRIPTION "Number of failed CCR Update attempts"
    ::= { affirmedServiceconstructInterfaceAaaGroupDiameterStatisticsChassisLevelEndhostIntfTypeEntry 20 }

affirmedServiceconstructInterfaceAaaGroupDiameterStatisticsChassisLevelEndhostIntfTypeNumCCAUpdate3xxx OBJECT-TYPE
    SYNTAX      ConfdString
    MAX-ACCESS  read-only
    STATUS      current
    DESCRIPTION "Number of failed CCR Update attempts due to 3xx error"
    ::= { affirmedServiceconstructInterfaceAaaGroupDiameterStatisticsChassisLevelEndhostIntfTypeEntry 21 }

affirmedServiceconstructInterfaceAaaGroupDiameterStatisticsChassisLevelEndhostIntfTypeNumCCAUpdate4xxx OBJECT-TYPE
    SYNTAX      ConfdString
    MAX-ACCESS  read-only
    STATUS      current
    DESCRIPTION "Number of failed CCA Update received with 4xx error"
    ::= { affirmedServiceconstructInterfaceAaaGroupDiameterStatisticsChassisLevelEndhostIntfTypeEntry 22 }

affirmedServiceconstructInterfaceAaaGroupDiameterStatisticsChassisLevelEndhostIntfTypeNumCCAUpdate5xxx OBJECT-TYPE
    SYNTAX      ConfdString
    MAX-ACCESS  read-only
    STATUS      current
    DESCRIPTION "Number of failed CCA Update received with 5xx error"
    ::= { affirmedServiceconstructInterfaceAaaGroupDiameterStatisticsChassisLevelEndhostIntfTypeEntry 23 }

affirmedServiceconstructInterfaceAaaGroupDiameterStatisticsChassisLevelEndhostIntfTypeNumCCRUpdateTimeout OBJECT-TYPE
    SYNTAX      ConfdString
    MAX-ACCESS  read-only
    STATUS      current
    DESCRIPTION "Number of CCR Update attempts that timed out"
    ::= { affirmedServiceconstructInterfaceAaaGroupDiameterStatisticsChassisLevelEndhostIntfTypeEntry 24 }

affirmedServiceconstructInterfaceAaaGroupDiameterStatisticsChassisLevelEndhostIntfTypeNumCCRUpdateAborted OBJECT-TYPE
    SYNTAX      ConfdString
    MAX-ACCESS  read-only
    STATUS      current
    DESCRIPTION "Number of CCR Update attempts that were aborted due to response received from another peer"
    ::= { affirmedServiceconstructInterfaceAaaGroupDiameterStatisticsChassisLevelEndhostIntfTypeEntry 25 }

affirmedServiceconstructInterfaceAaaGroupDiameterStatisticsChassisLevelEndhostIntfTypeNumCCAUpdateDelayedSuccess OBJECT-TYPE
    SYNTAX      ConfdString
    MAX-ACCESS  read-only
    STATUS      current
    DESCRIPTION "Number of CCA Update success which were received after the request had been re-transmitted to another server"
    ::= { affirmedServiceconstructInterfaceAaaGroupDiameterStatisticsChassisLevelEndhostIntfTypeEntry 26 }

affirmedServiceconstructInterfaceAaaGroupDiameterStatisticsChassisLevelEndhostIntfTypeNumCCAUpdateDelayedFailure OBJECT-TYPE
    SYNTAX      ConfdString
    MAX-ACCESS  read-only
    STATUS      current
    DESCRIPTION "Number of CCA Update failures which were received after the request had been re-transmitted to another server"
    ::= { affirmedServiceconstructInterfaceAaaGroupDiameterStatisticsChassisLevelEndhostIntfTypeEntry 27 }

affirmedServiceconstructInterfaceAaaGroupDiameterStatisticsChassisLevelEndhostIntfTypeNumCCAUpdateDelayed3xxx OBJECT-TYPE
    SYNTAX      ConfdString
    MAX-ACCESS  read-only
    STATUS      current
    DESCRIPTION "Number of CCA Update 3xx errors which were received after the request had been re-transmitted to another server"
    ::= { affirmedServiceconstructInterfaceAaaGroupDiameterStatisticsChassisLevelEndhostIntfTypeEntry 28 }

affirmedServiceconstructInterfaceAaaGroupDiameterStatisticsChassisLevelEndhostIntfTypeNumCCAUpdateRcvdFirstAttempt OBJECT-TYPE
    SYNTAX      ConfdString
    MAX-ACCESS  read-only
    STATUS      current
    DESCRIPTION "Number of CCA Update requests for which response was received when first transmitted "
    ::= { affirmedServiceconstructInterfaceAaaGroupDiameterStatisticsChassisLevelEndhostIntfTypeEntry 29 }

affirmedServiceconstructInterfaceAaaGroupDiameterStatisticsChassisLevelEndhostIntfTypeNumCCAUpdateRcvdReTx OBJECT-TYPE
    SYNTAX      ConfdString
    MAX-ACCESS  read-only
    STATUS      current
    DESCRIPTION "Number of CCR Update Requests for which response was received when message was retransmitted"
    ::= { affirmedServiceconstructInterfaceAaaGroupDiameterStatisticsChassisLevelEndhostIntfTypeEntry 30 }

affirmedServiceconstructInterfaceAaaGroupDiameterStatisticsChassisLevelEndhostIntfTypeNumCCRTerminateAttempted OBJECT-TYPE
    SYNTAX      ConfdString
    MAX-ACCESS  read-only
    STATUS      current
    DESCRIPTION "Number of CCR Terminate attempts made"
    ::= { affirmedServiceconstructInterfaceAaaGroupDiameterStatisticsChassisLevelEndhostIntfTypeEntry 31 }

affirmedServiceconstructInterfaceAaaGroupDiameterStatisticsChassisLevelEndhostIntfTypeNumCCRTerminateSuccess OBJECT-TYPE
    SYNTAX      ConfdString
    MAX-ACCESS  read-only
    STATUS      current
    DESCRIPTION "Number of successful CCR Terminate attempts"
    ::= { affirmedServiceconstructInterfaceAaaGroupDiameterStatisticsChassisLevelEndhostIntfTypeEntry 32 }

affirmedServiceconstructInterfaceAaaGroupDiameterStatisticsChassisLevelEndhostIntfTypeNumCCRTerminateFailure OBJECT-TYPE
    SYNTAX      ConfdString
    MAX-ACCESS  read-only
    STATUS      current
    DESCRIPTION "Number of failed CCR Terminate attempts"
    ::= { affirmedServiceconstructInterfaceAaaGroupDiameterStatisticsChassisLevelEndhostIntfTypeEntry 33 }

affirmedServiceconstructInterfaceAaaGroupDiameterStatisticsChassisLevelEndhostIntfTypeNumCCATerminate3xxx OBJECT-TYPE
    SYNTAX      ConfdString
    MAX-ACCESS  read-only
    STATUS      current
    DESCRIPTION "Number of failed CCR Terminate attempts due to 3xx error"
    ::= { affirmedServiceconstructInterfaceAaaGroupDiameterStatisticsChassisLevelEndhostIntfTypeEntry 34 }

affirmedServiceconstructInterfaceAaaGroupDiameterStatisticsChassisLevelEndhostIntfTypeNumCCATerminate4xxx OBJECT-TYPE
    SYNTAX      ConfdString
    MAX-ACCESS  read-only
    STATUS      current
    DESCRIPTION "Number of failed CCA Terminate received with 4xx error"
    ::= { affirmedServiceconstructInterfaceAaaGroupDiameterStatisticsChassisLevelEndhostIntfTypeEntry 35 }

affirmedServiceconstructInterfaceAaaGroupDiameterStatisticsChassisLevelEndhostIntfTypeNumCCATerminate5xxx OBJECT-TYPE
    SYNTAX      ConfdString
    MAX-ACCESS  read-only
    STATUS      current
    DESCRIPTION "Number of failed CCA Terminate received with 5xx error"
    ::= { affirmedServiceconstructInterfaceAaaGroupDiameterStatisticsChassisLevelEndhostIntfTypeEntry 36 }

affirmedServiceconstructInterfaceAaaGroupDiameterStatisticsChassisLevelEndhostIntfTypeNumCCRTerminateTimeout OBJECT-TYPE
    SYNTAX      ConfdString
    MAX-ACCESS  read-only
    STATUS      current
    DESCRIPTION "Number of CCR Terminate attempts that timed out"
    ::= { affirmedServiceconstructInterfaceAaaGroupDiameterStatisticsChassisLevelEndhostIntfTypeEntry 37 }

affirmedServiceconstructInterfaceAaaGroupDiameterStatisticsChassisLevelEndhostIntfTypeNumCCRTerminateAborted OBJECT-TYPE
    SYNTAX      ConfdString
    MAX-ACCESS  read-only
    STATUS      current
    DESCRIPTION "Number of CCR Terminate attempts that were aborted due to response received from another peer"
    ::= { affirmedServiceconstructInterfaceAaaGroupDiameterStatisticsChassisLevelEndhostIntfTypeEntry 38 }

affirmedServiceconstructInterfaceAaaGroupDiameterStatisticsChassisLevelEndhostIntfTypeNumCCATerminateDelayedSuccess OBJECT-TYPE
    SYNTAX      ConfdString
    MAX-ACCESS  read-only
    STATUS      current
    DESCRIPTION "Number of CCA Terminate success which were received after the request had been re-transmitted to another server"
    ::= { affirmedServiceconstructInterfaceAaaGroupDiameterStatisticsChassisLevelEndhostIntfTypeEntry 39 }

affirmedServiceconstructInterfaceAaaGroupDiameterStatisticsChassisLevelEndhostIntfTypeNumCCATerminateDelayedFailure OBJECT-TYPE
    SYNTAX      ConfdString
    MAX-ACCESS  read-only
    STATUS      current
    DESCRIPTION "Number of CCA Terminate failures which were received after the request had been re-transmitted to another server"
    ::= { affirmedServiceconstructInterfaceAaaGroupDiameterStatisticsChassisLevelEndhostIntfTypeEntry 40 }

affirmedServiceconstructInterfaceAaaGroupDiameterStatisticsChassisLevelEndhostIntfTypeNumCCATerminateDelayed3xxx OBJECT-TYPE
    SYNTAX      ConfdString
    MAX-ACCESS  read-only
    STATUS      current
    DESCRIPTION "Number of CCA Terminate 3xx errors which were received after the request had been re-transmitted to another server"
    ::= { affirmedServiceconstructInterfaceAaaGroupDiameterStatisticsChassisLevelEndhostIntfTypeEntry 41 }

affirmedServiceconstructInterfaceAaaGroupDiameterStatisticsChassisLevelEndhostIntfTypeNumCCATerminateRcvdFirstAttempt OBJECT-TYPE
    SYNTAX      ConfdString
    MAX-ACCESS  read-only
    STATUS      current
    DESCRIPTION "Number of CCA Terminate requests for which response was received when first transmitted "
    ::= { affirmedServiceconstructInterfaceAaaGroupDiameterStatisticsChassisLevelEndhostIntfTypeEntry 42 }

affirmedServiceconstructInterfaceAaaGroupDiameterStatisticsChassisLevelEndhostIntfTypeNumCCATerminateRcvdReTx OBJECT-TYPE
    SYNTAX      ConfdString
    MAX-ACCESS  read-only
    STATUS      current
    DESCRIPTION "Number of CCR Terminate Requests for which response was received when message was retransmitted"
    ::= { affirmedServiceconstructInterfaceAaaGroupDiameterStatisticsChassisLevelEndhostIntfTypeEntry 43 }

affirmedServiceconstructInterfaceAaaGroupDiameterStatisticsChassisLevelEndhostIntfTypeNumCCRTerminateStoredForReplay OBJECT-TYPE
    SYNTAX      ConfdString
    MAX-ACCESS  read-only
    STATUS      current
    DESCRIPTION "Number of CCR Terminate Requests stored for replay"
    ::= { affirmedServiceconstructInterfaceAaaGroupDiameterStatisticsChassisLevelEndhostIntfTypeEntry 44 }

affirmedServiceconstructInterfaceAaaGroupDiameterStatisticsChassisLevelEndhostIntfTypeNumDiameterSessions OBJECT-TYPE
    SYNTAX      ConfdString
    MAX-ACCESS  read-only
    STATUS      current
    DESCRIPTION "Number of subscribers using the diameter connection"
    ::= { affirmedServiceconstructInterfaceAaaGroupDiameterStatisticsChassisLevelEndhostIntfTypeEntry 45 }

affirmedServiceconstructInterfaceAaaGroupDiameterStatisticsChassisLevelEndhostIntfTypeNumCCRTerminateReplay OBJECT-TYPE
    SYNTAX      ConfdString
    MAX-ACCESS  read-only
    STATUS      current
    DESCRIPTION "Number of CCR Terminate Requests that were replayed"
    ::= { affirmedServiceconstructInterfaceAaaGroupDiameterStatisticsChassisLevelEndhostIntfTypeEntry 46 }

affirmedServiceconstructInterfaceAaaGroupDiameterStatisticsChassisLevelEndhostIntfTypeNumCCRTerminateReplayReTx OBJECT-TYPE
    SYNTAX      ConfdString
    MAX-ACCESS  read-only
    STATUS      current
    DESCRIPTION "Number of CCR Terminate Requests that were replayed"
    ::= { affirmedServiceconstructInterfaceAaaGroupDiameterStatisticsChassisLevelEndhostIntfTypeEntry 47 }

affirmedServiceconstructInterfaceAaaGroupDiameterStatisticsChassisLevelEndhostIntfTypeNumCCRTerminateReplaySuccess OBJECT-TYPE
    SYNTAX      ConfdString
    MAX-ACCESS  read-only
    STATUS      current
    DESCRIPTION "Number of CCR Terminate Requests that were replayed and successful"
    ::= { affirmedServiceconstructInterfaceAaaGroupDiameterStatisticsChassisLevelEndhostIntfTypeEntry 48 }

affirmedServiceconstructInterfaceAaaGroupDiameterStatisticsChassisLevelEndhostIntfTypeNumCCRTerminateReplayFailure OBJECT-TYPE
    SYNTAX      ConfdString
    MAX-ACCESS  read-only
    STATUS      current
    DESCRIPTION "Number of CCR Terminate Requests that were replayed and failed"
    ::= { affirmedServiceconstructInterfaceAaaGroupDiameterStatisticsChassisLevelEndhostIntfTypeEntry 49 }

affirmedServiceconstructInterfaceAaaGroupDiameterStatisticsChassisLevelEndhostIntfTypeNumACRStartAttempted OBJECT-TYPE
    SYNTAX      ConfdString
    MAX-ACCESS  read-only
    STATUS      current
    DESCRIPTION "Number of ACR Start Request attempts made"
    ::= { affirmedServiceconstructInterfaceAaaGroupDiameterStatisticsChassisLevelEndhostIntfTypeEntry 50 }

affirmedServiceconstructInterfaceAaaGroupDiameterStatisticsChassisLevelEndhostIntfTypeNumACRStartReTx OBJECT-TYPE
    SYNTAX      ConfdString
    MAX-ACCESS  read-only
    STATUS      current
    DESCRIPTION "Number of retransmitted ACR Start Requests"
    ::= { affirmedServiceconstructInterfaceAaaGroupDiameterStatisticsChassisLevelEndhostIntfTypeEntry 51 }

affirmedServiceconstructInterfaceAaaGroupDiameterStatisticsChassisLevelEndhostIntfTypeNumACRStartSuccess OBJECT-TYPE
    SYNTAX      ConfdString
    MAX-ACCESS  read-only
    STATUS      current
    DESCRIPTION "Number of successful ACR Start Requests"
    ::= { affirmedServiceconstructInterfaceAaaGroupDiameterStatisticsChassisLevelEndhostIntfTypeEntry 52 }

affirmedServiceconstructInterfaceAaaGroupDiameterStatisticsChassisLevelEndhostIntfTypeNumACRStartFailure OBJECT-TYPE
    SYNTAX      ConfdString
    MAX-ACCESS  read-only
    STATUS      current
    DESCRIPTION "Number of failed ACR Start Requests"
    ::= { affirmedServiceconstructInterfaceAaaGroupDiameterStatisticsChassisLevelEndhostIntfTypeEntry 53 }

affirmedServiceconstructInterfaceAaaGroupDiameterStatisticsChassisLevelEndhostIntfTypeNumACRStartTimeout OBJECT-TYPE
    SYNTAX      ConfdString
    MAX-ACCESS  read-only
    STATUS      current
    DESCRIPTION "Number of ACR Start Timeouts"
    ::= { affirmedServiceconstructInterfaceAaaGroupDiameterStatisticsChassisLevelEndhostIntfTypeEntry 54 }

affirmedServiceconstructInterfaceAaaGroupDiameterStatisticsChassisLevelEndhostIntfTypeNumACRStartAborted OBJECT-TYPE
    SYNTAX      ConfdString
    MAX-ACCESS  read-only
    STATUS      current
    DESCRIPTION "Number of ACR Start Requests Aborted due to response received from another peer"
    ::= { affirmedServiceconstructInterfaceAaaGroupDiameterStatisticsChassisLevelEndhostIntfTypeEntry 55 }

affirmedServiceconstructInterfaceAaaGroupDiameterStatisticsChassisLevelEndhostIntfTypeNumACRStartDelayedSuccess OBJECT-TYPE
    SYNTAX      ConfdString
    MAX-ACCESS  read-only
    STATUS      current
    DESCRIPTION "Number of ACR Start Success Responses received late - transaction was completed or the request was sent to a different server"
    ::= { affirmedServiceconstructInterfaceAaaGroupDiameterStatisticsChassisLevelEndhostIntfTypeEntry 56 }

affirmedServiceconstructInterfaceAaaGroupDiameterStatisticsChassisLevelEndhostIntfTypeNumACRStartDelayedFailure OBJECT-TYPE
    SYNTAX      ConfdString
    MAX-ACCESS  read-only
    STATUS      current
    DESCRIPTION "Number of ACR Start Failure Responses received late - transaction was completed or the request was sent to a different server"
    ::= { affirmedServiceconstructInterfaceAaaGroupDiameterStatisticsChassisLevelEndhostIntfTypeEntry 57 }

affirmedServiceconstructInterfaceAaaGroupDiameterStatisticsChassisLevelEndhostIntfTypeNumACRStartDropped OBJECT-TYPE
    SYNTAX      ConfdString
    MAX-ACCESS  read-only
    STATUS      current
    DESCRIPTION "Number of ACR Start Requests Droppedr"
    ::= { affirmedServiceconstructInterfaceAaaGroupDiameterStatisticsChassisLevelEndhostIntfTypeEntry 58 }

affirmedServiceconstructInterfaceAaaGroupDiameterStatisticsChassisLevelEndhostIntfTypeNumACRStartWriteToDisk OBJECT-TYPE
    SYNTAX      ConfdString
    MAX-ACCESS  read-only
    STATUS      current
    DESCRIPTION "Number of ACR Start write to disk after failed to send to OFCS Server"
    ::= { affirmedServiceconstructInterfaceAaaGroupDiameterStatisticsChassisLevelEndhostIntfTypeEntry 59 }

affirmedServiceconstructInterfaceAaaGroupDiameterStatisticsChassisLevelEndhostIntfTypeNumACRInterimAttempted OBJECT-TYPE
    SYNTAX      ConfdString
    MAX-ACCESS  read-only
    STATUS      current
    DESCRIPTION "Number of ACR Interim Request attempts made"
    ::= { affirmedServiceconstructInterfaceAaaGroupDiameterStatisticsChassisLevelEndhostIntfTypeEntry 60 }

affirmedServiceconstructInterfaceAaaGroupDiameterStatisticsChassisLevelEndhostIntfTypeNumACRInterimReTx OBJECT-TYPE
    SYNTAX      ConfdString
    MAX-ACCESS  read-only
    STATUS      current
    DESCRIPTION "Number of retransmitted ACR Interim Requests"
    ::= { affirmedServiceconstructInterfaceAaaGroupDiameterStatisticsChassisLevelEndhostIntfTypeEntry 61 }

affirmedServiceconstructInterfaceAaaGroupDiameterStatisticsChassisLevelEndhostIntfTypeNumACRInterimSuccess OBJECT-TYPE
    SYNTAX      ConfdString
    MAX-ACCESS  read-only
    STATUS      current
    DESCRIPTION "Number of successful ACR Interim Requests"
    ::= { affirmedServiceconstructInterfaceAaaGroupDiameterStatisticsChassisLevelEndhostIntfTypeEntry 62 }

affirmedServiceconstructInterfaceAaaGroupDiameterStatisticsChassisLevelEndhostIntfTypeNumACRInterimFailure OBJECT-TYPE
    SYNTAX      ConfdString
    MAX-ACCESS  read-only
    STATUS      current
    DESCRIPTION "Number of failed ACR Interim Requests"
    ::= { affirmedServiceconstructInterfaceAaaGroupDiameterStatisticsChassisLevelEndhostIntfTypeEntry 63 }

affirmedServiceconstructInterfaceAaaGroupDiameterStatisticsChassisLevelEndhostIntfTypeNumACRInterimTimeout OBJECT-TYPE
    SYNTAX      ConfdString
    MAX-ACCESS  read-only
    STATUS      current
    DESCRIPTION "Number of ACR Interim Timeouts"
    ::= { affirmedServiceconstructInterfaceAaaGroupDiameterStatisticsChassisLevelEndhostIntfTypeEntry 64 }

affirmedServiceconstructInterfaceAaaGroupDiameterStatisticsChassisLevelEndhostIntfTypeNumACRInterimAborted OBJECT-TYPE
    SYNTAX      ConfdString
    MAX-ACCESS  read-only
    STATUS      current
    DESCRIPTION "Number of ACR Interim Requests Aborted due to response received from another peer"
    ::= { affirmedServiceconstructInterfaceAaaGroupDiameterStatisticsChassisLevelEndhostIntfTypeEntry 65 }

affirmedServiceconstructInterfaceAaaGroupDiameterStatisticsChassisLevelEndhostIntfTypeNumACRInterimDelayedSuccess OBJECT-TYPE
    SYNTAX      ConfdString
    MAX-ACCESS  read-only
    STATUS      current
    DESCRIPTION "Number of ACR Interim Success Responses received late - transaction was completed or the request was sent to a different server"
    ::= { affirmedServiceconstructInterfaceAaaGroupDiameterStatisticsChassisLevelEndhostIntfTypeEntry 66 }

affirmedServiceconstructInterfaceAaaGroupDiameterStatisticsChassisLevelEndhostIntfTypeNumACRInterimDelayedFailure OBJECT-TYPE
    SYNTAX      ConfdString
    MAX-ACCESS  read-only
    STATUS      current
    DESCRIPTION "Number of ACR Interim Failure Responses received late - transaction was completed or the request was sent to a different server"
    ::= { affirmedServiceconstructInterfaceAaaGroupDiameterStatisticsChassisLevelEndhostIntfTypeEntry 67 }

affirmedServiceconstructInterfaceAaaGroupDiameterStatisticsChassisLevelEndhostIntfTypeNumACRInterimDropped OBJECT-TYPE
    SYNTAX      ConfdString
    MAX-ACCESS  read-only
    STATUS      current
    DESCRIPTION "Number of ACR Interim Requests Droppedr"
    ::= { affirmedServiceconstructInterfaceAaaGroupDiameterStatisticsChassisLevelEndhostIntfTypeEntry 68 }

affirmedServiceconstructInterfaceAaaGroupDiameterStatisticsChassisLevelEndhostIntfTypeNumACRInterimWriteToDisk OBJECT-TYPE
    SYNTAX      ConfdString
    MAX-ACCESS  read-only
    STATUS      current
    DESCRIPTION "Number of ACR Interim write to disk after failed to send to OFCS Server"
    ::= { affirmedServiceconstructInterfaceAaaGroupDiameterStatisticsChassisLevelEndhostIntfTypeEntry 69 }

affirmedServiceconstructInterfaceAaaGroupDiameterStatisticsChassisLevelEndhostIntfTypeNumACRStopAttempted OBJECT-TYPE
    SYNTAX      ConfdString
    MAX-ACCESS  read-only
    STATUS      current
    DESCRIPTION "Number of ACR Stop Request attempts made"
    ::= { affirmedServiceconstructInterfaceAaaGroupDiameterStatisticsChassisLevelEndhostIntfTypeEntry 70 }

affirmedServiceconstructInterfaceAaaGroupDiameterStatisticsChassisLevelEndhostIntfTypeNumACRStopReTx OBJECT-TYPE
    SYNTAX      ConfdString
    MAX-ACCESS  read-only
    STATUS      current
    DESCRIPTION "Number of retransmitted ACR Stop Requests"
    ::= { affirmedServiceconstructInterfaceAaaGroupDiameterStatisticsChassisLevelEndhostIntfTypeEntry 71 }

affirmedServiceconstructInterfaceAaaGroupDiameterStatisticsChassisLevelEndhostIntfTypeNumACRStopSuccess OBJECT-TYPE
    SYNTAX      ConfdString
    MAX-ACCESS  read-only
    STATUS      current
    DESCRIPTION "Number of successful ACR Stop Requests"
    ::= { affirmedServiceconstructInterfaceAaaGroupDiameterStatisticsChassisLevelEndhostIntfTypeEntry 72 }

affirmedServiceconstructInterfaceAaaGroupDiameterStatisticsChassisLevelEndhostIntfTypeNumACRStopFailure OBJECT-TYPE
    SYNTAX      ConfdString
    MAX-ACCESS  read-only
    STATUS      current
    DESCRIPTION "Number of failed ACR Stop Requests"
    ::= { affirmedServiceconstructInterfaceAaaGroupDiameterStatisticsChassisLevelEndhostIntfTypeEntry 73 }

affirmedServiceconstructInterfaceAaaGroupDiameterStatisticsChassisLevelEndhostIntfTypeNumACRStopTimeout OBJECT-TYPE
    SYNTAX      ConfdString
    MAX-ACCESS  read-only
    STATUS      current
    DESCRIPTION "Number of ACR Stop Timeouts"
    ::= { affirmedServiceconstructInterfaceAaaGroupDiameterStatisticsChassisLevelEndhostIntfTypeEntry 74 }

affirmedServiceconstructInterfaceAaaGroupDiameterStatisticsChassisLevelEndhostIntfTypeNumACRStopAborted OBJECT-TYPE
    SYNTAX      ConfdString
    MAX-ACCESS  read-only
    STATUS      current
    DESCRIPTION "Number of ACR Stop Requests Aborted due to response received from another peer"
    ::= { affirmedServiceconstructInterfaceAaaGroupDiameterStatisticsChassisLevelEndhostIntfTypeEntry 75 }

affirmedServiceconstructInterfaceAaaGroupDiameterStatisticsChassisLevelEndhostIntfTypeNumACRStopDelayedSuccess OBJECT-TYPE
    SYNTAX      ConfdString
    MAX-ACCESS  read-only
    STATUS      current
    DESCRIPTION "Number of ACR Stop Success Responses received late - transaction was completed or the request was sent to a different server"
    ::= { affirmedServiceconstructInterfaceAaaGroupDiameterStatisticsChassisLevelEndhostIntfTypeEntry 76 }

affirmedServiceconstructInterfaceAaaGroupDiameterStatisticsChassisLevelEndhostIntfTypeNumACRStopDelayedFailure OBJECT-TYPE
    SYNTAX      ConfdString
    MAX-ACCESS  read-only
    STATUS      current
    DESCRIPTION "Number of ACR Stop Failure Responses received late - transaction was completed or the request was sent to a different server"
    ::= { affirmedServiceconstructInterfaceAaaGroupDiameterStatisticsChassisLevelEndhostIntfTypeEntry 77 }

affirmedServiceconstructInterfaceAaaGroupDiameterStatisticsChassisLevelEndhostIntfTypeNumACRStopDropped OBJECT-TYPE
    SYNTAX      ConfdString
    MAX-ACCESS  read-only
    STATUS      current
    DESCRIPTION "Number of ACR Stop Requests Droppedr"
    ::= { affirmedServiceconstructInterfaceAaaGroupDiameterStatisticsChassisLevelEndhostIntfTypeEntry 78 }

affirmedServiceconstructInterfaceAaaGroupDiameterStatisticsChassisLevelEndhostIntfTypeNumACRStopWriteToDisk OBJECT-TYPE
    SYNTAX      ConfdString
    MAX-ACCESS  read-only
    STATUS      current
    DESCRIPTION "Number of ACR Stop write to disk after failed to send to OFCS Server"
    ::= { affirmedServiceconstructInterfaceAaaGroupDiameterStatisticsChassisLevelEndhostIntfTypeEntry 79 }

affirmedServiceconstructInterfaceAaaGroupDiameterStatisticsChassisLevelEndhostIntfTypeNumACREventAttempted OBJECT-TYPE
    SYNTAX      ConfdString
    MAX-ACCESS  read-only
    STATUS      current
    DESCRIPTION "Number of ACR Event Request attempts made"
    ::= { affirmedServiceconstructInterfaceAaaGroupDiameterStatisticsChassisLevelEndhostIntfTypeEntry 80 }

affirmedServiceconstructInterfaceAaaGroupDiameterStatisticsChassisLevelEndhostIntfTypeNumACREventReTx OBJECT-TYPE
    SYNTAX      ConfdString
    MAX-ACCESS  read-only
    STATUS      current
    DESCRIPTION "Number of retransmitted ACR Event Requests"
    ::= { affirmedServiceconstructInterfaceAaaGroupDiameterStatisticsChassisLevelEndhostIntfTypeEntry 81 }

affirmedServiceconstructInterfaceAaaGroupDiameterStatisticsChassisLevelEndhostIntfTypeNumACREventSuccess OBJECT-TYPE
    SYNTAX      ConfdString
    MAX-ACCESS  read-only
    STATUS      current
    DESCRIPTION "Number of successful ACR Event Requests"
    ::= { affirmedServiceconstructInterfaceAaaGroupDiameterStatisticsChassisLevelEndhostIntfTypeEntry 82 }

affirmedServiceconstructInterfaceAaaGroupDiameterStatisticsChassisLevelEndhostIntfTypeNumACREventFailure OBJECT-TYPE
    SYNTAX      ConfdString
    MAX-ACCESS  read-only
    STATUS      current
    DESCRIPTION "Number of failed ACR Event Requests"
    ::= { affirmedServiceconstructInterfaceAaaGroupDiameterStatisticsChassisLevelEndhostIntfTypeEntry 83 }

affirmedServiceconstructInterfaceAaaGroupDiameterStatisticsChassisLevelEndhostIntfTypeNumACREventTimeout OBJECT-TYPE
    SYNTAX      ConfdString
    MAX-ACCESS  read-only
    STATUS      current
    DESCRIPTION "Number of ACR Event Timeouts"
    ::= { affirmedServiceconstructInterfaceAaaGroupDiameterStatisticsChassisLevelEndhostIntfTypeEntry 84 }

affirmedServiceconstructInterfaceAaaGroupDiameterStatisticsChassisLevelEndhostIntfTypeNumACREventAborted OBJECT-TYPE
    SYNTAX      ConfdString
    MAX-ACCESS  read-only
    STATUS      current
    DESCRIPTION "Number of ACR Event Requests Aborted due to response received from another peer"
    ::= { affirmedServiceconstructInterfaceAaaGroupDiameterStatisticsChassisLevelEndhostIntfTypeEntry 85 }

affirmedServiceconstructInterfaceAaaGroupDiameterStatisticsChassisLevelEndhostIntfTypeNumACREventDelayedSuccess OBJECT-TYPE
    SYNTAX      ConfdString
    MAX-ACCESS  read-only
    STATUS      current
    DESCRIPTION "Number of ACR Event Success Responses received late - transaction was completed or the request was sent to a different server"
    ::= { affirmedServiceconstructInterfaceAaaGroupDiameterStatisticsChassisLevelEndhostIntfTypeEntry 86 }

affirmedServiceconstructInterfaceAaaGroupDiameterStatisticsChassisLevelEndhostIntfTypeNumACREventDelayedFailure OBJECT-TYPE
    SYNTAX      ConfdString
    MAX-ACCESS  read-only
    STATUS      current
    DESCRIPTION "Number of ACR Event Failure Responses received late - transaction was completed or the request was sent to a different server"
    ::= { affirmedServiceconstructInterfaceAaaGroupDiameterStatisticsChassisLevelEndhostIntfTypeEntry 87 }

affirmedServiceconstructInterfaceAaaGroupDiameterStatisticsChassisLevelEndhostIntfTypeNumACREventDropped OBJECT-TYPE
    SYNTAX      ConfdString
    MAX-ACCESS  read-only
    STATUS      current
    DESCRIPTION "Number of ACR Event Requests Droppedr"
    ::= { affirmedServiceconstructInterfaceAaaGroupDiameterStatisticsChassisLevelEndhostIntfTypeEntry 88 }

affirmedServiceconstructInterfaceAaaGroupDiameterStatisticsChassisLevelEndhostIntfTypeNumACREventWriteToDisk OBJECT-TYPE
    SYNTAX      ConfdString
    MAX-ACCESS  read-only
    STATUS      current
    DESCRIPTION "Number of ACR Event write to disk after failed to send to OFCS Server"
    ::= { affirmedServiceconstructInterfaceAaaGroupDiameterStatisticsChassisLevelEndhostIntfTypeEntry 89 }

affirmedServiceconstructInterfaceAaaGroupDiameterStatisticsChassisLevelEndhostIntfTypeNumACRWriteToDiskFailure OBJECT-TYPE
    SYNTAX      ConfdString
    MAX-ACCESS  read-only
    STATUS      current
    DESCRIPTION "Number of ACR write to disk Failure"
    ::= { affirmedServiceconstructInterfaceAaaGroupDiameterStatisticsChassisLevelEndhostIntfTypeEntry 90 }

affirmedServiceconstructInterfaceAaaGroupDiameterStatisticsChassisLevelEndhostIntfTypeNumAARInitialAttempted OBJECT-TYPE
    SYNTAX      ConfdString
    MAX-ACCESS  read-only
    STATUS      current
    DESCRIPTION "Number of AAR Initial attempts made"
    ::= { affirmedServiceconstructInterfaceAaaGroupDiameterStatisticsChassisLevelEndhostIntfTypeEntry 91 }

affirmedServiceconstructInterfaceAaaGroupDiameterStatisticsChassisLevelEndhostIntfTypeNumAARInitialSuccess OBJECT-TYPE
    SYNTAX      ConfdString
    MAX-ACCESS  read-only
    STATUS      current
    DESCRIPTION "Number of successful AAR Initial attempts"
    ::= { affirmedServiceconstructInterfaceAaaGroupDiameterStatisticsChassisLevelEndhostIntfTypeEntry 92 }

affirmedServiceconstructInterfaceAaaGroupDiameterStatisticsChassisLevelEndhostIntfTypeNumAARInitialFailure OBJECT-TYPE
    SYNTAX      ConfdString
    MAX-ACCESS  read-only
    STATUS      current
    DESCRIPTION "Number of failed AAR Initial attempts"
    ::= { affirmedServiceconstructInterfaceAaaGroupDiameterStatisticsChassisLevelEndhostIntfTypeEntry 93 }

affirmedServiceconstructInterfaceAaaGroupDiameterStatisticsChassisLevelEndhostIntfTypeNumAARInitialTimeout OBJECT-TYPE
    SYNTAX      ConfdString
    MAX-ACCESS  read-only
    STATUS      current
    DESCRIPTION "Number of AAR Initial attempts that timed out"
    ::= { affirmedServiceconstructInterfaceAaaGroupDiameterStatisticsChassisLevelEndhostIntfTypeEntry 94 }

affirmedServiceconstructInterfaceAaaGroupDiameterStatisticsChassisLevelEndhostIntfTypeNumAARAborted OBJECT-TYPE
    SYNTAX      ConfdString
    MAX-ACCESS  read-only
    STATUS      current
    DESCRIPTION "Number of AAR attempts that were aborted due to response received from another peer"
    ::= { affirmedServiceconstructInterfaceAaaGroupDiameterStatisticsChassisLevelEndhostIntfTypeEntry 95 }

affirmedServiceconstructInterfaceAaaGroupDiameterStatisticsChassisLevelEndhostIntfTypeNumAAAInitialRcvdFirstAttempt OBJECT-TYPE
    SYNTAX      ConfdString
    MAX-ACCESS  read-only
    STATUS      current
    DESCRIPTION "Number of AAR Initial requests for which response was received when first transmitted "
    ::= { affirmedServiceconstructInterfaceAaaGroupDiameterStatisticsChassisLevelEndhostIntfTypeEntry 96 }

affirmedServiceconstructInterfaceAaaGroupDiameterStatisticsChassisLevelEndhostIntfTypeNumAAAInitialRcvdReTx OBJECT-TYPE
    SYNTAX      ConfdString
    MAX-ACCESS  read-only
    STATUS      current
    DESCRIPTION "Number of AAR Initial Requests for which response was received when message was retransmitted"
    ::= { affirmedServiceconstructInterfaceAaaGroupDiameterStatisticsChassisLevelEndhostIntfTypeEntry 97 }

affirmedServiceconstructInterfaceAaaGroupDiameterStatisticsChassisLevelEndhostIntfTypeNumSTRAttempted OBJECT-TYPE
    SYNTAX      ConfdString
    MAX-ACCESS  read-only
    STATUS      current
    DESCRIPTION "Number of STR attempts made"
    ::= { affirmedServiceconstructInterfaceAaaGroupDiameterStatisticsChassisLevelEndhostIntfTypeEntry 98 }

affirmedServiceconstructInterfaceAaaGroupDiameterStatisticsChassisLevelEndhostIntfTypeNumSTRRetransmission OBJECT-TYPE
    SYNTAX      ConfdString
    MAX-ACCESS  read-only
    STATUS      current
    DESCRIPTION "Number of STR retransmits"
    ::= { affirmedServiceconstructInterfaceAaaGroupDiameterStatisticsChassisLevelEndhostIntfTypeEntry 99 }

affirmedServiceconstructInterfaceAaaGroupDiameterStatisticsChassisLevelEndhostIntfTypeNumSTRSuccess OBJECT-TYPE
    SYNTAX      ConfdString
    MAX-ACCESS  read-only
    STATUS      current
    DESCRIPTION "Number of successful STR attempts"
    ::= { affirmedServiceconstructInterfaceAaaGroupDiameterStatisticsChassisLevelEndhostIntfTypeEntry 100 }

affirmedServiceconstructInterfaceAaaGroupDiameterStatisticsChassisLevelEndhostIntfTypeNumSTRFailure OBJECT-TYPE
    SYNTAX      ConfdString
    MAX-ACCESS  read-only
    STATUS      current
    DESCRIPTION "Number of failed STR attempts"
    ::= { affirmedServiceconstructInterfaceAaaGroupDiameterStatisticsChassisLevelEndhostIntfTypeEntry 101 }

affirmedServiceconstructInterfaceAaaGroupDiameterStatisticsChassisLevelEndhostIntfTypeNumSTRTimeout OBJECT-TYPE
    SYNTAX      ConfdString
    MAX-ACCESS  read-only
    STATUS      current
    DESCRIPTION "Number of STR attempts that timed out"
    ::= { affirmedServiceconstructInterfaceAaaGroupDiameterStatisticsChassisLevelEndhostIntfTypeEntry 102 }

affirmedServiceconstructInterfaceAaaGroupDiameterStatisticsChassisLevelEndhostIntfTypeNumSTARcvdFirstAttempt OBJECT-TYPE
    SYNTAX      ConfdString
    MAX-ACCESS  read-only
    STATUS      current
    DESCRIPTION "Number of STR requests for which response was received when first transmitted "
    ::= { affirmedServiceconstructInterfaceAaaGroupDiameterStatisticsChassisLevelEndhostIntfTypeEntry 103 }

affirmedServiceconstructInterfaceAaaGroupDiameterStatisticsChassisLevelEndhostIntfTypeNumSTARcvdReTx OBJECT-TYPE
    SYNTAX      ConfdString
    MAX-ACCESS  read-only
    STATUS      current
    DESCRIPTION "Number of STR Requests for which response was received when message was retransmitted"
    ::= { affirmedServiceconstructInterfaceAaaGroupDiameterStatisticsChassisLevelEndhostIntfTypeEntry 104 }

affirmedServiceconstructInterfaceAaaGroupDiameterStatisticsChassisLevelEndhostIntfTypeNumSTRDropByPoc OBJECT-TYPE
    SYNTAX      ConfdString
    MAX-ACCESS  read-only
    STATUS      current
    DESCRIPTION "Number of STR Requests are not sent as a result of peer overload control"
    ::= { affirmedServiceconstructInterfaceAaaGroupDiameterStatisticsChassisLevelEndhostIntfTypeEntry 105 }

affirmedServiceconstructInterfaceAaaGroupDiameterStatisticsChassisLevelEndhostIntfTypeNumSTRRedirect OBJECT-TYPE
    SYNTAX      ConfdString
    MAX-ACCESS  read-only
    STATUS      current
    DESCRIPTION "Number of STR Requests are redirected"
    ::= { affirmedServiceconstructInterfaceAaaGroupDiameterStatisticsChassisLevelEndhostIntfTypeEntry 106 }

affirmedServiceconstructInterfaceAaaGroupDiameterStatisticsChassisLevelEndhostIntfTypeNumHandoffAARAttempted OBJECT-TYPE
    SYNTAX      ConfdString
    MAX-ACCESS  read-only
    STATUS      current
    DESCRIPTION "Number of Handoff AAR attempts made"
    ::= { affirmedServiceconstructInterfaceAaaGroupDiameterStatisticsChassisLevelEndhostIntfTypeEntry 107 }

affirmedServiceconstructInterfaceAaaGroupDiameterStatisticsChassisLevelEndhostIntfTypeNumHandoffAARSuccess OBJECT-TYPE
    SYNTAX      ConfdString
    MAX-ACCESS  read-only
    STATUS      current
    DESCRIPTION "Number of successful Handoff AAR attempts"
    ::= { affirmedServiceconstructInterfaceAaaGroupDiameterStatisticsChassisLevelEndhostIntfTypeEntry 108 }

affirmedServiceconstructInterfaceAaaGroupDiameterStatisticsChassisLevelEndhostIntfTypeNumHandoffAARFailure OBJECT-TYPE
    SYNTAX      ConfdString
    MAX-ACCESS  read-only
    STATUS      current
    DESCRIPTION "Number of failed Handoff AAR attempts"
    ::= { affirmedServiceconstructInterfaceAaaGroupDiameterStatisticsChassisLevelEndhostIntfTypeEntry 109 }

affirmedServiceconstructInterfaceAaaGroupDiameterStatisticsChassisLevelEndhostIntfTypeNumHandoffAARTimeout OBJECT-TYPE
    SYNTAX      ConfdString
    MAX-ACCESS  read-only
    STATUS      current
    DESCRIPTION "Number of Handoff AAR attempts that timed out"
    ::= { affirmedServiceconstructInterfaceAaaGroupDiameterStatisticsChassisLevelEndhostIntfTypeEntry 110 }

affirmedServiceconstructInterfaceAaaGroupDiameterStatisticsChassisLevelEndhostIntfTypeNumHandoffAAARcvdFirstAttempt OBJECT-TYPE
    SYNTAX      ConfdString
    MAX-ACCESS  read-only
    STATUS      current
    DESCRIPTION "Number of Handoff AAR requests for which response was received when first transmitted "
    ::= { affirmedServiceconstructInterfaceAaaGroupDiameterStatisticsChassisLevelEndhostIntfTypeEntry 111 }

affirmedServiceconstructInterfaceAaaGroupDiameterStatisticsChassisLevelEndhostIntfTypeNumHandoffAAARcvdReTx OBJECT-TYPE
    SYNTAX      ConfdString
    MAX-ACCESS  read-only
    STATUS      current
    DESCRIPTION "Number of Handoff AAR Requests for which response was received when message was retransmitted"
    ::= { affirmedServiceconstructInterfaceAaaGroupDiameterStatisticsChassisLevelEndhostIntfTypeEntry 112 }

affirmedServiceconstructInterfaceAaaGroupDiameterStatisticsChassisLevelEndhostIntfTypeNumRarInitAARAttempted OBJECT-TYPE
    SYNTAX      ConfdString
    MAX-ACCESS  read-only
    STATUS      current
    DESCRIPTION "Number of RAR Initiated AAR attempts made"
    ::= { affirmedServiceconstructInterfaceAaaGroupDiameterStatisticsChassisLevelEndhostIntfTypeEntry 113 }

affirmedServiceconstructInterfaceAaaGroupDiameterStatisticsChassisLevelEndhostIntfTypeNumRarInitAARSuccess OBJECT-TYPE
    SYNTAX      ConfdString
    MAX-ACCESS  read-only
    STATUS      current
    DESCRIPTION "Number of successful RAR Initiated AAR attempts"
    ::= { affirmedServiceconstructInterfaceAaaGroupDiameterStatisticsChassisLevelEndhostIntfTypeEntry 114 }

affirmedServiceconstructInterfaceAaaGroupDiameterStatisticsChassisLevelEndhostIntfTypeNumRarInitAARFailure OBJECT-TYPE
    SYNTAX      ConfdString
    MAX-ACCESS  read-only
    STATUS      current
    DESCRIPTION "Number of failed RAR Initiated AAR failures"
    ::= { affirmedServiceconstructInterfaceAaaGroupDiameterStatisticsChassisLevelEndhostIntfTypeEntry 115 }

affirmedServiceconstructInterfaceAaaGroupDiameterStatisticsChassisLevelEndhostIntfTypeNumRarInitAARTimeout OBJECT-TYPE
    SYNTAX      ConfdString
    MAX-ACCESS  read-only
    STATUS      current
    DESCRIPTION "Number of RAR Initiated AAR attempts that timed out"
    ::= { affirmedServiceconstructInterfaceAaaGroupDiameterStatisticsChassisLevelEndhostIntfTypeEntry 116 }

affirmedServiceconstructInterfaceAaaGroupDiameterStatisticsChassisLevelEndhostIntfTypeNumRarInitAAARcvdFirstAttempt OBJECT-TYPE
    SYNTAX      ConfdString
    MAX-ACCESS  read-only
    STATUS      current
    DESCRIPTION "Number of RAR Initiated AAR requests for which response was received when first transmitted "
    ::= { affirmedServiceconstructInterfaceAaaGroupDiameterStatisticsChassisLevelEndhostIntfTypeEntry 117 }

affirmedServiceconstructInterfaceAaaGroupDiameterStatisticsChassisLevelEndhostIntfTypeNumRarInitAAARcvdReTx OBJECT-TYPE
    SYNTAX      ConfdString
    MAX-ACCESS  read-only
    STATUS      current
    DESCRIPTION "Number of RAR Initiated AAR Requests for which response was received when message was retransmitted"
    ::= { affirmedServiceconstructInterfaceAaaGroupDiameterStatisticsChassisLevelEndhostIntfTypeEntry 118 }

affirmedServiceconstructInterfaceAaaGroupDiameterStatisticsChassisLevelEndhostIntfTypeNumRARInitAARDropByPoc OBJECT-TYPE
    SYNTAX      ConfdString
    MAX-ACCESS  read-only
    STATUS      current
    DESCRIPTION "Number of RAR Initiated AAR Requests are not sent as a result of peer overload control"
    ::= { affirmedServiceconstructInterfaceAaaGroupDiameterStatisticsChassisLevelEndhostIntfTypeEntry 119 }

affirmedServiceconstructInterfaceAaaGroupDiameterStatisticsChassisLevelEndhostIntfTypeNumRARInitAARRedirect OBJECT-TYPE
    SYNTAX      ConfdString
    MAX-ACCESS  read-only
    STATUS      current
    DESCRIPTION "Number of RAR Initiated AAR Requests are redirected"
    ::= { affirmedServiceconstructInterfaceAaaGroupDiameterStatisticsChassisLevelEndhostIntfTypeEntry 120 }

affirmedServiceconstructInterfaceAaaGroupDiameterStatisticsChassisLevelEndhostIntfTypeNumDERInitialAttempted OBJECT-TYPE
    SYNTAX      ConfdString
    MAX-ACCESS  read-only
    STATUS      current
    DESCRIPTION "Number of initial authentication DER attempts"
    ::= { affirmedServiceconstructInterfaceAaaGroupDiameterStatisticsChassisLevelEndhostIntfTypeEntry 121 }

affirmedServiceconstructInterfaceAaaGroupDiameterStatisticsChassisLevelEndhostIntfTypeNumDERRetransmission OBJECT-TYPE
    SYNTAX      ConfdString
    MAX-ACCESS  read-only
    STATUS      current
    DESCRIPTION "Number of initial authentication DER retransmits"
    ::= { affirmedServiceconstructInterfaceAaaGroupDiameterStatisticsChassisLevelEndhostIntfTypeEntry 122 }

affirmedServiceconstructInterfaceAaaGroupDiameterStatisticsChassisLevelEndhostIntfTypeNumDERInitialSuccess OBJECT-TYPE
    SYNTAX      ConfdString
    MAX-ACCESS  read-only
    STATUS      current
    DESCRIPTION "Number of initial authentication DER that succeeded"
    ::= { affirmedServiceconstructInterfaceAaaGroupDiameterStatisticsChassisLevelEndhostIntfTypeEntry 123 }

affirmedServiceconstructInterfaceAaaGroupDiameterStatisticsChassisLevelEndhostIntfTypeNumDERInitialFailure OBJECT-TYPE
    SYNTAX      ConfdString
    MAX-ACCESS  read-only
    STATUS      current
    DESCRIPTION "Number of initial authentication DER attempts that failed"
    ::= { affirmedServiceconstructInterfaceAaaGroupDiameterStatisticsChassisLevelEndhostIntfTypeEntry 124 }

affirmedServiceconstructInterfaceAaaGroupDiameterStatisticsChassisLevelEndhostIntfTypeNumDERInitialTimeout OBJECT-TYPE
    SYNTAX      ConfdString
    MAX-ACCESS  read-only
    STATUS      current
    DESCRIPTION "Number of initial authentication DER attempts that timed out"
    ::= { affirmedServiceconstructInterfaceAaaGroupDiameterStatisticsChassisLevelEndhostIntfTypeEntry 125 }

affirmedServiceconstructInterfaceAaaGroupDiameterStatisticsChassisLevelEndhostIntfTypeNumDERInitialChallenge OBJECT-TYPE
    SYNTAX      ConfdString
    MAX-ACCESS  read-only
    STATUS      current
    DESCRIPTION "Number of initial authentication DER requests sent with challenge "
    ::= { affirmedServiceconstructInterfaceAaaGroupDiameterStatisticsChassisLevelEndhostIntfTypeEntry 126 }

affirmedServiceconstructInterfaceAaaGroupDiameterStatisticsChassisLevelEndhostIntfTypeNumDERInitialNotification OBJECT-TYPE
    SYNTAX      ConfdString
    MAX-ACCESS  read-only
    STATUS      current
    DESCRIPTION "Number of initial authentication DER requests sent with notification"
    ::= { affirmedServiceconstructInterfaceAaaGroupDiameterStatisticsChassisLevelEndhostIntfTypeEntry 127 }

affirmedServiceconstructInterfaceAaaGroupDiameterStatisticsChassisLevelEndhostIntfTypeNumDERInitialDropByPoc OBJECT-TYPE
    SYNTAX      ConfdString
    MAX-ACCESS  read-only
    STATUS      current
    DESCRIPTION "Number of initial authentication DER requests are not sent as a result of peer overload control"
    ::= { affirmedServiceconstructInterfaceAaaGroupDiameterStatisticsChassisLevelEndhostIntfTypeEntry 128 }

affirmedServiceconstructInterfaceAaaGroupDiameterStatisticsChassisLevelEndhostIntfTypeNumDERInitialRedirect OBJECT-TYPE
    SYNTAX      ConfdString
    MAX-ACCESS  read-only
    STATUS      current
    DESCRIPTION "Number of initial authentication DER requests are redirected"
    ::= { affirmedServiceconstructInterfaceAaaGroupDiameterStatisticsChassisLevelEndhostIntfTypeEntry 129 }

affirmedServiceconstructInterfaceAaaGroupDiameterStatisticsChassisLevelEndhostIntfTypeNumDERReAuthAttempted OBJECT-TYPE
    SYNTAX      ConfdString
    MAX-ACCESS  read-only
    STATUS      current
    DESCRIPTION "Number of re-authentication DER attempts made"
    ::= { affirmedServiceconstructInterfaceAaaGroupDiameterStatisticsChassisLevelEndhostIntfTypeEntry 130 }

affirmedServiceconstructInterfaceAaaGroupDiameterStatisticsChassisLevelEndhostIntfTypeNumDERReAuthSuccess OBJECT-TYPE
    SYNTAX      ConfdString
    MAX-ACCESS  read-only
    STATUS      current
    DESCRIPTION "Number of re-authentication DER attempts that succeeded"
    ::= { affirmedServiceconstructInterfaceAaaGroupDiameterStatisticsChassisLevelEndhostIntfTypeEntry 131 }

affirmedServiceconstructInterfaceAaaGroupDiameterStatisticsChassisLevelEndhostIntfTypeNumDERReAuthFailure OBJECT-TYPE
    SYNTAX      ConfdString
    MAX-ACCESS  read-only
    STATUS      current
    DESCRIPTION "Number of re-authentication DER attempts that failed"
    ::= { affirmedServiceconstructInterfaceAaaGroupDiameterStatisticsChassisLevelEndhostIntfTypeEntry 132 }

affirmedServiceconstructInterfaceAaaGroupDiameterStatisticsChassisLevelEndhostIntfTypeNumDERReAuthTimeout OBJECT-TYPE
    SYNTAX      ConfdString
    MAX-ACCESS  read-only
    STATUS      current
    DESCRIPTION "Number of re-authentication DER attempts that timed out"
    ::= { affirmedServiceconstructInterfaceAaaGroupDiameterStatisticsChassisLevelEndhostIntfTypeEntry 133 }

affirmedServiceconstructInterfaceAaaGroupDiameterStatisticsChassisLevelEndhostIntfTypeNumDERReAuthChallenge OBJECT-TYPE
    SYNTAX      ConfdString
    MAX-ACCESS  read-only
    STATUS      current
    DESCRIPTION "Number of re-authentication DER attempts sent with Challenges"
    ::= { affirmedServiceconstructInterfaceAaaGroupDiameterStatisticsChassisLevelEndhostIntfTypeEntry 134 }

affirmedServiceconstructInterfaceAaaGroupDiameterStatisticsChassisLevelEndhostIntfTypeNumDERReAuthNotification OBJECT-TYPE
    SYNTAX      ConfdString
    MAX-ACCESS  read-only
    STATUS      current
    DESCRIPTION "Number of re-authentication DER attempts sent with Notification"
    ::= { affirmedServiceconstructInterfaceAaaGroupDiameterStatisticsChassisLevelEndhostIntfTypeEntry 135 }

affirmedServiceconstructInterfaceAaaGroupDiameterStatisticsChassisLevelEndhostIntfTypeNumDERReAuthDropByPoc OBJECT-TYPE
    SYNTAX      ConfdString
    MAX-ACCESS  read-only
    STATUS      current
    DESCRIPTION "Number of re-authentication DER requests are not sent as a result of peer overload control"
    ::= { affirmedServiceconstructInterfaceAaaGroupDiameterStatisticsChassisLevelEndhostIntfTypeEntry 136 }

affirmedServiceconstructInterfaceAaaGroupDiameterStatisticsChassisLevelEndhostIntfTypeNumDERReAuthRedirect OBJECT-TYPE
    SYNTAX      ConfdString
    MAX-ACCESS  read-only
    STATUS      current
    DESCRIPTION "Number of r-authentication DER requests are redirected"
    ::= { affirmedServiceconstructInterfaceAaaGroupDiameterStatisticsChassisLevelEndhostIntfTypeEntry 137 }

affirmedServiceconstructInterfaceAaaGroupDiameterStatisticsChassisLevelEndhostIntfTypeNumRarRcvd OBJECT-TYPE
    SYNTAX      ConfdString
    MAX-ACCESS  read-only
    STATUS      current
    DESCRIPTION "Number of Diameter RAR request received"
    ::= { affirmedServiceconstructInterfaceAaaGroupDiameterStatisticsChassisLevelEndhostIntfTypeEntry 138 }

affirmedServiceconstructInterfaceAaaGroupDiameterStatisticsChassisLevelEndhostIntfTypeNumRarFailure OBJECT-TYPE
    SYNTAX      ConfdString
    MAX-ACCESS  read-only
    STATUS      current
    DESCRIPTION "Number of Diameter RAR failed as sessions no longer exist"
    ::= { affirmedServiceconstructInterfaceAaaGroupDiameterStatisticsChassisLevelEndhostIntfTypeEntry 139 }

affirmedServiceconstructInterfaceAaaGroupDiameterStatisticsChassisLevelEndhostIntfTypeNumAsrRcvd OBJECT-TYPE
    SYNTAX      ConfdString
    MAX-ACCESS  read-only
    STATUS      current
    DESCRIPTION "Number of Diameter ASR request received"
    ::= { affirmedServiceconstructInterfaceAaaGroupDiameterStatisticsChassisLevelEndhostIntfTypeEntry 140 }

affirmedServiceconstructInterfaceAaaGroupDiameterStatisticsChassisLevelEndhostIntfTypeNumAsrFailure OBJECT-TYPE
    SYNTAX      ConfdString
    MAX-ACCESS  read-only
    STATUS      current
    DESCRIPTION "Number of Diameter ASR failed as sessions no longer exist"
    ::= { affirmedServiceconstructInterfaceAaaGroupDiameterStatisticsChassisLevelEndhostIntfTypeEntry 141 }

affirmedServiceconstructInterfaceAaaGroupDiameterStatisticsChassisLevelEndhostIntfTypeNumCCAInitialDroppedBadSeqNum OBJECT-TYPE
    SYNTAX      ConfdString
    MAX-ACCESS  read-only
    STATUS      current
    DESCRIPTION "Number of CCA Initial that were dropped due to unexpected sequence number in the response received from peer"
    ::= { affirmedServiceconstructInterfaceAaaGroupDiameterStatisticsChassisLevelEndhostIntfTypeEntry 142 }

affirmedServiceconstructInterfaceAaaGroupDiameterStatisticsChassisLevelEndhostIntfTypeNumCCAInitialDroppedNoSession OBJECT-TYPE
    SYNTAX      ConfdString
    MAX-ACCESS  read-only
    STATUS      current
    DESCRIPTION "Number of CCA Initial that were dropped due to session not found"
    ::= { affirmedServiceconstructInterfaceAaaGroupDiameterStatisticsChassisLevelEndhostIntfTypeEntry 143 }

affirmedServiceconstructInterfaceAaaGroupDiameterStatisticsChassisLevelEndhostIntfTypeNumCCAInitialDroppedNoProc OBJECT-TYPE
    SYNTAX      ConfdString
    MAX-ACCESS  read-only
    STATUS      current
    DESCRIPTION "Number of CCA Initial that were dropped due to no matching transaction"
    ::= { affirmedServiceconstructInterfaceAaaGroupDiameterStatisticsChassisLevelEndhostIntfTypeEntry 144 }

affirmedServiceconstructInterfaceAaaGroupDiameterStatisticsChassisLevelEndhostIntfTypeNumCCAUpdateDroppedBadSeqNum OBJECT-TYPE
    SYNTAX      ConfdString
    MAX-ACCESS  read-only
    STATUS      current
    DESCRIPTION "Number of CCA Update that were dropped due to unexpected sequence number in the response received from peer"
    ::= { affirmedServiceconstructInterfaceAaaGroupDiameterStatisticsChassisLevelEndhostIntfTypeEntry 145 }

affirmedServiceconstructInterfaceAaaGroupDiameterStatisticsChassisLevelEndhostIntfTypeNumCCAUpdateDroppedNoSession OBJECT-TYPE
    SYNTAX      ConfdString
    MAX-ACCESS  read-only
    STATUS      current
    DESCRIPTION "Number of CCA Update that were dropped due to session not found"
    ::= { affirmedServiceconstructInterfaceAaaGroupDiameterStatisticsChassisLevelEndhostIntfTypeEntry 146 }

affirmedServiceconstructInterfaceAaaGroupDiameterStatisticsChassisLevelEndhostIntfTypeNumCCAUpdateDroppedNoProc OBJECT-TYPE
    SYNTAX      ConfdString
    MAX-ACCESS  read-only
    STATUS      current
    DESCRIPTION "Number of CCA Update that were dropped due to no matching transaction"
    ::= { affirmedServiceconstructInterfaceAaaGroupDiameterStatisticsChassisLevelEndhostIntfTypeEntry 147 }

affirmedServiceconstructInterfaceAaaGroupDiameterStatisticsChassisLevelEndhostIntfTypeNumCCATerminateDroppedBadSeqNum OBJECT-TYPE
    SYNTAX      ConfdString
    MAX-ACCESS  read-only
    STATUS      current
    DESCRIPTION "Number of CCA Terminate that were dropped due to unexpected sequence number in the response received from peer"
    ::= { affirmedServiceconstructInterfaceAaaGroupDiameterStatisticsChassisLevelEndhostIntfTypeEntry 148 }

affirmedServiceconstructInterfaceAaaGroupDiameterStatisticsChassisLevelEndhostIntfTypeNumCCATerminateDroppedNoSession OBJECT-TYPE
    SYNTAX      ConfdString
    MAX-ACCESS  read-only
    STATUS      current
    DESCRIPTION "Number of CCA Terminate that were dropped due to session not found"
    ::= { affirmedServiceconstructInterfaceAaaGroupDiameterStatisticsChassisLevelEndhostIntfTypeEntry 149 }

affirmedServiceconstructInterfaceAaaGroupDiameterStatisticsChassisLevelEndhostIntfTypeNumCCATerminateDroppedNoProc OBJECT-TYPE
    SYNTAX      ConfdString
    MAX-ACCESS  read-only
    STATUS      current
    DESCRIPTION "Number of CCA Terminate that were dropped due to no matching transaction"
    ::= { affirmedServiceconstructInterfaceAaaGroupDiameterStatisticsChassisLevelEndhostIntfTypeEntry 150 }

affirmedServiceconstructInterfaceAaaGroupDiameterStatisticsChassisLevelEndhostIntfTypeNumCCAPendingTransaction OBJECT-TYPE
    SYNTAX      ConfdString
    MAX-ACCESS  read-only
    STATUS      current
    DESCRIPTION "Number of CCA Received with Experimental Result Code Pending Transaction"
    ::= { affirmedServiceconstructInterfaceAaaGroupDiameterStatisticsChassisLevelEndhostIntfTypeEntry 151 }

affirmedServiceconstructInterfaceAaaGroupDiameterStatisticsChassisLevelEndhostIntfTypeNumRarReceived OBJECT-TYPE
    SYNTAX      Unsigned32
    MAX-ACCESS  read-only
    STATUS      current
    DESCRIPTION "Number of RAR messages received from peer"
    ::= { affirmedServiceconstructInterfaceAaaGroupDiameterStatisticsChassisLevelEndhostIntfTypeEntry 152 }

affirmedServiceconstructInterfaceAaaGroupDiameterStatisticsChassisLevelEndhostIntfTypeNumRaaSuccess OBJECT-TYPE
    SYNTAX      Unsigned32
    MAX-ACCESS  read-only
    STATUS      current
    DESCRIPTION "Number of RAA success messages sent to peer"
    ::= { affirmedServiceconstructInterfaceAaaGroupDiameterStatisticsChassisLevelEndhostIntfTypeEntry 153 }

affirmedServiceconstructInterfaceAaaGroupDiameterStatisticsChassisLevelEndhostIntfTypeNumRaaSendFailure OBJECT-TYPE
    SYNTAX      Unsigned32
    MAX-ACCESS  read-only
    STATUS      current
    DESCRIPTION "Number of RAA messages failed to send to peer"
    ::= { affirmedServiceconstructInterfaceAaaGroupDiameterStatisticsChassisLevelEndhostIntfTypeEntry 154 }

affirmedServiceconstructInterfaceAaaGroupDiameterStatisticsChassisLevelEndhostIntfTypeNumRaaFailures OBJECT-TYPE
    SYNTAX      Unsigned32
    MAX-ACCESS  read-only
    STATUS      current
    DESCRIPTION "Number of RAA failure messages sent to peer"
    ::= { affirmedServiceconstructInterfaceAaaGroupDiameterStatisticsChassisLevelEndhostIntfTypeEntry 155 }

affirmedServiceconstructInterfaceAaaGroupDiameterStatisticsChassisLevelEndhostIntfTypeNumRaaFailuresUnknownSession OBJECT-TYPE
    SYNTAX      Unsigned32
    MAX-ACCESS  read-only
    STATUS      current
    DESCRIPTION "Number of RAA failure messages due to unknown session sent to peer"
    ::= { affirmedServiceconstructInterfaceAaaGroupDiameterStatisticsChassisLevelEndhostIntfTypeEntry 156 }

affirmedServiceconstructInterfaceAaaGroupDiameterStatisticsChassisLevelEndhostIntfTypeNumRaaFailuresMissingAVP OBJECT-TYPE
    SYNTAX      Unsigned32
    MAX-ACCESS  read-only
    STATUS      current
    DESCRIPTION "Number of RAA failure messages due to missing AVPs sent to peer"
    ::= { affirmedServiceconstructInterfaceAaaGroupDiameterStatisticsChassisLevelEndhostIntfTypeEntry 157 }

affirmedServiceconstructInterfaceAaaGroupDiameterStatisticsChassisLevelEndhostIntfTypeNumRaaFailuresAuthRejected OBJECT-TYPE
    SYNTAX      Unsigned32
    MAX-ACCESS  read-only
    STATUS      current
    DESCRIPTION "Number of RAA failure messages due to authentication rejection sent to peer"
    ::= { affirmedServiceconstructInterfaceAaaGroupDiameterStatisticsChassisLevelEndhostIntfTypeEntry 158 }

affirmedServiceconstructInterfaceAaaGroupDiameterStatisticsChassisLevelEndhostIntfTypeNumRaaFailuresAppUnsupported OBJECT-TYPE
    SYNTAX      Unsigned32
    MAX-ACCESS  read-only
    STATUS      current
    DESCRIPTION "Number of RAA failure messages due to unknown application ID sent to peer"
    ::= { affirmedServiceconstructInterfaceAaaGroupDiameterStatisticsChassisLevelEndhostIntfTypeEntry 159 }

affirmedServiceconstructInterfaceAaaGroupDiameterStatisticsChassisLevelEndhostIntfTypeNumRaaFailuresRealmNotServed OBJECT-TYPE
    SYNTAX      Unsigned32
    MAX-ACCESS  read-only
    STATUS      current
    DESCRIPTION "Number of RAA failure messages sent to peer due to Destination Realm in RAR not being recognized"
    ::= { affirmedServiceconstructInterfaceAaaGroupDiameterStatisticsChassisLevelEndhostIntfTypeEntry 160 }

affirmedServiceconstructInterfaceAaaGroupDiameterStatisticsChassisLevelEndhostIntfTypeNumRaaFailuresUnableToDeliver OBJECT-TYPE
    SYNTAX      Unsigned32
    MAX-ACCESS  read-only
    STATUS      current
    DESCRIPTION "Number of RAA failure messages sent to peer due to Destination Host in RAR not being found"
    ::= { affirmedServiceconstructInterfaceAaaGroupDiameterStatisticsChassisLevelEndhostIntfTypeEntry 161 }

affirmedServiceconstructInterfaceAaaGroupDiameterStatisticsChassisLevelEndhostIntfTypeNumRaaFailuresTooBusy OBJECT-TYPE
    SYNTAX      Unsigned32
    MAX-ACCESS  read-only
    STATUS      current
    DESCRIPTION "Number of RAA failure messages sent to peer due to Gateway too busy to process RAR"
    ::= { affirmedServiceconstructInterfaceAaaGroupDiameterStatisticsChassisLevelEndhostIntfTypeEntry 162 }

affirmedServiceconstructInterfaceAaaGroupDiameterStatisticsChassisLevelEndhostIntfTypeNumRaaPendingTransaction OBJECT-TYPE
    SYNTAX      Unsigned32
    MAX-ACCESS  read-only
    STATUS      current
    DESCRIPTION "Number of RAA with Experimental Result Code Pending Transaction"
    ::= { affirmedServiceconstructInterfaceAaaGroupDiameterStatisticsChassisLevelEndhostIntfTypeEntry 163 }

affirmedServiceconstructInterfaceAaaGroupDiameterStatisticsChassisLevelEndhostIntfTypeNumTimesPeerDeactivated OBJECT-TYPE
    SYNTAX      ConfdString
    MAX-ACCESS  read-only
    STATUS      current
    DESCRIPTION "Number of times the peer went down"
    ::= { affirmedServiceconstructInterfaceAaaGroupDiameterStatisticsChassisLevelEndhostIntfTypeEntry 164 }

affirmedServiceconstructInterfaceAaaGroupDiameterStatisticsChassisLevelEndhostIntfTypeNumTimesPeerFlowOffRcvd OBJECT-TYPE
    SYNTAX      ConfdString
    MAX-ACCESS  read-only
    STATUS      current
    DESCRIPTION "Number of times flow-off received for peer"
    ::= { affirmedServiceconstructInterfaceAaaGroupDiameterStatisticsChassisLevelEndhostIntfTypeEntry 165 }

affirmedServiceconstructInterfaceAaaGroupDiameterStatisticsChassisLevelEndhostIntfTypeNumAuthLifetmrInitAARAttmpted OBJECT-TYPE
    SYNTAX      ConfdString
    MAX-ACCESS  read-only
    STATUS      current
    DESCRIPTION "Number of Authorization-Lifetime timer Initiated AAR attempts made"
    ::= { affirmedServiceconstructInterfaceAaaGroupDiameterStatisticsChassisLevelEndhostIntfTypeEntry 166 }

affirmedServiceconstructInterfaceAaaGroupDiameterStatisticsChassisLevelEndhostIntfTypeNumAuthLifetimerInitAARSuccess OBJECT-TYPE
    SYNTAX      ConfdString
    MAX-ACCESS  read-only
    STATUS      current
    DESCRIPTION "Number of Authorization-Lifetime timer Initiated AAR success"
    ::= { affirmedServiceconstructInterfaceAaaGroupDiameterStatisticsChassisLevelEndhostIntfTypeEntry 167 }

affirmedServiceconstructInterfaceAaaGroupDiameterStatisticsChassisLevelEndhostIntfTypeNumAuthLifetimerInitAARFailure OBJECT-TYPE
    SYNTAX      ConfdString
    MAX-ACCESS  read-only
    STATUS      current
    DESCRIPTION "Number of Authorization-Lifetime timer Initiated AAR failure"
    ::= { affirmedServiceconstructInterfaceAaaGroupDiameterStatisticsChassisLevelEndhostIntfTypeEntry 168 }

affirmedServiceconstructInterfaceAaaGroupDiameterStatisticsChassisLevelEndhostIntfTypeNumAuthLifetimerInitAARTimeout OBJECT-TYPE
    SYNTAX      ConfdString
    MAX-ACCESS  read-only
    STATUS      current
    DESCRIPTION "Number of Authorization-Lifetime timer Initiated AAR attempts that timed out"
    ::= { affirmedServiceconstructInterfaceAaaGroupDiameterStatisticsChassisLevelEndhostIntfTypeEntry 169 }

affirmedServiceconstructInterfaceAaaGroupDiameterStatisticsChassisLevelEndhostIntfTypeNumAuthLifetmrInitAAARxFirstAt OBJECT-TYPE
    SYNTAX      ConfdString
    MAX-ACCESS  read-only
    STATUS      current
    DESCRIPTION "Number of Authorization-Lifetime timer Initiated AAR requests for which response was received when first transmitted "
    ::= { affirmedServiceconstructInterfaceAaaGroupDiameterStatisticsChassisLevelEndhostIntfTypeEntry 170 }

affirmedServiceconstructInterfaceAaaGroupDiameterStatisticsChassisLevelEndhostIntfTypeNumAuthLifetmrInitAAARxReTx OBJECT-TYPE
    SYNTAX      ConfdString
    MAX-ACCESS  read-only
    STATUS      current
    DESCRIPTION "Number of Authorization-Lifetime timer Initiated AAR Requests for which response was received when message was retransmitted"
    ::= { affirmedServiceconstructInterfaceAaaGroupDiameterStatisticsChassisLevelEndhostIntfTypeEntry 171 }

affirmedServiceconstructInterfaceAaaGroupDiameterStatisticsChassisLevelEndhostIntfTypeNumAuthLifetimerInitAARDropByPoc OBJECT-TYPE
    SYNTAX      ConfdString
    MAX-ACCESS  read-only
    STATUS      current
    DESCRIPTION "Number of Authorization-Lifetime timer Initiated AAR Requests are not sent as a result of peer overload control"
    ::= { affirmedServiceconstructInterfaceAaaGroupDiameterStatisticsChassisLevelEndhostIntfTypeEntry 172 }

affirmedServiceconstructInterfaceAaaGroupDiameterStatisticsChassisLevelEndhostIntfTypeNumAuthLifetimerInitAARRedirect OBJECT-TYPE
    SYNTAX      ConfdString
    MAX-ACCESS  read-only
    STATUS      current
    DESCRIPTION "Number of Authorization-Lifetime timer Initiated AAR Requests are redirected"
    ::= { affirmedServiceconstructInterfaceAaaGroupDiameterStatisticsChassisLevelEndhostIntfTypeEntry 173 }

affirmedServiceconstructInterfaceAaaGroupDiameterStatisticsChassisLevelEndhostIntfTypeNumAuthLifetimerInitAARRetry OBJECT-TYPE
    SYNTAX      ConfdString
    MAX-ACCESS  read-only
    STATUS      current
    DESCRIPTION "Number of Authorization-Lifetime AAR retransmits"
    ::= { affirmedServiceconstructInterfaceAaaGroupDiameterStatisticsChassisLevelEndhostIntfTypeEntry 174 }

affirmedServiceconstructInterfaceAaaGroupDiameterStatisticsChassisLevelEndhostIntfTypeNumAuthGraceTmrInitAARAtmpted OBJECT-TYPE
    SYNTAX      ConfdString
    MAX-ACCESS  read-only
    STATUS      current
    DESCRIPTION "Number of Auth-Grace-Period timer Initiated AAR attempts made"
    ::= { affirmedServiceconstructInterfaceAaaGroupDiameterStatisticsChassisLevelEndhostIntfTypeEntry 175 }

affirmedServiceconstructInterfaceAaaGroupDiameterStatisticsChassisLevelEndhostIntfTypeNumAuthGraceTmrInitAARSuccess OBJECT-TYPE
    SYNTAX      ConfdString
    MAX-ACCESS  read-only
    STATUS      current
    DESCRIPTION "Number of Auth-Grace-Period timer Initiated AAR success"
    ::= { affirmedServiceconstructInterfaceAaaGroupDiameterStatisticsChassisLevelEndhostIntfTypeEntry 176 }

affirmedServiceconstructInterfaceAaaGroupDiameterStatisticsChassisLevelEndhostIntfTypeNumAuthGraceTmrInitAARFailure OBJECT-TYPE
    SYNTAX      ConfdString
    MAX-ACCESS  read-only
    STATUS      current
    DESCRIPTION "Number of Auth-Grace-Period timer Initiated AAR failure"
    ::= { affirmedServiceconstructInterfaceAaaGroupDiameterStatisticsChassisLevelEndhostIntfTypeEntry 177 }

affirmedServiceconstructInterfaceAaaGroupDiameterStatisticsChassisLevelEndhostIntfTypeNumAuthGraceTmrInitAARTimeout OBJECT-TYPE
    SYNTAX      ConfdString
    MAX-ACCESS  read-only
    STATUS      current
    DESCRIPTION "Number of Auth-Grace-Period timer Initiated AAR attempts that timed out"
    ::= { affirmedServiceconstructInterfaceAaaGroupDiameterStatisticsChassisLevelEndhostIntfTypeEntry 178 }

affirmedServiceconstructInterfaceAaaGroupDiameterStatisticsChassisLevelEndhostIntfTypeNumAuthGraceTmrInitAAARxFstAt OBJECT-TYPE
    SYNTAX      ConfdString
    MAX-ACCESS  read-only
    STATUS      current
    DESCRIPTION "Number of Auth-Grace-Period timer Initiated AAR requests for which response was received when first transmitted "
    ::= { affirmedServiceconstructInterfaceAaaGroupDiameterStatisticsChassisLevelEndhostIntfTypeEntry 179 }

affirmedServiceconstructInterfaceAaaGroupDiameterStatisticsChassisLevelEndhostIntfTypeNumAuthGraceTmrInitAAARxReTx OBJECT-TYPE
    SYNTAX      ConfdString
    MAX-ACCESS  read-only
    STATUS      current
    DESCRIPTION "Number of Auth-Grace-Period timer Initiated AAR Requests for which response was received when message was retransmitted"
    ::= { affirmedServiceconstructInterfaceAaaGroupDiameterStatisticsChassisLevelEndhostIntfTypeEntry 180 }

affirmedServiceconstructInterfaceAaaGroupDiameterStatisticsChassisLevelEndhostIntfTypeNumAuthGraceTmrInitAARRetry OBJECT-TYPE
    SYNTAX      ConfdString
    MAX-ACCESS  read-only
    STATUS      current
    DESCRIPTION "Number of Auth-Grace-Period AAR retransmits"
    ::= { affirmedServiceconstructInterfaceAaaGroupDiameterStatisticsChassisLevelEndhostIntfTypeEntry 181 }

affirmedServiceconstructInterfaceAaaGroupDiameterStatisticsChassisLevelEndhostIntfTypeNumCCREventTx OBJECT-TYPE
    SYNTAX      ConfdString
    MAX-ACCESS  read-only
    STATUS      current
    DESCRIPTION "Number of CCR Event-Request has been transmitted"
    ::= { affirmedServiceconstructInterfaceAaaGroupDiameterStatisticsChassisLevelEndhostIntfTypeEntry 182 }

affirmedServiceconstructInterfaceAaaGroupDiameterStatisticsChassisLevelEndhostIntfTypeNumCCAEventRx OBJECT-TYPE
    SYNTAX      ConfdString
    MAX-ACCESS  read-only
    STATUS      current
    DESCRIPTION "Number of CCA Event-Request has been received"
    ::= { affirmedServiceconstructInterfaceAaaGroupDiameterStatisticsChassisLevelEndhostIntfTypeEntry 183 }

affirmedServiceconstructInterfaceAaaGroupDiameterStatisticsChassisLevelEndhostIntfTypeNumCCREventTimeout OBJECT-TYPE
    SYNTAX      ConfdString
    MAX-ACCESS  read-only
    STATUS      current
    DESCRIPTION "Number of CCR Event-Request has been timed out"
    ::= { affirmedServiceconstructInterfaceAaaGroupDiameterStatisticsChassisLevelEndhostIntfTypeEntry 184 }

affirmedServiceconstructInterfaceAaaGroupDiameterStatisticsChassisLevelEndhostIntfTypeNumNIRAttempted OBJECT-TYPE
    SYNTAX      ConfdString
    MAX-ACCESS  read-only
    STATUS      current
    DESCRIPTION "Number of NIR attempts made"
    ::= { affirmedServiceconstructInterfaceAaaGroupDiameterStatisticsChassisLevelEndhostIntfTypeEntry 185 }

affirmedServiceconstructInterfaceAaaGroupDiameterStatisticsChassisLevelEndhostIntfTypeNumNIRSuccess OBJECT-TYPE
    SYNTAX      ConfdString
    MAX-ACCESS  read-only
    STATUS      current
    DESCRIPTION "Number of NIR success responses received"
    ::= { affirmedServiceconstructInterfaceAaaGroupDiameterStatisticsChassisLevelEndhostIntfTypeEntry 186 }

affirmedServiceconstructInterfaceAaaGroupDiameterStatisticsChassisLevelEndhostIntfTypeNumNIRFailure OBJECT-TYPE
    SYNTAX      ConfdString
    MAX-ACCESS  read-only
    STATUS      current
    DESCRIPTION "Number of NIR failure responses received"
    ::= { affirmedServiceconstructInterfaceAaaGroupDiameterStatisticsChassisLevelEndhostIntfTypeEntry 187 }

affirmedServiceconstructInterfaceAaaGroupDiameterStatisticsChassisLevelEndhostIntfTypeNumNIRTimeout OBJECT-TYPE
    SYNTAX      ConfdString
    MAX-ACCESS  read-only
    STATUS      current
    DESCRIPTION "Number of NIR attempts timed out "
    ::= { affirmedServiceconstructInterfaceAaaGroupDiameterStatisticsChassisLevelEndhostIntfTypeEntry 188 }

affirmedServiceconstructInterfaceAaaGroupDiameterStatisticsChassisLevelEndhostIntfTypeNumNIRAborted OBJECT-TYPE
    SYNTAX      ConfdString
    MAX-ACCESS  read-only
    STATUS      current
    DESCRIPTION "Number of NIR attempts aborted"
    ::= { affirmedServiceconstructInterfaceAaaGroupDiameterStatisticsChassisLevelEndhostIntfTypeEntry 189 }

affirmedServiceconstructInterfaceAaaGroupDiameterStatisticsChassisLevelEndhostIntfTypeNumNIRcvdFirstAttempt OBJECT-TYPE
    SYNTAX      ConfdString
    MAX-ACCESS  read-only
    STATUS      current
    DESCRIPTION "Number of NIA received to the initial NIR request"
    ::= { affirmedServiceconstructInterfaceAaaGroupDiameterStatisticsChassisLevelEndhostIntfTypeEntry 190 }

affirmedServiceconstructInterfaceAaaGroupDiameterStatisticsChassisLevelEndhostIntfTypeNumNIARcvdReTx OBJECT-TYPE
    SYNTAX      ConfdString
    MAX-ACCESS  read-only
    STATUS      current
    DESCRIPTION "Number of NIA received to the retransmitted NIR request"
    ::= { affirmedServiceconstructInterfaceAaaGroupDiameterStatisticsChassisLevelEndhostIntfTypeEntry 191 }

affirmedServiceconstructInterfaceAaaGroupDiameterStatisticsChassisLevelEndhostIntfTypeNumNIA3xxx OBJECT-TYPE
    SYNTAX      ConfdString
    MAX-ACCESS  read-only
    STATUS      current
    DESCRIPTION "Number of NIA received with 3xxx result code"
    ::= { affirmedServiceconstructInterfaceAaaGroupDiameterStatisticsChassisLevelEndhostIntfTypeEntry 192 }

affirmedServiceconstructInterfaceAaaGroupDiameterStatisticsChassisLevelEndhostIntfTypeNumNIA4xxx OBJECT-TYPE
    SYNTAX      ConfdString
    MAX-ACCESS  read-only
    STATUS      current
    DESCRIPTION "Number of NIA received with 4xxx result code"
    ::= { affirmedServiceconstructInterfaceAaaGroupDiameterStatisticsChassisLevelEndhostIntfTypeEntry 193 }

affirmedServiceconstructInterfaceAaaGroupDiameterStatisticsChassisLevelEndhostIntfTypeNumNIA5xxx OBJECT-TYPE
    SYNTAX      ConfdString
    MAX-ACCESS  read-only
    STATUS      current
    DESCRIPTION "Number of NIA received with 5xxx result code"
    ::= { affirmedServiceconstructInterfaceAaaGroupDiameterStatisticsChassisLevelEndhostIntfTypeEntry 194 }

affirmedServiceconstructInterfaceAaaGroupDiameterStatisticsChassisLevelEndhostIntfTypeNumNIADelayedSuccess OBJECT-TYPE
    SYNTAX      ConfdString
    MAX-ACCESS  read-only
    STATUS      current
    DESCRIPTION "Number of NIA success received after the request had been re-transmitted to another server"
    ::= { affirmedServiceconstructInterfaceAaaGroupDiameterStatisticsChassisLevelEndhostIntfTypeEntry 195 }

affirmedServiceconstructInterfaceAaaGroupDiameterStatisticsChassisLevelEndhostIntfTypeNumNIADelayedFailure OBJECT-TYPE
    SYNTAX      ConfdString
    MAX-ACCESS  read-only
    STATUS      current
    DESCRIPTION "Number of NIA failures received after the request had been re-transmitted to another server"
    ::= { affirmedServiceconstructInterfaceAaaGroupDiameterStatisticsChassisLevelEndhostIntfTypeEntry 196 }

affirmedServiceconstructInterfaceAaaGroupDiameterStatisticsChassisLevelEndhostIntfTypeNumNIADelayed3xxx OBJECT-TYPE
    SYNTAX      ConfdString
    MAX-ACCESS  read-only
    STATUS      current
    DESCRIPTION "Number of NIA received with 3xxx result code after the request had been re-transmitted to another server"
    ::= { affirmedServiceconstructInterfaceAaaGroupDiameterStatisticsChassisLevelEndhostIntfTypeEntry 197 }

affirmedServiceconstructInterfaceAaaGroupDiameterStatisticsChassisLevelEndhostIntfTypeNumNIADroppedNoProc OBJECT-TYPE
    SYNTAX      ConfdString
    MAX-ACCESS  read-only
    STATUS      current
    DESCRIPTION "Number of NIA dropped due to no matching transaction identifier"
    ::= { affirmedServiceconstructInterfaceAaaGroupDiameterStatisticsChassisLevelEndhostIntfTypeEntry 198 }

affirmedServiceconstructInterfaceAaaGroupDiameterStatisticsChassisLevelEndhostIntfTypeNumCIRAttempted OBJECT-TYPE
    SYNTAX      ConfdString
    MAX-ACCESS  read-only
    STATUS      current
    DESCRIPTION "Number of CIR attempts made"
    ::= { affirmedServiceconstructInterfaceAaaGroupDiameterStatisticsChassisLevelEndhostIntfTypeEntry 199 }

affirmedServiceconstructInterfaceAaaGroupDiameterStatisticsChassisLevelEndhostIntfTypeNumCIRSuccess OBJECT-TYPE
    SYNTAX      ConfdString
    MAX-ACCESS  read-only
    STATUS      current
    DESCRIPTION "Number of CIR success responses received"
    ::= { affirmedServiceconstructInterfaceAaaGroupDiameterStatisticsChassisLevelEndhostIntfTypeEntry 200 }

affirmedServiceconstructInterfaceAaaGroupDiameterStatisticsChassisLevelEndhostIntfTypeNumCIRFailure OBJECT-TYPE
    SYNTAX      ConfdString
    MAX-ACCESS  read-only
    STATUS      current
    DESCRIPTION "Number of CIR failure responses received"
    ::= { affirmedServiceconstructInterfaceAaaGroupDiameterStatisticsChassisLevelEndhostIntfTypeEntry 201 }

affirmedServiceconstructInterfaceAaaGroupDiameterStatisticsChassisLevelEndhostIntfTypeNumCIRTimeout OBJECT-TYPE
    SYNTAX      ConfdString
    MAX-ACCESS  read-only
    STATUS      current
    DESCRIPTION "Number of CIR attempts timed out"
    ::= { affirmedServiceconstructInterfaceAaaGroupDiameterStatisticsChassisLevelEndhostIntfTypeEntry 202 }

affirmedServiceconstructInterfaceAaaGroupDiameterStatisticsChassisLevelEndhostIntfTypeNumCIRAborted OBJECT-TYPE
    SYNTAX      ConfdString
    MAX-ACCESS  read-only
    STATUS      current
    DESCRIPTION "Number of CIR attempts aborted"
    ::= { affirmedServiceconstructInterfaceAaaGroupDiameterStatisticsChassisLevelEndhostIntfTypeEntry 203 }

affirmedServiceconstructInterfaceAaaGroupDiameterStatisticsChassisLevelEndhostIntfTypeNumCIRcvdFirstAttempt OBJECT-TYPE
    SYNTAX      ConfdString
    MAX-ACCESS  read-only
    STATUS      current
    DESCRIPTION "Number of CIA received to the initial CIR request"
    ::= { affirmedServiceconstructInterfaceAaaGroupDiameterStatisticsChassisLevelEndhostIntfTypeEntry 204 }

affirmedServiceconstructInterfaceAaaGroupDiameterStatisticsChassisLevelEndhostIntfTypeNumCIARcvdReTx OBJECT-TYPE
    SYNTAX      ConfdString
    MAX-ACCESS  read-only
    STATUS      current
    DESCRIPTION "Number of CIA received to the retransmitted CIR request"
    ::= { affirmedServiceconstructInterfaceAaaGroupDiameterStatisticsChassisLevelEndhostIntfTypeEntry 205 }

affirmedServiceconstructInterfaceAaaGroupDiameterStatisticsChassisLevelEndhostIntfTypeNumCIA3xxx OBJECT-TYPE
    SYNTAX      ConfdString
    MAX-ACCESS  read-only
    STATUS      current
    DESCRIPTION "Number of CIA received with 3xxx result code"
    ::= { affirmedServiceconstructInterfaceAaaGroupDiameterStatisticsChassisLevelEndhostIntfTypeEntry 206 }

affirmedServiceconstructInterfaceAaaGroupDiameterStatisticsChassisLevelEndhostIntfTypeNumCIA4xxx OBJECT-TYPE
    SYNTAX      ConfdString
    MAX-ACCESS  read-only
    STATUS      current
    DESCRIPTION "Number of CIA received with 4xxx result code"
    ::= { affirmedServiceconstructInterfaceAaaGroupDiameterStatisticsChassisLevelEndhostIntfTypeEntry 207 }

affirmedServiceconstructInterfaceAaaGroupDiameterStatisticsChassisLevelEndhostIntfTypeNumCIA5xxx OBJECT-TYPE
    SYNTAX      ConfdString
    MAX-ACCESS  read-only
    STATUS      current
    DESCRIPTION "Number of CIA received with 5xxx result code"
    ::= { affirmedServiceconstructInterfaceAaaGroupDiameterStatisticsChassisLevelEndhostIntfTypeEntry 208 }

affirmedServiceconstructInterfaceAaaGroupDiameterStatisticsChassisLevelEndhostIntfTypeNumCIADelayedSuccess OBJECT-TYPE
    SYNTAX      ConfdString
    MAX-ACCESS  read-only
    STATUS      current
    DESCRIPTION "Number of CIA success received after the request had been re-transmitted to another server"
    ::= { affirmedServiceconstructInterfaceAaaGroupDiameterStatisticsChassisLevelEndhostIntfTypeEntry 209 }

affirmedServiceconstructInterfaceAaaGroupDiameterStatisticsChassisLevelEndhostIntfTypeNumCIADelayedFailure OBJECT-TYPE
    SYNTAX      ConfdString
    MAX-ACCESS  read-only
    STATUS      current
    DESCRIPTION "Number of CIA failures received after the request had been re-transmitted to another server"
    ::= { affirmedServiceconstructInterfaceAaaGroupDiameterStatisticsChassisLevelEndhostIntfTypeEntry 210 }

affirmedServiceconstructInterfaceAaaGroupDiameterStatisticsChassisLevelEndhostIntfTypeNumCIADelayed3xxx OBJECT-TYPE
    SYNTAX      ConfdString
    MAX-ACCESS  read-only
    STATUS      current
    DESCRIPTION "Number of CIA received with 3xxx result code after the request had been re-transmitted to another server"
    ::= { affirmedServiceconstructInterfaceAaaGroupDiameterStatisticsChassisLevelEndhostIntfTypeEntry 211 }

affirmedServiceconstructInterfaceAaaGroupDiameterStatisticsChassisLevelEndhostIntfTypeNumCIADroppedNoProc OBJECT-TYPE
    SYNTAX      ConfdString
    MAX-ACCESS  read-only
    STATUS      current
    DESCRIPTION "Number of CIA dropped due to no matching transaction identifier"
    ::= { affirmedServiceconstructInterfaceAaaGroupDiameterStatisticsChassisLevelEndhostIntfTypeEntry 212 }

affirmedServiceconstructInterfaceAaaGroupDiameterStatisticsChassisLevelEndhostIntfTypeNumTDRAttempted OBJECT-TYPE
    SYNTAX      ConfdString
    MAX-ACCESS  read-only
    STATUS      current
    DESCRIPTION "Number of TDR attempts made"
    ::= { affirmedServiceconstructInterfaceAaaGroupDiameterStatisticsChassisLevelEndhostIntfTypeEntry 213 }

affirmedServiceconstructInterfaceAaaGroupDiameterStatisticsChassisLevelEndhostIntfTypeNumTDRSuccess OBJECT-TYPE
    SYNTAX      ConfdString
    MAX-ACCESS  read-only
    STATUS      current
    DESCRIPTION "Number of TDR success responses received"
    ::= { affirmedServiceconstructInterfaceAaaGroupDiameterStatisticsChassisLevelEndhostIntfTypeEntry 214 }

affirmedServiceconstructInterfaceAaaGroupDiameterStatisticsChassisLevelEndhostIntfTypeNumTDRFailure OBJECT-TYPE
    SYNTAX      ConfdString
    MAX-ACCESS  read-only
    STATUS      current
    DESCRIPTION "Number of TDR failure responses received"
    ::= { affirmedServiceconstructInterfaceAaaGroupDiameterStatisticsChassisLevelEndhostIntfTypeEntry 215 }

affirmedServiceconstructInterfaceAaaGroupDiameterStatisticsChassisLevelEndhostIntfTypeNumTDRTimeout OBJECT-TYPE
    SYNTAX      ConfdString
    MAX-ACCESS  read-only
    STATUS      current
    DESCRIPTION "Number of TDR attempts timed out"
    ::= { affirmedServiceconstructInterfaceAaaGroupDiameterStatisticsChassisLevelEndhostIntfTypeEntry 216 }

affirmedServiceconstructInterfaceAaaGroupDiameterStatisticsChassisLevelEndhostIntfTypeNumTDRAborted OBJECT-TYPE
    SYNTAX      ConfdString
    MAX-ACCESS  read-only
    STATUS      current
    DESCRIPTION "Number of TDR attempts aborted"
    ::= { affirmedServiceconstructInterfaceAaaGroupDiameterStatisticsChassisLevelEndhostIntfTypeEntry 217 }

affirmedServiceconstructInterfaceAaaGroupDiameterStatisticsChassisLevelEndhostIntfTypeNumTDARcvdFirstAttempt OBJECT-TYPE
    SYNTAX      ConfdString
    MAX-ACCESS  read-only
    STATUS      current
    DESCRIPTION "Number of TDA received to the initial request"
    ::= { affirmedServiceconstructInterfaceAaaGroupDiameterStatisticsChassisLevelEndhostIntfTypeEntry 218 }

affirmedServiceconstructInterfaceAaaGroupDiameterStatisticsChassisLevelEndhostIntfTypeNumTDARcvdReTx OBJECT-TYPE
    SYNTAX      ConfdString
    MAX-ACCESS  read-only
    STATUS      current
    DESCRIPTION "Number of TDA received to the retransmitted TDR request"
    ::= { affirmedServiceconstructInterfaceAaaGroupDiameterStatisticsChassisLevelEndhostIntfTypeEntry 219 }

affirmedServiceconstructInterfaceAaaGroupDiameterStatisticsChassisLevelEndhostIntfTypeNumTDA3xxx OBJECT-TYPE
    SYNTAX      ConfdString
    MAX-ACCESS  read-only
    STATUS      current
    DESCRIPTION "Number of TDA received with 3xxx result code"
    ::= { affirmedServiceconstructInterfaceAaaGroupDiameterStatisticsChassisLevelEndhostIntfTypeEntry 220 }

affirmedServiceconstructInterfaceAaaGroupDiameterStatisticsChassisLevelEndhostIntfTypeNumTDA4xxx OBJECT-TYPE
    SYNTAX      ConfdString
    MAX-ACCESS  read-only
    STATUS      current
    DESCRIPTION "Number of TDA received with 4xxx result code"
    ::= { affirmedServiceconstructInterfaceAaaGroupDiameterStatisticsChassisLevelEndhostIntfTypeEntry 221 }

affirmedServiceconstructInterfaceAaaGroupDiameterStatisticsChassisLevelEndhostIntfTypeNumTDA5xxx OBJECT-TYPE
    SYNTAX      ConfdString
    MAX-ACCESS  read-only
    STATUS      current
    DESCRIPTION "Number of TDA received with 5xxx result code"
    ::= { affirmedServiceconstructInterfaceAaaGroupDiameterStatisticsChassisLevelEndhostIntfTypeEntry 222 }

affirmedServiceconstructInterfaceAaaGroupDiameterStatisticsChassisLevelEndhostIntfTypeNumTDADroppedNoProc OBJECT-TYPE
    SYNTAX      ConfdString
    MAX-ACCESS  read-only
    STATUS      current
    DESCRIPTION "Number of TDA dropped due to no matching transaction"
    ::= { affirmedServiceconstructInterfaceAaaGroupDiameterStatisticsChassisLevelEndhostIntfTypeEntry 223 }

affirmedServiceconstructInterfaceAaaGroupDiameterStatisticsChassisLevelEndhostIntfTypeNumCmrCReceived OBJECT-TYPE
    SYNTAX      ConfdString
    MAX-ACCESS  read-only
    STATUS      current
    DESCRIPTION "Number of CMR connection establishment requests received"
    ::= { affirmedServiceconstructInterfaceAaaGroupDiameterStatisticsChassisLevelEndhostIntfTypeEntry 224 }

affirmedServiceconstructInterfaceAaaGroupDiameterStatisticsChassisLevelEndhostIntfTypeNumCMACSuccess OBJECT-TYPE
    SYNTAX      ConfdString
    MAX-ACCESS  read-only
    STATUS      current
    DESCRIPTION "Number of CMR connection establishment success responses sent"
    ::= { affirmedServiceconstructInterfaceAaaGroupDiameterStatisticsChassisLevelEndhostIntfTypeEntry 225 }

affirmedServiceconstructInterfaceAaaGroupDiameterStatisticsChassisLevelEndhostIntfTypeNumCMACFailures OBJECT-TYPE
    SYNTAX      ConfdString
    MAX-ACCESS  read-only
    STATUS      current
    DESCRIPTION "Number of CMR connection establishment failure responses sent"
    ::= { affirmedServiceconstructInterfaceAaaGroupDiameterStatisticsChassisLevelEndhostIntfTypeEntry 226 }

affirmedServiceconstructInterfaceAaaGroupDiameterStatisticsChassisLevelEndhostIntfTypeNumCMACFailuresUnknownSession OBJECT-TYPE
    SYNTAX      ConfdString
    MAX-ACCESS  read-only
    STATUS      current
    DESCRIPTION "Number of CMR connection establishment failures due to unknown session"
    ::= { affirmedServiceconstructInterfaceAaaGroupDiameterStatisticsChassisLevelEndhostIntfTypeEntry 227 }

affirmedServiceconstructInterfaceAaaGroupDiameterStatisticsChassisLevelEndhostIntfTypeNumCMACFailuresMissingAVP OBJECT-TYPE
    SYNTAX      ConfdString
    MAX-ACCESS  read-only
    STATUS      current
    DESCRIPTION "Number of CMR connection establishment failures due to missing AVPs"
    ::= { affirmedServiceconstructInterfaceAaaGroupDiameterStatisticsChassisLevelEndhostIntfTypeEntry 228 }

affirmedServiceconstructInterfaceAaaGroupDiameterStatisticsChassisLevelEndhostIntfTypeNumCmrUReceived OBJECT-TYPE
    SYNTAX      ConfdString
    MAX-ACCESS  read-only
    STATUS      current
    DESCRIPTION "Number of CMR connection update requests received"
    ::= { affirmedServiceconstructInterfaceAaaGroupDiameterStatisticsChassisLevelEndhostIntfTypeEntry 229 }

affirmedServiceconstructInterfaceAaaGroupDiameterStatisticsChassisLevelEndhostIntfTypeNumCMAUSuccess OBJECT-TYPE
    SYNTAX      ConfdString
    MAX-ACCESS  read-only
    STATUS      current
    DESCRIPTION "Number of CMR connection update success responses sent"
    ::= { affirmedServiceconstructInterfaceAaaGroupDiameterStatisticsChassisLevelEndhostIntfTypeEntry 230 }

affirmedServiceconstructInterfaceAaaGroupDiameterStatisticsChassisLevelEndhostIntfTypeNumCMAUFailures OBJECT-TYPE
    SYNTAX      ConfdString
    MAX-ACCESS  read-only
    STATUS      current
    DESCRIPTION "Number of CMR connection update failure responses sent"
    ::= { affirmedServiceconstructInterfaceAaaGroupDiameterStatisticsChassisLevelEndhostIntfTypeEntry 231 }

affirmedServiceconstructInterfaceAaaGroupDiameterStatisticsChassisLevelEndhostIntfTypeNumCMAUFailuresUnknownSession OBJECT-TYPE
    SYNTAX      ConfdString
    MAX-ACCESS  read-only
    STATUS      current
    DESCRIPTION "Number of CMR connection update failures due to unknown session"
    ::= { affirmedServiceconstructInterfaceAaaGroupDiameterStatisticsChassisLevelEndhostIntfTypeEntry 232 }

affirmedServiceconstructInterfaceAaaGroupDiameterStatisticsChassisLevelEndhostIntfTypeNumCMAUFailuresMissingAVP OBJECT-TYPE
    SYNTAX      ConfdString
    MAX-ACCESS  read-only
    STATUS      current
    DESCRIPTION "Number of CMR connection update failures due to missing AVPs"
    ::= { affirmedServiceconstructInterfaceAaaGroupDiameterStatisticsChassisLevelEndhostIntfTypeEntry 233 }

affirmedServiceconstructInterfaceAaaGroupDiameterStatisticsChassisLevelEndhostIntfTypeNumCmrRReceived OBJECT-TYPE
    SYNTAX      ConfdString
    MAX-ACCESS  read-only
    STATUS      current
    DESCRIPTION "Number of CMR connection release requests received"
    ::= { affirmedServiceconstructInterfaceAaaGroupDiameterStatisticsChassisLevelEndhostIntfTypeEntry 234 }

affirmedServiceconstructInterfaceAaaGroupDiameterStatisticsChassisLevelEndhostIntfTypeNumCMARSuccess OBJECT-TYPE
    SYNTAX      ConfdString
    MAX-ACCESS  read-only
    STATUS      current
    DESCRIPTION "Number of CMR connection release success responses sent"
    ::= { affirmedServiceconstructInterfaceAaaGroupDiameterStatisticsChassisLevelEndhostIntfTypeEntry 235 }

affirmedServiceconstructInterfaceAaaGroupDiameterStatisticsChassisLevelEndhostIntfTypeNumCMARFailures OBJECT-TYPE
    SYNTAX      ConfdString
    MAX-ACCESS  read-only
    STATUS      current
    DESCRIPTION "Number of CMR connection release failure responses sent"
    ::= { affirmedServiceconstructInterfaceAaaGroupDiameterStatisticsChassisLevelEndhostIntfTypeEntry 236 }

affirmedServiceconstructInterfaceAaaGroupDiameterStatisticsChassisLevelEndhostIntfTypeNumCMARFailuresUnknownSession OBJECT-TYPE
    SYNTAX      ConfdString
    MAX-ACCESS  read-only
    STATUS      current
    DESCRIPTION "Number of CMR connection release failures due to unknown session"
    ::= { affirmedServiceconstructInterfaceAaaGroupDiameterStatisticsChassisLevelEndhostIntfTypeEntry 237 }

affirmedServiceconstructInterfaceAaaGroupDiameterStatisticsChassisLevelEndhostIntfTypeNumCMARFailuresMissingAVP OBJECT-TYPE
    SYNTAX      ConfdString
    MAX-ACCESS  read-only
    STATUS      current
    DESCRIPTION "Number of CMR connection release failures due to missing AVPs"
    ::= { affirmedServiceconstructInterfaceAaaGroupDiameterStatisticsChassisLevelEndhostIntfTypeEntry 238 }

affirmedServiceconstructInterfaceAaaGroupDiameterStatisticsChassisLevelEndhostIntfTypeNumCMRRScefInitAttempted OBJECT-TYPE
    SYNTAX      ConfdString
    MAX-ACCESS  read-only
    STATUS      current
    DESCRIPTION "Number of CMR connection release attempts made"
    ::= { affirmedServiceconstructInterfaceAaaGroupDiameterStatisticsChassisLevelEndhostIntfTypeEntry 239 }

affirmedServiceconstructInterfaceAaaGroupDiameterStatisticsChassisLevelEndhostIntfTypeNumCMRRScefInitSuccess OBJECT-TYPE
    SYNTAX      ConfdString
    MAX-ACCESS  read-only
    STATUS      current
    DESCRIPTION "Number of CMR connection release success responses received"
    ::= { affirmedServiceconstructInterfaceAaaGroupDiameterStatisticsChassisLevelEndhostIntfTypeEntry 240 }

affirmedServiceconstructInterfaceAaaGroupDiameterStatisticsChassisLevelEndhostIntfTypeNumCMRRScefInitFailure OBJECT-TYPE
    SYNTAX      ConfdString
    MAX-ACCESS  read-only
    STATUS      current
    DESCRIPTION "Number of CMR connection release failure responses received"
    ::= { affirmedServiceconstructInterfaceAaaGroupDiameterStatisticsChassisLevelEndhostIntfTypeEntry 241 }

affirmedServiceconstructInterfaceAaaGroupDiameterStatisticsChassisLevelEndhostIntfTypeNumCMRRScefInitTimeout OBJECT-TYPE
    SYNTAX      ConfdString
    MAX-ACCESS  read-only
    STATUS      current
    DESCRIPTION "Number of CMR connection release attempts timed out"
    ::= { affirmedServiceconstructInterfaceAaaGroupDiameterStatisticsChassisLevelEndhostIntfTypeEntry 242 }

affirmedServiceconstructInterfaceAaaGroupDiameterStatisticsChassisLevelEndhostIntfTypeNumCMRRScefInitAborted OBJECT-TYPE
    SYNTAX      ConfdString
    MAX-ACCESS  read-only
    STATUS      current
    DESCRIPTION "Number of CMR connection release attempts aborted"
    ::= { affirmedServiceconstructInterfaceAaaGroupDiameterStatisticsChassisLevelEndhostIntfTypeEntry 243 }

affirmedServiceconstructInterfaceAaaGroupDiameterStatisticsChassisLevelEndhostIntfTypeNumCMARScefInitRcvdFirstAttempt OBJECT-TYPE
    SYNTAX      ConfdString
    MAX-ACCESS  read-only
    STATUS      current
    DESCRIPTION "Number of CMR connection release responses received to the initial request"
    ::= { affirmedServiceconstructInterfaceAaaGroupDiameterStatisticsChassisLevelEndhostIntfTypeEntry 244 }

affirmedServiceconstructInterfaceAaaGroupDiameterStatisticsChassisLevelEndhostIntfTypeNumCMARScefInitRcvdReTx OBJECT-TYPE
    SYNTAX      ConfdString
    MAX-ACCESS  read-only
    STATUS      current
    DESCRIPTION "Number of CMR connection release responses received to the retransmitted request"
    ::= { affirmedServiceconstructInterfaceAaaGroupDiameterStatisticsChassisLevelEndhostIntfTypeEntry 245 }

affirmedServiceconstructInterfaceAaaGroupDiameterStatisticsChassisLevelEndhostIntfTypeNumCMARScefInit3xxx OBJECT-TYPE
    SYNTAX      ConfdString
    MAX-ACCESS  read-only
    STATUS      current
    DESCRIPTION "Number of CMR connection release responses received with 3xxx result code"
    ::= { affirmedServiceconstructInterfaceAaaGroupDiameterStatisticsChassisLevelEndhostIntfTypeEntry 246 }

affirmedServiceconstructInterfaceAaaGroupDiameterStatisticsChassisLevelEndhostIntfTypeNumCMARScefInit4xxx OBJECT-TYPE
    SYNTAX      ConfdString
    MAX-ACCESS  read-only
    STATUS      current
    DESCRIPTION "Number of CMR Connection Release responses received with 4xxx result code"
    ::= { affirmedServiceconstructInterfaceAaaGroupDiameterStatisticsChassisLevelEndhostIntfTypeEntry 247 }

affirmedServiceconstructInterfaceAaaGroupDiameterStatisticsChassisLevelEndhostIntfTypeNumCMARScefInit5xxx OBJECT-TYPE
    SYNTAX      ConfdString
    MAX-ACCESS  read-only
    STATUS      current
    DESCRIPTION "Number of CMR Connection Release responses received with 5xxx result code"
    ::= { affirmedServiceconstructInterfaceAaaGroupDiameterStatisticsChassisLevelEndhostIntfTypeEntry 248 }

affirmedServiceconstructInterfaceAaaGroupDiameterStatisticsChassisLevelEndhostIntfTypeNumCMARScefInitDroppedNoProc OBJECT-TYPE
    SYNTAX      ConfdString
    MAX-ACCESS  read-only
    STATUS      current
    DESCRIPTION "Number of CMR connection release answers dropped due to no matching transaction"
    ::= { affirmedServiceconstructInterfaceAaaGroupDiameterStatisticsChassisLevelEndhostIntfTypeEntry 249 }

affirmedServiceconstructInterfaceAaaGroupDiameterStatisticsChassisLevelEndhostIntfTypeNumODRReceived OBJECT-TYPE
    SYNTAX      ConfdString
    MAX-ACCESS  read-only
    STATUS      current
    DESCRIPTION "Number of ODR messages received"
    ::= { affirmedServiceconstructInterfaceAaaGroupDiameterStatisticsChassisLevelEndhostIntfTypeEntry 250 }

affirmedServiceconstructInterfaceAaaGroupDiameterStatisticsChassisLevelEndhostIntfTypeNumODASuccess OBJECT-TYPE
    SYNTAX      ConfdString
    MAX-ACCESS  read-only
    STATUS      current
    DESCRIPTION "Number of ODR success responses sent"
    ::= { affirmedServiceconstructInterfaceAaaGroupDiameterStatisticsChassisLevelEndhostIntfTypeEntry 251 }

affirmedServiceconstructInterfaceAaaGroupDiameterStatisticsChassisLevelEndhostIntfTypeNumODAFailures OBJECT-TYPE
    SYNTAX      ConfdString
    MAX-ACCESS  read-only
    STATUS      current
    DESCRIPTION "Number of ODR failure responses sent"
    ::= { affirmedServiceconstructInterfaceAaaGroupDiameterStatisticsChassisLevelEndhostIntfTypeEntry 252 }

affirmedServiceconstructInterfaceAaaGroupDiameterStatisticsChassisLevelEndhostIntfTypeNumODAFailuresUnknownSession OBJECT-TYPE
    SYNTAX      ConfdString
    MAX-ACCESS  read-only
    STATUS      current
    DESCRIPTION "Number of ODR failures due to unknown session"
    ::= { affirmedServiceconstructInterfaceAaaGroupDiameterStatisticsChassisLevelEndhostIntfTypeEntry 253 }

affirmedServiceconstructInterfaceAaaGroupDiameterStatisticsChassisLevelEndhostIntfTypeNumODAFailuresMissingAVP OBJECT-TYPE
    SYNTAX      ConfdString
    MAX-ACCESS  read-only
    STATUS      current
    DESCRIPTION "Number of ODR failures due to missing AVPs"
    ::= { affirmedServiceconstructInterfaceAaaGroupDiameterStatisticsChassisLevelEndhostIntfTypeEntry 254 }

affirmedServiceconstructInterfaceAaaGroupDiameterStatisticsChassisLevelEndhostIntfTypeNumODAFailuresUnableToDeliver OBJECT-TYPE
    SYNTAX      ConfdString
    MAX-ACCESS  read-only
    STATUS      current
    DESCRIPTION "Number of ODR failures due to Destination Host in ODR not being found"
    ::= { affirmedServiceconstructInterfaceAaaGroupDiameterStatisticsChassisLevelEndhostIntfTypeEntry 255 }

affirmedServiceconstructInterfaceAaaGroupDiameterStatisticsChassisLevelEndhostIntfTypeNumRIRReceived OBJECT-TYPE
    SYNTAX      ConfdString
    MAX-ACCESS  read-only
    STATUS      current
    DESCRIPTION "Number of RIR messages received"
    ::= { affirmedServiceconstructInterfaceAaaGroupDiameterStatisticsChassisLevelEndhostIntfTypeEntry 256 }

affirmedServiceconstructInterfaceAaaGroupDiameterStatisticsChassisLevelEndhostIntfTypeNumRIASuccess OBJECT-TYPE
    SYNTAX      ConfdString
    MAX-ACCESS  read-only
    STATUS      current
    DESCRIPTION "Number of RIR success responses sent"
    ::= { affirmedServiceconstructInterfaceAaaGroupDiameterStatisticsChassisLevelEndhostIntfTypeEntry 257 }

affirmedServiceconstructInterfaceAaaGroupDiameterStatisticsChassisLevelEndhostIntfTypeNumRIAFailures OBJECT-TYPE
    SYNTAX      ConfdString
    MAX-ACCESS  read-only
    STATUS      current
    DESCRIPTION "Number of RIR failure responses sent"
    ::= { affirmedServiceconstructInterfaceAaaGroupDiameterStatisticsChassisLevelEndhostIntfTypeEntry 258 }

affirmedServiceconstructInterfaceAaaGroupDiameterStatisticsChassisLevelEndhostIntfTypeNumRIAFailuresUnknownScefRefId OBJECT-TYPE
    SYNTAX      ConfdString
    MAX-ACCESS  read-only
    STATUS      current
    DESCRIPTION "Number of RIR failures due to unknown SCEF Reference Identifier"
    ::= { affirmedServiceconstructInterfaceAaaGroupDiameterStatisticsChassisLevelEndhostIntfTypeEntry 259 }

affirmedServiceconstructInterfaceAaaGroupDiameterStatisticsChassisLevelEndhostIntfTypeNumRIAFailuresUnknownSession OBJECT-TYPE
    SYNTAX      ConfdString
    MAX-ACCESS  read-only
    STATUS      current
    DESCRIPTION "Number of RIR failures due to context not found"
    ::= { affirmedServiceconstructInterfaceAaaGroupDiameterStatisticsChassisLevelEndhostIntfTypeEntry 260 }

affirmedServiceconstructInterfaceAaaGroupDiameterStatisticsChassisLevelEndhostIntfTypeNumRIAFailuresMissingAVP OBJECT-TYPE
    SYNTAX      ConfdString
    MAX-ACCESS  read-only
    STATUS      current
    DESCRIPTION "Number of RIR failures due to missing AVPs"
    ::= { affirmedServiceconstructInterfaceAaaGroupDiameterStatisticsChassisLevelEndhostIntfTypeEntry 261 }

affirmedServiceconstructInterfaceAaaGroupDiameterStatisticsChassisLevelEndhostIntfTypeNumRIAFailuresUnableToDeliver OBJECT-TYPE
    SYNTAX      ConfdString
    MAX-ACCESS  read-only
    STATUS      current
    DESCRIPTION "Number of RIR failures due to Destination Host in RIR not being found"
    ::= { affirmedServiceconstructInterfaceAaaGroupDiameterStatisticsChassisLevelEndhostIntfTypeEntry 262 }

affirmedServiceconstructInterfaceAaaGroupDiameterStatisticsChassisLevelEndhostIntfTypeNumSIRAttempted OBJECT-TYPE
    SYNTAX      ConfdString
    MAX-ACCESS  read-only
    STATUS      current
    DESCRIPTION "Number of SIR attempts made"
    ::= { affirmedServiceconstructInterfaceAaaGroupDiameterStatisticsChassisLevelEndhostIntfTypeEntry 263 }

affirmedServiceconstructInterfaceAaaGroupDiameterStatisticsChassisLevelEndhostIntfTypeNumSIRSuccess OBJECT-TYPE
    SYNTAX      ConfdString
    MAX-ACCESS  read-only
    STATUS      current
    DESCRIPTION "Number of SIR success responses received"
    ::= { affirmedServiceconstructInterfaceAaaGroupDiameterStatisticsChassisLevelEndhostIntfTypeEntry 264 }

affirmedServiceconstructInterfaceAaaGroupDiameterStatisticsChassisLevelEndhostIntfTypeNumSIRFailure OBJECT-TYPE
    SYNTAX      ConfdString
    MAX-ACCESS  read-only
    STATUS      current
    DESCRIPTION "Number of SIR failure responses received"
    ::= { affirmedServiceconstructInterfaceAaaGroupDiameterStatisticsChassisLevelEndhostIntfTypeEntry 265 }

affirmedServiceconstructInterfaceAaaGroupDiameterStatisticsChassisLevelEndhostIntfTypeNumSIRTimeout OBJECT-TYPE
    SYNTAX      ConfdString
    MAX-ACCESS  read-only
    STATUS      current
    DESCRIPTION "Number of SIR attempts timed out"
    ::= { affirmedServiceconstructInterfaceAaaGroupDiameterStatisticsChassisLevelEndhostIntfTypeEntry 266 }

affirmedServiceconstructInterfaceAaaGroupDiameterStatisticsChassisLevelEndhostIntfTypeNumSIRAborted OBJECT-TYPE
    SYNTAX      ConfdString
    MAX-ACCESS  read-only
    STATUS      current
    DESCRIPTION "Number of SIR attempts aborted"
    ::= { affirmedServiceconstructInterfaceAaaGroupDiameterStatisticsChassisLevelEndhostIntfTypeEntry 267 }

affirmedServiceconstructInterfaceAaaGroupDiameterStatisticsChassisLevelEndhostIntfTypeNumSIRcvdFirstAttempt OBJECT-TYPE
    SYNTAX      ConfdString
    MAX-ACCESS  read-only
    STATUS      current
    DESCRIPTION "Number of SIA received to the initial SIR request"
    ::= { affirmedServiceconstructInterfaceAaaGroupDiameterStatisticsChassisLevelEndhostIntfTypeEntry 268 }

affirmedServiceconstructInterfaceAaaGroupDiameterStatisticsChassisLevelEndhostIntfTypeNumSIARcvdReTx OBJECT-TYPE
    SYNTAX      ConfdString
    MAX-ACCESS  read-only
    STATUS      current
    DESCRIPTION "Number of SIA received to the retransmitted SIR request"
    ::= { affirmedServiceconstructInterfaceAaaGroupDiameterStatisticsChassisLevelEndhostIntfTypeEntry 269 }

affirmedServiceconstructInterfaceAaaGroupDiameterStatisticsChassisLevelEndhostIntfTypeNumSIA3xxx OBJECT-TYPE
    SYNTAX      ConfdString
    MAX-ACCESS  read-only
    STATUS      current
    DESCRIPTION "Number of SIA received with 3xxx result code"
    ::= { affirmedServiceconstructInterfaceAaaGroupDiameterStatisticsChassisLevelEndhostIntfTypeEntry 270 }

affirmedServiceconstructInterfaceAaaGroupDiameterStatisticsChassisLevelEndhostIntfTypeNumSIA4xxx OBJECT-TYPE
    SYNTAX      ConfdString
    MAX-ACCESS  read-only
    STATUS      current
    DESCRIPTION "Number of SIA received with 4xxx result code"
    ::= { affirmedServiceconstructInterfaceAaaGroupDiameterStatisticsChassisLevelEndhostIntfTypeEntry 271 }

affirmedServiceconstructInterfaceAaaGroupDiameterStatisticsChassisLevelEndhostIntfTypeNumSIA5xxx OBJECT-TYPE
    SYNTAX      ConfdString
    MAX-ACCESS  read-only
    STATUS      current
    DESCRIPTION "Number of SIA received with 5xxx result code"
    ::= { affirmedServiceconstructInterfaceAaaGroupDiameterStatisticsChassisLevelEndhostIntfTypeEntry 272 }

affirmedServiceconstructInterfaceAaaGroupDiameterStatisticsChassisLevelEndhostIntfTypeNumSIADelayedSuccess OBJECT-TYPE
    SYNTAX      ConfdString
    MAX-ACCESS  read-only
    STATUS      current
    DESCRIPTION "Number of SIA success received after the request had been re-transmitted to another server"
    ::= { affirmedServiceconstructInterfaceAaaGroupDiameterStatisticsChassisLevelEndhostIntfTypeEntry 273 }

affirmedServiceconstructInterfaceAaaGroupDiameterStatisticsChassisLevelEndhostIntfTypeNumSIADelayedFailure OBJECT-TYPE
    SYNTAX      ConfdString
    MAX-ACCESS  read-only
    STATUS      current
    DESCRIPTION "Number of SIA failures received after the request had been re-transmitted to another server"
    ::= { affirmedServiceconstructInterfaceAaaGroupDiameterStatisticsChassisLevelEndhostIntfTypeEntry 274 }

affirmedServiceconstructInterfaceAaaGroupDiameterStatisticsChassisLevelEndhostIntfTypeNumSIADelayed3xxx OBJECT-TYPE
    SYNTAX      ConfdString
    MAX-ACCESS  read-only
    STATUS      current
    DESCRIPTION "Number of SIA received with 3xxx result code after the request had been re-transmitted to another server"
    ::= { affirmedServiceconstructInterfaceAaaGroupDiameterStatisticsChassisLevelEndhostIntfTypeEntry 275 }

affirmedServiceconstructInterfaceAaaGroupDiameterStatisticsChassisLevelEndhostIntfTypeNumSIADroppedNoProc OBJECT-TYPE
    SYNTAX      ConfdString
    MAX-ACCESS  read-only
    STATUS      current
    DESCRIPTION "Number of SIA dropped due to no matching transaction identifier"
    ::= { affirmedServiceconstructInterfaceAaaGroupDiameterStatisticsChassisLevelEndhostIntfTypeEntry 276 }

affirmedServiceconstructInterfaceAaaGroupDiameterStatisticsChassisLevelEndhostIntfTypeNumDTRAttempted OBJECT-TYPE
    SYNTAX      ConfdString
    MAX-ACCESS  read-only
    STATUS      current
    DESCRIPTION "Number of DTR attempts made"
    ::= { affirmedServiceconstructInterfaceAaaGroupDiameterStatisticsChassisLevelEndhostIntfTypeEntry 277 }

affirmedServiceconstructInterfaceAaaGroupDiameterStatisticsChassisLevelEndhostIntfTypeNumDTRSuccess OBJECT-TYPE
    SYNTAX      ConfdString
    MAX-ACCESS  read-only
    STATUS      current
    DESCRIPTION "Number of DTR success responses received"
    ::= { affirmedServiceconstructInterfaceAaaGroupDiameterStatisticsChassisLevelEndhostIntfTypeEntry 278 }

affirmedServiceconstructInterfaceAaaGroupDiameterStatisticsChassisLevelEndhostIntfTypeNumDTRFailure OBJECT-TYPE
    SYNTAX      ConfdString
    MAX-ACCESS  read-only
    STATUS      current
    DESCRIPTION "Number of DTR failure responses received"
    ::= { affirmedServiceconstructInterfaceAaaGroupDiameterStatisticsChassisLevelEndhostIntfTypeEntry 279 }

affirmedServiceconstructInterfaceAaaGroupDiameterStatisticsChassisLevelEndhostIntfTypeNumDTRTimeout OBJECT-TYPE
    SYNTAX      ConfdString
    MAX-ACCESS  read-only
    STATUS      current
    DESCRIPTION "Number of DTR attempts timed out"
    ::= { affirmedServiceconstructInterfaceAaaGroupDiameterStatisticsChassisLevelEndhostIntfTypeEntry 280 }

affirmedServiceconstructInterfaceAaaGroupDiameterStatisticsChassisLevelEndhostIntfTypeNumDTRAborted OBJECT-TYPE
    SYNTAX      ConfdString
    MAX-ACCESS  read-only
    STATUS      current
    DESCRIPTION "Number of DTR attempts aborted"
    ::= { affirmedServiceconstructInterfaceAaaGroupDiameterStatisticsChassisLevelEndhostIntfTypeEntry 281 }

affirmedServiceconstructInterfaceAaaGroupDiameterStatisticsChassisLevelEndhostIntfTypeNumDTRcvdFirstAttempt OBJECT-TYPE
    SYNTAX      ConfdString
    MAX-ACCESS  read-only
    STATUS      current
    DESCRIPTION "Number of DTA received to the initial DTR request"
    ::= { affirmedServiceconstructInterfaceAaaGroupDiameterStatisticsChassisLevelEndhostIntfTypeEntry 282 }

affirmedServiceconstructInterfaceAaaGroupDiameterStatisticsChassisLevelEndhostIntfTypeNumDTARcvdReTx OBJECT-TYPE
    SYNTAX      ConfdString
    MAX-ACCESS  read-only
    STATUS      current
    DESCRIPTION "Number of DTA received to the retransmitted DTR request"
    ::= { affirmedServiceconstructInterfaceAaaGroupDiameterStatisticsChassisLevelEndhostIntfTypeEntry 283 }

affirmedServiceconstructInterfaceAaaGroupDiameterStatisticsChassisLevelEndhostIntfTypeNumDTA3xxx OBJECT-TYPE
    SYNTAX      ConfdString
    MAX-ACCESS  read-only
    STATUS      current
    DESCRIPTION "Number of DTA received with 3xxx result code"
    ::= { affirmedServiceconstructInterfaceAaaGroupDiameterStatisticsChassisLevelEndhostIntfTypeEntry 284 }

affirmedServiceconstructInterfaceAaaGroupDiameterStatisticsChassisLevelEndhostIntfTypeNumDTA4xxx OBJECT-TYPE
    SYNTAX      ConfdString
    MAX-ACCESS  read-only
    STATUS      current
    DESCRIPTION "Number of DTA received with 4xxx result code"
    ::= { affirmedServiceconstructInterfaceAaaGroupDiameterStatisticsChassisLevelEndhostIntfTypeEntry 285 }

affirmedServiceconstructInterfaceAaaGroupDiameterStatisticsChassisLevelEndhostIntfTypeNumDTA5xxx OBJECT-TYPE
    SYNTAX      ConfdString
    MAX-ACCESS  read-only
    STATUS      current
    DESCRIPTION "Number of DTA received with 5xxx result code"
    ::= { affirmedServiceconstructInterfaceAaaGroupDiameterStatisticsChassisLevelEndhostIntfTypeEntry 286 }

affirmedServiceconstructInterfaceAaaGroupDiameterStatisticsChassisLevelEndhostIntfTypeNumDTADelayedSuccess OBJECT-TYPE
    SYNTAX      ConfdString
    MAX-ACCESS  read-only
    STATUS      current
    DESCRIPTION "Number of DTA success received after the request had been re-transmitted to another server"
    ::= { affirmedServiceconstructInterfaceAaaGroupDiameterStatisticsChassisLevelEndhostIntfTypeEntry 287 }

affirmedServiceconstructInterfaceAaaGroupDiameterStatisticsChassisLevelEndhostIntfTypeNumDTADelayedFailure OBJECT-TYPE
    SYNTAX      ConfdString
    MAX-ACCESS  read-only
    STATUS      current
    DESCRIPTION "Number of DTA failures received after the request had been re-transmitted to another server"
    ::= { affirmedServiceconstructInterfaceAaaGroupDiameterStatisticsChassisLevelEndhostIntfTypeEntry 288 }

affirmedServiceconstructInterfaceAaaGroupDiameterStatisticsChassisLevelEndhostIntfTypeNumDTADelayed3xxx OBJECT-TYPE
    SYNTAX      ConfdString
    MAX-ACCESS  read-only
    STATUS      current
    DESCRIPTION "Number of DTA received with 3xxx result code after the request had been re-transmitted to another server"
    ::= { affirmedServiceconstructInterfaceAaaGroupDiameterStatisticsChassisLevelEndhostIntfTypeEntry 289 }

affirmedServiceconstructInterfaceAaaGroupDiameterStatisticsChassisLevelEndhostIntfTypeNumDTADroppedNoProc OBJECT-TYPE
    SYNTAX      ConfdString
    MAX-ACCESS  read-only
    STATUS      current
    DESCRIPTION "Number of DTA dropped due to no matching transaction identifier"
    ::= { affirmedServiceconstructInterfaceAaaGroupDiameterStatisticsChassisLevelEndhostIntfTypeEntry 290 }

affirmedServiceconstructInterfaceAaaGroupDiameterStatisticsChassisLevelEndhostIntfTypeNumDTRTriggerAttempted OBJECT-TYPE
    SYNTAX      ConfdString
    MAX-ACCESS  read-only
    STATUS      current
    DESCRIPTION "Number of DTR trigger attempts made"
    ::= { affirmedServiceconstructInterfaceAaaGroupDiameterStatisticsChassisLevelEndhostIntfTypeEntry 291 }

affirmedServiceconstructInterfaceAaaGroupDiameterStatisticsChassisLevelEndhostIntfTypeNumDTRTriggerSuccess OBJECT-TYPE
    SYNTAX      ConfdString
    MAX-ACCESS  read-only
    STATUS      current
    DESCRIPTION "Number of DTR trigger success responses received"
    ::= { affirmedServiceconstructInterfaceAaaGroupDiameterStatisticsChassisLevelEndhostIntfTypeEntry 292 }

affirmedServiceconstructInterfaceAaaGroupDiameterStatisticsChassisLevelEndhostIntfTypeNumDTRTriggerFailure OBJECT-TYPE
    SYNTAX      ConfdString
    MAX-ACCESS  read-only
    STATUS      current
    DESCRIPTION "Number of DTR trigger failure responses received"
    ::= { affirmedServiceconstructInterfaceAaaGroupDiameterStatisticsChassisLevelEndhostIntfTypeEntry 293 }

affirmedServiceconstructInterfaceAaaGroupDiameterStatisticsChassisLevelEndhostIntfTypeNumDTRTriggerTimeout OBJECT-TYPE
    SYNTAX      ConfdString
    MAX-ACCESS  read-only
    STATUS      current
    DESCRIPTION "Number of DTR trigger attempts timed out"
    ::= { affirmedServiceconstructInterfaceAaaGroupDiameterStatisticsChassisLevelEndhostIntfTypeEntry 294 }

affirmedServiceconstructInterfaceAaaGroupDiameterStatisticsChassisLevelEndhostIntfTypeNumDTRTriggerAborted OBJECT-TYPE
    SYNTAX      ConfdString
    MAX-ACCESS  read-only
    STATUS      current
    DESCRIPTION "Number of DTR trigger attempts aborted"
    ::= { affirmedServiceconstructInterfaceAaaGroupDiameterStatisticsChassisLevelEndhostIntfTypeEntry 295 }

affirmedServiceconstructInterfaceAaaGroupDiameterStatisticsChassisLevelEndhostIntfTypeNumDTRTriggercvdFirstAttempt OBJECT-TYPE
    SYNTAX      ConfdString
    MAX-ACCESS  read-only
    STATUS      current
    DESCRIPTION "Number of DTA received to the initial DTR trigger request"
    ::= { affirmedServiceconstructInterfaceAaaGroupDiameterStatisticsChassisLevelEndhostIntfTypeEntry 296 }

affirmedServiceconstructInterfaceAaaGroupDiameterStatisticsChassisLevelEndhostIntfTypeNumDTATriggerRcvdReTx OBJECT-TYPE
    SYNTAX      ConfdString
    MAX-ACCESS  read-only
    STATUS      current
    DESCRIPTION "Number of DTA received to the retransmitted DTR trigger request"
    ::= { affirmedServiceconstructInterfaceAaaGroupDiameterStatisticsChassisLevelEndhostIntfTypeEntry 297 }

affirmedServiceconstructInterfaceAaaGroupDiameterStatisticsChassisLevelEndhostIntfTypeNumDTATrigger3xxx OBJECT-TYPE
    SYNTAX      ConfdString
    MAX-ACCESS  read-only
    STATUS      current
    DESCRIPTION "Number of DTA received for the trigger action with 3xxx result code"
    ::= { affirmedServiceconstructInterfaceAaaGroupDiameterStatisticsChassisLevelEndhostIntfTypeEntry 298 }

affirmedServiceconstructInterfaceAaaGroupDiameterStatisticsChassisLevelEndhostIntfTypeNumDTATrigger4xxx OBJECT-TYPE
    SYNTAX      ConfdString
    MAX-ACCESS  read-only
    STATUS      current
    DESCRIPTION "Number of DTA received for the trigger action with 4xxx result code"
    ::= { affirmedServiceconstructInterfaceAaaGroupDiameterStatisticsChassisLevelEndhostIntfTypeEntry 299 }

affirmedServiceconstructInterfaceAaaGroupDiameterStatisticsChassisLevelEndhostIntfTypeNumDTATrigger5xxx OBJECT-TYPE
    SYNTAX      ConfdString
    MAX-ACCESS  read-only
    STATUS      current
    DESCRIPTION "Number of DTA received for the trigger action with 5xxx result code"
    ::= { affirmedServiceconstructInterfaceAaaGroupDiameterStatisticsChassisLevelEndhostIntfTypeEntry 300 }

affirmedServiceconstructInterfaceAaaGroupDiameterStatisticsChassisLevelEndhostIntfTypeNumDTATriggerDelayedSuccess OBJECT-TYPE
    SYNTAX      ConfdString
    MAX-ACCESS  read-only
    STATUS      current
    DESCRIPTION "Number of DTA success received for the trigger action after the request had been re-transmitted to another server"
    ::= { affirmedServiceconstructInterfaceAaaGroupDiameterStatisticsChassisLevelEndhostIntfTypeEntry 301 }

affirmedServiceconstructInterfaceAaaGroupDiameterStatisticsChassisLevelEndhostIntfTypeNumDTATriggerDelayedFailure OBJECT-TYPE
    SYNTAX      ConfdString
    MAX-ACCESS  read-only
    STATUS      current
    DESCRIPTION "Number of DTA failures received for the trigger action after the request had been re-transmitted to another server"
    ::= { affirmedServiceconstructInterfaceAaaGroupDiameterStatisticsChassisLevelEndhostIntfTypeEntry 302 }

affirmedServiceconstructInterfaceAaaGroupDiameterStatisticsChassisLevelEndhostIntfTypeNumDTATriggerDelayed3xxx OBJECT-TYPE
    SYNTAX      ConfdString
    MAX-ACCESS  read-only
    STATUS      current
    DESCRIPTION "Number of DTA received with 3xxx result code for the trigger action after the request had been re-transmitted to another server"
    ::= { affirmedServiceconstructInterfaceAaaGroupDiameterStatisticsChassisLevelEndhostIntfTypeEntry 303 }

affirmedServiceconstructInterfaceAaaGroupDiameterStatisticsChassisLevelEndhostIntfTypeNumDTATriggerDroppedNoProc OBJECT-TYPE
    SYNTAX      ConfdString
    MAX-ACCESS  read-only
    STATUS      current
    DESCRIPTION "Number of DTA for the trigger action dropped due to no matching transaction identifier"
    ::= { affirmedServiceconstructInterfaceAaaGroupDiameterStatisticsChassisLevelEndhostIntfTypeEntry 304 }

affirmedServiceconstructInterfaceAaaGroupDiameterStatisticsChassisLevelEndhostIntfTypeNumDTRRecallAttempted OBJECT-TYPE
    SYNTAX      ConfdString
    MAX-ACCESS  read-only
    STATUS      current
    DESCRIPTION "Number of DTR recall attempts made"
    ::= { affirmedServiceconstructInterfaceAaaGroupDiameterStatisticsChassisLevelEndhostIntfTypeEntry 305 }

affirmedServiceconstructInterfaceAaaGroupDiameterStatisticsChassisLevelEndhostIntfTypeNumDTRRecallSuccess OBJECT-TYPE
    SYNTAX      ConfdString
    MAX-ACCESS  read-only
    STATUS      current
    DESCRIPTION "Number of DTR recall success responses received"
    ::= { affirmedServiceconstructInterfaceAaaGroupDiameterStatisticsChassisLevelEndhostIntfTypeEntry 306 }

affirmedServiceconstructInterfaceAaaGroupDiameterStatisticsChassisLevelEndhostIntfTypeNumDTRRecallFailure OBJECT-TYPE
    SYNTAX      ConfdString
    MAX-ACCESS  read-only
    STATUS      current
    DESCRIPTION "Number of DTR recall failure responses received"
    ::= { affirmedServiceconstructInterfaceAaaGroupDiameterStatisticsChassisLevelEndhostIntfTypeEntry 307 }

affirmedServiceconstructInterfaceAaaGroupDiameterStatisticsChassisLevelEndhostIntfTypeNumDTRRecallTimeout OBJECT-TYPE
    SYNTAX      ConfdString
    MAX-ACCESS  read-only
    STATUS      current
    DESCRIPTION "Number of DTR recall attempts timed out"
    ::= { affirmedServiceconstructInterfaceAaaGroupDiameterStatisticsChassisLevelEndhostIntfTypeEntry 308 }

affirmedServiceconstructInterfaceAaaGroupDiameterStatisticsChassisLevelEndhostIntfTypeNumDTRRecallAborted OBJECT-TYPE
    SYNTAX      ConfdString
    MAX-ACCESS  read-only
    STATUS      current
    DESCRIPTION "Number of DTR recall attempts aborted"
    ::= { affirmedServiceconstructInterfaceAaaGroupDiameterStatisticsChassisLevelEndhostIntfTypeEntry 309 }

affirmedServiceconstructInterfaceAaaGroupDiameterStatisticsChassisLevelEndhostIntfTypeNumDTRRecallcvdFirstAttempt OBJECT-TYPE
    SYNTAX      ConfdString
    MAX-ACCESS  read-only
    STATUS      current
    DESCRIPTION "Number of DTA received to the initial DTR recall request"
    ::= { affirmedServiceconstructInterfaceAaaGroupDiameterStatisticsChassisLevelEndhostIntfTypeEntry 310 }

affirmedServiceconstructInterfaceAaaGroupDiameterStatisticsChassisLevelEndhostIntfTypeNumDTARecallRcvdReTx OBJECT-TYPE
    SYNTAX      ConfdString
    MAX-ACCESS  read-only
    STATUS      current
    DESCRIPTION "Number of DTA received to the retransmitted DTR recall request"
    ::= { affirmedServiceconstructInterfaceAaaGroupDiameterStatisticsChassisLevelEndhostIntfTypeEntry 311 }

affirmedServiceconstructInterfaceAaaGroupDiameterStatisticsChassisLevelEndhostIntfTypeNumDTARecall3xxx OBJECT-TYPE
    SYNTAX      ConfdString
    MAX-ACCESS  read-only
    STATUS      current
    DESCRIPTION "Number of DTA received for the recall action with 3xxx result code"
    ::= { affirmedServiceconstructInterfaceAaaGroupDiameterStatisticsChassisLevelEndhostIntfTypeEntry 312 }

affirmedServiceconstructInterfaceAaaGroupDiameterStatisticsChassisLevelEndhostIntfTypeNumDTARecall4xxx OBJECT-TYPE
    SYNTAX      ConfdString
    MAX-ACCESS  read-only
    STATUS      current
    DESCRIPTION "Number of DTA received for the recall action with 4xxx result code"
    ::= { affirmedServiceconstructInterfaceAaaGroupDiameterStatisticsChassisLevelEndhostIntfTypeEntry 313 }

affirmedServiceconstructInterfaceAaaGroupDiameterStatisticsChassisLevelEndhostIntfTypeNumDTARecall5xxx OBJECT-TYPE
    SYNTAX      ConfdString
    MAX-ACCESS  read-only
    STATUS      current
    DESCRIPTION "Number of DTA received for the recall action with 5xxx result code"
    ::= { affirmedServiceconstructInterfaceAaaGroupDiameterStatisticsChassisLevelEndhostIntfTypeEntry 314 }

affirmedServiceconstructInterfaceAaaGroupDiameterStatisticsChassisLevelEndhostIntfTypeNumDTARecallDelayedSuccess OBJECT-TYPE
    SYNTAX      ConfdString
    MAX-ACCESS  read-only
    STATUS      current
    DESCRIPTION "Number of DTA success received for the recall action after the request had been re-transmitted to another server"
    ::= { affirmedServiceconstructInterfaceAaaGroupDiameterStatisticsChassisLevelEndhostIntfTypeEntry 315 }

affirmedServiceconstructInterfaceAaaGroupDiameterStatisticsChassisLevelEndhostIntfTypeNumDTARecallDelayedFailure OBJECT-TYPE
    SYNTAX      ConfdString
    MAX-ACCESS  read-only
    STATUS      current
    DESCRIPTION "Number of DTA failures received for the recall action after the request had been re-transmitted to another server"
    ::= { affirmedServiceconstructInterfaceAaaGroupDiameterStatisticsChassisLevelEndhostIntfTypeEntry 316 }

affirmedServiceconstructInterfaceAaaGroupDiameterStatisticsChassisLevelEndhostIntfTypeNumDTARecallDelayed3xxx OBJECT-TYPE
    SYNTAX      ConfdString
    MAX-ACCESS  read-only
    STATUS      current
    DESCRIPTION "Number of DTA received with 3xxx result code for the recall action after the request had been re-transmitted to another server"
    ::= { affirmedServiceconstructInterfaceAaaGroupDiameterStatisticsChassisLevelEndhostIntfTypeEntry 317 }

affirmedServiceconstructInterfaceAaaGroupDiameterStatisticsChassisLevelEndhostIntfTypeNumDTARecallDroppedNoProc OBJECT-TYPE
    SYNTAX      ConfdString
    MAX-ACCESS  read-only
    STATUS      current
    DESCRIPTION "Number of DTA for the recall action dropped due to no matching transaction identifier"
    ::= { affirmedServiceconstructInterfaceAaaGroupDiameterStatisticsChassisLevelEndhostIntfTypeEntry 318 }

affirmedServiceconstructInterfaceAaaGroupDiameterStatisticsChassisLevelEndhostIntfTypeNumDTRReplaceAttempted OBJECT-TYPE
    SYNTAX      ConfdString
    MAX-ACCESS  read-only
    STATUS      current
    DESCRIPTION "Number of DTR replace attempts made"
    ::= { affirmedServiceconstructInterfaceAaaGroupDiameterStatisticsChassisLevelEndhostIntfTypeEntry 319 }

affirmedServiceconstructInterfaceAaaGroupDiameterStatisticsChassisLevelEndhostIntfTypeNumDTRReplaceSuccess OBJECT-TYPE
    SYNTAX      ConfdString
    MAX-ACCESS  read-only
    STATUS      current
    DESCRIPTION "Number of DTR replace success responses received"
    ::= { affirmedServiceconstructInterfaceAaaGroupDiameterStatisticsChassisLevelEndhostIntfTypeEntry 320 }

affirmedServiceconstructInterfaceAaaGroupDiameterStatisticsChassisLevelEndhostIntfTypeNumDTRReplaceFailure OBJECT-TYPE
    SYNTAX      ConfdString
    MAX-ACCESS  read-only
    STATUS      current
    DESCRIPTION "Number of DTR replace failure responses received"
    ::= { affirmedServiceconstructInterfaceAaaGroupDiameterStatisticsChassisLevelEndhostIntfTypeEntry 321 }

affirmedServiceconstructInterfaceAaaGroupDiameterStatisticsChassisLevelEndhostIntfTypeNumDTRReplaceTimeout OBJECT-TYPE
    SYNTAX      ConfdString
    MAX-ACCESS  read-only
    STATUS      current
    DESCRIPTION "Number of DTR replace attempts timed out"
    ::= { affirmedServiceconstructInterfaceAaaGroupDiameterStatisticsChassisLevelEndhostIntfTypeEntry 322 }

affirmedServiceconstructInterfaceAaaGroupDiameterStatisticsChassisLevelEndhostIntfTypeNumDTRReplaceAborted OBJECT-TYPE
    SYNTAX      ConfdString
    MAX-ACCESS  read-only
    STATUS      current
    DESCRIPTION "Number of DTR replace attempts aborted"
    ::= { affirmedServiceconstructInterfaceAaaGroupDiameterStatisticsChassisLevelEndhostIntfTypeEntry 323 }

affirmedServiceconstructInterfaceAaaGroupDiameterStatisticsChassisLevelEndhostIntfTypeNumDTRReplacecvdFirstAttempt OBJECT-TYPE
    SYNTAX      ConfdString
    MAX-ACCESS  read-only
    STATUS      current
    DESCRIPTION "Number of DTA received to the initial DTR replace request"
    ::= { affirmedServiceconstructInterfaceAaaGroupDiameterStatisticsChassisLevelEndhostIntfTypeEntry 324 }

affirmedServiceconstructInterfaceAaaGroupDiameterStatisticsChassisLevelEndhostIntfTypeNumDTAReplaceRcvdReTx OBJECT-TYPE
    SYNTAX      ConfdString
    MAX-ACCESS  read-only
    STATUS      current
    DESCRIPTION "Number of DTA received to the retransmitted DTR replace request"
    ::= { affirmedServiceconstructInterfaceAaaGroupDiameterStatisticsChassisLevelEndhostIntfTypeEntry 325 }

affirmedServiceconstructInterfaceAaaGroupDiameterStatisticsChassisLevelEndhostIntfTypeNumDTAReplace3xxx OBJECT-TYPE
    SYNTAX      ConfdString
    MAX-ACCESS  read-only
    STATUS      current
    DESCRIPTION "Number of DTA received for the replace action with 3xxx result code"
    ::= { affirmedServiceconstructInterfaceAaaGroupDiameterStatisticsChassisLevelEndhostIntfTypeEntry 326 }

affirmedServiceconstructInterfaceAaaGroupDiameterStatisticsChassisLevelEndhostIntfTypeNumDTAReplace4xxx OBJECT-TYPE
    SYNTAX      ConfdString
    MAX-ACCESS  read-only
    STATUS      current
    DESCRIPTION "Number of DTA received for the replace action with 4xxx result code"
    ::= { affirmedServiceconstructInterfaceAaaGroupDiameterStatisticsChassisLevelEndhostIntfTypeEntry 327 }

affirmedServiceconstructInterfaceAaaGroupDiameterStatisticsChassisLevelEndhostIntfTypeNumDTAReplace5xxx OBJECT-TYPE
    SYNTAX      ConfdString
    MAX-ACCESS  read-only
    STATUS      current
    DESCRIPTION "Number of DTA received for the replace action with 5xxx result code"
    ::= { affirmedServiceconstructInterfaceAaaGroupDiameterStatisticsChassisLevelEndhostIntfTypeEntry 328 }

affirmedServiceconstructInterfaceAaaGroupDiameterStatisticsChassisLevelEndhostIntfTypeNumDTAReplaceDelayedSuccess OBJECT-TYPE
    SYNTAX      ConfdString
    MAX-ACCESS  read-only
    STATUS      current
    DESCRIPTION "Number of DTA success received for the replace action after the request had been re-transmitted to another server"
    ::= { affirmedServiceconstructInterfaceAaaGroupDiameterStatisticsChassisLevelEndhostIntfTypeEntry 329 }

affirmedServiceconstructInterfaceAaaGroupDiameterStatisticsChassisLevelEndhostIntfTypeNumDTAReplaceDelayedFailure OBJECT-TYPE
    SYNTAX      ConfdString
    MAX-ACCESS  read-only
    STATUS      current
    DESCRIPTION "Number of DTA failures received for the replace action after the request had been re-transmitted to another server"
    ::= { affirmedServiceconstructInterfaceAaaGroupDiameterStatisticsChassisLevelEndhostIntfTypeEntry 330 }

affirmedServiceconstructInterfaceAaaGroupDiameterStatisticsChassisLevelEndhostIntfTypeNumDTAReplaceDelayed3xxx OBJECT-TYPE
    SYNTAX      ConfdString
    MAX-ACCESS  read-only
    STATUS      current
    DESCRIPTION "Number of DTA received with 3xxx result code for the replace action after the request had been re-transmitted to another server"
    ::= { affirmedServiceconstructInterfaceAaaGroupDiameterStatisticsChassisLevelEndhostIntfTypeEntry 331 }

affirmedServiceconstructInterfaceAaaGroupDiameterStatisticsChassisLevelEndhostIntfTypeNumDTAReplaceDroppedNoProc OBJECT-TYPE
    SYNTAX      ConfdString
    MAX-ACCESS  read-only
    STATUS      current
    DESCRIPTION "Number of DTA for the replace action dropped due to no matching transaction identifier"
    ::= { affirmedServiceconstructInterfaceAaaGroupDiameterStatisticsChassisLevelEndhostIntfTypeEntry 332 }

affirmedServiceconstructInterfaceAaaGroupDiameterStatisticsChassisLevelEndhostIntfTypeNumDRRReceived OBJECT-TYPE
    SYNTAX      ConfdString
    MAX-ACCESS  read-only
    STATUS      current
    DESCRIPTION "Number of DRR messages received"
    ::= { affirmedServiceconstructInterfaceAaaGroupDiameterStatisticsChassisLevelEndhostIntfTypeEntry 333 }

affirmedServiceconstructInterfaceAaaGroupDiameterStatisticsChassisLevelEndhostIntfTypeNumDRASuccess OBJECT-TYPE
    SYNTAX      ConfdString
    MAX-ACCESS  read-only
    STATUS      current
    DESCRIPTION "Number of DRR success responses sent"
    ::= { affirmedServiceconstructInterfaceAaaGroupDiameterStatisticsChassisLevelEndhostIntfTypeEntry 334 }

affirmedServiceconstructInterfaceAaaGroupDiameterStatisticsChassisLevelEndhostIntfTypeNumDRAFailures OBJECT-TYPE
    SYNTAX      ConfdString
    MAX-ACCESS  read-only
    STATUS      current
    DESCRIPTION "Number of DRR failure responses sent"
    ::= { affirmedServiceconstructInterfaceAaaGroupDiameterStatisticsChassisLevelEndhostIntfTypeEntry 335 }

affirmedServiceconstructInterfaceAaaGroupDiameterStatisticsChassisLevelEndhostIntfTypeNumDRAFailuresUnknownRefId OBJECT-TYPE
    SYNTAX      ConfdString
    MAX-ACCESS  read-only
    STATUS      current
    DESCRIPTION "Number of DRR failures due to unknown Reference Identifier"
    ::= { affirmedServiceconstructInterfaceAaaGroupDiameterStatisticsChassisLevelEndhostIntfTypeEntry 336 }

affirmedServiceconstructInterfaceAaaGroupDiameterStatisticsChassisLevelEndhostIntfTypeNumDRAFailuresUnknownSession OBJECT-TYPE
    SYNTAX      ConfdString
    MAX-ACCESS  read-only
    STATUS      current
    DESCRIPTION "Number of DRR failures due to context not found"
    ::= { affirmedServiceconstructInterfaceAaaGroupDiameterStatisticsChassisLevelEndhostIntfTypeEntry 337 }

affirmedServiceconstructInterfaceAaaGroupDiameterStatisticsChassisLevelEndhostIntfTypeNumDRAFailuresMissingAVP OBJECT-TYPE
    SYNTAX      ConfdString
    MAX-ACCESS  read-only
    STATUS      current
    DESCRIPTION "Number of DRR failures due to missing AVPs"
    ::= { affirmedServiceconstructInterfaceAaaGroupDiameterStatisticsChassisLevelEndhostIntfTypeEntry 338 }

affirmedServiceconstructInterfaceAaaGroupDiameterStatisticsChassisLevelEndhostIntfTypeNumDRAFailuresUnableToDeliver OBJECT-TYPE
    SYNTAX      ConfdString
    MAX-ACCESS  read-only
    STATUS      current
    DESCRIPTION "Number of DRR failures due to Destination Host in DRR not being found"
    ::= { affirmedServiceconstructInterfaceAaaGroupDiameterStatisticsChassisLevelEndhostIntfTypeEntry 339 }

affirmedServiceconstructInterfaceAaaGroupDiameterStatisticsChassisLevelEndhostIntfTypeNumTsrReceived OBJECT-TYPE
    SYNTAX      Unsigned32
    MAX-ACCESS  read-only
    STATUS      current
    DESCRIPTION "Number of TSR messages received from peer"
    ::= { affirmedServiceconstructInterfaceAaaGroupDiameterStatisticsChassisLevelEndhostIntfTypeEntry 340 }

affirmedServiceconstructInterfaceAaaGroupDiameterStatisticsChassisLevelEndhostIntfTypeNumTsaSuccess OBJECT-TYPE
    SYNTAX      Unsigned32
    MAX-ACCESS  read-only
    STATUS      current
    DESCRIPTION "Number of TSA success messages sent to peer"
    ::= { affirmedServiceconstructInterfaceAaaGroupDiameterStatisticsChassisLevelEndhostIntfTypeEntry 341 }

affirmedServiceconstructInterfaceAaaGroupDiameterStatisticsChassisLevelEndhostIntfTypeNumTsaFailures OBJECT-TYPE
    SYNTAX      Unsigned32
    MAX-ACCESS  read-only
    STATUS      current
    DESCRIPTION "Number of TSA failures"
    ::= { affirmedServiceconstructInterfaceAaaGroupDiameterStatisticsChassisLevelEndhostIntfTypeEntry 342 }

affirmedServiceconstructInterfaceAaaGroupDiameterStatisticsChassisLevelEndhostIntfTypeNumAAAInitialDelayedSuccess OBJECT-TYPE
    SYNTAX      ConfdString
    MAX-ACCESS  read-only
    STATUS      current
    DESCRIPTION "Number of AAA Initial success which were received after the request had been re-transmitted to another server"
    ::= { affirmedServiceconstructInterfaceAaaGroupDiameterStatisticsChassisLevelEndhostIntfTypeEntry 343 }

affirmedServiceconstructInterfaceAaaGroupDiameterStatisticsChassisLevelEndhostIntfTypeNumAAAInitialDelayedFailure OBJECT-TYPE
    SYNTAX      ConfdString
    MAX-ACCESS  read-only
    STATUS      current
    DESCRIPTION "Number of AAA Initial failures which were received after the request had been re-transmitted to another server"
    ::= { affirmedServiceconstructInterfaceAaaGroupDiameterStatisticsChassisLevelEndhostIntfTypeEntry 344 }

affirmedServiceconstructInterfaceAaaGroupDiameterStatisticsChassisLevelEndhostIntfTypeNumAAAInitialDelayed3xxx OBJECT-TYPE
    SYNTAX      ConfdString
    MAX-ACCESS  read-only
    STATUS      current
    DESCRIPTION "Number of delayed AAA Initial 3xxx error which were received after the request had been re-transmitted to another server"
    ::= { affirmedServiceconstructInterfaceAaaGroupDiameterStatisticsChassisLevelEndhostIntfTypeEntry 345 }

affirmedServiceconstructInterfaceAaaGroupDiameterStatisticsChassisLevelEndhostIntfTypeNumCommandUnsupported OBJECT-TYPE
    SYNTAX      ConfdString
    MAX-ACCESS  read-only
    STATUS      current
    DESCRIPTION "Number of received response with result code 3001"
    ::= { affirmedServiceconstructInterfaceAaaGroupDiameterStatisticsChassisLevelEndhostIntfTypeEntry 346 }

affirmedServiceconstructInterfaceAaaGroupDiameterStatisticsChassisLevelEndhostIntfTypeNumUnableToDeliver OBJECT-TYPE
    SYNTAX      ConfdString
    MAX-ACCESS  read-only
    STATUS      current
    DESCRIPTION "Number of received response with result code 3002"
    ::= { affirmedServiceconstructInterfaceAaaGroupDiameterStatisticsChassisLevelEndhostIntfTypeEntry 347 }

affirmedServiceconstructInterfaceAaaGroupDiameterStatisticsChassisLevelEndhostIntfTypeNumRealmNotServed OBJECT-TYPE
    SYNTAX      ConfdString
    MAX-ACCESS  read-only
    STATUS      current
    DESCRIPTION "Number of received response with result code 3003"
    ::= { affirmedServiceconstructInterfaceAaaGroupDiameterStatisticsChassisLevelEndhostIntfTypeEntry 348 }

affirmedServiceconstructInterfaceAaaGroupDiameterStatisticsChassisLevelEndhostIntfTypeNumTooBusy OBJECT-TYPE
    SYNTAX      ConfdString
    MAX-ACCESS  read-only
    STATUS      current
    DESCRIPTION "Number of received response with result code 3004"
    ::= { affirmedServiceconstructInterfaceAaaGroupDiameterStatisticsChassisLevelEndhostIntfTypeEntry 349 }

affirmedServiceconstructInterfaceAaaGroupDiameterStatisticsChassisLevelEndhostIntfTypeNumLoopDetected OBJECT-TYPE
    SYNTAX      ConfdString
    MAX-ACCESS  read-only
    STATUS      current
    DESCRIPTION "Number of received response with result code 3005"
    ::= { affirmedServiceconstructInterfaceAaaGroupDiameterStatisticsChassisLevelEndhostIntfTypeEntry 350 }

affirmedServiceconstructInterfaceAaaGroupDiameterStatisticsChassisLevelEndhostIntfTypeNumRedirectIndication OBJECT-TYPE
    SYNTAX      ConfdString
    MAX-ACCESS  read-only
    STATUS      current
    DESCRIPTION "Number of received response with result code 3006"
    ::= { affirmedServiceconstructInterfaceAaaGroupDiameterStatisticsChassisLevelEndhostIntfTypeEntry 351 }

affirmedServiceconstructInterfaceAaaGroupDiameterStatisticsChassisLevelEndhostIntfTypeNumApplicationUnsupported OBJECT-TYPE
    SYNTAX      ConfdString
    MAX-ACCESS  read-only
    STATUS      current
    DESCRIPTION "Number of received response with result code 3007"
    ::= { affirmedServiceconstructInterfaceAaaGroupDiameterStatisticsChassisLevelEndhostIntfTypeEntry 352 }

affirmedServiceconstructInterfaceAaaGroupDiameterStatisticsChassisLevelEndhostIntfTypeNumInvalidHdrBits OBJECT-TYPE
    SYNTAX      ConfdString
    MAX-ACCESS  read-only
    STATUS      current
    DESCRIPTION "Number of received response with result code 3008"
    ::= { affirmedServiceconstructInterfaceAaaGroupDiameterStatisticsChassisLevelEndhostIntfTypeEntry 353 }

affirmedServiceconstructInterfaceAaaGroupDiameterStatisticsChassisLevelEndhostIntfTypeNumInvalidAvpBits OBJECT-TYPE
    SYNTAX      ConfdString
    MAX-ACCESS  read-only
    STATUS      current
    DESCRIPTION "Number of received response with result code 3009"
    ::= { affirmedServiceconstructInterfaceAaaGroupDiameterStatisticsChassisLevelEndhostIntfTypeEntry 354 }

affirmedServiceconstructInterfaceAaaGroupDiameterStatisticsChassisLevelEndhostIntfTypeNumUnknownPeer OBJECT-TYPE
    SYNTAX      ConfdString
    MAX-ACCESS  read-only
    STATUS      current
    DESCRIPTION "Number of received response with result code 3010"
    ::= { affirmedServiceconstructInterfaceAaaGroupDiameterStatisticsChassisLevelEndhostIntfTypeEntry 355 }

affirmedServiceconstructInterfaceAaaGroupDiameterStatisticsChassisLevelEndhostIntfTypeNumAuthenticationRejected OBJECT-TYPE
    SYNTAX      ConfdString
    MAX-ACCESS  read-only
    STATUS      current
    DESCRIPTION "Number of received response with result code 4001"
    ::= { affirmedServiceconstructInterfaceAaaGroupDiameterStatisticsChassisLevelEndhostIntfTypeEntry 356 }

affirmedServiceconstructInterfaceAaaGroupDiameterStatisticsChassisLevelEndhostIntfTypeNumOutOfSpace OBJECT-TYPE
    SYNTAX      ConfdString
    MAX-ACCESS  read-only
    STATUS      current
    DESCRIPTION "Number of received response with result code 4002"
    ::= { affirmedServiceconstructInterfaceAaaGroupDiameterStatisticsChassisLevelEndhostIntfTypeEntry 357 }

affirmedServiceconstructInterfaceAaaGroupDiameterStatisticsChassisLevelEndhostIntfTypeNumElectionLost OBJECT-TYPE
    SYNTAX      ConfdString
    MAX-ACCESS  read-only
    STATUS      current
    DESCRIPTION "Number of received response with result code 4003"
    ::= { affirmedServiceconstructInterfaceAaaGroupDiameterStatisticsChassisLevelEndhostIntfTypeEntry 358 }

affirmedServiceconstructInterfaceAaaGroupDiameterStatisticsChassisLevelEndhostIntfTypeNumAvpUnsupported OBJECT-TYPE
    SYNTAX      ConfdString
    MAX-ACCESS  read-only
    STATUS      current
    DESCRIPTION "Total number of received replies with result code 5001"
    ::= { affirmedServiceconstructInterfaceAaaGroupDiameterStatisticsChassisLevelEndhostIntfTypeEntry 359 }

affirmedServiceconstructInterfaceAaaGroupDiameterStatisticsChassisLevelEndhostIntfTypeNumUnknownSessionId OBJECT-TYPE
    SYNTAX      ConfdString
    MAX-ACCESS  read-only
    STATUS      current
    DESCRIPTION "Total number of received replies with result code 5002"
    ::= { affirmedServiceconstructInterfaceAaaGroupDiameterStatisticsChassisLevelEndhostIntfTypeEntry 360 }

affirmedServiceconstructInterfaceAaaGroupDiameterStatisticsChassisLevelEndhostIntfTypeNumAuthorizationRejected OBJECT-TYPE
    SYNTAX      ConfdString
    MAX-ACCESS  read-only
    STATUS      current
    DESCRIPTION "Number of received response with result code 5003"
    ::= { affirmedServiceconstructInterfaceAaaGroupDiameterStatisticsChassisLevelEndhostIntfTypeEntry 361 }

affirmedServiceconstructInterfaceAaaGroupDiameterStatisticsChassisLevelEndhostIntfTypeNumInvalidAvpValue OBJECT-TYPE
    SYNTAX      ConfdString
    MAX-ACCESS  read-only
    STATUS      current
    DESCRIPTION "Number of received response with result code 5004"
    ::= { affirmedServiceconstructInterfaceAaaGroupDiameterStatisticsChassisLevelEndhostIntfTypeEntry 362 }

affirmedServiceconstructInterfaceAaaGroupDiameterStatisticsChassisLevelEndhostIntfTypeNumMissingAvp OBJECT-TYPE
    SYNTAX      ConfdString
    MAX-ACCESS  read-only
    STATUS      current
    DESCRIPTION "Number of received response with result code 5005"
    ::= { affirmedServiceconstructInterfaceAaaGroupDiameterStatisticsChassisLevelEndhostIntfTypeEntry 363 }

affirmedServiceconstructInterfaceAaaGroupDiameterStatisticsChassisLevelEndhostIntfTypeNumResourcesExceeded OBJECT-TYPE
    SYNTAX      ConfdString
    MAX-ACCESS  read-only
    STATUS      current
    DESCRIPTION "Total number of receivd replies with result code 5006"
    ::= { affirmedServiceconstructInterfaceAaaGroupDiameterStatisticsChassisLevelEndhostIntfTypeEntry 364 }

affirmedServiceconstructInterfaceAaaGroupDiameterStatisticsChassisLevelEndhostIntfTypeNumContradictingAvps OBJECT-TYPE
    SYNTAX      ConfdString
    MAX-ACCESS  read-only
    STATUS      current
    DESCRIPTION "Total number of receivd replies with result code 5007"
    ::= { affirmedServiceconstructInterfaceAaaGroupDiameterStatisticsChassisLevelEndhostIntfTypeEntry 365 }

affirmedServiceconstructInterfaceAaaGroupDiameterStatisticsChassisLevelEndhostIntfTypeNumAvpNotAllowed OBJECT-TYPE
    SYNTAX      ConfdString
    MAX-ACCESS  read-only
    STATUS      current
    DESCRIPTION "Total number of received replies with result code 5008"
    ::= { affirmedServiceconstructInterfaceAaaGroupDiameterStatisticsChassisLevelEndhostIntfTypeEntry 366 }

affirmedServiceconstructInterfaceAaaGroupDiameterStatisticsChassisLevelEndhostIntfTypeNumOccursTooManyTimes OBJECT-TYPE
    SYNTAX      ConfdString
    MAX-ACCESS  read-only
    STATUS      current
    DESCRIPTION "Total number of received replies with result code 5009"
    ::= { affirmedServiceconstructInterfaceAaaGroupDiameterStatisticsChassisLevelEndhostIntfTypeEntry 367 }

affirmedServiceconstructInterfaceAaaGroupDiameterStatisticsChassisLevelEndhostIntfTypeNumNoCommonApplication OBJECT-TYPE
    SYNTAX      ConfdString
    MAX-ACCESS  read-only
    STATUS      current
    DESCRIPTION "Total number of received replies with result code 5010"
    ::= { affirmedServiceconstructInterfaceAaaGroupDiameterStatisticsChassisLevelEndhostIntfTypeEntry 368 }

affirmedServiceconstructInterfaceAaaGroupDiameterStatisticsChassisLevelEndhostIntfTypeNumUnableToComply OBJECT-TYPE
    SYNTAX      ConfdString
    MAX-ACCESS  read-only
    STATUS      current
    DESCRIPTION "Total number of received replies with result code 5012"
    ::= { affirmedServiceconstructInterfaceAaaGroupDiameterStatisticsChassisLevelEndhostIntfTypeEntry 369 }

affirmedServiceconstructInterfaceAaaGroupDiameterStatisticsChassisLevelEndhostIntfTypeNumInvalidBitInHdr OBJECT-TYPE
    SYNTAX      ConfdString
    MAX-ACCESS  read-only
    STATUS      current
    DESCRIPTION "Total number of received replies with result code 5013"
    ::= { affirmedServiceconstructInterfaceAaaGroupDiameterStatisticsChassisLevelEndhostIntfTypeEntry 370 }

affirmedServiceconstructInterfaceAaaGroupDiameterStatisticsChassisLevelEndhostIntfTypeNumInvalidAvpLength OBJECT-TYPE
    SYNTAX      ConfdString
    MAX-ACCESS  read-only
    STATUS      current
    DESCRIPTION "Total number of received replies with result code 5014"
    ::= { affirmedServiceconstructInterfaceAaaGroupDiameterStatisticsChassisLevelEndhostIntfTypeEntry 371 }

affirmedServiceconstructInterfaceAaaGroupDiameterStatisticsChassisLevelEndhostIntfTypeNumInvalidMessageLength OBJECT-TYPE
    SYNTAX      ConfdString
    MAX-ACCESS  read-only
    STATUS      current
    DESCRIPTION "Total number of received replies with result code 5015"
    ::= { affirmedServiceconstructInterfaceAaaGroupDiameterStatisticsChassisLevelEndhostIntfTypeEntry 372 }

affirmedServiceconstructInterfaceAaaGroupDiameterStatisticsChassisLevelEndhostIntfTypeNumInvalidAvpBitCombo OBJECT-TYPE
    SYNTAX      ConfdString
    MAX-ACCESS  read-only
    STATUS      current
    DESCRIPTION "Total number of received replies with result code 5016"
    ::= { affirmedServiceconstructInterfaceAaaGroupDiameterStatisticsChassisLevelEndhostIntfTypeEntry 373 }

affirmedServiceconstructInterfaceAaaGroupDiameterStatisticsChassisLevelEndhostIntfTypeNumNoCommonSecurity OBJECT-TYPE
    SYNTAX      ConfdString
    MAX-ACCESS  read-only
    STATUS      current
    DESCRIPTION "Total number of received replies with result code 5017"
    ::= { affirmedServiceconstructInterfaceAaaGroupDiameterStatisticsChassisLevelEndhostIntfTypeEntry 374 }

affirmedServiceconstructInterfaceAaaGroupDiameterStatisticsChassisLevelEndhostIntfTypeNumUserUnknown OBJECT-TYPE
    SYNTAX      ConfdString
    MAX-ACCESS  read-only
    STATUS      current
    DESCRIPTION "Number of received response with experiment-result code 5001"
    ::= { affirmedServiceconstructInterfaceAaaGroupDiameterStatisticsChassisLevelEndhostIntfTypeEntry 375 }

affirmedServiceconstructInterfaceAaaGroupDiameterStatisticsChassisLevelEndhostIntfTypeNumRoamingNotAllowed OBJECT-TYPE
    SYNTAX      ConfdString
    MAX-ACCESS  read-only
    STATUS      current
    DESCRIPTION "Total number of received replies with experiment-result code 5004"
    ::= { affirmedServiceconstructInterfaceAaaGroupDiameterStatisticsChassisLevelEndhostIntfTypeEntry 376 }

affirmedServiceconstructInterfaceAaaGroupDiameterStatisticsChassisLevelEndhostIntfTypeNumIdentityAlreadyRegistered OBJECT-TYPE
    SYNTAX      ConfdString
    MAX-ACCESS  read-only
    STATUS      current
    DESCRIPTION "Total number of received replies with experiment-result code 5005"
    ::= { affirmedServiceconstructInterfaceAaaGroupDiameterStatisticsChassisLevelEndhostIntfTypeEntry 377 }

affirmedServiceconstructInterfaceAaaGroupDiameterStatisticsChassisLevelEndhostIntfTypeNumOverloadRetryNotAllowed OBJECT-TYPE
    SYNTAX      ConfdString
    MAX-ACCESS  read-only
    STATUS      current
    DESCRIPTION "Total number of received replies with experiment-result code 5198"
    ::= { affirmedServiceconstructInterfaceAaaGroupDiameterStatisticsChassisLevelEndhostIntfTypeEntry 378 }

affirmedServiceconstructInterfaceAaaGroupDiameterStatisticsChassisLevelEndhostIntfTypeNumUnknownEpsSubscription OBJECT-TYPE
    SYNTAX      ConfdString
    MAX-ACCESS  read-only
    STATUS      current
    DESCRIPTION "Total number of received replies with experiment-result code 5420"
    ::= { affirmedServiceconstructInterfaceAaaGroupDiameterStatisticsChassisLevelEndhostIntfTypeEntry 379 }

affirmedServiceconstructInterfaceAaaGroupDiameterStatisticsChassisLevelEndhostIntfTypeNumUserNoNonGppSubscription OBJECT-TYPE
    SYNTAX      ConfdString
    MAX-ACCESS  read-only
    STATUS      current
    DESCRIPTION "Total number of received replies with experiment-result code 5450"
    ::= { affirmedServiceconstructInterfaceAaaGroupDiameterStatisticsChassisLevelEndhostIntfTypeEntry 380 }

affirmedServiceconstructInterfaceAaaGroupDiameterStatisticsChassisLevelEndhostIntfTypeNumUserNoApnSubscription OBJECT-TYPE
    SYNTAX      ConfdString
    MAX-ACCESS  read-only
    STATUS      current
    DESCRIPTION "Total number of received replies with experiment-result code 5451"
    ::= { affirmedServiceconstructInterfaceAaaGroupDiameterStatisticsChassisLevelEndhostIntfTypeEntry 381 }

affirmedServiceconstructInterfaceAaaGroupDiameterStatisticsChassisLevelEndhostIntfTypeNumRatTypeNotAllowed OBJECT-TYPE
    SYNTAX      ConfdString
    MAX-ACCESS  read-only
    STATUS      current
    DESCRIPTION "Total number of received replies with experiment-result code 5452"
    ::= { affirmedServiceconstructInterfaceAaaGroupDiameterStatisticsChassisLevelEndhostIntfTypeEntry 382 }

affirmedServiceconstructInterfaceAaaGroupDiameterStatisticsChassisLevelEndhostIntfTypeNumLateOverlappingRequest OBJECT-TYPE
    SYNTAX      ConfdString
    MAX-ACCESS  read-only
    STATUS      current
    DESCRIPTION "Total number of received replies with experiment-result code 5453"
    ::= { affirmedServiceconstructInterfaceAaaGroupDiameterStatisticsChassisLevelEndhostIntfTypeEntry 383 }

affirmedServiceconstructInterfaceAaaGroupDiameterStatisticsChassisLevelEndhostIntfTypeNumTimedOutRequest OBJECT-TYPE
    SYNTAX      ConfdString
    MAX-ACCESS  read-only
    STATUS      current
    DESCRIPTION "Total number of received replies with experiment-result code 5454"
    ::= { affirmedServiceconstructInterfaceAaaGroupDiameterStatisticsChassisLevelEndhostIntfTypeEntry 384 }

affirmedServiceconstructInterfaceAaaGroupDiameterStatisticsChassisLevelEndhostResultCodeStatisticsTable OBJECT-TYPE
    SYNTAX      SEQUENCE OF AffirmedServiceconstructInterfaceAaaGroupDiameterStatisticsChassisLevelEndhostResultCodeStatisticsEntry
    MAX-ACCESS  not-accessible
    STATUS      current
    DESCRIPTION ""
    ::= { affirmedServiceconstructInterfaceAaaGroupDiameterStatisticsChassisLevelEndhost 2 }

affirmedServiceconstructInterfaceAaaGroupDiameterStatisticsChassisLevelEndhostResultCodeStatisticsEntry OBJECT-TYPE
    SYNTAX      AffirmedServiceconstructInterfaceAaaGroupDiameterStatisticsChassisLevelEndhostResultCodeStatisticsEntry
    MAX-ACCESS  not-accessible
    STATUS      current
    DESCRIPTION ""
    INDEX { affirmedServiceconstructInterfaceAaaGroupDiameterStatisticsChassisLevelEndhostResultCodeStatisticsIntfType, affirmedServiceconstructInterfaceAaaGroupDiameterStatisticsChassisLevelEndhostResultCodeStatisticsNodeName, affirmedServiceconstructInterfaceAaaGroupDiameterStatisticsChassisLevelEndhostResultCodeStatisticsDraName, affirmedServiceconstructInterfaceAaaGroupDiameterStatisticsChassisLevelEndhostResultCodeStatisticsEndHostName, affirmedServiceconstructInterfaceAaaGroupDiameterStatisticsChassisLevelEndhostResultCodeStatisticsResultCode }
        ::= { affirmedServiceconstructInterfaceAaaGroupDiameterStatisticsChassisLevelEndhostResultCodeStatisticsTable 1 }

AffirmedServiceconstructInterfaceAaaGroupDiameterStatisticsChassisLevelEndhostResultCodeStatisticsEntry ::=
    SEQUENCE {
        affirmedServiceconstructInterfaceAaaGroupDiameterStatisticsChassisLevelEndhostResultCodeStatisticsIntfType String,
        affirmedServiceconstructInterfaceAaaGroupDiameterStatisticsChassisLevelEndhostResultCodeStatisticsNodeName String,
        affirmedServiceconstructInterfaceAaaGroupDiameterStatisticsChassisLevelEndhostResultCodeStatisticsDraName String,
        affirmedServiceconstructInterfaceAaaGroupDiameterStatisticsChassisLevelEndhostResultCodeStatisticsEndHostName String,
        affirmedServiceconstructInterfaceAaaGroupDiameterStatisticsChassisLevelEndhostResultCodeStatisticsResultCode String,
        affirmedServiceconstructInterfaceAaaGroupDiameterStatisticsChassisLevelEndhostResultCodeStatisticsNumInitialResponse ConfdString,
        affirmedServiceconstructInterfaceAaaGroupDiameterStatisticsChassisLevelEndhostResultCodeStatisticsNumUpdateResponse ConfdString,
        affirmedServiceconstructInterfaceAaaGroupDiameterStatisticsChassisLevelEndhostResultCodeStatisticsNumTerminateResponse ConfdString
    }

affirmedServiceconstructInterfaceAaaGroupDiameterStatisticsChassisLevelEndhostResultCodeStatisticsIntfType OBJECT-TYPE
    SYNTAX      String
    MAX-ACCESS  not-accessible
    STATUS      current
    DESCRIPTION "Diameter Interface Type: GX/GY"
    ::= { affirmedServiceconstructInterfaceAaaGroupDiameterStatisticsChassisLevelEndhostResultCodeStatisticsEntry 1 }

affirmedServiceconstructInterfaceAaaGroupDiameterStatisticsChassisLevelEndhostResultCodeStatisticsNodeName OBJECT-TYPE
    SYNTAX      String
    MAX-ACCESS  not-accessible
    STATUS      current
    DESCRIPTION "Local Diameter Server Node Name"
    ::= { affirmedServiceconstructInterfaceAaaGroupDiameterStatisticsChassisLevelEndhostResultCodeStatisticsEntry 2 }

affirmedServiceconstructInterfaceAaaGroupDiameterStatisticsChassisLevelEndhostResultCodeStatisticsDraName OBJECT-TYPE
    SYNTAX      String
    MAX-ACCESS  not-accessible
    STATUS      current
    DESCRIPTION "DRA name"
    ::= { affirmedServiceconstructInterfaceAaaGroupDiameterStatisticsChassisLevelEndhostResultCodeStatisticsEntry 3 }

affirmedServiceconstructInterfaceAaaGroupDiameterStatisticsChassisLevelEndhostResultCodeStatisticsEndHostName OBJECT-TYPE
    SYNTAX      String
    MAX-ACCESS  not-accessible
    STATUS      current
    DESCRIPTION "End Host name"
    ::= { affirmedServiceconstructInterfaceAaaGroupDiameterStatisticsChassisLevelEndhostResultCodeStatisticsEntry 4 }

affirmedServiceconstructInterfaceAaaGroupDiameterStatisticsChassisLevelEndhostResultCodeStatisticsResultCode OBJECT-TYPE
    SYNTAX      String
    MAX-ACCESS  not-accessible
    STATUS      current
    DESCRIPTION "Result Code"
    ::= { affirmedServiceconstructInterfaceAaaGroupDiameterStatisticsChassisLevelEndhostResultCodeStatisticsEntry 5 }

affirmedServiceconstructInterfaceAaaGroupDiameterStatisticsChassisLevelEndhostResultCodeStatisticsNumInitialResponse OBJECT-TYPE
    SYNTAX      ConfdString
    MAX-ACCESS  read-only
    STATUS      current
    DESCRIPTION "Total number of Inital Response Received with the result code "
    ::= { affirmedServiceconstructInterfaceAaaGroupDiameterStatisticsChassisLevelEndhostResultCodeStatisticsEntry 6 }

affirmedServiceconstructInterfaceAaaGroupDiameterStatisticsChassisLevelEndhostResultCodeStatisticsNumUpdateResponse OBJECT-TYPE
    SYNTAX      ConfdString
    MAX-ACCESS  read-only
    STATUS      current
    DESCRIPTION "Total number of Update Response Received with the result code "
    ::= { affirmedServiceconstructInterfaceAaaGroupDiameterStatisticsChassisLevelEndhostResultCodeStatisticsEntry 7 }

affirmedServiceconstructInterfaceAaaGroupDiameterStatisticsChassisLevelEndhostResultCodeStatisticsNumTerminateResponse OBJECT-TYPE
    SYNTAX      ConfdString
    MAX-ACCESS  read-only
    STATUS      current
    DESCRIPTION "Total number of Terminate Response Received with the result code "
    ::= { affirmedServiceconstructInterfaceAaaGroupDiameterStatisticsChassisLevelEndhostResultCodeStatisticsEntry 8 }

affirmedServiceconstructInterfaceAaaGroupDiameterNodeStatusTable OBJECT-TYPE
    SYNTAX      SEQUENCE OF AffirmedServiceconstructInterfaceAaaGroupDiameterNodeStatusEntry
    MAX-ACCESS  not-accessible
    STATUS      current
    DESCRIPTION ""
    ::= { affirmedServiceconstructInterfaceAaaGroupDiameter 1 }

affirmedServiceconstructInterfaceAaaGroupDiameterNodeStatusEntry OBJECT-TYPE
    SYNTAX      AffirmedServiceconstructInterfaceAaaGroupDiameterNodeStatusEntry
    MAX-ACCESS  not-accessible
    STATUS      current
    DESCRIPTION ""
    INDEX { affirmedServiceconstructInterfaceAaaGroupDiameterNodeStatusName }
        ::= { affirmedServiceconstructInterfaceAaaGroupDiameterNodeStatusTable 1 }

AffirmedServiceconstructInterfaceAaaGroupDiameterNodeStatusEntry ::=
    SEQUENCE {
        affirmedServiceconstructInterfaceAaaGroupDiameterNodeStatusName String,
        affirmedServiceconstructInterfaceAaaGroupDiameterNodeStatusOriginHost String,
        affirmedServiceconstructInterfaceAaaGroupDiameterNodeStatusOriginRealm String,
        affirmedServiceconstructInterfaceAaaGroupDiameterNodeStatusHostIPAddress String,
        affirmedServiceconstructInterfaceAaaGroupDiameterNodeStatusTransport INTEGER,
        affirmedServiceconstructInterfaceAaaGroupDiameterNodeStatusPort Unsigned32,
        affirmedServiceconstructInterfaceAaaGroupDiameterNodeStatusGeoRedundantGroup String,
        affirmedServiceconstructInterfaceAaaGroupDiameterNodeStatusStatus INTEGER,
        affirmedServiceconstructInterfaceAaaGroupDiameterNodeStatusSecondaryIPAddress String
    }

affirmedServiceconstructInterfaceAaaGroupDiameterNodeStatusName OBJECT-TYPE
    SYNTAX      String
    MAX-ACCESS  not-accessible
    STATUS      current
    DESCRIPTION "Local Diameter Node Name"
    ::= { affirmedServiceconstructInterfaceAaaGroupDiameterNodeStatusEntry 1 }

affirmedServiceconstructInterfaceAaaGroupDiameterNodeStatusOriginHost OBJECT-TYPE
    SYNTAX      String
    MAX-ACCESS  read-only
    STATUS      current
    DESCRIPTION "Local HostName in FQDN"
    ::= { affirmedServiceconstructInterfaceAaaGroupDiameterNodeStatusEntry 2 }

affirmedServiceconstructInterfaceAaaGroupDiameterNodeStatusOriginRealm OBJECT-TYPE
    SYNTAX      String
    MAX-ACCESS  read-only
    STATUS      current
    DESCRIPTION "Local Realm Name"
    ::= { affirmedServiceconstructInterfaceAaaGroupDiameterNodeStatusEntry 3 }

affirmedServiceconstructInterfaceAaaGroupDiameterNodeStatusHostIPAddress OBJECT-TYPE
    SYNTAX      String
    MAX-ACCESS  read-only
    STATUS      current
    DESCRIPTION "Signaling port IP Address"
    ::= { affirmedServiceconstructInterfaceAaaGroupDiameterNodeStatusEntry 4 }

affirmedServiceconstructInterfaceAaaGroupDiameterNodeStatusTransport OBJECT-TYPE
    SYNTAX      INTEGER {tcp(0),sctp(1)}
    MAX-ACCESS  read-only
    STATUS      current
    DESCRIPTION "Transport type"
    ::= { affirmedServiceconstructInterfaceAaaGroupDiameterNodeStatusEntry 5 }

affirmedServiceconstructInterfaceAaaGroupDiameterNodeStatusPort OBJECT-TYPE
    SYNTAX      Unsigned32
    MAX-ACCESS  read-only
    STATUS      current
    DESCRIPTION "Signaling port number"
    ::= { affirmedServiceconstructInterfaceAaaGroupDiameterNodeStatusEntry 6 }

affirmedServiceconstructInterfaceAaaGroupDiameterNodeStatusGeoRedundantGroup OBJECT-TYPE
    SYNTAX      String
    MAX-ACCESS  read-only
    STATUS      current
    DESCRIPTION "Geographic Redundancy Group Name"
    ::= { affirmedServiceconstructInterfaceAaaGroupDiameterNodeStatusEntry 7 }

affirmedServiceconstructInterfaceAaaGroupDiameterNodeStatusStatus OBJECT-TYPE
    SYNTAX      INTEGER {outofservice(0),inservice(1)}
    MAX-ACCESS  read-only
    STATUS      current
    DESCRIPTION "Signaling Port status"
    ::= { affirmedServiceconstructInterfaceAaaGroupDiameterNodeStatusEntry 8 }

affirmedServiceconstructInterfaceAaaGroupDiameterNodeStatusSecondaryIPAddress OBJECT-TYPE
    SYNTAX      String
    MAX-ACCESS  read-only
    STATUS      current
    DESCRIPTION "Secondary IP Address for SCTP"
    ::= { affirmedServiceconstructInterfaceAaaGroupDiameterNodeStatusEntry 9 }

affirmedServiceconstructInterfaceAaaGroupDiameterPeerStatusTable OBJECT-TYPE
    SYNTAX      SEQUENCE OF AffirmedServiceconstructInterfaceAaaGroupDiameterPeerStatusEntry
    MAX-ACCESS  not-accessible
    STATUS      current
    DESCRIPTION ""
    ::= { affirmedServiceconstructInterfaceAaaGroupDiameter 2 }

affirmedServiceconstructInterfaceAaaGroupDiameterPeerStatusEntry OBJECT-TYPE
    SYNTAX      AffirmedServiceconstructInterfaceAaaGroupDiameterPeerStatusEntry
    MAX-ACCESS  not-accessible
    STATUS      current
    DESCRIPTION ""
    INDEX { affirmedServiceconstructInterfaceAaaGroupDiameterPeerStatusNodeName, affirmedServiceconstructInterfaceAaaGroupDiameterPeerStatusHostName }
        ::= { affirmedServiceconstructInterfaceAaaGroupDiameterPeerStatusTable 1 }

AffirmedServiceconstructInterfaceAaaGroupDiameterPeerStatusEntry ::=
    SEQUENCE {
        affirmedServiceconstructInterfaceAaaGroupDiameterPeerStatusNodeName String,
        affirmedServiceconstructInterfaceAaaGroupDiameterPeerStatusHostName String,
        affirmedServiceconstructInterfaceAaaGroupDiameterPeerStatusRealm String,
        affirmedServiceconstructInterfaceAaaGroupDiameterPeerStatusIpAddress String,
        affirmedServiceconstructInterfaceAaaGroupDiameterPeerStatusPort Unsigned32,
        affirmedServiceconstructInterfaceAaaGroupDiameterPeerStatusTransport INTEGER,
        affirmedServiceconstructInterfaceAaaGroupDiameterPeerStatusRole INTEGER,
        affirmedServiceconstructInterfaceAaaGroupDiameterPeerStatusBackupHostName String,
        affirmedServiceconstructInterfaceAaaGroupDiameterPeerStatusStatus INTEGER,
        affirmedServiceconstructInterfaceAaaGroupDiameterPeerStatusLastStateChange String,
        affirmedServiceconstructInterfaceAaaGroupDiameterPeerStatusOverrideDestinationHostName String,
        affirmedServiceconstructInterfaceAaaGroupDiameterPeerStatusOriginHost String,
        affirmedServiceconstructInterfaceAaaGroupDiameterPeerStatusOriginRealm String,
        affirmedServiceconstructInterfaceAaaGroupDiameterPeerStatusLocalPort Unsigned32,
        affirmedServiceconstructInterfaceAaaGroupDiameterPeerStatusSecondaryIpAddress String,
        affirmedServiceconstructInterfaceAaaGroupDiameterPeerStatusAdminStatus INTEGER
    }

affirmedServiceconstructInterfaceAaaGroupDiameterPeerStatusNodeName OBJECT-TYPE
    SYNTAX      String
    MAX-ACCESS  not-accessible
    STATUS      current
    DESCRIPTION "Local Diameter Node Name"
    ::= { affirmedServiceconstructInterfaceAaaGroupDiameterPeerStatusEntry 1 }

affirmedServiceconstructInterfaceAaaGroupDiameterPeerStatusHostName OBJECT-TYPE
    SYNTAX      String
    MAX-ACCESS  not-accessible
    STATUS      current
    DESCRIPTION "Peer host name FQDN"
    ::= { affirmedServiceconstructInterfaceAaaGroupDiameterPeerStatusEntry 2 }

affirmedServiceconstructInterfaceAaaGroupDiameterPeerStatusRealm OBJECT-TYPE
    SYNTAX      String
    MAX-ACCESS  read-only
    STATUS      current
    DESCRIPTION "Peer realm name"
    ::= { affirmedServiceconstructInterfaceAaaGroupDiameterPeerStatusEntry 3 }

affirmedServiceconstructInterfaceAaaGroupDiameterPeerStatusIpAddress OBJECT-TYPE
    SYNTAX      String
    MAX-ACCESS  read-only
    STATUS      current
    DESCRIPTION "Address of Peer. Can be IPv4/IPv6"
    ::= { affirmedServiceconstructInterfaceAaaGroupDiameterPeerStatusEntry 4 }

affirmedServiceconstructInterfaceAaaGroupDiameterPeerStatusPort OBJECT-TYPE
    SYNTAX      Unsigned32
    MAX-ACCESS  read-only
    STATUS      current
    DESCRIPTION "peer port number"
    ::= { affirmedServiceconstructInterfaceAaaGroupDiameterPeerStatusEntry 5 }

affirmedServiceconstructInterfaceAaaGroupDiameterPeerStatusTransport OBJECT-TYPE
    SYNTAX      INTEGER {tcp(0),sctp(1)}
    MAX-ACCESS  read-only
    STATUS      current
    DESCRIPTION "transport type"
    ::= { affirmedServiceconstructInterfaceAaaGroupDiameterPeerStatusEntry 6 }

affirmedServiceconstructInterfaceAaaGroupDiameterPeerStatusRole OBJECT-TYPE
    SYNTAX      INTEGER {primary(0),secondary(1)}
    MAX-ACCESS  read-only
    STATUS      current
    DESCRIPTION "primary or secondary"
    ::= { affirmedServiceconstructInterfaceAaaGroupDiameterPeerStatusEntry 7 }

affirmedServiceconstructInterfaceAaaGroupDiameterPeerStatusBackupHostName OBJECT-TYPE
    SYNTAX      String
    MAX-ACCESS  read-only
    STATUS      current
    DESCRIPTION "backup server identity"
    ::= { affirmedServiceconstructInterfaceAaaGroupDiameterPeerStatusEntry 8 }

affirmedServiceconstructInterfaceAaaGroupDiameterPeerStatusStatus OBJECT-TYPE
    SYNTAX      INTEGER {initial(0),okay(1),suspect(2),down(3),reopen(4),okay-flowoff(5)}
    MAX-ACCESS  read-only
    STATUS      current
    DESCRIPTION "Peer node status"
    ::= { affirmedServiceconstructInterfaceAaaGroupDiameterPeerStatusEntry 9 }

affirmedServiceconstructInterfaceAaaGroupDiameterPeerStatusLastStateChange OBJECT-TYPE
    SYNTAX      String
    MAX-ACCESS  read-only
    STATUS      current
    DESCRIPTION "Time when state was last changed"
    ::= { affirmedServiceconstructInterfaceAaaGroupDiameterPeerStatusEntry 10 }

affirmedServiceconstructInterfaceAaaGroupDiameterPeerStatusOverrideDestinationHostName OBJECT-TYPE
    SYNTAX      String
    MAX-ACCESS  read-only
    STATUS      current
    DESCRIPTION "Hostname to override the configured peer hostname in the Destination-Host AVP in CCR-I (Gx, Gy) and AAR (S6b) messages"
    ::= { affirmedServiceconstructInterfaceAaaGroupDiameterPeerStatusEntry 11 }

affirmedServiceconstructInterfaceAaaGroupDiameterPeerStatusOriginHost OBJECT-TYPE
    SYNTAX      String
    MAX-ACCESS  read-only
    STATUS      current
    DESCRIPTION "Local HostName in FQDN"
    ::= { affirmedServiceconstructInterfaceAaaGroupDiameterPeerStatusEntry 12 }

affirmedServiceconstructInterfaceAaaGroupDiameterPeerStatusOriginRealm OBJECT-TYPE
    SYNTAX      String
    MAX-ACCESS  read-only
    STATUS      current
    DESCRIPTION "Local Realm Name"
    ::= { affirmedServiceconstructInterfaceAaaGroupDiameterPeerStatusEntry 13 }

affirmedServiceconstructInterfaceAaaGroupDiameterPeerStatusLocalPort OBJECT-TYPE
    SYNTAX      Unsigned32
    MAX-ACCESS  read-only
    STATUS      current
    DESCRIPTION "local port number"
    ::= { affirmedServiceconstructInterfaceAaaGroupDiameterPeerStatusEntry 14 }

affirmedServiceconstructInterfaceAaaGroupDiameterPeerStatusSecondaryIpAddress OBJECT-TYPE
    SYNTAX      String
    MAX-ACCESS  read-only
    STATUS      current
    DESCRIPTION "Secondary Address of Peer Host for SCTP"
    ::= { affirmedServiceconstructInterfaceAaaGroupDiameterPeerStatusEntry 15 }

affirmedServiceconstructInterfaceAaaGroupDiameterPeerStatusAdminStatus OBJECT-TYPE
    SYNTAX      INTEGER {disabled(0),enabled(1)}
    MAX-ACCESS  read-only
    STATUS      current
    DESCRIPTION "Admin Status"
    ::= { affirmedServiceconstructInterfaceAaaGroupDiameterPeerStatusEntry 16 }

affirmedServiceconstructInterfaceAaaGroupDiameterPeerStatsTable OBJECT-TYPE
    SYNTAX      SEQUENCE OF AffirmedServiceconstructInterfaceAaaGroupDiameterPeerStatsEntry
    MAX-ACCESS  not-accessible
    STATUS      current
    DESCRIPTION ""
    ::= { affirmedServiceconstructInterfaceAaaGroupDiameter 3 }

affirmedServiceconstructInterfaceAaaGroupDiameterPeerStatsEntry OBJECT-TYPE
    SYNTAX      AffirmedServiceconstructInterfaceAaaGroupDiameterPeerStatsEntry
    MAX-ACCESS  not-accessible
    STATUS      current
    DESCRIPTION ""
    INDEX { affirmedServiceconstructInterfaceAaaGroupDiameterPeerStatsNodeName, affirmedServiceconstructInterfaceAaaGroupDiameterPeerStatsHostName }
        ::= { affirmedServiceconstructInterfaceAaaGroupDiameterPeerStatsTable 1 }

AffirmedServiceconstructInterfaceAaaGroupDiameterPeerStatsEntry ::=
    SEQUENCE {
        affirmedServiceconstructInterfaceAaaGroupDiameterPeerStatsNodeName String,
        affirmedServiceconstructInterfaceAaaGroupDiameterPeerStatsHostName String,
        affirmedServiceconstructInterfaceAaaGroupDiameterPeerStatsRealm String,
        affirmedServiceconstructInterfaceAaaGroupDiameterPeerStatsNumOfProtocolError ConfdString,
        affirmedServiceconstructInterfaceAaaGroupDiameterPeerStatsNumOfPermanentFailure ConfdString,
        affirmedServiceconstructInterfaceAaaGroupDiameterPeerStatsNumOfRoutingFailure ConfdString,
        affirmedServiceconstructInterfaceAaaGroupDiameterPeerStatsNumOfOutRequest ConfdString,
        affirmedServiceconstructInterfaceAaaGroupDiameterPeerStatsNumOfOutResponse ConfdString,
        affirmedServiceconstructInterfaceAaaGroupDiameterPeerStatsNumOfInRequest ConfdString,
        affirmedServiceconstructInterfaceAaaGroupDiameterPeerStatsNumOfInResponse ConfdString
    }

affirmedServiceconstructInterfaceAaaGroupDiameterPeerStatsNodeName OBJECT-TYPE
    SYNTAX      String
    MAX-ACCESS  not-accessible
    STATUS      current
    DESCRIPTION "Local Diameter Node Name"
    ::= { affirmedServiceconstructInterfaceAaaGroupDiameterPeerStatsEntry 1 }

affirmedServiceconstructInterfaceAaaGroupDiameterPeerStatsHostName OBJECT-TYPE
    SYNTAX      String
    MAX-ACCESS  not-accessible
    STATUS      current
    DESCRIPTION "Peer host name FQDN"
    ::= { affirmedServiceconstructInterfaceAaaGroupDiameterPeerStatsEntry 2 }

affirmedServiceconstructInterfaceAaaGroupDiameterPeerStatsRealm OBJECT-TYPE
    SYNTAX      String
    MAX-ACCESS  read-only
    STATUS      current
    DESCRIPTION "peer realm name"
    ::= { affirmedServiceconstructInterfaceAaaGroupDiameterPeerStatsEntry 3 }

affirmedServiceconstructInterfaceAaaGroupDiameterPeerStatsNumOfProtocolError OBJECT-TYPE
    SYNTAX      ConfdString
    MAX-ACCESS  read-only
    STATUS      current
    DESCRIPTION "total number of protocol errors"
    ::= { affirmedServiceconstructInterfaceAaaGroupDiameterPeerStatsEntry 4 }

affirmedServiceconstructInterfaceAaaGroupDiameterPeerStatsNumOfPermanentFailure OBJECT-TYPE
    SYNTAX      ConfdString
    MAX-ACCESS  read-only
    STATUS      current
    DESCRIPTION "total number of request failure to the peer"
    ::= { affirmedServiceconstructInterfaceAaaGroupDiameterPeerStatsEntry 5 }

affirmedServiceconstructInterfaceAaaGroupDiameterPeerStatsNumOfRoutingFailure OBJECT-TYPE
    SYNTAX      ConfdString
    MAX-ACCESS  read-only
    STATUS      current
    DESCRIPTION "total number of routing failure to the peer"
    ::= { affirmedServiceconstructInterfaceAaaGroupDiameterPeerStatsEntry 6 }

affirmedServiceconstructInterfaceAaaGroupDiameterPeerStatsNumOfOutRequest OBJECT-TYPE
    SYNTAX      ConfdString
    MAX-ACCESS  read-only
    STATUS      current
    DESCRIPTION "total number of requests sent to the peer"
    ::= { affirmedServiceconstructInterfaceAaaGroupDiameterPeerStatsEntry 7 }

affirmedServiceconstructInterfaceAaaGroupDiameterPeerStatsNumOfOutResponse OBJECT-TYPE
    SYNTAX      ConfdString
    MAX-ACCESS  read-only
    STATUS      current
    DESCRIPTION "total number of responses sent to the peer"
    ::= { affirmedServiceconstructInterfaceAaaGroupDiameterPeerStatsEntry 8 }

affirmedServiceconstructInterfaceAaaGroupDiameterPeerStatsNumOfInRequest OBJECT-TYPE
    SYNTAX      ConfdString
    MAX-ACCESS  read-only
    STATUS      current
    DESCRIPTION "total number of requests received from the peer"
    ::= { affirmedServiceconstructInterfaceAaaGroupDiameterPeerStatsEntry 9 }

affirmedServiceconstructInterfaceAaaGroupDiameterPeerStatsNumOfInResponse OBJECT-TYPE
    SYNTAX      ConfdString
    MAX-ACCESS  read-only
    STATUS      current
    DESCRIPTION "total number of responses received from the peer"
    ::= { affirmedServiceconstructInterfaceAaaGroupDiameterPeerStatsEntry 10 }

affirmedServiceconstructInterfaceAaaGroupDiameterPeerCmdStatsTable OBJECT-TYPE
    SYNTAX      SEQUENCE OF AffirmedServiceconstructInterfaceAaaGroupDiameterPeerCmdStatsEntry
    MAX-ACCESS  not-accessible
    STATUS      current
    DESCRIPTION ""
    ::= { affirmedServiceconstructInterfaceAaaGroupDiameter 4 }

affirmedServiceconstructInterfaceAaaGroupDiameterPeerCmdStatsEntry OBJECT-TYPE
    SYNTAX      AffirmedServiceconstructInterfaceAaaGroupDiameterPeerCmdStatsEntry
    MAX-ACCESS  not-accessible
    STATUS      current
    DESCRIPTION ""
    INDEX { affirmedServiceconstructInterfaceAaaGroupDiameterPeerCmdStatsNodeName, affirmedServiceconstructInterfaceAaaGroupDiameterPeerCmdStatsHostName, affirmedServiceconstructInterfaceAaaGroupDiameterPeerCmdStatsCmdCode }
        ::= { affirmedServiceconstructInterfaceAaaGroupDiameterPeerCmdStatsTable 1 }

AffirmedServiceconstructInterfaceAaaGroupDiameterPeerCmdStatsEntry ::=
    SEQUENCE {
        affirmedServiceconstructInterfaceAaaGroupDiameterPeerCmdStatsNodeName String,
        affirmedServiceconstructInterfaceAaaGroupDiameterPeerCmdStatsHostName String,
        affirmedServiceconstructInterfaceAaaGroupDiameterPeerCmdStatsCmdCode Unsigned32,
        affirmedServiceconstructInterfaceAaaGroupDiameterPeerCmdStatsRealm String,
        affirmedServiceconstructInterfaceAaaGroupDiameterPeerCmdStatsNumOfOutRequest ConfdString,
        affirmedServiceconstructInterfaceAaaGroupDiameterPeerCmdStatsNumOfOutResponse ConfdString,
        affirmedServiceconstructInterfaceAaaGroupDiameterPeerCmdStatsNumOfInRequest ConfdString,
        affirmedServiceconstructInterfaceAaaGroupDiameterPeerCmdStatsNumOfInResponse ConfdString
    }

affirmedServiceconstructInterfaceAaaGroupDiameterPeerCmdStatsNodeName OBJECT-TYPE
    SYNTAX      String
    MAX-ACCESS  not-accessible
    STATUS      current
    DESCRIPTION "Local Diameter Node Name"
    ::= { affirmedServiceconstructInterfaceAaaGroupDiameterPeerCmdStatsEntry 1 }

affirmedServiceconstructInterfaceAaaGroupDiameterPeerCmdStatsHostName OBJECT-TYPE
    SYNTAX      String
    MAX-ACCESS  not-accessible
    STATUS      current
    DESCRIPTION "Peer host name FQDN"
    ::= { affirmedServiceconstructInterfaceAaaGroupDiameterPeerCmdStatsEntry 2 }

affirmedServiceconstructInterfaceAaaGroupDiameterPeerCmdStatsCmdCode OBJECT-TYPE
    SYNTAX      Unsigned32
    MAX-ACCESS  not-accessible
    STATUS      current
    DESCRIPTION "Diameter command code"
    ::= { affirmedServiceconstructInterfaceAaaGroupDiameterPeerCmdStatsEntry 3 }

affirmedServiceconstructInterfaceAaaGroupDiameterPeerCmdStatsRealm OBJECT-TYPE
    SYNTAX      String
    MAX-ACCESS  read-only
    STATUS      current
    DESCRIPTION "Peer realm name"
    ::= { affirmedServiceconstructInterfaceAaaGroupDiameterPeerCmdStatsEntry 4 }

affirmedServiceconstructInterfaceAaaGroupDiameterPeerCmdStatsNumOfOutRequest OBJECT-TYPE
    SYNTAX      ConfdString
    MAX-ACCESS  read-only
    STATUS      current
    DESCRIPTION "total number of request of the command sent to the peer"
    ::= { affirmedServiceconstructInterfaceAaaGroupDiameterPeerCmdStatsEntry 5 }

affirmedServiceconstructInterfaceAaaGroupDiameterPeerCmdStatsNumOfOutResponse OBJECT-TYPE
    SYNTAX      ConfdString
    MAX-ACCESS  read-only
    STATUS      current
    DESCRIPTION "total number of response for the command sent to the peer"
    ::= { affirmedServiceconstructInterfaceAaaGroupDiameterPeerCmdStatsEntry 6 }

affirmedServiceconstructInterfaceAaaGroupDiameterPeerCmdStatsNumOfInRequest OBJECT-TYPE
    SYNTAX      ConfdString
    MAX-ACCESS  read-only
    STATUS      current
    DESCRIPTION "total number of requests received from the peer"
    ::= { affirmedServiceconstructInterfaceAaaGroupDiameterPeerCmdStatsEntry 7 }

affirmedServiceconstructInterfaceAaaGroupDiameterPeerCmdStatsNumOfInResponse OBJECT-TYPE
    SYNTAX      ConfdString
    MAX-ACCESS  read-only
    STATUS      current
    DESCRIPTION "total number of responses received from the peer"
    ::= { affirmedServiceconstructInterfaceAaaGroupDiameterPeerCmdStatsEntry 8 }

affirmedServiceconstructInterfaceAaaGroupDiameterRoutingStatusTable OBJECT-TYPE
    SYNTAX      SEQUENCE OF AffirmedServiceconstructInterfaceAaaGroupDiameterRoutingStatusEntry
    MAX-ACCESS  not-accessible
    STATUS      current
    DESCRIPTION ""
    ::= { affirmedServiceconstructInterfaceAaaGroupDiameter 6 }

affirmedServiceconstructInterfaceAaaGroupDiameterRoutingStatusEntry OBJECT-TYPE
    SYNTAX      AffirmedServiceconstructInterfaceAaaGroupDiameterRoutingStatusEntry
    MAX-ACCESS  not-accessible
    STATUS      current
    DESCRIPTION ""
    INDEX { affirmedServiceconstructInterfaceAaaGroupDiameterRoutingStatusAppType, affirmedServiceconstructInterfaceAaaGroupDiameterRoutingStatusRealm, affirmedServiceconstructInterfaceAaaGroupDiameterRoutingStatusHostName, affirmedServiceconstructInterfaceAaaGroupDiameterRoutingStatusNextHop }
        ::= { affirmedServiceconstructInterfaceAaaGroupDiameterRoutingStatusTable 1 }

AffirmedServiceconstructInterfaceAaaGroupDiameterRoutingStatusEntry ::=
    SEQUENCE {
        affirmedServiceconstructInterfaceAaaGroupDiameterRoutingStatusAppType INTEGER,
        affirmedServiceconstructInterfaceAaaGroupDiameterRoutingStatusRealm String,
        affirmedServiceconstructInterfaceAaaGroupDiameterRoutingStatusHostName String,
        affirmedServiceconstructInterfaceAaaGroupDiameterRoutingStatusNextHop String,
        affirmedServiceconstructInterfaceAaaGroupDiameterRoutingStatusRole INTEGER,
        affirmedServiceconstructInterfaceAaaGroupDiameterRoutingStatusStatus INTEGER
    }

affirmedServiceconstructInterfaceAaaGroupDiameterRoutingStatusAppType OBJECT-TYPE
    SYNTAX      INTEGER {gx(1),gy(2),gz(3),s6b(4),sta(5),swm(6),flowauth(7),sxab(8),s6t(9),t6a(10),s6m(11),t4(12),sd(15)}
    MAX-ACCESS  not-accessible
    STATUS      current
    DESCRIPTION "Diameter Applications(Gx/Gy/Gz/S6b/Swm)"
    ::= { affirmedServiceconstructInterfaceAaaGroupDiameterRoutingStatusEntry 1 }

affirmedServiceconstructInterfaceAaaGroupDiameterRoutingStatusRealm OBJECT-TYPE
    SYNTAX      String
    MAX-ACCESS  not-accessible
    STATUS      current
    DESCRIPTION "Destination Realm"
    ::= { affirmedServiceconstructInterfaceAaaGroupDiameterRoutingStatusEntry 2 }

affirmedServiceconstructInterfaceAaaGroupDiameterRoutingStatusHostName OBJECT-TYPE
    SYNTAX      String
    MAX-ACCESS  not-accessible
    STATUS      current
    DESCRIPTION "End Host Name"
    ::= { affirmedServiceconstructInterfaceAaaGroupDiameterRoutingStatusEntry 3 }

affirmedServiceconstructInterfaceAaaGroupDiameterRoutingStatusNextHop OBJECT-TYPE
    SYNTAX      String
    MAX-ACCESS  not-accessible
    STATUS      current
    DESCRIPTION "Next Hop Name"
    ::= { affirmedServiceconstructInterfaceAaaGroupDiameterRoutingStatusEntry 4 }

affirmedServiceconstructInterfaceAaaGroupDiameterRoutingStatusRole OBJECT-TYPE
    SYNTAX      INTEGER {primary(0),secondary(1)}
    MAX-ACCESS  read-only
    STATUS      current
    DESCRIPTION "Primary/Secondary"
    ::= { affirmedServiceconstructInterfaceAaaGroupDiameterRoutingStatusEntry 5 }

affirmedServiceconstructInterfaceAaaGroupDiameterRoutingStatusStatus OBJECT-TYPE
    SYNTAX      INTEGER {initial(0),okay(1),suspect(2),down(3),reopen(4),okay-flowoff(5)}
    MAX-ACCESS  read-only
    STATUS      current
    DESCRIPTION "End Host server status"
    ::= { affirmedServiceconstructInterfaceAaaGroupDiameterRoutingStatusEntry 6 }

affirmedServiceconstructInterfaceAaaGroupGtppStatisticsChassisLevelPeerGtppNodeNameTable OBJECT-TYPE
    SYNTAX      SEQUENCE OF AffirmedServiceconstructInterfaceAaaGroupGtppStatisticsChassisLevelPeerGtppNodeNameEntry
    MAX-ACCESS  not-accessible
    STATUS      current
    DESCRIPTION ""
    ::= { affirmedServiceconstructInterfaceAaaGroupGtppStatisticsChassisLevelPeer 1 }

affirmedServiceconstructInterfaceAaaGroupGtppStatisticsChassisLevelPeerGtppNodeNameEntry OBJECT-TYPE
    SYNTAX      AffirmedServiceconstructInterfaceAaaGroupGtppStatisticsChassisLevelPeerGtppNodeNameEntry
    MAX-ACCESS  not-accessible
    STATUS      current
    DESCRIPTION ""
    INDEX { affirmedServiceconstructInterfaceAaaGroupGtppStatisticsChassisLevelPeerGtppNodeNameNodeName, affirmedServiceconstructInterfaceAaaGroupGtppStatisticsChassisLevelPeerGtppNodeNamePeerName }
        ::= { affirmedServiceconstructInterfaceAaaGroupGtppStatisticsChassisLevelPeerGtppNodeNameTable 1 }

AffirmedServiceconstructInterfaceAaaGroupGtppStatisticsChassisLevelPeerGtppNodeNameEntry ::=
    SEQUENCE {
        affirmedServiceconstructInterfaceAaaGroupGtppStatisticsChassisLevelPeerGtppNodeNameNodeName String,
        affirmedServiceconstructInterfaceAaaGroupGtppStatisticsChassisLevelPeerGtppNodeNamePeerName String,
        affirmedServiceconstructInterfaceAaaGroupGtppStatisticsChassisLevelPeerGtppNodeNameNumEchoReqTx ConfdString,
        affirmedServiceconstructInterfaceAaaGroupGtppStatisticsChassisLevelPeerGtppNodeNameNumEchoReqRx ConfdString,
        affirmedServiceconstructInterfaceAaaGroupGtppStatisticsChassisLevelPeerGtppNodeNameNumEchoRespTx ConfdString,
        affirmedServiceconstructInterfaceAaaGroupGtppStatisticsChassisLevelPeerGtppNodeNameNumEchoRespRx ConfdString,
        affirmedServiceconstructInterfaceAaaGroupGtppStatisticsChassisLevelPeerGtppNodeNameNumNodeAliveReqTx ConfdString,
        affirmedServiceconstructInterfaceAaaGroupGtppStatisticsChassisLevelPeerGtppNodeNameNumNodeAliveReqRx ConfdString,
        affirmedServiceconstructInterfaceAaaGroupGtppStatisticsChassisLevelPeerGtppNodeNameNumNodeAliveRespTx ConfdString,
        affirmedServiceconstructInterfaceAaaGroupGtppStatisticsChassisLevelPeerGtppNodeNameNumNodeAliveRespRx ConfdString,
        affirmedServiceconstructInterfaceAaaGroupGtppStatisticsChassisLevelPeerGtppNodeNameNumRedirectionReqRx ConfdString,
        affirmedServiceconstructInterfaceAaaGroupGtppStatisticsChassisLevelPeerGtppNodeNameNumRedirectionRespTx ConfdString,
        affirmedServiceconstructInterfaceAaaGroupGtppStatisticsChassisLevelPeerGtppNodeNameNumDataRecordTransferReqTx ConfdString,
        affirmedServiceconstructInterfaceAaaGroupGtppStatisticsChassisLevelPeerGtppNodeNameNumDataRecordTransferRespRx ConfdString,
        affirmedServiceconstructInterfaceAaaGroupGtppStatisticsChassisLevelPeerGtppNodeNameNumPotentialDupDataRecordRx ConfdString,
        affirmedServiceconstructInterfaceAaaGroupGtppStatisticsChassisLevelPeerGtppNodeNameNumPotentialDupEmptyDataRecordTx ConfdString,
        affirmedServiceconstructInterfaceAaaGroupGtppStatisticsChassisLevelPeerGtppNodeNameNumCancelReqTx ConfdString,
        affirmedServiceconstructInterfaceAaaGroupGtppStatisticsChassisLevelPeerGtppNodeNameNumReleaseReqTx ConfdString,
        affirmedServiceconstructInterfaceAaaGroupGtppStatisticsChassisLevelPeerGtppNodeNameNumReqFulfilledRx ConfdString,
        affirmedServiceconstructInterfaceAaaGroupGtppStatisticsChassisLevelPeerGtppNodeNameNumReqAcceptedRx ConfdString,
        affirmedServiceconstructInterfaceAaaGroupGtppStatisticsChassisLevelPeerGtppNodeNameNumLinkDeclaredAsUPBasedOnDataRecordResponse ConfdString,
        affirmedServiceconstructInterfaceAaaGroupGtppStatisticsChassisLevelPeerGtppNodeNameNumFirstDataRecordTransferReqTx ConfdString
    }

affirmedServiceconstructInterfaceAaaGroupGtppStatisticsChassisLevelPeerGtppNodeNameNodeName OBJECT-TYPE
    SYNTAX      String
    MAX-ACCESS  not-accessible
    STATUS      current
    DESCRIPTION "Local Gtpp Node Name"
    ::= { affirmedServiceconstructInterfaceAaaGroupGtppStatisticsChassisLevelPeerGtppNodeNameEntry 1 }

affirmedServiceconstructInterfaceAaaGroupGtppStatisticsChassisLevelPeerGtppNodeNamePeerName OBJECT-TYPE
    SYNTAX      String
    MAX-ACCESS  not-accessible
    STATUS      current
    DESCRIPTION "Peer name"
    ::= { affirmedServiceconstructInterfaceAaaGroupGtppStatisticsChassisLevelPeerGtppNodeNameEntry 2 }

affirmedServiceconstructInterfaceAaaGroupGtppStatisticsChassisLevelPeerGtppNodeNameNumEchoReqTx OBJECT-TYPE
    SYNTAX      ConfdString
    MAX-ACCESS  read-only
    STATUS      current
    DESCRIPTION "Number of Echo Request messages transmitted"
    ::= { affirmedServiceconstructInterfaceAaaGroupGtppStatisticsChassisLevelPeerGtppNodeNameEntry 3 }

affirmedServiceconstructInterfaceAaaGroupGtppStatisticsChassisLevelPeerGtppNodeNameNumEchoReqRx OBJECT-TYPE
    SYNTAX      ConfdString
    MAX-ACCESS  read-only
    STATUS      current
    DESCRIPTION "Number of Echo Request messages received"
    ::= { affirmedServiceconstructInterfaceAaaGroupGtppStatisticsChassisLevelPeerGtppNodeNameEntry 4 }

affirmedServiceconstructInterfaceAaaGroupGtppStatisticsChassisLevelPeerGtppNodeNameNumEchoRespTx OBJECT-TYPE
    SYNTAX      ConfdString
    MAX-ACCESS  read-only
    STATUS      current
    DESCRIPTION "Number of Echo Response messages transmitted"
    ::= { affirmedServiceconstructInterfaceAaaGroupGtppStatisticsChassisLevelPeerGtppNodeNameEntry 5 }

affirmedServiceconstructInterfaceAaaGroupGtppStatisticsChassisLevelPeerGtppNodeNameNumEchoRespRx OBJECT-TYPE
    SYNTAX      ConfdString
    MAX-ACCESS  read-only
    STATUS      current
    DESCRIPTION "Number of Echo Response messages received"
    ::= { affirmedServiceconstructInterfaceAaaGroupGtppStatisticsChassisLevelPeerGtppNodeNameEntry 6 }

affirmedServiceconstructInterfaceAaaGroupGtppStatisticsChassisLevelPeerGtppNodeNameNumNodeAliveReqTx OBJECT-TYPE
    SYNTAX      ConfdString
    MAX-ACCESS  read-only
    STATUS      current
    DESCRIPTION "Number of Node Alive Request messages transmitted"
    ::= { affirmedServiceconstructInterfaceAaaGroupGtppStatisticsChassisLevelPeerGtppNodeNameEntry 7 }

affirmedServiceconstructInterfaceAaaGroupGtppStatisticsChassisLevelPeerGtppNodeNameNumNodeAliveReqRx OBJECT-TYPE
    SYNTAX      ConfdString
    MAX-ACCESS  read-only
    STATUS      current
    DESCRIPTION "Number of Node Alive Request messages received"
    ::= { affirmedServiceconstructInterfaceAaaGroupGtppStatisticsChassisLevelPeerGtppNodeNameEntry 8 }

affirmedServiceconstructInterfaceAaaGroupGtppStatisticsChassisLevelPeerGtppNodeNameNumNodeAliveRespTx OBJECT-TYPE
    SYNTAX      ConfdString
    MAX-ACCESS  read-only
    STATUS      current
    DESCRIPTION "Number of Node Aive Response messages transmitted"
    ::= { affirmedServiceconstructInterfaceAaaGroupGtppStatisticsChassisLevelPeerGtppNodeNameEntry 9 }

affirmedServiceconstructInterfaceAaaGroupGtppStatisticsChassisLevelPeerGtppNodeNameNumNodeAliveRespRx OBJECT-TYPE
    SYNTAX      ConfdString
    MAX-ACCESS  read-only
    STATUS      current
    DESCRIPTION "Number of Node Alive Response messages received"
    ::= { affirmedServiceconstructInterfaceAaaGroupGtppStatisticsChassisLevelPeerGtppNodeNameEntry 10 }

affirmedServiceconstructInterfaceAaaGroupGtppStatisticsChassisLevelPeerGtppNodeNameNumRedirectionReqRx OBJECT-TYPE
    SYNTAX      ConfdString
    MAX-ACCESS  read-only
    STATUS      current
    DESCRIPTION "Number of Redirection Request messages received"
    ::= { affirmedServiceconstructInterfaceAaaGroupGtppStatisticsChassisLevelPeerGtppNodeNameEntry 11 }

affirmedServiceconstructInterfaceAaaGroupGtppStatisticsChassisLevelPeerGtppNodeNameNumRedirectionRespTx OBJECT-TYPE
    SYNTAX      ConfdString
    MAX-ACCESS  read-only
    STATUS      current
    DESCRIPTION "Number of Redirection Response messages transmitted"
    ::= { affirmedServiceconstructInterfaceAaaGroupGtppStatisticsChassisLevelPeerGtppNodeNameEntry 12 }

affirmedServiceconstructInterfaceAaaGroupGtppStatisticsChassisLevelPeerGtppNodeNameNumDataRecordTransferReqTx OBJECT-TYPE
    SYNTAX      ConfdString
    MAX-ACCESS  read-only
    STATUS      current
    DESCRIPTION "Number of Data Record Transfer Request messages transmitted"
    ::= { affirmedServiceconstructInterfaceAaaGroupGtppStatisticsChassisLevelPeerGtppNodeNameEntry 13 }

affirmedServiceconstructInterfaceAaaGroupGtppStatisticsChassisLevelPeerGtppNodeNameNumDataRecordTransferRespRx OBJECT-TYPE
    SYNTAX      ConfdString
    MAX-ACCESS  read-only
    STATUS      current
    DESCRIPTION "Number of Data Record Transfer Response messages received"
    ::= { affirmedServiceconstructInterfaceAaaGroupGtppStatisticsChassisLevelPeerGtppNodeNameEntry 14 }

affirmedServiceconstructInterfaceAaaGroupGtppStatisticsChassisLevelPeerGtppNodeNameNumPotentialDupDataRecordRx OBJECT-TYPE
    SYNTAX      ConfdString
    MAX-ACCESS  read-only
    STATUS      current
    DESCRIPTION "Number of Potential Duplicate Data Records received"
    ::= { affirmedServiceconstructInterfaceAaaGroupGtppStatisticsChassisLevelPeerGtppNodeNameEntry 15 }

affirmedServiceconstructInterfaceAaaGroupGtppStatisticsChassisLevelPeerGtppNodeNameNumPotentialDupEmptyDataRecordTx OBJECT-TYPE
    SYNTAX      ConfdString
    MAX-ACCESS  read-only
    STATUS      current
    DESCRIPTION "Number of Potential Duplicate Empty Data Record packets transmitted"
    ::= { affirmedServiceconstructInterfaceAaaGroupGtppStatisticsChassisLevelPeerGtppNodeNameEntry 16 }

affirmedServiceconstructInterfaceAaaGroupGtppStatisticsChassisLevelPeerGtppNodeNameNumCancelReqTx OBJECT-TYPE
    SYNTAX      ConfdString
    MAX-ACCESS  read-only
    STATUS      current
    DESCRIPTION "Number of Cancel Request messages received"
    ::= { affirmedServiceconstructInterfaceAaaGroupGtppStatisticsChassisLevelPeerGtppNodeNameEntry 17 }

affirmedServiceconstructInterfaceAaaGroupGtppStatisticsChassisLevelPeerGtppNodeNameNumReleaseReqTx OBJECT-TYPE
    SYNTAX      ConfdString
    MAX-ACCESS  read-only
    STATUS      current
    DESCRIPTION "Number of Release Request messages received"
    ::= { affirmedServiceconstructInterfaceAaaGroupGtppStatisticsChassisLevelPeerGtppNodeNameEntry 18 }

affirmedServiceconstructInterfaceAaaGroupGtppStatisticsChassisLevelPeerGtppNodeNameNumReqFulfilledRx OBJECT-TYPE
    SYNTAX      ConfdString
    MAX-ACCESS  read-only
    STATUS      current
    DESCRIPTION "Number of Request Fulfilled messages received"
    ::= { affirmedServiceconstructInterfaceAaaGroupGtppStatisticsChassisLevelPeerGtppNodeNameEntry 19 }

affirmedServiceconstructInterfaceAaaGroupGtppStatisticsChassisLevelPeerGtppNodeNameNumReqAcceptedRx OBJECT-TYPE
    SYNTAX      ConfdString
    MAX-ACCESS  read-only
    STATUS      current
    DESCRIPTION "Number of Request Accepted messages received"
    ::= { affirmedServiceconstructInterfaceAaaGroupGtppStatisticsChassisLevelPeerGtppNodeNameEntry 20 }

affirmedServiceconstructInterfaceAaaGroupGtppStatisticsChassisLevelPeerGtppNodeNameNumLinkDeclaredAsUPBasedOnDataRecordResponse OBJECT-TYPE
    SYNTAX      ConfdString
    MAX-ACCESS  read-only
    STATUS      current
    DESCRIPTION "Number of times Link declared UP on Data Record Response"
    ::= { affirmedServiceconstructInterfaceAaaGroupGtppStatisticsChassisLevelPeerGtppNodeNameEntry 21 }

affirmedServiceconstructInterfaceAaaGroupGtppStatisticsChassisLevelPeerGtppNodeNameNumFirstDataRecordTransferReqTx OBJECT-TYPE
    SYNTAX      ConfdString
    MAX-ACCESS  read-only
    STATUS      current
    DESCRIPTION "First Interim Data Record Request for a session transmitted"
    ::= { affirmedServiceconstructInterfaceAaaGroupGtppStatisticsChassisLevelPeerGtppNodeNameEntry 22 }

affirmedServiceconstructInterfaceAaaGroupGtppNodeStatusTable OBJECT-TYPE
    SYNTAX      SEQUENCE OF AffirmedServiceconstructInterfaceAaaGroupGtppNodeStatusEntry
    MAX-ACCESS  not-accessible
    STATUS      current
    DESCRIPTION ""
    ::= { affirmedServiceconstructInterfaceAaaGroupGtpp 1 }

affirmedServiceconstructInterfaceAaaGroupGtppNodeStatusEntry OBJECT-TYPE
    SYNTAX      AffirmedServiceconstructInterfaceAaaGroupGtppNodeStatusEntry
    MAX-ACCESS  not-accessible
    STATUS      current
    DESCRIPTION ""
    INDEX { affirmedServiceconstructInterfaceAaaGroupGtppNodeStatusName }
        ::= { affirmedServiceconstructInterfaceAaaGroupGtppNodeStatusTable 1 }

AffirmedServiceconstructInterfaceAaaGroupGtppNodeStatusEntry ::=
    SEQUENCE {
        affirmedServiceconstructInterfaceAaaGroupGtppNodeStatusName String,
        affirmedServiceconstructInterfaceAaaGroupGtppNodeStatusAdminstatus INTEGER,
        affirmedServiceconstructInterfaceAaaGroupGtppNodeStatusOperstatus INTEGER,
        affirmedServiceconstructInterfaceAaaGroupGtppNodeStatusOperReason String,
        affirmedServiceconstructInterfaceAaaGroupGtppNodeStatusHostPort Unsigned32,
        affirmedServiceconstructInterfaceAaaGroupGtppNodeStatusHostIpAddress String,
        affirmedServiceconstructInterfaceAaaGroupGtppNodeStatusDroppedPackets Unsigned32,
        affirmedServiceconstructInterfaceAaaGroupGtppNodeStatusDuplicatePackets Unsigned32,
        affirmedServiceconstructInterfaceAaaGroupGtppNodeStatusSeqOverRun Unsigned32
    }

affirmedServiceconstructInterfaceAaaGroupGtppNodeStatusName OBJECT-TYPE
    SYNTAX      String
    MAX-ACCESS  not-accessible
    STATUS      current
    DESCRIPTION "Gtpp Server Group Name"
    ::= { affirmedServiceconstructInterfaceAaaGroupGtppNodeStatusEntry 1 }

affirmedServiceconstructInterfaceAaaGroupGtppNodeStatusAdminstatus OBJECT-TYPE
    SYNTAX      INTEGER {disabled(0),enabled(1)}
    MAX-ACCESS  read-only
    STATUS      current
    DESCRIPTION "Admin status of Gtpp Server Group"
    ::= { affirmedServiceconstructInterfaceAaaGroupGtppNodeStatusEntry 2 }

affirmedServiceconstructInterfaceAaaGroupGtppNodeStatusOperstatus OBJECT-TYPE
    SYNTAX      INTEGER {outofservice(0),inservice(1)}
    MAX-ACCESS  read-only
    STATUS      current
    DESCRIPTION "Oper status of Gtpp Server Group"
    ::= { affirmedServiceconstructInterfaceAaaGroupGtppNodeStatusEntry 3 }

affirmedServiceconstructInterfaceAaaGroupGtppNodeStatusOperReason OBJECT-TYPE
    SYNTAX      String
    MAX-ACCESS  read-only
    STATUS      current
    DESCRIPTION "Operational Reason if state is not Operationally Up"
    ::= { affirmedServiceconstructInterfaceAaaGroupGtppNodeStatusEntry 4 }

affirmedServiceconstructInterfaceAaaGroupGtppNodeStatusHostPort OBJECT-TYPE
    SYNTAX      Unsigned32
    MAX-ACCESS  read-only
    STATUS      current
    DESCRIPTION "Server group local port number"
    ::= { affirmedServiceconstructInterfaceAaaGroupGtppNodeStatusEntry 5 }

affirmedServiceconstructInterfaceAaaGroupGtppNodeStatusHostIpAddress OBJECT-TYPE
    SYNTAX      String
    MAX-ACCESS  read-only
    STATUS      current
    DESCRIPTION "Server group host IP Address"
    ::= { affirmedServiceconstructInterfaceAaaGroupGtppNodeStatusEntry 6 }

affirmedServiceconstructInterfaceAaaGroupGtppNodeStatusDroppedPackets OBJECT-TYPE
    SYNTAX      Unsigned32
    MAX-ACCESS  read-only
    STATUS      current
    DESCRIPTION "number of dropped packets "
    ::= { affirmedServiceconstructInterfaceAaaGroupGtppNodeStatusEntry 7 }

affirmedServiceconstructInterfaceAaaGroupGtppNodeStatusDuplicatePackets OBJECT-TYPE
    SYNTAX      Unsigned32
    MAX-ACCESS  read-only
    STATUS      current
    DESCRIPTION "number of duplicate packets"
    ::= { affirmedServiceconstructInterfaceAaaGroupGtppNodeStatusEntry 8 }

affirmedServiceconstructInterfaceAaaGroupGtppNodeStatusSeqOverRun OBJECT-TYPE
    SYNTAX      Unsigned32
    MAX-ACCESS  read-only
    STATUS      current
    DESCRIPTION "number of packets with duplicate sequence numbers"
    ::= { affirmedServiceconstructInterfaceAaaGroupGtppNodeStatusEntry 9 }

affirmedServiceconstructInterfaceAaaGroupGtppPeerStatusTable OBJECT-TYPE
    SYNTAX      SEQUENCE OF AffirmedServiceconstructInterfaceAaaGroupGtppPeerStatusEntry
    MAX-ACCESS  not-accessible
    STATUS      current
    DESCRIPTION ""
    ::= { affirmedServiceconstructInterfaceAaaGroupGtpp 2 }

affirmedServiceconstructInterfaceAaaGroupGtppPeerStatusEntry OBJECT-TYPE
    SYNTAX      AffirmedServiceconstructInterfaceAaaGroupGtppPeerStatusEntry
    MAX-ACCESS  not-accessible
    STATUS      current
    DESCRIPTION ""
    INDEX { affirmedServiceconstructInterfaceAaaGroupGtppPeerStatusName, affirmedServiceconstructInterfaceAaaGroupGtppPeerStatusPeerName }
        ::= { affirmedServiceconstructInterfaceAaaGroupGtppPeerStatusTable 1 }

AffirmedServiceconstructInterfaceAaaGroupGtppPeerStatusEntry ::=
    SEQUENCE {
        affirmedServiceconstructInterfaceAaaGroupGtppPeerStatusName String,
        affirmedServiceconstructInterfaceAaaGroupGtppPeerStatusPeerName String,
        affirmedServiceconstructInterfaceAaaGroupGtppPeerStatusIpAddress String,
        affirmedServiceconstructInterfaceAaaGroupGtppPeerStatusPort Unsigned32,
        affirmedServiceconstructInterfaceAaaGroupGtppPeerStatusTransport INTEGER,
        affirmedServiceconstructInterfaceAaaGroupGtppPeerStatusRole INTEGER,
        affirmedServiceconstructInterfaceAaaGroupGtppPeerStatusAdminstatus INTEGER,
        affirmedServiceconstructInterfaceAaaGroupGtppPeerStatusOperstatus INTEGER,
        affirmedServiceconstructInterfaceAaaGroupGtppPeerStatusDataRecordRetryCount Unsigned32,
        affirmedServiceconstructInterfaceAaaGroupGtppPeerStatusDataRecordRespTimeout Unsigned32,
        affirmedServiceconstructInterfaceAaaGroupGtppPeerStatusEchoRetryCount Unsigned32,
        affirmedServiceconstructInterfaceAaaGroupGtppPeerStatusEchoRespTimer Unsigned32,
        affirmedServiceconstructInterfaceAaaGroupGtppPeerStatusPeriodicHealthCheckTimer Unsigned32,
        affirmedServiceconstructInterfaceAaaGroupGtppPeerStatusDataRecordResponseAsEchoSuccess INTEGER
    }

affirmedServiceconstructInterfaceAaaGroupGtppPeerStatusName OBJECT-TYPE
    SYNTAX      String
    MAX-ACCESS  not-accessible
    STATUS      current
    DESCRIPTION "Local Gtpp Node Name"
    ::= { affirmedServiceconstructInterfaceAaaGroupGtppPeerStatusEntry 1 }

affirmedServiceconstructInterfaceAaaGroupGtppPeerStatusPeerName OBJECT-TYPE
    SYNTAX      String
    MAX-ACCESS  not-accessible
    STATUS      current
    DESCRIPTION "Peer host name FQDN"
    ::= { affirmedServiceconstructInterfaceAaaGroupGtppPeerStatusEntry 2 }

affirmedServiceconstructInterfaceAaaGroupGtppPeerStatusIpAddress OBJECT-TYPE
    SYNTAX      String
    MAX-ACCESS  read-only
    STATUS      current
    DESCRIPTION "Address of Peer"
    ::= { affirmedServiceconstructInterfaceAaaGroupGtppPeerStatusEntry 3 }

affirmedServiceconstructInterfaceAaaGroupGtppPeerStatusPort OBJECT-TYPE
    SYNTAX      Unsigned32
    MAX-ACCESS  read-only
    STATUS      current
    DESCRIPTION "peer port number"
    ::= { affirmedServiceconstructInterfaceAaaGroupGtppPeerStatusEntry 4 }

affirmedServiceconstructInterfaceAaaGroupGtppPeerStatusTransport OBJECT-TYPE
    SYNTAX      INTEGER {udp(0),tcp(1)}
    MAX-ACCESS  read-only
    STATUS      current
    DESCRIPTION "transport type"
    ::= { affirmedServiceconstructInterfaceAaaGroupGtppPeerStatusEntry 5 }

affirmedServiceconstructInterfaceAaaGroupGtppPeerStatusRole OBJECT-TYPE
    SYNTAX      INTEGER {secondary(0),primary(1)}
    MAX-ACCESS  read-only
    STATUS      current
    DESCRIPTION "primary or secondary"
    ::= { affirmedServiceconstructInterfaceAaaGroupGtppPeerStatusEntry 6 }

affirmedServiceconstructInterfaceAaaGroupGtppPeerStatusAdminstatus OBJECT-TYPE
    SYNTAX      INTEGER {disabled(0),enabled(1)}
    MAX-ACCESS  read-only
    STATUS      current
    DESCRIPTION "Peer node admin status"
    ::= { affirmedServiceconstructInterfaceAaaGroupGtppPeerStatusEntry 7 }

affirmedServiceconstructInterfaceAaaGroupGtppPeerStatusOperstatus OBJECT-TYPE
    SYNTAX      INTEGER {initial(0),okay(1),active(2),down(3),reopen(4)}
    MAX-ACCESS  read-only
    STATUS      current
    DESCRIPTION "Peer node operational status"
    ::= { affirmedServiceconstructInterfaceAaaGroupGtppPeerStatusEntry 8 }

affirmedServiceconstructInterfaceAaaGroupGtppPeerStatusDataRecordRetryCount OBJECT-TYPE
    SYNTAX      Unsigned32
    MAX-ACCESS  read-only
    STATUS      current
    DESCRIPTION "Max number of retries for sending data record"
    ::= { affirmedServiceconstructInterfaceAaaGroupGtppPeerStatusEntry 9 }

affirmedServiceconstructInterfaceAaaGroupGtppPeerStatusDataRecordRespTimeout OBJECT-TYPE
    SYNTAX      Unsigned32
    MAX-ACCESS  read-only
    STATUS      current
    DESCRIPTION "Data record response timeout value in seconds"
    ::= { affirmedServiceconstructInterfaceAaaGroupGtppPeerStatusEntry 10 }

affirmedServiceconstructInterfaceAaaGroupGtppPeerStatusEchoRetryCount OBJECT-TYPE
    SYNTAX      Unsigned32
    MAX-ACCESS  read-only
    STATUS      current
    DESCRIPTION "Max number of echo request attempts"
    ::= { affirmedServiceconstructInterfaceAaaGroupGtppPeerStatusEntry 11 }

affirmedServiceconstructInterfaceAaaGroupGtppPeerStatusEchoRespTimer OBJECT-TYPE
    SYNTAX      Unsigned32
    MAX-ACCESS  read-only
    STATUS      current
    DESCRIPTION "Echo response timeout value in seconds"
    ::= { affirmedServiceconstructInterfaceAaaGroupGtppPeerStatusEntry 12 }

affirmedServiceconstructInterfaceAaaGroupGtppPeerStatusPeriodicHealthCheckTimer OBJECT-TYPE
    SYNTAX      Unsigned32
    MAX-ACCESS  read-only
    STATUS      current
    DESCRIPTION "Periodic health check interval value in seconds"
    ::= { affirmedServiceconstructInterfaceAaaGroupGtppPeerStatusEntry 13 }

affirmedServiceconstructInterfaceAaaGroupGtppPeerStatusDataRecordResponseAsEchoSuccess OBJECT-TYPE
    SYNTAX      INTEGER {disabled(0),enabled(1)}
    MAX-ACCESS  read-only
    STATUS      current
    DESCRIPTION "Data Record Response also served as Echo Response Success"
    ::= { affirmedServiceconstructInterfaceAaaGroupGtppPeerStatusEntry 14 }

affirmedServiceconstructInterfaceAaaGroupGtppPeerStatsTable OBJECT-TYPE
    SYNTAX      SEQUENCE OF AffirmedServiceconstructInterfaceAaaGroupGtppPeerStatsEntry
    MAX-ACCESS  not-accessible
    STATUS      current
    DESCRIPTION ""
    ::= { affirmedServiceconstructInterfaceAaaGroupGtpp 3 }

affirmedServiceconstructInterfaceAaaGroupGtppPeerStatsEntry OBJECT-TYPE
    SYNTAX      AffirmedServiceconstructInterfaceAaaGroupGtppPeerStatsEntry
    MAX-ACCESS  not-accessible
    STATUS      current
    DESCRIPTION ""
    INDEX { affirmedServiceconstructInterfaceAaaGroupGtppPeerStatsName, affirmedServiceconstructInterfaceAaaGroupGtppPeerStatsPeerName }
        ::= { affirmedServiceconstructInterfaceAaaGroupGtppPeerStatsTable 1 }

AffirmedServiceconstructInterfaceAaaGroupGtppPeerStatsEntry ::=
    SEQUENCE {
        affirmedServiceconstructInterfaceAaaGroupGtppPeerStatsName String,
        affirmedServiceconstructInterfaceAaaGroupGtppPeerStatsPeerName String,
        affirmedServiceconstructInterfaceAaaGroupGtppPeerStatsNumOfProtocolError ConfdString,
        affirmedServiceconstructInterfaceAaaGroupGtppPeerStatsNumOfPermanentFailure ConfdString,
        affirmedServiceconstructInterfaceAaaGroupGtppPeerStatsNumOfRoutingFailure ConfdString,
        affirmedServiceconstructInterfaceAaaGroupGtppPeerStatsNumOfOutRequest ConfdString,
        affirmedServiceconstructInterfaceAaaGroupGtppPeerStatsNumOfOutResponse ConfdString,
        affirmedServiceconstructInterfaceAaaGroupGtppPeerStatsNumOfInRequest ConfdString,
        affirmedServiceconstructInterfaceAaaGroupGtppPeerStatsNumOfInResponse ConfdString,
        affirmedServiceconstructInterfaceAaaGroupGtppPeerStatsNumOfLinkBounces ConfdString,
        affirmedServiceconstructInterfaceAaaGroupGtppPeerStatsNumOfPacerNoCreditFailure ConfdString,
        affirmedServiceconstructInterfaceAaaGroupGtppPeerStatsPacerHighWaterMark ConfdString
    }

affirmedServiceconstructInterfaceAaaGroupGtppPeerStatsName OBJECT-TYPE
    SYNTAX      String
    MAX-ACCESS  not-accessible
    STATUS      current
    DESCRIPTION "Local Gtpp Node Name"
    ::= { affirmedServiceconstructInterfaceAaaGroupGtppPeerStatsEntry 1 }

affirmedServiceconstructInterfaceAaaGroupGtppPeerStatsPeerName OBJECT-TYPE
    SYNTAX      String
    MAX-ACCESS  not-accessible
    STATUS      current
    DESCRIPTION "Peer host name"
    ::= { affirmedServiceconstructInterfaceAaaGroupGtppPeerStatsEntry 2 }

affirmedServiceconstructInterfaceAaaGroupGtppPeerStatsNumOfProtocolError OBJECT-TYPE
    SYNTAX      ConfdString
    MAX-ACCESS  read-only
    STATUS      current
    DESCRIPTION "total number of protocol errors"
    ::= { affirmedServiceconstructInterfaceAaaGroupGtppPeerStatsEntry 3 }

affirmedServiceconstructInterfaceAaaGroupGtppPeerStatsNumOfPermanentFailure OBJECT-TYPE
    SYNTAX      ConfdString
    MAX-ACCESS  read-only
    STATUS      current
    DESCRIPTION "total number of request failure to the peer"
    ::= { affirmedServiceconstructInterfaceAaaGroupGtppPeerStatsEntry 4 }

affirmedServiceconstructInterfaceAaaGroupGtppPeerStatsNumOfRoutingFailure OBJECT-TYPE
    SYNTAX      ConfdString
    MAX-ACCESS  read-only
    STATUS      current
    DESCRIPTION "total number of routing failure to the peer"
    ::= { affirmedServiceconstructInterfaceAaaGroupGtppPeerStatsEntry 5 }

affirmedServiceconstructInterfaceAaaGroupGtppPeerStatsNumOfOutRequest OBJECT-TYPE
    SYNTAX      ConfdString
    MAX-ACCESS  read-only
    STATUS      current
    DESCRIPTION "total number of requests sent to the peer"
    ::= { affirmedServiceconstructInterfaceAaaGroupGtppPeerStatsEntry 6 }

affirmedServiceconstructInterfaceAaaGroupGtppPeerStatsNumOfOutResponse OBJECT-TYPE
    SYNTAX      ConfdString
    MAX-ACCESS  read-only
    STATUS      current
    DESCRIPTION "total number of responses sent to the peer"
    ::= { affirmedServiceconstructInterfaceAaaGroupGtppPeerStatsEntry 7 }

affirmedServiceconstructInterfaceAaaGroupGtppPeerStatsNumOfInRequest OBJECT-TYPE
    SYNTAX      ConfdString
    MAX-ACCESS  read-only
    STATUS      current
    DESCRIPTION "total number of requests received from the peer"
    ::= { affirmedServiceconstructInterfaceAaaGroupGtppPeerStatsEntry 8 }

affirmedServiceconstructInterfaceAaaGroupGtppPeerStatsNumOfInResponse OBJECT-TYPE
    SYNTAX      ConfdString
    MAX-ACCESS  read-only
    STATUS      current
    DESCRIPTION "total number of responses received from the peer"
    ::= { affirmedServiceconstructInterfaceAaaGroupGtppPeerStatsEntry 9 }

affirmedServiceconstructInterfaceAaaGroupGtppPeerStatsNumOfLinkBounces OBJECT-TYPE
    SYNTAX      ConfdString
    MAX-ACCESS  read-only
    STATUS      current
    DESCRIPTION "total number of times link is bounced"
    ::= { affirmedServiceconstructInterfaceAaaGroupGtppPeerStatsEntry 10 }

affirmedServiceconstructInterfaceAaaGroupGtppPeerStatsNumOfPacerNoCreditFailure OBJECT-TYPE
    SYNTAX      ConfdString
    MAX-ACCESS  read-only
    STATUS      current
    DESCRIPTION "total number of request failed due to no credit available at pacer"
    ::= { affirmedServiceconstructInterfaceAaaGroupGtppPeerStatsEntry 11 }

affirmedServiceconstructInterfaceAaaGroupGtppPeerStatsPacerHighWaterMark OBJECT-TYPE
    SYNTAX      ConfdString
    MAX-ACCESS  read-only
    STATUS      current
    DESCRIPTION "highest number of pacer credits requested across all intervals"
    ::= { affirmedServiceconstructInterfaceAaaGroupGtppPeerStatsEntry 12 }

affirmedServiceconstructInterfaceAaaGroupGtppPeerCmdStatsTable OBJECT-TYPE
    SYNTAX      SEQUENCE OF AffirmedServiceconstructInterfaceAaaGroupGtppPeerCmdStatsEntry
    MAX-ACCESS  not-accessible
    STATUS      current
    DESCRIPTION ""
    ::= { affirmedServiceconstructInterfaceAaaGroupGtpp 4 }

affirmedServiceconstructInterfaceAaaGroupGtppPeerCmdStatsEntry OBJECT-TYPE
    SYNTAX      AffirmedServiceconstructInterfaceAaaGroupGtppPeerCmdStatsEntry
    MAX-ACCESS  not-accessible
    STATUS      current
    DESCRIPTION ""
    INDEX { affirmedServiceconstructInterfaceAaaGroupGtppPeerCmdStatsName, affirmedServiceconstructInterfaceAaaGroupGtppPeerCmdStatsPeerName }
        ::= { affirmedServiceconstructInterfaceAaaGroupGtppPeerCmdStatsTable 1 }

AffirmedServiceconstructInterfaceAaaGroupGtppPeerCmdStatsEntry ::=
    SEQUENCE {
        affirmedServiceconstructInterfaceAaaGroupGtppPeerCmdStatsName String,
        affirmedServiceconstructInterfaceAaaGroupGtppPeerCmdStatsPeerName String,
        affirmedServiceconstructInterfaceAaaGroupGtppPeerCmdStatsNumTxEchoReq ConfdString,
        affirmedServiceconstructInterfaceAaaGroupGtppPeerCmdStatsNumRxEchoResp ConfdString,
        affirmedServiceconstructInterfaceAaaGroupGtppPeerCmdStatsNumRxEchoReq ConfdString,
        affirmedServiceconstructInterfaceAaaGroupGtppPeerCmdStatsNumTxEchoResp ConfdString,
        affirmedServiceconstructInterfaceAaaGroupGtppPeerCmdStatsNumTxNodeAliveReq ConfdString,
        affirmedServiceconstructInterfaceAaaGroupGtppPeerCmdStatsNumRxNodeAliveResp ConfdString,
        affirmedServiceconstructInterfaceAaaGroupGtppPeerCmdStatsNumRxNodeAliveReq ConfdString,
        affirmedServiceconstructInterfaceAaaGroupGtppPeerCmdStatsNumTxNodeAliveResp ConfdString,
        affirmedServiceconstructInterfaceAaaGroupGtppPeerCmdStatsNumTxDataRecordTransferReq ConfdString,
        affirmedServiceconstructInterfaceAaaGroupGtppPeerCmdStatsNumRxDataRecordTransferResp ConfdString,
        affirmedServiceconstructInterfaceAaaGroupGtppPeerCmdStatsNumRxRedirectionReq ConfdString,
        affirmedServiceconstructInterfaceAaaGroupGtppPeerCmdStatsNumTxRedirectionResp ConfdString,
        affirmedServiceconstructInterfaceAaaGroupGtppPeerCmdStatsNumTxPdDataRecordTransferReq ConfdString,
        affirmedServiceconstructInterfaceAaaGroupGtppPeerCmdStatsNumTxPdEmptyDataRecordTransferReq ConfdString,
        affirmedServiceconstructInterfaceAaaGroupGtppPeerCmdStatsNumTxCancelReq ConfdString,
        affirmedServiceconstructInterfaceAaaGroupGtppPeerCmdStatsNumTxReleaseReq ConfdString,
        affirmedServiceconstructInterfaceAaaGroupGtppPeerCmdStatsNumRxPdDataRecordTransferResp ConfdString,
        affirmedServiceconstructInterfaceAaaGroupGtppPeerCmdStatsNumRxReqAccepted ConfdString,
        affirmedServiceconstructInterfaceAaaGroupGtppPeerCmdStatsNumRxReqFulfilled ConfdString
    }

affirmedServiceconstructInterfaceAaaGroupGtppPeerCmdStatsName OBJECT-TYPE
    SYNTAX      String
    MAX-ACCESS  not-accessible
    STATUS      current
    DESCRIPTION "Local Gtpp Node Name"
    ::= { affirmedServiceconstructInterfaceAaaGroupGtppPeerCmdStatsEntry 1 }

affirmedServiceconstructInterfaceAaaGroupGtppPeerCmdStatsPeerName OBJECT-TYPE
    SYNTAX      String
    MAX-ACCESS  not-accessible
    STATUS      current
    DESCRIPTION "Peer host name"
    ::= { affirmedServiceconstructInterfaceAaaGroupGtppPeerCmdStatsEntry 2 }

affirmedServiceconstructInterfaceAaaGroupGtppPeerCmdStatsNumTxEchoReq OBJECT-TYPE
    SYNTAX      ConfdString
    MAX-ACCESS  read-only
    STATUS      current
    DESCRIPTION "Echo Requests transmitted"
    ::= { affirmedServiceconstructInterfaceAaaGroupGtppPeerCmdStatsEntry 3 }

affirmedServiceconstructInterfaceAaaGroupGtppPeerCmdStatsNumRxEchoResp OBJECT-TYPE
    SYNTAX      ConfdString
    MAX-ACCESS  read-only
    STATUS      current
    DESCRIPTION "Echo Response received"
    ::= { affirmedServiceconstructInterfaceAaaGroupGtppPeerCmdStatsEntry 4 }

affirmedServiceconstructInterfaceAaaGroupGtppPeerCmdStatsNumRxEchoReq OBJECT-TYPE
    SYNTAX      ConfdString
    MAX-ACCESS  read-only
    STATUS      current
    DESCRIPTION "Echo Requests received"
    ::= { affirmedServiceconstructInterfaceAaaGroupGtppPeerCmdStatsEntry 5 }

affirmedServiceconstructInterfaceAaaGroupGtppPeerCmdStatsNumTxEchoResp OBJECT-TYPE
    SYNTAX      ConfdString
    MAX-ACCESS  read-only
    STATUS      current
    DESCRIPTION "Echo Response transmitted"
    ::= { affirmedServiceconstructInterfaceAaaGroupGtppPeerCmdStatsEntry 6 }

affirmedServiceconstructInterfaceAaaGroupGtppPeerCmdStatsNumTxNodeAliveReq OBJECT-TYPE
    SYNTAX      ConfdString
    MAX-ACCESS  read-only
    STATUS      current
    DESCRIPTION "NodeAlive Requests transmitted"
    ::= { affirmedServiceconstructInterfaceAaaGroupGtppPeerCmdStatsEntry 7 }

affirmedServiceconstructInterfaceAaaGroupGtppPeerCmdStatsNumRxNodeAliveResp OBJECT-TYPE
    SYNTAX      ConfdString
    MAX-ACCESS  read-only
    STATUS      current
    DESCRIPTION "Node Alive Request received"
    ::= { affirmedServiceconstructInterfaceAaaGroupGtppPeerCmdStatsEntry 8 }

affirmedServiceconstructInterfaceAaaGroupGtppPeerCmdStatsNumRxNodeAliveReq OBJECT-TYPE
    SYNTAX      ConfdString
    MAX-ACCESS  read-only
    STATUS      current
    DESCRIPTION "Node Alive Request received"
    ::= { affirmedServiceconstructInterfaceAaaGroupGtppPeerCmdStatsEntry 9 }

affirmedServiceconstructInterfaceAaaGroupGtppPeerCmdStatsNumTxNodeAliveResp OBJECT-TYPE
    SYNTAX      ConfdString
    MAX-ACCESS  read-only
    STATUS      current
    DESCRIPTION "Node Alive Response transmitted"
    ::= { affirmedServiceconstructInterfaceAaaGroupGtppPeerCmdStatsEntry 10 }

affirmedServiceconstructInterfaceAaaGroupGtppPeerCmdStatsNumTxDataRecordTransferReq OBJECT-TYPE
    SYNTAX      ConfdString
    MAX-ACCESS  read-only
    STATUS      current
    DESCRIPTION "Data Record Request transmitted"
    ::= { affirmedServiceconstructInterfaceAaaGroupGtppPeerCmdStatsEntry 11 }

affirmedServiceconstructInterfaceAaaGroupGtppPeerCmdStatsNumRxDataRecordTransferResp OBJECT-TYPE
    SYNTAX      ConfdString
    MAX-ACCESS  read-only
    STATUS      current
    DESCRIPTION "Data Record Response received"
    ::= { affirmedServiceconstructInterfaceAaaGroupGtppPeerCmdStatsEntry 12 }

affirmedServiceconstructInterfaceAaaGroupGtppPeerCmdStatsNumRxRedirectionReq OBJECT-TYPE
    SYNTAX      ConfdString
    MAX-ACCESS  read-only
    STATUS      current
    DESCRIPTION "Redirection Request received"
    ::= { affirmedServiceconstructInterfaceAaaGroupGtppPeerCmdStatsEntry 13 }

affirmedServiceconstructInterfaceAaaGroupGtppPeerCmdStatsNumTxRedirectionResp OBJECT-TYPE
    SYNTAX      ConfdString
    MAX-ACCESS  read-only
    STATUS      current
    DESCRIPTION "Redirection Response transmitted"
    ::= { affirmedServiceconstructInterfaceAaaGroupGtppPeerCmdStatsEntry 14 }

affirmedServiceconstructInterfaceAaaGroupGtppPeerCmdStatsNumTxPdDataRecordTransferReq OBJECT-TYPE
    SYNTAX      ConfdString
    MAX-ACCESS  read-only
    STATUS      current
    DESCRIPTION "Potential-Duplicate-Rec-Transmitted "
    ::= { affirmedServiceconstructInterfaceAaaGroupGtppPeerCmdStatsEntry 15 }

affirmedServiceconstructInterfaceAaaGroupGtppPeerCmdStatsNumTxPdEmptyDataRecordTransferReq OBJECT-TYPE
    SYNTAX      ConfdString
    MAX-ACCESS  read-only
    STATUS      current
    DESCRIPTION "Potential-Duplicate-EmptyRec-Transmitted "
    ::= { affirmedServiceconstructInterfaceAaaGroupGtppPeerCmdStatsEntry 16 }

affirmedServiceconstructInterfaceAaaGroupGtppPeerCmdStatsNumTxCancelReq OBJECT-TYPE
    SYNTAX      ConfdString
    MAX-ACCESS  read-only
    STATUS      current
    DESCRIPTION "Cancel Request transmitted"
    ::= { affirmedServiceconstructInterfaceAaaGroupGtppPeerCmdStatsEntry 17 }

affirmedServiceconstructInterfaceAaaGroupGtppPeerCmdStatsNumTxReleaseReq OBJECT-TYPE
    SYNTAX      ConfdString
    MAX-ACCESS  read-only
    STATUS      current
    DESCRIPTION "Release Request transmitted"
    ::= { affirmedServiceconstructInterfaceAaaGroupGtppPeerCmdStatsEntry 18 }

affirmedServiceconstructInterfaceAaaGroupGtppPeerCmdStatsNumRxPdDataRecordTransferResp OBJECT-TYPE
    SYNTAX      ConfdString
    MAX-ACCESS  read-only
    STATUS      current
    DESCRIPTION "Potential duplicate record resp received"
    ::= { affirmedServiceconstructInterfaceAaaGroupGtppPeerCmdStatsEntry 19 }

affirmedServiceconstructInterfaceAaaGroupGtppPeerCmdStatsNumRxReqAccepted OBJECT-TYPE
    SYNTAX      ConfdString
    MAX-ACCESS  read-only
    STATUS      current
    DESCRIPTION "Request accepted received"
    ::= { affirmedServiceconstructInterfaceAaaGroupGtppPeerCmdStatsEntry 20 }

affirmedServiceconstructInterfaceAaaGroupGtppPeerCmdStatsNumRxReqFulfilled OBJECT-TYPE
    SYNTAX      ConfdString
    MAX-ACCESS  read-only
    STATUS      current
    DESCRIPTION " Request Fulfilled received"
    ::= { affirmedServiceconstructInterfaceAaaGroupGtppPeerCmdStatsEntry 21 }

affirmedServiceconstructInterfaceAaaGroupRadiusStatusServerGroupTable OBJECT-TYPE
    SYNTAX      SEQUENCE OF AffirmedServiceconstructInterfaceAaaGroupRadiusStatusServerGroupEntry
    MAX-ACCESS  not-accessible
    STATUS      current
    DESCRIPTION ""
    ::= { affirmedServiceconstructInterfaceAaaGroupRadiusStatus 1 }

affirmedServiceconstructInterfaceAaaGroupRadiusStatusServerGroupEntry OBJECT-TYPE
    SYNTAX      AffirmedServiceconstructInterfaceAaaGroupRadiusStatusServerGroupEntry
    MAX-ACCESS  not-accessible
    STATUS      current
    DESCRIPTION ""
    INDEX { affirmedServiceconstructInterfaceAaaGroupRadiusStatusServerGroupName }
        ::= { affirmedServiceconstructInterfaceAaaGroupRadiusStatusServerGroupTable 1 }

AffirmedServiceconstructInterfaceAaaGroupRadiusStatusServerGroupEntry ::=
    SEQUENCE {
        affirmedServiceconstructInterfaceAaaGroupRadiusStatusServerGroupName String,
        affirmedServiceconstructInterfaceAaaGroupRadiusStatusServerGroupOperStatus INTEGER
    }

affirmedServiceconstructInterfaceAaaGroupRadiusStatusServerGroupName OBJECT-TYPE
    SYNTAX      String
    MAX-ACCESS  not-accessible
    STATUS      current
    DESCRIPTION "Server Group Name"
    ::= { affirmedServiceconstructInterfaceAaaGroupRadiusStatusServerGroupEntry 1 }

affirmedServiceconstructInterfaceAaaGroupRadiusStatusServerGroupOperStatus OBJECT-TYPE
    SYNTAX      INTEGER {up(101),down(102),partially-up(103),maint(104),dryup(105),congested(106),unknown(107)}
    MAX-ACCESS  read-only
    STATUS      current
    DESCRIPTION "Operational Status"
    ::= { affirmedServiceconstructInterfaceAaaGroupRadiusStatusServerGroupEntry 2 }

affirmedServiceconstructInterfaceAaaGroupRadiusStatusServerGroupPeerTable OBJECT-TYPE
    SYNTAX      SEQUENCE OF AffirmedServiceconstructInterfaceAaaGroupRadiusStatusServerGroupPeerEntry
    MAX-ACCESS  not-accessible
    STATUS      current
    DESCRIPTION ""
    ::= { affirmedServiceconstructInterfaceAaaGroupRadiusStatus 2 }

affirmedServiceconstructInterfaceAaaGroupRadiusStatusServerGroupPeerEntry OBJECT-TYPE
    SYNTAX      AffirmedServiceconstructInterfaceAaaGroupRadiusStatusServerGroupPeerEntry
    MAX-ACCESS  not-accessible
    STATUS      current
    DESCRIPTION ""
    INDEX { affirmedServiceconstructInterfaceAaaGroupRadiusStatusServerGroupPeerName, affirmedServiceconstructInterfaceAaaGroupRadiusStatusServerGroupPeerPeerName }
        ::= { affirmedServiceconstructInterfaceAaaGroupRadiusStatusServerGroupPeerTable 1 }

AffirmedServiceconstructInterfaceAaaGroupRadiusStatusServerGroupPeerEntry ::=
    SEQUENCE {
        affirmedServiceconstructInterfaceAaaGroupRadiusStatusServerGroupPeerName String,
        affirmedServiceconstructInterfaceAaaGroupRadiusStatusServerGroupPeerPeerName String,
        affirmedServiceconstructInterfaceAaaGroupRadiusStatusServerGroupPeerOperStatus INTEGER,
        affirmedServiceconstructInterfaceAaaGroupRadiusStatusServerGroupPeerAdminStatus INTEGER,
        affirmedServiceconstructInterfaceAaaGroupRadiusStatusServerGroupPeerPriority Unsigned32
    }

affirmedServiceconstructInterfaceAaaGroupRadiusStatusServerGroupPeerName OBJECT-TYPE
    SYNTAX      String
    MAX-ACCESS  not-accessible
    STATUS      current
    DESCRIPTION "Server Group Name"
    ::= { affirmedServiceconstructInterfaceAaaGroupRadiusStatusServerGroupPeerEntry 1 }

affirmedServiceconstructInterfaceAaaGroupRadiusStatusServerGroupPeerPeerName OBJECT-TYPE
    SYNTAX      String
    MAX-ACCESS  not-accessible
    STATUS      current
    DESCRIPTION "Radius Peer Name"
    ::= { affirmedServiceconstructInterfaceAaaGroupRadiusStatusServerGroupPeerEntry 2 }

affirmedServiceconstructInterfaceAaaGroupRadiusStatusServerGroupPeerOperStatus OBJECT-TYPE
    SYNTAX      INTEGER {up(101),down(102),partially-up(103),maint(104),dryup(105),congested(106),unknown(107)}
    MAX-ACCESS  read-only
    STATUS      current
    DESCRIPTION "Operational Status"
    ::= { affirmedServiceconstructInterfaceAaaGroupRadiusStatusServerGroupPeerEntry 3 }

affirmedServiceconstructInterfaceAaaGroupRadiusStatusServerGroupPeerAdminStatus OBJECT-TYPE
    SYNTAX      INTEGER {disabled(0),enabled(1)}
    MAX-ACCESS  read-only
    STATUS      current
    DESCRIPTION "Admin Status"
    ::= { affirmedServiceconstructInterfaceAaaGroupRadiusStatusServerGroupPeerEntry 4 }

affirmedServiceconstructInterfaceAaaGroupRadiusStatusServerGroupPeerPriority OBJECT-TYPE
    SYNTAX      Unsigned32
    MAX-ACCESS  read-only
    STATUS      current
    DESCRIPTION "Assigned Priority"
    ::= { affirmedServiceconstructInterfaceAaaGroupRadiusStatusServerGroupPeerEntry 5 }

affirmedServiceconstructInterfaceAaaGroupRadiusStatusPeerStatusTable OBJECT-TYPE
    SYNTAX      SEQUENCE OF AffirmedServiceconstructInterfaceAaaGroupRadiusStatusPeerStatusEntry
    MAX-ACCESS  not-accessible
    STATUS      current
    DESCRIPTION ""
    ::= { affirmedServiceconstructInterfaceAaaGroupRadiusStatus 3 }

affirmedServiceconstructInterfaceAaaGroupRadiusStatusPeerStatusEntry OBJECT-TYPE
    SYNTAX      AffirmedServiceconstructInterfaceAaaGroupRadiusStatusPeerStatusEntry
    MAX-ACCESS  not-accessible
    STATUS      current
    DESCRIPTION ""
    INDEX { affirmedServiceconstructInterfaceAaaGroupRadiusStatusPeerStatusServerName, affirmedServiceconstructInterfaceAaaGroupRadiusStatusPeerStatusPeerName, affirmedServiceconstructInterfaceAaaGroupRadiusStatusPeerStatusSlot }
        ::= { affirmedServiceconstructInterfaceAaaGroupRadiusStatusPeerStatusTable 1 }

AffirmedServiceconstructInterfaceAaaGroupRadiusStatusPeerStatusEntry ::=
    SEQUENCE {
        affirmedServiceconstructInterfaceAaaGroupRadiusStatusPeerStatusServerName String,
        affirmedServiceconstructInterfaceAaaGroupRadiusStatusPeerStatusPeerName String,
        affirmedServiceconstructInterfaceAaaGroupRadiusStatusPeerStatusSlot Unsigned32,
        affirmedServiceconstructInterfaceAaaGroupRadiusStatusPeerStatusOperStatus INTEGER,
        affirmedServiceconstructInterfaceAaaGroupRadiusStatusPeerStatusOperReason String,
        affirmedServiceconstructInterfaceAaaGroupRadiusStatusPeerStatusAdminStatus INTEGER,
        affirmedServiceconstructInterfaceAaaGroupRadiusStatusPeerStatusLocalIpAddress String,
        affirmedServiceconstructInterfaceAaaGroupRadiusStatusPeerStatusStartingLocalPortNum Unsigned32,
        affirmedServiceconstructInterfaceAaaGroupRadiusStatusPeerStatusEndingLocalPortNum Unsigned32,
        affirmedServiceconstructInterfaceAaaGroupRadiusStatusPeerStatusRemoteIpAddress String,
        affirmedServiceconstructInterfaceAaaGroupRadiusStatusPeerStatusRemotePortNum Unsigned32,
        affirmedServiceconstructInterfaceAaaGroupRadiusStatusPeerStatusPriority Unsigned32
    }

affirmedServiceconstructInterfaceAaaGroupRadiusStatusPeerStatusServerName OBJECT-TYPE
    SYNTAX      String
    MAX-ACCESS  not-accessible
    STATUS      current
    DESCRIPTION "Server Group Name"
    ::= { affirmedServiceconstructInterfaceAaaGroupRadiusStatusPeerStatusEntry 1 }

affirmedServiceconstructInterfaceAaaGroupRadiusStatusPeerStatusPeerName OBJECT-TYPE
    SYNTAX      String
    MAX-ACCESS  not-accessible
    STATUS      current
    DESCRIPTION "Radius Peer Name"
    ::= { affirmedServiceconstructInterfaceAaaGroupRadiusStatusPeerStatusEntry 2 }

affirmedServiceconstructInterfaceAaaGroupRadiusStatusPeerStatusSlot OBJECT-TYPE
    SYNTAX      Unsigned32
    MAX-ACCESS  not-accessible
    STATUS      current
    DESCRIPTION "slot number"
    ::= { affirmedServiceconstructInterfaceAaaGroupRadiusStatusPeerStatusEntry 3 }

affirmedServiceconstructInterfaceAaaGroupRadiusStatusPeerStatusOperStatus OBJECT-TYPE
    SYNTAX      INTEGER {up(101),down(102),partially-up(103),maint(104),dryup(105),congested(106),unknown(107)}
    MAX-ACCESS  read-only
    STATUS      current
    DESCRIPTION "Operational Status"
    ::= { affirmedServiceconstructInterfaceAaaGroupRadiusStatusPeerStatusEntry 4 }

affirmedServiceconstructInterfaceAaaGroupRadiusStatusPeerStatusOperReason OBJECT-TYPE
    SYNTAX      String
    MAX-ACCESS  read-only
    STATUS      current
    DESCRIPTION "Operational Reason if state is Operationally Down"
    ::= { affirmedServiceconstructInterfaceAaaGroupRadiusStatusPeerStatusEntry 5 }

affirmedServiceconstructInterfaceAaaGroupRadiusStatusPeerStatusAdminStatus OBJECT-TYPE
    SYNTAX      INTEGER {disabled(0),enabled(1)}
    MAX-ACCESS  read-only
    STATUS      current
    DESCRIPTION "Admin Status"
    ::= { affirmedServiceconstructInterfaceAaaGroupRadiusStatusPeerStatusEntry 6 }

affirmedServiceconstructInterfaceAaaGroupRadiusStatusPeerStatusLocalIpAddress OBJECT-TYPE
    SYNTAX      String
    MAX-ACCESS  read-only
    STATUS      current
    DESCRIPTION "Local Ip Address of Radius Interface. Can be IPv4/IPv6"
    ::= { affirmedServiceconstructInterfaceAaaGroupRadiusStatusPeerStatusEntry 7 }

affirmedServiceconstructInterfaceAaaGroupRadiusStatusPeerStatusStartingLocalPortNum OBJECT-TYPE
    SYNTAX      Unsigned32
    MAX-ACCESS  read-only
    STATUS      current
    DESCRIPTION "Start Local Port Number"
    ::= { affirmedServiceconstructInterfaceAaaGroupRadiusStatusPeerStatusEntry 8 }

affirmedServiceconstructInterfaceAaaGroupRadiusStatusPeerStatusEndingLocalPortNum OBJECT-TYPE
    SYNTAX      Unsigned32
    MAX-ACCESS  read-only
    STATUS      current
    DESCRIPTION "End Local Port Number"
    ::= { affirmedServiceconstructInterfaceAaaGroupRadiusStatusPeerStatusEntry 9 }

affirmedServiceconstructInterfaceAaaGroupRadiusStatusPeerStatusRemoteIpAddress OBJECT-TYPE
    SYNTAX      String
    MAX-ACCESS  read-only
    STATUS      current
    DESCRIPTION "Remote Ip Address of Radius Interface. Can be IPv4/IPv6"
    ::= { affirmedServiceconstructInterfaceAaaGroupRadiusStatusPeerStatusEntry 10 }

affirmedServiceconstructInterfaceAaaGroupRadiusStatusPeerStatusRemotePortNum OBJECT-TYPE
    SYNTAX      Unsigned32
    MAX-ACCESS  read-only
    STATUS      current
    DESCRIPTION "Remote Port Number"
    ::= { affirmedServiceconstructInterfaceAaaGroupRadiusStatusPeerStatusEntry 11 }

affirmedServiceconstructInterfaceAaaGroupRadiusStatusPeerStatusPriority OBJECT-TYPE
    SYNTAX      Unsigned32
    MAX-ACCESS  read-only
    STATUS      current
    DESCRIPTION "Assigned Priority"
    ::= { affirmedServiceconstructInterfaceAaaGroupRadiusStatusPeerStatusEntry 12 }

affirmedServiceconstructInterfaceAaaGroupRadiusStatisticsGridLevelProcStatsAllTable OBJECT-TYPE
    SYNTAX      SEQUENCE OF AffirmedServiceconstructInterfaceAaaGroupRadiusStatisticsGridLevelProcStatsAllEntry
    MAX-ACCESS  not-accessible
    STATUS      current
    DESCRIPTION ""
    ::= { affirmedServiceconstructInterfaceAaaGroupRadiusStatisticsGridLevelProcStats 1 }

affirmedServiceconstructInterfaceAaaGroupRadiusStatisticsGridLevelProcStatsAllEntry OBJECT-TYPE
    SYNTAX      AffirmedServiceconstructInterfaceAaaGroupRadiusStatisticsGridLevelProcStatsAllEntry
    MAX-ACCESS  not-accessible
    STATUS      current
    DESCRIPTION ""
    INDEX { affirmedServiceconstructInterfaceAaaGroupRadiusStatisticsGridLevelProcStatsAllGrid }
        ::= { affirmedServiceconstructInterfaceAaaGroupRadiusStatisticsGridLevelProcStatsAllTable 1 }

AffirmedServiceconstructInterfaceAaaGroupRadiusStatisticsGridLevelProcStatsAllEntry ::=
    SEQUENCE {
        affirmedServiceconstructInterfaceAaaGroupRadiusStatisticsGridLevelProcStatsAllGrid Unsigned32,
        affirmedServiceconstructInterfaceAaaGroupRadiusStatisticsGridLevelProcStatsAllNumAccessReqTx ConfdString,
        affirmedServiceconstructInterfaceAaaGroupRadiusStatisticsGridLevelProcStatsAllNumAccessAcceptRx ConfdString,
        affirmedServiceconstructInterfaceAaaGroupRadiusStatisticsGridLevelProcStatsAllNumAccessRejectRx ConfdString,
        affirmedServiceconstructInterfaceAaaGroupRadiusStatisticsGridLevelProcStatsAllNumAccessChallengeRx ConfdString,
        affirmedServiceconstructInterfaceAaaGroupRadiusStatisticsGridLevelProcStatsAllNumAccountRequestStartTx ConfdString,
        affirmedServiceconstructInterfaceAaaGroupRadiusStatisticsGridLevelProcStatsAllNumAccountRequestStartRespRx ConfdString,
        affirmedServiceconstructInterfaceAaaGroupRadiusStatisticsGridLevelProcStatsAllNumAccountRequestStopTx ConfdString,
        affirmedServiceconstructInterfaceAaaGroupRadiusStatisticsGridLevelProcStatsAllNumAccountRequestStopRespRx ConfdString,
        affirmedServiceconstructInterfaceAaaGroupRadiusStatisticsGridLevelProcStatsAllNumAccountRequestInterimUpdateTx ConfdString,
        affirmedServiceconstructInterfaceAaaGroupRadiusStatisticsGridLevelProcStatsAllNumAccountRequestInterimUpdateRespRx ConfdString,
        affirmedServiceconstructInterfaceAaaGroupRadiusStatisticsGridLevelProcStatsAllNumAccountRequestOnTx ConfdString,
        affirmedServiceconstructInterfaceAaaGroupRadiusStatisticsGridLevelProcStatsAllNumAccountRequestOnRespRx ConfdString,
        affirmedServiceconstructInterfaceAaaGroupRadiusStatisticsGridLevelProcStatsAllNumAccountRequestOffTx ConfdString,
        affirmedServiceconstructInterfaceAaaGroupRadiusStatisticsGridLevelProcStatsAllNumAccountRequestOffRespRx ConfdString,
        affirmedServiceconstructInterfaceAaaGroupRadiusStatisticsGridLevelProcStatsAllNumDisconnectRequestRx ConfdString,
        affirmedServiceconstructInterfaceAaaGroupRadiusStatisticsGridLevelProcStatsAllNumDisconnectAckTx ConfdString,
        affirmedServiceconstructInterfaceAaaGroupRadiusStatisticsGridLevelProcStatsAllNumDisconnectNackTx ConfdString,
        affirmedServiceconstructInterfaceAaaGroupRadiusStatisticsGridLevelProcStatsAllNumCoaRequestRx ConfdString,
        affirmedServiceconstructInterfaceAaaGroupRadiusStatisticsGridLevelProcStatsAllNumCoaAckTx ConfdString,
        affirmedServiceconstructInterfaceAaaGroupRadiusStatisticsGridLevelProcStatsAllNumCoaNackTx ConfdString,
        affirmedServiceconstructInterfaceAaaGroupRadiusStatisticsGridLevelProcStatsAllNumAccessRejectLocal ConfdString,
        affirmedServiceconstructInterfaceAaaGroupRadiusStatisticsGridLevelProcStatsAllNumAccountRequestStartRejectLocal ConfdString,
        affirmedServiceconstructInterfaceAaaGroupRadiusStatisticsGridLevelProcStatsAllNumAccountRequestStopRejectLocal ConfdString,
        affirmedServiceconstructInterfaceAaaGroupRadiusStatisticsGridLevelProcStatsAllNumAccountRequestInterimRejectLocal ConfdString,
        affirmedServiceconstructInterfaceAaaGroupRadiusStatisticsGridLevelProcStatsAllNumAccessReqTimeout ConfdString,
        affirmedServiceconstructInterfaceAaaGroupRadiusStatisticsGridLevelProcStatsAllNumAccountRequestStartTimeout ConfdString,
        affirmedServiceconstructInterfaceAaaGroupRadiusStatisticsGridLevelProcStatsAllNumAccountRequestStopTimeout ConfdString,
        affirmedServiceconstructInterfaceAaaGroupRadiusStatisticsGridLevelProcStatsAllNumAccountRequestInterimUpdateTimeout ConfdString,
        affirmedServiceconstructInterfaceAaaGroupRadiusStatisticsGridLevelProcStatsAllNumAccessReqReTx ConfdString,
        affirmedServiceconstructInterfaceAaaGroupRadiusStatisticsGridLevelProcStatsAllNumAccessAcceptRcvdReTx ConfdString,
        affirmedServiceconstructInterfaceAaaGroupRadiusStatisticsGridLevelProcStatsAllNumAccountRequestStartReTx ConfdString,
        affirmedServiceconstructInterfaceAaaGroupRadiusStatisticsGridLevelProcStatsAllNumAccountRequestStartRespRcvdReTx ConfdString,
        affirmedServiceconstructInterfaceAaaGroupRadiusStatisticsGridLevelProcStatsAllNumAccountRequestStopReTx ConfdString,
        affirmedServiceconstructInterfaceAaaGroupRadiusStatisticsGridLevelProcStatsAllNumAccountRequestStopRespRcvdReTx ConfdString,
        affirmedServiceconstructInterfaceAaaGroupRadiusStatisticsGridLevelProcStatsAllNumAccountRequestInterimUpdateReTx ConfdString,
        affirmedServiceconstructInterfaceAaaGroupRadiusStatisticsGridLevelProcStatsAllNumAccountRequestInterimUpdateRespRcvdReTx ConfdString,
        affirmedServiceconstructInterfaceAaaGroupRadiusStatisticsGridLevelProcStatsAllCumulativeCoaLatency ConfdString,
        affirmedServiceconstructInterfaceAaaGroupRadiusStatisticsGridLevelProcStatsAllCoaLatencySamples Unsigned32,
        affirmedServiceconstructInterfaceAaaGroupRadiusStatisticsGridLevelProcStatsAllAverageCoaLatency ConfdString,
        affirmedServiceconstructInterfaceAaaGroupRadiusStatisticsGridLevelProcStatsAllCumulativeDisconnectLatency ConfdString,
        affirmedServiceconstructInterfaceAaaGroupRadiusStatisticsGridLevelProcStatsAllDisconnectLatencySamples Unsigned32,
        affirmedServiceconstructInterfaceAaaGroupRadiusStatisticsGridLevelProcStatsAllAverageDisconnectLatency ConfdString,
        affirmedServiceconstructInterfaceAaaGroupRadiusStatisticsGridLevelProcStatsAllCumulativeLatency ConfdString,
        affirmedServiceconstructInterfaceAaaGroupRadiusStatisticsGridLevelProcStatsAllLatencySamples Unsigned32,
        affirmedServiceconstructInterfaceAaaGroupRadiusStatisticsGridLevelProcStatsAllAverageLatency ConfdString,
        affirmedServiceconstructInterfaceAaaGroupRadiusStatisticsGridLevelProcStatsAllNumPacerNoCreditFailure ConfdString
    }

affirmedServiceconstructInterfaceAaaGroupRadiusStatisticsGridLevelProcStatsAllGrid OBJECT-TYPE
    SYNTAX      Unsigned32
    MAX-ACCESS  not-accessible
    STATUS      current
    DESCRIPTION "grid ID - dummy key"
    ::= { affirmedServiceconstructInterfaceAaaGroupRadiusStatisticsGridLevelProcStatsAllEntry 1 }

affirmedServiceconstructInterfaceAaaGroupRadiusStatisticsGridLevelProcStatsAllNumAccessReqTx OBJECT-TYPE
    SYNTAX      ConfdString
    MAX-ACCESS  read-only
    STATUS      current
    DESCRIPTION "Number of Access Requests that were transmitted(excluding retransmissions)"
    ::= { affirmedServiceconstructInterfaceAaaGroupRadiusStatisticsGridLevelProcStatsAllEntry 2 }

affirmedServiceconstructInterfaceAaaGroupRadiusStatisticsGridLevelProcStatsAllNumAccessAcceptRx OBJECT-TYPE
    SYNTAX      ConfdString
    MAX-ACCESS  read-only
    STATUS      current
    DESCRIPTION "Number of Access Accepts received on first request itself(no retransmissions)"
    ::= { affirmedServiceconstructInterfaceAaaGroupRadiusStatisticsGridLevelProcStatsAllEntry 3 }

affirmedServiceconstructInterfaceAaaGroupRadiusStatisticsGridLevelProcStatsAllNumAccessRejectRx OBJECT-TYPE
    SYNTAX      ConfdString
    MAX-ACCESS  read-only
    STATUS      current
    DESCRIPTION "Number of Access Rejects received from peer"
    ::= { affirmedServiceconstructInterfaceAaaGroupRadiusStatisticsGridLevelProcStatsAllEntry 4 }

affirmedServiceconstructInterfaceAaaGroupRadiusStatisticsGridLevelProcStatsAllNumAccessChallengeRx OBJECT-TYPE
    SYNTAX      ConfdString
    MAX-ACCESS  read-only
    STATUS      current
    DESCRIPTION "Number of Access Challenges received from peer"
    ::= { affirmedServiceconstructInterfaceAaaGroupRadiusStatisticsGridLevelProcStatsAllEntry 5 }

affirmedServiceconstructInterfaceAaaGroupRadiusStatisticsGridLevelProcStatsAllNumAccountRequestStartTx OBJECT-TYPE
    SYNTAX      ConfdString
    MAX-ACCESS  read-only
    STATUS      current
    DESCRIPTION "Number of Account Request Starts that were transmitted(excluding retransmissions)"
    ::= { affirmedServiceconstructInterfaceAaaGroupRadiusStatisticsGridLevelProcStatsAllEntry 6 }

affirmedServiceconstructInterfaceAaaGroupRadiusStatisticsGridLevelProcStatsAllNumAccountRequestStartRespRx OBJECT-TYPE
    SYNTAX      ConfdString
    MAX-ACCESS  read-only
    STATUS      current
    DESCRIPTION "Number of Account Start Responses received on first attempted request "
    ::= { affirmedServiceconstructInterfaceAaaGroupRadiusStatisticsGridLevelProcStatsAllEntry 7 }

affirmedServiceconstructInterfaceAaaGroupRadiusStatisticsGridLevelProcStatsAllNumAccountRequestStopTx OBJECT-TYPE
    SYNTAX      ConfdString
    MAX-ACCESS  read-only
    STATUS      current
    DESCRIPTION "Number of Account Request Stops that were transmitted(excluding retransmissions)"
    ::= { affirmedServiceconstructInterfaceAaaGroupRadiusStatisticsGridLevelProcStatsAllEntry 8 }

affirmedServiceconstructInterfaceAaaGroupRadiusStatisticsGridLevelProcStatsAllNumAccountRequestStopRespRx OBJECT-TYPE
    SYNTAX      ConfdString
    MAX-ACCESS  read-only
    STATUS      current
    DESCRIPTION "Number of Account Stop Responses received on first attempted request "
    ::= { affirmedServiceconstructInterfaceAaaGroupRadiusStatisticsGridLevelProcStatsAllEntry 9 }

affirmedServiceconstructInterfaceAaaGroupRadiusStatisticsGridLevelProcStatsAllNumAccountRequestInterimUpdateTx OBJECT-TYPE
    SYNTAX      ConfdString
    MAX-ACCESS  read-only
    STATUS      current
    DESCRIPTION "Number of Account Request Interim Updates that were transmitted(excluding retransmissions)"
    ::= { affirmedServiceconstructInterfaceAaaGroupRadiusStatisticsGridLevelProcStatsAllEntry 10 }

affirmedServiceconstructInterfaceAaaGroupRadiusStatisticsGridLevelProcStatsAllNumAccountRequestInterimUpdateRespRx OBJECT-TYPE
    SYNTAX      ConfdString
    MAX-ACCESS  read-only
    STATUS      current
    DESCRIPTION "Number of Account Interim Update Responses received on first attempted request "
    ::= { affirmedServiceconstructInterfaceAaaGroupRadiusStatisticsGridLevelProcStatsAllEntry 11 }

affirmedServiceconstructInterfaceAaaGroupRadiusStatisticsGridLevelProcStatsAllNumAccountRequestOnTx OBJECT-TYPE
    SYNTAX      ConfdString
    MAX-ACCESS  read-only
    STATUS      current
    DESCRIPTION "Number of Account Request On sent to peer"
    ::= { affirmedServiceconstructInterfaceAaaGroupRadiusStatisticsGridLevelProcStatsAllEntry 12 }

affirmedServiceconstructInterfaceAaaGroupRadiusStatisticsGridLevelProcStatsAllNumAccountRequestOnRespRx OBJECT-TYPE
    SYNTAX      ConfdString
    MAX-ACCESS  read-only
    STATUS      current
    DESCRIPTION "Number of Account Request On Response received from peer"
    ::= { affirmedServiceconstructInterfaceAaaGroupRadiusStatisticsGridLevelProcStatsAllEntry 13 }

affirmedServiceconstructInterfaceAaaGroupRadiusStatisticsGridLevelProcStatsAllNumAccountRequestOffTx OBJECT-TYPE
    SYNTAX      ConfdString
    MAX-ACCESS  read-only
    STATUS      current
    DESCRIPTION "Number of Account Request Off sent to peer"
    ::= { affirmedServiceconstructInterfaceAaaGroupRadiusStatisticsGridLevelProcStatsAllEntry 14 }

affirmedServiceconstructInterfaceAaaGroupRadiusStatisticsGridLevelProcStatsAllNumAccountRequestOffRespRx OBJECT-TYPE
    SYNTAX      ConfdString
    MAX-ACCESS  read-only
    STATUS      current
    DESCRIPTION "Number of Account Request Off Response received from peer"
    ::= { affirmedServiceconstructInterfaceAaaGroupRadiusStatisticsGridLevelProcStatsAllEntry 15 }

affirmedServiceconstructInterfaceAaaGroupRadiusStatisticsGridLevelProcStatsAllNumDisconnectRequestRx OBJECT-TYPE
    SYNTAX      ConfdString
    MAX-ACCESS  read-only
    STATUS      current
    DESCRIPTION "Number of Disconnect Request received from peer"
    ::= { affirmedServiceconstructInterfaceAaaGroupRadiusStatisticsGridLevelProcStatsAllEntry 16 }

affirmedServiceconstructInterfaceAaaGroupRadiusStatisticsGridLevelProcStatsAllNumDisconnectAckTx OBJECT-TYPE
    SYNTAX      ConfdString
    MAX-ACCESS  read-only
    STATUS      current
    DESCRIPTION "Number of Disconnect ACK sent to peer"
    ::= { affirmedServiceconstructInterfaceAaaGroupRadiusStatisticsGridLevelProcStatsAllEntry 17 }

affirmedServiceconstructInterfaceAaaGroupRadiusStatisticsGridLevelProcStatsAllNumDisconnectNackTx OBJECT-TYPE
    SYNTAX      ConfdString
    MAX-ACCESS  read-only
    STATUS      current
    DESCRIPTION "Number of Disconnect NACK sent to peer"
    ::= { affirmedServiceconstructInterfaceAaaGroupRadiusStatisticsGridLevelProcStatsAllEntry 18 }

affirmedServiceconstructInterfaceAaaGroupRadiusStatisticsGridLevelProcStatsAllNumCoaRequestRx OBJECT-TYPE
    SYNTAX      ConfdString
    MAX-ACCESS  read-only
    STATUS      current
    DESCRIPTION "Number of Coa Request received from peer"
    ::= { affirmedServiceconstructInterfaceAaaGroupRadiusStatisticsGridLevelProcStatsAllEntry 19 }

affirmedServiceconstructInterfaceAaaGroupRadiusStatisticsGridLevelProcStatsAllNumCoaAckTx OBJECT-TYPE
    SYNTAX      ConfdString
    MAX-ACCESS  read-only
    STATUS      current
    DESCRIPTION "Number of Coa ACK sent to peer"
    ::= { affirmedServiceconstructInterfaceAaaGroupRadiusStatisticsGridLevelProcStatsAllEntry 20 }

affirmedServiceconstructInterfaceAaaGroupRadiusStatisticsGridLevelProcStatsAllNumCoaNackTx OBJECT-TYPE
    SYNTAX      ConfdString
    MAX-ACCESS  read-only
    STATUS      current
    DESCRIPTION "Number of Coa NACK sent to peer"
    ::= { affirmedServiceconstructInterfaceAaaGroupRadiusStatisticsGridLevelProcStatsAllEntry 21 }

affirmedServiceconstructInterfaceAaaGroupRadiusStatisticsGridLevelProcStatsAllNumAccessRejectLocal OBJECT-TYPE
    SYNTAX      ConfdString
    MAX-ACCESS  read-only
    STATUS      current
    DESCRIPTION "Number of Access Requests that were rejected locally"
    ::= { affirmedServiceconstructInterfaceAaaGroupRadiusStatisticsGridLevelProcStatsAllEntry 22 }

affirmedServiceconstructInterfaceAaaGroupRadiusStatisticsGridLevelProcStatsAllNumAccountRequestStartRejectLocal OBJECT-TYPE
    SYNTAX      ConfdString
    MAX-ACCESS  read-only
    STATUS      current
    DESCRIPTION "Number of Account Request(START) that were rejected locally"
    ::= { affirmedServiceconstructInterfaceAaaGroupRadiusStatisticsGridLevelProcStatsAllEntry 23 }

affirmedServiceconstructInterfaceAaaGroupRadiusStatisticsGridLevelProcStatsAllNumAccountRequestStopRejectLocal OBJECT-TYPE
    SYNTAX      ConfdString
    MAX-ACCESS  read-only
    STATUS      current
    DESCRIPTION "Number of Account Request(STOP) that were rejected locally"
    ::= { affirmedServiceconstructInterfaceAaaGroupRadiusStatisticsGridLevelProcStatsAllEntry 24 }

affirmedServiceconstructInterfaceAaaGroupRadiusStatisticsGridLevelProcStatsAllNumAccountRequestInterimRejectLocal OBJECT-TYPE
    SYNTAX      ConfdString
    MAX-ACCESS  read-only
    STATUS      current
    DESCRIPTION "Number of Account Request(INTERIM) that were rejected locally"
    ::= { affirmedServiceconstructInterfaceAaaGroupRadiusStatisticsGridLevelProcStatsAllEntry 25 }

affirmedServiceconstructInterfaceAaaGroupRadiusStatisticsGridLevelProcStatsAllNumAccessReqTimeout OBJECT-TYPE
    SYNTAX      ConfdString
    MAX-ACCESS  read-only
    STATUS      current
    DESCRIPTION "Number of Access Requests that timed out(includes retransmission timeouts)"
    ::= { affirmedServiceconstructInterfaceAaaGroupRadiusStatisticsGridLevelProcStatsAllEntry 26 }

affirmedServiceconstructInterfaceAaaGroupRadiusStatisticsGridLevelProcStatsAllNumAccountRequestStartTimeout OBJECT-TYPE
    SYNTAX      ConfdString
    MAX-ACCESS  read-only
    STATUS      current
    DESCRIPTION "Number of Account Request Starts that timed out(includes retransmission timeouts)"
    ::= { affirmedServiceconstructInterfaceAaaGroupRadiusStatisticsGridLevelProcStatsAllEntry 27 }

affirmedServiceconstructInterfaceAaaGroupRadiusStatisticsGridLevelProcStatsAllNumAccountRequestStopTimeout OBJECT-TYPE
    SYNTAX      ConfdString
    MAX-ACCESS  read-only
    STATUS      current
    DESCRIPTION "Number of Account Request Stops that timed out(includes retransmission timeouts)"
    ::= { affirmedServiceconstructInterfaceAaaGroupRadiusStatisticsGridLevelProcStatsAllEntry 28 }

affirmedServiceconstructInterfaceAaaGroupRadiusStatisticsGridLevelProcStatsAllNumAccountRequestInterimUpdateTimeout OBJECT-TYPE
    SYNTAX      ConfdString
    MAX-ACCESS  read-only
    STATUS      current
    DESCRIPTION "Number of Account Request Interim Updates that timed out(includes retransmission timeouts)"
    ::= { affirmedServiceconstructInterfaceAaaGroupRadiusStatisticsGridLevelProcStatsAllEntry 29 }

affirmedServiceconstructInterfaceAaaGroupRadiusStatisticsGridLevelProcStatsAllNumAccessReqReTx OBJECT-TYPE
    SYNTAX      ConfdString
    MAX-ACCESS  read-only
    STATUS      current
    DESCRIPTION "Number of Access Requests that were retransmitted"
    ::= { affirmedServiceconstructInterfaceAaaGroupRadiusStatisticsGridLevelProcStatsAllEntry 30 }

affirmedServiceconstructInterfaceAaaGroupRadiusStatisticsGridLevelProcStatsAllNumAccessAcceptRcvdReTx OBJECT-TYPE
    SYNTAX      ConfdString
    MAX-ACCESS  read-only
    STATUS      current
    DESCRIPTION "Number of Access Accepts that were received when Requests were retransmitted"
    ::= { affirmedServiceconstructInterfaceAaaGroupRadiusStatisticsGridLevelProcStatsAllEntry 31 }

affirmedServiceconstructInterfaceAaaGroupRadiusStatisticsGridLevelProcStatsAllNumAccountRequestStartReTx OBJECT-TYPE
    SYNTAX      ConfdString
    MAX-ACCESS  read-only
    STATUS      current
    DESCRIPTION "Number of Account Request Starts that were retransmitted"
    ::= { affirmedServiceconstructInterfaceAaaGroupRadiusStatisticsGridLevelProcStatsAllEntry 32 }

affirmedServiceconstructInterfaceAaaGroupRadiusStatisticsGridLevelProcStatsAllNumAccountRequestStartRespRcvdReTx OBJECT-TYPE
    SYNTAX      ConfdString
    MAX-ACCESS  read-only
    STATUS      current
    DESCRIPTION "Number of Account Request Start Responses received when requests were retransmitted "
    ::= { affirmedServiceconstructInterfaceAaaGroupRadiusStatisticsGridLevelProcStatsAllEntry 33 }

affirmedServiceconstructInterfaceAaaGroupRadiusStatisticsGridLevelProcStatsAllNumAccountRequestStopReTx OBJECT-TYPE
    SYNTAX      ConfdString
    MAX-ACCESS  read-only
    STATUS      current
    DESCRIPTION "Number of Account Request Stops that were retransmitted"
    ::= { affirmedServiceconstructInterfaceAaaGroupRadiusStatisticsGridLevelProcStatsAllEntry 34 }

affirmedServiceconstructInterfaceAaaGroupRadiusStatisticsGridLevelProcStatsAllNumAccountRequestStopRespRcvdReTx OBJECT-TYPE
    SYNTAX      ConfdString
    MAX-ACCESS  read-only
    STATUS      current
    DESCRIPTION "Number of Account Request Stop Responses received when requests were retransmitted "
    ::= { affirmedServiceconstructInterfaceAaaGroupRadiusStatisticsGridLevelProcStatsAllEntry 35 }

affirmedServiceconstructInterfaceAaaGroupRadiusStatisticsGridLevelProcStatsAllNumAccountRequestInterimUpdateReTx OBJECT-TYPE
    SYNTAX      ConfdString
    MAX-ACCESS  read-only
    STATUS      current
    DESCRIPTION "Number of Account Request InterimUpdates that were retransmitted"
    ::= { affirmedServiceconstructInterfaceAaaGroupRadiusStatisticsGridLevelProcStatsAllEntry 36 }

affirmedServiceconstructInterfaceAaaGroupRadiusStatisticsGridLevelProcStatsAllNumAccountRequestInterimUpdateRespRcvdReTx OBJECT-TYPE
    SYNTAX      ConfdString
    MAX-ACCESS  read-only
    STATUS      current
    DESCRIPTION "Number of Account Request Interim Update Responses received when requests were retransmitted "
    ::= { affirmedServiceconstructInterfaceAaaGroupRadiusStatisticsGridLevelProcStatsAllEntry 37 }

affirmedServiceconstructInterfaceAaaGroupRadiusStatisticsGridLevelProcStatsAllCumulativeCoaLatency OBJECT-TYPE
    SYNTAX      ConfdString
    MAX-ACCESS  read-only
    STATUS      current
    DESCRIPTION "Cumulative Latency in microseconds for RADIUS CoA messages"
    ::= { affirmedServiceconstructInterfaceAaaGroupRadiusStatisticsGridLevelProcStatsAllEntry 38 }

affirmedServiceconstructInterfaceAaaGroupRadiusStatisticsGridLevelProcStatsAllCoaLatencySamples OBJECT-TYPE
    SYNTAX      Unsigned32
    MAX-ACCESS  read-only
    STATUS      current
    DESCRIPTION "Samples for calculating average latency for RADIUS CoA messages"
    ::= { affirmedServiceconstructInterfaceAaaGroupRadiusStatisticsGridLevelProcStatsAllEntry 39 }

affirmedServiceconstructInterfaceAaaGroupRadiusStatisticsGridLevelProcStatsAllAverageCoaLatency OBJECT-TYPE
    SYNTAX      ConfdString
    MAX-ACCESS  read-only
    STATUS      current
    DESCRIPTION "Average Latency in microseconds for RADIUS CoA"
    ::= { affirmedServiceconstructInterfaceAaaGroupRadiusStatisticsGridLevelProcStatsAllEntry 40 }

affirmedServiceconstructInterfaceAaaGroupRadiusStatisticsGridLevelProcStatsAllCumulativeDisconnectLatency OBJECT-TYPE
    SYNTAX      ConfdString
    MAX-ACCESS  read-only
    STATUS      current
    DESCRIPTION "Cumulative Latency in microseconds for RADIUS Disconnect messages"
    ::= { affirmedServiceconstructInterfaceAaaGroupRadiusStatisticsGridLevelProcStatsAllEntry 41 }

affirmedServiceconstructInterfaceAaaGroupRadiusStatisticsGridLevelProcStatsAllDisconnectLatencySamples OBJECT-TYPE
    SYNTAX      Unsigned32
    MAX-ACCESS  read-only
    STATUS      current
    DESCRIPTION "Samples for calculating average latency for RADIUS Disconnect messages"
    ::= { affirmedServiceconstructInterfaceAaaGroupRadiusStatisticsGridLevelProcStatsAllEntry 42 }

affirmedServiceconstructInterfaceAaaGroupRadiusStatisticsGridLevelProcStatsAllAverageDisconnectLatency OBJECT-TYPE
    SYNTAX      ConfdString
    MAX-ACCESS  read-only
    STATUS      current
    DESCRIPTION "Average Latency in microseconds for RADIUS Disconnect"
    ::= { affirmedServiceconstructInterfaceAaaGroupRadiusStatisticsGridLevelProcStatsAllEntry 43 }

affirmedServiceconstructInterfaceAaaGroupRadiusStatisticsGridLevelProcStatsAllCumulativeLatency OBJECT-TYPE
    SYNTAX      ConfdString
    MAX-ACCESS  read-only
    STATUS      current
    DESCRIPTION "Cumulative Latency in microseconds for RADIUS messages"
    ::= { affirmedServiceconstructInterfaceAaaGroupRadiusStatisticsGridLevelProcStatsAllEntry 44 }

affirmedServiceconstructInterfaceAaaGroupRadiusStatisticsGridLevelProcStatsAllLatencySamples OBJECT-TYPE
    SYNTAX      Unsigned32
    MAX-ACCESS  read-only
    STATUS      current
    DESCRIPTION "Samples for calculating average latency for RADIUS messages"
    ::= { affirmedServiceconstructInterfaceAaaGroupRadiusStatisticsGridLevelProcStatsAllEntry 45 }

affirmedServiceconstructInterfaceAaaGroupRadiusStatisticsGridLevelProcStatsAllAverageLatency OBJECT-TYPE
    SYNTAX      ConfdString
    MAX-ACCESS  read-only
    STATUS      current
    DESCRIPTION "Average Latency in microseconds for RADIUS messages"
    ::= { affirmedServiceconstructInterfaceAaaGroupRadiusStatisticsGridLevelProcStatsAllEntry 46 }

affirmedServiceconstructInterfaceAaaGroupRadiusStatisticsGridLevelProcStatsAllNumPacerNoCreditFailure OBJECT-TYPE
    SYNTAX      ConfdString
    MAX-ACCESS  read-only
    STATUS      current
    DESCRIPTION "Number of failures for no credit"
    ::= { affirmedServiceconstructInterfaceAaaGroupRadiusStatisticsGridLevelProcStatsAllEntry 47 }

affirmedServiceconstructInterfaceAaaGroupRadiusStatisticsGridLevelProcStatsPeerTable OBJECT-TYPE
    SYNTAX      SEQUENCE OF AffirmedServiceconstructInterfaceAaaGroupRadiusStatisticsGridLevelProcStatsPeerEntry
    MAX-ACCESS  not-accessible
    STATUS      current
    DESCRIPTION ""
    ::= { affirmedServiceconstructInterfaceAaaGroupRadiusStatisticsGridLevelProcStats 2 }

affirmedServiceconstructInterfaceAaaGroupRadiusStatisticsGridLevelProcStatsPeerEntry OBJECT-TYPE
    SYNTAX      AffirmedServiceconstructInterfaceAaaGroupRadiusStatisticsGridLevelProcStatsPeerEntry
    MAX-ACCESS  not-accessible
    STATUS      current
    DESCRIPTION ""
    INDEX { affirmedServiceconstructInterfaceAaaGroupRadiusStatisticsGridLevelProcStatsPeerName }
        ::= { affirmedServiceconstructInterfaceAaaGroupRadiusStatisticsGridLevelProcStatsPeerTable 1 }

AffirmedServiceconstructInterfaceAaaGroupRadiusStatisticsGridLevelProcStatsPeerEntry ::=
    SEQUENCE {
        affirmedServiceconstructInterfaceAaaGroupRadiusStatisticsGridLevelProcStatsPeerName String,
        affirmedServiceconstructInterfaceAaaGroupRadiusStatisticsGridLevelProcStatsPeerNumAccessReqTx ConfdString,
        affirmedServiceconstructInterfaceAaaGroupRadiusStatisticsGridLevelProcStatsPeerNumAccessAcceptRx ConfdString,
        affirmedServiceconstructInterfaceAaaGroupRadiusStatisticsGridLevelProcStatsPeerNumAccessRejectRx ConfdString,
        affirmedServiceconstructInterfaceAaaGroupRadiusStatisticsGridLevelProcStatsPeerNumAccessChallengeRx ConfdString,
        affirmedServiceconstructInterfaceAaaGroupRadiusStatisticsGridLevelProcStatsPeerNumAccountRequestStartTx ConfdString,
        affirmedServiceconstructInterfaceAaaGroupRadiusStatisticsGridLevelProcStatsPeerNumAccountRequestStartRespRx ConfdString,
        affirmedServiceconstructInterfaceAaaGroupRadiusStatisticsGridLevelProcStatsPeerNumAccountRequestStopTx ConfdString,
        affirmedServiceconstructInterfaceAaaGroupRadiusStatisticsGridLevelProcStatsPeerNumAccountRequestStopRespRx ConfdString,
        affirmedServiceconstructInterfaceAaaGroupRadiusStatisticsGridLevelProcStatsPeerNumAccountRequestInterimUpdateTx ConfdString,
        affirmedServiceconstructInterfaceAaaGroupRadiusStatisticsGridLevelProcStatsPeerNumAccountRequestInterimUpdateRespRx ConfdString,
        affirmedServiceconstructInterfaceAaaGroupRadiusStatisticsGridLevelProcStatsPeerNumAccountRequestOnTx ConfdString,
        affirmedServiceconstructInterfaceAaaGroupRadiusStatisticsGridLevelProcStatsPeerNumAccountRequestOnRespRx ConfdString,
        affirmedServiceconstructInterfaceAaaGroupRadiusStatisticsGridLevelProcStatsPeerNumAccountRequestOffTx ConfdString,
        affirmedServiceconstructInterfaceAaaGroupRadiusStatisticsGridLevelProcStatsPeerNumAccountRequestOffRespRx ConfdString,
        affirmedServiceconstructInterfaceAaaGroupRadiusStatisticsGridLevelProcStatsPeerNumDisconnectRequestRx ConfdString,
        affirmedServiceconstructInterfaceAaaGroupRadiusStatisticsGridLevelProcStatsPeerNumDisconnectAckTx ConfdString,
        affirmedServiceconstructInterfaceAaaGroupRadiusStatisticsGridLevelProcStatsPeerNumDisconnectNackTx ConfdString,
        affirmedServiceconstructInterfaceAaaGroupRadiusStatisticsGridLevelProcStatsPeerNumCoaRequestRx ConfdString,
        affirmedServiceconstructInterfaceAaaGroupRadiusStatisticsGridLevelProcStatsPeerNumCoaAckTx ConfdString,
        affirmedServiceconstructInterfaceAaaGroupRadiusStatisticsGridLevelProcStatsPeerNumCoaNackTx ConfdString,
        affirmedServiceconstructInterfaceAaaGroupRadiusStatisticsGridLevelProcStatsPeerNumAccessRejectLocal ConfdString,
        affirmedServiceconstructInterfaceAaaGroupRadiusStatisticsGridLevelProcStatsPeerNumAccountRequestStartRejectLocal ConfdString,
        affirmedServiceconstructInterfaceAaaGroupRadiusStatisticsGridLevelProcStatsPeerNumAccountRequestStopRejectLocal ConfdString,
        affirmedServiceconstructInterfaceAaaGroupRadiusStatisticsGridLevelProcStatsPeerNumAccountRequestInterimRejectLocal ConfdString,
        affirmedServiceconstructInterfaceAaaGroupRadiusStatisticsGridLevelProcStatsPeerNumAccessReqTimeout ConfdString,
        affirmedServiceconstructInterfaceAaaGroupRadiusStatisticsGridLevelProcStatsPeerNumAccountRequestStartTimeout ConfdString,
        affirmedServiceconstructInterfaceAaaGroupRadiusStatisticsGridLevelProcStatsPeerNumAccountRequestStopTimeout ConfdString,
        affirmedServiceconstructInterfaceAaaGroupRadiusStatisticsGridLevelProcStatsPeerNumAccountRequestInterimUpdateTimeout ConfdString,
        affirmedServiceconstructInterfaceAaaGroupRadiusStatisticsGridLevelProcStatsPeerNumAccessReqReTx ConfdString,
        affirmedServiceconstructInterfaceAaaGroupRadiusStatisticsGridLevelProcStatsPeerNumAccessAcceptRcvdReTx ConfdString,
        affirmedServiceconstructInterfaceAaaGroupRadiusStatisticsGridLevelProcStatsPeerNumAccountRequestStartReTx ConfdString,
        affirmedServiceconstructInterfaceAaaGroupRadiusStatisticsGridLevelProcStatsPeerNumAccountRequestStartRespRcvdReTx ConfdString,
        affirmedServiceconstructInterfaceAaaGroupRadiusStatisticsGridLevelProcStatsPeerNumAccountRequestStopReTx ConfdString,
        affirmedServiceconstructInterfaceAaaGroupRadiusStatisticsGridLevelProcStatsPeerNumAccountRequestStopRespRcvdReTx ConfdString,
        affirmedServiceconstructInterfaceAaaGroupRadiusStatisticsGridLevelProcStatsPeerNumAccountRequestInterimUpdateReTx ConfdString,
        affirmedServiceconstructInterfaceAaaGroupRadiusStatisticsGridLevelProcStatsPeerNumAccountRequestInterimUpdateRespRcvdReTx ConfdString,
        affirmedServiceconstructInterfaceAaaGroupRadiusStatisticsGridLevelProcStatsPeerCumulativeCoaLatency ConfdString,
        affirmedServiceconstructInterfaceAaaGroupRadiusStatisticsGridLevelProcStatsPeerCoaLatencySamples Unsigned32,
        affirmedServiceconstructInterfaceAaaGroupRadiusStatisticsGridLevelProcStatsPeerAverageCoaLatency ConfdString,
        affirmedServiceconstructInterfaceAaaGroupRadiusStatisticsGridLevelProcStatsPeerCumulativeDisconnectLatency ConfdString,
        affirmedServiceconstructInterfaceAaaGroupRadiusStatisticsGridLevelProcStatsPeerDisconnectLatencySamples Unsigned32,
        affirmedServiceconstructInterfaceAaaGroupRadiusStatisticsGridLevelProcStatsPeerAverageDisconnectLatency ConfdString,
        affirmedServiceconstructInterfaceAaaGroupRadiusStatisticsGridLevelProcStatsPeerCumulativeLatency ConfdString,
        affirmedServiceconstructInterfaceAaaGroupRadiusStatisticsGridLevelProcStatsPeerLatencySamples Unsigned32,
        affirmedServiceconstructInterfaceAaaGroupRadiusStatisticsGridLevelProcStatsPeerAverageLatency ConfdString,
        affirmedServiceconstructInterfaceAaaGroupRadiusStatisticsGridLevelProcStatsPeerNumPacerNoCreditFailure ConfdString
    }

affirmedServiceconstructInterfaceAaaGroupRadiusStatisticsGridLevelProcStatsPeerName OBJECT-TYPE
    SYNTAX      String
    MAX-ACCESS  not-accessible
    STATUS      current
    DESCRIPTION "Peer Stats Table Name"
    ::= { affirmedServiceconstructInterfaceAaaGroupRadiusStatisticsGridLevelProcStatsPeerEntry 1 }

affirmedServiceconstructInterfaceAaaGroupRadiusStatisticsGridLevelProcStatsPeerNumAccessReqTx OBJECT-TYPE
    SYNTAX      ConfdString
    MAX-ACCESS  read-only
    STATUS      current
    DESCRIPTION "Number of Access Requests that were transmitted(excluding retransmissions)"
    ::= { affirmedServiceconstructInterfaceAaaGroupRadiusStatisticsGridLevelProcStatsPeerEntry 2 }

affirmedServiceconstructInterfaceAaaGroupRadiusStatisticsGridLevelProcStatsPeerNumAccessAcceptRx OBJECT-TYPE
    SYNTAX      ConfdString
    MAX-ACCESS  read-only
    STATUS      current
    DESCRIPTION "Number of Access Accepts received on first request itself(no retransmissions)"
    ::= { affirmedServiceconstructInterfaceAaaGroupRadiusStatisticsGridLevelProcStatsPeerEntry 3 }

affirmedServiceconstructInterfaceAaaGroupRadiusStatisticsGridLevelProcStatsPeerNumAccessRejectRx OBJECT-TYPE
    SYNTAX      ConfdString
    MAX-ACCESS  read-only
    STATUS      current
    DESCRIPTION "Number of Access Rejects received from peer"
    ::= { affirmedServiceconstructInterfaceAaaGroupRadiusStatisticsGridLevelProcStatsPeerEntry 4 }

affirmedServiceconstructInterfaceAaaGroupRadiusStatisticsGridLevelProcStatsPeerNumAccessChallengeRx OBJECT-TYPE
    SYNTAX      ConfdString
    MAX-ACCESS  read-only
    STATUS      current
    DESCRIPTION "Number of Access Challenges received from peer"
    ::= { affirmedServiceconstructInterfaceAaaGroupRadiusStatisticsGridLevelProcStatsPeerEntry 5 }

affirmedServiceconstructInterfaceAaaGroupRadiusStatisticsGridLevelProcStatsPeerNumAccountRequestStartTx OBJECT-TYPE
    SYNTAX      ConfdString
    MAX-ACCESS  read-only
    STATUS      current
    DESCRIPTION "Number of Account Request Starts that were transmitted(excluding retransmissions)"
    ::= { affirmedServiceconstructInterfaceAaaGroupRadiusStatisticsGridLevelProcStatsPeerEntry 6 }

affirmedServiceconstructInterfaceAaaGroupRadiusStatisticsGridLevelProcStatsPeerNumAccountRequestStartRespRx OBJECT-TYPE
    SYNTAX      ConfdString
    MAX-ACCESS  read-only
    STATUS      current
    DESCRIPTION "Number of Account Start Responses received on first attempted request "
    ::= { affirmedServiceconstructInterfaceAaaGroupRadiusStatisticsGridLevelProcStatsPeerEntry 7 }

affirmedServiceconstructInterfaceAaaGroupRadiusStatisticsGridLevelProcStatsPeerNumAccountRequestStopTx OBJECT-TYPE
    SYNTAX      ConfdString
    MAX-ACCESS  read-only
    STATUS      current
    DESCRIPTION "Number of Account Request Stops that were transmitted(excluding retransmissions)"
    ::= { affirmedServiceconstructInterfaceAaaGroupRadiusStatisticsGridLevelProcStatsPeerEntry 8 }

affirmedServiceconstructInterfaceAaaGroupRadiusStatisticsGridLevelProcStatsPeerNumAccountRequestStopRespRx OBJECT-TYPE
    SYNTAX      ConfdString
    MAX-ACCESS  read-only
    STATUS      current
    DESCRIPTION "Number of Account Stop Responses received on first attempted request "
    ::= { affirmedServiceconstructInterfaceAaaGroupRadiusStatisticsGridLevelProcStatsPeerEntry 9 }

affirmedServiceconstructInterfaceAaaGroupRadiusStatisticsGridLevelProcStatsPeerNumAccountRequestInterimUpdateTx OBJECT-TYPE
    SYNTAX      ConfdString
    MAX-ACCESS  read-only
    STATUS      current
    DESCRIPTION "Number of Account Request Interim Updates that were transmitted(excluding retransmissions)"
    ::= { affirmedServiceconstructInterfaceAaaGroupRadiusStatisticsGridLevelProcStatsPeerEntry 10 }

affirmedServiceconstructInterfaceAaaGroupRadiusStatisticsGridLevelProcStatsPeerNumAccountRequestInterimUpdateRespRx OBJECT-TYPE
    SYNTAX      ConfdString
    MAX-ACCESS  read-only
    STATUS      current
    DESCRIPTION "Number of Account Interim Update Responses received on first attempted request "
    ::= { affirmedServiceconstructInterfaceAaaGroupRadiusStatisticsGridLevelProcStatsPeerEntry 11 }

affirmedServiceconstructInterfaceAaaGroupRadiusStatisticsGridLevelProcStatsPeerNumAccountRequestOnTx OBJECT-TYPE
    SYNTAX      ConfdString
    MAX-ACCESS  read-only
    STATUS      current
    DESCRIPTION "Number of Account Request On sent to peer"
    ::= { affirmedServiceconstructInterfaceAaaGroupRadiusStatisticsGridLevelProcStatsPeerEntry 12 }

affirmedServiceconstructInterfaceAaaGroupRadiusStatisticsGridLevelProcStatsPeerNumAccountRequestOnRespRx OBJECT-TYPE
    SYNTAX      ConfdString
    MAX-ACCESS  read-only
    STATUS      current
    DESCRIPTION "Number of Account Request On Response received from peer"
    ::= { affirmedServiceconstructInterfaceAaaGroupRadiusStatisticsGridLevelProcStatsPeerEntry 13 }

affirmedServiceconstructInterfaceAaaGroupRadiusStatisticsGridLevelProcStatsPeerNumAccountRequestOffTx OBJECT-TYPE
    SYNTAX      ConfdString
    MAX-ACCESS  read-only
    STATUS      current
    DESCRIPTION "Number of Account Request Off sent to peer"
    ::= { affirmedServiceconstructInterfaceAaaGroupRadiusStatisticsGridLevelProcStatsPeerEntry 14 }

affirmedServiceconstructInterfaceAaaGroupRadiusStatisticsGridLevelProcStatsPeerNumAccountRequestOffRespRx OBJECT-TYPE
    SYNTAX      ConfdString
    MAX-ACCESS  read-only
    STATUS      current
    DESCRIPTION "Number of Account Request Off Response received from peer"
    ::= { affirmedServiceconstructInterfaceAaaGroupRadiusStatisticsGridLevelProcStatsPeerEntry 15 }

affirmedServiceconstructInterfaceAaaGroupRadiusStatisticsGridLevelProcStatsPeerNumDisconnectRequestRx OBJECT-TYPE
    SYNTAX      ConfdString
    MAX-ACCESS  read-only
    STATUS      current
    DESCRIPTION "Number of Disconnect Request received from peer"
    ::= { affirmedServiceconstructInterfaceAaaGroupRadiusStatisticsGridLevelProcStatsPeerEntry 16 }

affirmedServiceconstructInterfaceAaaGroupRadiusStatisticsGridLevelProcStatsPeerNumDisconnectAckTx OBJECT-TYPE
    SYNTAX      ConfdString
    MAX-ACCESS  read-only
    STATUS      current
    DESCRIPTION "Number of Disconnect ACK sent to peer"
    ::= { affirmedServiceconstructInterfaceAaaGroupRadiusStatisticsGridLevelProcStatsPeerEntry 17 }

affirmedServiceconstructInterfaceAaaGroupRadiusStatisticsGridLevelProcStatsPeerNumDisconnectNackTx OBJECT-TYPE
    SYNTAX      ConfdString
    MAX-ACCESS  read-only
    STATUS      current
    DESCRIPTION "Number of Disconnect NACK sent to peer"
    ::= { affirmedServiceconstructInterfaceAaaGroupRadiusStatisticsGridLevelProcStatsPeerEntry 18 }

affirmedServiceconstructInterfaceAaaGroupRadiusStatisticsGridLevelProcStatsPeerNumCoaRequestRx OBJECT-TYPE
    SYNTAX      ConfdString
    MAX-ACCESS  read-only
    STATUS      current
    DESCRIPTION "Number of Coa Request received from peer"
    ::= { affirmedServiceconstructInterfaceAaaGroupRadiusStatisticsGridLevelProcStatsPeerEntry 19 }

affirmedServiceconstructInterfaceAaaGroupRadiusStatisticsGridLevelProcStatsPeerNumCoaAckTx OBJECT-TYPE
    SYNTAX      ConfdString
    MAX-ACCESS  read-only
    STATUS      current
    DESCRIPTION "Number of Coa ACK sent to peer"
    ::= { affirmedServiceconstructInterfaceAaaGroupRadiusStatisticsGridLevelProcStatsPeerEntry 20 }

affirmedServiceconstructInterfaceAaaGroupRadiusStatisticsGridLevelProcStatsPeerNumCoaNackTx OBJECT-TYPE
    SYNTAX      ConfdString
    MAX-ACCESS  read-only
    STATUS      current
    DESCRIPTION "Number of Coa NACK sent to peer"
    ::= { affirmedServiceconstructInterfaceAaaGroupRadiusStatisticsGridLevelProcStatsPeerEntry 21 }

affirmedServiceconstructInterfaceAaaGroupRadiusStatisticsGridLevelProcStatsPeerNumAccessRejectLocal OBJECT-TYPE
    SYNTAX      ConfdString
    MAX-ACCESS  read-only
    STATUS      current
    DESCRIPTION "Number of Access Requests that were rejected locally"
    ::= { affirmedServiceconstructInterfaceAaaGroupRadiusStatisticsGridLevelProcStatsPeerEntry 22 }

affirmedServiceconstructInterfaceAaaGroupRadiusStatisticsGridLevelProcStatsPeerNumAccountRequestStartRejectLocal OBJECT-TYPE
    SYNTAX      ConfdString
    MAX-ACCESS  read-only
    STATUS      current
    DESCRIPTION "Number of Account Request(START) that were rejected locally"
    ::= { affirmedServiceconstructInterfaceAaaGroupRadiusStatisticsGridLevelProcStatsPeerEntry 23 }

affirmedServiceconstructInterfaceAaaGroupRadiusStatisticsGridLevelProcStatsPeerNumAccountRequestStopRejectLocal OBJECT-TYPE
    SYNTAX      ConfdString
    MAX-ACCESS  read-only
    STATUS      current
    DESCRIPTION "Number of Account Request(STOP) that were rejected locally"
    ::= { affirmedServiceconstructInterfaceAaaGroupRadiusStatisticsGridLevelProcStatsPeerEntry 24 }

affirmedServiceconstructInterfaceAaaGroupRadiusStatisticsGridLevelProcStatsPeerNumAccountRequestInterimRejectLocal OBJECT-TYPE
    SYNTAX      ConfdString
    MAX-ACCESS  read-only
    STATUS      current
    DESCRIPTION "Number of Account Request(INTERIM) that were rejected locally"
    ::= { affirmedServiceconstructInterfaceAaaGroupRadiusStatisticsGridLevelProcStatsPeerEntry 25 }

affirmedServiceconstructInterfaceAaaGroupRadiusStatisticsGridLevelProcStatsPeerNumAccessReqTimeout OBJECT-TYPE
    SYNTAX      ConfdString
    MAX-ACCESS  read-only
    STATUS      current
    DESCRIPTION "Number of Access Requests that timed out(includes retransmission timeouts)"
    ::= { affirmedServiceconstructInterfaceAaaGroupRadiusStatisticsGridLevelProcStatsPeerEntry 26 }

affirmedServiceconstructInterfaceAaaGroupRadiusStatisticsGridLevelProcStatsPeerNumAccountRequestStartTimeout OBJECT-TYPE
    SYNTAX      ConfdString
    MAX-ACCESS  read-only
    STATUS      current
    DESCRIPTION "Number of Account Request Starts that timed out(includes retransmission timeouts)"
    ::= { affirmedServiceconstructInterfaceAaaGroupRadiusStatisticsGridLevelProcStatsPeerEntry 27 }

affirmedServiceconstructInterfaceAaaGroupRadiusStatisticsGridLevelProcStatsPeerNumAccountRequestStopTimeout OBJECT-TYPE
    SYNTAX      ConfdString
    MAX-ACCESS  read-only
    STATUS      current
    DESCRIPTION "Number of Account Request Stops that timed out(includes retransmission timeouts)"
    ::= { affirmedServiceconstructInterfaceAaaGroupRadiusStatisticsGridLevelProcStatsPeerEntry 28 }

affirmedServiceconstructInterfaceAaaGroupRadiusStatisticsGridLevelProcStatsPeerNumAccountRequestInterimUpdateTimeout OBJECT-TYPE
    SYNTAX      ConfdString
    MAX-ACCESS  read-only
    STATUS      current
    DESCRIPTION "Number of Account Request Interim Updates that timed out(includes retransmission timeouts)"
    ::= { affirmedServiceconstructInterfaceAaaGroupRadiusStatisticsGridLevelProcStatsPeerEntry 29 }

affirmedServiceconstructInterfaceAaaGroupRadiusStatisticsGridLevelProcStatsPeerNumAccessReqReTx OBJECT-TYPE
    SYNTAX      ConfdString
    MAX-ACCESS  read-only
    STATUS      current
    DESCRIPTION "Number of Access Requests that were retransmitted"
    ::= { affirmedServiceconstructInterfaceAaaGroupRadiusStatisticsGridLevelProcStatsPeerEntry 30 }

affirmedServiceconstructInterfaceAaaGroupRadiusStatisticsGridLevelProcStatsPeerNumAccessAcceptRcvdReTx OBJECT-TYPE
    SYNTAX      ConfdString
    MAX-ACCESS  read-only
    STATUS      current
    DESCRIPTION "Number of Access Accepts that were received when Requests were retransmitted"
    ::= { affirmedServiceconstructInterfaceAaaGroupRadiusStatisticsGridLevelProcStatsPeerEntry 31 }

affirmedServiceconstructInterfaceAaaGroupRadiusStatisticsGridLevelProcStatsPeerNumAccountRequestStartReTx OBJECT-TYPE
    SYNTAX      ConfdString
    MAX-ACCESS  read-only
    STATUS      current
    DESCRIPTION "Number of Account Request Starts that were retransmitted"
    ::= { affirmedServiceconstructInterfaceAaaGroupRadiusStatisticsGridLevelProcStatsPeerEntry 32 }

affirmedServiceconstructInterfaceAaaGroupRadiusStatisticsGridLevelProcStatsPeerNumAccountRequestStartRespRcvdReTx OBJECT-TYPE
    SYNTAX      ConfdString
    MAX-ACCESS  read-only
    STATUS      current
    DESCRIPTION "Number of Account Request Start Responses received when requests were retransmitted "
    ::= { affirmedServiceconstructInterfaceAaaGroupRadiusStatisticsGridLevelProcStatsPeerEntry 33 }

affirmedServiceconstructInterfaceAaaGroupRadiusStatisticsGridLevelProcStatsPeerNumAccountRequestStopReTx OBJECT-TYPE
    SYNTAX      ConfdString
    MAX-ACCESS  read-only
    STATUS      current
    DESCRIPTION "Number of Account Request Stops that were retransmitted"
    ::= { affirmedServiceconstructInterfaceAaaGroupRadiusStatisticsGridLevelProcStatsPeerEntry 34 }

affirmedServiceconstructInterfaceAaaGroupRadiusStatisticsGridLevelProcStatsPeerNumAccountRequestStopRespRcvdReTx OBJECT-TYPE
    SYNTAX      ConfdString
    MAX-ACCESS  read-only
    STATUS      current
    DESCRIPTION "Number of Account Request Stop Responses received when requests were retransmitted "
    ::= { affirmedServiceconstructInterfaceAaaGroupRadiusStatisticsGridLevelProcStatsPeerEntry 35 }

affirmedServiceconstructInterfaceAaaGroupRadiusStatisticsGridLevelProcStatsPeerNumAccountRequestInterimUpdateReTx OBJECT-TYPE
    SYNTAX      ConfdString
    MAX-ACCESS  read-only
    STATUS      current
    DESCRIPTION "Number of Account Request InterimUpdates that were retransmitted"
    ::= { affirmedServiceconstructInterfaceAaaGroupRadiusStatisticsGridLevelProcStatsPeerEntry 36 }

affirmedServiceconstructInterfaceAaaGroupRadiusStatisticsGridLevelProcStatsPeerNumAccountRequestInterimUpdateRespRcvdReTx OBJECT-TYPE
    SYNTAX      ConfdString
    MAX-ACCESS  read-only
    STATUS      current
    DESCRIPTION "Number of Account Request Interim Update Responses received when requests were retransmitted "
    ::= { affirmedServiceconstructInterfaceAaaGroupRadiusStatisticsGridLevelProcStatsPeerEntry 37 }

affirmedServiceconstructInterfaceAaaGroupRadiusStatisticsGridLevelProcStatsPeerCumulativeCoaLatency OBJECT-TYPE
    SYNTAX      ConfdString
    MAX-ACCESS  read-only
    STATUS      current
    DESCRIPTION "Cumulative Latency in microseconds for RADIUS CoA messages"
    ::= { affirmedServiceconstructInterfaceAaaGroupRadiusStatisticsGridLevelProcStatsPeerEntry 38 }

affirmedServiceconstructInterfaceAaaGroupRadiusStatisticsGridLevelProcStatsPeerCoaLatencySamples OBJECT-TYPE
    SYNTAX      Unsigned32
    MAX-ACCESS  read-only
    STATUS      current
    DESCRIPTION "Samples for calculating average latency for RADIUS CoA messages"
    ::= { affirmedServiceconstructInterfaceAaaGroupRadiusStatisticsGridLevelProcStatsPeerEntry 39 }

affirmedServiceconstructInterfaceAaaGroupRadiusStatisticsGridLevelProcStatsPeerAverageCoaLatency OBJECT-TYPE
    SYNTAX      ConfdString
    MAX-ACCESS  read-only
    STATUS      current
    DESCRIPTION "Average Latency in microseconds for RADIUS CoA"
    ::= { affirmedServiceconstructInterfaceAaaGroupRadiusStatisticsGridLevelProcStatsPeerEntry 40 }

affirmedServiceconstructInterfaceAaaGroupRadiusStatisticsGridLevelProcStatsPeerCumulativeDisconnectLatency OBJECT-TYPE
    SYNTAX      ConfdString
    MAX-ACCESS  read-only
    STATUS      current
    DESCRIPTION "Cumulative Latency in microseconds for RADIUS Disconnect messages"
    ::= { affirmedServiceconstructInterfaceAaaGroupRadiusStatisticsGridLevelProcStatsPeerEntry 41 }

affirmedServiceconstructInterfaceAaaGroupRadiusStatisticsGridLevelProcStatsPeerDisconnectLatencySamples OBJECT-TYPE
    SYNTAX      Unsigned32
    MAX-ACCESS  read-only
    STATUS      current
    DESCRIPTION "Samples for calculating average latency for RADIUS Disconnect messages"
    ::= { affirmedServiceconstructInterfaceAaaGroupRadiusStatisticsGridLevelProcStatsPeerEntry 42 }

affirmedServiceconstructInterfaceAaaGroupRadiusStatisticsGridLevelProcStatsPeerAverageDisconnectLatency OBJECT-TYPE
    SYNTAX      ConfdString
    MAX-ACCESS  read-only
    STATUS      current
    DESCRIPTION "Average Latency in microseconds for RADIUS Disconnect"
    ::= { affirmedServiceconstructInterfaceAaaGroupRadiusStatisticsGridLevelProcStatsPeerEntry 43 }

affirmedServiceconstructInterfaceAaaGroupRadiusStatisticsGridLevelProcStatsPeerCumulativeLatency OBJECT-TYPE
    SYNTAX      ConfdString
    MAX-ACCESS  read-only
    STATUS      current
    DESCRIPTION "Cumulative Latency in microseconds for RADIUS messages"
    ::= { affirmedServiceconstructInterfaceAaaGroupRadiusStatisticsGridLevelProcStatsPeerEntry 44 }

affirmedServiceconstructInterfaceAaaGroupRadiusStatisticsGridLevelProcStatsPeerLatencySamples OBJECT-TYPE
    SYNTAX      Unsigned32
    MAX-ACCESS  read-only
    STATUS      current
    DESCRIPTION "Samples for calculating average latency for RADIUS messages"
    ::= { affirmedServiceconstructInterfaceAaaGroupRadiusStatisticsGridLevelProcStatsPeerEntry 45 }

affirmedServiceconstructInterfaceAaaGroupRadiusStatisticsGridLevelProcStatsPeerAverageLatency OBJECT-TYPE
    SYNTAX      ConfdString
    MAX-ACCESS  read-only
    STATUS      current
    DESCRIPTION "Average Latency in microseconds for RADIUS messages"
    ::= { affirmedServiceconstructInterfaceAaaGroupRadiusStatisticsGridLevelProcStatsPeerEntry 46 }

affirmedServiceconstructInterfaceAaaGroupRadiusStatisticsGridLevelProcStatsPeerNumPacerNoCreditFailure OBJECT-TYPE
    SYNTAX      ConfdString
    MAX-ACCESS  read-only
    STATUS      current
    DESCRIPTION "Number of failures for no credit"
    ::= { affirmedServiceconstructInterfaceAaaGroupRadiusStatisticsGridLevelProcStatsPeerEntry 47 }

affirmedServiceconstructInterfaceAaaGroupRadiusStatisticsChassisLevelProcStatsAllTable OBJECT-TYPE
    SYNTAX      SEQUENCE OF AffirmedServiceconstructInterfaceAaaGroupRadiusStatisticsChassisLevelProcStatsAllEntry
    MAX-ACCESS  not-accessible
    STATUS      current
    DESCRIPTION ""
    ::= { affirmedServiceconstructInterfaceAaaGroupRadiusStatisticsChassisLevelProcStats 1 }

affirmedServiceconstructInterfaceAaaGroupRadiusStatisticsChassisLevelProcStatsAllEntry OBJECT-TYPE
    SYNTAX      AffirmedServiceconstructInterfaceAaaGroupRadiusStatisticsChassisLevelProcStatsAllEntry
    MAX-ACCESS  not-accessible
    STATUS      current
    DESCRIPTION ""
    INDEX { affirmedServiceconstructInterfaceAaaGroupRadiusStatisticsChassisLevelProcStatsAllChassis }
        ::= { affirmedServiceconstructInterfaceAaaGroupRadiusStatisticsChassisLevelProcStatsAllTable 1 }

AffirmedServiceconstructInterfaceAaaGroupRadiusStatisticsChassisLevelProcStatsAllEntry ::=
    SEQUENCE {
        affirmedServiceconstructInterfaceAaaGroupRadiusStatisticsChassisLevelProcStatsAllChassis Unsigned32,
        affirmedServiceconstructInterfaceAaaGroupRadiusStatisticsChassisLevelProcStatsAllNumAccessReqTx ConfdString,
        affirmedServiceconstructInterfaceAaaGroupRadiusStatisticsChassisLevelProcStatsAllNumAccessAcceptRx ConfdString,
        affirmedServiceconstructInterfaceAaaGroupRadiusStatisticsChassisLevelProcStatsAllNumAccessRejectRx ConfdString,
        affirmedServiceconstructInterfaceAaaGroupRadiusStatisticsChassisLevelProcStatsAllNumAccessChallengeRx ConfdString,
        affirmedServiceconstructInterfaceAaaGroupRadiusStatisticsChassisLevelProcStatsAllNumAccountRequestStartTx ConfdString,
        affirmedServiceconstructInterfaceAaaGroupRadiusStatisticsChassisLevelProcStatsAllNumAccountRequestStartRespRx ConfdString,
        affirmedServiceconstructInterfaceAaaGroupRadiusStatisticsChassisLevelProcStatsAllNumAccountRequestStopTx ConfdString,
        affirmedServiceconstructInterfaceAaaGroupRadiusStatisticsChassisLevelProcStatsAllNumAccountRequestStopRespRx ConfdString,
        affirmedServiceconstructInterfaceAaaGroupRadiusStatisticsChassisLevelProcStatsAllNumAccountRequestInterimUpdateTx ConfdString,
        affirmedServiceconstructInterfaceAaaGroupRadiusStatisticsChassisLevelProcStatsAllNumAccountRequestInterimUpdateRespRx ConfdString,
        affirmedServiceconstructInterfaceAaaGroupRadiusStatisticsChassisLevelProcStatsAllNumAccountRequestOnTx ConfdString,
        affirmedServiceconstructInterfaceAaaGroupRadiusStatisticsChassisLevelProcStatsAllNumAccountRequestOnRespRx ConfdString,
        affirmedServiceconstructInterfaceAaaGroupRadiusStatisticsChassisLevelProcStatsAllNumAccountRequestOffTx ConfdString,
        affirmedServiceconstructInterfaceAaaGroupRadiusStatisticsChassisLevelProcStatsAllNumAccountRequestOffRespRx ConfdString,
        affirmedServiceconstructInterfaceAaaGroupRadiusStatisticsChassisLevelProcStatsAllNumDisconnectRequestRx ConfdString,
        affirmedServiceconstructInterfaceAaaGroupRadiusStatisticsChassisLevelProcStatsAllNumDisconnectAckTx ConfdString,
        affirmedServiceconstructInterfaceAaaGroupRadiusStatisticsChassisLevelProcStatsAllNumDisconnectNackTx ConfdString,
        affirmedServiceconstructInterfaceAaaGroupRadiusStatisticsChassisLevelProcStatsAllNumCoaRequestRx ConfdString,
        affirmedServiceconstructInterfaceAaaGroupRadiusStatisticsChassisLevelProcStatsAllNumCoaAckTx ConfdString,
        affirmedServiceconstructInterfaceAaaGroupRadiusStatisticsChassisLevelProcStatsAllNumCoaNackTx ConfdString,
        affirmedServiceconstructInterfaceAaaGroupRadiusStatisticsChassisLevelProcStatsAllNumAccessRejectLocal ConfdString,
        affirmedServiceconstructInterfaceAaaGroupRadiusStatisticsChassisLevelProcStatsAllNumAccountRequestStartRejectLocal ConfdString,
        affirmedServiceconstructInterfaceAaaGroupRadiusStatisticsChassisLevelProcStatsAllNumAccountRequestStopRejectLocal ConfdString,
        affirmedServiceconstructInterfaceAaaGroupRadiusStatisticsChassisLevelProcStatsAllNumAccountRequestInterimRejectLocal ConfdString,
        affirmedServiceconstructInterfaceAaaGroupRadiusStatisticsChassisLevelProcStatsAllNumAccessReqTimeout ConfdString,
        affirmedServiceconstructInterfaceAaaGroupRadiusStatisticsChassisLevelProcStatsAllNumAccountRequestStartTimeout ConfdString,
        affirmedServiceconstructInterfaceAaaGroupRadiusStatisticsChassisLevelProcStatsAllNumAccountRequestStopTimeout ConfdString,
        affirmedServiceconstructInterfaceAaaGroupRadiusStatisticsChassisLevelProcStatsAllNumAccountRequestInterimUpdateTimeout ConfdString,
        affirmedServiceconstructInterfaceAaaGroupRadiusStatisticsChassisLevelProcStatsAllNumAccessReqReTx ConfdString,
        affirmedServiceconstructInterfaceAaaGroupRadiusStatisticsChassisLevelProcStatsAllNumAccessAcceptRcvdReTx ConfdString,
        affirmedServiceconstructInterfaceAaaGroupRadiusStatisticsChassisLevelProcStatsAllNumAccountRequestStartReTx ConfdString,
        affirmedServiceconstructInterfaceAaaGroupRadiusStatisticsChassisLevelProcStatsAllNumAccountRequestStartRespRcvdReTx ConfdString,
        affirmedServiceconstructInterfaceAaaGroupRadiusStatisticsChassisLevelProcStatsAllNumAccountRequestStopReTx ConfdString,
        affirmedServiceconstructInterfaceAaaGroupRadiusStatisticsChassisLevelProcStatsAllNumAccountRequestStopRespRcvdReTx ConfdString,
        affirmedServiceconstructInterfaceAaaGroupRadiusStatisticsChassisLevelProcStatsAllNumAccountRequestInterimUpdateReTx ConfdString,
        affirmedServiceconstructInterfaceAaaGroupRadiusStatisticsChassisLevelProcStatsAllNumAccountRequestInterimUpdateRespRcvdReTx ConfdString,
        affirmedServiceconstructInterfaceAaaGroupRadiusStatisticsChassisLevelProcStatsAllCumulativeCoaLatency ConfdString,
        affirmedServiceconstructInterfaceAaaGroupRadiusStatisticsChassisLevelProcStatsAllCoaLatencySamples Unsigned32,
        affirmedServiceconstructInterfaceAaaGroupRadiusStatisticsChassisLevelProcStatsAllAverageCoaLatency ConfdString,
        affirmedServiceconstructInterfaceAaaGroupRadiusStatisticsChassisLevelProcStatsAllCumulativeDisconnectLatency ConfdString,
        affirmedServiceconstructInterfaceAaaGroupRadiusStatisticsChassisLevelProcStatsAllDisconnectLatencySamples Unsigned32,
        affirmedServiceconstructInterfaceAaaGroupRadiusStatisticsChassisLevelProcStatsAllAverageDisconnectLatency ConfdString,
        affirmedServiceconstructInterfaceAaaGroupRadiusStatisticsChassisLevelProcStatsAllCumulativeLatency ConfdString,
        affirmedServiceconstructInterfaceAaaGroupRadiusStatisticsChassisLevelProcStatsAllLatencySamples Unsigned32,
        affirmedServiceconstructInterfaceAaaGroupRadiusStatisticsChassisLevelProcStatsAllAverageLatency ConfdString,
        affirmedServiceconstructInterfaceAaaGroupRadiusStatisticsChassisLevelProcStatsAllNumPacerNoCreditFailure ConfdString
    }

affirmedServiceconstructInterfaceAaaGroupRadiusStatisticsChassisLevelProcStatsAllChassis OBJECT-TYPE
    SYNTAX      Unsigned32
    MAX-ACCESS  not-accessible
    STATUS      current
    DESCRIPTION "chassis ID"
    ::= { affirmedServiceconstructInterfaceAaaGroupRadiusStatisticsChassisLevelProcStatsAllEntry 1 }

affirmedServiceconstructInterfaceAaaGroupRadiusStatisticsChassisLevelProcStatsAllNumAccessReqTx OBJECT-TYPE
    SYNTAX      ConfdString
    MAX-ACCESS  read-only
    STATUS      current
    DESCRIPTION "Number of Access Requests that were transmitted(excluding retransmissions)"
    ::= { affirmedServiceconstructInterfaceAaaGroupRadiusStatisticsChassisLevelProcStatsAllEntry 2 }

affirmedServiceconstructInterfaceAaaGroupRadiusStatisticsChassisLevelProcStatsAllNumAccessAcceptRx OBJECT-TYPE
    SYNTAX      ConfdString
    MAX-ACCESS  read-only
    STATUS      current
    DESCRIPTION "Number of Access Accepts received on first request itself(no retransmissions)"
    ::= { affirmedServiceconstructInterfaceAaaGroupRadiusStatisticsChassisLevelProcStatsAllEntry 3 }

affirmedServiceconstructInterfaceAaaGroupRadiusStatisticsChassisLevelProcStatsAllNumAccessRejectRx OBJECT-TYPE
    SYNTAX      ConfdString
    MAX-ACCESS  read-only
    STATUS      current
    DESCRIPTION "Number of Access Rejects received from peer"
    ::= { affirmedServiceconstructInterfaceAaaGroupRadiusStatisticsChassisLevelProcStatsAllEntry 4 }

affirmedServiceconstructInterfaceAaaGroupRadiusStatisticsChassisLevelProcStatsAllNumAccessChallengeRx OBJECT-TYPE
    SYNTAX      ConfdString
    MAX-ACCESS  read-only
    STATUS      current
    DESCRIPTION "Number of Access Challenges received from peer"
    ::= { affirmedServiceconstructInterfaceAaaGroupRadiusStatisticsChassisLevelProcStatsAllEntry 5 }

affirmedServiceconstructInterfaceAaaGroupRadiusStatisticsChassisLevelProcStatsAllNumAccountRequestStartTx OBJECT-TYPE
    SYNTAX      ConfdString
    MAX-ACCESS  read-only
    STATUS      current
    DESCRIPTION "Number of Account Request Starts that were transmitted(excluding retransmissions)"
    ::= { affirmedServiceconstructInterfaceAaaGroupRadiusStatisticsChassisLevelProcStatsAllEntry 6 }

affirmedServiceconstructInterfaceAaaGroupRadiusStatisticsChassisLevelProcStatsAllNumAccountRequestStartRespRx OBJECT-TYPE
    SYNTAX      ConfdString
    MAX-ACCESS  read-only
    STATUS      current
    DESCRIPTION "Number of Account Start Responses received on first attempted request "
    ::= { affirmedServiceconstructInterfaceAaaGroupRadiusStatisticsChassisLevelProcStatsAllEntry 7 }

affirmedServiceconstructInterfaceAaaGroupRadiusStatisticsChassisLevelProcStatsAllNumAccountRequestStopTx OBJECT-TYPE
    SYNTAX      ConfdString
    MAX-ACCESS  read-only
    STATUS      current
    DESCRIPTION "Number of Account Request Stops that were transmitted(excluding retransmissions)"
    ::= { affirmedServiceconstructInterfaceAaaGroupRadiusStatisticsChassisLevelProcStatsAllEntry 8 }

affirmedServiceconstructInterfaceAaaGroupRadiusStatisticsChassisLevelProcStatsAllNumAccountRequestStopRespRx OBJECT-TYPE
    SYNTAX      ConfdString
    MAX-ACCESS  read-only
    STATUS      current
    DESCRIPTION "Number of Account Stop Responses received on first attempted request "
    ::= { affirmedServiceconstructInterfaceAaaGroupRadiusStatisticsChassisLevelProcStatsAllEntry 9 }

affirmedServiceconstructInterfaceAaaGroupRadiusStatisticsChassisLevelProcStatsAllNumAccountRequestInterimUpdateTx OBJECT-TYPE
    SYNTAX      ConfdString
    MAX-ACCESS  read-only
    STATUS      current
    DESCRIPTION "Number of Account Request Interim Updates that were transmitted(excluding retransmissions)"
    ::= { affirmedServiceconstructInterfaceAaaGroupRadiusStatisticsChassisLevelProcStatsAllEntry 10 }

affirmedServiceconstructInterfaceAaaGroupRadiusStatisticsChassisLevelProcStatsAllNumAccountRequestInterimUpdateRespRx OBJECT-TYPE
    SYNTAX      ConfdString
    MAX-ACCESS  read-only
    STATUS      current
    DESCRIPTION "Number of Account Interim Update Responses received on first attempted request "
    ::= { affirmedServiceconstructInterfaceAaaGroupRadiusStatisticsChassisLevelProcStatsAllEntry 11 }

affirmedServiceconstructInterfaceAaaGroupRadiusStatisticsChassisLevelProcStatsAllNumAccountRequestOnTx OBJECT-TYPE
    SYNTAX      ConfdString
    MAX-ACCESS  read-only
    STATUS      current
    DESCRIPTION "Number of Account Request On sent to peer"
    ::= { affirmedServiceconstructInterfaceAaaGroupRadiusStatisticsChassisLevelProcStatsAllEntry 12 }

affirmedServiceconstructInterfaceAaaGroupRadiusStatisticsChassisLevelProcStatsAllNumAccountRequestOnRespRx OBJECT-TYPE
    SYNTAX      ConfdString
    MAX-ACCESS  read-only
    STATUS      current
    DESCRIPTION "Number of Account Request On Response received from peer"
    ::= { affirmedServiceconstructInterfaceAaaGroupRadiusStatisticsChassisLevelProcStatsAllEntry 13 }

affirmedServiceconstructInterfaceAaaGroupRadiusStatisticsChassisLevelProcStatsAllNumAccountRequestOffTx OBJECT-TYPE
    SYNTAX      ConfdString
    MAX-ACCESS  read-only
    STATUS      current
    DESCRIPTION "Number of Account Request Off sent to peer"
    ::= { affirmedServiceconstructInterfaceAaaGroupRadiusStatisticsChassisLevelProcStatsAllEntry 14 }

affirmedServiceconstructInterfaceAaaGroupRadiusStatisticsChassisLevelProcStatsAllNumAccountRequestOffRespRx OBJECT-TYPE
    SYNTAX      ConfdString
    MAX-ACCESS  read-only
    STATUS      current
    DESCRIPTION "Number of Account Request Off Response received from peer"
    ::= { affirmedServiceconstructInterfaceAaaGroupRadiusStatisticsChassisLevelProcStatsAllEntry 15 }

affirmedServiceconstructInterfaceAaaGroupRadiusStatisticsChassisLevelProcStatsAllNumDisconnectRequestRx OBJECT-TYPE
    SYNTAX      ConfdString
    MAX-ACCESS  read-only
    STATUS      current
    DESCRIPTION "Number of Disconnect Request received from peer"
    ::= { affirmedServiceconstructInterfaceAaaGroupRadiusStatisticsChassisLevelProcStatsAllEntry 16 }

affirmedServiceconstructInterfaceAaaGroupRadiusStatisticsChassisLevelProcStatsAllNumDisconnectAckTx OBJECT-TYPE
    SYNTAX      ConfdString
    MAX-ACCESS  read-only
    STATUS      current
    DESCRIPTION "Number of Disconnect ACK sent to peer"
    ::= { affirmedServiceconstructInterfaceAaaGroupRadiusStatisticsChassisLevelProcStatsAllEntry 17 }

affirmedServiceconstructInterfaceAaaGroupRadiusStatisticsChassisLevelProcStatsAllNumDisconnectNackTx OBJECT-TYPE
    SYNTAX      ConfdString
    MAX-ACCESS  read-only
    STATUS      current
    DESCRIPTION "Number of Disconnect NACK sent to peer"
    ::= { affirmedServiceconstructInterfaceAaaGroupRadiusStatisticsChassisLevelProcStatsAllEntry 18 }

affirmedServiceconstructInterfaceAaaGroupRadiusStatisticsChassisLevelProcStatsAllNumCoaRequestRx OBJECT-TYPE
    SYNTAX      ConfdString
    MAX-ACCESS  read-only
    STATUS      current
    DESCRIPTION "Number of Coa Request received from peer"
    ::= { affirmedServiceconstructInterfaceAaaGroupRadiusStatisticsChassisLevelProcStatsAllEntry 19 }

affirmedServiceconstructInterfaceAaaGroupRadiusStatisticsChassisLevelProcStatsAllNumCoaAckTx OBJECT-TYPE
    SYNTAX      ConfdString
    MAX-ACCESS  read-only
    STATUS      current
    DESCRIPTION "Number of Coa ACK sent to peer"
    ::= { affirmedServiceconstructInterfaceAaaGroupRadiusStatisticsChassisLevelProcStatsAllEntry 20 }

affirmedServiceconstructInterfaceAaaGroupRadiusStatisticsChassisLevelProcStatsAllNumCoaNackTx OBJECT-TYPE
    SYNTAX      ConfdString
    MAX-ACCESS  read-only
    STATUS      current
    DESCRIPTION "Number of Coa NACK sent to peer"
    ::= { affirmedServiceconstructInterfaceAaaGroupRadiusStatisticsChassisLevelProcStatsAllEntry 21 }

affirmedServiceconstructInterfaceAaaGroupRadiusStatisticsChassisLevelProcStatsAllNumAccessRejectLocal OBJECT-TYPE
    SYNTAX      ConfdString
    MAX-ACCESS  read-only
    STATUS      current
    DESCRIPTION "Number of Access Requests that were rejected locally"
    ::= { affirmedServiceconstructInterfaceAaaGroupRadiusStatisticsChassisLevelProcStatsAllEntry 22 }

affirmedServiceconstructInterfaceAaaGroupRadiusStatisticsChassisLevelProcStatsAllNumAccountRequestStartRejectLocal OBJECT-TYPE
    SYNTAX      ConfdString
    MAX-ACCESS  read-only
    STATUS      current
    DESCRIPTION "Number of Account Request(START) that were rejected locally"
    ::= { affirmedServiceconstructInterfaceAaaGroupRadiusStatisticsChassisLevelProcStatsAllEntry 23 }

affirmedServiceconstructInterfaceAaaGroupRadiusStatisticsChassisLevelProcStatsAllNumAccountRequestStopRejectLocal OBJECT-TYPE
    SYNTAX      ConfdString
    MAX-ACCESS  read-only
    STATUS      current
    DESCRIPTION "Number of Account Request(STOP) that were rejected locally"
    ::= { affirmedServiceconstructInterfaceAaaGroupRadiusStatisticsChassisLevelProcStatsAllEntry 24 }

affirmedServiceconstructInterfaceAaaGroupRadiusStatisticsChassisLevelProcStatsAllNumAccountRequestInterimRejectLocal OBJECT-TYPE
    SYNTAX      ConfdString
    MAX-ACCESS  read-only
    STATUS      current
    DESCRIPTION "Number of Account Request(INTERIM) that were rejected locally"
    ::= { affirmedServiceconstructInterfaceAaaGroupRadiusStatisticsChassisLevelProcStatsAllEntry 25 }

affirmedServiceconstructInterfaceAaaGroupRadiusStatisticsChassisLevelProcStatsAllNumAccessReqTimeout OBJECT-TYPE
    SYNTAX      ConfdString
    MAX-ACCESS  read-only
    STATUS      current
    DESCRIPTION "Number of Access Requests that timed out(includes retransmission timeouts)"
    ::= { affirmedServiceconstructInterfaceAaaGroupRadiusStatisticsChassisLevelProcStatsAllEntry 26 }

affirmedServiceconstructInterfaceAaaGroupRadiusStatisticsChassisLevelProcStatsAllNumAccountRequestStartTimeout OBJECT-TYPE
    SYNTAX      ConfdString
    MAX-ACCESS  read-only
    STATUS      current
    DESCRIPTION "Number of Account Request Starts that timed out(includes retransmission timeouts)"
    ::= { affirmedServiceconstructInterfaceAaaGroupRadiusStatisticsChassisLevelProcStatsAllEntry 27 }

affirmedServiceconstructInterfaceAaaGroupRadiusStatisticsChassisLevelProcStatsAllNumAccountRequestStopTimeout OBJECT-TYPE
    SYNTAX      ConfdString
    MAX-ACCESS  read-only
    STATUS      current
    DESCRIPTION "Number of Account Request Stops that timed out(includes retransmission timeouts)"
    ::= { affirmedServiceconstructInterfaceAaaGroupRadiusStatisticsChassisLevelProcStatsAllEntry 28 }

affirmedServiceconstructInterfaceAaaGroupRadiusStatisticsChassisLevelProcStatsAllNumAccountRequestInterimUpdateTimeout OBJECT-TYPE
    SYNTAX      ConfdString
    MAX-ACCESS  read-only
    STATUS      current
    DESCRIPTION "Number of Account Request Interim Updates that timed out(includes retransmission timeouts)"
    ::= { affirmedServiceconstructInterfaceAaaGroupRadiusStatisticsChassisLevelProcStatsAllEntry 29 }

affirmedServiceconstructInterfaceAaaGroupRadiusStatisticsChassisLevelProcStatsAllNumAccessReqReTx OBJECT-TYPE
    SYNTAX      ConfdString
    MAX-ACCESS  read-only
    STATUS      current
    DESCRIPTION "Number of Access Requests that were retransmitted"
    ::= { affirmedServiceconstructInterfaceAaaGroupRadiusStatisticsChassisLevelProcStatsAllEntry 30 }

affirmedServiceconstructInterfaceAaaGroupRadiusStatisticsChassisLevelProcStatsAllNumAccessAcceptRcvdReTx OBJECT-TYPE
    SYNTAX      ConfdString
    MAX-ACCESS  read-only
    STATUS      current
    DESCRIPTION "Number of Access Accepts that were received when Requests were retransmitted"
    ::= { affirmedServiceconstructInterfaceAaaGroupRadiusStatisticsChassisLevelProcStatsAllEntry 31 }

affirmedServiceconstructInterfaceAaaGroupRadiusStatisticsChassisLevelProcStatsAllNumAccountRequestStartReTx OBJECT-TYPE
    SYNTAX      ConfdString
    MAX-ACCESS  read-only
    STATUS      current
    DESCRIPTION "Number of Account Request Starts that were retransmitted"
    ::= { affirmedServiceconstructInterfaceAaaGroupRadiusStatisticsChassisLevelProcStatsAllEntry 32 }

affirmedServiceconstructInterfaceAaaGroupRadiusStatisticsChassisLevelProcStatsAllNumAccountRequestStartRespRcvdReTx OBJECT-TYPE
    SYNTAX      ConfdString
    MAX-ACCESS  read-only
    STATUS      current
    DESCRIPTION "Number of Account Request Start Responses received when requests were retransmitted "
    ::= { affirmedServiceconstructInterfaceAaaGroupRadiusStatisticsChassisLevelProcStatsAllEntry 33 }

affirmedServiceconstructInterfaceAaaGroupRadiusStatisticsChassisLevelProcStatsAllNumAccountRequestStopReTx OBJECT-TYPE
    SYNTAX      ConfdString
    MAX-ACCESS  read-only
    STATUS      current
    DESCRIPTION "Number of Account Request Stops that were retransmitted"
    ::= { affirmedServiceconstructInterfaceAaaGroupRadiusStatisticsChassisLevelProcStatsAllEntry 34 }

affirmedServiceconstructInterfaceAaaGroupRadiusStatisticsChassisLevelProcStatsAllNumAccountRequestStopRespRcvdReTx OBJECT-TYPE
    SYNTAX      ConfdString
    MAX-ACCESS  read-only
    STATUS      current
    DESCRIPTION "Number of Account Request Stop Responses received when requests were retransmitted "
    ::= { affirmedServiceconstructInterfaceAaaGroupRadiusStatisticsChassisLevelProcStatsAllEntry 35 }

affirmedServiceconstructInterfaceAaaGroupRadiusStatisticsChassisLevelProcStatsAllNumAccountRequestInterimUpdateReTx OBJECT-TYPE
    SYNTAX      ConfdString
    MAX-ACCESS  read-only
    STATUS      current
    DESCRIPTION "Number of Account Request InterimUpdates that were retransmitted"
    ::= { affirmedServiceconstructInterfaceAaaGroupRadiusStatisticsChassisLevelProcStatsAllEntry 36 }

affirmedServiceconstructInterfaceAaaGroupRadiusStatisticsChassisLevelProcStatsAllNumAccountRequestInterimUpdateRespRcvdReTx OBJECT-TYPE
    SYNTAX      ConfdString
    MAX-ACCESS  read-only
    STATUS      current
    DESCRIPTION "Number of Account Request Interim Update Responses received when requests were retransmitted "
    ::= { affirmedServiceconstructInterfaceAaaGroupRadiusStatisticsChassisLevelProcStatsAllEntry 37 }

affirmedServiceconstructInterfaceAaaGroupRadiusStatisticsChassisLevelProcStatsAllCumulativeCoaLatency OBJECT-TYPE
    SYNTAX      ConfdString
    MAX-ACCESS  read-only
    STATUS      current
    DESCRIPTION "Cumulative Latency in microseconds for RADIUS CoA messages"
    ::= { affirmedServiceconstructInterfaceAaaGroupRadiusStatisticsChassisLevelProcStatsAllEntry 38 }

affirmedServiceconstructInterfaceAaaGroupRadiusStatisticsChassisLevelProcStatsAllCoaLatencySamples OBJECT-TYPE
    SYNTAX      Unsigned32
    MAX-ACCESS  read-only
    STATUS      current
    DESCRIPTION "Samples for calculating average latency for RADIUS CoA messages"
    ::= { affirmedServiceconstructInterfaceAaaGroupRadiusStatisticsChassisLevelProcStatsAllEntry 39 }

affirmedServiceconstructInterfaceAaaGroupRadiusStatisticsChassisLevelProcStatsAllAverageCoaLatency OBJECT-TYPE
    SYNTAX      ConfdString
    MAX-ACCESS  read-only
    STATUS      current
    DESCRIPTION "Average Latency in microseconds for RADIUS CoA"
    ::= { affirmedServiceconstructInterfaceAaaGroupRadiusStatisticsChassisLevelProcStatsAllEntry 40 }

affirmedServiceconstructInterfaceAaaGroupRadiusStatisticsChassisLevelProcStatsAllCumulativeDisconnectLatency OBJECT-TYPE
    SYNTAX      ConfdString
    MAX-ACCESS  read-only
    STATUS      current
    DESCRIPTION "Cumulative Latency in microseconds for RADIUS Disconnect messages"
    ::= { affirmedServiceconstructInterfaceAaaGroupRadiusStatisticsChassisLevelProcStatsAllEntry 41 }

affirmedServiceconstructInterfaceAaaGroupRadiusStatisticsChassisLevelProcStatsAllDisconnectLatencySamples OBJECT-TYPE
    SYNTAX      Unsigned32
    MAX-ACCESS  read-only
    STATUS      current
    DESCRIPTION "Samples for calculating average latency for RADIUS Disconnect messages"
    ::= { affirmedServiceconstructInterfaceAaaGroupRadiusStatisticsChassisLevelProcStatsAllEntry 42 }

affirmedServiceconstructInterfaceAaaGroupRadiusStatisticsChassisLevelProcStatsAllAverageDisconnectLatency OBJECT-TYPE
    SYNTAX      ConfdString
    MAX-ACCESS  read-only
    STATUS      current
    DESCRIPTION "Average Latency in microseconds for RADIUS Disconnect"
    ::= { affirmedServiceconstructInterfaceAaaGroupRadiusStatisticsChassisLevelProcStatsAllEntry 43 }

affirmedServiceconstructInterfaceAaaGroupRadiusStatisticsChassisLevelProcStatsAllCumulativeLatency OBJECT-TYPE
    SYNTAX      ConfdString
    MAX-ACCESS  read-only
    STATUS      current
    DESCRIPTION "Cumulative Latency in microseconds for RADIUS messages"
    ::= { affirmedServiceconstructInterfaceAaaGroupRadiusStatisticsChassisLevelProcStatsAllEntry 44 }

affirmedServiceconstructInterfaceAaaGroupRadiusStatisticsChassisLevelProcStatsAllLatencySamples OBJECT-TYPE
    SYNTAX      Unsigned32
    MAX-ACCESS  read-only
    STATUS      current
    DESCRIPTION "Samples for calculating average latency for RADIUS messages"
    ::= { affirmedServiceconstructInterfaceAaaGroupRadiusStatisticsChassisLevelProcStatsAllEntry 45 }

affirmedServiceconstructInterfaceAaaGroupRadiusStatisticsChassisLevelProcStatsAllAverageLatency OBJECT-TYPE
    SYNTAX      ConfdString
    MAX-ACCESS  read-only
    STATUS      current
    DESCRIPTION "Average Latency in microseconds for RADIUS messages"
    ::= { affirmedServiceconstructInterfaceAaaGroupRadiusStatisticsChassisLevelProcStatsAllEntry 46 }

affirmedServiceconstructInterfaceAaaGroupRadiusStatisticsChassisLevelProcStatsAllNumPacerNoCreditFailure OBJECT-TYPE
    SYNTAX      ConfdString
    MAX-ACCESS  read-only
    STATUS      current
    DESCRIPTION "Number of failures for no credit"
    ::= { affirmedServiceconstructInterfaceAaaGroupRadiusStatisticsChassisLevelProcStatsAllEntry 47 }

affirmedServiceconstructInterfaceAaaGroupRadiusStatisticsChassisLevelProcStatsPeerTable OBJECT-TYPE
    SYNTAX      SEQUENCE OF AffirmedServiceconstructInterfaceAaaGroupRadiusStatisticsChassisLevelProcStatsPeerEntry
    MAX-ACCESS  not-accessible
    STATUS      current
    DESCRIPTION ""
    ::= { affirmedServiceconstructInterfaceAaaGroupRadiusStatisticsChassisLevelProcStats 2 }

affirmedServiceconstructInterfaceAaaGroupRadiusStatisticsChassisLevelProcStatsPeerEntry OBJECT-TYPE
    SYNTAX      AffirmedServiceconstructInterfaceAaaGroupRadiusStatisticsChassisLevelProcStatsPeerEntry
    MAX-ACCESS  not-accessible
    STATUS      current
    DESCRIPTION ""
    INDEX { affirmedServiceconstructInterfaceAaaGroupRadiusStatisticsChassisLevelProcStatsPeerName, affirmedServiceconstructInterfaceAaaGroupRadiusStatisticsChassisLevelProcStatsPeerChassis }
        ::= { affirmedServiceconstructInterfaceAaaGroupRadiusStatisticsChassisLevelProcStatsPeerTable 1 }

AffirmedServiceconstructInterfaceAaaGroupRadiusStatisticsChassisLevelProcStatsPeerEntry ::=
    SEQUENCE {
        affirmedServiceconstructInterfaceAaaGroupRadiusStatisticsChassisLevelProcStatsPeerName String,
        affirmedServiceconstructInterfaceAaaGroupRadiusStatisticsChassisLevelProcStatsPeerChassis Unsigned32,
        affirmedServiceconstructInterfaceAaaGroupRadiusStatisticsChassisLevelProcStatsPeerNumAccessReqTx ConfdString,
        affirmedServiceconstructInterfaceAaaGroupRadiusStatisticsChassisLevelProcStatsPeerNumAccessAcceptRx ConfdString,
        affirmedServiceconstructInterfaceAaaGroupRadiusStatisticsChassisLevelProcStatsPeerNumAccessRejectRx ConfdString,
        affirmedServiceconstructInterfaceAaaGroupRadiusStatisticsChassisLevelProcStatsPeerNumAccessChallengeRx ConfdString,
        affirmedServiceconstructInterfaceAaaGroupRadiusStatisticsChassisLevelProcStatsPeerNumAccountRequestStartTx ConfdString,
        affirmedServiceconstructInterfaceAaaGroupRadiusStatisticsChassisLevelProcStatsPeerNumAccountRequestStartRespRx ConfdString,
        affirmedServiceconstructInterfaceAaaGroupRadiusStatisticsChassisLevelProcStatsPeerNumAccountRequestStopTx ConfdString,
        affirmedServiceconstructInterfaceAaaGroupRadiusStatisticsChassisLevelProcStatsPeerNumAccountRequestStopRespRx ConfdString,
        affirmedServiceconstructInterfaceAaaGroupRadiusStatisticsChassisLevelProcStatsPeerNumAccountRequestInterimUpdateTx ConfdString,
        affirmedServiceconstructInterfaceAaaGroupRadiusStatisticsChassisLevelProcStatsPeerNumAccountRequestInterimUpdateRespRx ConfdString,
        affirmedServiceconstructInterfaceAaaGroupRadiusStatisticsChassisLevelProcStatsPeerNumAccountRequestOnTx ConfdString,
        affirmedServiceconstructInterfaceAaaGroupRadiusStatisticsChassisLevelProcStatsPeerNumAccountRequestOnRespRx ConfdString,
        affirmedServiceconstructInterfaceAaaGroupRadiusStatisticsChassisLevelProcStatsPeerNumAccountRequestOffTx ConfdString,
        affirmedServiceconstructInterfaceAaaGroupRadiusStatisticsChassisLevelProcStatsPeerNumAccountRequestOffRespRx ConfdString,
        affirmedServiceconstructInterfaceAaaGroupRadiusStatisticsChassisLevelProcStatsPeerNumDisconnectRequestRx ConfdString,
        affirmedServiceconstructInterfaceAaaGroupRadiusStatisticsChassisLevelProcStatsPeerNumDisconnectAckTx ConfdString,
        affirmedServiceconstructInterfaceAaaGroupRadiusStatisticsChassisLevelProcStatsPeerNumDisconnectNackTx ConfdString,
        affirmedServiceconstructInterfaceAaaGroupRadiusStatisticsChassisLevelProcStatsPeerNumCoaRequestRx ConfdString,
        affirmedServiceconstructInterfaceAaaGroupRadiusStatisticsChassisLevelProcStatsPeerNumCoaAckTx ConfdString,
        affirmedServiceconstructInterfaceAaaGroupRadiusStatisticsChassisLevelProcStatsPeerNumCoaNackTx ConfdString,
        affirmedServiceconstructInterfaceAaaGroupRadiusStatisticsChassisLevelProcStatsPeerNumAccessRejectLocal ConfdString,
        affirmedServiceconstructInterfaceAaaGroupRadiusStatisticsChassisLevelProcStatsPeerNumAccountRequestStartRejectLocal ConfdString,
        affirmedServiceconstructInterfaceAaaGroupRadiusStatisticsChassisLevelProcStatsPeerNumAccountRequestStopRejectLocal ConfdString,
        affirmedServiceconstructInterfaceAaaGroupRadiusStatisticsChassisLevelProcStatsPeerNumAccountRequestInterimRejectLocal ConfdString,
        affirmedServiceconstructInterfaceAaaGroupRadiusStatisticsChassisLevelProcStatsPeerNumAccessReqTimeout ConfdString,
        affirmedServiceconstructInterfaceAaaGroupRadiusStatisticsChassisLevelProcStatsPeerNumAccountRequestStartTimeout ConfdString,
        affirmedServiceconstructInterfaceAaaGroupRadiusStatisticsChassisLevelProcStatsPeerNumAccountRequestStopTimeout ConfdString,
        affirmedServiceconstructInterfaceAaaGroupRadiusStatisticsChassisLevelProcStatsPeerNumAccountRequestInterimUpdateTimeout ConfdString,
        affirmedServiceconstructInterfaceAaaGroupRadiusStatisticsChassisLevelProcStatsPeerNumAccessReqReTx ConfdString,
        affirmedServiceconstructInterfaceAaaGroupRadiusStatisticsChassisLevelProcStatsPeerNumAccessAcceptRcvdReTx ConfdString,
        affirmedServiceconstructInterfaceAaaGroupRadiusStatisticsChassisLevelProcStatsPeerNumAccountRequestStartReTx ConfdString,
        affirmedServiceconstructInterfaceAaaGroupRadiusStatisticsChassisLevelProcStatsPeerNumAccountRequestStartRespRcvdReTx ConfdString,
        affirmedServiceconstructInterfaceAaaGroupRadiusStatisticsChassisLevelProcStatsPeerNumAccountRequestStopReTx ConfdString,
        affirmedServiceconstructInterfaceAaaGroupRadiusStatisticsChassisLevelProcStatsPeerNumAccountRequestStopRespRcvdReTx ConfdString,
        affirmedServiceconstructInterfaceAaaGroupRadiusStatisticsChassisLevelProcStatsPeerNumAccountRequestInterimUpdateReTx ConfdString,
        affirmedServiceconstructInterfaceAaaGroupRadiusStatisticsChassisLevelProcStatsPeerNumAccountRequestInterimUpdateRespRcvdReTx ConfdString,
        affirmedServiceconstructInterfaceAaaGroupRadiusStatisticsChassisLevelProcStatsPeerCumulativeCoaLatency ConfdString,
        affirmedServiceconstructInterfaceAaaGroupRadiusStatisticsChassisLevelProcStatsPeerCoaLatencySamples Unsigned32,
        affirmedServiceconstructInterfaceAaaGroupRadiusStatisticsChassisLevelProcStatsPeerAverageCoaLatency ConfdString,
        affirmedServiceconstructInterfaceAaaGroupRadiusStatisticsChassisLevelProcStatsPeerCumulativeDisconnectLatency ConfdString,
        affirmedServiceconstructInterfaceAaaGroupRadiusStatisticsChassisLevelProcStatsPeerDisconnectLatencySamples Unsigned32,
        affirmedServiceconstructInterfaceAaaGroupRadiusStatisticsChassisLevelProcStatsPeerAverageDisconnectLatency ConfdString,
        affirmedServiceconstructInterfaceAaaGroupRadiusStatisticsChassisLevelProcStatsPeerCumulativeLatency ConfdString,
        affirmedServiceconstructInterfaceAaaGroupRadiusStatisticsChassisLevelProcStatsPeerLatencySamples Unsigned32,
        affirmedServiceconstructInterfaceAaaGroupRadiusStatisticsChassisLevelProcStatsPeerAverageLatency ConfdString,
        affirmedServiceconstructInterfaceAaaGroupRadiusStatisticsChassisLevelProcStatsPeerNumPacerNoCreditFailure ConfdString
    }

affirmedServiceconstructInterfaceAaaGroupRadiusStatisticsChassisLevelProcStatsPeerName OBJECT-TYPE
    SYNTAX      String
    MAX-ACCESS  not-accessible
    STATUS      current
    DESCRIPTION "Peer Stats Table Name"
    ::= { affirmedServiceconstructInterfaceAaaGroupRadiusStatisticsChassisLevelProcStatsPeerEntry 1 }

affirmedServiceconstructInterfaceAaaGroupRadiusStatisticsChassisLevelProcStatsPeerChassis OBJECT-TYPE
    SYNTAX      Unsigned32
    MAX-ACCESS  not-accessible
    STATUS      current
    DESCRIPTION "chassis ID"
    ::= { affirmedServiceconstructInterfaceAaaGroupRadiusStatisticsChassisLevelProcStatsPeerEntry 2 }

affirmedServiceconstructInterfaceAaaGroupRadiusStatisticsChassisLevelProcStatsPeerNumAccessReqTx OBJECT-TYPE
    SYNTAX      ConfdString
    MAX-ACCESS  read-only
    STATUS      current
    DESCRIPTION "Number of Access Requests that were transmitted(excluding retransmissions)"
    ::= { affirmedServiceconstructInterfaceAaaGroupRadiusStatisticsChassisLevelProcStatsPeerEntry 3 }

affirmedServiceconstructInterfaceAaaGroupRadiusStatisticsChassisLevelProcStatsPeerNumAccessAcceptRx OBJECT-TYPE
    SYNTAX      ConfdString
    MAX-ACCESS  read-only
    STATUS      current
    DESCRIPTION "Number of Access Accepts received on first request itself(no retransmissions)"
    ::= { affirmedServiceconstructInterfaceAaaGroupRadiusStatisticsChassisLevelProcStatsPeerEntry 4 }

affirmedServiceconstructInterfaceAaaGroupRadiusStatisticsChassisLevelProcStatsPeerNumAccessRejectRx OBJECT-TYPE
    SYNTAX      ConfdString
    MAX-ACCESS  read-only
    STATUS      current
    DESCRIPTION "Number of Access Rejects received from peer"
    ::= { affirmedServiceconstructInterfaceAaaGroupRadiusStatisticsChassisLevelProcStatsPeerEntry 5 }

affirmedServiceconstructInterfaceAaaGroupRadiusStatisticsChassisLevelProcStatsPeerNumAccessChallengeRx OBJECT-TYPE
    SYNTAX      ConfdString
    MAX-ACCESS  read-only
    STATUS      current
    DESCRIPTION "Number of Access Challenges received from peer"
    ::= { affirmedServiceconstructInterfaceAaaGroupRadiusStatisticsChassisLevelProcStatsPeerEntry 6 }

affirmedServiceconstructInterfaceAaaGroupRadiusStatisticsChassisLevelProcStatsPeerNumAccountRequestStartTx OBJECT-TYPE
    SYNTAX      ConfdString
    MAX-ACCESS  read-only
    STATUS      current
    DESCRIPTION "Number of Account Request Starts that were transmitted(excluding retransmissions)"
    ::= { affirmedServiceconstructInterfaceAaaGroupRadiusStatisticsChassisLevelProcStatsPeerEntry 7 }

affirmedServiceconstructInterfaceAaaGroupRadiusStatisticsChassisLevelProcStatsPeerNumAccountRequestStartRespRx OBJECT-TYPE
    SYNTAX      ConfdString
    MAX-ACCESS  read-only
    STATUS      current
    DESCRIPTION "Number of Account Start Responses received on first attempted request "
    ::= { affirmedServiceconstructInterfaceAaaGroupRadiusStatisticsChassisLevelProcStatsPeerEntry 8 }

affirmedServiceconstructInterfaceAaaGroupRadiusStatisticsChassisLevelProcStatsPeerNumAccountRequestStopTx OBJECT-TYPE
    SYNTAX      ConfdString
    MAX-ACCESS  read-only
    STATUS      current
    DESCRIPTION "Number of Account Request Stops that were transmitted(excluding retransmissions)"
    ::= { affirmedServiceconstructInterfaceAaaGroupRadiusStatisticsChassisLevelProcStatsPeerEntry 9 }

affirmedServiceconstructInterfaceAaaGroupRadiusStatisticsChassisLevelProcStatsPeerNumAccountRequestStopRespRx OBJECT-TYPE
    SYNTAX      ConfdString
    MAX-ACCESS  read-only
    STATUS      current
    DESCRIPTION "Number of Account Stop Responses received on first attempted request "
    ::= { affirmedServiceconstructInterfaceAaaGroupRadiusStatisticsChassisLevelProcStatsPeerEntry 10 }

affirmedServiceconstructInterfaceAaaGroupRadiusStatisticsChassisLevelProcStatsPeerNumAccountRequestInterimUpdateTx OBJECT-TYPE
    SYNTAX      ConfdString
    MAX-ACCESS  read-only
    STATUS      current
    DESCRIPTION "Number of Account Request Interim Updates that were transmitted(excluding retransmissions)"
    ::= { affirmedServiceconstructInterfaceAaaGroupRadiusStatisticsChassisLevelProcStatsPeerEntry 11 }

affirmedServiceconstructInterfaceAaaGroupRadiusStatisticsChassisLevelProcStatsPeerNumAccountRequestInterimUpdateRespRx OBJECT-TYPE
    SYNTAX      ConfdString
    MAX-ACCESS  read-only
    STATUS      current
    DESCRIPTION "Number of Account Interim Update Responses received on first attempted request "
    ::= { affirmedServiceconstructInterfaceAaaGroupRadiusStatisticsChassisLevelProcStatsPeerEntry 12 }

affirmedServiceconstructInterfaceAaaGroupRadiusStatisticsChassisLevelProcStatsPeerNumAccountRequestOnTx OBJECT-TYPE
    SYNTAX      ConfdString
    MAX-ACCESS  read-only
    STATUS      current
    DESCRIPTION "Number of Account Request On sent to peer"
    ::= { affirmedServiceconstructInterfaceAaaGroupRadiusStatisticsChassisLevelProcStatsPeerEntry 13 }

affirmedServiceconstructInterfaceAaaGroupRadiusStatisticsChassisLevelProcStatsPeerNumAccountRequestOnRespRx OBJECT-TYPE
    SYNTAX      ConfdString
    MAX-ACCESS  read-only
    STATUS      current
    DESCRIPTION "Number of Account Request On Response received from peer"
    ::= { affirmedServiceconstructInterfaceAaaGroupRadiusStatisticsChassisLevelProcStatsPeerEntry 14 }

affirmedServiceconstructInterfaceAaaGroupRadiusStatisticsChassisLevelProcStatsPeerNumAccountRequestOffTx OBJECT-TYPE
    SYNTAX      ConfdString
    MAX-ACCESS  read-only
    STATUS      current
    DESCRIPTION "Number of Account Request Off sent to peer"
    ::= { affirmedServiceconstructInterfaceAaaGroupRadiusStatisticsChassisLevelProcStatsPeerEntry 15 }

affirmedServiceconstructInterfaceAaaGroupRadiusStatisticsChassisLevelProcStatsPeerNumAccountRequestOffRespRx OBJECT-TYPE
    SYNTAX      ConfdString
    MAX-ACCESS  read-only
    STATUS      current
    DESCRIPTION "Number of Account Request Off Response received from peer"
    ::= { affirmedServiceconstructInterfaceAaaGroupRadiusStatisticsChassisLevelProcStatsPeerEntry 16 }

affirmedServiceconstructInterfaceAaaGroupRadiusStatisticsChassisLevelProcStatsPeerNumDisconnectRequestRx OBJECT-TYPE
    SYNTAX      ConfdString
    MAX-ACCESS  read-only
    STATUS      current
    DESCRIPTION "Number of Disconnect Request received from peer"
    ::= { affirmedServiceconstructInterfaceAaaGroupRadiusStatisticsChassisLevelProcStatsPeerEntry 17 }

affirmedServiceconstructInterfaceAaaGroupRadiusStatisticsChassisLevelProcStatsPeerNumDisconnectAckTx OBJECT-TYPE
    SYNTAX      ConfdString
    MAX-ACCESS  read-only
    STATUS      current
    DESCRIPTION "Number of Disconnect ACK sent to peer"
    ::= { affirmedServiceconstructInterfaceAaaGroupRadiusStatisticsChassisLevelProcStatsPeerEntry 18 }

affirmedServiceconstructInterfaceAaaGroupRadiusStatisticsChassisLevelProcStatsPeerNumDisconnectNackTx OBJECT-TYPE
    SYNTAX      ConfdString
    MAX-ACCESS  read-only
    STATUS      current
    DESCRIPTION "Number of Disconnect NACK sent to peer"
    ::= { affirmedServiceconstructInterfaceAaaGroupRadiusStatisticsChassisLevelProcStatsPeerEntry 19 }

affirmedServiceconstructInterfaceAaaGroupRadiusStatisticsChassisLevelProcStatsPeerNumCoaRequestRx OBJECT-TYPE
    SYNTAX      ConfdString
    MAX-ACCESS  read-only
    STATUS      current
    DESCRIPTION "Number of Coa Request received from peer"
    ::= { affirmedServiceconstructInterfaceAaaGroupRadiusStatisticsChassisLevelProcStatsPeerEntry 20 }

affirmedServiceconstructInterfaceAaaGroupRadiusStatisticsChassisLevelProcStatsPeerNumCoaAckTx OBJECT-TYPE
    SYNTAX      ConfdString
    MAX-ACCESS  read-only
    STATUS      current
    DESCRIPTION "Number of Coa ACK sent to peer"
    ::= { affirmedServiceconstructInterfaceAaaGroupRadiusStatisticsChassisLevelProcStatsPeerEntry 21 }

affirmedServiceconstructInterfaceAaaGroupRadiusStatisticsChassisLevelProcStatsPeerNumCoaNackTx OBJECT-TYPE
    SYNTAX      ConfdString
    MAX-ACCESS  read-only
    STATUS      current
    DESCRIPTION "Number of Coa NACK sent to peer"
    ::= { affirmedServiceconstructInterfaceAaaGroupRadiusStatisticsChassisLevelProcStatsPeerEntry 22 }

affirmedServiceconstructInterfaceAaaGroupRadiusStatisticsChassisLevelProcStatsPeerNumAccessRejectLocal OBJECT-TYPE
    SYNTAX      ConfdString
    MAX-ACCESS  read-only
    STATUS      current
    DESCRIPTION "Number of Access Requests that were rejected locally"
    ::= { affirmedServiceconstructInterfaceAaaGroupRadiusStatisticsChassisLevelProcStatsPeerEntry 23 }

affirmedServiceconstructInterfaceAaaGroupRadiusStatisticsChassisLevelProcStatsPeerNumAccountRequestStartRejectLocal OBJECT-TYPE
    SYNTAX      ConfdString
    MAX-ACCESS  read-only
    STATUS      current
    DESCRIPTION "Number of Account Request(START) that were rejected locally"
    ::= { affirmedServiceconstructInterfaceAaaGroupRadiusStatisticsChassisLevelProcStatsPeerEntry 24 }

affirmedServiceconstructInterfaceAaaGroupRadiusStatisticsChassisLevelProcStatsPeerNumAccountRequestStopRejectLocal OBJECT-TYPE
    SYNTAX      ConfdString
    MAX-ACCESS  read-only
    STATUS      current
    DESCRIPTION "Number of Account Request(STOP) that were rejected locally"
    ::= { affirmedServiceconstructInterfaceAaaGroupRadiusStatisticsChassisLevelProcStatsPeerEntry 25 }

affirmedServiceconstructInterfaceAaaGroupRadiusStatisticsChassisLevelProcStatsPeerNumAccountRequestInterimRejectLocal OBJECT-TYPE
    SYNTAX      ConfdString
    MAX-ACCESS  read-only
    STATUS      current
    DESCRIPTION "Number of Account Request(INTERIM) that were rejected locally"
    ::= { affirmedServiceconstructInterfaceAaaGroupRadiusStatisticsChassisLevelProcStatsPeerEntry 26 }

affirmedServiceconstructInterfaceAaaGroupRadiusStatisticsChassisLevelProcStatsPeerNumAccessReqTimeout OBJECT-TYPE
    SYNTAX      ConfdString
    MAX-ACCESS  read-only
    STATUS      current
    DESCRIPTION "Number of Access Requests that timed out(includes retransmission timeouts)"
    ::= { affirmedServiceconstructInterfaceAaaGroupRadiusStatisticsChassisLevelProcStatsPeerEntry 27 }

affirmedServiceconstructInterfaceAaaGroupRadiusStatisticsChassisLevelProcStatsPeerNumAccountRequestStartTimeout OBJECT-TYPE
    SYNTAX      ConfdString
    MAX-ACCESS  read-only
    STATUS      current
    DESCRIPTION "Number of Account Request Starts that timed out(includes retransmission timeouts)"
    ::= { affirmedServiceconstructInterfaceAaaGroupRadiusStatisticsChassisLevelProcStatsPeerEntry 28 }

affirmedServiceconstructInterfaceAaaGroupRadiusStatisticsChassisLevelProcStatsPeerNumAccountRequestStopTimeout OBJECT-TYPE
    SYNTAX      ConfdString
    MAX-ACCESS  read-only
    STATUS      current
    DESCRIPTION "Number of Account Request Stops that timed out(includes retransmission timeouts)"
    ::= { affirmedServiceconstructInterfaceAaaGroupRadiusStatisticsChassisLevelProcStatsPeerEntry 29 }

affirmedServiceconstructInterfaceAaaGroupRadiusStatisticsChassisLevelProcStatsPeerNumAccountRequestInterimUpdateTimeout OBJECT-TYPE
    SYNTAX      ConfdString
    MAX-ACCESS  read-only
    STATUS      current
    DESCRIPTION "Number of Account Request Interim Updates that timed out(includes retransmission timeouts)"
    ::= { affirmedServiceconstructInterfaceAaaGroupRadiusStatisticsChassisLevelProcStatsPeerEntry 30 }

affirmedServiceconstructInterfaceAaaGroupRadiusStatisticsChassisLevelProcStatsPeerNumAccessReqReTx OBJECT-TYPE
    SYNTAX      ConfdString
    MAX-ACCESS  read-only
    STATUS      current
    DESCRIPTION "Number of Access Requests that were retransmitted"
    ::= { affirmedServiceconstructInterfaceAaaGroupRadiusStatisticsChassisLevelProcStatsPeerEntry 31 }

affirmedServiceconstructInterfaceAaaGroupRadiusStatisticsChassisLevelProcStatsPeerNumAccessAcceptRcvdReTx OBJECT-TYPE
    SYNTAX      ConfdString
    MAX-ACCESS  read-only
    STATUS      current
    DESCRIPTION "Number of Access Accepts that were received when Requests were retransmitted"
    ::= { affirmedServiceconstructInterfaceAaaGroupRadiusStatisticsChassisLevelProcStatsPeerEntry 32 }

affirmedServiceconstructInterfaceAaaGroupRadiusStatisticsChassisLevelProcStatsPeerNumAccountRequestStartReTx OBJECT-TYPE
    SYNTAX      ConfdString
    MAX-ACCESS  read-only
    STATUS      current
    DESCRIPTION "Number of Account Request Starts that were retransmitted"
    ::= { affirmedServiceconstructInterfaceAaaGroupRadiusStatisticsChassisLevelProcStatsPeerEntry 33 }

affirmedServiceconstructInterfaceAaaGroupRadiusStatisticsChassisLevelProcStatsPeerNumAccountRequestStartRespRcvdReTx OBJECT-TYPE
    SYNTAX      ConfdString
    MAX-ACCESS  read-only
    STATUS      current
    DESCRIPTION "Number of Account Request Start Responses received when requests were retransmitted "
    ::= { affirmedServiceconstructInterfaceAaaGroupRadiusStatisticsChassisLevelProcStatsPeerEntry 34 }

affirmedServiceconstructInterfaceAaaGroupRadiusStatisticsChassisLevelProcStatsPeerNumAccountRequestStopReTx OBJECT-TYPE
    SYNTAX      ConfdString
    MAX-ACCESS  read-only
    STATUS      current
    DESCRIPTION "Number of Account Request Stops that were retransmitted"
    ::= { affirmedServiceconstructInterfaceAaaGroupRadiusStatisticsChassisLevelProcStatsPeerEntry 35 }

affirmedServiceconstructInterfaceAaaGroupRadiusStatisticsChassisLevelProcStatsPeerNumAccountRequestStopRespRcvdReTx OBJECT-TYPE
    SYNTAX      ConfdString
    MAX-ACCESS  read-only
    STATUS      current
    DESCRIPTION "Number of Account Request Stop Responses received when requests were retransmitted "
    ::= { affirmedServiceconstructInterfaceAaaGroupRadiusStatisticsChassisLevelProcStatsPeerEntry 36 }

affirmedServiceconstructInterfaceAaaGroupRadiusStatisticsChassisLevelProcStatsPeerNumAccountRequestInterimUpdateReTx OBJECT-TYPE
    SYNTAX      ConfdString
    MAX-ACCESS  read-only
    STATUS      current
    DESCRIPTION "Number of Account Request InterimUpdates that were retransmitted"
    ::= { affirmedServiceconstructInterfaceAaaGroupRadiusStatisticsChassisLevelProcStatsPeerEntry 37 }

affirmedServiceconstructInterfaceAaaGroupRadiusStatisticsChassisLevelProcStatsPeerNumAccountRequestInterimUpdateRespRcvdReTx OBJECT-TYPE
    SYNTAX      ConfdString
    MAX-ACCESS  read-only
    STATUS      current
    DESCRIPTION "Number of Account Request Interim Update Responses received when requests were retransmitted "
    ::= { affirmedServiceconstructInterfaceAaaGroupRadiusStatisticsChassisLevelProcStatsPeerEntry 38 }

affirmedServiceconstructInterfaceAaaGroupRadiusStatisticsChassisLevelProcStatsPeerCumulativeCoaLatency OBJECT-TYPE
    SYNTAX      ConfdString
    MAX-ACCESS  read-only
    STATUS      current
    DESCRIPTION "Cumulative Latency in microseconds for RADIUS CoA messages"
    ::= { affirmedServiceconstructInterfaceAaaGroupRadiusStatisticsChassisLevelProcStatsPeerEntry 39 }

affirmedServiceconstructInterfaceAaaGroupRadiusStatisticsChassisLevelProcStatsPeerCoaLatencySamples OBJECT-TYPE
    SYNTAX      Unsigned32
    MAX-ACCESS  read-only
    STATUS      current
    DESCRIPTION "Samples for calculating average latency for RADIUS CoA messages"
    ::= { affirmedServiceconstructInterfaceAaaGroupRadiusStatisticsChassisLevelProcStatsPeerEntry 40 }

affirmedServiceconstructInterfaceAaaGroupRadiusStatisticsChassisLevelProcStatsPeerAverageCoaLatency OBJECT-TYPE
    SYNTAX      ConfdString
    MAX-ACCESS  read-only
    STATUS      current
    DESCRIPTION "Average Latency in microseconds for RADIUS CoA"
    ::= { affirmedServiceconstructInterfaceAaaGroupRadiusStatisticsChassisLevelProcStatsPeerEntry 41 }

affirmedServiceconstructInterfaceAaaGroupRadiusStatisticsChassisLevelProcStatsPeerCumulativeDisconnectLatency OBJECT-TYPE
    SYNTAX      ConfdString
    MAX-ACCESS  read-only
    STATUS      current
    DESCRIPTION "Cumulative Latency in microseconds for RADIUS Disconnect messages"
    ::= { affirmedServiceconstructInterfaceAaaGroupRadiusStatisticsChassisLevelProcStatsPeerEntry 42 }

affirmedServiceconstructInterfaceAaaGroupRadiusStatisticsChassisLevelProcStatsPeerDisconnectLatencySamples OBJECT-TYPE
    SYNTAX      Unsigned32
    MAX-ACCESS  read-only
    STATUS      current
    DESCRIPTION "Samples for calculating average latency for RADIUS Disconnect messages"
    ::= { affirmedServiceconstructInterfaceAaaGroupRadiusStatisticsChassisLevelProcStatsPeerEntry 43 }

affirmedServiceconstructInterfaceAaaGroupRadiusStatisticsChassisLevelProcStatsPeerAverageDisconnectLatency OBJECT-TYPE
    SYNTAX      ConfdString
    MAX-ACCESS  read-only
    STATUS      current
    DESCRIPTION "Average Latency in microseconds for RADIUS Disconnect"
    ::= { affirmedServiceconstructInterfaceAaaGroupRadiusStatisticsChassisLevelProcStatsPeerEntry 44 }

affirmedServiceconstructInterfaceAaaGroupRadiusStatisticsChassisLevelProcStatsPeerCumulativeLatency OBJECT-TYPE
    SYNTAX      ConfdString
    MAX-ACCESS  read-only
    STATUS      current
    DESCRIPTION "Cumulative Latency in microseconds for RADIUS messages"
    ::= { affirmedServiceconstructInterfaceAaaGroupRadiusStatisticsChassisLevelProcStatsPeerEntry 45 }

affirmedServiceconstructInterfaceAaaGroupRadiusStatisticsChassisLevelProcStatsPeerLatencySamples OBJECT-TYPE
    SYNTAX      Unsigned32
    MAX-ACCESS  read-only
    STATUS      current
    DESCRIPTION "Samples for calculating average latency for RADIUS messages"
    ::= { affirmedServiceconstructInterfaceAaaGroupRadiusStatisticsChassisLevelProcStatsPeerEntry 46 }

affirmedServiceconstructInterfaceAaaGroupRadiusStatisticsChassisLevelProcStatsPeerAverageLatency OBJECT-TYPE
    SYNTAX      ConfdString
    MAX-ACCESS  read-only
    STATUS      current
    DESCRIPTION "Average Latency in microseconds for RADIUS messages"
    ::= { affirmedServiceconstructInterfaceAaaGroupRadiusStatisticsChassisLevelProcStatsPeerEntry 47 }

affirmedServiceconstructInterfaceAaaGroupRadiusStatisticsChassisLevelProcStatsPeerNumPacerNoCreditFailure OBJECT-TYPE
    SYNTAX      ConfdString
    MAX-ACCESS  read-only
    STATUS      current
    DESCRIPTION "Number of failures for no credit"
    ::= { affirmedServiceconstructInterfaceAaaGroupRadiusStatisticsChassisLevelProcStatsPeerEntry 48 }

affirmedServiceconstructInterfaceAaaGroupRadiusStatisticsSlotLevelProcStatsAllTable OBJECT-TYPE
    SYNTAX      SEQUENCE OF AffirmedServiceconstructInterfaceAaaGroupRadiusStatisticsSlotLevelProcStatsAllEntry
    MAX-ACCESS  not-accessible
    STATUS      current
    DESCRIPTION ""
    ::= { affirmedServiceconstructInterfaceAaaGroupRadiusStatisticsSlotLevelProcStats 1 }

affirmedServiceconstructInterfaceAaaGroupRadiusStatisticsSlotLevelProcStatsAllEntry OBJECT-TYPE
    SYNTAX      AffirmedServiceconstructInterfaceAaaGroupRadiusStatisticsSlotLevelProcStatsAllEntry
    MAX-ACCESS  not-accessible
    STATUS      current
    DESCRIPTION ""
    INDEX { affirmedServiceconstructInterfaceAaaGroupRadiusStatisticsSlotLevelProcStatsAllChassis, affirmedServiceconstructInterfaceAaaGroupRadiusStatisticsSlotLevelProcStatsAllSlot }
        ::= { affirmedServiceconstructInterfaceAaaGroupRadiusStatisticsSlotLevelProcStatsAllTable 1 }

AffirmedServiceconstructInterfaceAaaGroupRadiusStatisticsSlotLevelProcStatsAllEntry ::=
    SEQUENCE {
        affirmedServiceconstructInterfaceAaaGroupRadiusStatisticsSlotLevelProcStatsAllChassis Unsigned32,
        affirmedServiceconstructInterfaceAaaGroupRadiusStatisticsSlotLevelProcStatsAllSlot Unsigned32,
        affirmedServiceconstructInterfaceAaaGroupRadiusStatisticsSlotLevelProcStatsAllNumAccessReqTx ConfdString,
        affirmedServiceconstructInterfaceAaaGroupRadiusStatisticsSlotLevelProcStatsAllNumAccessAcceptRx ConfdString,
        affirmedServiceconstructInterfaceAaaGroupRadiusStatisticsSlotLevelProcStatsAllNumAccessRejectRx ConfdString,
        affirmedServiceconstructInterfaceAaaGroupRadiusStatisticsSlotLevelProcStatsAllNumAccessChallengeRx ConfdString,
        affirmedServiceconstructInterfaceAaaGroupRadiusStatisticsSlotLevelProcStatsAllNumAccountRequestStartTx ConfdString,
        affirmedServiceconstructInterfaceAaaGroupRadiusStatisticsSlotLevelProcStatsAllNumAccountRequestStartRespRx ConfdString,
        affirmedServiceconstructInterfaceAaaGroupRadiusStatisticsSlotLevelProcStatsAllNumAccountRequestStopTx ConfdString,
        affirmedServiceconstructInterfaceAaaGroupRadiusStatisticsSlotLevelProcStatsAllNumAccountRequestStopRespRx ConfdString,
        affirmedServiceconstructInterfaceAaaGroupRadiusStatisticsSlotLevelProcStatsAllNumAccountRequestInterimUpdateTx ConfdString,
        affirmedServiceconstructInterfaceAaaGroupRadiusStatisticsSlotLevelProcStatsAllNumAccountRequestInterimUpdateRespRx ConfdString,
        affirmedServiceconstructInterfaceAaaGroupRadiusStatisticsSlotLevelProcStatsAllNumAccountRequestOnTx ConfdString,
        affirmedServiceconstructInterfaceAaaGroupRadiusStatisticsSlotLevelProcStatsAllNumAccountRequestOnRespRx ConfdString,
        affirmedServiceconstructInterfaceAaaGroupRadiusStatisticsSlotLevelProcStatsAllNumAccountRequestOffTx ConfdString,
        affirmedServiceconstructInterfaceAaaGroupRadiusStatisticsSlotLevelProcStatsAllNumAccountRequestOffRespRx ConfdString,
        affirmedServiceconstructInterfaceAaaGroupRadiusStatisticsSlotLevelProcStatsAllNumDisconnectRequestRx ConfdString,
        affirmedServiceconstructInterfaceAaaGroupRadiusStatisticsSlotLevelProcStatsAllNumDisconnectAckTx ConfdString,
        affirmedServiceconstructInterfaceAaaGroupRadiusStatisticsSlotLevelProcStatsAllNumDisconnectNackTx ConfdString,
        affirmedServiceconstructInterfaceAaaGroupRadiusStatisticsSlotLevelProcStatsAllNumCoaRequestRx ConfdString,
        affirmedServiceconstructInterfaceAaaGroupRadiusStatisticsSlotLevelProcStatsAllNumCoaAckTx ConfdString,
        affirmedServiceconstructInterfaceAaaGroupRadiusStatisticsSlotLevelProcStatsAllNumCoaNackTx ConfdString,
        affirmedServiceconstructInterfaceAaaGroupRadiusStatisticsSlotLevelProcStatsAllNumAccessRejectLocal ConfdString,
        affirmedServiceconstructInterfaceAaaGroupRadiusStatisticsSlotLevelProcStatsAllNumAccountRequestStartRejectLocal ConfdString,
        affirmedServiceconstructInterfaceAaaGroupRadiusStatisticsSlotLevelProcStatsAllNumAccountRequestStopRejectLocal ConfdString,
        affirmedServiceconstructInterfaceAaaGroupRadiusStatisticsSlotLevelProcStatsAllNumAccountRequestInterimRejectLocal ConfdString,
        affirmedServiceconstructInterfaceAaaGroupRadiusStatisticsSlotLevelProcStatsAllNumAccessReqTimeout ConfdString,
        affirmedServiceconstructInterfaceAaaGroupRadiusStatisticsSlotLevelProcStatsAllNumAccountRequestStartTimeout ConfdString,
        affirmedServiceconstructInterfaceAaaGroupRadiusStatisticsSlotLevelProcStatsAllNumAccountRequestStopTimeout ConfdString,
        affirmedServiceconstructInterfaceAaaGroupRadiusStatisticsSlotLevelProcStatsAllNumAccountRequestInterimUpdateTimeout ConfdString,
        affirmedServiceconstructInterfaceAaaGroupRadiusStatisticsSlotLevelProcStatsAllNumAccessReqReTx ConfdString,
        affirmedServiceconstructInterfaceAaaGroupRadiusStatisticsSlotLevelProcStatsAllNumAccessAcceptRcvdReTx ConfdString,
        affirmedServiceconstructInterfaceAaaGroupRadiusStatisticsSlotLevelProcStatsAllNumAccountRequestStartReTx ConfdString,
        affirmedServiceconstructInterfaceAaaGroupRadiusStatisticsSlotLevelProcStatsAllNumAccountRequestStartRespRcvdReTx ConfdString,
        affirmedServiceconstructInterfaceAaaGroupRadiusStatisticsSlotLevelProcStatsAllNumAccountRequestStopReTx ConfdString,
        affirmedServiceconstructInterfaceAaaGroupRadiusStatisticsSlotLevelProcStatsAllNumAccountRequestStopRespRcvdReTx ConfdString,
        affirmedServiceconstructInterfaceAaaGroupRadiusStatisticsSlotLevelProcStatsAllNumAccountRequestInterimUpdateReTx ConfdString,
        affirmedServiceconstructInterfaceAaaGroupRadiusStatisticsSlotLevelProcStatsAllNumAccountRequestInterimUpdateRespRcvdReTx ConfdString,
        affirmedServiceconstructInterfaceAaaGroupRadiusStatisticsSlotLevelProcStatsAllCumulativeCoaLatency ConfdString,
        affirmedServiceconstructInterfaceAaaGroupRadiusStatisticsSlotLevelProcStatsAllCoaLatencySamples Unsigned32,
        affirmedServiceconstructInterfaceAaaGroupRadiusStatisticsSlotLevelProcStatsAllAverageCoaLatency ConfdString,
        affirmedServiceconstructInterfaceAaaGroupRadiusStatisticsSlotLevelProcStatsAllCumulativeDisconnectLatency ConfdString,
        affirmedServiceconstructInterfaceAaaGroupRadiusStatisticsSlotLevelProcStatsAllDisconnectLatencySamples Unsigned32,
        affirmedServiceconstructInterfaceAaaGroupRadiusStatisticsSlotLevelProcStatsAllAverageDisconnectLatency ConfdString,
        affirmedServiceconstructInterfaceAaaGroupRadiusStatisticsSlotLevelProcStatsAllCumulativeLatency ConfdString,
        affirmedServiceconstructInterfaceAaaGroupRadiusStatisticsSlotLevelProcStatsAllLatencySamples Unsigned32,
        affirmedServiceconstructInterfaceAaaGroupRadiusStatisticsSlotLevelProcStatsAllAverageLatency ConfdString,
        affirmedServiceconstructInterfaceAaaGroupRadiusStatisticsSlotLevelProcStatsAllNumPacerNoCreditFailure ConfdString
    }

affirmedServiceconstructInterfaceAaaGroupRadiusStatisticsSlotLevelProcStatsAllChassis OBJECT-TYPE
    SYNTAX      Unsigned32
    MAX-ACCESS  not-accessible
    STATUS      current
    DESCRIPTION "chassis ID"
    ::= { affirmedServiceconstructInterfaceAaaGroupRadiusStatisticsSlotLevelProcStatsAllEntry 1 }

affirmedServiceconstructInterfaceAaaGroupRadiusStatisticsSlotLevelProcStatsAllSlot OBJECT-TYPE
    SYNTAX      Unsigned32
    MAX-ACCESS  not-accessible
    STATUS      current
    DESCRIPTION "slot number"
    ::= { affirmedServiceconstructInterfaceAaaGroupRadiusStatisticsSlotLevelProcStatsAllEntry 2 }

affirmedServiceconstructInterfaceAaaGroupRadiusStatisticsSlotLevelProcStatsAllNumAccessReqTx OBJECT-TYPE
    SYNTAX      ConfdString
    MAX-ACCESS  read-only
    STATUS      current
    DESCRIPTION "Number of Access Requests that were transmitted(excluding retransmissions)"
    ::= { affirmedServiceconstructInterfaceAaaGroupRadiusStatisticsSlotLevelProcStatsAllEntry 3 }

affirmedServiceconstructInterfaceAaaGroupRadiusStatisticsSlotLevelProcStatsAllNumAccessAcceptRx OBJECT-TYPE
    SYNTAX      ConfdString
    MAX-ACCESS  read-only
    STATUS      current
    DESCRIPTION "Number of Access Accepts received on first request itself(no retransmissions)"
    ::= { affirmedServiceconstructInterfaceAaaGroupRadiusStatisticsSlotLevelProcStatsAllEntry 4 }

affirmedServiceconstructInterfaceAaaGroupRadiusStatisticsSlotLevelProcStatsAllNumAccessRejectRx OBJECT-TYPE
    SYNTAX      ConfdString
    MAX-ACCESS  read-only
    STATUS      current
    DESCRIPTION "Number of Access Rejects received from peer"
    ::= { affirmedServiceconstructInterfaceAaaGroupRadiusStatisticsSlotLevelProcStatsAllEntry 5 }

affirmedServiceconstructInterfaceAaaGroupRadiusStatisticsSlotLevelProcStatsAllNumAccessChallengeRx OBJECT-TYPE
    SYNTAX      ConfdString
    MAX-ACCESS  read-only
    STATUS      current
    DESCRIPTION "Number of Access Challenges received from peer"
    ::= { affirmedServiceconstructInterfaceAaaGroupRadiusStatisticsSlotLevelProcStatsAllEntry 6 }

affirmedServiceconstructInterfaceAaaGroupRadiusStatisticsSlotLevelProcStatsAllNumAccountRequestStartTx OBJECT-TYPE
    SYNTAX      ConfdString
    MAX-ACCESS  read-only
    STATUS      current
    DESCRIPTION "Number of Account Request Starts that were transmitted(excluding retransmissions)"
    ::= { affirmedServiceconstructInterfaceAaaGroupRadiusStatisticsSlotLevelProcStatsAllEntry 7 }

affirmedServiceconstructInterfaceAaaGroupRadiusStatisticsSlotLevelProcStatsAllNumAccountRequestStartRespRx OBJECT-TYPE
    SYNTAX      ConfdString
    MAX-ACCESS  read-only
    STATUS      current
    DESCRIPTION "Number of Account Start Responses received on first attempted request "
    ::= { affirmedServiceconstructInterfaceAaaGroupRadiusStatisticsSlotLevelProcStatsAllEntry 8 }

affirmedServiceconstructInterfaceAaaGroupRadiusStatisticsSlotLevelProcStatsAllNumAccountRequestStopTx OBJECT-TYPE
    SYNTAX      ConfdString
    MAX-ACCESS  read-only
    STATUS      current
    DESCRIPTION "Number of Account Request Stops that were transmitted(excluding retransmissions)"
    ::= { affirmedServiceconstructInterfaceAaaGroupRadiusStatisticsSlotLevelProcStatsAllEntry 9 }

affirmedServiceconstructInterfaceAaaGroupRadiusStatisticsSlotLevelProcStatsAllNumAccountRequestStopRespRx OBJECT-TYPE
    SYNTAX      ConfdString
    MAX-ACCESS  read-only
    STATUS      current
    DESCRIPTION "Number of Account Stop Responses received on first attempted request "
    ::= { affirmedServiceconstructInterfaceAaaGroupRadiusStatisticsSlotLevelProcStatsAllEntry 10 }

affirmedServiceconstructInterfaceAaaGroupRadiusStatisticsSlotLevelProcStatsAllNumAccountRequestInterimUpdateTx OBJECT-TYPE
    SYNTAX      ConfdString
    MAX-ACCESS  read-only
    STATUS      current
    DESCRIPTION "Number of Account Request Interim Updates that were transmitted(excluding retransmissions)"
    ::= { affirmedServiceconstructInterfaceAaaGroupRadiusStatisticsSlotLevelProcStatsAllEntry 11 }

affirmedServiceconstructInterfaceAaaGroupRadiusStatisticsSlotLevelProcStatsAllNumAccountRequestInterimUpdateRespRx OBJECT-TYPE
    SYNTAX      ConfdString
    MAX-ACCESS  read-only
    STATUS      current
    DESCRIPTION "Number of Account Interim Update Responses received on first attempted request "
    ::= { affirmedServiceconstructInterfaceAaaGroupRadiusStatisticsSlotLevelProcStatsAllEntry 12 }

affirmedServiceconstructInterfaceAaaGroupRadiusStatisticsSlotLevelProcStatsAllNumAccountRequestOnTx OBJECT-TYPE
    SYNTAX      ConfdString
    MAX-ACCESS  read-only
    STATUS      current
    DESCRIPTION "Number of Account Request On sent to peer"
    ::= { affirmedServiceconstructInterfaceAaaGroupRadiusStatisticsSlotLevelProcStatsAllEntry 13 }

affirmedServiceconstructInterfaceAaaGroupRadiusStatisticsSlotLevelProcStatsAllNumAccountRequestOnRespRx OBJECT-TYPE
    SYNTAX      ConfdString
    MAX-ACCESS  read-only
    STATUS      current
    DESCRIPTION "Number of Account Request On Response received from peer"
    ::= { affirmedServiceconstructInterfaceAaaGroupRadiusStatisticsSlotLevelProcStatsAllEntry 14 }

affirmedServiceconstructInterfaceAaaGroupRadiusStatisticsSlotLevelProcStatsAllNumAccountRequestOffTx OBJECT-TYPE
    SYNTAX      ConfdString
    MAX-ACCESS  read-only
    STATUS      current
    DESCRIPTION "Number of Account Request Off sent to peer"
    ::= { affirmedServiceconstructInterfaceAaaGroupRadiusStatisticsSlotLevelProcStatsAllEntry 15 }

affirmedServiceconstructInterfaceAaaGroupRadiusStatisticsSlotLevelProcStatsAllNumAccountRequestOffRespRx OBJECT-TYPE
    SYNTAX      ConfdString
    MAX-ACCESS  read-only
    STATUS      current
    DESCRIPTION "Number of Account Request Off Response received from peer"
    ::= { affirmedServiceconstructInterfaceAaaGroupRadiusStatisticsSlotLevelProcStatsAllEntry 16 }

affirmedServiceconstructInterfaceAaaGroupRadiusStatisticsSlotLevelProcStatsAllNumDisconnectRequestRx OBJECT-TYPE
    SYNTAX      ConfdString
    MAX-ACCESS  read-only
    STATUS      current
    DESCRIPTION "Number of Disconnect Request received from peer"
    ::= { affirmedServiceconstructInterfaceAaaGroupRadiusStatisticsSlotLevelProcStatsAllEntry 17 }

affirmedServiceconstructInterfaceAaaGroupRadiusStatisticsSlotLevelProcStatsAllNumDisconnectAckTx OBJECT-TYPE
    SYNTAX      ConfdString
    MAX-ACCESS  read-only
    STATUS      current
    DESCRIPTION "Number of Disconnect ACK sent to peer"
    ::= { affirmedServiceconstructInterfaceAaaGroupRadiusStatisticsSlotLevelProcStatsAllEntry 18 }

affirmedServiceconstructInterfaceAaaGroupRadiusStatisticsSlotLevelProcStatsAllNumDisconnectNackTx OBJECT-TYPE
    SYNTAX      ConfdString
    MAX-ACCESS  read-only
    STATUS      current
    DESCRIPTION "Number of Disconnect NACK sent to peer"
    ::= { affirmedServiceconstructInterfaceAaaGroupRadiusStatisticsSlotLevelProcStatsAllEntry 19 }

affirmedServiceconstructInterfaceAaaGroupRadiusStatisticsSlotLevelProcStatsAllNumCoaRequestRx OBJECT-TYPE
    SYNTAX      ConfdString
    MAX-ACCESS  read-only
    STATUS      current
    DESCRIPTION "Number of Coa Request received from peer"
    ::= { affirmedServiceconstructInterfaceAaaGroupRadiusStatisticsSlotLevelProcStatsAllEntry 20 }

affirmedServiceconstructInterfaceAaaGroupRadiusStatisticsSlotLevelProcStatsAllNumCoaAckTx OBJECT-TYPE
    SYNTAX      ConfdString
    MAX-ACCESS  read-only
    STATUS      current
    DESCRIPTION "Number of Coa ACK sent to peer"
    ::= { affirmedServiceconstructInterfaceAaaGroupRadiusStatisticsSlotLevelProcStatsAllEntry 21 }

affirmedServiceconstructInterfaceAaaGroupRadiusStatisticsSlotLevelProcStatsAllNumCoaNackTx OBJECT-TYPE
    SYNTAX      ConfdString
    MAX-ACCESS  read-only
    STATUS      current
    DESCRIPTION "Number of Coa NACK sent to peer"
    ::= { affirmedServiceconstructInterfaceAaaGroupRadiusStatisticsSlotLevelProcStatsAllEntry 22 }

affirmedServiceconstructInterfaceAaaGroupRadiusStatisticsSlotLevelProcStatsAllNumAccessRejectLocal OBJECT-TYPE
    SYNTAX      ConfdString
    MAX-ACCESS  read-only
    STATUS      current
    DESCRIPTION "Number of Access Requests that were rejected locally"
    ::= { affirmedServiceconstructInterfaceAaaGroupRadiusStatisticsSlotLevelProcStatsAllEntry 23 }

affirmedServiceconstructInterfaceAaaGroupRadiusStatisticsSlotLevelProcStatsAllNumAccountRequestStartRejectLocal OBJECT-TYPE
    SYNTAX      ConfdString
    MAX-ACCESS  read-only
    STATUS      current
    DESCRIPTION "Number of Account Request(START) that were rejected locally"
    ::= { affirmedServiceconstructInterfaceAaaGroupRadiusStatisticsSlotLevelProcStatsAllEntry 24 }

affirmedServiceconstructInterfaceAaaGroupRadiusStatisticsSlotLevelProcStatsAllNumAccountRequestStopRejectLocal OBJECT-TYPE
    SYNTAX      ConfdString
    MAX-ACCESS  read-only
    STATUS      current
    DESCRIPTION "Number of Account Request(STOP) that were rejected locally"
    ::= { affirmedServiceconstructInterfaceAaaGroupRadiusStatisticsSlotLevelProcStatsAllEntry 25 }

affirmedServiceconstructInterfaceAaaGroupRadiusStatisticsSlotLevelProcStatsAllNumAccountRequestInterimRejectLocal OBJECT-TYPE
    SYNTAX      ConfdString
    MAX-ACCESS  read-only
    STATUS      current
    DESCRIPTION "Number of Account Request(INTERIM) that were rejected locally"
    ::= { affirmedServiceconstructInterfaceAaaGroupRadiusStatisticsSlotLevelProcStatsAllEntry 26 }

affirmedServiceconstructInterfaceAaaGroupRadiusStatisticsSlotLevelProcStatsAllNumAccessReqTimeout OBJECT-TYPE
    SYNTAX      ConfdString
    MAX-ACCESS  read-only
    STATUS      current
    DESCRIPTION "Number of Access Requests that timed out(includes retransmission timeouts)"
    ::= { affirmedServiceconstructInterfaceAaaGroupRadiusStatisticsSlotLevelProcStatsAllEntry 27 }

affirmedServiceconstructInterfaceAaaGroupRadiusStatisticsSlotLevelProcStatsAllNumAccountRequestStartTimeout OBJECT-TYPE
    SYNTAX      ConfdString
    MAX-ACCESS  read-only
    STATUS      current
    DESCRIPTION "Number of Account Request Starts that timed out(includes retransmission timeouts)"
    ::= { affirmedServiceconstructInterfaceAaaGroupRadiusStatisticsSlotLevelProcStatsAllEntry 28 }

affirmedServiceconstructInterfaceAaaGroupRadiusStatisticsSlotLevelProcStatsAllNumAccountRequestStopTimeout OBJECT-TYPE
    SYNTAX      ConfdString
    MAX-ACCESS  read-only
    STATUS      current
    DESCRIPTION "Number of Account Request Stops that timed out(includes retransmission timeouts)"
    ::= { affirmedServiceconstructInterfaceAaaGroupRadiusStatisticsSlotLevelProcStatsAllEntry 29 }

affirmedServiceconstructInterfaceAaaGroupRadiusStatisticsSlotLevelProcStatsAllNumAccountRequestInterimUpdateTimeout OBJECT-TYPE
    SYNTAX      ConfdString
    MAX-ACCESS  read-only
    STATUS      current
    DESCRIPTION "Number of Account Request Interim Updates that timed out(includes retransmission timeouts)"
    ::= { affirmedServiceconstructInterfaceAaaGroupRadiusStatisticsSlotLevelProcStatsAllEntry 30 }

affirmedServiceconstructInterfaceAaaGroupRadiusStatisticsSlotLevelProcStatsAllNumAccessReqReTx OBJECT-TYPE
    SYNTAX      ConfdString
    MAX-ACCESS  read-only
    STATUS      current
    DESCRIPTION "Number of Access Requests that were retransmitted"
    ::= { affirmedServiceconstructInterfaceAaaGroupRadiusStatisticsSlotLevelProcStatsAllEntry 31 }

affirmedServiceconstructInterfaceAaaGroupRadiusStatisticsSlotLevelProcStatsAllNumAccessAcceptRcvdReTx OBJECT-TYPE
    SYNTAX      ConfdString
    MAX-ACCESS  read-only
    STATUS      current
    DESCRIPTION "Number of Access Accepts that were received when Requests were retransmitted"
    ::= { affirmedServiceconstructInterfaceAaaGroupRadiusStatisticsSlotLevelProcStatsAllEntry 32 }

affirmedServiceconstructInterfaceAaaGroupRadiusStatisticsSlotLevelProcStatsAllNumAccountRequestStartReTx OBJECT-TYPE
    SYNTAX      ConfdString
    MAX-ACCESS  read-only
    STATUS      current
    DESCRIPTION "Number of Account Request Starts that were retransmitted"
    ::= { affirmedServiceconstructInterfaceAaaGroupRadiusStatisticsSlotLevelProcStatsAllEntry 33 }

affirmedServiceconstructInterfaceAaaGroupRadiusStatisticsSlotLevelProcStatsAllNumAccountRequestStartRespRcvdReTx OBJECT-TYPE
    SYNTAX      ConfdString
    MAX-ACCESS  read-only
    STATUS      current
    DESCRIPTION "Number of Account Request Start Responses received when requests were retransmitted "
    ::= { affirmedServiceconstructInterfaceAaaGroupRadiusStatisticsSlotLevelProcStatsAllEntry 34 }

affirmedServiceconstructInterfaceAaaGroupRadiusStatisticsSlotLevelProcStatsAllNumAccountRequestStopReTx OBJECT-TYPE
    SYNTAX      ConfdString
    MAX-ACCESS  read-only
    STATUS      current
    DESCRIPTION "Number of Account Request Stops that were retransmitted"
    ::= { affirmedServiceconstructInterfaceAaaGroupRadiusStatisticsSlotLevelProcStatsAllEntry 35 }

affirmedServiceconstructInterfaceAaaGroupRadiusStatisticsSlotLevelProcStatsAllNumAccountRequestStopRespRcvdReTx OBJECT-TYPE
    SYNTAX      ConfdString
    MAX-ACCESS  read-only
    STATUS      current
    DESCRIPTION "Number of Account Request Stop Responses received when requests were retransmitted "
    ::= { affirmedServiceconstructInterfaceAaaGroupRadiusStatisticsSlotLevelProcStatsAllEntry 36 }

affirmedServiceconstructInterfaceAaaGroupRadiusStatisticsSlotLevelProcStatsAllNumAccountRequestInterimUpdateReTx OBJECT-TYPE
    SYNTAX      ConfdString
    MAX-ACCESS  read-only
    STATUS      current
    DESCRIPTION "Number of Account Request InterimUpdates that were retransmitted"
    ::= { affirmedServiceconstructInterfaceAaaGroupRadiusStatisticsSlotLevelProcStatsAllEntry 37 }

affirmedServiceconstructInterfaceAaaGroupRadiusStatisticsSlotLevelProcStatsAllNumAccountRequestInterimUpdateRespRcvdReTx OBJECT-TYPE
    SYNTAX      ConfdString
    MAX-ACCESS  read-only
    STATUS      current
    DESCRIPTION "Number of Account Request Interim Update Responses received when requests were retransmitted "
    ::= { affirmedServiceconstructInterfaceAaaGroupRadiusStatisticsSlotLevelProcStatsAllEntry 38 }

affirmedServiceconstructInterfaceAaaGroupRadiusStatisticsSlotLevelProcStatsAllCumulativeCoaLatency OBJECT-TYPE
    SYNTAX      ConfdString
    MAX-ACCESS  read-only
    STATUS      current
    DESCRIPTION "Cumulative Latency in microseconds for RADIUS CoA messages"
    ::= { affirmedServiceconstructInterfaceAaaGroupRadiusStatisticsSlotLevelProcStatsAllEntry 39 }

affirmedServiceconstructInterfaceAaaGroupRadiusStatisticsSlotLevelProcStatsAllCoaLatencySamples OBJECT-TYPE
    SYNTAX      Unsigned32
    MAX-ACCESS  read-only
    STATUS      current
    DESCRIPTION "Samples for calculating average latency for RADIUS CoA messages"
    ::= { affirmedServiceconstructInterfaceAaaGroupRadiusStatisticsSlotLevelProcStatsAllEntry 40 }

affirmedServiceconstructInterfaceAaaGroupRadiusStatisticsSlotLevelProcStatsAllAverageCoaLatency OBJECT-TYPE
    SYNTAX      ConfdString
    MAX-ACCESS  read-only
    STATUS      current
    DESCRIPTION "Average Latency in microseconds for RADIUS CoA"
    ::= { affirmedServiceconstructInterfaceAaaGroupRadiusStatisticsSlotLevelProcStatsAllEntry 41 }

affirmedServiceconstructInterfaceAaaGroupRadiusStatisticsSlotLevelProcStatsAllCumulativeDisconnectLatency OBJECT-TYPE
    SYNTAX      ConfdString
    MAX-ACCESS  read-only
    STATUS      current
    DESCRIPTION "Cumulative Latency in microseconds for RADIUS Disconnect messages"
    ::= { affirmedServiceconstructInterfaceAaaGroupRadiusStatisticsSlotLevelProcStatsAllEntry 42 }

affirmedServiceconstructInterfaceAaaGroupRadiusStatisticsSlotLevelProcStatsAllDisconnectLatencySamples OBJECT-TYPE
    SYNTAX      Unsigned32
    MAX-ACCESS  read-only
    STATUS      current
    DESCRIPTION "Samples for calculating average latency for RADIUS Disconnect messages"
    ::= { affirmedServiceconstructInterfaceAaaGroupRadiusStatisticsSlotLevelProcStatsAllEntry 43 }

affirmedServiceconstructInterfaceAaaGroupRadiusStatisticsSlotLevelProcStatsAllAverageDisconnectLatency OBJECT-TYPE
    SYNTAX      ConfdString
    MAX-ACCESS  read-only
    STATUS      current
    DESCRIPTION "Average Latency in microseconds for RADIUS Disconnect"
    ::= { affirmedServiceconstructInterfaceAaaGroupRadiusStatisticsSlotLevelProcStatsAllEntry 44 }

affirmedServiceconstructInterfaceAaaGroupRadiusStatisticsSlotLevelProcStatsAllCumulativeLatency OBJECT-TYPE
    SYNTAX      ConfdString
    MAX-ACCESS  read-only
    STATUS      current
    DESCRIPTION "Cumulative Latency in microseconds for RADIUS messages"
    ::= { affirmedServiceconstructInterfaceAaaGroupRadiusStatisticsSlotLevelProcStatsAllEntry 45 }

affirmedServiceconstructInterfaceAaaGroupRadiusStatisticsSlotLevelProcStatsAllLatencySamples OBJECT-TYPE
    SYNTAX      Unsigned32
    MAX-ACCESS  read-only
    STATUS      current
    DESCRIPTION "Samples for calculating average latency for RADIUS messages"
    ::= { affirmedServiceconstructInterfaceAaaGroupRadiusStatisticsSlotLevelProcStatsAllEntry 46 }

affirmedServiceconstructInterfaceAaaGroupRadiusStatisticsSlotLevelProcStatsAllAverageLatency OBJECT-TYPE
    SYNTAX      ConfdString
    MAX-ACCESS  read-only
    STATUS      current
    DESCRIPTION "Average Latency in microseconds for RADIUS messages"
    ::= { affirmedServiceconstructInterfaceAaaGroupRadiusStatisticsSlotLevelProcStatsAllEntry 47 }

affirmedServiceconstructInterfaceAaaGroupRadiusStatisticsSlotLevelProcStatsAllNumPacerNoCreditFailure OBJECT-TYPE
    SYNTAX      ConfdString
    MAX-ACCESS  read-only
    STATUS      current
    DESCRIPTION "Number of failures for no credit"
    ::= { affirmedServiceconstructInterfaceAaaGroupRadiusStatisticsSlotLevelProcStatsAllEntry 48 }

affirmedServiceconstructInterfaceAaaGroupRadiusStatisticsSlotLevelProcStatsPeerTable OBJECT-TYPE
    SYNTAX      SEQUENCE OF AffirmedServiceconstructInterfaceAaaGroupRadiusStatisticsSlotLevelProcStatsPeerEntry
    MAX-ACCESS  not-accessible
    STATUS      current
    DESCRIPTION ""
    ::= { affirmedServiceconstructInterfaceAaaGroupRadiusStatisticsSlotLevelProcStats 2 }

affirmedServiceconstructInterfaceAaaGroupRadiusStatisticsSlotLevelProcStatsPeerEntry OBJECT-TYPE
    SYNTAX      AffirmedServiceconstructInterfaceAaaGroupRadiusStatisticsSlotLevelProcStatsPeerEntry
    MAX-ACCESS  not-accessible
    STATUS      current
    DESCRIPTION ""
    INDEX { affirmedServiceconstructInterfaceAaaGroupRadiusStatisticsSlotLevelProcStatsPeerName, affirmedServiceconstructInterfaceAaaGroupRadiusStatisticsSlotLevelProcStatsPeerChassis, affirmedServiceconstructInterfaceAaaGroupRadiusStatisticsSlotLevelProcStatsPeerSlot }
        ::= { affirmedServiceconstructInterfaceAaaGroupRadiusStatisticsSlotLevelProcStatsPeerTable 1 }

AffirmedServiceconstructInterfaceAaaGroupRadiusStatisticsSlotLevelProcStatsPeerEntry ::=
    SEQUENCE {
        affirmedServiceconstructInterfaceAaaGroupRadiusStatisticsSlotLevelProcStatsPeerName String,
        affirmedServiceconstructInterfaceAaaGroupRadiusStatisticsSlotLevelProcStatsPeerChassis Unsigned32,
        affirmedServiceconstructInterfaceAaaGroupRadiusStatisticsSlotLevelProcStatsPeerSlot Unsigned32,
        affirmedServiceconstructInterfaceAaaGroupRadiusStatisticsSlotLevelProcStatsPeerNumAccessReqTx ConfdString,
        affirmedServiceconstructInterfaceAaaGroupRadiusStatisticsSlotLevelProcStatsPeerNumAccessAcceptRx ConfdString,
        affirmedServiceconstructInterfaceAaaGroupRadiusStatisticsSlotLevelProcStatsPeerNumAccessRejectRx ConfdString,
        affirmedServiceconstructInterfaceAaaGroupRadiusStatisticsSlotLevelProcStatsPeerNumAccessChallengeRx ConfdString,
        affirmedServiceconstructInterfaceAaaGroupRadiusStatisticsSlotLevelProcStatsPeerNumAccountRequestStartTx ConfdString,
        affirmedServiceconstructInterfaceAaaGroupRadiusStatisticsSlotLevelProcStatsPeerNumAccountRequestStartRespRx ConfdString,
        affirmedServiceconstructInterfaceAaaGroupRadiusStatisticsSlotLevelProcStatsPeerNumAccountRequestStopTx ConfdString,
        affirmedServiceconstructInterfaceAaaGroupRadiusStatisticsSlotLevelProcStatsPeerNumAccountRequestStopRespRx ConfdString,
        affirmedServiceconstructInterfaceAaaGroupRadiusStatisticsSlotLevelProcStatsPeerNumAccountRequestInterimUpdateTx ConfdString,
        affirmedServiceconstructInterfaceAaaGroupRadiusStatisticsSlotLevelProcStatsPeerNumAccountRequestInterimUpdateRespRx ConfdString,
        affirmedServiceconstructInterfaceAaaGroupRadiusStatisticsSlotLevelProcStatsPeerNumAccountRequestOnTx ConfdString,
        affirmedServiceconstructInterfaceAaaGroupRadiusStatisticsSlotLevelProcStatsPeerNumAccountRequestOnRespRx ConfdString,
        affirmedServiceconstructInterfaceAaaGroupRadiusStatisticsSlotLevelProcStatsPeerNumAccountRequestOffTx ConfdString,
        affirmedServiceconstructInterfaceAaaGroupRadiusStatisticsSlotLevelProcStatsPeerNumAccountRequestOffRespRx ConfdString,
        affirmedServiceconstructInterfaceAaaGroupRadiusStatisticsSlotLevelProcStatsPeerNumDisconnectRequestRx ConfdString,
        affirmedServiceconstructInterfaceAaaGroupRadiusStatisticsSlotLevelProcStatsPeerNumDisconnectAckTx ConfdString,
        affirmedServiceconstructInterfaceAaaGroupRadiusStatisticsSlotLevelProcStatsPeerNumDisconnectNackTx ConfdString,
        affirmedServiceconstructInterfaceAaaGroupRadiusStatisticsSlotLevelProcStatsPeerNumCoaRequestRx ConfdString,
        affirmedServiceconstructInterfaceAaaGroupRadiusStatisticsSlotLevelProcStatsPeerNumCoaAckTx ConfdString,
        affirmedServiceconstructInterfaceAaaGroupRadiusStatisticsSlotLevelProcStatsPeerNumCoaNackTx ConfdString,
        affirmedServiceconstructInterfaceAaaGroupRadiusStatisticsSlotLevelProcStatsPeerNumAccessRejectLocal ConfdString,
        affirmedServiceconstructInterfaceAaaGroupRadiusStatisticsSlotLevelProcStatsPeerNumAccountRequestStartRejectLocal ConfdString,
        affirmedServiceconstructInterfaceAaaGroupRadiusStatisticsSlotLevelProcStatsPeerNumAccountRequestStopRejectLocal ConfdString,
        affirmedServiceconstructInterfaceAaaGroupRadiusStatisticsSlotLevelProcStatsPeerNumAccountRequestInterimRejectLocal ConfdString,
        affirmedServiceconstructInterfaceAaaGroupRadiusStatisticsSlotLevelProcStatsPeerNumAccessReqTimeout ConfdString,
        affirmedServiceconstructInterfaceAaaGroupRadiusStatisticsSlotLevelProcStatsPeerNumAccountRequestStartTimeout ConfdString,
        affirmedServiceconstructInterfaceAaaGroupRadiusStatisticsSlotLevelProcStatsPeerNumAccountRequestStopTimeout ConfdString,
        affirmedServiceconstructInterfaceAaaGroupRadiusStatisticsSlotLevelProcStatsPeerNumAccountRequestInterimUpdateTimeout ConfdString,
        affirmedServiceconstructInterfaceAaaGroupRadiusStatisticsSlotLevelProcStatsPeerNumAccessReqReTx ConfdString,
        affirmedServiceconstructInterfaceAaaGroupRadiusStatisticsSlotLevelProcStatsPeerNumAccessAcceptRcvdReTx ConfdString,
        affirmedServiceconstructInterfaceAaaGroupRadiusStatisticsSlotLevelProcStatsPeerNumAccountRequestStartReTx ConfdString,
        affirmedServiceconstructInterfaceAaaGroupRadiusStatisticsSlotLevelProcStatsPeerNumAccountRequestStartRespRcvdReTx ConfdString,
        affirmedServiceconstructInterfaceAaaGroupRadiusStatisticsSlotLevelProcStatsPeerNumAccountRequestStopReTx ConfdString,
        affirmedServiceconstructInterfaceAaaGroupRadiusStatisticsSlotLevelProcStatsPeerNumAccountRequestStopRespRcvdReTx ConfdString,
        affirmedServiceconstructInterfaceAaaGroupRadiusStatisticsSlotLevelProcStatsPeerNumAccountRequestInterimUpdateReTx ConfdString,
        affirmedServiceconstructInterfaceAaaGroupRadiusStatisticsSlotLevelProcStatsPeerNumAccountRequestInterimUpdateRespRcvdReTx ConfdString,
        affirmedServiceconstructInterfaceAaaGroupRadiusStatisticsSlotLevelProcStatsPeerCumulativeCoaLatency ConfdString,
        affirmedServiceconstructInterfaceAaaGroupRadiusStatisticsSlotLevelProcStatsPeerCoaLatencySamples Unsigned32,
        affirmedServiceconstructInterfaceAaaGroupRadiusStatisticsSlotLevelProcStatsPeerAverageCoaLatency ConfdString,
        affirmedServiceconstructInterfaceAaaGroupRadiusStatisticsSlotLevelProcStatsPeerCumulativeDisconnectLatency ConfdString,
        affirmedServiceconstructInterfaceAaaGroupRadiusStatisticsSlotLevelProcStatsPeerDisconnectLatencySamples Unsigned32,
        affirmedServiceconstructInterfaceAaaGroupRadiusStatisticsSlotLevelProcStatsPeerAverageDisconnectLatency ConfdString,
        affirmedServiceconstructInterfaceAaaGroupRadiusStatisticsSlotLevelProcStatsPeerCumulativeLatency ConfdString,
        affirmedServiceconstructInterfaceAaaGroupRadiusStatisticsSlotLevelProcStatsPeerLatencySamples Unsigned32,
        affirmedServiceconstructInterfaceAaaGroupRadiusStatisticsSlotLevelProcStatsPeerAverageLatency ConfdString,
        affirmedServiceconstructInterfaceAaaGroupRadiusStatisticsSlotLevelProcStatsPeerNumPacerNoCreditFailure ConfdString
    }

affirmedServiceconstructInterfaceAaaGroupRadiusStatisticsSlotLevelProcStatsPeerName OBJECT-TYPE
    SYNTAX      String
    MAX-ACCESS  not-accessible
    STATUS      current
    DESCRIPTION "Peer Stats Table Name"
    ::= { affirmedServiceconstructInterfaceAaaGroupRadiusStatisticsSlotLevelProcStatsPeerEntry 1 }

affirmedServiceconstructInterfaceAaaGroupRadiusStatisticsSlotLevelProcStatsPeerChassis OBJECT-TYPE
    SYNTAX      Unsigned32
    MAX-ACCESS  not-accessible
    STATUS      current
    DESCRIPTION "chassis ID"
    ::= { affirmedServiceconstructInterfaceAaaGroupRadiusStatisticsSlotLevelProcStatsPeerEntry 2 }

affirmedServiceconstructInterfaceAaaGroupRadiusStatisticsSlotLevelProcStatsPeerSlot OBJECT-TYPE
    SYNTAX      Unsigned32
    MAX-ACCESS  not-accessible
    STATUS      current
    DESCRIPTION "slot number"
    ::= { affirmedServiceconstructInterfaceAaaGroupRadiusStatisticsSlotLevelProcStatsPeerEntry 3 }

affirmedServiceconstructInterfaceAaaGroupRadiusStatisticsSlotLevelProcStatsPeerNumAccessReqTx OBJECT-TYPE
    SYNTAX      ConfdString
    MAX-ACCESS  read-only
    STATUS      current
    DESCRIPTION "Number of Access Requests that were transmitted(excluding retransmissions)"
    ::= { affirmedServiceconstructInterfaceAaaGroupRadiusStatisticsSlotLevelProcStatsPeerEntry 4 }

affirmedServiceconstructInterfaceAaaGroupRadiusStatisticsSlotLevelProcStatsPeerNumAccessAcceptRx OBJECT-TYPE
    SYNTAX      ConfdString
    MAX-ACCESS  read-only
    STATUS      current
    DESCRIPTION "Number of Access Accepts received on first request itself(no retransmissions)"
    ::= { affirmedServiceconstructInterfaceAaaGroupRadiusStatisticsSlotLevelProcStatsPeerEntry 5 }

affirmedServiceconstructInterfaceAaaGroupRadiusStatisticsSlotLevelProcStatsPeerNumAccessRejectRx OBJECT-TYPE
    SYNTAX      ConfdString
    MAX-ACCESS  read-only
    STATUS      current
    DESCRIPTION "Number of Access Rejects received from peer"
    ::= { affirmedServiceconstructInterfaceAaaGroupRadiusStatisticsSlotLevelProcStatsPeerEntry 6 }

affirmedServiceconstructInterfaceAaaGroupRadiusStatisticsSlotLevelProcStatsPeerNumAccessChallengeRx OBJECT-TYPE
    SYNTAX      ConfdString
    MAX-ACCESS  read-only
    STATUS      current
    DESCRIPTION "Number of Access Challenges received from peer"
    ::= { affirmedServiceconstructInterfaceAaaGroupRadiusStatisticsSlotLevelProcStatsPeerEntry 7 }

affirmedServiceconstructInterfaceAaaGroupRadiusStatisticsSlotLevelProcStatsPeerNumAccountRequestStartTx OBJECT-TYPE
    SYNTAX      ConfdString
    MAX-ACCESS  read-only
    STATUS      current
    DESCRIPTION "Number of Account Request Starts that were transmitted(excluding retransmissions)"
    ::= { affirmedServiceconstructInterfaceAaaGroupRadiusStatisticsSlotLevelProcStatsPeerEntry 8 }

affirmedServiceconstructInterfaceAaaGroupRadiusStatisticsSlotLevelProcStatsPeerNumAccountRequestStartRespRx OBJECT-TYPE
    SYNTAX      ConfdString
    MAX-ACCESS  read-only
    STATUS      current
    DESCRIPTION "Number of Account Start Responses received on first attempted request "
    ::= { affirmedServiceconstructInterfaceAaaGroupRadiusStatisticsSlotLevelProcStatsPeerEntry 9 }

affirmedServiceconstructInterfaceAaaGroupRadiusStatisticsSlotLevelProcStatsPeerNumAccountRequestStopTx OBJECT-TYPE
    SYNTAX      ConfdString
    MAX-ACCESS  read-only
    STATUS      current
    DESCRIPTION "Number of Account Request Stops that were transmitted(excluding retransmissions)"
    ::= { affirmedServiceconstructInterfaceAaaGroupRadiusStatisticsSlotLevelProcStatsPeerEntry 10 }

affirmedServiceconstructInterfaceAaaGroupRadiusStatisticsSlotLevelProcStatsPeerNumAccountRequestStopRespRx OBJECT-TYPE
    SYNTAX      ConfdString
    MAX-ACCESS  read-only
    STATUS      current
    DESCRIPTION "Number of Account Stop Responses received on first attempted request "
    ::= { affirmedServiceconstructInterfaceAaaGroupRadiusStatisticsSlotLevelProcStatsPeerEntry 11 }

affirmedServiceconstructInterfaceAaaGroupRadiusStatisticsSlotLevelProcStatsPeerNumAccountRequestInterimUpdateTx OBJECT-TYPE
    SYNTAX      ConfdString
    MAX-ACCESS  read-only
    STATUS      current
    DESCRIPTION "Number of Account Request Interim Updates that were transmitted(excluding retransmissions)"
    ::= { affirmedServiceconstructInterfaceAaaGroupRadiusStatisticsSlotLevelProcStatsPeerEntry 12 }

affirmedServiceconstructInterfaceAaaGroupRadiusStatisticsSlotLevelProcStatsPeerNumAccountRequestInterimUpdateRespRx OBJECT-TYPE
    SYNTAX      ConfdString
    MAX-ACCESS  read-only
    STATUS      current
    DESCRIPTION "Number of Account Interim Update Responses received on first attempted request "
    ::= { affirmedServiceconstructInterfaceAaaGroupRadiusStatisticsSlotLevelProcStatsPeerEntry 13 }

affirmedServiceconstructInterfaceAaaGroupRadiusStatisticsSlotLevelProcStatsPeerNumAccountRequestOnTx OBJECT-TYPE
    SYNTAX      ConfdString
    MAX-ACCESS  read-only
    STATUS      current
    DESCRIPTION "Number of Account Request On sent to peer"
    ::= { affirmedServiceconstructInterfaceAaaGroupRadiusStatisticsSlotLevelProcStatsPeerEntry 14 }

affirmedServiceconstructInterfaceAaaGroupRadiusStatisticsSlotLevelProcStatsPeerNumAccountRequestOnRespRx OBJECT-TYPE
    SYNTAX      ConfdString
    MAX-ACCESS  read-only
    STATUS      current
    DESCRIPTION "Number of Account Request On Response received from peer"
    ::= { affirmedServiceconstructInterfaceAaaGroupRadiusStatisticsSlotLevelProcStatsPeerEntry 15 }

affirmedServiceconstructInterfaceAaaGroupRadiusStatisticsSlotLevelProcStatsPeerNumAccountRequestOffTx OBJECT-TYPE
    SYNTAX      ConfdString
    MAX-ACCESS  read-only
    STATUS      current
    DESCRIPTION "Number of Account Request Off sent to peer"
    ::= { affirmedServiceconstructInterfaceAaaGroupRadiusStatisticsSlotLevelProcStatsPeerEntry 16 }

affirmedServiceconstructInterfaceAaaGroupRadiusStatisticsSlotLevelProcStatsPeerNumAccountRequestOffRespRx OBJECT-TYPE
    SYNTAX      ConfdString
    MAX-ACCESS  read-only
    STATUS      current
    DESCRIPTION "Number of Account Request Off Response received from peer"
    ::= { affirmedServiceconstructInterfaceAaaGroupRadiusStatisticsSlotLevelProcStatsPeerEntry 17 }

affirmedServiceconstructInterfaceAaaGroupRadiusStatisticsSlotLevelProcStatsPeerNumDisconnectRequestRx OBJECT-TYPE
    SYNTAX      ConfdString
    MAX-ACCESS  read-only
    STATUS      current
    DESCRIPTION "Number of Disconnect Request received from peer"
    ::= { affirmedServiceconstructInterfaceAaaGroupRadiusStatisticsSlotLevelProcStatsPeerEntry 18 }

affirmedServiceconstructInterfaceAaaGroupRadiusStatisticsSlotLevelProcStatsPeerNumDisconnectAckTx OBJECT-TYPE
    SYNTAX      ConfdString
    MAX-ACCESS  read-only
    STATUS      current
    DESCRIPTION "Number of Disconnect ACK sent to peer"
    ::= { affirmedServiceconstructInterfaceAaaGroupRadiusStatisticsSlotLevelProcStatsPeerEntry 19 }

affirmedServiceconstructInterfaceAaaGroupRadiusStatisticsSlotLevelProcStatsPeerNumDisconnectNackTx OBJECT-TYPE
    SYNTAX      ConfdString
    MAX-ACCESS  read-only
    STATUS      current
    DESCRIPTION "Number of Disconnect NACK sent to peer"
    ::= { affirmedServiceconstructInterfaceAaaGroupRadiusStatisticsSlotLevelProcStatsPeerEntry 20 }

affirmedServiceconstructInterfaceAaaGroupRadiusStatisticsSlotLevelProcStatsPeerNumCoaRequestRx OBJECT-TYPE
    SYNTAX      ConfdString
    MAX-ACCESS  read-only
    STATUS      current
    DESCRIPTION "Number of Coa Request received from peer"
    ::= { affirmedServiceconstructInterfaceAaaGroupRadiusStatisticsSlotLevelProcStatsPeerEntry 21 }

affirmedServiceconstructInterfaceAaaGroupRadiusStatisticsSlotLevelProcStatsPeerNumCoaAckTx OBJECT-TYPE
    SYNTAX      ConfdString
    MAX-ACCESS  read-only
    STATUS      current
    DESCRIPTION "Number of Coa ACK sent to peer"
    ::= { affirmedServiceconstructInterfaceAaaGroupRadiusStatisticsSlotLevelProcStatsPeerEntry 22 }

affirmedServiceconstructInterfaceAaaGroupRadiusStatisticsSlotLevelProcStatsPeerNumCoaNackTx OBJECT-TYPE
    SYNTAX      ConfdString
    MAX-ACCESS  read-only
    STATUS      current
    DESCRIPTION "Number of Coa NACK sent to peer"
    ::= { affirmedServiceconstructInterfaceAaaGroupRadiusStatisticsSlotLevelProcStatsPeerEntry 23 }

affirmedServiceconstructInterfaceAaaGroupRadiusStatisticsSlotLevelProcStatsPeerNumAccessRejectLocal OBJECT-TYPE
    SYNTAX      ConfdString
    MAX-ACCESS  read-only
    STATUS      current
    DESCRIPTION "Number of Access Requests that were rejected locally"
    ::= { affirmedServiceconstructInterfaceAaaGroupRadiusStatisticsSlotLevelProcStatsPeerEntry 24 }

affirmedServiceconstructInterfaceAaaGroupRadiusStatisticsSlotLevelProcStatsPeerNumAccountRequestStartRejectLocal OBJECT-TYPE
    SYNTAX      ConfdString
    MAX-ACCESS  read-only
    STATUS      current
    DESCRIPTION "Number of Account Request(START) that were rejected locally"
    ::= { affirmedServiceconstructInterfaceAaaGroupRadiusStatisticsSlotLevelProcStatsPeerEntry 25 }

affirmedServiceconstructInterfaceAaaGroupRadiusStatisticsSlotLevelProcStatsPeerNumAccountRequestStopRejectLocal OBJECT-TYPE
    SYNTAX      ConfdString
    MAX-ACCESS  read-only
    STATUS      current
    DESCRIPTION "Number of Account Request(STOP) that were rejected locally"
    ::= { affirmedServiceconstructInterfaceAaaGroupRadiusStatisticsSlotLevelProcStatsPeerEntry 26 }

affirmedServiceconstructInterfaceAaaGroupRadiusStatisticsSlotLevelProcStatsPeerNumAccountRequestInterimRejectLocal OBJECT-TYPE
    SYNTAX      ConfdString
    MAX-ACCESS  read-only
    STATUS      current
    DESCRIPTION "Number of Account Request(INTERIM) that were rejected locally"
    ::= { affirmedServiceconstructInterfaceAaaGroupRadiusStatisticsSlotLevelProcStatsPeerEntry 27 }

affirmedServiceconstructInterfaceAaaGroupRadiusStatisticsSlotLevelProcStatsPeerNumAccessReqTimeout OBJECT-TYPE
    SYNTAX      ConfdString
    MAX-ACCESS  read-only
    STATUS      current
    DESCRIPTION "Number of Access Requests that timed out(includes retransmission timeouts)"
    ::= { affirmedServiceconstructInterfaceAaaGroupRadiusStatisticsSlotLevelProcStatsPeerEntry 28 }

affirmedServiceconstructInterfaceAaaGroupRadiusStatisticsSlotLevelProcStatsPeerNumAccountRequestStartTimeout OBJECT-TYPE
    SYNTAX      ConfdString
    MAX-ACCESS  read-only
    STATUS      current
    DESCRIPTION "Number of Account Request Starts that timed out(includes retransmission timeouts)"
    ::= { affirmedServiceconstructInterfaceAaaGroupRadiusStatisticsSlotLevelProcStatsPeerEntry 29 }

affirmedServiceconstructInterfaceAaaGroupRadiusStatisticsSlotLevelProcStatsPeerNumAccountRequestStopTimeout OBJECT-TYPE
    SYNTAX      ConfdString
    MAX-ACCESS  read-only
    STATUS      current
    DESCRIPTION "Number of Account Request Stops that timed out(includes retransmission timeouts)"
    ::= { affirmedServiceconstructInterfaceAaaGroupRadiusStatisticsSlotLevelProcStatsPeerEntry 30 }

affirmedServiceconstructInterfaceAaaGroupRadiusStatisticsSlotLevelProcStatsPeerNumAccountRequestInterimUpdateTimeout OBJECT-TYPE
    SYNTAX      ConfdString
    MAX-ACCESS  read-only
    STATUS      current
    DESCRIPTION "Number of Account Request Interim Updates that timed out(includes retransmission timeouts)"
    ::= { affirmedServiceconstructInterfaceAaaGroupRadiusStatisticsSlotLevelProcStatsPeerEntry 31 }

affirmedServiceconstructInterfaceAaaGroupRadiusStatisticsSlotLevelProcStatsPeerNumAccessReqReTx OBJECT-TYPE
    SYNTAX      ConfdString
    MAX-ACCESS  read-only
    STATUS      current
    DESCRIPTION "Number of Access Requests that were retransmitted"
    ::= { affirmedServiceconstructInterfaceAaaGroupRadiusStatisticsSlotLevelProcStatsPeerEntry 32 }

affirmedServiceconstructInterfaceAaaGroupRadiusStatisticsSlotLevelProcStatsPeerNumAccessAcceptRcvdReTx OBJECT-TYPE
    SYNTAX      ConfdString
    MAX-ACCESS  read-only
    STATUS      current
    DESCRIPTION "Number of Access Accepts that were received when Requests were retransmitted"
    ::= { affirmedServiceconstructInterfaceAaaGroupRadiusStatisticsSlotLevelProcStatsPeerEntry 33 }

affirmedServiceconstructInterfaceAaaGroupRadiusStatisticsSlotLevelProcStatsPeerNumAccountRequestStartReTx OBJECT-TYPE
    SYNTAX      ConfdString
    MAX-ACCESS  read-only
    STATUS      current
    DESCRIPTION "Number of Account Request Starts that were retransmitted"
    ::= { affirmedServiceconstructInterfaceAaaGroupRadiusStatisticsSlotLevelProcStatsPeerEntry 34 }

affirmedServiceconstructInterfaceAaaGroupRadiusStatisticsSlotLevelProcStatsPeerNumAccountRequestStartRespRcvdReTx OBJECT-TYPE
    SYNTAX      ConfdString
    MAX-ACCESS  read-only
    STATUS      current
    DESCRIPTION "Number of Account Request Start Responses received when requests were retransmitted "
    ::= { affirmedServiceconstructInterfaceAaaGroupRadiusStatisticsSlotLevelProcStatsPeerEntry 35 }

affirmedServiceconstructInterfaceAaaGroupRadiusStatisticsSlotLevelProcStatsPeerNumAccountRequestStopReTx OBJECT-TYPE
    SYNTAX      ConfdString
    MAX-ACCESS  read-only
    STATUS      current
    DESCRIPTION "Number of Account Request Stops that were retransmitted"
    ::= { affirmedServiceconstructInterfaceAaaGroupRadiusStatisticsSlotLevelProcStatsPeerEntry 36 }

affirmedServiceconstructInterfaceAaaGroupRadiusStatisticsSlotLevelProcStatsPeerNumAccountRequestStopRespRcvdReTx OBJECT-TYPE
    SYNTAX      ConfdString
    MAX-ACCESS  read-only
    STATUS      current
    DESCRIPTION "Number of Account Request Stop Responses received when requests were retransmitted "
    ::= { affirmedServiceconstructInterfaceAaaGroupRadiusStatisticsSlotLevelProcStatsPeerEntry 37 }

affirmedServiceconstructInterfaceAaaGroupRadiusStatisticsSlotLevelProcStatsPeerNumAccountRequestInterimUpdateReTx OBJECT-TYPE
    SYNTAX      ConfdString
    MAX-ACCESS  read-only
    STATUS      current
    DESCRIPTION "Number of Account Request InterimUpdates that were retransmitted"
    ::= { affirmedServiceconstructInterfaceAaaGroupRadiusStatisticsSlotLevelProcStatsPeerEntry 38 }

affirmedServiceconstructInterfaceAaaGroupRadiusStatisticsSlotLevelProcStatsPeerNumAccountRequestInterimUpdateRespRcvdReTx OBJECT-TYPE
    SYNTAX      ConfdString
    MAX-ACCESS  read-only
    STATUS      current
    DESCRIPTION "Number of Account Request Interim Update Responses received when requests were retransmitted "
    ::= { affirmedServiceconstructInterfaceAaaGroupRadiusStatisticsSlotLevelProcStatsPeerEntry 39 }

affirmedServiceconstructInterfaceAaaGroupRadiusStatisticsSlotLevelProcStatsPeerCumulativeCoaLatency OBJECT-TYPE
    SYNTAX      ConfdString
    MAX-ACCESS  read-only
    STATUS      current
    DESCRIPTION "Cumulative Latency in microseconds for RADIUS CoA messages"
    ::= { affirmedServiceconstructInterfaceAaaGroupRadiusStatisticsSlotLevelProcStatsPeerEntry 40 }

affirmedServiceconstructInterfaceAaaGroupRadiusStatisticsSlotLevelProcStatsPeerCoaLatencySamples OBJECT-TYPE
    SYNTAX      Unsigned32
    MAX-ACCESS  read-only
    STATUS      current
    DESCRIPTION "Samples for calculating average latency for RADIUS CoA messages"
    ::= { affirmedServiceconstructInterfaceAaaGroupRadiusStatisticsSlotLevelProcStatsPeerEntry 41 }

affirmedServiceconstructInterfaceAaaGroupRadiusStatisticsSlotLevelProcStatsPeerAverageCoaLatency OBJECT-TYPE
    SYNTAX      ConfdString
    MAX-ACCESS  read-only
    STATUS      current
    DESCRIPTION "Average Latency in microseconds for RADIUS CoA"
    ::= { affirmedServiceconstructInterfaceAaaGroupRadiusStatisticsSlotLevelProcStatsPeerEntry 42 }

affirmedServiceconstructInterfaceAaaGroupRadiusStatisticsSlotLevelProcStatsPeerCumulativeDisconnectLatency OBJECT-TYPE
    SYNTAX      ConfdString
    MAX-ACCESS  read-only
    STATUS      current
    DESCRIPTION "Cumulative Latency in microseconds for RADIUS Disconnect messages"
    ::= { affirmedServiceconstructInterfaceAaaGroupRadiusStatisticsSlotLevelProcStatsPeerEntry 43 }

affirmedServiceconstructInterfaceAaaGroupRadiusStatisticsSlotLevelProcStatsPeerDisconnectLatencySamples OBJECT-TYPE
    SYNTAX      Unsigned32
    MAX-ACCESS  read-only
    STATUS      current
    DESCRIPTION "Samples for calculating average latency for RADIUS Disconnect messages"
    ::= { affirmedServiceconstructInterfaceAaaGroupRadiusStatisticsSlotLevelProcStatsPeerEntry 44 }

affirmedServiceconstructInterfaceAaaGroupRadiusStatisticsSlotLevelProcStatsPeerAverageDisconnectLatency OBJECT-TYPE
    SYNTAX      ConfdString
    MAX-ACCESS  read-only
    STATUS      current
    DESCRIPTION "Average Latency in microseconds for RADIUS Disconnect"
    ::= { affirmedServiceconstructInterfaceAaaGroupRadiusStatisticsSlotLevelProcStatsPeerEntry 45 }

affirmedServiceconstructInterfaceAaaGroupRadiusStatisticsSlotLevelProcStatsPeerCumulativeLatency OBJECT-TYPE
    SYNTAX      ConfdString
    MAX-ACCESS  read-only
    STATUS      current
    DESCRIPTION "Cumulative Latency in microseconds for RADIUS messages"
    ::= { affirmedServiceconstructInterfaceAaaGroupRadiusStatisticsSlotLevelProcStatsPeerEntry 46 }

affirmedServiceconstructInterfaceAaaGroupRadiusStatisticsSlotLevelProcStatsPeerLatencySamples OBJECT-TYPE
    SYNTAX      Unsigned32
    MAX-ACCESS  read-only
    STATUS      current
    DESCRIPTION "Samples for calculating average latency for RADIUS messages"
    ::= { affirmedServiceconstructInterfaceAaaGroupRadiusStatisticsSlotLevelProcStatsPeerEntry 47 }

affirmedServiceconstructInterfaceAaaGroupRadiusStatisticsSlotLevelProcStatsPeerAverageLatency OBJECT-TYPE
    SYNTAX      ConfdString
    MAX-ACCESS  read-only
    STATUS      current
    DESCRIPTION "Average Latency in microseconds for RADIUS messages"
    ::= { affirmedServiceconstructInterfaceAaaGroupRadiusStatisticsSlotLevelProcStatsPeerEntry 48 }

affirmedServiceconstructInterfaceAaaGroupRadiusStatisticsSlotLevelProcStatsPeerNumPacerNoCreditFailure OBJECT-TYPE
    SYNTAX      ConfdString
    MAX-ACCESS  read-only
    STATUS      current
    DESCRIPTION "Number of failures for no credit"
    ::= { affirmedServiceconstructInterfaceAaaGroupRadiusStatisticsSlotLevelProcStatsPeerEntry 49 }

affirmedServiceconstructInterfaceAaaGroupRadiusServerStatisticsChassisLevelServerStatsAllTable OBJECT-TYPE
    SYNTAX      SEQUENCE OF AffirmedServiceconstructInterfaceAaaGroupRadiusServerStatisticsChassisLevelServerStatsAllEntry
    MAX-ACCESS  not-accessible
    STATUS      current
    DESCRIPTION ""
    ::= { affirmedServiceconstructInterfaceAaaGroupRadiusServerStatisticsChassisLevelServerStats 1 }

affirmedServiceconstructInterfaceAaaGroupRadiusServerStatisticsChassisLevelServerStatsAllEntry OBJECT-TYPE
    SYNTAX      AffirmedServiceconstructInterfaceAaaGroupRadiusServerStatisticsChassisLevelServerStatsAllEntry
    MAX-ACCESS  not-accessible
    STATUS      current
    DESCRIPTION ""
    INDEX { affirmedServiceconstructInterfaceAaaGroupRadiusServerStatisticsChassisLevelServerStatsAllChassis }
        ::= { affirmedServiceconstructInterfaceAaaGroupRadiusServerStatisticsChassisLevelServerStatsAllTable 1 }

AffirmedServiceconstructInterfaceAaaGroupRadiusServerStatisticsChassisLevelServerStatsAllEntry ::=
    SEQUENCE {
        affirmedServiceconstructInterfaceAaaGroupRadiusServerStatisticsChassisLevelServerStatsAllChassis Unsigned32,
        affirmedServiceconstructInterfaceAaaGroupRadiusServerStatisticsChassisLevelServerStatsAllNumRx ConfdString,
        affirmedServiceconstructInterfaceAaaGroupRadiusServerStatisticsChassisLevelServerStatsAllNumAccessReqRx ConfdString,
        affirmedServiceconstructInterfaceAaaGroupRadiusServerStatisticsChassisLevelServerStatsAllNumAccountReqRx ConfdString,
        affirmedServiceconstructInterfaceAaaGroupRadiusServerStatisticsChassisLevelServerStatsAllNumDropErrorsRx ConfdString,
        affirmedServiceconstructInterfaceAaaGroupRadiusServerStatisticsChassisLevelServerStatsAllNumAccessAcceptTx ConfdString,
        affirmedServiceconstructInterfaceAaaGroupRadiusServerStatisticsChassisLevelServerStatsAllNumAccessRejectTx ConfdString,
        affirmedServiceconstructInterfaceAaaGroupRadiusServerStatisticsChassisLevelServerStatsAllNumAccessChallengeTx ConfdString,
        affirmedServiceconstructInterfaceAaaGroupRadiusServerStatisticsChassisLevelServerStatsAllNumAccountRespTx ConfdString,
        affirmedServiceconstructInterfaceAaaGroupRadiusServerStatisticsChassisLevelServerStatsAllNumDisconnectReqTx ConfdString,
        affirmedServiceconstructInterfaceAaaGroupRadiusServerStatisticsChassisLevelServerStatsAllNumDisconnectAckRx ConfdString,
        affirmedServiceconstructInterfaceAaaGroupRadiusServerStatisticsChassisLevelServerStatsAllNumDisconnectNakRx ConfdString
    }

affirmedServiceconstructInterfaceAaaGroupRadiusServerStatisticsChassisLevelServerStatsAllChassis OBJECT-TYPE
    SYNTAX      Unsigned32
    MAX-ACCESS  not-accessible
    STATUS      current
    DESCRIPTION "chassis ID"
    ::= { affirmedServiceconstructInterfaceAaaGroupRadiusServerStatisticsChassisLevelServerStatsAllEntry 1 }

affirmedServiceconstructInterfaceAaaGroupRadiusServerStatisticsChassisLevelServerStatsAllNumRx OBJECT-TYPE
    SYNTAX      ConfdString
    MAX-ACCESS  read-only
    STATUS      current
    DESCRIPTION "Number of messages received"
    ::= { affirmedServiceconstructInterfaceAaaGroupRadiusServerStatisticsChassisLevelServerStatsAllEntry 2 }

affirmedServiceconstructInterfaceAaaGroupRadiusServerStatisticsChassisLevelServerStatsAllNumAccessReqRx OBJECT-TYPE
    SYNTAX      ConfdString
    MAX-ACCESS  read-only
    STATUS      current
    DESCRIPTION "Number of Access Requests received"
    ::= { affirmedServiceconstructInterfaceAaaGroupRadiusServerStatisticsChassisLevelServerStatsAllEntry 3 }

affirmedServiceconstructInterfaceAaaGroupRadiusServerStatisticsChassisLevelServerStatsAllNumAccountReqRx OBJECT-TYPE
    SYNTAX      ConfdString
    MAX-ACCESS  read-only
    STATUS      current
    DESCRIPTION "Number of Acccount Requests received"
    ::= { affirmedServiceconstructInterfaceAaaGroupRadiusServerStatisticsChassisLevelServerStatsAllEntry 4 }

affirmedServiceconstructInterfaceAaaGroupRadiusServerStatisticsChassisLevelServerStatsAllNumDropErrorsRx OBJECT-TYPE
    SYNTAX      ConfdString
    MAX-ACCESS  read-only
    STATUS      current
    DESCRIPTION "Number of received messages dropped in error"
    ::= { affirmedServiceconstructInterfaceAaaGroupRadiusServerStatisticsChassisLevelServerStatsAllEntry 5 }

affirmedServiceconstructInterfaceAaaGroupRadiusServerStatisticsChassisLevelServerStatsAllNumAccessAcceptTx OBJECT-TYPE
    SYNTAX      ConfdString
    MAX-ACCESS  read-only
    STATUS      current
    DESCRIPTION "Number of Access Accepts sent"
    ::= { affirmedServiceconstructInterfaceAaaGroupRadiusServerStatisticsChassisLevelServerStatsAllEntry 6 }

affirmedServiceconstructInterfaceAaaGroupRadiusServerStatisticsChassisLevelServerStatsAllNumAccessRejectTx OBJECT-TYPE
    SYNTAX      ConfdString
    MAX-ACCESS  read-only
    STATUS      current
    DESCRIPTION "Number of Access Rejects sent"
    ::= { affirmedServiceconstructInterfaceAaaGroupRadiusServerStatisticsChassisLevelServerStatsAllEntry 7 }

affirmedServiceconstructInterfaceAaaGroupRadiusServerStatisticsChassisLevelServerStatsAllNumAccessChallengeTx OBJECT-TYPE
    SYNTAX      ConfdString
    MAX-ACCESS  read-only
    STATUS      current
    DESCRIPTION "Number of Access Challenges sent"
    ::= { affirmedServiceconstructInterfaceAaaGroupRadiusServerStatisticsChassisLevelServerStatsAllEntry 8 }

affirmedServiceconstructInterfaceAaaGroupRadiusServerStatisticsChassisLevelServerStatsAllNumAccountRespTx OBJECT-TYPE
    SYNTAX      ConfdString
    MAX-ACCESS  read-only
    STATUS      current
    DESCRIPTION "Number of Account Responses sent"
    ::= { affirmedServiceconstructInterfaceAaaGroupRadiusServerStatisticsChassisLevelServerStatsAllEntry 9 }

affirmedServiceconstructInterfaceAaaGroupRadiusServerStatisticsChassisLevelServerStatsAllNumDisconnectReqTx OBJECT-TYPE
    SYNTAX      ConfdString
    MAX-ACCESS  read-only
    STATUS      current
    DESCRIPTION "Number of Disconnect Requests sent"
    ::= { affirmedServiceconstructInterfaceAaaGroupRadiusServerStatisticsChassisLevelServerStatsAllEntry 10 }

affirmedServiceconstructInterfaceAaaGroupRadiusServerStatisticsChassisLevelServerStatsAllNumDisconnectAckRx OBJECT-TYPE
    SYNTAX      ConfdString
    MAX-ACCESS  read-only
    STATUS      current
    DESCRIPTION "Number of Disconnect ACK received"
    ::= { affirmedServiceconstructInterfaceAaaGroupRadiusServerStatisticsChassisLevelServerStatsAllEntry 11 }

affirmedServiceconstructInterfaceAaaGroupRadiusServerStatisticsChassisLevelServerStatsAllNumDisconnectNakRx OBJECT-TYPE
    SYNTAX      ConfdString
    MAX-ACCESS  read-only
    STATUS      current
    DESCRIPTION "Number of Disconnect NAK received"
    ::= { affirmedServiceconstructInterfaceAaaGroupRadiusServerStatisticsChassisLevelServerStatsAllEntry 12 }

affirmedServiceconstructInterfaceAaaGroupRadiusServerStatisticsChassisLevelServerStatsServerTable OBJECT-TYPE
    SYNTAX      SEQUENCE OF AffirmedServiceconstructInterfaceAaaGroupRadiusServerStatisticsChassisLevelServerStatsServerEntry
    MAX-ACCESS  not-accessible
    STATUS      current
    DESCRIPTION ""
    ::= { affirmedServiceconstructInterfaceAaaGroupRadiusServerStatisticsChassisLevelServerStats 2 }

affirmedServiceconstructInterfaceAaaGroupRadiusServerStatisticsChassisLevelServerStatsServerEntry OBJECT-TYPE
    SYNTAX      AffirmedServiceconstructInterfaceAaaGroupRadiusServerStatisticsChassisLevelServerStatsServerEntry
    MAX-ACCESS  not-accessible
    STATUS      current
    DESCRIPTION ""
    INDEX { affirmedServiceconstructInterfaceAaaGroupRadiusServerStatisticsChassisLevelServerStatsServerName, affirmedServiceconstructInterfaceAaaGroupRadiusServerStatisticsChassisLevelServerStatsServerChassis }
        ::= { affirmedServiceconstructInterfaceAaaGroupRadiusServerStatisticsChassisLevelServerStatsServerTable 1 }

AffirmedServiceconstructInterfaceAaaGroupRadiusServerStatisticsChassisLevelServerStatsServerEntry ::=
    SEQUENCE {
        affirmedServiceconstructInterfaceAaaGroupRadiusServerStatisticsChassisLevelServerStatsServerName String,
        affirmedServiceconstructInterfaceAaaGroupRadiusServerStatisticsChassisLevelServerStatsServerChassis Unsigned32,
        affirmedServiceconstructInterfaceAaaGroupRadiusServerStatisticsChassisLevelServerStatsServerNumRx ConfdString,
        affirmedServiceconstructInterfaceAaaGroupRadiusServerStatisticsChassisLevelServerStatsServerNumAccessReqRx ConfdString,
        affirmedServiceconstructInterfaceAaaGroupRadiusServerStatisticsChassisLevelServerStatsServerNumAccountReqRx ConfdString,
        affirmedServiceconstructInterfaceAaaGroupRadiusServerStatisticsChassisLevelServerStatsServerNumDropErrorsRx ConfdString,
        affirmedServiceconstructInterfaceAaaGroupRadiusServerStatisticsChassisLevelServerStatsServerNumAccessAcceptTx ConfdString,
        affirmedServiceconstructInterfaceAaaGroupRadiusServerStatisticsChassisLevelServerStatsServerNumAccessRejectTx ConfdString,
        affirmedServiceconstructInterfaceAaaGroupRadiusServerStatisticsChassisLevelServerStatsServerNumAccessChallengeTx ConfdString,
        affirmedServiceconstructInterfaceAaaGroupRadiusServerStatisticsChassisLevelServerStatsServerNumAccountRespTx ConfdString,
        affirmedServiceconstructInterfaceAaaGroupRadiusServerStatisticsChassisLevelServerStatsServerNumDisconnectReqTx ConfdString,
        affirmedServiceconstructInterfaceAaaGroupRadiusServerStatisticsChassisLevelServerStatsServerNumDisconnectAckRx ConfdString,
        affirmedServiceconstructInterfaceAaaGroupRadiusServerStatisticsChassisLevelServerStatsServerNumDisconnectNakRx ConfdString
    }

affirmedServiceconstructInterfaceAaaGroupRadiusServerStatisticsChassisLevelServerStatsServerName OBJECT-TYPE
    SYNTAX      String
    MAX-ACCESS  not-accessible
    STATUS      current
    DESCRIPTION "Server Stats Table Name"
    ::= { affirmedServiceconstructInterfaceAaaGroupRadiusServerStatisticsChassisLevelServerStatsServerEntry 1 }

affirmedServiceconstructInterfaceAaaGroupRadiusServerStatisticsChassisLevelServerStatsServerChassis OBJECT-TYPE
    SYNTAX      Unsigned32
    MAX-ACCESS  not-accessible
    STATUS      current
    DESCRIPTION "chassis ID"
    ::= { affirmedServiceconstructInterfaceAaaGroupRadiusServerStatisticsChassisLevelServerStatsServerEntry 2 }

affirmedServiceconstructInterfaceAaaGroupRadiusServerStatisticsChassisLevelServerStatsServerNumRx OBJECT-TYPE
    SYNTAX      ConfdString
    MAX-ACCESS  read-only
    STATUS      current
    DESCRIPTION "Number of messages received"
    ::= { affirmedServiceconstructInterfaceAaaGroupRadiusServerStatisticsChassisLevelServerStatsServerEntry 3 }

affirmedServiceconstructInterfaceAaaGroupRadiusServerStatisticsChassisLevelServerStatsServerNumAccessReqRx OBJECT-TYPE
    SYNTAX      ConfdString
    MAX-ACCESS  read-only
    STATUS      current
    DESCRIPTION "Number of Access Requests received"
    ::= { affirmedServiceconstructInterfaceAaaGroupRadiusServerStatisticsChassisLevelServerStatsServerEntry 4 }

affirmedServiceconstructInterfaceAaaGroupRadiusServerStatisticsChassisLevelServerStatsServerNumAccountReqRx OBJECT-TYPE
    SYNTAX      ConfdString
    MAX-ACCESS  read-only
    STATUS      current
    DESCRIPTION "Number of Acccount Requests received"
    ::= { affirmedServiceconstructInterfaceAaaGroupRadiusServerStatisticsChassisLevelServerStatsServerEntry 5 }

affirmedServiceconstructInterfaceAaaGroupRadiusServerStatisticsChassisLevelServerStatsServerNumDropErrorsRx OBJECT-TYPE
    SYNTAX      ConfdString
    MAX-ACCESS  read-only
    STATUS      current
    DESCRIPTION "Number of received messages dropped in error"
    ::= { affirmedServiceconstructInterfaceAaaGroupRadiusServerStatisticsChassisLevelServerStatsServerEntry 6 }

affirmedServiceconstructInterfaceAaaGroupRadiusServerStatisticsChassisLevelServerStatsServerNumAccessAcceptTx OBJECT-TYPE
    SYNTAX      ConfdString
    MAX-ACCESS  read-only
    STATUS      current
    DESCRIPTION "Number of Access Accepts sent"
    ::= { affirmedServiceconstructInterfaceAaaGroupRadiusServerStatisticsChassisLevelServerStatsServerEntry 7 }

affirmedServiceconstructInterfaceAaaGroupRadiusServerStatisticsChassisLevelServerStatsServerNumAccessRejectTx OBJECT-TYPE
    SYNTAX      ConfdString
    MAX-ACCESS  read-only
    STATUS      current
    DESCRIPTION "Number of Access Rejects sent"
    ::= { affirmedServiceconstructInterfaceAaaGroupRadiusServerStatisticsChassisLevelServerStatsServerEntry 8 }

affirmedServiceconstructInterfaceAaaGroupRadiusServerStatisticsChassisLevelServerStatsServerNumAccessChallengeTx OBJECT-TYPE
    SYNTAX      ConfdString
    MAX-ACCESS  read-only
    STATUS      current
    DESCRIPTION "Number of Access Challenges sent"
    ::= { affirmedServiceconstructInterfaceAaaGroupRadiusServerStatisticsChassisLevelServerStatsServerEntry 9 }

affirmedServiceconstructInterfaceAaaGroupRadiusServerStatisticsChassisLevelServerStatsServerNumAccountRespTx OBJECT-TYPE
    SYNTAX      ConfdString
    MAX-ACCESS  read-only
    STATUS      current
    DESCRIPTION "Number of Account Responses sent"
    ::= { affirmedServiceconstructInterfaceAaaGroupRadiusServerStatisticsChassisLevelServerStatsServerEntry 10 }

affirmedServiceconstructInterfaceAaaGroupRadiusServerStatisticsChassisLevelServerStatsServerNumDisconnectReqTx OBJECT-TYPE
    SYNTAX      ConfdString
    MAX-ACCESS  read-only
    STATUS      current
    DESCRIPTION "Number of Disconnect Requests sent"
    ::= { affirmedServiceconstructInterfaceAaaGroupRadiusServerStatisticsChassisLevelServerStatsServerEntry 11 }

affirmedServiceconstructInterfaceAaaGroupRadiusServerStatisticsChassisLevelServerStatsServerNumDisconnectAckRx OBJECT-TYPE
    SYNTAX      ConfdString
    MAX-ACCESS  read-only
    STATUS      current
    DESCRIPTION "Number of Disconnect ACK received"
    ::= { affirmedServiceconstructInterfaceAaaGroupRadiusServerStatisticsChassisLevelServerStatsServerEntry 12 }

affirmedServiceconstructInterfaceAaaGroupRadiusServerStatisticsChassisLevelServerStatsServerNumDisconnectNakRx OBJECT-TYPE
    SYNTAX      ConfdString
    MAX-ACCESS  read-only
    STATUS      current
    DESCRIPTION "Number of Disconnect NAK received"
    ::= { affirmedServiceconstructInterfaceAaaGroupRadiusServerStatisticsChassisLevelServerStatsServerEntry 13 }

affirmedServiceconstructInterfaceIpmsStatisticsPeerTable OBJECT-TYPE
    SYNTAX      SEQUENCE OF AffirmedServiceconstructInterfaceIpmsStatisticsPeerEntry
    MAX-ACCESS  not-accessible
    STATUS      current
    DESCRIPTION ""
    ::= { affirmedServiceconstructInterfaceIpmsStatistics 1 }

affirmedServiceconstructInterfaceIpmsStatisticsPeerEntry OBJECT-TYPE
    SYNTAX      AffirmedServiceconstructInterfaceIpmsStatisticsPeerEntry
    MAX-ACCESS  not-accessible
    STATUS      current
    DESCRIPTION ""
    INDEX { affirmedServiceconstructInterfaceIpmsStatisticsPeerName }
        ::= { affirmedServiceconstructInterfaceIpmsStatisticsPeerTable 1 }

AffirmedServiceconstructInterfaceIpmsStatisticsPeerEntry ::=
    SEQUENCE {
        affirmedServiceconstructInterfaceIpmsStatisticsPeerName String,
        affirmedServiceconstructInterfaceIpmsStatisticsPeerNumUeIdRequestsRx ConfdString,
        affirmedServiceconstructInterfaceIpmsStatisticsPeerNumUeIdAnswersTx ConfdString,
        affirmedServiceconstructInterfaceIpmsStatisticsPeerNumUeIdRequestsMmscRx ConfdString,
        affirmedServiceconstructInterfaceIpmsStatisticsPeerUeIdRequestsUstoreRx ConfdString,
        affirmedServiceconstructInterfaceIpmsStatisticsPeerNumUeIdRequestsIpnmsRx ConfdString,
        affirmedServiceconstructInterfaceIpmsStatisticsPeerNumUeIdRequestsPhonebillRx ConfdString,
        affirmedServiceconstructInterfaceIpmsStatisticsPeerNumUeIdRequestsWapGwRx ConfdString,
        affirmedServiceconstructInterfaceIpmsStatisticsPeerNumUeIdRequestsEtcRx ConfdString,
        affirmedServiceconstructInterfaceIpmsStatisticsPeerNumUeIdRequestsIpv4Rx ConfdString,
        affirmedServiceconstructInterfaceIpmsStatisticsPeerNumUeIdRequestsIpv6Rx ConfdString,
        affirmedServiceconstructInterfaceIpmsStatisticsPeerNumUeIdAnswersSuccessTx ConfdString,
        affirmedServiceconstructInterfaceIpmsStatisticsPeerNumUeIdAnswersPartialSuccessTx ConfdString,
        affirmedServiceconstructInterfaceIpmsStatisticsPeerNumUeIdAnswersInvalidStructureTx ConfdString,
        affirmedServiceconstructInterfaceIpmsStatisticsPeerNumUeIdAnswersSystemOverloadTx ConfdString,
        affirmedServiceconstructInterfaceIpmsStatisticsPeerNumUeIdAnswersTpsControlledTx ConfdString,
        affirmedServiceconstructInterfaceIpmsStatisticsPeerNumUeIdAnswersNoSubscribersTx ConfdString,
        affirmedServiceconstructInterfaceIpmsStatisticsPeerNumUeIdAnswersUndefinedErrorsTx ConfdString,
        affirmedServiceconstructInterfaceIpmsStatisticsPeerNumUeIdAnswersFailedTx ConfdString,
        affirmedServiceconstructInterfaceIpmsStatisticsPeerNumUeIdAnswersIpv4Tx ConfdString,
        affirmedServiceconstructInterfaceIpmsStatisticsPeerNumUeIdAnswersIpv6Tx ConfdString,
        affirmedServiceconstructInterfaceIpmsStatisticsPeerNumUeIdRequestUnregisteredServer ConfdString,
        affirmedServiceconstructInterfaceIpmsStatisticsPeerNumUeIdMiscDrops ConfdString
    }

affirmedServiceconstructInterfaceIpmsStatisticsPeerName OBJECT-TYPE
    SYNTAX      String
    MAX-ACCESS  not-accessible
    STATUS      current
    DESCRIPTION "Peer Stats Table Name"
    ::= { affirmedServiceconstructInterfaceIpmsStatisticsPeerEntry 1 }

affirmedServiceconstructInterfaceIpmsStatisticsPeerNumUeIdRequestsRx OBJECT-TYPE
    SYNTAX      ConfdString
    MAX-ACCESS  read-only
    STATUS      current
    DESCRIPTION "Number of UE Id Requests Rx"
    ::= { affirmedServiceconstructInterfaceIpmsStatisticsPeerEntry 2 }

affirmedServiceconstructInterfaceIpmsStatisticsPeerNumUeIdAnswersTx OBJECT-TYPE
    SYNTAX      ConfdString
    MAX-ACCESS  read-only
    STATUS      current
    DESCRIPTION "Number of UE Id Answers Tx"
    ::= { affirmedServiceconstructInterfaceIpmsStatisticsPeerEntry 3 }

affirmedServiceconstructInterfaceIpmsStatisticsPeerNumUeIdRequestsMmscRx OBJECT-TYPE
    SYNTAX      ConfdString
    MAX-ACCESS  read-only
    STATUS      current
    DESCRIPTION "Number of UE Id Requests Mmsc Rx"
    ::= { affirmedServiceconstructInterfaceIpmsStatisticsPeerEntry 4 }

affirmedServiceconstructInterfaceIpmsStatisticsPeerUeIdRequestsUstoreRx OBJECT-TYPE
    SYNTAX      ConfdString
    MAX-ACCESS  read-only
    STATUS      current
    DESCRIPTION "Number of UE Id Requests Ustore Rx"
    ::= { affirmedServiceconstructInterfaceIpmsStatisticsPeerEntry 5 }

affirmedServiceconstructInterfaceIpmsStatisticsPeerNumUeIdRequestsIpnmsRx OBJECT-TYPE
    SYNTAX      ConfdString
    MAX-ACCESS  read-only
    STATUS      current
    DESCRIPTION "Number of UE Id Requests Ipnms Rx"
    ::= { affirmedServiceconstructInterfaceIpmsStatisticsPeerEntry 6 }

affirmedServiceconstructInterfaceIpmsStatisticsPeerNumUeIdRequestsPhonebillRx OBJECT-TYPE
    SYNTAX      ConfdString
    MAX-ACCESS  read-only
    STATUS      current
    DESCRIPTION "Number of UE Id Requests Phonebill Rx"
    ::= { affirmedServiceconstructInterfaceIpmsStatisticsPeerEntry 7 }

affirmedServiceconstructInterfaceIpmsStatisticsPeerNumUeIdRequestsWapGwRx OBJECT-TYPE
    SYNTAX      ConfdString
    MAX-ACCESS  read-only
    STATUS      current
    DESCRIPTION "Number of UE Id Requests Wap Gw Rx"
    ::= { affirmedServiceconstructInterfaceIpmsStatisticsPeerEntry 8 }

affirmedServiceconstructInterfaceIpmsStatisticsPeerNumUeIdRequestsEtcRx OBJECT-TYPE
    SYNTAX      ConfdString
    MAX-ACCESS  read-only
    STATUS      current
    DESCRIPTION "Number of UE Id Request Etc Rx"
    ::= { affirmedServiceconstructInterfaceIpmsStatisticsPeerEntry 9 }

affirmedServiceconstructInterfaceIpmsStatisticsPeerNumUeIdRequestsIpv4Rx OBJECT-TYPE
    SYNTAX      ConfdString
    MAX-ACCESS  read-only
    STATUS      current
    DESCRIPTION "Number of UE Id Requests Ipv4 Rx"
    ::= { affirmedServiceconstructInterfaceIpmsStatisticsPeerEntry 10 }

affirmedServiceconstructInterfaceIpmsStatisticsPeerNumUeIdRequestsIpv6Rx OBJECT-TYPE
    SYNTAX      ConfdString
    MAX-ACCESS  read-only
    STATUS      current
    DESCRIPTION "Number of UE Id Requests Ipv6 Rx"
    ::= { affirmedServiceconstructInterfaceIpmsStatisticsPeerEntry 11 }

affirmedServiceconstructInterfaceIpmsStatisticsPeerNumUeIdAnswersSuccessTx OBJECT-TYPE
    SYNTAX      ConfdString
    MAX-ACCESS  read-only
    STATUS      current
    DESCRIPTION "Number of UE Id Answers Success Tx"
    ::= { affirmedServiceconstructInterfaceIpmsStatisticsPeerEntry 12 }

affirmedServiceconstructInterfaceIpmsStatisticsPeerNumUeIdAnswersPartialSuccessTx OBJECT-TYPE
    SYNTAX      ConfdString
    MAX-ACCESS  read-only
    STATUS      current
    DESCRIPTION "Number of UE Id Answers Partial Success Tx"
    ::= { affirmedServiceconstructInterfaceIpmsStatisticsPeerEntry 13 }

affirmedServiceconstructInterfaceIpmsStatisticsPeerNumUeIdAnswersInvalidStructureTx OBJECT-TYPE
    SYNTAX      ConfdString
    MAX-ACCESS  read-only
    STATUS      current
    DESCRIPTION "Number of UE Id Answers Invalid Structure Tx"
    ::= { affirmedServiceconstructInterfaceIpmsStatisticsPeerEntry 14 }

affirmedServiceconstructInterfaceIpmsStatisticsPeerNumUeIdAnswersSystemOverloadTx OBJECT-TYPE
    SYNTAX      ConfdString
    MAX-ACCESS  read-only
    STATUS      current
    DESCRIPTION "Number of UE Id Answers System Overload Tx"
    ::= { affirmedServiceconstructInterfaceIpmsStatisticsPeerEntry 15 }

affirmedServiceconstructInterfaceIpmsStatisticsPeerNumUeIdAnswersTpsControlledTx OBJECT-TYPE
    SYNTAX      ConfdString
    MAX-ACCESS  read-only
    STATUS      current
    DESCRIPTION "Number of UE Id Answers Tps Controlled Tx"
    ::= { affirmedServiceconstructInterfaceIpmsStatisticsPeerEntry 16 }

affirmedServiceconstructInterfaceIpmsStatisticsPeerNumUeIdAnswersNoSubscribersTx OBJECT-TYPE
    SYNTAX      ConfdString
    MAX-ACCESS  read-only
    STATUS      current
    DESCRIPTION "Number of UE Id Answers No Subscribers Tx"
    ::= { affirmedServiceconstructInterfaceIpmsStatisticsPeerEntry 17 }

affirmedServiceconstructInterfaceIpmsStatisticsPeerNumUeIdAnswersUndefinedErrorsTx OBJECT-TYPE
    SYNTAX      ConfdString
    MAX-ACCESS  read-only
    STATUS      current
    DESCRIPTION "Number of UE Id Answers Undefined Errors Tx"
    ::= { affirmedServiceconstructInterfaceIpmsStatisticsPeerEntry 18 }

affirmedServiceconstructInterfaceIpmsStatisticsPeerNumUeIdAnswersFailedTx OBJECT-TYPE
    SYNTAX      ConfdString
    MAX-ACCESS  read-only
    STATUS      current
    DESCRIPTION "Number of UE Id Answers Failed Tx"
    ::= { affirmedServiceconstructInterfaceIpmsStatisticsPeerEntry 19 }

affirmedServiceconstructInterfaceIpmsStatisticsPeerNumUeIdAnswersIpv4Tx OBJECT-TYPE
    SYNTAX      ConfdString
    MAX-ACCESS  read-only
    STATUS      current
    DESCRIPTION "Number of UE Id Answers IPv4 Tx"
    ::= { affirmedServiceconstructInterfaceIpmsStatisticsPeerEntry 20 }

affirmedServiceconstructInterfaceIpmsStatisticsPeerNumUeIdAnswersIpv6Tx OBJECT-TYPE
    SYNTAX      ConfdString
    MAX-ACCESS  read-only
    STATUS      current
    DESCRIPTION "Number of UE Id Answers IPv6 Tx"
    ::= { affirmedServiceconstructInterfaceIpmsStatisticsPeerEntry 21 }

affirmedServiceconstructInterfaceIpmsStatisticsPeerNumUeIdRequestUnregisteredServer OBJECT-TYPE
    SYNTAX      ConfdString
    MAX-ACCESS  read-only
    STATUS      current
    DESCRIPTION "Number of UE Id Request Unregistered Server"
    ::= { affirmedServiceconstructInterfaceIpmsStatisticsPeerEntry 22 }

affirmedServiceconstructInterfaceIpmsStatisticsPeerNumUeIdMiscDrops OBJECT-TYPE
    SYNTAX      ConfdString
    MAX-ACCESS  read-only
    STATUS      current
    DESCRIPTION "Number of UE Id Misc Drops"
    ::= { affirmedServiceconstructInterfaceIpmsStatisticsPeerEntry 23 }

affirmedServiceconstructInterfaceIpmsStatusPeerStatusTable OBJECT-TYPE
    SYNTAX      SEQUENCE OF AffirmedServiceconstructInterfaceIpmsStatusPeerStatusEntry
    MAX-ACCESS  not-accessible
    STATUS      current
    DESCRIPTION ""
    ::= { affirmedServiceconstructInterfaceIpmsStatus 1 }

affirmedServiceconstructInterfaceIpmsStatusPeerStatusEntry OBJECT-TYPE
    SYNTAX      AffirmedServiceconstructInterfaceIpmsStatusPeerStatusEntry
    MAX-ACCESS  not-accessible
    STATUS      current
    DESCRIPTION ""
    INDEX { affirmedServiceconstructInterfaceIpmsStatusPeerStatusServerName, affirmedServiceconstructInterfaceIpmsStatusPeerStatusPeerName }
        ::= { affirmedServiceconstructInterfaceIpmsStatusPeerStatusTable 1 }

AffirmedServiceconstructInterfaceIpmsStatusPeerStatusEntry ::=
    SEQUENCE {
        affirmedServiceconstructInterfaceIpmsStatusPeerStatusServerName String,
        affirmedServiceconstructInterfaceIpmsStatusPeerStatusPeerName String,
        affirmedServiceconstructInterfaceIpmsStatusPeerStatusOperStatus INTEGER,
        affirmedServiceconstructInterfaceIpmsStatusPeerStatusOperReason String,
        affirmedServiceconstructInterfaceIpmsStatusPeerStatusAdminStatus INTEGER,
        affirmedServiceconstructInterfaceIpmsStatusPeerStatusLocalIpAddress String,
        affirmedServiceconstructInterfaceIpmsStatusPeerStatusLocalPortNum Unsigned32,
        affirmedServiceconstructInterfaceIpmsStatusPeerStatusRemoteIpAddress String,
        affirmedServiceconstructInterfaceIpmsStatusPeerStatusRemotePortNum Unsigned32
    }

affirmedServiceconstructInterfaceIpmsStatusPeerStatusServerName OBJECT-TYPE
    SYNTAX      String
    MAX-ACCESS  not-accessible
    STATUS      current
    DESCRIPTION "Server Group Name"
    ::= { affirmedServiceconstructInterfaceIpmsStatusPeerStatusEntry 1 }

affirmedServiceconstructInterfaceIpmsStatusPeerStatusPeerName OBJECT-TYPE
    SYNTAX      String
    MAX-ACCESS  not-accessible
    STATUS      current
    DESCRIPTION "Ipms Peer Name"
    ::= { affirmedServiceconstructInterfaceIpmsStatusPeerStatusEntry 2 }

affirmedServiceconstructInterfaceIpmsStatusPeerStatusOperStatus OBJECT-TYPE
    SYNTAX      INTEGER {up(101),down(102),partially-up(103),maint(104),dryup(105),congested(106),unknown(107)}
    MAX-ACCESS  read-only
    STATUS      current
    DESCRIPTION "Operational Status"
    ::= { affirmedServiceconstructInterfaceIpmsStatusPeerStatusEntry 3 }

affirmedServiceconstructInterfaceIpmsStatusPeerStatusOperReason OBJECT-TYPE
    SYNTAX      String
    MAX-ACCESS  read-only
    STATUS      current
    DESCRIPTION "Operational Reason if state is Operationally Down"
    ::= { affirmedServiceconstructInterfaceIpmsStatusPeerStatusEntry 4 }

affirmedServiceconstructInterfaceIpmsStatusPeerStatusAdminStatus OBJECT-TYPE
    SYNTAX      INTEGER {disabled(0),enabled(1)}
    MAX-ACCESS  read-only
    STATUS      current
    DESCRIPTION "Admin Status"
    ::= { affirmedServiceconstructInterfaceIpmsStatusPeerStatusEntry 5 }

affirmedServiceconstructInterfaceIpmsStatusPeerStatusLocalIpAddress OBJECT-TYPE
    SYNTAX      String
    MAX-ACCESS  read-only
    STATUS      current
    DESCRIPTION "Local Ip Address of Ipms Interface. Can be IPv4/IPv6"
    ::= { affirmedServiceconstructInterfaceIpmsStatusPeerStatusEntry 6 }

affirmedServiceconstructInterfaceIpmsStatusPeerStatusLocalPortNum OBJECT-TYPE
    SYNTAX      Unsigned32
    MAX-ACCESS  read-only
    STATUS      current
    DESCRIPTION "Start Local Port Number"
    ::= { affirmedServiceconstructInterfaceIpmsStatusPeerStatusEntry 7 }

affirmedServiceconstructInterfaceIpmsStatusPeerStatusRemoteIpAddress OBJECT-TYPE
    SYNTAX      String
    MAX-ACCESS  read-only
    STATUS      current
    DESCRIPTION "Remote Ip Address of Ipms Interface. Can be IPv4/IPv6"
    ::= { affirmedServiceconstructInterfaceIpmsStatusPeerStatusEntry 8 }

affirmedServiceconstructInterfaceIpmsStatusPeerStatusRemotePortNum OBJECT-TYPE
    SYNTAX      Unsigned32
    MAX-ACCESS  read-only
    STATUS      current
    DESCRIPTION "Remote Port Number"
    ::= { affirmedServiceconstructInterfaceIpmsStatusPeerStatusEntry 9 }

affirmedServiceconstructInterfaceDb-interfaceStatisticsTable OBJECT-TYPE
    SYNTAX      SEQUENCE OF AffirmedServiceconstructInterfaceDb-interfaceStatisticsEntry
    MAX-ACCESS  not-accessible
    STATUS      current
    DESCRIPTION ""
    ::= { affirmedServiceconstructInterfaceDb-interface 1 }

affirmedServiceconstructInterfaceDb-interfaceStatisticsEntry OBJECT-TYPE
    SYNTAX      AffirmedServiceconstructInterfaceDb-interfaceStatisticsEntry
    MAX-ACCESS  not-accessible
    STATUS      current
    DESCRIPTION ""
    INDEX { affirmedServiceconstructInterfaceDb-interfaceStatisticsChassis, affirmedServiceconstructInterfaceDb-interfaceStatisticsName }
        ::= { affirmedServiceconstructInterfaceDb-interfaceStatisticsTable 1 }

AffirmedServiceconstructInterfaceDb-interfaceStatisticsEntry ::=
    SEQUENCE {
        affirmedServiceconstructInterfaceDb-interfaceStatisticsName String,
        affirmedServiceconstructInterfaceDb-interfaceStatisticsChassis Unsigned32,
        affirmedServiceconstructInterfaceDb-interfaceStatisticsNumGetReq ConfdString,
        affirmedServiceconstructInterfaceDb-interfaceStatisticsNumSetReq ConfdString,
        affirmedServiceconstructInterfaceDb-interfaceStatisticsNumDeleteReq ConfdString,
        affirmedServiceconstructInterfaceDb-interfaceStatisticsNumGetReqTimeout ConfdString,
        affirmedServiceconstructInterfaceDb-interfaceStatisticsNumSetReqTimeout ConfdString,
        affirmedServiceconstructInterfaceDb-interfaceStatisticsNumDeleteReqTimeout ConfdString
    }

affirmedServiceconstructInterfaceDb-interfaceStatisticsName OBJECT-TYPE
    SYNTAX      String
    MAX-ACCESS  not-accessible
    STATUS      current
    DESCRIPTION "Table Name"
    ::= { affirmedServiceconstructInterfaceDb-interfaceStatisticsEntry 1 }

affirmedServiceconstructInterfaceDb-interfaceStatisticsChassis OBJECT-TYPE
    SYNTAX      Unsigned32
    MAX-ACCESS  not-accessible
    STATUS      current
    DESCRIPTION "chassis ID"
    ::= { affirmedServiceconstructInterfaceDb-interfaceStatisticsEntry 2 }

affirmedServiceconstructInterfaceDb-interfaceStatisticsNumGetReq OBJECT-TYPE
    SYNTAX      ConfdString
    MAX-ACCESS  read-only
    STATUS      current
    DESCRIPTION "Total number of GET requests sent"
    ::= { affirmedServiceconstructInterfaceDb-interfaceStatisticsEntry 3 }

affirmedServiceconstructInterfaceDb-interfaceStatisticsNumSetReq OBJECT-TYPE
    SYNTAX      ConfdString
    MAX-ACCESS  read-only
    STATUS      current
    DESCRIPTION "Total number of SET requests sent"
    ::= { affirmedServiceconstructInterfaceDb-interfaceStatisticsEntry 4 }

affirmedServiceconstructInterfaceDb-interfaceStatisticsNumDeleteReq OBJECT-TYPE
    SYNTAX      ConfdString
    MAX-ACCESS  read-only
    STATUS      current
    DESCRIPTION "Total number of DELETE requests sent"
    ::= { affirmedServiceconstructInterfaceDb-interfaceStatisticsEntry 5 }

affirmedServiceconstructInterfaceDb-interfaceStatisticsNumGetReqTimeout OBJECT-TYPE
    SYNTAX      ConfdString
    MAX-ACCESS  read-only
    STATUS      current
    DESCRIPTION "Total number of GET requests timeout"
    ::= { affirmedServiceconstructInterfaceDb-interfaceStatisticsEntry 6 }

affirmedServiceconstructInterfaceDb-interfaceStatisticsNumSetReqTimeout OBJECT-TYPE
    SYNTAX      ConfdString
    MAX-ACCESS  read-only
    STATUS      current
    DESCRIPTION "Total number of SET requests timeout"
    ::= { affirmedServiceconstructInterfaceDb-interfaceStatisticsEntry 7 }

affirmedServiceconstructInterfaceDb-interfaceStatisticsNumDeleteReqTimeout OBJECT-TYPE
    SYNTAX      ConfdString
    MAX-ACCESS  read-only
    STATUS      current
    DESCRIPTION "Total number of DELETE requests timeout"
    ::= { affirmedServiceconstructInterfaceDb-interfaceStatisticsEntry 8 }

affirmedServiceconstructInterfaceT8InterfaceStatisticsDebugRestClientHttpStatsTable OBJECT-TYPE
    SYNTAX      SEQUENCE OF AffirmedServiceconstructInterfaceT8InterfaceStatisticsDebugRestClientHttpStatsEntry
    MAX-ACCESS  not-accessible
    STATUS      current
    DESCRIPTION ""
    ::= { affirmedServiceconstructInterfaceT8InterfaceStatisticsDebugRestClient 1 }

affirmedServiceconstructInterfaceT8InterfaceStatisticsDebugRestClientHttpStatsEntry OBJECT-TYPE
    SYNTAX      AffirmedServiceconstructInterfaceT8InterfaceStatisticsDebugRestClientHttpStatsEntry
    MAX-ACCESS  not-accessible
    STATUS      current
    DESCRIPTION ""
    INDEX { affirmedServiceconstructInterfaceT8InterfaceStatisticsDebugRestClientHttpStatsServiceName }
        ::= { affirmedServiceconstructInterfaceT8InterfaceStatisticsDebugRestClientHttpStatsTable 1 }

AffirmedServiceconstructInterfaceT8InterfaceStatisticsDebugRestClientHttpStatsEntry ::=
    SEQUENCE {
        affirmedServiceconstructInterfaceT8InterfaceStatisticsDebugRestClientHttpStatsServiceName String,
        affirmedServiceconstructInterfaceT8InterfaceStatisticsDebugRestClientHttpStatsHTTPClientConnectionTotal ConfdString,
        affirmedServiceconstructInterfaceT8InterfaceStatisticsDebugRestClientHttpStatsHTTPClientConnectionsInUse ConfdString,
        affirmedServiceconstructInterfaceT8InterfaceStatisticsDebugRestClientHttpStatsHTTPClientConnectionTerminated ConfdString,
        affirmedServiceconstructInterfaceT8InterfaceStatisticsDebugRestClientHttpStatsHTTPClientIPV4 ConfdString,
        affirmedServiceconstructInterfaceT8InterfaceStatisticsDebugRestClientHttpStatsHTTPClientIPV6 ConfdString,
        affirmedServiceconstructInterfaceT8InterfaceStatisticsDebugRestClientHttpStatsHTTPClientErrorsTotal ConfdString,
        affirmedServiceconstructInterfaceT8InterfaceStatisticsDebugRestClientHttpStatsHTTPClientTCPConnectionTimeout ConfdString,
        affirmedServiceconstructInterfaceT8InterfaceStatisticsDebugRestClientHttpStatsHTTPClientHTTPLevelMaxRetryExceeded ConfdString,
        affirmedServiceconstructInterfaceT8InterfaceStatisticsDebugRestClientHttpStatsHTTPClientTCPLevelMaxRetryExceeded ConfdString,
        affirmedServiceconstructInterfaceT8InterfaceStatisticsDebugRestClientHttpStatsHTTPClientRejectedAgeExceeded ConfdString,
        affirmedServiceconstructInterfaceT8InterfaceStatisticsDebugRestClientHttpStatsHTTPClientTCPDropsByPeer ConfdString,
        affirmedServiceconstructInterfaceT8InterfaceStatisticsDebugRestClientHttpStatsHTTPClientReadError ConfdString,
        affirmedServiceconstructInterfaceT8InterfaceStatisticsDebugRestClientHttpStatsHTTPClientWriteError ConfdString,
        affirmedServiceconstructInterfaceT8InterfaceStatisticsDebugRestClientHttpStatsHTTPClientConnRefusedError ConfdString,
        affirmedServiceconstructInterfaceT8InterfaceStatisticsDebugRestClientHttpStatsHTTPClientEOFError ConfdString
    }

affirmedServiceconstructInterfaceT8InterfaceStatisticsDebugRestClientHttpStatsServiceName OBJECT-TYPE
    SYNTAX      String
    MAX-ACCESS  not-accessible
    STATUS      current
    DESCRIPTION "Task Service Name"
    ::= { affirmedServiceconstructInterfaceT8InterfaceStatisticsDebugRestClientHttpStatsEntry 1 }

affirmedServiceconstructInterfaceT8InterfaceStatisticsDebugRestClientHttpStatsHTTPClientConnectionTotal OBJECT-TYPE
    SYNTAX      ConfdString
    MAX-ACCESS  read-only
    STATUS      current
    DESCRIPTION "Client Connections - Total"
    ::= { affirmedServiceconstructInterfaceT8InterfaceStatisticsDebugRestClientHttpStatsEntry 2 }

affirmedServiceconstructInterfaceT8InterfaceStatisticsDebugRestClientHttpStatsHTTPClientConnectionsInUse OBJECT-TYPE
    SYNTAX      ConfdString
    MAX-ACCESS  read-only
    STATUS      current
    DESCRIPTION "Client Connections - Currently in Use"
    ::= { affirmedServiceconstructInterfaceT8InterfaceStatisticsDebugRestClientHttpStatsEntry 3 }

affirmedServiceconstructInterfaceT8InterfaceStatisticsDebugRestClientHttpStatsHTTPClientConnectionTerminated OBJECT-TYPE
    SYNTAX      ConfdString
    MAX-ACCESS  read-only
    STATUS      current
    DESCRIPTION "Client Connections - Terminated"
    ::= { affirmedServiceconstructInterfaceT8InterfaceStatisticsDebugRestClientHttpStatsEntry 4 }

affirmedServiceconstructInterfaceT8InterfaceStatisticsDebugRestClientHttpStatsHTTPClientIPV4 OBJECT-TYPE
    SYNTAX      ConfdString
    MAX-ACCESS  read-only
    STATUS      current
    DESCRIPTION "Client Connections - IPv4"
    ::= { affirmedServiceconstructInterfaceT8InterfaceStatisticsDebugRestClientHttpStatsEntry 5 }

affirmedServiceconstructInterfaceT8InterfaceStatisticsDebugRestClientHttpStatsHTTPClientIPV6 OBJECT-TYPE
    SYNTAX      ConfdString
    MAX-ACCESS  read-only
    STATUS      current
    DESCRIPTION "Client Connections - IPv6"
    ::= { affirmedServiceconstructInterfaceT8InterfaceStatisticsDebugRestClientHttpStatsEntry 6 }

affirmedServiceconstructInterfaceT8InterfaceStatisticsDebugRestClientHttpStatsHTTPClientErrorsTotal OBJECT-TYPE
    SYNTAX      ConfdString
    MAX-ACCESS  read-only
    STATUS      current
    DESCRIPTION "Client Errors - Total"
    ::= { affirmedServiceconstructInterfaceT8InterfaceStatisticsDebugRestClientHttpStatsEntry 7 }

affirmedServiceconstructInterfaceT8InterfaceStatisticsDebugRestClientHttpStatsHTTPClientTCPConnectionTimeout OBJECT-TYPE
    SYNTAX      ConfdString
    MAX-ACCESS  read-only
    STATUS      current
    DESCRIPTION "Client Errors - Connection Timeout"
    ::= { affirmedServiceconstructInterfaceT8InterfaceStatisticsDebugRestClientHttpStatsEntry 8 }

affirmedServiceconstructInterfaceT8InterfaceStatisticsDebugRestClientHttpStatsHTTPClientHTTPLevelMaxRetryExceeded OBJECT-TYPE
    SYNTAX      ConfdString
    MAX-ACCESS  read-only
    STATUS      current
    DESCRIPTION "Client Errors - HTTP Level Max Retry Exceeded"
    ::= { affirmedServiceconstructInterfaceT8InterfaceStatisticsDebugRestClientHttpStatsEntry 9 }

affirmedServiceconstructInterfaceT8InterfaceStatisticsDebugRestClientHttpStatsHTTPClientTCPLevelMaxRetryExceeded OBJECT-TYPE
    SYNTAX      ConfdString
    MAX-ACCESS  read-only
    STATUS      current
    DESCRIPTION "Client Errors - TCP Level Max Retry Exceeded"
    ::= { affirmedServiceconstructInterfaceT8InterfaceStatisticsDebugRestClientHttpStatsEntry 10 }

affirmedServiceconstructInterfaceT8InterfaceStatisticsDebugRestClientHttpStatsHTTPClientRejectedAgeExceeded OBJECT-TYPE
    SYNTAX      ConfdString
    MAX-ACCESS  read-only
    STATUS      current
    DESCRIPTION "Client Errors - Request Age Exceeded"
    ::= { affirmedServiceconstructInterfaceT8InterfaceStatisticsDebugRestClientHttpStatsEntry 11 }

affirmedServiceconstructInterfaceT8InterfaceStatisticsDebugRestClientHttpStatsHTTPClientTCPDropsByPeer OBJECT-TYPE
    SYNTAX      ConfdString
    MAX-ACCESS  read-only
    STATUS      current
    DESCRIPTION "Client Errors - TCP Drops By Peer"
    ::= { affirmedServiceconstructInterfaceT8InterfaceStatisticsDebugRestClientHttpStatsEntry 12 }

affirmedServiceconstructInterfaceT8InterfaceStatisticsDebugRestClientHttpStatsHTTPClientReadError OBJECT-TYPE
    SYNTAX      ConfdString
    MAX-ACCESS  read-only
    STATUS      current
    DESCRIPTION "Client Errors - Read Error"
    ::= { affirmedServiceconstructInterfaceT8InterfaceStatisticsDebugRestClientHttpStatsEntry 13 }

affirmedServiceconstructInterfaceT8InterfaceStatisticsDebugRestClientHttpStatsHTTPClientWriteError OBJECT-TYPE
    SYNTAX      ConfdString
    MAX-ACCESS  read-only
    STATUS      current
    DESCRIPTION "Client Errors - Write Error"
    ::= { affirmedServiceconstructInterfaceT8InterfaceStatisticsDebugRestClientHttpStatsEntry 14 }

affirmedServiceconstructInterfaceT8InterfaceStatisticsDebugRestClientHttpStatsHTTPClientConnRefusedError OBJECT-TYPE
    SYNTAX      ConfdString
    MAX-ACCESS  read-only
    STATUS      current
    DESCRIPTION "Client Errors - Conn Refused Error"
    ::= { affirmedServiceconstructInterfaceT8InterfaceStatisticsDebugRestClientHttpStatsEntry 15 }

affirmedServiceconstructInterfaceT8InterfaceStatisticsDebugRestClientHttpStatsHTTPClientEOFError OBJECT-TYPE
    SYNTAX      ConfdString
    MAX-ACCESS  read-only
    STATUS      current
    DESCRIPTION "Client Errors - EOF Error"
    ::= { affirmedServiceconstructInterfaceT8InterfaceStatisticsDebugRestClientHttpStatsEntry 16 }

affirmedServiceconstructInterfaceT8InterfaceStatisticsDebugRestClientHttpsStatsTable OBJECT-TYPE
    SYNTAX      SEQUENCE OF AffirmedServiceconstructInterfaceT8InterfaceStatisticsDebugRestClientHttpsStatsEntry
    MAX-ACCESS  not-accessible
    STATUS      current
    DESCRIPTION ""
    ::= { affirmedServiceconstructInterfaceT8InterfaceStatisticsDebugRestClient 2 }

affirmedServiceconstructInterfaceT8InterfaceStatisticsDebugRestClientHttpsStatsEntry OBJECT-TYPE
    SYNTAX      AffirmedServiceconstructInterfaceT8InterfaceStatisticsDebugRestClientHttpsStatsEntry
    MAX-ACCESS  not-accessible
    STATUS      current
    DESCRIPTION ""
    INDEX { affirmedServiceconstructInterfaceT8InterfaceStatisticsDebugRestClientHttpsStatsServiceName }
        ::= { affirmedServiceconstructInterfaceT8InterfaceStatisticsDebugRestClientHttpsStatsTable 1 }

AffirmedServiceconstructInterfaceT8InterfaceStatisticsDebugRestClientHttpsStatsEntry ::=
    SEQUENCE {
        affirmedServiceconstructInterfaceT8InterfaceStatisticsDebugRestClientHttpsStatsServiceName String,
        affirmedServiceconstructInterfaceT8InterfaceStatisticsDebugRestClientHttpsStatsHTTPsClientConnectionTotal ConfdString,
        affirmedServiceconstructInterfaceT8InterfaceStatisticsDebugRestClientHttpsStatsHTTPsClientConnectionsInUse ConfdString,
        affirmedServiceconstructInterfaceT8InterfaceStatisticsDebugRestClientHttpsStatsHTTPsClientConnectionTerminated ConfdString,
        affirmedServiceconstructInterfaceT8InterfaceStatisticsDebugRestClientHttpsStatsHTTPsClientIPV4 ConfdString,
        affirmedServiceconstructInterfaceT8InterfaceStatisticsDebugRestClientHttpsStatsHTTPsClientIPV6 ConfdString,
        affirmedServiceconstructInterfaceT8InterfaceStatisticsDebugRestClientHttpsStatsHTTPsClientErrorsTotal ConfdString,
        affirmedServiceconstructInterfaceT8InterfaceStatisticsDebugRestClientHttpsStatsHTTPsClientTCPConnectionTimeout ConfdString,
        affirmedServiceconstructInterfaceT8InterfaceStatisticsDebugRestClientHttpsStatsHTTPsClientTLSHandShakeFailureError ConfdString,
        affirmedServiceconstructInterfaceT8InterfaceStatisticsDebugRestClientHttpsStatsHTTPsClientHTTPsLevelMaxRetryExceeded ConfdString,
        affirmedServiceconstructInterfaceT8InterfaceStatisticsDebugRestClientHttpsStatsHTTPsClientTCPLevelMaxRetryExceeded ConfdString,
        affirmedServiceconstructInterfaceT8InterfaceStatisticsDebugRestClientHttpsStatsHTTPsClientRejectedAgeExceeded ConfdString,
        affirmedServiceconstructInterfaceT8InterfaceStatisticsDebugRestClientHttpsStatsHTTPsClientTCPDropsByPeer ConfdString,
        affirmedServiceconstructInterfaceT8InterfaceStatisticsDebugRestClientHttpsStatsHTTPsClientReadError ConfdString,
        affirmedServiceconstructInterfaceT8InterfaceStatisticsDebugRestClientHttpsStatsHTTPsClientWriteError ConfdString,
        affirmedServiceconstructInterfaceT8InterfaceStatisticsDebugRestClientHttpsStatsHTTPsClientConnRefusedError ConfdString,
        affirmedServiceconstructInterfaceT8InterfaceStatisticsDebugRestClientHttpsStatsHTTPsClientEOFError ConfdString
    }

affirmedServiceconstructInterfaceT8InterfaceStatisticsDebugRestClientHttpsStatsServiceName OBJECT-TYPE
    SYNTAX      String
    MAX-ACCESS  not-accessible
    STATUS      current
    DESCRIPTION "Task Service Name"
    ::= { affirmedServiceconstructInterfaceT8InterfaceStatisticsDebugRestClientHttpsStatsEntry 1 }

affirmedServiceconstructInterfaceT8InterfaceStatisticsDebugRestClientHttpsStatsHTTPsClientConnectionTotal OBJECT-TYPE
    SYNTAX      ConfdString
    MAX-ACCESS  read-only
    STATUS      current
    DESCRIPTION "Client Connections - Total"
    ::= { affirmedServiceconstructInterfaceT8InterfaceStatisticsDebugRestClientHttpsStatsEntry 2 }

affirmedServiceconstructInterfaceT8InterfaceStatisticsDebugRestClientHttpsStatsHTTPsClientConnectionsInUse OBJECT-TYPE
    SYNTAX      ConfdString
    MAX-ACCESS  read-only
    STATUS      current
    DESCRIPTION "Client Connections - Currently in Use"
    ::= { affirmedServiceconstructInterfaceT8InterfaceStatisticsDebugRestClientHttpsStatsEntry 3 }

affirmedServiceconstructInterfaceT8InterfaceStatisticsDebugRestClientHttpsStatsHTTPsClientConnectionTerminated OBJECT-TYPE
    SYNTAX      ConfdString
    MAX-ACCESS  read-only
    STATUS      current
    DESCRIPTION "Client Connections - Terminated"
    ::= { affirmedServiceconstructInterfaceT8InterfaceStatisticsDebugRestClientHttpsStatsEntry 4 }

affirmedServiceconstructInterfaceT8InterfaceStatisticsDebugRestClientHttpsStatsHTTPsClientIPV4 OBJECT-TYPE
    SYNTAX      ConfdString
    MAX-ACCESS  read-only
    STATUS      current
    DESCRIPTION "Client Connections - IPv4"
    ::= { affirmedServiceconstructInterfaceT8InterfaceStatisticsDebugRestClientHttpsStatsEntry 5 }

affirmedServiceconstructInterfaceT8InterfaceStatisticsDebugRestClientHttpsStatsHTTPsClientIPV6 OBJECT-TYPE
    SYNTAX      ConfdString
    MAX-ACCESS  read-only
    STATUS      current
    DESCRIPTION "Client Connections - IPv6"
    ::= { affirmedServiceconstructInterfaceT8InterfaceStatisticsDebugRestClientHttpsStatsEntry 6 }

affirmedServiceconstructInterfaceT8InterfaceStatisticsDebugRestClientHttpsStatsHTTPsClientErrorsTotal OBJECT-TYPE
    SYNTAX      ConfdString
    MAX-ACCESS  read-only
    STATUS      current
    DESCRIPTION "Client Errors - Total"
    ::= { affirmedServiceconstructInterfaceT8InterfaceStatisticsDebugRestClientHttpsStatsEntry 7 }

affirmedServiceconstructInterfaceT8InterfaceStatisticsDebugRestClientHttpsStatsHTTPsClientTCPConnectionTimeout OBJECT-TYPE
    SYNTAX      ConfdString
    MAX-ACCESS  read-only
    STATUS      current
    DESCRIPTION "Client Errors - Connection Timeout"
    ::= { affirmedServiceconstructInterfaceT8InterfaceStatisticsDebugRestClientHttpsStatsEntry 8 }

affirmedServiceconstructInterfaceT8InterfaceStatisticsDebugRestClientHttpsStatsHTTPsClientTLSHandShakeFailureError OBJECT-TYPE
    SYNTAX      ConfdString
    MAX-ACCESS  read-only
    STATUS      current
    DESCRIPTION "Client Errors - TLS Handshake Failure"
    ::= { affirmedServiceconstructInterfaceT8InterfaceStatisticsDebugRestClientHttpsStatsEntry 9 }

affirmedServiceconstructInterfaceT8InterfaceStatisticsDebugRestClientHttpsStatsHTTPsClientHTTPsLevelMaxRetryExceeded OBJECT-TYPE
    SYNTAX      ConfdString
    MAX-ACCESS  read-only
    STATUS      current
    DESCRIPTION "Client Errors - HTTP Level Max Retry Exceeded"
    ::= { affirmedServiceconstructInterfaceT8InterfaceStatisticsDebugRestClientHttpsStatsEntry 10 }

affirmedServiceconstructInterfaceT8InterfaceStatisticsDebugRestClientHttpsStatsHTTPsClientTCPLevelMaxRetryExceeded OBJECT-TYPE
    SYNTAX      ConfdString
    MAX-ACCESS  read-only
    STATUS      current
    DESCRIPTION "Client Errors - TCP Level Max Retry Exceeded"
    ::= { affirmedServiceconstructInterfaceT8InterfaceStatisticsDebugRestClientHttpsStatsEntry 11 }

affirmedServiceconstructInterfaceT8InterfaceStatisticsDebugRestClientHttpsStatsHTTPsClientRejectedAgeExceeded OBJECT-TYPE
    SYNTAX      ConfdString
    MAX-ACCESS  read-only
    STATUS      current
    DESCRIPTION "Client Errors - Request Age Exceeded"
    ::= { affirmedServiceconstructInterfaceT8InterfaceStatisticsDebugRestClientHttpsStatsEntry 12 }

affirmedServiceconstructInterfaceT8InterfaceStatisticsDebugRestClientHttpsStatsHTTPsClientTCPDropsByPeer OBJECT-TYPE
    SYNTAX      ConfdString
    MAX-ACCESS  read-only
    STATUS      current
    DESCRIPTION "Client Errors - TCP Drops By Peer"
    ::= { affirmedServiceconstructInterfaceT8InterfaceStatisticsDebugRestClientHttpsStatsEntry 13 }

affirmedServiceconstructInterfaceT8InterfaceStatisticsDebugRestClientHttpsStatsHTTPsClientReadError OBJECT-TYPE
    SYNTAX      ConfdString
    MAX-ACCESS  read-only
    STATUS      current
    DESCRIPTION "Client Errors - Read Error"
    ::= { affirmedServiceconstructInterfaceT8InterfaceStatisticsDebugRestClientHttpsStatsEntry 14 }

affirmedServiceconstructInterfaceT8InterfaceStatisticsDebugRestClientHttpsStatsHTTPsClientWriteError OBJECT-TYPE
    SYNTAX      ConfdString
    MAX-ACCESS  read-only
    STATUS      current
    DESCRIPTION "Client Errors - Write Error"
    ::= { affirmedServiceconstructInterfaceT8InterfaceStatisticsDebugRestClientHttpsStatsEntry 15 }

affirmedServiceconstructInterfaceT8InterfaceStatisticsDebugRestClientHttpsStatsHTTPsClientConnRefusedError OBJECT-TYPE
    SYNTAX      ConfdString
    MAX-ACCESS  read-only
    STATUS      current
    DESCRIPTION "Client Errors - Conn Refused Error"
    ::= { affirmedServiceconstructInterfaceT8InterfaceStatisticsDebugRestClientHttpsStatsEntry 16 }

affirmedServiceconstructInterfaceT8InterfaceStatisticsDebugRestClientHttpsStatsHTTPsClientEOFError OBJECT-TYPE
    SYNTAX      ConfdString
    MAX-ACCESS  read-only
    STATUS      current
    DESCRIPTION "Client Errors - EOF Error"
    ::= { affirmedServiceconstructInterfaceT8InterfaceStatisticsDebugRestClientHttpsStatsEntry 17 }

affirmedServiceconstructInterfaceT8InterfaceStatisticsRest-clientTable OBJECT-TYPE
    SYNTAX      SEQUENCE OF AffirmedServiceconstructInterfaceT8InterfaceStatisticsRest-clientEntry
    MAX-ACCESS  not-accessible
    STATUS      current
    DESCRIPTION ""
    ::= { affirmedServiceconstructInterfaceT8InterfaceStatistics 3 }

affirmedServiceconstructInterfaceT8InterfaceStatisticsRest-clientEntry OBJECT-TYPE
    SYNTAX      AffirmedServiceconstructInterfaceT8InterfaceStatisticsRest-clientEntry
    MAX-ACCESS  not-accessible
    STATUS      current
    DESCRIPTION ""
    INDEX { affirmedServiceconstructInterfaceT8InterfaceStatisticsRest-clientChassis, affirmedServiceconstructInterfaceT8InterfaceStatisticsRest-clientName }
        ::= { affirmedServiceconstructInterfaceT8InterfaceStatisticsRest-clientTable 1 }

AffirmedServiceconstructInterfaceT8InterfaceStatisticsRest-clientEntry ::=
    SEQUENCE {
        affirmedServiceconstructInterfaceT8InterfaceStatisticsRest-clientName String,
        affirmedServiceconstructInterfaceT8InterfaceStatisticsRest-clientChassis Unsigned32,
        affirmedServiceconstructInterfaceT8InterfaceStatisticsRest-clientHttpTxPostReqAttempted ConfdString,
        affirmedServiceconstructInterfaceT8InterfaceStatisticsRest-clientHttpTxPostTimeOut ConfdString,
        affirmedServiceconstructInterfaceT8InterfaceStatisticsRest-clientHttpTxPost2XXResp ConfdString,
        affirmedServiceconstructInterfaceT8InterfaceStatisticsRest-clientHttpTxPost3XXResp ConfdString,
        affirmedServiceconstructInterfaceT8InterfaceStatisticsRest-clientHttpTxPost4XXResp ConfdString,
        affirmedServiceconstructInterfaceT8InterfaceStatisticsRest-clientHttpTxPost5XXResp ConfdString,
        affirmedServiceconstructInterfaceT8InterfaceStatisticsRest-clientHttpTxPostDropped ConfdString,
        affirmedServiceconstructInterfaceT8InterfaceStatisticsRest-clientHttpTxPostNiddConfigUpdateNotificationsAttempted ConfdString,
        affirmedServiceconstructInterfaceT8InterfaceStatisticsRest-clientHttpTxPostNiddConfigUpdateNotificationsTimeOut ConfdString,
        affirmedServiceconstructInterfaceT8InterfaceStatisticsRest-clientHttpTxPostNiddConfigUpdateNotifications2XXResp ConfdString,
        affirmedServiceconstructInterfaceT8InterfaceStatisticsRest-clientHttpTxPostNiddConfigUpdateNotifications3XXResp ConfdString,
        affirmedServiceconstructInterfaceT8InterfaceStatisticsRest-clientHttpTxPostNiddConfigUpdateNotifications4XXResp ConfdString,
        affirmedServiceconstructInterfaceT8InterfaceStatisticsRest-clientHttpTxPostNiddConfigUpdateNotifications5XXResp ConfdString,
        affirmedServiceconstructInterfaceT8InterfaceStatisticsRest-clientHttpTxPostNiddConfigUpdateNotificationsDropped ConfdString,
        affirmedServiceconstructInterfaceT8InterfaceStatisticsRest-clientHttpTxPostNiddDLDataDeliveryStatusNotificationsAttempted ConfdString,
        affirmedServiceconstructInterfaceT8InterfaceStatisticsRest-clientHttpTxPostNiddDLDataDeliveryStatusNotificationsTimeOut ConfdString,
        affirmedServiceconstructInterfaceT8InterfaceStatisticsRest-clientHttpTxPostNiddDLDataDeliveryStatusNotification2XXResp ConfdString,
        affirmedServiceconstructInterfaceT8InterfaceStatisticsRest-clientHttpTxPostNiddDLDataDeliveryStatusNotification3XXResp ConfdString,
        affirmedServiceconstructInterfaceT8InterfaceStatisticsRest-clientHttpTxPostNiddDLDataDeliveryStatusNotification4XXResp ConfdString,
        affirmedServiceconstructInterfaceT8InterfaceStatisticsRest-clientHttpTxPostNiddDLDataDeliveryStatusNotification5XXResp ConfdString,
        affirmedServiceconstructInterfaceT8InterfaceStatisticsRest-clientHttpTxPostNiddDLDataDeliveryStatusNotificationDropped ConfdString,
        affirmedServiceconstructInterfaceT8InterfaceStatisticsRest-clientHttpTxPostNiddUpLinkDataNotificationsAttempted ConfdString,
        affirmedServiceconstructInterfaceT8InterfaceStatisticsRest-clientHttpTxPostNiddUpLinkDataNotificationsTimeOut ConfdString,
        affirmedServiceconstructInterfaceT8InterfaceStatisticsRest-clientHttpTxPostNiddUpLinkDataNotification2XXResp ConfdString,
        affirmedServiceconstructInterfaceT8InterfaceStatisticsRest-clientHttpTxPostNiddUpLinkDataNotification3XXResp ConfdString,
        affirmedServiceconstructInterfaceT8InterfaceStatisticsRest-clientHttpTxPostNiddUpLinkDataNotification4XXResp ConfdString,
        affirmedServiceconstructInterfaceT8InterfaceStatisticsRest-clientHttpTxPostNiddUpLinkDataNotification5XXResp ConfdString,
        affirmedServiceconstructInterfaceT8InterfaceStatisticsRest-clientHttpTxPostNiddUpLinkDataNotificationDropped ConfdString,
        affirmedServiceconstructInterfaceT8InterfaceStatisticsRest-clientHttpTxPostMonteReportNotificationsAttempted ConfdString,
        affirmedServiceconstructInterfaceT8InterfaceStatisticsRest-clientHttpTxPostMonteReportNotificationsTimeOut ConfdString,
        affirmedServiceconstructInterfaceT8InterfaceStatisticsRest-clientHttpTxPostMonteReportNotifications2XXResp ConfdString,
        affirmedServiceconstructInterfaceT8InterfaceStatisticsRest-clientHttpTxPostMonteReportNotifications3XXResp ConfdString,
        affirmedServiceconstructInterfaceT8InterfaceStatisticsRest-clientHttpTxPostMonteReportNotifications4XXResp ConfdString,
        affirmedServiceconstructInterfaceT8InterfaceStatisticsRest-clientHttpTxPostMonteReportNotifications5XXResp ConfdString,
        affirmedServiceconstructInterfaceT8InterfaceStatisticsRest-clientHttpTxPostMonteReportNotificationsDropped ConfdString,
        affirmedServiceconstructInterfaceT8InterfaceStatisticsRest-clientHttpTxPostDeviceTrgReportNotificationsAttempted ConfdString,
        affirmedServiceconstructInterfaceT8InterfaceStatisticsRest-clientHttpTxPostDeviceTrgReportNotificationsTimeOut ConfdString,
        affirmedServiceconstructInterfaceT8InterfaceStatisticsRest-clientHttpTxPostDeviceTrgReportNotifications2XXResp ConfdString,
        affirmedServiceconstructInterfaceT8InterfaceStatisticsRest-clientHttpTxPostDeviceTrgReportNotifications3XXResp ConfdString,
        affirmedServiceconstructInterfaceT8InterfaceStatisticsRest-clientHttpTxPostDeviceTrgReportNotifications4XXResp ConfdString,
        affirmedServiceconstructInterfaceT8InterfaceStatisticsRest-clientHttpTxPostDeviceTrgReportNotifications5XXResp ConfdString,
        affirmedServiceconstructInterfaceT8InterfaceStatisticsRest-clientHttpTxPostDeviceTrgReportNotificationsDropped ConfdString,
        affirmedServiceconstructInterfaceT8InterfaceStatisticsRest-clientHttpTxPost401Unauthorized ConfdString,
        affirmedServiceconstructInterfaceT8InterfaceStatisticsRest-clientHttpTxPostNiddConfigUpdateNotificationsUnauthorized ConfdString,
        affirmedServiceconstructInterfaceT8InterfaceStatisticsRest-clientHttpTxPostNiddDLDataDeliveryStatusNotificationUnauth ConfdString,
        affirmedServiceconstructInterfaceT8InterfaceStatisticsRest-clientHttpTxPostNiddUpLinkDataNotificationsUnauthorized ConfdString,
        affirmedServiceconstructInterfaceT8InterfaceStatisticsRest-clientHttpTxPostMonteReportNotificationsUnauthorized ConfdString
    }

affirmedServiceconstructInterfaceT8InterfaceStatisticsRest-clientName OBJECT-TYPE
    SYNTAX      String
    MAX-ACCESS  not-accessible
    STATUS      current
    DESCRIPTION "Table Name"
    ::= { affirmedServiceconstructInterfaceT8InterfaceStatisticsRest-clientEntry 1 }

affirmedServiceconstructInterfaceT8InterfaceStatisticsRest-clientChassis OBJECT-TYPE
    SYNTAX      Unsigned32
    MAX-ACCESS  not-accessible
    STATUS      current
    DESCRIPTION "chassis ID"
    ::= { affirmedServiceconstructInterfaceT8InterfaceStatisticsRest-clientEntry 2 }

affirmedServiceconstructInterfaceT8InterfaceStatisticsRest-clientHttpTxPostReqAttempted OBJECT-TYPE
    SYNTAX      ConfdString
    MAX-ACCESS  read-only
    STATUS      current
    DESCRIPTION "Total number of HTTP POST requests attempted"
    ::= { affirmedServiceconstructInterfaceT8InterfaceStatisticsRest-clientEntry 3 }

affirmedServiceconstructInterfaceT8InterfaceStatisticsRest-clientHttpTxPostTimeOut OBJECT-TYPE
    SYNTAX      ConfdString
    MAX-ACCESS  read-only
    STATUS      current
    DESCRIPTION "Total number of timeout happened for the HTTP POST requests while waiting for the response from server"
    ::= { affirmedServiceconstructInterfaceT8InterfaceStatisticsRest-clientEntry 4 }

affirmedServiceconstructInterfaceT8InterfaceStatisticsRest-clientHttpTxPost2XXResp OBJECT-TYPE
    SYNTAX      ConfdString
    MAX-ACCESS  read-only
    STATUS      current
    DESCRIPTION "Total number of 2xx responses received for the HTTP POST requests"
    ::= { affirmedServiceconstructInterfaceT8InterfaceStatisticsRest-clientEntry 5 }

affirmedServiceconstructInterfaceT8InterfaceStatisticsRest-clientHttpTxPost3XXResp OBJECT-TYPE
    SYNTAX      ConfdString
    MAX-ACCESS  read-only
    STATUS      current
    DESCRIPTION "Total number of 3xx responses received for the HTTP POST requests"
    ::= { affirmedServiceconstructInterfaceT8InterfaceStatisticsRest-clientEntry 6 }

affirmedServiceconstructInterfaceT8InterfaceStatisticsRest-clientHttpTxPost4XXResp OBJECT-TYPE
    SYNTAX      ConfdString
    MAX-ACCESS  read-only
    STATUS      current
    DESCRIPTION "Total number of 4xx error responses received for the HTTP POST requests"
    ::= { affirmedServiceconstructInterfaceT8InterfaceStatisticsRest-clientEntry 7 }

affirmedServiceconstructInterfaceT8InterfaceStatisticsRest-clientHttpTxPost5XXResp OBJECT-TYPE
    SYNTAX      ConfdString
    MAX-ACCESS  read-only
    STATUS      current
    DESCRIPTION "Total number of 5xx error responses received for the HTTP POST requests"
    ::= { affirmedServiceconstructInterfaceT8InterfaceStatisticsRest-clientEntry 8 }

affirmedServiceconstructInterfaceT8InterfaceStatisticsRest-clientHttpTxPostDropped OBJECT-TYPE
    SYNTAX      ConfdString
    MAX-ACCESS  read-only
    STATUS      current
    DESCRIPTION "Total number of HTTP POST request dropped because of no response from the server"
    ::= { affirmedServiceconstructInterfaceT8InterfaceStatisticsRest-clientEntry 9 }

affirmedServiceconstructInterfaceT8InterfaceStatisticsRest-clientHttpTxPostNiddConfigUpdateNotificationsAttempted OBJECT-TYPE
    SYNTAX      ConfdString
    MAX-ACCESS  read-only
    STATUS      current
    DESCRIPTION "Total number of NIDD configuration update notifications attempted"
    ::= { affirmedServiceconstructInterfaceT8InterfaceStatisticsRest-clientEntry 10 }

affirmedServiceconstructInterfaceT8InterfaceStatisticsRest-clientHttpTxPostNiddConfigUpdateNotificationsTimeOut OBJECT-TYPE
    SYNTAX      ConfdString
    MAX-ACCESS  read-only
    STATUS      current
    DESCRIPTION "Total number of timeout happened for NIDD configuration update notifications"
    ::= { affirmedServiceconstructInterfaceT8InterfaceStatisticsRest-clientEntry 11 }

affirmedServiceconstructInterfaceT8InterfaceStatisticsRest-clientHttpTxPostNiddConfigUpdateNotifications2XXResp OBJECT-TYPE
    SYNTAX      ConfdString
    MAX-ACCESS  read-only
    STATUS      current
    DESCRIPTION "Total number of 2xx responses received for NIDD configuration update notifications"
    ::= { affirmedServiceconstructInterfaceT8InterfaceStatisticsRest-clientEntry 12 }

affirmedServiceconstructInterfaceT8InterfaceStatisticsRest-clientHttpTxPostNiddConfigUpdateNotifications3XXResp OBJECT-TYPE
    SYNTAX      ConfdString
    MAX-ACCESS  read-only
    STATUS      current
    DESCRIPTION "Total number of 3xx responses received for NIDD configuration update notifications"
    ::= { affirmedServiceconstructInterfaceT8InterfaceStatisticsRest-clientEntry 13 }

affirmedServiceconstructInterfaceT8InterfaceStatisticsRest-clientHttpTxPostNiddConfigUpdateNotifications4XXResp OBJECT-TYPE
    SYNTAX      ConfdString
    MAX-ACCESS  read-only
    STATUS      current
    DESCRIPTION "Total number of 4xx error responses received for NIDD configuration update notifications"
    ::= { affirmedServiceconstructInterfaceT8InterfaceStatisticsRest-clientEntry 14 }

affirmedServiceconstructInterfaceT8InterfaceStatisticsRest-clientHttpTxPostNiddConfigUpdateNotifications5XXResp OBJECT-TYPE
    SYNTAX      ConfdString
    MAX-ACCESS  read-only
    STATUS      current
    DESCRIPTION "Total number of 5xx error responses received for NIDD configuration update notifications"
    ::= { affirmedServiceconstructInterfaceT8InterfaceStatisticsRest-clientEntry 15 }

affirmedServiceconstructInterfaceT8InterfaceStatisticsRest-clientHttpTxPostNiddConfigUpdateNotificationsDropped OBJECT-TYPE
    SYNTAX      ConfdString
    MAX-ACCESS  read-only
    STATUS      current
    DESCRIPTION "Total number of NIDD configuration update notifications dropped because of no response from the server"
    ::= { affirmedServiceconstructInterfaceT8InterfaceStatisticsRest-clientEntry 16 }

affirmedServiceconstructInterfaceT8InterfaceStatisticsRest-clientHttpTxPostNiddDLDataDeliveryStatusNotificationsAttempted OBJECT-TYPE
    SYNTAX      ConfdString
    MAX-ACCESS  read-only
    STATUS      current
    DESCRIPTION "Total number of NIDD downlink data delivery status notifications attempted"
    ::= { affirmedServiceconstructInterfaceT8InterfaceStatisticsRest-clientEntry 17 }

affirmedServiceconstructInterfaceT8InterfaceStatisticsRest-clientHttpTxPostNiddDLDataDeliveryStatusNotificationsTimeOut OBJECT-TYPE
    SYNTAX      ConfdString
    MAX-ACCESS  read-only
    STATUS      current
    DESCRIPTION "Total number of timeout happened for NIDD downlink data delivery status notifications"
    ::= { affirmedServiceconstructInterfaceT8InterfaceStatisticsRest-clientEntry 18 }

affirmedServiceconstructInterfaceT8InterfaceStatisticsRest-clientHttpTxPostNiddDLDataDeliveryStatusNotification2XXResp OBJECT-TYPE
    SYNTAX      ConfdString
    MAX-ACCESS  read-only
    STATUS      current
    DESCRIPTION "Total number of 2xx responses received for NIDD downlink data delivery status notifications"
    ::= { affirmedServiceconstructInterfaceT8InterfaceStatisticsRest-clientEntry 19 }

affirmedServiceconstructInterfaceT8InterfaceStatisticsRest-clientHttpTxPostNiddDLDataDeliveryStatusNotification3XXResp OBJECT-TYPE
    SYNTAX      ConfdString
    MAX-ACCESS  read-only
    STATUS      current
    DESCRIPTION "Total number of 3xx responses received for NIDD downlink data delivery status notifications"
    ::= { affirmedServiceconstructInterfaceT8InterfaceStatisticsRest-clientEntry 20 }

affirmedServiceconstructInterfaceT8InterfaceStatisticsRest-clientHttpTxPostNiddDLDataDeliveryStatusNotification4XXResp OBJECT-TYPE
    SYNTAX      ConfdString
    MAX-ACCESS  read-only
    STATUS      current
    DESCRIPTION "Total number of 4xx error responses received for NIDD downlink data delivery status notifications"
    ::= { affirmedServiceconstructInterfaceT8InterfaceStatisticsRest-clientEntry 21 }

affirmedServiceconstructInterfaceT8InterfaceStatisticsRest-clientHttpTxPostNiddDLDataDeliveryStatusNotification5XXResp OBJECT-TYPE
    SYNTAX      ConfdString
    MAX-ACCESS  read-only
    STATUS      current
    DESCRIPTION "Total number of 5xx error responses received for NIDD downlink data delivery status notifications"
    ::= { affirmedServiceconstructInterfaceT8InterfaceStatisticsRest-clientEntry 22 }

affirmedServiceconstructInterfaceT8InterfaceStatisticsRest-clientHttpTxPostNiddDLDataDeliveryStatusNotificationDropped OBJECT-TYPE
    SYNTAX      ConfdString
    MAX-ACCESS  read-only
    STATUS      current
    DESCRIPTION "Total number of NIDD downlink data delivery status notifications dropped because of no response from the server"
    ::= { affirmedServiceconstructInterfaceT8InterfaceStatisticsRest-clientEntry 23 }

affirmedServiceconstructInterfaceT8InterfaceStatisticsRest-clientHttpTxPostNiddUpLinkDataNotificationsAttempted OBJECT-TYPE
    SYNTAX      ConfdString
    MAX-ACCESS  read-only
    STATUS      current
    DESCRIPTION "Total number of NIDD uplink data notifications attempted"
    ::= { affirmedServiceconstructInterfaceT8InterfaceStatisticsRest-clientEntry 24 }

affirmedServiceconstructInterfaceT8InterfaceStatisticsRest-clientHttpTxPostNiddUpLinkDataNotificationsTimeOut OBJECT-TYPE
    SYNTAX      ConfdString
    MAX-ACCESS  read-only
    STATUS      current
    DESCRIPTION "Total number of timeout happened for NIDD uplink data notifications"
    ::= { affirmedServiceconstructInterfaceT8InterfaceStatisticsRest-clientEntry 25 }

affirmedServiceconstructInterfaceT8InterfaceStatisticsRest-clientHttpTxPostNiddUpLinkDataNotification2XXResp OBJECT-TYPE
    SYNTAX      ConfdString
    MAX-ACCESS  read-only
    STATUS      current
    DESCRIPTION "Total number of 2xx responses received for NIDD uplink data notifications"
    ::= { affirmedServiceconstructInterfaceT8InterfaceStatisticsRest-clientEntry 26 }

affirmedServiceconstructInterfaceT8InterfaceStatisticsRest-clientHttpTxPostNiddUpLinkDataNotification3XXResp OBJECT-TYPE
    SYNTAX      ConfdString
    MAX-ACCESS  read-only
    STATUS      current
    DESCRIPTION "Total number of 3xx responses received for NIDD uplink data notifications"
    ::= { affirmedServiceconstructInterfaceT8InterfaceStatisticsRest-clientEntry 27 }

affirmedServiceconstructInterfaceT8InterfaceStatisticsRest-clientHttpTxPostNiddUpLinkDataNotification4XXResp OBJECT-TYPE
    SYNTAX      ConfdString
    MAX-ACCESS  read-only
    STATUS      current
    DESCRIPTION "Total number of 4xx error responses received for NIDD uplink data notifications"
    ::= { affirmedServiceconstructInterfaceT8InterfaceStatisticsRest-clientEntry 28 }

affirmedServiceconstructInterfaceT8InterfaceStatisticsRest-clientHttpTxPostNiddUpLinkDataNotification5XXResp OBJECT-TYPE
    SYNTAX      ConfdString
    MAX-ACCESS  read-only
    STATUS      current
    DESCRIPTION "Total number of 5xx error responses received for NIDD uplink data notifications"
    ::= { affirmedServiceconstructInterfaceT8InterfaceStatisticsRest-clientEntry 29 }

affirmedServiceconstructInterfaceT8InterfaceStatisticsRest-clientHttpTxPostNiddUpLinkDataNotificationDropped OBJECT-TYPE
    SYNTAX      ConfdString
    MAX-ACCESS  read-only
    STATUS      current
    DESCRIPTION "Total number of NIDD uplink data notifications dropped because of no response from the server"
    ::= { affirmedServiceconstructInterfaceT8InterfaceStatisticsRest-clientEntry 30 }

affirmedServiceconstructInterfaceT8InterfaceStatisticsRest-clientHttpTxPostMonteReportNotificationsAttempted OBJECT-TYPE
    SYNTAX      ConfdString
    MAX-ACCESS  read-only
    STATUS      current
    DESCRIPTION "Total number of Monitoring event report notifications attempted"
    ::= { affirmedServiceconstructInterfaceT8InterfaceStatisticsRest-clientEntry 31 }

affirmedServiceconstructInterfaceT8InterfaceStatisticsRest-clientHttpTxPostMonteReportNotificationsTimeOut OBJECT-TYPE
    SYNTAX      ConfdString
    MAX-ACCESS  read-only
    STATUS      current
    DESCRIPTION "Total number of timeout happened for Monitoring event report notifications"
    ::= { affirmedServiceconstructInterfaceT8InterfaceStatisticsRest-clientEntry 32 }

affirmedServiceconstructInterfaceT8InterfaceStatisticsRest-clientHttpTxPostMonteReportNotifications2XXResp OBJECT-TYPE
    SYNTAX      ConfdString
    MAX-ACCESS  read-only
    STATUS      current
    DESCRIPTION "Total number of 2xx responses received for Monitoring event report notifications"
    ::= { affirmedServiceconstructInterfaceT8InterfaceStatisticsRest-clientEntry 33 }

affirmedServiceconstructInterfaceT8InterfaceStatisticsRest-clientHttpTxPostMonteReportNotifications3XXResp OBJECT-TYPE
    SYNTAX      ConfdString
    MAX-ACCESS  read-only
    STATUS      current
    DESCRIPTION "Total number of 3xx responses received for Monitoring event report notifications"
    ::= { affirmedServiceconstructInterfaceT8InterfaceStatisticsRest-clientEntry 34 }

affirmedServiceconstructInterfaceT8InterfaceStatisticsRest-clientHttpTxPostMonteReportNotifications4XXResp OBJECT-TYPE
    SYNTAX      ConfdString
    MAX-ACCESS  read-only
    STATUS      current
    DESCRIPTION "Total number of 4xx error responses received for Monitoring event report notifications"
    ::= { affirmedServiceconstructInterfaceT8InterfaceStatisticsRest-clientEntry 35 }

affirmedServiceconstructInterfaceT8InterfaceStatisticsRest-clientHttpTxPostMonteReportNotifications5XXResp OBJECT-TYPE
    SYNTAX      ConfdString
    MAX-ACCESS  read-only
    STATUS      current
    DESCRIPTION "Total number of 5xx error responses received for Monitoring event report notifications"
    ::= { affirmedServiceconstructInterfaceT8InterfaceStatisticsRest-clientEntry 36 }

affirmedServiceconstructInterfaceT8InterfaceStatisticsRest-clientHttpTxPostMonteReportNotificationsDropped OBJECT-TYPE
    SYNTAX      ConfdString
    MAX-ACCESS  read-only
    STATUS      current
    DESCRIPTION "Total number of Monitoring event report notifications dropped because of no response from the server"
    ::= { affirmedServiceconstructInterfaceT8InterfaceStatisticsRest-clientEntry 37 }

affirmedServiceconstructInterfaceT8InterfaceStatisticsRest-clientHttpTxPostDeviceTrgReportNotificationsAttempted OBJECT-TYPE
    SYNTAX      ConfdString
    MAX-ACCESS  read-only
    STATUS      current
    DESCRIPTION "Total number of Device Trigger delivery report notifications attempted"
    ::= { affirmedServiceconstructInterfaceT8InterfaceStatisticsRest-clientEntry 38 }

affirmedServiceconstructInterfaceT8InterfaceStatisticsRest-clientHttpTxPostDeviceTrgReportNotificationsTimeOut OBJECT-TYPE
    SYNTAX      ConfdString
    MAX-ACCESS  read-only
    STATUS      current
    DESCRIPTION "Total number of timeout happened for Device Trigger delivery report notifications"
    ::= { affirmedServiceconstructInterfaceT8InterfaceStatisticsRest-clientEntry 39 }

affirmedServiceconstructInterfaceT8InterfaceStatisticsRest-clientHttpTxPostDeviceTrgReportNotifications2XXResp OBJECT-TYPE
    SYNTAX      ConfdString
    MAX-ACCESS  read-only
    STATUS      current
    DESCRIPTION "Total number of 2xx responses received for Device Trigger delivery report notifications"
    ::= { affirmedServiceconstructInterfaceT8InterfaceStatisticsRest-clientEntry 40 }

affirmedServiceconstructInterfaceT8InterfaceStatisticsRest-clientHttpTxPostDeviceTrgReportNotifications3XXResp OBJECT-TYPE
    SYNTAX      ConfdString
    MAX-ACCESS  read-only
    STATUS      current
    DESCRIPTION "Total number of 3xx responses received for Device Trigger delivery report notifications"
    ::= { affirmedServiceconstructInterfaceT8InterfaceStatisticsRest-clientEntry 41 }

affirmedServiceconstructInterfaceT8InterfaceStatisticsRest-clientHttpTxPostDeviceTrgReportNotifications4XXResp OBJECT-TYPE
    SYNTAX      ConfdString
    MAX-ACCESS  read-only
    STATUS      current
    DESCRIPTION "Total number of 4xx error responses received for Device Trigger delivery report notifications"
    ::= { affirmedServiceconstructInterfaceT8InterfaceStatisticsRest-clientEntry 42 }

affirmedServiceconstructInterfaceT8InterfaceStatisticsRest-clientHttpTxPostDeviceTrgReportNotifications5XXResp OBJECT-TYPE
    SYNTAX      ConfdString
    MAX-ACCESS  read-only
    STATUS      current
    DESCRIPTION "Total number of 5xx error responses received for Device Trigger delivery report notifications"
    ::= { affirmedServiceconstructInterfaceT8InterfaceStatisticsRest-clientEntry 43 }

affirmedServiceconstructInterfaceT8InterfaceStatisticsRest-clientHttpTxPostDeviceTrgReportNotificationsDropped OBJECT-TYPE
    SYNTAX      ConfdString
    MAX-ACCESS  read-only
    STATUS      current
    DESCRIPTION "Total number of Device Trigger delivery report notifications dropped because of no response from the server"
    ::= { affirmedServiceconstructInterfaceT8InterfaceStatisticsRest-clientEntry 44 }

affirmedServiceconstructInterfaceT8InterfaceStatisticsRest-clientHttpTxPost401Unauthorized OBJECT-TYPE
    SYNTAX      ConfdString
    MAX-ACCESS  read-only
    STATUS      current
    DESCRIPTION "Total number of 401 unauthorized responses received for HTTP POST requests from the server"
    ::= { affirmedServiceconstructInterfaceT8InterfaceStatisticsRest-clientEntry 45 }

affirmedServiceconstructInterfaceT8InterfaceStatisticsRest-clientHttpTxPostNiddConfigUpdateNotificationsUnauthorized OBJECT-TYPE
    SYNTAX      ConfdString
    MAX-ACCESS  read-only
    STATUS      current
    DESCRIPTION "Total number of 401 unauthorized responses recevied for NIDD configuration update notifications from the server"
    ::= { affirmedServiceconstructInterfaceT8InterfaceStatisticsRest-clientEntry 46 }

affirmedServiceconstructInterfaceT8InterfaceStatisticsRest-clientHttpTxPostNiddDLDataDeliveryStatusNotificationUnauth OBJECT-TYPE
    SYNTAX      ConfdString
    MAX-ACCESS  read-only
    STATUS      current
    DESCRIPTION "Total number of 401 unauthorized responses received for NIDD downlink data delivery status notifications from the server"
    ::= { affirmedServiceconstructInterfaceT8InterfaceStatisticsRest-clientEntry 47 }

affirmedServiceconstructInterfaceT8InterfaceStatisticsRest-clientHttpTxPostNiddUpLinkDataNotificationsUnauthorized OBJECT-TYPE
    SYNTAX      ConfdString
    MAX-ACCESS  read-only
    STATUS      current
    DESCRIPTION "Total number of 401 unauthorized responses received for NIDD uplink data notifications from the server"
    ::= { affirmedServiceconstructInterfaceT8InterfaceStatisticsRest-clientEntry 48 }

affirmedServiceconstructInterfaceT8InterfaceStatisticsRest-clientHttpTxPostMonteReportNotificationsUnauthorized OBJECT-TYPE
    SYNTAX      ConfdString
    MAX-ACCESS  read-only
    STATUS      current
    DESCRIPTION "Total number of 401 unauthorized responses received for Monitoring event report notifications from the server"
    ::= { affirmedServiceconstructInterfaceT8InterfaceStatisticsRest-clientEntry 49 }

affirmedServiceconstructInterfaceT8InterfaceStatisticsRest-serverTable OBJECT-TYPE
    SYNTAX      SEQUENCE OF AffirmedServiceconstructInterfaceT8InterfaceStatisticsRest-serverEntry
    MAX-ACCESS  not-accessible
    STATUS      current
    DESCRIPTION ""
    ::= { affirmedServiceconstructInterfaceT8InterfaceStatistics 2 }

affirmedServiceconstructInterfaceT8InterfaceStatisticsRest-serverEntry OBJECT-TYPE
    SYNTAX      AffirmedServiceconstructInterfaceT8InterfaceStatisticsRest-serverEntry
    MAX-ACCESS  not-accessible
    STATUS      current
    DESCRIPTION ""
    INDEX { affirmedServiceconstructInterfaceT8InterfaceStatisticsRest-serverChassis, affirmedServiceconstructInterfaceT8InterfaceStatisticsRest-serverName }
        ::= { affirmedServiceconstructInterfaceT8InterfaceStatisticsRest-serverTable 1 }

AffirmedServiceconstructInterfaceT8InterfaceStatisticsRest-serverEntry ::=
    SEQUENCE {
        affirmedServiceconstructInterfaceT8InterfaceStatisticsRest-serverName String,
        affirmedServiceconstructInterfaceT8InterfaceStatisticsRest-serverChassis Unsigned32,
        affirmedServiceconstructInterfaceT8InterfaceStatisticsRest-serverHttpRxPostReq ConfdString,
        affirmedServiceconstructInterfaceT8InterfaceStatisticsRest-serverHttpRxPost2XXResp ConfdString,
        affirmedServiceconstructInterfaceT8InterfaceStatisticsRest-serverHttpRxPost3XXResp ConfdString,
        affirmedServiceconstructInterfaceT8InterfaceStatisticsRest-serverHttpRxPost4XXResp ConfdString,
        affirmedServiceconstructInterfaceT8InterfaceStatisticsRest-serverHttpRxPost5XXResp ConfdString,
        affirmedServiceconstructInterfaceT8InterfaceStatisticsRest-serverHttpRxGetReq ConfdString,
        affirmedServiceconstructInterfaceT8InterfaceStatisticsRest-serverHttpRxGet2XXResp ConfdString,
        affirmedServiceconstructInterfaceT8InterfaceStatisticsRest-serverHttpRxGet3XXResp ConfdString,
        affirmedServiceconstructInterfaceT8InterfaceStatisticsRest-serverHttpRxGet4XXResp ConfdString,
        affirmedServiceconstructInterfaceT8InterfaceStatisticsRest-serverHttpRxGet5XXResp ConfdString,
        affirmedServiceconstructInterfaceT8InterfaceStatisticsRest-serverHttpRxPutReq ConfdString,
        affirmedServiceconstructInterfaceT8InterfaceStatisticsRest-serverHttpRxPut2XXResp ConfdString,
        affirmedServiceconstructInterfaceT8InterfaceStatisticsRest-serverHttpRxPut3XXResp ConfdString,
        affirmedServiceconstructInterfaceT8InterfaceStatisticsRest-serverHttpRxPut4XXResp ConfdString,
        affirmedServiceconstructInterfaceT8InterfaceStatisticsRest-serverHttpRxPut5XXResp ConfdString,
        affirmedServiceconstructInterfaceT8InterfaceStatisticsRest-serverHttpRxPatchReq ConfdString,
        affirmedServiceconstructInterfaceT8InterfaceStatisticsRest-serverHttpRxPatch2XXResp ConfdString,
        affirmedServiceconstructInterfaceT8InterfaceStatisticsRest-serverHttpRxPatch3XXResp ConfdString,
        affirmedServiceconstructInterfaceT8InterfaceStatisticsRest-serverHttpRxPatch4XXResp ConfdString,
        affirmedServiceconstructInterfaceT8InterfaceStatisticsRest-serverHttpRxPatch5XXResp ConfdString,
        affirmedServiceconstructInterfaceT8InterfaceStatisticsRest-serverHttpRxDeleteReq ConfdString,
        affirmedServiceconstructInterfaceT8InterfaceStatisticsRest-serverHttpRxDelete2XXResp ConfdString,
        affirmedServiceconstructInterfaceT8InterfaceStatisticsRest-serverHttpRxDelete3XXResp ConfdString,
        affirmedServiceconstructInterfaceT8InterfaceStatisticsRest-serverHttpRxDelete4XXResp ConfdString,
        affirmedServiceconstructInterfaceT8InterfaceStatisticsRest-serverHttpRxDelete5XXResp ConfdString,
        affirmedServiceconstructInterfaceT8InterfaceStatisticsRest-serverHttpRxPostNiddConfigReq ConfdString,
        affirmedServiceconstructInterfaceT8InterfaceStatisticsRest-serverHttpRxPostNiddConfigSuccessResp ConfdString,
        affirmedServiceconstructInterfaceT8InterfaceStatisticsRest-serverHttpRxPostNiddConfigFailure400 ConfdString,
        affirmedServiceconstructInterfaceT8InterfaceStatisticsRest-serverHttpRxPostNiddConfigFailure401 ConfdString,
        affirmedServiceconstructInterfaceT8InterfaceStatisticsRest-serverHttpRxPostNiddConfigFailure403 ConfdString,
        affirmedServiceconstructInterfaceT8InterfaceStatisticsRest-serverHttpRxPostNiddConfigFailure404 ConfdString,
        affirmedServiceconstructInterfaceT8InterfaceStatisticsRest-serverHttpRxPostNiddConfigFailure409 ConfdString,
        affirmedServiceconstructInterfaceT8InterfaceStatisticsRest-serverHttpRxPostNiddConfigFailure412 ConfdString,
        affirmedServiceconstructInterfaceT8InterfaceStatisticsRest-serverHttpRxPostNiddConfigFailure500 ConfdString,
        affirmedServiceconstructInterfaceT8InterfaceStatisticsRest-serverHttpRxPostNiddConfigFailure503 ConfdString,
        affirmedServiceconstructInterfaceT8InterfaceStatisticsRest-serverHttpRxPatchNiddConfigReq ConfdString,
        affirmedServiceconstructInterfaceT8InterfaceStatisticsRest-serverHttpRxPatchNiddConfigSuccessResp ConfdString,
        affirmedServiceconstructInterfaceT8InterfaceStatisticsRest-serverHttpRxPatchNiddConfigFailure400 ConfdString,
        affirmedServiceconstructInterfaceT8InterfaceStatisticsRest-serverHttpRxPatchNiddConfigFailure401 ConfdString,
        affirmedServiceconstructInterfaceT8InterfaceStatisticsRest-serverHttpRxPatchNiddConfigFailure403 ConfdString,
        affirmedServiceconstructInterfaceT8InterfaceStatisticsRest-serverHttpRxPatchNiddConfigFailure404 ConfdString,
        affirmedServiceconstructInterfaceT8InterfaceStatisticsRest-serverHttpRxPatchNiddConfigFailure409 ConfdString,
        affirmedServiceconstructInterfaceT8InterfaceStatisticsRest-serverHttpRxPatchNiddConfigFailure412 ConfdString,
        affirmedServiceconstructInterfaceT8InterfaceStatisticsRest-serverHttpRxPatchNiddConfigFailure500 ConfdString,
        affirmedServiceconstructInterfaceT8InterfaceStatisticsRest-serverHttpRxPatchNiddConfigFailure503 ConfdString,
        affirmedServiceconstructInterfaceT8InterfaceStatisticsRest-serverHttpRxGetNiddConfigReq ConfdString,
        affirmedServiceconstructInterfaceT8InterfaceStatisticsRest-serverHttpRxGetNiddConfigSuccessResp ConfdString,
        affirmedServiceconstructInterfaceT8InterfaceStatisticsRest-serverHttpRxGetNiddConfigFailure400 ConfdString,
        affirmedServiceconstructInterfaceT8InterfaceStatisticsRest-serverHttpRxGetNiddConfigFailure401 ConfdString,
        affirmedServiceconstructInterfaceT8InterfaceStatisticsRest-serverHttpRxGetNiddConfigFailure403 ConfdString,
        affirmedServiceconstructInterfaceT8InterfaceStatisticsRest-serverHttpRxGetNiddConfigFailure404 ConfdString,
        affirmedServiceconstructInterfaceT8InterfaceStatisticsRest-serverHttpRxGetNiddConfigFailure409 ConfdString,
        affirmedServiceconstructInterfaceT8InterfaceStatisticsRest-serverHttpRxGetNiddConfigFailure412 ConfdString,
        affirmedServiceconstructInterfaceT8InterfaceStatisticsRest-serverHttpRxGetNiddConfigFailure500 ConfdString,
        affirmedServiceconstructInterfaceT8InterfaceStatisticsRest-serverHttpRxGetNiddConfigFailure503 ConfdString,
        affirmedServiceconstructInterfaceT8InterfaceStatisticsRest-serverHttpRxDeleteNiddConfigReq ConfdString,
        affirmedServiceconstructInterfaceT8InterfaceStatisticsRest-serverHttpRxDeleteNiddConfigSuccessResp ConfdString,
        affirmedServiceconstructInterfaceT8InterfaceStatisticsRest-serverHttpRxDeleteNiddConfigFailure400 ConfdString,
        affirmedServiceconstructInterfaceT8InterfaceStatisticsRest-serverHttpRxDeleteNiddConfigFailure401 ConfdString,
        affirmedServiceconstructInterfaceT8InterfaceStatisticsRest-serverHttpRxDeleteNiddConfigFailure403 ConfdString,
        affirmedServiceconstructInterfaceT8InterfaceStatisticsRest-serverHttpRxDeleteNiddConfigFailure404 ConfdString,
        affirmedServiceconstructInterfaceT8InterfaceStatisticsRest-serverHttpRxDeleteNiddConfigFailure409 ConfdString,
        affirmedServiceconstructInterfaceT8InterfaceStatisticsRest-serverHttpRxDeleteNiddConfigFailure412 ConfdString,
        affirmedServiceconstructInterfaceT8InterfaceStatisticsRest-serverHttpRxDeleteNiddConfigFailure500 ConfdString,
        affirmedServiceconstructInterfaceT8InterfaceStatisticsRest-serverHttpRxDeleteNiddConfigFailure503 ConfdString,
        affirmedServiceconstructInterfaceT8InterfaceStatisticsRest-serverHttpRxPostNiddDownLinkDataReq ConfdString,
        affirmedServiceconstructInterfaceT8InterfaceStatisticsRest-serverHttpRxPostNiddDownLinkDataSuccessResp ConfdString,
        affirmedServiceconstructInterfaceT8InterfaceStatisticsRest-serverHttpRxPostNiddDownLinkDataFailure400 ConfdString,
        affirmedServiceconstructInterfaceT8InterfaceStatisticsRest-serverHttpRxPostNiddDownLinkDataFailure401 ConfdString,
        affirmedServiceconstructInterfaceT8InterfaceStatisticsRest-serverHttpRxPostNiddDownLinkDataFailure403 ConfdString,
        affirmedServiceconstructInterfaceT8InterfaceStatisticsRest-serverHttpRxPostNiddDownLinkDataFailure404 ConfdString,
        affirmedServiceconstructInterfaceT8InterfaceStatisticsRest-serverHttpRxPostNiddDownLinkDataFailure409 ConfdString,
        affirmedServiceconstructInterfaceT8InterfaceStatisticsRest-serverHttpRxPostNiddDownLinkDataFailure412 ConfdString,
        affirmedServiceconstructInterfaceT8InterfaceStatisticsRest-serverHttpRxPostNiddDownLinkDataFailure500 ConfdString,
        affirmedServiceconstructInterfaceT8InterfaceStatisticsRest-serverHttpRxPostNiddDownLinkDataFailure503 ConfdString,
        affirmedServiceconstructInterfaceT8InterfaceStatisticsRest-serverHttpRxPutNiddDownLinkDataReq ConfdString,
        affirmedServiceconstructInterfaceT8InterfaceStatisticsRest-serverHttpRxPutNiddDownLinkDataSuccessResp ConfdString,
        affirmedServiceconstructInterfaceT8InterfaceStatisticsRest-serverHttpRxPutNiddDownLinkDataFailureResp ConfdString,
        affirmedServiceconstructInterfaceT8InterfaceStatisticsRest-serverHttpRxGetNiddDownLinkDataReq ConfdString,
        affirmedServiceconstructInterfaceT8InterfaceStatisticsRest-serverHttpRxGetNiddDownLinkDataSuccessResp ConfdString,
        affirmedServiceconstructInterfaceT8InterfaceStatisticsRest-serverHttpRxGetNiddDownLinkDataFailure400 ConfdString,
        affirmedServiceconstructInterfaceT8InterfaceStatisticsRest-serverHttpRxGetNiddDownLinkDataFailure401 ConfdString,
        affirmedServiceconstructInterfaceT8InterfaceStatisticsRest-serverHttpRxGetNiddDownLinkDataFailure403 ConfdString,
        affirmedServiceconstructInterfaceT8InterfaceStatisticsRest-serverHttpRxGetNiddDownLinkDataFailure404 ConfdString,
        affirmedServiceconstructInterfaceT8InterfaceStatisticsRest-serverHttpRxGetNiddDownLinkDataFailure409 ConfdString,
        affirmedServiceconstructInterfaceT8InterfaceStatisticsRest-serverHttpRxGetNiddDownLinkDataFailure412 ConfdString,
        affirmedServiceconstructInterfaceT8InterfaceStatisticsRest-serverHttpRxGetNiddDownLinkDataFailure500 ConfdString,
        affirmedServiceconstructInterfaceT8InterfaceStatisticsRest-serverHttpRxGetNiddDownLinkDataFailure503 ConfdString,
        affirmedServiceconstructInterfaceT8InterfaceStatisticsRest-serverHttpRxPostMonteEventReq ConfdString,
        affirmedServiceconstructInterfaceT8InterfaceStatisticsRest-serverHttpRxPostMonteEventSuccessResp ConfdString,
        affirmedServiceconstructInterfaceT8InterfaceStatisticsRest-serverHttpRxPostMonteEventFailure400 ConfdString,
        affirmedServiceconstructInterfaceT8InterfaceStatisticsRest-serverHttpRxPostMonteEventFailure401 ConfdString,
        affirmedServiceconstructInterfaceT8InterfaceStatisticsRest-serverHttpRxPostMonteEventFailure403 ConfdString,
        affirmedServiceconstructInterfaceT8InterfaceStatisticsRest-serverHttpRxPostMonteEventFailure404 ConfdString,
        affirmedServiceconstructInterfaceT8InterfaceStatisticsRest-serverHttpRxPostMonteEventFailure409 ConfdString,
        affirmedServiceconstructInterfaceT8InterfaceStatisticsRest-serverHttpRxPostMonteEventFailure412 ConfdString,
        affirmedServiceconstructInterfaceT8InterfaceStatisticsRest-serverHttpRxPostMonteEventFailure500 ConfdString,
        affirmedServiceconstructInterfaceT8InterfaceStatisticsRest-serverHttpRxPostMonteEventFailure503 ConfdString,
        affirmedServiceconstructInterfaceT8InterfaceStatisticsRest-serverHttpRxPutMonteEventReq ConfdString,
        affirmedServiceconstructInterfaceT8InterfaceStatisticsRest-serverHttpRxPutMonteEventSuccessResp ConfdString,
        affirmedServiceconstructInterfaceT8InterfaceStatisticsRest-serverHttpRxPutMonteEventFailure400 ConfdString,
        affirmedServiceconstructInterfaceT8InterfaceStatisticsRest-serverHttpRxPutMonteEventFailure401 ConfdString,
        affirmedServiceconstructInterfaceT8InterfaceStatisticsRest-serverHttpRxPutMonteEventFailure403 ConfdString,
        affirmedServiceconstructInterfaceT8InterfaceStatisticsRest-serverHttpRxPutMonteEventFailure404 ConfdString,
        affirmedServiceconstructInterfaceT8InterfaceStatisticsRest-serverHttpRxPutMonteEventFailure409 ConfdString,
        affirmedServiceconstructInterfaceT8InterfaceStatisticsRest-serverHttpRxPutMonteEventFailure412 ConfdString,
        affirmedServiceconstructInterfaceT8InterfaceStatisticsRest-serverHttpRxPutMonteEventFailure500 ConfdString,
        affirmedServiceconstructInterfaceT8InterfaceStatisticsRest-serverHttpRxPutMonteEventFailure503 ConfdString,
        affirmedServiceconstructInterfaceT8InterfaceStatisticsRest-serverHttpRxGetMonteEventReq ConfdString,
        affirmedServiceconstructInterfaceT8InterfaceStatisticsRest-serverHttpRxGetMonteEventSuccessResp ConfdString,
        affirmedServiceconstructInterfaceT8InterfaceStatisticsRest-serverHttpRxGetMonteEventFailure400 ConfdString,
        affirmedServiceconstructInterfaceT8InterfaceStatisticsRest-serverHttpRxGetMonteEventFailure401 ConfdString,
        affirmedServiceconstructInterfaceT8InterfaceStatisticsRest-serverHttpRxGetMonteEventFailure403 ConfdString,
        affirmedServiceconstructInterfaceT8InterfaceStatisticsRest-serverHttpRxGetMonteEventFailure404 ConfdString,
        affirmedServiceconstructInterfaceT8InterfaceStatisticsRest-serverHttpRxGetMonteEventFailure409 ConfdString,
        affirmedServiceconstructInterfaceT8InterfaceStatisticsRest-serverHttpRxGetMonteEventFailure412 ConfdString,
        affirmedServiceconstructInterfaceT8InterfaceStatisticsRest-serverHttpRxGetMonteEventFailure500 ConfdString,
        affirmedServiceconstructInterfaceT8InterfaceStatisticsRest-serverHttpRxGetMonteEventFailure503 ConfdString,
        affirmedServiceconstructInterfaceT8InterfaceStatisticsRest-serverHttpRxDeleteMonteEventReq ConfdString,
        affirmedServiceconstructInterfaceT8InterfaceStatisticsRest-serverHttpRxDeleteMonteEventSuccessResp ConfdString,
        affirmedServiceconstructInterfaceT8InterfaceStatisticsRest-serverHttpRxDeleteMonteEventFailure400 ConfdString,
        affirmedServiceconstructInterfaceT8InterfaceStatisticsRest-serverHttpRxDeleteMonteEventFailure401 ConfdString,
        affirmedServiceconstructInterfaceT8InterfaceStatisticsRest-serverHttpRxDeleteMonteEventFailure403 ConfdString,
        affirmedServiceconstructInterfaceT8InterfaceStatisticsRest-serverHttpRxDeleteMonteEventFailure404 ConfdString,
        affirmedServiceconstructInterfaceT8InterfaceStatisticsRest-serverHttpRxDeleteMonteEventFailure409 ConfdString,
        affirmedServiceconstructInterfaceT8InterfaceStatisticsRest-serverHttpRxDeleteMonteEventFailure412 ConfdString,
        affirmedServiceconstructInterfaceT8InterfaceStatisticsRest-serverHttpRxDeleteMonteEventFailure500 ConfdString,
        affirmedServiceconstructInterfaceT8InterfaceStatisticsRest-serverHttpRxDeleteMonteEventFailure503 ConfdString,
        affirmedServiceconstructInterfaceT8InterfaceStatisticsRest-serverHttpRxPostDeviceTriggerReq ConfdString,
        affirmedServiceconstructInterfaceT8InterfaceStatisticsRest-serverHttpRxPostDeviceTriggerSuccessResp ConfdString,
        affirmedServiceconstructInterfaceT8InterfaceStatisticsRest-serverHttpRxPostDeviceTriggerFailureResp ConfdString,
        affirmedServiceconstructInterfaceT8InterfaceStatisticsRest-serverHttpRxPutDeviceTriggerReq ConfdString,
        affirmedServiceconstructInterfaceT8InterfaceStatisticsRest-serverHttpRxPutDeviceTriggerSuccessResp ConfdString,
        affirmedServiceconstructInterfaceT8InterfaceStatisticsRest-serverHttpRxPutDeviceTriggerFailureResp ConfdString,
        affirmedServiceconstructInterfaceT8InterfaceStatisticsRest-serverHttpRxGetDeviceTriggerReq ConfdString,
        affirmedServiceconstructInterfaceT8InterfaceStatisticsRest-serverHttpRxGetDeviceTriggerSuccessResp ConfdString,
        affirmedServiceconstructInterfaceT8InterfaceStatisticsRest-serverHttpRxGetDeviceTriggerFailureResp ConfdString,
        affirmedServiceconstructInterfaceT8InterfaceStatisticsRest-serverHttpRxDeleteDeviceTriggerReq ConfdString,
        affirmedServiceconstructInterfaceT8InterfaceStatisticsRest-serverHttpRxDeleteDeviceTriggerSuccessResp ConfdString,
        affirmedServiceconstructInterfaceT8InterfaceStatisticsRest-serverHttpRxDeleteDeviceTriggerFailureResp ConfdString,
        affirmedServiceconstructInterfaceT8InterfaceStatisticsRest-serverHttpRxGetInvalidRouteReq ConfdString,
        affirmedServiceconstructInterfaceT8InterfaceStatisticsRest-serverHttpRxGetInvalidRoute2XXResp ConfdString,
        affirmedServiceconstructInterfaceT8InterfaceStatisticsRest-serverHttpRxGetInvalidRoute3XXResp ConfdString,
        affirmedServiceconstructInterfaceT8InterfaceStatisticsRest-serverHttpRxGetInvalidRoute4XXResp ConfdString,
        affirmedServiceconstructInterfaceT8InterfaceStatisticsRest-serverHttpRxGetInvalidRoute5XXResp ConfdString,
        affirmedServiceconstructInterfaceT8InterfaceStatisticsRest-serverHttpRxGetInvalidResourceReq ConfdString,
        affirmedServiceconstructInterfaceT8InterfaceStatisticsRest-serverHttpRxGetInvalidResource2XXResp ConfdString,
        affirmedServiceconstructInterfaceT8InterfaceStatisticsRest-serverHttpRxGetInvalidResource3XXResp ConfdString,
        affirmedServiceconstructInterfaceT8InterfaceStatisticsRest-serverHttpRxGetInvalidResource4XXResp ConfdString,
        affirmedServiceconstructInterfaceT8InterfaceStatisticsRest-serverHttpRxGetInvalidResource5XXResp ConfdString,
        affirmedServiceconstructInterfaceT8InterfaceStatisticsRest-serverHttpRxGetInvalidMethodReq ConfdString,
        affirmedServiceconstructInterfaceT8InterfaceStatisticsRest-serverHttpRxGetInvalidMethod2XXResp ConfdString,
        affirmedServiceconstructInterfaceT8InterfaceStatisticsRest-serverHttpRxGetInvalidMethod3XXResp ConfdString,
        affirmedServiceconstructInterfaceT8InterfaceStatisticsRest-serverHttpRxGetInvalidMethod4XXResp ConfdString,
        affirmedServiceconstructInterfaceT8InterfaceStatisticsRest-serverHttpRxGetInvalidMethod5XXResp ConfdString,
        affirmedServiceconstructInterfaceT8InterfaceStatisticsRest-serverHttpRxGetParseErrorReq ConfdString,
        affirmedServiceconstructInterfaceT8InterfaceStatisticsRest-serverHttpRxGetParseError2XXResp ConfdString,
        affirmedServiceconstructInterfaceT8InterfaceStatisticsRest-serverHttpRxGetParseError3XXResp ConfdString,
        affirmedServiceconstructInterfaceT8InterfaceStatisticsRest-serverHttpRxGetParseError4XXResp ConfdString,
        affirmedServiceconstructInterfaceT8InterfaceStatisticsRest-serverHttpRxGetParseError5XXResp ConfdString,
        affirmedServiceconstructInterfaceT8InterfaceStatisticsRest-serverHttpRxGetBadContentReq ConfdString,
        affirmedServiceconstructInterfaceT8InterfaceStatisticsRest-serverHttpRxGetBadContent2XXResp ConfdString,
        affirmedServiceconstructInterfaceT8InterfaceStatisticsRest-serverHttpRxGetBadContent3XXResp ConfdString,
        affirmedServiceconstructInterfaceT8InterfaceStatisticsRest-serverHttpRxGetBadContent4XXResp ConfdString,
        affirmedServiceconstructInterfaceT8InterfaceStatisticsRest-serverHttpRxGetBadContent5XXResp ConfdString,
        affirmedServiceconstructInterfaceT8InterfaceStatisticsRest-serverHttpRxGetBadContentTypeReq ConfdString,
        affirmedServiceconstructInterfaceT8InterfaceStatisticsRest-serverHttpRxGetBadContentType2XXResp ConfdString,
        affirmedServiceconstructInterfaceT8InterfaceStatisticsRest-serverHttpRxGetBadContentType3XXResp ConfdString,
        affirmedServiceconstructInterfaceT8InterfaceStatisticsRest-serverHttpRxGetBadContentType4XXResp ConfdString,
        affirmedServiceconstructInterfaceT8InterfaceStatisticsRest-serverHttpRxGetBadContentType5XXResp ConfdString,
        affirmedServiceconstructInterfaceT8InterfaceStatisticsRest-serverHttpRxGetInternalServerErrorReq ConfdString,
        affirmedServiceconstructInterfaceT8InterfaceStatisticsRest-serverHttpRxGetInternalServerError2XXResp ConfdString,
        affirmedServiceconstructInterfaceT8InterfaceStatisticsRest-serverHttpRxGetInternalServerError3XXResp ConfdString,
        affirmedServiceconstructInterfaceT8InterfaceStatisticsRest-serverHttpRxGetInternalServerError4XXResp ConfdString,
        affirmedServiceconstructInterfaceT8InterfaceStatisticsRest-serverHttpRxGetInternalServerError5XXResp ConfdString,
        affirmedServiceconstructInterfaceT8InterfaceStatisticsRest-serverHttpRxDeleteNiddDownLinkDataReq ConfdString,
        affirmedServiceconstructInterfaceT8InterfaceStatisticsRest-serverHttpRxDeleteNiddDownLinkDataSuccessResp ConfdString,
        affirmedServiceconstructInterfaceT8InterfaceStatisticsRest-serverHttpRxDeleteNiddDownLinkDataFailure400 ConfdString,
        affirmedServiceconstructInterfaceT8InterfaceStatisticsRest-serverHttpRxDeleteNiddDownLinkDataFailure401 ConfdString,
        affirmedServiceconstructInterfaceT8InterfaceStatisticsRest-serverHttpRxDeleteNiddDownLinkDataFailure403 ConfdString,
        affirmedServiceconstructInterfaceT8InterfaceStatisticsRest-serverHttpRxDeleteNiddDownLinkDataFailure404 ConfdString,
        affirmedServiceconstructInterfaceT8InterfaceStatisticsRest-serverHttpRxDeleteNiddDownLinkDataFailure409 ConfdString,
        affirmedServiceconstructInterfaceT8InterfaceStatisticsRest-serverHttpRxDeleteNiddDownLinkDataFailure412 ConfdString,
        affirmedServiceconstructInterfaceT8InterfaceStatisticsRest-serverHttpRxDeleteNiddDownLinkDataFailure500 ConfdString,
        affirmedServiceconstructInterfaceT8InterfaceStatisticsRest-serverHttpRxDeleteNiddDownLinkDataFailure503 ConfdString,
        affirmedServiceconstructInterfaceT8InterfaceStatisticsRest-serverHttpRxPutNiddDownLinkDataFailure400 ConfdString,
        affirmedServiceconstructInterfaceT8InterfaceStatisticsRest-serverHttpRxPutNiddDownLinkDataFailure401 ConfdString,
        affirmedServiceconstructInterfaceT8InterfaceStatisticsRest-serverHttpRxPutNiddDownLinkDataFailure403 ConfdString,
        affirmedServiceconstructInterfaceT8InterfaceStatisticsRest-serverHttpRxPutNiddDownLinkDataFailure404 ConfdString,
        affirmedServiceconstructInterfaceT8InterfaceStatisticsRest-serverHttpRxPutNiddDownLinkDataFailure409 ConfdString,
        affirmedServiceconstructInterfaceT8InterfaceStatisticsRest-serverHttpRxPutNiddDownLinkDataFailure412 ConfdString,
        affirmedServiceconstructInterfaceT8InterfaceStatisticsRest-serverHttpRxPutNiddDownLinkDataFailure500 ConfdString,
        affirmedServiceconstructInterfaceT8InterfaceStatisticsRest-serverHttpRxPutNiddDownLinkDataFailure503 ConfdString
    }

affirmedServiceconstructInterfaceT8InterfaceStatisticsRest-serverName OBJECT-TYPE
    SYNTAX      String
    MAX-ACCESS  not-accessible
    STATUS      current
    DESCRIPTION "Table Name"
    ::= { affirmedServiceconstructInterfaceT8InterfaceStatisticsRest-serverEntry 1 }

affirmedServiceconstructInterfaceT8InterfaceStatisticsRest-serverChassis OBJECT-TYPE
    SYNTAX      Unsigned32
    MAX-ACCESS  not-accessible
    STATUS      current
    DESCRIPTION "chassis ID"
    ::= { affirmedServiceconstructInterfaceT8InterfaceStatisticsRest-serverEntry 2 }

affirmedServiceconstructInterfaceT8InterfaceStatisticsRest-serverHttpRxPostReq OBJECT-TYPE
    SYNTAX      ConfdString
    MAX-ACCESS  read-only
    STATUS      current
    DESCRIPTION "Total number of HTTP POST requests received"
    ::= { affirmedServiceconstructInterfaceT8InterfaceStatisticsRest-serverEntry 3 }

affirmedServiceconstructInterfaceT8InterfaceStatisticsRest-serverHttpRxPost2XXResp OBJECT-TYPE
    SYNTAX      ConfdString
    MAX-ACCESS  read-only
    STATUS      current
    DESCRIPTION "Total number of 2xx responses sent for the received HTTP POST request"
    ::= { affirmedServiceconstructInterfaceT8InterfaceStatisticsRest-serverEntry 4 }

affirmedServiceconstructInterfaceT8InterfaceStatisticsRest-serverHttpRxPost3XXResp OBJECT-TYPE
    SYNTAX      ConfdString
    MAX-ACCESS  read-only
    STATUS      current
    DESCRIPTION "Total number of 3xx responses sent for the received HTTP POST request"
    ::= { affirmedServiceconstructInterfaceT8InterfaceStatisticsRest-serverEntry 5 }

affirmedServiceconstructInterfaceT8InterfaceStatisticsRest-serverHttpRxPost4XXResp OBJECT-TYPE
    SYNTAX      ConfdString
    MAX-ACCESS  read-only
    STATUS      current
    DESCRIPTION "Total number of 4xx error responses sent for the received HTTP POST request"
    ::= { affirmedServiceconstructInterfaceT8InterfaceStatisticsRest-serverEntry 6 }

affirmedServiceconstructInterfaceT8InterfaceStatisticsRest-serverHttpRxPost5XXResp OBJECT-TYPE
    SYNTAX      ConfdString
    MAX-ACCESS  read-only
    STATUS      current
    DESCRIPTION "Total number of 5xx error responses sent for the received HTTP POST request"
    ::= { affirmedServiceconstructInterfaceT8InterfaceStatisticsRest-serverEntry 7 }

affirmedServiceconstructInterfaceT8InterfaceStatisticsRest-serverHttpRxGetReq OBJECT-TYPE
    SYNTAX      ConfdString
    MAX-ACCESS  read-only
    STATUS      current
    DESCRIPTION "Total number of HTTP GET requests received"
    ::= { affirmedServiceconstructInterfaceT8InterfaceStatisticsRest-serverEntry 8 }

affirmedServiceconstructInterfaceT8InterfaceStatisticsRest-serverHttpRxGet2XXResp OBJECT-TYPE
    SYNTAX      ConfdString
    MAX-ACCESS  read-only
    STATUS      current
    DESCRIPTION "Total number of 2xx responses sent for the received HTTP GET request"
    ::= { affirmedServiceconstructInterfaceT8InterfaceStatisticsRest-serverEntry 9 }

affirmedServiceconstructInterfaceT8InterfaceStatisticsRest-serverHttpRxGet3XXResp OBJECT-TYPE
    SYNTAX      ConfdString
    MAX-ACCESS  read-only
    STATUS      current
    DESCRIPTION "Total number of 3xx responses sent for the received HTTP GET request"
    ::= { affirmedServiceconstructInterfaceT8InterfaceStatisticsRest-serverEntry 10 }

affirmedServiceconstructInterfaceT8InterfaceStatisticsRest-serverHttpRxGet4XXResp OBJECT-TYPE
    SYNTAX      ConfdString
    MAX-ACCESS  read-only
    STATUS      current
    DESCRIPTION "Total number of 4xx error responses sent for the received HTTP GET request"
    ::= { affirmedServiceconstructInterfaceT8InterfaceStatisticsRest-serverEntry 11 }

affirmedServiceconstructInterfaceT8InterfaceStatisticsRest-serverHttpRxGet5XXResp OBJECT-TYPE
    SYNTAX      ConfdString
    MAX-ACCESS  read-only
    STATUS      current
    DESCRIPTION "Total number of 5xx error responses sent for the received HTTP GET request"
    ::= { affirmedServiceconstructInterfaceT8InterfaceStatisticsRest-serverEntry 12 }

affirmedServiceconstructInterfaceT8InterfaceStatisticsRest-serverHttpRxPutReq OBJECT-TYPE
    SYNTAX      ConfdString
    MAX-ACCESS  read-only
    STATUS      current
    DESCRIPTION "Total number of HTTP PUT requests received"
    ::= { affirmedServiceconstructInterfaceT8InterfaceStatisticsRest-serverEntry 13 }

affirmedServiceconstructInterfaceT8InterfaceStatisticsRest-serverHttpRxPut2XXResp OBJECT-TYPE
    SYNTAX      ConfdString
    MAX-ACCESS  read-only
    STATUS      current
    DESCRIPTION "Total number of 2xx responses sent for the received HTTP PUT request"
    ::= { affirmedServiceconstructInterfaceT8InterfaceStatisticsRest-serverEntry 14 }

affirmedServiceconstructInterfaceT8InterfaceStatisticsRest-serverHttpRxPut3XXResp OBJECT-TYPE
    SYNTAX      ConfdString
    MAX-ACCESS  read-only
    STATUS      current
    DESCRIPTION "Total number of 3xx responses sent for the received HTTP PUT request"
    ::= { affirmedServiceconstructInterfaceT8InterfaceStatisticsRest-serverEntry 15 }

affirmedServiceconstructInterfaceT8InterfaceStatisticsRest-serverHttpRxPut4XXResp OBJECT-TYPE
    SYNTAX      ConfdString
    MAX-ACCESS  read-only
    STATUS      current
    DESCRIPTION "Total number of 4xx error responses sent for the received HTTP PUT request"
    ::= { affirmedServiceconstructInterfaceT8InterfaceStatisticsRest-serverEntry 16 }

affirmedServiceconstructInterfaceT8InterfaceStatisticsRest-serverHttpRxPut5XXResp OBJECT-TYPE
    SYNTAX      ConfdString
    MAX-ACCESS  read-only
    STATUS      current
    DESCRIPTION "Total number of 5xx error responses sent for the received HTTP PUT request"
    ::= { affirmedServiceconstructInterfaceT8InterfaceStatisticsRest-serverEntry 17 }

affirmedServiceconstructInterfaceT8InterfaceStatisticsRest-serverHttpRxPatchReq OBJECT-TYPE
    SYNTAX      ConfdString
    MAX-ACCESS  read-only
    STATUS      current
    DESCRIPTION "Total number of HTTP PATCH requests received"
    ::= { affirmedServiceconstructInterfaceT8InterfaceStatisticsRest-serverEntry 18 }

affirmedServiceconstructInterfaceT8InterfaceStatisticsRest-serverHttpRxPatch2XXResp OBJECT-TYPE
    SYNTAX      ConfdString
    MAX-ACCESS  read-only
    STATUS      current
    DESCRIPTION "Total number of 2xx responses sent for the received HTTP PATCH request"
    ::= { affirmedServiceconstructInterfaceT8InterfaceStatisticsRest-serverEntry 19 }

affirmedServiceconstructInterfaceT8InterfaceStatisticsRest-serverHttpRxPatch3XXResp OBJECT-TYPE
    SYNTAX      ConfdString
    MAX-ACCESS  read-only
    STATUS      current
    DESCRIPTION "Total number of 3xx responses sent for the received HTTP PATCH request"
    ::= { affirmedServiceconstructInterfaceT8InterfaceStatisticsRest-serverEntry 20 }

affirmedServiceconstructInterfaceT8InterfaceStatisticsRest-serverHttpRxPatch4XXResp OBJECT-TYPE
    SYNTAX      ConfdString
    MAX-ACCESS  read-only
    STATUS      current
    DESCRIPTION "Total number of 4xx error responses sent for the received HTTP PATCH request"
    ::= { affirmedServiceconstructInterfaceT8InterfaceStatisticsRest-serverEntry 21 }

affirmedServiceconstructInterfaceT8InterfaceStatisticsRest-serverHttpRxPatch5XXResp OBJECT-TYPE
    SYNTAX      ConfdString
    MAX-ACCESS  read-only
    STATUS      current
    DESCRIPTION "Total number of 5xx error responses sent for the received HTTP PATCH request"
    ::= { affirmedServiceconstructInterfaceT8InterfaceStatisticsRest-serverEntry 22 }

affirmedServiceconstructInterfaceT8InterfaceStatisticsRest-serverHttpRxDeleteReq OBJECT-TYPE
    SYNTAX      ConfdString
    MAX-ACCESS  read-only
    STATUS      current
    DESCRIPTION "Total number of HTTP DELETE requests received"
    ::= { affirmedServiceconstructInterfaceT8InterfaceStatisticsRest-serverEntry 23 }

affirmedServiceconstructInterfaceT8InterfaceStatisticsRest-serverHttpRxDelete2XXResp OBJECT-TYPE
    SYNTAX      ConfdString
    MAX-ACCESS  read-only
    STATUS      current
    DESCRIPTION "Total number of 2xx responses sent for the received HTTP DELETE request"
    ::= { affirmedServiceconstructInterfaceT8InterfaceStatisticsRest-serverEntry 24 }

affirmedServiceconstructInterfaceT8InterfaceStatisticsRest-serverHttpRxDelete3XXResp OBJECT-TYPE
    SYNTAX      ConfdString
    MAX-ACCESS  read-only
    STATUS      current
    DESCRIPTION "Total number of 3xx responses sent for the received HTTP DELETE request"
    ::= { affirmedServiceconstructInterfaceT8InterfaceStatisticsRest-serverEntry 25 }

affirmedServiceconstructInterfaceT8InterfaceStatisticsRest-serverHttpRxDelete4XXResp OBJECT-TYPE
    SYNTAX      ConfdString
    MAX-ACCESS  read-only
    STATUS      current
    DESCRIPTION "Total number of 4xx error responses sent for the received HTTP DELETE request"
    ::= { affirmedServiceconstructInterfaceT8InterfaceStatisticsRest-serverEntry 26 }

affirmedServiceconstructInterfaceT8InterfaceStatisticsRest-serverHttpRxDelete5XXResp OBJECT-TYPE
    SYNTAX      ConfdString
    MAX-ACCESS  read-only
    STATUS      current
    DESCRIPTION "Total number of 5xx error responses sent for the received HTTP DELETE request"
    ::= { affirmedServiceconstructInterfaceT8InterfaceStatisticsRest-serverEntry 27 }

affirmedServiceconstructInterfaceT8InterfaceStatisticsRest-serverHttpRxPostNiddConfigReq OBJECT-TYPE
    SYNTAX      ConfdString
    MAX-ACCESS  read-only
    STATUS      current
    DESCRIPTION "Total number of NIDD configuration POST requests received"
    ::= { affirmedServiceconstructInterfaceT8InterfaceStatisticsRest-serverEntry 28 }

affirmedServiceconstructInterfaceT8InterfaceStatisticsRest-serverHttpRxPostNiddConfigSuccessResp OBJECT-TYPE
    SYNTAX      ConfdString
    MAX-ACCESS  read-only
    STATUS      current
    DESCRIPTION "Total number of NIDD configuration POST requests accepted"
    ::= { affirmedServiceconstructInterfaceT8InterfaceStatisticsRest-serverEntry 29 }

affirmedServiceconstructInterfaceT8InterfaceStatisticsRest-serverHttpRxPostNiddConfigFailure400 OBJECT-TYPE
    SYNTAX      ConfdString
    MAX-ACCESS  read-only
    STATUS      current
    DESCRIPTION "Total number of NIDD configuration POST failures - 400 Bad Request"
    ::= { affirmedServiceconstructInterfaceT8InterfaceStatisticsRest-serverEntry 30 }

affirmedServiceconstructInterfaceT8InterfaceStatisticsRest-serverHttpRxPostNiddConfigFailure401 OBJECT-TYPE
    SYNTAX      ConfdString
    MAX-ACCESS  read-only
    STATUS      current
    DESCRIPTION "Total number of NIDD configuration POST failures - 401 Unauthorized"
    ::= { affirmedServiceconstructInterfaceT8InterfaceStatisticsRest-serverEntry 31 }

affirmedServiceconstructInterfaceT8InterfaceStatisticsRest-serverHttpRxPostNiddConfigFailure403 OBJECT-TYPE
    SYNTAX      ConfdString
    MAX-ACCESS  read-only
    STATUS      current
    DESCRIPTION "Total number of NIDD configuration POST failures - 403 Forbidden"
    ::= { affirmedServiceconstructInterfaceT8InterfaceStatisticsRest-serverEntry 32 }

affirmedServiceconstructInterfaceT8InterfaceStatisticsRest-serverHttpRxPostNiddConfigFailure404 OBJECT-TYPE
    SYNTAX      ConfdString
    MAX-ACCESS  read-only
    STATUS      current
    DESCRIPTION "Total number of NIDD configuration POST failures - 404 Not Found"
    ::= { affirmedServiceconstructInterfaceT8InterfaceStatisticsRest-serverEntry 33 }

affirmedServiceconstructInterfaceT8InterfaceStatisticsRest-serverHttpRxPostNiddConfigFailure409 OBJECT-TYPE
    SYNTAX      ConfdString
    MAX-ACCESS  read-only
    STATUS      current
    DESCRIPTION "Total number of NIDD configuration POST failures - 409 Conflict"
    ::= { affirmedServiceconstructInterfaceT8InterfaceStatisticsRest-serverEntry 34 }

affirmedServiceconstructInterfaceT8InterfaceStatisticsRest-serverHttpRxPostNiddConfigFailure412 OBJECT-TYPE
    SYNTAX      ConfdString
    MAX-ACCESS  read-only
    STATUS      current
    DESCRIPTION "Total number of NIDD configuration POST failures - 412 Precondition Failed"
    ::= { affirmedServiceconstructInterfaceT8InterfaceStatisticsRest-serverEntry 35 }

affirmedServiceconstructInterfaceT8InterfaceStatisticsRest-serverHttpRxPostNiddConfigFailure500 OBJECT-TYPE
    SYNTAX      ConfdString
    MAX-ACCESS  read-only
    STATUS      current
    DESCRIPTION "Total number of NIDD configuration POST failures - 500 Internal Server Error"
    ::= { affirmedServiceconstructInterfaceT8InterfaceStatisticsRest-serverEntry 36 }

affirmedServiceconstructInterfaceT8InterfaceStatisticsRest-serverHttpRxPostNiddConfigFailure503 OBJECT-TYPE
    SYNTAX      ConfdString
    MAX-ACCESS  read-only
    STATUS      current
    DESCRIPTION "Total number of NIDD configuration POST failures - 503 Service Unavailable"
    ::= { affirmedServiceconstructInterfaceT8InterfaceStatisticsRest-serverEntry 37 }

affirmedServiceconstructInterfaceT8InterfaceStatisticsRest-serverHttpRxPatchNiddConfigReq OBJECT-TYPE
    SYNTAX      ConfdString
    MAX-ACCESS  read-only
    STATUS      current
    DESCRIPTION "Total number of NIDD configuration PATCH requests received"
    ::= { affirmedServiceconstructInterfaceT8InterfaceStatisticsRest-serverEntry 38 }

affirmedServiceconstructInterfaceT8InterfaceStatisticsRest-serverHttpRxPatchNiddConfigSuccessResp OBJECT-TYPE
    SYNTAX      ConfdString
    MAX-ACCESS  read-only
    STATUS      current
    DESCRIPTION "Total number of NIDD configuration PATCH requests accepted"
    ::= { affirmedServiceconstructInterfaceT8InterfaceStatisticsRest-serverEntry 39 }

affirmedServiceconstructInterfaceT8InterfaceStatisticsRest-serverHttpRxPatchNiddConfigFailure400 OBJECT-TYPE
    SYNTAX      ConfdString
    MAX-ACCESS  read-only
    STATUS      current
    DESCRIPTION "Total number of NIDD configuration PATCH failures - 400 Bad Request"
    ::= { affirmedServiceconstructInterfaceT8InterfaceStatisticsRest-serverEntry 40 }

affirmedServiceconstructInterfaceT8InterfaceStatisticsRest-serverHttpRxPatchNiddConfigFailure401 OBJECT-TYPE
    SYNTAX      ConfdString
    MAX-ACCESS  read-only
    STATUS      current
    DESCRIPTION "Total number of NIDD configuration PATCH failures - 401 Unauthorized"
    ::= { affirmedServiceconstructInterfaceT8InterfaceStatisticsRest-serverEntry 41 }

affirmedServiceconstructInterfaceT8InterfaceStatisticsRest-serverHttpRxPatchNiddConfigFailure403 OBJECT-TYPE
    SYNTAX      ConfdString
    MAX-ACCESS  read-only
    STATUS      current
    DESCRIPTION "Total number of NIDD configuration PATCH failures - 403 Forbidden"
    ::= { affirmedServiceconstructInterfaceT8InterfaceStatisticsRest-serverEntry 42 }

affirmedServiceconstructInterfaceT8InterfaceStatisticsRest-serverHttpRxPatchNiddConfigFailure404 OBJECT-TYPE
    SYNTAX      ConfdString
    MAX-ACCESS  read-only
    STATUS      current
    DESCRIPTION "Total number of NIDD configuration PATCH failures - 404 Not Found"
    ::= { affirmedServiceconstructInterfaceT8InterfaceStatisticsRest-serverEntry 43 }

affirmedServiceconstructInterfaceT8InterfaceStatisticsRest-serverHttpRxPatchNiddConfigFailure409 OBJECT-TYPE
    SYNTAX      ConfdString
    MAX-ACCESS  read-only
    STATUS      current
    DESCRIPTION "Total number of NIDD configuration PATCH failures - 409 Conflict"
    ::= { affirmedServiceconstructInterfaceT8InterfaceStatisticsRest-serverEntry 44 }

affirmedServiceconstructInterfaceT8InterfaceStatisticsRest-serverHttpRxPatchNiddConfigFailure412 OBJECT-TYPE
    SYNTAX      ConfdString
    MAX-ACCESS  read-only
    STATUS      current
    DESCRIPTION "Total number of NIDD configuration PATCH failures - 412 Precondition Failed"
    ::= { affirmedServiceconstructInterfaceT8InterfaceStatisticsRest-serverEntry 45 }

affirmedServiceconstructInterfaceT8InterfaceStatisticsRest-serverHttpRxPatchNiddConfigFailure500 OBJECT-TYPE
    SYNTAX      ConfdString
    MAX-ACCESS  read-only
    STATUS      current
    DESCRIPTION "Total number of NIDD configuration PATCH failures - 500 Internal Server Error"
    ::= { affirmedServiceconstructInterfaceT8InterfaceStatisticsRest-serverEntry 46 }

affirmedServiceconstructInterfaceT8InterfaceStatisticsRest-serverHttpRxPatchNiddConfigFailure503 OBJECT-TYPE
    SYNTAX      ConfdString
    MAX-ACCESS  read-only
    STATUS      current
    DESCRIPTION "Total number of NIDD configuration PATCH failures - 503 Service Unavailable"
    ::= { affirmedServiceconstructInterfaceT8InterfaceStatisticsRest-serverEntry 47 }

affirmedServiceconstructInterfaceT8InterfaceStatisticsRest-serverHttpRxGetNiddConfigReq OBJECT-TYPE
    SYNTAX      ConfdString
    MAX-ACCESS  read-only
    STATUS      current
    DESCRIPTION "Total number of NIDD configuration GET requests received"
    ::= { affirmedServiceconstructInterfaceT8InterfaceStatisticsRest-serverEntry 48 }

affirmedServiceconstructInterfaceT8InterfaceStatisticsRest-serverHttpRxGetNiddConfigSuccessResp OBJECT-TYPE
    SYNTAX      ConfdString
    MAX-ACCESS  read-only
    STATUS      current
    DESCRIPTION "Total number of NIDD configuration GET requests accepted"
    ::= { affirmedServiceconstructInterfaceT8InterfaceStatisticsRest-serverEntry 49 }

affirmedServiceconstructInterfaceT8InterfaceStatisticsRest-serverHttpRxGetNiddConfigFailure400 OBJECT-TYPE
    SYNTAX      ConfdString
    MAX-ACCESS  read-only
    STATUS      current
    DESCRIPTION "Total number of NIDD configuration GET failures - 400 Bad Request"
    ::= { affirmedServiceconstructInterfaceT8InterfaceStatisticsRest-serverEntry 50 }

affirmedServiceconstructInterfaceT8InterfaceStatisticsRest-serverHttpRxGetNiddConfigFailure401 OBJECT-TYPE
    SYNTAX      ConfdString
    MAX-ACCESS  read-only
    STATUS      current
    DESCRIPTION "Total number of NIDD configuration GET failures - 401 Unauthorized"
    ::= { affirmedServiceconstructInterfaceT8InterfaceStatisticsRest-serverEntry 51 }

affirmedServiceconstructInterfaceT8InterfaceStatisticsRest-serverHttpRxGetNiddConfigFailure403 OBJECT-TYPE
    SYNTAX      ConfdString
    MAX-ACCESS  read-only
    STATUS      current
    DESCRIPTION "Total number of NIDD configuration GET failures - 403 Forbidden"
    ::= { affirmedServiceconstructInterfaceT8InterfaceStatisticsRest-serverEntry 52 }

affirmedServiceconstructInterfaceT8InterfaceStatisticsRest-serverHttpRxGetNiddConfigFailure404 OBJECT-TYPE
    SYNTAX      ConfdString
    MAX-ACCESS  read-only
    STATUS      current
    DESCRIPTION "Total number of NIDD configuration GET failures - 404 Not Found"
    ::= { affirmedServiceconstructInterfaceT8InterfaceStatisticsRest-serverEntry 53 }

affirmedServiceconstructInterfaceT8InterfaceStatisticsRest-serverHttpRxGetNiddConfigFailure409 OBJECT-TYPE
    SYNTAX      ConfdString
    MAX-ACCESS  read-only
    STATUS      current
    DESCRIPTION "Total number of NIDD configuration GET failures - 409 Conflict"
    ::= { affirmedServiceconstructInterfaceT8InterfaceStatisticsRest-serverEntry 54 }

affirmedServiceconstructInterfaceT8InterfaceStatisticsRest-serverHttpRxGetNiddConfigFailure412 OBJECT-TYPE
    SYNTAX      ConfdString
    MAX-ACCESS  read-only
    STATUS      current
    DESCRIPTION "Total number of NIDD configuration GET failures - 412 Precondition Failed"
    ::= { affirmedServiceconstructInterfaceT8InterfaceStatisticsRest-serverEntry 55 }

affirmedServiceconstructInterfaceT8InterfaceStatisticsRest-serverHttpRxGetNiddConfigFailure500 OBJECT-TYPE
    SYNTAX      ConfdString
    MAX-ACCESS  read-only
    STATUS      current
    DESCRIPTION "Total number of NIDD configuration GET failures - 500 Internal Server Error"
    ::= { affirmedServiceconstructInterfaceT8InterfaceStatisticsRest-serverEntry 56 }

affirmedServiceconstructInterfaceT8InterfaceStatisticsRest-serverHttpRxGetNiddConfigFailure503 OBJECT-TYPE
    SYNTAX      ConfdString
    MAX-ACCESS  read-only
    STATUS      current
    DESCRIPTION "Total number of NIDD configuration GET failures - 503 Service Unavailable"
    ::= { affirmedServiceconstructInterfaceT8InterfaceStatisticsRest-serverEntry 57 }

affirmedServiceconstructInterfaceT8InterfaceStatisticsRest-serverHttpRxDeleteNiddConfigReq OBJECT-TYPE
    SYNTAX      ConfdString
    MAX-ACCESS  read-only
    STATUS      current
    DESCRIPTION "Total number of NIDD configuration DELETE requests received"
    ::= { affirmedServiceconstructInterfaceT8InterfaceStatisticsRest-serverEntry 58 }

affirmedServiceconstructInterfaceT8InterfaceStatisticsRest-serverHttpRxDeleteNiddConfigSuccessResp OBJECT-TYPE
    SYNTAX      ConfdString
    MAX-ACCESS  read-only
    STATUS      current
    DESCRIPTION "Total number of NIDD configuration DELETE requests accepted"
    ::= { affirmedServiceconstructInterfaceT8InterfaceStatisticsRest-serverEntry 59 }

affirmedServiceconstructInterfaceT8InterfaceStatisticsRest-serverHttpRxDeleteNiddConfigFailure400 OBJECT-TYPE
    SYNTAX      ConfdString
    MAX-ACCESS  read-only
    STATUS      current
    DESCRIPTION "Total number of NIDD configuration DELETE failures - 400 Bad Request"
    ::= { affirmedServiceconstructInterfaceT8InterfaceStatisticsRest-serverEntry 60 }

affirmedServiceconstructInterfaceT8InterfaceStatisticsRest-serverHttpRxDeleteNiddConfigFailure401 OBJECT-TYPE
    SYNTAX      ConfdString
    MAX-ACCESS  read-only
    STATUS      current
    DESCRIPTION "Total number of NIDD configuration DELETE failures - 401 Unauthorized"
    ::= { affirmedServiceconstructInterfaceT8InterfaceStatisticsRest-serverEntry 61 }

affirmedServiceconstructInterfaceT8InterfaceStatisticsRest-serverHttpRxDeleteNiddConfigFailure403 OBJECT-TYPE
    SYNTAX      ConfdString
    MAX-ACCESS  read-only
    STATUS      current
    DESCRIPTION "Total number of NIDD configuration DELETE failures - 403 Forbidden"
    ::= { affirmedServiceconstructInterfaceT8InterfaceStatisticsRest-serverEntry 62 }

affirmedServiceconstructInterfaceT8InterfaceStatisticsRest-serverHttpRxDeleteNiddConfigFailure404 OBJECT-TYPE
    SYNTAX      ConfdString
    MAX-ACCESS  read-only
    STATUS      current
    DESCRIPTION "Total number of NIDD configuration DELETE failures - 404 Not Found"
    ::= { affirmedServiceconstructInterfaceT8InterfaceStatisticsRest-serverEntry 63 }

affirmedServiceconstructInterfaceT8InterfaceStatisticsRest-serverHttpRxDeleteNiddConfigFailure409 OBJECT-TYPE
    SYNTAX      ConfdString
    MAX-ACCESS  read-only
    STATUS      current
    DESCRIPTION "Total number of NIDD configuration DELETE failures - 409 Conflict"
    ::= { affirmedServiceconstructInterfaceT8InterfaceStatisticsRest-serverEntry 64 }

affirmedServiceconstructInterfaceT8InterfaceStatisticsRest-serverHttpRxDeleteNiddConfigFailure412 OBJECT-TYPE
    SYNTAX      ConfdString
    MAX-ACCESS  read-only
    STATUS      current
    DESCRIPTION "Total number of NIDD configuration DELETE failures - 412 Precondition Failed"
    ::= { affirmedServiceconstructInterfaceT8InterfaceStatisticsRest-serverEntry 65 }

affirmedServiceconstructInterfaceT8InterfaceStatisticsRest-serverHttpRxDeleteNiddConfigFailure500 OBJECT-TYPE
    SYNTAX      ConfdString
    MAX-ACCESS  read-only
    STATUS      current
    DESCRIPTION "Total number of NIDD configuration DELETE failures - 500 Internal Server Error"
    ::= { affirmedServiceconstructInterfaceT8InterfaceStatisticsRest-serverEntry 66 }

affirmedServiceconstructInterfaceT8InterfaceStatisticsRest-serverHttpRxDeleteNiddConfigFailure503 OBJECT-TYPE
    SYNTAX      ConfdString
    MAX-ACCESS  read-only
    STATUS      current
    DESCRIPTION "Total number of NIDD configuration DELETE failures - 503 Service Unavailable"
    ::= { affirmedServiceconstructInterfaceT8InterfaceStatisticsRest-serverEntry 67 }

affirmedServiceconstructInterfaceT8InterfaceStatisticsRest-serverHttpRxPostNiddDownLinkDataReq OBJECT-TYPE
    SYNTAX      ConfdString
    MAX-ACCESS  read-only
    STATUS      current
    DESCRIPTION "Total number of NIDD downlink data delivery POST requests received"
    ::= { affirmedServiceconstructInterfaceT8InterfaceStatisticsRest-serverEntry 68 }

affirmedServiceconstructInterfaceT8InterfaceStatisticsRest-serverHttpRxPostNiddDownLinkDataSuccessResp OBJECT-TYPE
    SYNTAX      ConfdString
    MAX-ACCESS  read-only
    STATUS      current
    DESCRIPTION "Total number of NIDD downlink data delivery POST requests accepted"
    ::= { affirmedServiceconstructInterfaceT8InterfaceStatisticsRest-serverEntry 69 }

affirmedServiceconstructInterfaceT8InterfaceStatisticsRest-serverHttpRxPostNiddDownLinkDataFailure400 OBJECT-TYPE
    SYNTAX      ConfdString
    MAX-ACCESS  read-only
    STATUS      current
    DESCRIPTION "Total number of NIDD downlink data delivery POST failures - 400 Bad Request"
    ::= { affirmedServiceconstructInterfaceT8InterfaceStatisticsRest-serverEntry 70 }

affirmedServiceconstructInterfaceT8InterfaceStatisticsRest-serverHttpRxPostNiddDownLinkDataFailure401 OBJECT-TYPE
    SYNTAX      ConfdString
    MAX-ACCESS  read-only
    STATUS      current
    DESCRIPTION "Total number of NIDD downlink data delivery POST failures - 401 Unauthorized"
    ::= { affirmedServiceconstructInterfaceT8InterfaceStatisticsRest-serverEntry 71 }

affirmedServiceconstructInterfaceT8InterfaceStatisticsRest-serverHttpRxPostNiddDownLinkDataFailure403 OBJECT-TYPE
    SYNTAX      ConfdString
    MAX-ACCESS  read-only
    STATUS      current
    DESCRIPTION "Total number of NIDD downlink data delivery POST failures - 403 Forbidden"
    ::= { affirmedServiceconstructInterfaceT8InterfaceStatisticsRest-serverEntry 72 }

affirmedServiceconstructInterfaceT8InterfaceStatisticsRest-serverHttpRxPostNiddDownLinkDataFailure404 OBJECT-TYPE
    SYNTAX      ConfdString
    MAX-ACCESS  read-only
    STATUS      current
    DESCRIPTION "Total number of NIDD downlink data delivery POST failures - 404 Not Found"
    ::= { affirmedServiceconstructInterfaceT8InterfaceStatisticsRest-serverEntry 73 }

affirmedServiceconstructInterfaceT8InterfaceStatisticsRest-serverHttpRxPostNiddDownLinkDataFailure409 OBJECT-TYPE
    SYNTAX      ConfdString
    MAX-ACCESS  read-only
    STATUS      current
    DESCRIPTION "Total number of NIDD downlink data delivery POST failures - 409 Conflict"
    ::= { affirmedServiceconstructInterfaceT8InterfaceStatisticsRest-serverEntry 74 }

affirmedServiceconstructInterfaceT8InterfaceStatisticsRest-serverHttpRxPostNiddDownLinkDataFailure412 OBJECT-TYPE
    SYNTAX      ConfdString
    MAX-ACCESS  read-only
    STATUS      current
    DESCRIPTION "Total number of NIDD downlink data delivery POST failures - 412 Precondition Failed"
    ::= { affirmedServiceconstructInterfaceT8InterfaceStatisticsRest-serverEntry 75 }

affirmedServiceconstructInterfaceT8InterfaceStatisticsRest-serverHttpRxPostNiddDownLinkDataFailure500 OBJECT-TYPE
    SYNTAX      ConfdString
    MAX-ACCESS  read-only
    STATUS      current
    DESCRIPTION "Total number of NIDD downlink data delivery POST failures - 500 Internal Server Error"
    ::= { affirmedServiceconstructInterfaceT8InterfaceStatisticsRest-serverEntry 76 }

affirmedServiceconstructInterfaceT8InterfaceStatisticsRest-serverHttpRxPostNiddDownLinkDataFailure503 OBJECT-TYPE
    SYNTAX      ConfdString
    MAX-ACCESS  read-only
    STATUS      current
    DESCRIPTION "Total number of NIDD downlink data delivery POST failures - 503 Service Unavailable"
    ::= { affirmedServiceconstructInterfaceT8InterfaceStatisticsRest-serverEntry 77 }

affirmedServiceconstructInterfaceT8InterfaceStatisticsRest-serverHttpRxPutNiddDownLinkDataReq OBJECT-TYPE
    SYNTAX      ConfdString
    MAX-ACCESS  read-only
    STATUS      current
    DESCRIPTION "Total number of NIDD downlink data delivery PUT requests received"
    ::= { affirmedServiceconstructInterfaceT8InterfaceStatisticsRest-serverEntry 78 }

affirmedServiceconstructInterfaceT8InterfaceStatisticsRest-serverHttpRxPutNiddDownLinkDataSuccessResp OBJECT-TYPE
    SYNTAX      ConfdString
    MAX-ACCESS  read-only
    STATUS      current
    DESCRIPTION "Total number of NIDD downlink data delivery PUT requests accepted"
    ::= { affirmedServiceconstructInterfaceT8InterfaceStatisticsRest-serverEntry 79 }

affirmedServiceconstructInterfaceT8InterfaceStatisticsRest-serverHttpRxPutNiddDownLinkDataFailureResp OBJECT-TYPE
    SYNTAX      ConfdString
    MAX-ACCESS  read-only
    STATUS      current
    DESCRIPTION "Total number of NIDD downlink data delivery PUT requests failed"
    ::= { affirmedServiceconstructInterfaceT8InterfaceStatisticsRest-serverEntry 80 }

affirmedServiceconstructInterfaceT8InterfaceStatisticsRest-serverHttpRxGetNiddDownLinkDataReq OBJECT-TYPE
    SYNTAX      ConfdString
    MAX-ACCESS  read-only
    STATUS      current
    DESCRIPTION "Total number of NIDD downlink data delivery GET requests received"
    ::= { affirmedServiceconstructInterfaceT8InterfaceStatisticsRest-serverEntry 81 }

affirmedServiceconstructInterfaceT8InterfaceStatisticsRest-serverHttpRxGetNiddDownLinkDataSuccessResp OBJECT-TYPE
    SYNTAX      ConfdString
    MAX-ACCESS  read-only
    STATUS      current
    DESCRIPTION "Total number of NIDD downlink data delivery GET requests accepted"
    ::= { affirmedServiceconstructInterfaceT8InterfaceStatisticsRest-serverEntry 82 }

affirmedServiceconstructInterfaceT8InterfaceStatisticsRest-serverHttpRxGetNiddDownLinkDataFailure400 OBJECT-TYPE
    SYNTAX      ConfdString
    MAX-ACCESS  read-only
    STATUS      current
    DESCRIPTION "Total number of NIDD downlink data delivery GET failures - 400 Bad Request"
    ::= { affirmedServiceconstructInterfaceT8InterfaceStatisticsRest-serverEntry 83 }

affirmedServiceconstructInterfaceT8InterfaceStatisticsRest-serverHttpRxGetNiddDownLinkDataFailure401 OBJECT-TYPE
    SYNTAX      ConfdString
    MAX-ACCESS  read-only
    STATUS      current
    DESCRIPTION "Total number of NIDD downlink data delivery GET failures - 401 Unauthorized"
    ::= { affirmedServiceconstructInterfaceT8InterfaceStatisticsRest-serverEntry 84 }

affirmedServiceconstructInterfaceT8InterfaceStatisticsRest-serverHttpRxGetNiddDownLinkDataFailure403 OBJECT-TYPE
    SYNTAX      ConfdString
    MAX-ACCESS  read-only
    STATUS      current
    DESCRIPTION "Total number of NIDD downlink data delivery GET failures - 403 Forbidden"
    ::= { affirmedServiceconstructInterfaceT8InterfaceStatisticsRest-serverEntry 85 }

affirmedServiceconstructInterfaceT8InterfaceStatisticsRest-serverHttpRxGetNiddDownLinkDataFailure404 OBJECT-TYPE
    SYNTAX      ConfdString
    MAX-ACCESS  read-only
    STATUS      current
    DESCRIPTION "Total number of NIDD downlink data delivery GET failures - 404 Not Found"
    ::= { affirmedServiceconstructInterfaceT8InterfaceStatisticsRest-serverEntry 86 }

affirmedServiceconstructInterfaceT8InterfaceStatisticsRest-serverHttpRxGetNiddDownLinkDataFailure409 OBJECT-TYPE
    SYNTAX      ConfdString
    MAX-ACCESS  read-only
    STATUS      current
    DESCRIPTION "Total number of NIDD downlink data delivery GET failures - 409 Conflict"
    ::= { affirmedServiceconstructInterfaceT8InterfaceStatisticsRest-serverEntry 87 }

affirmedServiceconstructInterfaceT8InterfaceStatisticsRest-serverHttpRxGetNiddDownLinkDataFailure412 OBJECT-TYPE
    SYNTAX      ConfdString
    MAX-ACCESS  read-only
    STATUS      current
    DESCRIPTION "Total number of NIDD downlink data delivery GET failures - 412 Precondition Failed"
    ::= { affirmedServiceconstructInterfaceT8InterfaceStatisticsRest-serverEntry 88 }

affirmedServiceconstructInterfaceT8InterfaceStatisticsRest-serverHttpRxGetNiddDownLinkDataFailure500 OBJECT-TYPE
    SYNTAX      ConfdString
    MAX-ACCESS  read-only
    STATUS      current
    DESCRIPTION "Total number of NIDD downlink data delivery GET failures - 500 Internal Server Error"
    ::= { affirmedServiceconstructInterfaceT8InterfaceStatisticsRest-serverEntry 89 }

affirmedServiceconstructInterfaceT8InterfaceStatisticsRest-serverHttpRxGetNiddDownLinkDataFailure503 OBJECT-TYPE
    SYNTAX      ConfdString
    MAX-ACCESS  read-only
    STATUS      current
    DESCRIPTION "Total number of NIDD downlink data delivery GET failures - 503 Service Unavailable"
    ::= { affirmedServiceconstructInterfaceT8InterfaceStatisticsRest-serverEntry 90 }

affirmedServiceconstructInterfaceT8InterfaceStatisticsRest-serverHttpRxPostMonteEventReq OBJECT-TYPE
    SYNTAX      ConfdString
    MAX-ACCESS  read-only
    STATUS      current
    DESCRIPTION "Total number of MONTE event subscriptions POST requests received"
    ::= { affirmedServiceconstructInterfaceT8InterfaceStatisticsRest-serverEntry 91 }

affirmedServiceconstructInterfaceT8InterfaceStatisticsRest-serverHttpRxPostMonteEventSuccessResp OBJECT-TYPE
    SYNTAX      ConfdString
    MAX-ACCESS  read-only
    STATUS      current
    DESCRIPTION "Total number of MONTE event subscriptions POST requests accepted"
    ::= { affirmedServiceconstructInterfaceT8InterfaceStatisticsRest-serverEntry 92 }

affirmedServiceconstructInterfaceT8InterfaceStatisticsRest-serverHttpRxPostMonteEventFailure400 OBJECT-TYPE
    SYNTAX      ConfdString
    MAX-ACCESS  read-only
    STATUS      current
    DESCRIPTION "Total number of MONTE event subscriptions POST failures - 400 Bad Request"
    ::= { affirmedServiceconstructInterfaceT8InterfaceStatisticsRest-serverEntry 93 }

affirmedServiceconstructInterfaceT8InterfaceStatisticsRest-serverHttpRxPostMonteEventFailure401 OBJECT-TYPE
    SYNTAX      ConfdString
    MAX-ACCESS  read-only
    STATUS      current
    DESCRIPTION "Total number of MONTE event subscriptions POST failures - 401 Unauthorized"
    ::= { affirmedServiceconstructInterfaceT8InterfaceStatisticsRest-serverEntry 94 }

affirmedServiceconstructInterfaceT8InterfaceStatisticsRest-serverHttpRxPostMonteEventFailure403 OBJECT-TYPE
    SYNTAX      ConfdString
    MAX-ACCESS  read-only
    STATUS      current
    DESCRIPTION "Total number of MONTE event subscriptions POST failures - 403 Forbidden"
    ::= { affirmedServiceconstructInterfaceT8InterfaceStatisticsRest-serverEntry 95 }

affirmedServiceconstructInterfaceT8InterfaceStatisticsRest-serverHttpRxPostMonteEventFailure404 OBJECT-TYPE
    SYNTAX      ConfdString
    MAX-ACCESS  read-only
    STATUS      current
    DESCRIPTION "Total number of MONTE event subscriptions POST failures - 404 Not Found"
    ::= { affirmedServiceconstructInterfaceT8InterfaceStatisticsRest-serverEntry 96 }

affirmedServiceconstructInterfaceT8InterfaceStatisticsRest-serverHttpRxPostMonteEventFailure409 OBJECT-TYPE
    SYNTAX      ConfdString
    MAX-ACCESS  read-only
    STATUS      current
    DESCRIPTION "Total number of MONTE event subscriptions POST failures - 409 Conflict"
    ::= { affirmedServiceconstructInterfaceT8InterfaceStatisticsRest-serverEntry 97 }

affirmedServiceconstructInterfaceT8InterfaceStatisticsRest-serverHttpRxPostMonteEventFailure412 OBJECT-TYPE
    SYNTAX      ConfdString
    MAX-ACCESS  read-only
    STATUS      current
    DESCRIPTION "Total number of MONTE event subscriptions POST failures - 412 Precondition Failed"
    ::= { affirmedServiceconstructInterfaceT8InterfaceStatisticsRest-serverEntry 98 }

affirmedServiceconstructInterfaceT8InterfaceStatisticsRest-serverHttpRxPostMonteEventFailure500 OBJECT-TYPE
    SYNTAX      ConfdString
    MAX-ACCESS  read-only
    STATUS      current
    DESCRIPTION "Total number of MONTE event subscriptions POST failures - 500 Internal Server Error"
    ::= { affirmedServiceconstructInterfaceT8InterfaceStatisticsRest-serverEntry 99 }

affirmedServiceconstructInterfaceT8InterfaceStatisticsRest-serverHttpRxPostMonteEventFailure503 OBJECT-TYPE
    SYNTAX      ConfdString
    MAX-ACCESS  read-only
    STATUS      current
    DESCRIPTION "Total number of MONTE event subscriptions POST failures - 503 Service Unavailable"
    ::= { affirmedServiceconstructInterfaceT8InterfaceStatisticsRest-serverEntry 100 }

affirmedServiceconstructInterfaceT8InterfaceStatisticsRest-serverHttpRxPutMonteEventReq OBJECT-TYPE
    SYNTAX      ConfdString
    MAX-ACCESS  read-only
    STATUS      current
    DESCRIPTION "Total number of MONTE event subscriptions PUT requests received"
    ::= { affirmedServiceconstructInterfaceT8InterfaceStatisticsRest-serverEntry 101 }

affirmedServiceconstructInterfaceT8InterfaceStatisticsRest-serverHttpRxPutMonteEventSuccessResp OBJECT-TYPE
    SYNTAX      ConfdString
    MAX-ACCESS  read-only
    STATUS      current
    DESCRIPTION "Total number of MONTE event subscriptions PUT requests accepted"
    ::= { affirmedServiceconstructInterfaceT8InterfaceStatisticsRest-serverEntry 102 }

affirmedServiceconstructInterfaceT8InterfaceStatisticsRest-serverHttpRxPutMonteEventFailure400 OBJECT-TYPE
    SYNTAX      ConfdString
    MAX-ACCESS  read-only
    STATUS      current
    DESCRIPTION "Total number of MONTE event subscriptions PUT failures - 400 Bad Request"
    ::= { affirmedServiceconstructInterfaceT8InterfaceStatisticsRest-serverEntry 103 }

affirmedServiceconstructInterfaceT8InterfaceStatisticsRest-serverHttpRxPutMonteEventFailure401 OBJECT-TYPE
    SYNTAX      ConfdString
    MAX-ACCESS  read-only
    STATUS      current
    DESCRIPTION "Total number of MONTE event subscriptions PUT failures - 401 Unauthorized"
    ::= { affirmedServiceconstructInterfaceT8InterfaceStatisticsRest-serverEntry 104 }

affirmedServiceconstructInterfaceT8InterfaceStatisticsRest-serverHttpRxPutMonteEventFailure403 OBJECT-TYPE
    SYNTAX      ConfdString
    MAX-ACCESS  read-only
    STATUS      current
    DESCRIPTION "Total number of MONTE event subscriptions PUT failures - 403 Forbidden"
    ::= { affirmedServiceconstructInterfaceT8InterfaceStatisticsRest-serverEntry 105 }

affirmedServiceconstructInterfaceT8InterfaceStatisticsRest-serverHttpRxPutMonteEventFailure404 OBJECT-TYPE
    SYNTAX      ConfdString
    MAX-ACCESS  read-only
    STATUS      current
    DESCRIPTION "Total number of MONTE event subscriptions PUT failures - 404 Not Found"
    ::= { affirmedServiceconstructInterfaceT8InterfaceStatisticsRest-serverEntry 106 }

affirmedServiceconstructInterfaceT8InterfaceStatisticsRest-serverHttpRxPutMonteEventFailure409 OBJECT-TYPE
    SYNTAX      ConfdString
    MAX-ACCESS  read-only
    STATUS      current
    DESCRIPTION "Total number of MONTE event subscriptions PUT failures - 409 Conflict"
    ::= { affirmedServiceconstructInterfaceT8InterfaceStatisticsRest-serverEntry 107 }

affirmedServiceconstructInterfaceT8InterfaceStatisticsRest-serverHttpRxPutMonteEventFailure412 OBJECT-TYPE
    SYNTAX      ConfdString
    MAX-ACCESS  read-only
    STATUS      current
    DESCRIPTION "Total number of MONTE event subscriptions PUT failures - 412 Precondition Failed"
    ::= { affirmedServiceconstructInterfaceT8InterfaceStatisticsRest-serverEntry 108 }

affirmedServiceconstructInterfaceT8InterfaceStatisticsRest-serverHttpRxPutMonteEventFailure500 OBJECT-TYPE
    SYNTAX      ConfdString
    MAX-ACCESS  read-only
    STATUS      current
    DESCRIPTION "Total number of MONTE event subscriptions PUT failures - 500 Internal Server Error"
    ::= { affirmedServiceconstructInterfaceT8InterfaceStatisticsRest-serverEntry 109 }

affirmedServiceconstructInterfaceT8InterfaceStatisticsRest-serverHttpRxPutMonteEventFailure503 OBJECT-TYPE
    SYNTAX      ConfdString
    MAX-ACCESS  read-only
    STATUS      current
    DESCRIPTION "Total number of MONTE event subscriptions PUT failures - 503 Service Unavailable"
    ::= { affirmedServiceconstructInterfaceT8InterfaceStatisticsRest-serverEntry 110 }

affirmedServiceconstructInterfaceT8InterfaceStatisticsRest-serverHttpRxGetMonteEventReq OBJECT-TYPE
    SYNTAX      ConfdString
    MAX-ACCESS  read-only
    STATUS      current
    DESCRIPTION "Total number of MONTE event subscriptions GET requests received"
    ::= { affirmedServiceconstructInterfaceT8InterfaceStatisticsRest-serverEntry 111 }

affirmedServiceconstructInterfaceT8InterfaceStatisticsRest-serverHttpRxGetMonteEventSuccessResp OBJECT-TYPE
    SYNTAX      ConfdString
    MAX-ACCESS  read-only
    STATUS      current
    DESCRIPTION "Total number of MONTE event subscriptions GET requests accepted"
    ::= { affirmedServiceconstructInterfaceT8InterfaceStatisticsRest-serverEntry 112 }

affirmedServiceconstructInterfaceT8InterfaceStatisticsRest-serverHttpRxGetMonteEventFailure400 OBJECT-TYPE
    SYNTAX      ConfdString
    MAX-ACCESS  read-only
    STATUS      current
    DESCRIPTION "Total number of MONTE event subscriptions GET failures - 400 Bad Request"
    ::= { affirmedServiceconstructInterfaceT8InterfaceStatisticsRest-serverEntry 113 }

affirmedServiceconstructInterfaceT8InterfaceStatisticsRest-serverHttpRxGetMonteEventFailure401 OBJECT-TYPE
    SYNTAX      ConfdString
    MAX-ACCESS  read-only
    STATUS      current
    DESCRIPTION "Total number of MONTE event subscriptions GET failures - 401 Unauthorized"
    ::= { affirmedServiceconstructInterfaceT8InterfaceStatisticsRest-serverEntry 114 }

affirmedServiceconstructInterfaceT8InterfaceStatisticsRest-serverHttpRxGetMonteEventFailure403 OBJECT-TYPE
    SYNTAX      ConfdString
    MAX-ACCESS  read-only
    STATUS      current
    DESCRIPTION "Total number of MONTE event subscriptions GET failures - 403 Forbidden"
    ::= { affirmedServiceconstructInterfaceT8InterfaceStatisticsRest-serverEntry 115 }

affirmedServiceconstructInterfaceT8InterfaceStatisticsRest-serverHttpRxGetMonteEventFailure404 OBJECT-TYPE
    SYNTAX      ConfdString
    MAX-ACCESS  read-only
    STATUS      current
    DESCRIPTION "Total number of MONTE event subscriptions GET failures - 404 Not Found"
    ::= { affirmedServiceconstructInterfaceT8InterfaceStatisticsRest-serverEntry 116 }

affirmedServiceconstructInterfaceT8InterfaceStatisticsRest-serverHttpRxGetMonteEventFailure409 OBJECT-TYPE
    SYNTAX      ConfdString
    MAX-ACCESS  read-only
    STATUS      current
    DESCRIPTION "Total number of MONTE event subscriptions GET failures - 409 Conflict"
    ::= { affirmedServiceconstructInterfaceT8InterfaceStatisticsRest-serverEntry 117 }

affirmedServiceconstructInterfaceT8InterfaceStatisticsRest-serverHttpRxGetMonteEventFailure412 OBJECT-TYPE
    SYNTAX      ConfdString
    MAX-ACCESS  read-only
    STATUS      current
    DESCRIPTION "Total number of MONTE event subscriptions GET failures - 412 Precondition Failed"
    ::= { affirmedServiceconstructInterfaceT8InterfaceStatisticsRest-serverEntry 118 }

affirmedServiceconstructInterfaceT8InterfaceStatisticsRest-serverHttpRxGetMonteEventFailure500 OBJECT-TYPE
    SYNTAX      ConfdString
    MAX-ACCESS  read-only
    STATUS      current
    DESCRIPTION "Total number of MONTE event subscriptions GET failures - 500 Internal Server Error"
    ::= { affirmedServiceconstructInterfaceT8InterfaceStatisticsRest-serverEntry 119 }

affirmedServiceconstructInterfaceT8InterfaceStatisticsRest-serverHttpRxGetMonteEventFailure503 OBJECT-TYPE
    SYNTAX      ConfdString
    MAX-ACCESS  read-only
    STATUS      current
    DESCRIPTION "Total number of MONTE event subscriptions GET failures - 503 Service Unavailable"
    ::= { affirmedServiceconstructInterfaceT8InterfaceStatisticsRest-serverEntry 120 }

affirmedServiceconstructInterfaceT8InterfaceStatisticsRest-serverHttpRxDeleteMonteEventReq OBJECT-TYPE
    SYNTAX      ConfdString
    MAX-ACCESS  read-only
    STATUS      current
    DESCRIPTION "Total number of MONTE event subscriptions DELETE requests received"
    ::= { affirmedServiceconstructInterfaceT8InterfaceStatisticsRest-serverEntry 121 }

affirmedServiceconstructInterfaceT8InterfaceStatisticsRest-serverHttpRxDeleteMonteEventSuccessResp OBJECT-TYPE
    SYNTAX      ConfdString
    MAX-ACCESS  read-only
    STATUS      current
    DESCRIPTION "Total number of MONTE event subscriptions DELETE requests accepted"
    ::= { affirmedServiceconstructInterfaceT8InterfaceStatisticsRest-serverEntry 122 }

affirmedServiceconstructInterfaceT8InterfaceStatisticsRest-serverHttpRxDeleteMonteEventFailure400 OBJECT-TYPE
    SYNTAX      ConfdString
    MAX-ACCESS  read-only
    STATUS      current
    DESCRIPTION "Total number of MONTE event subscriptions DELETE failures - 400 Bad Request"
    ::= { affirmedServiceconstructInterfaceT8InterfaceStatisticsRest-serverEntry 123 }

affirmedServiceconstructInterfaceT8InterfaceStatisticsRest-serverHttpRxDeleteMonteEventFailure401 OBJECT-TYPE
    SYNTAX      ConfdString
    MAX-ACCESS  read-only
    STATUS      current
    DESCRIPTION "Total number of MONTE event subscriptions DELETE failures - 401 Unauthorized"
    ::= { affirmedServiceconstructInterfaceT8InterfaceStatisticsRest-serverEntry 124 }

affirmedServiceconstructInterfaceT8InterfaceStatisticsRest-serverHttpRxDeleteMonteEventFailure403 OBJECT-TYPE
    SYNTAX      ConfdString
    MAX-ACCESS  read-only
    STATUS      current
    DESCRIPTION "Total number of MONTE event subscriptions DELETE failures - 403 Forbidden"
    ::= { affirmedServiceconstructInterfaceT8InterfaceStatisticsRest-serverEntry 125 }

affirmedServiceconstructInterfaceT8InterfaceStatisticsRest-serverHttpRxDeleteMonteEventFailure404 OBJECT-TYPE
    SYNTAX      ConfdString
    MAX-ACCESS  read-only
    STATUS      current
    DESCRIPTION "Total number of MONTE event subscriptions DELETE failures - 404 Not Found"
    ::= { affirmedServiceconstructInterfaceT8InterfaceStatisticsRest-serverEntry 126 }

affirmedServiceconstructInterfaceT8InterfaceStatisticsRest-serverHttpRxDeleteMonteEventFailure409 OBJECT-TYPE
    SYNTAX      ConfdString
    MAX-ACCESS  read-only
    STATUS      current
    DESCRIPTION "Total number of MONTE event subscriptions DELETE failures - 409 Conflict"
    ::= { affirmedServiceconstructInterfaceT8InterfaceStatisticsRest-serverEntry 127 }

affirmedServiceconstructInterfaceT8InterfaceStatisticsRest-serverHttpRxDeleteMonteEventFailure412 OBJECT-TYPE
    SYNTAX      ConfdString
    MAX-ACCESS  read-only
    STATUS      current
    DESCRIPTION "Total number of MONTE event subscriptions DELETE failures - 412 Precondition Failed"
    ::= { affirmedServiceconstructInterfaceT8InterfaceStatisticsRest-serverEntry 128 }

affirmedServiceconstructInterfaceT8InterfaceStatisticsRest-serverHttpRxDeleteMonteEventFailure500 OBJECT-TYPE
    SYNTAX      ConfdString
    MAX-ACCESS  read-only
    STATUS      current
    DESCRIPTION "Total number of MONTE event subscriptions DELETE failures - 500 Internal Server Error"
    ::= { affirmedServiceconstructInterfaceT8InterfaceStatisticsRest-serverEntry 129 }

affirmedServiceconstructInterfaceT8InterfaceStatisticsRest-serverHttpRxDeleteMonteEventFailure503 OBJECT-TYPE
    SYNTAX      ConfdString
    MAX-ACCESS  read-only
    STATUS      current
    DESCRIPTION "Total number of MONTE event subscriptions DELETE failures - 503 Service Unavailable"
    ::= { affirmedServiceconstructInterfaceT8InterfaceStatisticsRest-serverEntry 130 }

affirmedServiceconstructInterfaceT8InterfaceStatisticsRest-serverHttpRxPostDeviceTriggerReq OBJECT-TYPE
    SYNTAX      ConfdString
    MAX-ACCESS  read-only
    STATUS      current
    DESCRIPTION "Total number of Device Triggering transaction POST requests received"
    ::= { affirmedServiceconstructInterfaceT8InterfaceStatisticsRest-serverEntry 131 }

affirmedServiceconstructInterfaceT8InterfaceStatisticsRest-serverHttpRxPostDeviceTriggerSuccessResp OBJECT-TYPE
    SYNTAX      ConfdString
    MAX-ACCESS  read-only
    STATUS      current
    DESCRIPTION "Total number of Device Triggering transaction POST requests accepted"
    ::= { affirmedServiceconstructInterfaceT8InterfaceStatisticsRest-serverEntry 132 }

affirmedServiceconstructInterfaceT8InterfaceStatisticsRest-serverHttpRxPostDeviceTriggerFailureResp OBJECT-TYPE
    SYNTAX      ConfdString
    MAX-ACCESS  read-only
    STATUS      current
    DESCRIPTION "Total number of Device Triggering transaction POST requests failed"
    ::= { affirmedServiceconstructInterfaceT8InterfaceStatisticsRest-serverEntry 133 }

affirmedServiceconstructInterfaceT8InterfaceStatisticsRest-serverHttpRxPutDeviceTriggerReq OBJECT-TYPE
    SYNTAX      ConfdString
    MAX-ACCESS  read-only
    STATUS      current
    DESCRIPTION "Total number of Device Triggering transaction PUT requests received"
    ::= { affirmedServiceconstructInterfaceT8InterfaceStatisticsRest-serverEntry 134 }

affirmedServiceconstructInterfaceT8InterfaceStatisticsRest-serverHttpRxPutDeviceTriggerSuccessResp OBJECT-TYPE
    SYNTAX      ConfdString
    MAX-ACCESS  read-only
    STATUS      current
    DESCRIPTION "Total number of Device Triggering transaction PUT requests accepted"
    ::= { affirmedServiceconstructInterfaceT8InterfaceStatisticsRest-serverEntry 135 }

affirmedServiceconstructInterfaceT8InterfaceStatisticsRest-serverHttpRxPutDeviceTriggerFailureResp OBJECT-TYPE
    SYNTAX      ConfdString
    MAX-ACCESS  read-only
    STATUS      current
    DESCRIPTION "Total number of Device Triggering transaction PUT requests failed"
    ::= { affirmedServiceconstructInterfaceT8InterfaceStatisticsRest-serverEntry 136 }

affirmedServiceconstructInterfaceT8InterfaceStatisticsRest-serverHttpRxGetDeviceTriggerReq OBJECT-TYPE
    SYNTAX      ConfdString
    MAX-ACCESS  read-only
    STATUS      current
    DESCRIPTION "Total number of Device Triggering transaction GET requests received"
    ::= { affirmedServiceconstructInterfaceT8InterfaceStatisticsRest-serverEntry 137 }

affirmedServiceconstructInterfaceT8InterfaceStatisticsRest-serverHttpRxGetDeviceTriggerSuccessResp OBJECT-TYPE
    SYNTAX      ConfdString
    MAX-ACCESS  read-only
    STATUS      current
    DESCRIPTION "Total number of Device Triggering transaction GET requests accepted"
    ::= { affirmedServiceconstructInterfaceT8InterfaceStatisticsRest-serverEntry 138 }

affirmedServiceconstructInterfaceT8InterfaceStatisticsRest-serverHttpRxGetDeviceTriggerFailureResp OBJECT-TYPE
    SYNTAX      ConfdString
    MAX-ACCESS  read-only
    STATUS      current
    DESCRIPTION "Total number of Device Triggering transaction GET requests failed"
    ::= { affirmedServiceconstructInterfaceT8InterfaceStatisticsRest-serverEntry 139 }

affirmedServiceconstructInterfaceT8InterfaceStatisticsRest-serverHttpRxDeleteDeviceTriggerReq OBJECT-TYPE
    SYNTAX      ConfdString
    MAX-ACCESS  read-only
    STATUS      current
    DESCRIPTION "Total number of Device Triggering transaction DELETE requests received"
    ::= { affirmedServiceconstructInterfaceT8InterfaceStatisticsRest-serverEntry 140 }

affirmedServiceconstructInterfaceT8InterfaceStatisticsRest-serverHttpRxDeleteDeviceTriggerSuccessResp OBJECT-TYPE
    SYNTAX      ConfdString
    MAX-ACCESS  read-only
    STATUS      current
    DESCRIPTION "Total number of Device Triggering transaction DELETE requests accepted"
    ::= { affirmedServiceconstructInterfaceT8InterfaceStatisticsRest-serverEntry 141 }

affirmedServiceconstructInterfaceT8InterfaceStatisticsRest-serverHttpRxDeleteDeviceTriggerFailureResp OBJECT-TYPE
    SYNTAX      ConfdString
    MAX-ACCESS  read-only
    STATUS      current
    DESCRIPTION "Total number of Device Triggering transaction DELETE requests failed"
    ::= { affirmedServiceconstructInterfaceT8InterfaceStatisticsRest-serverEntry 142 }

affirmedServiceconstructInterfaceT8InterfaceStatisticsRest-serverHttpRxGetInvalidRouteReq OBJECT-TYPE
    SYNTAX      ConfdString
    MAX-ACCESS  read-only
    STATUS      current
    DESCRIPTION "Total number of Invalid Route GET requests received"
    ::= { affirmedServiceconstructInterfaceT8InterfaceStatisticsRest-serverEntry 143 }

affirmedServiceconstructInterfaceT8InterfaceStatisticsRest-serverHttpRxGetInvalidRoute2XXResp OBJECT-TYPE
    SYNTAX      ConfdString
    MAX-ACCESS  read-only
    STATUS      current
    DESCRIPTION "Total number of Invalid Route GET responses - 2XX Success"
    ::= { affirmedServiceconstructInterfaceT8InterfaceStatisticsRest-serverEntry 144 }

affirmedServiceconstructInterfaceT8InterfaceStatisticsRest-serverHttpRxGetInvalidRoute3XXResp OBJECT-TYPE
    SYNTAX      ConfdString
    MAX-ACCESS  read-only
    STATUS      current
    DESCRIPTION "Total number of Invalid Route GET failures - 3XX Responses"
    ::= { affirmedServiceconstructInterfaceT8InterfaceStatisticsRest-serverEntry 145 }

affirmedServiceconstructInterfaceT8InterfaceStatisticsRest-serverHttpRxGetInvalidRoute4XXResp OBJECT-TYPE
    SYNTAX      ConfdString
    MAX-ACCESS  read-only
    STATUS      current
    DESCRIPTION "Total number of Invalid Route GET failures - 4XX Failures"
    ::= { affirmedServiceconstructInterfaceT8InterfaceStatisticsRest-serverEntry 146 }

affirmedServiceconstructInterfaceT8InterfaceStatisticsRest-serverHttpRxGetInvalidRoute5XXResp OBJECT-TYPE
    SYNTAX      ConfdString
    MAX-ACCESS  read-only
    STATUS      current
    DESCRIPTION "Total number of Invalid Route GET failures - 5XX Failures"
    ::= { affirmedServiceconstructInterfaceT8InterfaceStatisticsRest-serverEntry 147 }

affirmedServiceconstructInterfaceT8InterfaceStatisticsRest-serverHttpRxGetInvalidResourceReq OBJECT-TYPE
    SYNTAX      ConfdString
    MAX-ACCESS  read-only
    STATUS      current
    DESCRIPTION "Total number of Invalid Resource GET requests received"
    ::= { affirmedServiceconstructInterfaceT8InterfaceStatisticsRest-serverEntry 148 }

affirmedServiceconstructInterfaceT8InterfaceStatisticsRest-serverHttpRxGetInvalidResource2XXResp OBJECT-TYPE
    SYNTAX      ConfdString
    MAX-ACCESS  read-only
    STATUS      current
    DESCRIPTION "Total number of Invalid Resource GET responses - 2XX Success"
    ::= { affirmedServiceconstructInterfaceT8InterfaceStatisticsRest-serverEntry 149 }

affirmedServiceconstructInterfaceT8InterfaceStatisticsRest-serverHttpRxGetInvalidResource3XXResp OBJECT-TYPE
    SYNTAX      ConfdString
    MAX-ACCESS  read-only
    STATUS      current
    DESCRIPTION "Total number of Invalid Resource GET failures - 3XX Responses"
    ::= { affirmedServiceconstructInterfaceT8InterfaceStatisticsRest-serverEntry 150 }

affirmedServiceconstructInterfaceT8InterfaceStatisticsRest-serverHttpRxGetInvalidResource4XXResp OBJECT-TYPE
    SYNTAX      ConfdString
    MAX-ACCESS  read-only
    STATUS      current
    DESCRIPTION "Total number of Invalid Resource GET failures - 4XX Failures"
    ::= { affirmedServiceconstructInterfaceT8InterfaceStatisticsRest-serverEntry 151 }

affirmedServiceconstructInterfaceT8InterfaceStatisticsRest-serverHttpRxGetInvalidResource5XXResp OBJECT-TYPE
    SYNTAX      ConfdString
    MAX-ACCESS  read-only
    STATUS      current
    DESCRIPTION "Total number of Invalid Resource GET failures - 5XX Failures"
    ::= { affirmedServiceconstructInterfaceT8InterfaceStatisticsRest-serverEntry 152 }

affirmedServiceconstructInterfaceT8InterfaceStatisticsRest-serverHttpRxGetInvalidMethodReq OBJECT-TYPE
    SYNTAX      ConfdString
    MAX-ACCESS  read-only
    STATUS      current
    DESCRIPTION "Total number of Invalid Method GET requests received"
    ::= { affirmedServiceconstructInterfaceT8InterfaceStatisticsRest-serverEntry 153 }

affirmedServiceconstructInterfaceT8InterfaceStatisticsRest-serverHttpRxGetInvalidMethod2XXResp OBJECT-TYPE
    SYNTAX      ConfdString
    MAX-ACCESS  read-only
    STATUS      current
    DESCRIPTION "Total number of Invalid Method GET responses - 2XX Success"
    ::= { affirmedServiceconstructInterfaceT8InterfaceStatisticsRest-serverEntry 154 }

affirmedServiceconstructInterfaceT8InterfaceStatisticsRest-serverHttpRxGetInvalidMethod3XXResp OBJECT-TYPE
    SYNTAX      ConfdString
    MAX-ACCESS  read-only
    STATUS      current
    DESCRIPTION "Total number of Invalid Method GET failures - 3XX Responses"
    ::= { affirmedServiceconstructInterfaceT8InterfaceStatisticsRest-serverEntry 155 }

affirmedServiceconstructInterfaceT8InterfaceStatisticsRest-serverHttpRxGetInvalidMethod4XXResp OBJECT-TYPE
    SYNTAX      ConfdString
    MAX-ACCESS  read-only
    STATUS      current
    DESCRIPTION "Total number of Invalid Method GET failures - 4XX Failures"
    ::= { affirmedServiceconstructInterfaceT8InterfaceStatisticsRest-serverEntry 156 }

affirmedServiceconstructInterfaceT8InterfaceStatisticsRest-serverHttpRxGetInvalidMethod5XXResp OBJECT-TYPE
    SYNTAX      ConfdString
    MAX-ACCESS  read-only
    STATUS      current
    DESCRIPTION "Total number of Invalid Method GET failures - 5XX Failures"
    ::= { affirmedServiceconstructInterfaceT8InterfaceStatisticsRest-serverEntry 157 }

affirmedServiceconstructInterfaceT8InterfaceStatisticsRest-serverHttpRxGetParseErrorReq OBJECT-TYPE
    SYNTAX      ConfdString
    MAX-ACCESS  read-only
    STATUS      current
    DESCRIPTION "Total number of Parse Error GET requests received"
    ::= { affirmedServiceconstructInterfaceT8InterfaceStatisticsRest-serverEntry 158 }

affirmedServiceconstructInterfaceT8InterfaceStatisticsRest-serverHttpRxGetParseError2XXResp OBJECT-TYPE
    SYNTAX      ConfdString
    MAX-ACCESS  read-only
    STATUS      current
    DESCRIPTION "Total number of Parse Error GET responses - 2XX Success"
    ::= { affirmedServiceconstructInterfaceT8InterfaceStatisticsRest-serverEntry 159 }

affirmedServiceconstructInterfaceT8InterfaceStatisticsRest-serverHttpRxGetParseError3XXResp OBJECT-TYPE
    SYNTAX      ConfdString
    MAX-ACCESS  read-only
    STATUS      current
    DESCRIPTION "Total number of Parse Error GET failures - 3XX Responses"
    ::= { affirmedServiceconstructInterfaceT8InterfaceStatisticsRest-serverEntry 160 }

affirmedServiceconstructInterfaceT8InterfaceStatisticsRest-serverHttpRxGetParseError4XXResp OBJECT-TYPE
    SYNTAX      ConfdString
    MAX-ACCESS  read-only
    STATUS      current
    DESCRIPTION "Total number of Parse Error GET failures - 4XX Failures"
    ::= { affirmedServiceconstructInterfaceT8InterfaceStatisticsRest-serverEntry 161 }

affirmedServiceconstructInterfaceT8InterfaceStatisticsRest-serverHttpRxGetParseError5XXResp OBJECT-TYPE
    SYNTAX      ConfdString
    MAX-ACCESS  read-only
    STATUS      current
    DESCRIPTION "Total number of Parse Error GET failures - 5XX Failures"
    ::= { affirmedServiceconstructInterfaceT8InterfaceStatisticsRest-serverEntry 162 }

affirmedServiceconstructInterfaceT8InterfaceStatisticsRest-serverHttpRxGetBadContentReq OBJECT-TYPE
    SYNTAX      ConfdString
    MAX-ACCESS  read-only
    STATUS      current
    DESCRIPTION "Total number of Bad Content GET requests received"
    ::= { affirmedServiceconstructInterfaceT8InterfaceStatisticsRest-serverEntry 163 }

affirmedServiceconstructInterfaceT8InterfaceStatisticsRest-serverHttpRxGetBadContent2XXResp OBJECT-TYPE
    SYNTAX      ConfdString
    MAX-ACCESS  read-only
    STATUS      current
    DESCRIPTION "Total number of Bad Content GET responses - 2XX Success"
    ::= { affirmedServiceconstructInterfaceT8InterfaceStatisticsRest-serverEntry 164 }

affirmedServiceconstructInterfaceT8InterfaceStatisticsRest-serverHttpRxGetBadContent3XXResp OBJECT-TYPE
    SYNTAX      ConfdString
    MAX-ACCESS  read-only
    STATUS      current
    DESCRIPTION "Total number of Bad Content GET failures - 3XX Responses"
    ::= { affirmedServiceconstructInterfaceT8InterfaceStatisticsRest-serverEntry 165 }

affirmedServiceconstructInterfaceT8InterfaceStatisticsRest-serverHttpRxGetBadContent4XXResp OBJECT-TYPE
    SYNTAX      ConfdString
    MAX-ACCESS  read-only
    STATUS      current
    DESCRIPTION "Total number of Bad Content GET failures - 4XX Failures"
    ::= { affirmedServiceconstructInterfaceT8InterfaceStatisticsRest-serverEntry 166 }

affirmedServiceconstructInterfaceT8InterfaceStatisticsRest-serverHttpRxGetBadContent5XXResp OBJECT-TYPE
    SYNTAX      ConfdString
    MAX-ACCESS  read-only
    STATUS      current
    DESCRIPTION "Total number of Bad Content GET failures - 5XX Failures"
    ::= { affirmedServiceconstructInterfaceT8InterfaceStatisticsRest-serverEntry 167 }

affirmedServiceconstructInterfaceT8InterfaceStatisticsRest-serverHttpRxGetBadContentTypeReq OBJECT-TYPE
    SYNTAX      ConfdString
    MAX-ACCESS  read-only
    STATUS      current
    DESCRIPTION "Total number of Bad Content-Type GET requests received"
    ::= { affirmedServiceconstructInterfaceT8InterfaceStatisticsRest-serverEntry 168 }

affirmedServiceconstructInterfaceT8InterfaceStatisticsRest-serverHttpRxGetBadContentType2XXResp OBJECT-TYPE
    SYNTAX      ConfdString
    MAX-ACCESS  read-only
    STATUS      current
    DESCRIPTION "Total number of Bad Content-Type GET responses - 2XX Success"
    ::= { affirmedServiceconstructInterfaceT8InterfaceStatisticsRest-serverEntry 169 }

affirmedServiceconstructInterfaceT8InterfaceStatisticsRest-serverHttpRxGetBadContentType3XXResp OBJECT-TYPE
    SYNTAX      ConfdString
    MAX-ACCESS  read-only
    STATUS      current
    DESCRIPTION "Total number of Bad Content-Type GET failures - 3XX Responses"
    ::= { affirmedServiceconstructInterfaceT8InterfaceStatisticsRest-serverEntry 170 }

affirmedServiceconstructInterfaceT8InterfaceStatisticsRest-serverHttpRxGetBadContentType4XXResp OBJECT-TYPE
    SYNTAX      ConfdString
    MAX-ACCESS  read-only
    STATUS      current
    DESCRIPTION "Total number of Bad Content-Type GET failures - 4XX Failures"
    ::= { affirmedServiceconstructInterfaceT8InterfaceStatisticsRest-serverEntry 171 }

affirmedServiceconstructInterfaceT8InterfaceStatisticsRest-serverHttpRxGetBadContentType5XXResp OBJECT-TYPE
    SYNTAX      ConfdString
    MAX-ACCESS  read-only
    STATUS      current
    DESCRIPTION "Total number of Bad Content-Type GET failures - 5XX Failures"
    ::= { affirmedServiceconstructInterfaceT8InterfaceStatisticsRest-serverEntry 172 }

affirmedServiceconstructInterfaceT8InterfaceStatisticsRest-serverHttpRxGetInternalServerErrorReq OBJECT-TYPE
    SYNTAX      ConfdString
    MAX-ACCESS  read-only
    STATUS      current
    DESCRIPTION "Total number of Internal Server Error GET requests received"
    ::= { affirmedServiceconstructInterfaceT8InterfaceStatisticsRest-serverEntry 173 }

affirmedServiceconstructInterfaceT8InterfaceStatisticsRest-serverHttpRxGetInternalServerError2XXResp OBJECT-TYPE
    SYNTAX      ConfdString
    MAX-ACCESS  read-only
    STATUS      current
    DESCRIPTION "Total number of Internal Server Error GET responses - 2XX Success"
    ::= { affirmedServiceconstructInterfaceT8InterfaceStatisticsRest-serverEntry 174 }

affirmedServiceconstructInterfaceT8InterfaceStatisticsRest-serverHttpRxGetInternalServerError3XXResp OBJECT-TYPE
    SYNTAX      ConfdString
    MAX-ACCESS  read-only
    STATUS      current
    DESCRIPTION "Total number of Internal Server Error GET failures - 3XX Responses"
    ::= { affirmedServiceconstructInterfaceT8InterfaceStatisticsRest-serverEntry 175 }

affirmedServiceconstructInterfaceT8InterfaceStatisticsRest-serverHttpRxGetInternalServerError4XXResp OBJECT-TYPE
    SYNTAX      ConfdString
    MAX-ACCESS  read-only
    STATUS      current
    DESCRIPTION "Total number of Internal Server Error GET failures - 4XX Failures"
    ::= { affirmedServiceconstructInterfaceT8InterfaceStatisticsRest-serverEntry 176 }

affirmedServiceconstructInterfaceT8InterfaceStatisticsRest-serverHttpRxGetInternalServerError5XXResp OBJECT-TYPE
    SYNTAX      ConfdString
    MAX-ACCESS  read-only
    STATUS      current
    DESCRIPTION "Total number of Internal Server Error GET failures - 5XX Failures"
    ::= { affirmedServiceconstructInterfaceT8InterfaceStatisticsRest-serverEntry 177 }

affirmedServiceconstructInterfaceT8InterfaceStatisticsRest-serverHttpRxDeleteNiddDownLinkDataReq OBJECT-TYPE
    SYNTAX      ConfdString
    MAX-ACCESS  read-only
    STATUS      current
    DESCRIPTION "Total number of NIDD downlink data delivery DELETE requests received"
    ::= { affirmedServiceconstructInterfaceT8InterfaceStatisticsRest-serverEntry 178 }

affirmedServiceconstructInterfaceT8InterfaceStatisticsRest-serverHttpRxDeleteNiddDownLinkDataSuccessResp OBJECT-TYPE
    SYNTAX      ConfdString
    MAX-ACCESS  read-only
    STATUS      current
    DESCRIPTION "Total number of NIDD downlink data delivery DELETE requests accepted"
    ::= { affirmedServiceconstructInterfaceT8InterfaceStatisticsRest-serverEntry 179 }

affirmedServiceconstructInterfaceT8InterfaceStatisticsRest-serverHttpRxDeleteNiddDownLinkDataFailure400 OBJECT-TYPE
    SYNTAX      ConfdString
    MAX-ACCESS  read-only
    STATUS      current
    DESCRIPTION "Total number of NIDD downlink data delivery DELETE failures - 400 Bad Request"
    ::= { affirmedServiceconstructInterfaceT8InterfaceStatisticsRest-serverEntry 180 }

affirmedServiceconstructInterfaceT8InterfaceStatisticsRest-serverHttpRxDeleteNiddDownLinkDataFailure401 OBJECT-TYPE
    SYNTAX      ConfdString
    MAX-ACCESS  read-only
    STATUS      current
    DESCRIPTION "Total number of NIDD downlink data delivery DELETE failures - 401 Unauthorized"
    ::= { affirmedServiceconstructInterfaceT8InterfaceStatisticsRest-serverEntry 181 }

affirmedServiceconstructInterfaceT8InterfaceStatisticsRest-serverHttpRxDeleteNiddDownLinkDataFailure403 OBJECT-TYPE
    SYNTAX      ConfdString
    MAX-ACCESS  read-only
    STATUS      current
    DESCRIPTION "Total number of NIDD downlink data delivery DELETE failures - 403 Forbidden"
    ::= { affirmedServiceconstructInterfaceT8InterfaceStatisticsRest-serverEntry 182 }

affirmedServiceconstructInterfaceT8InterfaceStatisticsRest-serverHttpRxDeleteNiddDownLinkDataFailure404 OBJECT-TYPE
    SYNTAX      ConfdString
    MAX-ACCESS  read-only
    STATUS      current
    DESCRIPTION "Total number of NIDD downlink data delivery DELETE failures - 404 Not Found"
    ::= { affirmedServiceconstructInterfaceT8InterfaceStatisticsRest-serverEntry 183 }

affirmedServiceconstructInterfaceT8InterfaceStatisticsRest-serverHttpRxDeleteNiddDownLinkDataFailure409 OBJECT-TYPE
    SYNTAX      ConfdString
    MAX-ACCESS  read-only
    STATUS      current
    DESCRIPTION "Total number of NIDD downlink data delivery DELETE failures - 409 Conflict"
    ::= { affirmedServiceconstructInterfaceT8InterfaceStatisticsRest-serverEntry 184 }

affirmedServiceconstructInterfaceT8InterfaceStatisticsRest-serverHttpRxDeleteNiddDownLinkDataFailure412 OBJECT-TYPE
    SYNTAX      ConfdString
    MAX-ACCESS  read-only
    STATUS      current
    DESCRIPTION "Total number of NIDD downlink data delivery DELETE failures - 412 Precondition Failed"
    ::= { affirmedServiceconstructInterfaceT8InterfaceStatisticsRest-serverEntry 185 }

affirmedServiceconstructInterfaceT8InterfaceStatisticsRest-serverHttpRxDeleteNiddDownLinkDataFailure500 OBJECT-TYPE
    SYNTAX      ConfdString
    MAX-ACCESS  read-only
    STATUS      current
    DESCRIPTION "Total number of NIDD downlink data delivery DELETE failures - 500 Internal Server Error"
    ::= { affirmedServiceconstructInterfaceT8InterfaceStatisticsRest-serverEntry 186 }

affirmedServiceconstructInterfaceT8InterfaceStatisticsRest-serverHttpRxDeleteNiddDownLinkDataFailure503 OBJECT-TYPE
    SYNTAX      ConfdString
    MAX-ACCESS  read-only
    STATUS      current
    DESCRIPTION "Total number of NIDD downlink data delivery DELETE failures - 503 Service Unavailable"
    ::= { affirmedServiceconstructInterfaceT8InterfaceStatisticsRest-serverEntry 187 }

affirmedServiceconstructInterfaceT8InterfaceStatisticsRest-serverHttpRxPutNiddDownLinkDataFailure400 OBJECT-TYPE
    SYNTAX      ConfdString
    MAX-ACCESS  read-only
    STATUS      current
    DESCRIPTION "Total number of NIDD downlink data delivery PUT failures - 400 Bad Request"
    ::= { affirmedServiceconstructInterfaceT8InterfaceStatisticsRest-serverEntry 188 }

affirmedServiceconstructInterfaceT8InterfaceStatisticsRest-serverHttpRxPutNiddDownLinkDataFailure401 OBJECT-TYPE
    SYNTAX      ConfdString
    MAX-ACCESS  read-only
    STATUS      current
    DESCRIPTION "Total number of NIDD downlink data delivery PUT failures - 401 Unauthorized"
    ::= { affirmedServiceconstructInterfaceT8InterfaceStatisticsRest-serverEntry 189 }

affirmedServiceconstructInterfaceT8InterfaceStatisticsRest-serverHttpRxPutNiddDownLinkDataFailure403 OBJECT-TYPE
    SYNTAX      ConfdString
    MAX-ACCESS  read-only
    STATUS      current
    DESCRIPTION "Total number of NIDD downlink data delivery PUT failures - 403 Forbidden"
    ::= { affirmedServiceconstructInterfaceT8InterfaceStatisticsRest-serverEntry 190 }

affirmedServiceconstructInterfaceT8InterfaceStatisticsRest-serverHttpRxPutNiddDownLinkDataFailure404 OBJECT-TYPE
    SYNTAX      ConfdString
    MAX-ACCESS  read-only
    STATUS      current
    DESCRIPTION "Total number of NIDD downlink data delivery PUT failures - 404 Not Found"
    ::= { affirmedServiceconstructInterfaceT8InterfaceStatisticsRest-serverEntry 191 }

affirmedServiceconstructInterfaceT8InterfaceStatisticsRest-serverHttpRxPutNiddDownLinkDataFailure409 OBJECT-TYPE
    SYNTAX      ConfdString
    MAX-ACCESS  read-only
    STATUS      current
    DESCRIPTION "Total number of NIDD downlink data delivery PUT failures - 409 Conflict"
    ::= { affirmedServiceconstructInterfaceT8InterfaceStatisticsRest-serverEntry 192 }

affirmedServiceconstructInterfaceT8InterfaceStatisticsRest-serverHttpRxPutNiddDownLinkDataFailure412 OBJECT-TYPE
    SYNTAX      ConfdString
    MAX-ACCESS  read-only
    STATUS      current
    DESCRIPTION "Total number of NIDD downlink data delivery PUT failures - 412 Precondition Failed"
    ::= { affirmedServiceconstructInterfaceT8InterfaceStatisticsRest-serverEntry 193 }

affirmedServiceconstructInterfaceT8InterfaceStatisticsRest-serverHttpRxPutNiddDownLinkDataFailure500 OBJECT-TYPE
    SYNTAX      ConfdString
    MAX-ACCESS  read-only
    STATUS      current
    DESCRIPTION "Total number of NIDD downlink data delivery PUT failures - 500 Internal Server Error"
    ::= { affirmedServiceconstructInterfaceT8InterfaceStatisticsRest-serverEntry 194 }

affirmedServiceconstructInterfaceT8InterfaceStatisticsRest-serverHttpRxPutNiddDownLinkDataFailure503 OBJECT-TYPE
    SYNTAX      ConfdString
    MAX-ACCESS  read-only
    STATUS      current
    DESCRIPTION "Total number of NIDD downlink data delivery PUT failures - 503 Service Unavailable"
    ::= { affirmedServiceconstructInterfaceT8InterfaceStatisticsRest-serverEntry 195 }

affirmedServiceconstructInterfaceT8InterfaceStatisticsRest-server-allTable OBJECT-TYPE
    SYNTAX      SEQUENCE OF AffirmedServiceconstructInterfaceT8InterfaceStatisticsRest-server-allEntry
    MAX-ACCESS  not-accessible
    STATUS      current
    DESCRIPTION ""
    ::= { affirmedServiceconstructInterfaceT8InterfaceStatistics 1 }

affirmedServiceconstructInterfaceT8InterfaceStatisticsRest-server-allEntry OBJECT-TYPE
    SYNTAX      AffirmedServiceconstructInterfaceT8InterfaceStatisticsRest-server-allEntry
    MAX-ACCESS  not-accessible
    STATUS      current
    DESCRIPTION ""
    INDEX { affirmedServiceconstructInterfaceT8InterfaceStatisticsRest-server-allChassis }
        ::= { affirmedServiceconstructInterfaceT8InterfaceStatisticsRest-server-allTable 1 }

AffirmedServiceconstructInterfaceT8InterfaceStatisticsRest-server-allEntry ::=
    SEQUENCE {
        affirmedServiceconstructInterfaceT8InterfaceStatisticsRest-server-allChassis Unsigned32,
        affirmedServiceconstructInterfaceT8InterfaceStatisticsRest-server-allHttpRxPostReq ConfdString,
        affirmedServiceconstructInterfaceT8InterfaceStatisticsRest-server-allHttpRxPost2XXResp ConfdString,
        affirmedServiceconstructInterfaceT8InterfaceStatisticsRest-server-allHttpRxPost3XXResp ConfdString,
        affirmedServiceconstructInterfaceT8InterfaceStatisticsRest-server-allHttpRxPost4XXResp ConfdString,
        affirmedServiceconstructInterfaceT8InterfaceStatisticsRest-server-allHttpRxPost5XXResp ConfdString,
        affirmedServiceconstructInterfaceT8InterfaceStatisticsRest-server-allHttpRxGetReq ConfdString,
        affirmedServiceconstructInterfaceT8InterfaceStatisticsRest-server-allHttpRxGet2XXResp ConfdString,
        affirmedServiceconstructInterfaceT8InterfaceStatisticsRest-server-allHttpRxGet3XXResp ConfdString,
        affirmedServiceconstructInterfaceT8InterfaceStatisticsRest-server-allHttpRxGet4XXResp ConfdString,
        affirmedServiceconstructInterfaceT8InterfaceStatisticsRest-server-allHttpRxGet5XXResp ConfdString,
        affirmedServiceconstructInterfaceT8InterfaceStatisticsRest-server-allHttpRxPutReq ConfdString,
        affirmedServiceconstructInterfaceT8InterfaceStatisticsRest-server-allHttpRxPut2XXResp ConfdString,
        affirmedServiceconstructInterfaceT8InterfaceStatisticsRest-server-allHttpRxPut3XXResp ConfdString,
        affirmedServiceconstructInterfaceT8InterfaceStatisticsRest-server-allHttpRxPut4XXResp ConfdString,
        affirmedServiceconstructInterfaceT8InterfaceStatisticsRest-server-allHttpRxPut5XXResp ConfdString,
        affirmedServiceconstructInterfaceT8InterfaceStatisticsRest-server-allHttpRxPatchReq ConfdString,
        affirmedServiceconstructInterfaceT8InterfaceStatisticsRest-server-allHttpRxPatch2XXResp ConfdString,
        affirmedServiceconstructInterfaceT8InterfaceStatisticsRest-server-allHttpRxPatch3XXResp ConfdString,
        affirmedServiceconstructInterfaceT8InterfaceStatisticsRest-server-allHttpRxPatch4XXResp ConfdString,
        affirmedServiceconstructInterfaceT8InterfaceStatisticsRest-server-allHttpRxPatch5XXResp ConfdString,
        affirmedServiceconstructInterfaceT8InterfaceStatisticsRest-server-allHttpRxDeleteReq ConfdString,
        affirmedServiceconstructInterfaceT8InterfaceStatisticsRest-server-allHttpRxDelete2XXResp ConfdString,
        affirmedServiceconstructInterfaceT8InterfaceStatisticsRest-server-allHttpRxDelete3XXResp ConfdString,
        affirmedServiceconstructInterfaceT8InterfaceStatisticsRest-server-allHttpRxDelete4XXResp ConfdString,
        affirmedServiceconstructInterfaceT8InterfaceStatisticsRest-server-allHttpRxDelete5XXResp ConfdString,
        affirmedServiceconstructInterfaceT8InterfaceStatisticsRest-server-allHttpRxPostNiddConfigReq ConfdString,
        affirmedServiceconstructInterfaceT8InterfaceStatisticsRest-server-allHttpRxPostNiddConfigSuccessResp ConfdString,
        affirmedServiceconstructInterfaceT8InterfaceStatisticsRest-server-allHttpRxPostNiddConfigFailure400 ConfdString,
        affirmedServiceconstructInterfaceT8InterfaceStatisticsRest-server-allHttpRxPostNiddConfigFailure401 ConfdString,
        affirmedServiceconstructInterfaceT8InterfaceStatisticsRest-server-allHttpRxPostNiddConfigFailure403 ConfdString,
        affirmedServiceconstructInterfaceT8InterfaceStatisticsRest-server-allHttpRxPostNiddConfigFailure404 ConfdString,
        affirmedServiceconstructInterfaceT8InterfaceStatisticsRest-server-allHttpRxPostNiddConfigFailure409 ConfdString,
        affirmedServiceconstructInterfaceT8InterfaceStatisticsRest-server-allHttpRxPostNiddConfigFailure412 ConfdString,
        affirmedServiceconstructInterfaceT8InterfaceStatisticsRest-server-allHttpRxPostNiddConfigFailure500 ConfdString,
        affirmedServiceconstructInterfaceT8InterfaceStatisticsRest-server-allHttpRxPostNiddConfigFailure503 ConfdString,
        affirmedServiceconstructInterfaceT8InterfaceStatisticsRest-server-allHttpRxPatchNiddConfigReq ConfdString,
        affirmedServiceconstructInterfaceT8InterfaceStatisticsRest-server-allHttpRxPatchNiddConfigSuccessResp ConfdString,
        affirmedServiceconstructInterfaceT8InterfaceStatisticsRest-server-allHttpRxPatchNiddConfigFailure400 ConfdString,
        affirmedServiceconstructInterfaceT8InterfaceStatisticsRest-server-allHttpRxPatchNiddConfigFailure401 ConfdString,
        affirmedServiceconstructInterfaceT8InterfaceStatisticsRest-server-allHttpRxPatchNiddConfigFailure403 ConfdString,
        affirmedServiceconstructInterfaceT8InterfaceStatisticsRest-server-allHttpRxPatchNiddConfigFailure404 ConfdString,
        affirmedServiceconstructInterfaceT8InterfaceStatisticsRest-server-allHttpRxPatchNiddConfigFailure409 ConfdString,
        affirmedServiceconstructInterfaceT8InterfaceStatisticsRest-server-allHttpRxPatchNiddConfigFailure412 ConfdString,
        affirmedServiceconstructInterfaceT8InterfaceStatisticsRest-server-allHttpRxPatchNiddConfigFailure500 ConfdString,
        affirmedServiceconstructInterfaceT8InterfaceStatisticsRest-server-allHttpRxPatchNiddConfigFailure503 ConfdString,
        affirmedServiceconstructInterfaceT8InterfaceStatisticsRest-server-allHttpRxGetNiddConfigReq ConfdString,
        affirmedServiceconstructInterfaceT8InterfaceStatisticsRest-server-allHttpRxGetNiddConfigSuccessResp ConfdString,
        affirmedServiceconstructInterfaceT8InterfaceStatisticsRest-server-allHttpRxGetNiddConfigFailure400 ConfdString,
        affirmedServiceconstructInterfaceT8InterfaceStatisticsRest-server-allHttpRxGetNiddConfigFailure401 ConfdString,
        affirmedServiceconstructInterfaceT8InterfaceStatisticsRest-server-allHttpRxGetNiddConfigFailure403 ConfdString,
        affirmedServiceconstructInterfaceT8InterfaceStatisticsRest-server-allHttpRxGetNiddConfigFailure404 ConfdString,
        affirmedServiceconstructInterfaceT8InterfaceStatisticsRest-server-allHttpRxGetNiddConfigFailure409 ConfdString,
        affirmedServiceconstructInterfaceT8InterfaceStatisticsRest-server-allHttpRxGetNiddConfigFailure412 ConfdString,
        affirmedServiceconstructInterfaceT8InterfaceStatisticsRest-server-allHttpRxGetNiddConfigFailure500 ConfdString,
        affirmedServiceconstructInterfaceT8InterfaceStatisticsRest-server-allHttpRxGetNiddConfigFailure503 ConfdString,
        affirmedServiceconstructInterfaceT8InterfaceStatisticsRest-server-allHttpRxDeleteNiddConfigReq ConfdString,
        affirmedServiceconstructInterfaceT8InterfaceStatisticsRest-server-allHttpRxDeleteNiddConfigSuccessResp ConfdString,
        affirmedServiceconstructInterfaceT8InterfaceStatisticsRest-server-allHttpRxDeleteNiddConfigFailure400 ConfdString,
        affirmedServiceconstructInterfaceT8InterfaceStatisticsRest-server-allHttpRxDeleteNiddConfigFailure401 ConfdString,
        affirmedServiceconstructInterfaceT8InterfaceStatisticsRest-server-allHttpRxDeleteNiddConfigFailure403 ConfdString,
        affirmedServiceconstructInterfaceT8InterfaceStatisticsRest-server-allHttpRxDeleteNiddConfigFailure404 ConfdString,
        affirmedServiceconstructInterfaceT8InterfaceStatisticsRest-server-allHttpRxDeleteNiddConfigFailure409 ConfdString,
        affirmedServiceconstructInterfaceT8InterfaceStatisticsRest-server-allHttpRxDeleteNiddConfigFailure412 ConfdString,
        affirmedServiceconstructInterfaceT8InterfaceStatisticsRest-server-allHttpRxDeleteNiddConfigFailure500 ConfdString,
        affirmedServiceconstructInterfaceT8InterfaceStatisticsRest-server-allHttpRxDeleteNiddConfigFailure503 ConfdString,
        affirmedServiceconstructInterfaceT8InterfaceStatisticsRest-server-allHttpRxPostNiddDownLinkDataReq ConfdString,
        affirmedServiceconstructInterfaceT8InterfaceStatisticsRest-server-allHttpRxPostNiddDownLinkDataSuccessResp ConfdString,
        affirmedServiceconstructInterfaceT8InterfaceStatisticsRest-server-allHttpRxPostNiddDownLinkDataFailure400 ConfdString,
        affirmedServiceconstructInterfaceT8InterfaceStatisticsRest-server-allHttpRxPostNiddDownLinkDataFailure401 ConfdString,
        affirmedServiceconstructInterfaceT8InterfaceStatisticsRest-server-allHttpRxPostNiddDownLinkDataFailure403 ConfdString,
        affirmedServiceconstructInterfaceT8InterfaceStatisticsRest-server-allHttpRxPostNiddDownLinkDataFailure404 ConfdString,
        affirmedServiceconstructInterfaceT8InterfaceStatisticsRest-server-allHttpRxPostNiddDownLinkDataFailure409 ConfdString,
        affirmedServiceconstructInterfaceT8InterfaceStatisticsRest-server-allHttpRxPostNiddDownLinkDataFailure412 ConfdString,
        affirmedServiceconstructInterfaceT8InterfaceStatisticsRest-server-allHttpRxPostNiddDownLinkDataFailure500 ConfdString,
        affirmedServiceconstructInterfaceT8InterfaceStatisticsRest-server-allHttpRxPostNiddDownLinkDataFailure503 ConfdString,
        affirmedServiceconstructInterfaceT8InterfaceStatisticsRest-server-allHttpRxPutNiddDownLinkDataReq ConfdString,
        affirmedServiceconstructInterfaceT8InterfaceStatisticsRest-server-allHttpRxPutNiddDownLinkDataSuccessResp ConfdString,
        affirmedServiceconstructInterfaceT8InterfaceStatisticsRest-server-allHttpRxPutNiddDownLinkDataFailureResp ConfdString,
        affirmedServiceconstructInterfaceT8InterfaceStatisticsRest-server-allHttpRxGetNiddDownLinkDataReq ConfdString,
        affirmedServiceconstructInterfaceT8InterfaceStatisticsRest-server-allHttpRxGetNiddDownLinkDataSuccessResp ConfdString,
        affirmedServiceconstructInterfaceT8InterfaceStatisticsRest-server-allHttpRxGetNiddDownLinkDataFailure400 ConfdString,
        affirmedServiceconstructInterfaceT8InterfaceStatisticsRest-server-allHttpRxGetNiddDownLinkDataFailure401 ConfdString,
        affirmedServiceconstructInterfaceT8InterfaceStatisticsRest-server-allHttpRxGetNiddDownLinkDataFailure403 ConfdString,
        affirmedServiceconstructInterfaceT8InterfaceStatisticsRest-server-allHttpRxGetNiddDownLinkDataFailure404 ConfdString,
        affirmedServiceconstructInterfaceT8InterfaceStatisticsRest-server-allHttpRxGetNiddDownLinkDataFailure409 ConfdString,
        affirmedServiceconstructInterfaceT8InterfaceStatisticsRest-server-allHttpRxGetNiddDownLinkDataFailure412 ConfdString,
        affirmedServiceconstructInterfaceT8InterfaceStatisticsRest-server-allHttpRxGetNiddDownLinkDataFailure500 ConfdString,
        affirmedServiceconstructInterfaceT8InterfaceStatisticsRest-server-allHttpRxGetNiddDownLinkDataFailure503 ConfdString,
        affirmedServiceconstructInterfaceT8InterfaceStatisticsRest-server-allHttpRxPostMonteEventReq ConfdString,
        affirmedServiceconstructInterfaceT8InterfaceStatisticsRest-server-allHttpRxPostMonteEventSuccessResp ConfdString,
        affirmedServiceconstructInterfaceT8InterfaceStatisticsRest-server-allHttpRxPostMonteEventFailure400 ConfdString,
        affirmedServiceconstructInterfaceT8InterfaceStatisticsRest-server-allHttpRxPostMonteEventFailure401 ConfdString,
        affirmedServiceconstructInterfaceT8InterfaceStatisticsRest-server-allHttpRxPostMonteEventFailure403 ConfdString,
        affirmedServiceconstructInterfaceT8InterfaceStatisticsRest-server-allHttpRxPostMonteEventFailure404 ConfdString,
        affirmedServiceconstructInterfaceT8InterfaceStatisticsRest-server-allHttpRxPostMonteEventFailure409 ConfdString,
        affirmedServiceconstructInterfaceT8InterfaceStatisticsRest-server-allHttpRxPostMonteEventFailure412 ConfdString,
        affirmedServiceconstructInterfaceT8InterfaceStatisticsRest-server-allHttpRxPostMonteEventFailure500 ConfdString,
        affirmedServiceconstructInterfaceT8InterfaceStatisticsRest-server-allHttpRxPostMonteEventFailure503 ConfdString,
        affirmedServiceconstructInterfaceT8InterfaceStatisticsRest-server-allHttpRxPutMonteEventReq ConfdString,
        affirmedServiceconstructInterfaceT8InterfaceStatisticsRest-server-allHttpRxPutMonteEventSuccessResp ConfdString,
        affirmedServiceconstructInterfaceT8InterfaceStatisticsRest-server-allHttpRxPutMonteEventFailure400 ConfdString,
        affirmedServiceconstructInterfaceT8InterfaceStatisticsRest-server-allHttpRxPutMonteEventFailure401 ConfdString,
        affirmedServiceconstructInterfaceT8InterfaceStatisticsRest-server-allHttpRxPutMonteEventFailure403 ConfdString,
        affirmedServiceconstructInterfaceT8InterfaceStatisticsRest-server-allHttpRxPutMonteEventFailure404 ConfdString,
        affirmedServiceconstructInterfaceT8InterfaceStatisticsRest-server-allHttpRxPutMonteEventFailure409 ConfdString,
        affirmedServiceconstructInterfaceT8InterfaceStatisticsRest-server-allHttpRxPutMonteEventFailure412 ConfdString,
        affirmedServiceconstructInterfaceT8InterfaceStatisticsRest-server-allHttpRxPutMonteEventFailure500 ConfdString,
        affirmedServiceconstructInterfaceT8InterfaceStatisticsRest-server-allHttpRxPutMonteEventFailure503 ConfdString,
        affirmedServiceconstructInterfaceT8InterfaceStatisticsRest-server-allHttpRxGetMonteEventReq ConfdString,
        affirmedServiceconstructInterfaceT8InterfaceStatisticsRest-server-allHttpRxGetMonteEventSuccessResp ConfdString,
        affirmedServiceconstructInterfaceT8InterfaceStatisticsRest-server-allHttpRxGetMonteEventFailure400 ConfdString,
        affirmedServiceconstructInterfaceT8InterfaceStatisticsRest-server-allHttpRxGetMonteEventFailure401 ConfdString,
        affirmedServiceconstructInterfaceT8InterfaceStatisticsRest-server-allHttpRxGetMonteEventFailure403 ConfdString,
        affirmedServiceconstructInterfaceT8InterfaceStatisticsRest-server-allHttpRxGetMonteEventFailure404 ConfdString,
        affirmedServiceconstructInterfaceT8InterfaceStatisticsRest-server-allHttpRxGetMonteEventFailure409 ConfdString,
        affirmedServiceconstructInterfaceT8InterfaceStatisticsRest-server-allHttpRxGetMonteEventFailure412 ConfdString,
        affirmedServiceconstructInterfaceT8InterfaceStatisticsRest-server-allHttpRxGetMonteEventFailure500 ConfdString,
        affirmedServiceconstructInterfaceT8InterfaceStatisticsRest-server-allHttpRxGetMonteEventFailure503 ConfdString,
        affirmedServiceconstructInterfaceT8InterfaceStatisticsRest-server-allHttpRxDeleteMonteEventReq ConfdString,
        affirmedServiceconstructInterfaceT8InterfaceStatisticsRest-server-allHttpRxDeleteMonteEventSuccessResp ConfdString,
        affirmedServiceconstructInterfaceT8InterfaceStatisticsRest-server-allHttpRxDeleteMonteEventFailure400 ConfdString,
        affirmedServiceconstructInterfaceT8InterfaceStatisticsRest-server-allHttpRxDeleteMonteEventFailure401 ConfdString,
        affirmedServiceconstructInterfaceT8InterfaceStatisticsRest-server-allHttpRxDeleteMonteEventFailure403 ConfdString,
        affirmedServiceconstructInterfaceT8InterfaceStatisticsRest-server-allHttpRxDeleteMonteEventFailure404 ConfdString,
        affirmedServiceconstructInterfaceT8InterfaceStatisticsRest-server-allHttpRxDeleteMonteEventFailure409 ConfdString,
        affirmedServiceconstructInterfaceT8InterfaceStatisticsRest-server-allHttpRxDeleteMonteEventFailure412 ConfdString,
        affirmedServiceconstructInterfaceT8InterfaceStatisticsRest-server-allHttpRxDeleteMonteEventFailure500 ConfdString,
        affirmedServiceconstructInterfaceT8InterfaceStatisticsRest-server-allHttpRxDeleteMonteEventFailure503 ConfdString,
        affirmedServiceconstructInterfaceT8InterfaceStatisticsRest-server-allHttpRxPostDeviceTriggerReq ConfdString,
        affirmedServiceconstructInterfaceT8InterfaceStatisticsRest-server-allHttpRxPostDeviceTriggerSuccessResp ConfdString,
        affirmedServiceconstructInterfaceT8InterfaceStatisticsRest-server-allHttpRxPostDeviceTriggerFailureResp ConfdString,
        affirmedServiceconstructInterfaceT8InterfaceStatisticsRest-server-allHttpRxPutDeviceTriggerReq ConfdString,
        affirmedServiceconstructInterfaceT8InterfaceStatisticsRest-server-allHttpRxPutDeviceTriggerSuccessResp ConfdString,
        affirmedServiceconstructInterfaceT8InterfaceStatisticsRest-server-allHttpRxPutDeviceTriggerFailureResp ConfdString,
        affirmedServiceconstructInterfaceT8InterfaceStatisticsRest-server-allHttpRxGetDeviceTriggerReq ConfdString,
        affirmedServiceconstructInterfaceT8InterfaceStatisticsRest-server-allHttpRxGetDeviceTriggerSuccessResp ConfdString,
        affirmedServiceconstructInterfaceT8InterfaceStatisticsRest-server-allHttpRxGetDeviceTriggerFailureResp ConfdString,
        affirmedServiceconstructInterfaceT8InterfaceStatisticsRest-server-allHttpRxDeleteDeviceTriggerReq ConfdString,
        affirmedServiceconstructInterfaceT8InterfaceStatisticsRest-server-allHttpRxDeleteDeviceTriggerSuccessResp ConfdString,
        affirmedServiceconstructInterfaceT8InterfaceStatisticsRest-server-allHttpRxDeleteDeviceTriggerFailureResp ConfdString,
        affirmedServiceconstructInterfaceT8InterfaceStatisticsRest-server-allHttpRxGetInvalidRouteReq ConfdString,
        affirmedServiceconstructInterfaceT8InterfaceStatisticsRest-server-allHttpRxGetInvalidRoute2XXResp ConfdString,
        affirmedServiceconstructInterfaceT8InterfaceStatisticsRest-server-allHttpRxGetInvalidRoute3XXResp ConfdString,
        affirmedServiceconstructInterfaceT8InterfaceStatisticsRest-server-allHttpRxGetInvalidRoute4XXResp ConfdString,
        affirmedServiceconstructInterfaceT8InterfaceStatisticsRest-server-allHttpRxGetInvalidRoute5XXResp ConfdString,
        affirmedServiceconstructInterfaceT8InterfaceStatisticsRest-server-allHttpRxGetInvalidResourceReq ConfdString,
        affirmedServiceconstructInterfaceT8InterfaceStatisticsRest-server-allHttpRxGetInvalidResource2XXResp ConfdString,
        affirmedServiceconstructInterfaceT8InterfaceStatisticsRest-server-allHttpRxGetInvalidResource3XXResp ConfdString,
        affirmedServiceconstructInterfaceT8InterfaceStatisticsRest-server-allHttpRxGetInvalidResource4XXResp ConfdString,
        affirmedServiceconstructInterfaceT8InterfaceStatisticsRest-server-allHttpRxGetInvalidResource5XXResp ConfdString,
        affirmedServiceconstructInterfaceT8InterfaceStatisticsRest-server-allHttpRxGetInvalidMethodReq ConfdString,
        affirmedServiceconstructInterfaceT8InterfaceStatisticsRest-server-allHttpRxGetInvalidMethod2XXResp ConfdString,
        affirmedServiceconstructInterfaceT8InterfaceStatisticsRest-server-allHttpRxGetInvalidMethod3XXResp ConfdString,
        affirmedServiceconstructInterfaceT8InterfaceStatisticsRest-server-allHttpRxGetInvalidMethod4XXResp ConfdString,
        affirmedServiceconstructInterfaceT8InterfaceStatisticsRest-server-allHttpRxGetInvalidMethod5XXResp ConfdString,
        affirmedServiceconstructInterfaceT8InterfaceStatisticsRest-server-allHttpRxGetParseErrorReq ConfdString,
        affirmedServiceconstructInterfaceT8InterfaceStatisticsRest-server-allHttpRxGetParseError2XXResp ConfdString,
        affirmedServiceconstructInterfaceT8InterfaceStatisticsRest-server-allHttpRxGetParseError3XXResp ConfdString,
        affirmedServiceconstructInterfaceT8InterfaceStatisticsRest-server-allHttpRxGetParseError4XXResp ConfdString,
        affirmedServiceconstructInterfaceT8InterfaceStatisticsRest-server-allHttpRxGetParseError5XXResp ConfdString,
        affirmedServiceconstructInterfaceT8InterfaceStatisticsRest-server-allHttpRxGetBadContentReq ConfdString,
        affirmedServiceconstructInterfaceT8InterfaceStatisticsRest-server-allHttpRxGetBadContent2XXResp ConfdString,
        affirmedServiceconstructInterfaceT8InterfaceStatisticsRest-server-allHttpRxGetBadContent3XXResp ConfdString,
        affirmedServiceconstructInterfaceT8InterfaceStatisticsRest-server-allHttpRxGetBadContent4XXResp ConfdString,
        affirmedServiceconstructInterfaceT8InterfaceStatisticsRest-server-allHttpRxGetBadContent5XXResp ConfdString,
        affirmedServiceconstructInterfaceT8InterfaceStatisticsRest-server-allHttpRxGetBadContentTypeReq ConfdString,
        affirmedServiceconstructInterfaceT8InterfaceStatisticsRest-server-allHttpRxGetBadContentType2XXResp ConfdString,
        affirmedServiceconstructInterfaceT8InterfaceStatisticsRest-server-allHttpRxGetBadContentType3XXResp ConfdString,
        affirmedServiceconstructInterfaceT8InterfaceStatisticsRest-server-allHttpRxGetBadContentType4XXResp ConfdString,
        affirmedServiceconstructInterfaceT8InterfaceStatisticsRest-server-allHttpRxGetBadContentType5XXResp ConfdString,
        affirmedServiceconstructInterfaceT8InterfaceStatisticsRest-server-allHttpRxGetInternalServerErrorReq ConfdString,
        affirmedServiceconstructInterfaceT8InterfaceStatisticsRest-server-allHttpRxGetInternalServerError2XXResp ConfdString,
        affirmedServiceconstructInterfaceT8InterfaceStatisticsRest-server-allHttpRxGetInternalServerError3XXResp ConfdString,
        affirmedServiceconstructInterfaceT8InterfaceStatisticsRest-server-allHttpRxGetInternalServerError4XXResp ConfdString,
        affirmedServiceconstructInterfaceT8InterfaceStatisticsRest-server-allHttpRxGetInternalServerError5XXResp ConfdString,
        affirmedServiceconstructInterfaceT8InterfaceStatisticsRest-server-allHttpRxDeleteNiddDownLinkDataReq ConfdString,
        affirmedServiceconstructInterfaceT8InterfaceStatisticsRest-server-allHttpRxDeleteNiddDownLinkDataSuccessResp ConfdString,
        affirmedServiceconstructInterfaceT8InterfaceStatisticsRest-server-allHttpRxDeleteNiddDownLinkDataFailure400 ConfdString,
        affirmedServiceconstructInterfaceT8InterfaceStatisticsRest-server-allHttpRxDeleteNiddDownLinkDataFailure401 ConfdString,
        affirmedServiceconstructInterfaceT8InterfaceStatisticsRest-server-allHttpRxDeleteNiddDownLinkDataFailure403 ConfdString,
        affirmedServiceconstructInterfaceT8InterfaceStatisticsRest-server-allHttpRxDeleteNiddDownLinkDataFailure404 ConfdString,
        affirmedServiceconstructInterfaceT8InterfaceStatisticsRest-server-allHttpRxDeleteNiddDownLinkDataFailure409 ConfdString,
        affirmedServiceconstructInterfaceT8InterfaceStatisticsRest-server-allHttpRxDeleteNiddDownLinkDataFailure412 ConfdString,
        affirmedServiceconstructInterfaceT8InterfaceStatisticsRest-server-allHttpRxDeleteNiddDownLinkDataFailure500 ConfdString,
        affirmedServiceconstructInterfaceT8InterfaceStatisticsRest-server-allHttpRxDeleteNiddDownLinkDataFailure503 ConfdString,
        affirmedServiceconstructInterfaceT8InterfaceStatisticsRest-server-allHttpRxPutNiddDownLinkDataFailure400 ConfdString,
        affirmedServiceconstructInterfaceT8InterfaceStatisticsRest-server-allHttpRxPutNiddDownLinkDataFailure401 ConfdString,
        affirmedServiceconstructInterfaceT8InterfaceStatisticsRest-server-allHttpRxPutNiddDownLinkDataFailure403 ConfdString,
        affirmedServiceconstructInterfaceT8InterfaceStatisticsRest-server-allHttpRxPutNiddDownLinkDataFailure404 ConfdString,
        affirmedServiceconstructInterfaceT8InterfaceStatisticsRest-server-allHttpRxPutNiddDownLinkDataFailure409 ConfdString,
        affirmedServiceconstructInterfaceT8InterfaceStatisticsRest-server-allHttpRxPutNiddDownLinkDataFailure412 ConfdString,
        affirmedServiceconstructInterfaceT8InterfaceStatisticsRest-server-allHttpRxPutNiddDownLinkDataFailure500 ConfdString,
        affirmedServiceconstructInterfaceT8InterfaceStatisticsRest-server-allHttpRxPutNiddDownLinkDataFailure503 ConfdString
    }

affirmedServiceconstructInterfaceT8InterfaceStatisticsRest-server-allChassis OBJECT-TYPE
    SYNTAX      Unsigned32
    MAX-ACCESS  not-accessible
    STATUS      current
    DESCRIPTION "chassis ID"
    ::= { affirmedServiceconstructInterfaceT8InterfaceStatisticsRest-server-allEntry 1 }

affirmedServiceconstructInterfaceT8InterfaceStatisticsRest-server-allHttpRxPostReq OBJECT-TYPE
    SYNTAX      ConfdString
    MAX-ACCESS  read-only
    STATUS      current
    DESCRIPTION "Total number of HTTP POST requests received"
    ::= { affirmedServiceconstructInterfaceT8InterfaceStatisticsRest-server-allEntry 2 }

affirmedServiceconstructInterfaceT8InterfaceStatisticsRest-server-allHttpRxPost2XXResp OBJECT-TYPE
    SYNTAX      ConfdString
    MAX-ACCESS  read-only
    STATUS      current
    DESCRIPTION "Total number of 2xx responses sent for the received HTTP POST request"
    ::= { affirmedServiceconstructInterfaceT8InterfaceStatisticsRest-server-allEntry 3 }

affirmedServiceconstructInterfaceT8InterfaceStatisticsRest-server-allHttpRxPost3XXResp OBJECT-TYPE
    SYNTAX      ConfdString
    MAX-ACCESS  read-only
    STATUS      current
    DESCRIPTION "Total number of 3xx responses sent for the received HTTP POST request"
    ::= { affirmedServiceconstructInterfaceT8InterfaceStatisticsRest-server-allEntry 4 }

affirmedServiceconstructInterfaceT8InterfaceStatisticsRest-server-allHttpRxPost4XXResp OBJECT-TYPE
    SYNTAX      ConfdString
    MAX-ACCESS  read-only
    STATUS      current
    DESCRIPTION "Total number of 4xx error responses sent for the received HTTP POST request"
    ::= { affirmedServiceconstructInterfaceT8InterfaceStatisticsRest-server-allEntry 5 }

affirmedServiceconstructInterfaceT8InterfaceStatisticsRest-server-allHttpRxPost5XXResp OBJECT-TYPE
    SYNTAX      ConfdString
    MAX-ACCESS  read-only
    STATUS      current
    DESCRIPTION "Total number of 5xx error responses sent for the received HTTP POST request"
    ::= { affirmedServiceconstructInterfaceT8InterfaceStatisticsRest-server-allEntry 6 }

affirmedServiceconstructInterfaceT8InterfaceStatisticsRest-server-allHttpRxGetReq OBJECT-TYPE
    SYNTAX      ConfdString
    MAX-ACCESS  read-only
    STATUS      current
    DESCRIPTION "Total number of HTTP GET requests received"
    ::= { affirmedServiceconstructInterfaceT8InterfaceStatisticsRest-server-allEntry 7 }

affirmedServiceconstructInterfaceT8InterfaceStatisticsRest-server-allHttpRxGet2XXResp OBJECT-TYPE
    SYNTAX      ConfdString
    MAX-ACCESS  read-only
    STATUS      current
    DESCRIPTION "Total number of 2xx responses sent for the received HTTP GET request"
    ::= { affirmedServiceconstructInterfaceT8InterfaceStatisticsRest-server-allEntry 8 }

affirmedServiceconstructInterfaceT8InterfaceStatisticsRest-server-allHttpRxGet3XXResp OBJECT-TYPE
    SYNTAX      ConfdString
    MAX-ACCESS  read-only
    STATUS      current
    DESCRIPTION "Total number of 3xx responses sent for the received HTTP GET request"
    ::= { affirmedServiceconstructInterfaceT8InterfaceStatisticsRest-server-allEntry 9 }

affirmedServiceconstructInterfaceT8InterfaceStatisticsRest-server-allHttpRxGet4XXResp OBJECT-TYPE
    SYNTAX      ConfdString
    MAX-ACCESS  read-only
    STATUS      current
    DESCRIPTION "Total number of 4xx error responses sent for the received HTTP GET request"
    ::= { affirmedServiceconstructInterfaceT8InterfaceStatisticsRest-server-allEntry 10 }

affirmedServiceconstructInterfaceT8InterfaceStatisticsRest-server-allHttpRxGet5XXResp OBJECT-TYPE
    SYNTAX      ConfdString
    MAX-ACCESS  read-only
    STATUS      current
    DESCRIPTION "Total number of 5xx error responses sent for the received HTTP GET request"
    ::= { affirmedServiceconstructInterfaceT8InterfaceStatisticsRest-server-allEntry 11 }

affirmedServiceconstructInterfaceT8InterfaceStatisticsRest-server-allHttpRxPutReq OBJECT-TYPE
    SYNTAX      ConfdString
    MAX-ACCESS  read-only
    STATUS      current
    DESCRIPTION "Total number of HTTP PUT requests received"
    ::= { affirmedServiceconstructInterfaceT8InterfaceStatisticsRest-server-allEntry 12 }

affirmedServiceconstructInterfaceT8InterfaceStatisticsRest-server-allHttpRxPut2XXResp OBJECT-TYPE
    SYNTAX      ConfdString
    MAX-ACCESS  read-only
    STATUS      current
    DESCRIPTION "Total number of 2xx responses sent for the received HTTP PUT request"
    ::= { affirmedServiceconstructInterfaceT8InterfaceStatisticsRest-server-allEntry 13 }

affirmedServiceconstructInterfaceT8InterfaceStatisticsRest-server-allHttpRxPut3XXResp OBJECT-TYPE
    SYNTAX      ConfdString
    MAX-ACCESS  read-only
    STATUS      current
    DESCRIPTION "Total number of 3xx responses sent for the received HTTP PUT request"
    ::= { affirmedServiceconstructInterfaceT8InterfaceStatisticsRest-server-allEntry 14 }

affirmedServiceconstructInterfaceT8InterfaceStatisticsRest-server-allHttpRxPut4XXResp OBJECT-TYPE
    SYNTAX      ConfdString
    MAX-ACCESS  read-only
    STATUS      current
    DESCRIPTION "Total number of 4xx error responses sent for the received HTTP PUT request"
    ::= { affirmedServiceconstructInterfaceT8InterfaceStatisticsRest-server-allEntry 15 }

affirmedServiceconstructInterfaceT8InterfaceStatisticsRest-server-allHttpRxPut5XXResp OBJECT-TYPE
    SYNTAX      ConfdString
    MAX-ACCESS  read-only
    STATUS      current
    DESCRIPTION "Total number of 5xx error responses sent for the received HTTP PUT request"
    ::= { affirmedServiceconstructInterfaceT8InterfaceStatisticsRest-server-allEntry 16 }

affirmedServiceconstructInterfaceT8InterfaceStatisticsRest-server-allHttpRxPatchReq OBJECT-TYPE
    SYNTAX      ConfdString
    MAX-ACCESS  read-only
    STATUS      current
    DESCRIPTION "Total number of HTTP PATCH requests received"
    ::= { affirmedServiceconstructInterfaceT8InterfaceStatisticsRest-server-allEntry 17 }

affirmedServiceconstructInterfaceT8InterfaceStatisticsRest-server-allHttpRxPatch2XXResp OBJECT-TYPE
    SYNTAX      ConfdString
    MAX-ACCESS  read-only
    STATUS      current
    DESCRIPTION "Total number of 2xx responses sent for the received HTTP PATCH request"
    ::= { affirmedServiceconstructInterfaceT8InterfaceStatisticsRest-server-allEntry 18 }

affirmedServiceconstructInterfaceT8InterfaceStatisticsRest-server-allHttpRxPatch3XXResp OBJECT-TYPE
    SYNTAX      ConfdString
    MAX-ACCESS  read-only
    STATUS      current
    DESCRIPTION "Total number of 3xx responses sent for the received HTTP PATCH request"
    ::= { affirmedServiceconstructInterfaceT8InterfaceStatisticsRest-server-allEntry 19 }

affirmedServiceconstructInterfaceT8InterfaceStatisticsRest-server-allHttpRxPatch4XXResp OBJECT-TYPE
    SYNTAX      ConfdString
    MAX-ACCESS  read-only
    STATUS      current
    DESCRIPTION "Total number of 4xx error responses sent for the received HTTP PATCH request"
    ::= { affirmedServiceconstructInterfaceT8InterfaceStatisticsRest-server-allEntry 20 }

affirmedServiceconstructInterfaceT8InterfaceStatisticsRest-server-allHttpRxPatch5XXResp OBJECT-TYPE
    SYNTAX      ConfdString
    MAX-ACCESS  read-only
    STATUS      current
    DESCRIPTION "Total number of 5xx error responses sent for the received HTTP PATCH request"
    ::= { affirmedServiceconstructInterfaceT8InterfaceStatisticsRest-server-allEntry 21 }

affirmedServiceconstructInterfaceT8InterfaceStatisticsRest-server-allHttpRxDeleteReq OBJECT-TYPE
    SYNTAX      ConfdString
    MAX-ACCESS  read-only
    STATUS      current
    DESCRIPTION "Total number of HTTP DELETE requests received"
    ::= { affirmedServiceconstructInterfaceT8InterfaceStatisticsRest-server-allEntry 22 }

affirmedServiceconstructInterfaceT8InterfaceStatisticsRest-server-allHttpRxDelete2XXResp OBJECT-TYPE
    SYNTAX      ConfdString
    MAX-ACCESS  read-only
    STATUS      current
    DESCRIPTION "Total number of 2xx responses sent for the received HTTP DELETE request"
    ::= { affirmedServiceconstructInterfaceT8InterfaceStatisticsRest-server-allEntry 23 }

affirmedServiceconstructInterfaceT8InterfaceStatisticsRest-server-allHttpRxDelete3XXResp OBJECT-TYPE
    SYNTAX      ConfdString
    MAX-ACCESS  read-only
    STATUS      current
    DESCRIPTION "Total number of 3xx responses sent for the received HTTP DELETE request"
    ::= { affirmedServiceconstructInterfaceT8InterfaceStatisticsRest-server-allEntry 24 }

affirmedServiceconstructInterfaceT8InterfaceStatisticsRest-server-allHttpRxDelete4XXResp OBJECT-TYPE
    SYNTAX      ConfdString
    MAX-ACCESS  read-only
    STATUS      current
    DESCRIPTION "Total number of 4xx error responses sent for the received HTTP DELETE request"
    ::= { affirmedServiceconstructInterfaceT8InterfaceStatisticsRest-server-allEntry 25 }

affirmedServiceconstructInterfaceT8InterfaceStatisticsRest-server-allHttpRxDelete5XXResp OBJECT-TYPE
    SYNTAX      ConfdString
    MAX-ACCESS  read-only
    STATUS      current
    DESCRIPTION "Total number of 5xx error responses sent for the received HTTP DELETE request"
    ::= { affirmedServiceconstructInterfaceT8InterfaceStatisticsRest-server-allEntry 26 }

affirmedServiceconstructInterfaceT8InterfaceStatisticsRest-server-allHttpRxPostNiddConfigReq OBJECT-TYPE
    SYNTAX      ConfdString
    MAX-ACCESS  read-only
    STATUS      current
    DESCRIPTION "Total number of NIDD configuration POST requests received"
    ::= { affirmedServiceconstructInterfaceT8InterfaceStatisticsRest-server-allEntry 27 }

affirmedServiceconstructInterfaceT8InterfaceStatisticsRest-server-allHttpRxPostNiddConfigSuccessResp OBJECT-TYPE
    SYNTAX      ConfdString
    MAX-ACCESS  read-only
    STATUS      current
    DESCRIPTION "Total number of NIDD configuration POST requests accepted"
    ::= { affirmedServiceconstructInterfaceT8InterfaceStatisticsRest-server-allEntry 28 }

affirmedServiceconstructInterfaceT8InterfaceStatisticsRest-server-allHttpRxPostNiddConfigFailure400 OBJECT-TYPE
    SYNTAX      ConfdString
    MAX-ACCESS  read-only
    STATUS      current
    DESCRIPTION "Total number of NIDD configuration POST failures - 400 Bad Request"
    ::= { affirmedServiceconstructInterfaceT8InterfaceStatisticsRest-server-allEntry 29 }

affirmedServiceconstructInterfaceT8InterfaceStatisticsRest-server-allHttpRxPostNiddConfigFailure401 OBJECT-TYPE
    SYNTAX      ConfdString
    MAX-ACCESS  read-only
    STATUS      current
    DESCRIPTION "Total number of NIDD configuration POST failures - 401 Unauthorized"
    ::= { affirmedServiceconstructInterfaceT8InterfaceStatisticsRest-server-allEntry 30 }

affirmedServiceconstructInterfaceT8InterfaceStatisticsRest-server-allHttpRxPostNiddConfigFailure403 OBJECT-TYPE
    SYNTAX      ConfdString
    MAX-ACCESS  read-only
    STATUS      current
    DESCRIPTION "Total number of NIDD configuration POST failures - 403 Forbidden"
    ::= { affirmedServiceconstructInterfaceT8InterfaceStatisticsRest-server-allEntry 31 }

affirmedServiceconstructInterfaceT8InterfaceStatisticsRest-server-allHttpRxPostNiddConfigFailure404 OBJECT-TYPE
    SYNTAX      ConfdString
    MAX-ACCESS  read-only
    STATUS      current
    DESCRIPTION "Total number of NIDD configuration POST failures - 404 Not Found"
    ::= { affirmedServiceconstructInterfaceT8InterfaceStatisticsRest-server-allEntry 32 }

affirmedServiceconstructInterfaceT8InterfaceStatisticsRest-server-allHttpRxPostNiddConfigFailure409 OBJECT-TYPE
    SYNTAX      ConfdString
    MAX-ACCESS  read-only
    STATUS      current
    DESCRIPTION "Total number of NIDD configuration POST failures - 409 Conflict"
    ::= { affirmedServiceconstructInterfaceT8InterfaceStatisticsRest-server-allEntry 33 }

affirmedServiceconstructInterfaceT8InterfaceStatisticsRest-server-allHttpRxPostNiddConfigFailure412 OBJECT-TYPE
    SYNTAX      ConfdString
    MAX-ACCESS  read-only
    STATUS      current
    DESCRIPTION "Total number of NIDD configuration POST failures - 412 Precondition Failed"
    ::= { affirmedServiceconstructInterfaceT8InterfaceStatisticsRest-server-allEntry 34 }

affirmedServiceconstructInterfaceT8InterfaceStatisticsRest-server-allHttpRxPostNiddConfigFailure500 OBJECT-TYPE
    SYNTAX      ConfdString
    MAX-ACCESS  read-only
    STATUS      current
    DESCRIPTION "Total number of NIDD configuration POST failures - 500 Internal Server Error"
    ::= { affirmedServiceconstructInterfaceT8InterfaceStatisticsRest-server-allEntry 35 }

affirmedServiceconstructInterfaceT8InterfaceStatisticsRest-server-allHttpRxPostNiddConfigFailure503 OBJECT-TYPE
    SYNTAX      ConfdString
    MAX-ACCESS  read-only
    STATUS      current
    DESCRIPTION "Total number of NIDD configuration POST failures - 503 Service Unavailable"
    ::= { affirmedServiceconstructInterfaceT8InterfaceStatisticsRest-server-allEntry 36 }

affirmedServiceconstructInterfaceT8InterfaceStatisticsRest-server-allHttpRxPatchNiddConfigReq OBJECT-TYPE
    SYNTAX      ConfdString
    MAX-ACCESS  read-only
    STATUS      current
    DESCRIPTION "Total number of NIDD configuration PATCH requests received"
    ::= { affirmedServiceconstructInterfaceT8InterfaceStatisticsRest-server-allEntry 37 }

affirmedServiceconstructInterfaceT8InterfaceStatisticsRest-server-allHttpRxPatchNiddConfigSuccessResp OBJECT-TYPE
    SYNTAX      ConfdString
    MAX-ACCESS  read-only
    STATUS      current
    DESCRIPTION "Total number of NIDD configuration PATCH requests accepted"
    ::= { affirmedServiceconstructInterfaceT8InterfaceStatisticsRest-server-allEntry 38 }

affirmedServiceconstructInterfaceT8InterfaceStatisticsRest-server-allHttpRxPatchNiddConfigFailure400 OBJECT-TYPE
    SYNTAX      ConfdString
    MAX-ACCESS  read-only
    STATUS      current
    DESCRIPTION "Total number of NIDD configuration PATCH failures - 400 Bad Request"
    ::= { affirmedServiceconstructInterfaceT8InterfaceStatisticsRest-server-allEntry 39 }

affirmedServiceconstructInterfaceT8InterfaceStatisticsRest-server-allHttpRxPatchNiddConfigFailure401 OBJECT-TYPE
    SYNTAX      ConfdString
    MAX-ACCESS  read-only
    STATUS      current
    DESCRIPTION "Total number of NIDD configuration PATCH failures - 401 Unauthorized"
    ::= { affirmedServiceconstructInterfaceT8InterfaceStatisticsRest-server-allEntry 40 }

affirmedServiceconstructInterfaceT8InterfaceStatisticsRest-server-allHttpRxPatchNiddConfigFailure403 OBJECT-TYPE
    SYNTAX      ConfdString
    MAX-ACCESS  read-only
    STATUS      current
    DESCRIPTION "Total number of NIDD configuration PATCH failures - 403 Forbidden"
    ::= { affirmedServiceconstructInterfaceT8InterfaceStatisticsRest-server-allEntry 41 }

affirmedServiceconstructInterfaceT8InterfaceStatisticsRest-server-allHttpRxPatchNiddConfigFailure404 OBJECT-TYPE
    SYNTAX      ConfdString
    MAX-ACCESS  read-only
    STATUS      current
    DESCRIPTION "Total number of NIDD configuration PATCH failures - 404 Not Found"
    ::= { affirmedServiceconstructInterfaceT8InterfaceStatisticsRest-server-allEntry 42 }

affirmedServiceconstructInterfaceT8InterfaceStatisticsRest-server-allHttpRxPatchNiddConfigFailure409 OBJECT-TYPE
    SYNTAX      ConfdString
    MAX-ACCESS  read-only
    STATUS      current
    DESCRIPTION "Total number of NIDD configuration PATCH failures - 409 Conflict"
    ::= { affirmedServiceconstructInterfaceT8InterfaceStatisticsRest-server-allEntry 43 }

affirmedServiceconstructInterfaceT8InterfaceStatisticsRest-server-allHttpRxPatchNiddConfigFailure412 OBJECT-TYPE
    SYNTAX      ConfdString
    MAX-ACCESS  read-only
    STATUS      current
    DESCRIPTION "Total number of NIDD configuration PATCH failures - 412 Precondition Failed"
    ::= { affirmedServiceconstructInterfaceT8InterfaceStatisticsRest-server-allEntry 44 }

affirmedServiceconstructInterfaceT8InterfaceStatisticsRest-server-allHttpRxPatchNiddConfigFailure500 OBJECT-TYPE
    SYNTAX      ConfdString
    MAX-ACCESS  read-only
    STATUS      current
    DESCRIPTION "Total number of NIDD configuration PATCH failures - 500 Internal Server Error"
    ::= { affirmedServiceconstructInterfaceT8InterfaceStatisticsRest-server-allEntry 45 }

affirmedServiceconstructInterfaceT8InterfaceStatisticsRest-server-allHttpRxPatchNiddConfigFailure503 OBJECT-TYPE
    SYNTAX      ConfdString
    MAX-ACCESS  read-only
    STATUS      current
    DESCRIPTION "Total number of NIDD configuration PATCH failures - 503 Service Unavailable"
    ::= { affirmedServiceconstructInterfaceT8InterfaceStatisticsRest-server-allEntry 46 }

affirmedServiceconstructInterfaceT8InterfaceStatisticsRest-server-allHttpRxGetNiddConfigReq OBJECT-TYPE
    SYNTAX      ConfdString
    MAX-ACCESS  read-only
    STATUS      current
    DESCRIPTION "Total number of NIDD configuration GET requests received"
    ::= { affirmedServiceconstructInterfaceT8InterfaceStatisticsRest-server-allEntry 47 }

affirmedServiceconstructInterfaceT8InterfaceStatisticsRest-server-allHttpRxGetNiddConfigSuccessResp OBJECT-TYPE
    SYNTAX      ConfdString
    MAX-ACCESS  read-only
    STATUS      current
    DESCRIPTION "Total number of NIDD configuration GET requests accepted"
    ::= { affirmedServiceconstructInterfaceT8InterfaceStatisticsRest-server-allEntry 48 }

affirmedServiceconstructInterfaceT8InterfaceStatisticsRest-server-allHttpRxGetNiddConfigFailure400 OBJECT-TYPE
    SYNTAX      ConfdString
    MAX-ACCESS  read-only
    STATUS      current
    DESCRIPTION "Total number of NIDD configuration GET failures - 400 Bad Request"
    ::= { affirmedServiceconstructInterfaceT8InterfaceStatisticsRest-server-allEntry 49 }

affirmedServiceconstructInterfaceT8InterfaceStatisticsRest-server-allHttpRxGetNiddConfigFailure401 OBJECT-TYPE
    SYNTAX      ConfdString
    MAX-ACCESS  read-only
    STATUS      current
    DESCRIPTION "Total number of NIDD configuration GET failures - 401 Unauthorized"
    ::= { affirmedServiceconstructInterfaceT8InterfaceStatisticsRest-server-allEntry 50 }

affirmedServiceconstructInterfaceT8InterfaceStatisticsRest-server-allHttpRxGetNiddConfigFailure403 OBJECT-TYPE
    SYNTAX      ConfdString
    MAX-ACCESS  read-only
    STATUS      current
    DESCRIPTION "Total number of NIDD configuration GET failures - 403 Forbidden"
    ::= { affirmedServiceconstructInterfaceT8InterfaceStatisticsRest-server-allEntry 51 }

affirmedServiceconstructInterfaceT8InterfaceStatisticsRest-server-allHttpRxGetNiddConfigFailure404 OBJECT-TYPE
    SYNTAX      ConfdString
    MAX-ACCESS  read-only
    STATUS      current
    DESCRIPTION "Total number of NIDD configuration GET failures - 404 Not Found"
    ::= { affirmedServiceconstructInterfaceT8InterfaceStatisticsRest-server-allEntry 52 }

affirmedServiceconstructInterfaceT8InterfaceStatisticsRest-server-allHttpRxGetNiddConfigFailure409 OBJECT-TYPE
    SYNTAX      ConfdString
    MAX-ACCESS  read-only
    STATUS      current
    DESCRIPTION "Total number of NIDD configuration GET failures - 409 Conflict"
    ::= { affirmedServiceconstructInterfaceT8InterfaceStatisticsRest-server-allEntry 53 }

affirmedServiceconstructInterfaceT8InterfaceStatisticsRest-server-allHttpRxGetNiddConfigFailure412 OBJECT-TYPE
    SYNTAX      ConfdString
    MAX-ACCESS  read-only
    STATUS      current
    DESCRIPTION "Total number of NIDD configuration GET failures - 412 Precondition Failed"
    ::= { affirmedServiceconstructInterfaceT8InterfaceStatisticsRest-server-allEntry 54 }

affirmedServiceconstructInterfaceT8InterfaceStatisticsRest-server-allHttpRxGetNiddConfigFailure500 OBJECT-TYPE
    SYNTAX      ConfdString
    MAX-ACCESS  read-only
    STATUS      current
    DESCRIPTION "Total number of NIDD configuration GET failures - 500 Internal Server Error"
    ::= { affirmedServiceconstructInterfaceT8InterfaceStatisticsRest-server-allEntry 55 }

affirmedServiceconstructInterfaceT8InterfaceStatisticsRest-server-allHttpRxGetNiddConfigFailure503 OBJECT-TYPE
    SYNTAX      ConfdString
    MAX-ACCESS  read-only
    STATUS      current
    DESCRIPTION "Total number of NIDD configuration GET failures - 503 Service Unavailable"
    ::= { affirmedServiceconstructInterfaceT8InterfaceStatisticsRest-server-allEntry 56 }

affirmedServiceconstructInterfaceT8InterfaceStatisticsRest-server-allHttpRxDeleteNiddConfigReq OBJECT-TYPE
    SYNTAX      ConfdString
    MAX-ACCESS  read-only
    STATUS      current
    DESCRIPTION "Total number of NIDD configuration DELETE requests received"
    ::= { affirmedServiceconstructInterfaceT8InterfaceStatisticsRest-server-allEntry 57 }

affirmedServiceconstructInterfaceT8InterfaceStatisticsRest-server-allHttpRxDeleteNiddConfigSuccessResp OBJECT-TYPE
    SYNTAX      ConfdString
    MAX-ACCESS  read-only
    STATUS      current
    DESCRIPTION "Total number of NIDD configuration DELETE requests accepted"
    ::= { affirmedServiceconstructInterfaceT8InterfaceStatisticsRest-server-allEntry 58 }

affirmedServiceconstructInterfaceT8InterfaceStatisticsRest-server-allHttpRxDeleteNiddConfigFailure400 OBJECT-TYPE
    SYNTAX      ConfdString
    MAX-ACCESS  read-only
    STATUS      current
    DESCRIPTION "Total number of NIDD configuration DELETE failures - 400 Bad Request"
    ::= { affirmedServiceconstructInterfaceT8InterfaceStatisticsRest-server-allEntry 59 }

affirmedServiceconstructInterfaceT8InterfaceStatisticsRest-server-allHttpRxDeleteNiddConfigFailure401 OBJECT-TYPE
    SYNTAX      ConfdString
    MAX-ACCESS  read-only
    STATUS      current
    DESCRIPTION "Total number of NIDD configuration DELETE failures - 401 Unauthorized"
    ::= { affirmedServiceconstructInterfaceT8InterfaceStatisticsRest-server-allEntry 60 }

affirmedServiceconstructInterfaceT8InterfaceStatisticsRest-server-allHttpRxDeleteNiddConfigFailure403 OBJECT-TYPE
    SYNTAX      ConfdString
    MAX-ACCESS  read-only
    STATUS      current
    DESCRIPTION "Total number of NIDD configuration DELETE failures - 403 Forbidden"
    ::= { affirmedServiceconstructInterfaceT8InterfaceStatisticsRest-server-allEntry 61 }

affirmedServiceconstructInterfaceT8InterfaceStatisticsRest-server-allHttpRxDeleteNiddConfigFailure404 OBJECT-TYPE
    SYNTAX      ConfdString
    MAX-ACCESS  read-only
    STATUS      current
    DESCRIPTION "Total number of NIDD configuration DELETE failures - 404 Not Found"
    ::= { affirmedServiceconstructInterfaceT8InterfaceStatisticsRest-server-allEntry 62 }

affirmedServiceconstructInterfaceT8InterfaceStatisticsRest-server-allHttpRxDeleteNiddConfigFailure409 OBJECT-TYPE
    SYNTAX      ConfdString
    MAX-ACCESS  read-only
    STATUS      current
    DESCRIPTION "Total number of NIDD configuration DELETE failures - 409 Conflict"
    ::= { affirmedServiceconstructInterfaceT8InterfaceStatisticsRest-server-allEntry 63 }

affirmedServiceconstructInterfaceT8InterfaceStatisticsRest-server-allHttpRxDeleteNiddConfigFailure412 OBJECT-TYPE
    SYNTAX      ConfdString
    MAX-ACCESS  read-only
    STATUS      current
    DESCRIPTION "Total number of NIDD configuration DELETE failures - 412 Precondition Failed"
    ::= { affirmedServiceconstructInterfaceT8InterfaceStatisticsRest-server-allEntry 64 }

affirmedServiceconstructInterfaceT8InterfaceStatisticsRest-server-allHttpRxDeleteNiddConfigFailure500 OBJECT-TYPE
    SYNTAX      ConfdString
    MAX-ACCESS  read-only
    STATUS      current
    DESCRIPTION "Total number of NIDD configuration DELETE failures - 500 Internal Server Error"
    ::= { affirmedServiceconstructInterfaceT8InterfaceStatisticsRest-server-allEntry 65 }

affirmedServiceconstructInterfaceT8InterfaceStatisticsRest-server-allHttpRxDeleteNiddConfigFailure503 OBJECT-TYPE
    SYNTAX      ConfdString
    MAX-ACCESS  read-only
    STATUS      current
    DESCRIPTION "Total number of NIDD configuration DELETE failures - 503 Service Unavailable"
    ::= { affirmedServiceconstructInterfaceT8InterfaceStatisticsRest-server-allEntry 66 }

affirmedServiceconstructInterfaceT8InterfaceStatisticsRest-server-allHttpRxPostNiddDownLinkDataReq OBJECT-TYPE
    SYNTAX      ConfdString
    MAX-ACCESS  read-only
    STATUS      current
    DESCRIPTION "Total number of NIDD downlink data delivery POST requests received"
    ::= { affirmedServiceconstructInterfaceT8InterfaceStatisticsRest-server-allEntry 67 }

affirmedServiceconstructInterfaceT8InterfaceStatisticsRest-server-allHttpRxPostNiddDownLinkDataSuccessResp OBJECT-TYPE
    SYNTAX      ConfdString
    MAX-ACCESS  read-only
    STATUS      current
    DESCRIPTION "Total number of NIDD downlink data delivery POST requests accepted"
    ::= { affirmedServiceconstructInterfaceT8InterfaceStatisticsRest-server-allEntry 68 }

affirmedServiceconstructInterfaceT8InterfaceStatisticsRest-server-allHttpRxPostNiddDownLinkDataFailure400 OBJECT-TYPE
    SYNTAX      ConfdString
    MAX-ACCESS  read-only
    STATUS      current
    DESCRIPTION "Total number of NIDD downlink data delivery POST failures - 400 Bad Request"
    ::= { affirmedServiceconstructInterfaceT8InterfaceStatisticsRest-server-allEntry 69 }

affirmedServiceconstructInterfaceT8InterfaceStatisticsRest-server-allHttpRxPostNiddDownLinkDataFailure401 OBJECT-TYPE
    SYNTAX      ConfdString
    MAX-ACCESS  read-only
    STATUS      current
    DESCRIPTION "Total number of NIDD downlink data delivery POST failures - 401 Unauthorized"
    ::= { affirmedServiceconstructInterfaceT8InterfaceStatisticsRest-server-allEntry 70 }

affirmedServiceconstructInterfaceT8InterfaceStatisticsRest-server-allHttpRxPostNiddDownLinkDataFailure403 OBJECT-TYPE
    SYNTAX      ConfdString
    MAX-ACCESS  read-only
    STATUS      current
    DESCRIPTION "Total number of NIDD downlink data delivery POST failures - 403 Forbidden"
    ::= { affirmedServiceconstructInterfaceT8InterfaceStatisticsRest-server-allEntry 71 }

affirmedServiceconstructInterfaceT8InterfaceStatisticsRest-server-allHttpRxPostNiddDownLinkDataFailure404 OBJECT-TYPE
    SYNTAX      ConfdString
    MAX-ACCESS  read-only
    STATUS      current
    DESCRIPTION "Total number of NIDD downlink data delivery POST failures - 404 Not Found"
    ::= { affirmedServiceconstructInterfaceT8InterfaceStatisticsRest-server-allEntry 72 }

affirmedServiceconstructInterfaceT8InterfaceStatisticsRest-server-allHttpRxPostNiddDownLinkDataFailure409 OBJECT-TYPE
    SYNTAX      ConfdString
    MAX-ACCESS  read-only
    STATUS      current
    DESCRIPTION "Total number of NIDD downlink data delivery POST failures - 409 Conflict"
    ::= { affirmedServiceconstructInterfaceT8InterfaceStatisticsRest-server-allEntry 73 }

affirmedServiceconstructInterfaceT8InterfaceStatisticsRest-server-allHttpRxPostNiddDownLinkDataFailure412 OBJECT-TYPE
    SYNTAX      ConfdString
    MAX-ACCESS  read-only
    STATUS      current
    DESCRIPTION "Total number of NIDD downlink data delivery POST failures - 412 Precondition Failed"
    ::= { affirmedServiceconstructInterfaceT8InterfaceStatisticsRest-server-allEntry 74 }

affirmedServiceconstructInterfaceT8InterfaceStatisticsRest-server-allHttpRxPostNiddDownLinkDataFailure500 OBJECT-TYPE
    SYNTAX      ConfdString
    MAX-ACCESS  read-only
    STATUS      current
    DESCRIPTION "Total number of NIDD downlink data delivery POST failures - 500 Internal Server Error"
    ::= { affirmedServiceconstructInterfaceT8InterfaceStatisticsRest-server-allEntry 75 }

affirmedServiceconstructInterfaceT8InterfaceStatisticsRest-server-allHttpRxPostNiddDownLinkDataFailure503 OBJECT-TYPE
    SYNTAX      ConfdString
    MAX-ACCESS  read-only
    STATUS      current
    DESCRIPTION "Total number of NIDD downlink data delivery POST failures - 503 Service Unavailable"
    ::= { affirmedServiceconstructInterfaceT8InterfaceStatisticsRest-server-allEntry 76 }

affirmedServiceconstructInterfaceT8InterfaceStatisticsRest-server-allHttpRxPutNiddDownLinkDataReq OBJECT-TYPE
    SYNTAX      ConfdString
    MAX-ACCESS  read-only
    STATUS      current
    DESCRIPTION "Total number of NIDD downlink data delivery PUT requests received"
    ::= { affirmedServiceconstructInterfaceT8InterfaceStatisticsRest-server-allEntry 77 }

affirmedServiceconstructInterfaceT8InterfaceStatisticsRest-server-allHttpRxPutNiddDownLinkDataSuccessResp OBJECT-TYPE
    SYNTAX      ConfdString
    MAX-ACCESS  read-only
    STATUS      current
    DESCRIPTION "Total number of NIDD downlink data delivery PUT requests accepted"
    ::= { affirmedServiceconstructInterfaceT8InterfaceStatisticsRest-server-allEntry 78 }

affirmedServiceconstructInterfaceT8InterfaceStatisticsRest-server-allHttpRxPutNiddDownLinkDataFailureResp OBJECT-TYPE
    SYNTAX      ConfdString
    MAX-ACCESS  read-only
    STATUS      current
    DESCRIPTION "Total number of NIDD downlink data delivery PUT requests failed"
    ::= { affirmedServiceconstructInterfaceT8InterfaceStatisticsRest-server-allEntry 79 }

affirmedServiceconstructInterfaceT8InterfaceStatisticsRest-server-allHttpRxGetNiddDownLinkDataReq OBJECT-TYPE
    SYNTAX      ConfdString
    MAX-ACCESS  read-only
    STATUS      current
    DESCRIPTION "Total number of NIDD downlink data delivery GET requests received"
    ::= { affirmedServiceconstructInterfaceT8InterfaceStatisticsRest-server-allEntry 80 }

affirmedServiceconstructInterfaceT8InterfaceStatisticsRest-server-allHttpRxGetNiddDownLinkDataSuccessResp OBJECT-TYPE
    SYNTAX      ConfdString
    MAX-ACCESS  read-only
    STATUS      current
    DESCRIPTION "Total number of NIDD downlink data delivery GET requests accepted"
    ::= { affirmedServiceconstructInterfaceT8InterfaceStatisticsRest-server-allEntry 81 }

affirmedServiceconstructInterfaceT8InterfaceStatisticsRest-server-allHttpRxGetNiddDownLinkDataFailure400 OBJECT-TYPE
    SYNTAX      ConfdString
    MAX-ACCESS  read-only
    STATUS      current
    DESCRIPTION "Total number of NIDD downlink data delivery GET failures - 400 Bad Request"
    ::= { affirmedServiceconstructInterfaceT8InterfaceStatisticsRest-server-allEntry 82 }

affirmedServiceconstructInterfaceT8InterfaceStatisticsRest-server-allHttpRxGetNiddDownLinkDataFailure401 OBJECT-TYPE
    SYNTAX      ConfdString
    MAX-ACCESS  read-only
    STATUS      current
    DESCRIPTION "Total number of NIDD downlink data delivery GET failures - 401 Unauthorized"
    ::= { affirmedServiceconstructInterfaceT8InterfaceStatisticsRest-server-allEntry 83 }

affirmedServiceconstructInterfaceT8InterfaceStatisticsRest-server-allHttpRxGetNiddDownLinkDataFailure403 OBJECT-TYPE
    SYNTAX      ConfdString
    MAX-ACCESS  read-only
    STATUS      current
    DESCRIPTION "Total number of NIDD downlink data delivery GET failures - 403 Forbidden"
    ::= { affirmedServiceconstructInterfaceT8InterfaceStatisticsRest-server-allEntry 84 }

affirmedServiceconstructInterfaceT8InterfaceStatisticsRest-server-allHttpRxGetNiddDownLinkDataFailure404 OBJECT-TYPE
    SYNTAX      ConfdString
    MAX-ACCESS  read-only
    STATUS      current
    DESCRIPTION "Total number of NIDD downlink data delivery GET failures - 404 Not Found"
    ::= { affirmedServiceconstructInterfaceT8InterfaceStatisticsRest-server-allEntry 85 }

affirmedServiceconstructInterfaceT8InterfaceStatisticsRest-server-allHttpRxGetNiddDownLinkDataFailure409 OBJECT-TYPE
    SYNTAX      ConfdString
    MAX-ACCESS  read-only
    STATUS      current
    DESCRIPTION "Total number of NIDD downlink data delivery GET failures - 409 Conflict"
    ::= { affirmedServiceconstructInterfaceT8InterfaceStatisticsRest-server-allEntry 86 }

affirmedServiceconstructInterfaceT8InterfaceStatisticsRest-server-allHttpRxGetNiddDownLinkDataFailure412 OBJECT-TYPE
    SYNTAX      ConfdString
    MAX-ACCESS  read-only
    STATUS      current
    DESCRIPTION "Total number of NIDD downlink data delivery GET failures - 412 Precondition Failed"
    ::= { affirmedServiceconstructInterfaceT8InterfaceStatisticsRest-server-allEntry 87 }

affirmedServiceconstructInterfaceT8InterfaceStatisticsRest-server-allHttpRxGetNiddDownLinkDataFailure500 OBJECT-TYPE
    SYNTAX      ConfdString
    MAX-ACCESS  read-only
    STATUS      current
    DESCRIPTION "Total number of NIDD downlink data delivery GET failures - 500 Internal Server Error"
    ::= { affirmedServiceconstructInterfaceT8InterfaceStatisticsRest-server-allEntry 88 }

affirmedServiceconstructInterfaceT8InterfaceStatisticsRest-server-allHttpRxGetNiddDownLinkDataFailure503 OBJECT-TYPE
    SYNTAX      ConfdString
    MAX-ACCESS  read-only
    STATUS      current
    DESCRIPTION "Total number of NIDD downlink data delivery GET failures - 503 Service Unavailable"
    ::= { affirmedServiceconstructInterfaceT8InterfaceStatisticsRest-server-allEntry 89 }

affirmedServiceconstructInterfaceT8InterfaceStatisticsRest-server-allHttpRxPostMonteEventReq OBJECT-TYPE
    SYNTAX      ConfdString
    MAX-ACCESS  read-only
    STATUS      current
    DESCRIPTION "Total number of MONTE event subscriptions POST requests received"
    ::= { affirmedServiceconstructInterfaceT8InterfaceStatisticsRest-server-allEntry 90 }

affirmedServiceconstructInterfaceT8InterfaceStatisticsRest-server-allHttpRxPostMonteEventSuccessResp OBJECT-TYPE
    SYNTAX      ConfdString
    MAX-ACCESS  read-only
    STATUS      current
    DESCRIPTION "Total number of MONTE event subscriptions POST requests accepted"
    ::= { affirmedServiceconstructInterfaceT8InterfaceStatisticsRest-server-allEntry 91 }

affirmedServiceconstructInterfaceT8InterfaceStatisticsRest-server-allHttpRxPostMonteEventFailure400 OBJECT-TYPE
    SYNTAX      ConfdString
    MAX-ACCESS  read-only
    STATUS      current
    DESCRIPTION "Total number of MONTE event subscriptions POST failures - 400 Bad Request"
    ::= { affirmedServiceconstructInterfaceT8InterfaceStatisticsRest-server-allEntry 92 }

affirmedServiceconstructInterfaceT8InterfaceStatisticsRest-server-allHttpRxPostMonteEventFailure401 OBJECT-TYPE
    SYNTAX      ConfdString
    MAX-ACCESS  read-only
    STATUS      current
    DESCRIPTION "Total number of MONTE event subscriptions POST failures - 401 Unauthorized"
    ::= { affirmedServiceconstructInterfaceT8InterfaceStatisticsRest-server-allEntry 93 }

affirmedServiceconstructInterfaceT8InterfaceStatisticsRest-server-allHttpRxPostMonteEventFailure403 OBJECT-TYPE
    SYNTAX      ConfdString
    MAX-ACCESS  read-only
    STATUS      current
    DESCRIPTION "Total number of MONTE event subscriptions POST failures - 403 Forbidden"
    ::= { affirmedServiceconstructInterfaceT8InterfaceStatisticsRest-server-allEntry 94 }

affirmedServiceconstructInterfaceT8InterfaceStatisticsRest-server-allHttpRxPostMonteEventFailure404 OBJECT-TYPE
    SYNTAX      ConfdString
    MAX-ACCESS  read-only
    STATUS      current
    DESCRIPTION "Total number of MONTE event subscriptions POST failures - 404 Not Found"
    ::= { affirmedServiceconstructInterfaceT8InterfaceStatisticsRest-server-allEntry 95 }

affirmedServiceconstructInterfaceT8InterfaceStatisticsRest-server-allHttpRxPostMonteEventFailure409 OBJECT-TYPE
    SYNTAX      ConfdString
    MAX-ACCESS  read-only
    STATUS      current
    DESCRIPTION "Total number of MONTE event subscriptions POST failures - 409 Conflict"
    ::= { affirmedServiceconstructInterfaceT8InterfaceStatisticsRest-server-allEntry 96 }

affirmedServiceconstructInterfaceT8InterfaceStatisticsRest-server-allHttpRxPostMonteEventFailure412 OBJECT-TYPE
    SYNTAX      ConfdString
    MAX-ACCESS  read-only
    STATUS      current
    DESCRIPTION "Total number of MONTE event subscriptions POST failures - 412 Precondition Failed"
    ::= { affirmedServiceconstructInterfaceT8InterfaceStatisticsRest-server-allEntry 97 }

affirmedServiceconstructInterfaceT8InterfaceStatisticsRest-server-allHttpRxPostMonteEventFailure500 OBJECT-TYPE
    SYNTAX      ConfdString
    MAX-ACCESS  read-only
    STATUS      current
    DESCRIPTION "Total number of MONTE event subscriptions POST failures - 500 Internal Server Error"
    ::= { affirmedServiceconstructInterfaceT8InterfaceStatisticsRest-server-allEntry 98 }

affirmedServiceconstructInterfaceT8InterfaceStatisticsRest-server-allHttpRxPostMonteEventFailure503 OBJECT-TYPE
    SYNTAX      ConfdString
    MAX-ACCESS  read-only
    STATUS      current
    DESCRIPTION "Total number of MONTE event subscriptions POST failures - 503 Service Unavailable"
    ::= { affirmedServiceconstructInterfaceT8InterfaceStatisticsRest-server-allEntry 99 }

affirmedServiceconstructInterfaceT8InterfaceStatisticsRest-server-allHttpRxPutMonteEventReq OBJECT-TYPE
    SYNTAX      ConfdString
    MAX-ACCESS  read-only
    STATUS      current
    DESCRIPTION "Total number of MONTE event subscriptions PUT requests received"
    ::= { affirmedServiceconstructInterfaceT8InterfaceStatisticsRest-server-allEntry 100 }

affirmedServiceconstructInterfaceT8InterfaceStatisticsRest-server-allHttpRxPutMonteEventSuccessResp OBJECT-TYPE
    SYNTAX      ConfdString
    MAX-ACCESS  read-only
    STATUS      current
    DESCRIPTION "Total number of MONTE event subscriptions PUT requests accepted"
    ::= { affirmedServiceconstructInterfaceT8InterfaceStatisticsRest-server-allEntry 101 }

affirmedServiceconstructInterfaceT8InterfaceStatisticsRest-server-allHttpRxPutMonteEventFailure400 OBJECT-TYPE
    SYNTAX      ConfdString
    MAX-ACCESS  read-only
    STATUS      current
    DESCRIPTION "Total number of MONTE event subscriptions PUT failures - 400 Bad Request"
    ::= { affirmedServiceconstructInterfaceT8InterfaceStatisticsRest-server-allEntry 102 }

affirmedServiceconstructInterfaceT8InterfaceStatisticsRest-server-allHttpRxPutMonteEventFailure401 OBJECT-TYPE
    SYNTAX      ConfdString
    MAX-ACCESS  read-only
    STATUS      current
    DESCRIPTION "Total number of MONTE event subscriptions PUT failures - 401 Unauthorized"
    ::= { affirmedServiceconstructInterfaceT8InterfaceStatisticsRest-server-allEntry 103 }

affirmedServiceconstructInterfaceT8InterfaceStatisticsRest-server-allHttpRxPutMonteEventFailure403 OBJECT-TYPE
    SYNTAX      ConfdString
    MAX-ACCESS  read-only
    STATUS      current
    DESCRIPTION "Total number of MONTE event subscriptions PUT failures - 403 Forbidden"
    ::= { affirmedServiceconstructInterfaceT8InterfaceStatisticsRest-server-allEntry 104 }

affirmedServiceconstructInterfaceT8InterfaceStatisticsRest-server-allHttpRxPutMonteEventFailure404 OBJECT-TYPE
    SYNTAX      ConfdString
    MAX-ACCESS  read-only
    STATUS      current
    DESCRIPTION "Total number of MONTE event subscriptions PUT failures - 404 Not Found"
    ::= { affirmedServiceconstructInterfaceT8InterfaceStatisticsRest-server-allEntry 105 }

affirmedServiceconstructInterfaceT8InterfaceStatisticsRest-server-allHttpRxPutMonteEventFailure409 OBJECT-TYPE
    SYNTAX      ConfdString
    MAX-ACCESS  read-only
    STATUS      current
    DESCRIPTION "Total number of MONTE event subscriptions PUT failures - 409 Conflict"
    ::= { affirmedServiceconstructInterfaceT8InterfaceStatisticsRest-server-allEntry 106 }

affirmedServiceconstructInterfaceT8InterfaceStatisticsRest-server-allHttpRxPutMonteEventFailure412 OBJECT-TYPE
    SYNTAX      ConfdString
    MAX-ACCESS  read-only
    STATUS      current
    DESCRIPTION "Total number of MONTE event subscriptions PUT failures - 412 Precondition Failed"
    ::= { affirmedServiceconstructInterfaceT8InterfaceStatisticsRest-server-allEntry 107 }

affirmedServiceconstructInterfaceT8InterfaceStatisticsRest-server-allHttpRxPutMonteEventFailure500 OBJECT-TYPE
    SYNTAX      ConfdString
    MAX-ACCESS  read-only
    STATUS      current
    DESCRIPTION "Total number of MONTE event subscriptions PUT failures - 500 Internal Server Error"
    ::= { affirmedServiceconstructInterfaceT8InterfaceStatisticsRest-server-allEntry 108 }

affirmedServiceconstructInterfaceT8InterfaceStatisticsRest-server-allHttpRxPutMonteEventFailure503 OBJECT-TYPE
    SYNTAX      ConfdString
    MAX-ACCESS  read-only
    STATUS      current
    DESCRIPTION "Total number of MONTE event subscriptions PUT failures - 503 Service Unavailable"
    ::= { affirmedServiceconstructInterfaceT8InterfaceStatisticsRest-server-allEntry 109 }

affirmedServiceconstructInterfaceT8InterfaceStatisticsRest-server-allHttpRxGetMonteEventReq OBJECT-TYPE
    SYNTAX      ConfdString
    MAX-ACCESS  read-only
    STATUS      current
    DESCRIPTION "Total number of MONTE event subscriptions GET requests received"
    ::= { affirmedServiceconstructInterfaceT8InterfaceStatisticsRest-server-allEntry 110 }

affirmedServiceconstructInterfaceT8InterfaceStatisticsRest-server-allHttpRxGetMonteEventSuccessResp OBJECT-TYPE
    SYNTAX      ConfdString
    MAX-ACCESS  read-only
    STATUS      current
    DESCRIPTION "Total number of MONTE event subscriptions GET requests accepted"
    ::= { affirmedServiceconstructInterfaceT8InterfaceStatisticsRest-server-allEntry 111 }

affirmedServiceconstructInterfaceT8InterfaceStatisticsRest-server-allHttpRxGetMonteEventFailure400 OBJECT-TYPE
    SYNTAX      ConfdString
    MAX-ACCESS  read-only
    STATUS      current
    DESCRIPTION "Total number of MONTE event subscriptions GET failures - 400 Bad Request"
    ::= { affirmedServiceconstructInterfaceT8InterfaceStatisticsRest-server-allEntry 112 }

affirmedServiceconstructInterfaceT8InterfaceStatisticsRest-server-allHttpRxGetMonteEventFailure401 OBJECT-TYPE
    SYNTAX      ConfdString
    MAX-ACCESS  read-only
    STATUS      current
    DESCRIPTION "Total number of MONTE event subscriptions GET failures - 401 Unauthorized"
    ::= { affirmedServiceconstructInterfaceT8InterfaceStatisticsRest-server-allEntry 113 }

affirmedServiceconstructInterfaceT8InterfaceStatisticsRest-server-allHttpRxGetMonteEventFailure403 OBJECT-TYPE
    SYNTAX      ConfdString
    MAX-ACCESS  read-only
    STATUS      current
    DESCRIPTION "Total number of MONTE event subscriptions GET failures - 403 Forbidden"
    ::= { affirmedServiceconstructInterfaceT8InterfaceStatisticsRest-server-allEntry 114 }

affirmedServiceconstructInterfaceT8InterfaceStatisticsRest-server-allHttpRxGetMonteEventFailure404 OBJECT-TYPE
    SYNTAX      ConfdString
    MAX-ACCESS  read-only
    STATUS      current
    DESCRIPTION "Total number of MONTE event subscriptions GET failures - 404 Not Found"
    ::= { affirmedServiceconstructInterfaceT8InterfaceStatisticsRest-server-allEntry 115 }

affirmedServiceconstructInterfaceT8InterfaceStatisticsRest-server-allHttpRxGetMonteEventFailure409 OBJECT-TYPE
    SYNTAX      ConfdString
    MAX-ACCESS  read-only
    STATUS      current
    DESCRIPTION "Total number of MONTE event subscriptions GET failures - 409 Conflict"
    ::= { affirmedServiceconstructInterfaceT8InterfaceStatisticsRest-server-allEntry 116 }

affirmedServiceconstructInterfaceT8InterfaceStatisticsRest-server-allHttpRxGetMonteEventFailure412 OBJECT-TYPE
    SYNTAX      ConfdString
    MAX-ACCESS  read-only
    STATUS      current
    DESCRIPTION "Total number of MONTE event subscriptions GET failures - 412 Precondition Failed"
    ::= { affirmedServiceconstructInterfaceT8InterfaceStatisticsRest-server-allEntry 117 }

affirmedServiceconstructInterfaceT8InterfaceStatisticsRest-server-allHttpRxGetMonteEventFailure500 OBJECT-TYPE
    SYNTAX      ConfdString
    MAX-ACCESS  read-only
    STATUS      current
    DESCRIPTION "Total number of MONTE event subscriptions GET failures - 500 Internal Server Error"
    ::= { affirmedServiceconstructInterfaceT8InterfaceStatisticsRest-server-allEntry 118 }

affirmedServiceconstructInterfaceT8InterfaceStatisticsRest-server-allHttpRxGetMonteEventFailure503 OBJECT-TYPE
    SYNTAX      ConfdString
    MAX-ACCESS  read-only
    STATUS      current
    DESCRIPTION "Total number of MONTE event subscriptions GET failures - 503 Service Unavailable"
    ::= { affirmedServiceconstructInterfaceT8InterfaceStatisticsRest-server-allEntry 119 }

affirmedServiceconstructInterfaceT8InterfaceStatisticsRest-server-allHttpRxDeleteMonteEventReq OBJECT-TYPE
    SYNTAX      ConfdString
    MAX-ACCESS  read-only
    STATUS      current
    DESCRIPTION "Total number of MONTE event subscriptions DELETE requests received"
    ::= { affirmedServiceconstructInterfaceT8InterfaceStatisticsRest-server-allEntry 120 }

affirmedServiceconstructInterfaceT8InterfaceStatisticsRest-server-allHttpRxDeleteMonteEventSuccessResp OBJECT-TYPE
    SYNTAX      ConfdString
    MAX-ACCESS  read-only
    STATUS      current
    DESCRIPTION "Total number of MONTE event subscriptions DELETE requests accepted"
    ::= { affirmedServiceconstructInterfaceT8InterfaceStatisticsRest-server-allEntry 121 }

affirmedServiceconstructInterfaceT8InterfaceStatisticsRest-server-allHttpRxDeleteMonteEventFailure400 OBJECT-TYPE
    SYNTAX      ConfdString
    MAX-ACCESS  read-only
    STATUS      current
    DESCRIPTION "Total number of MONTE event subscriptions DELETE failures - 400 Bad Request"
    ::= { affirmedServiceconstructInterfaceT8InterfaceStatisticsRest-server-allEntry 122 }

affirmedServiceconstructInterfaceT8InterfaceStatisticsRest-server-allHttpRxDeleteMonteEventFailure401 OBJECT-TYPE
    SYNTAX      ConfdString
    MAX-ACCESS  read-only
    STATUS      current
    DESCRIPTION "Total number of MONTE event subscriptions DELETE failures - 401 Unauthorized"
    ::= { affirmedServiceconstructInterfaceT8InterfaceStatisticsRest-server-allEntry 123 }

affirmedServiceconstructInterfaceT8InterfaceStatisticsRest-server-allHttpRxDeleteMonteEventFailure403 OBJECT-TYPE
    SYNTAX      ConfdString
    MAX-ACCESS  read-only
    STATUS      current
    DESCRIPTION "Total number of MONTE event subscriptions DELETE failures - 403 Forbidden"
    ::= { affirmedServiceconstructInterfaceT8InterfaceStatisticsRest-server-allEntry 124 }

affirmedServiceconstructInterfaceT8InterfaceStatisticsRest-server-allHttpRxDeleteMonteEventFailure404 OBJECT-TYPE
    SYNTAX      ConfdString
    MAX-ACCESS  read-only
    STATUS      current
    DESCRIPTION "Total number of MONTE event subscriptions DELETE failures - 404 Not Found"
    ::= { affirmedServiceconstructInterfaceT8InterfaceStatisticsRest-server-allEntry 125 }

affirmedServiceconstructInterfaceT8InterfaceStatisticsRest-server-allHttpRxDeleteMonteEventFailure409 OBJECT-TYPE
    SYNTAX      ConfdString
    MAX-ACCESS  read-only
    STATUS      current
    DESCRIPTION "Total number of MONTE event subscriptions DELETE failures - 409 Conflict"
    ::= { affirmedServiceconstructInterfaceT8InterfaceStatisticsRest-server-allEntry 126 }

affirmedServiceconstructInterfaceT8InterfaceStatisticsRest-server-allHttpRxDeleteMonteEventFailure412 OBJECT-TYPE
    SYNTAX      ConfdString
    MAX-ACCESS  read-only
    STATUS      current
    DESCRIPTION "Total number of MONTE event subscriptions DELETE failures - 412 Precondition Failed"
    ::= { affirmedServiceconstructInterfaceT8InterfaceStatisticsRest-server-allEntry 127 }

affirmedServiceconstructInterfaceT8InterfaceStatisticsRest-server-allHttpRxDeleteMonteEventFailure500 OBJECT-TYPE
    SYNTAX      ConfdString
    MAX-ACCESS  read-only
    STATUS      current
    DESCRIPTION "Total number of MONTE event subscriptions DELETE failures - 500 Internal Server Error"
    ::= { affirmedServiceconstructInterfaceT8InterfaceStatisticsRest-server-allEntry 128 }

affirmedServiceconstructInterfaceT8InterfaceStatisticsRest-server-allHttpRxDeleteMonteEventFailure503 OBJECT-TYPE
    SYNTAX      ConfdString
    MAX-ACCESS  read-only
    STATUS      current
    DESCRIPTION "Total number of MONTE event subscriptions DELETE failures - 503 Service Unavailable"
    ::= { affirmedServiceconstructInterfaceT8InterfaceStatisticsRest-server-allEntry 129 }

affirmedServiceconstructInterfaceT8InterfaceStatisticsRest-server-allHttpRxPostDeviceTriggerReq OBJECT-TYPE
    SYNTAX      ConfdString
    MAX-ACCESS  read-only
    STATUS      current
    DESCRIPTION "Total number of Device Triggering transaction POST requests received"
    ::= { affirmedServiceconstructInterfaceT8InterfaceStatisticsRest-server-allEntry 130 }

affirmedServiceconstructInterfaceT8InterfaceStatisticsRest-server-allHttpRxPostDeviceTriggerSuccessResp OBJECT-TYPE
    SYNTAX      ConfdString
    MAX-ACCESS  read-only
    STATUS      current
    DESCRIPTION "Total number of Device Triggering transaction POST requests accepted"
    ::= { affirmedServiceconstructInterfaceT8InterfaceStatisticsRest-server-allEntry 131 }

affirmedServiceconstructInterfaceT8InterfaceStatisticsRest-server-allHttpRxPostDeviceTriggerFailureResp OBJECT-TYPE
    SYNTAX      ConfdString
    MAX-ACCESS  read-only
    STATUS      current
    DESCRIPTION "Total number of Device Triggering transaction POST requests failed"
    ::= { affirmedServiceconstructInterfaceT8InterfaceStatisticsRest-server-allEntry 132 }

affirmedServiceconstructInterfaceT8InterfaceStatisticsRest-server-allHttpRxPutDeviceTriggerReq OBJECT-TYPE
    SYNTAX      ConfdString
    MAX-ACCESS  read-only
    STATUS      current
    DESCRIPTION "Total number of Device Triggering transaction PUT requests received"
    ::= { affirmedServiceconstructInterfaceT8InterfaceStatisticsRest-server-allEntry 133 }

affirmedServiceconstructInterfaceT8InterfaceStatisticsRest-server-allHttpRxPutDeviceTriggerSuccessResp OBJECT-TYPE
    SYNTAX      ConfdString
    MAX-ACCESS  read-only
    STATUS      current
    DESCRIPTION "Total number of Device Triggering transaction PUT requests accepted"
    ::= { affirmedServiceconstructInterfaceT8InterfaceStatisticsRest-server-allEntry 134 }

affirmedServiceconstructInterfaceT8InterfaceStatisticsRest-server-allHttpRxPutDeviceTriggerFailureResp OBJECT-TYPE
    SYNTAX      ConfdString
    MAX-ACCESS  read-only
    STATUS      current
    DESCRIPTION "Total number of Device Triggering transaction PUT requests failed"
    ::= { affirmedServiceconstructInterfaceT8InterfaceStatisticsRest-server-allEntry 135 }

affirmedServiceconstructInterfaceT8InterfaceStatisticsRest-server-allHttpRxGetDeviceTriggerReq OBJECT-TYPE
    SYNTAX      ConfdString
    MAX-ACCESS  read-only
    STATUS      current
    DESCRIPTION "Total number of Device Triggering transaction GET requests received"
    ::= { affirmedServiceconstructInterfaceT8InterfaceStatisticsRest-server-allEntry 136 }

affirmedServiceconstructInterfaceT8InterfaceStatisticsRest-server-allHttpRxGetDeviceTriggerSuccessResp OBJECT-TYPE
    SYNTAX      ConfdString
    MAX-ACCESS  read-only
    STATUS      current
    DESCRIPTION "Total number of Device Triggering transaction GET requests accepted"
    ::= { affirmedServiceconstructInterfaceT8InterfaceStatisticsRest-server-allEntry 137 }

affirmedServiceconstructInterfaceT8InterfaceStatisticsRest-server-allHttpRxGetDeviceTriggerFailureResp OBJECT-TYPE
    SYNTAX      ConfdString
    MAX-ACCESS  read-only
    STATUS      current
    DESCRIPTION "Total number of Device Triggering transaction GET requests failed"
    ::= { affirmedServiceconstructInterfaceT8InterfaceStatisticsRest-server-allEntry 138 }

affirmedServiceconstructInterfaceT8InterfaceStatisticsRest-server-allHttpRxDeleteDeviceTriggerReq OBJECT-TYPE
    SYNTAX      ConfdString
    MAX-ACCESS  read-only
    STATUS      current
    DESCRIPTION "Total number of Device Triggering transaction DELETE requests received"
    ::= { affirmedServiceconstructInterfaceT8InterfaceStatisticsRest-server-allEntry 139 }

affirmedServiceconstructInterfaceT8InterfaceStatisticsRest-server-allHttpRxDeleteDeviceTriggerSuccessResp OBJECT-TYPE
    SYNTAX      ConfdString
    MAX-ACCESS  read-only
    STATUS      current
    DESCRIPTION "Total number of Device Triggering transaction DELETE requests accepted"
    ::= { affirmedServiceconstructInterfaceT8InterfaceStatisticsRest-server-allEntry 140 }

affirmedServiceconstructInterfaceT8InterfaceStatisticsRest-server-allHttpRxDeleteDeviceTriggerFailureResp OBJECT-TYPE
    SYNTAX      ConfdString
    MAX-ACCESS  read-only
    STATUS      current
    DESCRIPTION "Total number of Device Triggering transaction DELETE requests failed"
    ::= { affirmedServiceconstructInterfaceT8InterfaceStatisticsRest-server-allEntry 141 }

affirmedServiceconstructInterfaceT8InterfaceStatisticsRest-server-allHttpRxGetInvalidRouteReq OBJECT-TYPE
    SYNTAX      ConfdString
    MAX-ACCESS  read-only
    STATUS      current
    DESCRIPTION "Total number of Invalid Route GET requests received"
    ::= { affirmedServiceconstructInterfaceT8InterfaceStatisticsRest-server-allEntry 142 }

affirmedServiceconstructInterfaceT8InterfaceStatisticsRest-server-allHttpRxGetInvalidRoute2XXResp OBJECT-TYPE
    SYNTAX      ConfdString
    MAX-ACCESS  read-only
    STATUS      current
    DESCRIPTION "Total number of Invalid Route GET responses - 2XX Success"
    ::= { affirmedServiceconstructInterfaceT8InterfaceStatisticsRest-server-allEntry 143 }

affirmedServiceconstructInterfaceT8InterfaceStatisticsRest-server-allHttpRxGetInvalidRoute3XXResp OBJECT-TYPE
    SYNTAX      ConfdString
    MAX-ACCESS  read-only
    STATUS      current
    DESCRIPTION "Total number of Invalid Route GET failures - 3XX Responses"
    ::= { affirmedServiceconstructInterfaceT8InterfaceStatisticsRest-server-allEntry 144 }

affirmedServiceconstructInterfaceT8InterfaceStatisticsRest-server-allHttpRxGetInvalidRoute4XXResp OBJECT-TYPE
    SYNTAX      ConfdString
    MAX-ACCESS  read-only
    STATUS      current
    DESCRIPTION "Total number of Invalid Route GET failures - 4XX Failures"
    ::= { affirmedServiceconstructInterfaceT8InterfaceStatisticsRest-server-allEntry 145 }

affirmedServiceconstructInterfaceT8InterfaceStatisticsRest-server-allHttpRxGetInvalidRoute5XXResp OBJECT-TYPE
    SYNTAX      ConfdString
    MAX-ACCESS  read-only
    STATUS      current
    DESCRIPTION "Total number of Invalid Route GET failures - 5XX Failures"
    ::= { affirmedServiceconstructInterfaceT8InterfaceStatisticsRest-server-allEntry 146 }

affirmedServiceconstructInterfaceT8InterfaceStatisticsRest-server-allHttpRxGetInvalidResourceReq OBJECT-TYPE
    SYNTAX      ConfdString
    MAX-ACCESS  read-only
    STATUS      current
    DESCRIPTION "Total number of Invalid Resource GET requests received"
    ::= { affirmedServiceconstructInterfaceT8InterfaceStatisticsRest-server-allEntry 147 }

affirmedServiceconstructInterfaceT8InterfaceStatisticsRest-server-allHttpRxGetInvalidResource2XXResp OBJECT-TYPE
    SYNTAX      ConfdString
    MAX-ACCESS  read-only
    STATUS      current
    DESCRIPTION "Total number of Invalid Resource GET responses - 2XX Success"
    ::= { affirmedServiceconstructInterfaceT8InterfaceStatisticsRest-server-allEntry 148 }

affirmedServiceconstructInterfaceT8InterfaceStatisticsRest-server-allHttpRxGetInvalidResource3XXResp OBJECT-TYPE
    SYNTAX      ConfdString
    MAX-ACCESS  read-only
    STATUS      current
    DESCRIPTION "Total number of Invalid Resource GET failures - 3XX Responses"
    ::= { affirmedServiceconstructInterfaceT8InterfaceStatisticsRest-server-allEntry 149 }

affirmedServiceconstructInterfaceT8InterfaceStatisticsRest-server-allHttpRxGetInvalidResource4XXResp OBJECT-TYPE
    SYNTAX      ConfdString
    MAX-ACCESS  read-only
    STATUS      current
    DESCRIPTION "Total number of Invalid Resource GET failures - 4XX Failures"
    ::= { affirmedServiceconstructInterfaceT8InterfaceStatisticsRest-server-allEntry 150 }

affirmedServiceconstructInterfaceT8InterfaceStatisticsRest-server-allHttpRxGetInvalidResource5XXResp OBJECT-TYPE
    SYNTAX      ConfdString
    MAX-ACCESS  read-only
    STATUS      current
    DESCRIPTION "Total number of Invalid Resource GET failures - 5XX Failures"
    ::= { affirmedServiceconstructInterfaceT8InterfaceStatisticsRest-server-allEntry 151 }

affirmedServiceconstructInterfaceT8InterfaceStatisticsRest-server-allHttpRxGetInvalidMethodReq OBJECT-TYPE
    SYNTAX      ConfdString
    MAX-ACCESS  read-only
    STATUS      current
    DESCRIPTION "Total number of Invalid Method GET requests received"
    ::= { affirmedServiceconstructInterfaceT8InterfaceStatisticsRest-server-allEntry 152 }

affirmedServiceconstructInterfaceT8InterfaceStatisticsRest-server-allHttpRxGetInvalidMethod2XXResp OBJECT-TYPE
    SYNTAX      ConfdString
    MAX-ACCESS  read-only
    STATUS      current
    DESCRIPTION "Total number of Invalid Method GET responses - 2XX Success"
    ::= { affirmedServiceconstructInterfaceT8InterfaceStatisticsRest-server-allEntry 153 }

affirmedServiceconstructInterfaceT8InterfaceStatisticsRest-server-allHttpRxGetInvalidMethod3XXResp OBJECT-TYPE
    SYNTAX      ConfdString
    MAX-ACCESS  read-only
    STATUS      current
    DESCRIPTION "Total number of Invalid Method GET failures - 3XX Responses"
    ::= { affirmedServiceconstructInterfaceT8InterfaceStatisticsRest-server-allEntry 154 }

affirmedServiceconstructInterfaceT8InterfaceStatisticsRest-server-allHttpRxGetInvalidMethod4XXResp OBJECT-TYPE
    SYNTAX      ConfdString
    MAX-ACCESS  read-only
    STATUS      current
    DESCRIPTION "Total number of Invalid Method GET failures - 4XX Failures"
    ::= { affirmedServiceconstructInterfaceT8InterfaceStatisticsRest-server-allEntry 155 }

affirmedServiceconstructInterfaceT8InterfaceStatisticsRest-server-allHttpRxGetInvalidMethod5XXResp OBJECT-TYPE
    SYNTAX      ConfdString
    MAX-ACCESS  read-only
    STATUS      current
    DESCRIPTION "Total number of Invalid Method GET failures - 5XX Failures"
    ::= { affirmedServiceconstructInterfaceT8InterfaceStatisticsRest-server-allEntry 156 }

affirmedServiceconstructInterfaceT8InterfaceStatisticsRest-server-allHttpRxGetParseErrorReq OBJECT-TYPE
    SYNTAX      ConfdString
    MAX-ACCESS  read-only
    STATUS      current
    DESCRIPTION "Total number of Parse Error GET requests received"
    ::= { affirmedServiceconstructInterfaceT8InterfaceStatisticsRest-server-allEntry 157 }

affirmedServiceconstructInterfaceT8InterfaceStatisticsRest-server-allHttpRxGetParseError2XXResp OBJECT-TYPE
    SYNTAX      ConfdString
    MAX-ACCESS  read-only
    STATUS      current
    DESCRIPTION "Total number of Parse Error GET responses - 2XX Success"
    ::= { affirmedServiceconstructInterfaceT8InterfaceStatisticsRest-server-allEntry 158 }

affirmedServiceconstructInterfaceT8InterfaceStatisticsRest-server-allHttpRxGetParseError3XXResp OBJECT-TYPE
    SYNTAX      ConfdString
    MAX-ACCESS  read-only
    STATUS      current
    DESCRIPTION "Total number of Parse Error GET failures - 3XX Responses"
    ::= { affirmedServiceconstructInterfaceT8InterfaceStatisticsRest-server-allEntry 159 }

affirmedServiceconstructInterfaceT8InterfaceStatisticsRest-server-allHttpRxGetParseError4XXResp OBJECT-TYPE
    SYNTAX      ConfdString
    MAX-ACCESS  read-only
    STATUS      current
    DESCRIPTION "Total number of Parse Error GET failures - 4XX Failures"
    ::= { affirmedServiceconstructInterfaceT8InterfaceStatisticsRest-server-allEntry 160 }

affirmedServiceconstructInterfaceT8InterfaceStatisticsRest-server-allHttpRxGetParseError5XXResp OBJECT-TYPE
    SYNTAX      ConfdString
    MAX-ACCESS  read-only
    STATUS      current
    DESCRIPTION "Total number of Parse Error GET failures - 5XX Failures"
    ::= { affirmedServiceconstructInterfaceT8InterfaceStatisticsRest-server-allEntry 161 }

affirmedServiceconstructInterfaceT8InterfaceStatisticsRest-server-allHttpRxGetBadContentReq OBJECT-TYPE
    SYNTAX      ConfdString
    MAX-ACCESS  read-only
    STATUS      current
    DESCRIPTION "Total number of Bad Content GET requests received"
    ::= { affirmedServiceconstructInterfaceT8InterfaceStatisticsRest-server-allEntry 162 }

affirmedServiceconstructInterfaceT8InterfaceStatisticsRest-server-allHttpRxGetBadContent2XXResp OBJECT-TYPE
    SYNTAX      ConfdString
    MAX-ACCESS  read-only
    STATUS      current
    DESCRIPTION "Total number of Bad Content GET responses - 2XX Success"
    ::= { affirmedServiceconstructInterfaceT8InterfaceStatisticsRest-server-allEntry 163 }

affirmedServiceconstructInterfaceT8InterfaceStatisticsRest-server-allHttpRxGetBadContent3XXResp OBJECT-TYPE
    SYNTAX      ConfdString
    MAX-ACCESS  read-only
    STATUS      current
    DESCRIPTION "Total number of Bad Content GET failures - 3XX Responses"
    ::= { affirmedServiceconstructInterfaceT8InterfaceStatisticsRest-server-allEntry 164 }

affirmedServiceconstructInterfaceT8InterfaceStatisticsRest-server-allHttpRxGetBadContent4XXResp OBJECT-TYPE
    SYNTAX      ConfdString
    MAX-ACCESS  read-only
    STATUS      current
    DESCRIPTION "Total number of Bad Content GET failures - 4XX Failures"
    ::= { affirmedServiceconstructInterfaceT8InterfaceStatisticsRest-server-allEntry 165 }

affirmedServiceconstructInterfaceT8InterfaceStatisticsRest-server-allHttpRxGetBadContent5XXResp OBJECT-TYPE
    SYNTAX      ConfdString
    MAX-ACCESS  read-only
    STATUS      current
    DESCRIPTION "Total number of Bad Content GET failures - 5XX Failures"
    ::= { affirmedServiceconstructInterfaceT8InterfaceStatisticsRest-server-allEntry 166 }

affirmedServiceconstructInterfaceT8InterfaceStatisticsRest-server-allHttpRxGetBadContentTypeReq OBJECT-TYPE
    SYNTAX      ConfdString
    MAX-ACCESS  read-only
    STATUS      current
    DESCRIPTION "Total number of Bad Content-Type GET requests received"
    ::= { affirmedServiceconstructInterfaceT8InterfaceStatisticsRest-server-allEntry 167 }

affirmedServiceconstructInterfaceT8InterfaceStatisticsRest-server-allHttpRxGetBadContentType2XXResp OBJECT-TYPE
    SYNTAX      ConfdString
    MAX-ACCESS  read-only
    STATUS      current
    DESCRIPTION "Total number of Bad Content-Type GET responses - 2XX Success"
    ::= { affirmedServiceconstructInterfaceT8InterfaceStatisticsRest-server-allEntry 168 }

affirmedServiceconstructInterfaceT8InterfaceStatisticsRest-server-allHttpRxGetBadContentType3XXResp OBJECT-TYPE
    SYNTAX      ConfdString
    MAX-ACCESS  read-only
    STATUS      current
    DESCRIPTION "Total number of Bad Content-Type GET failures - 3XX Responses"
    ::= { affirmedServiceconstructInterfaceT8InterfaceStatisticsRest-server-allEntry 169 }

affirmedServiceconstructInterfaceT8InterfaceStatisticsRest-server-allHttpRxGetBadContentType4XXResp OBJECT-TYPE
    SYNTAX      ConfdString
    MAX-ACCESS  read-only
    STATUS      current
    DESCRIPTION "Total number of Bad Content-Type GET failures - 4XX Failures"
    ::= { affirmedServiceconstructInterfaceT8InterfaceStatisticsRest-server-allEntry 170 }

affirmedServiceconstructInterfaceT8InterfaceStatisticsRest-server-allHttpRxGetBadContentType5XXResp OBJECT-TYPE
    SYNTAX      ConfdString
    MAX-ACCESS  read-only
    STATUS      current
    DESCRIPTION "Total number of Bad Content-Type GET failures - 5XX Failures"
    ::= { affirmedServiceconstructInterfaceT8InterfaceStatisticsRest-server-allEntry 171 }

affirmedServiceconstructInterfaceT8InterfaceStatisticsRest-server-allHttpRxGetInternalServerErrorReq OBJECT-TYPE
    SYNTAX      ConfdString
    MAX-ACCESS  read-only
    STATUS      current
    DESCRIPTION "Total number of Internal Server Error GET requests received"
    ::= { affirmedServiceconstructInterfaceT8InterfaceStatisticsRest-server-allEntry 172 }

affirmedServiceconstructInterfaceT8InterfaceStatisticsRest-server-allHttpRxGetInternalServerError2XXResp OBJECT-TYPE
    SYNTAX      ConfdString
    MAX-ACCESS  read-only
    STATUS      current
    DESCRIPTION "Total number of Internal Server Error GET responses - 2XX Success"
    ::= { affirmedServiceconstructInterfaceT8InterfaceStatisticsRest-server-allEntry 173 }

affirmedServiceconstructInterfaceT8InterfaceStatisticsRest-server-allHttpRxGetInternalServerError3XXResp OBJECT-TYPE
    SYNTAX      ConfdString
    MAX-ACCESS  read-only
    STATUS      current
    DESCRIPTION "Total number of Internal Server Error GET failures - 3XX Responses"
    ::= { affirmedServiceconstructInterfaceT8InterfaceStatisticsRest-server-allEntry 174 }

affirmedServiceconstructInterfaceT8InterfaceStatisticsRest-server-allHttpRxGetInternalServerError4XXResp OBJECT-TYPE
    SYNTAX      ConfdString
    MAX-ACCESS  read-only
    STATUS      current
    DESCRIPTION "Total number of Internal Server Error GET failures - 4XX Failures"
    ::= { affirmedServiceconstructInterfaceT8InterfaceStatisticsRest-server-allEntry 175 }

affirmedServiceconstructInterfaceT8InterfaceStatisticsRest-server-allHttpRxGetInternalServerError5XXResp OBJECT-TYPE
    SYNTAX      ConfdString
    MAX-ACCESS  read-only
    STATUS      current
    DESCRIPTION "Total number of Internal Server Error GET failures - 5XX Failures"
    ::= { affirmedServiceconstructInterfaceT8InterfaceStatisticsRest-server-allEntry 176 }

affirmedServiceconstructInterfaceT8InterfaceStatisticsRest-server-allHttpRxDeleteNiddDownLinkDataReq OBJECT-TYPE
    SYNTAX      ConfdString
    MAX-ACCESS  read-only
    STATUS      current
    DESCRIPTION "Total number of NIDD downlink data delivery DELETE requests received"
    ::= { affirmedServiceconstructInterfaceT8InterfaceStatisticsRest-server-allEntry 177 }

affirmedServiceconstructInterfaceT8InterfaceStatisticsRest-server-allHttpRxDeleteNiddDownLinkDataSuccessResp OBJECT-TYPE
    SYNTAX      ConfdString
    MAX-ACCESS  read-only
    STATUS      current
    DESCRIPTION "Total number of NIDD downlink data delivery DELETE requests accepted"
    ::= { affirmedServiceconstructInterfaceT8InterfaceStatisticsRest-server-allEntry 178 }

affirmedServiceconstructInterfaceT8InterfaceStatisticsRest-server-allHttpRxDeleteNiddDownLinkDataFailure400 OBJECT-TYPE
    SYNTAX      ConfdString
    MAX-ACCESS  read-only
    STATUS      current
    DESCRIPTION "Total number of NIDD downlink data delivery DELETE failures - 400 Bad Request"
    ::= { affirmedServiceconstructInterfaceT8InterfaceStatisticsRest-server-allEntry 179 }

affirmedServiceconstructInterfaceT8InterfaceStatisticsRest-server-allHttpRxDeleteNiddDownLinkDataFailure401 OBJECT-TYPE
    SYNTAX      ConfdString
    MAX-ACCESS  read-only
    STATUS      current
    DESCRIPTION "Total number of NIDD downlink data delivery DELETE failures - 401 Unauthorized"
    ::= { affirmedServiceconstructInterfaceT8InterfaceStatisticsRest-server-allEntry 180 }

affirmedServiceconstructInterfaceT8InterfaceStatisticsRest-server-allHttpRxDeleteNiddDownLinkDataFailure403 OBJECT-TYPE
    SYNTAX      ConfdString
    MAX-ACCESS  read-only
    STATUS      current
    DESCRIPTION "Total number of NIDD downlink data delivery DELETE failures - 403 Forbidden"
    ::= { affirmedServiceconstructInterfaceT8InterfaceStatisticsRest-server-allEntry 181 }

affirmedServiceconstructInterfaceT8InterfaceStatisticsRest-server-allHttpRxDeleteNiddDownLinkDataFailure404 OBJECT-TYPE
    SYNTAX      ConfdString
    MAX-ACCESS  read-only
    STATUS      current
    DESCRIPTION "Total number of NIDD downlink data delivery DELETE failures - 404 Not Found"
    ::= { affirmedServiceconstructInterfaceT8InterfaceStatisticsRest-server-allEntry 182 }

affirmedServiceconstructInterfaceT8InterfaceStatisticsRest-server-allHttpRxDeleteNiddDownLinkDataFailure409 OBJECT-TYPE
    SYNTAX      ConfdString
    MAX-ACCESS  read-only
    STATUS      current
    DESCRIPTION "Total number of NIDD downlink data delivery DELETE failures - 409 Conflict"
    ::= { affirmedServiceconstructInterfaceT8InterfaceStatisticsRest-server-allEntry 183 }

affirmedServiceconstructInterfaceT8InterfaceStatisticsRest-server-allHttpRxDeleteNiddDownLinkDataFailure412 OBJECT-TYPE
    SYNTAX      ConfdString
    MAX-ACCESS  read-only
    STATUS      current
    DESCRIPTION "Total number of NIDD downlink data delivery DELETE failures - 412 Precondition Failed"
    ::= { affirmedServiceconstructInterfaceT8InterfaceStatisticsRest-server-allEntry 184 }

affirmedServiceconstructInterfaceT8InterfaceStatisticsRest-server-allHttpRxDeleteNiddDownLinkDataFailure500 OBJECT-TYPE
    SYNTAX      ConfdString
    MAX-ACCESS  read-only
    STATUS      current
    DESCRIPTION "Total number of NIDD downlink data delivery DELETE failures - 500 Internal Server Error"
    ::= { affirmedServiceconstructInterfaceT8InterfaceStatisticsRest-server-allEntry 185 }

affirmedServiceconstructInterfaceT8InterfaceStatisticsRest-server-allHttpRxDeleteNiddDownLinkDataFailure503 OBJECT-TYPE
    SYNTAX      ConfdString
    MAX-ACCESS  read-only
    STATUS      current
    DESCRIPTION "Total number of NIDD downlink data delivery DELETE failures - 503 Service Unavailable"
    ::= { affirmedServiceconstructInterfaceT8InterfaceStatisticsRest-server-allEntry 186 }

affirmedServiceconstructInterfaceT8InterfaceStatisticsRest-server-allHttpRxPutNiddDownLinkDataFailure400 OBJECT-TYPE
    SYNTAX      ConfdString
    MAX-ACCESS  read-only
    STATUS      current
    DESCRIPTION "Total number of NIDD downlink data delivery PUT failures - 400 Bad Request"
    ::= { affirmedServiceconstructInterfaceT8InterfaceStatisticsRest-server-allEntry 187 }

affirmedServiceconstructInterfaceT8InterfaceStatisticsRest-server-allHttpRxPutNiddDownLinkDataFailure401 OBJECT-TYPE
    SYNTAX      ConfdString
    MAX-ACCESS  read-only
    STATUS      current
    DESCRIPTION "Total number of NIDD downlink data delivery PUT failures - 401 Unauthorized"
    ::= { affirmedServiceconstructInterfaceT8InterfaceStatisticsRest-server-allEntry 188 }

affirmedServiceconstructInterfaceT8InterfaceStatisticsRest-server-allHttpRxPutNiddDownLinkDataFailure403 OBJECT-TYPE
    SYNTAX      ConfdString
    MAX-ACCESS  read-only
    STATUS      current
    DESCRIPTION "Total number of NIDD downlink data delivery PUT failures - 403 Forbidden"
    ::= { affirmedServiceconstructInterfaceT8InterfaceStatisticsRest-server-allEntry 189 }

affirmedServiceconstructInterfaceT8InterfaceStatisticsRest-server-allHttpRxPutNiddDownLinkDataFailure404 OBJECT-TYPE
    SYNTAX      ConfdString
    MAX-ACCESS  read-only
    STATUS      current
    DESCRIPTION "Total number of NIDD downlink data delivery PUT failures - 404 Not Found"
    ::= { affirmedServiceconstructInterfaceT8InterfaceStatisticsRest-server-allEntry 190 }

affirmedServiceconstructInterfaceT8InterfaceStatisticsRest-server-allHttpRxPutNiddDownLinkDataFailure409 OBJECT-TYPE
    SYNTAX      ConfdString
    MAX-ACCESS  read-only
    STATUS      current
    DESCRIPTION "Total number of NIDD downlink data delivery PUT failures - 409 Conflict"
    ::= { affirmedServiceconstructInterfaceT8InterfaceStatisticsRest-server-allEntry 191 }

affirmedServiceconstructInterfaceT8InterfaceStatisticsRest-server-allHttpRxPutNiddDownLinkDataFailure412 OBJECT-TYPE
    SYNTAX      ConfdString
    MAX-ACCESS  read-only
    STATUS      current
    DESCRIPTION "Total number of NIDD downlink data delivery PUT failures - 412 Precondition Failed"
    ::= { affirmedServiceconstructInterfaceT8InterfaceStatisticsRest-server-allEntry 192 }

affirmedServiceconstructInterfaceT8InterfaceStatisticsRest-server-allHttpRxPutNiddDownLinkDataFailure500 OBJECT-TYPE
    SYNTAX      ConfdString
    MAX-ACCESS  read-only
    STATUS      current
    DESCRIPTION "Total number of NIDD downlink data delivery PUT failures - 500 Internal Server Error"
    ::= { affirmedServiceconstructInterfaceT8InterfaceStatisticsRest-server-allEntry 193 }

affirmedServiceconstructInterfaceT8InterfaceStatisticsRest-server-allHttpRxPutNiddDownLinkDataFailure503 OBJECT-TYPE
    SYNTAX      ConfdString
    MAX-ACCESS  read-only
    STATUS      current
    DESCRIPTION "Total number of NIDD downlink data delivery PUT failures - 503 Service Unavailable"
    ::= { affirmedServiceconstructInterfaceT8InterfaceStatisticsRest-server-allEntry 194 }

affirmedServiceconstructControlServiceProfileDhcpLocalServerstatisticsTable OBJECT-TYPE
    SYNTAX      SEQUENCE OF AffirmedServiceconstructControlServiceProfileDhcpLocalServerstatisticsEntry
    MAX-ACCESS  not-accessible
    STATUS      current
    DESCRIPTION ""
    ::= { affirmedServiceconstructControlServiceProfileDhcp 1 }

affirmedServiceconstructControlServiceProfileDhcpLocalServerstatisticsEntry OBJECT-TYPE
    SYNTAX      AffirmedServiceconstructControlServiceProfileDhcpLocalServerstatisticsEntry
    MAX-ACCESS  not-accessible
    STATUS      current
    DESCRIPTION ""
    INDEX { affirmedServiceconstructControlServiceProfileDhcpLocalServerstatisticsDhcpLocalServerName }
        ::= { affirmedServiceconstructControlServiceProfileDhcpLocalServerstatisticsTable 1 }

AffirmedServiceconstructControlServiceProfileDhcpLocalServerstatisticsEntry ::=
    SEQUENCE {
        affirmedServiceconstructControlServiceProfileDhcpLocalServerstatisticsDhcpLocalServerName String,
        affirmedServiceconstructControlServiceProfileDhcpLocalServerstatisticsDhcpServerStatDiscoverUpstrRx Unsigned32,
        affirmedServiceconstructControlServiceProfileDhcpLocalServerstatisticsDhcpServerStatRequestUpstrRx Unsigned32,
        affirmedServiceconstructControlServiceProfileDhcpLocalServerstatisticsDhcpServerStatReleaseUpstrRx Unsigned32,
        affirmedServiceconstructControlServiceProfileDhcpLocalServerstatisticsDhcpServerStatUnsuppMsgUpstrRx Unsigned32,
        affirmedServiceconstructControlServiceProfileDhcpLocalServerstatisticsDhcpServerStatMsgOptionDecodeErrUpstrRx Unsigned32,
        affirmedServiceconstructControlServiceProfileDhcpLocalServerstatisticsDhcpServerStatServerIdOptionDecodeErrUpstrRx Unsigned32,
        affirmedServiceconstructControlServiceProfileDhcpLocalServerstatisticsDhcpServerStatReqIpOptionDecodeErrUpstrRx Unsigned32,
        affirmedServiceconstructControlServiceProfileDhcpLocalServerstatisticsDhcpServerStatLeaseTimeOptionDecodeErrUpstrRx Unsigned32,
        affirmedServiceconstructControlServiceProfileDhcpLocalServerstatisticsDhcpServerStatErrUpstrTx Unsigned32,
        affirmedServiceconstructControlServiceProfileDhcpLocalServerstatisticsDhcpServerStatOfferDownstrTx Unsigned32,
        affirmedServiceconstructControlServiceProfileDhcpLocalServerstatisticsDhcpServerStatDeclineDownstrTx Unsigned32,
        affirmedServiceconstructControlServiceProfileDhcpLocalServerstatisticsDhcpServerStatAckDownstrTx Unsigned32,
        affirmedServiceconstructControlServiceProfileDhcpLocalServerstatisticsDhcpServerStatNackDownstrTx Unsigned32,
        affirmedServiceconstructControlServiceProfileDhcpLocalServerstatisticsDhcpServerStatErrDownstrTx Unsigned32
    }

affirmedServiceconstructControlServiceProfileDhcpLocalServerstatisticsDhcpLocalServerName OBJECT-TYPE
    SYNTAX      String
    MAX-ACCESS  not-accessible
    STATUS      current
    DESCRIPTION "Name of the DHCP server profile"
    ::= { affirmedServiceconstructControlServiceProfileDhcpLocalServerstatisticsEntry 1 }

affirmedServiceconstructControlServiceProfileDhcpLocalServerstatisticsDhcpServerStatDiscoverUpstrRx OBJECT-TYPE
    SYNTAX      Unsigned32
    MAX-ACCESS  read-only
    STATUS      current
    DESCRIPTION "Discovers received"
    ::= { affirmedServiceconstructControlServiceProfileDhcpLocalServerstatisticsEntry 2 }

affirmedServiceconstructControlServiceProfileDhcpLocalServerstatisticsDhcpServerStatRequestUpstrRx OBJECT-TYPE
    SYNTAX      Unsigned32
    MAX-ACCESS  read-only
    STATUS      current
    DESCRIPTION "Requests received"
    ::= { affirmedServiceconstructControlServiceProfileDhcpLocalServerstatisticsEntry 3 }

affirmedServiceconstructControlServiceProfileDhcpLocalServerstatisticsDhcpServerStatReleaseUpstrRx OBJECT-TYPE
    SYNTAX      Unsigned32
    MAX-ACCESS  read-only
    STATUS      current
    DESCRIPTION "Releases received"
    ::= { affirmedServiceconstructControlServiceProfileDhcpLocalServerstatisticsEntry 4 }

affirmedServiceconstructControlServiceProfileDhcpLocalServerstatisticsDhcpServerStatUnsuppMsgUpstrRx OBJECT-TYPE
    SYNTAX      Unsigned32
    MAX-ACCESS  read-only
    STATUS      current
    DESCRIPTION "Unsupported messages received"
    ::= { affirmedServiceconstructControlServiceProfileDhcpLocalServerstatisticsEntry 5 }

affirmedServiceconstructControlServiceProfileDhcpLocalServerstatisticsDhcpServerStatMsgOptionDecodeErrUpstrRx OBJECT-TYPE
    SYNTAX      Unsigned32
    MAX-ACCESS  read-only
    STATUS      current
    DESCRIPTION "Message options decode errors received"
    ::= { affirmedServiceconstructControlServiceProfileDhcpLocalServerstatisticsEntry 6 }

affirmedServiceconstructControlServiceProfileDhcpLocalServerstatisticsDhcpServerStatServerIdOptionDecodeErrUpstrRx OBJECT-TYPE
    SYNTAX      Unsigned32
    MAX-ACCESS  read-only
    STATUS      current
    DESCRIPTION "Server ID option decode errors received"
    ::= { affirmedServiceconstructControlServiceProfileDhcpLocalServerstatisticsEntry 7 }

affirmedServiceconstructControlServiceProfileDhcpLocalServerstatisticsDhcpServerStatReqIpOptionDecodeErrUpstrRx OBJECT-TYPE
    SYNTAX      Unsigned32
    MAX-ACCESS  read-only
    STATUS      current
    DESCRIPTION "Requested IP option decode errors received"
    ::= { affirmedServiceconstructControlServiceProfileDhcpLocalServerstatisticsEntry 8 }

affirmedServiceconstructControlServiceProfileDhcpLocalServerstatisticsDhcpServerStatLeaseTimeOptionDecodeErrUpstrRx OBJECT-TYPE
    SYNTAX      Unsigned32
    MAX-ACCESS  read-only
    STATUS      current
    DESCRIPTION "Lease time option decode errors received"
    ::= { affirmedServiceconstructControlServiceProfileDhcpLocalServerstatisticsEntry 9 }

affirmedServiceconstructControlServiceProfileDhcpLocalServerstatisticsDhcpServerStatErrUpstrTx OBJECT-TYPE
    SYNTAX      Unsigned32
    MAX-ACCESS  read-only
    STATUS      current
    DESCRIPTION "Received errors"
    ::= { affirmedServiceconstructControlServiceProfileDhcpLocalServerstatisticsEntry 10 }

affirmedServiceconstructControlServiceProfileDhcpLocalServerstatisticsDhcpServerStatOfferDownstrTx OBJECT-TYPE
    SYNTAX      Unsigned32
    MAX-ACCESS  read-only
    STATUS      current
    DESCRIPTION "Offers transmitted"
    ::= { affirmedServiceconstructControlServiceProfileDhcpLocalServerstatisticsEntry 11 }

affirmedServiceconstructControlServiceProfileDhcpLocalServerstatisticsDhcpServerStatDeclineDownstrTx OBJECT-TYPE
    SYNTAX      Unsigned32
    MAX-ACCESS  read-only
    STATUS      current
    DESCRIPTION "Declines transmitted"
    ::= { affirmedServiceconstructControlServiceProfileDhcpLocalServerstatisticsEntry 12 }

affirmedServiceconstructControlServiceProfileDhcpLocalServerstatisticsDhcpServerStatAckDownstrTx OBJECT-TYPE
    SYNTAX      Unsigned32
    MAX-ACCESS  read-only
    STATUS      current
    DESCRIPTION "ACKs transmitted"
    ::= { affirmedServiceconstructControlServiceProfileDhcpLocalServerstatisticsEntry 13 }

affirmedServiceconstructControlServiceProfileDhcpLocalServerstatisticsDhcpServerStatNackDownstrTx OBJECT-TYPE
    SYNTAX      Unsigned32
    MAX-ACCESS  read-only
    STATUS      current
    DESCRIPTION "NACKs transmitted"
    ::= { affirmedServiceconstructControlServiceProfileDhcpLocalServerstatisticsEntry 14 }

affirmedServiceconstructControlServiceProfileDhcpLocalServerstatisticsDhcpServerStatErrDownstrTx OBJECT-TYPE
    SYNTAX      Unsigned32
    MAX-ACCESS  read-only
    STATUS      current
    DESCRIPTION "transmit-errors"
    ::= { affirmedServiceconstructControlServiceProfileDhcpLocalServerstatisticsEntry 15 }

affirmedServiceconstructUrlListStatsHistoryTable OBJECT-TYPE
    SYNTAX      SEQUENCE OF AffirmedServiceconstructUrlListStatsHistoryEntry
    MAX-ACCESS  not-accessible
    STATUS      current
    DESCRIPTION ""
    ::= { affirmedServiceconstructUrlListStats 1 }

affirmedServiceconstructUrlListStatsHistoryEntry OBJECT-TYPE
    SYNTAX      AffirmedServiceconstructUrlListStatsHistoryEntry
    MAX-ACCESS  not-accessible
    STATUS      current
    DESCRIPTION ""
    INDEX { affirmedServiceconstructUrlListStatsHistoryName }
        ::= { affirmedServiceconstructUrlListStatsHistoryTable 1 }

AffirmedServiceconstructUrlListStatsHistoryEntry ::=
    SEQUENCE {
        affirmedServiceconstructUrlListStatsHistoryName String,
        affirmedServiceconstructUrlListStatsHistoryResult String
    }

affirmedServiceconstructUrlListStatsHistoryName OBJECT-TYPE
    SYNTAX      String
    MAX-ACCESS  not-accessible
    STATUS      current
    DESCRIPTION "URL-list name"
    ::= { affirmedServiceconstructUrlListStatsHistoryEntry 1 }

affirmedServiceconstructUrlListStatsHistoryResult OBJECT-TYPE
    SYNTAX      String
    MAX-ACCESS  read-only
    STATUS      current
    DESCRIPTION ""
    ::= { affirmedServiceconstructUrlListStatsHistoryEntry 2 }

affirmedServiceconstructUrlListStatsSummaryTable OBJECT-TYPE
    SYNTAX      SEQUENCE OF AffirmedServiceconstructUrlListStatsSummaryEntry
    MAX-ACCESS  not-accessible
    STATUS      current
    DESCRIPTION ""
    ::= { affirmedServiceconstructUrlListStats 2 }

affirmedServiceconstructUrlListStatsSummaryEntry OBJECT-TYPE
    SYNTAX      AffirmedServiceconstructUrlListStatsSummaryEntry
    MAX-ACCESS  not-accessible
    STATUS      current
    DESCRIPTION ""
    INDEX { affirmedServiceconstructUrlListStatsSummaryName }
        ::= { affirmedServiceconstructUrlListStatsSummaryTable 1 }

AffirmedServiceconstructUrlListStatsSummaryEntry ::=
    SEQUENCE {
        affirmedServiceconstructUrlListStatsSummaryName String,
        affirmedServiceconstructUrlListStatsSummaryLastTime String,
        affirmedServiceconstructUrlListStatsSummaryLastResult String,
        affirmedServiceconstructUrlListStatsSummaryLastImportType String,
        affirmedServiceconstructUrlListStatsSummaryLastImportNum Unsigned32,
        affirmedServiceconstructUrlListStatsSummaryLastSize Unsigned32,
        affirmedServiceconstructUrlListStatsSummaryNextTime String,
        affirmedServiceconstructUrlListStatsSummaryTotalEntry Unsigned32,
        affirmedServiceconstructUrlListStatsSummaryTotalReject Unsigned32,
        affirmedServiceconstructUrlListStatsSummaryImportFileName String
    }

affirmedServiceconstructUrlListStatsSummaryName OBJECT-TYPE
    SYNTAX      String
    MAX-ACCESS  not-accessible
    STATUS      current
    DESCRIPTION "URL-list name"
    ::= { affirmedServiceconstructUrlListStatsSummaryEntry 1 }

affirmedServiceconstructUrlListStatsSummaryLastTime OBJECT-TYPE
    SYNTAX      String
    MAX-ACCESS  read-only
    STATUS      current
    DESCRIPTION "Last Import Time"
    ::= { affirmedServiceconstructUrlListStatsSummaryEntry 2 }

affirmedServiceconstructUrlListStatsSummaryLastResult OBJECT-TYPE
    SYNTAX      String
    MAX-ACCESS  read-only
    STATUS      current
    DESCRIPTION "Last Import Result"
    ::= { affirmedServiceconstructUrlListStatsSummaryEntry 3 }

affirmedServiceconstructUrlListStatsSummaryLastImportType OBJECT-TYPE
    SYNTAX      String
    MAX-ACCESS  read-only
    STATUS      current
    DESCRIPTION "Import Type"
    ::= { affirmedServiceconstructUrlListStatsSummaryEntry 4 }

affirmedServiceconstructUrlListStatsSummaryLastImportNum OBJECT-TYPE
    SYNTAX      Unsigned32
    MAX-ACCESS  read-only
    STATUS      current
    DESCRIPTION "Last Import Number"
    ::= { affirmedServiceconstructUrlListStatsSummaryEntry 5 }

affirmedServiceconstructUrlListStatsSummaryLastSize OBJECT-TYPE
    SYNTAX      Unsigned32
    MAX-ACCESS  read-only
    STATUS      current
    DESCRIPTION "Last Import File Size(Bytes)"
    ::= { affirmedServiceconstructUrlListStatsSummaryEntry 6 }

affirmedServiceconstructUrlListStatsSummaryNextTime OBJECT-TYPE
    SYNTAX      String
    MAX-ACCESS  read-only
    STATUS      current
    DESCRIPTION "Next Scheduled Import Time"
    ::= { affirmedServiceconstructUrlListStatsSummaryEntry 7 }

affirmedServiceconstructUrlListStatsSummaryTotalEntry OBJECT-TYPE
    SYNTAX      Unsigned32
    MAX-ACCESS  read-only
    STATUS      current
    DESCRIPTION "Number Of Accepted Entries"
    ::= { affirmedServiceconstructUrlListStatsSummaryEntry 8 }

affirmedServiceconstructUrlListStatsSummaryTotalReject OBJECT-TYPE
    SYNTAX      Unsigned32
    MAX-ACCESS  read-only
    STATUS      current
    DESCRIPTION "Number Of Rejected Entries"
    ::= { affirmedServiceconstructUrlListStatsSummaryEntry 9 }

affirmedServiceconstructUrlListStatsSummaryImportFileName OBJECT-TYPE
    SYNTAX      String
    MAX-ACCESS  read-only
    STATUS      current
    DESCRIPTION "Import File Name"
    ::= { affirmedServiceconstructUrlListStatsSummaryEntry 10 }

affirmedServiceconstructUrlListStatsDetailTable OBJECT-TYPE
    SYNTAX      SEQUENCE OF AffirmedServiceconstructUrlListStatsDetailEntry
    MAX-ACCESS  not-accessible
    STATUS      current
    DESCRIPTION ""
    ::= { affirmedServiceconstructUrlListStats 3 }

affirmedServiceconstructUrlListStatsDetailEntry OBJECT-TYPE
    SYNTAX      AffirmedServiceconstructUrlListStatsDetailEntry
    MAX-ACCESS  not-accessible
    STATUS      current
    DESCRIPTION ""
    INDEX { affirmedServiceconstructUrlListStatsDetailName }
        ::= { affirmedServiceconstructUrlListStatsDetailTable 1 }

AffirmedServiceconstructUrlListStatsDetailEntry ::=
    SEQUENCE {
        affirmedServiceconstructUrlListStatsDetailName String,
        affirmedServiceconstructUrlListStatsDetailLastTime String,
        affirmedServiceconstructUrlListStatsDetailLastResult String,
        affirmedServiceconstructUrlListStatsDetailLastImportType String,
        affirmedServiceconstructUrlListStatsDetailLastImportNum Unsigned32,
        affirmedServiceconstructUrlListStatsDetailLastSize Unsigned32,
        affirmedServiceconstructUrlListStatsDetailNextTime String,
        affirmedServiceconstructUrlListStatsDetailTotalEntry Unsigned32,
        affirmedServiceconstructUrlListStatsDetailEntries String,
        affirmedServiceconstructUrlListStatsDetailTotalReject Unsigned32,
        affirmedServiceconstructUrlListStatsDetailRejectedEntries String,
        affirmedServiceconstructUrlListStatsDetailImportFileName String
    }

affirmedServiceconstructUrlListStatsDetailName OBJECT-TYPE
    SYNTAX      String
    MAX-ACCESS  not-accessible
    STATUS      current
    DESCRIPTION "URL-list name"
    ::= { affirmedServiceconstructUrlListStatsDetailEntry 1 }

affirmedServiceconstructUrlListStatsDetailLastTime OBJECT-TYPE
    SYNTAX      String
    MAX-ACCESS  read-only
    STATUS      current
    DESCRIPTION "Last Import Time"
    ::= { affirmedServiceconstructUrlListStatsDetailEntry 2 }

affirmedServiceconstructUrlListStatsDetailLastResult OBJECT-TYPE
    SYNTAX      String
    MAX-ACCESS  read-only
    STATUS      current
    DESCRIPTION "Last Import Result"
    ::= { affirmedServiceconstructUrlListStatsDetailEntry 3 }

affirmedServiceconstructUrlListStatsDetailLastImportType OBJECT-TYPE
    SYNTAX      String
    MAX-ACCESS  read-only
    STATUS      current
    DESCRIPTION "Import Type"
    ::= { affirmedServiceconstructUrlListStatsDetailEntry 4 }

affirmedServiceconstructUrlListStatsDetailLastImportNum OBJECT-TYPE
    SYNTAX      Unsigned32
    MAX-ACCESS  read-only
    STATUS      current
    DESCRIPTION "Last Import Number"
    ::= { affirmedServiceconstructUrlListStatsDetailEntry 5 }

affirmedServiceconstructUrlListStatsDetailLastSize OBJECT-TYPE
    SYNTAX      Unsigned32
    MAX-ACCESS  read-only
    STATUS      current
    DESCRIPTION "Last Import File Size(Bytes)"
    ::= { affirmedServiceconstructUrlListStatsDetailEntry 6 }

affirmedServiceconstructUrlListStatsDetailNextTime OBJECT-TYPE
    SYNTAX      String
    MAX-ACCESS  read-only
    STATUS      current
    DESCRIPTION "Next Scheduled Import Time"
    ::= { affirmedServiceconstructUrlListStatsDetailEntry 7 }

affirmedServiceconstructUrlListStatsDetailTotalEntry OBJECT-TYPE
    SYNTAX      Unsigned32
    MAX-ACCESS  read-only
    STATUS      current
    DESCRIPTION "Number Of Accepted Entries"
    ::= { affirmedServiceconstructUrlListStatsDetailEntry 8 }

affirmedServiceconstructUrlListStatsDetailEntries OBJECT-TYPE
    SYNTAX      String
    MAX-ACCESS  read-only
    STATUS      current
    DESCRIPTION "Accepted Entries"
    ::= { affirmedServiceconstructUrlListStatsDetailEntry 9 }

affirmedServiceconstructUrlListStatsDetailTotalReject OBJECT-TYPE
    SYNTAX      Unsigned32
    MAX-ACCESS  read-only
    STATUS      current
    DESCRIPTION "Number Of Rejected Entries"
    ::= { affirmedServiceconstructUrlListStatsDetailEntry 10 }

affirmedServiceconstructUrlListStatsDetailRejectedEntries OBJECT-TYPE
    SYNTAX      String
    MAX-ACCESS  read-only
    STATUS      current
    DESCRIPTION "Rejected Entries"
    ::= { affirmedServiceconstructUrlListStatsDetailEntry 11 }

affirmedServiceconstructUrlListStatsDetailImportFileName OBJECT-TYPE
    SYNTAX      String
    MAX-ACCESS  read-only
    STATUS      current
    DESCRIPTION "Import File Name"
    ::= { affirmedServiceconstructUrlListStatsDetailEntry 12 }

affirmedServiceconstructDeviceDatabaseStatsHistoryTable OBJECT-TYPE
    SYNTAX      SEQUENCE OF AffirmedServiceconstructDeviceDatabaseStatsHistoryEntry
    MAX-ACCESS  not-accessible
    STATUS      current
    DESCRIPTION ""
    ::= { affirmedServiceconstructDeviceDatabaseStats 1 }

affirmedServiceconstructDeviceDatabaseStatsHistoryEntry OBJECT-TYPE
    SYNTAX      AffirmedServiceconstructDeviceDatabaseStatsHistoryEntry
    MAX-ACCESS  not-accessible
    STATUS      current
    DESCRIPTION ""
    INDEX { affirmedServiceconstructDeviceDatabaseStatsHistoryName }
        ::= { affirmedServiceconstructDeviceDatabaseStatsHistoryTable 1 }

AffirmedServiceconstructDeviceDatabaseStatsHistoryEntry ::=
    SEQUENCE {
        affirmedServiceconstructDeviceDatabaseStatsHistoryName String,
        affirmedServiceconstructDeviceDatabaseStatsHistoryResult String
    }

affirmedServiceconstructDeviceDatabaseStatsHistoryName OBJECT-TYPE
    SYNTAX      String
    MAX-ACCESS  not-accessible
    STATUS      current
    DESCRIPTION "Device database name"
    ::= { affirmedServiceconstructDeviceDatabaseStatsHistoryEntry 1 }

affirmedServiceconstructDeviceDatabaseStatsHistoryResult OBJECT-TYPE
    SYNTAX      String
    MAX-ACCESS  read-only
    STATUS      current
    DESCRIPTION ""
    ::= { affirmedServiceconstructDeviceDatabaseStatsHistoryEntry 2 }

affirmedServiceconstructDeviceDatabaseStatsSummaryTable OBJECT-TYPE
    SYNTAX      SEQUENCE OF AffirmedServiceconstructDeviceDatabaseStatsSummaryEntry
    MAX-ACCESS  not-accessible
    STATUS      current
    DESCRIPTION ""
    ::= { affirmedServiceconstructDeviceDatabaseStats 2 }

affirmedServiceconstructDeviceDatabaseStatsSummaryEntry OBJECT-TYPE
    SYNTAX      AffirmedServiceconstructDeviceDatabaseStatsSummaryEntry
    MAX-ACCESS  not-accessible
    STATUS      current
    DESCRIPTION ""
    INDEX { affirmedServiceconstructDeviceDatabaseStatsSummaryName }
        ::= { affirmedServiceconstructDeviceDatabaseStatsSummaryTable 1 }

AffirmedServiceconstructDeviceDatabaseStatsSummaryEntry ::=
    SEQUENCE {
        affirmedServiceconstructDeviceDatabaseStatsSummaryName String,
        affirmedServiceconstructDeviceDatabaseStatsSummaryLastTime String,
        affirmedServiceconstructDeviceDatabaseStatsSummaryLastResult String,
        affirmedServiceconstructDeviceDatabaseStatsSummaryLastImportType String,
        affirmedServiceconstructDeviceDatabaseStatsSummaryLastImportNum Unsigned32,
        affirmedServiceconstructDeviceDatabaseStatsSummaryLastSize Unsigned32,
        affirmedServiceconstructDeviceDatabaseStatsSummaryNextTime String,
        affirmedServiceconstructDeviceDatabaseStatsSummaryTotalEntry Unsigned32,
        affirmedServiceconstructDeviceDatabaseStatsSummaryTotalReject Unsigned32,
        affirmedServiceconstructDeviceDatabaseStatsSummaryImportFileName String
    }

affirmedServiceconstructDeviceDatabaseStatsSummaryName OBJECT-TYPE
    SYNTAX      String
    MAX-ACCESS  not-accessible
    STATUS      current
    DESCRIPTION "Device database name"
    ::= { affirmedServiceconstructDeviceDatabaseStatsSummaryEntry 1 }

affirmedServiceconstructDeviceDatabaseStatsSummaryLastTime OBJECT-TYPE
    SYNTAX      String
    MAX-ACCESS  read-only
    STATUS      current
    DESCRIPTION "Last Import Time"
    ::= { affirmedServiceconstructDeviceDatabaseStatsSummaryEntry 2 }

affirmedServiceconstructDeviceDatabaseStatsSummaryLastResult OBJECT-TYPE
    SYNTAX      String
    MAX-ACCESS  read-only
    STATUS      current
    DESCRIPTION "Last Import Result"
    ::= { affirmedServiceconstructDeviceDatabaseStatsSummaryEntry 3 }

affirmedServiceconstructDeviceDatabaseStatsSummaryLastImportType OBJECT-TYPE
    SYNTAX      String
    MAX-ACCESS  read-only
    STATUS      current
    DESCRIPTION "Import Type"
    ::= { affirmedServiceconstructDeviceDatabaseStatsSummaryEntry 4 }

affirmedServiceconstructDeviceDatabaseStatsSummaryLastImportNum OBJECT-TYPE
    SYNTAX      Unsigned32
    MAX-ACCESS  read-only
    STATUS      current
    DESCRIPTION "Last Import Number"
    ::= { affirmedServiceconstructDeviceDatabaseStatsSummaryEntry 5 }

affirmedServiceconstructDeviceDatabaseStatsSummaryLastSize OBJECT-TYPE
    SYNTAX      Unsigned32
    MAX-ACCESS  read-only
    STATUS      current
    DESCRIPTION "Last Import File Size(Bytes)"
    ::= { affirmedServiceconstructDeviceDatabaseStatsSummaryEntry 6 }

affirmedServiceconstructDeviceDatabaseStatsSummaryNextTime OBJECT-TYPE
    SYNTAX      String
    MAX-ACCESS  read-only
    STATUS      current
    DESCRIPTION "Next Scheduled Import Time"
    ::= { affirmedServiceconstructDeviceDatabaseStatsSummaryEntry 7 }

affirmedServiceconstructDeviceDatabaseStatsSummaryTotalEntry OBJECT-TYPE
    SYNTAX      Unsigned32
    MAX-ACCESS  read-only
    STATUS      current
    DESCRIPTION "Number Of Accepted Entries"
    ::= { affirmedServiceconstructDeviceDatabaseStatsSummaryEntry 8 }

affirmedServiceconstructDeviceDatabaseStatsSummaryTotalReject OBJECT-TYPE
    SYNTAX      Unsigned32
    MAX-ACCESS  read-only
    STATUS      current
    DESCRIPTION "Number Of Rejected Entries"
    ::= { affirmedServiceconstructDeviceDatabaseStatsSummaryEntry 9 }

affirmedServiceconstructDeviceDatabaseStatsSummaryImportFileName OBJECT-TYPE
    SYNTAX      String
    MAX-ACCESS  read-only
    STATUS      current
    DESCRIPTION "Import File Name"
    ::= { affirmedServiceconstructDeviceDatabaseStatsSummaryEntry 10 }

affirmedServiceconstructDeviceDatabaseStatsDetailTable OBJECT-TYPE
    SYNTAX      SEQUENCE OF AffirmedServiceconstructDeviceDatabaseStatsDetailEntry
    MAX-ACCESS  not-accessible
    STATUS      current
    DESCRIPTION ""
    ::= { affirmedServiceconstructDeviceDatabaseStats 3 }

affirmedServiceconstructDeviceDatabaseStatsDetailEntry OBJECT-TYPE
    SYNTAX      AffirmedServiceconstructDeviceDatabaseStatsDetailEntry
    MAX-ACCESS  not-accessible
    STATUS      current
    DESCRIPTION ""
    INDEX { affirmedServiceconstructDeviceDatabaseStatsDetailName }
        ::= { affirmedServiceconstructDeviceDatabaseStatsDetailTable 1 }

AffirmedServiceconstructDeviceDatabaseStatsDetailEntry ::=
    SEQUENCE {
        affirmedServiceconstructDeviceDatabaseStatsDetailName String,
        affirmedServiceconstructDeviceDatabaseStatsDetailLastTime String,
        affirmedServiceconstructDeviceDatabaseStatsDetailLastResult String,
        affirmedServiceconstructDeviceDatabaseStatsDetailLastImportType String,
        affirmedServiceconstructDeviceDatabaseStatsDetailLastImportNum Unsigned32,
        affirmedServiceconstructDeviceDatabaseStatsDetailLastSize Unsigned32,
        affirmedServiceconstructDeviceDatabaseStatsDetailNextTime String,
        affirmedServiceconstructDeviceDatabaseStatsDetailTotalEntry Unsigned32,
        affirmedServiceconstructDeviceDatabaseStatsDetailEntries String,
        affirmedServiceconstructDeviceDatabaseStatsDetailTotalReject Unsigned32,
        affirmedServiceconstructDeviceDatabaseStatsDetailRejectedEntries String,
        affirmedServiceconstructDeviceDatabaseStatsDetailImportFileName String
    }

affirmedServiceconstructDeviceDatabaseStatsDetailName OBJECT-TYPE
    SYNTAX      String
    MAX-ACCESS  not-accessible
    STATUS      current
    DESCRIPTION "Device-Database name"
    ::= { affirmedServiceconstructDeviceDatabaseStatsDetailEntry 1 }

affirmedServiceconstructDeviceDatabaseStatsDetailLastTime OBJECT-TYPE
    SYNTAX      String
    MAX-ACCESS  read-only
    STATUS      current
    DESCRIPTION "Last Import Time"
    ::= { affirmedServiceconstructDeviceDatabaseStatsDetailEntry 2 }

affirmedServiceconstructDeviceDatabaseStatsDetailLastResult OBJECT-TYPE
    SYNTAX      String
    MAX-ACCESS  read-only
    STATUS      current
    DESCRIPTION "Last Import Result"
    ::= { affirmedServiceconstructDeviceDatabaseStatsDetailEntry 3 }

affirmedServiceconstructDeviceDatabaseStatsDetailLastImportType OBJECT-TYPE
    SYNTAX      String
    MAX-ACCESS  read-only
    STATUS      current
    DESCRIPTION "Import Type"
    ::= { affirmedServiceconstructDeviceDatabaseStatsDetailEntry 4 }

affirmedServiceconstructDeviceDatabaseStatsDetailLastImportNum OBJECT-TYPE
    SYNTAX      Unsigned32
    MAX-ACCESS  read-only
    STATUS      current
    DESCRIPTION "Last Import Number"
    ::= { affirmedServiceconstructDeviceDatabaseStatsDetailEntry 5 }

affirmedServiceconstructDeviceDatabaseStatsDetailLastSize OBJECT-TYPE
    SYNTAX      Unsigned32
    MAX-ACCESS  read-only
    STATUS      current
    DESCRIPTION "Last Import File Size(Bytes)"
    ::= { affirmedServiceconstructDeviceDatabaseStatsDetailEntry 6 }

affirmedServiceconstructDeviceDatabaseStatsDetailNextTime OBJECT-TYPE
    SYNTAX      String
    MAX-ACCESS  read-only
    STATUS      current
    DESCRIPTION "Next Scheduled Import Time"
    ::= { affirmedServiceconstructDeviceDatabaseStatsDetailEntry 7 }

affirmedServiceconstructDeviceDatabaseStatsDetailTotalEntry OBJECT-TYPE
    SYNTAX      Unsigned32
    MAX-ACCESS  read-only
    STATUS      current
    DESCRIPTION "Number Of Accepted Entries"
    ::= { affirmedServiceconstructDeviceDatabaseStatsDetailEntry 8 }

affirmedServiceconstructDeviceDatabaseStatsDetailEntries OBJECT-TYPE
    SYNTAX      String
    MAX-ACCESS  read-only
    STATUS      current
    DESCRIPTION "Accepted Entries"
    ::= { affirmedServiceconstructDeviceDatabaseStatsDetailEntry 9 }

affirmedServiceconstructDeviceDatabaseStatsDetailTotalReject OBJECT-TYPE
    SYNTAX      Unsigned32
    MAX-ACCESS  read-only
    STATUS      current
    DESCRIPTION "Number Of Rejected Entries"
    ::= { affirmedServiceconstructDeviceDatabaseStatsDetailEntry 10 }

affirmedServiceconstructDeviceDatabaseStatsDetailRejectedEntries OBJECT-TYPE
    SYNTAX      String
    MAX-ACCESS  read-only
    STATUS      current
    DESCRIPTION "Rejected Entries"
    ::= { affirmedServiceconstructDeviceDatabaseStatsDetailEntry 11 }

affirmedServiceconstructDeviceDatabaseStatsDetailImportFileName OBJECT-TYPE
    SYNTAX      String
    MAX-ACCESS  read-only
    STATUS      current
    DESCRIPTION "Import File Name"
    ::= { affirmedServiceconstructDeviceDatabaseStatsDetailEntry 12 }

affirmedServiceconstructFilterHashListStatsHistoryTable OBJECT-TYPE
    SYNTAX      SEQUENCE OF AffirmedServiceconstructFilterHashListStatsHistoryEntry
    MAX-ACCESS  not-accessible
    STATUS      current
    DESCRIPTION ""
    ::= { affirmedServiceconstructFilterHashListStats 1 }

affirmedServiceconstructFilterHashListStatsHistoryEntry OBJECT-TYPE
    SYNTAX      AffirmedServiceconstructFilterHashListStatsHistoryEntry
    MAX-ACCESS  not-accessible
    STATUS      current
    DESCRIPTION ""
    INDEX { affirmedServiceconstructFilterHashListStatsHistoryName }
        ::= { affirmedServiceconstructFilterHashListStatsHistoryTable 1 }

AffirmedServiceconstructFilterHashListStatsHistoryEntry ::=
    SEQUENCE {
        affirmedServiceconstructFilterHashListStatsHistoryName String,
        affirmedServiceconstructFilterHashListStatsHistoryResult String
    }

affirmedServiceconstructFilterHashListStatsHistoryName OBJECT-TYPE
    SYNTAX      String
    MAX-ACCESS  not-accessible
    STATUS      current
    DESCRIPTION "Filter-Hash-List name"
    ::= { affirmedServiceconstructFilterHashListStatsHistoryEntry 1 }

affirmedServiceconstructFilterHashListStatsHistoryResult OBJECT-TYPE
    SYNTAX      String
    MAX-ACCESS  read-only
    STATUS      current
    DESCRIPTION ""
    ::= { affirmedServiceconstructFilterHashListStatsHistoryEntry 2 }

affirmedServiceconstructFilterHashListStatsSummaryTable OBJECT-TYPE
    SYNTAX      SEQUENCE OF AffirmedServiceconstructFilterHashListStatsSummaryEntry
    MAX-ACCESS  not-accessible
    STATUS      current
    DESCRIPTION ""
    ::= { affirmedServiceconstructFilterHashListStats 2 }

affirmedServiceconstructFilterHashListStatsSummaryEntry OBJECT-TYPE
    SYNTAX      AffirmedServiceconstructFilterHashListStatsSummaryEntry
    MAX-ACCESS  not-accessible
    STATUS      current
    DESCRIPTION ""
    INDEX { affirmedServiceconstructFilterHashListStatsSummaryName }
        ::= { affirmedServiceconstructFilterHashListStatsSummaryTable 1 }

AffirmedServiceconstructFilterHashListStatsSummaryEntry ::=
    SEQUENCE {
        affirmedServiceconstructFilterHashListStatsSummaryName String,
        affirmedServiceconstructFilterHashListStatsSummaryLastTime String,
        affirmedServiceconstructFilterHashListStatsSummaryLastResult String,
        affirmedServiceconstructFilterHashListStatsSummaryLastImportType String,
        affirmedServiceconstructFilterHashListStatsSummaryLastImportNum Unsigned32,
        affirmedServiceconstructFilterHashListStatsSummaryLastSize Unsigned32,
        affirmedServiceconstructFilterHashListStatsSummaryNextTime String,
        affirmedServiceconstructFilterHashListStatsSummaryTotalEntry Unsigned32,
        affirmedServiceconstructFilterHashListStatsSummaryTotalReject Unsigned32,
        affirmedServiceconstructFilterHashListStatsSummaryImportFileName String
    }

affirmedServiceconstructFilterHashListStatsSummaryName OBJECT-TYPE
    SYNTAX      String
    MAX-ACCESS  not-accessible
    STATUS      current
    DESCRIPTION "Filter-Hash-List name"
    ::= { affirmedServiceconstructFilterHashListStatsSummaryEntry 1 }

affirmedServiceconstructFilterHashListStatsSummaryLastTime OBJECT-TYPE
    SYNTAX      String
    MAX-ACCESS  read-only
    STATUS      current
    DESCRIPTION "Last Import Time"
    ::= { affirmedServiceconstructFilterHashListStatsSummaryEntry 2 }

affirmedServiceconstructFilterHashListStatsSummaryLastResult OBJECT-TYPE
    SYNTAX      String
    MAX-ACCESS  read-only
    STATUS      current
    DESCRIPTION "Last Import Result"
    ::= { affirmedServiceconstructFilterHashListStatsSummaryEntry 3 }

affirmedServiceconstructFilterHashListStatsSummaryLastImportType OBJECT-TYPE
    SYNTAX      String
    MAX-ACCESS  read-only
    STATUS      current
    DESCRIPTION "Import Type"
    ::= { affirmedServiceconstructFilterHashListStatsSummaryEntry 4 }

affirmedServiceconstructFilterHashListStatsSummaryLastImportNum OBJECT-TYPE
    SYNTAX      Unsigned32
    MAX-ACCESS  read-only
    STATUS      current
    DESCRIPTION "Last Import Number"
    ::= { affirmedServiceconstructFilterHashListStatsSummaryEntry 5 }

affirmedServiceconstructFilterHashListStatsSummaryLastSize OBJECT-TYPE
    SYNTAX      Unsigned32
    MAX-ACCESS  read-only
    STATUS      current
    DESCRIPTION "Last Import File Size(Bytes)"
    ::= { affirmedServiceconstructFilterHashListStatsSummaryEntry 6 }

affirmedServiceconstructFilterHashListStatsSummaryNextTime OBJECT-TYPE
    SYNTAX      String
    MAX-ACCESS  read-only
    STATUS      current
    DESCRIPTION "Next Scheduled Import Time"
    ::= { affirmedServiceconstructFilterHashListStatsSummaryEntry 7 }

affirmedServiceconstructFilterHashListStatsSummaryTotalEntry OBJECT-TYPE
    SYNTAX      Unsigned32
    MAX-ACCESS  read-only
    STATUS      current
    DESCRIPTION "Number Of Accepted Entries"
    ::= { affirmedServiceconstructFilterHashListStatsSummaryEntry 8 }

affirmedServiceconstructFilterHashListStatsSummaryTotalReject OBJECT-TYPE
    SYNTAX      Unsigned32
    MAX-ACCESS  read-only
    STATUS      current
    DESCRIPTION "Number Of Rejected Entries"
    ::= { affirmedServiceconstructFilterHashListStatsSummaryEntry 9 }

affirmedServiceconstructFilterHashListStatsSummaryImportFileName OBJECT-TYPE
    SYNTAX      String
    MAX-ACCESS  read-only
    STATUS      current
    DESCRIPTION "Import File Name"
    ::= { affirmedServiceconstructFilterHashListStatsSummaryEntry 10 }

affirmedServiceconstructShowCodeMappingListTable OBJECT-TYPE
    SYNTAX      SEQUENCE OF AffirmedServiceconstructShowCodeMappingListEntry
    MAX-ACCESS  not-accessible
    STATUS      current
    DESCRIPTION ""
    ::= { affirmedServiceconstruct 7 }

affirmedServiceconstructShowCodeMappingListEntry OBJECT-TYPE
    SYNTAX      AffirmedServiceconstructShowCodeMappingListEntry
    MAX-ACCESS  not-accessible
    STATUS      current
    DESCRIPTION ""
    INDEX { affirmedServiceconstructShowCodeMappingListListName, affirmedServiceconstructShowCodeMappingListInCode, affirmedServiceconstructShowCodeMappingListGwName, affirmedServiceconstructShowCodeMappingListCodeType }
        ::= { affirmedServiceconstructShowCodeMappingListTable 1 }

AffirmedServiceconstructShowCodeMappingListEntry ::=
    SEQUENCE {
        affirmedServiceconstructShowCodeMappingListListName String,
        affirmedServiceconstructShowCodeMappingListInCode Unsigned32,
        affirmedServiceconstructShowCodeMappingListGwName String,
        affirmedServiceconstructShowCodeMappingListCodeType INTEGER,
        affirmedServiceconstructShowCodeMappingListOutCode Unsigned32,
        affirmedServiceconstructShowCodeMappingListInCodeUserDesc String
    }

affirmedServiceconstructShowCodeMappingListListName OBJECT-TYPE
    SYNTAX      String
    MAX-ACCESS  not-accessible
    STATUS      current
    DESCRIPTION "List Name"
    ::= { affirmedServiceconstructShowCodeMappingListEntry 1 }

affirmedServiceconstructShowCodeMappingListInCode OBJECT-TYPE
    SYNTAX      Unsigned32
    MAX-ACCESS  not-accessible
    STATUS      current
    DESCRIPTION "Incoming code value"
    ::= { affirmedServiceconstructShowCodeMappingListEntry 2 }

affirmedServiceconstructShowCodeMappingListGwName OBJECT-TYPE
    SYNTAX      String
    MAX-ACCESS  not-accessible
    STATUS      current
    DESCRIPTION "Gatway using the code"
    ::= { affirmedServiceconstructShowCodeMappingListEntry 3 }

affirmedServiceconstructShowCodeMappingListCodeType OBJECT-TYPE
    SYNTAX      INTEGER {unused(0),s2b(1),swm(2),s2a(3),sta(4),swm-experimental(5)}
    MAX-ACCESS  not-accessible
    STATUS      current
    DESCRIPTION "Type of code"
    ::= { affirmedServiceconstructShowCodeMappingListEntry 4 }

affirmedServiceconstructShowCodeMappingListOutCode OBJECT-TYPE
    SYNTAX      Unsigned32
    MAX-ACCESS  read-only
    STATUS      current
    DESCRIPTION "Outgoing code value"
    ::= { affirmedServiceconstructShowCodeMappingListEntry 5 }

affirmedServiceconstructShowCodeMappingListInCodeUserDesc OBJECT-TYPE
    SYNTAX      String
    MAX-ACCESS  read-only
    STATUS      current
    DESCRIPTION "Description of Incoming Code"
    ::= { affirmedServiceconstructShowCodeMappingListEntry 6 }

affirmedServiceconstructWorkflowDataStatsTable OBJECT-TYPE
    SYNTAX      SEQUENCE OF AffirmedServiceconstructWorkflowDataStatsEntry
    MAX-ACCESS  not-accessible
    STATUS      current
    DESCRIPTION ""
    ::= { affirmedServiceconstruct 3 }

affirmedServiceconstructWorkflowDataStatsEntry OBJECT-TYPE
    SYNTAX      AffirmedServiceconstructWorkflowDataStatsEntry
    MAX-ACCESS  not-accessible
    STATUS      current
    DESCRIPTION ""
    INDEX { affirmedServiceconstructWorkflowDataStatsDummyIndex }
        ::= { affirmedServiceconstructWorkflowDataStatsTable 1 }

AffirmedServiceconstructWorkflowDataStatsEntry ::=
    SEQUENCE {
        affirmedServiceconstructWorkflowDataStatsDummyIndex Unsigned32,
        affirmedServiceconstructWorkflowDataStatsLocalgirxpkts ConfdString,
        affirmedServiceconstructWorkflowDataStatsLocalgirxbytes ConfdString,
        affirmedServiceconstructWorkflowDataStatsLocalgitxpkts ConfdString,
        affirmedServiceconstructWorkflowDataStatsLocalgitxbytes ConfdString,
        affirmedServiceconstructWorkflowDataStatsLocalgitunnelrxpkts ConfdString,
        affirmedServiceconstructWorkflowDataStatsLocalgitunnelrxbytes ConfdString,
        affirmedServiceconstructWorkflowDataStatsLocalgierrorpkts ConfdString,
        affirmedServiceconstructWorkflowDataStatsLocalgierrorbytes ConfdString,
        affirmedServiceconstructWorkflowDataStatsLocalgnrxpkts ConfdString,
        affirmedServiceconstructWorkflowDataStatsLocalgnrxbytes ConfdString,
        affirmedServiceconstructWorkflowDataStatsLocalgntxpkts ConfdString,
        affirmedServiceconstructWorkflowDataStatsLocalgntxbytes ConfdString,
        affirmedServiceconstructWorkflowDataStatsLocalgntunnelrxpkts ConfdString,
        affirmedServiceconstructWorkflowDataStatsLocalgntunnelrxbytes ConfdString,
        affirmedServiceconstructWorkflowDataStatsLocalgnerrorpkts ConfdString,
        affirmedServiceconstructWorkflowDataStatsLocalgnerrorbytes ConfdString,
        affirmedServiceconstructWorkflowDataStatsFabricgirxpkts ConfdString,
        affirmedServiceconstructWorkflowDataStatsFabricgirxbytes ConfdString,
        affirmedServiceconstructWorkflowDataStatsFabricgitxpkts ConfdString,
        affirmedServiceconstructWorkflowDataStatsFabricgitxbytes ConfdString,
        affirmedServiceconstructWorkflowDataStatsFabricgitunnelrxpkts ConfdString,
        affirmedServiceconstructWorkflowDataStatsFabricgitunnelrxbytes ConfdString,
        affirmedServiceconstructWorkflowDataStatsFabricgierrorpkts ConfdString,
        affirmedServiceconstructWorkflowDataStatsFabricgierrorbytes ConfdString,
        affirmedServiceconstructWorkflowDataStatsFabricgnrxpkts ConfdString,
        affirmedServiceconstructWorkflowDataStatsFabricgnrxbytes ConfdString,
        affirmedServiceconstructWorkflowDataStatsFabricgntxpkts ConfdString,
        affirmedServiceconstructWorkflowDataStatsFabricgntxbytes ConfdString,
        affirmedServiceconstructWorkflowDataStatsFabricgntunnelrxpkts ConfdString,
        affirmedServiceconstructWorkflowDataStatsFabricgntunnelrxbytes ConfdString,
        affirmedServiceconstructWorkflowDataStatsFabricgnerrorpkts ConfdString,
        affirmedServiceconstructWorkflowDataStatsFabricgnerrorbytes ConfdString,
        affirmedServiceconstructWorkflowDataStatsTndrxpkts ConfdString,
        affirmedServiceconstructWorkflowDataStatsTndrxbytes ConfdString,
        affirmedServiceconstructWorkflowDataStatsTndtxpkts ConfdString,
        affirmedServiceconstructWorkflowDataStatsTndtxbytes ConfdString,
        affirmedServiceconstructWorkflowDataStatsTnderrortxpkts ConfdString,
        affirmedServiceconstructWorkflowDataStatsTnderrortxbytes ConfdString,
        affirmedServiceconstructWorkflowDataStatsForcedrops ConfdString,
        affirmedServiceconstructWorkflowDataStatsUerouterupstreamsubnetrxpkts ConfdString,
        affirmedServiceconstructWorkflowDataStatsUeroutertcpmssadjustedpkts ConfdString,
        affirmedServiceconstructWorkflowDataStatsGisessionlookup ConfdString,
        affirmedServiceconstructWorkflowDataStatsGnsessionlookup ConfdString,
        affirmedServiceconstructWorkflowDataStatsGnbearerlookup ConfdString,
        affirmedServiceconstructWorkflowDataStatsTndsessionlookup ConfdString,
        affirmedServiceconstructWorkflowDataStatsDiscardpkts ConfdString,
        affirmedServiceconstructWorkflowDataStatsUeroutertcpmssadjustedgntxpkts ConfdString,
        affirmedServiceconstructWorkflowDataStatsUeroutertcpmssadjusterrorpkts ConfdString,
        affirmedServiceconstructWorkflowDataStatsUlcolocatedsessionpkts ConfdString,
        affirmedServiceconstructWorkflowDataStatsDlcolocatedsessionpkts ConfdString
    }

affirmedServiceconstructWorkflowDataStatsDummyIndex OBJECT-TYPE
    SYNTAX      Unsigned32
    MAX-ACCESS  not-accessible
    STATUS      current
    DESCRIPTION ""
    ::= { affirmedServiceconstructWorkflowDataStatsEntry 1 }

affirmedServiceconstructWorkflowDataStatsLocalgirxpkts OBJECT-TYPE
    SYNTAX      ConfdString
    MAX-ACCESS  read-only
    STATUS      current
    DESCRIPTION "Local Gi received packets"
    ::= { affirmedServiceconstructWorkflowDataStatsEntry 2 }

affirmedServiceconstructWorkflowDataStatsLocalgirxbytes OBJECT-TYPE
    SYNTAX      ConfdString
    MAX-ACCESS  read-only
    STATUS      current
    DESCRIPTION "Local Gi received bytes"
    ::= { affirmedServiceconstructWorkflowDataStatsEntry 3 }

affirmedServiceconstructWorkflowDataStatsLocalgitxpkts OBJECT-TYPE
    SYNTAX      ConfdString
    MAX-ACCESS  read-only
    STATUS      current
    DESCRIPTION "Local Gi transmitted packets"
    ::= { affirmedServiceconstructWorkflowDataStatsEntry 4 }

affirmedServiceconstructWorkflowDataStatsLocalgitxbytes OBJECT-TYPE
    SYNTAX      ConfdString
    MAX-ACCESS  read-only
    STATUS      current
    DESCRIPTION "Local Gi transmitted bytes"
    ::= { affirmedServiceconstructWorkflowDataStatsEntry 5 }

affirmedServiceconstructWorkflowDataStatsLocalgitunnelrxpkts OBJECT-TYPE
    SYNTAX      ConfdString
    MAX-ACCESS  read-only
    STATUS      current
    DESCRIPTION "Local Gi tunnel received packets"
    ::= { affirmedServiceconstructWorkflowDataStatsEntry 6 }

affirmedServiceconstructWorkflowDataStatsLocalgitunnelrxbytes OBJECT-TYPE
    SYNTAX      ConfdString
    MAX-ACCESS  read-only
    STATUS      current
    DESCRIPTION "Local Gi tunnel received bytes"
    ::= { affirmedServiceconstructWorkflowDataStatsEntry 7 }

affirmedServiceconstructWorkflowDataStatsLocalgierrorpkts OBJECT-TYPE
    SYNTAX      ConfdString
    MAX-ACCESS  read-only
    STATUS      current
    DESCRIPTION "Local Gi error packets"
    ::= { affirmedServiceconstructWorkflowDataStatsEntry 8 }

affirmedServiceconstructWorkflowDataStatsLocalgierrorbytes OBJECT-TYPE
    SYNTAX      ConfdString
    MAX-ACCESS  read-only
    STATUS      current
    DESCRIPTION "Local Gi error bytes"
    ::= { affirmedServiceconstructWorkflowDataStatsEntry 9 }

affirmedServiceconstructWorkflowDataStatsLocalgnrxpkts OBJECT-TYPE
    SYNTAX      ConfdString
    MAX-ACCESS  read-only
    STATUS      current
    DESCRIPTION "Local Gn received packets"
    ::= { affirmedServiceconstructWorkflowDataStatsEntry 10 }

affirmedServiceconstructWorkflowDataStatsLocalgnrxbytes OBJECT-TYPE
    SYNTAX      ConfdString
    MAX-ACCESS  read-only
    STATUS      current
    DESCRIPTION "Local Gn received bytes"
    ::= { affirmedServiceconstructWorkflowDataStatsEntry 11 }

affirmedServiceconstructWorkflowDataStatsLocalgntxpkts OBJECT-TYPE
    SYNTAX      ConfdString
    MAX-ACCESS  read-only
    STATUS      current
    DESCRIPTION "Local Gn transmitted packets"
    ::= { affirmedServiceconstructWorkflowDataStatsEntry 12 }

affirmedServiceconstructWorkflowDataStatsLocalgntxbytes OBJECT-TYPE
    SYNTAX      ConfdString
    MAX-ACCESS  read-only
    STATUS      current
    DESCRIPTION "Local Gn transmitted bytes"
    ::= { affirmedServiceconstructWorkflowDataStatsEntry 13 }

affirmedServiceconstructWorkflowDataStatsLocalgntunnelrxpkts OBJECT-TYPE
    SYNTAX      ConfdString
    MAX-ACCESS  read-only
    STATUS      current
    DESCRIPTION "Local Gn tunnel received packets"
    ::= { affirmedServiceconstructWorkflowDataStatsEntry 14 }

affirmedServiceconstructWorkflowDataStatsLocalgntunnelrxbytes OBJECT-TYPE
    SYNTAX      ConfdString
    MAX-ACCESS  read-only
    STATUS      current
    DESCRIPTION "Local Gn tunnel received bytes"
    ::= { affirmedServiceconstructWorkflowDataStatsEntry 15 }

affirmedServiceconstructWorkflowDataStatsLocalgnerrorpkts OBJECT-TYPE
    SYNTAX      ConfdString
    MAX-ACCESS  read-only
    STATUS      current
    DESCRIPTION "Local Gn error packets"
    ::= { affirmedServiceconstructWorkflowDataStatsEntry 16 }

affirmedServiceconstructWorkflowDataStatsLocalgnerrorbytes OBJECT-TYPE
    SYNTAX      ConfdString
    MAX-ACCESS  read-only
    STATUS      current
    DESCRIPTION "Local Gn error bytes"
    ::= { affirmedServiceconstructWorkflowDataStatsEntry 17 }

affirmedServiceconstructWorkflowDataStatsFabricgirxpkts OBJECT-TYPE
    SYNTAX      ConfdString
    MAX-ACCESS  read-only
    STATUS      current
    DESCRIPTION "Fabric Gi received packets"
    ::= { affirmedServiceconstructWorkflowDataStatsEntry 18 }

affirmedServiceconstructWorkflowDataStatsFabricgirxbytes OBJECT-TYPE
    SYNTAX      ConfdString
    MAX-ACCESS  read-only
    STATUS      current
    DESCRIPTION "Fabric Gi received bytes"
    ::= { affirmedServiceconstructWorkflowDataStatsEntry 19 }

affirmedServiceconstructWorkflowDataStatsFabricgitxpkts OBJECT-TYPE
    SYNTAX      ConfdString
    MAX-ACCESS  read-only
    STATUS      current
    DESCRIPTION "Fabric Gi transmitted packets"
    ::= { affirmedServiceconstructWorkflowDataStatsEntry 20 }

affirmedServiceconstructWorkflowDataStatsFabricgitxbytes OBJECT-TYPE
    SYNTAX      ConfdString
    MAX-ACCESS  read-only
    STATUS      current
    DESCRIPTION "Fabric Gi transmitted bytes"
    ::= { affirmedServiceconstructWorkflowDataStatsEntry 21 }

affirmedServiceconstructWorkflowDataStatsFabricgitunnelrxpkts OBJECT-TYPE
    SYNTAX      ConfdString
    MAX-ACCESS  read-only
    STATUS      current
    DESCRIPTION "Fabric Gi tunnel received packets"
    ::= { affirmedServiceconstructWorkflowDataStatsEntry 22 }

affirmedServiceconstructWorkflowDataStatsFabricgitunnelrxbytes OBJECT-TYPE
    SYNTAX      ConfdString
    MAX-ACCESS  read-only
    STATUS      current
    DESCRIPTION "Fabric Gi tunnel received bytes"
    ::= { affirmedServiceconstructWorkflowDataStatsEntry 23 }

affirmedServiceconstructWorkflowDataStatsFabricgierrorpkts OBJECT-TYPE
    SYNTAX      ConfdString
    MAX-ACCESS  read-only
    STATUS      current
    DESCRIPTION "Fabric Gi error packets"
    ::= { affirmedServiceconstructWorkflowDataStatsEntry 24 }

affirmedServiceconstructWorkflowDataStatsFabricgierrorbytes OBJECT-TYPE
    SYNTAX      ConfdString
    MAX-ACCESS  read-only
    STATUS      current
    DESCRIPTION "Fabric Gi error bytes"
    ::= { affirmedServiceconstructWorkflowDataStatsEntry 25 }

affirmedServiceconstructWorkflowDataStatsFabricgnrxpkts OBJECT-TYPE
    SYNTAX      ConfdString
    MAX-ACCESS  read-only
    STATUS      current
    DESCRIPTION "Fabric Gn received packets"
    ::= { affirmedServiceconstructWorkflowDataStatsEntry 26 }

affirmedServiceconstructWorkflowDataStatsFabricgnrxbytes OBJECT-TYPE
    SYNTAX      ConfdString
    MAX-ACCESS  read-only
    STATUS      current
    DESCRIPTION "Fabric Gn received bytes"
    ::= { affirmedServiceconstructWorkflowDataStatsEntry 27 }

affirmedServiceconstructWorkflowDataStatsFabricgntxpkts OBJECT-TYPE
    SYNTAX      ConfdString
    MAX-ACCESS  read-only
    STATUS      current
    DESCRIPTION "Fabric Gn transmitted packets"
    ::= { affirmedServiceconstructWorkflowDataStatsEntry 28 }

affirmedServiceconstructWorkflowDataStatsFabricgntxbytes OBJECT-TYPE
    SYNTAX      ConfdString
    MAX-ACCESS  read-only
    STATUS      current
    DESCRIPTION "Fabric Gn transmitted bytes"
    ::= { affirmedServiceconstructWorkflowDataStatsEntry 29 }

affirmedServiceconstructWorkflowDataStatsFabricgntunnelrxpkts OBJECT-TYPE
    SYNTAX      ConfdString
    MAX-ACCESS  read-only
    STATUS      current
    DESCRIPTION "Fabric Gn tunnel received packets"
    ::= { affirmedServiceconstructWorkflowDataStatsEntry 30 }

affirmedServiceconstructWorkflowDataStatsFabricgntunnelrxbytes OBJECT-TYPE
    SYNTAX      ConfdString
    MAX-ACCESS  read-only
    STATUS      current
    DESCRIPTION "Fabric Gn tunnel received bytes"
    ::= { affirmedServiceconstructWorkflowDataStatsEntry 31 }

affirmedServiceconstructWorkflowDataStatsFabricgnerrorpkts OBJECT-TYPE
    SYNTAX      ConfdString
    MAX-ACCESS  read-only
    STATUS      current
    DESCRIPTION "Fabric Gn error packets"
    ::= { affirmedServiceconstructWorkflowDataStatsEntry 32 }

affirmedServiceconstructWorkflowDataStatsFabricgnerrorbytes OBJECT-TYPE
    SYNTAX      ConfdString
    MAX-ACCESS  read-only
    STATUS      current
    DESCRIPTION "Fabric Gn error bytes"
    ::= { affirmedServiceconstructWorkflowDataStatsEntry 33 }

affirmedServiceconstructWorkflowDataStatsTndrxpkts OBJECT-TYPE
    SYNTAX      ConfdString
    MAX-ACCESS  read-only
    STATUS      current
    DESCRIPTION "TND rx packets"
    ::= { affirmedServiceconstructWorkflowDataStatsEntry 34 }

affirmedServiceconstructWorkflowDataStatsTndrxbytes OBJECT-TYPE
    SYNTAX      ConfdString
    MAX-ACCESS  read-only
    STATUS      current
    DESCRIPTION "TND rx bytes"
    ::= { affirmedServiceconstructWorkflowDataStatsEntry 35 }

affirmedServiceconstructWorkflowDataStatsTndtxpkts OBJECT-TYPE
    SYNTAX      ConfdString
    MAX-ACCESS  read-only
    STATUS      current
    DESCRIPTION "TND tx packets"
    ::= { affirmedServiceconstructWorkflowDataStatsEntry 36 }

affirmedServiceconstructWorkflowDataStatsTndtxbytes OBJECT-TYPE
    SYNTAX      ConfdString
    MAX-ACCESS  read-only
    STATUS      current
    DESCRIPTION "TND tx bytes"
    ::= { affirmedServiceconstructWorkflowDataStatsEntry 37 }

affirmedServiceconstructWorkflowDataStatsTnderrortxpkts OBJECT-TYPE
    SYNTAX      ConfdString
    MAX-ACCESS  read-only
    STATUS      current
    DESCRIPTION "TND tx error packets"
    ::= { affirmedServiceconstructWorkflowDataStatsEntry 38 }

affirmedServiceconstructWorkflowDataStatsTnderrortxbytes OBJECT-TYPE
    SYNTAX      ConfdString
    MAX-ACCESS  read-only
    STATUS      current
    DESCRIPTION "TND error bytes"
    ::= { affirmedServiceconstructWorkflowDataStatsEntry 39 }

affirmedServiceconstructWorkflowDataStatsForcedrops OBJECT-TYPE
    SYNTAX      ConfdString
    MAX-ACCESS  read-only
    STATUS      current
    DESCRIPTION "Force drops"
    ::= { affirmedServiceconstructWorkflowDataStatsEntry 40 }

affirmedServiceconstructWorkflowDataStatsUerouterupstreamsubnetrxpkts OBJECT-TYPE
    SYNTAX      ConfdString
    MAX-ACCESS  read-only
    STATUS      current
    DESCRIPTION "UE router upstream subnet rx packets"
    ::= { affirmedServiceconstructWorkflowDataStatsEntry 41 }

affirmedServiceconstructWorkflowDataStatsUeroutertcpmssadjustedpkts OBJECT-TYPE
    SYNTAX      ConfdString
    MAX-ACCESS  read-only
    STATUS      current
    DESCRIPTION "UE router TCP MSS adjusted packets"
    ::= { affirmedServiceconstructWorkflowDataStatsEntry 42 }

affirmedServiceconstructWorkflowDataStatsGisessionlookup OBJECT-TYPE
    SYNTAX      ConfdString
    MAX-ACCESS  read-only
    STATUS      current
    DESCRIPTION "Gi session lookup"
    ::= { affirmedServiceconstructWorkflowDataStatsEntry 43 }

affirmedServiceconstructWorkflowDataStatsGnsessionlookup OBJECT-TYPE
    SYNTAX      ConfdString
    MAX-ACCESS  read-only
    STATUS      current
    DESCRIPTION "Gn session lookup"
    ::= { affirmedServiceconstructWorkflowDataStatsEntry 44 }

affirmedServiceconstructWorkflowDataStatsGnbearerlookup OBJECT-TYPE
    SYNTAX      ConfdString
    MAX-ACCESS  read-only
    STATUS      current
    DESCRIPTION "Gn bearer lookup"
    ::= { affirmedServiceconstructWorkflowDataStatsEntry 45 }

affirmedServiceconstructWorkflowDataStatsTndsessionlookup OBJECT-TYPE
    SYNTAX      ConfdString
    MAX-ACCESS  read-only
    STATUS      current
    DESCRIPTION "TND session lookup"
    ::= { affirmedServiceconstructWorkflowDataStatsEntry 46 }

affirmedServiceconstructWorkflowDataStatsDiscardpkts OBJECT-TYPE
    SYNTAX      ConfdString
    MAX-ACCESS  read-only
    STATUS      current
    DESCRIPTION "Discard packets"
    ::= { affirmedServiceconstructWorkflowDataStatsEntry 47 }

affirmedServiceconstructWorkflowDataStatsUeroutertcpmssadjustedgntxpkts OBJECT-TYPE
    SYNTAX      ConfdString
    MAX-ACCESS  read-only
    STATUS      current
    DESCRIPTION "UE router TCP MSS adjusted packets transmitted on GN"
    ::= { affirmedServiceconstructWorkflowDataStatsEntry 48 }

affirmedServiceconstructWorkflowDataStatsUeroutertcpmssadjusterrorpkts OBJECT-TYPE
    SYNTAX      ConfdString
    MAX-ACCESS  read-only
    STATUS      current
    DESCRIPTION "UE router TCP MSS adjust error packets"
    ::= { affirmedServiceconstructWorkflowDataStatsEntry 49 }

affirmedServiceconstructWorkflowDataStatsUlcolocatedsessionpkts OBJECT-TYPE
    SYNTAX      ConfdString
    MAX-ACCESS  read-only
    STATUS      current
    DESCRIPTION "Uplink packets to a co-located session"
    ::= { affirmedServiceconstructWorkflowDataStatsEntry 50 }

affirmedServiceconstructWorkflowDataStatsDlcolocatedsessionpkts OBJECT-TYPE
    SYNTAX      ConfdString
    MAX-ACCESS  read-only
    STATUS      current
    DESCRIPTION "Downlink packets to a co-located session"
    ::= { affirmedServiceconstructWorkflowDataStatsEntry 51 }

affirmedServiceconstructManifestInterfaceStatsStatisticsClusterLevelSummaryTable OBJECT-TYPE
    SYNTAX      SEQUENCE OF AffirmedServiceconstructManifestInterfaceStatsStatisticsClusterLevelSummaryEntry
    MAX-ACCESS  not-accessible
    STATUS      current
    DESCRIPTION ""
    ::= { affirmedServiceconstructManifestInterfaceStatsStatisticsClusterLevel 1 }

affirmedServiceconstructManifestInterfaceStatsStatisticsClusterLevelSummaryEntry OBJECT-TYPE
    SYNTAX      AffirmedServiceconstructManifestInterfaceStatsStatisticsClusterLevelSummaryEntry
    MAX-ACCESS  not-accessible
    STATUS      current
    DESCRIPTION ""
    INDEX { affirmedServiceconstructManifestInterfaceStatsStatisticsClusterLevelSummaryChassis }
        ::= { affirmedServiceconstructManifestInterfaceStatsStatisticsClusterLevelSummaryTable 1 }

AffirmedServiceconstructManifestInterfaceStatsStatisticsClusterLevelSummaryEntry ::=
    SEQUENCE {
        affirmedServiceconstructManifestInterfaceStatsStatisticsClusterLevelSummaryChassis Unsigned32,
        affirmedServiceconstructManifestInterfaceStatsStatisticsClusterLevelSummaryNummfitotalrequestmessage ConfdString,
        affirmedServiceconstructManifestInterfaceStatsStatisticsClusterLevelSummaryNummfitotalrequestcount ConfdString,
        affirmedServiceconstructManifestInterfaceStatsStatisticsClusterLevelSummaryNummfitotalresponsesuccess ConfdString,
        affirmedServiceconstructManifestInterfaceStatsStatisticsClusterLevelSummaryNummfitotalresponsefailure ConfdString
    }

affirmedServiceconstructManifestInterfaceStatsStatisticsClusterLevelSummaryChassis OBJECT-TYPE
    SYNTAX      Unsigned32
    MAX-ACCESS  not-accessible
    STATUS      current
    DESCRIPTION "chassis ID"
    ::= { affirmedServiceconstructManifestInterfaceStatsStatisticsClusterLevelSummaryEntry 1 }

affirmedServiceconstructManifestInterfaceStatsStatisticsClusterLevelSummaryNummfitotalrequestmessage OBJECT-TYPE
    SYNTAX      ConfdString
    MAX-ACCESS  read-only
    STATUS      current
    DESCRIPTION "Number of Total MFI requests received from GW"
    ::= { affirmedServiceconstructManifestInterfaceStatsStatisticsClusterLevelSummaryEntry 2 }

affirmedServiceconstructManifestInterfaceStatsStatisticsClusterLevelSummaryNummfitotalrequestcount OBJECT-TYPE
    SYNTAX      ConfdString
    MAX-ACCESS  read-only
    STATUS      current
    DESCRIPTION "Number of Total MFI TDF application IDs received from GW"
    ::= { affirmedServiceconstructManifestInterfaceStatsStatisticsClusterLevelSummaryEntry 3 }

affirmedServiceconstructManifestInterfaceStatsStatisticsClusterLevelSummaryNummfitotalresponsesuccess OBJECT-TYPE
    SYNTAX      ConfdString
    MAX-ACCESS  read-only
    STATUS      current
    DESCRIPTION "Number of Total MFI Responses sent back to GW"
    ::= { affirmedServiceconstructManifestInterfaceStatsStatisticsClusterLevelSummaryEntry 4 }

affirmedServiceconstructManifestInterfaceStatsStatisticsClusterLevelSummaryNummfitotalresponsefailure OBJECT-TYPE
    SYNTAX      ConfdString
    MAX-ACCESS  read-only
    STATUS      current
    DESCRIPTION "Number of Total MFI Response Failed sending to GW"
    ::= { affirmedServiceconstructManifestInterfaceStatsStatisticsClusterLevelSummaryEntry 5 }

affirmedServiceconstructManifestInterfaceStatsStatisticsClusterLevelDetailTable OBJECT-TYPE
    SYNTAX      SEQUENCE OF AffirmedServiceconstructManifestInterfaceStatsStatisticsClusterLevelDetailEntry
    MAX-ACCESS  not-accessible
    STATUS      current
    DESCRIPTION ""
    ::= { affirmedServiceconstructManifestInterfaceStatsStatisticsClusterLevel 2 }

affirmedServiceconstructManifestInterfaceStatsStatisticsClusterLevelDetailEntry OBJECT-TYPE
    SYNTAX      AffirmedServiceconstructManifestInterfaceStatsStatisticsClusterLevelDetailEntry
    MAX-ACCESS  not-accessible
    STATUS      current
    DESCRIPTION ""
    INDEX { affirmedServiceconstructManifestInterfaceStatsStatisticsClusterLevelDetailChassis }
        ::= { affirmedServiceconstructManifestInterfaceStatsStatisticsClusterLevelDetailTable 1 }

AffirmedServiceconstructManifestInterfaceStatsStatisticsClusterLevelDetailEntry ::=
    SEQUENCE {
        affirmedServiceconstructManifestInterfaceStatsStatisticsClusterLevelDetailChassis Unsigned32,
        affirmedServiceconstructManifestInterfaceStatsStatisticsClusterLevelDetailNummfirequestnoservicename ConfdString,
        affirmedServiceconstructManifestInterfaceStatsStatisticsClusterLevelDetailNummfirequestnosessionid ConfdString,
        affirmedServiceconstructManifestInterfaceStatsStatisticsClusterLevelDetailNummfirequestnotdfapplicationid ConfdString,
        affirmedServiceconstructManifestInterfaceStatsStatisticsClusterLevelDetailNummfirequestnoprofileautoindex ConfdString,
        affirmedServiceconstructManifestInterfaceStatsStatisticsClusterLevelDetailNummfirequestnomanifesturl ConfdString,
        affirmedServiceconstructManifestInterfaceStatsStatisticsClusterLevelDetailNummfirequestgwservicenotfound ConfdString,
        affirmedServiceconstructManifestInterfaceStatsStatisticsClusterLevelDetailNummfirequestmfiprofilenotfound ConfdString,
        affirmedServiceconstructManifestInterfaceStatsStatisticsClusterLevelDetailNummfirequestmfiprofiledisabled ConfdString,
        affirmedServiceconstructManifestInterfaceStatsStatisticsClusterLevelDetailNummfirequestportsnotinitialized ConfdString,
        affirmedServiceconstructManifestInterfaceStatsStatisticsClusterLevelDetailNummfimanifestdownloadattempts ConfdString,
        affirmedServiceconstructManifestInterfaceStatsStatisticsClusterLevelDetailNummfimanifestdownloadsuccesses ConfdString,
        affirmedServiceconstructManifestInterfaceStatsStatisticsClusterLevelDetailNummfimanifestdownloaderrors ConfdString,
        affirmedServiceconstructManifestInterfaceStatsStatisticsClusterLevelDetailNummfimanifestinvalid ConfdString,
        affirmedServiceconstructManifestInterfaceStatsStatisticsClusterLevelDetailNummfimanifestreceived ConfdString,
        affirmedServiceconstructManifestInterfaceStatsStatisticsClusterLevelDetailNummficertificatedownloadattempts ConfdString,
        affirmedServiceconstructManifestInterfaceStatsStatisticsClusterLevelDetailNummficertificatedownloadsuccesses ConfdString,
        affirmedServiceconstructManifestInterfaceStatsStatisticsClusterLevelDetailNummficertificatedownloaderrors ConfdString,
        affirmedServiceconstructManifestInterfaceStatsStatisticsClusterLevelDetailNummficertificateinvalid ConfdString,
        affirmedServiceconstructManifestInterfaceStatsStatisticsClusterLevelDetailNummficertificatereceived ConfdString,
        affirmedServiceconstructManifestInterfaceStatsStatisticsClusterLevelDetailNummficrldownloadattempts ConfdString,
        affirmedServiceconstructManifestInterfaceStatsStatisticsClusterLevelDetailNummficrldownloadsuccesses ConfdString,
        affirmedServiceconstructManifestInterfaceStatsStatisticsClusterLevelDetailNummficrldownloaderrors ConfdString,
        affirmedServiceconstructManifestInterfaceStatsStatisticsClusterLevelDetailNummficrlinvalid ConfdString,
        affirmedServiceconstructManifestInterfaceStatsStatisticsClusterLevelDetailNummficrlreceived ConfdString,
        affirmedServiceconstructManifestInterfaceStatsStatisticsClusterLevelDetailNummfiparserdecodeerrors ConfdString,
        affirmedServiceconstructManifestInterfaceStatsStatisticsClusterLevelDetailNummfiparsersignatureverificationfailures ConfdString,
        affirmedServiceconstructManifestInterfaceStatsStatisticsClusterLevelDetailNummfiparserexpiredvaliditytime ConfdString,
        affirmedServiceconstructManifestInterfaceStatsStatisticsClusterLevelDetailNummfidnsqueriessent ConfdString,
        affirmedServiceconstructManifestInterfaceStatsStatisticsClusterLevelDetailNummfidnsresponsessuccess ConfdString,
        affirmedServiceconstructManifestInterfaceStatsStatisticsClusterLevelDetailNummfidnssendfailed ConfdString,
        affirmedServiceconstructManifestInterfaceStatsStatisticsClusterLevelDetailNummfidnsresponsesfailed ConfdString,
        affirmedServiceconstructManifestInterfaceStatsStatisticsClusterLevelDetailNummfiresponsesendsuccesses ConfdString,
        affirmedServiceconstructManifestInterfaceStatsStatisticsClusterLevelDetailNummfiresponsesendfailures ConfdString,
        affirmedServiceconstructManifestInterfaceStatsStatisticsClusterLevelDetailNummfiresponsetftempty ConfdString,
        affirmedServiceconstructManifestInterfaceStatsStatisticsClusterLevelDetailNummfiresponsenoservicename ConfdString,
        affirmedServiceconstructManifestInterfaceStatsStatisticsClusterLevelDetailNummfiresponseprocessingfailures ConfdString,
        affirmedServiceconstructManifestInterfaceStatsStatisticsClusterLevelDetailNummfiparserunsupportedversion ConfdString,
        affirmedServiceconstructManifestInterfaceStatsStatisticsClusterLevelDetailNummfiparserjsonparseerror ConfdString,
        affirmedServiceconstructManifestInterfaceStatsStatisticsClusterLevelDetailNummfidnsdomainsreceived ConfdString
    }

affirmedServiceconstructManifestInterfaceStatsStatisticsClusterLevelDetailChassis OBJECT-TYPE
    SYNTAX      Unsigned32
    MAX-ACCESS  not-accessible
    STATUS      current
    DESCRIPTION "chassis ID"
    ::= { affirmedServiceconstructManifestInterfaceStatsStatisticsClusterLevelDetailEntry 1 }

affirmedServiceconstructManifestInterfaceStatsStatisticsClusterLevelDetailNummfirequestnoservicename OBJECT-TYPE
    SYNTAX      ConfdString
    MAX-ACCESS  read-only
    STATUS      current
    DESCRIPTION "Number of MFI requests without Service Name"
    ::= { affirmedServiceconstructManifestInterfaceStatsStatisticsClusterLevelDetailEntry 2 }

affirmedServiceconstructManifestInterfaceStatsStatisticsClusterLevelDetailNummfirequestnosessionid OBJECT-TYPE
    SYNTAX      ConfdString
    MAX-ACCESS  read-only
    STATUS      current
    DESCRIPTION "Number of MFI requests without GW Session ID"
    ::= { affirmedServiceconstructManifestInterfaceStatsStatisticsClusterLevelDetailEntry 3 }

affirmedServiceconstructManifestInterfaceStatsStatisticsClusterLevelDetailNummfirequestnotdfapplicationid OBJECT-TYPE
    SYNTAX      ConfdString
    MAX-ACCESS  read-only
    STATUS      current
    DESCRIPTION "Number of MFI requests without TDF Application ID"
    ::= { affirmedServiceconstructManifestInterfaceStatsStatisticsClusterLevelDetailEntry 4 }

affirmedServiceconstructManifestInterfaceStatsStatisticsClusterLevelDetailNummfirequestnoprofileautoindex OBJECT-TYPE
    SYNTAX      ConfdString
    MAX-ACCESS  read-only
    STATUS      current
    DESCRIPTION "Number of MFI requests without MFI Profile AutoIndex"
    ::= { affirmedServiceconstructManifestInterfaceStatsStatisticsClusterLevelDetailEntry 5 }

affirmedServiceconstructManifestInterfaceStatsStatisticsClusterLevelDetailNummfirequestnomanifesturl OBJECT-TYPE
    SYNTAX      ConfdString
    MAX-ACCESS  read-only
    STATUS      current
    DESCRIPTION "Number of MFI requests without Manifest URL"
    ::= { affirmedServiceconstructManifestInterfaceStatsStatisticsClusterLevelDetailEntry 6 }

affirmedServiceconstructManifestInterfaceStatsStatisticsClusterLevelDetailNummfirequestgwservicenotfound OBJECT-TYPE
    SYNTAX      ConfdString
    MAX-ACCESS  read-only
    STATUS      current
    DESCRIPTION "Number of MFI requests where GW Service Name is not found"
    ::= { affirmedServiceconstructManifestInterfaceStatsStatisticsClusterLevelDetailEntry 7 }

affirmedServiceconstructManifestInterfaceStatsStatisticsClusterLevelDetailNummfirequestmfiprofilenotfound OBJECT-TYPE
    SYNTAX      ConfdString
    MAX-ACCESS  read-only
    STATUS      current
    DESCRIPTION "Number of MFI requests where MFI Profile is not found"
    ::= { affirmedServiceconstructManifestInterfaceStatsStatisticsClusterLevelDetailEntry 8 }

affirmedServiceconstructManifestInterfaceStatsStatisticsClusterLevelDetailNummfirequestmfiprofiledisabled OBJECT-TYPE
    SYNTAX      ConfdString
    MAX-ACCESS  read-only
    STATUS      current
    DESCRIPTION "Number of MFI requests where MFI Profile is Disabled"
    ::= { affirmedServiceconstructManifestInterfaceStatsStatisticsClusterLevelDetailEntry 9 }

affirmedServiceconstructManifestInterfaceStatsStatisticsClusterLevelDetailNummfirequestportsnotinitialized OBJECT-TYPE
    SYNTAX      ConfdString
    MAX-ACCESS  read-only
    STATUS      current
    DESCRIPTION "Number of MFI requests where Ports are not Initialized"
    ::= { affirmedServiceconstructManifestInterfaceStatsStatisticsClusterLevelDetailEntry 10 }

affirmedServiceconstructManifestInterfaceStatsStatisticsClusterLevelDetailNummfimanifestdownloadattempts OBJECT-TYPE
    SYNTAX      ConfdString
    MAX-ACCESS  read-only
    STATUS      current
    DESCRIPTION "Number of MFI Manifest Download Attempts"
    ::= { affirmedServiceconstructManifestInterfaceStatsStatisticsClusterLevelDetailEntry 11 }

affirmedServiceconstructManifestInterfaceStatsStatisticsClusterLevelDetailNummfimanifestdownloadsuccesses OBJECT-TYPE
    SYNTAX      ConfdString
    MAX-ACCESS  read-only
    STATUS      current
    DESCRIPTION "Number of MFI Manifest Download Successes"
    ::= { affirmedServiceconstructManifestInterfaceStatsStatisticsClusterLevelDetailEntry 12 }

affirmedServiceconstructManifestInterfaceStatsStatisticsClusterLevelDetailNummfimanifestdownloaderrors OBJECT-TYPE
    SYNTAX      ConfdString
    MAX-ACCESS  read-only
    STATUS      current
    DESCRIPTION "Number of MFI Manifest Download Errors"
    ::= { affirmedServiceconstructManifestInterfaceStatsStatisticsClusterLevelDetailEntry 13 }

affirmedServiceconstructManifestInterfaceStatsStatisticsClusterLevelDetailNummfimanifestinvalid OBJECT-TYPE
    SYNTAX      ConfdString
    MAX-ACCESS  read-only
    STATUS      current
    DESCRIPTION "Number of MFI Manifests that are invalid"
    ::= { affirmedServiceconstructManifestInterfaceStatsStatisticsClusterLevelDetailEntry 14 }

affirmedServiceconstructManifestInterfaceStatsStatisticsClusterLevelDetailNummfimanifestreceived OBJECT-TYPE
    SYNTAX      ConfdString
    MAX-ACCESS  read-only
    STATUS      current
    DESCRIPTION "Number of MFI Manifests that are received"
    ::= { affirmedServiceconstructManifestInterfaceStatsStatisticsClusterLevelDetailEntry 15 }

affirmedServiceconstructManifestInterfaceStatsStatisticsClusterLevelDetailNummficertificatedownloadattempts OBJECT-TYPE
    SYNTAX      ConfdString
    MAX-ACCESS  read-only
    STATUS      current
    DESCRIPTION "Number of MFI Manifest Certificate Download Attempts"
    ::= { affirmedServiceconstructManifestInterfaceStatsStatisticsClusterLevelDetailEntry 16 }

affirmedServiceconstructManifestInterfaceStatsStatisticsClusterLevelDetailNummficertificatedownloadsuccesses OBJECT-TYPE
    SYNTAX      ConfdString
    MAX-ACCESS  read-only
    STATUS      current
    DESCRIPTION "Number of MFI Manifest Certificate Download Successes"
    ::= { affirmedServiceconstructManifestInterfaceStatsStatisticsClusterLevelDetailEntry 17 }

affirmedServiceconstructManifestInterfaceStatsStatisticsClusterLevelDetailNummficertificatedownloaderrors OBJECT-TYPE
    SYNTAX      ConfdString
    MAX-ACCESS  read-only
    STATUS      current
    DESCRIPTION "Number of MFI Manifest Certificate Download Errors"
    ::= { affirmedServiceconstructManifestInterfaceStatsStatisticsClusterLevelDetailEntry 18 }

affirmedServiceconstructManifestInterfaceStatsStatisticsClusterLevelDetailNummficertificateinvalid OBJECT-TYPE
    SYNTAX      ConfdString
    MAX-ACCESS  read-only
    STATUS      current
    DESCRIPTION "Number of MFI Manifest Certificates that are invalid"
    ::= { affirmedServiceconstructManifestInterfaceStatsStatisticsClusterLevelDetailEntry 19 }

affirmedServiceconstructManifestInterfaceStatsStatisticsClusterLevelDetailNummficertificatereceived OBJECT-TYPE
    SYNTAX      ConfdString
    MAX-ACCESS  read-only
    STATUS      current
    DESCRIPTION "Number of MFI Manifest Certificates that are received"
    ::= { affirmedServiceconstructManifestInterfaceStatsStatisticsClusterLevelDetailEntry 20 }

affirmedServiceconstructManifestInterfaceStatsStatisticsClusterLevelDetailNummficrldownloadattempts OBJECT-TYPE
    SYNTAX      ConfdString
    MAX-ACCESS  read-only
    STATUS      current
    DESCRIPTION "Number of MFI Manifest CRL Download Attempts"
    ::= { affirmedServiceconstructManifestInterfaceStatsStatisticsClusterLevelDetailEntry 21 }

affirmedServiceconstructManifestInterfaceStatsStatisticsClusterLevelDetailNummficrldownloadsuccesses OBJECT-TYPE
    SYNTAX      ConfdString
    MAX-ACCESS  read-only
    STATUS      current
    DESCRIPTION "Number of MFI Manifest CRL Download Successes"
    ::= { affirmedServiceconstructManifestInterfaceStatsStatisticsClusterLevelDetailEntry 22 }

affirmedServiceconstructManifestInterfaceStatsStatisticsClusterLevelDetailNummficrldownloaderrors OBJECT-TYPE
    SYNTAX      ConfdString
    MAX-ACCESS  read-only
    STATUS      current
    DESCRIPTION "Number of MFI Manifest CRL Download Errors"
    ::= { affirmedServiceconstructManifestInterfaceStatsStatisticsClusterLevelDetailEntry 23 }

affirmedServiceconstructManifestInterfaceStatsStatisticsClusterLevelDetailNummficrlinvalid OBJECT-TYPE
    SYNTAX      ConfdString
    MAX-ACCESS  read-only
    STATUS      current
    DESCRIPTION "Number of MFI Manifest CRLs that are invalid"
    ::= { affirmedServiceconstructManifestInterfaceStatsStatisticsClusterLevelDetailEntry 24 }

affirmedServiceconstructManifestInterfaceStatsStatisticsClusterLevelDetailNummficrlreceived OBJECT-TYPE
    SYNTAX      ConfdString
    MAX-ACCESS  read-only
    STATUS      current
    DESCRIPTION "Number of MFI Manifest CRLs that are received"
    ::= { affirmedServiceconstructManifestInterfaceStatsStatisticsClusterLevelDetailEntry 25 }

affirmedServiceconstructManifestInterfaceStatsStatisticsClusterLevelDetailNummfiparserdecodeerrors OBJECT-TYPE
    SYNTAX      ConfdString
    MAX-ACCESS  read-only
    STATUS      current
    DESCRIPTION "Number of MFI Manifest Decode Errors"
    ::= { affirmedServiceconstructManifestInterfaceStatsStatisticsClusterLevelDetailEntry 26 }

affirmedServiceconstructManifestInterfaceStatsStatisticsClusterLevelDetailNummfiparsersignatureverificationfailures OBJECT-TYPE
    SYNTAX      ConfdString
    MAX-ACCESS  read-only
    STATUS      current
    DESCRIPTION "Number of MFI Manifest Signature Verification Failures"
    ::= { affirmedServiceconstructManifestInterfaceStatsStatisticsClusterLevelDetailEntry 27 }

affirmedServiceconstructManifestInterfaceStatsStatisticsClusterLevelDetailNummfiparserexpiredvaliditytime OBJECT-TYPE
    SYNTAX      ConfdString
    MAX-ACCESS  read-only
    STATUS      current
    DESCRIPTION "Number of MFI Manifest Expired Validity Time"
    ::= { affirmedServiceconstructManifestInterfaceStatsStatisticsClusterLevelDetailEntry 28 }

affirmedServiceconstructManifestInterfaceStatsStatisticsClusterLevelDetailNummfidnsqueriessent OBJECT-TYPE
    SYNTAX      ConfdString
    MAX-ACCESS  read-only
    STATUS      current
    DESCRIPTION "Number of MFI Manifest DNS Queries Sent"
    ::= { affirmedServiceconstructManifestInterfaceStatsStatisticsClusterLevelDetailEntry 29 }

affirmedServiceconstructManifestInterfaceStatsStatisticsClusterLevelDetailNummfidnsresponsessuccess OBJECT-TYPE
    SYNTAX      ConfdString
    MAX-ACCESS  read-only
    STATUS      current
    DESCRIPTION "Number of MFI Manifest DNS Responses Success"
    ::= { affirmedServiceconstructManifestInterfaceStatsStatisticsClusterLevelDetailEntry 30 }

affirmedServiceconstructManifestInterfaceStatsStatisticsClusterLevelDetailNummfidnssendfailed OBJECT-TYPE
    SYNTAX      ConfdString
    MAX-ACCESS  read-only
    STATUS      current
    DESCRIPTION "Number of MFI Manifest DNS Send Failures"
    ::= { affirmedServiceconstructManifestInterfaceStatsStatisticsClusterLevelDetailEntry 31 }

affirmedServiceconstructManifestInterfaceStatsStatisticsClusterLevelDetailNummfidnsresponsesfailed OBJECT-TYPE
    SYNTAX      ConfdString
    MAX-ACCESS  read-only
    STATUS      current
    DESCRIPTION "Number of MFI Manifest DNS Responses Failed"
    ::= { affirmedServiceconstructManifestInterfaceStatsStatisticsClusterLevelDetailEntry 32 }

affirmedServiceconstructManifestInterfaceStatsStatisticsClusterLevelDetailNummfiresponsesendsuccesses OBJECT-TYPE
    SYNTAX      ConfdString
    MAX-ACCESS  read-only
    STATUS      current
    DESCRIPTION "Number of MFI Response Send Successes"
    ::= { affirmedServiceconstructManifestInterfaceStatsStatisticsClusterLevelDetailEntry 33 }

affirmedServiceconstructManifestInterfaceStatsStatisticsClusterLevelDetailNummfiresponsesendfailures OBJECT-TYPE
    SYNTAX      ConfdString
    MAX-ACCESS  read-only
    STATUS      current
    DESCRIPTION "Number of MFI Response Send Failures"
    ::= { affirmedServiceconstructManifestInterfaceStatsStatisticsClusterLevelDetailEntry 34 }

affirmedServiceconstructManifestInterfaceStatsStatisticsClusterLevelDetailNummfiresponsetftempty OBJECT-TYPE
    SYNTAX      ConfdString
    MAX-ACCESS  read-only
    STATUS      current
    DESCRIPTION "Number of MFI Response TFT empty"
    ::= { affirmedServiceconstructManifestInterfaceStatsStatisticsClusterLevelDetailEntry 35 }

affirmedServiceconstructManifestInterfaceStatsStatisticsClusterLevelDetailNummfiresponsenoservicename OBJECT-TYPE
    SYNTAX      ConfdString
    MAX-ACCESS  read-only
    STATUS      current
    DESCRIPTION "Number of MFI Response Failures due to Service Name not Found"
    ::= { affirmedServiceconstructManifestInterfaceStatsStatisticsClusterLevelDetailEntry 36 }

affirmedServiceconstructManifestInterfaceStatsStatisticsClusterLevelDetailNummfiresponseprocessingfailures OBJECT-TYPE
    SYNTAX      ConfdString
    MAX-ACCESS  read-only
    STATUS      current
    DESCRIPTION "Number of MFI Response Processing Failures"
    ::= { affirmedServiceconstructManifestInterfaceStatsStatisticsClusterLevelDetailEntry 37 }

affirmedServiceconstructManifestInterfaceStatsStatisticsClusterLevelDetailNummfiparserunsupportedversion OBJECT-TYPE
    SYNTAX      ConfdString
    MAX-ACCESS  read-only
    STATUS      current
    DESCRIPTION "Number of MFI Manifest Unsupported Version"
    ::= { affirmedServiceconstructManifestInterfaceStatsStatisticsClusterLevelDetailEntry 38 }

affirmedServiceconstructManifestInterfaceStatsStatisticsClusterLevelDetailNummfiparserjsonparseerror OBJECT-TYPE
    SYNTAX      ConfdString
    MAX-ACCESS  read-only
    STATUS      current
    DESCRIPTION "Number of MFI Manifest JSON Parse Error"
    ::= { affirmedServiceconstructManifestInterfaceStatsStatisticsClusterLevelDetailEntry 39 }

affirmedServiceconstructManifestInterfaceStatsStatisticsClusterLevelDetailNummfidnsdomainsreceived OBJECT-TYPE
    SYNTAX      ConfdString
    MAX-ACCESS  read-only
    STATUS      current
    DESCRIPTION "Number of MFI Manifest Domains Received in the JSON"
    ::= { affirmedServiceconstructManifestInterfaceStatsStatisticsClusterLevelDetailEntry 40 }

affirmedServiceconstructRadiusMappingStatisticsTable OBJECT-TYPE
    SYNTAX      SEQUENCE OF AffirmedServiceconstructRadiusMappingStatisticsEntry
    MAX-ACCESS  not-accessible
    STATUS      current
    DESCRIPTION ""
    ::= { affirmedServiceconstructRadiusMapping 1 }

affirmedServiceconstructRadiusMappingStatisticsEntry OBJECT-TYPE
    SYNTAX      AffirmedServiceconstructRadiusMappingStatisticsEntry
    MAX-ACCESS  not-accessible
    STATUS      current
    DESCRIPTION ""
    INDEX { affirmedServiceconstructRadiusMappingStatisticsName }
        ::= { affirmedServiceconstructRadiusMappingStatisticsTable 1 }

AffirmedServiceconstructRadiusMappingStatisticsEntry ::=
    SEQUENCE {
        affirmedServiceconstructRadiusMappingStatisticsName String,
        affirmedServiceconstructRadiusMappingStatisticsNumOutgoingReplacements ConfdString,
        affirmedServiceconstructRadiusMappingStatisticsNumOutgoingRemovals ConfdString,
        affirmedServiceconstructRadiusMappingStatisticsNumOutgoingFormatSubstitutions ConfdString,
        affirmedServiceconstructRadiusMappingStatisticsNumOutgoingReplacementFailures ConfdString,
        affirmedServiceconstructRadiusMappingStatisticsNumIncomingReplacements ConfdString,
        affirmedServiceconstructRadiusMappingStatisticsNumIncomingRemovals ConfdString,
        affirmedServiceconstructRadiusMappingStatisticsNumIncomingMatches ConfdString,
        affirmedServiceconstructRadiusMappingStatisticsNumIncomingMatchFailures ConfdString,
        affirmedServiceconstructRadiusMappingStatisticsNumIncomingReplacementFailures ConfdString
    }

affirmedServiceconstructRadiusMappingStatisticsName OBJECT-TYPE
    SYNTAX      String
    MAX-ACCESS  not-accessible
    STATUS      current
    DESCRIPTION "Mapping Template Name"
    ::= { affirmedServiceconstructRadiusMappingStatisticsEntry 1 }

affirmedServiceconstructRadiusMappingStatisticsNumOutgoingReplacements OBJECT-TYPE
    SYNTAX      ConfdString
    MAX-ACCESS  read-only
    STATUS      current
    DESCRIPTION "Total number of outgoing replacements"
    ::= { affirmedServiceconstructRadiusMappingStatisticsEntry 2 }

affirmedServiceconstructRadiusMappingStatisticsNumOutgoingRemovals OBJECT-TYPE
    SYNTAX      ConfdString
    MAX-ACCESS  read-only
    STATUS      current
    DESCRIPTION "Total number of outgoing attributes removed"
    ::= { affirmedServiceconstructRadiusMappingStatisticsEntry 3 }

affirmedServiceconstructRadiusMappingStatisticsNumOutgoingFormatSubstitutions OBJECT-TYPE
    SYNTAX      ConfdString
    MAX-ACCESS  read-only
    STATUS      current
    DESCRIPTION "Number of outgoing substitutions using from-format"
    ::= { affirmedServiceconstructRadiusMappingStatisticsEntry 4 }

affirmedServiceconstructRadiusMappingStatisticsNumOutgoingReplacementFailures OBJECT-TYPE
    SYNTAX      ConfdString
    MAX-ACCESS  read-only
    STATUS      current
    DESCRIPTION "Number of outgoing replacement failures"
    ::= { affirmedServiceconstructRadiusMappingStatisticsEntry 5 }

affirmedServiceconstructRadiusMappingStatisticsNumIncomingReplacements OBJECT-TYPE
    SYNTAX      ConfdString
    MAX-ACCESS  read-only
    STATUS      current
    DESCRIPTION "Total number of incoming replacements"
    ::= { affirmedServiceconstructRadiusMappingStatisticsEntry 6 }

affirmedServiceconstructRadiusMappingStatisticsNumIncomingRemovals OBJECT-TYPE
    SYNTAX      ConfdString
    MAX-ACCESS  read-only
    STATUS      current
    DESCRIPTION "Total number of incoming attributes removed"
    ::= { affirmedServiceconstructRadiusMappingStatisticsEntry 7 }

affirmedServiceconstructRadiusMappingStatisticsNumIncomingMatches OBJECT-TYPE
    SYNTAX      ConfdString
    MAX-ACCESS  read-only
    STATUS      current
    DESCRIPTION "Number of incoming matches using to-format"
    ::= { affirmedServiceconstructRadiusMappingStatisticsEntry 8 }

affirmedServiceconstructRadiusMappingStatisticsNumIncomingMatchFailures OBJECT-TYPE
    SYNTAX      ConfdString
    MAX-ACCESS  read-only
    STATUS      current
    DESCRIPTION "Number of match failures using to-format"
    ::= { affirmedServiceconstructRadiusMappingStatisticsEntry 9 }

affirmedServiceconstructRadiusMappingStatisticsNumIncomingReplacementFailures OBJECT-TYPE
    SYNTAX      ConfdString
    MAX-ACCESS  read-only
    STATUS      current
    DESCRIPTION "Number of incoming replacement failures"
    ::= { affirmedServiceconstructRadiusMappingStatisticsEntry 10 }

affirmedServiceconstructDhcpMappingStatisticsTable OBJECT-TYPE
    SYNTAX      SEQUENCE OF AffirmedServiceconstructDhcpMappingStatisticsEntry
    MAX-ACCESS  not-accessible
    STATUS      current
    DESCRIPTION ""
    ::= { affirmedServiceconstructDhcpMapping 1 }

affirmedServiceconstructDhcpMappingStatisticsEntry OBJECT-TYPE
    SYNTAX      AffirmedServiceconstructDhcpMappingStatisticsEntry
    MAX-ACCESS  not-accessible
    STATUS      current
    DESCRIPTION ""
    INDEX { affirmedServiceconstructDhcpMappingStatisticsName }
        ::= { affirmedServiceconstructDhcpMappingStatisticsTable 1 }

AffirmedServiceconstructDhcpMappingStatisticsEntry ::=
    SEQUENCE {
        affirmedServiceconstructDhcpMappingStatisticsName String,
        affirmedServiceconstructDhcpMappingStatisticsNumOutgoingReplacements ConfdString,
        affirmedServiceconstructDhcpMappingStatisticsNumOutgoingRemovals ConfdString,
        affirmedServiceconstructDhcpMappingStatisticsNumOutgoingFormatSubstitutions ConfdString,
        affirmedServiceconstructDhcpMappingStatisticsNumOutgoingReplacementFailures ConfdString,
        affirmedServiceconstructDhcpMappingStatisticsNumIncomingReplacements ConfdString,
        affirmedServiceconstructDhcpMappingStatisticsNumIncomingRemovals ConfdString,
        affirmedServiceconstructDhcpMappingStatisticsNumIncomingMatches ConfdString,
        affirmedServiceconstructDhcpMappingStatisticsNumIncomingMatchFailures ConfdString,
        affirmedServiceconstructDhcpMappingStatisticsNumIncomingReplacementFailures ConfdString
    }

affirmedServiceconstructDhcpMappingStatisticsName OBJECT-TYPE
    SYNTAX      String
    MAX-ACCESS  not-accessible
    STATUS      current
    DESCRIPTION "Mapping Template Name"
    ::= { affirmedServiceconstructDhcpMappingStatisticsEntry 1 }

affirmedServiceconstructDhcpMappingStatisticsNumOutgoingReplacements OBJECT-TYPE
    SYNTAX      ConfdString
    MAX-ACCESS  read-only
    STATUS      current
    DESCRIPTION "Total number of outgoing replacements"
    ::= { affirmedServiceconstructDhcpMappingStatisticsEntry 2 }

affirmedServiceconstructDhcpMappingStatisticsNumOutgoingRemovals OBJECT-TYPE
    SYNTAX      ConfdString
    MAX-ACCESS  read-only
    STATUS      current
    DESCRIPTION "Total number of outgoing attributes removed"
    ::= { affirmedServiceconstructDhcpMappingStatisticsEntry 3 }

affirmedServiceconstructDhcpMappingStatisticsNumOutgoingFormatSubstitutions OBJECT-TYPE
    SYNTAX      ConfdString
    MAX-ACCESS  read-only
    STATUS      current
    DESCRIPTION "Number of outgoing substitutions using from-format"
    ::= { affirmedServiceconstructDhcpMappingStatisticsEntry 4 }

affirmedServiceconstructDhcpMappingStatisticsNumOutgoingReplacementFailures OBJECT-TYPE
    SYNTAX      ConfdString
    MAX-ACCESS  read-only
    STATUS      current
    DESCRIPTION "Number of outgoing replacement failures"
    ::= { affirmedServiceconstructDhcpMappingStatisticsEntry 5 }

affirmedServiceconstructDhcpMappingStatisticsNumIncomingReplacements OBJECT-TYPE
    SYNTAX      ConfdString
    MAX-ACCESS  read-only
    STATUS      current
    DESCRIPTION "Total number of incoming replacements"
    ::= { affirmedServiceconstructDhcpMappingStatisticsEntry 6 }

affirmedServiceconstructDhcpMappingStatisticsNumIncomingRemovals OBJECT-TYPE
    SYNTAX      ConfdString
    MAX-ACCESS  read-only
    STATUS      current
    DESCRIPTION "Total number of incoming attributes removed"
    ::= { affirmedServiceconstructDhcpMappingStatisticsEntry 7 }

affirmedServiceconstructDhcpMappingStatisticsNumIncomingMatches OBJECT-TYPE
    SYNTAX      ConfdString
    MAX-ACCESS  read-only
    STATUS      current
    DESCRIPTION "Number of incoming matches using to-format"
    ::= { affirmedServiceconstructDhcpMappingStatisticsEntry 8 }

affirmedServiceconstructDhcpMappingStatisticsNumIncomingMatchFailures OBJECT-TYPE
    SYNTAX      ConfdString
    MAX-ACCESS  read-only
    STATUS      current
    DESCRIPTION "Number of match failures using to-format"
    ::= { affirmedServiceconstructDhcpMappingStatisticsEntry 9 }

affirmedServiceconstructDhcpMappingStatisticsNumIncomingReplacementFailures OBJECT-TYPE
    SYNTAX      ConfdString
    MAX-ACCESS  read-only
    STATUS      current
    DESCRIPTION "Number of incoming replacement failures"
    ::= { affirmedServiceconstructDhcpMappingStatisticsEntry 10 }

END

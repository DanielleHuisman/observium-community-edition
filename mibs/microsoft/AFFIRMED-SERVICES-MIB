AFFIRMED-SERVICES-MIB DEFINITIONS ::= BEGIN
IMPORTS
    MODULE-IDENTITY, OBJECT-TYPE,
    Integer32, Unsigned32, Counter32, Counter64,
    Gauge32, IpAddress
        FROM SNMPv2-SMI
    TEXTUAL-CONVENTION, RowStatus, DateAndTime,
    TruthValue
        FROM SNMPv2-TC
;

affirmedServicesMIB MODULE-IDENTITY
    ORGANIZATION "Affirmed Networks, Inc."
    CONTACT-INFO "Affirmed Networks, Inc. 35 Nagog Park, Acton, MA, USA"
    DESCRIPTION ""
    ::= { 1 3 6 1 4 1 37963 10 3 }

ConfdString ::= TEXTUAL-CONVENTION
    DISPLAY-HINT "1t"
    STATUS      current
    DESCRIPTION "xs: and confd: types mapped to strings"
    SYNTAX      OCTET STRING

String ::= TEXTUAL-CONVENTION
    DISPLAY-HINT "1t"
    STATUS      current
    DESCRIPTION "xs:string"
    SYNTAX      OCTET STRING

affirmedServices OBJECT IDENTIFIER ::= { affirmedServicesMIB 1 }

affirmedServicesContentHttpServerService OBJECT IDENTIFIER ::= { affirmedServices 10 }

affirmedServicesContentHttpServerServiceStatistics OBJECT IDENTIFIER ::= { affirmedServicesContentHttpServerService 1 }

affirmedServicesContentHttpServerServiceStatisticsCluster-level OBJECT IDENTIFIER ::= { affirmedServicesContentHttpServerServiceStatistics 3 }

affirmedServicesContentHttpServerServiceStatisticsNode-level OBJECT IDENTIFIER ::= { affirmedServicesContentHttpServerServiceStatistics 4 }

affirmedServicesContentHttpServerServiceStatisticsChassisLevel OBJECT IDENTIFIER ::= { affirmedServicesContentHttpServerServiceStatistics 1 }

affirmedServicesContentHttpServerServiceStatisticsChassisLevelServerPlugin OBJECT IDENTIFIER ::= { affirmedServicesContentHttpServerServiceStatisticsChassisLevel 1 }

affirmedServicesContentHttpServerServiceStatisticsChassisLevelContentInsertion OBJECT IDENTIFIER ::= { affirmedServicesContentHttpServerServiceStatisticsChassisLevel 2 }

affirmedServicesContentHttpServerServiceStatisticsSlotLevel OBJECT IDENTIFIER ::= { affirmedServicesContentHttpServerServiceStatistics 2 }

affirmedServicesContentHttpServerServiceStatisticsSlotLevelServerPlugin OBJECT IDENTIFIER ::= { affirmedServicesContentHttpServerServiceStatisticsSlotLevel 1 }

affirmedServicesContentHttpServerServiceStatisticsSlotLevelContentInsertion OBJECT IDENTIFIER ::= { affirmedServicesContentHttpServerServiceStatisticsSlotLevel 2 }

affirmedServicesDnsServerService OBJECT IDENTIFIER ::= { affirmedServices 14 }

affirmedServicesDnsServerServiceStatistics OBJECT IDENTIFIER ::= { affirmedServicesDnsServerService 1 }

affirmedServicesDnsServerServiceStatisticsCluster-level OBJECT IDENTIFIER ::= { affirmedServicesDnsServerServiceStatistics 1 }

affirmedServicesDnsServerServiceStatisticsNode-level OBJECT IDENTIFIER ::= { affirmedServicesDnsServerServiceStatistics 2 }

affirmedServicesQos OBJECT IDENTIFIER ::= { affirmedServices 4 }

affirmedServicesVideoAdaptationService OBJECT IDENTIFIER ::= { affirmedServices 11 }

affirmedServicesVideoAdaptationServiceStatistics OBJECT IDENTIFIER ::= { affirmedServicesVideoAdaptationService 1 }

affirmedServicesVideoAdaptationServiceStatisticsChassisLevel OBJECT IDENTIFIER ::= { affirmedServicesVideoAdaptationServiceStatistics 1 }

affirmedServicesVideoAdaptationServiceStatisticsChassisLevelOnlineTranscoding OBJECT IDENTIFIER ::= { affirmedServicesVideoAdaptationServiceStatisticsChassisLevel 1 }

affirmedServicesVideoAdaptationServiceStatisticsChassisLevelOfflineTranscoding OBJECT IDENTIFIER ::= { affirmedServicesVideoAdaptationServiceStatisticsChassisLevel 2 }

affirmedServicesVideoAdaptationServiceStatisticsSlotLevel OBJECT IDENTIFIER ::= { affirmedServicesVideoAdaptationServiceStatistics 2 }

affirmedServicesVideoAdaptationServiceStatisticsSlotLevelOnlineTranscoding OBJECT IDENTIFIER ::= { affirmedServicesVideoAdaptationServiceStatisticsSlotLevel 1 }

affirmedServicesVideoAdaptationServiceStatisticsSlotLevelOfflineTranscoding OBJECT IDENTIFIER ::= { affirmedServicesVideoAdaptationServiceStatisticsSlotLevel 2 }

affirmedServicesContentFilterService OBJECT IDENTIFIER ::= { affirmedServices 2 }

affirmedServicesContentFilterServiceStatistics OBJECT IDENTIFIER ::= { affirmedServicesContentFilterService 3 }

affirmedServicesContentFilterServiceStatisticsCluster-level OBJECT IDENTIFIER ::= { affirmedServicesContentFilterServiceStatistics 1 }

affirmedServicesContentFilterServiceStatisticsNode-level OBJECT IDENTIFIER ::= { affirmedServicesContentFilterServiceStatistics 2 }

affirmedServicesContentHttpProxyService OBJECT IDENTIFIER ::= { affirmedServices 5 }

affirmedServicesContentHttpProxyServiceLtmiKeyStats OBJECT IDENTIFIER ::= { affirmedServicesContentHttpProxyService 2 }

affirmedServicesContentHttpProxyServiceStatistics OBJECT IDENTIFIER ::= { affirmedServicesContentHttpProxyService 3 }

affirmedServicesContentHttpProxyServiceStatisticsCluster-level OBJECT IDENTIFIER ::= { affirmedServicesContentHttpProxyServiceStatistics 4 }

affirmedServicesContentHttpProxyServiceStatisticsNode-level OBJECT IDENTIFIER ::= { affirmedServicesContentHttpProxyServiceStatistics 5 }

affirmedServicesContentHttpProxyServiceStatisticsGridLevel OBJECT IDENTIFIER ::= { affirmedServicesContentHttpProxyServiceStatistics 1 }

affirmedServicesContentHttpProxyServiceStatisticsGridLevelVideoPacing OBJECT IDENTIFIER ::= { affirmedServicesContentHttpProxyServiceStatisticsGridLevel 1 }

affirmedServicesContentHttpProxyServiceStatisticsGridLevelVideoPacingDetail OBJECT IDENTIFIER ::= { affirmedServicesContentHttpProxyServiceStatisticsGridLevelVideoPacing 2 }

affirmedServicesContentHttpProxyServiceStatisticsGridLevelPVideoPacing OBJECT IDENTIFIER ::= { affirmedServicesContentHttpProxyServiceStatisticsGridLevel 2 }

affirmedServicesContentHttpProxyServiceStatisticsGridLevelPVideoPacingDetail OBJECT IDENTIFIER ::= { affirmedServicesContentHttpProxyServiceStatisticsGridLevelPVideoPacing 2 }

affirmedServicesContentHttpProxyServiceStatisticsChassisLevel OBJECT IDENTIFIER ::= { affirmedServicesContentHttpProxyServiceStatistics 2 }

affirmedServicesContentHttpProxyServiceStatisticsChassisLevelVideoPacing OBJECT IDENTIFIER ::= { affirmedServicesContentHttpProxyServiceStatisticsChassisLevel 1 }

affirmedServicesContentHttpProxyServiceStatisticsChassisLevelVideoPacingDetail OBJECT IDENTIFIER ::= { affirmedServicesContentHttpProxyServiceStatisticsChassisLevelVideoPacing 2 }

affirmedServicesContentHttpProxyServiceStatisticsChassisLevelPVideoPacing OBJECT IDENTIFIER ::= { affirmedServicesContentHttpProxyServiceStatisticsChassisLevel 2 }

affirmedServicesContentHttpProxyServiceStatisticsChassisLevelPVideoPacingDetail OBJECT IDENTIFIER ::= { affirmedServicesContentHttpProxyServiceStatisticsChassisLevelPVideoPacing 2 }

affirmedServicesContentHttpProxyServiceStatisticsChassisLevelOptimizationSavings OBJECT IDENTIFIER ::= { affirmedServicesContentHttpProxyServiceStatisticsChassisLevel 4 }

affirmedServicesContentHttpProxyServiceStatisticsChassisLevelContentInsertion OBJECT IDENTIFIER ::= { affirmedServicesContentHttpProxyServiceStatisticsChassisLevel 3 }

affirmedServicesContentHttpProxyServiceStatisticsChassisLevelTollFreeData OBJECT IDENTIFIER ::= { affirmedServicesContentHttpProxyServiceStatisticsChassisLevel 5 }

affirmedServicesContentHttpProxyServiceStatisticsChassisLevelAbrRateLimiting OBJECT IDENTIFIER ::= { affirmedServicesContentHttpProxyServiceStatisticsChassisLevel 6 }

affirmedServicesContentHttpProxyServiceStatisticsChassisLevelTcpSplicing OBJECT IDENTIFIER ::= { affirmedServicesContentHttpProxyServiceStatisticsChassisLevel 7 }

affirmedServicesContentHttpProxyServiceStatisticsChassisLevelBuffer OBJECT IDENTIFIER ::= { affirmedServicesContentHttpProxyServiceStatisticsChassisLevel 8 }

affirmedServicesContentHttpProxyServiceStatisticsChassisLevelTcpMeasurement OBJECT IDENTIFIER ::= { affirmedServicesContentHttpProxyServiceStatisticsChassisLevel 9 }

affirmedServicesContentHttpProxyServiceStatisticsChassisLevelTcpMeasurements OBJECT IDENTIFIER ::= { affirmedServicesContentHttpProxyServiceStatisticsChassisLevel 10 }

affirmedServicesContentHttpProxyServiceStatisticsChassisLevelUdpProxy OBJECT IDENTIFIER ::= { affirmedServicesContentHttpProxyServiceStatisticsChassisLevel 23 }

affirmedServicesContentHttpProxyServiceStatisticsChassisLevelWebImageOpt OBJECT IDENTIFIER ::= { affirmedServicesContentHttpProxyServiceStatisticsChassisLevel 14 }

affirmedServicesContentHttpProxyServiceStatisticsChassisLevelMediaType OBJECT IDENTIFIER ::= { affirmedServicesContentHttpProxyServiceStatisticsChassisLevel 11 }

affirmedServicesContentHttpProxyServiceStatisticsSlotLevel OBJECT IDENTIFIER ::= { affirmedServicesContentHttpProxyServiceStatistics 3 }

affirmedServicesContentHttpProxyServiceStatisticsSlotLevelContentInsertion OBJECT IDENTIFIER ::= { affirmedServicesContentHttpProxyServiceStatisticsSlotLevel 1 }

affirmedServicesContentHttpProxyServiceStatisticsSlotLevelTollFreeData OBJECT IDENTIFIER ::= { affirmedServicesContentHttpProxyServiceStatisticsSlotLevel 2 }

affirmedServicesContentHttpProxyServiceStatisticsSlotLevelTcpSplicing OBJECT IDENTIFIER ::= { affirmedServicesContentHttpProxyServiceStatisticsSlotLevel 3 }

affirmedServicesContentHttpProxyServiceStatisticsSlotLevelAbrRateLimiting OBJECT IDENTIFIER ::= { affirmedServicesContentHttpProxyServiceStatisticsSlotLevel 4 }

affirmedServicesContentHttpProxyServiceStatisticsSlotLevelBuffer OBJECT IDENTIFIER ::= { affirmedServicesContentHttpProxyServiceStatisticsSlotLevel 5 }

affirmedServicesContentHttpProxyServiceStatisticsSlotLevelTcpMeasurement OBJECT IDENTIFIER ::= { affirmedServicesContentHttpProxyServiceStatisticsSlotLevel 6 }

affirmedServicesContentHttpProxyServiceStatisticsSlotLevelTcpMeasurements OBJECT IDENTIFIER ::= { affirmedServicesContentHttpProxyServiceStatisticsSlotLevel 7 }

affirmedServicesContentHttpProxyServiceStatisticsSlotLevelUdpProxy OBJECT IDENTIFIER ::= { affirmedServicesContentHttpProxyServiceStatisticsSlotLevel 20 }

affirmedServicesContentHttpProxyServiceStatisticsSlotLevelWebImageOpt OBJECT IDENTIFIER ::= { affirmedServicesContentHttpProxyServiceStatisticsSlotLevel 11 }

affirmedServicesContentHttpProxyServiceStatisticsSlotLevelMediaType OBJECT IDENTIFIER ::= { affirmedServicesContentHttpProxyServiceStatisticsSlotLevel 8 }

affirmedServicesCharging OBJECT IDENTIFIER ::= { affirmedServices 3 }

affirmedServicesSteering OBJECT IDENTIFIER ::= { affirmedServices 1 }

affirmedServicesContentCacheProxyService OBJECT IDENTIFIER ::= { affirmedServices 12 }

affirmedServicesContentCacheProxyServiceStatistics OBJECT IDENTIFIER ::= { affirmedServicesContentCacheProxyService 1 }

affirmedServicesContentCacheProxyServiceStatisticsCluster-level OBJECT IDENTIFIER ::= { affirmedServicesContentCacheProxyServiceStatistics 1 }

affirmedServicesContentCacheProxyServiceStatisticsNode-level OBJECT IDENTIFIER ::= { affirmedServicesContentCacheProxyServiceStatistics 2 }

affirmedServicesMetering OBJECT IDENTIFIER ::= { affirmedServices 7 }

affirmedServicesDnsProxyService OBJECT IDENTIFIER ::= { affirmedServices 6 }

affirmedServicesDnsProxyServiceDnsReverseCache OBJECT IDENTIFIER ::= { affirmedServicesDnsProxyService 5 }

affirmedServicesDnsProxyServiceDnsReverseCacheBackgroundResolution OBJECT IDENTIFIER ::= { affirmedServicesDnsProxyServiceDnsReverseCache 1 }

affirmedServicesDnsProxyServiceStatistics OBJECT IDENTIFIER ::= { affirmedServicesDnsProxyService 6 }

affirmedServicesDnsProxyServiceStatisticsClusterLevel OBJECT IDENTIFIER ::= { affirmedServicesDnsProxyServiceStatistics 1 }

affirmedServicesNatService OBJECT IDENTIFIER ::= { affirmedServices 9 }

affirmedServicesNatServiceNat OBJECT IDENTIFIER ::= { affirmedServicesNatService 3 }

affirmedServicesNatServiceNatClusterLevel OBJECT IDENTIFIER ::= { affirmedServicesNatServiceNat 1 }

affirmedServicesNatServiceNatNodeLevel OBJECT IDENTIFIER ::= { affirmedServicesNatServiceNat 2 }

affirmedServicesNatServiceNatSession OBJECT IDENTIFIER ::= { affirmedServicesNatServiceNat 3 }

affirmedServicesNatServiceNatSessionFlow-group OBJECT IDENTIFIER ::= { affirmedServicesNatServiceNatSession 1 }

affirmedServicesNatServiceNatStatistical OBJECT IDENTIFIER ::= { affirmedServicesNatServiceNat 4 }

affirmedServicesNatServiceNatGuaranteed OBJECT IDENTIFIER ::= { affirmedServicesNatServiceNat 5 }

affirmedServicesNatServiceNatDeterministic OBJECT IDENTIFIER ::= { affirmedServicesNatServiceNat 6 }

affirmedServicesNatServiceNatPerfStats OBJECT IDENTIFIER ::= { affirmedServicesNatServiceNat 7 }

affirmedServicesNatServiceNatPerfStatsNodeLevel OBJECT IDENTIFIER ::= { affirmedServicesNatServiceNatPerfStats 2 }

affirmedServicesNatServiceNatPerfStatsClusterLevel OBJECT IDENTIFIER ::= { affirmedServicesNatServiceNatPerfStats 3 }

affirmedServicesNatServiceConnTracker OBJECT IDENTIFIER ::= { affirmedServicesNatService 4 }

affirmedServicesNatServiceConnTrackerClusterLevel OBJECT IDENTIFIER ::= { affirmedServicesNatServiceConnTracker 1 }

affirmedServicesNatServiceConnTrackerNodeLevel OBJECT IDENTIFIER ::= { affirmedServicesNatServiceConnTracker 2 }

affirmedServicesContentHealthCheckService OBJECT IDENTIFIER ::= { affirmedServices 13 }

affirmedServicesContentHealthCheckServiceStatistics OBJECT IDENTIFIER ::= { affirmedServicesContentHealthCheckService 1 }

affirmedServicesContentHealthCheckServiceStatisticsCluster-level OBJECT IDENTIFIER ::= { affirmedServicesContentHealthCheckServiceStatistics 1 }

affirmedServicesContentWapGwService OBJECT IDENTIFIER ::= { affirmedServices 8 }

affirmedServicesContentWapGwServiceStatistics OBJECT IDENTIFIER ::= { affirmedServicesContentWapGwService 2 }

affirmedServicesContentWapGwServiceStatisticsChassisLevel OBJECT IDENTIFIER ::= { affirmedServicesContentWapGwServiceStatistics 1 }

affirmedServicesContentWapGwServiceStatisticsNodeLevel OBJECT IDENTIFIER ::= { affirmedServicesContentWapGwServiceStatistics 2 }

affirmedServicesContentHttpServerServiceStatisticsCluster-levelSummaryTable OBJECT-TYPE
    SYNTAX      SEQUENCE OF AffirmedServicesContentHttpServerServiceStatisticsCluster-levelSummaryEntry
    MAX-ACCESS  not-accessible
    STATUS      current
    DESCRIPTION ""
    ::= { affirmedServicesContentHttpServerServiceStatisticsCluster-level 1 }

affirmedServicesContentHttpServerServiceStatisticsCluster-levelSummaryEntry OBJECT-TYPE
    SYNTAX      AffirmedServicesContentHttpServerServiceStatisticsCluster-levelSummaryEntry
    MAX-ACCESS  not-accessible
    STATUS      current
    DESCRIPTION ""
    INDEX { affirmedServicesContentHttpServerServiceStatisticsCluster-levelSummaryChassis }
        ::= { affirmedServicesContentHttpServerServiceStatisticsCluster-levelSummaryTable 1 }

AffirmedServicesContentHttpServerServiceStatisticsCluster-levelSummaryEntry ::=
    SEQUENCE {
        affirmedServicesContentHttpServerServiceStatisticsCluster-levelSummaryChassis Unsigned32,
        affirmedServicesContentHttpServerServiceStatisticsCluster-levelSummaryNumserverserviceattempts ConfdString,
        affirmedServicesContentHttpServerServiceStatisticsCluster-levelSummaryNumserverservicesuccess ConfdString,
        affirmedServicesContentHttpServerServiceStatisticsCluster-levelSummaryNumserverserviceabortedbyclient ConfdString,
        affirmedServicesContentHttpServerServiceStatisticsCluster-levelSummaryNumserverservicefailed ConfdString
    }

affirmedServicesContentHttpServerServiceStatisticsCluster-levelSummaryChassis OBJECT-TYPE
    SYNTAX      Unsigned32
    MAX-ACCESS  not-accessible
    STATUS      current
    DESCRIPTION "chassis ID"
    ::= { affirmedServicesContentHttpServerServiceStatisticsCluster-levelSummaryEntry 1 }

affirmedServicesContentHttpServerServiceStatisticsCluster-levelSummaryNumserverserviceattempts OBJECT-TYPE
    SYNTAX      ConfdString
    MAX-ACCESS  read-only
    STATUS      current
    DESCRIPTION "Total number of server service attempts"
    ::= { affirmedServicesContentHttpServerServiceStatisticsCluster-levelSummaryEntry 2 }

affirmedServicesContentHttpServerServiceStatisticsCluster-levelSummaryNumserverservicesuccess OBJECT-TYPE
    SYNTAX      ConfdString
    MAX-ACCESS  read-only
    STATUS      current
    DESCRIPTION "Total number of server service success"
    ::= { affirmedServicesContentHttpServerServiceStatisticsCluster-levelSummaryEntry 3 }

affirmedServicesContentHttpServerServiceStatisticsCluster-levelSummaryNumserverserviceabortedbyclient OBJECT-TYPE
    SYNTAX      ConfdString
    MAX-ACCESS  read-only
    STATUS      current
    DESCRIPTION "Total number of server services aborted by client"
    ::= { affirmedServicesContentHttpServerServiceStatisticsCluster-levelSummaryEntry 4 }

affirmedServicesContentHttpServerServiceStatisticsCluster-levelSummaryNumserverservicefailed OBJECT-TYPE
    SYNTAX      ConfdString
    MAX-ACCESS  read-only
    STATUS      current
    DESCRIPTION "Total number of server service failed"
    ::= { affirmedServicesContentHttpServerServiceStatisticsCluster-levelSummaryEntry 5 }

affirmedServicesContentHttpServerServiceStatisticsNode-levelSummaryTable OBJECT-TYPE
    SYNTAX      SEQUENCE OF AffirmedServicesContentHttpServerServiceStatisticsNode-levelSummaryEntry
    MAX-ACCESS  not-accessible
    STATUS      current
    DESCRIPTION ""
    ::= { affirmedServicesContentHttpServerServiceStatisticsNode-level 1 }

affirmedServicesContentHttpServerServiceStatisticsNode-levelSummaryEntry OBJECT-TYPE
    SYNTAX      AffirmedServicesContentHttpServerServiceStatisticsNode-levelSummaryEntry
    MAX-ACCESS  not-accessible
    STATUS      current
    DESCRIPTION ""
    INDEX { affirmedServicesContentHttpServerServiceStatisticsNode-levelSummaryChassis, affirmedServicesContentHttpServerServiceStatisticsNode-levelSummarySlot }
        ::= { affirmedServicesContentHttpServerServiceStatisticsNode-levelSummaryTable 1 }

AffirmedServicesContentHttpServerServiceStatisticsNode-levelSummaryEntry ::=
    SEQUENCE {
        affirmedServicesContentHttpServerServiceStatisticsNode-levelSummaryChassis Unsigned32,
        affirmedServicesContentHttpServerServiceStatisticsNode-levelSummarySlot INTEGER,
        affirmedServicesContentHttpServerServiceStatisticsNode-levelSummaryNumserverserviceattempts ConfdString,
        affirmedServicesContentHttpServerServiceStatisticsNode-levelSummaryNumserverservicesuccess ConfdString,
        affirmedServicesContentHttpServerServiceStatisticsNode-levelSummaryNumserverserviceabortedbyclient ConfdString,
        affirmedServicesContentHttpServerServiceStatisticsNode-levelSummaryNumserverservicefailed ConfdString
    }

affirmedServicesContentHttpServerServiceStatisticsNode-levelSummaryChassis OBJECT-TYPE
    SYNTAX      Unsigned32
    MAX-ACCESS  not-accessible
    STATUS      current
    DESCRIPTION "chassis ID"
    ::= { affirmedServicesContentHttpServerServiceStatisticsNode-levelSummaryEntry 1 }

affirmedServicesContentHttpServerServiceStatisticsNode-levelSummarySlot OBJECT-TYPE
    SYNTAX      INTEGER {a1(1),a2(2),a3(3),a4(4),a5(5),a6(6),a7(7),a8(8),a9(9),a10(10),a11(11),a12(12),a13(13),a14(14),a15(15),a16(16),a17(17),a18(18),a19(19),a20(20),a21(21),a22(22),a23(23),a24(24),a25(25),a26(26),a27(27),a28(28),a29(29),a30(30),a31(31),a32(32),a33(33),a34(34),a35(35),a36(36),a37(37),a38(38),a39(39),a40(40),a41(41),a42(42),a43(43),a44(44),a45(45),a46(46),a47(47),a48(48),a49(49),a50(50),a51(51),a52(52),a53(53),a54(54),a55(55),a56(56),a57(57),a58(58),a59(59),a60(60),a61(61),a62(62),a63(63),a64(64),a65(65),a66(66),a67(67),a68(68),a69(69),a70(70),a71(71),a72(72),a73(73),a74(74),a75(75),a76(76),a77(77),a78(78),a79(79),a80(80),a81(81),a82(82),a83(83),a84(84),a85(85),a86(86),a87(87),a88(88),a89(89),a90(90),a91(91),a92(92),a93(93),a94(94),a95(95),a96(96),a97(97),a98(98),a99(99),a100(100),a101(101),a102(102),a103(103),a104(104),a105(105),a106(106),a107(107),a108(108),a109(109),a110(110),a111(111),a112(112),a113(113),a114(114),a115(115),a116(116),a117(117),a118(118),a119(119),a120(120),a121(121),a122(122),a123(123),a124(124),a125(125),a126(126),a127(127),a128(128)}
    MAX-ACCESS  not-accessible
    STATUS      current
    DESCRIPTION "slot number"
    ::= { affirmedServicesContentHttpServerServiceStatisticsNode-levelSummaryEntry 2 }

affirmedServicesContentHttpServerServiceStatisticsNode-levelSummaryNumserverserviceattempts OBJECT-TYPE
    SYNTAX      ConfdString
    MAX-ACCESS  read-only
    STATUS      current
    DESCRIPTION "Total number of server service attempts"
    ::= { affirmedServicesContentHttpServerServiceStatisticsNode-levelSummaryEntry 3 }

affirmedServicesContentHttpServerServiceStatisticsNode-levelSummaryNumserverservicesuccess OBJECT-TYPE
    SYNTAX      ConfdString
    MAX-ACCESS  read-only
    STATUS      current
    DESCRIPTION "Total number of server service success"
    ::= { affirmedServicesContentHttpServerServiceStatisticsNode-levelSummaryEntry 4 }

affirmedServicesContentHttpServerServiceStatisticsNode-levelSummaryNumserverserviceabortedbyclient OBJECT-TYPE
    SYNTAX      ConfdString
    MAX-ACCESS  read-only
    STATUS      current
    DESCRIPTION "Total number of server services aborted by client"
    ::= { affirmedServicesContentHttpServerServiceStatisticsNode-levelSummaryEntry 5 }

affirmedServicesContentHttpServerServiceStatisticsNode-levelSummaryNumserverservicefailed OBJECT-TYPE
    SYNTAX      ConfdString
    MAX-ACCESS  read-only
    STATUS      current
    DESCRIPTION "Total number of server service failed"
    ::= { affirmedServicesContentHttpServerServiceStatisticsNode-levelSummaryEntry 6 }

affirmedServicesContentHttpServerServiceStatisticsChassisLevelServerPluginPluginEntryTable OBJECT-TYPE
    SYNTAX      SEQUENCE OF AffirmedServicesContentHttpServerServiceStatisticsChassisLevelServerPluginPluginEntryEntry
    MAX-ACCESS  not-accessible
    STATUS      current
    DESCRIPTION ""
    ::= { affirmedServicesContentHttpServerServiceStatisticsChassisLevelServerPlugin 1 }

affirmedServicesContentHttpServerServiceStatisticsChassisLevelServerPluginPluginEntryEntry OBJECT-TYPE
    SYNTAX      AffirmedServicesContentHttpServerServiceStatisticsChassisLevelServerPluginPluginEntryEntry
    MAX-ACCESS  not-accessible
    STATUS      current
    DESCRIPTION ""
    INDEX { affirmedServicesContentHttpServerServiceStatisticsChassisLevelServerPluginPluginEntryName, affirmedServicesContentHttpServerServiceStatisticsChassisLevelServerPluginPluginEntryChassis }
        ::= { affirmedServicesContentHttpServerServiceStatisticsChassisLevelServerPluginPluginEntryTable 1 }

AffirmedServicesContentHttpServerServiceStatisticsChassisLevelServerPluginPluginEntryEntry ::=
    SEQUENCE {
        affirmedServicesContentHttpServerServiceStatisticsChassisLevelServerPluginPluginEntryName String,
        affirmedServicesContentHttpServerServiceStatisticsChassisLevelServerPluginPluginEntryChassis Unsigned32,
        affirmedServicesContentHttpServerServiceStatisticsChassisLevelServerPluginPluginEntryNumpluginattempts ConfdString,
        affirmedServicesContentHttpServerServiceStatisticsChassisLevelServerPluginPluginEntryNumpluginsuccesses ConfdString,
        affirmedServicesContentHttpServerServiceStatisticsChassisLevelServerPluginPluginEntryNumpluginfailures ConfdString,
        affirmedServicesContentHttpServerServiceStatisticsChassisLevelServerPluginPluginEntryNumpluginhttperrorresponses ConfdString,
        affirmedServicesContentHttpServerServiceStatisticsChassisLevelServerPluginPluginEntryNumpluginhttpokresponses ConfdString,
        affirmedServicesContentHttpServerServiceStatisticsChassisLevelServerPluginPluginEntryNumplugininternalfailures ConfdString,
        affirmedServicesContentHttpServerServiceStatisticsChassisLevelServerPluginPluginEntryNumplugininvalidrequest ConfdString,
        affirmedServicesContentHttpServerServiceStatisticsChassisLevelServerPluginPluginEntryNumpluginnoconsent ConfdString
    }

affirmedServicesContentHttpServerServiceStatisticsChassisLevelServerPluginPluginEntryName OBJECT-TYPE
    SYNTAX      String
    MAX-ACCESS  not-accessible
    STATUS      current
    DESCRIPTION "Name of the server plugin"
    ::= { affirmedServicesContentHttpServerServiceStatisticsChassisLevelServerPluginPluginEntryEntry 1 }

affirmedServicesContentHttpServerServiceStatisticsChassisLevelServerPluginPluginEntryChassis OBJECT-TYPE
    SYNTAX      Unsigned32
    MAX-ACCESS  not-accessible
    STATUS      current
    DESCRIPTION "chassis ID"
    ::= { affirmedServicesContentHttpServerServiceStatisticsChassisLevelServerPluginPluginEntryEntry 2 }

affirmedServicesContentHttpServerServiceStatisticsChassisLevelServerPluginPluginEntryNumpluginattempts OBJECT-TYPE
    SYNTAX      ConfdString
    MAX-ACCESS  read-only
    STATUS      current
    DESCRIPTION "Total number of plugin attempts"
    ::= { affirmedServicesContentHttpServerServiceStatisticsChassisLevelServerPluginPluginEntryEntry 3 }

affirmedServicesContentHttpServerServiceStatisticsChassisLevelServerPluginPluginEntryNumpluginsuccesses OBJECT-TYPE
    SYNTAX      ConfdString
    MAX-ACCESS  read-only
    STATUS      current
    DESCRIPTION "Total number of plugin successes"
    ::= { affirmedServicesContentHttpServerServiceStatisticsChassisLevelServerPluginPluginEntryEntry 4 }

affirmedServicesContentHttpServerServiceStatisticsChassisLevelServerPluginPluginEntryNumpluginfailures OBJECT-TYPE
    SYNTAX      ConfdString
    MAX-ACCESS  read-only
    STATUS      current
    DESCRIPTION "Total number of plugin failures"
    ::= { affirmedServicesContentHttpServerServiceStatisticsChassisLevelServerPluginPluginEntryEntry 5 }

affirmedServicesContentHttpServerServiceStatisticsChassisLevelServerPluginPluginEntryNumpluginhttperrorresponses OBJECT-TYPE
    SYNTAX      ConfdString
    MAX-ACCESS  read-only
    STATUS      current
    DESCRIPTION "Total number of plugin HTTP error responses"
    ::= { affirmedServicesContentHttpServerServiceStatisticsChassisLevelServerPluginPluginEntryEntry 6 }

affirmedServicesContentHttpServerServiceStatisticsChassisLevelServerPluginPluginEntryNumpluginhttpokresponses OBJECT-TYPE
    SYNTAX      ConfdString
    MAX-ACCESS  read-only
    STATUS      current
    DESCRIPTION "Total number of plugin HTTP OK responses"
    ::= { affirmedServicesContentHttpServerServiceStatisticsChassisLevelServerPluginPluginEntryEntry 7 }

affirmedServicesContentHttpServerServiceStatisticsChassisLevelServerPluginPluginEntryNumplugininternalfailures OBJECT-TYPE
    SYNTAX      ConfdString
    MAX-ACCESS  read-only
    STATUS      current
    DESCRIPTION "Total number of plugin internal failures"
    ::= { affirmedServicesContentHttpServerServiceStatisticsChassisLevelServerPluginPluginEntryEntry 8 }

affirmedServicesContentHttpServerServiceStatisticsChassisLevelServerPluginPluginEntryNumplugininvalidrequest OBJECT-TYPE
    SYNTAX      ConfdString
    MAX-ACCESS  read-only
    STATUS      current
    DESCRIPTION "Total number of invalid requests sent to plugin"
    ::= { affirmedServicesContentHttpServerServiceStatisticsChassisLevelServerPluginPluginEntryEntry 9 }

affirmedServicesContentHttpServerServiceStatisticsChassisLevelServerPluginPluginEntryNumpluginnoconsent OBJECT-TYPE
    SYNTAX      ConfdString
    MAX-ACCESS  read-only
    STATUS      current
    DESCRIPTION "Total number of invalid requests due to invalid/missing consent ID"
    ::= { affirmedServicesContentHttpServerServiceStatisticsChassisLevelServerPluginPluginEntryEntry 10 }

affirmedServicesContentHttpServerServiceStatisticsChassisLevelContentInsertionScriptTable OBJECT-TYPE
    SYNTAX      SEQUENCE OF AffirmedServicesContentHttpServerServiceStatisticsChassisLevelContentInsertionScriptEntry
    MAX-ACCESS  not-accessible
    STATUS      current
    DESCRIPTION ""
    ::= { affirmedServicesContentHttpServerServiceStatisticsChassisLevelContentInsertion 1 }

affirmedServicesContentHttpServerServiceStatisticsChassisLevelContentInsertionScriptEntry OBJECT-TYPE
    SYNTAX      AffirmedServicesContentHttpServerServiceStatisticsChassisLevelContentInsertionScriptEntry
    MAX-ACCESS  not-accessible
    STATUS      current
    DESCRIPTION ""
    INDEX { affirmedServicesContentHttpServerServiceStatisticsChassisLevelContentInsertionScriptChassis }
        ::= { affirmedServicesContentHttpServerServiceStatisticsChassisLevelContentInsertionScriptTable 1 }

AffirmedServicesContentHttpServerServiceStatisticsChassisLevelContentInsertionScriptEntry ::=
    SEQUENCE {
        affirmedServicesContentHttpServerServiceStatisticsChassisLevelContentInsertionScriptChassis Unsigned32,
        affirmedServicesContentHttpServerServiceStatisticsChassisLevelContentInsertionScriptScriptinsertionattempts ConfdString,
        affirmedServicesContentHttpServerServiceStatisticsChassisLevelContentInsertionScriptScriptinsertionsuccesses ConfdString,
        affirmedServicesContentHttpServerServiceStatisticsChassisLevelContentInsertionScriptScriptinsertioncancels ConfdString,
        affirmedServicesContentHttpServerServiceStatisticsChassisLevelContentInsertionScriptScriptinsertionfailures ConfdString,
        affirmedServicesContentHttpServerServiceStatisticsChassisLevelContentInsertionScriptScriptinsertionaborts ConfdString
    }

affirmedServicesContentHttpServerServiceStatisticsChassisLevelContentInsertionScriptChassis OBJECT-TYPE
    SYNTAX      Unsigned32
    MAX-ACCESS  not-accessible
    STATUS      current
    DESCRIPTION "chassis ID"
    ::= { affirmedServicesContentHttpServerServiceStatisticsChassisLevelContentInsertionScriptEntry 1 }

affirmedServicesContentHttpServerServiceStatisticsChassisLevelContentInsertionScriptScriptinsertionattempts OBJECT-TYPE
    SYNTAX      ConfdString
    MAX-ACCESS  read-only
    STATUS      current
    DESCRIPTION "Number of Script Insertion Attempts"
    ::= { affirmedServicesContentHttpServerServiceStatisticsChassisLevelContentInsertionScriptEntry 2 }

affirmedServicesContentHttpServerServiceStatisticsChassisLevelContentInsertionScriptScriptinsertionsuccesses OBJECT-TYPE
    SYNTAX      ConfdString
    MAX-ACCESS  read-only
    STATUS      current
    DESCRIPTION "Number of Script Insertion Successes"
    ::= { affirmedServicesContentHttpServerServiceStatisticsChassisLevelContentInsertionScriptEntry 3 }

affirmedServicesContentHttpServerServiceStatisticsChassisLevelContentInsertionScriptScriptinsertioncancels OBJECT-TYPE
    SYNTAX      ConfdString
    MAX-ACCESS  read-only
    STATUS      current
    DESCRIPTION "Number of Script Insertion Cancels"
    ::= { affirmedServicesContentHttpServerServiceStatisticsChassisLevelContentInsertionScriptEntry 4 }

affirmedServicesContentHttpServerServiceStatisticsChassisLevelContentInsertionScriptScriptinsertionfailures OBJECT-TYPE
    SYNTAX      ConfdString
    MAX-ACCESS  read-only
    STATUS      current
    DESCRIPTION "Number of Script Insertion Failures"
    ::= { affirmedServicesContentHttpServerServiceStatisticsChassisLevelContentInsertionScriptEntry 5 }

affirmedServicesContentHttpServerServiceStatisticsChassisLevelContentInsertionScriptScriptinsertionaborts OBJECT-TYPE
    SYNTAX      ConfdString
    MAX-ACCESS  read-only
    STATUS      current
    DESCRIPTION "Number of Script Insertion Aborts"
    ::= { affirmedServicesContentHttpServerServiceStatisticsChassisLevelContentInsertionScriptEntry 6 }

affirmedServicesContentHttpServerServiceStatisticsChassisLevelContentInsertionObjectTable OBJECT-TYPE
    SYNTAX      SEQUENCE OF AffirmedServicesContentHttpServerServiceStatisticsChassisLevelContentInsertionObjectEntry
    MAX-ACCESS  not-accessible
    STATUS      current
    DESCRIPTION ""
    ::= { affirmedServicesContentHttpServerServiceStatisticsChassisLevelContentInsertion 2 }

affirmedServicesContentHttpServerServiceStatisticsChassisLevelContentInsertionObjectEntry OBJECT-TYPE
    SYNTAX      AffirmedServicesContentHttpServerServiceStatisticsChassisLevelContentInsertionObjectEntry
    MAX-ACCESS  not-accessible
    STATUS      current
    DESCRIPTION ""
    INDEX { affirmedServicesContentHttpServerServiceStatisticsChassisLevelContentInsertionObjectChassis }
        ::= { affirmedServicesContentHttpServerServiceStatisticsChassisLevelContentInsertionObjectTable 1 }

AffirmedServicesContentHttpServerServiceStatisticsChassisLevelContentInsertionObjectEntry ::=
    SEQUENCE {
        affirmedServicesContentHttpServerServiceStatisticsChassisLevelContentInsertionObjectChassis Unsigned32,
        affirmedServicesContentHttpServerServiceStatisticsChassisLevelContentInsertionObjectObjectinsertionattempts ConfdString,
        affirmedServicesContentHttpServerServiceStatisticsChassisLevelContentInsertionObjectObjectinsertionsuccesses ConfdString,
        affirmedServicesContentHttpServerServiceStatisticsChassisLevelContentInsertionObjectObjectinsertioncancels ConfdString,
        affirmedServicesContentHttpServerServiceStatisticsChassisLevelContentInsertionObjectObjectinsertionfailures ConfdString,
        affirmedServicesContentHttpServerServiceStatisticsChassisLevelContentInsertionObjectObjectinsertionaborts ConfdString,
        affirmedServicesContentHttpServerServiceStatisticsChassisLevelContentInsertionObjectObjectinsertionimagesserved ConfdString,
        affirmedServicesContentHttpServerServiceStatisticsChassisLevelContentInsertionObjectObjectinsertionvideosserved ConfdString,
        affirmedServicesContentHttpServerServiceStatisticsChassisLevelContentInsertionObjectObjectinsertionhtmlserved ConfdString
    }

affirmedServicesContentHttpServerServiceStatisticsChassisLevelContentInsertionObjectChassis OBJECT-TYPE
    SYNTAX      Unsigned32
    MAX-ACCESS  not-accessible
    STATUS      current
    DESCRIPTION "chassis ID"
    ::= { affirmedServicesContentHttpServerServiceStatisticsChassisLevelContentInsertionObjectEntry 1 }

affirmedServicesContentHttpServerServiceStatisticsChassisLevelContentInsertionObjectObjectinsertionattempts OBJECT-TYPE
    SYNTAX      ConfdString
    MAX-ACCESS  read-only
    STATUS      current
    DESCRIPTION "Number of Object Insertion Attempts"
    ::= { affirmedServicesContentHttpServerServiceStatisticsChassisLevelContentInsertionObjectEntry 2 }

affirmedServicesContentHttpServerServiceStatisticsChassisLevelContentInsertionObjectObjectinsertionsuccesses OBJECT-TYPE
    SYNTAX      ConfdString
    MAX-ACCESS  read-only
    STATUS      current
    DESCRIPTION "Number of Object Insertion Successes"
    ::= { affirmedServicesContentHttpServerServiceStatisticsChassisLevelContentInsertionObjectEntry 3 }

affirmedServicesContentHttpServerServiceStatisticsChassisLevelContentInsertionObjectObjectinsertioncancels OBJECT-TYPE
    SYNTAX      ConfdString
    MAX-ACCESS  read-only
    STATUS      current
    DESCRIPTION "Number of Object Insertion Cancels"
    ::= { affirmedServicesContentHttpServerServiceStatisticsChassisLevelContentInsertionObjectEntry 4 }

affirmedServicesContentHttpServerServiceStatisticsChassisLevelContentInsertionObjectObjectinsertionfailures OBJECT-TYPE
    SYNTAX      ConfdString
    MAX-ACCESS  read-only
    STATUS      current
    DESCRIPTION "Number of Object Insertion Failures"
    ::= { affirmedServicesContentHttpServerServiceStatisticsChassisLevelContentInsertionObjectEntry 5 }

affirmedServicesContentHttpServerServiceStatisticsChassisLevelContentInsertionObjectObjectinsertionaborts OBJECT-TYPE
    SYNTAX      ConfdString
    MAX-ACCESS  read-only
    STATUS      current
    DESCRIPTION "Number of Object Insertion Aborts"
    ::= { affirmedServicesContentHttpServerServiceStatisticsChassisLevelContentInsertionObjectEntry 6 }

affirmedServicesContentHttpServerServiceStatisticsChassisLevelContentInsertionObjectObjectinsertionimagesserved OBJECT-TYPE
    SYNTAX      ConfdString
    MAX-ACCESS  read-only
    STATUS      current
    DESCRIPTION "Number of Images Inserted"
    ::= { affirmedServicesContentHttpServerServiceStatisticsChassisLevelContentInsertionObjectEntry 7 }

affirmedServicesContentHttpServerServiceStatisticsChassisLevelContentInsertionObjectObjectinsertionvideosserved OBJECT-TYPE
    SYNTAX      ConfdString
    MAX-ACCESS  read-only
    STATUS      current
    DESCRIPTION "Number of Videos Inserted"
    ::= { affirmedServicesContentHttpServerServiceStatisticsChassisLevelContentInsertionObjectEntry 8 }

affirmedServicesContentHttpServerServiceStatisticsChassisLevelContentInsertionObjectObjectinsertionhtmlserved OBJECT-TYPE
    SYNTAX      ConfdString
    MAX-ACCESS  read-only
    STATUS      current
    DESCRIPTION "Number of HTML Inserted"
    ::= { affirmedServicesContentHttpServerServiceStatisticsChassisLevelContentInsertionObjectEntry 9 }

affirmedServicesContentHttpServerServiceStatisticsSlotLevelServerPluginPluginEntryTable OBJECT-TYPE
    SYNTAX      SEQUENCE OF AffirmedServicesContentHttpServerServiceStatisticsSlotLevelServerPluginPluginEntryEntry
    MAX-ACCESS  not-accessible
    STATUS      current
    DESCRIPTION ""
    ::= { affirmedServicesContentHttpServerServiceStatisticsSlotLevelServerPlugin 1 }

affirmedServicesContentHttpServerServiceStatisticsSlotLevelServerPluginPluginEntryEntry OBJECT-TYPE
    SYNTAX      AffirmedServicesContentHttpServerServiceStatisticsSlotLevelServerPluginPluginEntryEntry
    MAX-ACCESS  not-accessible
    STATUS      current
    DESCRIPTION ""
    INDEX { affirmedServicesContentHttpServerServiceStatisticsSlotLevelServerPluginPluginEntryName, affirmedServicesContentHttpServerServiceStatisticsSlotLevelServerPluginPluginEntryChassis, affirmedServicesContentHttpServerServiceStatisticsSlotLevelServerPluginPluginEntrySlot }
        ::= { affirmedServicesContentHttpServerServiceStatisticsSlotLevelServerPluginPluginEntryTable 1 }

AffirmedServicesContentHttpServerServiceStatisticsSlotLevelServerPluginPluginEntryEntry ::=
    SEQUENCE {
        affirmedServicesContentHttpServerServiceStatisticsSlotLevelServerPluginPluginEntryName String,
        affirmedServicesContentHttpServerServiceStatisticsSlotLevelServerPluginPluginEntryChassis Unsigned32,
        affirmedServicesContentHttpServerServiceStatisticsSlotLevelServerPluginPluginEntrySlot INTEGER,
        affirmedServicesContentHttpServerServiceStatisticsSlotLevelServerPluginPluginEntryNumpluginattempts ConfdString,
        affirmedServicesContentHttpServerServiceStatisticsSlotLevelServerPluginPluginEntryNumpluginsuccesses ConfdString,
        affirmedServicesContentHttpServerServiceStatisticsSlotLevelServerPluginPluginEntryNumpluginfailures ConfdString,
        affirmedServicesContentHttpServerServiceStatisticsSlotLevelServerPluginPluginEntryNumpluginhttperrorresponses ConfdString,
        affirmedServicesContentHttpServerServiceStatisticsSlotLevelServerPluginPluginEntryNumpluginhttpokresponses ConfdString,
        affirmedServicesContentHttpServerServiceStatisticsSlotLevelServerPluginPluginEntryNumplugininternalfailures ConfdString,
        affirmedServicesContentHttpServerServiceStatisticsSlotLevelServerPluginPluginEntryNumplugininvalidrequest ConfdString,
        affirmedServicesContentHttpServerServiceStatisticsSlotLevelServerPluginPluginEntryNumpluginnoconsent ConfdString
    }

affirmedServicesContentHttpServerServiceStatisticsSlotLevelServerPluginPluginEntryName OBJECT-TYPE
    SYNTAX      String
    MAX-ACCESS  not-accessible
    STATUS      current
    DESCRIPTION "Name of the server plugin"
    ::= { affirmedServicesContentHttpServerServiceStatisticsSlotLevelServerPluginPluginEntryEntry 1 }

affirmedServicesContentHttpServerServiceStatisticsSlotLevelServerPluginPluginEntryChassis OBJECT-TYPE
    SYNTAX      Unsigned32
    MAX-ACCESS  not-accessible
    STATUS      current
    DESCRIPTION "chassis ID"
    ::= { affirmedServicesContentHttpServerServiceStatisticsSlotLevelServerPluginPluginEntryEntry 2 }

affirmedServicesContentHttpServerServiceStatisticsSlotLevelServerPluginPluginEntrySlot OBJECT-TYPE
    SYNTAX      INTEGER {a1(1),a2(2),a3(3),a4(4),a5(5),a6(6),a7(7),a8(8),a9(9),a10(10),a11(11),a12(12),a13(13),a14(14),a15(15),a16(16),a17(17),a18(18),a19(19),a20(20),a21(21),a22(22),a23(23),a24(24),a25(25),a26(26),a27(27),a28(28),a29(29),a30(30),a31(31),a32(32),a33(33),a34(34),a35(35),a36(36),a37(37),a38(38),a39(39),a40(40),a41(41),a42(42),a43(43),a44(44),a45(45),a46(46),a47(47),a48(48),a49(49),a50(50),a51(51),a52(52),a53(53),a54(54),a55(55),a56(56),a57(57),a58(58),a59(59),a60(60),a61(61),a62(62),a63(63),a64(64),a65(65),a66(66),a67(67),a68(68),a69(69),a70(70),a71(71),a72(72),a73(73),a74(74),a75(75),a76(76),a77(77),a78(78),a79(79),a80(80),a81(81),a82(82),a83(83),a84(84),a85(85),a86(86),a87(87),a88(88),a89(89),a90(90),a91(91),a92(92),a93(93),a94(94),a95(95),a96(96),a97(97),a98(98),a99(99),a100(100),a101(101),a102(102),a103(103),a104(104),a105(105),a106(106),a107(107),a108(108),a109(109),a110(110),a111(111),a112(112),a113(113),a114(114),a115(115),a116(116),a117(117),a118(118),a119(119),a120(120),a121(121),a122(122),a123(123),a124(124),a125(125),a126(126),a127(127),a128(128)}
    MAX-ACCESS  not-accessible
    STATUS      current
    DESCRIPTION "slot number"
    ::= { affirmedServicesContentHttpServerServiceStatisticsSlotLevelServerPluginPluginEntryEntry 3 }

affirmedServicesContentHttpServerServiceStatisticsSlotLevelServerPluginPluginEntryNumpluginattempts OBJECT-TYPE
    SYNTAX      ConfdString
    MAX-ACCESS  read-only
    STATUS      current
    DESCRIPTION "Total number of plugin attempts"
    ::= { affirmedServicesContentHttpServerServiceStatisticsSlotLevelServerPluginPluginEntryEntry 4 }

affirmedServicesContentHttpServerServiceStatisticsSlotLevelServerPluginPluginEntryNumpluginsuccesses OBJECT-TYPE
    SYNTAX      ConfdString
    MAX-ACCESS  read-only
    STATUS      current
    DESCRIPTION "Total number of plugin successes"
    ::= { affirmedServicesContentHttpServerServiceStatisticsSlotLevelServerPluginPluginEntryEntry 5 }

affirmedServicesContentHttpServerServiceStatisticsSlotLevelServerPluginPluginEntryNumpluginfailures OBJECT-TYPE
    SYNTAX      ConfdString
    MAX-ACCESS  read-only
    STATUS      current
    DESCRIPTION "Total number of plugin failures"
    ::= { affirmedServicesContentHttpServerServiceStatisticsSlotLevelServerPluginPluginEntryEntry 6 }

affirmedServicesContentHttpServerServiceStatisticsSlotLevelServerPluginPluginEntryNumpluginhttperrorresponses OBJECT-TYPE
    SYNTAX      ConfdString
    MAX-ACCESS  read-only
    STATUS      current
    DESCRIPTION "Total number of plugin HTTP error responses"
    ::= { affirmedServicesContentHttpServerServiceStatisticsSlotLevelServerPluginPluginEntryEntry 7 }

affirmedServicesContentHttpServerServiceStatisticsSlotLevelServerPluginPluginEntryNumpluginhttpokresponses OBJECT-TYPE
    SYNTAX      ConfdString
    MAX-ACCESS  read-only
    STATUS      current
    DESCRIPTION "Total number of plugin HTTP OK responses"
    ::= { affirmedServicesContentHttpServerServiceStatisticsSlotLevelServerPluginPluginEntryEntry 8 }

affirmedServicesContentHttpServerServiceStatisticsSlotLevelServerPluginPluginEntryNumplugininternalfailures OBJECT-TYPE
    SYNTAX      ConfdString
    MAX-ACCESS  read-only
    STATUS      current
    DESCRIPTION "Total number of plugin internal failures"
    ::= { affirmedServicesContentHttpServerServiceStatisticsSlotLevelServerPluginPluginEntryEntry 9 }

affirmedServicesContentHttpServerServiceStatisticsSlotLevelServerPluginPluginEntryNumplugininvalidrequest OBJECT-TYPE
    SYNTAX      ConfdString
    MAX-ACCESS  read-only
    STATUS      current
    DESCRIPTION "Total number of invalid requests sent to plugin"
    ::= { affirmedServicesContentHttpServerServiceStatisticsSlotLevelServerPluginPluginEntryEntry 10 }

affirmedServicesContentHttpServerServiceStatisticsSlotLevelServerPluginPluginEntryNumpluginnoconsent OBJECT-TYPE
    SYNTAX      ConfdString
    MAX-ACCESS  read-only
    STATUS      current
    DESCRIPTION "Total number of invalid requests due to invalid/missing consent ID"
    ::= { affirmedServicesContentHttpServerServiceStatisticsSlotLevelServerPluginPluginEntryEntry 11 }

affirmedServicesContentHttpServerServiceStatisticsSlotLevelContentInsertionScriptTable OBJECT-TYPE
    SYNTAX      SEQUENCE OF AffirmedServicesContentHttpServerServiceStatisticsSlotLevelContentInsertionScriptEntry
    MAX-ACCESS  not-accessible
    STATUS      current
    DESCRIPTION ""
    ::= { affirmedServicesContentHttpServerServiceStatisticsSlotLevelContentInsertion 1 }

affirmedServicesContentHttpServerServiceStatisticsSlotLevelContentInsertionScriptEntry OBJECT-TYPE
    SYNTAX      AffirmedServicesContentHttpServerServiceStatisticsSlotLevelContentInsertionScriptEntry
    MAX-ACCESS  not-accessible
    STATUS      current
    DESCRIPTION ""
    INDEX { affirmedServicesContentHttpServerServiceStatisticsSlotLevelContentInsertionScriptChassis, affirmedServicesContentHttpServerServiceStatisticsSlotLevelContentInsertionScriptSlot }
        ::= { affirmedServicesContentHttpServerServiceStatisticsSlotLevelContentInsertionScriptTable 1 }

AffirmedServicesContentHttpServerServiceStatisticsSlotLevelContentInsertionScriptEntry ::=
    SEQUENCE {
        affirmedServicesContentHttpServerServiceStatisticsSlotLevelContentInsertionScriptChassis Unsigned32,
        affirmedServicesContentHttpServerServiceStatisticsSlotLevelContentInsertionScriptSlot INTEGER,
        affirmedServicesContentHttpServerServiceStatisticsSlotLevelContentInsertionScriptScriptinsertionattempts ConfdString,
        affirmedServicesContentHttpServerServiceStatisticsSlotLevelContentInsertionScriptScriptinsertionsuccesses ConfdString,
        affirmedServicesContentHttpServerServiceStatisticsSlotLevelContentInsertionScriptScriptinsertioncancels ConfdString,
        affirmedServicesContentHttpServerServiceStatisticsSlotLevelContentInsertionScriptScriptinsertionfailures ConfdString,
        affirmedServicesContentHttpServerServiceStatisticsSlotLevelContentInsertionScriptScriptinsertionaborts ConfdString
    }

affirmedServicesContentHttpServerServiceStatisticsSlotLevelContentInsertionScriptChassis OBJECT-TYPE
    SYNTAX      Unsigned32
    MAX-ACCESS  not-accessible
    STATUS      current
    DESCRIPTION "chassis ID"
    ::= { affirmedServicesContentHttpServerServiceStatisticsSlotLevelContentInsertionScriptEntry 1 }

affirmedServicesContentHttpServerServiceStatisticsSlotLevelContentInsertionScriptSlot OBJECT-TYPE
    SYNTAX      INTEGER {a1(1),a2(2),a3(3),a4(4),a5(5),a6(6),a7(7),a8(8),a9(9),a10(10),a11(11),a12(12),a13(13),a14(14),a15(15),a16(16),a17(17),a18(18),a19(19),a20(20),a21(21),a22(22),a23(23),a24(24),a25(25),a26(26),a27(27),a28(28),a29(29),a30(30),a31(31),a32(32),a33(33),a34(34),a35(35),a36(36),a37(37),a38(38),a39(39),a40(40),a41(41),a42(42),a43(43),a44(44),a45(45),a46(46),a47(47),a48(48),a49(49),a50(50),a51(51),a52(52),a53(53),a54(54),a55(55),a56(56),a57(57),a58(58),a59(59),a60(60),a61(61),a62(62),a63(63),a64(64),a65(65),a66(66),a67(67),a68(68),a69(69),a70(70),a71(71),a72(72),a73(73),a74(74),a75(75),a76(76),a77(77),a78(78),a79(79),a80(80),a81(81),a82(82),a83(83),a84(84),a85(85),a86(86),a87(87),a88(88),a89(89),a90(90),a91(91),a92(92),a93(93),a94(94),a95(95),a96(96),a97(97),a98(98),a99(99),a100(100),a101(101),a102(102),a103(103),a104(104),a105(105),a106(106),a107(107),a108(108),a109(109),a110(110),a111(111),a112(112),a113(113),a114(114),a115(115),a116(116),a117(117),a118(118),a119(119),a120(120),a121(121),a122(122),a123(123),a124(124),a125(125),a126(126),a127(127),a128(128)}
    MAX-ACCESS  not-accessible
    STATUS      current
    DESCRIPTION "slot number"
    ::= { affirmedServicesContentHttpServerServiceStatisticsSlotLevelContentInsertionScriptEntry 2 }

affirmedServicesContentHttpServerServiceStatisticsSlotLevelContentInsertionScriptScriptinsertionattempts OBJECT-TYPE
    SYNTAX      ConfdString
    MAX-ACCESS  read-only
    STATUS      current
    DESCRIPTION "Number of Script Insertion Attempts"
    ::= { affirmedServicesContentHttpServerServiceStatisticsSlotLevelContentInsertionScriptEntry 3 }

affirmedServicesContentHttpServerServiceStatisticsSlotLevelContentInsertionScriptScriptinsertionsuccesses OBJECT-TYPE
    SYNTAX      ConfdString
    MAX-ACCESS  read-only
    STATUS      current
    DESCRIPTION "Number of Script Insertion Successes"
    ::= { affirmedServicesContentHttpServerServiceStatisticsSlotLevelContentInsertionScriptEntry 4 }

affirmedServicesContentHttpServerServiceStatisticsSlotLevelContentInsertionScriptScriptinsertioncancels OBJECT-TYPE
    SYNTAX      ConfdString
    MAX-ACCESS  read-only
    STATUS      current
    DESCRIPTION "Number of Script Insertion Cancels"
    ::= { affirmedServicesContentHttpServerServiceStatisticsSlotLevelContentInsertionScriptEntry 5 }

affirmedServicesContentHttpServerServiceStatisticsSlotLevelContentInsertionScriptScriptinsertionfailures OBJECT-TYPE
    SYNTAX      ConfdString
    MAX-ACCESS  read-only
    STATUS      current
    DESCRIPTION "Number of Script Insertion Failures"
    ::= { affirmedServicesContentHttpServerServiceStatisticsSlotLevelContentInsertionScriptEntry 6 }

affirmedServicesContentHttpServerServiceStatisticsSlotLevelContentInsertionScriptScriptinsertionaborts OBJECT-TYPE
    SYNTAX      ConfdString
    MAX-ACCESS  read-only
    STATUS      current
    DESCRIPTION "Number of Script Insertion Aborts"
    ::= { affirmedServicesContentHttpServerServiceStatisticsSlotLevelContentInsertionScriptEntry 7 }

affirmedServicesContentHttpServerServiceStatisticsSlotLevelContentInsertionObjectTable OBJECT-TYPE
    SYNTAX      SEQUENCE OF AffirmedServicesContentHttpServerServiceStatisticsSlotLevelContentInsertionObjectEntry
    MAX-ACCESS  not-accessible
    STATUS      current
    DESCRIPTION ""
    ::= { affirmedServicesContentHttpServerServiceStatisticsSlotLevelContentInsertion 2 }

affirmedServicesContentHttpServerServiceStatisticsSlotLevelContentInsertionObjectEntry OBJECT-TYPE
    SYNTAX      AffirmedServicesContentHttpServerServiceStatisticsSlotLevelContentInsertionObjectEntry
    MAX-ACCESS  not-accessible
    STATUS      current
    DESCRIPTION ""
    INDEX { affirmedServicesContentHttpServerServiceStatisticsSlotLevelContentInsertionObjectChassis, affirmedServicesContentHttpServerServiceStatisticsSlotLevelContentInsertionObjectSlot }
        ::= { affirmedServicesContentHttpServerServiceStatisticsSlotLevelContentInsertionObjectTable 1 }

AffirmedServicesContentHttpServerServiceStatisticsSlotLevelContentInsertionObjectEntry ::=
    SEQUENCE {
        affirmedServicesContentHttpServerServiceStatisticsSlotLevelContentInsertionObjectChassis Unsigned32,
        affirmedServicesContentHttpServerServiceStatisticsSlotLevelContentInsertionObjectSlot INTEGER,
        affirmedServicesContentHttpServerServiceStatisticsSlotLevelContentInsertionObjectObjectinsertionattempts ConfdString,
        affirmedServicesContentHttpServerServiceStatisticsSlotLevelContentInsertionObjectObjectinsertionsuccesses ConfdString,
        affirmedServicesContentHttpServerServiceStatisticsSlotLevelContentInsertionObjectObjectinsertioncancels ConfdString,
        affirmedServicesContentHttpServerServiceStatisticsSlotLevelContentInsertionObjectObjectinsertionfailures ConfdString,
        affirmedServicesContentHttpServerServiceStatisticsSlotLevelContentInsertionObjectObjectinsertionaborts ConfdString,
        affirmedServicesContentHttpServerServiceStatisticsSlotLevelContentInsertionObjectObjectinsertionimagesserved ConfdString,
        affirmedServicesContentHttpServerServiceStatisticsSlotLevelContentInsertionObjectObjectinsertionvideosserved ConfdString,
        affirmedServicesContentHttpServerServiceStatisticsSlotLevelContentInsertionObjectObjectinsertionhtmlserved ConfdString
    }

affirmedServicesContentHttpServerServiceStatisticsSlotLevelContentInsertionObjectChassis OBJECT-TYPE
    SYNTAX      Unsigned32
    MAX-ACCESS  not-accessible
    STATUS      current
    DESCRIPTION "chassis ID"
    ::= { affirmedServicesContentHttpServerServiceStatisticsSlotLevelContentInsertionObjectEntry 1 }

affirmedServicesContentHttpServerServiceStatisticsSlotLevelContentInsertionObjectSlot OBJECT-TYPE
    SYNTAX      INTEGER {a1(1),a2(2),a3(3),a4(4),a5(5),a6(6),a7(7),a8(8),a9(9),a10(10),a11(11),a12(12),a13(13),a14(14),a15(15),a16(16),a17(17),a18(18),a19(19),a20(20),a21(21),a22(22),a23(23),a24(24),a25(25),a26(26),a27(27),a28(28),a29(29),a30(30),a31(31),a32(32),a33(33),a34(34),a35(35),a36(36),a37(37),a38(38),a39(39),a40(40),a41(41),a42(42),a43(43),a44(44),a45(45),a46(46),a47(47),a48(48),a49(49),a50(50),a51(51),a52(52),a53(53),a54(54),a55(55),a56(56),a57(57),a58(58),a59(59),a60(60),a61(61),a62(62),a63(63),a64(64),a65(65),a66(66),a67(67),a68(68),a69(69),a70(70),a71(71),a72(72),a73(73),a74(74),a75(75),a76(76),a77(77),a78(78),a79(79),a80(80),a81(81),a82(82),a83(83),a84(84),a85(85),a86(86),a87(87),a88(88),a89(89),a90(90),a91(91),a92(92),a93(93),a94(94),a95(95),a96(96),a97(97),a98(98),a99(99),a100(100),a101(101),a102(102),a103(103),a104(104),a105(105),a106(106),a107(107),a108(108),a109(109),a110(110),a111(111),a112(112),a113(113),a114(114),a115(115),a116(116),a117(117),a118(118),a119(119),a120(120),a121(121),a122(122),a123(123),a124(124),a125(125),a126(126),a127(127),a128(128)}
    MAX-ACCESS  not-accessible
    STATUS      current
    DESCRIPTION "slot number"
    ::= { affirmedServicesContentHttpServerServiceStatisticsSlotLevelContentInsertionObjectEntry 2 }

affirmedServicesContentHttpServerServiceStatisticsSlotLevelContentInsertionObjectObjectinsertionattempts OBJECT-TYPE
    SYNTAX      ConfdString
    MAX-ACCESS  read-only
    STATUS      current
    DESCRIPTION "Number of Object Insertion Attempts"
    ::= { affirmedServicesContentHttpServerServiceStatisticsSlotLevelContentInsertionObjectEntry 3 }

affirmedServicesContentHttpServerServiceStatisticsSlotLevelContentInsertionObjectObjectinsertionsuccesses OBJECT-TYPE
    SYNTAX      ConfdString
    MAX-ACCESS  read-only
    STATUS      current
    DESCRIPTION "Number of Object Insertion Successes"
    ::= { affirmedServicesContentHttpServerServiceStatisticsSlotLevelContentInsertionObjectEntry 4 }

affirmedServicesContentHttpServerServiceStatisticsSlotLevelContentInsertionObjectObjectinsertioncancels OBJECT-TYPE
    SYNTAX      ConfdString
    MAX-ACCESS  read-only
    STATUS      current
    DESCRIPTION "Number of Object Insertion Cancels"
    ::= { affirmedServicesContentHttpServerServiceStatisticsSlotLevelContentInsertionObjectEntry 5 }

affirmedServicesContentHttpServerServiceStatisticsSlotLevelContentInsertionObjectObjectinsertionfailures OBJECT-TYPE
    SYNTAX      ConfdString
    MAX-ACCESS  read-only
    STATUS      current
    DESCRIPTION "Number of Object Insertion Failures"
    ::= { affirmedServicesContentHttpServerServiceStatisticsSlotLevelContentInsertionObjectEntry 6 }

affirmedServicesContentHttpServerServiceStatisticsSlotLevelContentInsertionObjectObjectinsertionaborts OBJECT-TYPE
    SYNTAX      ConfdString
    MAX-ACCESS  read-only
    STATUS      current
    DESCRIPTION "Number of Object Insertion Aborts"
    ::= { affirmedServicesContentHttpServerServiceStatisticsSlotLevelContentInsertionObjectEntry 7 }

affirmedServicesContentHttpServerServiceStatisticsSlotLevelContentInsertionObjectObjectinsertionimagesserved OBJECT-TYPE
    SYNTAX      ConfdString
    MAX-ACCESS  read-only
    STATUS      current
    DESCRIPTION "Number of Images Inserted"
    ::= { affirmedServicesContentHttpServerServiceStatisticsSlotLevelContentInsertionObjectEntry 8 }

affirmedServicesContentHttpServerServiceStatisticsSlotLevelContentInsertionObjectObjectinsertionvideosserved OBJECT-TYPE
    SYNTAX      ConfdString
    MAX-ACCESS  read-only
    STATUS      current
    DESCRIPTION "Number of Videos Inserted"
    ::= { affirmedServicesContentHttpServerServiceStatisticsSlotLevelContentInsertionObjectEntry 9 }

affirmedServicesContentHttpServerServiceStatisticsSlotLevelContentInsertionObjectObjectinsertionhtmlserved OBJECT-TYPE
    SYNTAX      ConfdString
    MAX-ACCESS  read-only
    STATUS      current
    DESCRIPTION "Number of HTML Inserted"
    ::= { affirmedServicesContentHttpServerServiceStatisticsSlotLevelContentInsertionObjectEntry 10 }

affirmedServicesDnsServerServiceStatisticsCluster-levelSummaryTable OBJECT-TYPE
    SYNTAX      SEQUENCE OF AffirmedServicesDnsServerServiceStatisticsCluster-levelSummaryEntry
    MAX-ACCESS  not-accessible
    STATUS      current
    DESCRIPTION ""
    ::= { affirmedServicesDnsServerServiceStatisticsCluster-level 1 }

affirmedServicesDnsServerServiceStatisticsCluster-levelSummaryEntry OBJECT-TYPE
    SYNTAX      AffirmedServicesDnsServerServiceStatisticsCluster-levelSummaryEntry
    MAX-ACCESS  not-accessible
    STATUS      current
    DESCRIPTION ""
    INDEX { affirmedServicesDnsServerServiceStatisticsCluster-levelSummaryChassis }
        ::= { affirmedServicesDnsServerServiceStatisticsCluster-levelSummaryTable 1 }

AffirmedServicesDnsServerServiceStatisticsCluster-levelSummaryEntry ::=
    SEQUENCE {
        affirmedServicesDnsServerServiceStatisticsCluster-levelSummaryChassis Unsigned32,
        affirmedServicesDnsServerServiceStatisticsCluster-levelSummaryNumdnsserversummaryattempts ConfdString,
        affirmedServicesDnsServerServiceStatisticsCluster-levelSummaryNumdnsserversummarysuccesses ConfdString,
        affirmedServicesDnsServerServiceStatisticsCluster-levelSummaryNumdnsserversummaryfailures ConfdString,
        affirmedServicesDnsServerServiceStatisticsCluster-levelSummaryNumdnsserversummarydupqueries ConfdString,
        affirmedServicesDnsServerServiceStatisticsCluster-levelSummaryNumdnsserversummaryblockedqueries ConfdString,
        affirmedServicesDnsServerServiceStatisticsCluster-levelSummaryNumdnsserversummaryrecursiveclients ConfdString,
        affirmedServicesDnsServerServiceStatisticsCluster-levelSummaryNumdnsserversummaryipv4requests ConfdString,
        affirmedServicesDnsServerServiceStatisticsCluster-levelSummaryNumdnsserversummaryipv6requests ConfdString,
        affirmedServicesDnsServerServiceStatisticsCluster-levelSummaryNumdnsserversummarytcprequests ConfdString,
        affirmedServicesDnsServerServiceStatisticsCluster-levelSummaryNumdnsserversummaryudprequests ConfdString
    }

affirmedServicesDnsServerServiceStatisticsCluster-levelSummaryChassis OBJECT-TYPE
    SYNTAX      Unsigned32
    MAX-ACCESS  not-accessible
    STATUS      current
    DESCRIPTION "chassis ID"
    ::= { affirmedServicesDnsServerServiceStatisticsCluster-levelSummaryEntry 1 }

affirmedServicesDnsServerServiceStatisticsCluster-levelSummaryNumdnsserversummaryattempts OBJECT-TYPE
    SYNTAX      ConfdString
    MAX-ACCESS  read-only
    STATUS      current
    DESCRIPTION "Number of Dns Server query attempts"
    ::= { affirmedServicesDnsServerServiceStatisticsCluster-levelSummaryEntry 2 }

affirmedServicesDnsServerServiceStatisticsCluster-levelSummaryNumdnsserversummarysuccesses OBJECT-TYPE
    SYNTAX      ConfdString
    MAX-ACCESS  read-only
    STATUS      current
    DESCRIPTION "Number of Dns Server queries with successful responses"
    ::= { affirmedServicesDnsServerServiceStatisticsCluster-levelSummaryEntry 3 }

affirmedServicesDnsServerServiceStatisticsCluster-levelSummaryNumdnsserversummaryfailures OBJECT-TYPE
    SYNTAX      ConfdString
    MAX-ACCESS  read-only
    STATUS      current
    DESCRIPTION "Number of Dns Server queries with failures"
    ::= { affirmedServicesDnsServerServiceStatisticsCluster-levelSummaryEntry 4 }

affirmedServicesDnsServerServiceStatisticsCluster-levelSummaryNumdnsserversummarydupqueries OBJECT-TYPE
    SYNTAX      ConfdString
    MAX-ACCESS  read-only
    STATUS      current
    DESCRIPTION "Number of Dns Server Duplicate Queries Received"
    ::= { affirmedServicesDnsServerServiceStatisticsCluster-levelSummaryEntry 5 }

affirmedServicesDnsServerServiceStatisticsCluster-levelSummaryNumdnsserversummaryblockedqueries OBJECT-TYPE
    SYNTAX      ConfdString
    MAX-ACCESS  read-only
    STATUS      current
    DESCRIPTION "Number of Dns Server Queries Blocked"
    ::= { affirmedServicesDnsServerServiceStatisticsCluster-levelSummaryEntry 6 }

affirmedServicesDnsServerServiceStatisticsCluster-levelSummaryNumdnsserversummaryrecursiveclients OBJECT-TYPE
    SYNTAX      ConfdString
    MAX-ACCESS  read-only
    STATUS      current
    DESCRIPTION "Number of Dns Server current Recursive Clients"
    ::= { affirmedServicesDnsServerServiceStatisticsCluster-levelSummaryEntry 7 }

affirmedServicesDnsServerServiceStatisticsCluster-levelSummaryNumdnsserversummaryipv4requests OBJECT-TYPE
    SYNTAX      ConfdString
    MAX-ACCESS  read-only
    STATUS      current
    DESCRIPTION "Number of Dns Server ipv4 requests"
    ::= { affirmedServicesDnsServerServiceStatisticsCluster-levelSummaryEntry 8 }

affirmedServicesDnsServerServiceStatisticsCluster-levelSummaryNumdnsserversummaryipv6requests OBJECT-TYPE
    SYNTAX      ConfdString
    MAX-ACCESS  read-only
    STATUS      current
    DESCRIPTION "Number of Dns Server ipv6 requests"
    ::= { affirmedServicesDnsServerServiceStatisticsCluster-levelSummaryEntry 9 }

affirmedServicesDnsServerServiceStatisticsCluster-levelSummaryNumdnsserversummarytcprequests OBJECT-TYPE
    SYNTAX      ConfdString
    MAX-ACCESS  read-only
    STATUS      current
    DESCRIPTION "Number of Dns Server TCP requests"
    ::= { affirmedServicesDnsServerServiceStatisticsCluster-levelSummaryEntry 10 }

affirmedServicesDnsServerServiceStatisticsCluster-levelSummaryNumdnsserversummaryudprequests OBJECT-TYPE
    SYNTAX      ConfdString
    MAX-ACCESS  read-only
    STATUS      current
    DESCRIPTION "Number of Dns Server UDP requests"
    ::= { affirmedServicesDnsServerServiceStatisticsCluster-levelSummaryEntry 11 }

affirmedServicesDnsServerServiceStatisticsCluster-levelDetailTable OBJECT-TYPE
    SYNTAX      SEQUENCE OF AffirmedServicesDnsServerServiceStatisticsCluster-levelDetailEntry
    MAX-ACCESS  not-accessible
    STATUS      current
    DESCRIPTION ""
    ::= { affirmedServicesDnsServerServiceStatisticsCluster-level 2 }

affirmedServicesDnsServerServiceStatisticsCluster-levelDetailEntry OBJECT-TYPE
    SYNTAX      AffirmedServicesDnsServerServiceStatisticsCluster-levelDetailEntry
    MAX-ACCESS  not-accessible
    STATUS      current
    DESCRIPTION ""
    INDEX { affirmedServicesDnsServerServiceStatisticsCluster-levelDetailChassis }
        ::= { affirmedServicesDnsServerServiceStatisticsCluster-levelDetailTable 1 }

AffirmedServicesDnsServerServiceStatisticsCluster-levelDetailEntry ::=
    SEQUENCE {
        affirmedServicesDnsServerServiceStatisticsCluster-levelDetailChassis Unsigned32,
        affirmedServicesDnsServerServiceStatisticsCluster-levelDetailNumdnsserverdetailipv4requests ConfdString,
        affirmedServicesDnsServerServiceStatisticsCluster-levelDetailNumdnsserverdetailipv6requests ConfdString,
        affirmedServicesDnsServerServiceStatisticsCluster-levelDetailNumdnsserverdetailednsrequests ConfdString,
        affirmedServicesDnsServerServiceStatisticsCluster-levelDetailNumdnsserverdetailtcprequests ConfdString,
        affirmedServicesDnsServerServiceStatisticsCluster-levelDetailNumdnsserverdetailresponses ConfdString,
        affirmedServicesDnsServerServiceStatisticsCluster-levelDetailNumdnsserverdetailednsresponses ConfdString,
        affirmedServicesDnsServerServiceStatisticsCluster-levelDetailNumdnsserverdetailquerysuccessresponses ConfdString,
        affirmedServicesDnsServerServiceStatisticsCluster-levelDetailNumdnsserverdetailauthoritativeresponses ConfdString,
        affirmedServicesDnsServerServiceStatisticsCluster-levelDetailNumdnsserverdetailnonauthoritativeresponses ConfdString,
        affirmedServicesDnsServerServiceStatisticsCluster-levelDetailNumdnsserverdetailnoerrornodataresponses ConfdString,
        affirmedServicesDnsServerServiceStatisticsCluster-levelDetailNumdnsserverdetailservfailresponses ConfdString,
        affirmedServicesDnsServerServiceStatisticsCluster-levelDetailNumdnsserverdetailformerrresponses ConfdString,
        affirmedServicesDnsServerServiceStatisticsCluster-levelDetailNumdnsserverdetailnxdomainresponses ConfdString,
        affirmedServicesDnsServerServiceStatisticsCluster-levelDetailNumdnsserverdetailrecursion ConfdString,
        affirmedServicesDnsServerServiceStatisticsCluster-levelDetailNumdnsserverdetailrecursiveclients ConfdString,
        affirmedServicesDnsServerServiceStatisticsCluster-levelDetailNumdnsserverdetaildupqueries ConfdString,
        affirmedServicesDnsServerServiceStatisticsCluster-levelDetailNumdnsserverdetailudpqueries ConfdString,
        affirmedServicesDnsServerServiceStatisticsCluster-levelDetailNumdnsserverdetailtcpqueries ConfdString
    }

affirmedServicesDnsServerServiceStatisticsCluster-levelDetailChassis OBJECT-TYPE
    SYNTAX      Unsigned32
    MAX-ACCESS  not-accessible
    STATUS      current
    DESCRIPTION "chassis ID"
    ::= { affirmedServicesDnsServerServiceStatisticsCluster-levelDetailEntry 1 }

affirmedServicesDnsServerServiceStatisticsCluster-levelDetailNumdnsserverdetailipv4requests OBJECT-TYPE
    SYNTAX      ConfdString
    MAX-ACCESS  read-only
    STATUS      current
    DESCRIPTION "Number of Dns Server IPv4 requests"
    ::= { affirmedServicesDnsServerServiceStatisticsCluster-levelDetailEntry 2 }

affirmedServicesDnsServerServiceStatisticsCluster-levelDetailNumdnsserverdetailipv6requests OBJECT-TYPE
    SYNTAX      ConfdString
    MAX-ACCESS  read-only
    STATUS      current
    DESCRIPTION "Number of Dns Server IPv6 requests"
    ::= { affirmedServicesDnsServerServiceStatisticsCluster-levelDetailEntry 3 }

affirmedServicesDnsServerServiceStatisticsCluster-levelDetailNumdnsserverdetailednsrequests OBJECT-TYPE
    SYNTAX      ConfdString
    MAX-ACCESS  read-only
    STATUS      current
    DESCRIPTION "Number of Dns Server EDNS reuqests"
    ::= { affirmedServicesDnsServerServiceStatisticsCluster-levelDetailEntry 4 }

affirmedServicesDnsServerServiceStatisticsCluster-levelDetailNumdnsserverdetailtcprequests OBJECT-TYPE
    SYNTAX      ConfdString
    MAX-ACCESS  read-only
    STATUS      current
    DESCRIPTION "Number of Dns Server TCP requests"
    ::= { affirmedServicesDnsServerServiceStatisticsCluster-levelDetailEntry 5 }

affirmedServicesDnsServerServiceStatisticsCluster-levelDetailNumdnsserverdetailresponses OBJECT-TYPE
    SYNTAX      ConfdString
    MAX-ACCESS  read-only
    STATUS      current
    DESCRIPTION "Number of Dns Server responses"
    ::= { affirmedServicesDnsServerServiceStatisticsCluster-levelDetailEntry 6 }

affirmedServicesDnsServerServiceStatisticsCluster-levelDetailNumdnsserverdetailednsresponses OBJECT-TYPE
    SYNTAX      ConfdString
    MAX-ACCESS  read-only
    STATUS      current
    DESCRIPTION "Number of Dns Server EDNS responses"
    ::= { affirmedServicesDnsServerServiceStatisticsCluster-levelDetailEntry 7 }

affirmedServicesDnsServerServiceStatisticsCluster-levelDetailNumdnsserverdetailquerysuccessresponses OBJECT-TYPE
    SYNTAX      ConfdString
    MAX-ACCESS  read-only
    STATUS      current
    DESCRIPTION "Number of Dns Server query successful responses"
    ::= { affirmedServicesDnsServerServiceStatisticsCluster-levelDetailEntry 8 }

affirmedServicesDnsServerServiceStatisticsCluster-levelDetailNumdnsserverdetailauthoritativeresponses OBJECT-TYPE
    SYNTAX      ConfdString
    MAX-ACCESS  read-only
    STATUS      current
    DESCRIPTION "Number of Dns Server authoritative responses"
    ::= { affirmedServicesDnsServerServiceStatisticsCluster-levelDetailEntry 9 }

affirmedServicesDnsServerServiceStatisticsCluster-levelDetailNumdnsserverdetailnonauthoritativeresponses OBJECT-TYPE
    SYNTAX      ConfdString
    MAX-ACCESS  read-only
    STATUS      current
    DESCRIPTION "Number of Dns Server non authoritative responses"
    ::= { affirmedServicesDnsServerServiceStatisticsCluster-levelDetailEntry 10 }

affirmedServicesDnsServerServiceStatisticsCluster-levelDetailNumdnsserverdetailnoerrornodataresponses OBJECT-TYPE
    SYNTAX      ConfdString
    MAX-ACCESS  read-only
    STATUS      current
    DESCRIPTION "Number of Dns Server NOERROR responses with no data"
    ::= { affirmedServicesDnsServerServiceStatisticsCluster-levelDetailEntry 11 }

affirmedServicesDnsServerServiceStatisticsCluster-levelDetailNumdnsserverdetailservfailresponses OBJECT-TYPE
    SYNTAX      ConfdString
    MAX-ACCESS  read-only
    STATUS      current
    DESCRIPTION "Number of Dns Server SERVFAIL responses"
    ::= { affirmedServicesDnsServerServiceStatisticsCluster-levelDetailEntry 12 }

affirmedServicesDnsServerServiceStatisticsCluster-levelDetailNumdnsserverdetailformerrresponses OBJECT-TYPE
    SYNTAX      ConfdString
    MAX-ACCESS  read-only
    STATUS      current
    DESCRIPTION "Number of Dns Server FORMERR responses"
    ::= { affirmedServicesDnsServerServiceStatisticsCluster-levelDetailEntry 13 }

affirmedServicesDnsServerServiceStatisticsCluster-levelDetailNumdnsserverdetailnxdomainresponses OBJECT-TYPE
    SYNTAX      ConfdString
    MAX-ACCESS  read-only
    STATUS      current
    DESCRIPTION "Number of Dns Server NXDOMAIN responses"
    ::= { affirmedServicesDnsServerServiceStatisticsCluster-levelDetailEntry 14 }

affirmedServicesDnsServerServiceStatisticsCluster-levelDetailNumdnsserverdetailrecursion OBJECT-TYPE
    SYNTAX      ConfdString
    MAX-ACCESS  read-only
    STATUS      current
    DESCRIPTION "Number of Dns Server Queries that caused Recursion"
    ::= { affirmedServicesDnsServerServiceStatisticsCluster-levelDetailEntry 15 }

affirmedServicesDnsServerServiceStatisticsCluster-levelDetailNumdnsserverdetailrecursiveclients OBJECT-TYPE
    SYNTAX      ConfdString
    MAX-ACCESS  read-only
    STATUS      current
    DESCRIPTION "Number of Dns Server current Recursive Clients"
    ::= { affirmedServicesDnsServerServiceStatisticsCluster-levelDetailEntry 16 }

affirmedServicesDnsServerServiceStatisticsCluster-levelDetailNumdnsserverdetaildupqueries OBJECT-TYPE
    SYNTAX      ConfdString
    MAX-ACCESS  read-only
    STATUS      current
    DESCRIPTION "Number of Dns Server Duplicate Queries Received"
    ::= { affirmedServicesDnsServerServiceStatisticsCluster-levelDetailEntry 17 }

affirmedServicesDnsServerServiceStatisticsCluster-levelDetailNumdnsserverdetailudpqueries OBJECT-TYPE
    SYNTAX      ConfdString
    MAX-ACCESS  read-only
    STATUS      current
    DESCRIPTION "Number of Dns Server UDP Queries"
    ::= { affirmedServicesDnsServerServiceStatisticsCluster-levelDetailEntry 18 }

affirmedServicesDnsServerServiceStatisticsCluster-levelDetailNumdnsserverdetailtcpqueries OBJECT-TYPE
    SYNTAX      ConfdString
    MAX-ACCESS  read-only
    STATUS      current
    DESCRIPTION "Number of Dns Server TCP Queries"
    ::= { affirmedServicesDnsServerServiceStatisticsCluster-levelDetailEntry 19 }

affirmedServicesDnsServerServiceStatisticsCluster-levelQuerytypeTable OBJECT-TYPE
    SYNTAX      SEQUENCE OF AffirmedServicesDnsServerServiceStatisticsCluster-levelQuerytypeEntry
    MAX-ACCESS  not-accessible
    STATUS      current
    DESCRIPTION ""
    ::= { affirmedServicesDnsServerServiceStatisticsCluster-level 3 }

affirmedServicesDnsServerServiceStatisticsCluster-levelQuerytypeEntry OBJECT-TYPE
    SYNTAX      AffirmedServicesDnsServerServiceStatisticsCluster-levelQuerytypeEntry
    MAX-ACCESS  not-accessible
    STATUS      current
    DESCRIPTION ""
    INDEX { affirmedServicesDnsServerServiceStatisticsCluster-levelQuerytypeChassis }
        ::= { affirmedServicesDnsServerServiceStatisticsCluster-levelQuerytypeTable 1 }

AffirmedServicesDnsServerServiceStatisticsCluster-levelQuerytypeEntry ::=
    SEQUENCE {
        affirmedServicesDnsServerServiceStatisticsCluster-levelQuerytypeChassis Unsigned32,
        affirmedServicesDnsServerServiceStatisticsCluster-levelQuerytypeNumdnsserverquerytypea ConfdString,
        affirmedServicesDnsServerServiceStatisticsCluster-levelQuerytypeNumdnsserverquerytypeaaaa ConfdString,
        affirmedServicesDnsServerServiceStatisticsCluster-levelQuerytypeNumdnsserverquerytypecname ConfdString,
        affirmedServicesDnsServerServiceStatisticsCluster-levelQuerytypeNumdnsserverquerytypednskey ConfdString,
        affirmedServicesDnsServerServiceStatisticsCluster-levelQuerytypeNumdnsserverquerytypemx ConfdString,
        affirmedServicesDnsServerServiceStatisticsCluster-levelQuerytypeNumdnsserverquerytypens ConfdString,
        affirmedServicesDnsServerServiceStatisticsCluster-levelQuerytypeNumdnsserverquerytypeptr ConfdString,
        affirmedServicesDnsServerServiceStatisticsCluster-levelQuerytypeNumdnsserverquerytyperrsig ConfdString,
        affirmedServicesDnsServerServiceStatisticsCluster-levelQuerytypeNumdnsserverquerytypetsig ConfdString,
        affirmedServicesDnsServerServiceStatisticsCluster-levelQuerytypeNumdnsserverquerytypeds ConfdString,
        affirmedServicesDnsServerServiceStatisticsCluster-levelQuerytypeNumdnsserverquerytypehinfo ConfdString,
        affirmedServicesDnsServerServiceStatisticsCluster-levelQuerytypeNumdnsserverquerytypesoa ConfdString,
        affirmedServicesDnsServerServiceStatisticsCluster-levelQuerytypeNumdnsserverquerytypeaxfr ConfdString,
        affirmedServicesDnsServerServiceStatisticsCluster-levelQuerytypeNumdnsserverquerytypeany ConfdString
    }

affirmedServicesDnsServerServiceStatisticsCluster-levelQuerytypeChassis OBJECT-TYPE
    SYNTAX      Unsigned32
    MAX-ACCESS  not-accessible
    STATUS      current
    DESCRIPTION "chassis ID"
    ::= { affirmedServicesDnsServerServiceStatisticsCluster-levelQuerytypeEntry 1 }

affirmedServicesDnsServerServiceStatisticsCluster-levelQuerytypeNumdnsserverquerytypea OBJECT-TYPE
    SYNTAX      ConfdString
    MAX-ACCESS  read-only
    STATUS      current
    DESCRIPTION "Number of Dns Server A record queries"
    ::= { affirmedServicesDnsServerServiceStatisticsCluster-levelQuerytypeEntry 2 }

affirmedServicesDnsServerServiceStatisticsCluster-levelQuerytypeNumdnsserverquerytypeaaaa OBJECT-TYPE
    SYNTAX      ConfdString
    MAX-ACCESS  read-only
    STATUS      current
    DESCRIPTION "Number of Dns Server AAAA record queries"
    ::= { affirmedServicesDnsServerServiceStatisticsCluster-levelQuerytypeEntry 3 }

affirmedServicesDnsServerServiceStatisticsCluster-levelQuerytypeNumdnsserverquerytypecname OBJECT-TYPE
    SYNTAX      ConfdString
    MAX-ACCESS  read-only
    STATUS      current
    DESCRIPTION "Number of Dns Server CNAME record queries"
    ::= { affirmedServicesDnsServerServiceStatisticsCluster-levelQuerytypeEntry 4 }

affirmedServicesDnsServerServiceStatisticsCluster-levelQuerytypeNumdnsserverquerytypednskey OBJECT-TYPE
    SYNTAX      ConfdString
    MAX-ACCESS  read-only
    STATUS      current
    DESCRIPTION "Number of Dns Server DNSKEY record queries"
    ::= { affirmedServicesDnsServerServiceStatisticsCluster-levelQuerytypeEntry 5 }

affirmedServicesDnsServerServiceStatisticsCluster-levelQuerytypeNumdnsserverquerytypemx OBJECT-TYPE
    SYNTAX      ConfdString
    MAX-ACCESS  read-only
    STATUS      current
    DESCRIPTION "Number of Dns Server MX record queries"
    ::= { affirmedServicesDnsServerServiceStatisticsCluster-levelQuerytypeEntry 6 }

affirmedServicesDnsServerServiceStatisticsCluster-levelQuerytypeNumdnsserverquerytypens OBJECT-TYPE
    SYNTAX      ConfdString
    MAX-ACCESS  read-only
    STATUS      current
    DESCRIPTION "Number of Dns Server NS record queries"
    ::= { affirmedServicesDnsServerServiceStatisticsCluster-levelQuerytypeEntry 7 }

affirmedServicesDnsServerServiceStatisticsCluster-levelQuerytypeNumdnsserverquerytypeptr OBJECT-TYPE
    SYNTAX      ConfdString
    MAX-ACCESS  read-only
    STATUS      current
    DESCRIPTION "Number of Dns Server PTR record queries"
    ::= { affirmedServicesDnsServerServiceStatisticsCluster-levelQuerytypeEntry 8 }

affirmedServicesDnsServerServiceStatisticsCluster-levelQuerytypeNumdnsserverquerytyperrsig OBJECT-TYPE
    SYNTAX      ConfdString
    MAX-ACCESS  read-only
    STATUS      current
    DESCRIPTION "Number of Dns Server RRSIG record queries"
    ::= { affirmedServicesDnsServerServiceStatisticsCluster-levelQuerytypeEntry 9 }

affirmedServicesDnsServerServiceStatisticsCluster-levelQuerytypeNumdnsserverquerytypetsig OBJECT-TYPE
    SYNTAX      ConfdString
    MAX-ACCESS  read-only
    STATUS      current
    DESCRIPTION "Number of Dns Server TSIG record queries"
    ::= { affirmedServicesDnsServerServiceStatisticsCluster-levelQuerytypeEntry 10 }

affirmedServicesDnsServerServiceStatisticsCluster-levelQuerytypeNumdnsserverquerytypeds OBJECT-TYPE
    SYNTAX      ConfdString
    MAX-ACCESS  read-only
    STATUS      current
    DESCRIPTION "Number of Dns Server DS record queries"
    ::= { affirmedServicesDnsServerServiceStatisticsCluster-levelQuerytypeEntry 11 }

affirmedServicesDnsServerServiceStatisticsCluster-levelQuerytypeNumdnsserverquerytypehinfo OBJECT-TYPE
    SYNTAX      ConfdString
    MAX-ACCESS  read-only
    STATUS      current
    DESCRIPTION "Number of Dns Server HINFO record queries"
    ::= { affirmedServicesDnsServerServiceStatisticsCluster-levelQuerytypeEntry 12 }

affirmedServicesDnsServerServiceStatisticsCluster-levelQuerytypeNumdnsserverquerytypesoa OBJECT-TYPE
    SYNTAX      ConfdString
    MAX-ACCESS  read-only
    STATUS      current
    DESCRIPTION "Number of Dns Server SOA record queries"
    ::= { affirmedServicesDnsServerServiceStatisticsCluster-levelQuerytypeEntry 13 }

affirmedServicesDnsServerServiceStatisticsCluster-levelQuerytypeNumdnsserverquerytypeaxfr OBJECT-TYPE
    SYNTAX      ConfdString
    MAX-ACCESS  read-only
    STATUS      current
    DESCRIPTION "Number of Dns Server AXFR record queries"
    ::= { affirmedServicesDnsServerServiceStatisticsCluster-levelQuerytypeEntry 14 }

affirmedServicesDnsServerServiceStatisticsCluster-levelQuerytypeNumdnsserverquerytypeany OBJECT-TYPE
    SYNTAX      ConfdString
    MAX-ACCESS  read-only
    STATUS      current
    DESCRIPTION "Number of Dns Server record queries of Other types"
    ::= { affirmedServicesDnsServerServiceStatisticsCluster-levelQuerytypeEntry 15 }

affirmedServicesDnsServerServiceStatisticsCluster-levelFailureTable OBJECT-TYPE
    SYNTAX      SEQUENCE OF AffirmedServicesDnsServerServiceStatisticsCluster-levelFailureEntry
    MAX-ACCESS  not-accessible
    STATUS      current
    DESCRIPTION ""
    ::= { affirmedServicesDnsServerServiceStatisticsCluster-level 4 }

affirmedServicesDnsServerServiceStatisticsCluster-levelFailureEntry OBJECT-TYPE
    SYNTAX      AffirmedServicesDnsServerServiceStatisticsCluster-levelFailureEntry
    MAX-ACCESS  not-accessible
    STATUS      current
    DESCRIPTION ""
    INDEX { affirmedServicesDnsServerServiceStatisticsCluster-levelFailureChassis }
        ::= { affirmedServicesDnsServerServiceStatisticsCluster-levelFailureTable 1 }

AffirmedServicesDnsServerServiceStatisticsCluster-levelFailureEntry ::=
    SEQUENCE {
        affirmedServicesDnsServerServiceStatisticsCluster-levelFailureChassis Unsigned32,
        affirmedServicesDnsServerServiceStatisticsCluster-levelFailureNumdnsserverfailureservfail ConfdString,
        affirmedServicesDnsServerServiceStatisticsCluster-levelFailureNumdnsserverfailureformerr ConfdString,
        affirmedServicesDnsServerServiceStatisticsCluster-levelFailureNumdnsserverfailurequeryother ConfdString,
        affirmedServicesDnsServerServiceStatisticsCluster-levelFailureNumdnsserverfailuredynamicupdatefwd ConfdString,
        affirmedServicesDnsServerServiceStatisticsCluster-levelFailureNumdnsserverfailuredynamicupdate ConfdString,
        affirmedServicesDnsServerServiceStatisticsCluster-levelFailureNumdnsserverfailuredynamicupdateprereq ConfdString,
        affirmedServicesDnsServerServiceStatisticsCluster-levelFailureNumdnsserverfailurezonexfr ConfdString,
        affirmedServicesDnsServerServiceStatisticsCluster-levelFailureNumdnsserverfailureednsversion ConfdString,
        affirmedServicesDnsServerServiceStatisticsCluster-levelFailureNumdnsserverfailureinvalidsig ConfdString,
        affirmedServicesDnsServerServiceStatisticsCluster-levelFailureNumdnsserverfailureauthqueriesrej ConfdString,
        affirmedServicesDnsServerServiceStatisticsCluster-levelFailureNumdnsserverfailurerecqueriesrej ConfdString,
        affirmedServicesDnsServerServiceStatisticsCluster-levelFailureNumdnsserverfailurexfrrej ConfdString,
        affirmedServicesDnsServerServiceStatisticsCluster-levelFailureNumdnsserverfailuredynamicupdaterej ConfdString,
        affirmedServicesDnsServerServiceStatisticsCluster-levelFailureNumdnsserverfailurenotifyrej ConfdString
    }

affirmedServicesDnsServerServiceStatisticsCluster-levelFailureChassis OBJECT-TYPE
    SYNTAX      Unsigned32
    MAX-ACCESS  not-accessible
    STATUS      current
    DESCRIPTION "chassis ID"
    ::= { affirmedServicesDnsServerServiceStatisticsCluster-levelFailureEntry 1 }

affirmedServicesDnsServerServiceStatisticsCluster-levelFailureNumdnsserverfailureservfail OBJECT-TYPE
    SYNTAX      ConfdString
    MAX-ACCESS  read-only
    STATUS      current
    DESCRIPTION "Number of Dns Server SERVFAIL failures"
    ::= { affirmedServicesDnsServerServiceStatisticsCluster-levelFailureEntry 2 }

affirmedServicesDnsServerServiceStatisticsCluster-levelFailureNumdnsserverfailureformerr OBJECT-TYPE
    SYNTAX      ConfdString
    MAX-ACCESS  read-only
    STATUS      current
    DESCRIPTION "Number of Dns Server FORMERR failures"
    ::= { affirmedServicesDnsServerServiceStatisticsCluster-levelFailureEntry 3 }

affirmedServicesDnsServerServiceStatisticsCluster-levelFailureNumdnsserverfailurequeryother OBJECT-TYPE
    SYNTAX      ConfdString
    MAX-ACCESS  read-only
    STATUS      current
    DESCRIPTION "Number of Dns Server other query failures"
    ::= { affirmedServicesDnsServerServiceStatisticsCluster-levelFailureEntry 4 }

affirmedServicesDnsServerServiceStatisticsCluster-levelFailureNumdnsserverfailuredynamicupdatefwd OBJECT-TYPE
    SYNTAX      ConfdString
    MAX-ACCESS  read-only
    STATUS      current
    DESCRIPTION "Number of Dns Server Dynamic Update forward failures"
    ::= { affirmedServicesDnsServerServiceStatisticsCluster-levelFailureEntry 5 }

affirmedServicesDnsServerServiceStatisticsCluster-levelFailureNumdnsserverfailuredynamicupdate OBJECT-TYPE
    SYNTAX      ConfdString
    MAX-ACCESS  read-only
    STATUS      current
    DESCRIPTION "Number of Dns Server Dynamic Update failures"
    ::= { affirmedServicesDnsServerServiceStatisticsCluster-levelFailureEntry 6 }

affirmedServicesDnsServerServiceStatisticsCluster-levelFailureNumdnsserverfailuredynamicupdateprereq OBJECT-TYPE
    SYNTAX      ConfdString
    MAX-ACCESS  read-only
    STATUS      current
    DESCRIPTION "Number of Dns Server Dynamic Updates rejected due to prerequisite failures"
    ::= { affirmedServicesDnsServerServiceStatisticsCluster-levelFailureEntry 7 }

affirmedServicesDnsServerServiceStatisticsCluster-levelFailureNumdnsserverfailurezonexfr OBJECT-TYPE
    SYNTAX      ConfdString
    MAX-ACCESS  read-only
    STATUS      current
    DESCRIPTION "Number of Dns Server Zone transfer failures"
    ::= { affirmedServicesDnsServerServiceStatisticsCluster-levelFailureEntry 8 }

affirmedServicesDnsServerServiceStatisticsCluster-levelFailureNumdnsserverfailureednsversion OBJECT-TYPE
    SYNTAX      ConfdString
    MAX-ACCESS  read-only
    STATUS      current
    DESCRIPTION "Number of Dns Server Bad EDNS version failures"
    ::= { affirmedServicesDnsServerServiceStatisticsCluster-levelFailureEntry 9 }

affirmedServicesDnsServerServiceStatisticsCluster-levelFailureNumdnsserverfailureinvalidsig OBJECT-TYPE
    SYNTAX      ConfdString
    MAX-ACCESS  read-only
    STATUS      current
    DESCRIPTION "Number of Dns Server Invalid SIG or TSIG(0) failures"
    ::= { affirmedServicesDnsServerServiceStatisticsCluster-levelFailureEntry 10 }

affirmedServicesDnsServerServiceStatisticsCluster-levelFailureNumdnsserverfailureauthqueriesrej OBJECT-TYPE
    SYNTAX      ConfdString
    MAX-ACCESS  read-only
    STATUS      current
    DESCRIPTION "Number of Dns Server Authoritative Queries Rejected"
    ::= { affirmedServicesDnsServerServiceStatisticsCluster-levelFailureEntry 11 }

affirmedServicesDnsServerServiceStatisticsCluster-levelFailureNumdnsserverfailurerecqueriesrej OBJECT-TYPE
    SYNTAX      ConfdString
    MAX-ACCESS  read-only
    STATUS      current
    DESCRIPTION "Number of Dns Server Recursive Queries Rejected"
    ::= { affirmedServicesDnsServerServiceStatisticsCluster-levelFailureEntry 12 }

affirmedServicesDnsServerServiceStatisticsCluster-levelFailureNumdnsserverfailurexfrrej OBJECT-TYPE
    SYNTAX      ConfdString
    MAX-ACCESS  read-only
    STATUS      current
    DESCRIPTION "Number of Dns Server Zone Transfer Requests Rejected"
    ::= { affirmedServicesDnsServerServiceStatisticsCluster-levelFailureEntry 13 }

affirmedServicesDnsServerServiceStatisticsCluster-levelFailureNumdnsserverfailuredynamicupdaterej OBJECT-TYPE
    SYNTAX      ConfdString
    MAX-ACCESS  read-only
    STATUS      current
    DESCRIPTION "Number of Dns Server Dynamic Update Requests Rejected"
    ::= { affirmedServicesDnsServerServiceStatisticsCluster-levelFailureEntry 14 }

affirmedServicesDnsServerServiceStatisticsCluster-levelFailureNumdnsserverfailurenotifyrej OBJECT-TYPE
    SYNTAX      ConfdString
    MAX-ACCESS  read-only
    STATUS      current
    DESCRIPTION "Number of Dns Server Incoming Notifies Rejected"
    ::= { affirmedServicesDnsServerServiceStatisticsCluster-levelFailureEntry 15 }

affirmedServicesDnsServerServiceStatisticsCluster-levelCacheTable OBJECT-TYPE
    SYNTAX      SEQUENCE OF AffirmedServicesDnsServerServiceStatisticsCluster-levelCacheEntry
    MAX-ACCESS  not-accessible
    STATUS      current
    DESCRIPTION ""
    ::= { affirmedServicesDnsServerServiceStatisticsCluster-level 5 }

affirmedServicesDnsServerServiceStatisticsCluster-levelCacheEntry OBJECT-TYPE
    SYNTAX      AffirmedServicesDnsServerServiceStatisticsCluster-levelCacheEntry
    MAX-ACCESS  not-accessible
    STATUS      current
    DESCRIPTION ""
    INDEX { affirmedServicesDnsServerServiceStatisticsCluster-levelCacheChassis }
        ::= { affirmedServicesDnsServerServiceStatisticsCluster-levelCacheTable 1 }

AffirmedServicesDnsServerServiceStatisticsCluster-levelCacheEntry ::=
    SEQUENCE {
        affirmedServicesDnsServerServiceStatisticsCluster-levelCacheChassis Unsigned32,
        affirmedServicesDnsServerServiceStatisticsCluster-levelCacheNumdnsservercachehits ConfdString,
        affirmedServicesDnsServerServiceStatisticsCluster-levelCacheNumdnsservercachemisses ConfdString,
        affirmedServicesDnsServerServiceStatisticsCluster-levelCacheNumdnsservercachequeryhits ConfdString,
        affirmedServicesDnsServerServiceStatisticsCluster-levelCacheNumdnsservercachequerymisses ConfdString,
        affirmedServicesDnsServerServiceStatisticsCluster-levelCacheNumdnsservercachedeletelru ConfdString,
        affirmedServicesDnsServerServiceStatisticsCluster-levelCacheNumdnsservercachedeletettl ConfdString,
        affirmedServicesDnsServerServiceStatisticsCluster-levelCacheNumdnsservercachedbnodes ConfdString,
        affirmedServicesDnsServerServiceStatisticsCluster-levelCacheNumdnsservercachedbhashbuckets ConfdString,
        affirmedServicesDnsServerServiceStatisticsCluster-levelCacheNumdnsservercachetreememtotal ConfdString,
        affirmedServicesDnsServerServiceStatisticsCluster-levelCacheNumdnsservercachetreememinuse ConfdString,
        affirmedServicesDnsServerServiceStatisticsCluster-levelCacheNumdnsservercachetreememmax ConfdString,
        affirmedServicesDnsServerServiceStatisticsCluster-levelCacheNumdnsservercacheheapmemtotal ConfdString,
        affirmedServicesDnsServerServiceStatisticsCluster-levelCacheNumdnsservercacheheapmeminuse ConfdString,
        affirmedServicesDnsServerServiceStatisticsCluster-levelCacheNumdnsservercacheheapmemmax ConfdString
    }

affirmedServicesDnsServerServiceStatisticsCluster-levelCacheChassis OBJECT-TYPE
    SYNTAX      Unsigned32
    MAX-ACCESS  not-accessible
    STATUS      current
    DESCRIPTION "chassis ID"
    ::= { affirmedServicesDnsServerServiceStatisticsCluster-levelCacheEntry 1 }

affirmedServicesDnsServerServiceStatisticsCluster-levelCacheNumdnsservercachehits OBJECT-TYPE
    SYNTAX      ConfdString
    MAX-ACCESS  read-only
    STATUS      current
    DESCRIPTION "Number of Dns Server Cache hits"
    ::= { affirmedServicesDnsServerServiceStatisticsCluster-levelCacheEntry 2 }

affirmedServicesDnsServerServiceStatisticsCluster-levelCacheNumdnsservercachemisses OBJECT-TYPE
    SYNTAX      ConfdString
    MAX-ACCESS  read-only
    STATUS      current
    DESCRIPTION "Number of Dns Server Cache misses"
    ::= { affirmedServicesDnsServerServiceStatisticsCluster-levelCacheEntry 3 }

affirmedServicesDnsServerServiceStatisticsCluster-levelCacheNumdnsservercachequeryhits OBJECT-TYPE
    SYNTAX      ConfdString
    MAX-ACCESS  read-only
    STATUS      current
    DESCRIPTION "Number of Dns Server Cache Query hits"
    ::= { affirmedServicesDnsServerServiceStatisticsCluster-levelCacheEntry 4 }

affirmedServicesDnsServerServiceStatisticsCluster-levelCacheNumdnsservercachequerymisses OBJECT-TYPE
    SYNTAX      ConfdString
    MAX-ACCESS  read-only
    STATUS      current
    DESCRIPTION "Number of Dns Server Cache Query misses"
    ::= { affirmedServicesDnsServerServiceStatisticsCluster-levelCacheEntry 5 }

affirmedServicesDnsServerServiceStatisticsCluster-levelCacheNumdnsservercachedeletelru OBJECT-TYPE
    SYNTAX      ConfdString
    MAX-ACCESS  read-only
    STATUS      current
    DESCRIPTION "Number of Dns Server Cache LRU deletions"
    ::= { affirmedServicesDnsServerServiceStatisticsCluster-levelCacheEntry 6 }

affirmedServicesDnsServerServiceStatisticsCluster-levelCacheNumdnsservercachedeletettl OBJECT-TYPE
    SYNTAX      ConfdString
    MAX-ACCESS  read-only
    STATUS      current
    DESCRIPTION "Number of Dns Server Cache TTL deletions"
    ::= { affirmedServicesDnsServerServiceStatisticsCluster-levelCacheEntry 7 }

affirmedServicesDnsServerServiceStatisticsCluster-levelCacheNumdnsservercachedbnodes OBJECT-TYPE
    SYNTAX      ConfdString
    MAX-ACCESS  read-only
    STATUS      current
    DESCRIPTION "Number of Dns Server Cache database nodes"
    ::= { affirmedServicesDnsServerServiceStatisticsCluster-levelCacheEntry 8 }

affirmedServicesDnsServerServiceStatisticsCluster-levelCacheNumdnsservercachedbhashbuckets OBJECT-TYPE
    SYNTAX      ConfdString
    MAX-ACCESS  read-only
    STATUS      current
    DESCRIPTION "Number of Dns Server Cache database hash buckets"
    ::= { affirmedServicesDnsServerServiceStatisticsCluster-levelCacheEntry 9 }

affirmedServicesDnsServerServiceStatisticsCluster-levelCacheNumdnsservercachetreememtotal OBJECT-TYPE
    SYNTAX      ConfdString
    MAX-ACCESS  read-only
    STATUS      current
    DESCRIPTION "Dns Server Cache tree memory total"
    ::= { affirmedServicesDnsServerServiceStatisticsCluster-levelCacheEntry 10 }

affirmedServicesDnsServerServiceStatisticsCluster-levelCacheNumdnsservercachetreememinuse OBJECT-TYPE
    SYNTAX      ConfdString
    MAX-ACCESS  read-only
    STATUS      current
    DESCRIPTION "Dns Server Cache tree memory in use"
    ::= { affirmedServicesDnsServerServiceStatisticsCluster-levelCacheEntry 11 }

affirmedServicesDnsServerServiceStatisticsCluster-levelCacheNumdnsservercachetreememmax OBJECT-TYPE
    SYNTAX      ConfdString
    MAX-ACCESS  read-only
    STATUS      current
    DESCRIPTION "Dns Server Cache tree memory max"
    ::= { affirmedServicesDnsServerServiceStatisticsCluster-levelCacheEntry 12 }

affirmedServicesDnsServerServiceStatisticsCluster-levelCacheNumdnsservercacheheapmemtotal OBJECT-TYPE
    SYNTAX      ConfdString
    MAX-ACCESS  read-only
    STATUS      current
    DESCRIPTION "Dns Server Cache heap memory total"
    ::= { affirmedServicesDnsServerServiceStatisticsCluster-levelCacheEntry 13 }

affirmedServicesDnsServerServiceStatisticsCluster-levelCacheNumdnsservercacheheapmeminuse OBJECT-TYPE
    SYNTAX      ConfdString
    MAX-ACCESS  read-only
    STATUS      current
    DESCRIPTION "Dns Server Cache heap memory in use"
    ::= { affirmedServicesDnsServerServiceStatisticsCluster-levelCacheEntry 14 }

affirmedServicesDnsServerServiceStatisticsCluster-levelCacheNumdnsservercacheheapmemmax OBJECT-TYPE
    SYNTAX      ConfdString
    MAX-ACCESS  read-only
    STATUS      current
    DESCRIPTION "Dns Server Cache heap memory max"
    ::= { affirmedServicesDnsServerServiceStatisticsCluster-levelCacheEntry 15 }

affirmedServicesDnsServerServiceStatisticsCluster-levelSocketTable OBJECT-TYPE
    SYNTAX      SEQUENCE OF AffirmedServicesDnsServerServiceStatisticsCluster-levelSocketEntry
    MAX-ACCESS  not-accessible
    STATUS      current
    DESCRIPTION ""
    ::= { affirmedServicesDnsServerServiceStatisticsCluster-level 6 }

affirmedServicesDnsServerServiceStatisticsCluster-levelSocketEntry OBJECT-TYPE
    SYNTAX      AffirmedServicesDnsServerServiceStatisticsCluster-levelSocketEntry
    MAX-ACCESS  not-accessible
    STATUS      current
    DESCRIPTION ""
    INDEX { affirmedServicesDnsServerServiceStatisticsCluster-levelSocketChassis }
        ::= { affirmedServicesDnsServerServiceStatisticsCluster-levelSocketTable 1 }

AffirmedServicesDnsServerServiceStatisticsCluster-levelSocketEntry ::=
    SEQUENCE {
        affirmedServicesDnsServerServiceStatisticsCluster-levelSocketChassis Unsigned32,
        affirmedServicesDnsServerServiceStatisticsCluster-levelSocketNumdnsserversockudpopen ConfdString,
        affirmedServicesDnsServerServiceStatisticsCluster-levelSocketNumdnsserversockudpopenfail ConfdString,
        affirmedServicesDnsServerServiceStatisticsCluster-levelSocketNumdnsserversockudpclose ConfdString,
        affirmedServicesDnsServerServiceStatisticsCluster-levelSocketNumdnsserversockudpbindfail ConfdString,
        affirmedServicesDnsServerServiceStatisticsCluster-levelSocketNumdnsserversockudpconnect ConfdString,
        affirmedServicesDnsServerServiceStatisticsCluster-levelSocketNumdnsserversockudpconnectfail ConfdString,
        affirmedServicesDnsServerServiceStatisticsCluster-levelSocketNumdnsserversockudpsendfail ConfdString,
        affirmedServicesDnsServerServiceStatisticsCluster-levelSocketNumdnsserversockudprecvfail ConfdString,
        affirmedServicesDnsServerServiceStatisticsCluster-levelSocketNumdnsserversocktcpopen ConfdString,
        affirmedServicesDnsServerServiceStatisticsCluster-levelSocketNumdnsserversocktcpopenfail ConfdString,
        affirmedServicesDnsServerServiceStatisticsCluster-levelSocketNumdnsserversocktcpclose ConfdString,
        affirmedServicesDnsServerServiceStatisticsCluster-levelSocketNumdnsserversocktcpbindfail ConfdString,
        affirmedServicesDnsServerServiceStatisticsCluster-levelSocketNumdnsserversocktcpconnect ConfdString,
        affirmedServicesDnsServerServiceStatisticsCluster-levelSocketNumdnsserversocktcpconnectfail ConfdString,
        affirmedServicesDnsServerServiceStatisticsCluster-levelSocketNumdnsserversocktcpaccept ConfdString,
        affirmedServicesDnsServerServiceStatisticsCluster-levelSocketNumdnsserversocktcpacceptfail ConfdString,
        affirmedServicesDnsServerServiceStatisticsCluster-levelSocketNumdnsserversocktcpsendfail ConfdString,
        affirmedServicesDnsServerServiceStatisticsCluster-levelSocketNumdnsserversocktcprecvfail ConfdString
    }

affirmedServicesDnsServerServiceStatisticsCluster-levelSocketChassis OBJECT-TYPE
    SYNTAX      Unsigned32
    MAX-ACCESS  not-accessible
    STATUS      current
    DESCRIPTION "chassis ID"
    ::= { affirmedServicesDnsServerServiceStatisticsCluster-levelSocketEntry 1 }

affirmedServicesDnsServerServiceStatisticsCluster-levelSocketNumdnsserversockudpopen OBJECT-TYPE
    SYNTAX      ConfdString
    MAX-ACCESS  read-only
    STATUS      current
    DESCRIPTION "Number of Dns Server UDP sockets opened successfully"
    ::= { affirmedServicesDnsServerServiceStatisticsCluster-levelSocketEntry 2 }

affirmedServicesDnsServerServiceStatisticsCluster-levelSocketNumdnsserversockudpopenfail OBJECT-TYPE
    SYNTAX      ConfdString
    MAX-ACCESS  read-only
    STATUS      current
    DESCRIPTION "Number of Dns Server UDP sockets failed to open"
    ::= { affirmedServicesDnsServerServiceStatisticsCluster-levelSocketEntry 3 }

affirmedServicesDnsServerServiceStatisticsCluster-levelSocketNumdnsserversockudpclose OBJECT-TYPE
    SYNTAX      ConfdString
    MAX-ACCESS  read-only
    STATUS      current
    DESCRIPTION "Number of Dns Server UDP sockets closed"
    ::= { affirmedServicesDnsServerServiceStatisticsCluster-levelSocketEntry 4 }

affirmedServicesDnsServerServiceStatisticsCluster-levelSocketNumdnsserversockudpbindfail OBJECT-TYPE
    SYNTAX      ConfdString
    MAX-ACCESS  read-only
    STATUS      current
    DESCRIPTION "Number of Dns Server UDP sockets Bind failed"
    ::= { affirmedServicesDnsServerServiceStatisticsCluster-levelSocketEntry 5 }

affirmedServicesDnsServerServiceStatisticsCluster-levelSocketNumdnsserversockudpconnect OBJECT-TYPE
    SYNTAX      ConfdString
    MAX-ACCESS  read-only
    STATUS      current
    DESCRIPTION "Number of Dns Server UDP sockets connected successfully"
    ::= { affirmedServicesDnsServerServiceStatisticsCluster-levelSocketEntry 6 }

affirmedServicesDnsServerServiceStatisticsCluster-levelSocketNumdnsserversockudpconnectfail OBJECT-TYPE
    SYNTAX      ConfdString
    MAX-ACCESS  read-only
    STATUS      current
    DESCRIPTION "Number of Dns Server UDP sockets failed to connect"
    ::= { affirmedServicesDnsServerServiceStatisticsCluster-levelSocketEntry 7 }

affirmedServicesDnsServerServiceStatisticsCluster-levelSocketNumdnsserversockudpsendfail OBJECT-TYPE
    SYNTAX      ConfdString
    MAX-ACCESS  read-only
    STATUS      current
    DESCRIPTION "Number of Dns Server UDP sockets failed to send"
    ::= { affirmedServicesDnsServerServiceStatisticsCluster-levelSocketEntry 8 }

affirmedServicesDnsServerServiceStatisticsCluster-levelSocketNumdnsserversockudprecvfail OBJECT-TYPE
    SYNTAX      ConfdString
    MAX-ACCESS  read-only
    STATUS      current
    DESCRIPTION "Number of Dns Server UDP sockets failed to receive"
    ::= { affirmedServicesDnsServerServiceStatisticsCluster-levelSocketEntry 9 }

affirmedServicesDnsServerServiceStatisticsCluster-levelSocketNumdnsserversocktcpopen OBJECT-TYPE
    SYNTAX      ConfdString
    MAX-ACCESS  read-only
    STATUS      current
    DESCRIPTION "Number of Dns Server TCP sockets opened successfully"
    ::= { affirmedServicesDnsServerServiceStatisticsCluster-levelSocketEntry 10 }

affirmedServicesDnsServerServiceStatisticsCluster-levelSocketNumdnsserversocktcpopenfail OBJECT-TYPE
    SYNTAX      ConfdString
    MAX-ACCESS  read-only
    STATUS      current
    DESCRIPTION "Number of Dns Server TCP sockets failed to open"
    ::= { affirmedServicesDnsServerServiceStatisticsCluster-levelSocketEntry 11 }

affirmedServicesDnsServerServiceStatisticsCluster-levelSocketNumdnsserversocktcpclose OBJECT-TYPE
    SYNTAX      ConfdString
    MAX-ACCESS  read-only
    STATUS      current
    DESCRIPTION "Number of Dns Server TCP sockets closed"
    ::= { affirmedServicesDnsServerServiceStatisticsCluster-levelSocketEntry 12 }

affirmedServicesDnsServerServiceStatisticsCluster-levelSocketNumdnsserversocktcpbindfail OBJECT-TYPE
    SYNTAX      ConfdString
    MAX-ACCESS  read-only
    STATUS      current
    DESCRIPTION "Number of Dns Server TCP sockets Bind failed"
    ::= { affirmedServicesDnsServerServiceStatisticsCluster-levelSocketEntry 13 }

affirmedServicesDnsServerServiceStatisticsCluster-levelSocketNumdnsserversocktcpconnect OBJECT-TYPE
    SYNTAX      ConfdString
    MAX-ACCESS  read-only
    STATUS      current
    DESCRIPTION "Number of Dns Server TCP sockets connected successfully"
    ::= { affirmedServicesDnsServerServiceStatisticsCluster-levelSocketEntry 14 }

affirmedServicesDnsServerServiceStatisticsCluster-levelSocketNumdnsserversocktcpconnectfail OBJECT-TYPE
    SYNTAX      ConfdString
    MAX-ACCESS  read-only
    STATUS      current
    DESCRIPTION "Number of Dns Server TCP sockets failed to connect"
    ::= { affirmedServicesDnsServerServiceStatisticsCluster-levelSocketEntry 15 }

affirmedServicesDnsServerServiceStatisticsCluster-levelSocketNumdnsserversocktcpaccept OBJECT-TYPE
    SYNTAX      ConfdString
    MAX-ACCESS  read-only
    STATUS      current
    DESCRIPTION "Number of Dns Server TCP sockets accepted connections"
    ::= { affirmedServicesDnsServerServiceStatisticsCluster-levelSocketEntry 16 }

affirmedServicesDnsServerServiceStatisticsCluster-levelSocketNumdnsserversocktcpacceptfail OBJECT-TYPE
    SYNTAX      ConfdString
    MAX-ACCESS  read-only
    STATUS      current
    DESCRIPTION "Number of Dns Server TCP sockets connections failed to accept"
    ::= { affirmedServicesDnsServerServiceStatisticsCluster-levelSocketEntry 17 }

affirmedServicesDnsServerServiceStatisticsCluster-levelSocketNumdnsserversocktcpsendfail OBJECT-TYPE
    SYNTAX      ConfdString
    MAX-ACCESS  read-only
    STATUS      current
    DESCRIPTION "Number of Dns Server TCP sockets failed to send"
    ::= { affirmedServicesDnsServerServiceStatisticsCluster-levelSocketEntry 18 }

affirmedServicesDnsServerServiceStatisticsCluster-levelSocketNumdnsserversocktcprecvfail OBJECT-TYPE
    SYNTAX      ConfdString
    MAX-ACCESS  read-only
    STATUS      current
    DESCRIPTION "Number of Dns Server TCP sockets failed to receive"
    ::= { affirmedServicesDnsServerServiceStatisticsCluster-levelSocketEntry 19 }

affirmedServicesDnsServerServiceStatisticsCluster-levelResolverTable OBJECT-TYPE
    SYNTAX      SEQUENCE OF AffirmedServicesDnsServerServiceStatisticsCluster-levelResolverEntry
    MAX-ACCESS  not-accessible
    STATUS      current
    DESCRIPTION ""
    ::= { affirmedServicesDnsServerServiceStatisticsCluster-level 7 }

affirmedServicesDnsServerServiceStatisticsCluster-levelResolverEntry OBJECT-TYPE
    SYNTAX      AffirmedServicesDnsServerServiceStatisticsCluster-levelResolverEntry
    MAX-ACCESS  not-accessible
    STATUS      current
    DESCRIPTION ""
    INDEX { affirmedServicesDnsServerServiceStatisticsCluster-levelResolverChassis }
        ::= { affirmedServicesDnsServerServiceStatisticsCluster-levelResolverTable 1 }

AffirmedServicesDnsServerServiceStatisticsCluster-levelResolverEntry ::=
    SEQUENCE {
        affirmedServicesDnsServerServiceStatisticsCluster-levelResolverChassis Unsigned32,
        affirmedServicesDnsServerServiceStatisticsCluster-levelResolverNumdnsserverresolvipv4queries ConfdString,
        affirmedServicesDnsServerServiceStatisticsCluster-levelResolverNumdnsserverresolvipv6queries ConfdString,
        affirmedServicesDnsServerServiceStatisticsCluster-levelResolverNumdnsserverresolvipv4responses ConfdString,
        affirmedServicesDnsServerServiceStatisticsCluster-levelResolverNumdnsserverresolvipv6responses ConfdString,
        affirmedServicesDnsServerServiceStatisticsCluster-levelResolverNumdnsserverresolvnxdomainresponses ConfdString,
        affirmedServicesDnsServerServiceStatisticsCluster-levelResolverNumdnsserverresolvservfailresponses ConfdString,
        affirmedServicesDnsServerServiceStatisticsCluster-levelResolverNumdnsserverresolvformerrresponses ConfdString,
        affirmedServicesDnsServerServiceStatisticsCluster-levelResolverNumdnsserverresolvothererrresponses ConfdString,
        affirmedServicesDnsServerServiceStatisticsCluster-levelResolverNumdnsserverresolvednsfail ConfdString,
        affirmedServicesDnsServerServiceStatisticsCluster-levelResolverNumdnsserverresolvmismatchresponses ConfdString,
        affirmedServicesDnsServerServiceStatisticsCluster-levelResolverNumdnsserverresolvtruncatedresponses ConfdString,
        affirmedServicesDnsServerServiceStatisticsCluster-levelResolverNumdnsserverresolvlamedelegations ConfdString,
        affirmedServicesDnsServerServiceStatisticsCluster-levelResolverNumdnsserverresolvqueryretries ConfdString,
        affirmedServicesDnsServerServiceStatisticsCluster-levelResolverNumdnsserverresolvqueryaborts ConfdString,
        affirmedServicesDnsServerServiceStatisticsCluster-levelResolverNumdnsserverresolvquerysockfail ConfdString,
        affirmedServicesDnsServerServiceStatisticsCluster-levelResolverNumdnsserverresolvquerytimeout ConfdString,
        affirmedServicesDnsServerServiceStatisticsCluster-levelResolverNumdnsserverresolvgluefetchipv4 ConfdString,
        affirmedServicesDnsServerServiceStatisticsCluster-levelResolverNumdnsserverresolvgluefetchipv6 ConfdString,
        affirmedServicesDnsServerServiceStatisticsCluster-levelResolverNumdnsserverresolvgluefetchipv4fail ConfdString,
        affirmedServicesDnsServerServiceStatisticsCluster-levelResolverNumdnsserverresolvgluefetchipv6fail ConfdString,
        affirmedServicesDnsServerServiceStatisticsCluster-levelResolverNumdnsserverresolvvalattempt ConfdString,
        affirmedServicesDnsServerServiceStatisticsCluster-levelResolverNumdnsserverresolvvalok ConfdString,
        affirmedServicesDnsServerServiceStatisticsCluster-levelResolverNumdnsserverresolvvalnegok ConfdString,
        affirmedServicesDnsServerServiceStatisticsCluster-levelResolverNumdnsserverresolvvalfail ConfdString,
        affirmedServicesDnsServerServiceStatisticsCluster-levelResolverNumdnsserverresolvqueryrtt0 ConfdString,
        affirmedServicesDnsServerServiceStatisticsCluster-levelResolverNumdnsserverresolvqueryrtt1 ConfdString,
        affirmedServicesDnsServerServiceStatisticsCluster-levelResolverNumdnsserverresolvqueryrtt2 ConfdString,
        affirmedServicesDnsServerServiceStatisticsCluster-levelResolverNumdnsserverresolvqueryrtt3 ConfdString,
        affirmedServicesDnsServerServiceStatisticsCluster-levelResolverNumdnsserverresolvqueryrtt4 ConfdString,
        affirmedServicesDnsServerServiceStatisticsCluster-levelResolverNumdnsserverresolvqueryrtt5 ConfdString,
        affirmedServicesDnsServerServiceStatisticsCluster-levelResolverNumdnsserverresolvnfetch ConfdString,
        affirmedServicesDnsServerServiceStatisticsCluster-levelResolverNumdnsserverresolvdisprequdp ConfdString,
        affirmedServicesDnsServerServiceStatisticsCluster-levelResolverNumdnsserverresolvdispreqtcp ConfdString,
        affirmedServicesDnsServerServiceStatisticsCluster-levelResolverNumdnsserverresolvbuckets ConfdString,
        affirmedServicesDnsServerServiceStatisticsCluster-levelResolverNumdnsserverresolvrefused ConfdString,
        affirmedServicesDnsServerServiceStatisticsCluster-levelResolverNumdnsserverresolvcookienew ConfdString,
        affirmedServicesDnsServerServiceStatisticsCluster-levelResolverNumdnsserverresolvcookieout ConfdString,
        affirmedServicesDnsServerServiceStatisticsCluster-levelResolverNumdnsserverresolvcookiein ConfdString,
        affirmedServicesDnsServerServiceStatisticsCluster-levelResolverNumdnsserverresolvcookieok ConfdString,
        affirmedServicesDnsServerServiceStatisticsCluster-levelResolverNumdnsserverresolvbadvers ConfdString,
        affirmedServicesDnsServerServiceStatisticsCluster-levelResolverNumdnsserverresolvbadcookie ConfdString,
        affirmedServicesDnsServerServiceStatisticsCluster-levelResolverNumdnsserverresolvzonequota ConfdString,
        affirmedServicesDnsServerServiceStatisticsCluster-levelResolverNumdnsserverresolvserverquota ConfdString,
        affirmedServicesDnsServerServiceStatisticsCluster-levelResolverNumdnsserverresolvnextitem ConfdString
    }

affirmedServicesDnsServerServiceStatisticsCluster-levelResolverChassis OBJECT-TYPE
    SYNTAX      Unsigned32
    MAX-ACCESS  not-accessible
    STATUS      current
    DESCRIPTION "chassis ID"
    ::= { affirmedServicesDnsServerServiceStatisticsCluster-levelResolverEntry 1 }

affirmedServicesDnsServerServiceStatisticsCluster-levelResolverNumdnsserverresolvipv4queries OBJECT-TYPE
    SYNTAX      ConfdString
    MAX-ACCESS  read-only
    STATUS      current
    DESCRIPTION "Number of Dns Server Resolver IPv4 queries sent"
    ::= { affirmedServicesDnsServerServiceStatisticsCluster-levelResolverEntry 2 }

affirmedServicesDnsServerServiceStatisticsCluster-levelResolverNumdnsserverresolvipv6queries OBJECT-TYPE
    SYNTAX      ConfdString
    MAX-ACCESS  read-only
    STATUS      current
    DESCRIPTION "Number of Dns Server Resolver IPv6 queries sent"
    ::= { affirmedServicesDnsServerServiceStatisticsCluster-levelResolverEntry 3 }

affirmedServicesDnsServerServiceStatisticsCluster-levelResolverNumdnsserverresolvipv4responses OBJECT-TYPE
    SYNTAX      ConfdString
    MAX-ACCESS  read-only
    STATUS      current
    DESCRIPTION "Number of Dns Server Resolver IPv4 responses received"
    ::= { affirmedServicesDnsServerServiceStatisticsCluster-levelResolverEntry 4 }

affirmedServicesDnsServerServiceStatisticsCluster-levelResolverNumdnsserverresolvipv6responses OBJECT-TYPE
    SYNTAX      ConfdString
    MAX-ACCESS  read-only
    STATUS      current
    DESCRIPTION "Number of Dns Server Resolver IPv6 responses received"
    ::= { affirmedServicesDnsServerServiceStatisticsCluster-levelResolverEntry 5 }

affirmedServicesDnsServerServiceStatisticsCluster-levelResolverNumdnsserverresolvnxdomainresponses OBJECT-TYPE
    SYNTAX      ConfdString
    MAX-ACCESS  read-only
    STATUS      current
    DESCRIPTION "Number of Dns Server Resolver NXDOMAIN responses received"
    ::= { affirmedServicesDnsServerServiceStatisticsCluster-levelResolverEntry 6 }

affirmedServicesDnsServerServiceStatisticsCluster-levelResolverNumdnsserverresolvservfailresponses OBJECT-TYPE
    SYNTAX      ConfdString
    MAX-ACCESS  read-only
    STATUS      current
    DESCRIPTION "Number of Dns Server Resolver SERVFAIL responses received"
    ::= { affirmedServicesDnsServerServiceStatisticsCluster-levelResolverEntry 7 }

affirmedServicesDnsServerServiceStatisticsCluster-levelResolverNumdnsserverresolvformerrresponses OBJECT-TYPE
    SYNTAX      ConfdString
    MAX-ACCESS  read-only
    STATUS      current
    DESCRIPTION "Number of Dns Server Resolver FORMERR responses received"
    ::= { affirmedServicesDnsServerServiceStatisticsCluster-levelResolverEntry 8 }

affirmedServicesDnsServerServiceStatisticsCluster-levelResolverNumdnsserverresolvothererrresponses OBJECT-TYPE
    SYNTAX      ConfdString
    MAX-ACCESS  read-only
    STATUS      current
    DESCRIPTION "Number of Dns Server Resolver Other Error responses received"
    ::= { affirmedServicesDnsServerServiceStatisticsCluster-levelResolverEntry 9 }

affirmedServicesDnsServerServiceStatisticsCluster-levelResolverNumdnsserverresolvednsfail OBJECT-TYPE
    SYNTAX      ConfdString
    MAX-ACCESS  read-only
    STATUS      current
    DESCRIPTION "Number of Dns Server Resolver EDNS0 query Failures"
    ::= { affirmedServicesDnsServerServiceStatisticsCluster-levelResolverEntry 10 }

affirmedServicesDnsServerServiceStatisticsCluster-levelResolverNumdnsserverresolvmismatchresponses OBJECT-TYPE
    SYNTAX      ConfdString
    MAX-ACCESS  read-only
    STATUS      current
    DESCRIPTION "Number of Dns Server Resolver Mismatch responses received"
    ::= { affirmedServicesDnsServerServiceStatisticsCluster-levelResolverEntry 11 }

affirmedServicesDnsServerServiceStatisticsCluster-levelResolverNumdnsserverresolvtruncatedresponses OBJECT-TYPE
    SYNTAX      ConfdString
    MAX-ACCESS  read-only
    STATUS      current
    DESCRIPTION "Number of Dns Server Resolver Truncated responses received"
    ::= { affirmedServicesDnsServerServiceStatisticsCluster-levelResolverEntry 12 }

affirmedServicesDnsServerServiceStatisticsCluster-levelResolverNumdnsserverresolvlamedelegations OBJECT-TYPE
    SYNTAX      ConfdString
    MAX-ACCESS  read-only
    STATUS      current
    DESCRIPTION "Number of Dns Server Resolver Lame Delegations received"
    ::= { affirmedServicesDnsServerServiceStatisticsCluster-levelResolverEntry 13 }

affirmedServicesDnsServerServiceStatisticsCluster-levelResolverNumdnsserverresolvqueryretries OBJECT-TYPE
    SYNTAX      ConfdString
    MAX-ACCESS  read-only
    STATUS      current
    DESCRIPTION "Number of Dns Server Resolver Query Retries Performed"
    ::= { affirmedServicesDnsServerServiceStatisticsCluster-levelResolverEntry 14 }

affirmedServicesDnsServerServiceStatisticsCluster-levelResolverNumdnsserverresolvqueryaborts OBJECT-TYPE
    SYNTAX      ConfdString
    MAX-ACCESS  read-only
    STATUS      current
    DESCRIPTION "Number of Dns Server Resolver Queries Aborted"
    ::= { affirmedServicesDnsServerServiceStatisticsCluster-levelResolverEntry 15 }

affirmedServicesDnsServerServiceStatisticsCluster-levelResolverNumdnsserverresolvquerysockfail OBJECT-TYPE
    SYNTAX      ConfdString
    MAX-ACCESS  read-only
    STATUS      current
    DESCRIPTION "Number of Dns Server Resolver Failures in opening query sockets"
    ::= { affirmedServicesDnsServerServiceStatisticsCluster-levelResolverEntry 16 }

affirmedServicesDnsServerServiceStatisticsCluster-levelResolverNumdnsserverresolvquerytimeout OBJECT-TYPE
    SYNTAX      ConfdString
    MAX-ACCESS  read-only
    STATUS      current
    DESCRIPTION "Number of Dns Server Resolver Query timeouts"
    ::= { affirmedServicesDnsServerServiceStatisticsCluster-levelResolverEntry 17 }

affirmedServicesDnsServerServiceStatisticsCluster-levelResolverNumdnsserverresolvgluefetchipv4 OBJECT-TYPE
    SYNTAX      ConfdString
    MAX-ACCESS  read-only
    STATUS      current
    DESCRIPTION "Number of Dns Server Resolver IPv4 NS Address fetches"
    ::= { affirmedServicesDnsServerServiceStatisticsCluster-levelResolverEntry 18 }

affirmedServicesDnsServerServiceStatisticsCluster-levelResolverNumdnsserverresolvgluefetchipv6 OBJECT-TYPE
    SYNTAX      ConfdString
    MAX-ACCESS  read-only
    STATUS      current
    DESCRIPTION "Number of Dns Server Resolver IPv6 NS Address fetches"
    ::= { affirmedServicesDnsServerServiceStatisticsCluster-levelResolverEntry 19 }

affirmedServicesDnsServerServiceStatisticsCluster-levelResolverNumdnsserverresolvgluefetchipv4fail OBJECT-TYPE
    SYNTAX      ConfdString
    MAX-ACCESS  read-only
    STATUS      current
    DESCRIPTION "Number of Dns Server Resolver IPv4 NS Address fetches failed"
    ::= { affirmedServicesDnsServerServiceStatisticsCluster-levelResolverEntry 20 }

affirmedServicesDnsServerServiceStatisticsCluster-levelResolverNumdnsserverresolvgluefetchipv6fail OBJECT-TYPE
    SYNTAX      ConfdString
    MAX-ACCESS  read-only
    STATUS      current
    DESCRIPTION "Number of Dns Server Resolver IPv6 NS Address fetches failed"
    ::= { affirmedServicesDnsServerServiceStatisticsCluster-levelResolverEntry 21 }

affirmedServicesDnsServerServiceStatisticsCluster-levelResolverNumdnsserverresolvvalattempt OBJECT-TYPE
    SYNTAX      ConfdString
    MAX-ACCESS  read-only
    STATUS      current
    DESCRIPTION "Number of Dns Server Resolver DNSSEC Validation Attempted"
    ::= { affirmedServicesDnsServerServiceStatisticsCluster-levelResolverEntry 22 }

affirmedServicesDnsServerServiceStatisticsCluster-levelResolverNumdnsserverresolvvalok OBJECT-TYPE
    SYNTAX      ConfdString
    MAX-ACCESS  read-only
    STATUS      current
    DESCRIPTION "Number of Dns Server Resolver DNSSEC Validation Succeeded"
    ::= { affirmedServicesDnsServerServiceStatisticsCluster-levelResolverEntry 23 }

affirmedServicesDnsServerServiceStatisticsCluster-levelResolverNumdnsserverresolvvalnegok OBJECT-TYPE
    SYNTAX      ConfdString
    MAX-ACCESS  read-only
    STATUS      current
    DESCRIPTION "Number of Dns Server Resolver DNSSEC Validation on Negative Info Succeeded"
    ::= { affirmedServicesDnsServerServiceStatisticsCluster-levelResolverEntry 24 }

affirmedServicesDnsServerServiceStatisticsCluster-levelResolverNumdnsserverresolvvalfail OBJECT-TYPE
    SYNTAX      ConfdString
    MAX-ACCESS  read-only
    STATUS      current
    DESCRIPTION "Number of Dns Server Resolver DNSSEC Validation Failed"
    ::= { affirmedServicesDnsServerServiceStatisticsCluster-levelResolverEntry 25 }

affirmedServicesDnsServerServiceStatisticsCluster-levelResolverNumdnsserverresolvqueryrtt0 OBJECT-TYPE
    SYNTAX      ConfdString
    MAX-ACCESS  read-only
    STATUS      current
    DESCRIPTION "Number of Dns Server Resolver queries with RTT < 10ms"
    ::= { affirmedServicesDnsServerServiceStatisticsCluster-levelResolverEntry 26 }

affirmedServicesDnsServerServiceStatisticsCluster-levelResolverNumdnsserverresolvqueryrtt1 OBJECT-TYPE
    SYNTAX      ConfdString
    MAX-ACCESS  read-only
    STATUS      current
    DESCRIPTION "Number of Dns Server Resolver queries with RTT 10-99ms"
    ::= { affirmedServicesDnsServerServiceStatisticsCluster-levelResolverEntry 27 }

affirmedServicesDnsServerServiceStatisticsCluster-levelResolverNumdnsserverresolvqueryrtt2 OBJECT-TYPE
    SYNTAX      ConfdString
    MAX-ACCESS  read-only
    STATUS      current
    DESCRIPTION "Number of Dns Server Resolver queries with RTT 100-499ms"
    ::= { affirmedServicesDnsServerServiceStatisticsCluster-levelResolverEntry 28 }

affirmedServicesDnsServerServiceStatisticsCluster-levelResolverNumdnsserverresolvqueryrtt3 OBJECT-TYPE
    SYNTAX      ConfdString
    MAX-ACCESS  read-only
    STATUS      current
    DESCRIPTION "Number of Dns Server Resolver queries with RTT 500-799ms"
    ::= { affirmedServicesDnsServerServiceStatisticsCluster-levelResolverEntry 29 }

affirmedServicesDnsServerServiceStatisticsCluster-levelResolverNumdnsserverresolvqueryrtt4 OBJECT-TYPE
    SYNTAX      ConfdString
    MAX-ACCESS  read-only
    STATUS      current
    DESCRIPTION "Number of Dns Server Resolver queries with RTT 800-1599ms"
    ::= { affirmedServicesDnsServerServiceStatisticsCluster-levelResolverEntry 30 }

affirmedServicesDnsServerServiceStatisticsCluster-levelResolverNumdnsserverresolvqueryrtt5 OBJECT-TYPE
    SYNTAX      ConfdString
    MAX-ACCESS  read-only
    STATUS      current
    DESCRIPTION "Number of Dns Server Resolver queries with RTT >= 1600ms"
    ::= { affirmedServicesDnsServerServiceStatisticsCluster-levelResolverEntry 31 }

affirmedServicesDnsServerServiceStatisticsCluster-levelResolverNumdnsserverresolvnfetch OBJECT-TYPE
    SYNTAX      ConfdString
    MAX-ACCESS  read-only
    STATUS      current
    DESCRIPTION "Number of Dns Server Resolver Active Fetches"
    ::= { affirmedServicesDnsServerServiceStatisticsCluster-levelResolverEntry 32 }

affirmedServicesDnsServerServiceStatisticsCluster-levelResolverNumdnsserverresolvdisprequdp OBJECT-TYPE
    SYNTAX      ConfdString
    MAX-ACCESS  read-only
    STATUS      current
    DESCRIPTION "Number of Dns Server Resolver UDP queries in progress"
    ::= { affirmedServicesDnsServerServiceStatisticsCluster-levelResolverEntry 33 }

affirmedServicesDnsServerServiceStatisticsCluster-levelResolverNumdnsserverresolvdispreqtcp OBJECT-TYPE
    SYNTAX      ConfdString
    MAX-ACCESS  read-only
    STATUS      current
    DESCRIPTION "Number of Dns Server Resolver TCP queries in progress"
    ::= { affirmedServicesDnsServerServiceStatisticsCluster-levelResolverEntry 34 }

affirmedServicesDnsServerServiceStatisticsCluster-levelResolverNumdnsserverresolvbuckets OBJECT-TYPE
    SYNTAX      ConfdString
    MAX-ACCESS  read-only
    STATUS      current
    DESCRIPTION "Number of Dns Server Resolver Bucket size"
    ::= { affirmedServicesDnsServerServiceStatisticsCluster-levelResolverEntry 35 }

affirmedServicesDnsServerServiceStatisticsCluster-levelResolverNumdnsserverresolvrefused OBJECT-TYPE
    SYNTAX      ConfdString
    MAX-ACCESS  read-only
    STATUS      current
    DESCRIPTION "Number of Dns Server Resolver REFUSED received"
    ::= { affirmedServicesDnsServerServiceStatisticsCluster-levelResolverEntry 36 }

affirmedServicesDnsServerServiceStatisticsCluster-levelResolverNumdnsserverresolvcookienew OBJECT-TYPE
    SYNTAX      ConfdString
    MAX-ACCESS  read-only
    STATUS      current
    DESCRIPTION "Number of Dns Server Resolver COOKIE send with client cookie only"
    ::= { affirmedServicesDnsServerServiceStatisticsCluster-levelResolverEntry 37 }

affirmedServicesDnsServerServiceStatisticsCluster-levelResolverNumdnsserverresolvcookieout OBJECT-TYPE
    SYNTAX      ConfdString
    MAX-ACCESS  read-only
    STATUS      current
    DESCRIPTION "Number of Dns Server Resolver COOKIE sent with client and server cookie"
    ::= { affirmedServicesDnsServerServiceStatisticsCluster-levelResolverEntry 38 }

affirmedServicesDnsServerServiceStatisticsCluster-levelResolverNumdnsserverresolvcookiein OBJECT-TYPE
    SYNTAX      ConfdString
    MAX-ACCESS  read-only
    STATUS      current
    DESCRIPTION "Number of Dns Server Resolver COOKIE replies received"
    ::= { affirmedServicesDnsServerServiceStatisticsCluster-levelResolverEntry 39 }

affirmedServicesDnsServerServiceStatisticsCluster-levelResolverNumdnsserverresolvcookieok OBJECT-TYPE
    SYNTAX      ConfdString
    MAX-ACCESS  read-only
    STATUS      current
    DESCRIPTION "Number of Dns Server Resolver COOKIE client ok"
    ::= { affirmedServicesDnsServerServiceStatisticsCluster-levelResolverEntry 40 }

affirmedServicesDnsServerServiceStatisticsCluster-levelResolverNumdnsserverresolvbadvers OBJECT-TYPE
    SYNTAX      ConfdString
    MAX-ACCESS  read-only
    STATUS      current
    DESCRIPTION "Number of Dns Server Resolver Bad EDNS version"
    ::= { affirmedServicesDnsServerServiceStatisticsCluster-levelResolverEntry 41 }

affirmedServicesDnsServerServiceStatisticsCluster-levelResolverNumdnsserverresolvbadcookie OBJECT-TYPE
    SYNTAX      ConfdString
    MAX-ACCESS  read-only
    STATUS      current
    DESCRIPTION "Number of Dns Server Resolver Bad cookie Rcode"
    ::= { affirmedServicesDnsServerServiceStatisticsCluster-levelResolverEntry 42 }

affirmedServicesDnsServerServiceStatisticsCluster-levelResolverNumdnsserverresolvzonequota OBJECT-TYPE
    SYNTAX      ConfdString
    MAX-ACCESS  read-only
    STATUS      current
    DESCRIPTION "Number of Dns Server Resolver Spilled due to zone quota"
    ::= { affirmedServicesDnsServerServiceStatisticsCluster-levelResolverEntry 43 }

affirmedServicesDnsServerServiceStatisticsCluster-levelResolverNumdnsserverresolvserverquota OBJECT-TYPE
    SYNTAX      ConfdString
    MAX-ACCESS  read-only
    STATUS      current
    DESCRIPTION "Number of Dns Server Resolver Spilled due to server quota"
    ::= { affirmedServicesDnsServerServiceStatisticsCluster-levelResolverEntry 44 }

affirmedServicesDnsServerServiceStatisticsCluster-levelResolverNumdnsserverresolvnextitem OBJECT-TYPE
    SYNTAX      ConfdString
    MAX-ACCESS  read-only
    STATUS      current
    DESCRIPTION "Number of Dns Server Resolver Waited for next item"
    ::= { affirmedServicesDnsServerServiceStatisticsCluster-levelResolverEntry 45 }

affirmedServicesDnsServerServiceStatisticsNode-levelSummaryTable OBJECT-TYPE
    SYNTAX      SEQUENCE OF AffirmedServicesDnsServerServiceStatisticsNode-levelSummaryEntry
    MAX-ACCESS  not-accessible
    STATUS      current
    DESCRIPTION ""
    ::= { affirmedServicesDnsServerServiceStatisticsNode-level 1 }

affirmedServicesDnsServerServiceStatisticsNode-levelSummaryEntry OBJECT-TYPE
    SYNTAX      AffirmedServicesDnsServerServiceStatisticsNode-levelSummaryEntry
    MAX-ACCESS  not-accessible
    STATUS      current
    DESCRIPTION ""
    INDEX { affirmedServicesDnsServerServiceStatisticsNode-levelSummaryChassis, affirmedServicesDnsServerServiceStatisticsNode-levelSummarySlot }
        ::= { affirmedServicesDnsServerServiceStatisticsNode-levelSummaryTable 1 }

AffirmedServicesDnsServerServiceStatisticsNode-levelSummaryEntry ::=
    SEQUENCE {
        affirmedServicesDnsServerServiceStatisticsNode-levelSummaryChassis Unsigned32,
        affirmedServicesDnsServerServiceStatisticsNode-levelSummarySlot INTEGER,
        affirmedServicesDnsServerServiceStatisticsNode-levelSummaryNumdnsserversummaryattempts ConfdString,
        affirmedServicesDnsServerServiceStatisticsNode-levelSummaryNumdnsserversummarysuccesses ConfdString,
        affirmedServicesDnsServerServiceStatisticsNode-levelSummaryNumdnsserversummaryfailures ConfdString,
        affirmedServicesDnsServerServiceStatisticsNode-levelSummaryNumdnsserversummarydupqueries ConfdString,
        affirmedServicesDnsServerServiceStatisticsNode-levelSummaryNumdnsserversummaryblockedqueries ConfdString,
        affirmedServicesDnsServerServiceStatisticsNode-levelSummaryNumdnsserversummaryrecursiveclients ConfdString,
        affirmedServicesDnsServerServiceStatisticsNode-levelSummaryNumdnsserversummaryipv4requests ConfdString,
        affirmedServicesDnsServerServiceStatisticsNode-levelSummaryNumdnsserversummaryipv6requests ConfdString,
        affirmedServicesDnsServerServiceStatisticsNode-levelSummaryNumdnsserversummarytcprequests ConfdString,
        affirmedServicesDnsServerServiceStatisticsNode-levelSummaryNumdnsserversummaryudprequests ConfdString
    }

affirmedServicesDnsServerServiceStatisticsNode-levelSummaryChassis OBJECT-TYPE
    SYNTAX      Unsigned32
    MAX-ACCESS  not-accessible
    STATUS      current
    DESCRIPTION "chassis ID"
    ::= { affirmedServicesDnsServerServiceStatisticsNode-levelSummaryEntry 1 }

affirmedServicesDnsServerServiceStatisticsNode-levelSummarySlot OBJECT-TYPE
    SYNTAX      INTEGER {a1(1),a2(2),a3(3),a4(4),a5(5),a6(6),a7(7),a8(8),a9(9),a10(10),a11(11),a12(12),a13(13),a14(14),a15(15),a16(16),a17(17),a18(18),a19(19),a20(20),a21(21),a22(22),a23(23),a24(24),a25(25),a26(26),a27(27),a28(28),a29(29),a30(30),a31(31),a32(32),a33(33),a34(34),a35(35),a36(36),a37(37),a38(38),a39(39),a40(40),a41(41),a42(42),a43(43),a44(44),a45(45),a46(46),a47(47),a48(48),a49(49),a50(50),a51(51),a52(52),a53(53),a54(54),a55(55),a56(56),a57(57),a58(58),a59(59),a60(60),a61(61),a62(62),a63(63),a64(64),a65(65),a66(66),a67(67),a68(68),a69(69),a70(70),a71(71),a72(72),a73(73),a74(74),a75(75),a76(76),a77(77),a78(78),a79(79),a80(80),a81(81),a82(82),a83(83),a84(84),a85(85),a86(86),a87(87),a88(88),a89(89),a90(90),a91(91),a92(92),a93(93),a94(94),a95(95),a96(96),a97(97),a98(98),a99(99),a100(100),a101(101),a102(102),a103(103),a104(104),a105(105),a106(106),a107(107),a108(108),a109(109),a110(110),a111(111),a112(112),a113(113),a114(114),a115(115),a116(116),a117(117),a118(118),a119(119),a120(120),a121(121),a122(122),a123(123),a124(124),a125(125),a126(126),a127(127),a128(128)}
    MAX-ACCESS  not-accessible
    STATUS      current
    DESCRIPTION "slot number"
    ::= { affirmedServicesDnsServerServiceStatisticsNode-levelSummaryEntry 2 }

affirmedServicesDnsServerServiceStatisticsNode-levelSummaryNumdnsserversummaryattempts OBJECT-TYPE
    SYNTAX      ConfdString
    MAX-ACCESS  read-only
    STATUS      current
    DESCRIPTION "Number of Dns Server query attempts"
    ::= { affirmedServicesDnsServerServiceStatisticsNode-levelSummaryEntry 3 }

affirmedServicesDnsServerServiceStatisticsNode-levelSummaryNumdnsserversummarysuccesses OBJECT-TYPE
    SYNTAX      ConfdString
    MAX-ACCESS  read-only
    STATUS      current
    DESCRIPTION "Number of Dns Server queries with successful responses"
    ::= { affirmedServicesDnsServerServiceStatisticsNode-levelSummaryEntry 4 }

affirmedServicesDnsServerServiceStatisticsNode-levelSummaryNumdnsserversummaryfailures OBJECT-TYPE
    SYNTAX      ConfdString
    MAX-ACCESS  read-only
    STATUS      current
    DESCRIPTION "Number of Dns Server queries with failures"
    ::= { affirmedServicesDnsServerServiceStatisticsNode-levelSummaryEntry 5 }

affirmedServicesDnsServerServiceStatisticsNode-levelSummaryNumdnsserversummarydupqueries OBJECT-TYPE
    SYNTAX      ConfdString
    MAX-ACCESS  read-only
    STATUS      current
    DESCRIPTION "Number of Dns Server Duplicate Queries Received"
    ::= { affirmedServicesDnsServerServiceStatisticsNode-levelSummaryEntry 6 }

affirmedServicesDnsServerServiceStatisticsNode-levelSummaryNumdnsserversummaryblockedqueries OBJECT-TYPE
    SYNTAX      ConfdString
    MAX-ACCESS  read-only
    STATUS      current
    DESCRIPTION "Number of Dns Server Queries Blocked"
    ::= { affirmedServicesDnsServerServiceStatisticsNode-levelSummaryEntry 7 }

affirmedServicesDnsServerServiceStatisticsNode-levelSummaryNumdnsserversummaryrecursiveclients OBJECT-TYPE
    SYNTAX      ConfdString
    MAX-ACCESS  read-only
    STATUS      current
    DESCRIPTION "Number of Dns Server current Recursive Clients"
    ::= { affirmedServicesDnsServerServiceStatisticsNode-levelSummaryEntry 8 }

affirmedServicesDnsServerServiceStatisticsNode-levelSummaryNumdnsserversummaryipv4requests OBJECT-TYPE
    SYNTAX      ConfdString
    MAX-ACCESS  read-only
    STATUS      current
    DESCRIPTION "Number of Dns Server ipv4 requests"
    ::= { affirmedServicesDnsServerServiceStatisticsNode-levelSummaryEntry 9 }

affirmedServicesDnsServerServiceStatisticsNode-levelSummaryNumdnsserversummaryipv6requests OBJECT-TYPE
    SYNTAX      ConfdString
    MAX-ACCESS  read-only
    STATUS      current
    DESCRIPTION "Number of Dns Server ipv6 requests"
    ::= { affirmedServicesDnsServerServiceStatisticsNode-levelSummaryEntry 10 }

affirmedServicesDnsServerServiceStatisticsNode-levelSummaryNumdnsserversummarytcprequests OBJECT-TYPE
    SYNTAX      ConfdString
    MAX-ACCESS  read-only
    STATUS      current
    DESCRIPTION "Number of Dns Server TCP requests"
    ::= { affirmedServicesDnsServerServiceStatisticsNode-levelSummaryEntry 11 }

affirmedServicesDnsServerServiceStatisticsNode-levelSummaryNumdnsserversummaryudprequests OBJECT-TYPE
    SYNTAX      ConfdString
    MAX-ACCESS  read-only
    STATUS      current
    DESCRIPTION "Number of Dns Server UDP requests"
    ::= { affirmedServicesDnsServerServiceStatisticsNode-levelSummaryEntry 12 }

affirmedServicesDnsServerServiceStatisticsNode-levelDetailTable OBJECT-TYPE
    SYNTAX      SEQUENCE OF AffirmedServicesDnsServerServiceStatisticsNode-levelDetailEntry
    MAX-ACCESS  not-accessible
    STATUS      current
    DESCRIPTION ""
    ::= { affirmedServicesDnsServerServiceStatisticsNode-level 2 }

affirmedServicesDnsServerServiceStatisticsNode-levelDetailEntry OBJECT-TYPE
    SYNTAX      AffirmedServicesDnsServerServiceStatisticsNode-levelDetailEntry
    MAX-ACCESS  not-accessible
    STATUS      current
    DESCRIPTION ""
    INDEX { affirmedServicesDnsServerServiceStatisticsNode-levelDetailChassis, affirmedServicesDnsServerServiceStatisticsNode-levelDetailSlot }
        ::= { affirmedServicesDnsServerServiceStatisticsNode-levelDetailTable 1 }

AffirmedServicesDnsServerServiceStatisticsNode-levelDetailEntry ::=
    SEQUENCE {
        affirmedServicesDnsServerServiceStatisticsNode-levelDetailChassis Unsigned32,
        affirmedServicesDnsServerServiceStatisticsNode-levelDetailSlot INTEGER,
        affirmedServicesDnsServerServiceStatisticsNode-levelDetailNumdnsserverdetailipv4requests ConfdString,
        affirmedServicesDnsServerServiceStatisticsNode-levelDetailNumdnsserverdetailipv6requests ConfdString,
        affirmedServicesDnsServerServiceStatisticsNode-levelDetailNumdnsserverdetailednsrequests ConfdString,
        affirmedServicesDnsServerServiceStatisticsNode-levelDetailNumdnsserverdetailtcprequests ConfdString,
        affirmedServicesDnsServerServiceStatisticsNode-levelDetailNumdnsserverdetailresponses ConfdString,
        affirmedServicesDnsServerServiceStatisticsNode-levelDetailNumdnsserverdetailednsresponses ConfdString,
        affirmedServicesDnsServerServiceStatisticsNode-levelDetailNumdnsserverdetailquerysuccessresponses ConfdString,
        affirmedServicesDnsServerServiceStatisticsNode-levelDetailNumdnsserverdetailauthoritativeresponses ConfdString,
        affirmedServicesDnsServerServiceStatisticsNode-levelDetailNumdnsserverdetailnonauthoritativeresponses ConfdString,
        affirmedServicesDnsServerServiceStatisticsNode-levelDetailNumdnsserverdetailnoerrornodataresponses ConfdString,
        affirmedServicesDnsServerServiceStatisticsNode-levelDetailNumdnsserverdetailservfailresponses ConfdString,
        affirmedServicesDnsServerServiceStatisticsNode-levelDetailNumdnsserverdetailformerrresponses ConfdString,
        affirmedServicesDnsServerServiceStatisticsNode-levelDetailNumdnsserverdetailnxdomainresponses ConfdString,
        affirmedServicesDnsServerServiceStatisticsNode-levelDetailNumdnsserverdetailrecursion ConfdString,
        affirmedServicesDnsServerServiceStatisticsNode-levelDetailNumdnsserverdetailrecursiveclients ConfdString,
        affirmedServicesDnsServerServiceStatisticsNode-levelDetailNumdnsserverdetaildupqueries ConfdString,
        affirmedServicesDnsServerServiceStatisticsNode-levelDetailNumdnsserverdetailudpqueries ConfdString,
        affirmedServicesDnsServerServiceStatisticsNode-levelDetailNumdnsserverdetailtcpqueries ConfdString
    }

affirmedServicesDnsServerServiceStatisticsNode-levelDetailChassis OBJECT-TYPE
    SYNTAX      Unsigned32
    MAX-ACCESS  not-accessible
    STATUS      current
    DESCRIPTION "chassis ID"
    ::= { affirmedServicesDnsServerServiceStatisticsNode-levelDetailEntry 1 }

affirmedServicesDnsServerServiceStatisticsNode-levelDetailSlot OBJECT-TYPE
    SYNTAX      INTEGER {a1(1),a2(2),a3(3),a4(4),a5(5),a6(6),a7(7),a8(8),a9(9),a10(10),a11(11),a12(12),a13(13),a14(14),a15(15),a16(16),a17(17),a18(18),a19(19),a20(20),a21(21),a22(22),a23(23),a24(24),a25(25),a26(26),a27(27),a28(28),a29(29),a30(30),a31(31),a32(32),a33(33),a34(34),a35(35),a36(36),a37(37),a38(38),a39(39),a40(40),a41(41),a42(42),a43(43),a44(44),a45(45),a46(46),a47(47),a48(48),a49(49),a50(50),a51(51),a52(52),a53(53),a54(54),a55(55),a56(56),a57(57),a58(58),a59(59),a60(60),a61(61),a62(62),a63(63),a64(64),a65(65),a66(66),a67(67),a68(68),a69(69),a70(70),a71(71),a72(72),a73(73),a74(74),a75(75),a76(76),a77(77),a78(78),a79(79),a80(80),a81(81),a82(82),a83(83),a84(84),a85(85),a86(86),a87(87),a88(88),a89(89),a90(90),a91(91),a92(92),a93(93),a94(94),a95(95),a96(96),a97(97),a98(98),a99(99),a100(100),a101(101),a102(102),a103(103),a104(104),a105(105),a106(106),a107(107),a108(108),a109(109),a110(110),a111(111),a112(112),a113(113),a114(114),a115(115),a116(116),a117(117),a118(118),a119(119),a120(120),a121(121),a122(122),a123(123),a124(124),a125(125),a126(126),a127(127),a128(128)}
    MAX-ACCESS  not-accessible
    STATUS      current
    DESCRIPTION "slot number"
    ::= { affirmedServicesDnsServerServiceStatisticsNode-levelDetailEntry 2 }

affirmedServicesDnsServerServiceStatisticsNode-levelDetailNumdnsserverdetailipv4requests OBJECT-TYPE
    SYNTAX      ConfdString
    MAX-ACCESS  read-only
    STATUS      current
    DESCRIPTION "Number of Dns Server IPv4 requests"
    ::= { affirmedServicesDnsServerServiceStatisticsNode-levelDetailEntry 3 }

affirmedServicesDnsServerServiceStatisticsNode-levelDetailNumdnsserverdetailipv6requests OBJECT-TYPE
    SYNTAX      ConfdString
    MAX-ACCESS  read-only
    STATUS      current
    DESCRIPTION "Number of Dns Server IPv6 requests"
    ::= { affirmedServicesDnsServerServiceStatisticsNode-levelDetailEntry 4 }

affirmedServicesDnsServerServiceStatisticsNode-levelDetailNumdnsserverdetailednsrequests OBJECT-TYPE
    SYNTAX      ConfdString
    MAX-ACCESS  read-only
    STATUS      current
    DESCRIPTION "Number of Dns Server EDNS reuqests"
    ::= { affirmedServicesDnsServerServiceStatisticsNode-levelDetailEntry 5 }

affirmedServicesDnsServerServiceStatisticsNode-levelDetailNumdnsserverdetailtcprequests OBJECT-TYPE
    SYNTAX      ConfdString
    MAX-ACCESS  read-only
    STATUS      current
    DESCRIPTION "Number of Dns Server TCP requests"
    ::= { affirmedServicesDnsServerServiceStatisticsNode-levelDetailEntry 6 }

affirmedServicesDnsServerServiceStatisticsNode-levelDetailNumdnsserverdetailresponses OBJECT-TYPE
    SYNTAX      ConfdString
    MAX-ACCESS  read-only
    STATUS      current
    DESCRIPTION "Number of Dns Server responses"
    ::= { affirmedServicesDnsServerServiceStatisticsNode-levelDetailEntry 7 }

affirmedServicesDnsServerServiceStatisticsNode-levelDetailNumdnsserverdetailednsresponses OBJECT-TYPE
    SYNTAX      ConfdString
    MAX-ACCESS  read-only
    STATUS      current
    DESCRIPTION "Number of Dns Server EDNS responses"
    ::= { affirmedServicesDnsServerServiceStatisticsNode-levelDetailEntry 8 }

affirmedServicesDnsServerServiceStatisticsNode-levelDetailNumdnsserverdetailquerysuccessresponses OBJECT-TYPE
    SYNTAX      ConfdString
    MAX-ACCESS  read-only
    STATUS      current
    DESCRIPTION "Number of Dns Server query successful responses"
    ::= { affirmedServicesDnsServerServiceStatisticsNode-levelDetailEntry 9 }

affirmedServicesDnsServerServiceStatisticsNode-levelDetailNumdnsserverdetailauthoritativeresponses OBJECT-TYPE
    SYNTAX      ConfdString
    MAX-ACCESS  read-only
    STATUS      current
    DESCRIPTION "Number of Dns Server authoritative responses"
    ::= { affirmedServicesDnsServerServiceStatisticsNode-levelDetailEntry 10 }

affirmedServicesDnsServerServiceStatisticsNode-levelDetailNumdnsserverdetailnonauthoritativeresponses OBJECT-TYPE
    SYNTAX      ConfdString
    MAX-ACCESS  read-only
    STATUS      current
    DESCRIPTION "Number of Dns Server non authoritative responses"
    ::= { affirmedServicesDnsServerServiceStatisticsNode-levelDetailEntry 11 }

affirmedServicesDnsServerServiceStatisticsNode-levelDetailNumdnsserverdetailnoerrornodataresponses OBJECT-TYPE
    SYNTAX      ConfdString
    MAX-ACCESS  read-only
    STATUS      current
    DESCRIPTION "Number of Dns Server NOERROR responses with no data"
    ::= { affirmedServicesDnsServerServiceStatisticsNode-levelDetailEntry 12 }

affirmedServicesDnsServerServiceStatisticsNode-levelDetailNumdnsserverdetailservfailresponses OBJECT-TYPE
    SYNTAX      ConfdString
    MAX-ACCESS  read-only
    STATUS      current
    DESCRIPTION "Number of Dns Server SERVFAIL responses"
    ::= { affirmedServicesDnsServerServiceStatisticsNode-levelDetailEntry 13 }

affirmedServicesDnsServerServiceStatisticsNode-levelDetailNumdnsserverdetailformerrresponses OBJECT-TYPE
    SYNTAX      ConfdString
    MAX-ACCESS  read-only
    STATUS      current
    DESCRIPTION "Number of Dns Server FORMERR responses"
    ::= { affirmedServicesDnsServerServiceStatisticsNode-levelDetailEntry 14 }

affirmedServicesDnsServerServiceStatisticsNode-levelDetailNumdnsserverdetailnxdomainresponses OBJECT-TYPE
    SYNTAX      ConfdString
    MAX-ACCESS  read-only
    STATUS      current
    DESCRIPTION "Number of Dns Server NXDOMAIN responses"
    ::= { affirmedServicesDnsServerServiceStatisticsNode-levelDetailEntry 15 }

affirmedServicesDnsServerServiceStatisticsNode-levelDetailNumdnsserverdetailrecursion OBJECT-TYPE
    SYNTAX      ConfdString
    MAX-ACCESS  read-only
    STATUS      current
    DESCRIPTION "Number of Dns Server Queries that caused Recursion"
    ::= { affirmedServicesDnsServerServiceStatisticsNode-levelDetailEntry 16 }

affirmedServicesDnsServerServiceStatisticsNode-levelDetailNumdnsserverdetailrecursiveclients OBJECT-TYPE
    SYNTAX      ConfdString
    MAX-ACCESS  read-only
    STATUS      current
    DESCRIPTION "Number of Dns Server current Recursive Clients"
    ::= { affirmedServicesDnsServerServiceStatisticsNode-levelDetailEntry 17 }

affirmedServicesDnsServerServiceStatisticsNode-levelDetailNumdnsserverdetaildupqueries OBJECT-TYPE
    SYNTAX      ConfdString
    MAX-ACCESS  read-only
    STATUS      current
    DESCRIPTION "Number of Dns Server Duplicate Queries Received"
    ::= { affirmedServicesDnsServerServiceStatisticsNode-levelDetailEntry 18 }

affirmedServicesDnsServerServiceStatisticsNode-levelDetailNumdnsserverdetailudpqueries OBJECT-TYPE
    SYNTAX      ConfdString
    MAX-ACCESS  read-only
    STATUS      current
    DESCRIPTION "Number of Dns Server UDP Queries"
    ::= { affirmedServicesDnsServerServiceStatisticsNode-levelDetailEntry 19 }

affirmedServicesDnsServerServiceStatisticsNode-levelDetailNumdnsserverdetailtcpqueries OBJECT-TYPE
    SYNTAX      ConfdString
    MAX-ACCESS  read-only
    STATUS      current
    DESCRIPTION "Number of Dns Server TCP Queries"
    ::= { affirmedServicesDnsServerServiceStatisticsNode-levelDetailEntry 20 }

affirmedServicesDnsServerServiceStatisticsNode-levelQuerytypeTable OBJECT-TYPE
    SYNTAX      SEQUENCE OF AffirmedServicesDnsServerServiceStatisticsNode-levelQuerytypeEntry
    MAX-ACCESS  not-accessible
    STATUS      current
    DESCRIPTION ""
    ::= { affirmedServicesDnsServerServiceStatisticsNode-level 3 }

affirmedServicesDnsServerServiceStatisticsNode-levelQuerytypeEntry OBJECT-TYPE
    SYNTAX      AffirmedServicesDnsServerServiceStatisticsNode-levelQuerytypeEntry
    MAX-ACCESS  not-accessible
    STATUS      current
    DESCRIPTION ""
    INDEX { affirmedServicesDnsServerServiceStatisticsNode-levelQuerytypeChassis, affirmedServicesDnsServerServiceStatisticsNode-levelQuerytypeSlot }
        ::= { affirmedServicesDnsServerServiceStatisticsNode-levelQuerytypeTable 1 }

AffirmedServicesDnsServerServiceStatisticsNode-levelQuerytypeEntry ::=
    SEQUENCE {
        affirmedServicesDnsServerServiceStatisticsNode-levelQuerytypeChassis Unsigned32,
        affirmedServicesDnsServerServiceStatisticsNode-levelQuerytypeSlot INTEGER,
        affirmedServicesDnsServerServiceStatisticsNode-levelQuerytypeNumdnsserverquerytypea ConfdString,
        affirmedServicesDnsServerServiceStatisticsNode-levelQuerytypeNumdnsserverquerytypeaaaa ConfdString,
        affirmedServicesDnsServerServiceStatisticsNode-levelQuerytypeNumdnsserverquerytypecname ConfdString,
        affirmedServicesDnsServerServiceStatisticsNode-levelQuerytypeNumdnsserverquerytypednskey ConfdString,
        affirmedServicesDnsServerServiceStatisticsNode-levelQuerytypeNumdnsserverquerytypemx ConfdString,
        affirmedServicesDnsServerServiceStatisticsNode-levelQuerytypeNumdnsserverquerytypens ConfdString,
        affirmedServicesDnsServerServiceStatisticsNode-levelQuerytypeNumdnsserverquerytypeptr ConfdString,
        affirmedServicesDnsServerServiceStatisticsNode-levelQuerytypeNumdnsserverquerytyperrsig ConfdString,
        affirmedServicesDnsServerServiceStatisticsNode-levelQuerytypeNumdnsserverquerytypetsig ConfdString,
        affirmedServicesDnsServerServiceStatisticsNode-levelQuerytypeNumdnsserverquerytypeds ConfdString,
        affirmedServicesDnsServerServiceStatisticsNode-levelQuerytypeNumdnsserverquerytypehinfo ConfdString,
        affirmedServicesDnsServerServiceStatisticsNode-levelQuerytypeNumdnsserverquerytypesoa ConfdString,
        affirmedServicesDnsServerServiceStatisticsNode-levelQuerytypeNumdnsserverquerytypeaxfr ConfdString,
        affirmedServicesDnsServerServiceStatisticsNode-levelQuerytypeNumdnsserverquerytypeany ConfdString
    }

affirmedServicesDnsServerServiceStatisticsNode-levelQuerytypeChassis OBJECT-TYPE
    SYNTAX      Unsigned32
    MAX-ACCESS  not-accessible
    STATUS      current
    DESCRIPTION "chassis ID"
    ::= { affirmedServicesDnsServerServiceStatisticsNode-levelQuerytypeEntry 1 }

affirmedServicesDnsServerServiceStatisticsNode-levelQuerytypeSlot OBJECT-TYPE
    SYNTAX      INTEGER {a1(1),a2(2),a3(3),a4(4),a5(5),a6(6),a7(7),a8(8),a9(9),a10(10),a11(11),a12(12),a13(13),a14(14),a15(15),a16(16),a17(17),a18(18),a19(19),a20(20),a21(21),a22(22),a23(23),a24(24),a25(25),a26(26),a27(27),a28(28),a29(29),a30(30),a31(31),a32(32),a33(33),a34(34),a35(35),a36(36),a37(37),a38(38),a39(39),a40(40),a41(41),a42(42),a43(43),a44(44),a45(45),a46(46),a47(47),a48(48),a49(49),a50(50),a51(51),a52(52),a53(53),a54(54),a55(55),a56(56),a57(57),a58(58),a59(59),a60(60),a61(61),a62(62),a63(63),a64(64),a65(65),a66(66),a67(67),a68(68),a69(69),a70(70),a71(71),a72(72),a73(73),a74(74),a75(75),a76(76),a77(77),a78(78),a79(79),a80(80),a81(81),a82(82),a83(83),a84(84),a85(85),a86(86),a87(87),a88(88),a89(89),a90(90),a91(91),a92(92),a93(93),a94(94),a95(95),a96(96),a97(97),a98(98),a99(99),a100(100),a101(101),a102(102),a103(103),a104(104),a105(105),a106(106),a107(107),a108(108),a109(109),a110(110),a111(111),a112(112),a113(113),a114(114),a115(115),a116(116),a117(117),a118(118),a119(119),a120(120),a121(121),a122(122),a123(123),a124(124),a125(125),a126(126),a127(127),a128(128)}
    MAX-ACCESS  not-accessible
    STATUS      current
    DESCRIPTION "slot number"
    ::= { affirmedServicesDnsServerServiceStatisticsNode-levelQuerytypeEntry 2 }

affirmedServicesDnsServerServiceStatisticsNode-levelQuerytypeNumdnsserverquerytypea OBJECT-TYPE
    SYNTAX      ConfdString
    MAX-ACCESS  read-only
    STATUS      current
    DESCRIPTION "Number of Dns Server A record queries"
    ::= { affirmedServicesDnsServerServiceStatisticsNode-levelQuerytypeEntry 3 }

affirmedServicesDnsServerServiceStatisticsNode-levelQuerytypeNumdnsserverquerytypeaaaa OBJECT-TYPE
    SYNTAX      ConfdString
    MAX-ACCESS  read-only
    STATUS      current
    DESCRIPTION "Number of Dns Server AAAA record queries"
    ::= { affirmedServicesDnsServerServiceStatisticsNode-levelQuerytypeEntry 4 }

affirmedServicesDnsServerServiceStatisticsNode-levelQuerytypeNumdnsserverquerytypecname OBJECT-TYPE
    SYNTAX      ConfdString
    MAX-ACCESS  read-only
    STATUS      current
    DESCRIPTION "Number of Dns Server CNAME record queries"
    ::= { affirmedServicesDnsServerServiceStatisticsNode-levelQuerytypeEntry 5 }

affirmedServicesDnsServerServiceStatisticsNode-levelQuerytypeNumdnsserverquerytypednskey OBJECT-TYPE
    SYNTAX      ConfdString
    MAX-ACCESS  read-only
    STATUS      current
    DESCRIPTION "Number of Dns Server DNSKEY record queries"
    ::= { affirmedServicesDnsServerServiceStatisticsNode-levelQuerytypeEntry 6 }

affirmedServicesDnsServerServiceStatisticsNode-levelQuerytypeNumdnsserverquerytypemx OBJECT-TYPE
    SYNTAX      ConfdString
    MAX-ACCESS  read-only
    STATUS      current
    DESCRIPTION "Number of Dns Server MX record queries"
    ::= { affirmedServicesDnsServerServiceStatisticsNode-levelQuerytypeEntry 7 }

affirmedServicesDnsServerServiceStatisticsNode-levelQuerytypeNumdnsserverquerytypens OBJECT-TYPE
    SYNTAX      ConfdString
    MAX-ACCESS  read-only
    STATUS      current
    DESCRIPTION "Number of Dns Server NS record queries"
    ::= { affirmedServicesDnsServerServiceStatisticsNode-levelQuerytypeEntry 8 }

affirmedServicesDnsServerServiceStatisticsNode-levelQuerytypeNumdnsserverquerytypeptr OBJECT-TYPE
    SYNTAX      ConfdString
    MAX-ACCESS  read-only
    STATUS      current
    DESCRIPTION "Number of Dns Server PTR record queries"
    ::= { affirmedServicesDnsServerServiceStatisticsNode-levelQuerytypeEntry 9 }

affirmedServicesDnsServerServiceStatisticsNode-levelQuerytypeNumdnsserverquerytyperrsig OBJECT-TYPE
    SYNTAX      ConfdString
    MAX-ACCESS  read-only
    STATUS      current
    DESCRIPTION "Number of Dns Server RRSIG record queries"
    ::= { affirmedServicesDnsServerServiceStatisticsNode-levelQuerytypeEntry 10 }

affirmedServicesDnsServerServiceStatisticsNode-levelQuerytypeNumdnsserverquerytypetsig OBJECT-TYPE
    SYNTAX      ConfdString
    MAX-ACCESS  read-only
    STATUS      current
    DESCRIPTION "Number of Dns Server TSIG record queries"
    ::= { affirmedServicesDnsServerServiceStatisticsNode-levelQuerytypeEntry 11 }

affirmedServicesDnsServerServiceStatisticsNode-levelQuerytypeNumdnsserverquerytypeds OBJECT-TYPE
    SYNTAX      ConfdString
    MAX-ACCESS  read-only
    STATUS      current
    DESCRIPTION "Number of Dns Server DS record queries"
    ::= { affirmedServicesDnsServerServiceStatisticsNode-levelQuerytypeEntry 12 }

affirmedServicesDnsServerServiceStatisticsNode-levelQuerytypeNumdnsserverquerytypehinfo OBJECT-TYPE
    SYNTAX      ConfdString
    MAX-ACCESS  read-only
    STATUS      current
    DESCRIPTION "Number of Dns Server HINFO record queries"
    ::= { affirmedServicesDnsServerServiceStatisticsNode-levelQuerytypeEntry 13 }

affirmedServicesDnsServerServiceStatisticsNode-levelQuerytypeNumdnsserverquerytypesoa OBJECT-TYPE
    SYNTAX      ConfdString
    MAX-ACCESS  read-only
    STATUS      current
    DESCRIPTION "Number of Dns Server SOA record queries"
    ::= { affirmedServicesDnsServerServiceStatisticsNode-levelQuerytypeEntry 14 }

affirmedServicesDnsServerServiceStatisticsNode-levelQuerytypeNumdnsserverquerytypeaxfr OBJECT-TYPE
    SYNTAX      ConfdString
    MAX-ACCESS  read-only
    STATUS      current
    DESCRIPTION "Number of Dns Server AXFR record queries"
    ::= { affirmedServicesDnsServerServiceStatisticsNode-levelQuerytypeEntry 15 }

affirmedServicesDnsServerServiceStatisticsNode-levelQuerytypeNumdnsserverquerytypeany OBJECT-TYPE
    SYNTAX      ConfdString
    MAX-ACCESS  read-only
    STATUS      current
    DESCRIPTION "Number of Dns Server record queries of Other types"
    ::= { affirmedServicesDnsServerServiceStatisticsNode-levelQuerytypeEntry 16 }

affirmedServicesDnsServerServiceStatisticsNode-levelFailureTable OBJECT-TYPE
    SYNTAX      SEQUENCE OF AffirmedServicesDnsServerServiceStatisticsNode-levelFailureEntry
    MAX-ACCESS  not-accessible
    STATUS      current
    DESCRIPTION ""
    ::= { affirmedServicesDnsServerServiceStatisticsNode-level 4 }

affirmedServicesDnsServerServiceStatisticsNode-levelFailureEntry OBJECT-TYPE
    SYNTAX      AffirmedServicesDnsServerServiceStatisticsNode-levelFailureEntry
    MAX-ACCESS  not-accessible
    STATUS      current
    DESCRIPTION ""
    INDEX { affirmedServicesDnsServerServiceStatisticsNode-levelFailureChassis, affirmedServicesDnsServerServiceStatisticsNode-levelFailureSlot }
        ::= { affirmedServicesDnsServerServiceStatisticsNode-levelFailureTable 1 }

AffirmedServicesDnsServerServiceStatisticsNode-levelFailureEntry ::=
    SEQUENCE {
        affirmedServicesDnsServerServiceStatisticsNode-levelFailureChassis Unsigned32,
        affirmedServicesDnsServerServiceStatisticsNode-levelFailureSlot INTEGER,
        affirmedServicesDnsServerServiceStatisticsNode-levelFailureNumdnsserverfailureservfail ConfdString,
        affirmedServicesDnsServerServiceStatisticsNode-levelFailureNumdnsserverfailureformerr ConfdString,
        affirmedServicesDnsServerServiceStatisticsNode-levelFailureNumdnsserverfailurequeryother ConfdString,
        affirmedServicesDnsServerServiceStatisticsNode-levelFailureNumdnsserverfailuredynamicupdatefwd ConfdString,
        affirmedServicesDnsServerServiceStatisticsNode-levelFailureNumdnsserverfailuredynamicupdate ConfdString,
        affirmedServicesDnsServerServiceStatisticsNode-levelFailureNumdnsserverfailuredynamicupdateprereq ConfdString,
        affirmedServicesDnsServerServiceStatisticsNode-levelFailureNumdnsserverfailurezonexfr ConfdString,
        affirmedServicesDnsServerServiceStatisticsNode-levelFailureNumdnsserverfailureednsversion ConfdString,
        affirmedServicesDnsServerServiceStatisticsNode-levelFailureNumdnsserverfailureinvalidsig ConfdString,
        affirmedServicesDnsServerServiceStatisticsNode-levelFailureNumdnsserverfailureauthqueriesrej ConfdString,
        affirmedServicesDnsServerServiceStatisticsNode-levelFailureNumdnsserverfailurerecqueriesrej ConfdString,
        affirmedServicesDnsServerServiceStatisticsNode-levelFailureNumdnsserverfailurexfrrej ConfdString,
        affirmedServicesDnsServerServiceStatisticsNode-levelFailureNumdnsserverfailuredynamicupdaterej ConfdString,
        affirmedServicesDnsServerServiceStatisticsNode-levelFailureNumdnsserverfailurenotifyrej ConfdString
    }

affirmedServicesDnsServerServiceStatisticsNode-levelFailureChassis OBJECT-TYPE
    SYNTAX      Unsigned32
    MAX-ACCESS  not-accessible
    STATUS      current
    DESCRIPTION "chassis ID"
    ::= { affirmedServicesDnsServerServiceStatisticsNode-levelFailureEntry 1 }

affirmedServicesDnsServerServiceStatisticsNode-levelFailureSlot OBJECT-TYPE
    SYNTAX      INTEGER {a1(1),a2(2),a3(3),a4(4),a5(5),a6(6),a7(7),a8(8),a9(9),a10(10),a11(11),a12(12),a13(13),a14(14),a15(15),a16(16),a17(17),a18(18),a19(19),a20(20),a21(21),a22(22),a23(23),a24(24),a25(25),a26(26),a27(27),a28(28),a29(29),a30(30),a31(31),a32(32),a33(33),a34(34),a35(35),a36(36),a37(37),a38(38),a39(39),a40(40),a41(41),a42(42),a43(43),a44(44),a45(45),a46(46),a47(47),a48(48),a49(49),a50(50),a51(51),a52(52),a53(53),a54(54),a55(55),a56(56),a57(57),a58(58),a59(59),a60(60),a61(61),a62(62),a63(63),a64(64),a65(65),a66(66),a67(67),a68(68),a69(69),a70(70),a71(71),a72(72),a73(73),a74(74),a75(75),a76(76),a77(77),a78(78),a79(79),a80(80),a81(81),a82(82),a83(83),a84(84),a85(85),a86(86),a87(87),a88(88),a89(89),a90(90),a91(91),a92(92),a93(93),a94(94),a95(95),a96(96),a97(97),a98(98),a99(99),a100(100),a101(101),a102(102),a103(103),a104(104),a105(105),a106(106),a107(107),a108(108),a109(109),a110(110),a111(111),a112(112),a113(113),a114(114),a115(115),a116(116),a117(117),a118(118),a119(119),a120(120),a121(121),a122(122),a123(123),a124(124),a125(125),a126(126),a127(127),a128(128)}
    MAX-ACCESS  not-accessible
    STATUS      current
    DESCRIPTION "slot number"
    ::= { affirmedServicesDnsServerServiceStatisticsNode-levelFailureEntry 2 }

affirmedServicesDnsServerServiceStatisticsNode-levelFailureNumdnsserverfailureservfail OBJECT-TYPE
    SYNTAX      ConfdString
    MAX-ACCESS  read-only
    STATUS      current
    DESCRIPTION "Number of Dns Server SERVFAIL failures"
    ::= { affirmedServicesDnsServerServiceStatisticsNode-levelFailureEntry 3 }

affirmedServicesDnsServerServiceStatisticsNode-levelFailureNumdnsserverfailureformerr OBJECT-TYPE
    SYNTAX      ConfdString
    MAX-ACCESS  read-only
    STATUS      current
    DESCRIPTION "Number of Dns Server FORMERR failures"
    ::= { affirmedServicesDnsServerServiceStatisticsNode-levelFailureEntry 4 }

affirmedServicesDnsServerServiceStatisticsNode-levelFailureNumdnsserverfailurequeryother OBJECT-TYPE
    SYNTAX      ConfdString
    MAX-ACCESS  read-only
    STATUS      current
    DESCRIPTION "Number of Dns Server other query failures"
    ::= { affirmedServicesDnsServerServiceStatisticsNode-levelFailureEntry 5 }

affirmedServicesDnsServerServiceStatisticsNode-levelFailureNumdnsserverfailuredynamicupdatefwd OBJECT-TYPE
    SYNTAX      ConfdString
    MAX-ACCESS  read-only
    STATUS      current
    DESCRIPTION "Number of Dns Server Dynamic Update forward failures"
    ::= { affirmedServicesDnsServerServiceStatisticsNode-levelFailureEntry 6 }

affirmedServicesDnsServerServiceStatisticsNode-levelFailureNumdnsserverfailuredynamicupdate OBJECT-TYPE
    SYNTAX      ConfdString
    MAX-ACCESS  read-only
    STATUS      current
    DESCRIPTION "Number of Dns Server Dynamic Update failures"
    ::= { affirmedServicesDnsServerServiceStatisticsNode-levelFailureEntry 7 }

affirmedServicesDnsServerServiceStatisticsNode-levelFailureNumdnsserverfailuredynamicupdateprereq OBJECT-TYPE
    SYNTAX      ConfdString
    MAX-ACCESS  read-only
    STATUS      current
    DESCRIPTION "Number of Dns Server Dynamic Updates rejected due to prerequisite failures"
    ::= { affirmedServicesDnsServerServiceStatisticsNode-levelFailureEntry 8 }

affirmedServicesDnsServerServiceStatisticsNode-levelFailureNumdnsserverfailurezonexfr OBJECT-TYPE
    SYNTAX      ConfdString
    MAX-ACCESS  read-only
    STATUS      current
    DESCRIPTION "Number of Dns Server Zone transfer failures"
    ::= { affirmedServicesDnsServerServiceStatisticsNode-levelFailureEntry 9 }

affirmedServicesDnsServerServiceStatisticsNode-levelFailureNumdnsserverfailureednsversion OBJECT-TYPE
    SYNTAX      ConfdString
    MAX-ACCESS  read-only
    STATUS      current
    DESCRIPTION "Number of Dns Server Bad EDNS version failures"
    ::= { affirmedServicesDnsServerServiceStatisticsNode-levelFailureEntry 10 }

affirmedServicesDnsServerServiceStatisticsNode-levelFailureNumdnsserverfailureinvalidsig OBJECT-TYPE
    SYNTAX      ConfdString
    MAX-ACCESS  read-only
    STATUS      current
    DESCRIPTION "Number of Dns Server Invalid SIG or TSIG(0) failures"
    ::= { affirmedServicesDnsServerServiceStatisticsNode-levelFailureEntry 11 }

affirmedServicesDnsServerServiceStatisticsNode-levelFailureNumdnsserverfailureauthqueriesrej OBJECT-TYPE
    SYNTAX      ConfdString
    MAX-ACCESS  read-only
    STATUS      current
    DESCRIPTION "Number of Dns Server Authoritative Queries Rejected"
    ::= { affirmedServicesDnsServerServiceStatisticsNode-levelFailureEntry 12 }

affirmedServicesDnsServerServiceStatisticsNode-levelFailureNumdnsserverfailurerecqueriesrej OBJECT-TYPE
    SYNTAX      ConfdString
    MAX-ACCESS  read-only
    STATUS      current
    DESCRIPTION "Number of Dns Server Recursive Queries Rejected"
    ::= { affirmedServicesDnsServerServiceStatisticsNode-levelFailureEntry 13 }

affirmedServicesDnsServerServiceStatisticsNode-levelFailureNumdnsserverfailurexfrrej OBJECT-TYPE
    SYNTAX      ConfdString
    MAX-ACCESS  read-only
    STATUS      current
    DESCRIPTION "Number of Dns Server Zone Transfer Requests Rejected"
    ::= { affirmedServicesDnsServerServiceStatisticsNode-levelFailureEntry 14 }

affirmedServicesDnsServerServiceStatisticsNode-levelFailureNumdnsserverfailuredynamicupdaterej OBJECT-TYPE
    SYNTAX      ConfdString
    MAX-ACCESS  read-only
    STATUS      current
    DESCRIPTION "Number of Dns Server Dynamic Update Requests Rejected"
    ::= { affirmedServicesDnsServerServiceStatisticsNode-levelFailureEntry 15 }

affirmedServicesDnsServerServiceStatisticsNode-levelFailureNumdnsserverfailurenotifyrej OBJECT-TYPE
    SYNTAX      ConfdString
    MAX-ACCESS  read-only
    STATUS      current
    DESCRIPTION "Number of Dns Server Incoming Notifies Rejected"
    ::= { affirmedServicesDnsServerServiceStatisticsNode-levelFailureEntry 16 }

affirmedServicesDnsServerServiceStatisticsNode-levelCacheTable OBJECT-TYPE
    SYNTAX      SEQUENCE OF AffirmedServicesDnsServerServiceStatisticsNode-levelCacheEntry
    MAX-ACCESS  not-accessible
    STATUS      current
    DESCRIPTION ""
    ::= { affirmedServicesDnsServerServiceStatisticsNode-level 5 }

affirmedServicesDnsServerServiceStatisticsNode-levelCacheEntry OBJECT-TYPE
    SYNTAX      AffirmedServicesDnsServerServiceStatisticsNode-levelCacheEntry
    MAX-ACCESS  not-accessible
    STATUS      current
    DESCRIPTION ""
    INDEX { affirmedServicesDnsServerServiceStatisticsNode-levelCacheChassis, affirmedServicesDnsServerServiceStatisticsNode-levelCacheSlot }
        ::= { affirmedServicesDnsServerServiceStatisticsNode-levelCacheTable 1 }

AffirmedServicesDnsServerServiceStatisticsNode-levelCacheEntry ::=
    SEQUENCE {
        affirmedServicesDnsServerServiceStatisticsNode-levelCacheChassis Unsigned32,
        affirmedServicesDnsServerServiceStatisticsNode-levelCacheSlot INTEGER,
        affirmedServicesDnsServerServiceStatisticsNode-levelCacheNumdnsservercachehits ConfdString,
        affirmedServicesDnsServerServiceStatisticsNode-levelCacheNumdnsservercachemisses ConfdString,
        affirmedServicesDnsServerServiceStatisticsNode-levelCacheNumdnsservercachequeryhits ConfdString,
        affirmedServicesDnsServerServiceStatisticsNode-levelCacheNumdnsservercachequerymisses ConfdString,
        affirmedServicesDnsServerServiceStatisticsNode-levelCacheNumdnsservercachedeletelru ConfdString,
        affirmedServicesDnsServerServiceStatisticsNode-levelCacheNumdnsservercachedeletettl ConfdString,
        affirmedServicesDnsServerServiceStatisticsNode-levelCacheNumdnsservercachedbnodes ConfdString,
        affirmedServicesDnsServerServiceStatisticsNode-levelCacheNumdnsservercachedbhashbuckets ConfdString,
        affirmedServicesDnsServerServiceStatisticsNode-levelCacheNumdnsservercachetreememtotal ConfdString,
        affirmedServicesDnsServerServiceStatisticsNode-levelCacheNumdnsservercachetreememinuse ConfdString,
        affirmedServicesDnsServerServiceStatisticsNode-levelCacheNumdnsservercachetreememmax ConfdString,
        affirmedServicesDnsServerServiceStatisticsNode-levelCacheNumdnsservercacheheapmemtotal ConfdString,
        affirmedServicesDnsServerServiceStatisticsNode-levelCacheNumdnsservercacheheapmeminuse ConfdString,
        affirmedServicesDnsServerServiceStatisticsNode-levelCacheNumdnsservercacheheapmemmax ConfdString
    }

affirmedServicesDnsServerServiceStatisticsNode-levelCacheChassis OBJECT-TYPE
    SYNTAX      Unsigned32
    MAX-ACCESS  not-accessible
    STATUS      current
    DESCRIPTION "chassis ID"
    ::= { affirmedServicesDnsServerServiceStatisticsNode-levelCacheEntry 1 }

affirmedServicesDnsServerServiceStatisticsNode-levelCacheSlot OBJECT-TYPE
    SYNTAX      INTEGER {a1(1),a2(2),a3(3),a4(4),a5(5),a6(6),a7(7),a8(8),a9(9),a10(10),a11(11),a12(12),a13(13),a14(14),a15(15),a16(16),a17(17),a18(18),a19(19),a20(20),a21(21),a22(22),a23(23),a24(24),a25(25),a26(26),a27(27),a28(28),a29(29),a30(30),a31(31),a32(32),a33(33),a34(34),a35(35),a36(36),a37(37),a38(38),a39(39),a40(40),a41(41),a42(42),a43(43),a44(44),a45(45),a46(46),a47(47),a48(48),a49(49),a50(50),a51(51),a52(52),a53(53),a54(54),a55(55),a56(56),a57(57),a58(58),a59(59),a60(60),a61(61),a62(62),a63(63),a64(64),a65(65),a66(66),a67(67),a68(68),a69(69),a70(70),a71(71),a72(72),a73(73),a74(74),a75(75),a76(76),a77(77),a78(78),a79(79),a80(80),a81(81),a82(82),a83(83),a84(84),a85(85),a86(86),a87(87),a88(88),a89(89),a90(90),a91(91),a92(92),a93(93),a94(94),a95(95),a96(96),a97(97),a98(98),a99(99),a100(100),a101(101),a102(102),a103(103),a104(104),a105(105),a106(106),a107(107),a108(108),a109(109),a110(110),a111(111),a112(112),a113(113),a114(114),a115(115),a116(116),a117(117),a118(118),a119(119),a120(120),a121(121),a122(122),a123(123),a124(124),a125(125),a126(126),a127(127),a128(128)}
    MAX-ACCESS  not-accessible
    STATUS      current
    DESCRIPTION "slot number"
    ::= { affirmedServicesDnsServerServiceStatisticsNode-levelCacheEntry 2 }

affirmedServicesDnsServerServiceStatisticsNode-levelCacheNumdnsservercachehits OBJECT-TYPE
    SYNTAX      ConfdString
    MAX-ACCESS  read-only
    STATUS      current
    DESCRIPTION "Number of Dns Server Cache hits"
    ::= { affirmedServicesDnsServerServiceStatisticsNode-levelCacheEntry 3 }

affirmedServicesDnsServerServiceStatisticsNode-levelCacheNumdnsservercachemisses OBJECT-TYPE
    SYNTAX      ConfdString
    MAX-ACCESS  read-only
    STATUS      current
    DESCRIPTION "Number of Dns Server Cache misses"
    ::= { affirmedServicesDnsServerServiceStatisticsNode-levelCacheEntry 4 }

affirmedServicesDnsServerServiceStatisticsNode-levelCacheNumdnsservercachequeryhits OBJECT-TYPE
    SYNTAX      ConfdString
    MAX-ACCESS  read-only
    STATUS      current
    DESCRIPTION "Number of Dns Server Cache Query hits"
    ::= { affirmedServicesDnsServerServiceStatisticsNode-levelCacheEntry 5 }

affirmedServicesDnsServerServiceStatisticsNode-levelCacheNumdnsservercachequerymisses OBJECT-TYPE
    SYNTAX      ConfdString
    MAX-ACCESS  read-only
    STATUS      current
    DESCRIPTION "Number of Dns Server Cache Query misses"
    ::= { affirmedServicesDnsServerServiceStatisticsNode-levelCacheEntry 6 }

affirmedServicesDnsServerServiceStatisticsNode-levelCacheNumdnsservercachedeletelru OBJECT-TYPE
    SYNTAX      ConfdString
    MAX-ACCESS  read-only
    STATUS      current
    DESCRIPTION "Number of Dns Server Cache LRU deletions"
    ::= { affirmedServicesDnsServerServiceStatisticsNode-levelCacheEntry 7 }

affirmedServicesDnsServerServiceStatisticsNode-levelCacheNumdnsservercachedeletettl OBJECT-TYPE
    SYNTAX      ConfdString
    MAX-ACCESS  read-only
    STATUS      current
    DESCRIPTION "Number of Dns Server Cache TTL deletions"
    ::= { affirmedServicesDnsServerServiceStatisticsNode-levelCacheEntry 8 }

affirmedServicesDnsServerServiceStatisticsNode-levelCacheNumdnsservercachedbnodes OBJECT-TYPE
    SYNTAX      ConfdString
    MAX-ACCESS  read-only
    STATUS      current
    DESCRIPTION "Number of Dns Server Cache database nodes"
    ::= { affirmedServicesDnsServerServiceStatisticsNode-levelCacheEntry 9 }

affirmedServicesDnsServerServiceStatisticsNode-levelCacheNumdnsservercachedbhashbuckets OBJECT-TYPE
    SYNTAX      ConfdString
    MAX-ACCESS  read-only
    STATUS      current
    DESCRIPTION "Number of Dns Server Cache database hash buckets"
    ::= { affirmedServicesDnsServerServiceStatisticsNode-levelCacheEntry 10 }

affirmedServicesDnsServerServiceStatisticsNode-levelCacheNumdnsservercachetreememtotal OBJECT-TYPE
    SYNTAX      ConfdString
    MAX-ACCESS  read-only
    STATUS      current
    DESCRIPTION "Dns Server Cache tree memory total"
    ::= { affirmedServicesDnsServerServiceStatisticsNode-levelCacheEntry 11 }

affirmedServicesDnsServerServiceStatisticsNode-levelCacheNumdnsservercachetreememinuse OBJECT-TYPE
    SYNTAX      ConfdString
    MAX-ACCESS  read-only
    STATUS      current
    DESCRIPTION "Dns Server Cache tree memory in use"
    ::= { affirmedServicesDnsServerServiceStatisticsNode-levelCacheEntry 12 }

affirmedServicesDnsServerServiceStatisticsNode-levelCacheNumdnsservercachetreememmax OBJECT-TYPE
    SYNTAX      ConfdString
    MAX-ACCESS  read-only
    STATUS      current
    DESCRIPTION "Dns Server Cache tree memory max"
    ::= { affirmedServicesDnsServerServiceStatisticsNode-levelCacheEntry 13 }

affirmedServicesDnsServerServiceStatisticsNode-levelCacheNumdnsservercacheheapmemtotal OBJECT-TYPE
    SYNTAX      ConfdString
    MAX-ACCESS  read-only
    STATUS      current
    DESCRIPTION "Dns Server Cache heap memory total"
    ::= { affirmedServicesDnsServerServiceStatisticsNode-levelCacheEntry 14 }

affirmedServicesDnsServerServiceStatisticsNode-levelCacheNumdnsservercacheheapmeminuse OBJECT-TYPE
    SYNTAX      ConfdString
    MAX-ACCESS  read-only
    STATUS      current
    DESCRIPTION "Dns Server Cache heap memory in use"
    ::= { affirmedServicesDnsServerServiceStatisticsNode-levelCacheEntry 15 }

affirmedServicesDnsServerServiceStatisticsNode-levelCacheNumdnsservercacheheapmemmax OBJECT-TYPE
    SYNTAX      ConfdString
    MAX-ACCESS  read-only
    STATUS      current
    DESCRIPTION "Dns Server Cache heap memory max"
    ::= { affirmedServicesDnsServerServiceStatisticsNode-levelCacheEntry 16 }

affirmedServicesDnsServerServiceStatisticsNode-levelSocketTable OBJECT-TYPE
    SYNTAX      SEQUENCE OF AffirmedServicesDnsServerServiceStatisticsNode-levelSocketEntry
    MAX-ACCESS  not-accessible
    STATUS      current
    DESCRIPTION ""
    ::= { affirmedServicesDnsServerServiceStatisticsNode-level 6 }

affirmedServicesDnsServerServiceStatisticsNode-levelSocketEntry OBJECT-TYPE
    SYNTAX      AffirmedServicesDnsServerServiceStatisticsNode-levelSocketEntry
    MAX-ACCESS  not-accessible
    STATUS      current
    DESCRIPTION ""
    INDEX { affirmedServicesDnsServerServiceStatisticsNode-levelSocketChassis, affirmedServicesDnsServerServiceStatisticsNode-levelSocketSlot }
        ::= { affirmedServicesDnsServerServiceStatisticsNode-levelSocketTable 1 }

AffirmedServicesDnsServerServiceStatisticsNode-levelSocketEntry ::=
    SEQUENCE {
        affirmedServicesDnsServerServiceStatisticsNode-levelSocketChassis Unsigned32,
        affirmedServicesDnsServerServiceStatisticsNode-levelSocketSlot INTEGER,
        affirmedServicesDnsServerServiceStatisticsNode-levelSocketNumdnsserversockudpopen ConfdString,
        affirmedServicesDnsServerServiceStatisticsNode-levelSocketNumdnsserversockudpopenfail ConfdString,
        affirmedServicesDnsServerServiceStatisticsNode-levelSocketNumdnsserversockudpclose ConfdString,
        affirmedServicesDnsServerServiceStatisticsNode-levelSocketNumdnsserversockudpbindfail ConfdString,
        affirmedServicesDnsServerServiceStatisticsNode-levelSocketNumdnsserversockudpconnect ConfdString,
        affirmedServicesDnsServerServiceStatisticsNode-levelSocketNumdnsserversockudpconnectfail ConfdString,
        affirmedServicesDnsServerServiceStatisticsNode-levelSocketNumdnsserversockudpsendfail ConfdString,
        affirmedServicesDnsServerServiceStatisticsNode-levelSocketNumdnsserversockudprecvfail ConfdString,
        affirmedServicesDnsServerServiceStatisticsNode-levelSocketNumdnsserversocktcpopen ConfdString,
        affirmedServicesDnsServerServiceStatisticsNode-levelSocketNumdnsserversocktcpopenfail ConfdString,
        affirmedServicesDnsServerServiceStatisticsNode-levelSocketNumdnsserversocktcpclose ConfdString,
        affirmedServicesDnsServerServiceStatisticsNode-levelSocketNumdnsserversocktcpbindfail ConfdString,
        affirmedServicesDnsServerServiceStatisticsNode-levelSocketNumdnsserversocktcpconnect ConfdString,
        affirmedServicesDnsServerServiceStatisticsNode-levelSocketNumdnsserversocktcpconnectfail ConfdString,
        affirmedServicesDnsServerServiceStatisticsNode-levelSocketNumdnsserversocktcpaccept ConfdString,
        affirmedServicesDnsServerServiceStatisticsNode-levelSocketNumdnsserversocktcpacceptfail ConfdString,
        affirmedServicesDnsServerServiceStatisticsNode-levelSocketNumdnsserversocktcpsendfail ConfdString,
        affirmedServicesDnsServerServiceStatisticsNode-levelSocketNumdnsserversocktcprecvfail ConfdString
    }

affirmedServicesDnsServerServiceStatisticsNode-levelSocketChassis OBJECT-TYPE
    SYNTAX      Unsigned32
    MAX-ACCESS  not-accessible
    STATUS      current
    DESCRIPTION "chassis ID"
    ::= { affirmedServicesDnsServerServiceStatisticsNode-levelSocketEntry 1 }

affirmedServicesDnsServerServiceStatisticsNode-levelSocketSlot OBJECT-TYPE
    SYNTAX      INTEGER {a1(1),a2(2),a3(3),a4(4),a5(5),a6(6),a7(7),a8(8),a9(9),a10(10),a11(11),a12(12),a13(13),a14(14),a15(15),a16(16),a17(17),a18(18),a19(19),a20(20),a21(21),a22(22),a23(23),a24(24),a25(25),a26(26),a27(27),a28(28),a29(29),a30(30),a31(31),a32(32),a33(33),a34(34),a35(35),a36(36),a37(37),a38(38),a39(39),a40(40),a41(41),a42(42),a43(43),a44(44),a45(45),a46(46),a47(47),a48(48),a49(49),a50(50),a51(51),a52(52),a53(53),a54(54),a55(55),a56(56),a57(57),a58(58),a59(59),a60(60),a61(61),a62(62),a63(63),a64(64),a65(65),a66(66),a67(67),a68(68),a69(69),a70(70),a71(71),a72(72),a73(73),a74(74),a75(75),a76(76),a77(77),a78(78),a79(79),a80(80),a81(81),a82(82),a83(83),a84(84),a85(85),a86(86),a87(87),a88(88),a89(89),a90(90),a91(91),a92(92),a93(93),a94(94),a95(95),a96(96),a97(97),a98(98),a99(99),a100(100),a101(101),a102(102),a103(103),a104(104),a105(105),a106(106),a107(107),a108(108),a109(109),a110(110),a111(111),a112(112),a113(113),a114(114),a115(115),a116(116),a117(117),a118(118),a119(119),a120(120),a121(121),a122(122),a123(123),a124(124),a125(125),a126(126),a127(127),a128(128)}
    MAX-ACCESS  not-accessible
    STATUS      current
    DESCRIPTION "slot number"
    ::= { affirmedServicesDnsServerServiceStatisticsNode-levelSocketEntry 2 }

affirmedServicesDnsServerServiceStatisticsNode-levelSocketNumdnsserversockudpopen OBJECT-TYPE
    SYNTAX      ConfdString
    MAX-ACCESS  read-only
    STATUS      current
    DESCRIPTION "Number of Dns Server UDP sockets opened successfully"
    ::= { affirmedServicesDnsServerServiceStatisticsNode-levelSocketEntry 3 }

affirmedServicesDnsServerServiceStatisticsNode-levelSocketNumdnsserversockudpopenfail OBJECT-TYPE
    SYNTAX      ConfdString
    MAX-ACCESS  read-only
    STATUS      current
    DESCRIPTION "Number of Dns Server UDP sockets failed to open"
    ::= { affirmedServicesDnsServerServiceStatisticsNode-levelSocketEntry 4 }

affirmedServicesDnsServerServiceStatisticsNode-levelSocketNumdnsserversockudpclose OBJECT-TYPE
    SYNTAX      ConfdString
    MAX-ACCESS  read-only
    STATUS      current
    DESCRIPTION "Number of Dns Server UDP sockets closed"
    ::= { affirmedServicesDnsServerServiceStatisticsNode-levelSocketEntry 5 }

affirmedServicesDnsServerServiceStatisticsNode-levelSocketNumdnsserversockudpbindfail OBJECT-TYPE
    SYNTAX      ConfdString
    MAX-ACCESS  read-only
    STATUS      current
    DESCRIPTION "Number of Dns Server UDP sockets Bind failed"
    ::= { affirmedServicesDnsServerServiceStatisticsNode-levelSocketEntry 6 }

affirmedServicesDnsServerServiceStatisticsNode-levelSocketNumdnsserversockudpconnect OBJECT-TYPE
    SYNTAX      ConfdString
    MAX-ACCESS  read-only
    STATUS      current
    DESCRIPTION "Number of Dns Server UDP sockets connected successfully"
    ::= { affirmedServicesDnsServerServiceStatisticsNode-levelSocketEntry 7 }

affirmedServicesDnsServerServiceStatisticsNode-levelSocketNumdnsserversockudpconnectfail OBJECT-TYPE
    SYNTAX      ConfdString
    MAX-ACCESS  read-only
    STATUS      current
    DESCRIPTION "Number of Dns Server UDP sockets failed to connect"
    ::= { affirmedServicesDnsServerServiceStatisticsNode-levelSocketEntry 8 }

affirmedServicesDnsServerServiceStatisticsNode-levelSocketNumdnsserversockudpsendfail OBJECT-TYPE
    SYNTAX      ConfdString
    MAX-ACCESS  read-only
    STATUS      current
    DESCRIPTION "Number of Dns Server UDP sockets failed to send"
    ::= { affirmedServicesDnsServerServiceStatisticsNode-levelSocketEntry 9 }

affirmedServicesDnsServerServiceStatisticsNode-levelSocketNumdnsserversockudprecvfail OBJECT-TYPE
    SYNTAX      ConfdString
    MAX-ACCESS  read-only
    STATUS      current
    DESCRIPTION "Number of Dns Server UDP sockets failed to receive"
    ::= { affirmedServicesDnsServerServiceStatisticsNode-levelSocketEntry 10 }

affirmedServicesDnsServerServiceStatisticsNode-levelSocketNumdnsserversocktcpopen OBJECT-TYPE
    SYNTAX      ConfdString
    MAX-ACCESS  read-only
    STATUS      current
    DESCRIPTION "Number of Dns Server TCP sockets opened successfully"
    ::= { affirmedServicesDnsServerServiceStatisticsNode-levelSocketEntry 11 }

affirmedServicesDnsServerServiceStatisticsNode-levelSocketNumdnsserversocktcpopenfail OBJECT-TYPE
    SYNTAX      ConfdString
    MAX-ACCESS  read-only
    STATUS      current
    DESCRIPTION "Number of Dns Server TCP sockets failed to open"
    ::= { affirmedServicesDnsServerServiceStatisticsNode-levelSocketEntry 12 }

affirmedServicesDnsServerServiceStatisticsNode-levelSocketNumdnsserversocktcpclose OBJECT-TYPE
    SYNTAX      ConfdString
    MAX-ACCESS  read-only
    STATUS      current
    DESCRIPTION "Number of Dns Server TCP sockets closed"
    ::= { affirmedServicesDnsServerServiceStatisticsNode-levelSocketEntry 13 }

affirmedServicesDnsServerServiceStatisticsNode-levelSocketNumdnsserversocktcpbindfail OBJECT-TYPE
    SYNTAX      ConfdString
    MAX-ACCESS  read-only
    STATUS      current
    DESCRIPTION "Number of Dns Server TCP sockets Bind failed"
    ::= { affirmedServicesDnsServerServiceStatisticsNode-levelSocketEntry 14 }

affirmedServicesDnsServerServiceStatisticsNode-levelSocketNumdnsserversocktcpconnect OBJECT-TYPE
    SYNTAX      ConfdString
    MAX-ACCESS  read-only
    STATUS      current
    DESCRIPTION "Number of Dns Server TCP sockets connected successfully"
    ::= { affirmedServicesDnsServerServiceStatisticsNode-levelSocketEntry 15 }

affirmedServicesDnsServerServiceStatisticsNode-levelSocketNumdnsserversocktcpconnectfail OBJECT-TYPE
    SYNTAX      ConfdString
    MAX-ACCESS  read-only
    STATUS      current
    DESCRIPTION "Number of Dns Server TCP sockets failed to connect"
    ::= { affirmedServicesDnsServerServiceStatisticsNode-levelSocketEntry 16 }

affirmedServicesDnsServerServiceStatisticsNode-levelSocketNumdnsserversocktcpaccept OBJECT-TYPE
    SYNTAX      ConfdString
    MAX-ACCESS  read-only
    STATUS      current
    DESCRIPTION "Number of Dns Server TCP sockets accepted connections"
    ::= { affirmedServicesDnsServerServiceStatisticsNode-levelSocketEntry 17 }

affirmedServicesDnsServerServiceStatisticsNode-levelSocketNumdnsserversocktcpacceptfail OBJECT-TYPE
    SYNTAX      ConfdString
    MAX-ACCESS  read-only
    STATUS      current
    DESCRIPTION "Number of Dns Server TCP sockets connections failed to accept"
    ::= { affirmedServicesDnsServerServiceStatisticsNode-levelSocketEntry 18 }

affirmedServicesDnsServerServiceStatisticsNode-levelSocketNumdnsserversocktcpsendfail OBJECT-TYPE
    SYNTAX      ConfdString
    MAX-ACCESS  read-only
    STATUS      current
    DESCRIPTION "Number of Dns Server TCP sockets failed to send"
    ::= { affirmedServicesDnsServerServiceStatisticsNode-levelSocketEntry 19 }

affirmedServicesDnsServerServiceStatisticsNode-levelSocketNumdnsserversocktcprecvfail OBJECT-TYPE
    SYNTAX      ConfdString
    MAX-ACCESS  read-only
    STATUS      current
    DESCRIPTION "Number of Dns Server TCP sockets failed to receive"
    ::= { affirmedServicesDnsServerServiceStatisticsNode-levelSocketEntry 20 }

affirmedServicesDnsServerServiceStatisticsNode-levelResolverTable OBJECT-TYPE
    SYNTAX      SEQUENCE OF AffirmedServicesDnsServerServiceStatisticsNode-levelResolverEntry
    MAX-ACCESS  not-accessible
    STATUS      current
    DESCRIPTION ""
    ::= { affirmedServicesDnsServerServiceStatisticsNode-level 7 }

affirmedServicesDnsServerServiceStatisticsNode-levelResolverEntry OBJECT-TYPE
    SYNTAX      AffirmedServicesDnsServerServiceStatisticsNode-levelResolverEntry
    MAX-ACCESS  not-accessible
    STATUS      current
    DESCRIPTION ""
    INDEX { affirmedServicesDnsServerServiceStatisticsNode-levelResolverChassis, affirmedServicesDnsServerServiceStatisticsNode-levelResolverSlot }
        ::= { affirmedServicesDnsServerServiceStatisticsNode-levelResolverTable 1 }

AffirmedServicesDnsServerServiceStatisticsNode-levelResolverEntry ::=
    SEQUENCE {
        affirmedServicesDnsServerServiceStatisticsNode-levelResolverChassis Unsigned32,
        affirmedServicesDnsServerServiceStatisticsNode-levelResolverSlot INTEGER,
        affirmedServicesDnsServerServiceStatisticsNode-levelResolverNumdnsserverresolvipv4queries ConfdString,
        affirmedServicesDnsServerServiceStatisticsNode-levelResolverNumdnsserverresolvipv6queries ConfdString,
        affirmedServicesDnsServerServiceStatisticsNode-levelResolverNumdnsserverresolvipv4responses ConfdString,
        affirmedServicesDnsServerServiceStatisticsNode-levelResolverNumdnsserverresolvipv6responses ConfdString,
        affirmedServicesDnsServerServiceStatisticsNode-levelResolverNumdnsserverresolvnxdomainresponses ConfdString,
        affirmedServicesDnsServerServiceStatisticsNode-levelResolverNumdnsserverresolvservfailresponses ConfdString,
        affirmedServicesDnsServerServiceStatisticsNode-levelResolverNumdnsserverresolvformerrresponses ConfdString,
        affirmedServicesDnsServerServiceStatisticsNode-levelResolverNumdnsserverresolvothererrresponses ConfdString,
        affirmedServicesDnsServerServiceStatisticsNode-levelResolverNumdnsserverresolvednsfail ConfdString,
        affirmedServicesDnsServerServiceStatisticsNode-levelResolverNumdnsserverresolvmismatchresponses ConfdString,
        affirmedServicesDnsServerServiceStatisticsNode-levelResolverNumdnsserverresolvtruncatedresponses ConfdString,
        affirmedServicesDnsServerServiceStatisticsNode-levelResolverNumdnsserverresolvlamedelegations ConfdString,
        affirmedServicesDnsServerServiceStatisticsNode-levelResolverNumdnsserverresolvqueryretries ConfdString,
        affirmedServicesDnsServerServiceStatisticsNode-levelResolverNumdnsserverresolvqueryaborts ConfdString,
        affirmedServicesDnsServerServiceStatisticsNode-levelResolverNumdnsserverresolvquerysockfail ConfdString,
        affirmedServicesDnsServerServiceStatisticsNode-levelResolverNumdnsserverresolvquerytimeout ConfdString,
        affirmedServicesDnsServerServiceStatisticsNode-levelResolverNumdnsserverresolvgluefetchipv4 ConfdString,
        affirmedServicesDnsServerServiceStatisticsNode-levelResolverNumdnsserverresolvgluefetchipv6 ConfdString,
        affirmedServicesDnsServerServiceStatisticsNode-levelResolverNumdnsserverresolvgluefetchipv4fail ConfdString,
        affirmedServicesDnsServerServiceStatisticsNode-levelResolverNumdnsserverresolvgluefetchipv6fail ConfdString,
        affirmedServicesDnsServerServiceStatisticsNode-levelResolverNumdnsserverresolvvalattempt ConfdString,
        affirmedServicesDnsServerServiceStatisticsNode-levelResolverNumdnsserverresolvvalok ConfdString,
        affirmedServicesDnsServerServiceStatisticsNode-levelResolverNumdnsserverresolvvalnegok ConfdString,
        affirmedServicesDnsServerServiceStatisticsNode-levelResolverNumdnsserverresolvvalfail ConfdString,
        affirmedServicesDnsServerServiceStatisticsNode-levelResolverNumdnsserverresolvqueryrtt0 ConfdString,
        affirmedServicesDnsServerServiceStatisticsNode-levelResolverNumdnsserverresolvqueryrtt1 ConfdString,
        affirmedServicesDnsServerServiceStatisticsNode-levelResolverNumdnsserverresolvqueryrtt2 ConfdString,
        affirmedServicesDnsServerServiceStatisticsNode-levelResolverNumdnsserverresolvqueryrtt3 ConfdString,
        affirmedServicesDnsServerServiceStatisticsNode-levelResolverNumdnsserverresolvqueryrtt4 ConfdString,
        affirmedServicesDnsServerServiceStatisticsNode-levelResolverNumdnsserverresolvqueryrtt5 ConfdString,
        affirmedServicesDnsServerServiceStatisticsNode-levelResolverNumdnsserverresolvnfetch ConfdString,
        affirmedServicesDnsServerServiceStatisticsNode-levelResolverNumdnsserverresolvdisprequdp ConfdString,
        affirmedServicesDnsServerServiceStatisticsNode-levelResolverNumdnsserverresolvdispreqtcp ConfdString,
        affirmedServicesDnsServerServiceStatisticsNode-levelResolverNumdnsserverresolvbuckets ConfdString,
        affirmedServicesDnsServerServiceStatisticsNode-levelResolverNumdnsserverresolvrefused ConfdString,
        affirmedServicesDnsServerServiceStatisticsNode-levelResolverNumdnsserverresolvcookienew ConfdString,
        affirmedServicesDnsServerServiceStatisticsNode-levelResolverNumdnsserverresolvcookieout ConfdString,
        affirmedServicesDnsServerServiceStatisticsNode-levelResolverNumdnsserverresolvcookiein ConfdString,
        affirmedServicesDnsServerServiceStatisticsNode-levelResolverNumdnsserverresolvcookieok ConfdString,
        affirmedServicesDnsServerServiceStatisticsNode-levelResolverNumdnsserverresolvbadvers ConfdString,
        affirmedServicesDnsServerServiceStatisticsNode-levelResolverNumdnsserverresolvbadcookie ConfdString,
        affirmedServicesDnsServerServiceStatisticsNode-levelResolverNumdnsserverresolvzonequota ConfdString,
        affirmedServicesDnsServerServiceStatisticsNode-levelResolverNumdnsserverresolvserverquota ConfdString,
        affirmedServicesDnsServerServiceStatisticsNode-levelResolverNumdnsserverresolvnextitem ConfdString
    }

affirmedServicesDnsServerServiceStatisticsNode-levelResolverChassis OBJECT-TYPE
    SYNTAX      Unsigned32
    MAX-ACCESS  not-accessible
    STATUS      current
    DESCRIPTION "chassis ID"
    ::= { affirmedServicesDnsServerServiceStatisticsNode-levelResolverEntry 1 }

affirmedServicesDnsServerServiceStatisticsNode-levelResolverSlot OBJECT-TYPE
    SYNTAX      INTEGER {a1(1),a2(2),a3(3),a4(4),a5(5),a6(6),a7(7),a8(8),a9(9),a10(10),a11(11),a12(12),a13(13),a14(14),a15(15),a16(16),a17(17),a18(18),a19(19),a20(20),a21(21),a22(22),a23(23),a24(24),a25(25),a26(26),a27(27),a28(28),a29(29),a30(30),a31(31),a32(32),a33(33),a34(34),a35(35),a36(36),a37(37),a38(38),a39(39),a40(40),a41(41),a42(42),a43(43),a44(44),a45(45),a46(46),a47(47),a48(48),a49(49),a50(50),a51(51),a52(52),a53(53),a54(54),a55(55),a56(56),a57(57),a58(58),a59(59),a60(60),a61(61),a62(62),a63(63),a64(64),a65(65),a66(66),a67(67),a68(68),a69(69),a70(70),a71(71),a72(72),a73(73),a74(74),a75(75),a76(76),a77(77),a78(78),a79(79),a80(80),a81(81),a82(82),a83(83),a84(84),a85(85),a86(86),a87(87),a88(88),a89(89),a90(90),a91(91),a92(92),a93(93),a94(94),a95(95),a96(96),a97(97),a98(98),a99(99),a100(100),a101(101),a102(102),a103(103),a104(104),a105(105),a106(106),a107(107),a108(108),a109(109),a110(110),a111(111),a112(112),a113(113),a114(114),a115(115),a116(116),a117(117),a118(118),a119(119),a120(120),a121(121),a122(122),a123(123),a124(124),a125(125),a126(126),a127(127),a128(128)}
    MAX-ACCESS  not-accessible
    STATUS      current
    DESCRIPTION "slot number"
    ::= { affirmedServicesDnsServerServiceStatisticsNode-levelResolverEntry 2 }

affirmedServicesDnsServerServiceStatisticsNode-levelResolverNumdnsserverresolvipv4queries OBJECT-TYPE
    SYNTAX      ConfdString
    MAX-ACCESS  read-only
    STATUS      current
    DESCRIPTION "Number of Dns Server Resolver IPv4 queries sent"
    ::= { affirmedServicesDnsServerServiceStatisticsNode-levelResolverEntry 3 }

affirmedServicesDnsServerServiceStatisticsNode-levelResolverNumdnsserverresolvipv6queries OBJECT-TYPE
    SYNTAX      ConfdString
    MAX-ACCESS  read-only
    STATUS      current
    DESCRIPTION "Number of Dns Server Resolver IPv6 queries sent"
    ::= { affirmedServicesDnsServerServiceStatisticsNode-levelResolverEntry 4 }

affirmedServicesDnsServerServiceStatisticsNode-levelResolverNumdnsserverresolvipv4responses OBJECT-TYPE
    SYNTAX      ConfdString
    MAX-ACCESS  read-only
    STATUS      current
    DESCRIPTION "Number of Dns Server Resolver IPv4 responses received"
    ::= { affirmedServicesDnsServerServiceStatisticsNode-levelResolverEntry 5 }

affirmedServicesDnsServerServiceStatisticsNode-levelResolverNumdnsserverresolvipv6responses OBJECT-TYPE
    SYNTAX      ConfdString
    MAX-ACCESS  read-only
    STATUS      current
    DESCRIPTION "Number of Dns Server Resolver IPv6 responses received"
    ::= { affirmedServicesDnsServerServiceStatisticsNode-levelResolverEntry 6 }

affirmedServicesDnsServerServiceStatisticsNode-levelResolverNumdnsserverresolvnxdomainresponses OBJECT-TYPE
    SYNTAX      ConfdString
    MAX-ACCESS  read-only
    STATUS      current
    DESCRIPTION "Number of Dns Server Resolver NXDOMAIN responses received"
    ::= { affirmedServicesDnsServerServiceStatisticsNode-levelResolverEntry 7 }

affirmedServicesDnsServerServiceStatisticsNode-levelResolverNumdnsserverresolvservfailresponses OBJECT-TYPE
    SYNTAX      ConfdString
    MAX-ACCESS  read-only
    STATUS      current
    DESCRIPTION "Number of Dns Server Resolver SERVFAIL responses received"
    ::= { affirmedServicesDnsServerServiceStatisticsNode-levelResolverEntry 8 }

affirmedServicesDnsServerServiceStatisticsNode-levelResolverNumdnsserverresolvformerrresponses OBJECT-TYPE
    SYNTAX      ConfdString
    MAX-ACCESS  read-only
    STATUS      current
    DESCRIPTION "Number of Dns Server Resolver FORMERR responses received"
    ::= { affirmedServicesDnsServerServiceStatisticsNode-levelResolverEntry 9 }

affirmedServicesDnsServerServiceStatisticsNode-levelResolverNumdnsserverresolvothererrresponses OBJECT-TYPE
    SYNTAX      ConfdString
    MAX-ACCESS  read-only
    STATUS      current
    DESCRIPTION "Number of Dns Server Resolver Other Error responses received"
    ::= { affirmedServicesDnsServerServiceStatisticsNode-levelResolverEntry 10 }

affirmedServicesDnsServerServiceStatisticsNode-levelResolverNumdnsserverresolvednsfail OBJECT-TYPE
    SYNTAX      ConfdString
    MAX-ACCESS  read-only
    STATUS      current
    DESCRIPTION "Number of Dns Server Resolver EDNS0 query Failures"
    ::= { affirmedServicesDnsServerServiceStatisticsNode-levelResolverEntry 11 }

affirmedServicesDnsServerServiceStatisticsNode-levelResolverNumdnsserverresolvmismatchresponses OBJECT-TYPE
    SYNTAX      ConfdString
    MAX-ACCESS  read-only
    STATUS      current
    DESCRIPTION "Number of Dns Server Resolver Mismatch responses received"
    ::= { affirmedServicesDnsServerServiceStatisticsNode-levelResolverEntry 12 }

affirmedServicesDnsServerServiceStatisticsNode-levelResolverNumdnsserverresolvtruncatedresponses OBJECT-TYPE
    SYNTAX      ConfdString
    MAX-ACCESS  read-only
    STATUS      current
    DESCRIPTION "Number of Dns Server Resolver Truncated responses received"
    ::= { affirmedServicesDnsServerServiceStatisticsNode-levelResolverEntry 13 }

affirmedServicesDnsServerServiceStatisticsNode-levelResolverNumdnsserverresolvlamedelegations OBJECT-TYPE
    SYNTAX      ConfdString
    MAX-ACCESS  read-only
    STATUS      current
    DESCRIPTION "Number of Dns Server Resolver Lame Delegations received"
    ::= { affirmedServicesDnsServerServiceStatisticsNode-levelResolverEntry 14 }

affirmedServicesDnsServerServiceStatisticsNode-levelResolverNumdnsserverresolvqueryretries OBJECT-TYPE
    SYNTAX      ConfdString
    MAX-ACCESS  read-only
    STATUS      current
    DESCRIPTION "Number of Dns Server Resolver Query Retries Performed"
    ::= { affirmedServicesDnsServerServiceStatisticsNode-levelResolverEntry 15 }

affirmedServicesDnsServerServiceStatisticsNode-levelResolverNumdnsserverresolvqueryaborts OBJECT-TYPE
    SYNTAX      ConfdString
    MAX-ACCESS  read-only
    STATUS      current
    DESCRIPTION "Number of Dns Server Resolver Queries Aborted"
    ::= { affirmedServicesDnsServerServiceStatisticsNode-levelResolverEntry 16 }

affirmedServicesDnsServerServiceStatisticsNode-levelResolverNumdnsserverresolvquerysockfail OBJECT-TYPE
    SYNTAX      ConfdString
    MAX-ACCESS  read-only
    STATUS      current
    DESCRIPTION "Number of Dns Server Resolver Failures in opening query sockets"
    ::= { affirmedServicesDnsServerServiceStatisticsNode-levelResolverEntry 17 }

affirmedServicesDnsServerServiceStatisticsNode-levelResolverNumdnsserverresolvquerytimeout OBJECT-TYPE
    SYNTAX      ConfdString
    MAX-ACCESS  read-only
    STATUS      current
    DESCRIPTION "Number of Dns Server Resolver Query timeouts"
    ::= { affirmedServicesDnsServerServiceStatisticsNode-levelResolverEntry 18 }

affirmedServicesDnsServerServiceStatisticsNode-levelResolverNumdnsserverresolvgluefetchipv4 OBJECT-TYPE
    SYNTAX      ConfdString
    MAX-ACCESS  read-only
    STATUS      current
    DESCRIPTION "Number of Dns Server Resolver IPv4 NS Address fetches"
    ::= { affirmedServicesDnsServerServiceStatisticsNode-levelResolverEntry 19 }

affirmedServicesDnsServerServiceStatisticsNode-levelResolverNumdnsserverresolvgluefetchipv6 OBJECT-TYPE
    SYNTAX      ConfdString
    MAX-ACCESS  read-only
    STATUS      current
    DESCRIPTION "Number of Dns Server Resolver IPv6 NS Address fetches"
    ::= { affirmedServicesDnsServerServiceStatisticsNode-levelResolverEntry 20 }

affirmedServicesDnsServerServiceStatisticsNode-levelResolverNumdnsserverresolvgluefetchipv4fail OBJECT-TYPE
    SYNTAX      ConfdString
    MAX-ACCESS  read-only
    STATUS      current
    DESCRIPTION "Number of Dns Server Resolver IPv4 NS Address fetches failed"
    ::= { affirmedServicesDnsServerServiceStatisticsNode-levelResolverEntry 21 }

affirmedServicesDnsServerServiceStatisticsNode-levelResolverNumdnsserverresolvgluefetchipv6fail OBJECT-TYPE
    SYNTAX      ConfdString
    MAX-ACCESS  read-only
    STATUS      current
    DESCRIPTION "Number of Dns Server Resolver IPv6 NS Address fetches failed"
    ::= { affirmedServicesDnsServerServiceStatisticsNode-levelResolverEntry 22 }

affirmedServicesDnsServerServiceStatisticsNode-levelResolverNumdnsserverresolvvalattempt OBJECT-TYPE
    SYNTAX      ConfdString
    MAX-ACCESS  read-only
    STATUS      current
    DESCRIPTION "Number of Dns Server Resolver DNSSEC Validation Attempted"
    ::= { affirmedServicesDnsServerServiceStatisticsNode-levelResolverEntry 23 }

affirmedServicesDnsServerServiceStatisticsNode-levelResolverNumdnsserverresolvvalok OBJECT-TYPE
    SYNTAX      ConfdString
    MAX-ACCESS  read-only
    STATUS      current
    DESCRIPTION "Number of Dns Server Resolver DNSSEC Validation Succeeded"
    ::= { affirmedServicesDnsServerServiceStatisticsNode-levelResolverEntry 24 }

affirmedServicesDnsServerServiceStatisticsNode-levelResolverNumdnsserverresolvvalnegok OBJECT-TYPE
    SYNTAX      ConfdString
    MAX-ACCESS  read-only
    STATUS      current
    DESCRIPTION "Number of Dns Server Resolver DNSSEC Validation on Negative Info Succeeded"
    ::= { affirmedServicesDnsServerServiceStatisticsNode-levelResolverEntry 25 }

affirmedServicesDnsServerServiceStatisticsNode-levelResolverNumdnsserverresolvvalfail OBJECT-TYPE
    SYNTAX      ConfdString
    MAX-ACCESS  read-only
    STATUS      current
    DESCRIPTION "Number of Dns Server Resolver DNSSEC Validation Failed"
    ::= { affirmedServicesDnsServerServiceStatisticsNode-levelResolverEntry 26 }

affirmedServicesDnsServerServiceStatisticsNode-levelResolverNumdnsserverresolvqueryrtt0 OBJECT-TYPE
    SYNTAX      ConfdString
    MAX-ACCESS  read-only
    STATUS      current
    DESCRIPTION "Number of Dns Server Resolver queries with RTT < 10ms"
    ::= { affirmedServicesDnsServerServiceStatisticsNode-levelResolverEntry 27 }

affirmedServicesDnsServerServiceStatisticsNode-levelResolverNumdnsserverresolvqueryrtt1 OBJECT-TYPE
    SYNTAX      ConfdString
    MAX-ACCESS  read-only
    STATUS      current
    DESCRIPTION "Number of Dns Server Resolver queries with RTT 10-99ms"
    ::= { affirmedServicesDnsServerServiceStatisticsNode-levelResolverEntry 28 }

affirmedServicesDnsServerServiceStatisticsNode-levelResolverNumdnsserverresolvqueryrtt2 OBJECT-TYPE
    SYNTAX      ConfdString
    MAX-ACCESS  read-only
    STATUS      current
    DESCRIPTION "Number of Dns Server Resolver queries with RTT 100-499ms"
    ::= { affirmedServicesDnsServerServiceStatisticsNode-levelResolverEntry 29 }

affirmedServicesDnsServerServiceStatisticsNode-levelResolverNumdnsserverresolvqueryrtt3 OBJECT-TYPE
    SYNTAX      ConfdString
    MAX-ACCESS  read-only
    STATUS      current
    DESCRIPTION "Number of Dns Server Resolver queries with RTT 500-799ms"
    ::= { affirmedServicesDnsServerServiceStatisticsNode-levelResolverEntry 30 }

affirmedServicesDnsServerServiceStatisticsNode-levelResolverNumdnsserverresolvqueryrtt4 OBJECT-TYPE
    SYNTAX      ConfdString
    MAX-ACCESS  read-only
    STATUS      current
    DESCRIPTION "Number of Dns Server Resolver queries with RTT 800-1599ms"
    ::= { affirmedServicesDnsServerServiceStatisticsNode-levelResolverEntry 31 }

affirmedServicesDnsServerServiceStatisticsNode-levelResolverNumdnsserverresolvqueryrtt5 OBJECT-TYPE
    SYNTAX      ConfdString
    MAX-ACCESS  read-only
    STATUS      current
    DESCRIPTION "Number of Dns Server Resolver queries with RTT >= 1600ms"
    ::= { affirmedServicesDnsServerServiceStatisticsNode-levelResolverEntry 32 }

affirmedServicesDnsServerServiceStatisticsNode-levelResolverNumdnsserverresolvnfetch OBJECT-TYPE
    SYNTAX      ConfdString
    MAX-ACCESS  read-only
    STATUS      current
    DESCRIPTION "Number of Dns Server Resolver Active Fetches"
    ::= { affirmedServicesDnsServerServiceStatisticsNode-levelResolverEntry 33 }

affirmedServicesDnsServerServiceStatisticsNode-levelResolverNumdnsserverresolvdisprequdp OBJECT-TYPE
    SYNTAX      ConfdString
    MAX-ACCESS  read-only
    STATUS      current
    DESCRIPTION "Number of Dns Server Resolver UDP queries in progress"
    ::= { affirmedServicesDnsServerServiceStatisticsNode-levelResolverEntry 34 }

affirmedServicesDnsServerServiceStatisticsNode-levelResolverNumdnsserverresolvdispreqtcp OBJECT-TYPE
    SYNTAX      ConfdString
    MAX-ACCESS  read-only
    STATUS      current
    DESCRIPTION "Number of Dns Server Resolver TCP queries in progress"
    ::= { affirmedServicesDnsServerServiceStatisticsNode-levelResolverEntry 35 }

affirmedServicesDnsServerServiceStatisticsNode-levelResolverNumdnsserverresolvbuckets OBJECT-TYPE
    SYNTAX      ConfdString
    MAX-ACCESS  read-only
    STATUS      current
    DESCRIPTION "Number of Dns Server Resolver Bucket size"
    ::= { affirmedServicesDnsServerServiceStatisticsNode-levelResolverEntry 36 }

affirmedServicesDnsServerServiceStatisticsNode-levelResolverNumdnsserverresolvrefused OBJECT-TYPE
    SYNTAX      ConfdString
    MAX-ACCESS  read-only
    STATUS      current
    DESCRIPTION "Number of Dns Server Resolver REFUSED received"
    ::= { affirmedServicesDnsServerServiceStatisticsNode-levelResolverEntry 37 }

affirmedServicesDnsServerServiceStatisticsNode-levelResolverNumdnsserverresolvcookienew OBJECT-TYPE
    SYNTAX      ConfdString
    MAX-ACCESS  read-only
    STATUS      current
    DESCRIPTION "Number of Dns Server Resolver COOKIE send with client cookie only"
    ::= { affirmedServicesDnsServerServiceStatisticsNode-levelResolverEntry 38 }

affirmedServicesDnsServerServiceStatisticsNode-levelResolverNumdnsserverresolvcookieout OBJECT-TYPE
    SYNTAX      ConfdString
    MAX-ACCESS  read-only
    STATUS      current
    DESCRIPTION "Number of Dns Server Resolver COOKIE sent with client and server cookie"
    ::= { affirmedServicesDnsServerServiceStatisticsNode-levelResolverEntry 39 }

affirmedServicesDnsServerServiceStatisticsNode-levelResolverNumdnsserverresolvcookiein OBJECT-TYPE
    SYNTAX      ConfdString
    MAX-ACCESS  read-only
    STATUS      current
    DESCRIPTION "Number of Dns Server Resolver COOKIE replies received"
    ::= { affirmedServicesDnsServerServiceStatisticsNode-levelResolverEntry 40 }

affirmedServicesDnsServerServiceStatisticsNode-levelResolverNumdnsserverresolvcookieok OBJECT-TYPE
    SYNTAX      ConfdString
    MAX-ACCESS  read-only
    STATUS      current
    DESCRIPTION "Number of Dns Server Resolver COOKIE client ok"
    ::= { affirmedServicesDnsServerServiceStatisticsNode-levelResolverEntry 41 }

affirmedServicesDnsServerServiceStatisticsNode-levelResolverNumdnsserverresolvbadvers OBJECT-TYPE
    SYNTAX      ConfdString
    MAX-ACCESS  read-only
    STATUS      current
    DESCRIPTION "Number of Dns Server Resolver Bad EDNS version"
    ::= { affirmedServicesDnsServerServiceStatisticsNode-levelResolverEntry 42 }

affirmedServicesDnsServerServiceStatisticsNode-levelResolverNumdnsserverresolvbadcookie OBJECT-TYPE
    SYNTAX      ConfdString
    MAX-ACCESS  read-only
    STATUS      current
    DESCRIPTION "Number of Dns Server Resolver Bad cookie Rcode"
    ::= { affirmedServicesDnsServerServiceStatisticsNode-levelResolverEntry 43 }

affirmedServicesDnsServerServiceStatisticsNode-levelResolverNumdnsserverresolvzonequota OBJECT-TYPE
    SYNTAX      ConfdString
    MAX-ACCESS  read-only
    STATUS      current
    DESCRIPTION "Number of Dns Server Resolver Spilled due to zone quota"
    ::= { affirmedServicesDnsServerServiceStatisticsNode-levelResolverEntry 44 }

affirmedServicesDnsServerServiceStatisticsNode-levelResolverNumdnsserverresolvserverquota OBJECT-TYPE
    SYNTAX      ConfdString
    MAX-ACCESS  read-only
    STATUS      current
    DESCRIPTION "Number of Dns Server Resolver Spilled due to server quota"
    ::= { affirmedServicesDnsServerServiceStatisticsNode-levelResolverEntry 45 }

affirmedServicesDnsServerServiceStatisticsNode-levelResolverNumdnsserverresolvnextitem OBJECT-TYPE
    SYNTAX      ConfdString
    MAX-ACCESS  read-only
    STATUS      current
    DESCRIPTION "Number of Dns Server Resolver Waited for next item"
    ::= { affirmedServicesDnsServerServiceStatisticsNode-levelResolverEntry 46 }

affirmedServicesDnsServerServiceProtocolTable OBJECT-TYPE
    SYNTAX      SEQUENCE OF AffirmedServicesDnsServerServiceProtocolEntry
    MAX-ACCESS  not-accessible
    STATUS      current
    DESCRIPTION ""
    ::= { affirmedServicesDnsServerService 2 }

affirmedServicesDnsServerServiceProtocolEntry OBJECT-TYPE
    SYNTAX      AffirmedServicesDnsServerServiceProtocolEntry
    MAX-ACCESS  not-accessible
    STATUS      current
    DESCRIPTION ""
    INDEX { affirmedServicesDnsServerServiceProtocolCluster, affirmedServicesDnsServerServiceProtocolNode, affirmedServicesDnsServerServiceProtocolInst, affirmedServicesDnsServerServiceProtocolName }
        ::= { affirmedServicesDnsServerServiceProtocolTable 1 }

AffirmedServicesDnsServerServiceProtocolEntry ::=
    SEQUENCE {
        affirmedServicesDnsServerServiceProtocolCluster Unsigned32,
        affirmedServicesDnsServerServiceProtocolNode INTEGER,
        affirmedServicesDnsServerServiceProtocolInst Unsigned32,
        affirmedServicesDnsServerServiceProtocolName INTEGER,
        affirmedServicesDnsServerServiceProtocolResult String
    }

affirmedServicesDnsServerServiceProtocolCluster OBJECT-TYPE
    SYNTAX      Unsigned32
    MAX-ACCESS  not-accessible
    STATUS      current
    DESCRIPTION "cluster ID"
    ::= { affirmedServicesDnsServerServiceProtocolEntry 1 }

affirmedServicesDnsServerServiceProtocolNode OBJECT-TYPE
    SYNTAX      INTEGER {a1(1),a2(2),a3(3),a4(4),a5(5),a6(6),a7(7),a8(8),a9(9),a10(10),a11(11),a12(12),a13(13),a14(14),a15(15),a16(16),a17(17),a18(18),a19(19),a20(20),a21(21),a22(22),a23(23),a24(24),a25(25),a26(26),a27(27),a28(28),a29(29),a30(30),a31(31),a32(32),a33(33),a34(34),a35(35),a36(36),a37(37),a38(38),a39(39),a40(40),a41(41),a42(42),a43(43),a44(44),a45(45),a46(46),a47(47),a48(48),a49(49),a50(50),a51(51),a52(52),a53(53),a54(54),a55(55),a56(56),a57(57),a58(58),a59(59),a60(60),a61(61),a62(62),a63(63),a64(64),a65(65),a66(66),a67(67),a68(68),a69(69),a70(70),a71(71),a72(72),a73(73),a74(74),a75(75),a76(76),a77(77),a78(78),a79(79),a80(80),a81(81),a82(82),a83(83),a84(84),a85(85),a86(86),a87(87),a88(88),a89(89),a90(90),a91(91),a92(92),a93(93),a94(94),a95(95),a96(96),a97(97),a98(98),a99(99),a100(100),a101(101),a102(102),a103(103),a104(104),a105(105),a106(106),a107(107),a108(108),a109(109),a110(110),a111(111),a112(112),a113(113),a114(114),a115(115),a116(116),a117(117),a118(118),a119(119),a120(120),a121(121),a122(122),a123(123),a124(124),a125(125),a126(126),a127(127),a128(128)}
    MAX-ACCESS  not-accessible
    STATUS      current
    DESCRIPTION "node number"
    ::= { affirmedServicesDnsServerServiceProtocolEntry 2 }

affirmedServicesDnsServerServiceProtocolInst OBJECT-TYPE
    SYNTAX      Unsigned32
    MAX-ACCESS  not-accessible
    STATUS      current
    DESCRIPTION "DNS task instance number: 1..2"
    ::= { affirmedServicesDnsServerServiceProtocolEntry 3 }

affirmedServicesDnsServerServiceProtocolName OBJECT-TYPE
    SYNTAX      INTEGER {status(1),config(2)}
    MAX-ACCESS  not-accessible
    STATUS      current
    DESCRIPTION "Display debug options"
    ::= { affirmedServicesDnsServerServiceProtocolEntry 4 }

affirmedServicesDnsServerServiceProtocolResult OBJECT-TYPE
    SYNTAX      String
    MAX-ACCESS  read-only
    STATUS      current
    DESCRIPTION ""
    ::= { affirmedServicesDnsServerServiceProtocolEntry 5 }

affirmedServicesQosServiceDataFlowTable OBJECT-TYPE
    SYNTAX      SEQUENCE OF AffirmedServicesQosServiceDataFlowEntry
    MAX-ACCESS  not-accessible
    STATUS      current
    DESCRIPTION ""
    ::= { affirmedServicesQos 1 }

affirmedServicesQosServiceDataFlowEntry OBJECT-TYPE
    SYNTAX      AffirmedServicesQosServiceDataFlowEntry
    MAX-ACCESS  not-accessible
    STATUS      current
    DESCRIPTION ""
    INDEX { affirmedServicesQosServiceDataFlowQosPolicy, affirmedServicesQosServiceDataFlowQosFlowPriority, affirmedServicesQosServiceDataFlowServiceRulePriority, affirmedServicesQosServiceDataFlowQosFlow, affirmedServicesQosServiceDataFlowServiceRule }
        ::= { affirmedServicesQosServiceDataFlowTable 1 }

AffirmedServicesQosServiceDataFlowEntry ::=
    SEQUENCE {
        affirmedServicesQosServiceDataFlowQosPolicy String,
        affirmedServicesQosServiceDataFlowQosFlowPriority Unsigned32,
        affirmedServicesQosServiceDataFlowServiceRulePriority Unsigned32,
        affirmedServicesQosServiceDataFlowQosFlow String,
        affirmedServicesQosServiceDataFlowServiceRule String,
        affirmedServicesQosServiceDataFlowQosFlowId Unsigned32,
        affirmedServicesQosServiceDataFlowServiceRuleId Unsigned32
    }

affirmedServicesQosServiceDataFlowQosPolicy OBJECT-TYPE
    SYNTAX      String
    MAX-ACCESS  not-accessible
    STATUS      current
    DESCRIPTION "the name of the qos-policy"
    ::= { affirmedServicesQosServiceDataFlowEntry 1 }

affirmedServicesQosServiceDataFlowQosFlowPriority OBJECT-TYPE
    SYNTAX      Unsigned32
    MAX-ACCESS  not-accessible
    STATUS      current
    DESCRIPTION "the priority of the qos-flow"
    ::= { affirmedServicesQosServiceDataFlowEntry 2 }

affirmedServicesQosServiceDataFlowServiceRulePriority OBJECT-TYPE
    SYNTAX      Unsigned32
    MAX-ACCESS  not-accessible
    STATUS      current
    DESCRIPTION "the priority of the service-rule"
    ::= { affirmedServicesQosServiceDataFlowEntry 3 }

affirmedServicesQosServiceDataFlowQosFlow OBJECT-TYPE
    SYNTAX      String
    MAX-ACCESS  not-accessible
    STATUS      current
    DESCRIPTION "the name of the qos-flow"
    ::= { affirmedServicesQosServiceDataFlowEntry 4 }

affirmedServicesQosServiceDataFlowServiceRule OBJECT-TYPE
    SYNTAX      String
    MAX-ACCESS  not-accessible
    STATUS      current
    DESCRIPTION "the name of the service-rule"
    ::= { affirmedServicesQosServiceDataFlowEntry 5 }

affirmedServicesQosServiceDataFlowQosFlowId OBJECT-TYPE
    SYNTAX      Unsigned32
    MAX-ACCESS  read-only
    STATUS      current
    DESCRIPTION "the internal ID of the qos-flow, used to identify PDN-session service-data-flows {session-id, service-type=qos-policy, qos-flow-id, service-rule-id}"
    ::= { affirmedServicesQosServiceDataFlowEntry 6 }

affirmedServicesQosServiceDataFlowServiceRuleId OBJECT-TYPE
    SYNTAX      Unsigned32
    MAX-ACCESS  read-only
    STATUS      current
    DESCRIPTION "the internal ID of the service-rule, used to identify PDN-session service-data-flows {session-id, service-type=qos-policy, qos-flow-id, service-rule-id}"
    ::= { affirmedServicesQosServiceDataFlowEntry 7 }

affirmedServicesVideoAdaptationServiceStatisticsChassisLevelOnlineTranscodingSummaryTable OBJECT-TYPE
    SYNTAX      SEQUENCE OF AffirmedServicesVideoAdaptationServiceStatisticsChassisLevelOnlineTranscodingSummaryEntry
    MAX-ACCESS  not-accessible
    STATUS      current
    DESCRIPTION ""
    ::= { affirmedServicesVideoAdaptationServiceStatisticsChassisLevelOnlineTranscoding 1 }

affirmedServicesVideoAdaptationServiceStatisticsChassisLevelOnlineTranscodingSummaryEntry OBJECT-TYPE
    SYNTAX      AffirmedServicesVideoAdaptationServiceStatisticsChassisLevelOnlineTranscodingSummaryEntry
    MAX-ACCESS  not-accessible
    STATUS      current
    DESCRIPTION ""
    INDEX { affirmedServicesVideoAdaptationServiceStatisticsChassisLevelOnlineTranscodingSummaryChassis }
        ::= { affirmedServicesVideoAdaptationServiceStatisticsChassisLevelOnlineTranscodingSummaryTable 1 }

AffirmedServicesVideoAdaptationServiceStatisticsChassisLevelOnlineTranscodingSummaryEntry ::=
    SEQUENCE {
        affirmedServicesVideoAdaptationServiceStatisticsChassisLevelOnlineTranscodingSummaryChassis Unsigned32,
        affirmedServicesVideoAdaptationServiceStatisticsChassisLevelOnlineTranscodingSummaryNumotfattempts ConfdString,
        affirmedServicesVideoAdaptationServiceStatisticsChassisLevelOnlineTranscodingSummaryNumotfsuccesses ConfdString,
        affirmedServicesVideoAdaptationServiceStatisticsChassisLevelOnlineTranscodingSummaryNumotfcancels ConfdString,
        affirmedServicesVideoAdaptationServiceStatisticsChassisLevelOnlineTranscodingSummaryNumotffailures ConfdString,
        affirmedServicesVideoAdaptationServiceStatisticsChassisLevelOnlineTranscodingSummaryNumotfaborts ConfdString,
        affirmedServicesVideoAdaptationServiceStatisticsChassisLevelOnlineTranscodingSummaryNumotfcurrent ConfdString,
        affirmedServicesVideoAdaptationServiceStatisticsChassisLevelOnlineTranscodingSummaryNumotfbytesattempt ConfdString,
        affirmedServicesVideoAdaptationServiceStatisticsChassisLevelOnlineTranscodingSummaryNumotfbytesadapted ConfdString,
        affirmedServicesVideoAdaptationServiceStatisticsChassisLevelOnlineTranscodingSummaryNumotfbytescancel ConfdString,
        affirmedServicesVideoAdaptationServiceStatisticsChassisLevelOnlineTranscodingSummaryVideosizemin ConfdString,
        affirmedServicesVideoAdaptationServiceStatisticsChassisLevelOnlineTranscodingSummaryVideosizeavg ConfdString,
        affirmedServicesVideoAdaptationServiceStatisticsChassisLevelOnlineTranscodingSummaryVideosizemax ConfdString,
        affirmedServicesVideoAdaptationServiceStatisticsChassisLevelOnlineTranscodingSummaryAdaptedvideosizemin ConfdString,
        affirmedServicesVideoAdaptationServiceStatisticsChassisLevelOnlineTranscodingSummaryAdaptedvideosizeavg ConfdString,
        affirmedServicesVideoAdaptationServiceStatisticsChassisLevelOnlineTranscodingSummaryAdaptedvideosizemax ConfdString,
        affirmedServicesVideoAdaptationServiceStatisticsChassisLevelOnlineTranscodingSummaryAdditionallatencymin ConfdString,
        affirmedServicesVideoAdaptationServiceStatisticsChassisLevelOnlineTranscodingSummaryAdditionallatencyavg ConfdString,
        affirmedServicesVideoAdaptationServiceStatisticsChassisLevelOnlineTranscodingSummaryAdditionallatencymax ConfdString
    }

affirmedServicesVideoAdaptationServiceStatisticsChassisLevelOnlineTranscodingSummaryChassis OBJECT-TYPE
    SYNTAX      Unsigned32
    MAX-ACCESS  not-accessible
    STATUS      current
    DESCRIPTION "chassis ID"
    ::= { affirmedServicesVideoAdaptationServiceStatisticsChassisLevelOnlineTranscodingSummaryEntry 1 }

affirmedServicesVideoAdaptationServiceStatisticsChassisLevelOnlineTranscodingSummaryNumotfattempts OBJECT-TYPE
    SYNTAX      ConfdString
    MAX-ACCESS  read-only
    STATUS      current
    DESCRIPTION "Total number of Online Transcoding attempts"
    ::= { affirmedServicesVideoAdaptationServiceStatisticsChassisLevelOnlineTranscodingSummaryEntry 2 }

affirmedServicesVideoAdaptationServiceStatisticsChassisLevelOnlineTranscodingSummaryNumotfsuccesses OBJECT-TYPE
    SYNTAX      ConfdString
    MAX-ACCESS  read-only
    STATUS      current
    DESCRIPTION "Total number of Online Transcoding successes"
    ::= { affirmedServicesVideoAdaptationServiceStatisticsChassisLevelOnlineTranscodingSummaryEntry 3 }

affirmedServicesVideoAdaptationServiceStatisticsChassisLevelOnlineTranscodingSummaryNumotfcancels OBJECT-TYPE
    SYNTAX      ConfdString
    MAX-ACCESS  read-only
    STATUS      current
    DESCRIPTION "Total number of Online Transcoding cancels"
    ::= { affirmedServicesVideoAdaptationServiceStatisticsChassisLevelOnlineTranscodingSummaryEntry 4 }

affirmedServicesVideoAdaptationServiceStatisticsChassisLevelOnlineTranscodingSummaryNumotffailures OBJECT-TYPE
    SYNTAX      ConfdString
    MAX-ACCESS  read-only
    STATUS      current
    DESCRIPTION "Total number of Online Transcoding failures"
    ::= { affirmedServicesVideoAdaptationServiceStatisticsChassisLevelOnlineTranscodingSummaryEntry 5 }

affirmedServicesVideoAdaptationServiceStatisticsChassisLevelOnlineTranscodingSummaryNumotfaborts OBJECT-TYPE
    SYNTAX      ConfdString
    MAX-ACCESS  read-only
    STATUS      current
    DESCRIPTION "Total number of Online Transcoding aborts"
    ::= { affirmedServicesVideoAdaptationServiceStatisticsChassisLevelOnlineTranscodingSummaryEntry 6 }

affirmedServicesVideoAdaptationServiceStatisticsChassisLevelOnlineTranscodingSummaryNumotfcurrent OBJECT-TYPE
    SYNTAX      ConfdString
    MAX-ACCESS  read-only
    STATUS      current
    DESCRIPTION "Total number of Online Transcoding current"
    ::= { affirmedServicesVideoAdaptationServiceStatisticsChassisLevelOnlineTranscodingSummaryEntry 7 }

affirmedServicesVideoAdaptationServiceStatisticsChassisLevelOnlineTranscodingSummaryNumotfbytesattempt OBJECT-TYPE
    SYNTAX      ConfdString
    MAX-ACCESS  read-only
    STATUS      current
    DESCRIPTION "Total number of Online Transcoding bytes attempt"
    ::= { affirmedServicesVideoAdaptationServiceStatisticsChassisLevelOnlineTranscodingSummaryEntry 8 }

affirmedServicesVideoAdaptationServiceStatisticsChassisLevelOnlineTranscodingSummaryNumotfbytesadapted OBJECT-TYPE
    SYNTAX      ConfdString
    MAX-ACCESS  read-only
    STATUS      current
    DESCRIPTION "Total number of Online Transcoding bytes transcoded"
    ::= { affirmedServicesVideoAdaptationServiceStatisticsChassisLevelOnlineTranscodingSummaryEntry 9 }

affirmedServicesVideoAdaptationServiceStatisticsChassisLevelOnlineTranscodingSummaryNumotfbytescancel OBJECT-TYPE
    SYNTAX      ConfdString
    MAX-ACCESS  read-only
    STATUS      current
    DESCRIPTION "Total number of Online Transcoding bytes cancel"
    ::= { affirmedServicesVideoAdaptationServiceStatisticsChassisLevelOnlineTranscodingSummaryEntry 10 }

affirmedServicesVideoAdaptationServiceStatisticsChassisLevelOnlineTranscodingSummaryVideosizemin OBJECT-TYPE
    SYNTAX      ConfdString
    MAX-ACCESS  read-only
    STATUS      current
    DESCRIPTION "Online Transcoding Video Size Minimum (Bytes)"
    ::= { affirmedServicesVideoAdaptationServiceStatisticsChassisLevelOnlineTranscodingSummaryEntry 11 }

affirmedServicesVideoAdaptationServiceStatisticsChassisLevelOnlineTranscodingSummaryVideosizeavg OBJECT-TYPE
    SYNTAX      ConfdString
    MAX-ACCESS  read-only
    STATUS      current
    DESCRIPTION "Online Transcoding Video Size Average (Bytes)"
    ::= { affirmedServicesVideoAdaptationServiceStatisticsChassisLevelOnlineTranscodingSummaryEntry 12 }

affirmedServicesVideoAdaptationServiceStatisticsChassisLevelOnlineTranscodingSummaryVideosizemax OBJECT-TYPE
    SYNTAX      ConfdString
    MAX-ACCESS  read-only
    STATUS      current
    DESCRIPTION "Online Transcoding Video Size Maximum (Bytes)"
    ::= { affirmedServicesVideoAdaptationServiceStatisticsChassisLevelOnlineTranscodingSummaryEntry 13 }

affirmedServicesVideoAdaptationServiceStatisticsChassisLevelOnlineTranscodingSummaryAdaptedvideosizemin OBJECT-TYPE
    SYNTAX      ConfdString
    MAX-ACCESS  read-only
    STATUS      current
    DESCRIPTION "Online Transcoding Adapted Video Size Minimum (Bytes)"
    ::= { affirmedServicesVideoAdaptationServiceStatisticsChassisLevelOnlineTranscodingSummaryEntry 14 }

affirmedServicesVideoAdaptationServiceStatisticsChassisLevelOnlineTranscodingSummaryAdaptedvideosizeavg OBJECT-TYPE
    SYNTAX      ConfdString
    MAX-ACCESS  read-only
    STATUS      current
    DESCRIPTION "Online Transcoding Adapted Video Size Average (Bytes)"
    ::= { affirmedServicesVideoAdaptationServiceStatisticsChassisLevelOnlineTranscodingSummaryEntry 15 }

affirmedServicesVideoAdaptationServiceStatisticsChassisLevelOnlineTranscodingSummaryAdaptedvideosizemax OBJECT-TYPE
    SYNTAX      ConfdString
    MAX-ACCESS  read-only
    STATUS      current
    DESCRIPTION "Online Transcoding Adapted Video Size Maximum (Bytes)"
    ::= { affirmedServicesVideoAdaptationServiceStatisticsChassisLevelOnlineTranscodingSummaryEntry 16 }

affirmedServicesVideoAdaptationServiceStatisticsChassisLevelOnlineTranscodingSummaryAdditionallatencymin OBJECT-TYPE
    SYNTAX      ConfdString
    MAX-ACCESS  read-only
    STATUS      current
    DESCRIPTION "Online Transcoding Additional Latency Minimum (msecs)"
    ::= { affirmedServicesVideoAdaptationServiceStatisticsChassisLevelOnlineTranscodingSummaryEntry 17 }

affirmedServicesVideoAdaptationServiceStatisticsChassisLevelOnlineTranscodingSummaryAdditionallatencyavg OBJECT-TYPE
    SYNTAX      ConfdString
    MAX-ACCESS  read-only
    STATUS      current
    DESCRIPTION "Online Transcoding Additional Latency Average (msecs)"
    ::= { affirmedServicesVideoAdaptationServiceStatisticsChassisLevelOnlineTranscodingSummaryEntry 18 }

affirmedServicesVideoAdaptationServiceStatisticsChassisLevelOnlineTranscodingSummaryAdditionallatencymax OBJECT-TYPE
    SYNTAX      ConfdString
    MAX-ACCESS  read-only
    STATUS      current
    DESCRIPTION "Online Transcoding Additional Latency Maximum (msecs)"
    ::= { affirmedServicesVideoAdaptationServiceStatisticsChassisLevelOnlineTranscodingSummaryEntry 19 }

affirmedServicesVideoAdaptationServiceStatisticsChassisLevelOnlineTranscodingDetailTable OBJECT-TYPE
    SYNTAX      SEQUENCE OF AffirmedServicesVideoAdaptationServiceStatisticsChassisLevelOnlineTranscodingDetailEntry
    MAX-ACCESS  not-accessible
    STATUS      current
    DESCRIPTION ""
    ::= { affirmedServicesVideoAdaptationServiceStatisticsChassisLevelOnlineTranscoding 2 }

affirmedServicesVideoAdaptationServiceStatisticsChassisLevelOnlineTranscodingDetailEntry OBJECT-TYPE
    SYNTAX      AffirmedServicesVideoAdaptationServiceStatisticsChassisLevelOnlineTranscodingDetailEntry
    MAX-ACCESS  not-accessible
    STATUS      current
    DESCRIPTION ""
    INDEX { affirmedServicesVideoAdaptationServiceStatisticsChassisLevelOnlineTranscodingDetailChassis }
        ::= { affirmedServicesVideoAdaptationServiceStatisticsChassisLevelOnlineTranscodingDetailTable 1 }

AffirmedServicesVideoAdaptationServiceStatisticsChassisLevelOnlineTranscodingDetailEntry ::=
    SEQUENCE {
        affirmedServicesVideoAdaptationServiceStatisticsChassisLevelOnlineTranscodingDetailChassis Unsigned32,
        affirmedServicesVideoAdaptationServiceStatisticsChassisLevelOnlineTranscodingDetailNumotfflvattempts ConfdString,
        affirmedServicesVideoAdaptationServiceStatisticsChassisLevelOnlineTranscodingDetailNumotfflvsuccesses ConfdString,
        affirmedServicesVideoAdaptationServiceStatisticsChassisLevelOnlineTranscodingDetailNumotfflvcancels ConfdString,
        affirmedServicesVideoAdaptationServiceStatisticsChassisLevelOnlineTranscodingDetailNumotfflvfailures ConfdString,
        affirmedServicesVideoAdaptationServiceStatisticsChassisLevelOnlineTranscodingDetailNumotfflvaborts ConfdString,
        affirmedServicesVideoAdaptationServiceStatisticsChassisLevelOnlineTranscodingDetailNumotfmp4attempts ConfdString,
        affirmedServicesVideoAdaptationServiceStatisticsChassisLevelOnlineTranscodingDetailNumotfmp4successes ConfdString,
        affirmedServicesVideoAdaptationServiceStatisticsChassisLevelOnlineTranscodingDetailNumotfmp4cancels ConfdString,
        affirmedServicesVideoAdaptationServiceStatisticsChassisLevelOnlineTranscodingDetailNumotfmp4failures ConfdString,
        affirmedServicesVideoAdaptationServiceStatisticsChassisLevelOnlineTranscodingDetailNumotfmp4aborts ConfdString,
        affirmedServicesVideoAdaptationServiceStatisticsChassisLevelOnlineTranscodingDetailNumotfwebmattempts ConfdString,
        affirmedServicesVideoAdaptationServiceStatisticsChassisLevelOnlineTranscodingDetailNumotfwebmsuccesses ConfdString,
        affirmedServicesVideoAdaptationServiceStatisticsChassisLevelOnlineTranscodingDetailNumotfwebmcancels ConfdString,
        affirmedServicesVideoAdaptationServiceStatisticsChassisLevelOnlineTranscodingDetailNumotfwebmfailures ConfdString,
        affirmedServicesVideoAdaptationServiceStatisticsChassisLevelOnlineTranscodingDetailNumotfwebmaborts ConfdString,
        affirmedServicesVideoAdaptationServiceStatisticsChassisLevelOnlineTranscodingDetailNumotfoverloads ConfdString,
        affirmedServicesVideoAdaptationServiceStatisticsChassisLevelOnlineTranscodingDetailNumotfpolicymapentrymatched ConfdString,
        affirmedServicesVideoAdaptationServiceStatisticsChassisLevelOnlineTranscodingDetailNumotfpolicymapentrynotmatched ConfdString,
        affirmedServicesVideoAdaptationServiceStatisticsChassisLevelOnlineTranscodingDetailNumotfpolicyqoeused ConfdString,
        affirmedServicesVideoAdaptationServiceStatisticsChassisLevelOnlineTranscodingDetailNumotfinstanceqoeused ConfdString,
        affirmedServicesVideoAdaptationServiceStatisticsChassisLevelOnlineTranscodingDetailNumotfflvbytesattempted ConfdString,
        affirmedServicesVideoAdaptationServiceStatisticsChassisLevelOnlineTranscodingDetailNumotfflvbytesadapted ConfdString,
        affirmedServicesVideoAdaptationServiceStatisticsChassisLevelOnlineTranscodingDetailNumotfflvbytescanceled ConfdString,
        affirmedServicesVideoAdaptationServiceStatisticsChassisLevelOnlineTranscodingDetailNumotfmp4bytesattempted ConfdString,
        affirmedServicesVideoAdaptationServiceStatisticsChassisLevelOnlineTranscodingDetailNumotfmp4bytesadapted ConfdString,
        affirmedServicesVideoAdaptationServiceStatisticsChassisLevelOnlineTranscodingDetailNumotfmp4bytescanceled ConfdString,
        affirmedServicesVideoAdaptationServiceStatisticsChassisLevelOnlineTranscodingDetailNumotfwebmbytesattempted ConfdString,
        affirmedServicesVideoAdaptationServiceStatisticsChassisLevelOnlineTranscodingDetailNumotfwebmbytesadapted ConfdString,
        affirmedServicesVideoAdaptationServiceStatisticsChassisLevelOnlineTranscodingDetailNumotfwebmbytescanceled ConfdString
    }

affirmedServicesVideoAdaptationServiceStatisticsChassisLevelOnlineTranscodingDetailChassis OBJECT-TYPE
    SYNTAX      Unsigned32
    MAX-ACCESS  not-accessible
    STATUS      current
    DESCRIPTION "chassis ID"
    ::= { affirmedServicesVideoAdaptationServiceStatisticsChassisLevelOnlineTranscodingDetailEntry 1 }

affirmedServicesVideoAdaptationServiceStatisticsChassisLevelOnlineTranscodingDetailNumotfflvattempts OBJECT-TYPE
    SYNTAX      ConfdString
    MAX-ACCESS  read-only
    STATUS      current
    DESCRIPTION "Total number of Online Transcoding FLV attempts"
    ::= { affirmedServicesVideoAdaptationServiceStatisticsChassisLevelOnlineTranscodingDetailEntry 2 }

affirmedServicesVideoAdaptationServiceStatisticsChassisLevelOnlineTranscodingDetailNumotfflvsuccesses OBJECT-TYPE
    SYNTAX      ConfdString
    MAX-ACCESS  read-only
    STATUS      current
    DESCRIPTION "Total number of Online Transcoding FLV successes"
    ::= { affirmedServicesVideoAdaptationServiceStatisticsChassisLevelOnlineTranscodingDetailEntry 3 }

affirmedServicesVideoAdaptationServiceStatisticsChassisLevelOnlineTranscodingDetailNumotfflvcancels OBJECT-TYPE
    SYNTAX      ConfdString
    MAX-ACCESS  read-only
    STATUS      current
    DESCRIPTION "Total number of Online Transcoding FLV cancels"
    ::= { affirmedServicesVideoAdaptationServiceStatisticsChassisLevelOnlineTranscodingDetailEntry 4 }

affirmedServicesVideoAdaptationServiceStatisticsChassisLevelOnlineTranscodingDetailNumotfflvfailures OBJECT-TYPE
    SYNTAX      ConfdString
    MAX-ACCESS  read-only
    STATUS      current
    DESCRIPTION "Total number of Online Transcoding FLV failures"
    ::= { affirmedServicesVideoAdaptationServiceStatisticsChassisLevelOnlineTranscodingDetailEntry 5 }

affirmedServicesVideoAdaptationServiceStatisticsChassisLevelOnlineTranscodingDetailNumotfflvaborts OBJECT-TYPE
    SYNTAX      ConfdString
    MAX-ACCESS  read-only
    STATUS      current
    DESCRIPTION "Total number of Online Transcoding FLV aborts"
    ::= { affirmedServicesVideoAdaptationServiceStatisticsChassisLevelOnlineTranscodingDetailEntry 6 }

affirmedServicesVideoAdaptationServiceStatisticsChassisLevelOnlineTranscodingDetailNumotfmp4attempts OBJECT-TYPE
    SYNTAX      ConfdString
    MAX-ACCESS  read-only
    STATUS      current
    DESCRIPTION "Total number of Online Transcoding MP4 attempts"
    ::= { affirmedServicesVideoAdaptationServiceStatisticsChassisLevelOnlineTranscodingDetailEntry 7 }

affirmedServicesVideoAdaptationServiceStatisticsChassisLevelOnlineTranscodingDetailNumotfmp4successes OBJECT-TYPE
    SYNTAX      ConfdString
    MAX-ACCESS  read-only
    STATUS      current
    DESCRIPTION "Total number of Online Transcoding MP4 successes"
    ::= { affirmedServicesVideoAdaptationServiceStatisticsChassisLevelOnlineTranscodingDetailEntry 8 }

affirmedServicesVideoAdaptationServiceStatisticsChassisLevelOnlineTranscodingDetailNumotfmp4cancels OBJECT-TYPE
    SYNTAX      ConfdString
    MAX-ACCESS  read-only
    STATUS      current
    DESCRIPTION "Total number of Online Transcoding MP4 cancels"
    ::= { affirmedServicesVideoAdaptationServiceStatisticsChassisLevelOnlineTranscodingDetailEntry 9 }

affirmedServicesVideoAdaptationServiceStatisticsChassisLevelOnlineTranscodingDetailNumotfmp4failures OBJECT-TYPE
    SYNTAX      ConfdString
    MAX-ACCESS  read-only
    STATUS      current
    DESCRIPTION "Total number of Online Transcoding MP4 failures"
    ::= { affirmedServicesVideoAdaptationServiceStatisticsChassisLevelOnlineTranscodingDetailEntry 10 }

affirmedServicesVideoAdaptationServiceStatisticsChassisLevelOnlineTranscodingDetailNumotfmp4aborts OBJECT-TYPE
    SYNTAX      ConfdString
    MAX-ACCESS  read-only
    STATUS      current
    DESCRIPTION "Total number of Online Transcoding MP4 aborts"
    ::= { affirmedServicesVideoAdaptationServiceStatisticsChassisLevelOnlineTranscodingDetailEntry 11 }

affirmedServicesVideoAdaptationServiceStatisticsChassisLevelOnlineTranscodingDetailNumotfwebmattempts OBJECT-TYPE
    SYNTAX      ConfdString
    MAX-ACCESS  read-only
    STATUS      current
    DESCRIPTION "Total number of Online Transcoding WEBM attempts"
    ::= { affirmedServicesVideoAdaptationServiceStatisticsChassisLevelOnlineTranscodingDetailEntry 12 }

affirmedServicesVideoAdaptationServiceStatisticsChassisLevelOnlineTranscodingDetailNumotfwebmsuccesses OBJECT-TYPE
    SYNTAX      ConfdString
    MAX-ACCESS  read-only
    STATUS      current
    DESCRIPTION "Total number of Online Transcoding WEBM successes"
    ::= { affirmedServicesVideoAdaptationServiceStatisticsChassisLevelOnlineTranscodingDetailEntry 13 }

affirmedServicesVideoAdaptationServiceStatisticsChassisLevelOnlineTranscodingDetailNumotfwebmcancels OBJECT-TYPE
    SYNTAX      ConfdString
    MAX-ACCESS  read-only
    STATUS      current
    DESCRIPTION "Total number of Online Transcoding WEBM cancels"
    ::= { affirmedServicesVideoAdaptationServiceStatisticsChassisLevelOnlineTranscodingDetailEntry 14 }

affirmedServicesVideoAdaptationServiceStatisticsChassisLevelOnlineTranscodingDetailNumotfwebmfailures OBJECT-TYPE
    SYNTAX      ConfdString
    MAX-ACCESS  read-only
    STATUS      current
    DESCRIPTION "Total number of Online Transcoding WEBM failures"
    ::= { affirmedServicesVideoAdaptationServiceStatisticsChassisLevelOnlineTranscodingDetailEntry 15 }

affirmedServicesVideoAdaptationServiceStatisticsChassisLevelOnlineTranscodingDetailNumotfwebmaborts OBJECT-TYPE
    SYNTAX      ConfdString
    MAX-ACCESS  read-only
    STATUS      current
    DESCRIPTION "Total number of Online Transcoding WEBM aborts"
    ::= { affirmedServicesVideoAdaptationServiceStatisticsChassisLevelOnlineTranscodingDetailEntry 16 }

affirmedServicesVideoAdaptationServiceStatisticsChassisLevelOnlineTranscodingDetailNumotfoverloads OBJECT-TYPE
    SYNTAX      ConfdString
    MAX-ACCESS  read-only
    STATUS      current
    DESCRIPTION "Total number of Online Transcoding overload"
    ::= { affirmedServicesVideoAdaptationServiceStatisticsChassisLevelOnlineTranscodingDetailEntry 17 }

affirmedServicesVideoAdaptationServiceStatisticsChassisLevelOnlineTranscodingDetailNumotfpolicymapentrymatched OBJECT-TYPE
    SYNTAX      ConfdString
    MAX-ACCESS  read-only
    STATUS      current
    DESCRIPTION "Total number of times an Online Transcoding Policy Map Entry was Matched"
    ::= { affirmedServicesVideoAdaptationServiceStatisticsChassisLevelOnlineTranscodingDetailEntry 18 }

affirmedServicesVideoAdaptationServiceStatisticsChassisLevelOnlineTranscodingDetailNumotfpolicymapentrynotmatched OBJECT-TYPE
    SYNTAX      ConfdString
    MAX-ACCESS  read-only
    STATUS      current
    DESCRIPTION "Total number of time any Online Transcoding Policy Map Entry was not matched"
    ::= { affirmedServicesVideoAdaptationServiceStatisticsChassisLevelOnlineTranscodingDetailEntry 19 }

affirmedServicesVideoAdaptationServiceStatisticsChassisLevelOnlineTranscodingDetailNumotfpolicyqoeused OBJECT-TYPE
    SYNTAX      ConfdString
    MAX-ACCESS  read-only
    STATUS      current
    DESCRIPTION "Total number of Online Transcoding Policy QOE grade used"
    ::= { affirmedServicesVideoAdaptationServiceStatisticsChassisLevelOnlineTranscodingDetailEntry 20 }

affirmedServicesVideoAdaptationServiceStatisticsChassisLevelOnlineTranscodingDetailNumotfinstanceqoeused OBJECT-TYPE
    SYNTAX      ConfdString
    MAX-ACCESS  read-only
    STATUS      current
    DESCRIPTION "Total number of Video adaptation instance QOE grade used"
    ::= { affirmedServicesVideoAdaptationServiceStatisticsChassisLevelOnlineTranscodingDetailEntry 21 }

affirmedServicesVideoAdaptationServiceStatisticsChassisLevelOnlineTranscodingDetailNumotfflvbytesattempted OBJECT-TYPE
    SYNTAX      ConfdString
    MAX-ACCESS  read-only
    STATUS      current
    DESCRIPTION "Total number of Online Transcoding FLV bytes attempted"
    ::= { affirmedServicesVideoAdaptationServiceStatisticsChassisLevelOnlineTranscodingDetailEntry 22 }

affirmedServicesVideoAdaptationServiceStatisticsChassisLevelOnlineTranscodingDetailNumotfflvbytesadapted OBJECT-TYPE
    SYNTAX      ConfdString
    MAX-ACCESS  read-only
    STATUS      current
    DESCRIPTION "Total number of Online Transcoding FLV bytes adapted"
    ::= { affirmedServicesVideoAdaptationServiceStatisticsChassisLevelOnlineTranscodingDetailEntry 23 }

affirmedServicesVideoAdaptationServiceStatisticsChassisLevelOnlineTranscodingDetailNumotfflvbytescanceled OBJECT-TYPE
    SYNTAX      ConfdString
    MAX-ACCESS  read-only
    STATUS      current
    DESCRIPTION "Total number of Online Transcoding FLV bytes canceled"
    ::= { affirmedServicesVideoAdaptationServiceStatisticsChassisLevelOnlineTranscodingDetailEntry 24 }

affirmedServicesVideoAdaptationServiceStatisticsChassisLevelOnlineTranscodingDetailNumotfmp4bytesattempted OBJECT-TYPE
    SYNTAX      ConfdString
    MAX-ACCESS  read-only
    STATUS      current
    DESCRIPTION "Total number of Online Transcoding MP4 bytes attempted"
    ::= { affirmedServicesVideoAdaptationServiceStatisticsChassisLevelOnlineTranscodingDetailEntry 25 }

affirmedServicesVideoAdaptationServiceStatisticsChassisLevelOnlineTranscodingDetailNumotfmp4bytesadapted OBJECT-TYPE
    SYNTAX      ConfdString
    MAX-ACCESS  read-only
    STATUS      current
    DESCRIPTION "Total number of Online Transcoding MP4 bytes adapted"
    ::= { affirmedServicesVideoAdaptationServiceStatisticsChassisLevelOnlineTranscodingDetailEntry 26 }

affirmedServicesVideoAdaptationServiceStatisticsChassisLevelOnlineTranscodingDetailNumotfmp4bytescanceled OBJECT-TYPE
    SYNTAX      ConfdString
    MAX-ACCESS  read-only
    STATUS      current
    DESCRIPTION "Total number of Online Transcoding MP4 bytes canceled"
    ::= { affirmedServicesVideoAdaptationServiceStatisticsChassisLevelOnlineTranscodingDetailEntry 27 }

affirmedServicesVideoAdaptationServiceStatisticsChassisLevelOnlineTranscodingDetailNumotfwebmbytesattempted OBJECT-TYPE
    SYNTAX      ConfdString
    MAX-ACCESS  read-only
    STATUS      current
    DESCRIPTION "Total number of Online Transcoding WEBM bytes attempted"
    ::= { affirmedServicesVideoAdaptationServiceStatisticsChassisLevelOnlineTranscodingDetailEntry 28 }

affirmedServicesVideoAdaptationServiceStatisticsChassisLevelOnlineTranscodingDetailNumotfwebmbytesadapted OBJECT-TYPE
    SYNTAX      ConfdString
    MAX-ACCESS  read-only
    STATUS      current
    DESCRIPTION "Total number of Online Transcoding WEBM bytes adapted"
    ::= { affirmedServicesVideoAdaptationServiceStatisticsChassisLevelOnlineTranscodingDetailEntry 29 }

affirmedServicesVideoAdaptationServiceStatisticsChassisLevelOnlineTranscodingDetailNumotfwebmbytescanceled OBJECT-TYPE
    SYNTAX      ConfdString
    MAX-ACCESS  read-only
    STATUS      current
    DESCRIPTION "Total number of Online Transcoding WEBM bytes canceled"
    ::= { affirmedServicesVideoAdaptationServiceStatisticsChassisLevelOnlineTranscodingDetailEntry 30 }

affirmedServicesVideoAdaptationServiceStatisticsChassisLevelOnlineTranscodingFailureTable OBJECT-TYPE
    SYNTAX      SEQUENCE OF AffirmedServicesVideoAdaptationServiceStatisticsChassisLevelOnlineTranscodingFailureEntry
    MAX-ACCESS  not-accessible
    STATUS      current
    DESCRIPTION ""
    ::= { affirmedServicesVideoAdaptationServiceStatisticsChassisLevelOnlineTranscoding 3 }

affirmedServicesVideoAdaptationServiceStatisticsChassisLevelOnlineTranscodingFailureEntry OBJECT-TYPE
    SYNTAX      AffirmedServicesVideoAdaptationServiceStatisticsChassisLevelOnlineTranscodingFailureEntry
    MAX-ACCESS  not-accessible
    STATUS      current
    DESCRIPTION ""
    INDEX { affirmedServicesVideoAdaptationServiceStatisticsChassisLevelOnlineTranscodingFailureChassis }
        ::= { affirmedServicesVideoAdaptationServiceStatisticsChassisLevelOnlineTranscodingFailureTable 1 }

AffirmedServicesVideoAdaptationServiceStatisticsChassisLevelOnlineTranscodingFailureEntry ::=
    SEQUENCE {
        affirmedServicesVideoAdaptationServiceStatisticsChassisLevelOnlineTranscodingFailureChassis Unsigned32,
        affirmedServicesVideoAdaptationServiceStatisticsChassisLevelOnlineTranscodingFailureNumotfexceededmaxvideosize ConfdString,
        affirmedServicesVideoAdaptationServiceStatisticsChassisLevelOnlineTranscodingFailureNumotfbelowminvideosize ConfdString,
        affirmedServicesVideoAdaptationServiceStatisticsChassisLevelOnlineTranscodingFailureNumotfexceededmaxvideoduration ConfdString,
        affirmedServicesVideoAdaptationServiceStatisticsChassisLevelOnlineTranscodingFailureNumotfbelowminvideoduration ConfdString,
        affirmedServicesVideoAdaptationServiceStatisticsChassisLevelOnlineTranscodingFailureNumotfexceededmaxbitrate ConfdString,
        affirmedServicesVideoAdaptationServiceStatisticsChassisLevelOnlineTranscodingFailureNumotfexceededmaxframerate ConfdString,
        affirmedServicesVideoAdaptationServiceStatisticsChassisLevelOnlineTranscodingFailureNumotfunsupportedsrccontainer ConfdString,
        affirmedServicesVideoAdaptationServiceStatisticsChassisLevelOnlineTranscodingFailureNumotfunsupportedformat ConfdString,
        affirmedServicesVideoAdaptationServiceStatisticsChassisLevelOnlineTranscodingFailureNumotfunsupportedvideocodec ConfdString,
        affirmedServicesVideoAdaptationServiceStatisticsChassisLevelOnlineTranscodingFailureNumotfunsupportedaudiocodec ConfdString,
        affirmedServicesVideoAdaptationServiceStatisticsChassisLevelOnlineTranscodingFailureNumotffailureothers ConfdString,
        affirmedServicesVideoAdaptationServiceStatisticsChassisLevelOnlineTranscodingFailureNumotfcancelcontenttypemismatches ConfdString,
        affirmedServicesVideoAdaptationServiceStatisticsChassisLevelOnlineTranscodingFailureNumotfcancelnomapqoematch ConfdString,
        affirmedServicesVideoAdaptationServiceStatisticsChassisLevelOnlineTranscodingFailureNumotfcancelmapentrybypass ConfdString,
        affirmedServicesVideoAdaptationServiceStatisticsChassisLevelOnlineTranscodingFailureNumotfcancelcpuoverload ConfdString,
        affirmedServicesVideoAdaptationServiceStatisticsChassisLevelOnlineTranscodingFailureNumotfnosrcaudiostreampresent ConfdString,
        affirmedServicesVideoAdaptationServiceStatisticsChassisLevelOnlineTranscodingFailureNumotfnosrcvideostreampresent ConfdString,
        affirmedServicesVideoAdaptationServiceStatisticsChassisLevelOnlineTranscodingFailureNumotfunsupportedsrcaudiocodec ConfdString,
        affirmedServicesVideoAdaptationServiceStatisticsChassisLevelOnlineTranscodingFailureNumotfunsupportedsrcvideocodec ConfdString,
        affirmedServicesVideoAdaptationServiceStatisticsChassisLevelOnlineTranscodingFailureNumotfbelowbitratesavingsthreshold ConfdString,
        affirmedServicesVideoAdaptationServiceStatisticsChassisLevelOnlineTranscodingFailureNumotfsrcmediaformatnotsupported ConfdString,
        affirmedServicesVideoAdaptationServiceStatisticsChassisLevelOnlineTranscodingFailureNumotftgtmediaformatnotsupported ConfdString,
        affirmedServicesVideoAdaptationServiceStatisticsChassisLevelOnlineTranscodingFailureNumotftgtmediaformatparametersnotvalid ConfdString,
        affirmedServicesVideoAdaptationServiceStatisticsChassisLevelOnlineTranscodingFailureNumotftgtxcodingparametersnotvalid ConfdString,
        affirmedServicesVideoAdaptationServiceStatisticsChassisLevelOnlineTranscodingFailureNumotfcancelnomatchmapqoe ConfdString,
        affirmedServicesVideoAdaptationServiceStatisticsChassisLevelOnlineTranscodingFailureNumotfcancelsrcmediaisnotstreamable ConfdString,
        affirmedServicesVideoAdaptationServiceStatisticsChassisLevelOnlineTranscodingFailureNumotffailuredelayresponding ConfdString,
        affirmedServicesVideoAdaptationServiceStatisticsChassisLevelOnlineTranscodingFailureNumotfcouldnotfindsrcmediastream ConfdString,
        affirmedServicesVideoAdaptationServiceStatisticsChassisLevelOnlineTranscodingFailureNumotfcancelothers ConfdString,
        affirmedServicesVideoAdaptationServiceStatisticsChassisLevelOnlineTranscodingFailureNumotfbypassoptout ConfdString
    }

affirmedServicesVideoAdaptationServiceStatisticsChassisLevelOnlineTranscodingFailureChassis OBJECT-TYPE
    SYNTAX      Unsigned32
    MAX-ACCESS  not-accessible
    STATUS      current
    DESCRIPTION "chassis ID"
    ::= { affirmedServicesVideoAdaptationServiceStatisticsChassisLevelOnlineTranscodingFailureEntry 1 }

affirmedServicesVideoAdaptationServiceStatisticsChassisLevelOnlineTranscodingFailureNumotfexceededmaxvideosize OBJECT-TYPE
    SYNTAX      ConfdString
    MAX-ACCESS  read-only
    STATUS      current
    DESCRIPTION "Total number of Online Transcoding exceeded max video size "
    ::= { affirmedServicesVideoAdaptationServiceStatisticsChassisLevelOnlineTranscodingFailureEntry 2 }

affirmedServicesVideoAdaptationServiceStatisticsChassisLevelOnlineTranscodingFailureNumotfbelowminvideosize OBJECT-TYPE
    SYNTAX      ConfdString
    MAX-ACCESS  read-only
    STATUS      current
    DESCRIPTION "Total number of Online Transcoding below min video size"
    ::= { affirmedServicesVideoAdaptationServiceStatisticsChassisLevelOnlineTranscodingFailureEntry 3 }

affirmedServicesVideoAdaptationServiceStatisticsChassisLevelOnlineTranscodingFailureNumotfexceededmaxvideoduration OBJECT-TYPE
    SYNTAX      ConfdString
    MAX-ACCESS  read-only
    STATUS      current
    DESCRIPTION "Total number of Online Transcoding exceeded max video duration "
    ::= { affirmedServicesVideoAdaptationServiceStatisticsChassisLevelOnlineTranscodingFailureEntry 4 }

affirmedServicesVideoAdaptationServiceStatisticsChassisLevelOnlineTranscodingFailureNumotfbelowminvideoduration OBJECT-TYPE
    SYNTAX      ConfdString
    MAX-ACCESS  read-only
    STATUS      current
    DESCRIPTION "Total number of Online Transcoding below min video duration"
    ::= { affirmedServicesVideoAdaptationServiceStatisticsChassisLevelOnlineTranscodingFailureEntry 5 }

affirmedServicesVideoAdaptationServiceStatisticsChassisLevelOnlineTranscodingFailureNumotfexceededmaxbitrate OBJECT-TYPE
    SYNTAX      ConfdString
    MAX-ACCESS  read-only
    STATUS      current
    DESCRIPTION "Total number of Online Transcoding exceeded max video bitrate "
    ::= { affirmedServicesVideoAdaptationServiceStatisticsChassisLevelOnlineTranscodingFailureEntry 6 }

affirmedServicesVideoAdaptationServiceStatisticsChassisLevelOnlineTranscodingFailureNumotfexceededmaxframerate OBJECT-TYPE
    SYNTAX      ConfdString
    MAX-ACCESS  read-only
    STATUS      current
    DESCRIPTION "Total number of Online Transcoding exceeded max video framerate"
    ::= { affirmedServicesVideoAdaptationServiceStatisticsChassisLevelOnlineTranscodingFailureEntry 7 }

affirmedServicesVideoAdaptationServiceStatisticsChassisLevelOnlineTranscodingFailureNumotfunsupportedsrccontainer OBJECT-TYPE
    SYNTAX      ConfdString
    MAX-ACCESS  read-only
    STATUS      current
    DESCRIPTION "Total number of Online Transcoding Unsupported Source Container"
    ::= { affirmedServicesVideoAdaptationServiceStatisticsChassisLevelOnlineTranscodingFailureEntry 8 }

affirmedServicesVideoAdaptationServiceStatisticsChassisLevelOnlineTranscodingFailureNumotfunsupportedformat OBJECT-TYPE
    SYNTAX      ConfdString
    MAX-ACCESS  read-only
    STATUS      current
    DESCRIPTION "Total number of Online Transcoding Unsupported Format"
    ::= { affirmedServicesVideoAdaptationServiceStatisticsChassisLevelOnlineTranscodingFailureEntry 9 }

affirmedServicesVideoAdaptationServiceStatisticsChassisLevelOnlineTranscodingFailureNumotfunsupportedvideocodec OBJECT-TYPE
    SYNTAX      ConfdString
    MAX-ACCESS  read-only
    STATUS      current
    DESCRIPTION "Total number of Online Transcoding Unsupported Video Codec"
    ::= { affirmedServicesVideoAdaptationServiceStatisticsChassisLevelOnlineTranscodingFailureEntry 10 }

affirmedServicesVideoAdaptationServiceStatisticsChassisLevelOnlineTranscodingFailureNumotfunsupportedaudiocodec OBJECT-TYPE
    SYNTAX      ConfdString
    MAX-ACCESS  read-only
    STATUS      current
    DESCRIPTION "Total number of Online Transcoding Unsupported Audio Codec"
    ::= { affirmedServicesVideoAdaptationServiceStatisticsChassisLevelOnlineTranscodingFailureEntry 11 }

affirmedServicesVideoAdaptationServiceStatisticsChassisLevelOnlineTranscodingFailureNumotffailureothers OBJECT-TYPE
    SYNTAX      ConfdString
    MAX-ACCESS  read-only
    STATUS      current
    DESCRIPTION "Total number of Online Transcoding Failure With Other Reason"
    ::= { affirmedServicesVideoAdaptationServiceStatisticsChassisLevelOnlineTranscodingFailureEntry 12 }

affirmedServicesVideoAdaptationServiceStatisticsChassisLevelOnlineTranscodingFailureNumotfcancelcontenttypemismatches OBJECT-TYPE
    SYNTAX      ConfdString
    MAX-ACCESS  read-only
    STATUS      current
    DESCRIPTION "Total number of Online Transcoding Cancel Content-Type Mismatches"
    ::= { affirmedServicesVideoAdaptationServiceStatisticsChassisLevelOnlineTranscodingFailureEntry 13 }

affirmedServicesVideoAdaptationServiceStatisticsChassisLevelOnlineTranscodingFailureNumotfcancelnomapqoematch OBJECT-TYPE
    SYNTAX      ConfdString
    MAX-ACCESS  read-only
    STATUS      current
    DESCRIPTION "Total number of Online Transcoding Cancels due to no transcoding map or QOE grade"
    ::= { affirmedServicesVideoAdaptationServiceStatisticsChassisLevelOnlineTranscodingFailureEntry 14 }

affirmedServicesVideoAdaptationServiceStatisticsChassisLevelOnlineTranscodingFailureNumotfcancelmapentrybypass OBJECT-TYPE
    SYNTAX      ConfdString
    MAX-ACCESS  read-only
    STATUS      current
    DESCRIPTION "Total number of Online Transcoding Cancels due to Bypass set in the transcoding map entry"
    ::= { affirmedServicesVideoAdaptationServiceStatisticsChassisLevelOnlineTranscodingFailureEntry 15 }

affirmedServicesVideoAdaptationServiceStatisticsChassisLevelOnlineTranscodingFailureNumotfcancelcpuoverload OBJECT-TYPE
    SYNTAX      ConfdString
    MAX-ACCESS  read-only
    STATUS      current
    DESCRIPTION "Total number of Online Transcoding Cancel CPU Overload"
    ::= { affirmedServicesVideoAdaptationServiceStatisticsChassisLevelOnlineTranscodingFailureEntry 16 }

affirmedServicesVideoAdaptationServiceStatisticsChassisLevelOnlineTranscodingFailureNumotfnosrcaudiostreampresent OBJECT-TYPE
    SYNTAX      ConfdString
    MAX-ACCESS  read-only
    STATUS      current
    DESCRIPTION "Total number of Online Transcoding No Src Audio Stream Present"
    ::= { affirmedServicesVideoAdaptationServiceStatisticsChassisLevelOnlineTranscodingFailureEntry 17 }

affirmedServicesVideoAdaptationServiceStatisticsChassisLevelOnlineTranscodingFailureNumotfnosrcvideostreampresent OBJECT-TYPE
    SYNTAX      ConfdString
    MAX-ACCESS  read-only
    STATUS      current
    DESCRIPTION "Total number of Online Transcoding No Src Video Stream Present"
    ::= { affirmedServicesVideoAdaptationServiceStatisticsChassisLevelOnlineTranscodingFailureEntry 18 }

affirmedServicesVideoAdaptationServiceStatisticsChassisLevelOnlineTranscodingFailureNumotfunsupportedsrcaudiocodec OBJECT-TYPE
    SYNTAX      ConfdString
    MAX-ACCESS  read-only
    STATUS      current
    DESCRIPTION "Total number of Online Transcoding Unsupported Src Audio Codec"
    ::= { affirmedServicesVideoAdaptationServiceStatisticsChassisLevelOnlineTranscodingFailureEntry 19 }

affirmedServicesVideoAdaptationServiceStatisticsChassisLevelOnlineTranscodingFailureNumotfunsupportedsrcvideocodec OBJECT-TYPE
    SYNTAX      ConfdString
    MAX-ACCESS  read-only
    STATUS      current
    DESCRIPTION "Total number of Online Transcoding Unsupported Src Video Codec"
    ::= { affirmedServicesVideoAdaptationServiceStatisticsChassisLevelOnlineTranscodingFailureEntry 20 }

affirmedServicesVideoAdaptationServiceStatisticsChassisLevelOnlineTranscodingFailureNumotfbelowbitratesavingsthreshold OBJECT-TYPE
    SYNTAX      ConfdString
    MAX-ACCESS  read-only
    STATUS      current
    DESCRIPTION "Total number of Online Transcoding Below Bit Rate Savings Threshold"
    ::= { affirmedServicesVideoAdaptationServiceStatisticsChassisLevelOnlineTranscodingFailureEntry 21 }

affirmedServicesVideoAdaptationServiceStatisticsChassisLevelOnlineTranscodingFailureNumotfsrcmediaformatnotsupported OBJECT-TYPE
    SYNTAX      ConfdString
    MAX-ACCESS  read-only
    STATUS      current
    DESCRIPTION "Total number of Online Transcoding Src Media Format Not Supported"
    ::= { affirmedServicesVideoAdaptationServiceStatisticsChassisLevelOnlineTranscodingFailureEntry 22 }

affirmedServicesVideoAdaptationServiceStatisticsChassisLevelOnlineTranscodingFailureNumotftgtmediaformatnotsupported OBJECT-TYPE
    SYNTAX      ConfdString
    MAX-ACCESS  read-only
    STATUS      current
    DESCRIPTION "Total number of Online Transcoding Tgt Media Format Not Supported"
    ::= { affirmedServicesVideoAdaptationServiceStatisticsChassisLevelOnlineTranscodingFailureEntry 23 }

affirmedServicesVideoAdaptationServiceStatisticsChassisLevelOnlineTranscodingFailureNumotftgtmediaformatparametersnotvalid OBJECT-TYPE
    SYNTAX      ConfdString
    MAX-ACCESS  read-only
    STATUS      current
    DESCRIPTION "Total number of Online Transcoding Tgt Media Format Parameters Not Valid"
    ::= { affirmedServicesVideoAdaptationServiceStatisticsChassisLevelOnlineTranscodingFailureEntry 24 }

affirmedServicesVideoAdaptationServiceStatisticsChassisLevelOnlineTranscodingFailureNumotftgtxcodingparametersnotvalid OBJECT-TYPE
    SYNTAX      ConfdString
    MAX-ACCESS  read-only
    STATUS      current
    DESCRIPTION "Total number of Online Transcoding Target Transcoding Paramaters Not Valid"
    ::= { affirmedServicesVideoAdaptationServiceStatisticsChassisLevelOnlineTranscodingFailureEntry 25 }

affirmedServicesVideoAdaptationServiceStatisticsChassisLevelOnlineTranscodingFailureNumotfcancelnomatchmapqoe OBJECT-TYPE
    SYNTAX      ConfdString
    MAX-ACCESS  read-only
    STATUS      current
    DESCRIPTION "Total number of Online Transcoding Cancels due to no matching transcoding map entry or QOE grade"
    ::= { affirmedServicesVideoAdaptationServiceStatisticsChassisLevelOnlineTranscodingFailureEntry 26 }

affirmedServicesVideoAdaptationServiceStatisticsChassisLevelOnlineTranscodingFailureNumotfcancelsrcmediaisnotstreamable OBJECT-TYPE
    SYNTAX      ConfdString
    MAX-ACCESS  read-only
    STATUS      current
    DESCRIPTION "Total number of Online Transcoding Cancels due to source media is not streamable"
    ::= { affirmedServicesVideoAdaptationServiceStatisticsChassisLevelOnlineTranscodingFailureEntry 27 }

affirmedServicesVideoAdaptationServiceStatisticsChassisLevelOnlineTranscodingFailureNumotffailuredelayresponding OBJECT-TYPE
    SYNTAX      ConfdString
    MAX-ACCESS  read-only
    STATUS      current
    DESCRIPTION "Total number of Online Transcoding Failure due to Delay in Responding"
    ::= { affirmedServicesVideoAdaptationServiceStatisticsChassisLevelOnlineTranscodingFailureEntry 28 }

affirmedServicesVideoAdaptationServiceStatisticsChassisLevelOnlineTranscodingFailureNumotfcouldnotfindsrcmediastream OBJECT-TYPE
    SYNTAX      ConfdString
    MAX-ACCESS  read-only
    STATUS      current
    DESCRIPTION "Total number of Online Transcoding Cancel due to Could not Find/Determine Source Media Stream Info"
    ::= { affirmedServicesVideoAdaptationServiceStatisticsChassisLevelOnlineTranscodingFailureEntry 29 }

affirmedServicesVideoAdaptationServiceStatisticsChassisLevelOnlineTranscodingFailureNumotfcancelothers OBJECT-TYPE
    SYNTAX      ConfdString
    MAX-ACCESS  read-only
    STATUS      current
    DESCRIPTION "Total number of Online Transcoding Cancel With Other Reason"
    ::= { affirmedServicesVideoAdaptationServiceStatisticsChassisLevelOnlineTranscodingFailureEntry 30 }

affirmedServicesVideoAdaptationServiceStatisticsChassisLevelOnlineTranscodingFailureNumotfbypassoptout OBJECT-TYPE
    SYNTAX      ConfdString
    MAX-ACCESS  read-only
    STATUS      current
    DESCRIPTION "Total number of Online Transcoding Bypassed due to subscriber opting-out"
    ::= { affirmedServicesVideoAdaptationServiceStatisticsChassisLevelOnlineTranscodingFailureEntry 31 }

affirmedServicesVideoAdaptationServiceStatisticsChassisLevelOnlineTranscodingOrtDetailTable OBJECT-TYPE
    SYNTAX      SEQUENCE OF AffirmedServicesVideoAdaptationServiceStatisticsChassisLevelOnlineTranscodingOrtDetailEntry
    MAX-ACCESS  not-accessible
    STATUS      current
    DESCRIPTION ""
    ::= { affirmedServicesVideoAdaptationServiceStatisticsChassisLevelOnlineTranscoding 4 }

affirmedServicesVideoAdaptationServiceStatisticsChassisLevelOnlineTranscodingOrtDetailEntry OBJECT-TYPE
    SYNTAX      AffirmedServicesVideoAdaptationServiceStatisticsChassisLevelOnlineTranscodingOrtDetailEntry
    MAX-ACCESS  not-accessible
    STATUS      current
    DESCRIPTION ""
    INDEX { affirmedServicesVideoAdaptationServiceStatisticsChassisLevelOnlineTranscodingOrtDetailChassis }
        ::= { affirmedServicesVideoAdaptationServiceStatisticsChassisLevelOnlineTranscodingOrtDetailTable 1 }

AffirmedServicesVideoAdaptationServiceStatisticsChassisLevelOnlineTranscodingOrtDetailEntry ::=
    SEQUENCE {
        affirmedServicesVideoAdaptationServiceStatisticsChassisLevelOnlineTranscodingOrtDetailChassis Unsigned32,
        affirmedServicesVideoAdaptationServiceStatisticsChassisLevelOnlineTranscodingOrtDetailNumortsessionattempts ConfdString,
        affirmedServicesVideoAdaptationServiceStatisticsChassisLevelOnlineTranscodingOrtDetailNumortsessionsuccesses ConfdString,
        affirmedServicesVideoAdaptationServiceStatisticsChassisLevelOnlineTranscodingOrtDetailNumortsessioncancels ConfdString,
        affirmedServicesVideoAdaptationServiceStatisticsChassisLevelOnlineTranscodingOrtDetailNumortsessionfailures ConfdString,
        affirmedServicesVideoAdaptationServiceStatisticsChassisLevelOnlineTranscodingOrtDetailNumortsessionaborts ConfdString,
        affirmedServicesVideoAdaptationServiceStatisticsChassisLevelOnlineTranscodingOrtDetailNumortsessionoverloads ConfdString,
        affirmedServicesVideoAdaptationServiceStatisticsChassisLevelOnlineTranscodingOrtDetailNumortsessioncurrent ConfdString,
        affirmedServicesVideoAdaptationServiceStatisticsChassisLevelOnlineTranscodingOrtDetailNumortsessionduration ConfdString,
        affirmedServicesVideoAdaptationServiceStatisticsChassisLevelOnlineTranscodingOrtDetailNumortsessionbytesattempt ConfdString,
        affirmedServicesVideoAdaptationServiceStatisticsChassisLevelOnlineTranscodingOrtDetailNumortsessionbytesadapted ConfdString,
        affirmedServicesVideoAdaptationServiceStatisticsChassisLevelOnlineTranscodingOrtDetailNumortsessionbytescancel ConfdString,
        affirmedServicesVideoAdaptationServiceStatisticsChassisLevelOnlineTranscodingOrtDetailNumortsegmentsattempts ConfdString,
        affirmedServicesVideoAdaptationServiceStatisticsChassisLevelOnlineTranscodingOrtDetailNumortsegmentssuccesses ConfdString,
        affirmedServicesVideoAdaptationServiceStatisticsChassisLevelOnlineTranscodingOrtDetailNumortsegmentscancels ConfdString,
        affirmedServicesVideoAdaptationServiceStatisticsChassisLevelOnlineTranscodingOrtDetailNumortsegmentsfailures ConfdString,
        affirmedServicesVideoAdaptationServiceStatisticsChassisLevelOnlineTranscodingOrtDetailNumortsegmentsaborts ConfdString,
        affirmedServicesVideoAdaptationServiceStatisticsChassisLevelOnlineTranscodingOrtDetailNumortsegmentsoverloads ConfdString,
        affirmedServicesVideoAdaptationServiceStatisticsChassisLevelOnlineTranscodingOrtDetailNumortsegmentscurrent ConfdString,
        affirmedServicesVideoAdaptationServiceStatisticsChassisLevelOnlineTranscodingOrtDetailNumortsegmentsduration ConfdString,
        affirmedServicesVideoAdaptationServiceStatisticsChassisLevelOnlineTranscodingOrtDetailNumortsegmentsbytesattempt ConfdString,
        affirmedServicesVideoAdaptationServiceStatisticsChassisLevelOnlineTranscodingOrtDetailNumortsegmentsbytesadapted ConfdString,
        affirmedServicesVideoAdaptationServiceStatisticsChassisLevelOnlineTranscodingOrtDetailNumortsegmentsbytescancel ConfdString
    }

affirmedServicesVideoAdaptationServiceStatisticsChassisLevelOnlineTranscodingOrtDetailChassis OBJECT-TYPE
    SYNTAX      Unsigned32
    MAX-ACCESS  not-accessible
    STATUS      current
    DESCRIPTION "chassis ID"
    ::= { affirmedServicesVideoAdaptationServiceStatisticsChassisLevelOnlineTranscodingOrtDetailEntry 1 }

affirmedServicesVideoAdaptationServiceStatisticsChassisLevelOnlineTranscodingOrtDetailNumortsessionattempts OBJECT-TYPE
    SYNTAX      ConfdString
    MAX-ACCESS  read-only
    STATUS      current
    DESCRIPTION "Total number of Online Range Transcoding Session attempts"
    ::= { affirmedServicesVideoAdaptationServiceStatisticsChassisLevelOnlineTranscodingOrtDetailEntry 2 }

affirmedServicesVideoAdaptationServiceStatisticsChassisLevelOnlineTranscodingOrtDetailNumortsessionsuccesses OBJECT-TYPE
    SYNTAX      ConfdString
    MAX-ACCESS  read-only
    STATUS      current
    DESCRIPTION "Total number of Online Range Transcoding Session successes"
    ::= { affirmedServicesVideoAdaptationServiceStatisticsChassisLevelOnlineTranscodingOrtDetailEntry 3 }

affirmedServicesVideoAdaptationServiceStatisticsChassisLevelOnlineTranscodingOrtDetailNumortsessioncancels OBJECT-TYPE
    SYNTAX      ConfdString
    MAX-ACCESS  read-only
    STATUS      current
    DESCRIPTION "Total number of Online Range Transcoding Session cancels"
    ::= { affirmedServicesVideoAdaptationServiceStatisticsChassisLevelOnlineTranscodingOrtDetailEntry 4 }

affirmedServicesVideoAdaptationServiceStatisticsChassisLevelOnlineTranscodingOrtDetailNumortsessionfailures OBJECT-TYPE
    SYNTAX      ConfdString
    MAX-ACCESS  read-only
    STATUS      current
    DESCRIPTION "Total number of Online Range Transcoding Session failures"
    ::= { affirmedServicesVideoAdaptationServiceStatisticsChassisLevelOnlineTranscodingOrtDetailEntry 5 }

affirmedServicesVideoAdaptationServiceStatisticsChassisLevelOnlineTranscodingOrtDetailNumortsessionaborts OBJECT-TYPE
    SYNTAX      ConfdString
    MAX-ACCESS  read-only
    STATUS      current
    DESCRIPTION "Total number of Online Range Transcoding Session aborts"
    ::= { affirmedServicesVideoAdaptationServiceStatisticsChassisLevelOnlineTranscodingOrtDetailEntry 6 }

affirmedServicesVideoAdaptationServiceStatisticsChassisLevelOnlineTranscodingOrtDetailNumortsessionoverloads OBJECT-TYPE
    SYNTAX      ConfdString
    MAX-ACCESS  read-only
    STATUS      current
    DESCRIPTION "Total number of Online Range Transcoding Session Overloads"
    ::= { affirmedServicesVideoAdaptationServiceStatisticsChassisLevelOnlineTranscodingOrtDetailEntry 7 }

affirmedServicesVideoAdaptationServiceStatisticsChassisLevelOnlineTranscodingOrtDetailNumortsessioncurrent OBJECT-TYPE
    SYNTAX      ConfdString
    MAX-ACCESS  read-only
    STATUS      current
    DESCRIPTION "Total number of Online Range Transcoding Session current"
    ::= { affirmedServicesVideoAdaptationServiceStatisticsChassisLevelOnlineTranscodingOrtDetailEntry 8 }

affirmedServicesVideoAdaptationServiceStatisticsChassisLevelOnlineTranscodingOrtDetailNumortsessionduration OBJECT-TYPE
    SYNTAX      ConfdString
    MAX-ACCESS  read-only
    STATUS      current
    DESCRIPTION "Total range transcoded video duration in seconds"
    ::= { affirmedServicesVideoAdaptationServiceStatisticsChassisLevelOnlineTranscodingOrtDetailEntry 9 }

affirmedServicesVideoAdaptationServiceStatisticsChassisLevelOnlineTranscodingOrtDetailNumortsessionbytesattempt OBJECT-TYPE
    SYNTAX      ConfdString
    MAX-ACCESS  read-only
    STATUS      current
    DESCRIPTION "Total number of Online Range Transcoding Session Bytes Attempted (Bytes)"
    ::= { affirmedServicesVideoAdaptationServiceStatisticsChassisLevelOnlineTranscodingOrtDetailEntry 10 }

affirmedServicesVideoAdaptationServiceStatisticsChassisLevelOnlineTranscodingOrtDetailNumortsessionbytesadapted OBJECT-TYPE
    SYNTAX      ConfdString
    MAX-ACCESS  read-only
    STATUS      current
    DESCRIPTION "Total number of Online Range Transcoding Session Bytes Adapted (Bytes)"
    ::= { affirmedServicesVideoAdaptationServiceStatisticsChassisLevelOnlineTranscodingOrtDetailEntry 11 }

affirmedServicesVideoAdaptationServiceStatisticsChassisLevelOnlineTranscodingOrtDetailNumortsessionbytescancel OBJECT-TYPE
    SYNTAX      ConfdString
    MAX-ACCESS  read-only
    STATUS      current
    DESCRIPTION "Total number of Online Range Transcoding Session Bytes Cancelled (Bytes)"
    ::= { affirmedServicesVideoAdaptationServiceStatisticsChassisLevelOnlineTranscodingOrtDetailEntry 12 }

affirmedServicesVideoAdaptationServiceStatisticsChassisLevelOnlineTranscodingOrtDetailNumortsegmentsattempts OBJECT-TYPE
    SYNTAX      ConfdString
    MAX-ACCESS  read-only
    STATUS      current
    DESCRIPTION "Total number of Online Range Transcoding Segments attempts"
    ::= { affirmedServicesVideoAdaptationServiceStatisticsChassisLevelOnlineTranscodingOrtDetailEntry 13 }

affirmedServicesVideoAdaptationServiceStatisticsChassisLevelOnlineTranscodingOrtDetailNumortsegmentssuccesses OBJECT-TYPE
    SYNTAX      ConfdString
    MAX-ACCESS  read-only
    STATUS      current
    DESCRIPTION "Total number of Online Range Transcoding Segments successes"
    ::= { affirmedServicesVideoAdaptationServiceStatisticsChassisLevelOnlineTranscodingOrtDetailEntry 14 }

affirmedServicesVideoAdaptationServiceStatisticsChassisLevelOnlineTranscodingOrtDetailNumortsegmentscancels OBJECT-TYPE
    SYNTAX      ConfdString
    MAX-ACCESS  read-only
    STATUS      current
    DESCRIPTION "Total number of Online Range Transcoding Segments cancels"
    ::= { affirmedServicesVideoAdaptationServiceStatisticsChassisLevelOnlineTranscodingOrtDetailEntry 15 }

affirmedServicesVideoAdaptationServiceStatisticsChassisLevelOnlineTranscodingOrtDetailNumortsegmentsfailures OBJECT-TYPE
    SYNTAX      ConfdString
    MAX-ACCESS  read-only
    STATUS      current
    DESCRIPTION "Total number of Online Range Transcoding Segments failures"
    ::= { affirmedServicesVideoAdaptationServiceStatisticsChassisLevelOnlineTranscodingOrtDetailEntry 16 }

affirmedServicesVideoAdaptationServiceStatisticsChassisLevelOnlineTranscodingOrtDetailNumortsegmentsaborts OBJECT-TYPE
    SYNTAX      ConfdString
    MAX-ACCESS  read-only
    STATUS      current
    DESCRIPTION "Total number of Online Range Transcoding Segments aborts"
    ::= { affirmedServicesVideoAdaptationServiceStatisticsChassisLevelOnlineTranscodingOrtDetailEntry 17 }

affirmedServicesVideoAdaptationServiceStatisticsChassisLevelOnlineTranscodingOrtDetailNumortsegmentsoverloads OBJECT-TYPE
    SYNTAX      ConfdString
    MAX-ACCESS  read-only
    STATUS      current
    DESCRIPTION "Total number of Online Range Transcoding Segments Overloads"
    ::= { affirmedServicesVideoAdaptationServiceStatisticsChassisLevelOnlineTranscodingOrtDetailEntry 18 }

affirmedServicesVideoAdaptationServiceStatisticsChassisLevelOnlineTranscodingOrtDetailNumortsegmentscurrent OBJECT-TYPE
    SYNTAX      ConfdString
    MAX-ACCESS  read-only
    STATUS      current
    DESCRIPTION "Total number of Online Range Transcoding Segments current"
    ::= { affirmedServicesVideoAdaptationServiceStatisticsChassisLevelOnlineTranscodingOrtDetailEntry 19 }

affirmedServicesVideoAdaptationServiceStatisticsChassisLevelOnlineTranscodingOrtDetailNumortsegmentsduration OBJECT-TYPE
    SYNTAX      ConfdString
    MAX-ACCESS  read-only
    STATUS      current
    DESCRIPTION "Total range transcoded video duration in seconds"
    ::= { affirmedServicesVideoAdaptationServiceStatisticsChassisLevelOnlineTranscodingOrtDetailEntry 20 }

affirmedServicesVideoAdaptationServiceStatisticsChassisLevelOnlineTranscodingOrtDetailNumortsegmentsbytesattempt OBJECT-TYPE
    SYNTAX      ConfdString
    MAX-ACCESS  read-only
    STATUS      current
    DESCRIPTION "Total number of Online Range Transcoding Segments Bytes Attempted (Bytes)"
    ::= { affirmedServicesVideoAdaptationServiceStatisticsChassisLevelOnlineTranscodingOrtDetailEntry 21 }

affirmedServicesVideoAdaptationServiceStatisticsChassisLevelOnlineTranscodingOrtDetailNumortsegmentsbytesadapted OBJECT-TYPE
    SYNTAX      ConfdString
    MAX-ACCESS  read-only
    STATUS      current
    DESCRIPTION "Total number of Online Range Transcoding Segments Bytes Adapted (Bytes)"
    ::= { affirmedServicesVideoAdaptationServiceStatisticsChassisLevelOnlineTranscodingOrtDetailEntry 22 }

affirmedServicesVideoAdaptationServiceStatisticsChassisLevelOnlineTranscodingOrtDetailNumortsegmentsbytescancel OBJECT-TYPE
    SYNTAX      ConfdString
    MAX-ACCESS  read-only
    STATUS      current
    DESCRIPTION "Total number of Online Range Transcoding Segments Bytes Cancelled (Bytes)"
    ::= { affirmedServicesVideoAdaptationServiceStatisticsChassisLevelOnlineTranscodingOrtDetailEntry 23 }

affirmedServicesVideoAdaptationServiceStatisticsChassisLevelOnlineTranscodingOrtFailureTable OBJECT-TYPE
    SYNTAX      SEQUENCE OF AffirmedServicesVideoAdaptationServiceStatisticsChassisLevelOnlineTranscodingOrtFailureEntry
    MAX-ACCESS  not-accessible
    STATUS      current
    DESCRIPTION ""
    ::= { affirmedServicesVideoAdaptationServiceStatisticsChassisLevelOnlineTranscoding 5 }

affirmedServicesVideoAdaptationServiceStatisticsChassisLevelOnlineTranscodingOrtFailureEntry OBJECT-TYPE
    SYNTAX      AffirmedServicesVideoAdaptationServiceStatisticsChassisLevelOnlineTranscodingOrtFailureEntry
    MAX-ACCESS  not-accessible
    STATUS      current
    DESCRIPTION ""
    INDEX { affirmedServicesVideoAdaptationServiceStatisticsChassisLevelOnlineTranscodingOrtFailureChassis }
        ::= { affirmedServicesVideoAdaptationServiceStatisticsChassisLevelOnlineTranscodingOrtFailureTable 1 }

AffirmedServicesVideoAdaptationServiceStatisticsChassisLevelOnlineTranscodingOrtFailureEntry ::=
    SEQUENCE {
        affirmedServicesVideoAdaptationServiceStatisticsChassisLevelOnlineTranscodingOrtFailureChassis Unsigned32,
        affirmedServicesVideoAdaptationServiceStatisticsChassisLevelOnlineTranscodingOrtFailureNumortexceededmaxvideosize ConfdString,
        affirmedServicesVideoAdaptationServiceStatisticsChassisLevelOnlineTranscodingOrtFailureNumortbelowminvideosize ConfdString,
        affirmedServicesVideoAdaptationServiceStatisticsChassisLevelOnlineTranscodingOrtFailureNumortexceededmaxvideoduration ConfdString,
        affirmedServicesVideoAdaptationServiceStatisticsChassisLevelOnlineTranscodingOrtFailureNumortbelowminvideoduration ConfdString,
        affirmedServicesVideoAdaptationServiceStatisticsChassisLevelOnlineTranscodingOrtFailureNumortexceededmaxbitrate ConfdString,
        affirmedServicesVideoAdaptationServiceStatisticsChassisLevelOnlineTranscodingOrtFailureNumortexceededmaxframerate ConfdString,
        affirmedServicesVideoAdaptationServiceStatisticsChassisLevelOnlineTranscodingOrtFailureNumortunsupportedsrccontainer ConfdString,
        affirmedServicesVideoAdaptationServiceStatisticsChassisLevelOnlineTranscodingOrtFailureNumortunsupportedformat ConfdString,
        affirmedServicesVideoAdaptationServiceStatisticsChassisLevelOnlineTranscodingOrtFailureNumortunsupportedvideocodec ConfdString,
        affirmedServicesVideoAdaptationServiceStatisticsChassisLevelOnlineTranscodingOrtFailureNumortunsupportedaudiocodec ConfdString,
        affirmedServicesVideoAdaptationServiceStatisticsChassisLevelOnlineTranscodingOrtFailureNumortfailureothers ConfdString,
        affirmedServicesVideoAdaptationServiceStatisticsChassisLevelOnlineTranscodingOrtFailureNumortcancelcontenttypemismatches ConfdString,
        affirmedServicesVideoAdaptationServiceStatisticsChassisLevelOnlineTranscodingOrtFailureNumortcancelnomapqoematch ConfdString,
        affirmedServicesVideoAdaptationServiceStatisticsChassisLevelOnlineTranscodingOrtFailureNumortcancelmapentrybypass ConfdString,
        affirmedServicesVideoAdaptationServiceStatisticsChassisLevelOnlineTranscodingOrtFailureNumortcancelcpuoverload ConfdString,
        affirmedServicesVideoAdaptationServiceStatisticsChassisLevelOnlineTranscodingOrtFailureNumortnosrcaudiostreampresent ConfdString,
        affirmedServicesVideoAdaptationServiceStatisticsChassisLevelOnlineTranscodingOrtFailureNumortnosrcvideostreampresent ConfdString,
        affirmedServicesVideoAdaptationServiceStatisticsChassisLevelOnlineTranscodingOrtFailureNumortunsupportedsrcaudiocodec ConfdString,
        affirmedServicesVideoAdaptationServiceStatisticsChassisLevelOnlineTranscodingOrtFailureNumortunsupportedsrcvideocodec ConfdString,
        affirmedServicesVideoAdaptationServiceStatisticsChassisLevelOnlineTranscodingOrtFailureNumortbelowbitratesavingsthreshold ConfdString,
        affirmedServicesVideoAdaptationServiceStatisticsChassisLevelOnlineTranscodingOrtFailureNumortsrcmediaformatnotsupported ConfdString,
        affirmedServicesVideoAdaptationServiceStatisticsChassisLevelOnlineTranscodingOrtFailureNumorttgtmediaformatnotsupported ConfdString,
        affirmedServicesVideoAdaptationServiceStatisticsChassisLevelOnlineTranscodingOrtFailureNumorttgtmediaformatparametersnotvalid ConfdString,
        affirmedServicesVideoAdaptationServiceStatisticsChassisLevelOnlineTranscodingOrtFailureNumorttgtxcodingparametersnotvalid ConfdString,
        affirmedServicesVideoAdaptationServiceStatisticsChassisLevelOnlineTranscodingOrtFailureNumortcancelnomatchmapqoe ConfdString,
        affirmedServicesVideoAdaptationServiceStatisticsChassisLevelOnlineTranscodingOrtFailureNumortcancelsrcmediaisnotstreamable ConfdString,
        affirmedServicesVideoAdaptationServiceStatisticsChassisLevelOnlineTranscodingOrtFailureNumortfailuredelayresponding ConfdString,
        affirmedServicesVideoAdaptationServiceStatisticsChassisLevelOnlineTranscodingOrtFailureNumortcouldnotfindsrcmediastream ConfdString,
        affirmedServicesVideoAdaptationServiceStatisticsChassisLevelOnlineTranscodingOrtFailureNumortcancelothers ConfdString,
        affirmedServicesVideoAdaptationServiceStatisticsChassisLevelOnlineTranscodingOrtFailureNumortbypassoptout ConfdString,
        affirmedServicesVideoAdaptationServiceStatisticsChassisLevelOnlineTranscodingOrtFailureNumortbypassmedianotsupported ConfdString,
        affirmedServicesVideoAdaptationServiceStatisticsChassisLevelOnlineTranscodingOrtFailureNumortbypassrangerequestnotenabled ConfdString,
        affirmedServicesVideoAdaptationServiceStatisticsChassisLevelOnlineTranscodingOrtFailureNumortbypassmultipartrangerequest ConfdString,
        affirmedServicesVideoAdaptationServiceStatisticsChassisLevelOnlineTranscodingOrtFailureNumortbypassinitialrangenotzero ConfdString
    }

affirmedServicesVideoAdaptationServiceStatisticsChassisLevelOnlineTranscodingOrtFailureChassis OBJECT-TYPE
    SYNTAX      Unsigned32
    MAX-ACCESS  not-accessible
    STATUS      current
    DESCRIPTION "chassis ID"
    ::= { affirmedServicesVideoAdaptationServiceStatisticsChassisLevelOnlineTranscodingOrtFailureEntry 1 }

affirmedServicesVideoAdaptationServiceStatisticsChassisLevelOnlineTranscodingOrtFailureNumortexceededmaxvideosize OBJECT-TYPE
    SYNTAX      ConfdString
    MAX-ACCESS  read-only
    STATUS      current
    DESCRIPTION "Total number of Online Range Transcoding exceeded max video size "
    ::= { affirmedServicesVideoAdaptationServiceStatisticsChassisLevelOnlineTranscodingOrtFailureEntry 2 }

affirmedServicesVideoAdaptationServiceStatisticsChassisLevelOnlineTranscodingOrtFailureNumortbelowminvideosize OBJECT-TYPE
    SYNTAX      ConfdString
    MAX-ACCESS  read-only
    STATUS      current
    DESCRIPTION "Total number of Online Range Transcoding below min video size"
    ::= { affirmedServicesVideoAdaptationServiceStatisticsChassisLevelOnlineTranscodingOrtFailureEntry 3 }

affirmedServicesVideoAdaptationServiceStatisticsChassisLevelOnlineTranscodingOrtFailureNumortexceededmaxvideoduration OBJECT-TYPE
    SYNTAX      ConfdString
    MAX-ACCESS  read-only
    STATUS      current
    DESCRIPTION "Total number of Online Range Transcoding exceeded max video duration "
    ::= { affirmedServicesVideoAdaptationServiceStatisticsChassisLevelOnlineTranscodingOrtFailureEntry 4 }

affirmedServicesVideoAdaptationServiceStatisticsChassisLevelOnlineTranscodingOrtFailureNumortbelowminvideoduration OBJECT-TYPE
    SYNTAX      ConfdString
    MAX-ACCESS  read-only
    STATUS      current
    DESCRIPTION "Total number of Online Range Transcoding below min video duration"
    ::= { affirmedServicesVideoAdaptationServiceStatisticsChassisLevelOnlineTranscodingOrtFailureEntry 5 }

affirmedServicesVideoAdaptationServiceStatisticsChassisLevelOnlineTranscodingOrtFailureNumortexceededmaxbitrate OBJECT-TYPE
    SYNTAX      ConfdString
    MAX-ACCESS  read-only
    STATUS      current
    DESCRIPTION "Total number of Online Range Transcoding exceeded max video bitrate "
    ::= { affirmedServicesVideoAdaptationServiceStatisticsChassisLevelOnlineTranscodingOrtFailureEntry 6 }

affirmedServicesVideoAdaptationServiceStatisticsChassisLevelOnlineTranscodingOrtFailureNumortexceededmaxframerate OBJECT-TYPE
    SYNTAX      ConfdString
    MAX-ACCESS  read-only
    STATUS      current
    DESCRIPTION "Total number of Online Range Transcoding exceeded max video framerate"
    ::= { affirmedServicesVideoAdaptationServiceStatisticsChassisLevelOnlineTranscodingOrtFailureEntry 7 }

affirmedServicesVideoAdaptationServiceStatisticsChassisLevelOnlineTranscodingOrtFailureNumortunsupportedsrccontainer OBJECT-TYPE
    SYNTAX      ConfdString
    MAX-ACCESS  read-only
    STATUS      current
    DESCRIPTION "Total number of Online Range Transcoding Unsupported Source Container"
    ::= { affirmedServicesVideoAdaptationServiceStatisticsChassisLevelOnlineTranscodingOrtFailureEntry 8 }

affirmedServicesVideoAdaptationServiceStatisticsChassisLevelOnlineTranscodingOrtFailureNumortunsupportedformat OBJECT-TYPE
    SYNTAX      ConfdString
    MAX-ACCESS  read-only
    STATUS      current
    DESCRIPTION "Total number of Online Range Transcoding Unsupported Format"
    ::= { affirmedServicesVideoAdaptationServiceStatisticsChassisLevelOnlineTranscodingOrtFailureEntry 9 }

affirmedServicesVideoAdaptationServiceStatisticsChassisLevelOnlineTranscodingOrtFailureNumortunsupportedvideocodec OBJECT-TYPE
    SYNTAX      ConfdString
    MAX-ACCESS  read-only
    STATUS      current
    DESCRIPTION "Total number of Online Range Transcoding Unsupported Video Codec"
    ::= { affirmedServicesVideoAdaptationServiceStatisticsChassisLevelOnlineTranscodingOrtFailureEntry 10 }

affirmedServicesVideoAdaptationServiceStatisticsChassisLevelOnlineTranscodingOrtFailureNumortunsupportedaudiocodec OBJECT-TYPE
    SYNTAX      ConfdString
    MAX-ACCESS  read-only
    STATUS      current
    DESCRIPTION "Total number of Online Range Transcoding Unsupported Audio Codec"
    ::= { affirmedServicesVideoAdaptationServiceStatisticsChassisLevelOnlineTranscodingOrtFailureEntry 11 }

affirmedServicesVideoAdaptationServiceStatisticsChassisLevelOnlineTranscodingOrtFailureNumortfailureothers OBJECT-TYPE
    SYNTAX      ConfdString
    MAX-ACCESS  read-only
    STATUS      current
    DESCRIPTION "Total number of Online Range Transcoding Failure With Other Reason"
    ::= { affirmedServicesVideoAdaptationServiceStatisticsChassisLevelOnlineTranscodingOrtFailureEntry 12 }

affirmedServicesVideoAdaptationServiceStatisticsChassisLevelOnlineTranscodingOrtFailureNumortcancelcontenttypemismatches OBJECT-TYPE
    SYNTAX      ConfdString
    MAX-ACCESS  read-only
    STATUS      current
    DESCRIPTION "Total number of Online Range Transcoding Cancel Content-Type Mismatches"
    ::= { affirmedServicesVideoAdaptationServiceStatisticsChassisLevelOnlineTranscodingOrtFailureEntry 13 }

affirmedServicesVideoAdaptationServiceStatisticsChassisLevelOnlineTranscodingOrtFailureNumortcancelnomapqoematch OBJECT-TYPE
    SYNTAX      ConfdString
    MAX-ACCESS  read-only
    STATUS      current
    DESCRIPTION "Total number of Online Range Transcoding Cancels due to no transcoding map or QOE grade"
    ::= { affirmedServicesVideoAdaptationServiceStatisticsChassisLevelOnlineTranscodingOrtFailureEntry 14 }

affirmedServicesVideoAdaptationServiceStatisticsChassisLevelOnlineTranscodingOrtFailureNumortcancelmapentrybypass OBJECT-TYPE
    SYNTAX      ConfdString
    MAX-ACCESS  read-only
    STATUS      current
    DESCRIPTION "Total number of Online Range Transcoding Cancels due to Bypass set in the transcoding map entry"
    ::= { affirmedServicesVideoAdaptationServiceStatisticsChassisLevelOnlineTranscodingOrtFailureEntry 15 }

affirmedServicesVideoAdaptationServiceStatisticsChassisLevelOnlineTranscodingOrtFailureNumortcancelcpuoverload OBJECT-TYPE
    SYNTAX      ConfdString
    MAX-ACCESS  read-only
    STATUS      current
    DESCRIPTION "Total number of Online Range Transcoding Cancel CPU Overload"
    ::= { affirmedServicesVideoAdaptationServiceStatisticsChassisLevelOnlineTranscodingOrtFailureEntry 16 }

affirmedServicesVideoAdaptationServiceStatisticsChassisLevelOnlineTranscodingOrtFailureNumortnosrcaudiostreampresent OBJECT-TYPE
    SYNTAX      ConfdString
    MAX-ACCESS  read-only
    STATUS      current
    DESCRIPTION "Total number of Online Range Transcoding No Src Audio Stream Present"
    ::= { affirmedServicesVideoAdaptationServiceStatisticsChassisLevelOnlineTranscodingOrtFailureEntry 17 }

affirmedServicesVideoAdaptationServiceStatisticsChassisLevelOnlineTranscodingOrtFailureNumortnosrcvideostreampresent OBJECT-TYPE
    SYNTAX      ConfdString
    MAX-ACCESS  read-only
    STATUS      current
    DESCRIPTION "Total number of Online Range Transcoding No Src Video Stream Present"
    ::= { affirmedServicesVideoAdaptationServiceStatisticsChassisLevelOnlineTranscodingOrtFailureEntry 18 }

affirmedServicesVideoAdaptationServiceStatisticsChassisLevelOnlineTranscodingOrtFailureNumortunsupportedsrcaudiocodec OBJECT-TYPE
    SYNTAX      ConfdString
    MAX-ACCESS  read-only
    STATUS      current
    DESCRIPTION "Total number of Online Range Transcoding Unsupported Src Audio Codec"
    ::= { affirmedServicesVideoAdaptationServiceStatisticsChassisLevelOnlineTranscodingOrtFailureEntry 19 }

affirmedServicesVideoAdaptationServiceStatisticsChassisLevelOnlineTranscodingOrtFailureNumortunsupportedsrcvideocodec OBJECT-TYPE
    SYNTAX      ConfdString
    MAX-ACCESS  read-only
    STATUS      current
    DESCRIPTION "Total number of Online Range Transcoding Unsupported Src Video Codec"
    ::= { affirmedServicesVideoAdaptationServiceStatisticsChassisLevelOnlineTranscodingOrtFailureEntry 20 }

affirmedServicesVideoAdaptationServiceStatisticsChassisLevelOnlineTranscodingOrtFailureNumortbelowbitratesavingsthreshold OBJECT-TYPE
    SYNTAX      ConfdString
    MAX-ACCESS  read-only
    STATUS      current
    DESCRIPTION "Total number of Online Range Transcoding Below Bit Rate Savings Threshold"
    ::= { affirmedServicesVideoAdaptationServiceStatisticsChassisLevelOnlineTranscodingOrtFailureEntry 21 }

affirmedServicesVideoAdaptationServiceStatisticsChassisLevelOnlineTranscodingOrtFailureNumortsrcmediaformatnotsupported OBJECT-TYPE
    SYNTAX      ConfdString
    MAX-ACCESS  read-only
    STATUS      current
    DESCRIPTION "Total number of Online Range Transcoding Src Media Format Not Supported"
    ::= { affirmedServicesVideoAdaptationServiceStatisticsChassisLevelOnlineTranscodingOrtFailureEntry 22 }

affirmedServicesVideoAdaptationServiceStatisticsChassisLevelOnlineTranscodingOrtFailureNumorttgtmediaformatnotsupported OBJECT-TYPE
    SYNTAX      ConfdString
    MAX-ACCESS  read-only
    STATUS      current
    DESCRIPTION "Total number of Online Range Transcoding Tgt Media Format Not Supported"
    ::= { affirmedServicesVideoAdaptationServiceStatisticsChassisLevelOnlineTranscodingOrtFailureEntry 23 }

affirmedServicesVideoAdaptationServiceStatisticsChassisLevelOnlineTranscodingOrtFailureNumorttgtmediaformatparametersnotvalid OBJECT-TYPE
    SYNTAX      ConfdString
    MAX-ACCESS  read-only
    STATUS      current
    DESCRIPTION "Total number of Online Range Transcoding Tgt Media Format Parameters Not Valid"
    ::= { affirmedServicesVideoAdaptationServiceStatisticsChassisLevelOnlineTranscodingOrtFailureEntry 24 }

affirmedServicesVideoAdaptationServiceStatisticsChassisLevelOnlineTranscodingOrtFailureNumorttgtxcodingparametersnotvalid OBJECT-TYPE
    SYNTAX      ConfdString
    MAX-ACCESS  read-only
    STATUS      current
    DESCRIPTION "Total number of Online Range Transcoding Target Transcoding Paramaters Not Valid"
    ::= { affirmedServicesVideoAdaptationServiceStatisticsChassisLevelOnlineTranscodingOrtFailureEntry 25 }

affirmedServicesVideoAdaptationServiceStatisticsChassisLevelOnlineTranscodingOrtFailureNumortcancelnomatchmapqoe OBJECT-TYPE
    SYNTAX      ConfdString
    MAX-ACCESS  read-only
    STATUS      current
    DESCRIPTION "Total number of Online Range Transcoding Cancels due to no matching transcoding map entry or QOE grade"
    ::= { affirmedServicesVideoAdaptationServiceStatisticsChassisLevelOnlineTranscodingOrtFailureEntry 26 }

affirmedServicesVideoAdaptationServiceStatisticsChassisLevelOnlineTranscodingOrtFailureNumortcancelsrcmediaisnotstreamable OBJECT-TYPE
    SYNTAX      ConfdString
    MAX-ACCESS  read-only
    STATUS      current
    DESCRIPTION "Total number of Online Range Transcoding Cancels due to source media is not streamable"
    ::= { affirmedServicesVideoAdaptationServiceStatisticsChassisLevelOnlineTranscodingOrtFailureEntry 27 }

affirmedServicesVideoAdaptationServiceStatisticsChassisLevelOnlineTranscodingOrtFailureNumortfailuredelayresponding OBJECT-TYPE
    SYNTAX      ConfdString
    MAX-ACCESS  read-only
    STATUS      current
    DESCRIPTION "Total number of Online Range Transcoding Failure due to Delay in Responding"
    ::= { affirmedServicesVideoAdaptationServiceStatisticsChassisLevelOnlineTranscodingOrtFailureEntry 28 }

affirmedServicesVideoAdaptationServiceStatisticsChassisLevelOnlineTranscodingOrtFailureNumortcouldnotfindsrcmediastream OBJECT-TYPE
    SYNTAX      ConfdString
    MAX-ACCESS  read-only
    STATUS      current
    DESCRIPTION "Total number of Online Range Transcoding Cancel due to Could not Find/Determine Source Media Stream Info"
    ::= { affirmedServicesVideoAdaptationServiceStatisticsChassisLevelOnlineTranscodingOrtFailureEntry 29 }

affirmedServicesVideoAdaptationServiceStatisticsChassisLevelOnlineTranscodingOrtFailureNumortcancelothers OBJECT-TYPE
    SYNTAX      ConfdString
    MAX-ACCESS  read-only
    STATUS      current
    DESCRIPTION "Total number of Online Range Transcoding Cancel With Other Reason"
    ::= { affirmedServicesVideoAdaptationServiceStatisticsChassisLevelOnlineTranscodingOrtFailureEntry 30 }

affirmedServicesVideoAdaptationServiceStatisticsChassisLevelOnlineTranscodingOrtFailureNumortbypassoptout OBJECT-TYPE
    SYNTAX      ConfdString
    MAX-ACCESS  read-only
    STATUS      current
    DESCRIPTION "Total number of Online Range Transcoding Bypassed due to subscriber opting-out"
    ::= { affirmedServicesVideoAdaptationServiceStatisticsChassisLevelOnlineTranscodingOrtFailureEntry 31 }

affirmedServicesVideoAdaptationServiceStatisticsChassisLevelOnlineTranscodingOrtFailureNumortbypassmedianotsupported OBJECT-TYPE
    SYNTAX      ConfdString
    MAX-ACCESS  read-only
    STATUS      current
    DESCRIPTION "Total number of Online Range Transcoding Bypassed - MediaType Not Supported"
    ::= { affirmedServicesVideoAdaptationServiceStatisticsChassisLevelOnlineTranscodingOrtFailureEntry 32 }

affirmedServicesVideoAdaptationServiceStatisticsChassisLevelOnlineTranscodingOrtFailureNumortbypassrangerequestnotenabled OBJECT-TYPE
    SYNTAX      ConfdString
    MAX-ACCESS  read-only
    STATUS      current
    DESCRIPTION "Total number of Online Range Transcoding Bypassed - Range Request support not enabled"
    ::= { affirmedServicesVideoAdaptationServiceStatisticsChassisLevelOnlineTranscodingOrtFailureEntry 33 }

affirmedServicesVideoAdaptationServiceStatisticsChassisLevelOnlineTranscodingOrtFailureNumortbypassmultipartrangerequest OBJECT-TYPE
    SYNTAX      ConfdString
    MAX-ACCESS  read-only
    STATUS      current
    DESCRIPTION "Total number of Online Range Transcoding Bypassed - Multi Part Range Request"
    ::= { affirmedServicesVideoAdaptationServiceStatisticsChassisLevelOnlineTranscodingOrtFailureEntry 34 }

affirmedServicesVideoAdaptationServiceStatisticsChassisLevelOnlineTranscodingOrtFailureNumortbypassinitialrangenotzero OBJECT-TYPE
    SYNTAX      ConfdString
    MAX-ACCESS  read-only
    STATUS      current
    DESCRIPTION "Total number of Online Range Transcoding Bypassed - Initial Range not zero"
    ::= { affirmedServicesVideoAdaptationServiceStatisticsChassisLevelOnlineTranscodingOrtFailureEntry 35 }

affirmedServicesVideoAdaptationServiceStatisticsChassisLevelOfflineTranscodingSummaryTable OBJECT-TYPE
    SYNTAX      SEQUENCE OF AffirmedServicesVideoAdaptationServiceStatisticsChassisLevelOfflineTranscodingSummaryEntry
    MAX-ACCESS  not-accessible
    STATUS      current
    DESCRIPTION ""
    ::= { affirmedServicesVideoAdaptationServiceStatisticsChassisLevelOfflineTranscoding 1 }

affirmedServicesVideoAdaptationServiceStatisticsChassisLevelOfflineTranscodingSummaryEntry OBJECT-TYPE
    SYNTAX      AffirmedServicesVideoAdaptationServiceStatisticsChassisLevelOfflineTranscodingSummaryEntry
    MAX-ACCESS  not-accessible
    STATUS      current
    DESCRIPTION ""
    INDEX { affirmedServicesVideoAdaptationServiceStatisticsChassisLevelOfflineTranscodingSummaryChassis }
        ::= { affirmedServicesVideoAdaptationServiceStatisticsChassisLevelOfflineTranscodingSummaryTable 1 }

AffirmedServicesVideoAdaptationServiceStatisticsChassisLevelOfflineTranscodingSummaryEntry ::=
    SEQUENCE {
        affirmedServicesVideoAdaptationServiceStatisticsChassisLevelOfflineTranscodingSummaryChassis Unsigned32,
        affirmedServicesVideoAdaptationServiceStatisticsChassisLevelOfflineTranscodingSummaryNumofflineattempts ConfdString,
        affirmedServicesVideoAdaptationServiceStatisticsChassisLevelOfflineTranscodingSummaryNumofflinesuccesses ConfdString,
        affirmedServicesVideoAdaptationServiceStatisticsChassisLevelOfflineTranscodingSummaryNumofflinecancels ConfdString,
        affirmedServicesVideoAdaptationServiceStatisticsChassisLevelOfflineTranscodingSummaryNumofflinefailures ConfdString,
        affirmedServicesVideoAdaptationServiceStatisticsChassisLevelOfflineTranscodingSummaryNumofflineflvsuccesses ConfdString,
        affirmedServicesVideoAdaptationServiceStatisticsChassisLevelOfflineTranscodingSummaryNumofflineflvfailures ConfdString,
        affirmedServicesVideoAdaptationServiceStatisticsChassisLevelOfflineTranscodingSummaryNumofflinemp4successes ConfdString,
        affirmedServicesVideoAdaptationServiceStatisticsChassisLevelOfflineTranscodingSummaryNumofflinemp4failures ConfdString,
        affirmedServicesVideoAdaptationServiceStatisticsChassisLevelOfflineTranscodingSummaryNumofflinewebmsuccesses ConfdString,
        affirmedServicesVideoAdaptationServiceStatisticsChassisLevelOfflineTranscodingSummaryNumofflinewebmfailures ConfdString,
        affirmedServicesVideoAdaptationServiceStatisticsChassisLevelOfflineTranscodingSummaryNumofflineorigservingsuccess ConfdString,
        affirmedServicesVideoAdaptationServiceStatisticsChassisLevelOfflineTranscodingSummaryNumofflineorigservingabort ConfdString,
        affirmedServicesVideoAdaptationServiceStatisticsChassisLevelOfflineTranscodingSummaryNumofflineorigservingfailure ConfdString,
        affirmedServicesVideoAdaptationServiceStatisticsChassisLevelOfflineTranscodingSummaryNumofflineflvservingsuccess ConfdString,
        affirmedServicesVideoAdaptationServiceStatisticsChassisLevelOfflineTranscodingSummaryNumofflineflvservingabort ConfdString,
        affirmedServicesVideoAdaptationServiceStatisticsChassisLevelOfflineTranscodingSummaryNumofflineflvservingfailure ConfdString,
        affirmedServicesVideoAdaptationServiceStatisticsChassisLevelOfflineTranscodingSummaryNumofflinemp4servingsuccess ConfdString,
        affirmedServicesVideoAdaptationServiceStatisticsChassisLevelOfflineTranscodingSummaryNumofflinemp4servingabort ConfdString,
        affirmedServicesVideoAdaptationServiceStatisticsChassisLevelOfflineTranscodingSummaryNumofflinemp4servingfailure ConfdString,
        affirmedServicesVideoAdaptationServiceStatisticsChassisLevelOfflineTranscodingSummaryNumofflinewebmservingsuccess ConfdString,
        affirmedServicesVideoAdaptationServiceStatisticsChassisLevelOfflineTranscodingSummaryNumofflinewebmservingabort ConfdString,
        affirmedServicesVideoAdaptationServiceStatisticsChassisLevelOfflineTranscodingSummaryNumofflinewebmservingfailure ConfdString,
        affirmedServicesVideoAdaptationServiceStatisticsChassisLevelOfflineTranscodingSummaryNumofflineoriginalbytes ConfdString,
        affirmedServicesVideoAdaptationServiceStatisticsChassisLevelOfflineTranscodingSummaryNumofflineadaptedbytesserved ConfdString
    }

affirmedServicesVideoAdaptationServiceStatisticsChassisLevelOfflineTranscodingSummaryChassis OBJECT-TYPE
    SYNTAX      Unsigned32
    MAX-ACCESS  not-accessible
    STATUS      current
    DESCRIPTION "chassis ID"
    ::= { affirmedServicesVideoAdaptationServiceStatisticsChassisLevelOfflineTranscodingSummaryEntry 1 }

affirmedServicesVideoAdaptationServiceStatisticsChassisLevelOfflineTranscodingSummaryNumofflineattempts OBJECT-TYPE
    SYNTAX      ConfdString
    MAX-ACCESS  read-only
    STATUS      current
    DESCRIPTION "Total number of Offline Transcoding attempts"
    ::= { affirmedServicesVideoAdaptationServiceStatisticsChassisLevelOfflineTranscodingSummaryEntry 2 }

affirmedServicesVideoAdaptationServiceStatisticsChassisLevelOfflineTranscodingSummaryNumofflinesuccesses OBJECT-TYPE
    SYNTAX      ConfdString
    MAX-ACCESS  read-only
    STATUS      current
    DESCRIPTION "Total number of Offline Transcoding successes"
    ::= { affirmedServicesVideoAdaptationServiceStatisticsChassisLevelOfflineTranscodingSummaryEntry 3 }

affirmedServicesVideoAdaptationServiceStatisticsChassisLevelOfflineTranscodingSummaryNumofflinecancels OBJECT-TYPE
    SYNTAX      ConfdString
    MAX-ACCESS  read-only
    STATUS      current
    DESCRIPTION "Total number of Offline Transcoding cancels"
    ::= { affirmedServicesVideoAdaptationServiceStatisticsChassisLevelOfflineTranscodingSummaryEntry 4 }

affirmedServicesVideoAdaptationServiceStatisticsChassisLevelOfflineTranscodingSummaryNumofflinefailures OBJECT-TYPE
    SYNTAX      ConfdString
    MAX-ACCESS  read-only
    STATUS      current
    DESCRIPTION "Total number of Offline Transcoding failures"
    ::= { affirmedServicesVideoAdaptationServiceStatisticsChassisLevelOfflineTranscodingSummaryEntry 5 }

affirmedServicesVideoAdaptationServiceStatisticsChassisLevelOfflineTranscodingSummaryNumofflineflvsuccesses OBJECT-TYPE
    SYNTAX      ConfdString
    MAX-ACCESS  read-only
    STATUS      current
    DESCRIPTION "Number of videos transcoded successfully from FLV"
    ::= { affirmedServicesVideoAdaptationServiceStatisticsChassisLevelOfflineTranscodingSummaryEntry 6 }

affirmedServicesVideoAdaptationServiceStatisticsChassisLevelOfflineTranscodingSummaryNumofflineflvfailures OBJECT-TYPE
    SYNTAX      ConfdString
    MAX-ACCESS  read-only
    STATUS      current
    DESCRIPTION "Number of video transcoding failures from FLV"
    ::= { affirmedServicesVideoAdaptationServiceStatisticsChassisLevelOfflineTranscodingSummaryEntry 7 }

affirmedServicesVideoAdaptationServiceStatisticsChassisLevelOfflineTranscodingSummaryNumofflinemp4successes OBJECT-TYPE
    SYNTAX      ConfdString
    MAX-ACCESS  read-only
    STATUS      current
    DESCRIPTION "Number of videos transcoded successfully from MP4"
    ::= { affirmedServicesVideoAdaptationServiceStatisticsChassisLevelOfflineTranscodingSummaryEntry 8 }

affirmedServicesVideoAdaptationServiceStatisticsChassisLevelOfflineTranscodingSummaryNumofflinemp4failures OBJECT-TYPE
    SYNTAX      ConfdString
    MAX-ACCESS  read-only
    STATUS      current
    DESCRIPTION "Number of video transcoding failures from MP4"
    ::= { affirmedServicesVideoAdaptationServiceStatisticsChassisLevelOfflineTranscodingSummaryEntry 9 }

affirmedServicesVideoAdaptationServiceStatisticsChassisLevelOfflineTranscodingSummaryNumofflinewebmsuccesses OBJECT-TYPE
    SYNTAX      ConfdString
    MAX-ACCESS  read-only
    STATUS      current
    DESCRIPTION "Number of videos transcoded successfully from WEBM"
    ::= { affirmedServicesVideoAdaptationServiceStatisticsChassisLevelOfflineTranscodingSummaryEntry 10 }

affirmedServicesVideoAdaptationServiceStatisticsChassisLevelOfflineTranscodingSummaryNumofflinewebmfailures OBJECT-TYPE
    SYNTAX      ConfdString
    MAX-ACCESS  read-only
    STATUS      current
    DESCRIPTION "Number of video transcoding failures from WEBM"
    ::= { affirmedServicesVideoAdaptationServiceStatisticsChassisLevelOfflineTranscodingSummaryEntry 11 }

affirmedServicesVideoAdaptationServiceStatisticsChassisLevelOfflineTranscodingSummaryNumofflineorigservingsuccess OBJECT-TYPE
    SYNTAX      ConfdString
    MAX-ACCESS  read-only
    STATUS      current
    DESCRIPTION "Number of original videos serviced successfully"
    ::= { affirmedServicesVideoAdaptationServiceStatisticsChassisLevelOfflineTranscodingSummaryEntry 12 }

affirmedServicesVideoAdaptationServiceStatisticsChassisLevelOfflineTranscodingSummaryNumofflineorigservingabort OBJECT-TYPE
    SYNTAX      ConfdString
    MAX-ACCESS  read-only
    STATUS      current
    DESCRIPTION "Number of original video service aborts"
    ::= { affirmedServicesVideoAdaptationServiceStatisticsChassisLevelOfflineTranscodingSummaryEntry 13 }

affirmedServicesVideoAdaptationServiceStatisticsChassisLevelOfflineTranscodingSummaryNumofflineorigservingfailure OBJECT-TYPE
    SYNTAX      ConfdString
    MAX-ACCESS  read-only
    STATUS      current
    DESCRIPTION "Number of original video service failures"
    ::= { affirmedServicesVideoAdaptationServiceStatisticsChassisLevelOfflineTranscodingSummaryEntry 14 }

affirmedServicesVideoAdaptationServiceStatisticsChassisLevelOfflineTranscodingSummaryNumofflineflvservingsuccess OBJECT-TYPE
    SYNTAX      ConfdString
    MAX-ACCESS  read-only
    STATUS      current
    DESCRIPTION "Number of transcoded FLV videos serviced successfully"
    ::= { affirmedServicesVideoAdaptationServiceStatisticsChassisLevelOfflineTranscodingSummaryEntry 15 }

affirmedServicesVideoAdaptationServiceStatisticsChassisLevelOfflineTranscodingSummaryNumofflineflvservingabort OBJECT-TYPE
    SYNTAX      ConfdString
    MAX-ACCESS  read-only
    STATUS      current
    DESCRIPTION "Number of transcoded FLV video service aborts"
    ::= { affirmedServicesVideoAdaptationServiceStatisticsChassisLevelOfflineTranscodingSummaryEntry 16 }

affirmedServicesVideoAdaptationServiceStatisticsChassisLevelOfflineTranscodingSummaryNumofflineflvservingfailure OBJECT-TYPE
    SYNTAX      ConfdString
    MAX-ACCESS  read-only
    STATUS      current
    DESCRIPTION "Number of transcoded FLV video service failures"
    ::= { affirmedServicesVideoAdaptationServiceStatisticsChassisLevelOfflineTranscodingSummaryEntry 17 }

affirmedServicesVideoAdaptationServiceStatisticsChassisLevelOfflineTranscodingSummaryNumofflinemp4servingsuccess OBJECT-TYPE
    SYNTAX      ConfdString
    MAX-ACCESS  read-only
    STATUS      current
    DESCRIPTION "Number of transcoded MP4 videos serviced successfully"
    ::= { affirmedServicesVideoAdaptationServiceStatisticsChassisLevelOfflineTranscodingSummaryEntry 18 }

affirmedServicesVideoAdaptationServiceStatisticsChassisLevelOfflineTranscodingSummaryNumofflinemp4servingabort OBJECT-TYPE
    SYNTAX      ConfdString
    MAX-ACCESS  read-only
    STATUS      current
    DESCRIPTION "Number of transcoded MP4 video service aborts"
    ::= { affirmedServicesVideoAdaptationServiceStatisticsChassisLevelOfflineTranscodingSummaryEntry 19 }

affirmedServicesVideoAdaptationServiceStatisticsChassisLevelOfflineTranscodingSummaryNumofflinemp4servingfailure OBJECT-TYPE
    SYNTAX      ConfdString
    MAX-ACCESS  read-only
    STATUS      current
    DESCRIPTION "Number of transcoded MP4 video service failures"
    ::= { affirmedServicesVideoAdaptationServiceStatisticsChassisLevelOfflineTranscodingSummaryEntry 20 }

affirmedServicesVideoAdaptationServiceStatisticsChassisLevelOfflineTranscodingSummaryNumofflinewebmservingsuccess OBJECT-TYPE
    SYNTAX      ConfdString
    MAX-ACCESS  read-only
    STATUS      current
    DESCRIPTION "Number of transcoded WEBM videos serviced successfully"
    ::= { affirmedServicesVideoAdaptationServiceStatisticsChassisLevelOfflineTranscodingSummaryEntry 21 }

affirmedServicesVideoAdaptationServiceStatisticsChassisLevelOfflineTranscodingSummaryNumofflinewebmservingabort OBJECT-TYPE
    SYNTAX      ConfdString
    MAX-ACCESS  read-only
    STATUS      current
    DESCRIPTION "Number of transcoded WEBM video service aborts"
    ::= { affirmedServicesVideoAdaptationServiceStatisticsChassisLevelOfflineTranscodingSummaryEntry 22 }

affirmedServicesVideoAdaptationServiceStatisticsChassisLevelOfflineTranscodingSummaryNumofflinewebmservingfailure OBJECT-TYPE
    SYNTAX      ConfdString
    MAX-ACCESS  read-only
    STATUS      current
    DESCRIPTION "Number of transcoded WEBM video service failures"
    ::= { affirmedServicesVideoAdaptationServiceStatisticsChassisLevelOfflineTranscodingSummaryEntry 23 }

affirmedServicesVideoAdaptationServiceStatisticsChassisLevelOfflineTranscodingSummaryNumofflineoriginalbytes OBJECT-TYPE
    SYNTAX      ConfdString
    MAX-ACCESS  read-only
    STATUS      current
    DESCRIPTION "Total number of bytes of original video cached"
    ::= { affirmedServicesVideoAdaptationServiceStatisticsChassisLevelOfflineTranscodingSummaryEntry 24 }

affirmedServicesVideoAdaptationServiceStatisticsChassisLevelOfflineTranscodingSummaryNumofflineadaptedbytesserved OBJECT-TYPE
    SYNTAX      ConfdString
    MAX-ACCESS  read-only
    STATUS      current
    DESCRIPTION "Total number of Offline Transcoding adapted bytes served"
    ::= { affirmedServicesVideoAdaptationServiceStatisticsChassisLevelOfflineTranscodingSummaryEntry 25 }

affirmedServicesVideoAdaptationServiceStatisticsChassisLevelOfflineTranscodingDetailTable OBJECT-TYPE
    SYNTAX      SEQUENCE OF AffirmedServicesVideoAdaptationServiceStatisticsChassisLevelOfflineTranscodingDetailEntry
    MAX-ACCESS  not-accessible
    STATUS      current
    DESCRIPTION ""
    ::= { affirmedServicesVideoAdaptationServiceStatisticsChassisLevelOfflineTranscoding 2 }

affirmedServicesVideoAdaptationServiceStatisticsChassisLevelOfflineTranscodingDetailEntry OBJECT-TYPE
    SYNTAX      AffirmedServicesVideoAdaptationServiceStatisticsChassisLevelOfflineTranscodingDetailEntry
    MAX-ACCESS  not-accessible
    STATUS      current
    DESCRIPTION ""
    INDEX { affirmedServicesVideoAdaptationServiceStatisticsChassisLevelOfflineTranscodingDetailChassis }
        ::= { affirmedServicesVideoAdaptationServiceStatisticsChassisLevelOfflineTranscodingDetailTable 1 }

AffirmedServicesVideoAdaptationServiceStatisticsChassisLevelOfflineTranscodingDetailEntry ::=
    SEQUENCE {
        affirmedServicesVideoAdaptationServiceStatisticsChassisLevelOfflineTranscodingDetailChassis Unsigned32,
        affirmedServicesVideoAdaptationServiceStatisticsChassisLevelOfflineTranscodingDetailNumofflineflv2flvsuccesses ConfdString,
        affirmedServicesVideoAdaptationServiceStatisticsChassisLevelOfflineTranscodingDetailNumofflineflv2flvfailures ConfdString,
        affirmedServicesVideoAdaptationServiceStatisticsChassisLevelOfflineTranscodingDetailNumofflineflv2mp4successes ConfdString,
        affirmedServicesVideoAdaptationServiceStatisticsChassisLevelOfflineTranscodingDetailNumofflineflv2mp4failures ConfdString,
        affirmedServicesVideoAdaptationServiceStatisticsChassisLevelOfflineTranscodingDetailNumofflinemp42flvsuccesses ConfdString,
        affirmedServicesVideoAdaptationServiceStatisticsChassisLevelOfflineTranscodingDetailNumofflinemp42flvfailures ConfdString,
        affirmedServicesVideoAdaptationServiceStatisticsChassisLevelOfflineTranscodingDetailNumofflinemp42mp4successes ConfdString,
        affirmedServicesVideoAdaptationServiceStatisticsChassisLevelOfflineTranscodingDetailNumofflinemp42mp4failures ConfdString,
        affirmedServicesVideoAdaptationServiceStatisticsChassisLevelOfflineTranscodingDetailNumofflinewebm2webmsuccesses ConfdString,
        affirmedServicesVideoAdaptationServiceStatisticsChassisLevelOfflineTranscodingDetailNumofflinewebm2webmfailures ConfdString,
        affirmedServicesVideoAdaptationServiceStatisticsChassisLevelOfflineTranscodingDetailNumofflinecurrentvideosqueued ConfdString,
        affirmedServicesVideoAdaptationServiceStatisticsChassisLevelOfflineTranscodingDetailNumofflinemaxvideosqueued ConfdString,
        affirmedServicesVideoAdaptationServiceStatisticsChassisLevelOfflineTranscodingDetailOfflineavgwaittime ConfdString,
        affirmedServicesVideoAdaptationServiceStatisticsChassisLevelOfflineTranscodingDetailOfflinemaxwaittime ConfdString,
        affirmedServicesVideoAdaptationServiceStatisticsChassisLevelOfflineTranscodingDetailOfflineavgprocessingtime ConfdString
    }

affirmedServicesVideoAdaptationServiceStatisticsChassisLevelOfflineTranscodingDetailChassis OBJECT-TYPE
    SYNTAX      Unsigned32
    MAX-ACCESS  not-accessible
    STATUS      current
    DESCRIPTION "chassis ID"
    ::= { affirmedServicesVideoAdaptationServiceStatisticsChassisLevelOfflineTranscodingDetailEntry 1 }

affirmedServicesVideoAdaptationServiceStatisticsChassisLevelOfflineTranscodingDetailNumofflineflv2flvsuccesses OBJECT-TYPE
    SYNTAX      ConfdString
    MAX-ACCESS  read-only
    STATUS      current
    DESCRIPTION "Number of video transcoded successfully from FLV to FLV"
    ::= { affirmedServicesVideoAdaptationServiceStatisticsChassisLevelOfflineTranscodingDetailEntry 2 }

affirmedServicesVideoAdaptationServiceStatisticsChassisLevelOfflineTranscodingDetailNumofflineflv2flvfailures OBJECT-TYPE
    SYNTAX      ConfdString
    MAX-ACCESS  read-only
    STATUS      current
    DESCRIPTION "Number of video transcoded unsuccessfully from FLV to FLV"
    ::= { affirmedServicesVideoAdaptationServiceStatisticsChassisLevelOfflineTranscodingDetailEntry 3 }

affirmedServicesVideoAdaptationServiceStatisticsChassisLevelOfflineTranscodingDetailNumofflineflv2mp4successes OBJECT-TYPE
    SYNTAX      ConfdString
    MAX-ACCESS  read-only
    STATUS      current
    DESCRIPTION "Number of video transcoded successfully from FLV to MP4"
    ::= { affirmedServicesVideoAdaptationServiceStatisticsChassisLevelOfflineTranscodingDetailEntry 4 }

affirmedServicesVideoAdaptationServiceStatisticsChassisLevelOfflineTranscodingDetailNumofflineflv2mp4failures OBJECT-TYPE
    SYNTAX      ConfdString
    MAX-ACCESS  read-only
    STATUS      current
    DESCRIPTION "Number of video transcoded unsuccessfully from FLV to MP4"
    ::= { affirmedServicesVideoAdaptationServiceStatisticsChassisLevelOfflineTranscodingDetailEntry 5 }

affirmedServicesVideoAdaptationServiceStatisticsChassisLevelOfflineTranscodingDetailNumofflinemp42flvsuccesses OBJECT-TYPE
    SYNTAX      ConfdString
    MAX-ACCESS  read-only
    STATUS      current
    DESCRIPTION "Number of video transcoded successfully from MP4 to FLV"
    ::= { affirmedServicesVideoAdaptationServiceStatisticsChassisLevelOfflineTranscodingDetailEntry 6 }

affirmedServicesVideoAdaptationServiceStatisticsChassisLevelOfflineTranscodingDetailNumofflinemp42flvfailures OBJECT-TYPE
    SYNTAX      ConfdString
    MAX-ACCESS  read-only
    STATUS      current
    DESCRIPTION "Number of video transcoded unsuccessfully from MP4 to FLV"
    ::= { affirmedServicesVideoAdaptationServiceStatisticsChassisLevelOfflineTranscodingDetailEntry 7 }

affirmedServicesVideoAdaptationServiceStatisticsChassisLevelOfflineTranscodingDetailNumofflinemp42mp4successes OBJECT-TYPE
    SYNTAX      ConfdString
    MAX-ACCESS  read-only
    STATUS      current
    DESCRIPTION "Number of video transcoded successfully from MP4 to MP4"
    ::= { affirmedServicesVideoAdaptationServiceStatisticsChassisLevelOfflineTranscodingDetailEntry 8 }

affirmedServicesVideoAdaptationServiceStatisticsChassisLevelOfflineTranscodingDetailNumofflinemp42mp4failures OBJECT-TYPE
    SYNTAX      ConfdString
    MAX-ACCESS  read-only
    STATUS      current
    DESCRIPTION "Number of video transcoded unsuccessfully from MP4 to MP4"
    ::= { affirmedServicesVideoAdaptationServiceStatisticsChassisLevelOfflineTranscodingDetailEntry 9 }

affirmedServicesVideoAdaptationServiceStatisticsChassisLevelOfflineTranscodingDetailNumofflinewebm2webmsuccesses OBJECT-TYPE
    SYNTAX      ConfdString
    MAX-ACCESS  read-only
    STATUS      current
    DESCRIPTION "Number of video transcoded successfully from WEBM to WEBM"
    ::= { affirmedServicesVideoAdaptationServiceStatisticsChassisLevelOfflineTranscodingDetailEntry 10 }

affirmedServicesVideoAdaptationServiceStatisticsChassisLevelOfflineTranscodingDetailNumofflinewebm2webmfailures OBJECT-TYPE
    SYNTAX      ConfdString
    MAX-ACCESS  read-only
    STATUS      current
    DESCRIPTION "Number of video transcoded unsuccessfully from WEBM to WEBM"
    ::= { affirmedServicesVideoAdaptationServiceStatisticsChassisLevelOfflineTranscodingDetailEntry 11 }

affirmedServicesVideoAdaptationServiceStatisticsChassisLevelOfflineTranscodingDetailNumofflinecurrentvideosqueued OBJECT-TYPE
    SYNTAX      ConfdString
    MAX-ACCESS  read-only
    STATUS      current
    DESCRIPTION "Number of videos currently in the queue to be transcoded"
    ::= { affirmedServicesVideoAdaptationServiceStatisticsChassisLevelOfflineTranscodingDetailEntry 12 }

affirmedServicesVideoAdaptationServiceStatisticsChassisLevelOfflineTranscodingDetailNumofflinemaxvideosqueued OBJECT-TYPE
    SYNTAX      ConfdString
    MAX-ACCESS  read-only
    STATUS      current
    DESCRIPTION "Maximum number of videos in the queue to be transcoded"
    ::= { affirmedServicesVideoAdaptationServiceStatisticsChassisLevelOfflineTranscodingDetailEntry 13 }

affirmedServicesVideoAdaptationServiceStatisticsChassisLevelOfflineTranscodingDetailOfflineavgwaittime OBJECT-TYPE
    SYNTAX      ConfdString
    MAX-ACCESS  read-only
    STATUS      current
    DESCRIPTION "Average wait time(in secs) of videos in the queue to be transcoded"
    ::= { affirmedServicesVideoAdaptationServiceStatisticsChassisLevelOfflineTranscodingDetailEntry 14 }

affirmedServicesVideoAdaptationServiceStatisticsChassisLevelOfflineTranscodingDetailOfflinemaxwaittime OBJECT-TYPE
    SYNTAX      ConfdString
    MAX-ACCESS  read-only
    STATUS      current
    DESCRIPTION "Maximum wait time(in secs) of videos in the queue to be transcoded"
    ::= { affirmedServicesVideoAdaptationServiceStatisticsChassisLevelOfflineTranscodingDetailEntry 15 }

affirmedServicesVideoAdaptationServiceStatisticsChassisLevelOfflineTranscodingDetailOfflineavgprocessingtime OBJECT-TYPE
    SYNTAX      ConfdString
    MAX-ACCESS  read-only
    STATUS      current
    DESCRIPTION "Average processing time(in secs) for transcoding videos"
    ::= { affirmedServicesVideoAdaptationServiceStatisticsChassisLevelOfflineTranscodingDetailEntry 16 }

affirmedServicesVideoAdaptationServiceStatisticsChassisLevelOfflineTranscodingFailureTable OBJECT-TYPE
    SYNTAX      SEQUENCE OF AffirmedServicesVideoAdaptationServiceStatisticsChassisLevelOfflineTranscodingFailureEntry
    MAX-ACCESS  not-accessible
    STATUS      current
    DESCRIPTION ""
    ::= { affirmedServicesVideoAdaptationServiceStatisticsChassisLevelOfflineTranscoding 3 }

affirmedServicesVideoAdaptationServiceStatisticsChassisLevelOfflineTranscodingFailureEntry OBJECT-TYPE
    SYNTAX      AffirmedServicesVideoAdaptationServiceStatisticsChassisLevelOfflineTranscodingFailureEntry
    MAX-ACCESS  not-accessible
    STATUS      current
    DESCRIPTION ""
    INDEX { affirmedServicesVideoAdaptationServiceStatisticsChassisLevelOfflineTranscodingFailureChassis }
        ::= { affirmedServicesVideoAdaptationServiceStatisticsChassisLevelOfflineTranscodingFailureTable 1 }

AffirmedServicesVideoAdaptationServiceStatisticsChassisLevelOfflineTranscodingFailureEntry ::=
    SEQUENCE {
        affirmedServicesVideoAdaptationServiceStatisticsChassisLevelOfflineTranscodingFailureChassis Unsigned32,
        affirmedServicesVideoAdaptationServiceStatisticsChassisLevelOfflineTranscodingFailureNumofflineunsupportedformat ConfdString,
        affirmedServicesVideoAdaptationServiceStatisticsChassisLevelOfflineTranscodingFailureNumofflineunsupportedvideocodec ConfdString,
        affirmedServicesVideoAdaptationServiceStatisticsChassisLevelOfflineTranscodingFailureNumofflineunsupportedaudiocodec ConfdString
    }

affirmedServicesVideoAdaptationServiceStatisticsChassisLevelOfflineTranscodingFailureChassis OBJECT-TYPE
    SYNTAX      Unsigned32
    MAX-ACCESS  not-accessible
    STATUS      current
    DESCRIPTION "chassis ID"
    ::= { affirmedServicesVideoAdaptationServiceStatisticsChassisLevelOfflineTranscodingFailureEntry 1 }

affirmedServicesVideoAdaptationServiceStatisticsChassisLevelOfflineTranscodingFailureNumofflineunsupportedformat OBJECT-TYPE
    SYNTAX      ConfdString
    MAX-ACCESS  read-only
    STATUS      current
    DESCRIPTION "Total number of Offline Transcoding Unsupported Format"
    ::= { affirmedServicesVideoAdaptationServiceStatisticsChassisLevelOfflineTranscodingFailureEntry 2 }

affirmedServicesVideoAdaptationServiceStatisticsChassisLevelOfflineTranscodingFailureNumofflineunsupportedvideocodec OBJECT-TYPE
    SYNTAX      ConfdString
    MAX-ACCESS  read-only
    STATUS      current
    DESCRIPTION "Total number of Offline Transcoding Unsupported Video Codec"
    ::= { affirmedServicesVideoAdaptationServiceStatisticsChassisLevelOfflineTranscodingFailureEntry 3 }

affirmedServicesVideoAdaptationServiceStatisticsChassisLevelOfflineTranscodingFailureNumofflineunsupportedaudiocodec OBJECT-TYPE
    SYNTAX      ConfdString
    MAX-ACCESS  read-only
    STATUS      current
    DESCRIPTION "Total number of Offline Transcoding Unsupported Audio Codec"
    ::= { affirmedServicesVideoAdaptationServiceStatisticsChassisLevelOfflineTranscodingFailureEntry 4 }

affirmedServicesVideoAdaptationServiceStatisticsSlotLevelOnlineTranscodingSummaryTable OBJECT-TYPE
    SYNTAX      SEQUENCE OF AffirmedServicesVideoAdaptationServiceStatisticsSlotLevelOnlineTranscodingSummaryEntry
    MAX-ACCESS  not-accessible
    STATUS      current
    DESCRIPTION ""
    ::= { affirmedServicesVideoAdaptationServiceStatisticsSlotLevelOnlineTranscoding 1 }

affirmedServicesVideoAdaptationServiceStatisticsSlotLevelOnlineTranscodingSummaryEntry OBJECT-TYPE
    SYNTAX      AffirmedServicesVideoAdaptationServiceStatisticsSlotLevelOnlineTranscodingSummaryEntry
    MAX-ACCESS  not-accessible
    STATUS      current
    DESCRIPTION ""
    INDEX { affirmedServicesVideoAdaptationServiceStatisticsSlotLevelOnlineTranscodingSummaryChassis, affirmedServicesVideoAdaptationServiceStatisticsSlotLevelOnlineTranscodingSummarySlot }
        ::= { affirmedServicesVideoAdaptationServiceStatisticsSlotLevelOnlineTranscodingSummaryTable 1 }

AffirmedServicesVideoAdaptationServiceStatisticsSlotLevelOnlineTranscodingSummaryEntry ::=
    SEQUENCE {
        affirmedServicesVideoAdaptationServiceStatisticsSlotLevelOnlineTranscodingSummaryChassis Unsigned32,
        affirmedServicesVideoAdaptationServiceStatisticsSlotLevelOnlineTranscodingSummarySlot INTEGER,
        affirmedServicesVideoAdaptationServiceStatisticsSlotLevelOnlineTranscodingSummaryNumotfattempts ConfdString,
        affirmedServicesVideoAdaptationServiceStatisticsSlotLevelOnlineTranscodingSummaryNumotfsuccesses ConfdString,
        affirmedServicesVideoAdaptationServiceStatisticsSlotLevelOnlineTranscodingSummaryNumotfcancels ConfdString,
        affirmedServicesVideoAdaptationServiceStatisticsSlotLevelOnlineTranscodingSummaryNumotffailures ConfdString,
        affirmedServicesVideoAdaptationServiceStatisticsSlotLevelOnlineTranscodingSummaryNumotfaborts ConfdString,
        affirmedServicesVideoAdaptationServiceStatisticsSlotLevelOnlineTranscodingSummaryNumotfcurrent ConfdString,
        affirmedServicesVideoAdaptationServiceStatisticsSlotLevelOnlineTranscodingSummaryNumotfbytesattempt ConfdString,
        affirmedServicesVideoAdaptationServiceStatisticsSlotLevelOnlineTranscodingSummaryNumotfbytesadapted ConfdString,
        affirmedServicesVideoAdaptationServiceStatisticsSlotLevelOnlineTranscodingSummaryNumotfbytescancel ConfdString,
        affirmedServicesVideoAdaptationServiceStatisticsSlotLevelOnlineTranscodingSummaryVideosizemin ConfdString,
        affirmedServicesVideoAdaptationServiceStatisticsSlotLevelOnlineTranscodingSummaryVideosizeavg ConfdString,
        affirmedServicesVideoAdaptationServiceStatisticsSlotLevelOnlineTranscodingSummaryVideosizemax ConfdString,
        affirmedServicesVideoAdaptationServiceStatisticsSlotLevelOnlineTranscodingSummaryAdaptedvideosizemin ConfdString,
        affirmedServicesVideoAdaptationServiceStatisticsSlotLevelOnlineTranscodingSummaryAdaptedvideosizeavg ConfdString,
        affirmedServicesVideoAdaptationServiceStatisticsSlotLevelOnlineTranscodingSummaryAdaptedvideosizemax ConfdString,
        affirmedServicesVideoAdaptationServiceStatisticsSlotLevelOnlineTranscodingSummaryAdditionallatencymin ConfdString,
        affirmedServicesVideoAdaptationServiceStatisticsSlotLevelOnlineTranscodingSummaryAdditionallatencyavg ConfdString,
        affirmedServicesVideoAdaptationServiceStatisticsSlotLevelOnlineTranscodingSummaryAdditionallatencymax ConfdString
    }

affirmedServicesVideoAdaptationServiceStatisticsSlotLevelOnlineTranscodingSummaryChassis OBJECT-TYPE
    SYNTAX      Unsigned32
    MAX-ACCESS  not-accessible
    STATUS      current
    DESCRIPTION "chassis ID"
    ::= { affirmedServicesVideoAdaptationServiceStatisticsSlotLevelOnlineTranscodingSummaryEntry 1 }

affirmedServicesVideoAdaptationServiceStatisticsSlotLevelOnlineTranscodingSummarySlot OBJECT-TYPE
    SYNTAX      INTEGER {a1(1),a2(2),a3(3),a4(4),a5(5),a6(6),a7(7),a8(8),a9(9),a10(10),a11(11),a12(12),a13(13),a14(14),a15(15),a16(16),a17(17),a18(18),a19(19),a20(20),a21(21),a22(22),a23(23),a24(24),a25(25),a26(26),a27(27),a28(28),a29(29),a30(30),a31(31),a32(32),a33(33),a34(34),a35(35),a36(36),a37(37),a38(38),a39(39),a40(40),a41(41),a42(42),a43(43),a44(44),a45(45),a46(46),a47(47),a48(48),a49(49),a50(50),a51(51),a52(52),a53(53),a54(54),a55(55),a56(56),a57(57),a58(58),a59(59),a60(60),a61(61),a62(62),a63(63),a64(64),a65(65),a66(66),a67(67),a68(68),a69(69),a70(70),a71(71),a72(72),a73(73),a74(74),a75(75),a76(76),a77(77),a78(78),a79(79),a80(80),a81(81),a82(82),a83(83),a84(84),a85(85),a86(86),a87(87),a88(88),a89(89),a90(90),a91(91),a92(92),a93(93),a94(94),a95(95),a96(96),a97(97),a98(98),a99(99),a100(100),a101(101),a102(102),a103(103),a104(104),a105(105),a106(106),a107(107),a108(108),a109(109),a110(110),a111(111),a112(112),a113(113),a114(114),a115(115),a116(116),a117(117),a118(118),a119(119),a120(120),a121(121),a122(122),a123(123),a124(124),a125(125),a126(126),a127(127),a128(128)}
    MAX-ACCESS  not-accessible
    STATUS      current
    DESCRIPTION "slot number"
    ::= { affirmedServicesVideoAdaptationServiceStatisticsSlotLevelOnlineTranscodingSummaryEntry 2 }

affirmedServicesVideoAdaptationServiceStatisticsSlotLevelOnlineTranscodingSummaryNumotfattempts OBJECT-TYPE
    SYNTAX      ConfdString
    MAX-ACCESS  read-only
    STATUS      current
    DESCRIPTION "Total number of Online Transcoding attempts"
    ::= { affirmedServicesVideoAdaptationServiceStatisticsSlotLevelOnlineTranscodingSummaryEntry 3 }

affirmedServicesVideoAdaptationServiceStatisticsSlotLevelOnlineTranscodingSummaryNumotfsuccesses OBJECT-TYPE
    SYNTAX      ConfdString
    MAX-ACCESS  read-only
    STATUS      current
    DESCRIPTION "Total number of Online Transcoding successes"
    ::= { affirmedServicesVideoAdaptationServiceStatisticsSlotLevelOnlineTranscodingSummaryEntry 4 }

affirmedServicesVideoAdaptationServiceStatisticsSlotLevelOnlineTranscodingSummaryNumotfcancels OBJECT-TYPE
    SYNTAX      ConfdString
    MAX-ACCESS  read-only
    STATUS      current
    DESCRIPTION "Total number of Online Transcoding cancels"
    ::= { affirmedServicesVideoAdaptationServiceStatisticsSlotLevelOnlineTranscodingSummaryEntry 5 }

affirmedServicesVideoAdaptationServiceStatisticsSlotLevelOnlineTranscodingSummaryNumotffailures OBJECT-TYPE
    SYNTAX      ConfdString
    MAX-ACCESS  read-only
    STATUS      current
    DESCRIPTION "Total number of Online Transcoding failures"
    ::= { affirmedServicesVideoAdaptationServiceStatisticsSlotLevelOnlineTranscodingSummaryEntry 6 }

affirmedServicesVideoAdaptationServiceStatisticsSlotLevelOnlineTranscodingSummaryNumotfaborts OBJECT-TYPE
    SYNTAX      ConfdString
    MAX-ACCESS  read-only
    STATUS      current
    DESCRIPTION "Total number of Online Transcoding aborts"
    ::= { affirmedServicesVideoAdaptationServiceStatisticsSlotLevelOnlineTranscodingSummaryEntry 7 }

affirmedServicesVideoAdaptationServiceStatisticsSlotLevelOnlineTranscodingSummaryNumotfcurrent OBJECT-TYPE
    SYNTAX      ConfdString
    MAX-ACCESS  read-only
    STATUS      current
    DESCRIPTION "Total number of Online Transcoding current"
    ::= { affirmedServicesVideoAdaptationServiceStatisticsSlotLevelOnlineTranscodingSummaryEntry 8 }

affirmedServicesVideoAdaptationServiceStatisticsSlotLevelOnlineTranscodingSummaryNumotfbytesattempt OBJECT-TYPE
    SYNTAX      ConfdString
    MAX-ACCESS  read-only
    STATUS      current
    DESCRIPTION "Total number of Online Transcoding bytes attempt"
    ::= { affirmedServicesVideoAdaptationServiceStatisticsSlotLevelOnlineTranscodingSummaryEntry 9 }

affirmedServicesVideoAdaptationServiceStatisticsSlotLevelOnlineTranscodingSummaryNumotfbytesadapted OBJECT-TYPE
    SYNTAX      ConfdString
    MAX-ACCESS  read-only
    STATUS      current
    DESCRIPTION "Total number of Online Transcoding bytes transcoded"
    ::= { affirmedServicesVideoAdaptationServiceStatisticsSlotLevelOnlineTranscodingSummaryEntry 10 }

affirmedServicesVideoAdaptationServiceStatisticsSlotLevelOnlineTranscodingSummaryNumotfbytescancel OBJECT-TYPE
    SYNTAX      ConfdString
    MAX-ACCESS  read-only
    STATUS      current
    DESCRIPTION "Total number of Online Transcoding bytes cancel"
    ::= { affirmedServicesVideoAdaptationServiceStatisticsSlotLevelOnlineTranscodingSummaryEntry 11 }

affirmedServicesVideoAdaptationServiceStatisticsSlotLevelOnlineTranscodingSummaryVideosizemin OBJECT-TYPE
    SYNTAX      ConfdString
    MAX-ACCESS  read-only
    STATUS      current
    DESCRIPTION "Online Transcoding Video Size Minimum (Bytes)"
    ::= { affirmedServicesVideoAdaptationServiceStatisticsSlotLevelOnlineTranscodingSummaryEntry 12 }

affirmedServicesVideoAdaptationServiceStatisticsSlotLevelOnlineTranscodingSummaryVideosizeavg OBJECT-TYPE
    SYNTAX      ConfdString
    MAX-ACCESS  read-only
    STATUS      current
    DESCRIPTION "Online Transcoding Video Size Average (Bytes)"
    ::= { affirmedServicesVideoAdaptationServiceStatisticsSlotLevelOnlineTranscodingSummaryEntry 13 }

affirmedServicesVideoAdaptationServiceStatisticsSlotLevelOnlineTranscodingSummaryVideosizemax OBJECT-TYPE
    SYNTAX      ConfdString
    MAX-ACCESS  read-only
    STATUS      current
    DESCRIPTION "Online Transcoding Video Size Maximum (Bytes)"
    ::= { affirmedServicesVideoAdaptationServiceStatisticsSlotLevelOnlineTranscodingSummaryEntry 14 }

affirmedServicesVideoAdaptationServiceStatisticsSlotLevelOnlineTranscodingSummaryAdaptedvideosizemin OBJECT-TYPE
    SYNTAX      ConfdString
    MAX-ACCESS  read-only
    STATUS      current
    DESCRIPTION "Online Transcoding Adapted Video Size Minimum (Bytes)"
    ::= { affirmedServicesVideoAdaptationServiceStatisticsSlotLevelOnlineTranscodingSummaryEntry 15 }

affirmedServicesVideoAdaptationServiceStatisticsSlotLevelOnlineTranscodingSummaryAdaptedvideosizeavg OBJECT-TYPE
    SYNTAX      ConfdString
    MAX-ACCESS  read-only
    STATUS      current
    DESCRIPTION "Online Transcoding Adapted Video Size Average (Bytes)"
    ::= { affirmedServicesVideoAdaptationServiceStatisticsSlotLevelOnlineTranscodingSummaryEntry 16 }

affirmedServicesVideoAdaptationServiceStatisticsSlotLevelOnlineTranscodingSummaryAdaptedvideosizemax OBJECT-TYPE
    SYNTAX      ConfdString
    MAX-ACCESS  read-only
    STATUS      current
    DESCRIPTION "Online Transcoding Adapted Video Size Maximum (Bytes)"
    ::= { affirmedServicesVideoAdaptationServiceStatisticsSlotLevelOnlineTranscodingSummaryEntry 17 }

affirmedServicesVideoAdaptationServiceStatisticsSlotLevelOnlineTranscodingSummaryAdditionallatencymin OBJECT-TYPE
    SYNTAX      ConfdString
    MAX-ACCESS  read-only
    STATUS      current
    DESCRIPTION "Online Transcoding Additional Latency Minimum (msecs)"
    ::= { affirmedServicesVideoAdaptationServiceStatisticsSlotLevelOnlineTranscodingSummaryEntry 18 }

affirmedServicesVideoAdaptationServiceStatisticsSlotLevelOnlineTranscodingSummaryAdditionallatencyavg OBJECT-TYPE
    SYNTAX      ConfdString
    MAX-ACCESS  read-only
    STATUS      current
    DESCRIPTION "Online Transcoding Additional Latency Average (msecs)"
    ::= { affirmedServicesVideoAdaptationServiceStatisticsSlotLevelOnlineTranscodingSummaryEntry 19 }

affirmedServicesVideoAdaptationServiceStatisticsSlotLevelOnlineTranscodingSummaryAdditionallatencymax OBJECT-TYPE
    SYNTAX      ConfdString
    MAX-ACCESS  read-only
    STATUS      current
    DESCRIPTION "Online Transcoding Additional Latency Maximum (msecs)"
    ::= { affirmedServicesVideoAdaptationServiceStatisticsSlotLevelOnlineTranscodingSummaryEntry 20 }

affirmedServicesVideoAdaptationServiceStatisticsSlotLevelOnlineTranscodingDetailTable OBJECT-TYPE
    SYNTAX      SEQUENCE OF AffirmedServicesVideoAdaptationServiceStatisticsSlotLevelOnlineTranscodingDetailEntry
    MAX-ACCESS  not-accessible
    STATUS      current
    DESCRIPTION ""
    ::= { affirmedServicesVideoAdaptationServiceStatisticsSlotLevelOnlineTranscoding 2 }

affirmedServicesVideoAdaptationServiceStatisticsSlotLevelOnlineTranscodingDetailEntry OBJECT-TYPE
    SYNTAX      AffirmedServicesVideoAdaptationServiceStatisticsSlotLevelOnlineTranscodingDetailEntry
    MAX-ACCESS  not-accessible
    STATUS      current
    DESCRIPTION ""
    INDEX { affirmedServicesVideoAdaptationServiceStatisticsSlotLevelOnlineTranscodingDetailChassis, affirmedServicesVideoAdaptationServiceStatisticsSlotLevelOnlineTranscodingDetailSlot }
        ::= { affirmedServicesVideoAdaptationServiceStatisticsSlotLevelOnlineTranscodingDetailTable 1 }

AffirmedServicesVideoAdaptationServiceStatisticsSlotLevelOnlineTranscodingDetailEntry ::=
    SEQUENCE {
        affirmedServicesVideoAdaptationServiceStatisticsSlotLevelOnlineTranscodingDetailChassis Unsigned32,
        affirmedServicesVideoAdaptationServiceStatisticsSlotLevelOnlineTranscodingDetailSlot INTEGER,
        affirmedServicesVideoAdaptationServiceStatisticsSlotLevelOnlineTranscodingDetailNumotfflvattempts ConfdString,
        affirmedServicesVideoAdaptationServiceStatisticsSlotLevelOnlineTranscodingDetailNumotfflvsuccesses ConfdString,
        affirmedServicesVideoAdaptationServiceStatisticsSlotLevelOnlineTranscodingDetailNumotfflvcancels ConfdString,
        affirmedServicesVideoAdaptationServiceStatisticsSlotLevelOnlineTranscodingDetailNumotfflvfailures ConfdString,
        affirmedServicesVideoAdaptationServiceStatisticsSlotLevelOnlineTranscodingDetailNumotfflvaborts ConfdString,
        affirmedServicesVideoAdaptationServiceStatisticsSlotLevelOnlineTranscodingDetailNumotfmp4attempts ConfdString,
        affirmedServicesVideoAdaptationServiceStatisticsSlotLevelOnlineTranscodingDetailNumotfmp4successes ConfdString,
        affirmedServicesVideoAdaptationServiceStatisticsSlotLevelOnlineTranscodingDetailNumotfmp4cancels ConfdString,
        affirmedServicesVideoAdaptationServiceStatisticsSlotLevelOnlineTranscodingDetailNumotfmp4failures ConfdString,
        affirmedServicesVideoAdaptationServiceStatisticsSlotLevelOnlineTranscodingDetailNumotfmp4aborts ConfdString,
        affirmedServicesVideoAdaptationServiceStatisticsSlotLevelOnlineTranscodingDetailNumotfwebmattempts ConfdString,
        affirmedServicesVideoAdaptationServiceStatisticsSlotLevelOnlineTranscodingDetailNumotfwebmsuccesses ConfdString,
        affirmedServicesVideoAdaptationServiceStatisticsSlotLevelOnlineTranscodingDetailNumotfwebmcancels ConfdString,
        affirmedServicesVideoAdaptationServiceStatisticsSlotLevelOnlineTranscodingDetailNumotfwebmfailures ConfdString,
        affirmedServicesVideoAdaptationServiceStatisticsSlotLevelOnlineTranscodingDetailNumotfwebmaborts ConfdString,
        affirmedServicesVideoAdaptationServiceStatisticsSlotLevelOnlineTranscodingDetailNumotfoverloads ConfdString,
        affirmedServicesVideoAdaptationServiceStatisticsSlotLevelOnlineTranscodingDetailNumotfpolicymapentrymatched ConfdString,
        affirmedServicesVideoAdaptationServiceStatisticsSlotLevelOnlineTranscodingDetailNumotfpolicymapentrynotmatched ConfdString,
        affirmedServicesVideoAdaptationServiceStatisticsSlotLevelOnlineTranscodingDetailNumotfpolicyqoeused ConfdString,
        affirmedServicesVideoAdaptationServiceStatisticsSlotLevelOnlineTranscodingDetailNumotfinstanceqoeused ConfdString,
        affirmedServicesVideoAdaptationServiceStatisticsSlotLevelOnlineTranscodingDetailNumotfflvbytesattempted ConfdString,
        affirmedServicesVideoAdaptationServiceStatisticsSlotLevelOnlineTranscodingDetailNumotfflvbytesadapted ConfdString,
        affirmedServicesVideoAdaptationServiceStatisticsSlotLevelOnlineTranscodingDetailNumotfflvbytescanceled ConfdString,
        affirmedServicesVideoAdaptationServiceStatisticsSlotLevelOnlineTranscodingDetailNumotfmp4bytesattempted ConfdString,
        affirmedServicesVideoAdaptationServiceStatisticsSlotLevelOnlineTranscodingDetailNumotfmp4bytesadapted ConfdString,
        affirmedServicesVideoAdaptationServiceStatisticsSlotLevelOnlineTranscodingDetailNumotfmp4bytescanceled ConfdString,
        affirmedServicesVideoAdaptationServiceStatisticsSlotLevelOnlineTranscodingDetailNumotfwebmbytesattempted ConfdString,
        affirmedServicesVideoAdaptationServiceStatisticsSlotLevelOnlineTranscodingDetailNumotfwebmbytesadapted ConfdString,
        affirmedServicesVideoAdaptationServiceStatisticsSlotLevelOnlineTranscodingDetailNumotfwebmbytescanceled ConfdString
    }

affirmedServicesVideoAdaptationServiceStatisticsSlotLevelOnlineTranscodingDetailChassis OBJECT-TYPE
    SYNTAX      Unsigned32
    MAX-ACCESS  not-accessible
    STATUS      current
    DESCRIPTION "chassis ID"
    ::= { affirmedServicesVideoAdaptationServiceStatisticsSlotLevelOnlineTranscodingDetailEntry 1 }

affirmedServicesVideoAdaptationServiceStatisticsSlotLevelOnlineTranscodingDetailSlot OBJECT-TYPE
    SYNTAX      INTEGER {a1(1),a2(2),a3(3),a4(4),a5(5),a6(6),a7(7),a8(8),a9(9),a10(10),a11(11),a12(12),a13(13),a14(14),a15(15),a16(16),a17(17),a18(18),a19(19),a20(20),a21(21),a22(22),a23(23),a24(24),a25(25),a26(26),a27(27),a28(28),a29(29),a30(30),a31(31),a32(32),a33(33),a34(34),a35(35),a36(36),a37(37),a38(38),a39(39),a40(40),a41(41),a42(42),a43(43),a44(44),a45(45),a46(46),a47(47),a48(48),a49(49),a50(50),a51(51),a52(52),a53(53),a54(54),a55(55),a56(56),a57(57),a58(58),a59(59),a60(60),a61(61),a62(62),a63(63),a64(64),a65(65),a66(66),a67(67),a68(68),a69(69),a70(70),a71(71),a72(72),a73(73),a74(74),a75(75),a76(76),a77(77),a78(78),a79(79),a80(80),a81(81),a82(82),a83(83),a84(84),a85(85),a86(86),a87(87),a88(88),a89(89),a90(90),a91(91),a92(92),a93(93),a94(94),a95(95),a96(96),a97(97),a98(98),a99(99),a100(100),a101(101),a102(102),a103(103),a104(104),a105(105),a106(106),a107(107),a108(108),a109(109),a110(110),a111(111),a112(112),a113(113),a114(114),a115(115),a116(116),a117(117),a118(118),a119(119),a120(120),a121(121),a122(122),a123(123),a124(124),a125(125),a126(126),a127(127),a128(128)}
    MAX-ACCESS  not-accessible
    STATUS      current
    DESCRIPTION "slot number"
    ::= { affirmedServicesVideoAdaptationServiceStatisticsSlotLevelOnlineTranscodingDetailEntry 2 }

affirmedServicesVideoAdaptationServiceStatisticsSlotLevelOnlineTranscodingDetailNumotfflvattempts OBJECT-TYPE
    SYNTAX      ConfdString
    MAX-ACCESS  read-only
    STATUS      current
    DESCRIPTION "Total number of Online Transcoding FLV attempts"
    ::= { affirmedServicesVideoAdaptationServiceStatisticsSlotLevelOnlineTranscodingDetailEntry 3 }

affirmedServicesVideoAdaptationServiceStatisticsSlotLevelOnlineTranscodingDetailNumotfflvsuccesses OBJECT-TYPE
    SYNTAX      ConfdString
    MAX-ACCESS  read-only
    STATUS      current
    DESCRIPTION "Total number of Online Transcoding FLV successes"
    ::= { affirmedServicesVideoAdaptationServiceStatisticsSlotLevelOnlineTranscodingDetailEntry 4 }

affirmedServicesVideoAdaptationServiceStatisticsSlotLevelOnlineTranscodingDetailNumotfflvcancels OBJECT-TYPE
    SYNTAX      ConfdString
    MAX-ACCESS  read-only
    STATUS      current
    DESCRIPTION "Total number of Online Transcoding FLV cancels"
    ::= { affirmedServicesVideoAdaptationServiceStatisticsSlotLevelOnlineTranscodingDetailEntry 5 }

affirmedServicesVideoAdaptationServiceStatisticsSlotLevelOnlineTranscodingDetailNumotfflvfailures OBJECT-TYPE
    SYNTAX      ConfdString
    MAX-ACCESS  read-only
    STATUS      current
    DESCRIPTION "Total number of Online Transcoding FLV failures"
    ::= { affirmedServicesVideoAdaptationServiceStatisticsSlotLevelOnlineTranscodingDetailEntry 6 }

affirmedServicesVideoAdaptationServiceStatisticsSlotLevelOnlineTranscodingDetailNumotfflvaborts OBJECT-TYPE
    SYNTAX      ConfdString
    MAX-ACCESS  read-only
    STATUS      current
    DESCRIPTION "Total number of Online Transcoding FLV aborts"
    ::= { affirmedServicesVideoAdaptationServiceStatisticsSlotLevelOnlineTranscodingDetailEntry 7 }

affirmedServicesVideoAdaptationServiceStatisticsSlotLevelOnlineTranscodingDetailNumotfmp4attempts OBJECT-TYPE
    SYNTAX      ConfdString
    MAX-ACCESS  read-only
    STATUS      current
    DESCRIPTION "Total number of Online Transcoding MP4 attempts"
    ::= { affirmedServicesVideoAdaptationServiceStatisticsSlotLevelOnlineTranscodingDetailEntry 8 }

affirmedServicesVideoAdaptationServiceStatisticsSlotLevelOnlineTranscodingDetailNumotfmp4successes OBJECT-TYPE
    SYNTAX      ConfdString
    MAX-ACCESS  read-only
    STATUS      current
    DESCRIPTION "Total number of Online Transcoding MP4 successes"
    ::= { affirmedServicesVideoAdaptationServiceStatisticsSlotLevelOnlineTranscodingDetailEntry 9 }

affirmedServicesVideoAdaptationServiceStatisticsSlotLevelOnlineTranscodingDetailNumotfmp4cancels OBJECT-TYPE
    SYNTAX      ConfdString
    MAX-ACCESS  read-only
    STATUS      current
    DESCRIPTION "Total number of Online Transcoding MP4 cancels"
    ::= { affirmedServicesVideoAdaptationServiceStatisticsSlotLevelOnlineTranscodingDetailEntry 10 }

affirmedServicesVideoAdaptationServiceStatisticsSlotLevelOnlineTranscodingDetailNumotfmp4failures OBJECT-TYPE
    SYNTAX      ConfdString
    MAX-ACCESS  read-only
    STATUS      current
    DESCRIPTION "Total number of Online Transcoding MP4 failures"
    ::= { affirmedServicesVideoAdaptationServiceStatisticsSlotLevelOnlineTranscodingDetailEntry 11 }

affirmedServicesVideoAdaptationServiceStatisticsSlotLevelOnlineTranscodingDetailNumotfmp4aborts OBJECT-TYPE
    SYNTAX      ConfdString
    MAX-ACCESS  read-only
    STATUS      current
    DESCRIPTION "Total number of Online Transcoding MP4 aborts"
    ::= { affirmedServicesVideoAdaptationServiceStatisticsSlotLevelOnlineTranscodingDetailEntry 12 }

affirmedServicesVideoAdaptationServiceStatisticsSlotLevelOnlineTranscodingDetailNumotfwebmattempts OBJECT-TYPE
    SYNTAX      ConfdString
    MAX-ACCESS  read-only
    STATUS      current
    DESCRIPTION "Total number of Online Transcoding WEBM attempts"
    ::= { affirmedServicesVideoAdaptationServiceStatisticsSlotLevelOnlineTranscodingDetailEntry 13 }

affirmedServicesVideoAdaptationServiceStatisticsSlotLevelOnlineTranscodingDetailNumotfwebmsuccesses OBJECT-TYPE
    SYNTAX      ConfdString
    MAX-ACCESS  read-only
    STATUS      current
    DESCRIPTION "Total number of Online Transcoding WEBM successes"
    ::= { affirmedServicesVideoAdaptationServiceStatisticsSlotLevelOnlineTranscodingDetailEntry 14 }

affirmedServicesVideoAdaptationServiceStatisticsSlotLevelOnlineTranscodingDetailNumotfwebmcancels OBJECT-TYPE
    SYNTAX      ConfdString
    MAX-ACCESS  read-only
    STATUS      current
    DESCRIPTION "Total number of Online Transcoding WEBM cancels"
    ::= { affirmedServicesVideoAdaptationServiceStatisticsSlotLevelOnlineTranscodingDetailEntry 15 }

affirmedServicesVideoAdaptationServiceStatisticsSlotLevelOnlineTranscodingDetailNumotfwebmfailures OBJECT-TYPE
    SYNTAX      ConfdString
    MAX-ACCESS  read-only
    STATUS      current
    DESCRIPTION "Total number of Online Transcoding WEBM failures"
    ::= { affirmedServicesVideoAdaptationServiceStatisticsSlotLevelOnlineTranscodingDetailEntry 16 }

affirmedServicesVideoAdaptationServiceStatisticsSlotLevelOnlineTranscodingDetailNumotfwebmaborts OBJECT-TYPE
    SYNTAX      ConfdString
    MAX-ACCESS  read-only
    STATUS      current
    DESCRIPTION "Total number of Online Transcoding WEBM aborts"
    ::= { affirmedServicesVideoAdaptationServiceStatisticsSlotLevelOnlineTranscodingDetailEntry 17 }

affirmedServicesVideoAdaptationServiceStatisticsSlotLevelOnlineTranscodingDetailNumotfoverloads OBJECT-TYPE
    SYNTAX      ConfdString
    MAX-ACCESS  read-only
    STATUS      current
    DESCRIPTION "Total number of Online Transcoding overload"
    ::= { affirmedServicesVideoAdaptationServiceStatisticsSlotLevelOnlineTranscodingDetailEntry 18 }

affirmedServicesVideoAdaptationServiceStatisticsSlotLevelOnlineTranscodingDetailNumotfpolicymapentrymatched OBJECT-TYPE
    SYNTAX      ConfdString
    MAX-ACCESS  read-only
    STATUS      current
    DESCRIPTION "Total number of times an Online Transcoding Policy Map Entry was Matched"
    ::= { affirmedServicesVideoAdaptationServiceStatisticsSlotLevelOnlineTranscodingDetailEntry 19 }

affirmedServicesVideoAdaptationServiceStatisticsSlotLevelOnlineTranscodingDetailNumotfpolicymapentrynotmatched OBJECT-TYPE
    SYNTAX      ConfdString
    MAX-ACCESS  read-only
    STATUS      current
    DESCRIPTION "Total number of time any Online Transcoding Policy Map Entry was not matched"
    ::= { affirmedServicesVideoAdaptationServiceStatisticsSlotLevelOnlineTranscodingDetailEntry 20 }

affirmedServicesVideoAdaptationServiceStatisticsSlotLevelOnlineTranscodingDetailNumotfpolicyqoeused OBJECT-TYPE
    SYNTAX      ConfdString
    MAX-ACCESS  read-only
    STATUS      current
    DESCRIPTION "Total number of Online Transcoding Policy QOE grade used"
    ::= { affirmedServicesVideoAdaptationServiceStatisticsSlotLevelOnlineTranscodingDetailEntry 21 }

affirmedServicesVideoAdaptationServiceStatisticsSlotLevelOnlineTranscodingDetailNumotfinstanceqoeused OBJECT-TYPE
    SYNTAX      ConfdString
    MAX-ACCESS  read-only
    STATUS      current
    DESCRIPTION "Total number of Video adaptation instance QOE grade used"
    ::= { affirmedServicesVideoAdaptationServiceStatisticsSlotLevelOnlineTranscodingDetailEntry 22 }

affirmedServicesVideoAdaptationServiceStatisticsSlotLevelOnlineTranscodingDetailNumotfflvbytesattempted OBJECT-TYPE
    SYNTAX      ConfdString
    MAX-ACCESS  read-only
    STATUS      current
    DESCRIPTION "Total number of Online Transcoding FLV bytes attempted"
    ::= { affirmedServicesVideoAdaptationServiceStatisticsSlotLevelOnlineTranscodingDetailEntry 23 }

affirmedServicesVideoAdaptationServiceStatisticsSlotLevelOnlineTranscodingDetailNumotfflvbytesadapted OBJECT-TYPE
    SYNTAX      ConfdString
    MAX-ACCESS  read-only
    STATUS      current
    DESCRIPTION "Total number of Online Transcoding FLV bytes adapted"
    ::= { affirmedServicesVideoAdaptationServiceStatisticsSlotLevelOnlineTranscodingDetailEntry 24 }

affirmedServicesVideoAdaptationServiceStatisticsSlotLevelOnlineTranscodingDetailNumotfflvbytescanceled OBJECT-TYPE
    SYNTAX      ConfdString
    MAX-ACCESS  read-only
    STATUS      current
    DESCRIPTION "Total number of Online Transcoding FLV bytes canceled"
    ::= { affirmedServicesVideoAdaptationServiceStatisticsSlotLevelOnlineTranscodingDetailEntry 25 }

affirmedServicesVideoAdaptationServiceStatisticsSlotLevelOnlineTranscodingDetailNumotfmp4bytesattempted OBJECT-TYPE
    SYNTAX      ConfdString
    MAX-ACCESS  read-only
    STATUS      current
    DESCRIPTION "Total number of Online Transcoding MP4 bytes attempted"
    ::= { affirmedServicesVideoAdaptationServiceStatisticsSlotLevelOnlineTranscodingDetailEntry 26 }

affirmedServicesVideoAdaptationServiceStatisticsSlotLevelOnlineTranscodingDetailNumotfmp4bytesadapted OBJECT-TYPE
    SYNTAX      ConfdString
    MAX-ACCESS  read-only
    STATUS      current
    DESCRIPTION "Total number of Online Transcoding MP4 bytes adapted"
    ::= { affirmedServicesVideoAdaptationServiceStatisticsSlotLevelOnlineTranscodingDetailEntry 27 }

affirmedServicesVideoAdaptationServiceStatisticsSlotLevelOnlineTranscodingDetailNumotfmp4bytescanceled OBJECT-TYPE
    SYNTAX      ConfdString
    MAX-ACCESS  read-only
    STATUS      current
    DESCRIPTION "Total number of Online Transcoding MP4 bytes canceled"
    ::= { affirmedServicesVideoAdaptationServiceStatisticsSlotLevelOnlineTranscodingDetailEntry 28 }

affirmedServicesVideoAdaptationServiceStatisticsSlotLevelOnlineTranscodingDetailNumotfwebmbytesattempted OBJECT-TYPE
    SYNTAX      ConfdString
    MAX-ACCESS  read-only
    STATUS      current
    DESCRIPTION "Total number of Online Transcoding WEBM bytes attempted"
    ::= { affirmedServicesVideoAdaptationServiceStatisticsSlotLevelOnlineTranscodingDetailEntry 29 }

affirmedServicesVideoAdaptationServiceStatisticsSlotLevelOnlineTranscodingDetailNumotfwebmbytesadapted OBJECT-TYPE
    SYNTAX      ConfdString
    MAX-ACCESS  read-only
    STATUS      current
    DESCRIPTION "Total number of Online Transcoding WEBM bytes adapted"
    ::= { affirmedServicesVideoAdaptationServiceStatisticsSlotLevelOnlineTranscodingDetailEntry 30 }

affirmedServicesVideoAdaptationServiceStatisticsSlotLevelOnlineTranscodingDetailNumotfwebmbytescanceled OBJECT-TYPE
    SYNTAX      ConfdString
    MAX-ACCESS  read-only
    STATUS      current
    DESCRIPTION "Total number of Online Transcoding WEBM bytes canceled"
    ::= { affirmedServicesVideoAdaptationServiceStatisticsSlotLevelOnlineTranscodingDetailEntry 31 }

affirmedServicesVideoAdaptationServiceStatisticsSlotLevelOnlineTranscodingFailureTable OBJECT-TYPE
    SYNTAX      SEQUENCE OF AffirmedServicesVideoAdaptationServiceStatisticsSlotLevelOnlineTranscodingFailureEntry
    MAX-ACCESS  not-accessible
    STATUS      current
    DESCRIPTION ""
    ::= { affirmedServicesVideoAdaptationServiceStatisticsSlotLevelOnlineTranscoding 3 }

affirmedServicesVideoAdaptationServiceStatisticsSlotLevelOnlineTranscodingFailureEntry OBJECT-TYPE
    SYNTAX      AffirmedServicesVideoAdaptationServiceStatisticsSlotLevelOnlineTranscodingFailureEntry
    MAX-ACCESS  not-accessible
    STATUS      current
    DESCRIPTION ""
    INDEX { affirmedServicesVideoAdaptationServiceStatisticsSlotLevelOnlineTranscodingFailureChassis, affirmedServicesVideoAdaptationServiceStatisticsSlotLevelOnlineTranscodingFailureSlot }
        ::= { affirmedServicesVideoAdaptationServiceStatisticsSlotLevelOnlineTranscodingFailureTable 1 }

AffirmedServicesVideoAdaptationServiceStatisticsSlotLevelOnlineTranscodingFailureEntry ::=
    SEQUENCE {
        affirmedServicesVideoAdaptationServiceStatisticsSlotLevelOnlineTranscodingFailureChassis Unsigned32,
        affirmedServicesVideoAdaptationServiceStatisticsSlotLevelOnlineTranscodingFailureSlot INTEGER,
        affirmedServicesVideoAdaptationServiceStatisticsSlotLevelOnlineTranscodingFailureNumotfexceededmaxvideosize ConfdString,
        affirmedServicesVideoAdaptationServiceStatisticsSlotLevelOnlineTranscodingFailureNumotfbelowminvideosize ConfdString,
        affirmedServicesVideoAdaptationServiceStatisticsSlotLevelOnlineTranscodingFailureNumotfexceededmaxvideoduration ConfdString,
        affirmedServicesVideoAdaptationServiceStatisticsSlotLevelOnlineTranscodingFailureNumotfbelowminvideoduration ConfdString,
        affirmedServicesVideoAdaptationServiceStatisticsSlotLevelOnlineTranscodingFailureNumotfexceededmaxbitrate ConfdString,
        affirmedServicesVideoAdaptationServiceStatisticsSlotLevelOnlineTranscodingFailureNumotfexceededmaxframerate ConfdString,
        affirmedServicesVideoAdaptationServiceStatisticsSlotLevelOnlineTranscodingFailureNumotfunsupportedsrccontainer ConfdString,
        affirmedServicesVideoAdaptationServiceStatisticsSlotLevelOnlineTranscodingFailureNumotfunsupportedformat ConfdString,
        affirmedServicesVideoAdaptationServiceStatisticsSlotLevelOnlineTranscodingFailureNumotfunsupportedvideocodec ConfdString,
        affirmedServicesVideoAdaptationServiceStatisticsSlotLevelOnlineTranscodingFailureNumotfunsupportedaudiocodec ConfdString,
        affirmedServicesVideoAdaptationServiceStatisticsSlotLevelOnlineTranscodingFailureNumotffailureothers ConfdString,
        affirmedServicesVideoAdaptationServiceStatisticsSlotLevelOnlineTranscodingFailureNumotfcancelcontenttypemismatches ConfdString,
        affirmedServicesVideoAdaptationServiceStatisticsSlotLevelOnlineTranscodingFailureNumotfcancelnomapqoematch ConfdString,
        affirmedServicesVideoAdaptationServiceStatisticsSlotLevelOnlineTranscodingFailureNumotfcancelmapentrybypass ConfdString,
        affirmedServicesVideoAdaptationServiceStatisticsSlotLevelOnlineTranscodingFailureNumotfcancelcpuoverload ConfdString,
        affirmedServicesVideoAdaptationServiceStatisticsSlotLevelOnlineTranscodingFailureNumotfnosrcaudiostreampresent ConfdString,
        affirmedServicesVideoAdaptationServiceStatisticsSlotLevelOnlineTranscodingFailureNumotfnosrcvideostreampresent ConfdString,
        affirmedServicesVideoAdaptationServiceStatisticsSlotLevelOnlineTranscodingFailureNumotfunsupportedsrcaudiocodec ConfdString,
        affirmedServicesVideoAdaptationServiceStatisticsSlotLevelOnlineTranscodingFailureNumotfunsupportedsrcvideocodec ConfdString,
        affirmedServicesVideoAdaptationServiceStatisticsSlotLevelOnlineTranscodingFailureNumotfbelowbitratesavingsthreshold ConfdString,
        affirmedServicesVideoAdaptationServiceStatisticsSlotLevelOnlineTranscodingFailureNumotfsrcmediaformatnotsupported ConfdString,
        affirmedServicesVideoAdaptationServiceStatisticsSlotLevelOnlineTranscodingFailureNumotftgtmediaformatnotsupported ConfdString,
        affirmedServicesVideoAdaptationServiceStatisticsSlotLevelOnlineTranscodingFailureNumotftgtmediaformatparametersnotvalid ConfdString,
        affirmedServicesVideoAdaptationServiceStatisticsSlotLevelOnlineTranscodingFailureNumotftgtxcodingparametersnotvalid ConfdString,
        affirmedServicesVideoAdaptationServiceStatisticsSlotLevelOnlineTranscodingFailureNumotfcancelnomatchmapqoe ConfdString,
        affirmedServicesVideoAdaptationServiceStatisticsSlotLevelOnlineTranscodingFailureNumotfcancelsrcmediaisnotstreamable ConfdString,
        affirmedServicesVideoAdaptationServiceStatisticsSlotLevelOnlineTranscodingFailureNumotffailuredelayresponding ConfdString,
        affirmedServicesVideoAdaptationServiceStatisticsSlotLevelOnlineTranscodingFailureNumotfcouldnotfindsrcmediastream ConfdString,
        affirmedServicesVideoAdaptationServiceStatisticsSlotLevelOnlineTranscodingFailureNumotfcancelothers ConfdString,
        affirmedServicesVideoAdaptationServiceStatisticsSlotLevelOnlineTranscodingFailureNumotfbypassoptout ConfdString
    }

affirmedServicesVideoAdaptationServiceStatisticsSlotLevelOnlineTranscodingFailureChassis OBJECT-TYPE
    SYNTAX      Unsigned32
    MAX-ACCESS  not-accessible
    STATUS      current
    DESCRIPTION "chassis ID"
    ::= { affirmedServicesVideoAdaptationServiceStatisticsSlotLevelOnlineTranscodingFailureEntry 1 }

affirmedServicesVideoAdaptationServiceStatisticsSlotLevelOnlineTranscodingFailureSlot OBJECT-TYPE
    SYNTAX      INTEGER {a1(1),a2(2),a3(3),a4(4),a5(5),a6(6),a7(7),a8(8),a9(9),a10(10),a11(11),a12(12),a13(13),a14(14),a15(15),a16(16),a17(17),a18(18),a19(19),a20(20),a21(21),a22(22),a23(23),a24(24),a25(25),a26(26),a27(27),a28(28),a29(29),a30(30),a31(31),a32(32),a33(33),a34(34),a35(35),a36(36),a37(37),a38(38),a39(39),a40(40),a41(41),a42(42),a43(43),a44(44),a45(45),a46(46),a47(47),a48(48),a49(49),a50(50),a51(51),a52(52),a53(53),a54(54),a55(55),a56(56),a57(57),a58(58),a59(59),a60(60),a61(61),a62(62),a63(63),a64(64),a65(65),a66(66),a67(67),a68(68),a69(69),a70(70),a71(71),a72(72),a73(73),a74(74),a75(75),a76(76),a77(77),a78(78),a79(79),a80(80),a81(81),a82(82),a83(83),a84(84),a85(85),a86(86),a87(87),a88(88),a89(89),a90(90),a91(91),a92(92),a93(93),a94(94),a95(95),a96(96),a97(97),a98(98),a99(99),a100(100),a101(101),a102(102),a103(103),a104(104),a105(105),a106(106),a107(107),a108(108),a109(109),a110(110),a111(111),a112(112),a113(113),a114(114),a115(115),a116(116),a117(117),a118(118),a119(119),a120(120),a121(121),a122(122),a123(123),a124(124),a125(125),a126(126),a127(127),a128(128)}
    MAX-ACCESS  not-accessible
    STATUS      current
    DESCRIPTION "slot number"
    ::= { affirmedServicesVideoAdaptationServiceStatisticsSlotLevelOnlineTranscodingFailureEntry 2 }

affirmedServicesVideoAdaptationServiceStatisticsSlotLevelOnlineTranscodingFailureNumotfexceededmaxvideosize OBJECT-TYPE
    SYNTAX      ConfdString
    MAX-ACCESS  read-only
    STATUS      current
    DESCRIPTION "Total number of Online Transcoding exceeded max video size "
    ::= { affirmedServicesVideoAdaptationServiceStatisticsSlotLevelOnlineTranscodingFailureEntry 3 }

affirmedServicesVideoAdaptationServiceStatisticsSlotLevelOnlineTranscodingFailureNumotfbelowminvideosize OBJECT-TYPE
    SYNTAX      ConfdString
    MAX-ACCESS  read-only
    STATUS      current
    DESCRIPTION "Total number of Online Transcoding below min video size"
    ::= { affirmedServicesVideoAdaptationServiceStatisticsSlotLevelOnlineTranscodingFailureEntry 4 }

affirmedServicesVideoAdaptationServiceStatisticsSlotLevelOnlineTranscodingFailureNumotfexceededmaxvideoduration OBJECT-TYPE
    SYNTAX      ConfdString
    MAX-ACCESS  read-only
    STATUS      current
    DESCRIPTION "Total number of Online Transcoding exceeded max video duration "
    ::= { affirmedServicesVideoAdaptationServiceStatisticsSlotLevelOnlineTranscodingFailureEntry 5 }

affirmedServicesVideoAdaptationServiceStatisticsSlotLevelOnlineTranscodingFailureNumotfbelowminvideoduration OBJECT-TYPE
    SYNTAX      ConfdString
    MAX-ACCESS  read-only
    STATUS      current
    DESCRIPTION "Total number of Online Transcoding below min video duration"
    ::= { affirmedServicesVideoAdaptationServiceStatisticsSlotLevelOnlineTranscodingFailureEntry 6 }

affirmedServicesVideoAdaptationServiceStatisticsSlotLevelOnlineTranscodingFailureNumotfexceededmaxbitrate OBJECT-TYPE
    SYNTAX      ConfdString
    MAX-ACCESS  read-only
    STATUS      current
    DESCRIPTION "Total number of Online Transcoding exceeded max video bitrate "
    ::= { affirmedServicesVideoAdaptationServiceStatisticsSlotLevelOnlineTranscodingFailureEntry 7 }

affirmedServicesVideoAdaptationServiceStatisticsSlotLevelOnlineTranscodingFailureNumotfexceededmaxframerate OBJECT-TYPE
    SYNTAX      ConfdString
    MAX-ACCESS  read-only
    STATUS      current
    DESCRIPTION "Total number of Online Transcoding exceeded max video framerate"
    ::= { affirmedServicesVideoAdaptationServiceStatisticsSlotLevelOnlineTranscodingFailureEntry 8 }

affirmedServicesVideoAdaptationServiceStatisticsSlotLevelOnlineTranscodingFailureNumotfunsupportedsrccontainer OBJECT-TYPE
    SYNTAX      ConfdString
    MAX-ACCESS  read-only
    STATUS      current
    DESCRIPTION "Total number of Online Transcoding Unsupported Source Container"
    ::= { affirmedServicesVideoAdaptationServiceStatisticsSlotLevelOnlineTranscodingFailureEntry 9 }

affirmedServicesVideoAdaptationServiceStatisticsSlotLevelOnlineTranscodingFailureNumotfunsupportedformat OBJECT-TYPE
    SYNTAX      ConfdString
    MAX-ACCESS  read-only
    STATUS      current
    DESCRIPTION "Total number of Online Transcoding Unsupported Format"
    ::= { affirmedServicesVideoAdaptationServiceStatisticsSlotLevelOnlineTranscodingFailureEntry 10 }

affirmedServicesVideoAdaptationServiceStatisticsSlotLevelOnlineTranscodingFailureNumotfunsupportedvideocodec OBJECT-TYPE
    SYNTAX      ConfdString
    MAX-ACCESS  read-only
    STATUS      current
    DESCRIPTION "Total number of Online Transcoding Unsupported Video Codec"
    ::= { affirmedServicesVideoAdaptationServiceStatisticsSlotLevelOnlineTranscodingFailureEntry 11 }

affirmedServicesVideoAdaptationServiceStatisticsSlotLevelOnlineTranscodingFailureNumotfunsupportedaudiocodec OBJECT-TYPE
    SYNTAX      ConfdString
    MAX-ACCESS  read-only
    STATUS      current
    DESCRIPTION "Total number of Online Transcoding Unsupported Audio Codec"
    ::= { affirmedServicesVideoAdaptationServiceStatisticsSlotLevelOnlineTranscodingFailureEntry 12 }

affirmedServicesVideoAdaptationServiceStatisticsSlotLevelOnlineTranscodingFailureNumotffailureothers OBJECT-TYPE
    SYNTAX      ConfdString
    MAX-ACCESS  read-only
    STATUS      current
    DESCRIPTION "Total number of Online Transcoding Failure With Other Reason"
    ::= { affirmedServicesVideoAdaptationServiceStatisticsSlotLevelOnlineTranscodingFailureEntry 13 }

affirmedServicesVideoAdaptationServiceStatisticsSlotLevelOnlineTranscodingFailureNumotfcancelcontenttypemismatches OBJECT-TYPE
    SYNTAX      ConfdString
    MAX-ACCESS  read-only
    STATUS      current
    DESCRIPTION "Total number of Online Transcoding Cancel Content-Type Mismatches"
    ::= { affirmedServicesVideoAdaptationServiceStatisticsSlotLevelOnlineTranscodingFailureEntry 14 }

affirmedServicesVideoAdaptationServiceStatisticsSlotLevelOnlineTranscodingFailureNumotfcancelnomapqoematch OBJECT-TYPE
    SYNTAX      ConfdString
    MAX-ACCESS  read-only
    STATUS      current
    DESCRIPTION "Total number of Online Transcoding Cancels due to no transcoding map or QOE grade"
    ::= { affirmedServicesVideoAdaptationServiceStatisticsSlotLevelOnlineTranscodingFailureEntry 15 }

affirmedServicesVideoAdaptationServiceStatisticsSlotLevelOnlineTranscodingFailureNumotfcancelmapentrybypass OBJECT-TYPE
    SYNTAX      ConfdString
    MAX-ACCESS  read-only
    STATUS      current
    DESCRIPTION "Total number of Online Transcoding Cancels due to Bypass set in the transcoding map entry"
    ::= { affirmedServicesVideoAdaptationServiceStatisticsSlotLevelOnlineTranscodingFailureEntry 16 }

affirmedServicesVideoAdaptationServiceStatisticsSlotLevelOnlineTranscodingFailureNumotfcancelcpuoverload OBJECT-TYPE
    SYNTAX      ConfdString
    MAX-ACCESS  read-only
    STATUS      current
    DESCRIPTION "Total number of Online Transcoding Cancel CPU Overload"
    ::= { affirmedServicesVideoAdaptationServiceStatisticsSlotLevelOnlineTranscodingFailureEntry 17 }

affirmedServicesVideoAdaptationServiceStatisticsSlotLevelOnlineTranscodingFailureNumotfnosrcaudiostreampresent OBJECT-TYPE
    SYNTAX      ConfdString
    MAX-ACCESS  read-only
    STATUS      current
    DESCRIPTION "Total number of Online Transcoding No Src Audio Stream Present"
    ::= { affirmedServicesVideoAdaptationServiceStatisticsSlotLevelOnlineTranscodingFailureEntry 18 }

affirmedServicesVideoAdaptationServiceStatisticsSlotLevelOnlineTranscodingFailureNumotfnosrcvideostreampresent OBJECT-TYPE
    SYNTAX      ConfdString
    MAX-ACCESS  read-only
    STATUS      current
    DESCRIPTION "Total number of Online Transcoding No Src Video Stream Present"
    ::= { affirmedServicesVideoAdaptationServiceStatisticsSlotLevelOnlineTranscodingFailureEntry 19 }

affirmedServicesVideoAdaptationServiceStatisticsSlotLevelOnlineTranscodingFailureNumotfunsupportedsrcaudiocodec OBJECT-TYPE
    SYNTAX      ConfdString
    MAX-ACCESS  read-only
    STATUS      current
    DESCRIPTION "Total number of Online Transcoding Unsupported Src Audio Codec"
    ::= { affirmedServicesVideoAdaptationServiceStatisticsSlotLevelOnlineTranscodingFailureEntry 20 }

affirmedServicesVideoAdaptationServiceStatisticsSlotLevelOnlineTranscodingFailureNumotfunsupportedsrcvideocodec OBJECT-TYPE
    SYNTAX      ConfdString
    MAX-ACCESS  read-only
    STATUS      current
    DESCRIPTION "Total number of Online Transcoding Unsupported Src Video Codec"
    ::= { affirmedServicesVideoAdaptationServiceStatisticsSlotLevelOnlineTranscodingFailureEntry 21 }

affirmedServicesVideoAdaptationServiceStatisticsSlotLevelOnlineTranscodingFailureNumotfbelowbitratesavingsthreshold OBJECT-TYPE
    SYNTAX      ConfdString
    MAX-ACCESS  read-only
    STATUS      current
    DESCRIPTION "Total number of Online Transcoding Below Bit Rate Savings Threshold"
    ::= { affirmedServicesVideoAdaptationServiceStatisticsSlotLevelOnlineTranscodingFailureEntry 22 }

affirmedServicesVideoAdaptationServiceStatisticsSlotLevelOnlineTranscodingFailureNumotfsrcmediaformatnotsupported OBJECT-TYPE
    SYNTAX      ConfdString
    MAX-ACCESS  read-only
    STATUS      current
    DESCRIPTION "Total number of Online Transcoding Src Media Format Not Supported"
    ::= { affirmedServicesVideoAdaptationServiceStatisticsSlotLevelOnlineTranscodingFailureEntry 23 }

affirmedServicesVideoAdaptationServiceStatisticsSlotLevelOnlineTranscodingFailureNumotftgtmediaformatnotsupported OBJECT-TYPE
    SYNTAX      ConfdString
    MAX-ACCESS  read-only
    STATUS      current
    DESCRIPTION "Total number of Online Transcoding Tgt Media Format Not Supported"
    ::= { affirmedServicesVideoAdaptationServiceStatisticsSlotLevelOnlineTranscodingFailureEntry 24 }

affirmedServicesVideoAdaptationServiceStatisticsSlotLevelOnlineTranscodingFailureNumotftgtmediaformatparametersnotvalid OBJECT-TYPE
    SYNTAX      ConfdString
    MAX-ACCESS  read-only
    STATUS      current
    DESCRIPTION "Total number of Online Transcoding Tgt Media Format Parameters Not Valid"
    ::= { affirmedServicesVideoAdaptationServiceStatisticsSlotLevelOnlineTranscodingFailureEntry 25 }

affirmedServicesVideoAdaptationServiceStatisticsSlotLevelOnlineTranscodingFailureNumotftgtxcodingparametersnotvalid OBJECT-TYPE
    SYNTAX      ConfdString
    MAX-ACCESS  read-only
    STATUS      current
    DESCRIPTION "Total number of Online Transcoding Target Transcoding Paramaters Not Valid"
    ::= { affirmedServicesVideoAdaptationServiceStatisticsSlotLevelOnlineTranscodingFailureEntry 26 }

affirmedServicesVideoAdaptationServiceStatisticsSlotLevelOnlineTranscodingFailureNumotfcancelnomatchmapqoe OBJECT-TYPE
    SYNTAX      ConfdString
    MAX-ACCESS  read-only
    STATUS      current
    DESCRIPTION "Total number of Online Transcoding Cancels due to no matching transcoding map entry or QOE grade"
    ::= { affirmedServicesVideoAdaptationServiceStatisticsSlotLevelOnlineTranscodingFailureEntry 27 }

affirmedServicesVideoAdaptationServiceStatisticsSlotLevelOnlineTranscodingFailureNumotfcancelsrcmediaisnotstreamable OBJECT-TYPE
    SYNTAX      ConfdString
    MAX-ACCESS  read-only
    STATUS      current
    DESCRIPTION "Total number of Online Transcoding Cancels due to source media is not streamable"
    ::= { affirmedServicesVideoAdaptationServiceStatisticsSlotLevelOnlineTranscodingFailureEntry 28 }

affirmedServicesVideoAdaptationServiceStatisticsSlotLevelOnlineTranscodingFailureNumotffailuredelayresponding OBJECT-TYPE
    SYNTAX      ConfdString
    MAX-ACCESS  read-only
    STATUS      current
    DESCRIPTION "Total number of Online Transcoding Failure due to Delay in Responding"
    ::= { affirmedServicesVideoAdaptationServiceStatisticsSlotLevelOnlineTranscodingFailureEntry 29 }

affirmedServicesVideoAdaptationServiceStatisticsSlotLevelOnlineTranscodingFailureNumotfcouldnotfindsrcmediastream OBJECT-TYPE
    SYNTAX      ConfdString
    MAX-ACCESS  read-only
    STATUS      current
    DESCRIPTION "Total number of Online Transcoding Cancel due to Could not Find/Determine Source Media Stream Info"
    ::= { affirmedServicesVideoAdaptationServiceStatisticsSlotLevelOnlineTranscodingFailureEntry 30 }

affirmedServicesVideoAdaptationServiceStatisticsSlotLevelOnlineTranscodingFailureNumotfcancelothers OBJECT-TYPE
    SYNTAX      ConfdString
    MAX-ACCESS  read-only
    STATUS      current
    DESCRIPTION "Total number of Online Transcoding Cancel With Other Reason"
    ::= { affirmedServicesVideoAdaptationServiceStatisticsSlotLevelOnlineTranscodingFailureEntry 31 }

affirmedServicesVideoAdaptationServiceStatisticsSlotLevelOnlineTranscodingFailureNumotfbypassoptout OBJECT-TYPE
    SYNTAX      ConfdString
    MAX-ACCESS  read-only
    STATUS      current
    DESCRIPTION "Total number of Online Transcoding Bypassed due to subscriber opting-out"
    ::= { affirmedServicesVideoAdaptationServiceStatisticsSlotLevelOnlineTranscodingFailureEntry 32 }

affirmedServicesVideoAdaptationServiceStatisticsSlotLevelOnlineTranscodingOrtDetailTable OBJECT-TYPE
    SYNTAX      SEQUENCE OF AffirmedServicesVideoAdaptationServiceStatisticsSlotLevelOnlineTranscodingOrtDetailEntry
    MAX-ACCESS  not-accessible
    STATUS      current
    DESCRIPTION ""
    ::= { affirmedServicesVideoAdaptationServiceStatisticsSlotLevelOnlineTranscoding 4 }

affirmedServicesVideoAdaptationServiceStatisticsSlotLevelOnlineTranscodingOrtDetailEntry OBJECT-TYPE
    SYNTAX      AffirmedServicesVideoAdaptationServiceStatisticsSlotLevelOnlineTranscodingOrtDetailEntry
    MAX-ACCESS  not-accessible
    STATUS      current
    DESCRIPTION ""
    INDEX { affirmedServicesVideoAdaptationServiceStatisticsSlotLevelOnlineTranscodingOrtDetailChassis, affirmedServicesVideoAdaptationServiceStatisticsSlotLevelOnlineTranscodingOrtDetailSlot }
        ::= { affirmedServicesVideoAdaptationServiceStatisticsSlotLevelOnlineTranscodingOrtDetailTable 1 }

AffirmedServicesVideoAdaptationServiceStatisticsSlotLevelOnlineTranscodingOrtDetailEntry ::=
    SEQUENCE {
        affirmedServicesVideoAdaptationServiceStatisticsSlotLevelOnlineTranscodingOrtDetailChassis Unsigned32,
        affirmedServicesVideoAdaptationServiceStatisticsSlotLevelOnlineTranscodingOrtDetailSlot INTEGER,
        affirmedServicesVideoAdaptationServiceStatisticsSlotLevelOnlineTranscodingOrtDetailNumortsessionattempts ConfdString,
        affirmedServicesVideoAdaptationServiceStatisticsSlotLevelOnlineTranscodingOrtDetailNumortsessionsuccesses ConfdString,
        affirmedServicesVideoAdaptationServiceStatisticsSlotLevelOnlineTranscodingOrtDetailNumortsessioncancels ConfdString,
        affirmedServicesVideoAdaptationServiceStatisticsSlotLevelOnlineTranscodingOrtDetailNumortsessionfailures ConfdString,
        affirmedServicesVideoAdaptationServiceStatisticsSlotLevelOnlineTranscodingOrtDetailNumortsessionaborts ConfdString,
        affirmedServicesVideoAdaptationServiceStatisticsSlotLevelOnlineTranscodingOrtDetailNumortsessionoverloads ConfdString,
        affirmedServicesVideoAdaptationServiceStatisticsSlotLevelOnlineTranscodingOrtDetailNumortsessioncurrent ConfdString,
        affirmedServicesVideoAdaptationServiceStatisticsSlotLevelOnlineTranscodingOrtDetailNumortsessionduration ConfdString,
        affirmedServicesVideoAdaptationServiceStatisticsSlotLevelOnlineTranscodingOrtDetailNumortsessionbytesattempt ConfdString,
        affirmedServicesVideoAdaptationServiceStatisticsSlotLevelOnlineTranscodingOrtDetailNumortsessionbytesadapted ConfdString,
        affirmedServicesVideoAdaptationServiceStatisticsSlotLevelOnlineTranscodingOrtDetailNumortsessionbytescancel ConfdString,
        affirmedServicesVideoAdaptationServiceStatisticsSlotLevelOnlineTranscodingOrtDetailNumortsegmentsattempts ConfdString,
        affirmedServicesVideoAdaptationServiceStatisticsSlotLevelOnlineTranscodingOrtDetailNumortsegmentssuccesses ConfdString,
        affirmedServicesVideoAdaptationServiceStatisticsSlotLevelOnlineTranscodingOrtDetailNumortsegmentscancels ConfdString,
        affirmedServicesVideoAdaptationServiceStatisticsSlotLevelOnlineTranscodingOrtDetailNumortsegmentsfailures ConfdString,
        affirmedServicesVideoAdaptationServiceStatisticsSlotLevelOnlineTranscodingOrtDetailNumortsegmentsaborts ConfdString,
        affirmedServicesVideoAdaptationServiceStatisticsSlotLevelOnlineTranscodingOrtDetailNumortsegmentsoverloads ConfdString,
        affirmedServicesVideoAdaptationServiceStatisticsSlotLevelOnlineTranscodingOrtDetailNumortsegmentscurrent ConfdString,
        affirmedServicesVideoAdaptationServiceStatisticsSlotLevelOnlineTranscodingOrtDetailNumortsegmentsduration ConfdString,
        affirmedServicesVideoAdaptationServiceStatisticsSlotLevelOnlineTranscodingOrtDetailNumortsegmentsbytesattempt ConfdString,
        affirmedServicesVideoAdaptationServiceStatisticsSlotLevelOnlineTranscodingOrtDetailNumortsegmentsbytesadapted ConfdString,
        affirmedServicesVideoAdaptationServiceStatisticsSlotLevelOnlineTranscodingOrtDetailNumortsegmentsbytescancel ConfdString
    }

affirmedServicesVideoAdaptationServiceStatisticsSlotLevelOnlineTranscodingOrtDetailChassis OBJECT-TYPE
    SYNTAX      Unsigned32
    MAX-ACCESS  not-accessible
    STATUS      current
    DESCRIPTION "chassis ID"
    ::= { affirmedServicesVideoAdaptationServiceStatisticsSlotLevelOnlineTranscodingOrtDetailEntry 1 }

affirmedServicesVideoAdaptationServiceStatisticsSlotLevelOnlineTranscodingOrtDetailSlot OBJECT-TYPE
    SYNTAX      INTEGER {a1(1),a2(2),a3(3),a4(4),a5(5),a6(6),a7(7),a8(8),a9(9),a10(10),a11(11),a12(12),a13(13),a14(14),a15(15),a16(16),a17(17),a18(18),a19(19),a20(20),a21(21),a22(22),a23(23),a24(24),a25(25),a26(26),a27(27),a28(28),a29(29),a30(30),a31(31),a32(32),a33(33),a34(34),a35(35),a36(36),a37(37),a38(38),a39(39),a40(40),a41(41),a42(42),a43(43),a44(44),a45(45),a46(46),a47(47),a48(48),a49(49),a50(50),a51(51),a52(52),a53(53),a54(54),a55(55),a56(56),a57(57),a58(58),a59(59),a60(60),a61(61),a62(62),a63(63),a64(64),a65(65),a66(66),a67(67),a68(68),a69(69),a70(70),a71(71),a72(72),a73(73),a74(74),a75(75),a76(76),a77(77),a78(78),a79(79),a80(80),a81(81),a82(82),a83(83),a84(84),a85(85),a86(86),a87(87),a88(88),a89(89),a90(90),a91(91),a92(92),a93(93),a94(94),a95(95),a96(96),a97(97),a98(98),a99(99),a100(100),a101(101),a102(102),a103(103),a104(104),a105(105),a106(106),a107(107),a108(108),a109(109),a110(110),a111(111),a112(112),a113(113),a114(114),a115(115),a116(116),a117(117),a118(118),a119(119),a120(120),a121(121),a122(122),a123(123),a124(124),a125(125),a126(126),a127(127),a128(128)}
    MAX-ACCESS  not-accessible
    STATUS      current
    DESCRIPTION "slot number"
    ::= { affirmedServicesVideoAdaptationServiceStatisticsSlotLevelOnlineTranscodingOrtDetailEntry 2 }

affirmedServicesVideoAdaptationServiceStatisticsSlotLevelOnlineTranscodingOrtDetailNumortsessionattempts OBJECT-TYPE
    SYNTAX      ConfdString
    MAX-ACCESS  read-only
    STATUS      current
    DESCRIPTION "Total number of Online Range Transcoding Session attempts"
    ::= { affirmedServicesVideoAdaptationServiceStatisticsSlotLevelOnlineTranscodingOrtDetailEntry 3 }

affirmedServicesVideoAdaptationServiceStatisticsSlotLevelOnlineTranscodingOrtDetailNumortsessionsuccesses OBJECT-TYPE
    SYNTAX      ConfdString
    MAX-ACCESS  read-only
    STATUS      current
    DESCRIPTION "Total number of Online Range Transcoding Session successes"
    ::= { affirmedServicesVideoAdaptationServiceStatisticsSlotLevelOnlineTranscodingOrtDetailEntry 4 }

affirmedServicesVideoAdaptationServiceStatisticsSlotLevelOnlineTranscodingOrtDetailNumortsessioncancels OBJECT-TYPE
    SYNTAX      ConfdString
    MAX-ACCESS  read-only
    STATUS      current
    DESCRIPTION "Total number of Online Range Transcoding Session cancels"
    ::= { affirmedServicesVideoAdaptationServiceStatisticsSlotLevelOnlineTranscodingOrtDetailEntry 5 }

affirmedServicesVideoAdaptationServiceStatisticsSlotLevelOnlineTranscodingOrtDetailNumortsessionfailures OBJECT-TYPE
    SYNTAX      ConfdString
    MAX-ACCESS  read-only
    STATUS      current
    DESCRIPTION "Total number of Online Range Transcoding Session failures"
    ::= { affirmedServicesVideoAdaptationServiceStatisticsSlotLevelOnlineTranscodingOrtDetailEntry 6 }

affirmedServicesVideoAdaptationServiceStatisticsSlotLevelOnlineTranscodingOrtDetailNumortsessionaborts OBJECT-TYPE
    SYNTAX      ConfdString
    MAX-ACCESS  read-only
    STATUS      current
    DESCRIPTION "Total number of Online Range Transcoding Session aborts"
    ::= { affirmedServicesVideoAdaptationServiceStatisticsSlotLevelOnlineTranscodingOrtDetailEntry 7 }

affirmedServicesVideoAdaptationServiceStatisticsSlotLevelOnlineTranscodingOrtDetailNumortsessionoverloads OBJECT-TYPE
    SYNTAX      ConfdString
    MAX-ACCESS  read-only
    STATUS      current
    DESCRIPTION "Total number of Online Range Transcoding Session Overloads"
    ::= { affirmedServicesVideoAdaptationServiceStatisticsSlotLevelOnlineTranscodingOrtDetailEntry 8 }

affirmedServicesVideoAdaptationServiceStatisticsSlotLevelOnlineTranscodingOrtDetailNumortsessioncurrent OBJECT-TYPE
    SYNTAX      ConfdString
    MAX-ACCESS  read-only
    STATUS      current
    DESCRIPTION "Total number of Online Range Transcoding Session current"
    ::= { affirmedServicesVideoAdaptationServiceStatisticsSlotLevelOnlineTranscodingOrtDetailEntry 9 }

affirmedServicesVideoAdaptationServiceStatisticsSlotLevelOnlineTranscodingOrtDetailNumortsessionduration OBJECT-TYPE
    SYNTAX      ConfdString
    MAX-ACCESS  read-only
    STATUS      current
    DESCRIPTION "Total range transcoded video duration in seconds"
    ::= { affirmedServicesVideoAdaptationServiceStatisticsSlotLevelOnlineTranscodingOrtDetailEntry 10 }

affirmedServicesVideoAdaptationServiceStatisticsSlotLevelOnlineTranscodingOrtDetailNumortsessionbytesattempt OBJECT-TYPE
    SYNTAX      ConfdString
    MAX-ACCESS  read-only
    STATUS      current
    DESCRIPTION "Total number of Online Range Transcoding Session Bytes Attempted (Bytes)"
    ::= { affirmedServicesVideoAdaptationServiceStatisticsSlotLevelOnlineTranscodingOrtDetailEntry 11 }

affirmedServicesVideoAdaptationServiceStatisticsSlotLevelOnlineTranscodingOrtDetailNumortsessionbytesadapted OBJECT-TYPE
    SYNTAX      ConfdString
    MAX-ACCESS  read-only
    STATUS      current
    DESCRIPTION "Total number of Online Range Transcoding Session Bytes Adapted (Bytes)"
    ::= { affirmedServicesVideoAdaptationServiceStatisticsSlotLevelOnlineTranscodingOrtDetailEntry 12 }

affirmedServicesVideoAdaptationServiceStatisticsSlotLevelOnlineTranscodingOrtDetailNumortsessionbytescancel OBJECT-TYPE
    SYNTAX      ConfdString
    MAX-ACCESS  read-only
    STATUS      current
    DESCRIPTION "Total number of Online Range Transcoding Session Bytes Cancelled (Bytes)"
    ::= { affirmedServicesVideoAdaptationServiceStatisticsSlotLevelOnlineTranscodingOrtDetailEntry 13 }

affirmedServicesVideoAdaptationServiceStatisticsSlotLevelOnlineTranscodingOrtDetailNumortsegmentsattempts OBJECT-TYPE
    SYNTAX      ConfdString
    MAX-ACCESS  read-only
    STATUS      current
    DESCRIPTION "Total number of Online Range Transcoding Segments attempts"
    ::= { affirmedServicesVideoAdaptationServiceStatisticsSlotLevelOnlineTranscodingOrtDetailEntry 14 }

affirmedServicesVideoAdaptationServiceStatisticsSlotLevelOnlineTranscodingOrtDetailNumortsegmentssuccesses OBJECT-TYPE
    SYNTAX      ConfdString
    MAX-ACCESS  read-only
    STATUS      current
    DESCRIPTION "Total number of Online Range Transcoding Segments successes"
    ::= { affirmedServicesVideoAdaptationServiceStatisticsSlotLevelOnlineTranscodingOrtDetailEntry 15 }

affirmedServicesVideoAdaptationServiceStatisticsSlotLevelOnlineTranscodingOrtDetailNumortsegmentscancels OBJECT-TYPE
    SYNTAX      ConfdString
    MAX-ACCESS  read-only
    STATUS      current
    DESCRIPTION "Total number of Online Range Transcoding Segments cancels"
    ::= { affirmedServicesVideoAdaptationServiceStatisticsSlotLevelOnlineTranscodingOrtDetailEntry 16 }

affirmedServicesVideoAdaptationServiceStatisticsSlotLevelOnlineTranscodingOrtDetailNumortsegmentsfailures OBJECT-TYPE
    SYNTAX      ConfdString
    MAX-ACCESS  read-only
    STATUS      current
    DESCRIPTION "Total number of Online Range Transcoding Segments failures"
    ::= { affirmedServicesVideoAdaptationServiceStatisticsSlotLevelOnlineTranscodingOrtDetailEntry 17 }

affirmedServicesVideoAdaptationServiceStatisticsSlotLevelOnlineTranscodingOrtDetailNumortsegmentsaborts OBJECT-TYPE
    SYNTAX      ConfdString
    MAX-ACCESS  read-only
    STATUS      current
    DESCRIPTION "Total number of Online Range Transcoding Segments aborts"
    ::= { affirmedServicesVideoAdaptationServiceStatisticsSlotLevelOnlineTranscodingOrtDetailEntry 18 }

affirmedServicesVideoAdaptationServiceStatisticsSlotLevelOnlineTranscodingOrtDetailNumortsegmentsoverloads OBJECT-TYPE
    SYNTAX      ConfdString
    MAX-ACCESS  read-only
    STATUS      current
    DESCRIPTION "Total number of Online Range Transcoding Segments Overloads"
    ::= { affirmedServicesVideoAdaptationServiceStatisticsSlotLevelOnlineTranscodingOrtDetailEntry 19 }

affirmedServicesVideoAdaptationServiceStatisticsSlotLevelOnlineTranscodingOrtDetailNumortsegmentscurrent OBJECT-TYPE
    SYNTAX      ConfdString
    MAX-ACCESS  read-only
    STATUS      current
    DESCRIPTION "Total number of Online Range Transcoding Segments current"
    ::= { affirmedServicesVideoAdaptationServiceStatisticsSlotLevelOnlineTranscodingOrtDetailEntry 20 }

affirmedServicesVideoAdaptationServiceStatisticsSlotLevelOnlineTranscodingOrtDetailNumortsegmentsduration OBJECT-TYPE
    SYNTAX      ConfdString
    MAX-ACCESS  read-only
    STATUS      current
    DESCRIPTION "Total range transcoded video duration in seconds"
    ::= { affirmedServicesVideoAdaptationServiceStatisticsSlotLevelOnlineTranscodingOrtDetailEntry 21 }

affirmedServicesVideoAdaptationServiceStatisticsSlotLevelOnlineTranscodingOrtDetailNumortsegmentsbytesattempt OBJECT-TYPE
    SYNTAX      ConfdString
    MAX-ACCESS  read-only
    STATUS      current
    DESCRIPTION "Total number of Online Range Transcoding Segments Bytes Attempted (Bytes)"
    ::= { affirmedServicesVideoAdaptationServiceStatisticsSlotLevelOnlineTranscodingOrtDetailEntry 22 }

affirmedServicesVideoAdaptationServiceStatisticsSlotLevelOnlineTranscodingOrtDetailNumortsegmentsbytesadapted OBJECT-TYPE
    SYNTAX      ConfdString
    MAX-ACCESS  read-only
    STATUS      current
    DESCRIPTION "Total number of Online Range Transcoding Segments Bytes Adapted (Bytes)"
    ::= { affirmedServicesVideoAdaptationServiceStatisticsSlotLevelOnlineTranscodingOrtDetailEntry 23 }

affirmedServicesVideoAdaptationServiceStatisticsSlotLevelOnlineTranscodingOrtDetailNumortsegmentsbytescancel OBJECT-TYPE
    SYNTAX      ConfdString
    MAX-ACCESS  read-only
    STATUS      current
    DESCRIPTION "Total number of Online Range Transcoding Segments Bytes Cancelled (Bytes)"
    ::= { affirmedServicesVideoAdaptationServiceStatisticsSlotLevelOnlineTranscodingOrtDetailEntry 24 }

affirmedServicesVideoAdaptationServiceStatisticsSlotLevelOnlineTranscodingOrtFailureTable OBJECT-TYPE
    SYNTAX      SEQUENCE OF AffirmedServicesVideoAdaptationServiceStatisticsSlotLevelOnlineTranscodingOrtFailureEntry
    MAX-ACCESS  not-accessible
    STATUS      current
    DESCRIPTION ""
    ::= { affirmedServicesVideoAdaptationServiceStatisticsSlotLevelOnlineTranscoding 5 }

affirmedServicesVideoAdaptationServiceStatisticsSlotLevelOnlineTranscodingOrtFailureEntry OBJECT-TYPE
    SYNTAX      AffirmedServicesVideoAdaptationServiceStatisticsSlotLevelOnlineTranscodingOrtFailureEntry
    MAX-ACCESS  not-accessible
    STATUS      current
    DESCRIPTION ""
    INDEX { affirmedServicesVideoAdaptationServiceStatisticsSlotLevelOnlineTranscodingOrtFailureChassis, affirmedServicesVideoAdaptationServiceStatisticsSlotLevelOnlineTranscodingOrtFailureSlot }
        ::= { affirmedServicesVideoAdaptationServiceStatisticsSlotLevelOnlineTranscodingOrtFailureTable 1 }

AffirmedServicesVideoAdaptationServiceStatisticsSlotLevelOnlineTranscodingOrtFailureEntry ::=
    SEQUENCE {
        affirmedServicesVideoAdaptationServiceStatisticsSlotLevelOnlineTranscodingOrtFailureChassis Unsigned32,
        affirmedServicesVideoAdaptationServiceStatisticsSlotLevelOnlineTranscodingOrtFailureSlot INTEGER,
        affirmedServicesVideoAdaptationServiceStatisticsSlotLevelOnlineTranscodingOrtFailureNumortexceededmaxvideosize ConfdString,
        affirmedServicesVideoAdaptationServiceStatisticsSlotLevelOnlineTranscodingOrtFailureNumortbelowminvideosize ConfdString,
        affirmedServicesVideoAdaptationServiceStatisticsSlotLevelOnlineTranscodingOrtFailureNumortexceededmaxvideoduration ConfdString,
        affirmedServicesVideoAdaptationServiceStatisticsSlotLevelOnlineTranscodingOrtFailureNumortbelowminvideoduration ConfdString,
        affirmedServicesVideoAdaptationServiceStatisticsSlotLevelOnlineTranscodingOrtFailureNumortexceededmaxbitrate ConfdString,
        affirmedServicesVideoAdaptationServiceStatisticsSlotLevelOnlineTranscodingOrtFailureNumortexceededmaxframerate ConfdString,
        affirmedServicesVideoAdaptationServiceStatisticsSlotLevelOnlineTranscodingOrtFailureNumortunsupportedsrccontainer ConfdString,
        affirmedServicesVideoAdaptationServiceStatisticsSlotLevelOnlineTranscodingOrtFailureNumortunsupportedformat ConfdString,
        affirmedServicesVideoAdaptationServiceStatisticsSlotLevelOnlineTranscodingOrtFailureNumortunsupportedvideocodec ConfdString,
        affirmedServicesVideoAdaptationServiceStatisticsSlotLevelOnlineTranscodingOrtFailureNumortunsupportedaudiocodec ConfdString,
        affirmedServicesVideoAdaptationServiceStatisticsSlotLevelOnlineTranscodingOrtFailureNumortfailureothers ConfdString,
        affirmedServicesVideoAdaptationServiceStatisticsSlotLevelOnlineTranscodingOrtFailureNumortcancelcontenttypemismatches ConfdString,
        affirmedServicesVideoAdaptationServiceStatisticsSlotLevelOnlineTranscodingOrtFailureNumortcancelnomapqoematch ConfdString,
        affirmedServicesVideoAdaptationServiceStatisticsSlotLevelOnlineTranscodingOrtFailureNumortcancelmapentrybypass ConfdString,
        affirmedServicesVideoAdaptationServiceStatisticsSlotLevelOnlineTranscodingOrtFailureNumortcancelcpuoverload ConfdString,
        affirmedServicesVideoAdaptationServiceStatisticsSlotLevelOnlineTranscodingOrtFailureNumortnosrcaudiostreampresent ConfdString,
        affirmedServicesVideoAdaptationServiceStatisticsSlotLevelOnlineTranscodingOrtFailureNumortnosrcvideostreampresent ConfdString,
        affirmedServicesVideoAdaptationServiceStatisticsSlotLevelOnlineTranscodingOrtFailureNumortunsupportedsrcaudiocodec ConfdString,
        affirmedServicesVideoAdaptationServiceStatisticsSlotLevelOnlineTranscodingOrtFailureNumortunsupportedsrcvideocodec ConfdString,
        affirmedServicesVideoAdaptationServiceStatisticsSlotLevelOnlineTranscodingOrtFailureNumortbelowbitratesavingsthreshold ConfdString,
        affirmedServicesVideoAdaptationServiceStatisticsSlotLevelOnlineTranscodingOrtFailureNumortsrcmediaformatnotsupported ConfdString,
        affirmedServicesVideoAdaptationServiceStatisticsSlotLevelOnlineTranscodingOrtFailureNumorttgtmediaformatnotsupported ConfdString,
        affirmedServicesVideoAdaptationServiceStatisticsSlotLevelOnlineTranscodingOrtFailureNumorttgtmediaformatparametersnotvalid ConfdString,
        affirmedServicesVideoAdaptationServiceStatisticsSlotLevelOnlineTranscodingOrtFailureNumorttgtxcodingparametersnotvalid ConfdString,
        affirmedServicesVideoAdaptationServiceStatisticsSlotLevelOnlineTranscodingOrtFailureNumortcancelnomatchmapqoe ConfdString,
        affirmedServicesVideoAdaptationServiceStatisticsSlotLevelOnlineTranscodingOrtFailureNumortcancelsrcmediaisnotstreamable ConfdString,
        affirmedServicesVideoAdaptationServiceStatisticsSlotLevelOnlineTranscodingOrtFailureNumortfailuredelayresponding ConfdString,
        affirmedServicesVideoAdaptationServiceStatisticsSlotLevelOnlineTranscodingOrtFailureNumortcouldnotfindsrcmediastream ConfdString,
        affirmedServicesVideoAdaptationServiceStatisticsSlotLevelOnlineTranscodingOrtFailureNumortcancelothers ConfdString,
        affirmedServicesVideoAdaptationServiceStatisticsSlotLevelOnlineTranscodingOrtFailureNumortbypassoptout ConfdString,
        affirmedServicesVideoAdaptationServiceStatisticsSlotLevelOnlineTranscodingOrtFailureNumortbypassmedianotsupported ConfdString,
        affirmedServicesVideoAdaptationServiceStatisticsSlotLevelOnlineTranscodingOrtFailureNumortbypassrangerequestnotenabled ConfdString,
        affirmedServicesVideoAdaptationServiceStatisticsSlotLevelOnlineTranscodingOrtFailureNumortbypassmultipartrangerequest ConfdString,
        affirmedServicesVideoAdaptationServiceStatisticsSlotLevelOnlineTranscodingOrtFailureNumortbypassinitialrangenotzero ConfdString
    }

affirmedServicesVideoAdaptationServiceStatisticsSlotLevelOnlineTranscodingOrtFailureChassis OBJECT-TYPE
    SYNTAX      Unsigned32
    MAX-ACCESS  not-accessible
    STATUS      current
    DESCRIPTION "chassis ID"
    ::= { affirmedServicesVideoAdaptationServiceStatisticsSlotLevelOnlineTranscodingOrtFailureEntry 1 }

affirmedServicesVideoAdaptationServiceStatisticsSlotLevelOnlineTranscodingOrtFailureSlot OBJECT-TYPE
    SYNTAX      INTEGER {a1(1),a2(2),a3(3),a4(4),a5(5),a6(6),a7(7),a8(8),a9(9),a10(10),a11(11),a12(12),a13(13),a14(14),a15(15),a16(16),a17(17),a18(18),a19(19),a20(20),a21(21),a22(22),a23(23),a24(24),a25(25),a26(26),a27(27),a28(28),a29(29),a30(30),a31(31),a32(32),a33(33),a34(34),a35(35),a36(36),a37(37),a38(38),a39(39),a40(40),a41(41),a42(42),a43(43),a44(44),a45(45),a46(46),a47(47),a48(48),a49(49),a50(50),a51(51),a52(52),a53(53),a54(54),a55(55),a56(56),a57(57),a58(58),a59(59),a60(60),a61(61),a62(62),a63(63),a64(64),a65(65),a66(66),a67(67),a68(68),a69(69),a70(70),a71(71),a72(72),a73(73),a74(74),a75(75),a76(76),a77(77),a78(78),a79(79),a80(80),a81(81),a82(82),a83(83),a84(84),a85(85),a86(86),a87(87),a88(88),a89(89),a90(90),a91(91),a92(92),a93(93),a94(94),a95(95),a96(96),a97(97),a98(98),a99(99),a100(100),a101(101),a102(102),a103(103),a104(104),a105(105),a106(106),a107(107),a108(108),a109(109),a110(110),a111(111),a112(112),a113(113),a114(114),a115(115),a116(116),a117(117),a118(118),a119(119),a120(120),a121(121),a122(122),a123(123),a124(124),a125(125),a126(126),a127(127),a128(128)}
    MAX-ACCESS  not-accessible
    STATUS      current
    DESCRIPTION "slot number"
    ::= { affirmedServicesVideoAdaptationServiceStatisticsSlotLevelOnlineTranscodingOrtFailureEntry 2 }

affirmedServicesVideoAdaptationServiceStatisticsSlotLevelOnlineTranscodingOrtFailureNumortexceededmaxvideosize OBJECT-TYPE
    SYNTAX      ConfdString
    MAX-ACCESS  read-only
    STATUS      current
    DESCRIPTION "Total number of Online Range Transcoding exceeded max video size "
    ::= { affirmedServicesVideoAdaptationServiceStatisticsSlotLevelOnlineTranscodingOrtFailureEntry 3 }

affirmedServicesVideoAdaptationServiceStatisticsSlotLevelOnlineTranscodingOrtFailureNumortbelowminvideosize OBJECT-TYPE
    SYNTAX      ConfdString
    MAX-ACCESS  read-only
    STATUS      current
    DESCRIPTION "Total number of Online Range Transcoding below min video size"
    ::= { affirmedServicesVideoAdaptationServiceStatisticsSlotLevelOnlineTranscodingOrtFailureEntry 4 }

affirmedServicesVideoAdaptationServiceStatisticsSlotLevelOnlineTranscodingOrtFailureNumortexceededmaxvideoduration OBJECT-TYPE
    SYNTAX      ConfdString
    MAX-ACCESS  read-only
    STATUS      current
    DESCRIPTION "Total number of Online Range Transcoding exceeded max video duration "
    ::= { affirmedServicesVideoAdaptationServiceStatisticsSlotLevelOnlineTranscodingOrtFailureEntry 5 }

affirmedServicesVideoAdaptationServiceStatisticsSlotLevelOnlineTranscodingOrtFailureNumortbelowminvideoduration OBJECT-TYPE
    SYNTAX      ConfdString
    MAX-ACCESS  read-only
    STATUS      current
    DESCRIPTION "Total number of Online Range Transcoding below min video duration"
    ::= { affirmedServicesVideoAdaptationServiceStatisticsSlotLevelOnlineTranscodingOrtFailureEntry 6 }

affirmedServicesVideoAdaptationServiceStatisticsSlotLevelOnlineTranscodingOrtFailureNumortexceededmaxbitrate OBJECT-TYPE
    SYNTAX      ConfdString
    MAX-ACCESS  read-only
    STATUS      current
    DESCRIPTION "Total number of Online Range Transcoding exceeded max video bitrate "
    ::= { affirmedServicesVideoAdaptationServiceStatisticsSlotLevelOnlineTranscodingOrtFailureEntry 7 }

affirmedServicesVideoAdaptationServiceStatisticsSlotLevelOnlineTranscodingOrtFailureNumortexceededmaxframerate OBJECT-TYPE
    SYNTAX      ConfdString
    MAX-ACCESS  read-only
    STATUS      current
    DESCRIPTION "Total number of Online Range Transcoding exceeded max video framerate"
    ::= { affirmedServicesVideoAdaptationServiceStatisticsSlotLevelOnlineTranscodingOrtFailureEntry 8 }

affirmedServicesVideoAdaptationServiceStatisticsSlotLevelOnlineTranscodingOrtFailureNumortunsupportedsrccontainer OBJECT-TYPE
    SYNTAX      ConfdString
    MAX-ACCESS  read-only
    STATUS      current
    DESCRIPTION "Total number of Online Range Transcoding Unsupported Source Container"
    ::= { affirmedServicesVideoAdaptationServiceStatisticsSlotLevelOnlineTranscodingOrtFailureEntry 9 }

affirmedServicesVideoAdaptationServiceStatisticsSlotLevelOnlineTranscodingOrtFailureNumortunsupportedformat OBJECT-TYPE
    SYNTAX      ConfdString
    MAX-ACCESS  read-only
    STATUS      current
    DESCRIPTION "Total number of Online Range Transcoding Unsupported Format"
    ::= { affirmedServicesVideoAdaptationServiceStatisticsSlotLevelOnlineTranscodingOrtFailureEntry 10 }

affirmedServicesVideoAdaptationServiceStatisticsSlotLevelOnlineTranscodingOrtFailureNumortunsupportedvideocodec OBJECT-TYPE
    SYNTAX      ConfdString
    MAX-ACCESS  read-only
    STATUS      current
    DESCRIPTION "Total number of Online Range Transcoding Unsupported Video Codec"
    ::= { affirmedServicesVideoAdaptationServiceStatisticsSlotLevelOnlineTranscodingOrtFailureEntry 11 }

affirmedServicesVideoAdaptationServiceStatisticsSlotLevelOnlineTranscodingOrtFailureNumortunsupportedaudiocodec OBJECT-TYPE
    SYNTAX      ConfdString
    MAX-ACCESS  read-only
    STATUS      current
    DESCRIPTION "Total number of Online Range Transcoding Unsupported Audio Codec"
    ::= { affirmedServicesVideoAdaptationServiceStatisticsSlotLevelOnlineTranscodingOrtFailureEntry 12 }

affirmedServicesVideoAdaptationServiceStatisticsSlotLevelOnlineTranscodingOrtFailureNumortfailureothers OBJECT-TYPE
    SYNTAX      ConfdString
    MAX-ACCESS  read-only
    STATUS      current
    DESCRIPTION "Total number of Online Range Transcoding Failure With Other Reason"
    ::= { affirmedServicesVideoAdaptationServiceStatisticsSlotLevelOnlineTranscodingOrtFailureEntry 13 }

affirmedServicesVideoAdaptationServiceStatisticsSlotLevelOnlineTranscodingOrtFailureNumortcancelcontenttypemismatches OBJECT-TYPE
    SYNTAX      ConfdString
    MAX-ACCESS  read-only
    STATUS      current
    DESCRIPTION "Total number of Online Range Transcoding Cancel Content-Type Mismatches"
    ::= { affirmedServicesVideoAdaptationServiceStatisticsSlotLevelOnlineTranscodingOrtFailureEntry 14 }

affirmedServicesVideoAdaptationServiceStatisticsSlotLevelOnlineTranscodingOrtFailureNumortcancelnomapqoematch OBJECT-TYPE
    SYNTAX      ConfdString
    MAX-ACCESS  read-only
    STATUS      current
    DESCRIPTION "Total number of Online Range Transcoding Cancels due to no transcoding map or QOE grade"
    ::= { affirmedServicesVideoAdaptationServiceStatisticsSlotLevelOnlineTranscodingOrtFailureEntry 15 }

affirmedServicesVideoAdaptationServiceStatisticsSlotLevelOnlineTranscodingOrtFailureNumortcancelmapentrybypass OBJECT-TYPE
    SYNTAX      ConfdString
    MAX-ACCESS  read-only
    STATUS      current
    DESCRIPTION "Total number of Online Range Transcoding Cancels due to Bypass set in the transcoding map entry"
    ::= { affirmedServicesVideoAdaptationServiceStatisticsSlotLevelOnlineTranscodingOrtFailureEntry 16 }

affirmedServicesVideoAdaptationServiceStatisticsSlotLevelOnlineTranscodingOrtFailureNumortcancelcpuoverload OBJECT-TYPE
    SYNTAX      ConfdString
    MAX-ACCESS  read-only
    STATUS      current
    DESCRIPTION "Total number of Online Range Transcoding Cancel CPU Overload"
    ::= { affirmedServicesVideoAdaptationServiceStatisticsSlotLevelOnlineTranscodingOrtFailureEntry 17 }

affirmedServicesVideoAdaptationServiceStatisticsSlotLevelOnlineTranscodingOrtFailureNumortnosrcaudiostreampresent OBJECT-TYPE
    SYNTAX      ConfdString
    MAX-ACCESS  read-only
    STATUS      current
    DESCRIPTION "Total number of Online Range Transcoding No Src Audio Stream Present"
    ::= { affirmedServicesVideoAdaptationServiceStatisticsSlotLevelOnlineTranscodingOrtFailureEntry 18 }

affirmedServicesVideoAdaptationServiceStatisticsSlotLevelOnlineTranscodingOrtFailureNumortnosrcvideostreampresent OBJECT-TYPE
    SYNTAX      ConfdString
    MAX-ACCESS  read-only
    STATUS      current
    DESCRIPTION "Total number of Online Range Transcoding No Src Video Stream Present"
    ::= { affirmedServicesVideoAdaptationServiceStatisticsSlotLevelOnlineTranscodingOrtFailureEntry 19 }

affirmedServicesVideoAdaptationServiceStatisticsSlotLevelOnlineTranscodingOrtFailureNumortunsupportedsrcaudiocodec OBJECT-TYPE
    SYNTAX      ConfdString
    MAX-ACCESS  read-only
    STATUS      current
    DESCRIPTION "Total number of Online Range Transcoding Unsupported Src Audio Codec"
    ::= { affirmedServicesVideoAdaptationServiceStatisticsSlotLevelOnlineTranscodingOrtFailureEntry 20 }

affirmedServicesVideoAdaptationServiceStatisticsSlotLevelOnlineTranscodingOrtFailureNumortunsupportedsrcvideocodec OBJECT-TYPE
    SYNTAX      ConfdString
    MAX-ACCESS  read-only
    STATUS      current
    DESCRIPTION "Total number of Online Range Transcoding Unsupported Src Video Codec"
    ::= { affirmedServicesVideoAdaptationServiceStatisticsSlotLevelOnlineTranscodingOrtFailureEntry 21 }

affirmedServicesVideoAdaptationServiceStatisticsSlotLevelOnlineTranscodingOrtFailureNumortbelowbitratesavingsthreshold OBJECT-TYPE
    SYNTAX      ConfdString
    MAX-ACCESS  read-only
    STATUS      current
    DESCRIPTION "Total number of Online Range Transcoding Below Bit Rate Savings Threshold"
    ::= { affirmedServicesVideoAdaptationServiceStatisticsSlotLevelOnlineTranscodingOrtFailureEntry 22 }

affirmedServicesVideoAdaptationServiceStatisticsSlotLevelOnlineTranscodingOrtFailureNumortsrcmediaformatnotsupported OBJECT-TYPE
    SYNTAX      ConfdString
    MAX-ACCESS  read-only
    STATUS      current
    DESCRIPTION "Total number of Online Range Transcoding Src Media Format Not Supported"
    ::= { affirmedServicesVideoAdaptationServiceStatisticsSlotLevelOnlineTranscodingOrtFailureEntry 23 }

affirmedServicesVideoAdaptationServiceStatisticsSlotLevelOnlineTranscodingOrtFailureNumorttgtmediaformatnotsupported OBJECT-TYPE
    SYNTAX      ConfdString
    MAX-ACCESS  read-only
    STATUS      current
    DESCRIPTION "Total number of Online Range Transcoding Tgt Media Format Not Supported"
    ::= { affirmedServicesVideoAdaptationServiceStatisticsSlotLevelOnlineTranscodingOrtFailureEntry 24 }

affirmedServicesVideoAdaptationServiceStatisticsSlotLevelOnlineTranscodingOrtFailureNumorttgtmediaformatparametersnotvalid OBJECT-TYPE
    SYNTAX      ConfdString
    MAX-ACCESS  read-only
    STATUS      current
    DESCRIPTION "Total number of Online Range Transcoding Tgt Media Format Parameters Not Valid"
    ::= { affirmedServicesVideoAdaptationServiceStatisticsSlotLevelOnlineTranscodingOrtFailureEntry 25 }

affirmedServicesVideoAdaptationServiceStatisticsSlotLevelOnlineTranscodingOrtFailureNumorttgtxcodingparametersnotvalid OBJECT-TYPE
    SYNTAX      ConfdString
    MAX-ACCESS  read-only
    STATUS      current
    DESCRIPTION "Total number of Online Range Transcoding Target Transcoding Paramaters Not Valid"
    ::= { affirmedServicesVideoAdaptationServiceStatisticsSlotLevelOnlineTranscodingOrtFailureEntry 26 }

affirmedServicesVideoAdaptationServiceStatisticsSlotLevelOnlineTranscodingOrtFailureNumortcancelnomatchmapqoe OBJECT-TYPE
    SYNTAX      ConfdString
    MAX-ACCESS  read-only
    STATUS      current
    DESCRIPTION "Total number of Online Range Transcoding Cancels due to no matching transcoding map entry or QOE grade"
    ::= { affirmedServicesVideoAdaptationServiceStatisticsSlotLevelOnlineTranscodingOrtFailureEntry 27 }

affirmedServicesVideoAdaptationServiceStatisticsSlotLevelOnlineTranscodingOrtFailureNumortcancelsrcmediaisnotstreamable OBJECT-TYPE
    SYNTAX      ConfdString
    MAX-ACCESS  read-only
    STATUS      current
    DESCRIPTION "Total number of Online Range Transcoding Cancels due to source media is not streamable"
    ::= { affirmedServicesVideoAdaptationServiceStatisticsSlotLevelOnlineTranscodingOrtFailureEntry 28 }

affirmedServicesVideoAdaptationServiceStatisticsSlotLevelOnlineTranscodingOrtFailureNumortfailuredelayresponding OBJECT-TYPE
    SYNTAX      ConfdString
    MAX-ACCESS  read-only
    STATUS      current
    DESCRIPTION "Total number of Online Range Transcoding Failure due to Delay in Responding"
    ::= { affirmedServicesVideoAdaptationServiceStatisticsSlotLevelOnlineTranscodingOrtFailureEntry 29 }

affirmedServicesVideoAdaptationServiceStatisticsSlotLevelOnlineTranscodingOrtFailureNumortcouldnotfindsrcmediastream OBJECT-TYPE
    SYNTAX      ConfdString
    MAX-ACCESS  read-only
    STATUS      current
    DESCRIPTION "Total number of Online Range Transcoding Cancel due to Could not Find/Determine Source Media Stream Info"
    ::= { affirmedServicesVideoAdaptationServiceStatisticsSlotLevelOnlineTranscodingOrtFailureEntry 30 }

affirmedServicesVideoAdaptationServiceStatisticsSlotLevelOnlineTranscodingOrtFailureNumortcancelothers OBJECT-TYPE
    SYNTAX      ConfdString
    MAX-ACCESS  read-only
    STATUS      current
    DESCRIPTION "Total number of Online Range Transcoding Cancel With Other Reason"
    ::= { affirmedServicesVideoAdaptationServiceStatisticsSlotLevelOnlineTranscodingOrtFailureEntry 31 }

affirmedServicesVideoAdaptationServiceStatisticsSlotLevelOnlineTranscodingOrtFailureNumortbypassoptout OBJECT-TYPE
    SYNTAX      ConfdString
    MAX-ACCESS  read-only
    STATUS      current
    DESCRIPTION "Total number of Online Range Transcoding Bypassed due to subscriber opting-out"
    ::= { affirmedServicesVideoAdaptationServiceStatisticsSlotLevelOnlineTranscodingOrtFailureEntry 32 }

affirmedServicesVideoAdaptationServiceStatisticsSlotLevelOnlineTranscodingOrtFailureNumortbypassmedianotsupported OBJECT-TYPE
    SYNTAX      ConfdString
    MAX-ACCESS  read-only
    STATUS      current
    DESCRIPTION "Total number of Online Range Transcoding Bypassed - MediaType Not Supported"
    ::= { affirmedServicesVideoAdaptationServiceStatisticsSlotLevelOnlineTranscodingOrtFailureEntry 33 }

affirmedServicesVideoAdaptationServiceStatisticsSlotLevelOnlineTranscodingOrtFailureNumortbypassrangerequestnotenabled OBJECT-TYPE
    SYNTAX      ConfdString
    MAX-ACCESS  read-only
    STATUS      current
    DESCRIPTION "Total number of Online Range Transcoding Bypassed - Range Request support not enabled"
    ::= { affirmedServicesVideoAdaptationServiceStatisticsSlotLevelOnlineTranscodingOrtFailureEntry 34 }

affirmedServicesVideoAdaptationServiceStatisticsSlotLevelOnlineTranscodingOrtFailureNumortbypassmultipartrangerequest OBJECT-TYPE
    SYNTAX      ConfdString
    MAX-ACCESS  read-only
    STATUS      current
    DESCRIPTION "Total number of Online Range Transcoding Bypassed - Multi Part Range Request"
    ::= { affirmedServicesVideoAdaptationServiceStatisticsSlotLevelOnlineTranscodingOrtFailureEntry 35 }

affirmedServicesVideoAdaptationServiceStatisticsSlotLevelOnlineTranscodingOrtFailureNumortbypassinitialrangenotzero OBJECT-TYPE
    SYNTAX      ConfdString
    MAX-ACCESS  read-only
    STATUS      current
    DESCRIPTION "Total number of Online Range Transcoding Bypassed - Initial Range not zero"
    ::= { affirmedServicesVideoAdaptationServiceStatisticsSlotLevelOnlineTranscodingOrtFailureEntry 36 }

affirmedServicesVideoAdaptationServiceStatisticsSlotLevelOfflineTranscodingSummaryTable OBJECT-TYPE
    SYNTAX      SEQUENCE OF AffirmedServicesVideoAdaptationServiceStatisticsSlotLevelOfflineTranscodingSummaryEntry
    MAX-ACCESS  not-accessible
    STATUS      current
    DESCRIPTION ""
    ::= { affirmedServicesVideoAdaptationServiceStatisticsSlotLevelOfflineTranscoding 1 }

affirmedServicesVideoAdaptationServiceStatisticsSlotLevelOfflineTranscodingSummaryEntry OBJECT-TYPE
    SYNTAX      AffirmedServicesVideoAdaptationServiceStatisticsSlotLevelOfflineTranscodingSummaryEntry
    MAX-ACCESS  not-accessible
    STATUS      current
    DESCRIPTION ""
    INDEX { affirmedServicesVideoAdaptationServiceStatisticsSlotLevelOfflineTranscodingSummaryChassis, affirmedServicesVideoAdaptationServiceStatisticsSlotLevelOfflineTranscodingSummarySlot }
        ::= { affirmedServicesVideoAdaptationServiceStatisticsSlotLevelOfflineTranscodingSummaryTable 1 }

AffirmedServicesVideoAdaptationServiceStatisticsSlotLevelOfflineTranscodingSummaryEntry ::=
    SEQUENCE {
        affirmedServicesVideoAdaptationServiceStatisticsSlotLevelOfflineTranscodingSummaryChassis Unsigned32,
        affirmedServicesVideoAdaptationServiceStatisticsSlotLevelOfflineTranscodingSummarySlot INTEGER,
        affirmedServicesVideoAdaptationServiceStatisticsSlotLevelOfflineTranscodingSummaryNumofflineattempts ConfdString,
        affirmedServicesVideoAdaptationServiceStatisticsSlotLevelOfflineTranscodingSummaryNumofflinesuccesses ConfdString,
        affirmedServicesVideoAdaptationServiceStatisticsSlotLevelOfflineTranscodingSummaryNumofflinecancels ConfdString,
        affirmedServicesVideoAdaptationServiceStatisticsSlotLevelOfflineTranscodingSummaryNumofflinefailures ConfdString,
        affirmedServicesVideoAdaptationServiceStatisticsSlotLevelOfflineTranscodingSummaryNumofflineflvsuccesses ConfdString,
        affirmedServicesVideoAdaptationServiceStatisticsSlotLevelOfflineTranscodingSummaryNumofflineflvfailures ConfdString,
        affirmedServicesVideoAdaptationServiceStatisticsSlotLevelOfflineTranscodingSummaryNumofflinemp4successes ConfdString,
        affirmedServicesVideoAdaptationServiceStatisticsSlotLevelOfflineTranscodingSummaryNumofflinemp4failures ConfdString,
        affirmedServicesVideoAdaptationServiceStatisticsSlotLevelOfflineTranscodingSummaryNumofflinewebmsuccesses ConfdString,
        affirmedServicesVideoAdaptationServiceStatisticsSlotLevelOfflineTranscodingSummaryNumofflinewebmfailures ConfdString,
        affirmedServicesVideoAdaptationServiceStatisticsSlotLevelOfflineTranscodingSummaryNumofflineorigservingsuccess ConfdString,
        affirmedServicesVideoAdaptationServiceStatisticsSlotLevelOfflineTranscodingSummaryNumofflineorigservingabort ConfdString,
        affirmedServicesVideoAdaptationServiceStatisticsSlotLevelOfflineTranscodingSummaryNumofflineorigservingfailure ConfdString,
        affirmedServicesVideoAdaptationServiceStatisticsSlotLevelOfflineTranscodingSummaryNumofflineflvservingsuccess ConfdString,
        affirmedServicesVideoAdaptationServiceStatisticsSlotLevelOfflineTranscodingSummaryNumofflineflvservingabort ConfdString,
        affirmedServicesVideoAdaptationServiceStatisticsSlotLevelOfflineTranscodingSummaryNumofflineflvservingfailure ConfdString,
        affirmedServicesVideoAdaptationServiceStatisticsSlotLevelOfflineTranscodingSummaryNumofflinemp4servingsuccess ConfdString,
        affirmedServicesVideoAdaptationServiceStatisticsSlotLevelOfflineTranscodingSummaryNumofflinemp4servingabort ConfdString,
        affirmedServicesVideoAdaptationServiceStatisticsSlotLevelOfflineTranscodingSummaryNumofflinemp4servingfailure ConfdString,
        affirmedServicesVideoAdaptationServiceStatisticsSlotLevelOfflineTranscodingSummaryNumofflinewebmservingsuccess ConfdString,
        affirmedServicesVideoAdaptationServiceStatisticsSlotLevelOfflineTranscodingSummaryNumofflinewebmservingabort ConfdString,
        affirmedServicesVideoAdaptationServiceStatisticsSlotLevelOfflineTranscodingSummaryNumofflinewebmservingfailure ConfdString,
        affirmedServicesVideoAdaptationServiceStatisticsSlotLevelOfflineTranscodingSummaryNumofflineoriginalbytes ConfdString,
        affirmedServicesVideoAdaptationServiceStatisticsSlotLevelOfflineTranscodingSummaryNumofflineadaptedbytesserved ConfdString
    }

affirmedServicesVideoAdaptationServiceStatisticsSlotLevelOfflineTranscodingSummaryChassis OBJECT-TYPE
    SYNTAX      Unsigned32
    MAX-ACCESS  not-accessible
    STATUS      current
    DESCRIPTION "chassis ID"
    ::= { affirmedServicesVideoAdaptationServiceStatisticsSlotLevelOfflineTranscodingSummaryEntry 1 }

affirmedServicesVideoAdaptationServiceStatisticsSlotLevelOfflineTranscodingSummarySlot OBJECT-TYPE
    SYNTAX      INTEGER {a1(1),a2(2),a3(3),a4(4),a5(5),a6(6),a7(7),a8(8),a9(9),a10(10),a11(11),a12(12),a13(13),a14(14),a15(15),a16(16),a17(17),a18(18),a19(19),a20(20),a21(21),a22(22),a23(23),a24(24),a25(25),a26(26),a27(27),a28(28),a29(29),a30(30),a31(31),a32(32),a33(33),a34(34),a35(35),a36(36),a37(37),a38(38),a39(39),a40(40),a41(41),a42(42),a43(43),a44(44),a45(45),a46(46),a47(47),a48(48),a49(49),a50(50),a51(51),a52(52),a53(53),a54(54),a55(55),a56(56),a57(57),a58(58),a59(59),a60(60),a61(61),a62(62),a63(63),a64(64),a65(65),a66(66),a67(67),a68(68),a69(69),a70(70),a71(71),a72(72),a73(73),a74(74),a75(75),a76(76),a77(77),a78(78),a79(79),a80(80),a81(81),a82(82),a83(83),a84(84),a85(85),a86(86),a87(87),a88(88),a89(89),a90(90),a91(91),a92(92),a93(93),a94(94),a95(95),a96(96),a97(97),a98(98),a99(99),a100(100),a101(101),a102(102),a103(103),a104(104),a105(105),a106(106),a107(107),a108(108),a109(109),a110(110),a111(111),a112(112),a113(113),a114(114),a115(115),a116(116),a117(117),a118(118),a119(119),a120(120),a121(121),a122(122),a123(123),a124(124),a125(125),a126(126),a127(127),a128(128)}
    MAX-ACCESS  not-accessible
    STATUS      current
    DESCRIPTION "slot number"
    ::= { affirmedServicesVideoAdaptationServiceStatisticsSlotLevelOfflineTranscodingSummaryEntry 2 }

affirmedServicesVideoAdaptationServiceStatisticsSlotLevelOfflineTranscodingSummaryNumofflineattempts OBJECT-TYPE
    SYNTAX      ConfdString
    MAX-ACCESS  read-only
    STATUS      current
    DESCRIPTION "Total number of Offline Transcoding attempts"
    ::= { affirmedServicesVideoAdaptationServiceStatisticsSlotLevelOfflineTranscodingSummaryEntry 3 }

affirmedServicesVideoAdaptationServiceStatisticsSlotLevelOfflineTranscodingSummaryNumofflinesuccesses OBJECT-TYPE
    SYNTAX      ConfdString
    MAX-ACCESS  read-only
    STATUS      current
    DESCRIPTION "Total number of Offline Transcoding successes"
    ::= { affirmedServicesVideoAdaptationServiceStatisticsSlotLevelOfflineTranscodingSummaryEntry 4 }

affirmedServicesVideoAdaptationServiceStatisticsSlotLevelOfflineTranscodingSummaryNumofflinecancels OBJECT-TYPE
    SYNTAX      ConfdString
    MAX-ACCESS  read-only
    STATUS      current
    DESCRIPTION "Total number of Offline Transcoding cancels"
    ::= { affirmedServicesVideoAdaptationServiceStatisticsSlotLevelOfflineTranscodingSummaryEntry 5 }

affirmedServicesVideoAdaptationServiceStatisticsSlotLevelOfflineTranscodingSummaryNumofflinefailures OBJECT-TYPE
    SYNTAX      ConfdString
    MAX-ACCESS  read-only
    STATUS      current
    DESCRIPTION "Total number of Offline Transcoding failures"
    ::= { affirmedServicesVideoAdaptationServiceStatisticsSlotLevelOfflineTranscodingSummaryEntry 6 }

affirmedServicesVideoAdaptationServiceStatisticsSlotLevelOfflineTranscodingSummaryNumofflineflvsuccesses OBJECT-TYPE
    SYNTAX      ConfdString
    MAX-ACCESS  read-only
    STATUS      current
    DESCRIPTION "Number of videos transcoded successfully from FLV"
    ::= { affirmedServicesVideoAdaptationServiceStatisticsSlotLevelOfflineTranscodingSummaryEntry 7 }

affirmedServicesVideoAdaptationServiceStatisticsSlotLevelOfflineTranscodingSummaryNumofflineflvfailures OBJECT-TYPE
    SYNTAX      ConfdString
    MAX-ACCESS  read-only
    STATUS      current
    DESCRIPTION "Number of video transcoding failures from FLV"
    ::= { affirmedServicesVideoAdaptationServiceStatisticsSlotLevelOfflineTranscodingSummaryEntry 8 }

affirmedServicesVideoAdaptationServiceStatisticsSlotLevelOfflineTranscodingSummaryNumofflinemp4successes OBJECT-TYPE
    SYNTAX      ConfdString
    MAX-ACCESS  read-only
    STATUS      current
    DESCRIPTION "Number of videos transcoded successfully from MP4"
    ::= { affirmedServicesVideoAdaptationServiceStatisticsSlotLevelOfflineTranscodingSummaryEntry 9 }

affirmedServicesVideoAdaptationServiceStatisticsSlotLevelOfflineTranscodingSummaryNumofflinemp4failures OBJECT-TYPE
    SYNTAX      ConfdString
    MAX-ACCESS  read-only
    STATUS      current
    DESCRIPTION "Number of video transcoding failures from MP4"
    ::= { affirmedServicesVideoAdaptationServiceStatisticsSlotLevelOfflineTranscodingSummaryEntry 10 }

affirmedServicesVideoAdaptationServiceStatisticsSlotLevelOfflineTranscodingSummaryNumofflinewebmsuccesses OBJECT-TYPE
    SYNTAX      ConfdString
    MAX-ACCESS  read-only
    STATUS      current
    DESCRIPTION "Number of videos transcoded successfully from WEBM"
    ::= { affirmedServicesVideoAdaptationServiceStatisticsSlotLevelOfflineTranscodingSummaryEntry 11 }

affirmedServicesVideoAdaptationServiceStatisticsSlotLevelOfflineTranscodingSummaryNumofflinewebmfailures OBJECT-TYPE
    SYNTAX      ConfdString
    MAX-ACCESS  read-only
    STATUS      current
    DESCRIPTION "Number of video transcoding failures from WEBM"
    ::= { affirmedServicesVideoAdaptationServiceStatisticsSlotLevelOfflineTranscodingSummaryEntry 12 }

affirmedServicesVideoAdaptationServiceStatisticsSlotLevelOfflineTranscodingSummaryNumofflineorigservingsuccess OBJECT-TYPE
    SYNTAX      ConfdString
    MAX-ACCESS  read-only
    STATUS      current
    DESCRIPTION "Number of original videos serviced successfully"
    ::= { affirmedServicesVideoAdaptationServiceStatisticsSlotLevelOfflineTranscodingSummaryEntry 13 }

affirmedServicesVideoAdaptationServiceStatisticsSlotLevelOfflineTranscodingSummaryNumofflineorigservingabort OBJECT-TYPE
    SYNTAX      ConfdString
    MAX-ACCESS  read-only
    STATUS      current
    DESCRIPTION "Number of original video service aborts"
    ::= { affirmedServicesVideoAdaptationServiceStatisticsSlotLevelOfflineTranscodingSummaryEntry 14 }

affirmedServicesVideoAdaptationServiceStatisticsSlotLevelOfflineTranscodingSummaryNumofflineorigservingfailure OBJECT-TYPE
    SYNTAX      ConfdString
    MAX-ACCESS  read-only
    STATUS      current
    DESCRIPTION "Number of original video service failures"
    ::= { affirmedServicesVideoAdaptationServiceStatisticsSlotLevelOfflineTranscodingSummaryEntry 15 }

affirmedServicesVideoAdaptationServiceStatisticsSlotLevelOfflineTranscodingSummaryNumofflineflvservingsuccess OBJECT-TYPE
    SYNTAX      ConfdString
    MAX-ACCESS  read-only
    STATUS      current
    DESCRIPTION "Number of transcoded FLV videos serviced successfully"
    ::= { affirmedServicesVideoAdaptationServiceStatisticsSlotLevelOfflineTranscodingSummaryEntry 16 }

affirmedServicesVideoAdaptationServiceStatisticsSlotLevelOfflineTranscodingSummaryNumofflineflvservingabort OBJECT-TYPE
    SYNTAX      ConfdString
    MAX-ACCESS  read-only
    STATUS      current
    DESCRIPTION "Number of transcoded FLV video service aborts"
    ::= { affirmedServicesVideoAdaptationServiceStatisticsSlotLevelOfflineTranscodingSummaryEntry 17 }

affirmedServicesVideoAdaptationServiceStatisticsSlotLevelOfflineTranscodingSummaryNumofflineflvservingfailure OBJECT-TYPE
    SYNTAX      ConfdString
    MAX-ACCESS  read-only
    STATUS      current
    DESCRIPTION "Number of transcoded FLV video service failures"
    ::= { affirmedServicesVideoAdaptationServiceStatisticsSlotLevelOfflineTranscodingSummaryEntry 18 }

affirmedServicesVideoAdaptationServiceStatisticsSlotLevelOfflineTranscodingSummaryNumofflinemp4servingsuccess OBJECT-TYPE
    SYNTAX      ConfdString
    MAX-ACCESS  read-only
    STATUS      current
    DESCRIPTION "Number of transcoded MP4 videos serviced successfully"
    ::= { affirmedServicesVideoAdaptationServiceStatisticsSlotLevelOfflineTranscodingSummaryEntry 19 }

affirmedServicesVideoAdaptationServiceStatisticsSlotLevelOfflineTranscodingSummaryNumofflinemp4servingabort OBJECT-TYPE
    SYNTAX      ConfdString
    MAX-ACCESS  read-only
    STATUS      current
    DESCRIPTION "Number of transcoded MP4 video service aborts"
    ::= { affirmedServicesVideoAdaptationServiceStatisticsSlotLevelOfflineTranscodingSummaryEntry 20 }

affirmedServicesVideoAdaptationServiceStatisticsSlotLevelOfflineTranscodingSummaryNumofflinemp4servingfailure OBJECT-TYPE
    SYNTAX      ConfdString
    MAX-ACCESS  read-only
    STATUS      current
    DESCRIPTION "Number of transcoded MP4 video service failures"
    ::= { affirmedServicesVideoAdaptationServiceStatisticsSlotLevelOfflineTranscodingSummaryEntry 21 }

affirmedServicesVideoAdaptationServiceStatisticsSlotLevelOfflineTranscodingSummaryNumofflinewebmservingsuccess OBJECT-TYPE
    SYNTAX      ConfdString
    MAX-ACCESS  read-only
    STATUS      current
    DESCRIPTION "Number of transcoded WEBM videos serviced successfully"
    ::= { affirmedServicesVideoAdaptationServiceStatisticsSlotLevelOfflineTranscodingSummaryEntry 22 }

affirmedServicesVideoAdaptationServiceStatisticsSlotLevelOfflineTranscodingSummaryNumofflinewebmservingabort OBJECT-TYPE
    SYNTAX      ConfdString
    MAX-ACCESS  read-only
    STATUS      current
    DESCRIPTION "Number of transcoded WEBM video service aborts"
    ::= { affirmedServicesVideoAdaptationServiceStatisticsSlotLevelOfflineTranscodingSummaryEntry 23 }

affirmedServicesVideoAdaptationServiceStatisticsSlotLevelOfflineTranscodingSummaryNumofflinewebmservingfailure OBJECT-TYPE
    SYNTAX      ConfdString
    MAX-ACCESS  read-only
    STATUS      current
    DESCRIPTION "Number of transcoded WEBM video service failures"
    ::= { affirmedServicesVideoAdaptationServiceStatisticsSlotLevelOfflineTranscodingSummaryEntry 24 }

affirmedServicesVideoAdaptationServiceStatisticsSlotLevelOfflineTranscodingSummaryNumofflineoriginalbytes OBJECT-TYPE
    SYNTAX      ConfdString
    MAX-ACCESS  read-only
    STATUS      current
    DESCRIPTION "Total number of bytes of original video cached"
    ::= { affirmedServicesVideoAdaptationServiceStatisticsSlotLevelOfflineTranscodingSummaryEntry 25 }

affirmedServicesVideoAdaptationServiceStatisticsSlotLevelOfflineTranscodingSummaryNumofflineadaptedbytesserved OBJECT-TYPE
    SYNTAX      ConfdString
    MAX-ACCESS  read-only
    STATUS      current
    DESCRIPTION "Total number of Offline Transcoding adapted bytes served"
    ::= { affirmedServicesVideoAdaptationServiceStatisticsSlotLevelOfflineTranscodingSummaryEntry 26 }

affirmedServicesVideoAdaptationServiceStatisticsSlotLevelOfflineTranscodingDetailTable OBJECT-TYPE
    SYNTAX      SEQUENCE OF AffirmedServicesVideoAdaptationServiceStatisticsSlotLevelOfflineTranscodingDetailEntry
    MAX-ACCESS  not-accessible
    STATUS      current
    DESCRIPTION ""
    ::= { affirmedServicesVideoAdaptationServiceStatisticsSlotLevelOfflineTranscoding 2 }

affirmedServicesVideoAdaptationServiceStatisticsSlotLevelOfflineTranscodingDetailEntry OBJECT-TYPE
    SYNTAX      AffirmedServicesVideoAdaptationServiceStatisticsSlotLevelOfflineTranscodingDetailEntry
    MAX-ACCESS  not-accessible
    STATUS      current
    DESCRIPTION ""
    INDEX { affirmedServicesVideoAdaptationServiceStatisticsSlotLevelOfflineTranscodingDetailChassis, affirmedServicesVideoAdaptationServiceStatisticsSlotLevelOfflineTranscodingDetailSlot }
        ::= { affirmedServicesVideoAdaptationServiceStatisticsSlotLevelOfflineTranscodingDetailTable 1 }

AffirmedServicesVideoAdaptationServiceStatisticsSlotLevelOfflineTranscodingDetailEntry ::=
    SEQUENCE {
        affirmedServicesVideoAdaptationServiceStatisticsSlotLevelOfflineTranscodingDetailChassis Unsigned32,
        affirmedServicesVideoAdaptationServiceStatisticsSlotLevelOfflineTranscodingDetailSlot INTEGER,
        affirmedServicesVideoAdaptationServiceStatisticsSlotLevelOfflineTranscodingDetailNumofflineflv2flvsuccesses ConfdString,
        affirmedServicesVideoAdaptationServiceStatisticsSlotLevelOfflineTranscodingDetailNumofflineflv2flvfailures ConfdString,
        affirmedServicesVideoAdaptationServiceStatisticsSlotLevelOfflineTranscodingDetailNumofflineflv2mp4successes ConfdString,
        affirmedServicesVideoAdaptationServiceStatisticsSlotLevelOfflineTranscodingDetailNumofflineflv2mp4failures ConfdString,
        affirmedServicesVideoAdaptationServiceStatisticsSlotLevelOfflineTranscodingDetailNumofflinemp42flvsuccesses ConfdString,
        affirmedServicesVideoAdaptationServiceStatisticsSlotLevelOfflineTranscodingDetailNumofflinemp42flvfailures ConfdString,
        affirmedServicesVideoAdaptationServiceStatisticsSlotLevelOfflineTranscodingDetailNumofflinemp42mp4successes ConfdString,
        affirmedServicesVideoAdaptationServiceStatisticsSlotLevelOfflineTranscodingDetailNumofflinemp42mp4failures ConfdString,
        affirmedServicesVideoAdaptationServiceStatisticsSlotLevelOfflineTranscodingDetailNumofflinewebm2webmsuccesses ConfdString,
        affirmedServicesVideoAdaptationServiceStatisticsSlotLevelOfflineTranscodingDetailNumofflinewebm2webmfailures ConfdString,
        affirmedServicesVideoAdaptationServiceStatisticsSlotLevelOfflineTranscodingDetailNumofflinecurrentvideosqueued ConfdString,
        affirmedServicesVideoAdaptationServiceStatisticsSlotLevelOfflineTranscodingDetailNumofflinemaxvideosqueued ConfdString,
        affirmedServicesVideoAdaptationServiceStatisticsSlotLevelOfflineTranscodingDetailOfflineavgwaittime ConfdString,
        affirmedServicesVideoAdaptationServiceStatisticsSlotLevelOfflineTranscodingDetailOfflinemaxwaittime ConfdString,
        affirmedServicesVideoAdaptationServiceStatisticsSlotLevelOfflineTranscodingDetailOfflineavgprocessingtime ConfdString
    }

affirmedServicesVideoAdaptationServiceStatisticsSlotLevelOfflineTranscodingDetailChassis OBJECT-TYPE
    SYNTAX      Unsigned32
    MAX-ACCESS  not-accessible
    STATUS      current
    DESCRIPTION "chassis ID"
    ::= { affirmedServicesVideoAdaptationServiceStatisticsSlotLevelOfflineTranscodingDetailEntry 1 }

affirmedServicesVideoAdaptationServiceStatisticsSlotLevelOfflineTranscodingDetailSlot OBJECT-TYPE
    SYNTAX      INTEGER {a1(1),a2(2),a3(3),a4(4),a5(5),a6(6),a7(7),a8(8),a9(9),a10(10),a11(11),a12(12),a13(13),a14(14),a15(15),a16(16),a17(17),a18(18),a19(19),a20(20),a21(21),a22(22),a23(23),a24(24),a25(25),a26(26),a27(27),a28(28),a29(29),a30(30),a31(31),a32(32),a33(33),a34(34),a35(35),a36(36),a37(37),a38(38),a39(39),a40(40),a41(41),a42(42),a43(43),a44(44),a45(45),a46(46),a47(47),a48(48),a49(49),a50(50),a51(51),a52(52),a53(53),a54(54),a55(55),a56(56),a57(57),a58(58),a59(59),a60(60),a61(61),a62(62),a63(63),a64(64),a65(65),a66(66),a67(67),a68(68),a69(69),a70(70),a71(71),a72(72),a73(73),a74(74),a75(75),a76(76),a77(77),a78(78),a79(79),a80(80),a81(81),a82(82),a83(83),a84(84),a85(85),a86(86),a87(87),a88(88),a89(89),a90(90),a91(91),a92(92),a93(93),a94(94),a95(95),a96(96),a97(97),a98(98),a99(99),a100(100),a101(101),a102(102),a103(103),a104(104),a105(105),a106(106),a107(107),a108(108),a109(109),a110(110),a111(111),a112(112),a113(113),a114(114),a115(115),a116(116),a117(117),a118(118),a119(119),a120(120),a121(121),a122(122),a123(123),a124(124),a125(125),a126(126),a127(127),a128(128)}
    MAX-ACCESS  not-accessible
    STATUS      current
    DESCRIPTION "slot number"
    ::= { affirmedServicesVideoAdaptationServiceStatisticsSlotLevelOfflineTranscodingDetailEntry 2 }

affirmedServicesVideoAdaptationServiceStatisticsSlotLevelOfflineTranscodingDetailNumofflineflv2flvsuccesses OBJECT-TYPE
    SYNTAX      ConfdString
    MAX-ACCESS  read-only
    STATUS      current
    DESCRIPTION "Number of video transcoded successfully from FLV to FLV"
    ::= { affirmedServicesVideoAdaptationServiceStatisticsSlotLevelOfflineTranscodingDetailEntry 3 }

affirmedServicesVideoAdaptationServiceStatisticsSlotLevelOfflineTranscodingDetailNumofflineflv2flvfailures OBJECT-TYPE
    SYNTAX      ConfdString
    MAX-ACCESS  read-only
    STATUS      current
    DESCRIPTION "Number of video transcoded unsuccessfully from FLV to FLV"
    ::= { affirmedServicesVideoAdaptationServiceStatisticsSlotLevelOfflineTranscodingDetailEntry 4 }

affirmedServicesVideoAdaptationServiceStatisticsSlotLevelOfflineTranscodingDetailNumofflineflv2mp4successes OBJECT-TYPE
    SYNTAX      ConfdString
    MAX-ACCESS  read-only
    STATUS      current
    DESCRIPTION "Number of video transcoded successfully from FLV to MP4"
    ::= { affirmedServicesVideoAdaptationServiceStatisticsSlotLevelOfflineTranscodingDetailEntry 5 }

affirmedServicesVideoAdaptationServiceStatisticsSlotLevelOfflineTranscodingDetailNumofflineflv2mp4failures OBJECT-TYPE
    SYNTAX      ConfdString
    MAX-ACCESS  read-only
    STATUS      current
    DESCRIPTION "Number of video transcoded unsuccessfully from FLV to MP4"
    ::= { affirmedServicesVideoAdaptationServiceStatisticsSlotLevelOfflineTranscodingDetailEntry 6 }

affirmedServicesVideoAdaptationServiceStatisticsSlotLevelOfflineTranscodingDetailNumofflinemp42flvsuccesses OBJECT-TYPE
    SYNTAX      ConfdString
    MAX-ACCESS  read-only
    STATUS      current
    DESCRIPTION "Number of video transcoded successfully from MP4 to FLV"
    ::= { affirmedServicesVideoAdaptationServiceStatisticsSlotLevelOfflineTranscodingDetailEntry 7 }

affirmedServicesVideoAdaptationServiceStatisticsSlotLevelOfflineTranscodingDetailNumofflinemp42flvfailures OBJECT-TYPE
    SYNTAX      ConfdString
    MAX-ACCESS  read-only
    STATUS      current
    DESCRIPTION "Number of video transcoded unsuccessfully from MP4 to FLV"
    ::= { affirmedServicesVideoAdaptationServiceStatisticsSlotLevelOfflineTranscodingDetailEntry 8 }

affirmedServicesVideoAdaptationServiceStatisticsSlotLevelOfflineTranscodingDetailNumofflinemp42mp4successes OBJECT-TYPE
    SYNTAX      ConfdString
    MAX-ACCESS  read-only
    STATUS      current
    DESCRIPTION "Number of video transcoded successfully from MP4 to MP4"
    ::= { affirmedServicesVideoAdaptationServiceStatisticsSlotLevelOfflineTranscodingDetailEntry 9 }

affirmedServicesVideoAdaptationServiceStatisticsSlotLevelOfflineTranscodingDetailNumofflinemp42mp4failures OBJECT-TYPE
    SYNTAX      ConfdString
    MAX-ACCESS  read-only
    STATUS      current
    DESCRIPTION "Number of video transcoded unsuccessfully from MP4 to MP4"
    ::= { affirmedServicesVideoAdaptationServiceStatisticsSlotLevelOfflineTranscodingDetailEntry 10 }

affirmedServicesVideoAdaptationServiceStatisticsSlotLevelOfflineTranscodingDetailNumofflinewebm2webmsuccesses OBJECT-TYPE
    SYNTAX      ConfdString
    MAX-ACCESS  read-only
    STATUS      current
    DESCRIPTION "Number of video transcoded successfully from WEBM to WEBM"
    ::= { affirmedServicesVideoAdaptationServiceStatisticsSlotLevelOfflineTranscodingDetailEntry 11 }

affirmedServicesVideoAdaptationServiceStatisticsSlotLevelOfflineTranscodingDetailNumofflinewebm2webmfailures OBJECT-TYPE
    SYNTAX      ConfdString
    MAX-ACCESS  read-only
    STATUS      current
    DESCRIPTION "Number of video transcoded unsuccessfully from WEBM to WEBM"
    ::= { affirmedServicesVideoAdaptationServiceStatisticsSlotLevelOfflineTranscodingDetailEntry 12 }

affirmedServicesVideoAdaptationServiceStatisticsSlotLevelOfflineTranscodingDetailNumofflinecurrentvideosqueued OBJECT-TYPE
    SYNTAX      ConfdString
    MAX-ACCESS  read-only
    STATUS      current
    DESCRIPTION "Number of videos currently in the queue to be transcoded"
    ::= { affirmedServicesVideoAdaptationServiceStatisticsSlotLevelOfflineTranscodingDetailEntry 13 }

affirmedServicesVideoAdaptationServiceStatisticsSlotLevelOfflineTranscodingDetailNumofflinemaxvideosqueued OBJECT-TYPE
    SYNTAX      ConfdString
    MAX-ACCESS  read-only
    STATUS      current
    DESCRIPTION "Maximum number of videos in the queue to be transcoded"
    ::= { affirmedServicesVideoAdaptationServiceStatisticsSlotLevelOfflineTranscodingDetailEntry 14 }

affirmedServicesVideoAdaptationServiceStatisticsSlotLevelOfflineTranscodingDetailOfflineavgwaittime OBJECT-TYPE
    SYNTAX      ConfdString
    MAX-ACCESS  read-only
    STATUS      current
    DESCRIPTION "Average wait time(in secs) of videos in the queue to be transcoded"
    ::= { affirmedServicesVideoAdaptationServiceStatisticsSlotLevelOfflineTranscodingDetailEntry 15 }

affirmedServicesVideoAdaptationServiceStatisticsSlotLevelOfflineTranscodingDetailOfflinemaxwaittime OBJECT-TYPE
    SYNTAX      ConfdString
    MAX-ACCESS  read-only
    STATUS      current
    DESCRIPTION "Maximum wait time(in secs) of videos in the queue to be transcoded"
    ::= { affirmedServicesVideoAdaptationServiceStatisticsSlotLevelOfflineTranscodingDetailEntry 16 }

affirmedServicesVideoAdaptationServiceStatisticsSlotLevelOfflineTranscodingDetailOfflineavgprocessingtime OBJECT-TYPE
    SYNTAX      ConfdString
    MAX-ACCESS  read-only
    STATUS      current
    DESCRIPTION "Average processing time(in secs) for transcoding videos"
    ::= { affirmedServicesVideoAdaptationServiceStatisticsSlotLevelOfflineTranscodingDetailEntry 17 }

affirmedServicesVideoAdaptationServiceStatisticsSlotLevelOfflineTranscodingFailureTable OBJECT-TYPE
    SYNTAX      SEQUENCE OF AffirmedServicesVideoAdaptationServiceStatisticsSlotLevelOfflineTranscodingFailureEntry
    MAX-ACCESS  not-accessible
    STATUS      current
    DESCRIPTION ""
    ::= { affirmedServicesVideoAdaptationServiceStatisticsSlotLevelOfflineTranscoding 3 }

affirmedServicesVideoAdaptationServiceStatisticsSlotLevelOfflineTranscodingFailureEntry OBJECT-TYPE
    SYNTAX      AffirmedServicesVideoAdaptationServiceStatisticsSlotLevelOfflineTranscodingFailureEntry
    MAX-ACCESS  not-accessible
    STATUS      current
    DESCRIPTION ""
    INDEX { affirmedServicesVideoAdaptationServiceStatisticsSlotLevelOfflineTranscodingFailureChassis, affirmedServicesVideoAdaptationServiceStatisticsSlotLevelOfflineTranscodingFailureSlot }
        ::= { affirmedServicesVideoAdaptationServiceStatisticsSlotLevelOfflineTranscodingFailureTable 1 }

AffirmedServicesVideoAdaptationServiceStatisticsSlotLevelOfflineTranscodingFailureEntry ::=
    SEQUENCE {
        affirmedServicesVideoAdaptationServiceStatisticsSlotLevelOfflineTranscodingFailureChassis Unsigned32,
        affirmedServicesVideoAdaptationServiceStatisticsSlotLevelOfflineTranscodingFailureSlot INTEGER,
        affirmedServicesVideoAdaptationServiceStatisticsSlotLevelOfflineTranscodingFailureNumofflineunsupportedformat ConfdString,
        affirmedServicesVideoAdaptationServiceStatisticsSlotLevelOfflineTranscodingFailureNumofflineunsupportedvideocodec ConfdString,
        affirmedServicesVideoAdaptationServiceStatisticsSlotLevelOfflineTranscodingFailureNumofflineunsupportedaudiocodec ConfdString
    }

affirmedServicesVideoAdaptationServiceStatisticsSlotLevelOfflineTranscodingFailureChassis OBJECT-TYPE
    SYNTAX      Unsigned32
    MAX-ACCESS  not-accessible
    STATUS      current
    DESCRIPTION "chassis ID"
    ::= { affirmedServicesVideoAdaptationServiceStatisticsSlotLevelOfflineTranscodingFailureEntry 1 }

affirmedServicesVideoAdaptationServiceStatisticsSlotLevelOfflineTranscodingFailureSlot OBJECT-TYPE
    SYNTAX      INTEGER {a1(1),a2(2),a3(3),a4(4),a5(5),a6(6),a7(7),a8(8),a9(9),a10(10),a11(11),a12(12),a13(13),a14(14),a15(15),a16(16),a17(17),a18(18),a19(19),a20(20),a21(21),a22(22),a23(23),a24(24),a25(25),a26(26),a27(27),a28(28),a29(29),a30(30),a31(31),a32(32),a33(33),a34(34),a35(35),a36(36),a37(37),a38(38),a39(39),a40(40),a41(41),a42(42),a43(43),a44(44),a45(45),a46(46),a47(47),a48(48),a49(49),a50(50),a51(51),a52(52),a53(53),a54(54),a55(55),a56(56),a57(57),a58(58),a59(59),a60(60),a61(61),a62(62),a63(63),a64(64),a65(65),a66(66),a67(67),a68(68),a69(69),a70(70),a71(71),a72(72),a73(73),a74(74),a75(75),a76(76),a77(77),a78(78),a79(79),a80(80),a81(81),a82(82),a83(83),a84(84),a85(85),a86(86),a87(87),a88(88),a89(89),a90(90),a91(91),a92(92),a93(93),a94(94),a95(95),a96(96),a97(97),a98(98),a99(99),a100(100),a101(101),a102(102),a103(103),a104(104),a105(105),a106(106),a107(107),a108(108),a109(109),a110(110),a111(111),a112(112),a113(113),a114(114),a115(115),a116(116),a117(117),a118(118),a119(119),a120(120),a121(121),a122(122),a123(123),a124(124),a125(125),a126(126),a127(127),a128(128)}
    MAX-ACCESS  not-accessible
    STATUS      current
    DESCRIPTION "slot number"
    ::= { affirmedServicesVideoAdaptationServiceStatisticsSlotLevelOfflineTranscodingFailureEntry 2 }

affirmedServicesVideoAdaptationServiceStatisticsSlotLevelOfflineTranscodingFailureNumofflineunsupportedformat OBJECT-TYPE
    SYNTAX      ConfdString
    MAX-ACCESS  read-only
    STATUS      current
    DESCRIPTION "Total number of Offline Transcoding Unsupported Format"
    ::= { affirmedServicesVideoAdaptationServiceStatisticsSlotLevelOfflineTranscodingFailureEntry 3 }

affirmedServicesVideoAdaptationServiceStatisticsSlotLevelOfflineTranscodingFailureNumofflineunsupportedvideocodec OBJECT-TYPE
    SYNTAX      ConfdString
    MAX-ACCESS  read-only
    STATUS      current
    DESCRIPTION "Total number of Offline Transcoding Unsupported Video Codec"
    ::= { affirmedServicesVideoAdaptationServiceStatisticsSlotLevelOfflineTranscodingFailureEntry 4 }

affirmedServicesVideoAdaptationServiceStatisticsSlotLevelOfflineTranscodingFailureNumofflineunsupportedaudiocodec OBJECT-TYPE
    SYNTAX      ConfdString
    MAX-ACCESS  read-only
    STATUS      current
    DESCRIPTION "Total number of Offline Transcoding Unsupported Audio Codec"
    ::= { affirmedServicesVideoAdaptationServiceStatisticsSlotLevelOfflineTranscodingFailureEntry 5 }

affirmedServicesContentFilterServiceStatisticsCluster-levelSummaryTable OBJECT-TYPE
    SYNTAX      SEQUENCE OF AffirmedServicesContentFilterServiceStatisticsCluster-levelSummaryEntry
    MAX-ACCESS  not-accessible
    STATUS      current
    DESCRIPTION ""
    ::= { affirmedServicesContentFilterServiceStatisticsCluster-level 1 }

affirmedServicesContentFilterServiceStatisticsCluster-levelSummaryEntry OBJECT-TYPE
    SYNTAX      AffirmedServicesContentFilterServiceStatisticsCluster-levelSummaryEntry
    MAX-ACCESS  not-accessible
    STATUS      current
    DESCRIPTION ""
    INDEX { affirmedServicesContentFilterServiceStatisticsCluster-levelSummaryChassis }
        ::= { affirmedServicesContentFilterServiceStatisticsCluster-levelSummaryTable 1 }

AffirmedServicesContentFilterServiceStatisticsCluster-levelSummaryEntry ::=
    SEQUENCE {
        affirmedServicesContentFilterServiceStatisticsCluster-levelSummaryChassis Unsigned32,
        affirmedServicesContentFilterServiceStatisticsCluster-levelSummaryNumfilterserviceattempts ConfdString,
        affirmedServicesContentFilterServiceStatisticsCluster-levelSummaryNumfilterservicesuccess ConfdString,
        affirmedServicesContentFilterServiceStatisticsCluster-levelSummaryNumfilterserviceabortedbyclient ConfdString,
        affirmedServicesContentFilterServiceStatisticsCluster-levelSummaryNumfilterservicefailed ConfdString,
        affirmedServicesContentFilterServiceStatisticsCluster-levelSummaryNumfilterservicenomatch ConfdString,
        affirmedServicesContentFilterServiceStatisticsCluster-levelSummaryNumrequestterminated ConfdString,
        affirmedServicesContentFilterServiceStatisticsCluster-levelSummaryNumrequestredirected ConfdString,
        affirmedServicesContentFilterServiceStatisticsCluster-levelSummaryNumrequestblocked ConfdString,
        affirmedServicesContentFilterServiceStatisticsCluster-levelSummaryNumrequestallowed ConfdString,
        affirmedServicesContentFilterServiceStatisticsCluster-levelSummaryNumblacklisturlmatched ConfdString,
        affirmedServicesContentFilterServiceStatisticsCluster-levelSummaryNumblacklistdomainmatched ConfdString,
        affirmedServicesContentFilterServiceStatisticsCluster-levelSummaryNumcategoryurlmatched ConfdString,
        affirmedServicesContentFilterServiceStatisticsCluster-levelSummaryNumcategorydomainmatched ConfdString,
        affirmedServicesContentFilterServiceStatisticsCluster-levelSummaryNumwhitelisturlmatched ConfdString,
        affirmedServicesContentFilterServiceStatisticsCluster-levelSummaryNumwhitelistdomainmatched ConfdString,
        affirmedServicesContentFilterServiceStatisticsCluster-levelSummaryNumsrgmatched ConfdString,
        affirmedServicesContentFilterServiceStatisticsCluster-levelSummaryNumonlinecategorymatched ConfdString,
        affirmedServicesContentFilterServiceStatisticsCluster-levelSummaryNummalwarecategorymatched ConfdString,
        affirmedServicesContentFilterServiceStatisticsCluster-levelSummaryNumphishingcategorymatched ConfdString,
        affirmedServicesContentFilterServiceStatisticsCluster-levelSummaryNumiwfcategorymatched ConfdString,
        affirmedServicesContentFilterServiceStatisticsCluster-levelSummaryNumfilterhashlistmatched ConfdString,
        affirmedServicesContentFilterServiceStatisticsCluster-levelSummaryNumbingsafesearchenforced ConfdString,
        affirmedServicesContentFilterServiceStatisticsCluster-levelSummaryNumrequestredirectchangedallowrequestsameurl ConfdString,
        affirmedServicesContentFilterServiceStatisticsCluster-levelSummaryNumrequestredirectchangedallowinterval ConfdString,
        affirmedServicesContentFilterServiceStatisticsCluster-levelSummaryNumgooglesafesearchenforced ConfdString,
        affirmedServicesContentFilterServiceStatisticsCluster-levelSummaryNumyoutubesafesearchenforced ConfdString
    }

affirmedServicesContentFilterServiceStatisticsCluster-levelSummaryChassis OBJECT-TYPE
    SYNTAX      Unsigned32
    MAX-ACCESS  not-accessible
    STATUS      current
    DESCRIPTION "chassis ID"
    ::= { affirmedServicesContentFilterServiceStatisticsCluster-levelSummaryEntry 1 }

affirmedServicesContentFilterServiceStatisticsCluster-levelSummaryNumfilterserviceattempts OBJECT-TYPE
    SYNTAX      ConfdString
    MAX-ACCESS  read-only
    STATUS      current
    DESCRIPTION "Total number of filter service attempts"
    ::= { affirmedServicesContentFilterServiceStatisticsCluster-levelSummaryEntry 2 }

affirmedServicesContentFilterServiceStatisticsCluster-levelSummaryNumfilterservicesuccess OBJECT-TYPE
    SYNTAX      ConfdString
    MAX-ACCESS  read-only
    STATUS      current
    DESCRIPTION "Total number of filter service applied"
    ::= { affirmedServicesContentFilterServiceStatisticsCluster-levelSummaryEntry 3 }

affirmedServicesContentFilterServiceStatisticsCluster-levelSummaryNumfilterserviceabortedbyclient OBJECT-TYPE
    SYNTAX      ConfdString
    MAX-ACCESS  read-only
    STATUS      current
    DESCRIPTION "Total number of filter service aborted by client"
    ::= { affirmedServicesContentFilterServiceStatisticsCluster-levelSummaryEntry 4 }

affirmedServicesContentFilterServiceStatisticsCluster-levelSummaryNumfilterservicefailed OBJECT-TYPE
    SYNTAX      ConfdString
    MAX-ACCESS  read-only
    STATUS      current
    DESCRIPTION "Total number of filter service failed"
    ::= { affirmedServicesContentFilterServiceStatisticsCluster-levelSummaryEntry 5 }

affirmedServicesContentFilterServiceStatisticsCluster-levelSummaryNumfilterservicenomatch OBJECT-TYPE
    SYNTAX      ConfdString
    MAX-ACCESS  read-only
    STATUS      current
    DESCRIPTION "Total number of filter service not applied"
    ::= { affirmedServicesContentFilterServiceStatisticsCluster-levelSummaryEntry 6 }

affirmedServicesContentFilterServiceStatisticsCluster-levelSummaryNumrequestterminated OBJECT-TYPE
    SYNTAX      ConfdString
    MAX-ACCESS  read-only
    STATUS      current
    DESCRIPTION "Total number of request terminated"
    ::= { affirmedServicesContentFilterServiceStatisticsCluster-levelSummaryEntry 7 }

affirmedServicesContentFilterServiceStatisticsCluster-levelSummaryNumrequestredirected OBJECT-TYPE
    SYNTAX      ConfdString
    MAX-ACCESS  read-only
    STATUS      current
    DESCRIPTION "Total number of request redirected"
    ::= { affirmedServicesContentFilterServiceStatisticsCluster-levelSummaryEntry 8 }

affirmedServicesContentFilterServiceStatisticsCluster-levelSummaryNumrequestblocked OBJECT-TYPE
    SYNTAX      ConfdString
    MAX-ACCESS  read-only
    STATUS      current
    DESCRIPTION "Total number of request blocked"
    ::= { affirmedServicesContentFilterServiceStatisticsCluster-levelSummaryEntry 9 }

affirmedServicesContentFilterServiceStatisticsCluster-levelSummaryNumrequestallowed OBJECT-TYPE
    SYNTAX      ConfdString
    MAX-ACCESS  read-only
    STATUS      current
    DESCRIPTION "Total number of request allowed"
    ::= { affirmedServicesContentFilterServiceStatisticsCluster-levelSummaryEntry 10 }

affirmedServicesContentFilterServiceStatisticsCluster-levelSummaryNumblacklisturlmatched OBJECT-TYPE
    SYNTAX      ConfdString
    MAX-ACCESS  read-only
    STATUS      current
    DESCRIPTION "Total number of blackList URL matched"
    ::= { affirmedServicesContentFilterServiceStatisticsCluster-levelSummaryEntry 11 }

affirmedServicesContentFilterServiceStatisticsCluster-levelSummaryNumblacklistdomainmatched OBJECT-TYPE
    SYNTAX      ConfdString
    MAX-ACCESS  read-only
    STATUS      current
    DESCRIPTION "Total number of blackList domain matched"
    ::= { affirmedServicesContentFilterServiceStatisticsCluster-levelSummaryEntry 12 }

affirmedServicesContentFilterServiceStatisticsCluster-levelSummaryNumcategoryurlmatched OBJECT-TYPE
    SYNTAX      ConfdString
    MAX-ACCESS  read-only
    STATUS      current
    DESCRIPTION "Total number of static category URL matched"
    ::= { affirmedServicesContentFilterServiceStatisticsCluster-levelSummaryEntry 13 }

affirmedServicesContentFilterServiceStatisticsCluster-levelSummaryNumcategorydomainmatched OBJECT-TYPE
    SYNTAX      ConfdString
    MAX-ACCESS  read-only
    STATUS      current
    DESCRIPTION "Total number of static category domain matched"
    ::= { affirmedServicesContentFilterServiceStatisticsCluster-levelSummaryEntry 14 }

affirmedServicesContentFilterServiceStatisticsCluster-levelSummaryNumwhitelisturlmatched OBJECT-TYPE
    SYNTAX      ConfdString
    MAX-ACCESS  read-only
    STATUS      current
    DESCRIPTION "Total number of whitelist URL matched"
    ::= { affirmedServicesContentFilterServiceStatisticsCluster-levelSummaryEntry 15 }

affirmedServicesContentFilterServiceStatisticsCluster-levelSummaryNumwhitelistdomainmatched OBJECT-TYPE
    SYNTAX      ConfdString
    MAX-ACCESS  read-only
    STATUS      current
    DESCRIPTION "Total number of whitelist domain matched"
    ::= { affirmedServicesContentFilterServiceStatisticsCluster-levelSummaryEntry 16 }

affirmedServicesContentFilterServiceStatisticsCluster-levelSummaryNumsrgmatched OBJECT-TYPE
    SYNTAX      ConfdString
    MAX-ACCESS  read-only
    STATUS      current
    DESCRIPTION "Total number of Service-Rule matched"
    ::= { affirmedServicesContentFilterServiceStatisticsCluster-levelSummaryEntry 17 }

affirmedServicesContentFilterServiceStatisticsCluster-levelSummaryNumonlinecategorymatched OBJECT-TYPE
    SYNTAX      ConfdString
    MAX-ACCESS  read-only
    STATUS      current
    DESCRIPTION "Total number of online category groups matched"
    ::= { affirmedServicesContentFilterServiceStatisticsCluster-levelSummaryEntry 18 }

affirmedServicesContentFilterServiceStatisticsCluster-levelSummaryNummalwarecategorymatched OBJECT-TYPE
    SYNTAX      ConfdString
    MAX-ACCESS  read-only
    STATUS      current
    DESCRIPTION "Total number of malware category groups matched"
    ::= { affirmedServicesContentFilterServiceStatisticsCluster-levelSummaryEntry 19 }

affirmedServicesContentFilterServiceStatisticsCluster-levelSummaryNumphishingcategorymatched OBJECT-TYPE
    SYNTAX      ConfdString
    MAX-ACCESS  read-only
    STATUS      current
    DESCRIPTION "Total number of phishing category matched"
    ::= { affirmedServicesContentFilterServiceStatisticsCluster-levelSummaryEntry 20 }

affirmedServicesContentFilterServiceStatisticsCluster-levelSummaryNumiwfcategorymatched OBJECT-TYPE
    SYNTAX      ConfdString
    MAX-ACCESS  read-only
    STATUS      current
    DESCRIPTION "Total number of IWF category filter matched"
    ::= { affirmedServicesContentFilterServiceStatisticsCluster-levelSummaryEntry 21 }

affirmedServicesContentFilterServiceStatisticsCluster-levelSummaryNumfilterhashlistmatched OBJECT-TYPE
    SYNTAX      ConfdString
    MAX-ACCESS  read-only
    STATUS      current
    DESCRIPTION "Total number of Filter Hash List matched"
    ::= { affirmedServicesContentFilterServiceStatisticsCluster-levelSummaryEntry 22 }

affirmedServicesContentFilterServiceStatisticsCluster-levelSummaryNumbingsafesearchenforced OBJECT-TYPE
    SYNTAX      ConfdString
    MAX-ACCESS  read-only
    STATUS      current
    DESCRIPTION "Total number of Bing Safe Search enforced"
    ::= { affirmedServicesContentFilterServiceStatisticsCluster-levelSummaryEntry 23 }

affirmedServicesContentFilterServiceStatisticsCluster-levelSummaryNumrequestredirectchangedallowrequestsameurl OBJECT-TYPE
    SYNTAX      ConfdString
    MAX-ACCESS  read-only
    STATUS      current
    DESCRIPTION "Total number of redirect changed to allow - Request with Same URL"
    ::= { affirmedServicesContentFilterServiceStatisticsCluster-levelSummaryEntry 24 }

affirmedServicesContentFilterServiceStatisticsCluster-levelSummaryNumrequestredirectchangedallowinterval OBJECT-TYPE
    SYNTAX      ConfdString
    MAX-ACCESS  read-only
    STATUS      current
    DESCRIPTION "Total number of redirect changed to allow - Request within Redirect Interval"
    ::= { affirmedServicesContentFilterServiceStatisticsCluster-levelSummaryEntry 25 }

affirmedServicesContentFilterServiceStatisticsCluster-levelSummaryNumgooglesafesearchenforced OBJECT-TYPE
    SYNTAX      ConfdString
    MAX-ACCESS  read-only
    STATUS      current
    DESCRIPTION "Total number of Google Safe Search enforced"
    ::= { affirmedServicesContentFilterServiceStatisticsCluster-levelSummaryEntry 26 }

affirmedServicesContentFilterServiceStatisticsCluster-levelSummaryNumyoutubesafesearchenforced OBJECT-TYPE
    SYNTAX      ConfdString
    MAX-ACCESS  read-only
    STATUS      current
    DESCRIPTION "Total number of YouTube Safe Search enforced"
    ::= { affirmedServicesContentFilterServiceStatisticsCluster-levelSummaryEntry 27 }

affirmedServicesContentFilterServiceStatisticsCluster-levelInstanceTable OBJECT-TYPE
    SYNTAX      SEQUENCE OF AffirmedServicesContentFilterServiceStatisticsCluster-levelInstanceEntry
    MAX-ACCESS  not-accessible
    STATUS      current
    DESCRIPTION ""
    ::= { affirmedServicesContentFilterServiceStatisticsCluster-level 2 }

affirmedServicesContentFilterServiceStatisticsCluster-levelInstanceEntry OBJECT-TYPE
    SYNTAX      AffirmedServicesContentFilterServiceStatisticsCluster-levelInstanceEntry
    MAX-ACCESS  not-accessible
    STATUS      current
    DESCRIPTION ""
    INDEX { affirmedServicesContentFilterServiceStatisticsCluster-levelInstanceName, affirmedServicesContentFilterServiceStatisticsCluster-levelInstanceChassis }
        ::= { affirmedServicesContentFilterServiceStatisticsCluster-levelInstanceTable 1 }

AffirmedServicesContentFilterServiceStatisticsCluster-levelInstanceEntry ::=
    SEQUENCE {
        affirmedServicesContentFilterServiceStatisticsCluster-levelInstanceName String,
        affirmedServicesContentFilterServiceStatisticsCluster-levelInstanceChassis Unsigned32,
        affirmedServicesContentFilterServiceStatisticsCluster-levelInstanceNumrequestterminated ConfdString,
        affirmedServicesContentFilterServiceStatisticsCluster-levelInstanceNumrequestredirected ConfdString,
        affirmedServicesContentFilterServiceStatisticsCluster-levelInstanceNumrequestblocked ConfdString,
        affirmedServicesContentFilterServiceStatisticsCluster-levelInstanceNumrequestallowed ConfdString,
        affirmedServicesContentFilterServiceStatisticsCluster-levelInstanceNumsrgmatched ConfdString,
        affirmedServicesContentFilterServiceStatisticsCluster-levelInstanceNumcategoryurlmatched ConfdString,
        affirmedServicesContentFilterServiceStatisticsCluster-levelInstanceNumcategorydomainmatched ConfdString,
        affirmedServicesContentFilterServiceStatisticsCluster-levelInstanceNumonlinecategorymatched ConfdString,
        affirmedServicesContentFilterServiceStatisticsCluster-levelInstanceNummalwarecategorymatched ConfdString,
        affirmedServicesContentFilterServiceStatisticsCluster-levelInstanceNumphishingcategorymatched ConfdString,
        affirmedServicesContentFilterServiceStatisticsCluster-levelInstanceNumiwfcategorymatched ConfdString,
        affirmedServicesContentFilterServiceStatisticsCluster-levelInstanceNumfilterhashlistmatched ConfdString,
        affirmedServicesContentFilterServiceStatisticsCluster-levelInstanceNumbingsafesearchenforced ConfdString,
        affirmedServicesContentFilterServiceStatisticsCluster-levelInstanceNumrequestredirectchangedallowrequestredirectinterval ConfdString,
        affirmedServicesContentFilterServiceStatisticsCluster-levelInstanceNumrequestredirectchangedallowrequestsameurl ConfdString,
        affirmedServicesContentFilterServiceStatisticsCluster-levelInstanceNumgooglesafesearchenforced ConfdString,
        affirmedServicesContentFilterServiceStatisticsCluster-levelInstanceNumyoutubesafesearchenforced ConfdString
    }

affirmedServicesContentFilterServiceStatisticsCluster-levelInstanceName OBJECT-TYPE
    SYNTAX      String
    MAX-ACCESS  not-accessible
    STATUS      current
    DESCRIPTION "Name of content filter service instance"
    ::= { affirmedServicesContentFilterServiceStatisticsCluster-levelInstanceEntry 1 }

affirmedServicesContentFilterServiceStatisticsCluster-levelInstanceChassis OBJECT-TYPE
    SYNTAX      Unsigned32
    MAX-ACCESS  not-accessible
    STATUS      current
    DESCRIPTION "chassis ID"
    ::= { affirmedServicesContentFilterServiceStatisticsCluster-levelInstanceEntry 2 }

affirmedServicesContentFilterServiceStatisticsCluster-levelInstanceNumrequestterminated OBJECT-TYPE
    SYNTAX      ConfdString
    MAX-ACCESS  read-only
    STATUS      current
    DESCRIPTION "Total number of request terminated"
    ::= { affirmedServicesContentFilterServiceStatisticsCluster-levelInstanceEntry 3 }

affirmedServicesContentFilterServiceStatisticsCluster-levelInstanceNumrequestredirected OBJECT-TYPE
    SYNTAX      ConfdString
    MAX-ACCESS  read-only
    STATUS      current
    DESCRIPTION "Total number of request redirected"
    ::= { affirmedServicesContentFilterServiceStatisticsCluster-levelInstanceEntry 4 }

affirmedServicesContentFilterServiceStatisticsCluster-levelInstanceNumrequestblocked OBJECT-TYPE
    SYNTAX      ConfdString
    MAX-ACCESS  read-only
    STATUS      current
    DESCRIPTION "Total number of request blocked"
    ::= { affirmedServicesContentFilterServiceStatisticsCluster-levelInstanceEntry 5 }

affirmedServicesContentFilterServiceStatisticsCluster-levelInstanceNumrequestallowed OBJECT-TYPE
    SYNTAX      ConfdString
    MAX-ACCESS  read-only
    STATUS      current
    DESCRIPTION "Total number of request allowed"
    ::= { affirmedServicesContentFilterServiceStatisticsCluster-levelInstanceEntry 6 }

affirmedServicesContentFilterServiceStatisticsCluster-levelInstanceNumsrgmatched OBJECT-TYPE
    SYNTAX      ConfdString
    MAX-ACCESS  read-only
    STATUS      current
    DESCRIPTION "Total number of Service-Rule matched"
    ::= { affirmedServicesContentFilterServiceStatisticsCluster-levelInstanceEntry 7 }

affirmedServicesContentFilterServiceStatisticsCluster-levelInstanceNumcategoryurlmatched OBJECT-TYPE
    SYNTAX      ConfdString
    MAX-ACCESS  read-only
    STATUS      current
    DESCRIPTION "Total number of static category URL matched"
    ::= { affirmedServicesContentFilterServiceStatisticsCluster-levelInstanceEntry 8 }

affirmedServicesContentFilterServiceStatisticsCluster-levelInstanceNumcategorydomainmatched OBJECT-TYPE
    SYNTAX      ConfdString
    MAX-ACCESS  read-only
    STATUS      current
    DESCRIPTION "Total number of static category domain matched"
    ::= { affirmedServicesContentFilterServiceStatisticsCluster-levelInstanceEntry 9 }

affirmedServicesContentFilterServiceStatisticsCluster-levelInstanceNumonlinecategorymatched OBJECT-TYPE
    SYNTAX      ConfdString
    MAX-ACCESS  read-only
    STATUS      current
    DESCRIPTION "Total number of online category groups matched"
    ::= { affirmedServicesContentFilterServiceStatisticsCluster-levelInstanceEntry 10 }

affirmedServicesContentFilterServiceStatisticsCluster-levelInstanceNummalwarecategorymatched OBJECT-TYPE
    SYNTAX      ConfdString
    MAX-ACCESS  read-only
    STATUS      current
    DESCRIPTION "Total number of malware category groups matched"
    ::= { affirmedServicesContentFilterServiceStatisticsCluster-levelInstanceEntry 11 }

affirmedServicesContentFilterServiceStatisticsCluster-levelInstanceNumphishingcategorymatched OBJECT-TYPE
    SYNTAX      ConfdString
    MAX-ACCESS  read-only
    STATUS      current
    DESCRIPTION "Total number of phishing category matched"
    ::= { affirmedServicesContentFilterServiceStatisticsCluster-levelInstanceEntry 12 }

affirmedServicesContentFilterServiceStatisticsCluster-levelInstanceNumiwfcategorymatched OBJECT-TYPE
    SYNTAX      ConfdString
    MAX-ACCESS  read-only
    STATUS      current
    DESCRIPTION "Total number of IWF category matched"
    ::= { affirmedServicesContentFilterServiceStatisticsCluster-levelInstanceEntry 13 }

affirmedServicesContentFilterServiceStatisticsCluster-levelInstanceNumfilterhashlistmatched OBJECT-TYPE
    SYNTAX      ConfdString
    MAX-ACCESS  read-only
    STATUS      current
    DESCRIPTION "Total number of Filter Hash List matched"
    ::= { affirmedServicesContentFilterServiceStatisticsCluster-levelInstanceEntry 14 }

affirmedServicesContentFilterServiceStatisticsCluster-levelInstanceNumbingsafesearchenforced OBJECT-TYPE
    SYNTAX      ConfdString
    MAX-ACCESS  read-only
    STATUS      current
    DESCRIPTION "Total number of Bing Safe Search enforced"
    ::= { affirmedServicesContentFilterServiceStatisticsCluster-levelInstanceEntry 15 }

affirmedServicesContentFilterServiceStatisticsCluster-levelInstanceNumrequestredirectchangedallowrequestredirectinterval OBJECT-TYPE
    SYNTAX      ConfdString
    MAX-ACCESS  read-only
    STATUS      current
    DESCRIPTION "Total number of redirect changed to allow - Request within Redirect Interval"
    ::= { affirmedServicesContentFilterServiceStatisticsCluster-levelInstanceEntry 16 }

affirmedServicesContentFilterServiceStatisticsCluster-levelInstanceNumrequestredirectchangedallowrequestsameurl OBJECT-TYPE
    SYNTAX      ConfdString
    MAX-ACCESS  read-only
    STATUS      current
    DESCRIPTION "Total number of redirect changed to allow - Request with Same URL"
    ::= { affirmedServicesContentFilterServiceStatisticsCluster-levelInstanceEntry 17 }

affirmedServicesContentFilterServiceStatisticsCluster-levelInstanceNumgooglesafesearchenforced OBJECT-TYPE
    SYNTAX      ConfdString
    MAX-ACCESS  read-only
    STATUS      current
    DESCRIPTION "Total number of Google Safe Search enforced"
    ::= { affirmedServicesContentFilterServiceStatisticsCluster-levelInstanceEntry 18 }

affirmedServicesContentFilterServiceStatisticsCluster-levelInstanceNumyoutubesafesearchenforced OBJECT-TYPE
    SYNTAX      ConfdString
    MAX-ACCESS  read-only
    STATUS      current
    DESCRIPTION "Total number of YouTube Safe Search enforced"
    ::= { affirmedServicesContentFilterServiceStatisticsCluster-levelInstanceEntry 19 }

affirmedServicesContentFilterServiceStatisticsCluster-levelContentCategorizationTable OBJECT-TYPE
    SYNTAX      SEQUENCE OF AffirmedServicesContentFilterServiceStatisticsCluster-levelContentCategorizationEntry
    MAX-ACCESS  not-accessible
    STATUS      current
    DESCRIPTION ""
    ::= { affirmedServicesContentFilterServiceStatisticsCluster-level 3 }

affirmedServicesContentFilterServiceStatisticsCluster-levelContentCategorizationEntry OBJECT-TYPE
    SYNTAX      AffirmedServicesContentFilterServiceStatisticsCluster-levelContentCategorizationEntry
    MAX-ACCESS  not-accessible
    STATUS      current
    DESCRIPTION ""
    INDEX { affirmedServicesContentFilterServiceStatisticsCluster-levelContentCategorizationChassis }
        ::= { affirmedServicesContentFilterServiceStatisticsCluster-levelContentCategorizationTable 1 }

AffirmedServicesContentFilterServiceStatisticsCluster-levelContentCategorizationEntry ::=
    SEQUENCE {
        affirmedServicesContentFilterServiceStatisticsCluster-levelContentCategorizationChassis Unsigned32,
        affirmedServicesContentFilterServiceStatisticsCluster-levelContentCategorizationNumurlbasedlookups ConfdString,
        affirmedServicesContentFilterServiceStatisticsCluster-levelContentCategorizationNumresponsebasedlookups ConfdString,
        affirmedServicesContentFilterServiceStatisticsCluster-levelContentCategorizationNumcategoryabortion ConfdString,
        affirmedServicesContentFilterServiceStatisticsCluster-levelContentCategorizationNumcategoryadvertising ConfdString,
        affirmedServicesContentFilterServiceStatisticsCluster-levelContentCategorizationNumcategoryalcohol ConfdString,
        affirmedServicesContentFilterServiceStatisticsCluster-levelContentCategorizationNumcategoryanonymizer ConfdString,
        affirmedServicesContentFilterServiceStatisticsCluster-levelContentCategorizationNumcategoryartandmuseums ConfdString,
        affirmedServicesContentFilterServiceStatisticsCluster-levelContentCategorizationNumcategoryartnudes ConfdString,
        affirmedServicesContentFilterServiceStatisticsCluster-levelContentCategorizationNumcategoryautomatedwebapplication ConfdString,
        affirmedServicesContentFilterServiceStatisticsCluster-levelContentCategorizationNumcategoryautomotive ConfdString,
        affirmedServicesContentFilterServiceStatisticsCluster-levelContentCategorizationNumcategorybikini ConfdString,
        affirmedServicesContentFilterServiceStatisticsCluster-levelContentCategorizationNumcategoryblogging ConfdString,
        affirmedServicesContentFilterServiceStatisticsCluster-levelContentCategorizationNumcategorybusiness ConfdString,
        affirmedServicesContentFilterServiceStatisticsCluster-levelContentCategorizationNumcategorycashgambling ConfdString,
        affirmedServicesContentFilterServiceStatisticsCluster-levelContentCategorizationNumcategorychat ConfdString,
        affirmedServicesContentFilterServiceStatisticsCluster-levelContentCategorizationNumcategorycontentdeliverynetwork ConfdString,
        affirmedServicesContentFilterServiceStatisticsCluster-levelContentCategorizationNumcategorycriminalskills ConfdString,
        affirmedServicesContentFilterServiceStatisticsCluster-levelContentCategorizationNumcategorycults ConfdString,
        affirmedServicesContentFilterServiceStatisticsCluster-levelContentCategorizationNumcategorydrugs ConfdString,
        affirmedServicesContentFilterServiceStatisticsCluster-levelContentCategorizationNumcategorydynamic ConfdString,
        affirmedServicesContentFilterServiceStatisticsCluster-levelContentCategorizationNumcategoryeducational ConfdString,
        affirmedServicesContentFilterServiceStatisticsCluster-levelContentCategorizationNumcategoryenergy ConfdString,
        affirmedServicesContentFilterServiceStatisticsCluster-levelContentCategorizationNumcategoryenterprisewebmail ConfdString,
        affirmedServicesContentFilterServiceStatisticsCluster-levelContentCategorizationNumcategoryentertainment ConfdString,
        affirmedServicesContentFilterServiceStatisticsCluster-levelContentCategorizationNumcategoryfilesharing ConfdString,
        affirmedServicesContentFilterServiceStatisticsCluster-levelContentCategorizationNumcategoryfinanceandinvesting ConfdString,
        affirmedServicesContentFilterServiceStatisticsCluster-levelContentCategorizationNumcategoryfoodandrestaurants ConfdString,
        affirmedServicesContentFilterServiceStatisticsCluster-levelContentCategorizationNumcategoryforumsandmessageboards ConfdString,
        affirmedServicesContentFilterServiceStatisticsCluster-levelContentCategorizationNumcategoryfreewareandshareware ConfdString,
        affirmedServicesContentFilterServiceStatisticsCluster-levelContentCategorizationNumcategorygambling ConfdString,
        affirmedServicesContentFilterServiceStatisticsCluster-levelContentCategorizationNumcategorygaming ConfdString,
        affirmedServicesContentFilterServiceStatisticsCluster-levelContentCategorizationNumcategoryglamour ConfdString,
        affirmedServicesContentFilterServiceStatisticsCluster-levelContentCategorizationNumcategorygore ConfdString,
        affirmedServicesContentFilterServiceStatisticsCluster-levelContentCategorizationNumcategorygovernment ConfdString,
        affirmedServicesContentFilterServiceStatisticsCluster-levelContentCategorizationNumcategoryhacking ConfdString,
        affirmedServicesContentFilterServiceStatisticsCluster-levelContentCategorizationNumcategoryhate ConfdString,
        affirmedServicesContentFilterServiceStatisticsCluster-levelContentCategorizationNumcategoryhealth ConfdString,
        affirmedServicesContentFilterServiceStatisticsCluster-levelContentCategorizationNumcategoryhobby ConfdString,
        affirmedServicesContentFilterServiceStatisticsCluster-levelContentCategorizationNumcategoryhosting ConfdString,
        affirmedServicesContentFilterServiceStatisticsCluster-levelContentCategorizationNumcategoryinternettelephony ConfdString,
        affirmedServicesContentFilterServiceStatisticsCluster-levelContentCategorizationNumcategoryjobsearch ConfdString,
        affirmedServicesContentFilterServiceStatisticsCluster-levelContentCategorizationNumcategorykids ConfdString,
        affirmedServicesContentFilterServiceStatisticsCluster-levelContentCategorizationNumcategorylaw ConfdString,
        affirmedServicesContentFilterServiceStatisticsCluster-levelContentCategorizationNumcategorylifestyles ConfdString,
        affirmedServicesContentFilterServiceStatisticsCluster-levelContentCategorizationNumcategorymaturecontent ConfdString,
        affirmedServicesContentFilterServiceStatisticsCluster-levelContentCategorizationNumcategorymilitary ConfdString,
        affirmedServicesContentFilterServiceStatisticsCluster-levelContentCategorizationNumcategorymobileentertainment ConfdString,
        affirmedServicesContentFilterServiceStatisticsCluster-levelContentCategorizationNumcategorymusic ConfdString,
        affirmedServicesContentFilterServiceStatisticsCluster-levelContentCategorizationNumcategorynews ConfdString,
        affirmedServicesContentFilterServiceStatisticsCluster-levelContentCategorizationNumcategorynonprofit ConfdString,
        affirmedServicesContentFilterServiceStatisticsCluster-levelContentCategorizationNumcategoryobscene ConfdString,
        affirmedServicesContentFilterServiceStatisticsCluster-levelContentCategorizationNumcategoryoccult ConfdString,
        affirmedServicesContentFilterServiceStatisticsCluster-levelContentCategorizationNumcategoryonlinebackupandstorage ConfdString,
        affirmedServicesContentFilterServiceStatisticsCluster-levelContentCategorizationNumcategorypeertopeer ConfdString,
        affirmedServicesContentFilterServiceStatisticsCluster-levelContentCategorizationNumcategorypets ConfdString,
        affirmedServicesContentFilterServiceStatisticsCluster-levelContentCategorizationNumcategoryphotography ConfdString,
        affirmedServicesContentFilterServiceStatisticsCluster-levelContentCategorizationNumcategoryplaceholder ConfdString,
        affirmedServicesContentFilterServiceStatisticsCluster-levelContentCategorizationNumcategoryplagiarism ConfdString,
        affirmedServicesContentFilterServiceStatisticsCluster-levelContentCategorizationNumcategorypolitics ConfdString,
        affirmedServicesContentFilterServiceStatisticsCluster-levelContentCategorizationNumcategorypornography ConfdString,
        affirmedServicesContentFilterServiceStatisticsCluster-levelContentCategorizationNumcategoryportal ConfdString,
        affirmedServicesContentFilterServiceStatisticsCluster-levelContentCategorizationNumcategorypersonalsanddating ConfdString,
        affirmedServicesContentFilterServiceStatisticsCluster-levelContentCategorizationNumcategoryrealestate ConfdString,
        affirmedServicesContentFilterServiceStatisticsCluster-levelContentCategorizationNumcategoryreference ConfdString,
        affirmedServicesContentFilterServiceStatisticsCluster-levelContentCategorizationNumcategoryreligion ConfdString,
        affirmedServicesContentFilterServiceStatisticsCluster-levelContentCategorizationNumcategoryremoteaccess ConfdString,
        affirmedServicesContentFilterServiceStatisticsCluster-levelContentCategorizationNumcategoryscience ConfdString,
        affirmedServicesContentFilterServiceStatisticsCluster-levelContentCategorizationNumcategorysearch ConfdString,
        affirmedServicesContentFilterServiceStatisticsCluster-levelContentCategorizationNumcategoryselfharm ConfdString,
        affirmedServicesContentFilterServiceStatisticsCluster-levelContentCategorizationNumcategorysexualeducation ConfdString,
        affirmedServicesContentFilterServiceStatisticsCluster-levelContentCategorizationNumcategoryshopping ConfdString,
        affirmedServicesContentFilterServiceStatisticsCluster-levelContentCategorizationNumcategorysports ConfdString,
        affirmedServicesContentFilterServiceStatisticsCluster-levelContentCategorizationNumcategorystreamingmedia ConfdString,
        affirmedServicesContentFilterServiceStatisticsCluster-levelContentCategorizationNumcategorysuicide ConfdString,
        affirmedServicesContentFilterServiceStatisticsCluster-levelContentCategorizationNumcategorytechnologyandtelecommunication ConfdString,
        affirmedServicesContentFilterServiceStatisticsCluster-levelContentCategorizationNumcategorytobacco ConfdString,
        affirmedServicesContentFilterServiceStatisticsCluster-levelContentCategorizationNumcategorytravel ConfdString,
        affirmedServicesContentFilterServiceStatisticsCluster-levelContentCategorizationNumcategoryviolence ConfdString,
        affirmedServicesContentFilterServiceStatisticsCluster-levelContentCategorizationNumcategoryvirtualcommunity ConfdString,
        affirmedServicesContentFilterServiceStatisticsCluster-levelContentCategorizationNumcategoryweapons ConfdString,
        affirmedServicesContentFilterServiceStatisticsCluster-levelContentCategorizationNumcategorywebmail ConfdString,
        affirmedServicesContentFilterServiceStatisticsCluster-levelContentCategorizationNumcategorywedding ConfdString,
        affirmedServicesContentFilterServiceStatisticsCluster-levelContentCategorizationNumcategorywirelessbusiness ConfdString,
        affirmedServicesContentFilterServiceStatisticsCluster-levelContentCategorizationNumcategorywirelesschatsms ConfdString,
        affirmedServicesContentFilterServiceStatisticsCluster-levelContentCategorizationNumcategorywirelessdynamic ConfdString,
        affirmedServicesContentFilterServiceStatisticsCluster-levelContentCategorizationNumcategorywirelessentertainment ConfdString,
        affirmedServicesContentFilterServiceStatisticsCluster-levelContentCategorizationNumcategorywirelessfinance ConfdString,
        affirmedServicesContentFilterServiceStatisticsCluster-levelContentCategorizationNumcategorywirelessgambling ConfdString,
        affirmedServicesContentFilterServiceStatisticsCluster-levelContentCategorizationNumcategorywirelessnews ConfdString,
        affirmedServicesContentFilterServiceStatisticsCluster-levelContentCategorizationNumcategorywirelesspersonalsanddating ConfdString,
        affirmedServicesContentFilterServiceStatisticsCluster-levelContentCategorizationNumcategorywirelesspornography ConfdString,
        affirmedServicesContentFilterServiceStatisticsCluster-levelContentCategorizationNumcategorywirelesssports ConfdString,
        affirmedServicesContentFilterServiceStatisticsCluster-levelContentCategorizationNumcategorywirelesstravel ConfdString,
        affirmedServicesContentFilterServiceStatisticsCluster-levelContentCategorizationNumcategoryunknown ConfdString,
        affirmedServicesContentFilterServiceStatisticsCluster-levelContentCategorizationNumcategorymalware ConfdString,
        affirmedServicesContentFilterServiceStatisticsCluster-levelContentCategorizationNumcategoryphishing ConfdString,
        affirmedServicesContentFilterServiceStatisticsCluster-levelContentCategorizationNumcategoryiwf ConfdString,
        affirmedServicesContentFilterServiceStatisticsCluster-levelContentCategorizationNumcategorynocat ConfdString,
        affirmedServicesContentFilterServiceStatisticsCluster-levelContentCategorizationNumcategoryother ConfdString,
        affirmedServicesContentFilterServiceStatisticsCluster-levelContentCategorizationNumcategoryalcoholkids ConfdString,
        affirmedServicesContentFilterServiceStatisticsCluster-levelContentCategorizationNumcategorytobaccokids ConfdString,
        affirmedServicesContentFilterServiceStatisticsCluster-levelContentCategorizationNumcategorycyberbullying ConfdString,
        affirmedServicesContentFilterServiceStatisticsCluster-levelContentCategorizationNumhttpsrequestlookups ConfdString,
        affirmedServicesContentFilterServiceStatisticsCluster-levelContentCategorizationNumlookupfailure ConfdString,
        affirmedServicesContentFilterServiceStatisticsCluster-levelContentCategorizationNumquicrequestlookups ConfdString,
        affirmedServicesContentFilterServiceStatisticsCluster-levelContentCategorizationNumcategorybbfcwhitelist ConfdString,
        affirmedServicesContentFilterServiceStatisticsCluster-levelContentCategorizationNumcategorybbfcblacklist ConfdString,
        affirmedServicesContentFilterServiceStatisticsCluster-levelContentCategorizationNumcategorycannabidiol ConfdString,
        affirmedServicesContentFilterServiceStatisticsCluster-levelContentCategorizationNumcategorycloudinfrastructure ConfdString,
        affirmedServicesContentFilterServiceStatisticsCluster-levelContentCategorizationNumcategoryfireworks ConfdString,
        affirmedServicesContentFilterServiceStatisticsCluster-levelContentCategorizationNumcategorylingerie ConfdString,
        affirmedServicesContentFilterServiceStatisticsCluster-levelContentCategorizationNumcategorysexualadvice ConfdString,
        affirmedServicesContentFilterServiceStatisticsCluster-levelContentCategorizationNumcategorytracking ConfdString,
        affirmedServicesContentFilterServiceStatisticsCluster-levelContentCategorizationNumcategoryukdeablacklist ConfdString
    }

affirmedServicesContentFilterServiceStatisticsCluster-levelContentCategorizationChassis OBJECT-TYPE
    SYNTAX      Unsigned32
    MAX-ACCESS  not-accessible
    STATUS      current
    DESCRIPTION "chassis ID"
    ::= { affirmedServicesContentFilterServiceStatisticsCluster-levelContentCategorizationEntry 1 }

affirmedServicesContentFilterServiceStatisticsCluster-levelContentCategorizationNumurlbasedlookups OBJECT-TYPE
    SYNTAX      ConfdString
    MAX-ACCESS  read-only
    STATUS      current
    DESCRIPTION "Total number of HTTP request Lookups"
    ::= { affirmedServicesContentFilterServiceStatisticsCluster-levelContentCategorizationEntry 2 }

affirmedServicesContentFilterServiceStatisticsCluster-levelContentCategorizationNumresponsebasedlookups OBJECT-TYPE
    SYNTAX      ConfdString
    MAX-ACCESS  read-only
    STATUS      current
    DESCRIPTION "Total number of HTTP Response-based Lookups"
    ::= { affirmedServicesContentFilterServiceStatisticsCluster-levelContentCategorizationEntry 3 }

affirmedServicesContentFilterServiceStatisticsCluster-levelContentCategorizationNumcategoryabortion OBJECT-TYPE
    SYNTAX      ConfdString
    MAX-ACCESS  read-only
    STATUS      current
    DESCRIPTION "Total number of requests categorized as Abortion Online Category"
    ::= { affirmedServicesContentFilterServiceStatisticsCluster-levelContentCategorizationEntry 4 }

affirmedServicesContentFilterServiceStatisticsCluster-levelContentCategorizationNumcategoryadvertising OBJECT-TYPE
    SYNTAX      ConfdString
    MAX-ACCESS  read-only
    STATUS      current
    DESCRIPTION "Total number of requests categorized as Advertising Online Category"
    ::= { affirmedServicesContentFilterServiceStatisticsCluster-levelContentCategorizationEntry 5 }

affirmedServicesContentFilterServiceStatisticsCluster-levelContentCategorizationNumcategoryalcohol OBJECT-TYPE
    SYNTAX      ConfdString
    MAX-ACCESS  read-only
    STATUS      current
    DESCRIPTION "Total number of requests categorized as Alcohol Online Category"
    ::= { affirmedServicesContentFilterServiceStatisticsCluster-levelContentCategorizationEntry 6 }

affirmedServicesContentFilterServiceStatisticsCluster-levelContentCategorizationNumcategoryanonymizer OBJECT-TYPE
    SYNTAX      ConfdString
    MAX-ACCESS  read-only
    STATUS      current
    DESCRIPTION "Total number of requests categorized as Anonymizer Online Category"
    ::= { affirmedServicesContentFilterServiceStatisticsCluster-levelContentCategorizationEntry 7 }

affirmedServicesContentFilterServiceStatisticsCluster-levelContentCategorizationNumcategoryartandmuseums OBJECT-TYPE
    SYNTAX      ConfdString
    MAX-ACCESS  read-only
    STATUS      current
    DESCRIPTION "Total number of requests categorized as Art And Museums Online Category"
    ::= { affirmedServicesContentFilterServiceStatisticsCluster-levelContentCategorizationEntry 8 }

affirmedServicesContentFilterServiceStatisticsCluster-levelContentCategorizationNumcategoryartnudes OBJECT-TYPE
    SYNTAX      ConfdString
    MAX-ACCESS  read-only
    STATUS      current
    DESCRIPTION "Total number of requests categorized as Art Nudes Online Category"
    ::= { affirmedServicesContentFilterServiceStatisticsCluster-levelContentCategorizationEntry 9 }

affirmedServicesContentFilterServiceStatisticsCluster-levelContentCategorizationNumcategoryautomatedwebapplication OBJECT-TYPE
    SYNTAX      ConfdString
    MAX-ACCESS  read-only
    STATUS      current
    DESCRIPTION "Total number of requests categorized as Automated Web Application Online Category"
    ::= { affirmedServicesContentFilterServiceStatisticsCluster-levelContentCategorizationEntry 10 }

affirmedServicesContentFilterServiceStatisticsCluster-levelContentCategorizationNumcategoryautomotive OBJECT-TYPE
    SYNTAX      ConfdString
    MAX-ACCESS  read-only
    STATUS      current
    DESCRIPTION "Total number of requests categorized as Automotive Online Category"
    ::= { affirmedServicesContentFilterServiceStatisticsCluster-levelContentCategorizationEntry 11 }

affirmedServicesContentFilterServiceStatisticsCluster-levelContentCategorizationNumcategorybikini OBJECT-TYPE
    SYNTAX      ConfdString
    MAX-ACCESS  read-only
    STATUS      current
    DESCRIPTION "Total number of requests categorized as Bikini Online Category"
    ::= { affirmedServicesContentFilterServiceStatisticsCluster-levelContentCategorizationEntry 12 }

affirmedServicesContentFilterServiceStatisticsCluster-levelContentCategorizationNumcategoryblogging OBJECT-TYPE
    SYNTAX      ConfdString
    MAX-ACCESS  read-only
    STATUS      current
    DESCRIPTION "Total number of requests categorized as Blogging Online Category"
    ::= { affirmedServicesContentFilterServiceStatisticsCluster-levelContentCategorizationEntry 13 }

affirmedServicesContentFilterServiceStatisticsCluster-levelContentCategorizationNumcategorybusiness OBJECT-TYPE
    SYNTAX      ConfdString
    MAX-ACCESS  read-only
    STATUS      current
    DESCRIPTION "Total number of requests categorized as Business Online Category"
    ::= { affirmedServicesContentFilterServiceStatisticsCluster-levelContentCategorizationEntry 14 }

affirmedServicesContentFilterServiceStatisticsCluster-levelContentCategorizationNumcategorycashgambling OBJECT-TYPE
    SYNTAX      ConfdString
    MAX-ACCESS  read-only
    STATUS      current
    DESCRIPTION "Total number of requests categorized as Cash Gambling Online Category"
    ::= { affirmedServicesContentFilterServiceStatisticsCluster-levelContentCategorizationEntry 15 }

affirmedServicesContentFilterServiceStatisticsCluster-levelContentCategorizationNumcategorychat OBJECT-TYPE
    SYNTAX      ConfdString
    MAX-ACCESS  read-only
    STATUS      current
    DESCRIPTION "Total number of requests categorized as Chat Online Category"
    ::= { affirmedServicesContentFilterServiceStatisticsCluster-levelContentCategorizationEntry 16 }

affirmedServicesContentFilterServiceStatisticsCluster-levelContentCategorizationNumcategorycontentdeliverynetwork OBJECT-TYPE
    SYNTAX      ConfdString
    MAX-ACCESS  read-only
    STATUS      current
    DESCRIPTION "Total number of requests categorized as Content Delivery Network Online Category"
    ::= { affirmedServicesContentFilterServiceStatisticsCluster-levelContentCategorizationEntry 17 }

affirmedServicesContentFilterServiceStatisticsCluster-levelContentCategorizationNumcategorycriminalskills OBJECT-TYPE
    SYNTAX      ConfdString
    MAX-ACCESS  read-only
    STATUS      current
    DESCRIPTION "Total number of requests categorized as Criminal Skills Online Category"
    ::= { affirmedServicesContentFilterServiceStatisticsCluster-levelContentCategorizationEntry 18 }

affirmedServicesContentFilterServiceStatisticsCluster-levelContentCategorizationNumcategorycults OBJECT-TYPE
    SYNTAX      ConfdString
    MAX-ACCESS  read-only
    STATUS      current
    DESCRIPTION "Total number of requests categorized as Cults Online Category"
    ::= { affirmedServicesContentFilterServiceStatisticsCluster-levelContentCategorizationEntry 19 }

affirmedServicesContentFilterServiceStatisticsCluster-levelContentCategorizationNumcategorydrugs OBJECT-TYPE
    SYNTAX      ConfdString
    MAX-ACCESS  read-only
    STATUS      current
    DESCRIPTION "Total number of requests categorized as Drugs Online Category"
    ::= { affirmedServicesContentFilterServiceStatisticsCluster-levelContentCategorizationEntry 20 }

affirmedServicesContentFilterServiceStatisticsCluster-levelContentCategorizationNumcategorydynamic OBJECT-TYPE
    SYNTAX      ConfdString
    MAX-ACCESS  read-only
    STATUS      current
    DESCRIPTION "Total number of requests categorized as Dynamic Online Category"
    ::= { affirmedServicesContentFilterServiceStatisticsCluster-levelContentCategorizationEntry 21 }

affirmedServicesContentFilterServiceStatisticsCluster-levelContentCategorizationNumcategoryeducational OBJECT-TYPE
    SYNTAX      ConfdString
    MAX-ACCESS  read-only
    STATUS      current
    DESCRIPTION "Total number of requests categorized as Educational Online Category"
    ::= { affirmedServicesContentFilterServiceStatisticsCluster-levelContentCategorizationEntry 22 }

affirmedServicesContentFilterServiceStatisticsCluster-levelContentCategorizationNumcategoryenergy OBJECT-TYPE
    SYNTAX      ConfdString
    MAX-ACCESS  read-only
    STATUS      current
    DESCRIPTION "Total number of requests categorized as Energy Online Category"
    ::= { affirmedServicesContentFilterServiceStatisticsCluster-levelContentCategorizationEntry 23 }

affirmedServicesContentFilterServiceStatisticsCluster-levelContentCategorizationNumcategoryenterprisewebmail OBJECT-TYPE
    SYNTAX      ConfdString
    MAX-ACCESS  read-only
    STATUS      current
    DESCRIPTION "Total number of requests categorized as Enterprise Webmail Online Category"
    ::= { affirmedServicesContentFilterServiceStatisticsCluster-levelContentCategorizationEntry 24 }

affirmedServicesContentFilterServiceStatisticsCluster-levelContentCategorizationNumcategoryentertainment OBJECT-TYPE
    SYNTAX      ConfdString
    MAX-ACCESS  read-only
    STATUS      current
    DESCRIPTION "Total number of requests categorized as Entertainment Online Category"
    ::= { affirmedServicesContentFilterServiceStatisticsCluster-levelContentCategorizationEntry 25 }

affirmedServicesContentFilterServiceStatisticsCluster-levelContentCategorizationNumcategoryfilesharing OBJECT-TYPE
    SYNTAX      ConfdString
    MAX-ACCESS  read-only
    STATUS      current
    DESCRIPTION "Total number of requests categorized as Filesharing Online Category"
    ::= { affirmedServicesContentFilterServiceStatisticsCluster-levelContentCategorizationEntry 26 }

affirmedServicesContentFilterServiceStatisticsCluster-levelContentCategorizationNumcategoryfinanceandinvesting OBJECT-TYPE
    SYNTAX      ConfdString
    MAX-ACCESS  read-only
    STATUS      current
    DESCRIPTION "Total number of requests categorized as Finance And Investing Online Category"
    ::= { affirmedServicesContentFilterServiceStatisticsCluster-levelContentCategorizationEntry 27 }

affirmedServicesContentFilterServiceStatisticsCluster-levelContentCategorizationNumcategoryfoodandrestaurants OBJECT-TYPE
    SYNTAX      ConfdString
    MAX-ACCESS  read-only
    STATUS      current
    DESCRIPTION "Total number of requests categorized as Food And Restaurants Online Category"
    ::= { affirmedServicesContentFilterServiceStatisticsCluster-levelContentCategorizationEntry 28 }

affirmedServicesContentFilterServiceStatisticsCluster-levelContentCategorizationNumcategoryforumsandmessageboards OBJECT-TYPE
    SYNTAX      ConfdString
    MAX-ACCESS  read-only
    STATUS      current
    DESCRIPTION "Total number of requests categorized as Forums And Messageboards Online Category"
    ::= { affirmedServicesContentFilterServiceStatisticsCluster-levelContentCategorizationEntry 29 }

affirmedServicesContentFilterServiceStatisticsCluster-levelContentCategorizationNumcategoryfreewareandshareware OBJECT-TYPE
    SYNTAX      ConfdString
    MAX-ACCESS  read-only
    STATUS      current
    DESCRIPTION "Total number of requests categorized as Freeware And Shareware Online Category"
    ::= { affirmedServicesContentFilterServiceStatisticsCluster-levelContentCategorizationEntry 30 }

affirmedServicesContentFilterServiceStatisticsCluster-levelContentCategorizationNumcategorygambling OBJECT-TYPE
    SYNTAX      ConfdString
    MAX-ACCESS  read-only
    STATUS      current
    DESCRIPTION "Total number of requests categorized as Gambling Online Category"
    ::= { affirmedServicesContentFilterServiceStatisticsCluster-levelContentCategorizationEntry 31 }

affirmedServicesContentFilterServiceStatisticsCluster-levelContentCategorizationNumcategorygaming OBJECT-TYPE
    SYNTAX      ConfdString
    MAX-ACCESS  read-only
    STATUS      current
    DESCRIPTION "Total number of requests categorized as Gaming Online Category"
    ::= { affirmedServicesContentFilterServiceStatisticsCluster-levelContentCategorizationEntry 32 }

affirmedServicesContentFilterServiceStatisticsCluster-levelContentCategorizationNumcategoryglamour OBJECT-TYPE
    SYNTAX      ConfdString
    MAX-ACCESS  read-only
    STATUS      current
    DESCRIPTION "Total number of requests categorized as Glamour Online Category"
    ::= { affirmedServicesContentFilterServiceStatisticsCluster-levelContentCategorizationEntry 33 }

affirmedServicesContentFilterServiceStatisticsCluster-levelContentCategorizationNumcategorygore OBJECT-TYPE
    SYNTAX      ConfdString
    MAX-ACCESS  read-only
    STATUS      current
    DESCRIPTION "Total number of requests categorized as Gore Online Category"
    ::= { affirmedServicesContentFilterServiceStatisticsCluster-levelContentCategorizationEntry 34 }

affirmedServicesContentFilterServiceStatisticsCluster-levelContentCategorizationNumcategorygovernment OBJECT-TYPE
    SYNTAX      ConfdString
    MAX-ACCESS  read-only
    STATUS      current
    DESCRIPTION "Total number of requests categorized as Government Online Category"
    ::= { affirmedServicesContentFilterServiceStatisticsCluster-levelContentCategorizationEntry 35 }

affirmedServicesContentFilterServiceStatisticsCluster-levelContentCategorizationNumcategoryhacking OBJECT-TYPE
    SYNTAX      ConfdString
    MAX-ACCESS  read-only
    STATUS      current
    DESCRIPTION "Total number of requests categorized as Hacking Online Category"
    ::= { affirmedServicesContentFilterServiceStatisticsCluster-levelContentCategorizationEntry 36 }

affirmedServicesContentFilterServiceStatisticsCluster-levelContentCategorizationNumcategoryhate OBJECT-TYPE
    SYNTAX      ConfdString
    MAX-ACCESS  read-only
    STATUS      current
    DESCRIPTION "Total number of requests categorized as Hate Online Category"
    ::= { affirmedServicesContentFilterServiceStatisticsCluster-levelContentCategorizationEntry 37 }

affirmedServicesContentFilterServiceStatisticsCluster-levelContentCategorizationNumcategoryhealth OBJECT-TYPE
    SYNTAX      ConfdString
    MAX-ACCESS  read-only
    STATUS      current
    DESCRIPTION "Total number of requests categorized as Health Online Category"
    ::= { affirmedServicesContentFilterServiceStatisticsCluster-levelContentCategorizationEntry 38 }

affirmedServicesContentFilterServiceStatisticsCluster-levelContentCategorizationNumcategoryhobby OBJECT-TYPE
    SYNTAX      ConfdString
    MAX-ACCESS  read-only
    STATUS      current
    DESCRIPTION "Total number of requests categorized as Hobby Online Category"
    ::= { affirmedServicesContentFilterServiceStatisticsCluster-levelContentCategorizationEntry 39 }

affirmedServicesContentFilterServiceStatisticsCluster-levelContentCategorizationNumcategoryhosting OBJECT-TYPE
    SYNTAX      ConfdString
    MAX-ACCESS  read-only
    STATUS      current
    DESCRIPTION "Total number of requests categorized as Hosting Online Category"
    ::= { affirmedServicesContentFilterServiceStatisticsCluster-levelContentCategorizationEntry 40 }

affirmedServicesContentFilterServiceStatisticsCluster-levelContentCategorizationNumcategoryinternettelephony OBJECT-TYPE
    SYNTAX      ConfdString
    MAX-ACCESS  read-only
    STATUS      current
    DESCRIPTION "Total number of requests categorized as Internet Telephony Online Category"
    ::= { affirmedServicesContentFilterServiceStatisticsCluster-levelContentCategorizationEntry 41 }

affirmedServicesContentFilterServiceStatisticsCluster-levelContentCategorizationNumcategoryjobsearch OBJECT-TYPE
    SYNTAX      ConfdString
    MAX-ACCESS  read-only
    STATUS      current
    DESCRIPTION "Total number of requests categorized as Job Search Online Category"
    ::= { affirmedServicesContentFilterServiceStatisticsCluster-levelContentCategorizationEntry 42 }

affirmedServicesContentFilterServiceStatisticsCluster-levelContentCategorizationNumcategorykids OBJECT-TYPE
    SYNTAX      ConfdString
    MAX-ACCESS  read-only
    STATUS      current
    DESCRIPTION "Total number of requests categorized as Kids Online Category"
    ::= { affirmedServicesContentFilterServiceStatisticsCluster-levelContentCategorizationEntry 43 }

affirmedServicesContentFilterServiceStatisticsCluster-levelContentCategorizationNumcategorylaw OBJECT-TYPE
    SYNTAX      ConfdString
    MAX-ACCESS  read-only
    STATUS      current
    DESCRIPTION "Total number of requests categorized as Law Online Category"
    ::= { affirmedServicesContentFilterServiceStatisticsCluster-levelContentCategorizationEntry 44 }

affirmedServicesContentFilterServiceStatisticsCluster-levelContentCategorizationNumcategorylifestyles OBJECT-TYPE
    SYNTAX      ConfdString
    MAX-ACCESS  read-only
    STATUS      current
    DESCRIPTION "Total number of requests categorized as Lifestyles Online Category"
    ::= { affirmedServicesContentFilterServiceStatisticsCluster-levelContentCategorizationEntry 45 }

affirmedServicesContentFilterServiceStatisticsCluster-levelContentCategorizationNumcategorymaturecontent OBJECT-TYPE
    SYNTAX      ConfdString
    MAX-ACCESS  read-only
    STATUS      current
    DESCRIPTION "Total number of requests categorized as Mature Content Online Category"
    ::= { affirmedServicesContentFilterServiceStatisticsCluster-levelContentCategorizationEntry 46 }

affirmedServicesContentFilterServiceStatisticsCluster-levelContentCategorizationNumcategorymilitary OBJECT-TYPE
    SYNTAX      ConfdString
    MAX-ACCESS  read-only
    STATUS      current
    DESCRIPTION "Total number of requests categorized as Military Online Category"
    ::= { affirmedServicesContentFilterServiceStatisticsCluster-levelContentCategorizationEntry 47 }

affirmedServicesContentFilterServiceStatisticsCluster-levelContentCategorizationNumcategorymobileentertainment OBJECT-TYPE
    SYNTAX      ConfdString
    MAX-ACCESS  read-only
    STATUS      current
    DESCRIPTION "Total number of requests categorized as Mobile Entertainment Online Category"
    ::= { affirmedServicesContentFilterServiceStatisticsCluster-levelContentCategorizationEntry 48 }

affirmedServicesContentFilterServiceStatisticsCluster-levelContentCategorizationNumcategorymusic OBJECT-TYPE
    SYNTAX      ConfdString
    MAX-ACCESS  read-only
    STATUS      current
    DESCRIPTION "Total number of requests categorized as Music Online Category"
    ::= { affirmedServicesContentFilterServiceStatisticsCluster-levelContentCategorizationEntry 49 }

affirmedServicesContentFilterServiceStatisticsCluster-levelContentCategorizationNumcategorynews OBJECT-TYPE
    SYNTAX      ConfdString
    MAX-ACCESS  read-only
    STATUS      current
    DESCRIPTION "Total number of requests categorized as News Online Category"
    ::= { affirmedServicesContentFilterServiceStatisticsCluster-levelContentCategorizationEntry 50 }

affirmedServicesContentFilterServiceStatisticsCluster-levelContentCategorizationNumcategorynonprofit OBJECT-TYPE
    SYNTAX      ConfdString
    MAX-ACCESS  read-only
    STATUS      current
    DESCRIPTION "Total number of requests categorized as Non Profit Online Category"
    ::= { affirmedServicesContentFilterServiceStatisticsCluster-levelContentCategorizationEntry 51 }

affirmedServicesContentFilterServiceStatisticsCluster-levelContentCategorizationNumcategoryobscene OBJECT-TYPE
    SYNTAX      ConfdString
    MAX-ACCESS  read-only
    STATUS      current
    DESCRIPTION "Total number of requests categorized as Obscene Online Category"
    ::= { affirmedServicesContentFilterServiceStatisticsCluster-levelContentCategorizationEntry 52 }

affirmedServicesContentFilterServiceStatisticsCluster-levelContentCategorizationNumcategoryoccult OBJECT-TYPE
    SYNTAX      ConfdString
    MAX-ACCESS  read-only
    STATUS      current
    DESCRIPTION "Total number of requests categorized as Occult Online Category"
    ::= { affirmedServicesContentFilterServiceStatisticsCluster-levelContentCategorizationEntry 53 }

affirmedServicesContentFilterServiceStatisticsCluster-levelContentCategorizationNumcategoryonlinebackupandstorage OBJECT-TYPE
    SYNTAX      ConfdString
    MAX-ACCESS  read-only
    STATUS      current
    DESCRIPTION "Total number of requests categorized as Online Backup And Storage Online Category"
    ::= { affirmedServicesContentFilterServiceStatisticsCluster-levelContentCategorizationEntry 54 }

affirmedServicesContentFilterServiceStatisticsCluster-levelContentCategorizationNumcategorypeertopeer OBJECT-TYPE
    SYNTAX      ConfdString
    MAX-ACCESS  read-only
    STATUS      current
    DESCRIPTION "Total number of requests categorized as PeerToPeer Online Category"
    ::= { affirmedServicesContentFilterServiceStatisticsCluster-levelContentCategorizationEntry 55 }

affirmedServicesContentFilterServiceStatisticsCluster-levelContentCategorizationNumcategorypets OBJECT-TYPE
    SYNTAX      ConfdString
    MAX-ACCESS  read-only
    STATUS      current
    DESCRIPTION "Total number of requests categorized as Pets Online Category"
    ::= { affirmedServicesContentFilterServiceStatisticsCluster-levelContentCategorizationEntry 56 }

affirmedServicesContentFilterServiceStatisticsCluster-levelContentCategorizationNumcategoryphotography OBJECT-TYPE
    SYNTAX      ConfdString
    MAX-ACCESS  read-only
    STATUS      current
    DESCRIPTION "Total number of requests categorized as Photography Online Category"
    ::= { affirmedServicesContentFilterServiceStatisticsCluster-levelContentCategorizationEntry 57 }

affirmedServicesContentFilterServiceStatisticsCluster-levelContentCategorizationNumcategoryplaceholder OBJECT-TYPE
    SYNTAX      ConfdString
    MAX-ACCESS  read-only
    STATUS      current
    DESCRIPTION "Total number of requests categorized as Placeholder Online Category"
    ::= { affirmedServicesContentFilterServiceStatisticsCluster-levelContentCategorizationEntry 58 }

affirmedServicesContentFilterServiceStatisticsCluster-levelContentCategorizationNumcategoryplagiarism OBJECT-TYPE
    SYNTAX      ConfdString
    MAX-ACCESS  read-only
    STATUS      current
    DESCRIPTION "Total number of requests categorized as Plagiarism Online Category"
    ::= { affirmedServicesContentFilterServiceStatisticsCluster-levelContentCategorizationEntry 59 }

affirmedServicesContentFilterServiceStatisticsCluster-levelContentCategorizationNumcategorypolitics OBJECT-TYPE
    SYNTAX      ConfdString
    MAX-ACCESS  read-only
    STATUS      current
    DESCRIPTION "Total number of requests categorized as Politics Online Category"
    ::= { affirmedServicesContentFilterServiceStatisticsCluster-levelContentCategorizationEntry 60 }

affirmedServicesContentFilterServiceStatisticsCluster-levelContentCategorizationNumcategorypornography OBJECT-TYPE
    SYNTAX      ConfdString
    MAX-ACCESS  read-only
    STATUS      current
    DESCRIPTION "Total number of requests categorized as Pornography Online Category"
    ::= { affirmedServicesContentFilterServiceStatisticsCluster-levelContentCategorizationEntry 61 }

affirmedServicesContentFilterServiceStatisticsCluster-levelContentCategorizationNumcategoryportal OBJECT-TYPE
    SYNTAX      ConfdString
    MAX-ACCESS  read-only
    STATUS      current
    DESCRIPTION "Total number of requests categorized as Portal Online Category"
    ::= { affirmedServicesContentFilterServiceStatisticsCluster-levelContentCategorizationEntry 62 }

affirmedServicesContentFilterServiceStatisticsCluster-levelContentCategorizationNumcategorypersonalsanddating OBJECT-TYPE
    SYNTAX      ConfdString
    MAX-ACCESS  read-only
    STATUS      current
    DESCRIPTION "Total number of requests categorized as Personals And Dating Online Category"
    ::= { affirmedServicesContentFilterServiceStatisticsCluster-levelContentCategorizationEntry 63 }

affirmedServicesContentFilterServiceStatisticsCluster-levelContentCategorizationNumcategoryrealestate OBJECT-TYPE
    SYNTAX      ConfdString
    MAX-ACCESS  read-only
    STATUS      current
    DESCRIPTION "Total number of requests categorized as Real Estate Online Category"
    ::= { affirmedServicesContentFilterServiceStatisticsCluster-levelContentCategorizationEntry 64 }

affirmedServicesContentFilterServiceStatisticsCluster-levelContentCategorizationNumcategoryreference OBJECT-TYPE
    SYNTAX      ConfdString
    MAX-ACCESS  read-only
    STATUS      current
    DESCRIPTION "Total number of requests categorized as Reference Online Category"
    ::= { affirmedServicesContentFilterServiceStatisticsCluster-levelContentCategorizationEntry 65 }

affirmedServicesContentFilterServiceStatisticsCluster-levelContentCategorizationNumcategoryreligion OBJECT-TYPE
    SYNTAX      ConfdString
    MAX-ACCESS  read-only
    STATUS      current
    DESCRIPTION "Total number of requests categorized as Religion Online Category"
    ::= { affirmedServicesContentFilterServiceStatisticsCluster-levelContentCategorizationEntry 66 }

affirmedServicesContentFilterServiceStatisticsCluster-levelContentCategorizationNumcategoryremoteaccess OBJECT-TYPE
    SYNTAX      ConfdString
    MAX-ACCESS  read-only
    STATUS      current
    DESCRIPTION "Total number of requests categorized as Remote Access Online Category"
    ::= { affirmedServicesContentFilterServiceStatisticsCluster-levelContentCategorizationEntry 67 }

affirmedServicesContentFilterServiceStatisticsCluster-levelContentCategorizationNumcategoryscience OBJECT-TYPE
    SYNTAX      ConfdString
    MAX-ACCESS  read-only
    STATUS      current
    DESCRIPTION "Total number of requests categorized as Science Online Category"
    ::= { affirmedServicesContentFilterServiceStatisticsCluster-levelContentCategorizationEntry 68 }

affirmedServicesContentFilterServiceStatisticsCluster-levelContentCategorizationNumcategorysearch OBJECT-TYPE
    SYNTAX      ConfdString
    MAX-ACCESS  read-only
    STATUS      current
    DESCRIPTION "Total number of requests categorized as Search Online Category"
    ::= { affirmedServicesContentFilterServiceStatisticsCluster-levelContentCategorizationEntry 69 }

affirmedServicesContentFilterServiceStatisticsCluster-levelContentCategorizationNumcategoryselfharm OBJECT-TYPE
    SYNTAX      ConfdString
    MAX-ACCESS  read-only
    STATUS      current
    DESCRIPTION "Total number of requests categorized as Self Harm Online Category"
    ::= { affirmedServicesContentFilterServiceStatisticsCluster-levelContentCategorizationEntry 70 }

affirmedServicesContentFilterServiceStatisticsCluster-levelContentCategorizationNumcategorysexualeducation OBJECT-TYPE
    SYNTAX      ConfdString
    MAX-ACCESS  read-only
    STATUS      current
    DESCRIPTION "Total number of requests categorized as Sexual Education Online Category"
    ::= { affirmedServicesContentFilterServiceStatisticsCluster-levelContentCategorizationEntry 71 }

affirmedServicesContentFilterServiceStatisticsCluster-levelContentCategorizationNumcategoryshopping OBJECT-TYPE
    SYNTAX      ConfdString
    MAX-ACCESS  read-only
    STATUS      current
    DESCRIPTION "Total number of requests categorized as Shopping Online Category"
    ::= { affirmedServicesContentFilterServiceStatisticsCluster-levelContentCategorizationEntry 72 }

affirmedServicesContentFilterServiceStatisticsCluster-levelContentCategorizationNumcategorysports OBJECT-TYPE
    SYNTAX      ConfdString
    MAX-ACCESS  read-only
    STATUS      current
    DESCRIPTION "Total number of requests categorized as Sports Online Category"
    ::= { affirmedServicesContentFilterServiceStatisticsCluster-levelContentCategorizationEntry 73 }

affirmedServicesContentFilterServiceStatisticsCluster-levelContentCategorizationNumcategorystreamingmedia OBJECT-TYPE
    SYNTAX      ConfdString
    MAX-ACCESS  read-only
    STATUS      current
    DESCRIPTION "Total number of requests categorized as Streaming Media Online Category"
    ::= { affirmedServicesContentFilterServiceStatisticsCluster-levelContentCategorizationEntry 74 }

affirmedServicesContentFilterServiceStatisticsCluster-levelContentCategorizationNumcategorysuicide OBJECT-TYPE
    SYNTAX      ConfdString
    MAX-ACCESS  read-only
    STATUS      current
    DESCRIPTION "Total number of requests categorized as Suicide Online Category"
    ::= { affirmedServicesContentFilterServiceStatisticsCluster-levelContentCategorizationEntry 75 }

affirmedServicesContentFilterServiceStatisticsCluster-levelContentCategorizationNumcategorytechnologyandtelecommunication OBJECT-TYPE
    SYNTAX      ConfdString
    MAX-ACCESS  read-only
    STATUS      current
    DESCRIPTION "Total number of requests categorized as Technology And Telecommunication Online Category"
    ::= { affirmedServicesContentFilterServiceStatisticsCluster-levelContentCategorizationEntry 76 }

affirmedServicesContentFilterServiceStatisticsCluster-levelContentCategorizationNumcategorytobacco OBJECT-TYPE
    SYNTAX      ConfdString
    MAX-ACCESS  read-only
    STATUS      current
    DESCRIPTION "Total number of requests categorized as Tobacco Online Category"
    ::= { affirmedServicesContentFilterServiceStatisticsCluster-levelContentCategorizationEntry 77 }

affirmedServicesContentFilterServiceStatisticsCluster-levelContentCategorizationNumcategorytravel OBJECT-TYPE
    SYNTAX      ConfdString
    MAX-ACCESS  read-only
    STATUS      current
    DESCRIPTION "Total number of requests categorized as Travel Online Category"
    ::= { affirmedServicesContentFilterServiceStatisticsCluster-levelContentCategorizationEntry 78 }

affirmedServicesContentFilterServiceStatisticsCluster-levelContentCategorizationNumcategoryviolence OBJECT-TYPE
    SYNTAX      ConfdString
    MAX-ACCESS  read-only
    STATUS      current
    DESCRIPTION "Total number of requests categorized as Violence Online Category"
    ::= { affirmedServicesContentFilterServiceStatisticsCluster-levelContentCategorizationEntry 79 }

affirmedServicesContentFilterServiceStatisticsCluster-levelContentCategorizationNumcategoryvirtualcommunity OBJECT-TYPE
    SYNTAX      ConfdString
    MAX-ACCESS  read-only
    STATUS      current
    DESCRIPTION "Total number of requests categorized as Virtual Community Online Category"
    ::= { affirmedServicesContentFilterServiceStatisticsCluster-levelContentCategorizationEntry 80 }

affirmedServicesContentFilterServiceStatisticsCluster-levelContentCategorizationNumcategoryweapons OBJECT-TYPE
    SYNTAX      ConfdString
    MAX-ACCESS  read-only
    STATUS      current
    DESCRIPTION "Total number of requests categorized as Weapons Online Category"
    ::= { affirmedServicesContentFilterServiceStatisticsCluster-levelContentCategorizationEntry 81 }

affirmedServicesContentFilterServiceStatisticsCluster-levelContentCategorizationNumcategorywebmail OBJECT-TYPE
    SYNTAX      ConfdString
    MAX-ACCESS  read-only
    STATUS      current
    DESCRIPTION "Total number of requests categorized as Webmail Online Category"
    ::= { affirmedServicesContentFilterServiceStatisticsCluster-levelContentCategorizationEntry 82 }

affirmedServicesContentFilterServiceStatisticsCluster-levelContentCategorizationNumcategorywedding OBJECT-TYPE
    SYNTAX      ConfdString
    MAX-ACCESS  read-only
    STATUS      current
    DESCRIPTION "Total number of requests categorized as Wedding Online Category"
    ::= { affirmedServicesContentFilterServiceStatisticsCluster-levelContentCategorizationEntry 83 }

affirmedServicesContentFilterServiceStatisticsCluster-levelContentCategorizationNumcategorywirelessbusiness OBJECT-TYPE
    SYNTAX      ConfdString
    MAX-ACCESS  read-only
    STATUS      current
    DESCRIPTION "Total number of requests categorized as Wireless Business Online Category"
    ::= { affirmedServicesContentFilterServiceStatisticsCluster-levelContentCategorizationEntry 84 }

affirmedServicesContentFilterServiceStatisticsCluster-levelContentCategorizationNumcategorywirelesschatsms OBJECT-TYPE
    SYNTAX      ConfdString
    MAX-ACCESS  read-only
    STATUS      current
    DESCRIPTION "Total number of requests categorized as Wireless Chat and SMS Online Category"
    ::= { affirmedServicesContentFilterServiceStatisticsCluster-levelContentCategorizationEntry 85 }

affirmedServicesContentFilterServiceStatisticsCluster-levelContentCategorizationNumcategorywirelessdynamic OBJECT-TYPE
    SYNTAX      ConfdString
    MAX-ACCESS  read-only
    STATUS      current
    DESCRIPTION "Total number of requests categorized as Wireless Dynamic Online Category"
    ::= { affirmedServicesContentFilterServiceStatisticsCluster-levelContentCategorizationEntry 86 }

affirmedServicesContentFilterServiceStatisticsCluster-levelContentCategorizationNumcategorywirelessentertainment OBJECT-TYPE
    SYNTAX      ConfdString
    MAX-ACCESS  read-only
    STATUS      current
    DESCRIPTION "Total number of requests categorized as Wireless Entertainment Online Category"
    ::= { affirmedServicesContentFilterServiceStatisticsCluster-levelContentCategorizationEntry 87 }

affirmedServicesContentFilterServiceStatisticsCluster-levelContentCategorizationNumcategorywirelessfinance OBJECT-TYPE
    SYNTAX      ConfdString
    MAX-ACCESS  read-only
    STATUS      current
    DESCRIPTION "Total number of requests categorized as Wireless Finance Online Category"
    ::= { affirmedServicesContentFilterServiceStatisticsCluster-levelContentCategorizationEntry 88 }

affirmedServicesContentFilterServiceStatisticsCluster-levelContentCategorizationNumcategorywirelessgambling OBJECT-TYPE
    SYNTAX      ConfdString
    MAX-ACCESS  read-only
    STATUS      current
    DESCRIPTION "Total number of requests categorized as Wireless Gambling Online Category"
    ::= { affirmedServicesContentFilterServiceStatisticsCluster-levelContentCategorizationEntry 89 }

affirmedServicesContentFilterServiceStatisticsCluster-levelContentCategorizationNumcategorywirelessnews OBJECT-TYPE
    SYNTAX      ConfdString
    MAX-ACCESS  read-only
    STATUS      current
    DESCRIPTION "Total number of requests categorized as Wireless News Online Category"
    ::= { affirmedServicesContentFilterServiceStatisticsCluster-levelContentCategorizationEntry 90 }

affirmedServicesContentFilterServiceStatisticsCluster-levelContentCategorizationNumcategorywirelesspersonalsanddating OBJECT-TYPE
    SYNTAX      ConfdString
    MAX-ACCESS  read-only
    STATUS      current
    DESCRIPTION "Total number of requests categorized as Wireless Personals And Dating Online Category"
    ::= { affirmedServicesContentFilterServiceStatisticsCluster-levelContentCategorizationEntry 91 }

affirmedServicesContentFilterServiceStatisticsCluster-levelContentCategorizationNumcategorywirelesspornography OBJECT-TYPE
    SYNTAX      ConfdString
    MAX-ACCESS  read-only
    STATUS      current
    DESCRIPTION "Total number of requests categorized as Wireless Pornography Online Category"
    ::= { affirmedServicesContentFilterServiceStatisticsCluster-levelContentCategorizationEntry 92 }

affirmedServicesContentFilterServiceStatisticsCluster-levelContentCategorizationNumcategorywirelesssports OBJECT-TYPE
    SYNTAX      ConfdString
    MAX-ACCESS  read-only
    STATUS      current
    DESCRIPTION "Total number of requests categorized as Wireless Sports Online Category"
    ::= { affirmedServicesContentFilterServiceStatisticsCluster-levelContentCategorizationEntry 93 }

affirmedServicesContentFilterServiceStatisticsCluster-levelContentCategorizationNumcategorywirelesstravel OBJECT-TYPE
    SYNTAX      ConfdString
    MAX-ACCESS  read-only
    STATUS      current
    DESCRIPTION "Total number of requests categorized as Wireless Travel Online Category"
    ::= { affirmedServicesContentFilterServiceStatisticsCluster-levelContentCategorizationEntry 94 }

affirmedServicesContentFilterServiceStatisticsCluster-levelContentCategorizationNumcategoryunknown OBJECT-TYPE
    SYNTAX      ConfdString
    MAX-ACCESS  read-only
    STATUS      current
    DESCRIPTION "Total number of requests failed categorization"
    ::= { affirmedServicesContentFilterServiceStatisticsCluster-levelContentCategorizationEntry 95 }

affirmedServicesContentFilterServiceStatisticsCluster-levelContentCategorizationNumcategorymalware OBJECT-TYPE
    SYNTAX      ConfdString
    MAX-ACCESS  read-only
    STATUS      current
    DESCRIPTION "Total number of requests categorized as Malware Online Category"
    ::= { affirmedServicesContentFilterServiceStatisticsCluster-levelContentCategorizationEntry 96 }

affirmedServicesContentFilterServiceStatisticsCluster-levelContentCategorizationNumcategoryphishing OBJECT-TYPE
    SYNTAX      ConfdString
    MAX-ACCESS  read-only
    STATUS      current
    DESCRIPTION "Total number of requests categorized as Phishing Online Category"
    ::= { affirmedServicesContentFilterServiceStatisticsCluster-levelContentCategorizationEntry 97 }

affirmedServicesContentFilterServiceStatisticsCluster-levelContentCategorizationNumcategoryiwf OBJECT-TYPE
    SYNTAX      ConfdString
    MAX-ACCESS  read-only
    STATUS      current
    DESCRIPTION "Total number of requests categorized as internet watch foundation CAIC Online Category"
    ::= { affirmedServicesContentFilterServiceStatisticsCluster-levelContentCategorizationEntry 98 }

affirmedServicesContentFilterServiceStatisticsCluster-levelContentCategorizationNumcategorynocat OBJECT-TYPE
    SYNTAX      ConfdString
    MAX-ACCESS  read-only
    STATUS      current
    DESCRIPTION "Total number of requests categorized as none of well-known categories"
    ::= { affirmedServicesContentFilterServiceStatisticsCluster-levelContentCategorizationEntry 99 }

affirmedServicesContentFilterServiceStatisticsCluster-levelContentCategorizationNumcategoryother OBJECT-TYPE
    SYNTAX      ConfdString
    MAX-ACCESS  read-only
    STATUS      current
    DESCRIPTION "Total number of requests categorized as new category not yet supported by AN3K"
    ::= { affirmedServicesContentFilterServiceStatisticsCluster-levelContentCategorizationEntry 100 }

affirmedServicesContentFilterServiceStatisticsCluster-levelContentCategorizationNumcategoryalcoholkids OBJECT-TYPE
    SYNTAX      ConfdString
    MAX-ACCESS  read-only
    STATUS      current
    DESCRIPTION "Total number of requests categorized as Alcohol Kids Online Category"
    ::= { affirmedServicesContentFilterServiceStatisticsCluster-levelContentCategorizationEntry 101 }

affirmedServicesContentFilterServiceStatisticsCluster-levelContentCategorizationNumcategorytobaccokids OBJECT-TYPE
    SYNTAX      ConfdString
    MAX-ACCESS  read-only
    STATUS      current
    DESCRIPTION "Total number of requests categorized as Tobacco Kids Online Category"
    ::= { affirmedServicesContentFilterServiceStatisticsCluster-levelContentCategorizationEntry 102 }

affirmedServicesContentFilterServiceStatisticsCluster-levelContentCategorizationNumcategorycyberbullying OBJECT-TYPE
    SYNTAX      ConfdString
    MAX-ACCESS  read-only
    STATUS      current
    DESCRIPTION "Total number of requests categorized as Cyberbullying Online Category"
    ::= { affirmedServicesContentFilterServiceStatisticsCluster-levelContentCategorizationEntry 103 }

affirmedServicesContentFilterServiceStatisticsCluster-levelContentCategorizationNumhttpsrequestlookups OBJECT-TYPE
    SYNTAX      ConfdString
    MAX-ACCESS  read-only
    STATUS      current
    DESCRIPTION "Total number of HTTPS request Lookups"
    ::= { affirmedServicesContentFilterServiceStatisticsCluster-levelContentCategorizationEntry 104 }

affirmedServicesContentFilterServiceStatisticsCluster-levelContentCategorizationNumlookupfailure OBJECT-TYPE
    SYNTAX      ConfdString
    MAX-ACCESS  read-only
    STATUS      current
    DESCRIPTION "Total number of lookup failures"
    ::= { affirmedServicesContentFilterServiceStatisticsCluster-levelContentCategorizationEntry 105 }

affirmedServicesContentFilterServiceStatisticsCluster-levelContentCategorizationNumquicrequestlookups OBJECT-TYPE
    SYNTAX      ConfdString
    MAX-ACCESS  read-only
    STATUS      current
    DESCRIPTION "Total number of QUIC request Lookups"
    ::= { affirmedServicesContentFilterServiceStatisticsCluster-levelContentCategorizationEntry 106 }

affirmedServicesContentFilterServiceStatisticsCluster-levelContentCategorizationNumcategorybbfcwhitelist OBJECT-TYPE
    SYNTAX      ConfdString
    MAX-ACCESS  read-only
    STATUS      current
    DESCRIPTION "Total number of requests categorized as BBFCWhitelist Online Category"
    ::= { affirmedServicesContentFilterServiceStatisticsCluster-levelContentCategorizationEntry 107 }

affirmedServicesContentFilterServiceStatisticsCluster-levelContentCategorizationNumcategorybbfcblacklist OBJECT-TYPE
    SYNTAX      ConfdString
    MAX-ACCESS  read-only
    STATUS      current
    DESCRIPTION "Total number of requests categorized as BBFCBlacklist Online Category"
    ::= { affirmedServicesContentFilterServiceStatisticsCluster-levelContentCategorizationEntry 108 }

affirmedServicesContentFilterServiceStatisticsCluster-levelContentCategorizationNumcategorycannabidiol OBJECT-TYPE
    SYNTAX      ConfdString
    MAX-ACCESS  read-only
    STATUS      current
    DESCRIPTION "Total number of requests categorized as Cannabidiol Online Category"
    ::= { affirmedServicesContentFilterServiceStatisticsCluster-levelContentCategorizationEntry 109 }

affirmedServicesContentFilterServiceStatisticsCluster-levelContentCategorizationNumcategorycloudinfrastructure OBJECT-TYPE
    SYNTAX      ConfdString
    MAX-ACCESS  read-only
    STATUS      current
    DESCRIPTION "Total number of requests categorized as CloudInfrastructure Online Category"
    ::= { affirmedServicesContentFilterServiceStatisticsCluster-levelContentCategorizationEntry 110 }

affirmedServicesContentFilterServiceStatisticsCluster-levelContentCategorizationNumcategoryfireworks OBJECT-TYPE
    SYNTAX      ConfdString
    MAX-ACCESS  read-only
    STATUS      current
    DESCRIPTION "Total number of requests categorized as Fireworks Online Category"
    ::= { affirmedServicesContentFilterServiceStatisticsCluster-levelContentCategorizationEntry 111 }

affirmedServicesContentFilterServiceStatisticsCluster-levelContentCategorizationNumcategorylingerie OBJECT-TYPE
    SYNTAX      ConfdString
    MAX-ACCESS  read-only
    STATUS      current
    DESCRIPTION "Total number of requests categorized as Lingerie Online Category"
    ::= { affirmedServicesContentFilterServiceStatisticsCluster-levelContentCategorizationEntry 112 }

affirmedServicesContentFilterServiceStatisticsCluster-levelContentCategorizationNumcategorysexualadvice OBJECT-TYPE
    SYNTAX      ConfdString
    MAX-ACCESS  read-only
    STATUS      current
    DESCRIPTION "Total number of requests categorized as SexualAdvice Online Category"
    ::= { affirmedServicesContentFilterServiceStatisticsCluster-levelContentCategorizationEntry 113 }

affirmedServicesContentFilterServiceStatisticsCluster-levelContentCategorizationNumcategorytracking OBJECT-TYPE
    SYNTAX      ConfdString
    MAX-ACCESS  read-only
    STATUS      current
    DESCRIPTION "Total number of requests categorized as Tracking Online Category"
    ::= { affirmedServicesContentFilterServiceStatisticsCluster-levelContentCategorizationEntry 114 }

affirmedServicesContentFilterServiceStatisticsCluster-levelContentCategorizationNumcategoryukdeablacklist OBJECT-TYPE
    SYNTAX      ConfdString
    MAX-ACCESS  read-only
    STATUS      current
    DESCRIPTION "Total number of requests categorized as UKDEABlacklist Online Category"
    ::= { affirmedServicesContentFilterServiceStatisticsCluster-levelContentCategorizationEntry 115 }

affirmedServicesContentFilterServiceStatisticsClusterLevelInstContCatTable OBJECT-TYPE
    SYNTAX      SEQUENCE OF AffirmedServicesContentFilterServiceStatisticsClusterLevelInstContCatEntry
    MAX-ACCESS  not-accessible
    STATUS      current
    DESCRIPTION ""
    ::= { affirmedServicesContentFilterServiceStatisticsCluster-level 4 }

affirmedServicesContentFilterServiceStatisticsClusterLevelInstContCatEntry OBJECT-TYPE
    SYNTAX      AffirmedServicesContentFilterServiceStatisticsClusterLevelInstContCatEntry
    MAX-ACCESS  not-accessible
    STATUS      current
    DESCRIPTION ""
    INDEX { affirmedServicesContentFilterServiceStatisticsClusterLevelInstContCatName, affirmedServicesContentFilterServiceStatisticsClusterLevelInstContCatChassis }
        ::= { affirmedServicesContentFilterServiceStatisticsClusterLevelInstContCatTable 1 }

AffirmedServicesContentFilterServiceStatisticsClusterLevelInstContCatEntry ::=
    SEQUENCE {
        affirmedServicesContentFilterServiceStatisticsClusterLevelInstContCatName String,
        affirmedServicesContentFilterServiceStatisticsClusterLevelInstContCatChassis Unsigned32,
        affirmedServicesContentFilterServiceStatisticsClusterLevelInstContCatNumurlbasedlookups ConfdString,
        affirmedServicesContentFilterServiceStatisticsClusterLevelInstContCatNumresponsebasedlookups ConfdString,
        affirmedServicesContentFilterServiceStatisticsClusterLevelInstContCatNumcategoryabortion ConfdString,
        affirmedServicesContentFilterServiceStatisticsClusterLevelInstContCatNumcategoryadvertising ConfdString,
        affirmedServicesContentFilterServiceStatisticsClusterLevelInstContCatNumcategoryalcohol ConfdString,
        affirmedServicesContentFilterServiceStatisticsClusterLevelInstContCatNumcategoryanonymizer ConfdString,
        affirmedServicesContentFilterServiceStatisticsClusterLevelInstContCatNumcategoryartandmuseums ConfdString,
        affirmedServicesContentFilterServiceStatisticsClusterLevelInstContCatNumcategoryartnudes ConfdString,
        affirmedServicesContentFilterServiceStatisticsClusterLevelInstContCatNumcategoryautomatedwebapplication ConfdString,
        affirmedServicesContentFilterServiceStatisticsClusterLevelInstContCatNumcategoryautomotive ConfdString,
        affirmedServicesContentFilterServiceStatisticsClusterLevelInstContCatNumcategorybikini ConfdString,
        affirmedServicesContentFilterServiceStatisticsClusterLevelInstContCatNumcategoryblogging ConfdString,
        affirmedServicesContentFilterServiceStatisticsClusterLevelInstContCatNumcategorybusiness ConfdString,
        affirmedServicesContentFilterServiceStatisticsClusterLevelInstContCatNumcategorycashgambling ConfdString,
        affirmedServicesContentFilterServiceStatisticsClusterLevelInstContCatNumcategorychat ConfdString,
        affirmedServicesContentFilterServiceStatisticsClusterLevelInstContCatNumcategorycontentdeliverynetwork ConfdString,
        affirmedServicesContentFilterServiceStatisticsClusterLevelInstContCatNumcategorycriminalskills ConfdString,
        affirmedServicesContentFilterServiceStatisticsClusterLevelInstContCatNumcategorycults ConfdString,
        affirmedServicesContentFilterServiceStatisticsClusterLevelInstContCatNumcategorydrugs ConfdString,
        affirmedServicesContentFilterServiceStatisticsClusterLevelInstContCatNumcategorydynamic ConfdString,
        affirmedServicesContentFilterServiceStatisticsClusterLevelInstContCatNumcategoryeducational ConfdString,
        affirmedServicesContentFilterServiceStatisticsClusterLevelInstContCatNumcategoryenergy ConfdString,
        affirmedServicesContentFilterServiceStatisticsClusterLevelInstContCatNumcategoryenterprisewebmail ConfdString,
        affirmedServicesContentFilterServiceStatisticsClusterLevelInstContCatNumcategoryentertainment ConfdString,
        affirmedServicesContentFilterServiceStatisticsClusterLevelInstContCatNumcategoryfilesharing ConfdString,
        affirmedServicesContentFilterServiceStatisticsClusterLevelInstContCatNumcategoryfinanceandinvesting ConfdString,
        affirmedServicesContentFilterServiceStatisticsClusterLevelInstContCatNumcategoryfoodandrestaurants ConfdString,
        affirmedServicesContentFilterServiceStatisticsClusterLevelInstContCatNumcategoryforumsandmessageboards ConfdString,
        affirmedServicesContentFilterServiceStatisticsClusterLevelInstContCatNumcategoryfreewareandshareware ConfdString,
        affirmedServicesContentFilterServiceStatisticsClusterLevelInstContCatNumcategorygambling ConfdString,
        affirmedServicesContentFilterServiceStatisticsClusterLevelInstContCatNumcategorygaming ConfdString,
        affirmedServicesContentFilterServiceStatisticsClusterLevelInstContCatNumcategoryglamour ConfdString,
        affirmedServicesContentFilterServiceStatisticsClusterLevelInstContCatNumcategorygore ConfdString,
        affirmedServicesContentFilterServiceStatisticsClusterLevelInstContCatNumcategorygovernment ConfdString,
        affirmedServicesContentFilterServiceStatisticsClusterLevelInstContCatNumcategoryhacking ConfdString,
        affirmedServicesContentFilterServiceStatisticsClusterLevelInstContCatNumcategoryhate ConfdString,
        affirmedServicesContentFilterServiceStatisticsClusterLevelInstContCatNumcategoryhealth ConfdString,
        affirmedServicesContentFilterServiceStatisticsClusterLevelInstContCatNumcategoryhobby ConfdString,
        affirmedServicesContentFilterServiceStatisticsClusterLevelInstContCatNumcategoryhosting ConfdString,
        affirmedServicesContentFilterServiceStatisticsClusterLevelInstContCatNumcategoryinternettelephony ConfdString,
        affirmedServicesContentFilterServiceStatisticsClusterLevelInstContCatNumcategoryjobsearch ConfdString,
        affirmedServicesContentFilterServiceStatisticsClusterLevelInstContCatNumcategorykids ConfdString,
        affirmedServicesContentFilterServiceStatisticsClusterLevelInstContCatNumcategorylaw ConfdString,
        affirmedServicesContentFilterServiceStatisticsClusterLevelInstContCatNumcategorylifestyles ConfdString,
        affirmedServicesContentFilterServiceStatisticsClusterLevelInstContCatNumcategorymaturecontent ConfdString,
        affirmedServicesContentFilterServiceStatisticsClusterLevelInstContCatNumcategorymilitary ConfdString,
        affirmedServicesContentFilterServiceStatisticsClusterLevelInstContCatNumcategorymobileentertainment ConfdString,
        affirmedServicesContentFilterServiceStatisticsClusterLevelInstContCatNumcategorymusic ConfdString,
        affirmedServicesContentFilterServiceStatisticsClusterLevelInstContCatNumcategorynews ConfdString,
        affirmedServicesContentFilterServiceStatisticsClusterLevelInstContCatNumcategorynonprofit ConfdString,
        affirmedServicesContentFilterServiceStatisticsClusterLevelInstContCatNumcategoryobscene ConfdString,
        affirmedServicesContentFilterServiceStatisticsClusterLevelInstContCatNumcategoryoccult ConfdString,
        affirmedServicesContentFilterServiceStatisticsClusterLevelInstContCatNumcategoryonlinebackupandstorage ConfdString,
        affirmedServicesContentFilterServiceStatisticsClusterLevelInstContCatNumcategorypeertopeer ConfdString,
        affirmedServicesContentFilterServiceStatisticsClusterLevelInstContCatNumcategorypets ConfdString,
        affirmedServicesContentFilterServiceStatisticsClusterLevelInstContCatNumcategoryphotography ConfdString,
        affirmedServicesContentFilterServiceStatisticsClusterLevelInstContCatNumcategoryplaceholder ConfdString,
        affirmedServicesContentFilterServiceStatisticsClusterLevelInstContCatNumcategoryplagiarism ConfdString,
        affirmedServicesContentFilterServiceStatisticsClusterLevelInstContCatNumcategorypolitics ConfdString,
        affirmedServicesContentFilterServiceStatisticsClusterLevelInstContCatNumcategorypornography ConfdString,
        affirmedServicesContentFilterServiceStatisticsClusterLevelInstContCatNumcategoryportal ConfdString,
        affirmedServicesContentFilterServiceStatisticsClusterLevelInstContCatNumcategorypersonalsanddating ConfdString,
        affirmedServicesContentFilterServiceStatisticsClusterLevelInstContCatNumcategoryrealestate ConfdString,
        affirmedServicesContentFilterServiceStatisticsClusterLevelInstContCatNumcategoryreference ConfdString,
        affirmedServicesContentFilterServiceStatisticsClusterLevelInstContCatNumcategoryreligion ConfdString,
        affirmedServicesContentFilterServiceStatisticsClusterLevelInstContCatNumcategoryremoteaccess ConfdString,
        affirmedServicesContentFilterServiceStatisticsClusterLevelInstContCatNumcategoryscience ConfdString,
        affirmedServicesContentFilterServiceStatisticsClusterLevelInstContCatNumcategorysearch ConfdString,
        affirmedServicesContentFilterServiceStatisticsClusterLevelInstContCatNumcategoryselfharm ConfdString,
        affirmedServicesContentFilterServiceStatisticsClusterLevelInstContCatNumcategorysexualeducation ConfdString,
        affirmedServicesContentFilterServiceStatisticsClusterLevelInstContCatNumcategoryshopping ConfdString,
        affirmedServicesContentFilterServiceStatisticsClusterLevelInstContCatNumcategorysports ConfdString,
        affirmedServicesContentFilterServiceStatisticsClusterLevelInstContCatNumcategorystreamingmedia ConfdString,
        affirmedServicesContentFilterServiceStatisticsClusterLevelInstContCatNumcategorysuicide ConfdString,
        affirmedServicesContentFilterServiceStatisticsClusterLevelInstContCatNumcategorytechnologyandtelecommunication ConfdString,
        affirmedServicesContentFilterServiceStatisticsClusterLevelInstContCatNumcategorytobacco ConfdString,
        affirmedServicesContentFilterServiceStatisticsClusterLevelInstContCatNumcategorytravel ConfdString,
        affirmedServicesContentFilterServiceStatisticsClusterLevelInstContCatNumcategoryviolence ConfdString,
        affirmedServicesContentFilterServiceStatisticsClusterLevelInstContCatNumcategoryvirtualcommunity ConfdString,
        affirmedServicesContentFilterServiceStatisticsClusterLevelInstContCatNumcategoryweapons ConfdString,
        affirmedServicesContentFilterServiceStatisticsClusterLevelInstContCatNumcategorywebmail ConfdString,
        affirmedServicesContentFilterServiceStatisticsClusterLevelInstContCatNumcategorywedding ConfdString,
        affirmedServicesContentFilterServiceStatisticsClusterLevelInstContCatNumcategorywirelessbusiness ConfdString,
        affirmedServicesContentFilterServiceStatisticsClusterLevelInstContCatNumcategorywirelesschatsms ConfdString,
        affirmedServicesContentFilterServiceStatisticsClusterLevelInstContCatNumcategorywirelessdynamic ConfdString,
        affirmedServicesContentFilterServiceStatisticsClusterLevelInstContCatNumcategorywirelessentertainment ConfdString,
        affirmedServicesContentFilterServiceStatisticsClusterLevelInstContCatNumcategorywirelessfinance ConfdString,
        affirmedServicesContentFilterServiceStatisticsClusterLevelInstContCatNumcategorywirelessgambling ConfdString,
        affirmedServicesContentFilterServiceStatisticsClusterLevelInstContCatNumcategorywirelessnews ConfdString,
        affirmedServicesContentFilterServiceStatisticsClusterLevelInstContCatNumcategorywirelesspersonalsanddating ConfdString,
        affirmedServicesContentFilterServiceStatisticsClusterLevelInstContCatNumcategorywirelesspornography ConfdString,
        affirmedServicesContentFilterServiceStatisticsClusterLevelInstContCatNumcategorywirelesssports ConfdString,
        affirmedServicesContentFilterServiceStatisticsClusterLevelInstContCatNumcategorywirelesstravel ConfdString,
        affirmedServicesContentFilterServiceStatisticsClusterLevelInstContCatNumcategoryunknown ConfdString,
        affirmedServicesContentFilterServiceStatisticsClusterLevelInstContCatNumcategorymalware ConfdString,
        affirmedServicesContentFilterServiceStatisticsClusterLevelInstContCatNumcategoryphishing ConfdString,
        affirmedServicesContentFilterServiceStatisticsClusterLevelInstContCatNumcategoryiwf ConfdString,
        affirmedServicesContentFilterServiceStatisticsClusterLevelInstContCatNumcategorynocat ConfdString,
        affirmedServicesContentFilterServiceStatisticsClusterLevelInstContCatNumcategoryother ConfdString,
        affirmedServicesContentFilterServiceStatisticsClusterLevelInstContCatNumcategoryalcoholkids ConfdString,
        affirmedServicesContentFilterServiceStatisticsClusterLevelInstContCatNumcategorytobaccokids ConfdString,
        affirmedServicesContentFilterServiceStatisticsClusterLevelInstContCatNumcategorycyberbullying ConfdString,
        affirmedServicesContentFilterServiceStatisticsClusterLevelInstContCatNumhttpsrequestlookups ConfdString,
        affirmedServicesContentFilterServiceStatisticsClusterLevelInstContCatNumlookupfailure ConfdString,
        affirmedServicesContentFilterServiceStatisticsClusterLevelInstContCatNumquicrequestlookups ConfdString,
        affirmedServicesContentFilterServiceStatisticsClusterLevelInstContCatNumcategorybbfcwhitelist ConfdString,
        affirmedServicesContentFilterServiceStatisticsClusterLevelInstContCatNumcategorybbfcblacklist ConfdString,
        affirmedServicesContentFilterServiceStatisticsClusterLevelInstContCatNumcategorycannabidiol ConfdString,
        affirmedServicesContentFilterServiceStatisticsClusterLevelInstContCatNumcategorycloudinfrastructure ConfdString,
        affirmedServicesContentFilterServiceStatisticsClusterLevelInstContCatNumcategoryfireworks ConfdString,
        affirmedServicesContentFilterServiceStatisticsClusterLevelInstContCatNumcategorylingerie ConfdString,
        affirmedServicesContentFilterServiceStatisticsClusterLevelInstContCatNumcategorysexualadvice ConfdString,
        affirmedServicesContentFilterServiceStatisticsClusterLevelInstContCatNumcategorytracking ConfdString,
        affirmedServicesContentFilterServiceStatisticsClusterLevelInstContCatNumcategoryukdeablacklist ConfdString
    }

affirmedServicesContentFilterServiceStatisticsClusterLevelInstContCatName OBJECT-TYPE
    SYNTAX      String
    MAX-ACCESS  not-accessible
    STATUS      current
    DESCRIPTION "Name of content filter service instance"
    ::= { affirmedServicesContentFilterServiceStatisticsClusterLevelInstContCatEntry 1 }

affirmedServicesContentFilterServiceStatisticsClusterLevelInstContCatChassis OBJECT-TYPE
    SYNTAX      Unsigned32
    MAX-ACCESS  not-accessible
    STATUS      current
    DESCRIPTION "chassis ID"
    ::= { affirmedServicesContentFilterServiceStatisticsClusterLevelInstContCatEntry 2 }

affirmedServicesContentFilterServiceStatisticsClusterLevelInstContCatNumurlbasedlookups OBJECT-TYPE
    SYNTAX      ConfdString
    MAX-ACCESS  read-only
    STATUS      current
    DESCRIPTION "Total number of HTTP request Lookups"
    ::= { affirmedServicesContentFilterServiceStatisticsClusterLevelInstContCatEntry 3 }

affirmedServicesContentFilterServiceStatisticsClusterLevelInstContCatNumresponsebasedlookups OBJECT-TYPE
    SYNTAX      ConfdString
    MAX-ACCESS  read-only
    STATUS      current
    DESCRIPTION "Total number of HTTP Response-based Lookups"
    ::= { affirmedServicesContentFilterServiceStatisticsClusterLevelInstContCatEntry 4 }

affirmedServicesContentFilterServiceStatisticsClusterLevelInstContCatNumcategoryabortion OBJECT-TYPE
    SYNTAX      ConfdString
    MAX-ACCESS  read-only
    STATUS      current
    DESCRIPTION "Total number of requests categorized as Abortion Online Category"
    ::= { affirmedServicesContentFilterServiceStatisticsClusterLevelInstContCatEntry 5 }

affirmedServicesContentFilterServiceStatisticsClusterLevelInstContCatNumcategoryadvertising OBJECT-TYPE
    SYNTAX      ConfdString
    MAX-ACCESS  read-only
    STATUS      current
    DESCRIPTION "Total number of requests categorized as Advertising Online Category"
    ::= { affirmedServicesContentFilterServiceStatisticsClusterLevelInstContCatEntry 6 }

affirmedServicesContentFilterServiceStatisticsClusterLevelInstContCatNumcategoryalcohol OBJECT-TYPE
    SYNTAX      ConfdString
    MAX-ACCESS  read-only
    STATUS      current
    DESCRIPTION "Total number of requests categorized as Alcohol Online Category"
    ::= { affirmedServicesContentFilterServiceStatisticsClusterLevelInstContCatEntry 7 }

affirmedServicesContentFilterServiceStatisticsClusterLevelInstContCatNumcategoryanonymizer OBJECT-TYPE
    SYNTAX      ConfdString
    MAX-ACCESS  read-only
    STATUS      current
    DESCRIPTION "Total number of requests categorized as Anonymizer Online Category"
    ::= { affirmedServicesContentFilterServiceStatisticsClusterLevelInstContCatEntry 8 }

affirmedServicesContentFilterServiceStatisticsClusterLevelInstContCatNumcategoryartandmuseums OBJECT-TYPE
    SYNTAX      ConfdString
    MAX-ACCESS  read-only
    STATUS      current
    DESCRIPTION "Total number of requests categorized as Art And Museums Online Category"
    ::= { affirmedServicesContentFilterServiceStatisticsClusterLevelInstContCatEntry 9 }

affirmedServicesContentFilterServiceStatisticsClusterLevelInstContCatNumcategoryartnudes OBJECT-TYPE
    SYNTAX      ConfdString
    MAX-ACCESS  read-only
    STATUS      current
    DESCRIPTION "Total number of requests categorized as Art Nudes Online Category"
    ::= { affirmedServicesContentFilterServiceStatisticsClusterLevelInstContCatEntry 10 }

affirmedServicesContentFilterServiceStatisticsClusterLevelInstContCatNumcategoryautomatedwebapplication OBJECT-TYPE
    SYNTAX      ConfdString
    MAX-ACCESS  read-only
    STATUS      current
    DESCRIPTION "Total number of requests categorized as Automated Web Application Online Category"
    ::= { affirmedServicesContentFilterServiceStatisticsClusterLevelInstContCatEntry 11 }

affirmedServicesContentFilterServiceStatisticsClusterLevelInstContCatNumcategoryautomotive OBJECT-TYPE
    SYNTAX      ConfdString
    MAX-ACCESS  read-only
    STATUS      current
    DESCRIPTION "Total number of requests categorized as Automotive Online Category"
    ::= { affirmedServicesContentFilterServiceStatisticsClusterLevelInstContCatEntry 12 }

affirmedServicesContentFilterServiceStatisticsClusterLevelInstContCatNumcategorybikini OBJECT-TYPE
    SYNTAX      ConfdString
    MAX-ACCESS  read-only
    STATUS      current
    DESCRIPTION "Total number of requests categorized as Bikini Online Category"
    ::= { affirmedServicesContentFilterServiceStatisticsClusterLevelInstContCatEntry 13 }

affirmedServicesContentFilterServiceStatisticsClusterLevelInstContCatNumcategoryblogging OBJECT-TYPE
    SYNTAX      ConfdString
    MAX-ACCESS  read-only
    STATUS      current
    DESCRIPTION "Total number of requests categorized as Blogging Online Category"
    ::= { affirmedServicesContentFilterServiceStatisticsClusterLevelInstContCatEntry 14 }

affirmedServicesContentFilterServiceStatisticsClusterLevelInstContCatNumcategorybusiness OBJECT-TYPE
    SYNTAX      ConfdString
    MAX-ACCESS  read-only
    STATUS      current
    DESCRIPTION "Total number of requests categorized as Business Online Category"
    ::= { affirmedServicesContentFilterServiceStatisticsClusterLevelInstContCatEntry 15 }

affirmedServicesContentFilterServiceStatisticsClusterLevelInstContCatNumcategorycashgambling OBJECT-TYPE
    SYNTAX      ConfdString
    MAX-ACCESS  read-only
    STATUS      current
    DESCRIPTION "Total number of requests categorized as Cash Gambling Online Category"
    ::= { affirmedServicesContentFilterServiceStatisticsClusterLevelInstContCatEntry 16 }

affirmedServicesContentFilterServiceStatisticsClusterLevelInstContCatNumcategorychat OBJECT-TYPE
    SYNTAX      ConfdString
    MAX-ACCESS  read-only
    STATUS      current
    DESCRIPTION "Total number of requests categorized as Chat Online Category"
    ::= { affirmedServicesContentFilterServiceStatisticsClusterLevelInstContCatEntry 17 }

affirmedServicesContentFilterServiceStatisticsClusterLevelInstContCatNumcategorycontentdeliverynetwork OBJECT-TYPE
    SYNTAX      ConfdString
    MAX-ACCESS  read-only
    STATUS      current
    DESCRIPTION "Total number of requests categorized as Content Delivery Network Online Category"
    ::= { affirmedServicesContentFilterServiceStatisticsClusterLevelInstContCatEntry 18 }

affirmedServicesContentFilterServiceStatisticsClusterLevelInstContCatNumcategorycriminalskills OBJECT-TYPE
    SYNTAX      ConfdString
    MAX-ACCESS  read-only
    STATUS      current
    DESCRIPTION "Total number of requests categorized as Criminal Skills Online Category"
    ::= { affirmedServicesContentFilterServiceStatisticsClusterLevelInstContCatEntry 19 }

affirmedServicesContentFilterServiceStatisticsClusterLevelInstContCatNumcategorycults OBJECT-TYPE
    SYNTAX      ConfdString
    MAX-ACCESS  read-only
    STATUS      current
    DESCRIPTION "Total number of requests categorized as Cults Online Category"
    ::= { affirmedServicesContentFilterServiceStatisticsClusterLevelInstContCatEntry 20 }

affirmedServicesContentFilterServiceStatisticsClusterLevelInstContCatNumcategorydrugs OBJECT-TYPE
    SYNTAX      ConfdString
    MAX-ACCESS  read-only
    STATUS      current
    DESCRIPTION "Total number of requests categorized as Drugs Online Category"
    ::= { affirmedServicesContentFilterServiceStatisticsClusterLevelInstContCatEntry 21 }

affirmedServicesContentFilterServiceStatisticsClusterLevelInstContCatNumcategorydynamic OBJECT-TYPE
    SYNTAX      ConfdString
    MAX-ACCESS  read-only
    STATUS      current
    DESCRIPTION "Total number of requests categorized as Dynamic Online Category"
    ::= { affirmedServicesContentFilterServiceStatisticsClusterLevelInstContCatEntry 22 }

affirmedServicesContentFilterServiceStatisticsClusterLevelInstContCatNumcategoryeducational OBJECT-TYPE
    SYNTAX      ConfdString
    MAX-ACCESS  read-only
    STATUS      current
    DESCRIPTION "Total number of requests categorized as Educational Online Category"
    ::= { affirmedServicesContentFilterServiceStatisticsClusterLevelInstContCatEntry 23 }

affirmedServicesContentFilterServiceStatisticsClusterLevelInstContCatNumcategoryenergy OBJECT-TYPE
    SYNTAX      ConfdString
    MAX-ACCESS  read-only
    STATUS      current
    DESCRIPTION "Total number of requests categorized as Energy Online Category"
    ::= { affirmedServicesContentFilterServiceStatisticsClusterLevelInstContCatEntry 24 }

affirmedServicesContentFilterServiceStatisticsClusterLevelInstContCatNumcategoryenterprisewebmail OBJECT-TYPE
    SYNTAX      ConfdString
    MAX-ACCESS  read-only
    STATUS      current
    DESCRIPTION "Total number of requests categorized as Enterprise Webmail Online Category"
    ::= { affirmedServicesContentFilterServiceStatisticsClusterLevelInstContCatEntry 25 }

affirmedServicesContentFilterServiceStatisticsClusterLevelInstContCatNumcategoryentertainment OBJECT-TYPE
    SYNTAX      ConfdString
    MAX-ACCESS  read-only
    STATUS      current
    DESCRIPTION "Total number of requests categorized as Entertainment Online Category"
    ::= { affirmedServicesContentFilterServiceStatisticsClusterLevelInstContCatEntry 26 }

affirmedServicesContentFilterServiceStatisticsClusterLevelInstContCatNumcategoryfilesharing OBJECT-TYPE
    SYNTAX      ConfdString
    MAX-ACCESS  read-only
    STATUS      current
    DESCRIPTION "Total number of requests categorized as Filesharing Online Category"
    ::= { affirmedServicesContentFilterServiceStatisticsClusterLevelInstContCatEntry 27 }

affirmedServicesContentFilterServiceStatisticsClusterLevelInstContCatNumcategoryfinanceandinvesting OBJECT-TYPE
    SYNTAX      ConfdString
    MAX-ACCESS  read-only
    STATUS      current
    DESCRIPTION "Total number of requests categorized as Finance And Investing Online Category"
    ::= { affirmedServicesContentFilterServiceStatisticsClusterLevelInstContCatEntry 28 }

affirmedServicesContentFilterServiceStatisticsClusterLevelInstContCatNumcategoryfoodandrestaurants OBJECT-TYPE
    SYNTAX      ConfdString
    MAX-ACCESS  read-only
    STATUS      current
    DESCRIPTION "Total number of requests categorized as Food And Restaurants Online Category"
    ::= { affirmedServicesContentFilterServiceStatisticsClusterLevelInstContCatEntry 29 }

affirmedServicesContentFilterServiceStatisticsClusterLevelInstContCatNumcategoryforumsandmessageboards OBJECT-TYPE
    SYNTAX      ConfdString
    MAX-ACCESS  read-only
    STATUS      current
    DESCRIPTION "Total number of requests categorized as Forums And Messageboards Online Category"
    ::= { affirmedServicesContentFilterServiceStatisticsClusterLevelInstContCatEntry 30 }

affirmedServicesContentFilterServiceStatisticsClusterLevelInstContCatNumcategoryfreewareandshareware OBJECT-TYPE
    SYNTAX      ConfdString
    MAX-ACCESS  read-only
    STATUS      current
    DESCRIPTION "Total number of requests categorized as Freeware And Shareware Online Category"
    ::= { affirmedServicesContentFilterServiceStatisticsClusterLevelInstContCatEntry 31 }

affirmedServicesContentFilterServiceStatisticsClusterLevelInstContCatNumcategorygambling OBJECT-TYPE
    SYNTAX      ConfdString
    MAX-ACCESS  read-only
    STATUS      current
    DESCRIPTION "Total number of requests categorized as Gambling Online Category"
    ::= { affirmedServicesContentFilterServiceStatisticsClusterLevelInstContCatEntry 32 }

affirmedServicesContentFilterServiceStatisticsClusterLevelInstContCatNumcategorygaming OBJECT-TYPE
    SYNTAX      ConfdString
    MAX-ACCESS  read-only
    STATUS      current
    DESCRIPTION "Total number of requests categorized as Gaming Online Category"
    ::= { affirmedServicesContentFilterServiceStatisticsClusterLevelInstContCatEntry 33 }

affirmedServicesContentFilterServiceStatisticsClusterLevelInstContCatNumcategoryglamour OBJECT-TYPE
    SYNTAX      ConfdString
    MAX-ACCESS  read-only
    STATUS      current
    DESCRIPTION "Total number of requests categorized as Glamour Online Category"
    ::= { affirmedServicesContentFilterServiceStatisticsClusterLevelInstContCatEntry 34 }

affirmedServicesContentFilterServiceStatisticsClusterLevelInstContCatNumcategorygore OBJECT-TYPE
    SYNTAX      ConfdString
    MAX-ACCESS  read-only
    STATUS      current
    DESCRIPTION "Total number of requests categorized as Gore Online Category"
    ::= { affirmedServicesContentFilterServiceStatisticsClusterLevelInstContCatEntry 35 }

affirmedServicesContentFilterServiceStatisticsClusterLevelInstContCatNumcategorygovernment OBJECT-TYPE
    SYNTAX      ConfdString
    MAX-ACCESS  read-only
    STATUS      current
    DESCRIPTION "Total number of requests categorized as Government Online Category"
    ::= { affirmedServicesContentFilterServiceStatisticsClusterLevelInstContCatEntry 36 }

affirmedServicesContentFilterServiceStatisticsClusterLevelInstContCatNumcategoryhacking OBJECT-TYPE
    SYNTAX      ConfdString
    MAX-ACCESS  read-only
    STATUS      current
    DESCRIPTION "Total number of requests categorized as Hacking Online Category"
    ::= { affirmedServicesContentFilterServiceStatisticsClusterLevelInstContCatEntry 37 }

affirmedServicesContentFilterServiceStatisticsClusterLevelInstContCatNumcategoryhate OBJECT-TYPE
    SYNTAX      ConfdString
    MAX-ACCESS  read-only
    STATUS      current
    DESCRIPTION "Total number of requests categorized as Hate Online Category"
    ::= { affirmedServicesContentFilterServiceStatisticsClusterLevelInstContCatEntry 38 }

affirmedServicesContentFilterServiceStatisticsClusterLevelInstContCatNumcategoryhealth OBJECT-TYPE
    SYNTAX      ConfdString
    MAX-ACCESS  read-only
    STATUS      current
    DESCRIPTION "Total number of requests categorized as Health Online Category"
    ::= { affirmedServicesContentFilterServiceStatisticsClusterLevelInstContCatEntry 39 }

affirmedServicesContentFilterServiceStatisticsClusterLevelInstContCatNumcategoryhobby OBJECT-TYPE
    SYNTAX      ConfdString
    MAX-ACCESS  read-only
    STATUS      current
    DESCRIPTION "Total number of requests categorized as Hobby Online Category"
    ::= { affirmedServicesContentFilterServiceStatisticsClusterLevelInstContCatEntry 40 }

affirmedServicesContentFilterServiceStatisticsClusterLevelInstContCatNumcategoryhosting OBJECT-TYPE
    SYNTAX      ConfdString
    MAX-ACCESS  read-only
    STATUS      current
    DESCRIPTION "Total number of requests categorized as Hosting Online Category"
    ::= { affirmedServicesContentFilterServiceStatisticsClusterLevelInstContCatEntry 41 }

affirmedServicesContentFilterServiceStatisticsClusterLevelInstContCatNumcategoryinternettelephony OBJECT-TYPE
    SYNTAX      ConfdString
    MAX-ACCESS  read-only
    STATUS      current
    DESCRIPTION "Total number of requests categorized as Internet Telephony Online Category"
    ::= { affirmedServicesContentFilterServiceStatisticsClusterLevelInstContCatEntry 42 }

affirmedServicesContentFilterServiceStatisticsClusterLevelInstContCatNumcategoryjobsearch OBJECT-TYPE
    SYNTAX      ConfdString
    MAX-ACCESS  read-only
    STATUS      current
    DESCRIPTION "Total number of requests categorized as Job Search Online Category"
    ::= { affirmedServicesContentFilterServiceStatisticsClusterLevelInstContCatEntry 43 }

affirmedServicesContentFilterServiceStatisticsClusterLevelInstContCatNumcategorykids OBJECT-TYPE
    SYNTAX      ConfdString
    MAX-ACCESS  read-only
    STATUS      current
    DESCRIPTION "Total number of requests categorized as Kids Online Category"
    ::= { affirmedServicesContentFilterServiceStatisticsClusterLevelInstContCatEntry 44 }

affirmedServicesContentFilterServiceStatisticsClusterLevelInstContCatNumcategorylaw OBJECT-TYPE
    SYNTAX      ConfdString
    MAX-ACCESS  read-only
    STATUS      current
    DESCRIPTION "Total number of requests categorized as Law Online Category"
    ::= { affirmedServicesContentFilterServiceStatisticsClusterLevelInstContCatEntry 45 }

affirmedServicesContentFilterServiceStatisticsClusterLevelInstContCatNumcategorylifestyles OBJECT-TYPE
    SYNTAX      ConfdString
    MAX-ACCESS  read-only
    STATUS      current
    DESCRIPTION "Total number of requests categorized as Lifestyles Online Category"
    ::= { affirmedServicesContentFilterServiceStatisticsClusterLevelInstContCatEntry 46 }

affirmedServicesContentFilterServiceStatisticsClusterLevelInstContCatNumcategorymaturecontent OBJECT-TYPE
    SYNTAX      ConfdString
    MAX-ACCESS  read-only
    STATUS      current
    DESCRIPTION "Total number of requests categorized as Mature Content Online Category"
    ::= { affirmedServicesContentFilterServiceStatisticsClusterLevelInstContCatEntry 47 }

affirmedServicesContentFilterServiceStatisticsClusterLevelInstContCatNumcategorymilitary OBJECT-TYPE
    SYNTAX      ConfdString
    MAX-ACCESS  read-only
    STATUS      current
    DESCRIPTION "Total number of requests categorized as Military Online Category"
    ::= { affirmedServicesContentFilterServiceStatisticsClusterLevelInstContCatEntry 48 }

affirmedServicesContentFilterServiceStatisticsClusterLevelInstContCatNumcategorymobileentertainment OBJECT-TYPE
    SYNTAX      ConfdString
    MAX-ACCESS  read-only
    STATUS      current
    DESCRIPTION "Total number of requests categorized as Mobile Entertainment Online Category"
    ::= { affirmedServicesContentFilterServiceStatisticsClusterLevelInstContCatEntry 49 }

affirmedServicesContentFilterServiceStatisticsClusterLevelInstContCatNumcategorymusic OBJECT-TYPE
    SYNTAX      ConfdString
    MAX-ACCESS  read-only
    STATUS      current
    DESCRIPTION "Total number of requests categorized as Music Online Category"
    ::= { affirmedServicesContentFilterServiceStatisticsClusterLevelInstContCatEntry 50 }

affirmedServicesContentFilterServiceStatisticsClusterLevelInstContCatNumcategorynews OBJECT-TYPE
    SYNTAX      ConfdString
    MAX-ACCESS  read-only
    STATUS      current
    DESCRIPTION "Total number of requests categorized as News Online Category"
    ::= { affirmedServicesContentFilterServiceStatisticsClusterLevelInstContCatEntry 51 }

affirmedServicesContentFilterServiceStatisticsClusterLevelInstContCatNumcategorynonprofit OBJECT-TYPE
    SYNTAX      ConfdString
    MAX-ACCESS  read-only
    STATUS      current
    DESCRIPTION "Total number of requests categorized as Non Profit Online Category"
    ::= { affirmedServicesContentFilterServiceStatisticsClusterLevelInstContCatEntry 52 }

affirmedServicesContentFilterServiceStatisticsClusterLevelInstContCatNumcategoryobscene OBJECT-TYPE
    SYNTAX      ConfdString
    MAX-ACCESS  read-only
    STATUS      current
    DESCRIPTION "Total number of requests categorized as Obscene Online Category"
    ::= { affirmedServicesContentFilterServiceStatisticsClusterLevelInstContCatEntry 53 }

affirmedServicesContentFilterServiceStatisticsClusterLevelInstContCatNumcategoryoccult OBJECT-TYPE
    SYNTAX      ConfdString
    MAX-ACCESS  read-only
    STATUS      current
    DESCRIPTION "Total number of requests categorized as Occult Online Category"
    ::= { affirmedServicesContentFilterServiceStatisticsClusterLevelInstContCatEntry 54 }

affirmedServicesContentFilterServiceStatisticsClusterLevelInstContCatNumcategoryonlinebackupandstorage OBJECT-TYPE
    SYNTAX      ConfdString
    MAX-ACCESS  read-only
    STATUS      current
    DESCRIPTION "Total number of requests categorized as Online Backup And Storage Online Category"
    ::= { affirmedServicesContentFilterServiceStatisticsClusterLevelInstContCatEntry 55 }

affirmedServicesContentFilterServiceStatisticsClusterLevelInstContCatNumcategorypeertopeer OBJECT-TYPE
    SYNTAX      ConfdString
    MAX-ACCESS  read-only
    STATUS      current
    DESCRIPTION "Total number of requests categorized as PeerToPeer Online Category"
    ::= { affirmedServicesContentFilterServiceStatisticsClusterLevelInstContCatEntry 56 }

affirmedServicesContentFilterServiceStatisticsClusterLevelInstContCatNumcategorypets OBJECT-TYPE
    SYNTAX      ConfdString
    MAX-ACCESS  read-only
    STATUS      current
    DESCRIPTION "Total number of requests categorized as Pets Online Category"
    ::= { affirmedServicesContentFilterServiceStatisticsClusterLevelInstContCatEntry 57 }

affirmedServicesContentFilterServiceStatisticsClusterLevelInstContCatNumcategoryphotography OBJECT-TYPE
    SYNTAX      ConfdString
    MAX-ACCESS  read-only
    STATUS      current
    DESCRIPTION "Total number of requests categorized as Photography Online Category"
    ::= { affirmedServicesContentFilterServiceStatisticsClusterLevelInstContCatEntry 58 }

affirmedServicesContentFilterServiceStatisticsClusterLevelInstContCatNumcategoryplaceholder OBJECT-TYPE
    SYNTAX      ConfdString
    MAX-ACCESS  read-only
    STATUS      current
    DESCRIPTION "Total number of requests categorized as Placeholder Online Category"
    ::= { affirmedServicesContentFilterServiceStatisticsClusterLevelInstContCatEntry 59 }

affirmedServicesContentFilterServiceStatisticsClusterLevelInstContCatNumcategoryplagiarism OBJECT-TYPE
    SYNTAX      ConfdString
    MAX-ACCESS  read-only
    STATUS      current
    DESCRIPTION "Total number of requests categorized as Plagiarism Online Category"
    ::= { affirmedServicesContentFilterServiceStatisticsClusterLevelInstContCatEntry 60 }

affirmedServicesContentFilterServiceStatisticsClusterLevelInstContCatNumcategorypolitics OBJECT-TYPE
    SYNTAX      ConfdString
    MAX-ACCESS  read-only
    STATUS      current
    DESCRIPTION "Total number of requests categorized as Politics Online Category"
    ::= { affirmedServicesContentFilterServiceStatisticsClusterLevelInstContCatEntry 61 }

affirmedServicesContentFilterServiceStatisticsClusterLevelInstContCatNumcategorypornography OBJECT-TYPE
    SYNTAX      ConfdString
    MAX-ACCESS  read-only
    STATUS      current
    DESCRIPTION "Total number of requests categorized as Pornography Online Category"
    ::= { affirmedServicesContentFilterServiceStatisticsClusterLevelInstContCatEntry 62 }

affirmedServicesContentFilterServiceStatisticsClusterLevelInstContCatNumcategoryportal OBJECT-TYPE
    SYNTAX      ConfdString
    MAX-ACCESS  read-only
    STATUS      current
    DESCRIPTION "Total number of requests categorized as Portal Online Category"
    ::= { affirmedServicesContentFilterServiceStatisticsClusterLevelInstContCatEntry 63 }

affirmedServicesContentFilterServiceStatisticsClusterLevelInstContCatNumcategorypersonalsanddating OBJECT-TYPE
    SYNTAX      ConfdString
    MAX-ACCESS  read-only
    STATUS      current
    DESCRIPTION "Total number of requests categorized as Personals And Dating Online Category"
    ::= { affirmedServicesContentFilterServiceStatisticsClusterLevelInstContCatEntry 64 }

affirmedServicesContentFilterServiceStatisticsClusterLevelInstContCatNumcategoryrealestate OBJECT-TYPE
    SYNTAX      ConfdString
    MAX-ACCESS  read-only
    STATUS      current
    DESCRIPTION "Total number of requests categorized as Real Estate Online Category"
    ::= { affirmedServicesContentFilterServiceStatisticsClusterLevelInstContCatEntry 65 }

affirmedServicesContentFilterServiceStatisticsClusterLevelInstContCatNumcategoryreference OBJECT-TYPE
    SYNTAX      ConfdString
    MAX-ACCESS  read-only
    STATUS      current
    DESCRIPTION "Total number of requests categorized as Reference Online Category"
    ::= { affirmedServicesContentFilterServiceStatisticsClusterLevelInstContCatEntry 66 }

affirmedServicesContentFilterServiceStatisticsClusterLevelInstContCatNumcategoryreligion OBJECT-TYPE
    SYNTAX      ConfdString
    MAX-ACCESS  read-only
    STATUS      current
    DESCRIPTION "Total number of requests categorized as Religion Online Category"
    ::= { affirmedServicesContentFilterServiceStatisticsClusterLevelInstContCatEntry 67 }

affirmedServicesContentFilterServiceStatisticsClusterLevelInstContCatNumcategoryremoteaccess OBJECT-TYPE
    SYNTAX      ConfdString
    MAX-ACCESS  read-only
    STATUS      current
    DESCRIPTION "Total number of requests categorized as Remote Access Online Category"
    ::= { affirmedServicesContentFilterServiceStatisticsClusterLevelInstContCatEntry 68 }

affirmedServicesContentFilterServiceStatisticsClusterLevelInstContCatNumcategoryscience OBJECT-TYPE
    SYNTAX      ConfdString
    MAX-ACCESS  read-only
    STATUS      current
    DESCRIPTION "Total number of requests categorized as Science Online Category"
    ::= { affirmedServicesContentFilterServiceStatisticsClusterLevelInstContCatEntry 69 }

affirmedServicesContentFilterServiceStatisticsClusterLevelInstContCatNumcategorysearch OBJECT-TYPE
    SYNTAX      ConfdString
    MAX-ACCESS  read-only
    STATUS      current
    DESCRIPTION "Total number of requests categorized as Search Online Category"
    ::= { affirmedServicesContentFilterServiceStatisticsClusterLevelInstContCatEntry 70 }

affirmedServicesContentFilterServiceStatisticsClusterLevelInstContCatNumcategoryselfharm OBJECT-TYPE
    SYNTAX      ConfdString
    MAX-ACCESS  read-only
    STATUS      current
    DESCRIPTION "Total number of requests categorized as Self Harm Online Category"
    ::= { affirmedServicesContentFilterServiceStatisticsClusterLevelInstContCatEntry 71 }

affirmedServicesContentFilterServiceStatisticsClusterLevelInstContCatNumcategorysexualeducation OBJECT-TYPE
    SYNTAX      ConfdString
    MAX-ACCESS  read-only
    STATUS      current
    DESCRIPTION "Total number of requests categorized as Sexual Education Online Category"
    ::= { affirmedServicesContentFilterServiceStatisticsClusterLevelInstContCatEntry 72 }

affirmedServicesContentFilterServiceStatisticsClusterLevelInstContCatNumcategoryshopping OBJECT-TYPE
    SYNTAX      ConfdString
    MAX-ACCESS  read-only
    STATUS      current
    DESCRIPTION "Total number of requests categorized as Shopping Online Category"
    ::= { affirmedServicesContentFilterServiceStatisticsClusterLevelInstContCatEntry 73 }

affirmedServicesContentFilterServiceStatisticsClusterLevelInstContCatNumcategorysports OBJECT-TYPE
    SYNTAX      ConfdString
    MAX-ACCESS  read-only
    STATUS      current
    DESCRIPTION "Total number of requests categorized as Sports Online Category"
    ::= { affirmedServicesContentFilterServiceStatisticsClusterLevelInstContCatEntry 74 }

affirmedServicesContentFilterServiceStatisticsClusterLevelInstContCatNumcategorystreamingmedia OBJECT-TYPE
    SYNTAX      ConfdString
    MAX-ACCESS  read-only
    STATUS      current
    DESCRIPTION "Total number of requests categorized as Streaming Media Online Category"
    ::= { affirmedServicesContentFilterServiceStatisticsClusterLevelInstContCatEntry 75 }

affirmedServicesContentFilterServiceStatisticsClusterLevelInstContCatNumcategorysuicide OBJECT-TYPE
    SYNTAX      ConfdString
    MAX-ACCESS  read-only
    STATUS      current
    DESCRIPTION "Total number of requests categorized as Suicide Online Category"
    ::= { affirmedServicesContentFilterServiceStatisticsClusterLevelInstContCatEntry 76 }

affirmedServicesContentFilterServiceStatisticsClusterLevelInstContCatNumcategorytechnologyandtelecommunication OBJECT-TYPE
    SYNTAX      ConfdString
    MAX-ACCESS  read-only
    STATUS      current
    DESCRIPTION "Total number of requests categorized as Technology And Telecommunication Online Category"
    ::= { affirmedServicesContentFilterServiceStatisticsClusterLevelInstContCatEntry 77 }

affirmedServicesContentFilterServiceStatisticsClusterLevelInstContCatNumcategorytobacco OBJECT-TYPE
    SYNTAX      ConfdString
    MAX-ACCESS  read-only
    STATUS      current
    DESCRIPTION "Total number of requests categorized as Tobacco Online Category"
    ::= { affirmedServicesContentFilterServiceStatisticsClusterLevelInstContCatEntry 78 }

affirmedServicesContentFilterServiceStatisticsClusterLevelInstContCatNumcategorytravel OBJECT-TYPE
    SYNTAX      ConfdString
    MAX-ACCESS  read-only
    STATUS      current
    DESCRIPTION "Total number of requests categorized as Travel Online Category"
    ::= { affirmedServicesContentFilterServiceStatisticsClusterLevelInstContCatEntry 79 }

affirmedServicesContentFilterServiceStatisticsClusterLevelInstContCatNumcategoryviolence OBJECT-TYPE
    SYNTAX      ConfdString
    MAX-ACCESS  read-only
    STATUS      current
    DESCRIPTION "Total number of requests categorized as Violence Online Category"
    ::= { affirmedServicesContentFilterServiceStatisticsClusterLevelInstContCatEntry 80 }

affirmedServicesContentFilterServiceStatisticsClusterLevelInstContCatNumcategoryvirtualcommunity OBJECT-TYPE
    SYNTAX      ConfdString
    MAX-ACCESS  read-only
    STATUS      current
    DESCRIPTION "Total number of requests categorized as Virtual Community Online Category"
    ::= { affirmedServicesContentFilterServiceStatisticsClusterLevelInstContCatEntry 81 }

affirmedServicesContentFilterServiceStatisticsClusterLevelInstContCatNumcategoryweapons OBJECT-TYPE
    SYNTAX      ConfdString
    MAX-ACCESS  read-only
    STATUS      current
    DESCRIPTION "Total number of requests categorized as Weapons Online Category"
    ::= { affirmedServicesContentFilterServiceStatisticsClusterLevelInstContCatEntry 82 }

affirmedServicesContentFilterServiceStatisticsClusterLevelInstContCatNumcategorywebmail OBJECT-TYPE
    SYNTAX      ConfdString
    MAX-ACCESS  read-only
    STATUS      current
    DESCRIPTION "Total number of requests categorized as Webmail Online Category"
    ::= { affirmedServicesContentFilterServiceStatisticsClusterLevelInstContCatEntry 83 }

affirmedServicesContentFilterServiceStatisticsClusterLevelInstContCatNumcategorywedding OBJECT-TYPE
    SYNTAX      ConfdString
    MAX-ACCESS  read-only
    STATUS      current
    DESCRIPTION "Total number of requests categorized as Wedding Online Category"
    ::= { affirmedServicesContentFilterServiceStatisticsClusterLevelInstContCatEntry 84 }

affirmedServicesContentFilterServiceStatisticsClusterLevelInstContCatNumcategorywirelessbusiness OBJECT-TYPE
    SYNTAX      ConfdString
    MAX-ACCESS  read-only
    STATUS      current
    DESCRIPTION "Total number of requests categorized as Wireless Business Online Category"
    ::= { affirmedServicesContentFilterServiceStatisticsClusterLevelInstContCatEntry 85 }

affirmedServicesContentFilterServiceStatisticsClusterLevelInstContCatNumcategorywirelesschatsms OBJECT-TYPE
    SYNTAX      ConfdString
    MAX-ACCESS  read-only
    STATUS      current
    DESCRIPTION "Total number of requests categorized as Wireless Chat and SMS Online Category"
    ::= { affirmedServicesContentFilterServiceStatisticsClusterLevelInstContCatEntry 86 }

affirmedServicesContentFilterServiceStatisticsClusterLevelInstContCatNumcategorywirelessdynamic OBJECT-TYPE
    SYNTAX      ConfdString
    MAX-ACCESS  read-only
    STATUS      current
    DESCRIPTION "Total number of requests categorized as Wireless Dynamic Online Category"
    ::= { affirmedServicesContentFilterServiceStatisticsClusterLevelInstContCatEntry 87 }

affirmedServicesContentFilterServiceStatisticsClusterLevelInstContCatNumcategorywirelessentertainment OBJECT-TYPE
    SYNTAX      ConfdString
    MAX-ACCESS  read-only
    STATUS      current
    DESCRIPTION "Total number of requests categorized as Wireless Entertainment Online Category"
    ::= { affirmedServicesContentFilterServiceStatisticsClusterLevelInstContCatEntry 88 }

affirmedServicesContentFilterServiceStatisticsClusterLevelInstContCatNumcategorywirelessfinance OBJECT-TYPE
    SYNTAX      ConfdString
    MAX-ACCESS  read-only
    STATUS      current
    DESCRIPTION "Total number of requests categorized as Wireless Finance Online Category"
    ::= { affirmedServicesContentFilterServiceStatisticsClusterLevelInstContCatEntry 89 }

affirmedServicesContentFilterServiceStatisticsClusterLevelInstContCatNumcategorywirelessgambling OBJECT-TYPE
    SYNTAX      ConfdString
    MAX-ACCESS  read-only
    STATUS      current
    DESCRIPTION "Total number of requests categorized as Wireless Gambling Online Category"
    ::= { affirmedServicesContentFilterServiceStatisticsClusterLevelInstContCatEntry 90 }

affirmedServicesContentFilterServiceStatisticsClusterLevelInstContCatNumcategorywirelessnews OBJECT-TYPE
    SYNTAX      ConfdString
    MAX-ACCESS  read-only
    STATUS      current
    DESCRIPTION "Total number of requests categorized as Wireless News Online Category"
    ::= { affirmedServicesContentFilterServiceStatisticsClusterLevelInstContCatEntry 91 }

affirmedServicesContentFilterServiceStatisticsClusterLevelInstContCatNumcategorywirelesspersonalsanddating OBJECT-TYPE
    SYNTAX      ConfdString
    MAX-ACCESS  read-only
    STATUS      current
    DESCRIPTION "Total number of requests categorized as Wireless Personals And Dating Online Category"
    ::= { affirmedServicesContentFilterServiceStatisticsClusterLevelInstContCatEntry 92 }

affirmedServicesContentFilterServiceStatisticsClusterLevelInstContCatNumcategorywirelesspornography OBJECT-TYPE
    SYNTAX      ConfdString
    MAX-ACCESS  read-only
    STATUS      current
    DESCRIPTION "Total number of requests categorized as Wireless Pornography Online Category"
    ::= { affirmedServicesContentFilterServiceStatisticsClusterLevelInstContCatEntry 93 }

affirmedServicesContentFilterServiceStatisticsClusterLevelInstContCatNumcategorywirelesssports OBJECT-TYPE
    SYNTAX      ConfdString
    MAX-ACCESS  read-only
    STATUS      current
    DESCRIPTION "Total number of requests categorized as Wireless Sports Online Category"
    ::= { affirmedServicesContentFilterServiceStatisticsClusterLevelInstContCatEntry 94 }

affirmedServicesContentFilterServiceStatisticsClusterLevelInstContCatNumcategorywirelesstravel OBJECT-TYPE
    SYNTAX      ConfdString
    MAX-ACCESS  read-only
    STATUS      current
    DESCRIPTION "Total number of requests categorized as Wireless Travel Online Category"
    ::= { affirmedServicesContentFilterServiceStatisticsClusterLevelInstContCatEntry 95 }

affirmedServicesContentFilterServiceStatisticsClusterLevelInstContCatNumcategoryunknown OBJECT-TYPE
    SYNTAX      ConfdString
    MAX-ACCESS  read-only
    STATUS      current
    DESCRIPTION "Total number of requests failed categorization"
    ::= { affirmedServicesContentFilterServiceStatisticsClusterLevelInstContCatEntry 96 }

affirmedServicesContentFilterServiceStatisticsClusterLevelInstContCatNumcategorymalware OBJECT-TYPE
    SYNTAX      ConfdString
    MAX-ACCESS  read-only
    STATUS      current
    DESCRIPTION "Total number of requests categorized as Malware Online Category"
    ::= { affirmedServicesContentFilterServiceStatisticsClusterLevelInstContCatEntry 97 }

affirmedServicesContentFilterServiceStatisticsClusterLevelInstContCatNumcategoryphishing OBJECT-TYPE
    SYNTAX      ConfdString
    MAX-ACCESS  read-only
    STATUS      current
    DESCRIPTION "Total number of requests categorized as Phishing Online Category"
    ::= { affirmedServicesContentFilterServiceStatisticsClusterLevelInstContCatEntry 98 }

affirmedServicesContentFilterServiceStatisticsClusterLevelInstContCatNumcategoryiwf OBJECT-TYPE
    SYNTAX      ConfdString
    MAX-ACCESS  read-only
    STATUS      current
    DESCRIPTION "Total number of requests categorized as internet watch foundation CAIC Online Category"
    ::= { affirmedServicesContentFilterServiceStatisticsClusterLevelInstContCatEntry 99 }

affirmedServicesContentFilterServiceStatisticsClusterLevelInstContCatNumcategorynocat OBJECT-TYPE
    SYNTAX      ConfdString
    MAX-ACCESS  read-only
    STATUS      current
    DESCRIPTION "Total number of requests categorized as none of well-known categories"
    ::= { affirmedServicesContentFilterServiceStatisticsClusterLevelInstContCatEntry 100 }

affirmedServicesContentFilterServiceStatisticsClusterLevelInstContCatNumcategoryother OBJECT-TYPE
    SYNTAX      ConfdString
    MAX-ACCESS  read-only
    STATUS      current
    DESCRIPTION "Total number of requests categorized as new category not yet supported by AN3K"
    ::= { affirmedServicesContentFilterServiceStatisticsClusterLevelInstContCatEntry 101 }

affirmedServicesContentFilterServiceStatisticsClusterLevelInstContCatNumcategoryalcoholkids OBJECT-TYPE
    SYNTAX      ConfdString
    MAX-ACCESS  read-only
    STATUS      current
    DESCRIPTION "Total number of requests categorized as Alcohol Kids Online Category"
    ::= { affirmedServicesContentFilterServiceStatisticsClusterLevelInstContCatEntry 102 }

affirmedServicesContentFilterServiceStatisticsClusterLevelInstContCatNumcategorytobaccokids OBJECT-TYPE
    SYNTAX      ConfdString
    MAX-ACCESS  read-only
    STATUS      current
    DESCRIPTION "Total number of requests categorized as Tobacco Kids Online Category"
    ::= { affirmedServicesContentFilterServiceStatisticsClusterLevelInstContCatEntry 103 }

affirmedServicesContentFilterServiceStatisticsClusterLevelInstContCatNumcategorycyberbullying OBJECT-TYPE
    SYNTAX      ConfdString
    MAX-ACCESS  read-only
    STATUS      current
    DESCRIPTION "Total number of requests categorized as Cyberbullying Online Category"
    ::= { affirmedServicesContentFilterServiceStatisticsClusterLevelInstContCatEntry 104 }

affirmedServicesContentFilterServiceStatisticsClusterLevelInstContCatNumhttpsrequestlookups OBJECT-TYPE
    SYNTAX      ConfdString
    MAX-ACCESS  read-only
    STATUS      current
    DESCRIPTION "Total number of HTTPS request Lookups"
    ::= { affirmedServicesContentFilterServiceStatisticsClusterLevelInstContCatEntry 105 }

affirmedServicesContentFilterServiceStatisticsClusterLevelInstContCatNumlookupfailure OBJECT-TYPE
    SYNTAX      ConfdString
    MAX-ACCESS  read-only
    STATUS      current
    DESCRIPTION "Total number of lookup failures"
    ::= { affirmedServicesContentFilterServiceStatisticsClusterLevelInstContCatEntry 106 }

affirmedServicesContentFilterServiceStatisticsClusterLevelInstContCatNumquicrequestlookups OBJECT-TYPE
    SYNTAX      ConfdString
    MAX-ACCESS  read-only
    STATUS      current
    DESCRIPTION "Total number of QUIC request Lookups"
    ::= { affirmedServicesContentFilterServiceStatisticsClusterLevelInstContCatEntry 107 }

affirmedServicesContentFilterServiceStatisticsClusterLevelInstContCatNumcategorybbfcwhitelist OBJECT-TYPE
    SYNTAX      ConfdString
    MAX-ACCESS  read-only
    STATUS      current
    DESCRIPTION "Total number of requests categorized as BBFCWhitelist Online Category"
    ::= { affirmedServicesContentFilterServiceStatisticsClusterLevelInstContCatEntry 108 }

affirmedServicesContentFilterServiceStatisticsClusterLevelInstContCatNumcategorybbfcblacklist OBJECT-TYPE
    SYNTAX      ConfdString
    MAX-ACCESS  read-only
    STATUS      current
    DESCRIPTION "Total number of requests categorized as BBFCBlacklist Online Category"
    ::= { affirmedServicesContentFilterServiceStatisticsClusterLevelInstContCatEntry 109 }

affirmedServicesContentFilterServiceStatisticsClusterLevelInstContCatNumcategorycannabidiol OBJECT-TYPE
    SYNTAX      ConfdString
    MAX-ACCESS  read-only
    STATUS      current
    DESCRIPTION "Total number of requests categorized as Cannabidiol Online Category"
    ::= { affirmedServicesContentFilterServiceStatisticsClusterLevelInstContCatEntry 110 }

affirmedServicesContentFilterServiceStatisticsClusterLevelInstContCatNumcategorycloudinfrastructure OBJECT-TYPE
    SYNTAX      ConfdString
    MAX-ACCESS  read-only
    STATUS      current
    DESCRIPTION "Total number of requests categorized as CloudInfrastructure Online Category"
    ::= { affirmedServicesContentFilterServiceStatisticsClusterLevelInstContCatEntry 111 }

affirmedServicesContentFilterServiceStatisticsClusterLevelInstContCatNumcategoryfireworks OBJECT-TYPE
    SYNTAX      ConfdString
    MAX-ACCESS  read-only
    STATUS      current
    DESCRIPTION "Total number of requests categorized as Fireworks Online Category"
    ::= { affirmedServicesContentFilterServiceStatisticsClusterLevelInstContCatEntry 112 }

affirmedServicesContentFilterServiceStatisticsClusterLevelInstContCatNumcategorylingerie OBJECT-TYPE
    SYNTAX      ConfdString
    MAX-ACCESS  read-only
    STATUS      current
    DESCRIPTION "Total number of requests categorized as Lingerie Online Category"
    ::= { affirmedServicesContentFilterServiceStatisticsClusterLevelInstContCatEntry 113 }

affirmedServicesContentFilterServiceStatisticsClusterLevelInstContCatNumcategorysexualadvice OBJECT-TYPE
    SYNTAX      ConfdString
    MAX-ACCESS  read-only
    STATUS      current
    DESCRIPTION "Total number of requests categorized as SexualAdvice Online Category"
    ::= { affirmedServicesContentFilterServiceStatisticsClusterLevelInstContCatEntry 114 }

affirmedServicesContentFilterServiceStatisticsClusterLevelInstContCatNumcategorytracking OBJECT-TYPE
    SYNTAX      ConfdString
    MAX-ACCESS  read-only
    STATUS      current
    DESCRIPTION "Total number of requests categorized as Tracking Online Category"
    ::= { affirmedServicesContentFilterServiceStatisticsClusterLevelInstContCatEntry 115 }

affirmedServicesContentFilterServiceStatisticsClusterLevelInstContCatNumcategoryukdeablacklist OBJECT-TYPE
    SYNTAX      ConfdString
    MAX-ACCESS  read-only
    STATUS      current
    DESCRIPTION "Total number of requests categorized as UKDEABlacklist Online Category"
    ::= { affirmedServicesContentFilterServiceStatisticsClusterLevelInstContCatEntry 116 }

affirmedServicesContentFilterServiceStatisticsNode-levelSummaryTable OBJECT-TYPE
    SYNTAX      SEQUENCE OF AffirmedServicesContentFilterServiceStatisticsNode-levelSummaryEntry
    MAX-ACCESS  not-accessible
    STATUS      current
    DESCRIPTION ""
    ::= { affirmedServicesContentFilterServiceStatisticsNode-level 1 }

affirmedServicesContentFilterServiceStatisticsNode-levelSummaryEntry OBJECT-TYPE
    SYNTAX      AffirmedServicesContentFilterServiceStatisticsNode-levelSummaryEntry
    MAX-ACCESS  not-accessible
    STATUS      current
    DESCRIPTION ""
    INDEX { affirmedServicesContentFilterServiceStatisticsNode-levelSummaryChassis, affirmedServicesContentFilterServiceStatisticsNode-levelSummarySlot }
        ::= { affirmedServicesContentFilterServiceStatisticsNode-levelSummaryTable 1 }

AffirmedServicesContentFilterServiceStatisticsNode-levelSummaryEntry ::=
    SEQUENCE {
        affirmedServicesContentFilterServiceStatisticsNode-levelSummaryChassis Unsigned32,
        affirmedServicesContentFilterServiceStatisticsNode-levelSummarySlot INTEGER,
        affirmedServicesContentFilterServiceStatisticsNode-levelSummaryNumfilterserviceattempts ConfdString,
        affirmedServicesContentFilterServiceStatisticsNode-levelSummaryNumfilterservicesuccess ConfdString,
        affirmedServicesContentFilterServiceStatisticsNode-levelSummaryNumfilterserviceabortedbyclient ConfdString,
        affirmedServicesContentFilterServiceStatisticsNode-levelSummaryNumfilterservicefailed ConfdString,
        affirmedServicesContentFilterServiceStatisticsNode-levelSummaryNumfilterservicenomatch ConfdString,
        affirmedServicesContentFilterServiceStatisticsNode-levelSummaryNumrequestterminated ConfdString,
        affirmedServicesContentFilterServiceStatisticsNode-levelSummaryNumrequestredirected ConfdString,
        affirmedServicesContentFilterServiceStatisticsNode-levelSummaryNumrequestblocked ConfdString,
        affirmedServicesContentFilterServiceStatisticsNode-levelSummaryNumrequestallowed ConfdString,
        affirmedServicesContentFilterServiceStatisticsNode-levelSummaryNumblacklisturlmatched ConfdString,
        affirmedServicesContentFilterServiceStatisticsNode-levelSummaryNumblacklistdomainmatched ConfdString,
        affirmedServicesContentFilterServiceStatisticsNode-levelSummaryNumcategoryurlmatched ConfdString,
        affirmedServicesContentFilterServiceStatisticsNode-levelSummaryNumcategorydomainmatched ConfdString,
        affirmedServicesContentFilterServiceStatisticsNode-levelSummaryNumwhitelisturlmatched ConfdString,
        affirmedServicesContentFilterServiceStatisticsNode-levelSummaryNumwhitelistdomainmatched ConfdString,
        affirmedServicesContentFilterServiceStatisticsNode-levelSummaryNumsrgmatched ConfdString,
        affirmedServicesContentFilterServiceStatisticsNode-levelSummaryNumonlinecategorymatched ConfdString,
        affirmedServicesContentFilterServiceStatisticsNode-levelSummaryNummalwarecategorymatched ConfdString,
        affirmedServicesContentFilterServiceStatisticsNode-levelSummaryNumphishingcategorymatched ConfdString,
        affirmedServicesContentFilterServiceStatisticsNode-levelSummaryNumiwfcategorymatched ConfdString,
        affirmedServicesContentFilterServiceStatisticsNode-levelSummaryNumfilterhashlistmatched ConfdString,
        affirmedServicesContentFilterServiceStatisticsNode-levelSummaryNumbingsafesearchenforced ConfdString,
        affirmedServicesContentFilterServiceStatisticsNode-levelSummaryNumrequestredirectchangedallowrequestsameurl ConfdString,
        affirmedServicesContentFilterServiceStatisticsNode-levelSummaryNumrequestredirectchangedallowinterval ConfdString,
        affirmedServicesContentFilterServiceStatisticsNode-levelSummaryNumgooglesafesearchenforced ConfdString,
        affirmedServicesContentFilterServiceStatisticsNode-levelSummaryNumyoutubesafesearchenforced ConfdString
    }

affirmedServicesContentFilterServiceStatisticsNode-levelSummaryChassis OBJECT-TYPE
    SYNTAX      Unsigned32
    MAX-ACCESS  not-accessible
    STATUS      current
    DESCRIPTION "chassis ID"
    ::= { affirmedServicesContentFilterServiceStatisticsNode-levelSummaryEntry 1 }

affirmedServicesContentFilterServiceStatisticsNode-levelSummarySlot OBJECT-TYPE
    SYNTAX      INTEGER {a1(1),a2(2),a3(3),a4(4),a5(5),a6(6),a7(7),a8(8),a9(9),a10(10),a11(11),a12(12),a13(13),a14(14),a15(15),a16(16),a17(17),a18(18),a19(19),a20(20),a21(21),a22(22),a23(23),a24(24),a25(25),a26(26),a27(27),a28(28),a29(29),a30(30),a31(31),a32(32),a33(33),a34(34),a35(35),a36(36),a37(37),a38(38),a39(39),a40(40),a41(41),a42(42),a43(43),a44(44),a45(45),a46(46),a47(47),a48(48),a49(49),a50(50),a51(51),a52(52),a53(53),a54(54),a55(55),a56(56),a57(57),a58(58),a59(59),a60(60),a61(61),a62(62),a63(63),a64(64),a65(65),a66(66),a67(67),a68(68),a69(69),a70(70),a71(71),a72(72),a73(73),a74(74),a75(75),a76(76),a77(77),a78(78),a79(79),a80(80),a81(81),a82(82),a83(83),a84(84),a85(85),a86(86),a87(87),a88(88),a89(89),a90(90),a91(91),a92(92),a93(93),a94(94),a95(95),a96(96),a97(97),a98(98),a99(99),a100(100),a101(101),a102(102),a103(103),a104(104),a105(105),a106(106),a107(107),a108(108),a109(109),a110(110),a111(111),a112(112),a113(113),a114(114),a115(115),a116(116),a117(117),a118(118),a119(119),a120(120),a121(121),a122(122),a123(123),a124(124),a125(125),a126(126),a127(127),a128(128)}
    MAX-ACCESS  not-accessible
    STATUS      current
    DESCRIPTION "slot number"
    ::= { affirmedServicesContentFilterServiceStatisticsNode-levelSummaryEntry 2 }

affirmedServicesContentFilterServiceStatisticsNode-levelSummaryNumfilterserviceattempts OBJECT-TYPE
    SYNTAX      ConfdString
    MAX-ACCESS  read-only
    STATUS      current
    DESCRIPTION "Total number of filter service attempts"
    ::= { affirmedServicesContentFilterServiceStatisticsNode-levelSummaryEntry 3 }

affirmedServicesContentFilterServiceStatisticsNode-levelSummaryNumfilterservicesuccess OBJECT-TYPE
    SYNTAX      ConfdString
    MAX-ACCESS  read-only
    STATUS      current
    DESCRIPTION "Total number of filter service applied"
    ::= { affirmedServicesContentFilterServiceStatisticsNode-levelSummaryEntry 4 }

affirmedServicesContentFilterServiceStatisticsNode-levelSummaryNumfilterserviceabortedbyclient OBJECT-TYPE
    SYNTAX      ConfdString
    MAX-ACCESS  read-only
    STATUS      current
    DESCRIPTION "Total number of filter service aborted by client"
    ::= { affirmedServicesContentFilterServiceStatisticsNode-levelSummaryEntry 5 }

affirmedServicesContentFilterServiceStatisticsNode-levelSummaryNumfilterservicefailed OBJECT-TYPE
    SYNTAX      ConfdString
    MAX-ACCESS  read-only
    STATUS      current
    DESCRIPTION "Total number of filter service failed"
    ::= { affirmedServicesContentFilterServiceStatisticsNode-levelSummaryEntry 6 }

affirmedServicesContentFilterServiceStatisticsNode-levelSummaryNumfilterservicenomatch OBJECT-TYPE
    SYNTAX      ConfdString
    MAX-ACCESS  read-only
    STATUS      current
    DESCRIPTION "Total number of filter service not applied"
    ::= { affirmedServicesContentFilterServiceStatisticsNode-levelSummaryEntry 7 }

affirmedServicesContentFilterServiceStatisticsNode-levelSummaryNumrequestterminated OBJECT-TYPE
    SYNTAX      ConfdString
    MAX-ACCESS  read-only
    STATUS      current
    DESCRIPTION "Total number of request terminated"
    ::= { affirmedServicesContentFilterServiceStatisticsNode-levelSummaryEntry 8 }

affirmedServicesContentFilterServiceStatisticsNode-levelSummaryNumrequestredirected OBJECT-TYPE
    SYNTAX      ConfdString
    MAX-ACCESS  read-only
    STATUS      current
    DESCRIPTION "Total number of request redirected"
    ::= { affirmedServicesContentFilterServiceStatisticsNode-levelSummaryEntry 9 }

affirmedServicesContentFilterServiceStatisticsNode-levelSummaryNumrequestblocked OBJECT-TYPE
    SYNTAX      ConfdString
    MAX-ACCESS  read-only
    STATUS      current
    DESCRIPTION "Total number of request blocked"
    ::= { affirmedServicesContentFilterServiceStatisticsNode-levelSummaryEntry 10 }

affirmedServicesContentFilterServiceStatisticsNode-levelSummaryNumrequestallowed OBJECT-TYPE
    SYNTAX      ConfdString
    MAX-ACCESS  read-only
    STATUS      current
    DESCRIPTION "Total number of request allowed"
    ::= { affirmedServicesContentFilterServiceStatisticsNode-levelSummaryEntry 11 }

affirmedServicesContentFilterServiceStatisticsNode-levelSummaryNumblacklisturlmatched OBJECT-TYPE
    SYNTAX      ConfdString
    MAX-ACCESS  read-only
    STATUS      current
    DESCRIPTION "Total number of blackList URL matched"
    ::= { affirmedServicesContentFilterServiceStatisticsNode-levelSummaryEntry 12 }

affirmedServicesContentFilterServiceStatisticsNode-levelSummaryNumblacklistdomainmatched OBJECT-TYPE
    SYNTAX      ConfdString
    MAX-ACCESS  read-only
    STATUS      current
    DESCRIPTION "Total number of blackList domain matched"
    ::= { affirmedServicesContentFilterServiceStatisticsNode-levelSummaryEntry 13 }

affirmedServicesContentFilterServiceStatisticsNode-levelSummaryNumcategoryurlmatched OBJECT-TYPE
    SYNTAX      ConfdString
    MAX-ACCESS  read-only
    STATUS      current
    DESCRIPTION "Total number of static category URL matched"
    ::= { affirmedServicesContentFilterServiceStatisticsNode-levelSummaryEntry 14 }

affirmedServicesContentFilterServiceStatisticsNode-levelSummaryNumcategorydomainmatched OBJECT-TYPE
    SYNTAX      ConfdString
    MAX-ACCESS  read-only
    STATUS      current
    DESCRIPTION "Total number of static category domain matched"
    ::= { affirmedServicesContentFilterServiceStatisticsNode-levelSummaryEntry 15 }

affirmedServicesContentFilterServiceStatisticsNode-levelSummaryNumwhitelisturlmatched OBJECT-TYPE
    SYNTAX      ConfdString
    MAX-ACCESS  read-only
    STATUS      current
    DESCRIPTION "Total number of whitelist URL matched"
    ::= { affirmedServicesContentFilterServiceStatisticsNode-levelSummaryEntry 16 }

affirmedServicesContentFilterServiceStatisticsNode-levelSummaryNumwhitelistdomainmatched OBJECT-TYPE
    SYNTAX      ConfdString
    MAX-ACCESS  read-only
    STATUS      current
    DESCRIPTION "Total number of whitelist domain matched"
    ::= { affirmedServicesContentFilterServiceStatisticsNode-levelSummaryEntry 17 }

affirmedServicesContentFilterServiceStatisticsNode-levelSummaryNumsrgmatched OBJECT-TYPE
    SYNTAX      ConfdString
    MAX-ACCESS  read-only
    STATUS      current
    DESCRIPTION "Total number of Service-Rule matched"
    ::= { affirmedServicesContentFilterServiceStatisticsNode-levelSummaryEntry 18 }

affirmedServicesContentFilterServiceStatisticsNode-levelSummaryNumonlinecategorymatched OBJECT-TYPE
    SYNTAX      ConfdString
    MAX-ACCESS  read-only
    STATUS      current
    DESCRIPTION "Total number of online category groups matched"
    ::= { affirmedServicesContentFilterServiceStatisticsNode-levelSummaryEntry 19 }

affirmedServicesContentFilterServiceStatisticsNode-levelSummaryNummalwarecategorymatched OBJECT-TYPE
    SYNTAX      ConfdString
    MAX-ACCESS  read-only
    STATUS      current
    DESCRIPTION "Total number of malware category groups matched"
    ::= { affirmedServicesContentFilterServiceStatisticsNode-levelSummaryEntry 20 }

affirmedServicesContentFilterServiceStatisticsNode-levelSummaryNumphishingcategorymatched OBJECT-TYPE
    SYNTAX      ConfdString
    MAX-ACCESS  read-only
    STATUS      current
    DESCRIPTION "Total number of phishing category matched"
    ::= { affirmedServicesContentFilterServiceStatisticsNode-levelSummaryEntry 21 }

affirmedServicesContentFilterServiceStatisticsNode-levelSummaryNumiwfcategorymatched OBJECT-TYPE
    SYNTAX      ConfdString
    MAX-ACCESS  read-only
    STATUS      current
    DESCRIPTION "Total number of IWF category filter matched"
    ::= { affirmedServicesContentFilterServiceStatisticsNode-levelSummaryEntry 22 }

affirmedServicesContentFilterServiceStatisticsNode-levelSummaryNumfilterhashlistmatched OBJECT-TYPE
    SYNTAX      ConfdString
    MAX-ACCESS  read-only
    STATUS      current
    DESCRIPTION "Total number of Filter Hash List matched"
    ::= { affirmedServicesContentFilterServiceStatisticsNode-levelSummaryEntry 23 }

affirmedServicesContentFilterServiceStatisticsNode-levelSummaryNumbingsafesearchenforced OBJECT-TYPE
    SYNTAX      ConfdString
    MAX-ACCESS  read-only
    STATUS      current
    DESCRIPTION "Total number of Bing Safe Search enforced"
    ::= { affirmedServicesContentFilterServiceStatisticsNode-levelSummaryEntry 24 }

affirmedServicesContentFilterServiceStatisticsNode-levelSummaryNumrequestredirectchangedallowrequestsameurl OBJECT-TYPE
    SYNTAX      ConfdString
    MAX-ACCESS  read-only
    STATUS      current
    DESCRIPTION "Total number of redirect changed to allow - Request with Same URL"
    ::= { affirmedServicesContentFilterServiceStatisticsNode-levelSummaryEntry 25 }

affirmedServicesContentFilterServiceStatisticsNode-levelSummaryNumrequestredirectchangedallowinterval OBJECT-TYPE
    SYNTAX      ConfdString
    MAX-ACCESS  read-only
    STATUS      current
    DESCRIPTION "Total number of redirect changed to allow - Request within Redirect Interval"
    ::= { affirmedServicesContentFilterServiceStatisticsNode-levelSummaryEntry 26 }

affirmedServicesContentFilterServiceStatisticsNode-levelSummaryNumgooglesafesearchenforced OBJECT-TYPE
    SYNTAX      ConfdString
    MAX-ACCESS  read-only
    STATUS      current
    DESCRIPTION "Total number of Google Safe Search enforced"
    ::= { affirmedServicesContentFilterServiceStatisticsNode-levelSummaryEntry 27 }

affirmedServicesContentFilterServiceStatisticsNode-levelSummaryNumyoutubesafesearchenforced OBJECT-TYPE
    SYNTAX      ConfdString
    MAX-ACCESS  read-only
    STATUS      current
    DESCRIPTION "Total number of YouTube Safe Search enforced"
    ::= { affirmedServicesContentFilterServiceStatisticsNode-levelSummaryEntry 28 }

affirmedServicesContentFilterServiceStatisticsNode-levelInstanceTable OBJECT-TYPE
    SYNTAX      SEQUENCE OF AffirmedServicesContentFilterServiceStatisticsNode-levelInstanceEntry
    MAX-ACCESS  not-accessible
    STATUS      current
    DESCRIPTION ""
    ::= { affirmedServicesContentFilterServiceStatisticsNode-level 2 }

affirmedServicesContentFilterServiceStatisticsNode-levelInstanceEntry OBJECT-TYPE
    SYNTAX      AffirmedServicesContentFilterServiceStatisticsNode-levelInstanceEntry
    MAX-ACCESS  not-accessible
    STATUS      current
    DESCRIPTION ""
    INDEX { affirmedServicesContentFilterServiceStatisticsNode-levelInstanceName, affirmedServicesContentFilterServiceStatisticsNode-levelInstanceChassis, affirmedServicesContentFilterServiceStatisticsNode-levelInstanceSlot }
        ::= { affirmedServicesContentFilterServiceStatisticsNode-levelInstanceTable 1 }

AffirmedServicesContentFilterServiceStatisticsNode-levelInstanceEntry ::=
    SEQUENCE {
        affirmedServicesContentFilterServiceStatisticsNode-levelInstanceName String,
        affirmedServicesContentFilterServiceStatisticsNode-levelInstanceChassis Unsigned32,
        affirmedServicesContentFilterServiceStatisticsNode-levelInstanceSlot INTEGER,
        affirmedServicesContentFilterServiceStatisticsNode-levelInstanceNumrequestterminated ConfdString,
        affirmedServicesContentFilterServiceStatisticsNode-levelInstanceNumrequestredirected ConfdString,
        affirmedServicesContentFilterServiceStatisticsNode-levelInstanceNumrequestblocked ConfdString,
        affirmedServicesContentFilterServiceStatisticsNode-levelInstanceNumrequestallowed ConfdString,
        affirmedServicesContentFilterServiceStatisticsNode-levelInstanceNumsrgmatched ConfdString,
        affirmedServicesContentFilterServiceStatisticsNode-levelInstanceNumcategoryurlmatched ConfdString,
        affirmedServicesContentFilterServiceStatisticsNode-levelInstanceNumcategorydomainmatched ConfdString,
        affirmedServicesContentFilterServiceStatisticsNode-levelInstanceNumonlinecategorymatched ConfdString,
        affirmedServicesContentFilterServiceStatisticsNode-levelInstanceNummalwarecategorymatched ConfdString,
        affirmedServicesContentFilterServiceStatisticsNode-levelInstanceNumphishingcategorymatched ConfdString,
        affirmedServicesContentFilterServiceStatisticsNode-levelInstanceNumiwfcategorymatched ConfdString,
        affirmedServicesContentFilterServiceStatisticsNode-levelInstanceNumfilterhashlistmatched ConfdString,
        affirmedServicesContentFilterServiceStatisticsNode-levelInstanceNumbingsafesearchenforced ConfdString,
        affirmedServicesContentFilterServiceStatisticsNode-levelInstanceNumrequestredirectchangedallowrequestredirectinterval ConfdString,
        affirmedServicesContentFilterServiceStatisticsNode-levelInstanceNumrequestredirectchangedallowrequestsameurl ConfdString,
        affirmedServicesContentFilterServiceStatisticsNode-levelInstanceNumgooglesafesearchenforced ConfdString,
        affirmedServicesContentFilterServiceStatisticsNode-levelInstanceNumyoutubesafesearchenforced ConfdString
    }

affirmedServicesContentFilterServiceStatisticsNode-levelInstanceName OBJECT-TYPE
    SYNTAX      String
    MAX-ACCESS  not-accessible
    STATUS      current
    DESCRIPTION "Name of content filter service instance"
    ::= { affirmedServicesContentFilterServiceStatisticsNode-levelInstanceEntry 1 }

affirmedServicesContentFilterServiceStatisticsNode-levelInstanceChassis OBJECT-TYPE
    SYNTAX      Unsigned32
    MAX-ACCESS  not-accessible
    STATUS      current
    DESCRIPTION "chassis ID"
    ::= { affirmedServicesContentFilterServiceStatisticsNode-levelInstanceEntry 2 }

affirmedServicesContentFilterServiceStatisticsNode-levelInstanceSlot OBJECT-TYPE
    SYNTAX      INTEGER {a1(1),a2(2),a3(3),a4(4),a5(5),a6(6),a7(7),a8(8),a9(9),a10(10),a11(11),a12(12),a13(13),a14(14),a15(15),a16(16),a17(17),a18(18),a19(19),a20(20),a21(21),a22(22),a23(23),a24(24),a25(25),a26(26),a27(27),a28(28),a29(29),a30(30),a31(31),a32(32),a33(33),a34(34),a35(35),a36(36),a37(37),a38(38),a39(39),a40(40),a41(41),a42(42),a43(43),a44(44),a45(45),a46(46),a47(47),a48(48),a49(49),a50(50),a51(51),a52(52),a53(53),a54(54),a55(55),a56(56),a57(57),a58(58),a59(59),a60(60),a61(61),a62(62),a63(63),a64(64),a65(65),a66(66),a67(67),a68(68),a69(69),a70(70),a71(71),a72(72),a73(73),a74(74),a75(75),a76(76),a77(77),a78(78),a79(79),a80(80),a81(81),a82(82),a83(83),a84(84),a85(85),a86(86),a87(87),a88(88),a89(89),a90(90),a91(91),a92(92),a93(93),a94(94),a95(95),a96(96),a97(97),a98(98),a99(99),a100(100),a101(101),a102(102),a103(103),a104(104),a105(105),a106(106),a107(107),a108(108),a109(109),a110(110),a111(111),a112(112),a113(113),a114(114),a115(115),a116(116),a117(117),a118(118),a119(119),a120(120),a121(121),a122(122),a123(123),a124(124),a125(125),a126(126),a127(127),a128(128)}
    MAX-ACCESS  not-accessible
    STATUS      current
    DESCRIPTION "slot number"
    ::= { affirmedServicesContentFilterServiceStatisticsNode-levelInstanceEntry 3 }

affirmedServicesContentFilterServiceStatisticsNode-levelInstanceNumrequestterminated OBJECT-TYPE
    SYNTAX      ConfdString
    MAX-ACCESS  read-only
    STATUS      current
    DESCRIPTION "Total number of request terminated"
    ::= { affirmedServicesContentFilterServiceStatisticsNode-levelInstanceEntry 4 }

affirmedServicesContentFilterServiceStatisticsNode-levelInstanceNumrequestredirected OBJECT-TYPE
    SYNTAX      ConfdString
    MAX-ACCESS  read-only
    STATUS      current
    DESCRIPTION "Total number of request redirected"
    ::= { affirmedServicesContentFilterServiceStatisticsNode-levelInstanceEntry 5 }

affirmedServicesContentFilterServiceStatisticsNode-levelInstanceNumrequestblocked OBJECT-TYPE
    SYNTAX      ConfdString
    MAX-ACCESS  read-only
    STATUS      current
    DESCRIPTION "Total number of request blocked"
    ::= { affirmedServicesContentFilterServiceStatisticsNode-levelInstanceEntry 6 }

affirmedServicesContentFilterServiceStatisticsNode-levelInstanceNumrequestallowed OBJECT-TYPE
    SYNTAX      ConfdString
    MAX-ACCESS  read-only
    STATUS      current
    DESCRIPTION "Total number of request allowed"
    ::= { affirmedServicesContentFilterServiceStatisticsNode-levelInstanceEntry 7 }

affirmedServicesContentFilterServiceStatisticsNode-levelInstanceNumsrgmatched OBJECT-TYPE
    SYNTAX      ConfdString
    MAX-ACCESS  read-only
    STATUS      current
    DESCRIPTION "Total number of Service-Rule matched"
    ::= { affirmedServicesContentFilterServiceStatisticsNode-levelInstanceEntry 8 }

affirmedServicesContentFilterServiceStatisticsNode-levelInstanceNumcategoryurlmatched OBJECT-TYPE
    SYNTAX      ConfdString
    MAX-ACCESS  read-only
    STATUS      current
    DESCRIPTION "Total number of static category URL matched"
    ::= { affirmedServicesContentFilterServiceStatisticsNode-levelInstanceEntry 9 }

affirmedServicesContentFilterServiceStatisticsNode-levelInstanceNumcategorydomainmatched OBJECT-TYPE
    SYNTAX      ConfdString
    MAX-ACCESS  read-only
    STATUS      current
    DESCRIPTION "Total number of static category domain matched"
    ::= { affirmedServicesContentFilterServiceStatisticsNode-levelInstanceEntry 10 }

affirmedServicesContentFilterServiceStatisticsNode-levelInstanceNumonlinecategorymatched OBJECT-TYPE
    SYNTAX      ConfdString
    MAX-ACCESS  read-only
    STATUS      current
    DESCRIPTION "Total number of online category groups matched"
    ::= { affirmedServicesContentFilterServiceStatisticsNode-levelInstanceEntry 11 }

affirmedServicesContentFilterServiceStatisticsNode-levelInstanceNummalwarecategorymatched OBJECT-TYPE
    SYNTAX      ConfdString
    MAX-ACCESS  read-only
    STATUS      current
    DESCRIPTION "Total number of malware category groups matched"
    ::= { affirmedServicesContentFilterServiceStatisticsNode-levelInstanceEntry 12 }

affirmedServicesContentFilterServiceStatisticsNode-levelInstanceNumphishingcategorymatched OBJECT-TYPE
    SYNTAX      ConfdString
    MAX-ACCESS  read-only
    STATUS      current
    DESCRIPTION "Total number of phishing category matched"
    ::= { affirmedServicesContentFilterServiceStatisticsNode-levelInstanceEntry 13 }

affirmedServicesContentFilterServiceStatisticsNode-levelInstanceNumiwfcategorymatched OBJECT-TYPE
    SYNTAX      ConfdString
    MAX-ACCESS  read-only
    STATUS      current
    DESCRIPTION "Total number of IWF category matched"
    ::= { affirmedServicesContentFilterServiceStatisticsNode-levelInstanceEntry 14 }

affirmedServicesContentFilterServiceStatisticsNode-levelInstanceNumfilterhashlistmatched OBJECT-TYPE
    SYNTAX      ConfdString
    MAX-ACCESS  read-only
    STATUS      current
    DESCRIPTION "Total number of Filter Hash List matched"
    ::= { affirmedServicesContentFilterServiceStatisticsNode-levelInstanceEntry 15 }

affirmedServicesContentFilterServiceStatisticsNode-levelInstanceNumbingsafesearchenforced OBJECT-TYPE
    SYNTAX      ConfdString
    MAX-ACCESS  read-only
    STATUS      current
    DESCRIPTION "Total number of Bing Safe Search enforced"
    ::= { affirmedServicesContentFilterServiceStatisticsNode-levelInstanceEntry 16 }

affirmedServicesContentFilterServiceStatisticsNode-levelInstanceNumrequestredirectchangedallowrequestredirectinterval OBJECT-TYPE
    SYNTAX      ConfdString
    MAX-ACCESS  read-only
    STATUS      current
    DESCRIPTION "Total number of redirect changed to allow - Request within Redirect Interval"
    ::= { affirmedServicesContentFilterServiceStatisticsNode-levelInstanceEntry 17 }

affirmedServicesContentFilterServiceStatisticsNode-levelInstanceNumrequestredirectchangedallowrequestsameurl OBJECT-TYPE
    SYNTAX      ConfdString
    MAX-ACCESS  read-only
    STATUS      current
    DESCRIPTION "Total number of redirect changed to allow - Request with Same URL"
    ::= { affirmedServicesContentFilterServiceStatisticsNode-levelInstanceEntry 18 }

affirmedServicesContentFilterServiceStatisticsNode-levelInstanceNumgooglesafesearchenforced OBJECT-TYPE
    SYNTAX      ConfdString
    MAX-ACCESS  read-only
    STATUS      current
    DESCRIPTION "Total number of Google Safe Search enforced"
    ::= { affirmedServicesContentFilterServiceStatisticsNode-levelInstanceEntry 19 }

affirmedServicesContentFilterServiceStatisticsNode-levelInstanceNumyoutubesafesearchenforced OBJECT-TYPE
    SYNTAX      ConfdString
    MAX-ACCESS  read-only
    STATUS      current
    DESCRIPTION "Total number of YouTube Safe Search enforced"
    ::= { affirmedServicesContentFilterServiceStatisticsNode-levelInstanceEntry 20 }

affirmedServicesContentFilterServiceStatisticsNode-levelContentCategorizationTable OBJECT-TYPE
    SYNTAX      SEQUENCE OF AffirmedServicesContentFilterServiceStatisticsNode-levelContentCategorizationEntry
    MAX-ACCESS  not-accessible
    STATUS      current
    DESCRIPTION ""
    ::= { affirmedServicesContentFilterServiceStatisticsNode-level 3 }

affirmedServicesContentFilterServiceStatisticsNode-levelContentCategorizationEntry OBJECT-TYPE
    SYNTAX      AffirmedServicesContentFilterServiceStatisticsNode-levelContentCategorizationEntry
    MAX-ACCESS  not-accessible
    STATUS      current
    DESCRIPTION ""
    INDEX { affirmedServicesContentFilterServiceStatisticsNode-levelContentCategorizationChassis, affirmedServicesContentFilterServiceStatisticsNode-levelContentCategorizationSlot }
        ::= { affirmedServicesContentFilterServiceStatisticsNode-levelContentCategorizationTable 1 }

AffirmedServicesContentFilterServiceStatisticsNode-levelContentCategorizationEntry ::=
    SEQUENCE {
        affirmedServicesContentFilterServiceStatisticsNode-levelContentCategorizationChassis Unsigned32,
        affirmedServicesContentFilterServiceStatisticsNode-levelContentCategorizationSlot Unsigned32,
        affirmedServicesContentFilterServiceStatisticsNode-levelContentCategorizationNumurlbasedlookups ConfdString,
        affirmedServicesContentFilterServiceStatisticsNode-levelContentCategorizationNumresponsebasedlookups ConfdString,
        affirmedServicesContentFilterServiceStatisticsNode-levelContentCategorizationNumcategoryabortion ConfdString,
        affirmedServicesContentFilterServiceStatisticsNode-levelContentCategorizationNumcategoryadvertising ConfdString,
        affirmedServicesContentFilterServiceStatisticsNode-levelContentCategorizationNumcategoryalcohol ConfdString,
        affirmedServicesContentFilterServiceStatisticsNode-levelContentCategorizationNumcategoryanonymizer ConfdString,
        affirmedServicesContentFilterServiceStatisticsNode-levelContentCategorizationNumcategoryartandmuseums ConfdString,
        affirmedServicesContentFilterServiceStatisticsNode-levelContentCategorizationNumcategoryartnudes ConfdString,
        affirmedServicesContentFilterServiceStatisticsNode-levelContentCategorizationNumcategoryautomatedwebapplication ConfdString,
        affirmedServicesContentFilterServiceStatisticsNode-levelContentCategorizationNumcategoryautomotive ConfdString,
        affirmedServicesContentFilterServiceStatisticsNode-levelContentCategorizationNumcategorybikini ConfdString,
        affirmedServicesContentFilterServiceStatisticsNode-levelContentCategorizationNumcategoryblogging ConfdString,
        affirmedServicesContentFilterServiceStatisticsNode-levelContentCategorizationNumcategorybusiness ConfdString,
        affirmedServicesContentFilterServiceStatisticsNode-levelContentCategorizationNumcategorycashgambling ConfdString,
        affirmedServicesContentFilterServiceStatisticsNode-levelContentCategorizationNumcategorychat ConfdString,
        affirmedServicesContentFilterServiceStatisticsNode-levelContentCategorizationNumcategorycontentdeliverynetwork ConfdString,
        affirmedServicesContentFilterServiceStatisticsNode-levelContentCategorizationNumcategorycriminalskills ConfdString,
        affirmedServicesContentFilterServiceStatisticsNode-levelContentCategorizationNumcategorycults ConfdString,
        affirmedServicesContentFilterServiceStatisticsNode-levelContentCategorizationNumcategorydrugs ConfdString,
        affirmedServicesContentFilterServiceStatisticsNode-levelContentCategorizationNumcategorydynamic ConfdString,
        affirmedServicesContentFilterServiceStatisticsNode-levelContentCategorizationNumcategoryeducational ConfdString,
        affirmedServicesContentFilterServiceStatisticsNode-levelContentCategorizationNumcategoryenergy ConfdString,
        affirmedServicesContentFilterServiceStatisticsNode-levelContentCategorizationNumcategoryenterprisewebmail ConfdString,
        affirmedServicesContentFilterServiceStatisticsNode-levelContentCategorizationNumcategoryentertainment ConfdString,
        affirmedServicesContentFilterServiceStatisticsNode-levelContentCategorizationNumcategoryfilesharing ConfdString,
        affirmedServicesContentFilterServiceStatisticsNode-levelContentCategorizationNumcategoryfinanceandinvesting ConfdString,
        affirmedServicesContentFilterServiceStatisticsNode-levelContentCategorizationNumcategoryfoodandrestaurants ConfdString,
        affirmedServicesContentFilterServiceStatisticsNode-levelContentCategorizationNumcategoryforumsandmessageboards ConfdString,
        affirmedServicesContentFilterServiceStatisticsNode-levelContentCategorizationNumcategoryfreewareandshareware ConfdString,
        affirmedServicesContentFilterServiceStatisticsNode-levelContentCategorizationNumcategorygambling ConfdString,
        affirmedServicesContentFilterServiceStatisticsNode-levelContentCategorizationNumcategorygaming ConfdString,
        affirmedServicesContentFilterServiceStatisticsNode-levelContentCategorizationNumcategoryglamour ConfdString,
        affirmedServicesContentFilterServiceStatisticsNode-levelContentCategorizationNumcategorygore ConfdString,
        affirmedServicesContentFilterServiceStatisticsNode-levelContentCategorizationNumcategorygovernment ConfdString,
        affirmedServicesContentFilterServiceStatisticsNode-levelContentCategorizationNumcategoryhacking ConfdString,
        affirmedServicesContentFilterServiceStatisticsNode-levelContentCategorizationNumcategoryhate ConfdString,
        affirmedServicesContentFilterServiceStatisticsNode-levelContentCategorizationNumcategoryhealth ConfdString,
        affirmedServicesContentFilterServiceStatisticsNode-levelContentCategorizationNumcategoryhobby ConfdString,
        affirmedServicesContentFilterServiceStatisticsNode-levelContentCategorizationNumcategoryhosting ConfdString,
        affirmedServicesContentFilterServiceStatisticsNode-levelContentCategorizationNumcategoryinternettelephony ConfdString,
        affirmedServicesContentFilterServiceStatisticsNode-levelContentCategorizationNumcategoryjobsearch ConfdString,
        affirmedServicesContentFilterServiceStatisticsNode-levelContentCategorizationNumcategorykids ConfdString,
        affirmedServicesContentFilterServiceStatisticsNode-levelContentCategorizationNumcategorylaw ConfdString,
        affirmedServicesContentFilterServiceStatisticsNode-levelContentCategorizationNumcategorylifestyles ConfdString,
        affirmedServicesContentFilterServiceStatisticsNode-levelContentCategorizationNumcategorymaturecontent ConfdString,
        affirmedServicesContentFilterServiceStatisticsNode-levelContentCategorizationNumcategorymilitary ConfdString,
        affirmedServicesContentFilterServiceStatisticsNode-levelContentCategorizationNumcategorymobileentertainment ConfdString,
        affirmedServicesContentFilterServiceStatisticsNode-levelContentCategorizationNumcategorymusic ConfdString,
        affirmedServicesContentFilterServiceStatisticsNode-levelContentCategorizationNumcategorynews ConfdString,
        affirmedServicesContentFilterServiceStatisticsNode-levelContentCategorizationNumcategorynonprofit ConfdString,
        affirmedServicesContentFilterServiceStatisticsNode-levelContentCategorizationNumcategoryobscene ConfdString,
        affirmedServicesContentFilterServiceStatisticsNode-levelContentCategorizationNumcategoryoccult ConfdString,
        affirmedServicesContentFilterServiceStatisticsNode-levelContentCategorizationNumcategoryonlinebackupandstorage ConfdString,
        affirmedServicesContentFilterServiceStatisticsNode-levelContentCategorizationNumcategorypeertopeer ConfdString,
        affirmedServicesContentFilterServiceStatisticsNode-levelContentCategorizationNumcategorypets ConfdString,
        affirmedServicesContentFilterServiceStatisticsNode-levelContentCategorizationNumcategoryphotography ConfdString,
        affirmedServicesContentFilterServiceStatisticsNode-levelContentCategorizationNumcategoryplaceholder ConfdString,
        affirmedServicesContentFilterServiceStatisticsNode-levelContentCategorizationNumcategoryplagiarism ConfdString,
        affirmedServicesContentFilterServiceStatisticsNode-levelContentCategorizationNumcategorypolitics ConfdString,
        affirmedServicesContentFilterServiceStatisticsNode-levelContentCategorizationNumcategorypornography ConfdString,
        affirmedServicesContentFilterServiceStatisticsNode-levelContentCategorizationNumcategoryportal ConfdString,
        affirmedServicesContentFilterServiceStatisticsNode-levelContentCategorizationNumcategorypersonalsanddating ConfdString,
        affirmedServicesContentFilterServiceStatisticsNode-levelContentCategorizationNumcategoryrealestate ConfdString,
        affirmedServicesContentFilterServiceStatisticsNode-levelContentCategorizationNumcategoryreference ConfdString,
        affirmedServicesContentFilterServiceStatisticsNode-levelContentCategorizationNumcategoryreligion ConfdString,
        affirmedServicesContentFilterServiceStatisticsNode-levelContentCategorizationNumcategoryremoteaccess ConfdString,
        affirmedServicesContentFilterServiceStatisticsNode-levelContentCategorizationNumcategoryscience ConfdString,
        affirmedServicesContentFilterServiceStatisticsNode-levelContentCategorizationNumcategorysearch ConfdString,
        affirmedServicesContentFilterServiceStatisticsNode-levelContentCategorizationNumcategoryselfharm ConfdString,
        affirmedServicesContentFilterServiceStatisticsNode-levelContentCategorizationNumcategorysexualeducation ConfdString,
        affirmedServicesContentFilterServiceStatisticsNode-levelContentCategorizationNumcategoryshopping ConfdString,
        affirmedServicesContentFilterServiceStatisticsNode-levelContentCategorizationNumcategorysports ConfdString,
        affirmedServicesContentFilterServiceStatisticsNode-levelContentCategorizationNumcategorystreamingmedia ConfdString,
        affirmedServicesContentFilterServiceStatisticsNode-levelContentCategorizationNumcategorysuicide ConfdString,
        affirmedServicesContentFilterServiceStatisticsNode-levelContentCategorizationNumcategorytechnologyandtelecommunication ConfdString,
        affirmedServicesContentFilterServiceStatisticsNode-levelContentCategorizationNumcategorytobacco ConfdString,
        affirmedServicesContentFilterServiceStatisticsNode-levelContentCategorizationNumcategorytravel ConfdString,
        affirmedServicesContentFilterServiceStatisticsNode-levelContentCategorizationNumcategoryviolence ConfdString,
        affirmedServicesContentFilterServiceStatisticsNode-levelContentCategorizationNumcategoryvirtualcommunity ConfdString,
        affirmedServicesContentFilterServiceStatisticsNode-levelContentCategorizationNumcategoryweapons ConfdString,
        affirmedServicesContentFilterServiceStatisticsNode-levelContentCategorizationNumcategorywebmail ConfdString,
        affirmedServicesContentFilterServiceStatisticsNode-levelContentCategorizationNumcategorywedding ConfdString,
        affirmedServicesContentFilterServiceStatisticsNode-levelContentCategorizationNumcategorywirelessbusiness ConfdString,
        affirmedServicesContentFilterServiceStatisticsNode-levelContentCategorizationNumcategorywirelesschatsms ConfdString,
        affirmedServicesContentFilterServiceStatisticsNode-levelContentCategorizationNumcategorywirelessdynamic ConfdString,
        affirmedServicesContentFilterServiceStatisticsNode-levelContentCategorizationNumcategorywirelessentertainment ConfdString,
        affirmedServicesContentFilterServiceStatisticsNode-levelContentCategorizationNumcategorywirelessfinance ConfdString,
        affirmedServicesContentFilterServiceStatisticsNode-levelContentCategorizationNumcategorywirelessgambling ConfdString,
        affirmedServicesContentFilterServiceStatisticsNode-levelContentCategorizationNumcategorywirelessnews ConfdString,
        affirmedServicesContentFilterServiceStatisticsNode-levelContentCategorizationNumcategorywirelesspersonalsanddating ConfdString,
        affirmedServicesContentFilterServiceStatisticsNode-levelContentCategorizationNumcategorywirelesspornography ConfdString,
        affirmedServicesContentFilterServiceStatisticsNode-levelContentCategorizationNumcategorywirelesssports ConfdString,
        affirmedServicesContentFilterServiceStatisticsNode-levelContentCategorizationNumcategorywirelesstravel ConfdString,
        affirmedServicesContentFilterServiceStatisticsNode-levelContentCategorizationNumcategoryunknown ConfdString,
        affirmedServicesContentFilterServiceStatisticsNode-levelContentCategorizationNumcategorymalware ConfdString,
        affirmedServicesContentFilterServiceStatisticsNode-levelContentCategorizationNumcategoryphishing ConfdString,
        affirmedServicesContentFilterServiceStatisticsNode-levelContentCategorizationNumcategoryiwf ConfdString,
        affirmedServicesContentFilterServiceStatisticsNode-levelContentCategorizationNumcategorynocat ConfdString,
        affirmedServicesContentFilterServiceStatisticsNode-levelContentCategorizationNumcategoryother ConfdString,
        affirmedServicesContentFilterServiceStatisticsNode-levelContentCategorizationNumcategoryalcoholkids ConfdString,
        affirmedServicesContentFilterServiceStatisticsNode-levelContentCategorizationNumcategorytobaccokids ConfdString,
        affirmedServicesContentFilterServiceStatisticsNode-levelContentCategorizationNumcategorycyberbullying ConfdString,
        affirmedServicesContentFilterServiceStatisticsNode-levelContentCategorizationNumhttpsrequestlookups ConfdString,
        affirmedServicesContentFilterServiceStatisticsNode-levelContentCategorizationNumlookupfailure ConfdString,
        affirmedServicesContentFilterServiceStatisticsNode-levelContentCategorizationNumquicrequestlookups ConfdString,
        affirmedServicesContentFilterServiceStatisticsNode-levelContentCategorizationNumcategorybbfcwhitelist ConfdString,
        affirmedServicesContentFilterServiceStatisticsNode-levelContentCategorizationNumcategorybbfcblacklist ConfdString,
        affirmedServicesContentFilterServiceStatisticsNode-levelContentCategorizationNumcategorycannabidiol ConfdString,
        affirmedServicesContentFilterServiceStatisticsNode-levelContentCategorizationNumcategorycloudinfrastructure ConfdString,
        affirmedServicesContentFilterServiceStatisticsNode-levelContentCategorizationNumcategoryfireworks ConfdString,
        affirmedServicesContentFilterServiceStatisticsNode-levelContentCategorizationNumcategorylingerie ConfdString,
        affirmedServicesContentFilterServiceStatisticsNode-levelContentCategorizationNumcategorysexualadvice ConfdString,
        affirmedServicesContentFilterServiceStatisticsNode-levelContentCategorizationNumcategorytracking ConfdString,
        affirmedServicesContentFilterServiceStatisticsNode-levelContentCategorizationNumcategoryukdeablacklist ConfdString
    }

affirmedServicesContentFilterServiceStatisticsNode-levelContentCategorizationChassis OBJECT-TYPE
    SYNTAX      Unsigned32
    MAX-ACCESS  not-accessible
    STATUS      current
    DESCRIPTION "chassis ID"
    ::= { affirmedServicesContentFilterServiceStatisticsNode-levelContentCategorizationEntry 1 }

affirmedServicesContentFilterServiceStatisticsNode-levelContentCategorizationSlot OBJECT-TYPE
    SYNTAX      Unsigned32
    MAX-ACCESS  not-accessible
    STATUS      current
    DESCRIPTION "slot number"
    ::= { affirmedServicesContentFilterServiceStatisticsNode-levelContentCategorizationEntry 2 }

affirmedServicesContentFilterServiceStatisticsNode-levelContentCategorizationNumurlbasedlookups OBJECT-TYPE
    SYNTAX      ConfdString
    MAX-ACCESS  read-only
    STATUS      current
    DESCRIPTION "Total number of HTTP request Lookups"
    ::= { affirmedServicesContentFilterServiceStatisticsNode-levelContentCategorizationEntry 3 }

affirmedServicesContentFilterServiceStatisticsNode-levelContentCategorizationNumresponsebasedlookups OBJECT-TYPE
    SYNTAX      ConfdString
    MAX-ACCESS  read-only
    STATUS      current
    DESCRIPTION "Total number of HTTP Response-based Lookups"
    ::= { affirmedServicesContentFilterServiceStatisticsNode-levelContentCategorizationEntry 4 }

affirmedServicesContentFilterServiceStatisticsNode-levelContentCategorizationNumcategoryabortion OBJECT-TYPE
    SYNTAX      ConfdString
    MAX-ACCESS  read-only
    STATUS      current
    DESCRIPTION "Total number of requests categorized as Abortion Online Category"
    ::= { affirmedServicesContentFilterServiceStatisticsNode-levelContentCategorizationEntry 5 }

affirmedServicesContentFilterServiceStatisticsNode-levelContentCategorizationNumcategoryadvertising OBJECT-TYPE
    SYNTAX      ConfdString
    MAX-ACCESS  read-only
    STATUS      current
    DESCRIPTION "Total number of requests categorized as Advertising Online Category"
    ::= { affirmedServicesContentFilterServiceStatisticsNode-levelContentCategorizationEntry 6 }

affirmedServicesContentFilterServiceStatisticsNode-levelContentCategorizationNumcategoryalcohol OBJECT-TYPE
    SYNTAX      ConfdString
    MAX-ACCESS  read-only
    STATUS      current
    DESCRIPTION "Total number of requests categorized as Alcohol Online Category"
    ::= { affirmedServicesContentFilterServiceStatisticsNode-levelContentCategorizationEntry 7 }

affirmedServicesContentFilterServiceStatisticsNode-levelContentCategorizationNumcategoryanonymizer OBJECT-TYPE
    SYNTAX      ConfdString
    MAX-ACCESS  read-only
    STATUS      current
    DESCRIPTION "Total number of requests categorized as Anonymizer Online Category"
    ::= { affirmedServicesContentFilterServiceStatisticsNode-levelContentCategorizationEntry 8 }

affirmedServicesContentFilterServiceStatisticsNode-levelContentCategorizationNumcategoryartandmuseums OBJECT-TYPE
    SYNTAX      ConfdString
    MAX-ACCESS  read-only
    STATUS      current
    DESCRIPTION "Total number of requests categorized as Art And Museums Online Category"
    ::= { affirmedServicesContentFilterServiceStatisticsNode-levelContentCategorizationEntry 9 }

affirmedServicesContentFilterServiceStatisticsNode-levelContentCategorizationNumcategoryartnudes OBJECT-TYPE
    SYNTAX      ConfdString
    MAX-ACCESS  read-only
    STATUS      current
    DESCRIPTION "Total number of requests categorized as Art Nudes Online Category"
    ::= { affirmedServicesContentFilterServiceStatisticsNode-levelContentCategorizationEntry 10 }

affirmedServicesContentFilterServiceStatisticsNode-levelContentCategorizationNumcategoryautomatedwebapplication OBJECT-TYPE
    SYNTAX      ConfdString
    MAX-ACCESS  read-only
    STATUS      current
    DESCRIPTION "Total number of requests categorized as Automated Web Application Online Category"
    ::= { affirmedServicesContentFilterServiceStatisticsNode-levelContentCategorizationEntry 11 }

affirmedServicesContentFilterServiceStatisticsNode-levelContentCategorizationNumcategoryautomotive OBJECT-TYPE
    SYNTAX      ConfdString
    MAX-ACCESS  read-only
    STATUS      current
    DESCRIPTION "Total number of requests categorized as Automotive Online Category"
    ::= { affirmedServicesContentFilterServiceStatisticsNode-levelContentCategorizationEntry 12 }

affirmedServicesContentFilterServiceStatisticsNode-levelContentCategorizationNumcategorybikini OBJECT-TYPE
    SYNTAX      ConfdString
    MAX-ACCESS  read-only
    STATUS      current
    DESCRIPTION "Total number of requests categorized as Bikini Online Category"
    ::= { affirmedServicesContentFilterServiceStatisticsNode-levelContentCategorizationEntry 13 }

affirmedServicesContentFilterServiceStatisticsNode-levelContentCategorizationNumcategoryblogging OBJECT-TYPE
    SYNTAX      ConfdString
    MAX-ACCESS  read-only
    STATUS      current
    DESCRIPTION "Total number of requests categorized as Blogging Online Category"
    ::= { affirmedServicesContentFilterServiceStatisticsNode-levelContentCategorizationEntry 14 }

affirmedServicesContentFilterServiceStatisticsNode-levelContentCategorizationNumcategorybusiness OBJECT-TYPE
    SYNTAX      ConfdString
    MAX-ACCESS  read-only
    STATUS      current
    DESCRIPTION "Total number of requests categorized as Business Online Category"
    ::= { affirmedServicesContentFilterServiceStatisticsNode-levelContentCategorizationEntry 15 }

affirmedServicesContentFilterServiceStatisticsNode-levelContentCategorizationNumcategorycashgambling OBJECT-TYPE
    SYNTAX      ConfdString
    MAX-ACCESS  read-only
    STATUS      current
    DESCRIPTION "Total number of requests categorized as Cash Gambling Online Category"
    ::= { affirmedServicesContentFilterServiceStatisticsNode-levelContentCategorizationEntry 16 }

affirmedServicesContentFilterServiceStatisticsNode-levelContentCategorizationNumcategorychat OBJECT-TYPE
    SYNTAX      ConfdString
    MAX-ACCESS  read-only
    STATUS      current
    DESCRIPTION "Total number of requests categorized as Chat Online Category"
    ::= { affirmedServicesContentFilterServiceStatisticsNode-levelContentCategorizationEntry 17 }

affirmedServicesContentFilterServiceStatisticsNode-levelContentCategorizationNumcategorycontentdeliverynetwork OBJECT-TYPE
    SYNTAX      ConfdString
    MAX-ACCESS  read-only
    STATUS      current
    DESCRIPTION "Total number of requests categorized as Content Delivery Network Online Category"
    ::= { affirmedServicesContentFilterServiceStatisticsNode-levelContentCategorizationEntry 18 }

affirmedServicesContentFilterServiceStatisticsNode-levelContentCategorizationNumcategorycriminalskills OBJECT-TYPE
    SYNTAX      ConfdString
    MAX-ACCESS  read-only
    STATUS      current
    DESCRIPTION "Total number of requests categorized as Criminal Skills Online Category"
    ::= { affirmedServicesContentFilterServiceStatisticsNode-levelContentCategorizationEntry 19 }

affirmedServicesContentFilterServiceStatisticsNode-levelContentCategorizationNumcategorycults OBJECT-TYPE
    SYNTAX      ConfdString
    MAX-ACCESS  read-only
    STATUS      current
    DESCRIPTION "Total number of requests categorized as Cults Online Category"
    ::= { affirmedServicesContentFilterServiceStatisticsNode-levelContentCategorizationEntry 20 }

affirmedServicesContentFilterServiceStatisticsNode-levelContentCategorizationNumcategorydrugs OBJECT-TYPE
    SYNTAX      ConfdString
    MAX-ACCESS  read-only
    STATUS      current
    DESCRIPTION "Total number of requests categorized as Drugs Online Category"
    ::= { affirmedServicesContentFilterServiceStatisticsNode-levelContentCategorizationEntry 21 }

affirmedServicesContentFilterServiceStatisticsNode-levelContentCategorizationNumcategorydynamic OBJECT-TYPE
    SYNTAX      ConfdString
    MAX-ACCESS  read-only
    STATUS      current
    DESCRIPTION "Total number of requests categorized as Dynamic Online Category"
    ::= { affirmedServicesContentFilterServiceStatisticsNode-levelContentCategorizationEntry 22 }

affirmedServicesContentFilterServiceStatisticsNode-levelContentCategorizationNumcategoryeducational OBJECT-TYPE
    SYNTAX      ConfdString
    MAX-ACCESS  read-only
    STATUS      current
    DESCRIPTION "Total number of requests categorized as Educational Online Category"
    ::= { affirmedServicesContentFilterServiceStatisticsNode-levelContentCategorizationEntry 23 }

affirmedServicesContentFilterServiceStatisticsNode-levelContentCategorizationNumcategoryenergy OBJECT-TYPE
    SYNTAX      ConfdString
    MAX-ACCESS  read-only
    STATUS      current
    DESCRIPTION "Total number of requests categorized as Energy Online Category"
    ::= { affirmedServicesContentFilterServiceStatisticsNode-levelContentCategorizationEntry 24 }

affirmedServicesContentFilterServiceStatisticsNode-levelContentCategorizationNumcategoryenterprisewebmail OBJECT-TYPE
    SYNTAX      ConfdString
    MAX-ACCESS  read-only
    STATUS      current
    DESCRIPTION "Total number of requests categorized as Enterprise Webmail Online Category"
    ::= { affirmedServicesContentFilterServiceStatisticsNode-levelContentCategorizationEntry 25 }

affirmedServicesContentFilterServiceStatisticsNode-levelContentCategorizationNumcategoryentertainment OBJECT-TYPE
    SYNTAX      ConfdString
    MAX-ACCESS  read-only
    STATUS      current
    DESCRIPTION "Total number of requests categorized as Entertainment Online Category"
    ::= { affirmedServicesContentFilterServiceStatisticsNode-levelContentCategorizationEntry 26 }

affirmedServicesContentFilterServiceStatisticsNode-levelContentCategorizationNumcategoryfilesharing OBJECT-TYPE
    SYNTAX      ConfdString
    MAX-ACCESS  read-only
    STATUS      current
    DESCRIPTION "Total number of requests categorized as Filesharing Online Category"
    ::= { affirmedServicesContentFilterServiceStatisticsNode-levelContentCategorizationEntry 27 }

affirmedServicesContentFilterServiceStatisticsNode-levelContentCategorizationNumcategoryfinanceandinvesting OBJECT-TYPE
    SYNTAX      ConfdString
    MAX-ACCESS  read-only
    STATUS      current
    DESCRIPTION "Total number of requests categorized as Finance And Investing Online Category"
    ::= { affirmedServicesContentFilterServiceStatisticsNode-levelContentCategorizationEntry 28 }

affirmedServicesContentFilterServiceStatisticsNode-levelContentCategorizationNumcategoryfoodandrestaurants OBJECT-TYPE
    SYNTAX      ConfdString
    MAX-ACCESS  read-only
    STATUS      current
    DESCRIPTION "Total number of requests categorized as Food And Restaurants Online Category"
    ::= { affirmedServicesContentFilterServiceStatisticsNode-levelContentCategorizationEntry 29 }

affirmedServicesContentFilterServiceStatisticsNode-levelContentCategorizationNumcategoryforumsandmessageboards OBJECT-TYPE
    SYNTAX      ConfdString
    MAX-ACCESS  read-only
    STATUS      current
    DESCRIPTION "Total number of requests categorized as Forums And Messageboards Online Category"
    ::= { affirmedServicesContentFilterServiceStatisticsNode-levelContentCategorizationEntry 30 }

affirmedServicesContentFilterServiceStatisticsNode-levelContentCategorizationNumcategoryfreewareandshareware OBJECT-TYPE
    SYNTAX      ConfdString
    MAX-ACCESS  read-only
    STATUS      current
    DESCRIPTION "Total number of requests categorized as Freeware And Shareware Online Category"
    ::= { affirmedServicesContentFilterServiceStatisticsNode-levelContentCategorizationEntry 31 }

affirmedServicesContentFilterServiceStatisticsNode-levelContentCategorizationNumcategorygambling OBJECT-TYPE
    SYNTAX      ConfdString
    MAX-ACCESS  read-only
    STATUS      current
    DESCRIPTION "Total number of requests categorized as Gambling Online Category"
    ::= { affirmedServicesContentFilterServiceStatisticsNode-levelContentCategorizationEntry 32 }

affirmedServicesContentFilterServiceStatisticsNode-levelContentCategorizationNumcategorygaming OBJECT-TYPE
    SYNTAX      ConfdString
    MAX-ACCESS  read-only
    STATUS      current
    DESCRIPTION "Total number of requests categorized as Gaming Online Category"
    ::= { affirmedServicesContentFilterServiceStatisticsNode-levelContentCategorizationEntry 33 }

affirmedServicesContentFilterServiceStatisticsNode-levelContentCategorizationNumcategoryglamour OBJECT-TYPE
    SYNTAX      ConfdString
    MAX-ACCESS  read-only
    STATUS      current
    DESCRIPTION "Total number of requests categorized as Glamour Online Category"
    ::= { affirmedServicesContentFilterServiceStatisticsNode-levelContentCategorizationEntry 34 }

affirmedServicesContentFilterServiceStatisticsNode-levelContentCategorizationNumcategorygore OBJECT-TYPE
    SYNTAX      ConfdString
    MAX-ACCESS  read-only
    STATUS      current
    DESCRIPTION "Total number of requests categorized as Gore Online Category"
    ::= { affirmedServicesContentFilterServiceStatisticsNode-levelContentCategorizationEntry 35 }

affirmedServicesContentFilterServiceStatisticsNode-levelContentCategorizationNumcategorygovernment OBJECT-TYPE
    SYNTAX      ConfdString
    MAX-ACCESS  read-only
    STATUS      current
    DESCRIPTION "Total number of requests categorized as Government Online Category"
    ::= { affirmedServicesContentFilterServiceStatisticsNode-levelContentCategorizationEntry 36 }

affirmedServicesContentFilterServiceStatisticsNode-levelContentCategorizationNumcategoryhacking OBJECT-TYPE
    SYNTAX      ConfdString
    MAX-ACCESS  read-only
    STATUS      current
    DESCRIPTION "Total number of requests categorized as Hacking Online Category"
    ::= { affirmedServicesContentFilterServiceStatisticsNode-levelContentCategorizationEntry 37 }

affirmedServicesContentFilterServiceStatisticsNode-levelContentCategorizationNumcategoryhate OBJECT-TYPE
    SYNTAX      ConfdString
    MAX-ACCESS  read-only
    STATUS      current
    DESCRIPTION "Total number of requests categorized as Hate Online Category"
    ::= { affirmedServicesContentFilterServiceStatisticsNode-levelContentCategorizationEntry 38 }

affirmedServicesContentFilterServiceStatisticsNode-levelContentCategorizationNumcategoryhealth OBJECT-TYPE
    SYNTAX      ConfdString
    MAX-ACCESS  read-only
    STATUS      current
    DESCRIPTION "Total number of requests categorized as Health Online Category"
    ::= { affirmedServicesContentFilterServiceStatisticsNode-levelContentCategorizationEntry 39 }

affirmedServicesContentFilterServiceStatisticsNode-levelContentCategorizationNumcategoryhobby OBJECT-TYPE
    SYNTAX      ConfdString
    MAX-ACCESS  read-only
    STATUS      current
    DESCRIPTION "Total number of requests categorized as Hobby Online Category"
    ::= { affirmedServicesContentFilterServiceStatisticsNode-levelContentCategorizationEntry 40 }

affirmedServicesContentFilterServiceStatisticsNode-levelContentCategorizationNumcategoryhosting OBJECT-TYPE
    SYNTAX      ConfdString
    MAX-ACCESS  read-only
    STATUS      current
    DESCRIPTION "Total number of requests categorized as Hosting Online Category"
    ::= { affirmedServicesContentFilterServiceStatisticsNode-levelContentCategorizationEntry 41 }

affirmedServicesContentFilterServiceStatisticsNode-levelContentCategorizationNumcategoryinternettelephony OBJECT-TYPE
    SYNTAX      ConfdString
    MAX-ACCESS  read-only
    STATUS      current
    DESCRIPTION "Total number of requests categorized as Internet Telephony Online Category"
    ::= { affirmedServicesContentFilterServiceStatisticsNode-levelContentCategorizationEntry 42 }

affirmedServicesContentFilterServiceStatisticsNode-levelContentCategorizationNumcategoryjobsearch OBJECT-TYPE
    SYNTAX      ConfdString
    MAX-ACCESS  read-only
    STATUS      current
    DESCRIPTION "Total number of requests categorized as Job Search Online Category"
    ::= { affirmedServicesContentFilterServiceStatisticsNode-levelContentCategorizationEntry 43 }

affirmedServicesContentFilterServiceStatisticsNode-levelContentCategorizationNumcategorykids OBJECT-TYPE
    SYNTAX      ConfdString
    MAX-ACCESS  read-only
    STATUS      current
    DESCRIPTION "Total number of requests categorized as Kids Online Category"
    ::= { affirmedServicesContentFilterServiceStatisticsNode-levelContentCategorizationEntry 44 }

affirmedServicesContentFilterServiceStatisticsNode-levelContentCategorizationNumcategorylaw OBJECT-TYPE
    SYNTAX      ConfdString
    MAX-ACCESS  read-only
    STATUS      current
    DESCRIPTION "Total number of requests categorized as Law Online Category"
    ::= { affirmedServicesContentFilterServiceStatisticsNode-levelContentCategorizationEntry 45 }

affirmedServicesContentFilterServiceStatisticsNode-levelContentCategorizationNumcategorylifestyles OBJECT-TYPE
    SYNTAX      ConfdString
    MAX-ACCESS  read-only
    STATUS      current
    DESCRIPTION "Total number of requests categorized as Lifestyles Online Category"
    ::= { affirmedServicesContentFilterServiceStatisticsNode-levelContentCategorizationEntry 46 }

affirmedServicesContentFilterServiceStatisticsNode-levelContentCategorizationNumcategorymaturecontent OBJECT-TYPE
    SYNTAX      ConfdString
    MAX-ACCESS  read-only
    STATUS      current
    DESCRIPTION "Total number of requests categorized as Mature Content Online Category"
    ::= { affirmedServicesContentFilterServiceStatisticsNode-levelContentCategorizationEntry 47 }

affirmedServicesContentFilterServiceStatisticsNode-levelContentCategorizationNumcategorymilitary OBJECT-TYPE
    SYNTAX      ConfdString
    MAX-ACCESS  read-only
    STATUS      current
    DESCRIPTION "Total number of requests categorized as Military Online Category"
    ::= { affirmedServicesContentFilterServiceStatisticsNode-levelContentCategorizationEntry 48 }

affirmedServicesContentFilterServiceStatisticsNode-levelContentCategorizationNumcategorymobileentertainment OBJECT-TYPE
    SYNTAX      ConfdString
    MAX-ACCESS  read-only
    STATUS      current
    DESCRIPTION "Total number of requests categorized as Mobile Entertainment Online Category"
    ::= { affirmedServicesContentFilterServiceStatisticsNode-levelContentCategorizationEntry 49 }

affirmedServicesContentFilterServiceStatisticsNode-levelContentCategorizationNumcategorymusic OBJECT-TYPE
    SYNTAX      ConfdString
    MAX-ACCESS  read-only
    STATUS      current
    DESCRIPTION "Total number of requests categorized as Music Online Category"
    ::= { affirmedServicesContentFilterServiceStatisticsNode-levelContentCategorizationEntry 50 }

affirmedServicesContentFilterServiceStatisticsNode-levelContentCategorizationNumcategorynews OBJECT-TYPE
    SYNTAX      ConfdString
    MAX-ACCESS  read-only
    STATUS      current
    DESCRIPTION "Total number of requests categorized as News Online Category"
    ::= { affirmedServicesContentFilterServiceStatisticsNode-levelContentCategorizationEntry 51 }

affirmedServicesContentFilterServiceStatisticsNode-levelContentCategorizationNumcategorynonprofit OBJECT-TYPE
    SYNTAX      ConfdString
    MAX-ACCESS  read-only
    STATUS      current
    DESCRIPTION "Total number of requests categorized as Non Profit Online Category"
    ::= { affirmedServicesContentFilterServiceStatisticsNode-levelContentCategorizationEntry 52 }

affirmedServicesContentFilterServiceStatisticsNode-levelContentCategorizationNumcategoryobscene OBJECT-TYPE
    SYNTAX      ConfdString
    MAX-ACCESS  read-only
    STATUS      current
    DESCRIPTION "Total number of requests categorized as Obscene Online Category"
    ::= { affirmedServicesContentFilterServiceStatisticsNode-levelContentCategorizationEntry 53 }

affirmedServicesContentFilterServiceStatisticsNode-levelContentCategorizationNumcategoryoccult OBJECT-TYPE
    SYNTAX      ConfdString
    MAX-ACCESS  read-only
    STATUS      current
    DESCRIPTION "Total number of requests categorized as Occult Online Category"
    ::= { affirmedServicesContentFilterServiceStatisticsNode-levelContentCategorizationEntry 54 }

affirmedServicesContentFilterServiceStatisticsNode-levelContentCategorizationNumcategoryonlinebackupandstorage OBJECT-TYPE
    SYNTAX      ConfdString
    MAX-ACCESS  read-only
    STATUS      current
    DESCRIPTION "Total number of requests categorized as Online Backup And Storage Online Category"
    ::= { affirmedServicesContentFilterServiceStatisticsNode-levelContentCategorizationEntry 55 }

affirmedServicesContentFilterServiceStatisticsNode-levelContentCategorizationNumcategorypeertopeer OBJECT-TYPE
    SYNTAX      ConfdString
    MAX-ACCESS  read-only
    STATUS      current
    DESCRIPTION "Total number of requests categorized as PeerToPeer Online Category"
    ::= { affirmedServicesContentFilterServiceStatisticsNode-levelContentCategorizationEntry 56 }

affirmedServicesContentFilterServiceStatisticsNode-levelContentCategorizationNumcategorypets OBJECT-TYPE
    SYNTAX      ConfdString
    MAX-ACCESS  read-only
    STATUS      current
    DESCRIPTION "Total number of requests categorized as Pets Online Category"
    ::= { affirmedServicesContentFilterServiceStatisticsNode-levelContentCategorizationEntry 57 }

affirmedServicesContentFilterServiceStatisticsNode-levelContentCategorizationNumcategoryphotography OBJECT-TYPE
    SYNTAX      ConfdString
    MAX-ACCESS  read-only
    STATUS      current
    DESCRIPTION "Total number of requests categorized as Photography Online Category"
    ::= { affirmedServicesContentFilterServiceStatisticsNode-levelContentCategorizationEntry 58 }

affirmedServicesContentFilterServiceStatisticsNode-levelContentCategorizationNumcategoryplaceholder OBJECT-TYPE
    SYNTAX      ConfdString
    MAX-ACCESS  read-only
    STATUS      current
    DESCRIPTION "Total number of requests categorized as Placeholder Online Category"
    ::= { affirmedServicesContentFilterServiceStatisticsNode-levelContentCategorizationEntry 59 }

affirmedServicesContentFilterServiceStatisticsNode-levelContentCategorizationNumcategoryplagiarism OBJECT-TYPE
    SYNTAX      ConfdString
    MAX-ACCESS  read-only
    STATUS      current
    DESCRIPTION "Total number of requests categorized as Plagiarism Online Category"
    ::= { affirmedServicesContentFilterServiceStatisticsNode-levelContentCategorizationEntry 60 }

affirmedServicesContentFilterServiceStatisticsNode-levelContentCategorizationNumcategorypolitics OBJECT-TYPE
    SYNTAX      ConfdString
    MAX-ACCESS  read-only
    STATUS      current
    DESCRIPTION "Total number of requests categorized as Politics Online Category"
    ::= { affirmedServicesContentFilterServiceStatisticsNode-levelContentCategorizationEntry 61 }

affirmedServicesContentFilterServiceStatisticsNode-levelContentCategorizationNumcategorypornography OBJECT-TYPE
    SYNTAX      ConfdString
    MAX-ACCESS  read-only
    STATUS      current
    DESCRIPTION "Total number of requests categorized as Pornography Online Category"
    ::= { affirmedServicesContentFilterServiceStatisticsNode-levelContentCategorizationEntry 62 }

affirmedServicesContentFilterServiceStatisticsNode-levelContentCategorizationNumcategoryportal OBJECT-TYPE
    SYNTAX      ConfdString
    MAX-ACCESS  read-only
    STATUS      current
    DESCRIPTION "Total number of requests categorized as Portal Online Category"
    ::= { affirmedServicesContentFilterServiceStatisticsNode-levelContentCategorizationEntry 63 }

affirmedServicesContentFilterServiceStatisticsNode-levelContentCategorizationNumcategorypersonalsanddating OBJECT-TYPE
    SYNTAX      ConfdString
    MAX-ACCESS  read-only
    STATUS      current
    DESCRIPTION "Total number of requests categorized as Personals And Dating Online Category"
    ::= { affirmedServicesContentFilterServiceStatisticsNode-levelContentCategorizationEntry 64 }

affirmedServicesContentFilterServiceStatisticsNode-levelContentCategorizationNumcategoryrealestate OBJECT-TYPE
    SYNTAX      ConfdString
    MAX-ACCESS  read-only
    STATUS      current
    DESCRIPTION "Total number of requests categorized as Real Estate Online Category"
    ::= { affirmedServicesContentFilterServiceStatisticsNode-levelContentCategorizationEntry 65 }

affirmedServicesContentFilterServiceStatisticsNode-levelContentCategorizationNumcategoryreference OBJECT-TYPE
    SYNTAX      ConfdString
    MAX-ACCESS  read-only
    STATUS      current
    DESCRIPTION "Total number of requests categorized as Reference Online Category"
    ::= { affirmedServicesContentFilterServiceStatisticsNode-levelContentCategorizationEntry 66 }

affirmedServicesContentFilterServiceStatisticsNode-levelContentCategorizationNumcategoryreligion OBJECT-TYPE
    SYNTAX      ConfdString
    MAX-ACCESS  read-only
    STATUS      current
    DESCRIPTION "Total number of requests categorized as Religion Online Category"
    ::= { affirmedServicesContentFilterServiceStatisticsNode-levelContentCategorizationEntry 67 }

affirmedServicesContentFilterServiceStatisticsNode-levelContentCategorizationNumcategoryremoteaccess OBJECT-TYPE
    SYNTAX      ConfdString
    MAX-ACCESS  read-only
    STATUS      current
    DESCRIPTION "Total number of requests categorized as Remote Access Online Category"
    ::= { affirmedServicesContentFilterServiceStatisticsNode-levelContentCategorizationEntry 68 }

affirmedServicesContentFilterServiceStatisticsNode-levelContentCategorizationNumcategoryscience OBJECT-TYPE
    SYNTAX      ConfdString
    MAX-ACCESS  read-only
    STATUS      current
    DESCRIPTION "Total number of requests categorized as Science Online Category"
    ::= { affirmedServicesContentFilterServiceStatisticsNode-levelContentCategorizationEntry 69 }

affirmedServicesContentFilterServiceStatisticsNode-levelContentCategorizationNumcategorysearch OBJECT-TYPE
    SYNTAX      ConfdString
    MAX-ACCESS  read-only
    STATUS      current
    DESCRIPTION "Total number of requests categorized as Search Online Category"
    ::= { affirmedServicesContentFilterServiceStatisticsNode-levelContentCategorizationEntry 70 }

affirmedServicesContentFilterServiceStatisticsNode-levelContentCategorizationNumcategoryselfharm OBJECT-TYPE
    SYNTAX      ConfdString
    MAX-ACCESS  read-only
    STATUS      current
    DESCRIPTION "Total number of requests categorized as Self Harm Online Category"
    ::= { affirmedServicesContentFilterServiceStatisticsNode-levelContentCategorizationEntry 71 }

affirmedServicesContentFilterServiceStatisticsNode-levelContentCategorizationNumcategorysexualeducation OBJECT-TYPE
    SYNTAX      ConfdString
    MAX-ACCESS  read-only
    STATUS      current
    DESCRIPTION "Total number of requests categorized as Sexual Education Online Category"
    ::= { affirmedServicesContentFilterServiceStatisticsNode-levelContentCategorizationEntry 72 }

affirmedServicesContentFilterServiceStatisticsNode-levelContentCategorizationNumcategoryshopping OBJECT-TYPE
    SYNTAX      ConfdString
    MAX-ACCESS  read-only
    STATUS      current
    DESCRIPTION "Total number of requests categorized as Shopping Online Category"
    ::= { affirmedServicesContentFilterServiceStatisticsNode-levelContentCategorizationEntry 73 }

affirmedServicesContentFilterServiceStatisticsNode-levelContentCategorizationNumcategorysports OBJECT-TYPE
    SYNTAX      ConfdString
    MAX-ACCESS  read-only
    STATUS      current
    DESCRIPTION "Total number of requests categorized as Sports Online Category"
    ::= { affirmedServicesContentFilterServiceStatisticsNode-levelContentCategorizationEntry 74 }

affirmedServicesContentFilterServiceStatisticsNode-levelContentCategorizationNumcategorystreamingmedia OBJECT-TYPE
    SYNTAX      ConfdString
    MAX-ACCESS  read-only
    STATUS      current
    DESCRIPTION "Total number of requests categorized as Streaming Media Online Category"
    ::= { affirmedServicesContentFilterServiceStatisticsNode-levelContentCategorizationEntry 75 }

affirmedServicesContentFilterServiceStatisticsNode-levelContentCategorizationNumcategorysuicide OBJECT-TYPE
    SYNTAX      ConfdString
    MAX-ACCESS  read-only
    STATUS      current
    DESCRIPTION "Total number of requests categorized as Suicide Online Category"
    ::= { affirmedServicesContentFilterServiceStatisticsNode-levelContentCategorizationEntry 76 }

affirmedServicesContentFilterServiceStatisticsNode-levelContentCategorizationNumcategorytechnologyandtelecommunication OBJECT-TYPE
    SYNTAX      ConfdString
    MAX-ACCESS  read-only
    STATUS      current
    DESCRIPTION "Total number of requests categorized as Technology And Telecommunication Online Category"
    ::= { affirmedServicesContentFilterServiceStatisticsNode-levelContentCategorizationEntry 77 }

affirmedServicesContentFilterServiceStatisticsNode-levelContentCategorizationNumcategorytobacco OBJECT-TYPE
    SYNTAX      ConfdString
    MAX-ACCESS  read-only
    STATUS      current
    DESCRIPTION "Total number of requests categorized as Tobacco Online Category"
    ::= { affirmedServicesContentFilterServiceStatisticsNode-levelContentCategorizationEntry 78 }

affirmedServicesContentFilterServiceStatisticsNode-levelContentCategorizationNumcategorytravel OBJECT-TYPE
    SYNTAX      ConfdString
    MAX-ACCESS  read-only
    STATUS      current
    DESCRIPTION "Total number of requests categorized as Travel Online Category"
    ::= { affirmedServicesContentFilterServiceStatisticsNode-levelContentCategorizationEntry 79 }

affirmedServicesContentFilterServiceStatisticsNode-levelContentCategorizationNumcategoryviolence OBJECT-TYPE
    SYNTAX      ConfdString
    MAX-ACCESS  read-only
    STATUS      current
    DESCRIPTION "Total number of requests categorized as Violence Online Category"
    ::= { affirmedServicesContentFilterServiceStatisticsNode-levelContentCategorizationEntry 80 }

affirmedServicesContentFilterServiceStatisticsNode-levelContentCategorizationNumcategoryvirtualcommunity OBJECT-TYPE
    SYNTAX      ConfdString
    MAX-ACCESS  read-only
    STATUS      current
    DESCRIPTION "Total number of requests categorized as Virtual Community Online Category"
    ::= { affirmedServicesContentFilterServiceStatisticsNode-levelContentCategorizationEntry 81 }

affirmedServicesContentFilterServiceStatisticsNode-levelContentCategorizationNumcategoryweapons OBJECT-TYPE
    SYNTAX      ConfdString
    MAX-ACCESS  read-only
    STATUS      current
    DESCRIPTION "Total number of requests categorized as Weapons Online Category"
    ::= { affirmedServicesContentFilterServiceStatisticsNode-levelContentCategorizationEntry 82 }

affirmedServicesContentFilterServiceStatisticsNode-levelContentCategorizationNumcategorywebmail OBJECT-TYPE
    SYNTAX      ConfdString
    MAX-ACCESS  read-only
    STATUS      current
    DESCRIPTION "Total number of requests categorized as Webmail Online Category"
    ::= { affirmedServicesContentFilterServiceStatisticsNode-levelContentCategorizationEntry 83 }

affirmedServicesContentFilterServiceStatisticsNode-levelContentCategorizationNumcategorywedding OBJECT-TYPE
    SYNTAX      ConfdString
    MAX-ACCESS  read-only
    STATUS      current
    DESCRIPTION "Total number of requests categorized as Wedding Online Category"
    ::= { affirmedServicesContentFilterServiceStatisticsNode-levelContentCategorizationEntry 84 }

affirmedServicesContentFilterServiceStatisticsNode-levelContentCategorizationNumcategorywirelessbusiness OBJECT-TYPE
    SYNTAX      ConfdString
    MAX-ACCESS  read-only
    STATUS      current
    DESCRIPTION "Total number of requests categorized as Wireless Business Online Category"
    ::= { affirmedServicesContentFilterServiceStatisticsNode-levelContentCategorizationEntry 85 }

affirmedServicesContentFilterServiceStatisticsNode-levelContentCategorizationNumcategorywirelesschatsms OBJECT-TYPE
    SYNTAX      ConfdString
    MAX-ACCESS  read-only
    STATUS      current
    DESCRIPTION "Total number of requests categorized as Wireless Chat and SMS Online Category"
    ::= { affirmedServicesContentFilterServiceStatisticsNode-levelContentCategorizationEntry 86 }

affirmedServicesContentFilterServiceStatisticsNode-levelContentCategorizationNumcategorywirelessdynamic OBJECT-TYPE
    SYNTAX      ConfdString
    MAX-ACCESS  read-only
    STATUS      current
    DESCRIPTION "Total number of requests categorized as Wireless Dynamic Online Category"
    ::= { affirmedServicesContentFilterServiceStatisticsNode-levelContentCategorizationEntry 87 }

affirmedServicesContentFilterServiceStatisticsNode-levelContentCategorizationNumcategorywirelessentertainment OBJECT-TYPE
    SYNTAX      ConfdString
    MAX-ACCESS  read-only
    STATUS      current
    DESCRIPTION "Total number of requests categorized as Wireless Entertainment Online Category"
    ::= { affirmedServicesContentFilterServiceStatisticsNode-levelContentCategorizationEntry 88 }

affirmedServicesContentFilterServiceStatisticsNode-levelContentCategorizationNumcategorywirelessfinance OBJECT-TYPE
    SYNTAX      ConfdString
    MAX-ACCESS  read-only
    STATUS      current
    DESCRIPTION "Total number of requests categorized as Wireless Finance Online Category"
    ::= { affirmedServicesContentFilterServiceStatisticsNode-levelContentCategorizationEntry 89 }

affirmedServicesContentFilterServiceStatisticsNode-levelContentCategorizationNumcategorywirelessgambling OBJECT-TYPE
    SYNTAX      ConfdString
    MAX-ACCESS  read-only
    STATUS      current
    DESCRIPTION "Total number of requests categorized as Wireless Gambling Online Category"
    ::= { affirmedServicesContentFilterServiceStatisticsNode-levelContentCategorizationEntry 90 }

affirmedServicesContentFilterServiceStatisticsNode-levelContentCategorizationNumcategorywirelessnews OBJECT-TYPE
    SYNTAX      ConfdString
    MAX-ACCESS  read-only
    STATUS      current
    DESCRIPTION "Total number of requests categorized as Wireless News Online Category"
    ::= { affirmedServicesContentFilterServiceStatisticsNode-levelContentCategorizationEntry 91 }

affirmedServicesContentFilterServiceStatisticsNode-levelContentCategorizationNumcategorywirelesspersonalsanddating OBJECT-TYPE
    SYNTAX      ConfdString
    MAX-ACCESS  read-only
    STATUS      current
    DESCRIPTION "Total number of requests categorized as Wireless Personals And Dating Online Category"
    ::= { affirmedServicesContentFilterServiceStatisticsNode-levelContentCategorizationEntry 92 }

affirmedServicesContentFilterServiceStatisticsNode-levelContentCategorizationNumcategorywirelesspornography OBJECT-TYPE
    SYNTAX      ConfdString
    MAX-ACCESS  read-only
    STATUS      current
    DESCRIPTION "Total number of requests categorized as Wireless Pornography Online Category"
    ::= { affirmedServicesContentFilterServiceStatisticsNode-levelContentCategorizationEntry 93 }

affirmedServicesContentFilterServiceStatisticsNode-levelContentCategorizationNumcategorywirelesssports OBJECT-TYPE
    SYNTAX      ConfdString
    MAX-ACCESS  read-only
    STATUS      current
    DESCRIPTION "Total number of requests categorized as Wireless Sports Online Category"
    ::= { affirmedServicesContentFilterServiceStatisticsNode-levelContentCategorizationEntry 94 }

affirmedServicesContentFilterServiceStatisticsNode-levelContentCategorizationNumcategorywirelesstravel OBJECT-TYPE
    SYNTAX      ConfdString
    MAX-ACCESS  read-only
    STATUS      current
    DESCRIPTION "Total number of requests categorized as Wireless Travel Online Category"
    ::= { affirmedServicesContentFilterServiceStatisticsNode-levelContentCategorizationEntry 95 }

affirmedServicesContentFilterServiceStatisticsNode-levelContentCategorizationNumcategoryunknown OBJECT-TYPE
    SYNTAX      ConfdString
    MAX-ACCESS  read-only
    STATUS      current
    DESCRIPTION "Total number of requests failed categorization"
    ::= { affirmedServicesContentFilterServiceStatisticsNode-levelContentCategorizationEntry 96 }

affirmedServicesContentFilterServiceStatisticsNode-levelContentCategorizationNumcategorymalware OBJECT-TYPE
    SYNTAX      ConfdString
    MAX-ACCESS  read-only
    STATUS      current
    DESCRIPTION "Total number of requests categorized as Malware Online Category"
    ::= { affirmedServicesContentFilterServiceStatisticsNode-levelContentCategorizationEntry 97 }

affirmedServicesContentFilterServiceStatisticsNode-levelContentCategorizationNumcategoryphishing OBJECT-TYPE
    SYNTAX      ConfdString
    MAX-ACCESS  read-only
    STATUS      current
    DESCRIPTION "Total number of requests categorized as Phishing Online Category"
    ::= { affirmedServicesContentFilterServiceStatisticsNode-levelContentCategorizationEntry 98 }

affirmedServicesContentFilterServiceStatisticsNode-levelContentCategorizationNumcategoryiwf OBJECT-TYPE
    SYNTAX      ConfdString
    MAX-ACCESS  read-only
    STATUS      current
    DESCRIPTION "Total number of requests categorized as internet watch foundation CAIC Online Category"
    ::= { affirmedServicesContentFilterServiceStatisticsNode-levelContentCategorizationEntry 99 }

affirmedServicesContentFilterServiceStatisticsNode-levelContentCategorizationNumcategorynocat OBJECT-TYPE
    SYNTAX      ConfdString
    MAX-ACCESS  read-only
    STATUS      current
    DESCRIPTION "Total number of requests categorized as none of well-known categories"
    ::= { affirmedServicesContentFilterServiceStatisticsNode-levelContentCategorizationEntry 100 }

affirmedServicesContentFilterServiceStatisticsNode-levelContentCategorizationNumcategoryother OBJECT-TYPE
    SYNTAX      ConfdString
    MAX-ACCESS  read-only
    STATUS      current
    DESCRIPTION "Total number of requests categorized as new category not yet supported by AN3K"
    ::= { affirmedServicesContentFilterServiceStatisticsNode-levelContentCategorizationEntry 101 }

affirmedServicesContentFilterServiceStatisticsNode-levelContentCategorizationNumcategoryalcoholkids OBJECT-TYPE
    SYNTAX      ConfdString
    MAX-ACCESS  read-only
    STATUS      current
    DESCRIPTION "Total number of requests categorized as Alcohol Kids Online Category"
    ::= { affirmedServicesContentFilterServiceStatisticsNode-levelContentCategorizationEntry 102 }

affirmedServicesContentFilterServiceStatisticsNode-levelContentCategorizationNumcategorytobaccokids OBJECT-TYPE
    SYNTAX      ConfdString
    MAX-ACCESS  read-only
    STATUS      current
    DESCRIPTION "Total number of requests categorized as Tobacco Kids Online Category"
    ::= { affirmedServicesContentFilterServiceStatisticsNode-levelContentCategorizationEntry 103 }

affirmedServicesContentFilterServiceStatisticsNode-levelContentCategorizationNumcategorycyberbullying OBJECT-TYPE
    SYNTAX      ConfdString
    MAX-ACCESS  read-only
    STATUS      current
    DESCRIPTION "Total number of requests categorized as Cyberbullying Online Category"
    ::= { affirmedServicesContentFilterServiceStatisticsNode-levelContentCategorizationEntry 104 }

affirmedServicesContentFilterServiceStatisticsNode-levelContentCategorizationNumhttpsrequestlookups OBJECT-TYPE
    SYNTAX      ConfdString
    MAX-ACCESS  read-only
    STATUS      current
    DESCRIPTION "Total number of HTTPS request Lookups"
    ::= { affirmedServicesContentFilterServiceStatisticsNode-levelContentCategorizationEntry 105 }

affirmedServicesContentFilterServiceStatisticsNode-levelContentCategorizationNumlookupfailure OBJECT-TYPE
    SYNTAX      ConfdString
    MAX-ACCESS  read-only
    STATUS      current
    DESCRIPTION "Total number of lookup failures"
    ::= { affirmedServicesContentFilterServiceStatisticsNode-levelContentCategorizationEntry 106 }

affirmedServicesContentFilterServiceStatisticsNode-levelContentCategorizationNumquicrequestlookups OBJECT-TYPE
    SYNTAX      ConfdString
    MAX-ACCESS  read-only
    STATUS      current
    DESCRIPTION "Total number of QUIC request Lookups"
    ::= { affirmedServicesContentFilterServiceStatisticsNode-levelContentCategorizationEntry 107 }

affirmedServicesContentFilterServiceStatisticsNode-levelContentCategorizationNumcategorybbfcwhitelist OBJECT-TYPE
    SYNTAX      ConfdString
    MAX-ACCESS  read-only
    STATUS      current
    DESCRIPTION "Total number of requests categorized as BBFCWhitelist Online Category"
    ::= { affirmedServicesContentFilterServiceStatisticsNode-levelContentCategorizationEntry 108 }

affirmedServicesContentFilterServiceStatisticsNode-levelContentCategorizationNumcategorybbfcblacklist OBJECT-TYPE
    SYNTAX      ConfdString
    MAX-ACCESS  read-only
    STATUS      current
    DESCRIPTION "Total number of requests categorized as BBFCBlacklist Online Category"
    ::= { affirmedServicesContentFilterServiceStatisticsNode-levelContentCategorizationEntry 109 }

affirmedServicesContentFilterServiceStatisticsNode-levelContentCategorizationNumcategorycannabidiol OBJECT-TYPE
    SYNTAX      ConfdString
    MAX-ACCESS  read-only
    STATUS      current
    DESCRIPTION "Total number of requests categorized as Cannabidiol Online Category"
    ::= { affirmedServicesContentFilterServiceStatisticsNode-levelContentCategorizationEntry 110 }

affirmedServicesContentFilterServiceStatisticsNode-levelContentCategorizationNumcategorycloudinfrastructure OBJECT-TYPE
    SYNTAX      ConfdString
    MAX-ACCESS  read-only
    STATUS      current
    DESCRIPTION "Total number of requests categorized as CloudInfrastructure Online Category"
    ::= { affirmedServicesContentFilterServiceStatisticsNode-levelContentCategorizationEntry 111 }

affirmedServicesContentFilterServiceStatisticsNode-levelContentCategorizationNumcategoryfireworks OBJECT-TYPE
    SYNTAX      ConfdString
    MAX-ACCESS  read-only
    STATUS      current
    DESCRIPTION "Total number of requests categorized as Fireworks Online Category"
    ::= { affirmedServicesContentFilterServiceStatisticsNode-levelContentCategorizationEntry 112 }

affirmedServicesContentFilterServiceStatisticsNode-levelContentCategorizationNumcategorylingerie OBJECT-TYPE
    SYNTAX      ConfdString
    MAX-ACCESS  read-only
    STATUS      current
    DESCRIPTION "Total number of requests categorized as Lingerie Online Category"
    ::= { affirmedServicesContentFilterServiceStatisticsNode-levelContentCategorizationEntry 113 }

affirmedServicesContentFilterServiceStatisticsNode-levelContentCategorizationNumcategorysexualadvice OBJECT-TYPE
    SYNTAX      ConfdString
    MAX-ACCESS  read-only
    STATUS      current
    DESCRIPTION "Total number of requests categorized as SexualAdvice Online Category"
    ::= { affirmedServicesContentFilterServiceStatisticsNode-levelContentCategorizationEntry 114 }

affirmedServicesContentFilterServiceStatisticsNode-levelContentCategorizationNumcategorytracking OBJECT-TYPE
    SYNTAX      ConfdString
    MAX-ACCESS  read-only
    STATUS      current
    DESCRIPTION "Total number of requests categorized as Tracking Online Category"
    ::= { affirmedServicesContentFilterServiceStatisticsNode-levelContentCategorizationEntry 115 }

affirmedServicesContentFilterServiceStatisticsNode-levelContentCategorizationNumcategoryukdeablacklist OBJECT-TYPE
    SYNTAX      ConfdString
    MAX-ACCESS  read-only
    STATUS      current
    DESCRIPTION "Total number of requests categorized as UKDEABlacklist Online Category"
    ::= { affirmedServicesContentFilterServiceStatisticsNode-levelContentCategorizationEntry 116 }

affirmedServicesContentFilterServiceStatisticssNodeLevelInstContCatTable OBJECT-TYPE
    SYNTAX      SEQUENCE OF AffirmedServicesContentFilterServiceStatisticssNodeLevelInstContCatEntry
    MAX-ACCESS  not-accessible
    STATUS      current
    DESCRIPTION ""
    ::= { affirmedServicesContentFilterServiceStatisticsNode-level 4 }

affirmedServicesContentFilterServiceStatisticssNodeLevelInstContCatEntry OBJECT-TYPE
    SYNTAX      AffirmedServicesContentFilterServiceStatisticssNodeLevelInstContCatEntry
    MAX-ACCESS  not-accessible
    STATUS      current
    DESCRIPTION ""
    INDEX { affirmedServicesContentFilterServiceStatisticssNodeLevelInstContCatName, affirmedServicesContentFilterServiceStatisticssNodeLevelInstContCatChassis, affirmedServicesContentFilterServiceStatisticssNodeLevelInstContCatSlot }
        ::= { affirmedServicesContentFilterServiceStatisticssNodeLevelInstContCatTable 1 }

AffirmedServicesContentFilterServiceStatisticssNodeLevelInstContCatEntry ::=
    SEQUENCE {
        affirmedServicesContentFilterServiceStatisticssNodeLevelInstContCatName String,
        affirmedServicesContentFilterServiceStatisticssNodeLevelInstContCatChassis Unsigned32,
        affirmedServicesContentFilterServiceStatisticssNodeLevelInstContCatSlot Unsigned32,
        affirmedServicesContentFilterServiceStatisticssNodeLevelInstContCatNumurlbasedlookups ConfdString,
        affirmedServicesContentFilterServiceStatisticssNodeLevelInstContCatNumresponsebasedlookups ConfdString,
        affirmedServicesContentFilterServiceStatisticssNodeLevelInstContCatNumcategoryabortion ConfdString,
        affirmedServicesContentFilterServiceStatisticssNodeLevelInstContCatNumcategoryadvertising ConfdString,
        affirmedServicesContentFilterServiceStatisticssNodeLevelInstContCatNumcategoryalcohol ConfdString,
        affirmedServicesContentFilterServiceStatisticssNodeLevelInstContCatNumcategoryanonymizer ConfdString,
        affirmedServicesContentFilterServiceStatisticssNodeLevelInstContCatNumcategoryartandmuseums ConfdString,
        affirmedServicesContentFilterServiceStatisticssNodeLevelInstContCatNumcategoryartnudes ConfdString,
        affirmedServicesContentFilterServiceStatisticssNodeLevelInstContCatNumcategoryautomatedwebapplication ConfdString,
        affirmedServicesContentFilterServiceStatisticssNodeLevelInstContCatNumcategoryautomotive ConfdString,
        affirmedServicesContentFilterServiceStatisticssNodeLevelInstContCatNumcategorybikini ConfdString,
        affirmedServicesContentFilterServiceStatisticssNodeLevelInstContCatNumcategoryblogging ConfdString,
        affirmedServicesContentFilterServiceStatisticssNodeLevelInstContCatNumcategorybusiness ConfdString,
        affirmedServicesContentFilterServiceStatisticssNodeLevelInstContCatNumcategorycashgambling ConfdString,
        affirmedServicesContentFilterServiceStatisticssNodeLevelInstContCatNumcategorychat ConfdString,
        affirmedServicesContentFilterServiceStatisticssNodeLevelInstContCatNumcategorycontentdeliverynetwork ConfdString,
        affirmedServicesContentFilterServiceStatisticssNodeLevelInstContCatNumcategorycriminalskills ConfdString,
        affirmedServicesContentFilterServiceStatisticssNodeLevelInstContCatNumcategorycults ConfdString,
        affirmedServicesContentFilterServiceStatisticssNodeLevelInstContCatNumcategorydrugs ConfdString,
        affirmedServicesContentFilterServiceStatisticssNodeLevelInstContCatNumcategorydynamic ConfdString,
        affirmedServicesContentFilterServiceStatisticssNodeLevelInstContCatNumcategoryeducational ConfdString,
        affirmedServicesContentFilterServiceStatisticssNodeLevelInstContCatNumcategoryenergy ConfdString,
        affirmedServicesContentFilterServiceStatisticssNodeLevelInstContCatNumcategoryenterprisewebmail ConfdString,
        affirmedServicesContentFilterServiceStatisticssNodeLevelInstContCatNumcategoryentertainment ConfdString,
        affirmedServicesContentFilterServiceStatisticssNodeLevelInstContCatNumcategoryfilesharing ConfdString,
        affirmedServicesContentFilterServiceStatisticssNodeLevelInstContCatNumcategoryfinanceandinvesting ConfdString,
        affirmedServicesContentFilterServiceStatisticssNodeLevelInstContCatNumcategoryfoodandrestaurants ConfdString,
        affirmedServicesContentFilterServiceStatisticssNodeLevelInstContCatNumcategoryforumsandmessageboards ConfdString,
        affirmedServicesContentFilterServiceStatisticssNodeLevelInstContCatNumcategoryfreewareandshareware ConfdString,
        affirmedServicesContentFilterServiceStatisticssNodeLevelInstContCatNumcategorygambling ConfdString,
        affirmedServicesContentFilterServiceStatisticssNodeLevelInstContCatNumcategorygaming ConfdString,
        affirmedServicesContentFilterServiceStatisticssNodeLevelInstContCatNumcategoryglamour ConfdString,
        affirmedServicesContentFilterServiceStatisticssNodeLevelInstContCatNumcategorygore ConfdString,
        affirmedServicesContentFilterServiceStatisticssNodeLevelInstContCatNumcategorygovernment ConfdString,
        affirmedServicesContentFilterServiceStatisticssNodeLevelInstContCatNumcategoryhacking ConfdString,
        affirmedServicesContentFilterServiceStatisticssNodeLevelInstContCatNumcategoryhate ConfdString,
        affirmedServicesContentFilterServiceStatisticssNodeLevelInstContCatNumcategoryhealth ConfdString,
        affirmedServicesContentFilterServiceStatisticssNodeLevelInstContCatNumcategoryhobby ConfdString,
        affirmedServicesContentFilterServiceStatisticssNodeLevelInstContCatNumcategoryhosting ConfdString,
        affirmedServicesContentFilterServiceStatisticssNodeLevelInstContCatNumcategoryinternettelephony ConfdString,
        affirmedServicesContentFilterServiceStatisticssNodeLevelInstContCatNumcategoryjobsearch ConfdString,
        affirmedServicesContentFilterServiceStatisticssNodeLevelInstContCatNumcategorykids ConfdString,
        affirmedServicesContentFilterServiceStatisticssNodeLevelInstContCatNumcategorylaw ConfdString,
        affirmedServicesContentFilterServiceStatisticssNodeLevelInstContCatNumcategorylifestyles ConfdString,
        affirmedServicesContentFilterServiceStatisticssNodeLevelInstContCatNumcategorymaturecontent ConfdString,
        affirmedServicesContentFilterServiceStatisticssNodeLevelInstContCatNumcategorymilitary ConfdString,
        affirmedServicesContentFilterServiceStatisticssNodeLevelInstContCatNumcategorymobileentertainment ConfdString,
        affirmedServicesContentFilterServiceStatisticssNodeLevelInstContCatNumcategorymusic ConfdString,
        affirmedServicesContentFilterServiceStatisticssNodeLevelInstContCatNumcategorynews ConfdString,
        affirmedServicesContentFilterServiceStatisticssNodeLevelInstContCatNumcategorynonprofit ConfdString,
        affirmedServicesContentFilterServiceStatisticssNodeLevelInstContCatNumcategoryobscene ConfdString,
        affirmedServicesContentFilterServiceStatisticssNodeLevelInstContCatNumcategoryoccult ConfdString,
        affirmedServicesContentFilterServiceStatisticssNodeLevelInstContCatNumcategoryonlinebackupandstorage ConfdString,
        affirmedServicesContentFilterServiceStatisticssNodeLevelInstContCatNumcategorypeertopeer ConfdString,
        affirmedServicesContentFilterServiceStatisticssNodeLevelInstContCatNumcategorypets ConfdString,
        affirmedServicesContentFilterServiceStatisticssNodeLevelInstContCatNumcategoryphotography ConfdString,
        affirmedServicesContentFilterServiceStatisticssNodeLevelInstContCatNumcategoryplaceholder ConfdString,
        affirmedServicesContentFilterServiceStatisticssNodeLevelInstContCatNumcategoryplagiarism ConfdString,
        affirmedServicesContentFilterServiceStatisticssNodeLevelInstContCatNumcategorypolitics ConfdString,
        affirmedServicesContentFilterServiceStatisticssNodeLevelInstContCatNumcategorypornography ConfdString,
        affirmedServicesContentFilterServiceStatisticssNodeLevelInstContCatNumcategoryportal ConfdString,
        affirmedServicesContentFilterServiceStatisticssNodeLevelInstContCatNumcategorypersonalsanddating ConfdString,
        affirmedServicesContentFilterServiceStatisticssNodeLevelInstContCatNumcategoryrealestate ConfdString,
        affirmedServicesContentFilterServiceStatisticssNodeLevelInstContCatNumcategoryreference ConfdString,
        affirmedServicesContentFilterServiceStatisticssNodeLevelInstContCatNumcategoryreligion ConfdString,
        affirmedServicesContentFilterServiceStatisticssNodeLevelInstContCatNumcategoryremoteaccess ConfdString,
        affirmedServicesContentFilterServiceStatisticssNodeLevelInstContCatNumcategoryscience ConfdString,
        affirmedServicesContentFilterServiceStatisticssNodeLevelInstContCatNumcategorysearch ConfdString,
        affirmedServicesContentFilterServiceStatisticssNodeLevelInstContCatNumcategoryselfharm ConfdString,
        affirmedServicesContentFilterServiceStatisticssNodeLevelInstContCatNumcategorysexualeducation ConfdString,
        affirmedServicesContentFilterServiceStatisticssNodeLevelInstContCatNumcategoryshopping ConfdString,
        affirmedServicesContentFilterServiceStatisticssNodeLevelInstContCatNumcategorysports ConfdString,
        affirmedServicesContentFilterServiceStatisticssNodeLevelInstContCatNumcategorystreamingmedia ConfdString,
        affirmedServicesContentFilterServiceStatisticssNodeLevelInstContCatNumcategorysuicide ConfdString,
        affirmedServicesContentFilterServiceStatisticssNodeLevelInstContCatNumcategorytechnologyandtelecommunication ConfdString,
        affirmedServicesContentFilterServiceStatisticssNodeLevelInstContCatNumcategorytobacco ConfdString,
        affirmedServicesContentFilterServiceStatisticssNodeLevelInstContCatNumcategorytravel ConfdString,
        affirmedServicesContentFilterServiceStatisticssNodeLevelInstContCatNumcategoryviolence ConfdString,
        affirmedServicesContentFilterServiceStatisticssNodeLevelInstContCatNumcategoryvirtualcommunity ConfdString,
        affirmedServicesContentFilterServiceStatisticssNodeLevelInstContCatNumcategoryweapons ConfdString,
        affirmedServicesContentFilterServiceStatisticssNodeLevelInstContCatNumcategorywebmail ConfdString,
        affirmedServicesContentFilterServiceStatisticssNodeLevelInstContCatNumcategorywedding ConfdString,
        affirmedServicesContentFilterServiceStatisticssNodeLevelInstContCatNumcategorywirelessbusiness ConfdString,
        affirmedServicesContentFilterServiceStatisticssNodeLevelInstContCatNumcategorywirelesschatsms ConfdString,
        affirmedServicesContentFilterServiceStatisticssNodeLevelInstContCatNumcategorywirelessdynamic ConfdString,
        affirmedServicesContentFilterServiceStatisticssNodeLevelInstContCatNumcategorywirelessentertainment ConfdString,
        affirmedServicesContentFilterServiceStatisticssNodeLevelInstContCatNumcategorywirelessfinance ConfdString,
        affirmedServicesContentFilterServiceStatisticssNodeLevelInstContCatNumcategorywirelessgambling ConfdString,
        affirmedServicesContentFilterServiceStatisticssNodeLevelInstContCatNumcategorywirelessnews ConfdString,
        affirmedServicesContentFilterServiceStatisticssNodeLevelInstContCatNumcategorywirelesspersonalsanddating ConfdString,
        affirmedServicesContentFilterServiceStatisticssNodeLevelInstContCatNumcategorywirelesspornography ConfdString,
        affirmedServicesContentFilterServiceStatisticssNodeLevelInstContCatNumcategorywirelesssports ConfdString,
        affirmedServicesContentFilterServiceStatisticssNodeLevelInstContCatNumcategorywirelesstravel ConfdString,
        affirmedServicesContentFilterServiceStatisticssNodeLevelInstContCatNumcategoryunknown ConfdString,
        affirmedServicesContentFilterServiceStatisticssNodeLevelInstContCatNumcategorymalware ConfdString,
        affirmedServicesContentFilterServiceStatisticssNodeLevelInstContCatNumcategoryphishing ConfdString,
        affirmedServicesContentFilterServiceStatisticssNodeLevelInstContCatNumcategoryiwf ConfdString,
        affirmedServicesContentFilterServiceStatisticssNodeLevelInstContCatNumcategorynocat ConfdString,
        affirmedServicesContentFilterServiceStatisticssNodeLevelInstContCatNumcategoryother ConfdString,
        affirmedServicesContentFilterServiceStatisticssNodeLevelInstContCatNumcategoryalcoholkids ConfdString,
        affirmedServicesContentFilterServiceStatisticssNodeLevelInstContCatNumcategorytobaccokids ConfdString,
        affirmedServicesContentFilterServiceStatisticssNodeLevelInstContCatNumcategorycyberbullying ConfdString,
        affirmedServicesContentFilterServiceStatisticssNodeLevelInstContCatNumhttpsrequestlookups ConfdString,
        affirmedServicesContentFilterServiceStatisticssNodeLevelInstContCatNumlookupfailure ConfdString,
        affirmedServicesContentFilterServiceStatisticssNodeLevelInstContCatNumquicrequestlookups ConfdString,
        affirmedServicesContentFilterServiceStatisticssNodeLevelInstContCatNumcategorybbfcwhitelist ConfdString,
        affirmedServicesContentFilterServiceStatisticssNodeLevelInstContCatNumcategorybbfcblacklist ConfdString,
        affirmedServicesContentFilterServiceStatisticssNodeLevelInstContCatNumcategorycannabidiol ConfdString,
        affirmedServicesContentFilterServiceStatisticssNodeLevelInstContCatNumcategorycloudinfrastructure ConfdString,
        affirmedServicesContentFilterServiceStatisticssNodeLevelInstContCatNumcategoryfireworks ConfdString,
        affirmedServicesContentFilterServiceStatisticssNodeLevelInstContCatNumcategorylingerie ConfdString,
        affirmedServicesContentFilterServiceStatisticssNodeLevelInstContCatNumcategorysexualadvice ConfdString,
        affirmedServicesContentFilterServiceStatisticssNodeLevelInstContCatNumcategorytracking ConfdString,
        affirmedServicesContentFilterServiceStatisticssNodeLevelInstContCatNumcategoryukdeablacklist ConfdString
    }

affirmedServicesContentFilterServiceStatisticssNodeLevelInstContCatName OBJECT-TYPE
    SYNTAX      String
    MAX-ACCESS  not-accessible
    STATUS      current
    DESCRIPTION "Name of content filter service instance"
    ::= { affirmedServicesContentFilterServiceStatisticssNodeLevelInstContCatEntry 1 }

affirmedServicesContentFilterServiceStatisticssNodeLevelInstContCatChassis OBJECT-TYPE
    SYNTAX      Unsigned32
    MAX-ACCESS  not-accessible
    STATUS      current
    DESCRIPTION "chassis ID"
    ::= { affirmedServicesContentFilterServiceStatisticssNodeLevelInstContCatEntry 2 }

affirmedServicesContentFilterServiceStatisticssNodeLevelInstContCatSlot OBJECT-TYPE
    SYNTAX      Unsigned32
    MAX-ACCESS  not-accessible
    STATUS      current
    DESCRIPTION "slot number"
    ::= { affirmedServicesContentFilterServiceStatisticssNodeLevelInstContCatEntry 3 }

affirmedServicesContentFilterServiceStatisticssNodeLevelInstContCatNumurlbasedlookups OBJECT-TYPE
    SYNTAX      ConfdString
    MAX-ACCESS  read-only
    STATUS      current
    DESCRIPTION "Total number of HTTP request Lookups"
    ::= { affirmedServicesContentFilterServiceStatisticssNodeLevelInstContCatEntry 4 }

affirmedServicesContentFilterServiceStatisticssNodeLevelInstContCatNumresponsebasedlookups OBJECT-TYPE
    SYNTAX      ConfdString
    MAX-ACCESS  read-only
    STATUS      current
    DESCRIPTION "Total number of HTTP Response-based Lookups"
    ::= { affirmedServicesContentFilterServiceStatisticssNodeLevelInstContCatEntry 5 }

affirmedServicesContentFilterServiceStatisticssNodeLevelInstContCatNumcategoryabortion OBJECT-TYPE
    SYNTAX      ConfdString
    MAX-ACCESS  read-only
    STATUS      current
    DESCRIPTION "Total number of requests categorized as Abortion Online Category"
    ::= { affirmedServicesContentFilterServiceStatisticssNodeLevelInstContCatEntry 6 }

affirmedServicesContentFilterServiceStatisticssNodeLevelInstContCatNumcategoryadvertising OBJECT-TYPE
    SYNTAX      ConfdString
    MAX-ACCESS  read-only
    STATUS      current
    DESCRIPTION "Total number of requests categorized as Advertising Online Category"
    ::= { affirmedServicesContentFilterServiceStatisticssNodeLevelInstContCatEntry 7 }

affirmedServicesContentFilterServiceStatisticssNodeLevelInstContCatNumcategoryalcohol OBJECT-TYPE
    SYNTAX      ConfdString
    MAX-ACCESS  read-only
    STATUS      current
    DESCRIPTION "Total number of requests categorized as Alcohol Online Category"
    ::= { affirmedServicesContentFilterServiceStatisticssNodeLevelInstContCatEntry 8 }

affirmedServicesContentFilterServiceStatisticssNodeLevelInstContCatNumcategoryanonymizer OBJECT-TYPE
    SYNTAX      ConfdString
    MAX-ACCESS  read-only
    STATUS      current
    DESCRIPTION "Total number of requests categorized as Anonymizer Online Category"
    ::= { affirmedServicesContentFilterServiceStatisticssNodeLevelInstContCatEntry 9 }

affirmedServicesContentFilterServiceStatisticssNodeLevelInstContCatNumcategoryartandmuseums OBJECT-TYPE
    SYNTAX      ConfdString
    MAX-ACCESS  read-only
    STATUS      current
    DESCRIPTION "Total number of requests categorized as Art And Museums Online Category"
    ::= { affirmedServicesContentFilterServiceStatisticssNodeLevelInstContCatEntry 10 }

affirmedServicesContentFilterServiceStatisticssNodeLevelInstContCatNumcategoryartnudes OBJECT-TYPE
    SYNTAX      ConfdString
    MAX-ACCESS  read-only
    STATUS      current
    DESCRIPTION "Total number of requests categorized as Art Nudes Online Category"
    ::= { affirmedServicesContentFilterServiceStatisticssNodeLevelInstContCatEntry 11 }

affirmedServicesContentFilterServiceStatisticssNodeLevelInstContCatNumcategoryautomatedwebapplication OBJECT-TYPE
    SYNTAX      ConfdString
    MAX-ACCESS  read-only
    STATUS      current
    DESCRIPTION "Total number of requests categorized as Automated Web Application Online Category"
    ::= { affirmedServicesContentFilterServiceStatisticssNodeLevelInstContCatEntry 12 }

affirmedServicesContentFilterServiceStatisticssNodeLevelInstContCatNumcategoryautomotive OBJECT-TYPE
    SYNTAX      ConfdString
    MAX-ACCESS  read-only
    STATUS      current
    DESCRIPTION "Total number of requests categorized as Automotive Online Category"
    ::= { affirmedServicesContentFilterServiceStatisticssNodeLevelInstContCatEntry 13 }

affirmedServicesContentFilterServiceStatisticssNodeLevelInstContCatNumcategorybikini OBJECT-TYPE
    SYNTAX      ConfdString
    MAX-ACCESS  read-only
    STATUS      current
    DESCRIPTION "Total number of requests categorized as Bikini Online Category"
    ::= { affirmedServicesContentFilterServiceStatisticssNodeLevelInstContCatEntry 14 }

affirmedServicesContentFilterServiceStatisticssNodeLevelInstContCatNumcategoryblogging OBJECT-TYPE
    SYNTAX      ConfdString
    MAX-ACCESS  read-only
    STATUS      current
    DESCRIPTION "Total number of requests categorized as Blogging Online Category"
    ::= { affirmedServicesContentFilterServiceStatisticssNodeLevelInstContCatEntry 15 }

affirmedServicesContentFilterServiceStatisticssNodeLevelInstContCatNumcategorybusiness OBJECT-TYPE
    SYNTAX      ConfdString
    MAX-ACCESS  read-only
    STATUS      current
    DESCRIPTION "Total number of requests categorized as Business Online Category"
    ::= { affirmedServicesContentFilterServiceStatisticssNodeLevelInstContCatEntry 16 }

affirmedServicesContentFilterServiceStatisticssNodeLevelInstContCatNumcategorycashgambling OBJECT-TYPE
    SYNTAX      ConfdString
    MAX-ACCESS  read-only
    STATUS      current
    DESCRIPTION "Total number of requests categorized as Cash Gambling Online Category"
    ::= { affirmedServicesContentFilterServiceStatisticssNodeLevelInstContCatEntry 17 }

affirmedServicesContentFilterServiceStatisticssNodeLevelInstContCatNumcategorychat OBJECT-TYPE
    SYNTAX      ConfdString
    MAX-ACCESS  read-only
    STATUS      current
    DESCRIPTION "Total number of requests categorized as Chat Online Category"
    ::= { affirmedServicesContentFilterServiceStatisticssNodeLevelInstContCatEntry 18 }

affirmedServicesContentFilterServiceStatisticssNodeLevelInstContCatNumcategorycontentdeliverynetwork OBJECT-TYPE
    SYNTAX      ConfdString
    MAX-ACCESS  read-only
    STATUS      current
    DESCRIPTION "Total number of requests categorized as Content Delivery Network Online Category"
    ::= { affirmedServicesContentFilterServiceStatisticssNodeLevelInstContCatEntry 19 }

affirmedServicesContentFilterServiceStatisticssNodeLevelInstContCatNumcategorycriminalskills OBJECT-TYPE
    SYNTAX      ConfdString
    MAX-ACCESS  read-only
    STATUS      current
    DESCRIPTION "Total number of requests categorized as Criminal Skills Online Category"
    ::= { affirmedServicesContentFilterServiceStatisticssNodeLevelInstContCatEntry 20 }

affirmedServicesContentFilterServiceStatisticssNodeLevelInstContCatNumcategorycults OBJECT-TYPE
    SYNTAX      ConfdString
    MAX-ACCESS  read-only
    STATUS      current
    DESCRIPTION "Total number of requests categorized as Cults Online Category"
    ::= { affirmedServicesContentFilterServiceStatisticssNodeLevelInstContCatEntry 21 }

affirmedServicesContentFilterServiceStatisticssNodeLevelInstContCatNumcategorydrugs OBJECT-TYPE
    SYNTAX      ConfdString
    MAX-ACCESS  read-only
    STATUS      current
    DESCRIPTION "Total number of requests categorized as Drugs Online Category"
    ::= { affirmedServicesContentFilterServiceStatisticssNodeLevelInstContCatEntry 22 }

affirmedServicesContentFilterServiceStatisticssNodeLevelInstContCatNumcategorydynamic OBJECT-TYPE
    SYNTAX      ConfdString
    MAX-ACCESS  read-only
    STATUS      current
    DESCRIPTION "Total number of requests categorized as Dynamic Online Category"
    ::= { affirmedServicesContentFilterServiceStatisticssNodeLevelInstContCatEntry 23 }

affirmedServicesContentFilterServiceStatisticssNodeLevelInstContCatNumcategoryeducational OBJECT-TYPE
    SYNTAX      ConfdString
    MAX-ACCESS  read-only
    STATUS      current
    DESCRIPTION "Total number of requests categorized as Educational Online Category"
    ::= { affirmedServicesContentFilterServiceStatisticssNodeLevelInstContCatEntry 24 }

affirmedServicesContentFilterServiceStatisticssNodeLevelInstContCatNumcategoryenergy OBJECT-TYPE
    SYNTAX      ConfdString
    MAX-ACCESS  read-only
    STATUS      current
    DESCRIPTION "Total number of requests categorized as Energy Online Category"
    ::= { affirmedServicesContentFilterServiceStatisticssNodeLevelInstContCatEntry 25 }

affirmedServicesContentFilterServiceStatisticssNodeLevelInstContCatNumcategoryenterprisewebmail OBJECT-TYPE
    SYNTAX      ConfdString
    MAX-ACCESS  read-only
    STATUS      current
    DESCRIPTION "Total number of requests categorized as Enterprise Webmail Online Category"
    ::= { affirmedServicesContentFilterServiceStatisticssNodeLevelInstContCatEntry 26 }

affirmedServicesContentFilterServiceStatisticssNodeLevelInstContCatNumcategoryentertainment OBJECT-TYPE
    SYNTAX      ConfdString
    MAX-ACCESS  read-only
    STATUS      current
    DESCRIPTION "Total number of requests categorized as Entertainment Online Category"
    ::= { affirmedServicesContentFilterServiceStatisticssNodeLevelInstContCatEntry 27 }

affirmedServicesContentFilterServiceStatisticssNodeLevelInstContCatNumcategoryfilesharing OBJECT-TYPE
    SYNTAX      ConfdString
    MAX-ACCESS  read-only
    STATUS      current
    DESCRIPTION "Total number of requests categorized as Filesharing Online Category"
    ::= { affirmedServicesContentFilterServiceStatisticssNodeLevelInstContCatEntry 28 }

affirmedServicesContentFilterServiceStatisticssNodeLevelInstContCatNumcategoryfinanceandinvesting OBJECT-TYPE
    SYNTAX      ConfdString
    MAX-ACCESS  read-only
    STATUS      current
    DESCRIPTION "Total number of requests categorized as Finance And Investing Online Category"
    ::= { affirmedServicesContentFilterServiceStatisticssNodeLevelInstContCatEntry 29 }

affirmedServicesContentFilterServiceStatisticssNodeLevelInstContCatNumcategoryfoodandrestaurants OBJECT-TYPE
    SYNTAX      ConfdString
    MAX-ACCESS  read-only
    STATUS      current
    DESCRIPTION "Total number of requests categorized as Food And Restaurants Online Category"
    ::= { affirmedServicesContentFilterServiceStatisticssNodeLevelInstContCatEntry 30 }

affirmedServicesContentFilterServiceStatisticssNodeLevelInstContCatNumcategoryforumsandmessageboards OBJECT-TYPE
    SYNTAX      ConfdString
    MAX-ACCESS  read-only
    STATUS      current
    DESCRIPTION "Total number of requests categorized as Forums And Messageboards Online Category"
    ::= { affirmedServicesContentFilterServiceStatisticssNodeLevelInstContCatEntry 31 }

affirmedServicesContentFilterServiceStatisticssNodeLevelInstContCatNumcategoryfreewareandshareware OBJECT-TYPE
    SYNTAX      ConfdString
    MAX-ACCESS  read-only
    STATUS      current
    DESCRIPTION "Total number of requests categorized as Freeware And Shareware Online Category"
    ::= { affirmedServicesContentFilterServiceStatisticssNodeLevelInstContCatEntry 32 }

affirmedServicesContentFilterServiceStatisticssNodeLevelInstContCatNumcategorygambling OBJECT-TYPE
    SYNTAX      ConfdString
    MAX-ACCESS  read-only
    STATUS      current
    DESCRIPTION "Total number of requests categorized as Gambling Online Category"
    ::= { affirmedServicesContentFilterServiceStatisticssNodeLevelInstContCatEntry 33 }

affirmedServicesContentFilterServiceStatisticssNodeLevelInstContCatNumcategorygaming OBJECT-TYPE
    SYNTAX      ConfdString
    MAX-ACCESS  read-only
    STATUS      current
    DESCRIPTION "Total number of requests categorized as Gaming Online Category"
    ::= { affirmedServicesContentFilterServiceStatisticssNodeLevelInstContCatEntry 34 }

affirmedServicesContentFilterServiceStatisticssNodeLevelInstContCatNumcategoryglamour OBJECT-TYPE
    SYNTAX      ConfdString
    MAX-ACCESS  read-only
    STATUS      current
    DESCRIPTION "Total number of requests categorized as Glamour Online Category"
    ::= { affirmedServicesContentFilterServiceStatisticssNodeLevelInstContCatEntry 35 }

affirmedServicesContentFilterServiceStatisticssNodeLevelInstContCatNumcategorygore OBJECT-TYPE
    SYNTAX      ConfdString
    MAX-ACCESS  read-only
    STATUS      current
    DESCRIPTION "Total number of requests categorized as Gore Online Category"
    ::= { affirmedServicesContentFilterServiceStatisticssNodeLevelInstContCatEntry 36 }

affirmedServicesContentFilterServiceStatisticssNodeLevelInstContCatNumcategorygovernment OBJECT-TYPE
    SYNTAX      ConfdString
    MAX-ACCESS  read-only
    STATUS      current
    DESCRIPTION "Total number of requests categorized as Government Online Category"
    ::= { affirmedServicesContentFilterServiceStatisticssNodeLevelInstContCatEntry 37 }

affirmedServicesContentFilterServiceStatisticssNodeLevelInstContCatNumcategoryhacking OBJECT-TYPE
    SYNTAX      ConfdString
    MAX-ACCESS  read-only
    STATUS      current
    DESCRIPTION "Total number of requests categorized as Hacking Online Category"
    ::= { affirmedServicesContentFilterServiceStatisticssNodeLevelInstContCatEntry 38 }

affirmedServicesContentFilterServiceStatisticssNodeLevelInstContCatNumcategoryhate OBJECT-TYPE
    SYNTAX      ConfdString
    MAX-ACCESS  read-only
    STATUS      current
    DESCRIPTION "Total number of requests categorized as Hate Online Category"
    ::= { affirmedServicesContentFilterServiceStatisticssNodeLevelInstContCatEntry 39 }

affirmedServicesContentFilterServiceStatisticssNodeLevelInstContCatNumcategoryhealth OBJECT-TYPE
    SYNTAX      ConfdString
    MAX-ACCESS  read-only
    STATUS      current
    DESCRIPTION "Total number of requests categorized as Health Online Category"
    ::= { affirmedServicesContentFilterServiceStatisticssNodeLevelInstContCatEntry 40 }

affirmedServicesContentFilterServiceStatisticssNodeLevelInstContCatNumcategoryhobby OBJECT-TYPE
    SYNTAX      ConfdString
    MAX-ACCESS  read-only
    STATUS      current
    DESCRIPTION "Total number of requests categorized as Hobby Online Category"
    ::= { affirmedServicesContentFilterServiceStatisticssNodeLevelInstContCatEntry 41 }

affirmedServicesContentFilterServiceStatisticssNodeLevelInstContCatNumcategoryhosting OBJECT-TYPE
    SYNTAX      ConfdString
    MAX-ACCESS  read-only
    STATUS      current
    DESCRIPTION "Total number of requests categorized as Hosting Online Category"
    ::= { affirmedServicesContentFilterServiceStatisticssNodeLevelInstContCatEntry 42 }

affirmedServicesContentFilterServiceStatisticssNodeLevelInstContCatNumcategoryinternettelephony OBJECT-TYPE
    SYNTAX      ConfdString
    MAX-ACCESS  read-only
    STATUS      current
    DESCRIPTION "Total number of requests categorized as Internet Telephony Online Category"
    ::= { affirmedServicesContentFilterServiceStatisticssNodeLevelInstContCatEntry 43 }

affirmedServicesContentFilterServiceStatisticssNodeLevelInstContCatNumcategoryjobsearch OBJECT-TYPE
    SYNTAX      ConfdString
    MAX-ACCESS  read-only
    STATUS      current
    DESCRIPTION "Total number of requests categorized as Job Search Online Category"
    ::= { affirmedServicesContentFilterServiceStatisticssNodeLevelInstContCatEntry 44 }

affirmedServicesContentFilterServiceStatisticssNodeLevelInstContCatNumcategorykids OBJECT-TYPE
    SYNTAX      ConfdString
    MAX-ACCESS  read-only
    STATUS      current
    DESCRIPTION "Total number of requests categorized as Kids Online Category"
    ::= { affirmedServicesContentFilterServiceStatisticssNodeLevelInstContCatEntry 45 }

affirmedServicesContentFilterServiceStatisticssNodeLevelInstContCatNumcategorylaw OBJECT-TYPE
    SYNTAX      ConfdString
    MAX-ACCESS  read-only
    STATUS      current
    DESCRIPTION "Total number of requests categorized as Law Online Category"
    ::= { affirmedServicesContentFilterServiceStatisticssNodeLevelInstContCatEntry 46 }

affirmedServicesContentFilterServiceStatisticssNodeLevelInstContCatNumcategorylifestyles OBJECT-TYPE
    SYNTAX      ConfdString
    MAX-ACCESS  read-only
    STATUS      current
    DESCRIPTION "Total number of requests categorized as Lifestyles Online Category"
    ::= { affirmedServicesContentFilterServiceStatisticssNodeLevelInstContCatEntry 47 }

affirmedServicesContentFilterServiceStatisticssNodeLevelInstContCatNumcategorymaturecontent OBJECT-TYPE
    SYNTAX      ConfdString
    MAX-ACCESS  read-only
    STATUS      current
    DESCRIPTION "Total number of requests categorized as Mature Content Online Category"
    ::= { affirmedServicesContentFilterServiceStatisticssNodeLevelInstContCatEntry 48 }

affirmedServicesContentFilterServiceStatisticssNodeLevelInstContCatNumcategorymilitary OBJECT-TYPE
    SYNTAX      ConfdString
    MAX-ACCESS  read-only
    STATUS      current
    DESCRIPTION "Total number of requests categorized as Military Online Category"
    ::= { affirmedServicesContentFilterServiceStatisticssNodeLevelInstContCatEntry 49 }

affirmedServicesContentFilterServiceStatisticssNodeLevelInstContCatNumcategorymobileentertainment OBJECT-TYPE
    SYNTAX      ConfdString
    MAX-ACCESS  read-only
    STATUS      current
    DESCRIPTION "Total number of requests categorized as Mobile Entertainment Online Category"
    ::= { affirmedServicesContentFilterServiceStatisticssNodeLevelInstContCatEntry 50 }

affirmedServicesContentFilterServiceStatisticssNodeLevelInstContCatNumcategorymusic OBJECT-TYPE
    SYNTAX      ConfdString
    MAX-ACCESS  read-only
    STATUS      current
    DESCRIPTION "Total number of requests categorized as Music Online Category"
    ::= { affirmedServicesContentFilterServiceStatisticssNodeLevelInstContCatEntry 51 }

affirmedServicesContentFilterServiceStatisticssNodeLevelInstContCatNumcategorynews OBJECT-TYPE
    SYNTAX      ConfdString
    MAX-ACCESS  read-only
    STATUS      current
    DESCRIPTION "Total number of requests categorized as News Online Category"
    ::= { affirmedServicesContentFilterServiceStatisticssNodeLevelInstContCatEntry 52 }

affirmedServicesContentFilterServiceStatisticssNodeLevelInstContCatNumcategorynonprofit OBJECT-TYPE
    SYNTAX      ConfdString
    MAX-ACCESS  read-only
    STATUS      current
    DESCRIPTION "Total number of requests categorized as Non Profit Online Category"
    ::= { affirmedServicesContentFilterServiceStatisticssNodeLevelInstContCatEntry 53 }

affirmedServicesContentFilterServiceStatisticssNodeLevelInstContCatNumcategoryobscene OBJECT-TYPE
    SYNTAX      ConfdString
    MAX-ACCESS  read-only
    STATUS      current
    DESCRIPTION "Total number of requests categorized as Obscene Online Category"
    ::= { affirmedServicesContentFilterServiceStatisticssNodeLevelInstContCatEntry 54 }

affirmedServicesContentFilterServiceStatisticssNodeLevelInstContCatNumcategoryoccult OBJECT-TYPE
    SYNTAX      ConfdString
    MAX-ACCESS  read-only
    STATUS      current
    DESCRIPTION "Total number of requests categorized as Occult Online Category"
    ::= { affirmedServicesContentFilterServiceStatisticssNodeLevelInstContCatEntry 55 }

affirmedServicesContentFilterServiceStatisticssNodeLevelInstContCatNumcategoryonlinebackupandstorage OBJECT-TYPE
    SYNTAX      ConfdString
    MAX-ACCESS  read-only
    STATUS      current
    DESCRIPTION "Total number of requests categorized as Online Backup And Storage Online Category"
    ::= { affirmedServicesContentFilterServiceStatisticssNodeLevelInstContCatEntry 56 }

affirmedServicesContentFilterServiceStatisticssNodeLevelInstContCatNumcategorypeertopeer OBJECT-TYPE
    SYNTAX      ConfdString
    MAX-ACCESS  read-only
    STATUS      current
    DESCRIPTION "Total number of requests categorized as PeerToPeer Online Category"
    ::= { affirmedServicesContentFilterServiceStatisticssNodeLevelInstContCatEntry 57 }

affirmedServicesContentFilterServiceStatisticssNodeLevelInstContCatNumcategorypets OBJECT-TYPE
    SYNTAX      ConfdString
    MAX-ACCESS  read-only
    STATUS      current
    DESCRIPTION "Total number of requests categorized as Pets Online Category"
    ::= { affirmedServicesContentFilterServiceStatisticssNodeLevelInstContCatEntry 58 }

affirmedServicesContentFilterServiceStatisticssNodeLevelInstContCatNumcategoryphotography OBJECT-TYPE
    SYNTAX      ConfdString
    MAX-ACCESS  read-only
    STATUS      current
    DESCRIPTION "Total number of requests categorized as Photography Online Category"
    ::= { affirmedServicesContentFilterServiceStatisticssNodeLevelInstContCatEntry 59 }

affirmedServicesContentFilterServiceStatisticssNodeLevelInstContCatNumcategoryplaceholder OBJECT-TYPE
    SYNTAX      ConfdString
    MAX-ACCESS  read-only
    STATUS      current
    DESCRIPTION "Total number of requests categorized as Placeholder Online Category"
    ::= { affirmedServicesContentFilterServiceStatisticssNodeLevelInstContCatEntry 60 }

affirmedServicesContentFilterServiceStatisticssNodeLevelInstContCatNumcategoryplagiarism OBJECT-TYPE
    SYNTAX      ConfdString
    MAX-ACCESS  read-only
    STATUS      current
    DESCRIPTION "Total number of requests categorized as Plagiarism Online Category"
    ::= { affirmedServicesContentFilterServiceStatisticssNodeLevelInstContCatEntry 61 }

affirmedServicesContentFilterServiceStatisticssNodeLevelInstContCatNumcategorypolitics OBJECT-TYPE
    SYNTAX      ConfdString
    MAX-ACCESS  read-only
    STATUS      current
    DESCRIPTION "Total number of requests categorized as Politics Online Category"
    ::= { affirmedServicesContentFilterServiceStatisticssNodeLevelInstContCatEntry 62 }

affirmedServicesContentFilterServiceStatisticssNodeLevelInstContCatNumcategorypornography OBJECT-TYPE
    SYNTAX      ConfdString
    MAX-ACCESS  read-only
    STATUS      current
    DESCRIPTION "Total number of requests categorized as Pornography Online Category"
    ::= { affirmedServicesContentFilterServiceStatisticssNodeLevelInstContCatEntry 63 }

affirmedServicesContentFilterServiceStatisticssNodeLevelInstContCatNumcategoryportal OBJECT-TYPE
    SYNTAX      ConfdString
    MAX-ACCESS  read-only
    STATUS      current
    DESCRIPTION "Total number of requests categorized as Portal Online Category"
    ::= { affirmedServicesContentFilterServiceStatisticssNodeLevelInstContCatEntry 64 }

affirmedServicesContentFilterServiceStatisticssNodeLevelInstContCatNumcategorypersonalsanddating OBJECT-TYPE
    SYNTAX      ConfdString
    MAX-ACCESS  read-only
    STATUS      current
    DESCRIPTION "Total number of requests categorized as Personals And Dating Online Category"
    ::= { affirmedServicesContentFilterServiceStatisticssNodeLevelInstContCatEntry 65 }

affirmedServicesContentFilterServiceStatisticssNodeLevelInstContCatNumcategoryrealestate OBJECT-TYPE
    SYNTAX      ConfdString
    MAX-ACCESS  read-only
    STATUS      current
    DESCRIPTION "Total number of requests categorized as Real Estate Online Category"
    ::= { affirmedServicesContentFilterServiceStatisticssNodeLevelInstContCatEntry 66 }

affirmedServicesContentFilterServiceStatisticssNodeLevelInstContCatNumcategoryreference OBJECT-TYPE
    SYNTAX      ConfdString
    MAX-ACCESS  read-only
    STATUS      current
    DESCRIPTION "Total number of requests categorized as Reference Online Category"
    ::= { affirmedServicesContentFilterServiceStatisticssNodeLevelInstContCatEntry 67 }

affirmedServicesContentFilterServiceStatisticssNodeLevelInstContCatNumcategoryreligion OBJECT-TYPE
    SYNTAX      ConfdString
    MAX-ACCESS  read-only
    STATUS      current
    DESCRIPTION "Total number of requests categorized as Religion Online Category"
    ::= { affirmedServicesContentFilterServiceStatisticssNodeLevelInstContCatEntry 68 }

affirmedServicesContentFilterServiceStatisticssNodeLevelInstContCatNumcategoryremoteaccess OBJECT-TYPE
    SYNTAX      ConfdString
    MAX-ACCESS  read-only
    STATUS      current
    DESCRIPTION "Total number of requests categorized as Remote Access Online Category"
    ::= { affirmedServicesContentFilterServiceStatisticssNodeLevelInstContCatEntry 69 }

affirmedServicesContentFilterServiceStatisticssNodeLevelInstContCatNumcategoryscience OBJECT-TYPE
    SYNTAX      ConfdString
    MAX-ACCESS  read-only
    STATUS      current
    DESCRIPTION "Total number of requests categorized as Science Online Category"
    ::= { affirmedServicesContentFilterServiceStatisticssNodeLevelInstContCatEntry 70 }

affirmedServicesContentFilterServiceStatisticssNodeLevelInstContCatNumcategorysearch OBJECT-TYPE
    SYNTAX      ConfdString
    MAX-ACCESS  read-only
    STATUS      current
    DESCRIPTION "Total number of requests categorized as Search Online Category"
    ::= { affirmedServicesContentFilterServiceStatisticssNodeLevelInstContCatEntry 71 }

affirmedServicesContentFilterServiceStatisticssNodeLevelInstContCatNumcategoryselfharm OBJECT-TYPE
    SYNTAX      ConfdString
    MAX-ACCESS  read-only
    STATUS      current
    DESCRIPTION "Total number of requests categorized as Self Harm Online Category"
    ::= { affirmedServicesContentFilterServiceStatisticssNodeLevelInstContCatEntry 72 }

affirmedServicesContentFilterServiceStatisticssNodeLevelInstContCatNumcategorysexualeducation OBJECT-TYPE
    SYNTAX      ConfdString
    MAX-ACCESS  read-only
    STATUS      current
    DESCRIPTION "Total number of requests categorized as Sexual Education Online Category"
    ::= { affirmedServicesContentFilterServiceStatisticssNodeLevelInstContCatEntry 73 }

affirmedServicesContentFilterServiceStatisticssNodeLevelInstContCatNumcategoryshopping OBJECT-TYPE
    SYNTAX      ConfdString
    MAX-ACCESS  read-only
    STATUS      current
    DESCRIPTION "Total number of requests categorized as Shopping Online Category"
    ::= { affirmedServicesContentFilterServiceStatisticssNodeLevelInstContCatEntry 74 }

affirmedServicesContentFilterServiceStatisticssNodeLevelInstContCatNumcategorysports OBJECT-TYPE
    SYNTAX      ConfdString
    MAX-ACCESS  read-only
    STATUS      current
    DESCRIPTION "Total number of requests categorized as Sports Online Category"
    ::= { affirmedServicesContentFilterServiceStatisticssNodeLevelInstContCatEntry 75 }

affirmedServicesContentFilterServiceStatisticssNodeLevelInstContCatNumcategorystreamingmedia OBJECT-TYPE
    SYNTAX      ConfdString
    MAX-ACCESS  read-only
    STATUS      current
    DESCRIPTION "Total number of requests categorized as Streaming Media Online Category"
    ::= { affirmedServicesContentFilterServiceStatisticssNodeLevelInstContCatEntry 76 }

affirmedServicesContentFilterServiceStatisticssNodeLevelInstContCatNumcategorysuicide OBJECT-TYPE
    SYNTAX      ConfdString
    MAX-ACCESS  read-only
    STATUS      current
    DESCRIPTION "Total number of requests categorized as Suicide Online Category"
    ::= { affirmedServicesContentFilterServiceStatisticssNodeLevelInstContCatEntry 77 }

affirmedServicesContentFilterServiceStatisticssNodeLevelInstContCatNumcategorytechnologyandtelecommunication OBJECT-TYPE
    SYNTAX      ConfdString
    MAX-ACCESS  read-only
    STATUS      current
    DESCRIPTION "Total number of requests categorized as Technology And Telecommunication Online Category"
    ::= { affirmedServicesContentFilterServiceStatisticssNodeLevelInstContCatEntry 78 }

affirmedServicesContentFilterServiceStatisticssNodeLevelInstContCatNumcategorytobacco OBJECT-TYPE
    SYNTAX      ConfdString
    MAX-ACCESS  read-only
    STATUS      current
    DESCRIPTION "Total number of requests categorized as Tobacco Online Category"
    ::= { affirmedServicesContentFilterServiceStatisticssNodeLevelInstContCatEntry 79 }

affirmedServicesContentFilterServiceStatisticssNodeLevelInstContCatNumcategorytravel OBJECT-TYPE
    SYNTAX      ConfdString
    MAX-ACCESS  read-only
    STATUS      current
    DESCRIPTION "Total number of requests categorized as Travel Online Category"
    ::= { affirmedServicesContentFilterServiceStatisticssNodeLevelInstContCatEntry 80 }

affirmedServicesContentFilterServiceStatisticssNodeLevelInstContCatNumcategoryviolence OBJECT-TYPE
    SYNTAX      ConfdString
    MAX-ACCESS  read-only
    STATUS      current
    DESCRIPTION "Total number of requests categorized as Violence Online Category"
    ::= { affirmedServicesContentFilterServiceStatisticssNodeLevelInstContCatEntry 81 }

affirmedServicesContentFilterServiceStatisticssNodeLevelInstContCatNumcategoryvirtualcommunity OBJECT-TYPE
    SYNTAX      ConfdString
    MAX-ACCESS  read-only
    STATUS      current
    DESCRIPTION "Total number of requests categorized as Virtual Community Online Category"
    ::= { affirmedServicesContentFilterServiceStatisticssNodeLevelInstContCatEntry 82 }

affirmedServicesContentFilterServiceStatisticssNodeLevelInstContCatNumcategoryweapons OBJECT-TYPE
    SYNTAX      ConfdString
    MAX-ACCESS  read-only
    STATUS      current
    DESCRIPTION "Total number of requests categorized as Weapons Online Category"
    ::= { affirmedServicesContentFilterServiceStatisticssNodeLevelInstContCatEntry 83 }

affirmedServicesContentFilterServiceStatisticssNodeLevelInstContCatNumcategorywebmail OBJECT-TYPE
    SYNTAX      ConfdString
    MAX-ACCESS  read-only
    STATUS      current
    DESCRIPTION "Total number of requests categorized as Webmail Online Category"
    ::= { affirmedServicesContentFilterServiceStatisticssNodeLevelInstContCatEntry 84 }

affirmedServicesContentFilterServiceStatisticssNodeLevelInstContCatNumcategorywedding OBJECT-TYPE
    SYNTAX      ConfdString
    MAX-ACCESS  read-only
    STATUS      current
    DESCRIPTION "Total number of requests categorized as Wedding Online Category"
    ::= { affirmedServicesContentFilterServiceStatisticssNodeLevelInstContCatEntry 85 }

affirmedServicesContentFilterServiceStatisticssNodeLevelInstContCatNumcategorywirelessbusiness OBJECT-TYPE
    SYNTAX      ConfdString
    MAX-ACCESS  read-only
    STATUS      current
    DESCRIPTION "Total number of requests categorized as Wireless Business Online Category"
    ::= { affirmedServicesContentFilterServiceStatisticssNodeLevelInstContCatEntry 86 }

affirmedServicesContentFilterServiceStatisticssNodeLevelInstContCatNumcategorywirelesschatsms OBJECT-TYPE
    SYNTAX      ConfdString
    MAX-ACCESS  read-only
    STATUS      current
    DESCRIPTION "Total number of requests categorized as Wireless Chat and SMS Online Category"
    ::= { affirmedServicesContentFilterServiceStatisticssNodeLevelInstContCatEntry 87 }

affirmedServicesContentFilterServiceStatisticssNodeLevelInstContCatNumcategorywirelessdynamic OBJECT-TYPE
    SYNTAX      ConfdString
    MAX-ACCESS  read-only
    STATUS      current
    DESCRIPTION "Total number of requests categorized as Wireless Dynamic Online Category"
    ::= { affirmedServicesContentFilterServiceStatisticssNodeLevelInstContCatEntry 88 }

affirmedServicesContentFilterServiceStatisticssNodeLevelInstContCatNumcategorywirelessentertainment OBJECT-TYPE
    SYNTAX      ConfdString
    MAX-ACCESS  read-only
    STATUS      current
    DESCRIPTION "Total number of requests categorized as Wireless Entertainment Online Category"
    ::= { affirmedServicesContentFilterServiceStatisticssNodeLevelInstContCatEntry 89 }

affirmedServicesContentFilterServiceStatisticssNodeLevelInstContCatNumcategorywirelessfinance OBJECT-TYPE
    SYNTAX      ConfdString
    MAX-ACCESS  read-only
    STATUS      current
    DESCRIPTION "Total number of requests categorized as Wireless Finance Online Category"
    ::= { affirmedServicesContentFilterServiceStatisticssNodeLevelInstContCatEntry 90 }

affirmedServicesContentFilterServiceStatisticssNodeLevelInstContCatNumcategorywirelessgambling OBJECT-TYPE
    SYNTAX      ConfdString
    MAX-ACCESS  read-only
    STATUS      current
    DESCRIPTION "Total number of requests categorized as Wireless Gambling Online Category"
    ::= { affirmedServicesContentFilterServiceStatisticssNodeLevelInstContCatEntry 91 }

affirmedServicesContentFilterServiceStatisticssNodeLevelInstContCatNumcategorywirelessnews OBJECT-TYPE
    SYNTAX      ConfdString
    MAX-ACCESS  read-only
    STATUS      current
    DESCRIPTION "Total number of requests categorized as Wireless News Online Category"
    ::= { affirmedServicesContentFilterServiceStatisticssNodeLevelInstContCatEntry 92 }

affirmedServicesContentFilterServiceStatisticssNodeLevelInstContCatNumcategorywirelesspersonalsanddating OBJECT-TYPE
    SYNTAX      ConfdString
    MAX-ACCESS  read-only
    STATUS      current
    DESCRIPTION "Total number of requests categorized as Wireless Personals And Dating Online Category"
    ::= { affirmedServicesContentFilterServiceStatisticssNodeLevelInstContCatEntry 93 }

affirmedServicesContentFilterServiceStatisticssNodeLevelInstContCatNumcategorywirelesspornography OBJECT-TYPE
    SYNTAX      ConfdString
    MAX-ACCESS  read-only
    STATUS      current
    DESCRIPTION "Total number of requests categorized as Wireless Pornography Online Category"
    ::= { affirmedServicesContentFilterServiceStatisticssNodeLevelInstContCatEntry 94 }

affirmedServicesContentFilterServiceStatisticssNodeLevelInstContCatNumcategorywirelesssports OBJECT-TYPE
    SYNTAX      ConfdString
    MAX-ACCESS  read-only
    STATUS      current
    DESCRIPTION "Total number of requests categorized as Wireless Sports Online Category"
    ::= { affirmedServicesContentFilterServiceStatisticssNodeLevelInstContCatEntry 95 }

affirmedServicesContentFilterServiceStatisticssNodeLevelInstContCatNumcategorywirelesstravel OBJECT-TYPE
    SYNTAX      ConfdString
    MAX-ACCESS  read-only
    STATUS      current
    DESCRIPTION "Total number of requests categorized as Wireless Travel Online Category"
    ::= { affirmedServicesContentFilterServiceStatisticssNodeLevelInstContCatEntry 96 }

affirmedServicesContentFilterServiceStatisticssNodeLevelInstContCatNumcategoryunknown OBJECT-TYPE
    SYNTAX      ConfdString
    MAX-ACCESS  read-only
    STATUS      current
    DESCRIPTION "Total number of requests failed categorization"
    ::= { affirmedServicesContentFilterServiceStatisticssNodeLevelInstContCatEntry 97 }

affirmedServicesContentFilterServiceStatisticssNodeLevelInstContCatNumcategorymalware OBJECT-TYPE
    SYNTAX      ConfdString
    MAX-ACCESS  read-only
    STATUS      current
    DESCRIPTION "Total number of requests categorized as Malware Online Category"
    ::= { affirmedServicesContentFilterServiceStatisticssNodeLevelInstContCatEntry 98 }

affirmedServicesContentFilterServiceStatisticssNodeLevelInstContCatNumcategoryphishing OBJECT-TYPE
    SYNTAX      ConfdString
    MAX-ACCESS  read-only
    STATUS      current
    DESCRIPTION "Total number of requests categorized as Phishing Online Category"
    ::= { affirmedServicesContentFilterServiceStatisticssNodeLevelInstContCatEntry 99 }

affirmedServicesContentFilterServiceStatisticssNodeLevelInstContCatNumcategoryiwf OBJECT-TYPE
    SYNTAX      ConfdString
    MAX-ACCESS  read-only
    STATUS      current
    DESCRIPTION "Total number of requests categorized as internet watch foundation CAIC Online Category"
    ::= { affirmedServicesContentFilterServiceStatisticssNodeLevelInstContCatEntry 100 }

affirmedServicesContentFilterServiceStatisticssNodeLevelInstContCatNumcategorynocat OBJECT-TYPE
    SYNTAX      ConfdString
    MAX-ACCESS  read-only
    STATUS      current
    DESCRIPTION "Total number of requests categorized as none of well-known categories"
    ::= { affirmedServicesContentFilterServiceStatisticssNodeLevelInstContCatEntry 101 }

affirmedServicesContentFilterServiceStatisticssNodeLevelInstContCatNumcategoryother OBJECT-TYPE
    SYNTAX      ConfdString
    MAX-ACCESS  read-only
    STATUS      current
    DESCRIPTION "Total number of requests categorized as new category not yet supported by AN3K"
    ::= { affirmedServicesContentFilterServiceStatisticssNodeLevelInstContCatEntry 102 }

affirmedServicesContentFilterServiceStatisticssNodeLevelInstContCatNumcategoryalcoholkids OBJECT-TYPE
    SYNTAX      ConfdString
    MAX-ACCESS  read-only
    STATUS      current
    DESCRIPTION "Total number of requests categorized as Alcohol Kids Online Category"
    ::= { affirmedServicesContentFilterServiceStatisticssNodeLevelInstContCatEntry 103 }

affirmedServicesContentFilterServiceStatisticssNodeLevelInstContCatNumcategorytobaccokids OBJECT-TYPE
    SYNTAX      ConfdString
    MAX-ACCESS  read-only
    STATUS      current
    DESCRIPTION "Total number of requests categorized as Tobacco Kids Online Category"
    ::= { affirmedServicesContentFilterServiceStatisticssNodeLevelInstContCatEntry 104 }

affirmedServicesContentFilterServiceStatisticssNodeLevelInstContCatNumcategorycyberbullying OBJECT-TYPE
    SYNTAX      ConfdString
    MAX-ACCESS  read-only
    STATUS      current
    DESCRIPTION "Total number of requests categorized as Cyberbullying Online Category"
    ::= { affirmedServicesContentFilterServiceStatisticssNodeLevelInstContCatEntry 105 }

affirmedServicesContentFilterServiceStatisticssNodeLevelInstContCatNumhttpsrequestlookups OBJECT-TYPE
    SYNTAX      ConfdString
    MAX-ACCESS  read-only
    STATUS      current
    DESCRIPTION "Total number of HTTPS request Lookups"
    ::= { affirmedServicesContentFilterServiceStatisticssNodeLevelInstContCatEntry 106 }

affirmedServicesContentFilterServiceStatisticssNodeLevelInstContCatNumlookupfailure OBJECT-TYPE
    SYNTAX      ConfdString
    MAX-ACCESS  read-only
    STATUS      current
    DESCRIPTION "Total number of lookup failures"
    ::= { affirmedServicesContentFilterServiceStatisticssNodeLevelInstContCatEntry 107 }

affirmedServicesContentFilterServiceStatisticssNodeLevelInstContCatNumquicrequestlookups OBJECT-TYPE
    SYNTAX      ConfdString
    MAX-ACCESS  read-only
    STATUS      current
    DESCRIPTION "Total number of QUIC request Lookups"
    ::= { affirmedServicesContentFilterServiceStatisticssNodeLevelInstContCatEntry 108 }

affirmedServicesContentFilterServiceStatisticssNodeLevelInstContCatNumcategorybbfcwhitelist OBJECT-TYPE
    SYNTAX      ConfdString
    MAX-ACCESS  read-only
    STATUS      current
    DESCRIPTION "Total number of requests categorized as BBFCWhitelist Online Category"
    ::= { affirmedServicesContentFilterServiceStatisticssNodeLevelInstContCatEntry 109 }

affirmedServicesContentFilterServiceStatisticssNodeLevelInstContCatNumcategorybbfcblacklist OBJECT-TYPE
    SYNTAX      ConfdString
    MAX-ACCESS  read-only
    STATUS      current
    DESCRIPTION "Total number of requests categorized as BBFCBlacklist Online Category"
    ::= { affirmedServicesContentFilterServiceStatisticssNodeLevelInstContCatEntry 110 }

affirmedServicesContentFilterServiceStatisticssNodeLevelInstContCatNumcategorycannabidiol OBJECT-TYPE
    SYNTAX      ConfdString
    MAX-ACCESS  read-only
    STATUS      current
    DESCRIPTION "Total number of requests categorized as Cannabidiol Online Category"
    ::= { affirmedServicesContentFilterServiceStatisticssNodeLevelInstContCatEntry 111 }

affirmedServicesContentFilterServiceStatisticssNodeLevelInstContCatNumcategorycloudinfrastructure OBJECT-TYPE
    SYNTAX      ConfdString
    MAX-ACCESS  read-only
    STATUS      current
    DESCRIPTION "Total number of requests categorized as CloudInfrastructure Online Category"
    ::= { affirmedServicesContentFilterServiceStatisticssNodeLevelInstContCatEntry 112 }

affirmedServicesContentFilterServiceStatisticssNodeLevelInstContCatNumcategoryfireworks OBJECT-TYPE
    SYNTAX      ConfdString
    MAX-ACCESS  read-only
    STATUS      current
    DESCRIPTION "Total number of requests categorized as Fireworks Online Category"
    ::= { affirmedServicesContentFilterServiceStatisticssNodeLevelInstContCatEntry 113 }

affirmedServicesContentFilterServiceStatisticssNodeLevelInstContCatNumcategorylingerie OBJECT-TYPE
    SYNTAX      ConfdString
    MAX-ACCESS  read-only
    STATUS      current
    DESCRIPTION "Total number of requests categorized as Lingerie Online Category"
    ::= { affirmedServicesContentFilterServiceStatisticssNodeLevelInstContCatEntry 114 }

affirmedServicesContentFilterServiceStatisticssNodeLevelInstContCatNumcategorysexualadvice OBJECT-TYPE
    SYNTAX      ConfdString
    MAX-ACCESS  read-only
    STATUS      current
    DESCRIPTION "Total number of requests categorized as SexualAdvice Online Category"
    ::= { affirmedServicesContentFilterServiceStatisticssNodeLevelInstContCatEntry 115 }

affirmedServicesContentFilterServiceStatisticssNodeLevelInstContCatNumcategorytracking OBJECT-TYPE
    SYNTAX      ConfdString
    MAX-ACCESS  read-only
    STATUS      current
    DESCRIPTION "Total number of requests categorized as Tracking Online Category"
    ::= { affirmedServicesContentFilterServiceStatisticssNodeLevelInstContCatEntry 116 }

affirmedServicesContentFilterServiceStatisticssNodeLevelInstContCatNumcategoryukdeablacklist OBJECT-TYPE
    SYNTAX      ConfdString
    MAX-ACCESS  read-only
    STATUS      current
    DESCRIPTION "Total number of requests categorized as UKDEABlacklist Online Category"
    ::= { affirmedServicesContentFilterServiceStatisticssNodeLevelInstContCatEntry 117 }

affirmedServicesContentFilterServiceImportHistoryTable OBJECT-TYPE
    SYNTAX      SEQUENCE OF AffirmedServicesContentFilterServiceImportHistoryEntry
    MAX-ACCESS  not-accessible
    STATUS      current
    DESCRIPTION ""
    ::= { affirmedServicesContentFilterService 1 }

affirmedServicesContentFilterServiceImportHistoryEntry OBJECT-TYPE
    SYNTAX      AffirmedServicesContentFilterServiceImportHistoryEntry
    MAX-ACCESS  not-accessible
    STATUS      current
    DESCRIPTION ""
    INDEX { affirmedServicesContentFilterServiceImportHistoryName }
        ::= { affirmedServicesContentFilterServiceImportHistoryTable 1 }

AffirmedServicesContentFilterServiceImportHistoryEntry ::=
    SEQUENCE {
        affirmedServicesContentFilterServiceImportHistoryName String,
        affirmedServicesContentFilterServiceImportHistoryResult String
    }

affirmedServicesContentFilterServiceImportHistoryName OBJECT-TYPE
    SYNTAX      String
    MAX-ACCESS  not-accessible
    STATUS      current
    DESCRIPTION "category database name"
    ::= { affirmedServicesContentFilterServiceImportHistoryEntry 1 }

affirmedServicesContentFilterServiceImportHistoryResult OBJECT-TYPE
    SYNTAX      String
    MAX-ACCESS  read-only
    STATUS      current
    DESCRIPTION ""
    ::= { affirmedServicesContentFilterServiceImportHistoryEntry 2 }

affirmedServicesContentFilterServiceImportSummaryTable OBJECT-TYPE
    SYNTAX      SEQUENCE OF AffirmedServicesContentFilterServiceImportSummaryEntry
    MAX-ACCESS  not-accessible
    STATUS      current
    DESCRIPTION ""
    ::= { affirmedServicesContentFilterService 2 }

affirmedServicesContentFilterServiceImportSummaryEntry OBJECT-TYPE
    SYNTAX      AffirmedServicesContentFilterServiceImportSummaryEntry
    MAX-ACCESS  not-accessible
    STATUS      current
    DESCRIPTION ""
    INDEX { affirmedServicesContentFilterServiceImportSummaryName }
        ::= { affirmedServicesContentFilterServiceImportSummaryTable 1 }

AffirmedServicesContentFilterServiceImportSummaryEntry ::=
    SEQUENCE {
        affirmedServicesContentFilterServiceImportSummaryName String,
        affirmedServicesContentFilterServiceImportSummaryLastTime String,
        affirmedServicesContentFilterServiceImportSummaryLastResult String,
        affirmedServicesContentFilterServiceImportSummaryLastInstallResult String,
        affirmedServicesContentFilterServiceImportSummaryLastImportType String,
        affirmedServicesContentFilterServiceImportSummaryLastImportNum Unsigned32,
        affirmedServicesContentFilterServiceImportSummaryLastSize Unsigned32,
        affirmedServicesContentFilterServiceImportSummaryTotalEntry Unsigned32,
        affirmedServicesContentFilterServiceImportSummaryVersion String,
        affirmedServicesContentFilterServiceImportSummaryNextTime String
    }

affirmedServicesContentFilterServiceImportSummaryName OBJECT-TYPE
    SYNTAX      String
    MAX-ACCESS  not-accessible
    STATUS      current
    DESCRIPTION "category database name"
    ::= { affirmedServicesContentFilterServiceImportSummaryEntry 1 }

affirmedServicesContentFilterServiceImportSummaryLastTime OBJECT-TYPE
    SYNTAX      String
    MAX-ACCESS  read-only
    STATUS      current
    DESCRIPTION "Last Import Time"
    ::= { affirmedServicesContentFilterServiceImportSummaryEntry 2 }

affirmedServicesContentFilterServiceImportSummaryLastResult OBJECT-TYPE
    SYNTAX      String
    MAX-ACCESS  read-only
    STATUS      current
    DESCRIPTION "Last Import Result"
    ::= { affirmedServicesContentFilterServiceImportSummaryEntry 3 }

affirmedServicesContentFilterServiceImportSummaryLastInstallResult OBJECT-TYPE
    SYNTAX      String
    MAX-ACCESS  read-only
    STATUS      current
    DESCRIPTION "Last Install Result"
    ::= { affirmedServicesContentFilterServiceImportSummaryEntry 4 }

affirmedServicesContentFilterServiceImportSummaryLastImportType OBJECT-TYPE
    SYNTAX      String
    MAX-ACCESS  read-only
    STATUS      current
    DESCRIPTION "Last Import Type"
    ::= { affirmedServicesContentFilterServiceImportSummaryEntry 5 }

affirmedServicesContentFilterServiceImportSummaryLastImportNum OBJECT-TYPE
    SYNTAX      Unsigned32
    MAX-ACCESS  read-only
    STATUS      current
    DESCRIPTION "Last Import Number"
    ::= { affirmedServicesContentFilterServiceImportSummaryEntry 6 }

affirmedServicesContentFilterServiceImportSummaryLastSize OBJECT-TYPE
    SYNTAX      Unsigned32
    MAX-ACCESS  read-only
    STATUS      current
    DESCRIPTION "Database File Size"
    ::= { affirmedServicesContentFilterServiceImportSummaryEntry 7 }

affirmedServicesContentFilterServiceImportSummaryTotalEntry OBJECT-TYPE
    SYNTAX      Unsigned32
    MAX-ACCESS  read-only
    STATUS      current
    DESCRIPTION "Database Entries"
    ::= { affirmedServicesContentFilterServiceImportSummaryEntry 8 }

affirmedServicesContentFilterServiceImportSummaryVersion OBJECT-TYPE
    SYNTAX      String
    MAX-ACCESS  read-only
    STATUS      current
    DESCRIPTION "Database Version"
    ::= { affirmedServicesContentFilterServiceImportSummaryEntry 9 }

affirmedServicesContentFilterServiceImportSummaryNextTime OBJECT-TYPE
    SYNTAX      String
    MAX-ACCESS  read-only
    STATUS      current
    DESCRIPTION "Next Scheduled Import Time"
    ::= { affirmedServicesContentFilterServiceImportSummaryEntry 10 }

affirmedServicesContentHttpProxyServiceServiceDataFlowTable OBJECT-TYPE
    SYNTAX      SEQUENCE OF AffirmedServicesContentHttpProxyServiceServiceDataFlowEntry
    MAX-ACCESS  not-accessible
    STATUS      current
    DESCRIPTION ""
    ::= { affirmedServicesContentHttpProxyService 1 }

affirmedServicesContentHttpProxyServiceServiceDataFlowEntry OBJECT-TYPE
    SYNTAX      AffirmedServicesContentHttpProxyServiceServiceDataFlowEntry
    MAX-ACCESS  not-accessible
    STATUS      current
    DESCRIPTION ""
    INDEX { affirmedServicesContentHttpProxyServiceServiceDataFlowHttpProxy, affirmedServicesContentHttpProxyServiceServiceDataFlowHttpIpFlowPriority, affirmedServicesContentHttpProxyServiceServiceDataFlowServiceRulePriority, affirmedServicesContentHttpProxyServiceServiceDataFlowHttpIpFlow, affirmedServicesContentHttpProxyServiceServiceDataFlowServiceRule }
        ::= { affirmedServicesContentHttpProxyServiceServiceDataFlowTable 1 }

AffirmedServicesContentHttpProxyServiceServiceDataFlowEntry ::=
    SEQUENCE {
        affirmedServicesContentHttpProxyServiceServiceDataFlowHttpProxy String,
        affirmedServicesContentHttpProxyServiceServiceDataFlowHttpIpFlowPriority Unsigned32,
        affirmedServicesContentHttpProxyServiceServiceDataFlowServiceRulePriority Unsigned32,
        affirmedServicesContentHttpProxyServiceServiceDataFlowHttpIpFlow String,
        affirmedServicesContentHttpProxyServiceServiceDataFlowServiceRule String,
        affirmedServicesContentHttpProxyServiceServiceDataFlowHttpIpFlowId Unsigned32,
        affirmedServicesContentHttpProxyServiceServiceDataFlowServiceRuleId Unsigned32
    }

affirmedServicesContentHttpProxyServiceServiceDataFlowHttpProxy OBJECT-TYPE
    SYNTAX      String
    MAX-ACCESS  not-accessible
    STATUS      current
    DESCRIPTION "the name of the multi-protocol-proxy"
    ::= { affirmedServicesContentHttpProxyServiceServiceDataFlowEntry 1 }

affirmedServicesContentHttpProxyServiceServiceDataFlowHttpIpFlowPriority OBJECT-TYPE
    SYNTAX      Unsigned32
    MAX-ACCESS  not-accessible
    STATUS      current
    DESCRIPTION "the priority of the http-ip-flow"
    ::= { affirmedServicesContentHttpProxyServiceServiceDataFlowEntry 2 }

affirmedServicesContentHttpProxyServiceServiceDataFlowServiceRulePriority OBJECT-TYPE
    SYNTAX      Unsigned32
    MAX-ACCESS  not-accessible
    STATUS      current
    DESCRIPTION "the priority of the service-rule"
    ::= { affirmedServicesContentHttpProxyServiceServiceDataFlowEntry 3 }

affirmedServicesContentHttpProxyServiceServiceDataFlowHttpIpFlow OBJECT-TYPE
    SYNTAX      String
    MAX-ACCESS  not-accessible
    STATUS      current
    DESCRIPTION "the name of the http-ip-flow"
    ::= { affirmedServicesContentHttpProxyServiceServiceDataFlowEntry 4 }

affirmedServicesContentHttpProxyServiceServiceDataFlowServiceRule OBJECT-TYPE
    SYNTAX      String
    MAX-ACCESS  not-accessible
    STATUS      current
    DESCRIPTION "the name of the service-rule"
    ::= { affirmedServicesContentHttpProxyServiceServiceDataFlowEntry 5 }

affirmedServicesContentHttpProxyServiceServiceDataFlowHttpIpFlowId OBJECT-TYPE
    SYNTAX      Unsigned32
    MAX-ACCESS  read-only
    STATUS      current
    DESCRIPTION "the internal ID of the http-ip-flow, used to identify PDN-session service-data-flows {session-id, service-type=multi-protocol-proxy, http-ip-flow-id, service-rule-id}"
    ::= { affirmedServicesContentHttpProxyServiceServiceDataFlowEntry 6 }

affirmedServicesContentHttpProxyServiceServiceDataFlowServiceRuleId OBJECT-TYPE
    SYNTAX      Unsigned32
    MAX-ACCESS  read-only
    STATUS      current
    DESCRIPTION "the internal ID of the service-rule, used to identify PDN-session service-data-flows {session-id, service-type=multi-protocol-proxy, http-ip-flow-id, service-rule-id}"
    ::= { affirmedServicesContentHttpProxyServiceServiceDataFlowEntry 7 }

affirmedServicesContentHttpProxyServiceLtmiKeyStatsHistoryTable OBJECT-TYPE
    SYNTAX      SEQUENCE OF AffirmedServicesContentHttpProxyServiceLtmiKeyStatsHistoryEntry
    MAX-ACCESS  not-accessible
    STATUS      current
    DESCRIPTION ""
    ::= { affirmedServicesContentHttpProxyServiceLtmiKeyStats 1 }

affirmedServicesContentHttpProxyServiceLtmiKeyStatsHistoryEntry OBJECT-TYPE
    SYNTAX      AffirmedServicesContentHttpProxyServiceLtmiKeyStatsHistoryEntry
    MAX-ACCESS  not-accessible
    STATUS      current
    DESCRIPTION ""
    INDEX { affirmedServicesContentHttpProxyServiceLtmiKeyStatsHistoryName }
        ::= { affirmedServicesContentHttpProxyServiceLtmiKeyStatsHistoryTable 1 }

AffirmedServicesContentHttpProxyServiceLtmiKeyStatsHistoryEntry ::=
    SEQUENCE {
        affirmedServicesContentHttpProxyServiceLtmiKeyStatsHistoryName String,
        affirmedServicesContentHttpProxyServiceLtmiKeyStatsHistoryResult String
    }

affirmedServicesContentHttpProxyServiceLtmiKeyStatsHistoryName OBJECT-TYPE
    SYNTAX      String
    MAX-ACCESS  not-accessible
    STATUS      current
    DESCRIPTION ""
    ::= { affirmedServicesContentHttpProxyServiceLtmiKeyStatsHistoryEntry 1 }

affirmedServicesContentHttpProxyServiceLtmiKeyStatsHistoryResult OBJECT-TYPE
    SYNTAX      String
    MAX-ACCESS  read-only
    STATUS      current
    DESCRIPTION ""
    ::= { affirmedServicesContentHttpProxyServiceLtmiKeyStatsHistoryEntry 2 }

affirmedServicesContentHttpProxyServiceLtmiKeyStatsStatusTable OBJECT-TYPE
    SYNTAX      SEQUENCE OF AffirmedServicesContentHttpProxyServiceLtmiKeyStatsStatusEntry
    MAX-ACCESS  not-accessible
    STATUS      current
    DESCRIPTION ""
    ::= { affirmedServicesContentHttpProxyServiceLtmiKeyStats 2 }

affirmedServicesContentHttpProxyServiceLtmiKeyStatsStatusEntry OBJECT-TYPE
    SYNTAX      AffirmedServicesContentHttpProxyServiceLtmiKeyStatsStatusEntry
    MAX-ACCESS  not-accessible
    STATUS      current
    DESCRIPTION ""
    INDEX { affirmedServicesContentHttpProxyServiceLtmiKeyStatsStatusName }
        ::= { affirmedServicesContentHttpProxyServiceLtmiKeyStatsStatusTable 1 }

AffirmedServicesContentHttpProxyServiceLtmiKeyStatsStatusEntry ::=
    SEQUENCE {
        affirmedServicesContentHttpProxyServiceLtmiKeyStatsStatusName String,
        affirmedServicesContentHttpProxyServiceLtmiKeyStatsStatusLastTime String,
        affirmedServicesContentHttpProxyServiceLtmiKeyStatsStatusLastResult String,
        affirmedServicesContentHttpProxyServiceLtmiKeyStatsStatusLastImportType String,
        affirmedServicesContentHttpProxyServiceLtmiKeyStatsStatusLastImportNum Unsigned32,
        affirmedServicesContentHttpProxyServiceLtmiKeyStatsStatusLastSize Unsigned32,
        affirmedServicesContentHttpProxyServiceLtmiKeyStatsStatusNextTime String,
        affirmedServicesContentHttpProxyServiceLtmiKeyStatsStatusTotalEntry Unsigned32,
        affirmedServicesContentHttpProxyServiceLtmiKeyStatsStatusEntries String,
        affirmedServicesContentHttpProxyServiceLtmiKeyStatsStatusImportFileName String
    }

affirmedServicesContentHttpProxyServiceLtmiKeyStatsStatusName OBJECT-TYPE
    SYNTAX      String
    MAX-ACCESS  not-accessible
    STATUS      current
    DESCRIPTION ""
    ::= { affirmedServicesContentHttpProxyServiceLtmiKeyStatsStatusEntry 1 }

affirmedServicesContentHttpProxyServiceLtmiKeyStatsStatusLastTime OBJECT-TYPE
    SYNTAX      String
    MAX-ACCESS  read-only
    STATUS      current
    DESCRIPTION "Last Import Time"
    ::= { affirmedServicesContentHttpProxyServiceLtmiKeyStatsStatusEntry 2 }

affirmedServicesContentHttpProxyServiceLtmiKeyStatsStatusLastResult OBJECT-TYPE
    SYNTAX      String
    MAX-ACCESS  read-only
    STATUS      current
    DESCRIPTION "Last Import Result"
    ::= { affirmedServicesContentHttpProxyServiceLtmiKeyStatsStatusEntry 3 }

affirmedServicesContentHttpProxyServiceLtmiKeyStatsStatusLastImportType OBJECT-TYPE
    SYNTAX      String
    MAX-ACCESS  read-only
    STATUS      current
    DESCRIPTION "Import Type"
    ::= { affirmedServicesContentHttpProxyServiceLtmiKeyStatsStatusEntry 4 }

affirmedServicesContentHttpProxyServiceLtmiKeyStatsStatusLastImportNum OBJECT-TYPE
    SYNTAX      Unsigned32
    MAX-ACCESS  read-only
    STATUS      current
    DESCRIPTION "Last Import Number"
    ::= { affirmedServicesContentHttpProxyServiceLtmiKeyStatsStatusEntry 5 }

affirmedServicesContentHttpProxyServiceLtmiKeyStatsStatusLastSize OBJECT-TYPE
    SYNTAX      Unsigned32
    MAX-ACCESS  read-only
    STATUS      current
    DESCRIPTION "Last Import File Size(Bytes)"
    ::= { affirmedServicesContentHttpProxyServiceLtmiKeyStatsStatusEntry 6 }

affirmedServicesContentHttpProxyServiceLtmiKeyStatsStatusNextTime OBJECT-TYPE
    SYNTAX      String
    MAX-ACCESS  read-only
    STATUS      current
    DESCRIPTION "Next Scheduled Import Time"
    ::= { affirmedServicesContentHttpProxyServiceLtmiKeyStatsStatusEntry 7 }

affirmedServicesContentHttpProxyServiceLtmiKeyStatsStatusTotalEntry OBJECT-TYPE
    SYNTAX      Unsigned32
    MAX-ACCESS  read-only
    STATUS      current
    DESCRIPTION "Number Of Entries"
    ::= { affirmedServicesContentHttpProxyServiceLtmiKeyStatsStatusEntry 8 }

affirmedServicesContentHttpProxyServiceLtmiKeyStatsStatusEntries OBJECT-TYPE
    SYNTAX      String
    MAX-ACCESS  read-only
    STATUS      current
    DESCRIPTION "Entries"
    ::= { affirmedServicesContentHttpProxyServiceLtmiKeyStatsStatusEntry 9 }

affirmedServicesContentHttpProxyServiceLtmiKeyStatsStatusImportFileName OBJECT-TYPE
    SYNTAX      String
    MAX-ACCESS  read-only
    STATUS      current
    DESCRIPTION "Import URL"
    ::= { affirmedServicesContentHttpProxyServiceLtmiKeyStatsStatusEntry 10 }

affirmedServicesContentHttpProxyServiceStatisticsCluster-levelConnectionTable OBJECT-TYPE
    SYNTAX      SEQUENCE OF AffirmedServicesContentHttpProxyServiceStatisticsCluster-levelConnectionEntry
    MAX-ACCESS  not-accessible
    STATUS      current
    DESCRIPTION ""
    ::= { affirmedServicesContentHttpProxyServiceStatisticsCluster-level 2 }

affirmedServicesContentHttpProxyServiceStatisticsCluster-levelConnectionEntry OBJECT-TYPE
    SYNTAX      AffirmedServicesContentHttpProxyServiceStatisticsCluster-levelConnectionEntry
    MAX-ACCESS  not-accessible
    STATUS      current
    DESCRIPTION ""
    INDEX { affirmedServicesContentHttpProxyServiceStatisticsCluster-levelConnectionChassis }
        ::= { affirmedServicesContentHttpProxyServiceStatisticsCluster-levelConnectionTable 1 }

AffirmedServicesContentHttpProxyServiceStatisticsCluster-levelConnectionEntry ::=
    SEQUENCE {
        affirmedServicesContentHttpProxyServiceStatisticsCluster-levelConnectionChassis Unsigned32,
        affirmedServicesContentHttpProxyServiceStatisticsCluster-levelConnectionNumtotalclientconnections ConfdString,
        affirmedServicesContentHttpProxyServiceStatisticsCluster-levelConnectionNumcurrentclientconnections ConfdString,
        affirmedServicesContentHttpProxyServiceStatisticsCluster-levelConnectionNumkeepaliverequested ConfdString,
        affirmedServicesContentHttpProxyServiceStatisticsCluster-levelConnectionNumpersistentclientconnections ConfdString,
        affirmedServicesContentHttpProxyServiceStatisticsCluster-levelConnectionNumreusedclientconnections ConfdString,
        affirmedServicesContentHttpProxyServiceStatisticsCluster-levelConnectionNumpipelinedclientconnections ConfdString,
        affirmedServicesContentHttpProxyServiceStatisticsCluster-levelConnectionNumipv4clientconnections ConfdString,
        affirmedServicesContentHttpProxyServiceStatisticsCluster-levelConnectionNumipv6clientconnections ConfdString,
        affirmedServicesContentHttpProxyServiceStatisticsCluster-levelConnectionNumtotalserverconnections ConfdString,
        affirmedServicesContentHttpProxyServiceStatisticsCluster-levelConnectionNumcurrentserverconnections ConfdString,
        affirmedServicesContentHttpProxyServiceStatisticsCluster-levelConnectionNumipv4serverconnections ConfdString,
        affirmedServicesContentHttpProxyServiceStatisticsCluster-levelConnectionNumipv6serverconnections ConfdString,
        affirmedServicesContentHttpProxyServiceStatisticsCluster-levelConnectionNumcurrentlyidleserverconnections ConfdString,
        affirmedServicesContentHttpProxyServiceStatisticsCluster-levelConnectionNumreusedsameclientserverconnections ConfdString,
        affirmedServicesContentHttpProxyServiceStatisticsCluster-levelConnectionNumreusedserverconnections ConfdString,
        affirmedServicesContentHttpProxyServiceStatisticsCluster-levelConnectionNumprefipfamilyusedserverconnections ConfdString,
        affirmedServicesContentHttpProxyServiceStatisticsCluster-levelConnectionNumprefipfamilyunavailableserverconnections ConfdString,
        affirmedServicesContentHttpProxyServiceStatisticsCluster-levelConnectionNumtotalsmppconnections ConfdString,
        affirmedServicesContentHttpProxyServiceStatisticsCluster-levelConnectionNumcurrentsmppconnections ConfdString,
        affirmedServicesContentHttpProxyServiceStatisticsCluster-levelConnectionNumipv4smppconnections ConfdString,
        affirmedServicesContentHttpProxyServiceStatisticsCluster-levelConnectionNumipv6smppconnections ConfdString,
        affirmedServicesContentHttpProxyServiceStatisticsCluster-levelConnectionNumcurrentlyidlesmppconnections ConfdString,
        affirmedServicesContentHttpProxyServiceStatisticsCluster-levelConnectionNumreusedsameclientsmppconnections ConfdString,
        affirmedServicesContentHttpProxyServiceStatisticsCluster-levelConnectionNumreusedsmppconnections ConfdString,
        affirmedServicesContentHttpProxyServiceStatisticsCluster-levelConnectionNumconnectionerrorsmppconnections ConfdString,
        affirmedServicesContentHttpProxyServiceStatisticsCluster-levelConnectionNumbinderrorsmppconnections ConfdString,
        affirmedServicesContentHttpProxyServiceStatisticsCluster-levelConnectionNumsenderrorsmppconnections ConfdString,
        affirmedServicesContentHttpProxyServiceStatisticsCluster-levelConnectionNumunbinderrorsmppconnections ConfdString,
        affirmedServicesContentHttpProxyServiceStatisticsCluster-levelConnectionNumiptransparentserverconnections ConfdString,
        affirmedServicesContentHttpProxyServiceStatisticsCluster-levelConnectionNumnonhttpclientconnections ConfdString,
        affirmedServicesContentHttpProxyServiceStatisticsCluster-levelConnectionNumnorequestclientconnnections ConfdString,
        affirmedServicesContentHttpProxyServiceStatisticsCluster-levelConnectionNumreversehandoffclientconnnections ConfdString,
        affirmedServicesContentHttpProxyServiceStatisticsCluster-levelConnectionNumfailuresclientconnnections ConfdString,
        affirmedServicesContentHttpProxyServiceStatisticsCluster-levelConnectionNumfastopenattempts ConfdString,
        affirmedServicesContentHttpProxyServiceStatisticsCluster-levelConnectionNumfastopensuccesses ConfdString,
        affirmedServicesContentHttpProxyServiceStatisticsCluster-levelConnectionNumfastopenfailureinitconn ConfdString,
        affirmedServicesContentHttpProxyServiceStatisticsCluster-levelConnectionNumfastopenfailureduplicate ConfdString,
        affirmedServicesContentHttpProxyServiceStatisticsCluster-levelConnectionNumfastopenfailurealreadycreated ConfdString,
        affirmedServicesContentHttpProxyServiceStatisticsCluster-levelConnectionNumfastopenfailurepolicy ConfdString,
        affirmedServicesContentHttpProxyServiceStatisticsCluster-levelConnectionNumfastopenfailureother ConfdString,
        affirmedServicesContentHttpProxyServiceStatisticsCluster-levelConnectionNumfastopenlistfull ConfdString,
        affirmedServicesContentHttpProxyServiceStatisticsCluster-levelConnectionNumfastopencurrentpendingconn ConfdString,
        affirmedServicesContentHttpProxyServiceStatisticsCluster-levelConnectionNumfastopenaging ConfdString
    }

affirmedServicesContentHttpProxyServiceStatisticsCluster-levelConnectionChassis OBJECT-TYPE
    SYNTAX      Unsigned32
    MAX-ACCESS  not-accessible
    STATUS      current
    DESCRIPTION "chassis ID"
    ::= { affirmedServicesContentHttpProxyServiceStatisticsCluster-levelConnectionEntry 1 }

affirmedServicesContentHttpProxyServiceStatisticsCluster-levelConnectionNumtotalclientconnections OBJECT-TYPE
    SYNTAX      ConfdString
    MAX-ACCESS  read-only
    STATUS      current
    DESCRIPTION "Total number of client connections"
    ::= { affirmedServicesContentHttpProxyServiceStatisticsCluster-levelConnectionEntry 2 }

affirmedServicesContentHttpProxyServiceStatisticsCluster-levelConnectionNumcurrentclientconnections OBJECT-TYPE
    SYNTAX      ConfdString
    MAX-ACCESS  read-only
    STATUS      current
    DESCRIPTION "Total number of client connections currently in use"
    ::= { affirmedServicesContentHttpProxyServiceStatisticsCluster-levelConnectionEntry 3 }

affirmedServicesContentHttpProxyServiceStatisticsCluster-levelConnectionNumkeepaliverequested OBJECT-TYPE
    SYNTAX      ConfdString
    MAX-ACCESS  read-only
    STATUS      current
    DESCRIPTION "Total number of keep-alive requested from client"
    ::= { affirmedServicesContentHttpProxyServiceStatisticsCluster-levelConnectionEntry 4 }

affirmedServicesContentHttpProxyServiceStatisticsCluster-levelConnectionNumpersistentclientconnections OBJECT-TYPE
    SYNTAX      ConfdString
    MAX-ACCESS  read-only
    STATUS      current
    DESCRIPTION "Total number of persistent client connections"
    ::= { affirmedServicesContentHttpProxyServiceStatisticsCluster-levelConnectionEntry 5 }

affirmedServicesContentHttpProxyServiceStatisticsCluster-levelConnectionNumreusedclientconnections OBJECT-TYPE
    SYNTAX      ConfdString
    MAX-ACCESS  read-only
    STATUS      current
    DESCRIPTION "Total number of reused client connections"
    ::= { affirmedServicesContentHttpProxyServiceStatisticsCluster-levelConnectionEntry 6 }

affirmedServicesContentHttpProxyServiceStatisticsCluster-levelConnectionNumpipelinedclientconnections OBJECT-TYPE
    SYNTAX      ConfdString
    MAX-ACCESS  read-only
    STATUS      current
    DESCRIPTION "Total number of pipelined client connections"
    ::= { affirmedServicesContentHttpProxyServiceStatisticsCluster-levelConnectionEntry 7 }

affirmedServicesContentHttpProxyServiceStatisticsCluster-levelConnectionNumipv4clientconnections OBJECT-TYPE
    SYNTAX      ConfdString
    MAX-ACCESS  read-only
    STATUS      current
    DESCRIPTION "Total number of IPv4 client connections"
    ::= { affirmedServicesContentHttpProxyServiceStatisticsCluster-levelConnectionEntry 8 }

affirmedServicesContentHttpProxyServiceStatisticsCluster-levelConnectionNumipv6clientconnections OBJECT-TYPE
    SYNTAX      ConfdString
    MAX-ACCESS  read-only
    STATUS      current
    DESCRIPTION "Total number of IPv6 client connections"
    ::= { affirmedServicesContentHttpProxyServiceStatisticsCluster-levelConnectionEntry 9 }

affirmedServicesContentHttpProxyServiceStatisticsCluster-levelConnectionNumtotalserverconnections OBJECT-TYPE
    SYNTAX      ConfdString
    MAX-ACCESS  read-only
    STATUS      current
    DESCRIPTION "Total number of server connections"
    ::= { affirmedServicesContentHttpProxyServiceStatisticsCluster-levelConnectionEntry 10 }

affirmedServicesContentHttpProxyServiceStatisticsCluster-levelConnectionNumcurrentserverconnections OBJECT-TYPE
    SYNTAX      ConfdString
    MAX-ACCESS  read-only
    STATUS      current
    DESCRIPTION "Total number of server connections currently in use"
    ::= { affirmedServicesContentHttpProxyServiceStatisticsCluster-levelConnectionEntry 11 }

affirmedServicesContentHttpProxyServiceStatisticsCluster-levelConnectionNumipv4serverconnections OBJECT-TYPE
    SYNTAX      ConfdString
    MAX-ACCESS  read-only
    STATUS      current
    DESCRIPTION "Total number of IPv4 server connections"
    ::= { affirmedServicesContentHttpProxyServiceStatisticsCluster-levelConnectionEntry 12 }

affirmedServicesContentHttpProxyServiceStatisticsCluster-levelConnectionNumipv6serverconnections OBJECT-TYPE
    SYNTAX      ConfdString
    MAX-ACCESS  read-only
    STATUS      current
    DESCRIPTION "Total number of IPv6 server connections"
    ::= { affirmedServicesContentHttpProxyServiceStatisticsCluster-levelConnectionEntry 13 }

affirmedServicesContentHttpProxyServiceStatisticsCluster-levelConnectionNumcurrentlyidleserverconnections OBJECT-TYPE
    SYNTAX      ConfdString
    MAX-ACCESS  read-only
    STATUS      current
    DESCRIPTION "The number of idle server connections in the server connection pool"
    ::= { affirmedServicesContentHttpProxyServiceStatisticsCluster-levelConnectionEntry 14 }

affirmedServicesContentHttpProxyServiceStatisticsCluster-levelConnectionNumreusedsameclientserverconnections OBJECT-TYPE
    SYNTAX      ConfdString
    MAX-ACCESS  read-only
    STATUS      current
    DESCRIPTION "The number of times server connections were reused by same client connections"
    ::= { affirmedServicesContentHttpProxyServiceStatisticsCluster-levelConnectionEntry 15 }

affirmedServicesContentHttpProxyServiceStatisticsCluster-levelConnectionNumreusedserverconnections OBJECT-TYPE
    SYNTAX      ConfdString
    MAX-ACCESS  read-only
    STATUS      current
    DESCRIPTION "The number of times idle server connections were reused"
    ::= { affirmedServicesContentHttpProxyServiceStatisticsCluster-levelConnectionEntry 16 }

affirmedServicesContentHttpProxyServiceStatisticsCluster-levelConnectionNumprefipfamilyusedserverconnections OBJECT-TYPE
    SYNTAX      ConfdString
    MAX-ACCESS  read-only
    STATUS      current
    DESCRIPTION "Total number of preferred ip family used server connections"
    ::= { affirmedServicesContentHttpProxyServiceStatisticsCluster-levelConnectionEntry 17 }

affirmedServicesContentHttpProxyServiceStatisticsCluster-levelConnectionNumprefipfamilyunavailableserverconnections OBJECT-TYPE
    SYNTAX      ConfdString
    MAX-ACCESS  read-only
    STATUS      current
    DESCRIPTION "Total number of preferred ip family unavailable server connections"
    ::= { affirmedServicesContentHttpProxyServiceStatisticsCluster-levelConnectionEntry 18 }

affirmedServicesContentHttpProxyServiceStatisticsCluster-levelConnectionNumtotalsmppconnections OBJECT-TYPE
    SYNTAX      ConfdString
    MAX-ACCESS  read-only
    STATUS      current
    DESCRIPTION "Total number of smpp connections"
    ::= { affirmedServicesContentHttpProxyServiceStatisticsCluster-levelConnectionEntry 19 }

affirmedServicesContentHttpProxyServiceStatisticsCluster-levelConnectionNumcurrentsmppconnections OBJECT-TYPE
    SYNTAX      ConfdString
    MAX-ACCESS  read-only
    STATUS      current
    DESCRIPTION "Total number of smpp connections currently in use"
    ::= { affirmedServicesContentHttpProxyServiceStatisticsCluster-levelConnectionEntry 20 }

affirmedServicesContentHttpProxyServiceStatisticsCluster-levelConnectionNumipv4smppconnections OBJECT-TYPE
    SYNTAX      ConfdString
    MAX-ACCESS  read-only
    STATUS      current
    DESCRIPTION "Total number of IPv4 smpp connections"
    ::= { affirmedServicesContentHttpProxyServiceStatisticsCluster-levelConnectionEntry 21 }

affirmedServicesContentHttpProxyServiceStatisticsCluster-levelConnectionNumipv6smppconnections OBJECT-TYPE
    SYNTAX      ConfdString
    MAX-ACCESS  read-only
    STATUS      current
    DESCRIPTION "Total number of IPv6 smpp connections"
    ::= { affirmedServicesContentHttpProxyServiceStatisticsCluster-levelConnectionEntry 22 }

affirmedServicesContentHttpProxyServiceStatisticsCluster-levelConnectionNumcurrentlyidlesmppconnections OBJECT-TYPE
    SYNTAX      ConfdString
    MAX-ACCESS  read-only
    STATUS      current
    DESCRIPTION "The number of idle smpp connections in the server connection pool"
    ::= { affirmedServicesContentHttpProxyServiceStatisticsCluster-levelConnectionEntry 23 }

affirmedServicesContentHttpProxyServiceStatisticsCluster-levelConnectionNumreusedsameclientsmppconnections OBJECT-TYPE
    SYNTAX      ConfdString
    MAX-ACCESS  read-only
    STATUS      current
    DESCRIPTION "The number of times smpp connections were reused by same client connections"
    ::= { affirmedServicesContentHttpProxyServiceStatisticsCluster-levelConnectionEntry 24 }

affirmedServicesContentHttpProxyServiceStatisticsCluster-levelConnectionNumreusedsmppconnections OBJECT-TYPE
    SYNTAX      ConfdString
    MAX-ACCESS  read-only
    STATUS      current
    DESCRIPTION "The number of times idle smpp connections were reused"
    ::= { affirmedServicesContentHttpProxyServiceStatisticsCluster-levelConnectionEntry 25 }

affirmedServicesContentHttpProxyServiceStatisticsCluster-levelConnectionNumconnectionerrorsmppconnections OBJECT-TYPE
    SYNTAX      ConfdString
    MAX-ACCESS  read-only
    STATUS      current
    DESCRIPTION "The number of smpp connection errors"
    ::= { affirmedServicesContentHttpProxyServiceStatisticsCluster-levelConnectionEntry 26 }

affirmedServicesContentHttpProxyServiceStatisticsCluster-levelConnectionNumbinderrorsmppconnections OBJECT-TYPE
    SYNTAX      ConfdString
    MAX-ACCESS  read-only
    STATUS      current
    DESCRIPTION "The number of smpp bind errors"
    ::= { affirmedServicesContentHttpProxyServiceStatisticsCluster-levelConnectionEntry 27 }

affirmedServicesContentHttpProxyServiceStatisticsCluster-levelConnectionNumsenderrorsmppconnections OBJECT-TYPE
    SYNTAX      ConfdString
    MAX-ACCESS  read-only
    STATUS      current
    DESCRIPTION "The number of smpp send errors"
    ::= { affirmedServicesContentHttpProxyServiceStatisticsCluster-levelConnectionEntry 28 }

affirmedServicesContentHttpProxyServiceStatisticsCluster-levelConnectionNumunbinderrorsmppconnections OBJECT-TYPE
    SYNTAX      ConfdString
    MAX-ACCESS  read-only
    STATUS      current
    DESCRIPTION "The number of smpp unbind errors"
    ::= { affirmedServicesContentHttpProxyServiceStatisticsCluster-levelConnectionEntry 29 }

affirmedServicesContentHttpProxyServiceStatisticsCluster-levelConnectionNumiptransparentserverconnections OBJECT-TYPE
    SYNTAX      ConfdString
    MAX-ACCESS  read-only
    STATUS      current
    DESCRIPTION "Total number of IP transparent server connections"
    ::= { affirmedServicesContentHttpProxyServiceStatisticsCluster-levelConnectionEntry 30 }

affirmedServicesContentHttpProxyServiceStatisticsCluster-levelConnectionNumnonhttpclientconnections OBJECT-TYPE
    SYNTAX      ConfdString
    MAX-ACCESS  read-only
    STATUS      current
    DESCRIPTION "Total number of client connections with non-http request"
    ::= { affirmedServicesContentHttpProxyServiceStatisticsCluster-levelConnectionEntry 31 }

affirmedServicesContentHttpProxyServiceStatisticsCluster-levelConnectionNumnorequestclientconnnections OBJECT-TYPE
    SYNTAX      ConfdString
    MAX-ACCESS  read-only
    STATUS      current
    DESCRIPTION "Total number of client connections with request receive timeout"
    ::= { affirmedServicesContentHttpProxyServiceStatisticsCluster-levelConnectionEntry 32 }

affirmedServicesContentHttpProxyServiceStatisticsCluster-levelConnectionNumreversehandoffclientconnnections OBJECT-TYPE
    SYNTAX      ConfdString
    MAX-ACCESS  read-only
    STATUS      current
    DESCRIPTION "Total number of client connections from reverse handoff"
    ::= { affirmedServicesContentHttpProxyServiceStatisticsCluster-levelConnectionEntry 33 }

affirmedServicesContentHttpProxyServiceStatisticsCluster-levelConnectionNumfailuresclientconnnections OBJECT-TYPE
    SYNTAX      ConfdString
    MAX-ACCESS  read-only
    STATUS      current
    DESCRIPTION "Total number of client connection failures"
    ::= { affirmedServicesContentHttpProxyServiceStatisticsCluster-levelConnectionEntry 34 }

affirmedServicesContentHttpProxyServiceStatisticsCluster-levelConnectionNumfastopenattempts OBJECT-TYPE
    SYNTAX      ConfdString
    MAX-ACCESS  read-only
    STATUS      current
    DESCRIPTION "Total number of HTTP server connection fast open attempts"
    ::= { affirmedServicesContentHttpProxyServiceStatisticsCluster-levelConnectionEntry 35 }

affirmedServicesContentHttpProxyServiceStatisticsCluster-levelConnectionNumfastopensuccesses OBJECT-TYPE
    SYNTAX      ConfdString
    MAX-ACCESS  read-only
    STATUS      current
    DESCRIPTION "Total number of HTTP server connection fast open successes"
    ::= { affirmedServicesContentHttpProxyServiceStatisticsCluster-levelConnectionEntry 36 }

affirmedServicesContentHttpProxyServiceStatisticsCluster-levelConnectionNumfastopenfailureinitconn OBJECT-TYPE
    SYNTAX      ConfdString
    MAX-ACCESS  read-only
    STATUS      current
    DESCRIPTION "Total number of HTTP server connection fast open initialization failure"
    ::= { affirmedServicesContentHttpProxyServiceStatisticsCluster-levelConnectionEntry 37 }

affirmedServicesContentHttpProxyServiceStatisticsCluster-levelConnectionNumfastopenfailureduplicate OBJECT-TYPE
    SYNTAX      ConfdString
    MAX-ACCESS  read-only
    STATUS      current
    DESCRIPTION "Total number of HTTP server connection fast open duplicated connection"
    ::= { affirmedServicesContentHttpProxyServiceStatisticsCluster-levelConnectionEntry 38 }

affirmedServicesContentHttpProxyServiceStatisticsCluster-levelConnectionNumfastopenfailurealreadycreated OBJECT-TYPE
    SYNTAX      ConfdString
    MAX-ACCESS  read-only
    STATUS      current
    DESCRIPTION "Total number of HTTP server connection fast open already in the session"
    ::= { affirmedServicesContentHttpProxyServiceStatisticsCluster-levelConnectionEntry 39 }

affirmedServicesContentHttpProxyServiceStatisticsCluster-levelConnectionNumfastopenfailurepolicy OBJECT-TYPE
    SYNTAX      ConfdString
    MAX-ACCESS  read-only
    STATUS      current
    DESCRIPTION "Total number of HTTP server connection fast open policy reject"
    ::= { affirmedServicesContentHttpProxyServiceStatisticsCluster-levelConnectionEntry 40 }

affirmedServicesContentHttpProxyServiceStatisticsCluster-levelConnectionNumfastopenfailureother OBJECT-TYPE
    SYNTAX      ConfdString
    MAX-ACCESS  read-only
    STATUS      current
    DESCRIPTION "Total number of HTTP server connection fast open failure others"
    ::= { affirmedServicesContentHttpProxyServiceStatisticsCluster-levelConnectionEntry 41 }

affirmedServicesContentHttpProxyServiceStatisticsCluster-levelConnectionNumfastopenlistfull OBJECT-TYPE
    SYNTAX      ConfdString
    MAX-ACCESS  read-only
    STATUS      current
    DESCRIPTION "Total number of HTTP server connection fast open pending list full"
    ::= { affirmedServicesContentHttpProxyServiceStatisticsCluster-levelConnectionEntry 42 }

affirmedServicesContentHttpProxyServiceStatisticsCluster-levelConnectionNumfastopencurrentpendingconn OBJECT-TYPE
    SYNTAX      ConfdString
    MAX-ACCESS  read-only
    STATUS      current
    DESCRIPTION "Total number of HTTP server connection fast open in pending list"
    ::= { affirmedServicesContentHttpProxyServiceStatisticsCluster-levelConnectionEntry 43 }

affirmedServicesContentHttpProxyServiceStatisticsCluster-levelConnectionNumfastopenaging OBJECT-TYPE
    SYNTAX      ConfdString
    MAX-ACCESS  read-only
    STATUS      current
    DESCRIPTION "Total number of HTTP server connection fast open connection closed due to aging"
    ::= { affirmedServicesContentHttpProxyServiceStatisticsCluster-levelConnectionEntry 44 }

affirmedServicesContentHttpProxyServiceStatisticsCluster-levelDetailTable OBJECT-TYPE
    SYNTAX      SEQUENCE OF AffirmedServicesContentHttpProxyServiceStatisticsCluster-levelDetailEntry
    MAX-ACCESS  not-accessible
    STATUS      current
    DESCRIPTION ""
    ::= { affirmedServicesContentHttpProxyServiceStatisticsCluster-level 3 }

affirmedServicesContentHttpProxyServiceStatisticsCluster-levelDetailEntry OBJECT-TYPE
    SYNTAX      AffirmedServicesContentHttpProxyServiceStatisticsCluster-levelDetailEntry
    MAX-ACCESS  not-accessible
    STATUS      current
    DESCRIPTION ""
    INDEX { affirmedServicesContentHttpProxyServiceStatisticsCluster-levelDetailChassis }
        ::= { affirmedServicesContentHttpProxyServiceStatisticsCluster-levelDetailTable 1 }

AffirmedServicesContentHttpProxyServiceStatisticsCluster-levelDetailEntry ::=
    SEQUENCE {
        affirmedServicesContentHttpProxyServiceStatisticsCluster-levelDetailChassis Unsigned32,
        affirmedServicesContentHttpProxyServiceStatisticsCluster-levelDetailNumtotalrequestshttpv09 ConfdString,
        affirmedServicesContentHttpProxyServiceStatisticsCluster-levelDetailNumtotalrequestshttpv10 ConfdString,
        affirmedServicesContentHttpProxyServiceStatisticsCluster-levelDetailNumtotalrequestshttpv11 ConfdString,
        affirmedServicesContentHttpProxyServiceStatisticsCluster-levelDetailNumpersistenclientrequests ConfdString,
        affirmedServicesContentHttpProxyServiceStatisticsCluster-levelDetailNumpipelinedclientrequests ConfdString,
        affirmedServicesContentHttpProxyServiceStatisticsCluster-levelDetailNumipv4clientrequests ConfdString,
        affirmedServicesContentHttpProxyServiceStatisticsCluster-levelDetailNumipv6clientrequests ConfdString,
        affirmedServicesContentHttpProxyServiceStatisticsCluster-levelDetailNumparsediosrequests ConfdString,
        affirmedServicesContentHttpProxyServiceStatisticsCluster-levelDetailNumparsedandroidrequests ConfdString,
        affirmedServicesContentHttpProxyServiceStatisticsCluster-levelDetailNumparsedmozillarequests ConfdString,
        affirmedServicesContentHttpProxyServiceStatisticsCluster-levelDetailNumparsedsafarirequests ConfdString,
        affirmedServicesContentHttpProxyServiceStatisticsCluster-levelDetailNumparsedchromerequests ConfdString,
        affirmedServicesContentHttpProxyServiceStatisticsCluster-levelDetailServerhttpresponsesipv4 ConfdString,
        affirmedServicesContentHttpProxyServiceStatisticsCluster-levelDetailServerhttpresponsesipv6 ConfdString,
        affirmedServicesContentHttpProxyServiceStatisticsCluster-levelDetailClienthttprequestsizemin ConfdString,
        affirmedServicesContentHttpProxyServiceStatisticsCluster-levelDetailClienthttprequestsizeavg ConfdString,
        affirmedServicesContentHttpProxyServiceStatisticsCluster-levelDetailClienthttprequestsizemax ConfdString,
        affirmedServicesContentHttpProxyServiceStatisticsCluster-levelDetailClienthttpresponsesizemin ConfdString,
        affirmedServicesContentHttpProxyServiceStatisticsCluster-levelDetailClienthttpresponsesizeavg ConfdString,
        affirmedServicesContentHttpProxyServiceStatisticsCluster-levelDetailClienthttpresponsesizemax ConfdString,
        affirmedServicesContentHttpProxyServiceStatisticsCluster-levelDetailServicetimefromserveravg ConfdString,
        affirmedServicesContentHttpProxyServiceStatisticsCluster-levelDetailServicetimefromcacheavg ConfdString,
        affirmedServicesContentHttpProxyServiceStatisticsCluster-levelDetailNumtotalclientrequestschunked ConfdString,
        affirmedServicesContentHttpProxyServiceStatisticsCluster-levelDetailNumsuccessclientrequestschunked ConfdString,
        affirmedServicesContentHttpProxyServiceStatisticsCluster-levelDetailNumproxyserviceattemptschunked ConfdString,
        affirmedServicesContentHttpProxyServiceStatisticsCluster-levelDetailNumproxyservicesuccesscachedchunked ConfdString,
        affirmedServicesContentHttpProxyServiceStatisticsCluster-levelDetailNumproxyservicesuccesschunked ConfdString,
        affirmedServicesContentHttpProxyServiceStatisticsCluster-levelDetailNumbytesclientrequestchunked ConfdString,
        affirmedServicesContentHttpProxyServiceStatisticsCluster-levelDetailNumbytesserverresponsechunked ConfdString,
        affirmedServicesContentHttpProxyServiceStatisticsCluster-levelDetailNumproxyserviceattemptschunkedvideo ConfdString,
        affirmedServicesContentHttpProxyServiceStatisticsCluster-levelDetailNumproxyservicesuccesschunkedvideo ConfdString,
        affirmedServicesContentHttpProxyServiceStatisticsCluster-levelDetailNumproxyservicesuccesscachedchunkedvideo ConfdString,
        affirmedServicesContentHttpProxyServiceStatisticsCluster-levelDetailNumbytesserverresponsechunkedvideo ConfdString,
        affirmedServicesContentHttpProxyServiceStatisticsCluster-levelDetailNumconditionalclientrequests ConfdString,
        affirmedServicesContentHttpProxyServiceStatisticsCluster-levelDetailNumproxyservicepreconditionfailed ConfdString,
        affirmedServicesContentHttpProxyServiceStatisticsCluster-levelDetailNumproxyservicepreconditionnotmodified ConfdString,
        affirmedServicesContentHttpProxyServiceStatisticsCluster-levelDetailNumproxyservicepreconditionpartialcontentserved ConfdString,
        affirmedServicesContentHttpProxyServiceStatisticsCluster-levelDetailNumproxyservicepreconditionserved ConfdString,
        affirmedServicesContentHttpProxyServiceStatisticsCluster-levelDetailNumproxyservicepreconditionforwarded ConfdString,
        affirmedServicesContentHttpProxyServiceStatisticsCluster-levelDetailNumbufferedrequests ConfdString,
        affirmedServicesContentHttpProxyServiceStatisticsCluster-levelDetailNumbufferedresponses ConfdString,
        affirmedServicesContentHttpProxyServiceStatisticsCluster-levelDetailNumtransparentproxyrequests ConfdString,
        affirmedServicesContentHttpProxyServiceStatisticsCluster-levelDetailNumexplicitproxyrequests ConfdString,
        affirmedServicesContentHttpProxyServiceStatisticsCluster-levelDetailNumparsedlinuxrequests ConfdString,
        affirmedServicesContentHttpProxyServiceStatisticsCluster-levelDetailNumparsedmacintoshrequests ConfdString,
        affirmedServicesContentHttpProxyServiceStatisticsCluster-levelDetailNumparsedwindowsrequests ConfdString,
        affirmedServicesContentHttpProxyServiceStatisticsCluster-levelDetailNumparsedotherosrequests ConfdString,
        affirmedServicesContentHttpProxyServiceStatisticsCluster-levelDetailNumparsedinternetexplorerrequests ConfdString,
        affirmedServicesContentHttpProxyServiceStatisticsCluster-levelDetailNumparsedotherbrowserrequests ConfdString,
        affirmedServicesContentHttpProxyServiceStatisticsCluster-levelDetailNumhttpproxyrequestpolicyappliedtotal ConfdString,
        affirmedServicesContentHttpProxyServiceStatisticsCluster-levelDetailNumhttpproxyresponsepolicyappliedtotal ConfdString,
        affirmedServicesContentHttpProxyServiceStatisticsCluster-levelDetailClienthttpresponsestatusinformation ConfdString,
        affirmedServicesContentHttpProxyServiceStatisticsCluster-levelDetailClienthttpresponsestatussuccessok ConfdString,
        affirmedServicesContentHttpProxyServiceStatisticsCluster-levelDetailClienthttpresponsestatussuccessother ConfdString,
        affirmedServicesContentHttpProxyServiceStatisticsCluster-levelDetailClienthttpresponsestatusredirection ConfdString,
        affirmedServicesContentHttpProxyServiceStatisticsCluster-levelDetailClienthttpresponsestatusclienterror ConfdString,
        affirmedServicesContentHttpProxyServiceStatisticsCluster-levelDetailClienthttpresponsestatusservererror ConfdString
    }

affirmedServicesContentHttpProxyServiceStatisticsCluster-levelDetailChassis OBJECT-TYPE
    SYNTAX      Unsigned32
    MAX-ACCESS  not-accessible
    STATUS      current
    DESCRIPTION "chassis ID"
    ::= { affirmedServicesContentHttpProxyServiceStatisticsCluster-levelDetailEntry 1 }

affirmedServicesContentHttpProxyServiceStatisticsCluster-levelDetailNumtotalrequestshttpv09 OBJECT-TYPE
    SYNTAX      ConfdString
    MAX-ACCESS  read-only
    STATUS      current
    DESCRIPTION "Total number of Http V0.9 client requests received"
    ::= { affirmedServicesContentHttpProxyServiceStatisticsCluster-levelDetailEntry 2 }

affirmedServicesContentHttpProxyServiceStatisticsCluster-levelDetailNumtotalrequestshttpv10 OBJECT-TYPE
    SYNTAX      ConfdString
    MAX-ACCESS  read-only
    STATUS      current
    DESCRIPTION "Total number of Http V1.0 client requests received"
    ::= { affirmedServicesContentHttpProxyServiceStatisticsCluster-levelDetailEntry 3 }

affirmedServicesContentHttpProxyServiceStatisticsCluster-levelDetailNumtotalrequestshttpv11 OBJECT-TYPE
    SYNTAX      ConfdString
    MAX-ACCESS  read-only
    STATUS      current
    DESCRIPTION "Total number of Http V1.1 client requests received"
    ::= { affirmedServicesContentHttpProxyServiceStatisticsCluster-levelDetailEntry 4 }

affirmedServicesContentHttpProxyServiceStatisticsCluster-levelDetailNumpersistenclientrequests OBJECT-TYPE
    SYNTAX      ConfdString
    MAX-ACCESS  read-only
    STATUS      current
    DESCRIPTION "Total number of client requests persistent"
    ::= { affirmedServicesContentHttpProxyServiceStatisticsCluster-levelDetailEntry 5 }

affirmedServicesContentHttpProxyServiceStatisticsCluster-levelDetailNumpipelinedclientrequests OBJECT-TYPE
    SYNTAX      ConfdString
    MAX-ACCESS  read-only
    STATUS      current
    DESCRIPTION "Total number of pipelined client requests"
    ::= { affirmedServicesContentHttpProxyServiceStatisticsCluster-levelDetailEntry 6 }

affirmedServicesContentHttpProxyServiceStatisticsCluster-levelDetailNumipv4clientrequests OBJECT-TYPE
    SYNTAX      ConfdString
    MAX-ACCESS  read-only
    STATUS      current
    DESCRIPTION "Total number of IPv4 client requests"
    ::= { affirmedServicesContentHttpProxyServiceStatisticsCluster-levelDetailEntry 7 }

affirmedServicesContentHttpProxyServiceStatisticsCluster-levelDetailNumipv6clientrequests OBJECT-TYPE
    SYNTAX      ConfdString
    MAX-ACCESS  read-only
    STATUS      current
    DESCRIPTION "Total number of IPv6 client requests"
    ::= { affirmedServicesContentHttpProxyServiceStatisticsCluster-levelDetailEntry 8 }

affirmedServicesContentHttpProxyServiceStatisticsCluster-levelDetailNumparsediosrequests OBJECT-TYPE
    SYNTAX      ConfdString
    MAX-ACCESS  read-only
    STATUS      current
    DESCRIPTION "Total number of client requests parsed for iOS"
    ::= { affirmedServicesContentHttpProxyServiceStatisticsCluster-levelDetailEntry 9 }

affirmedServicesContentHttpProxyServiceStatisticsCluster-levelDetailNumparsedandroidrequests OBJECT-TYPE
    SYNTAX      ConfdString
    MAX-ACCESS  read-only
    STATUS      current
    DESCRIPTION "Total number of client requests parsed for Android"
    ::= { affirmedServicesContentHttpProxyServiceStatisticsCluster-levelDetailEntry 10 }

affirmedServicesContentHttpProxyServiceStatisticsCluster-levelDetailNumparsedmozillarequests OBJECT-TYPE
    SYNTAX      ConfdString
    MAX-ACCESS  read-only
    STATUS      current
    DESCRIPTION "Total number of client requests parsed for Firefox"
    ::= { affirmedServicesContentHttpProxyServiceStatisticsCluster-levelDetailEntry 11 }

affirmedServicesContentHttpProxyServiceStatisticsCluster-levelDetailNumparsedsafarirequests OBJECT-TYPE
    SYNTAX      ConfdString
    MAX-ACCESS  read-only
    STATUS      current
    DESCRIPTION "Total number of client requests parsed for Safari"
    ::= { affirmedServicesContentHttpProxyServiceStatisticsCluster-levelDetailEntry 12 }

affirmedServicesContentHttpProxyServiceStatisticsCluster-levelDetailNumparsedchromerequests OBJECT-TYPE
    SYNTAX      ConfdString
    MAX-ACCESS  read-only
    STATUS      current
    DESCRIPTION "Total number of client requests parsed for Chrome"
    ::= { affirmedServicesContentHttpProxyServiceStatisticsCluster-levelDetailEntry 13 }

affirmedServicesContentHttpProxyServiceStatisticsCluster-levelDetailServerhttpresponsesipv4 OBJECT-TYPE
    SYNTAX      ConfdString
    MAX-ACCESS  read-only
    STATUS      current
    DESCRIPTION "Total number of IPv4 server responses"
    ::= { affirmedServicesContentHttpProxyServiceStatisticsCluster-levelDetailEntry 14 }

affirmedServicesContentHttpProxyServiceStatisticsCluster-levelDetailServerhttpresponsesipv6 OBJECT-TYPE
    SYNTAX      ConfdString
    MAX-ACCESS  read-only
    STATUS      current
    DESCRIPTION "Total number of IPv6 server responses"
    ::= { affirmedServicesContentHttpProxyServiceStatisticsCluster-levelDetailEntry 15 }

affirmedServicesContentHttpProxyServiceStatisticsCluster-levelDetailClienthttprequestsizemin OBJECT-TYPE
    SYNTAX      ConfdString
    MAX-ACCESS  read-only
    STATUS      current
    DESCRIPTION "Client HTTP Request Size Min (Bytes)"
    ::= { affirmedServicesContentHttpProxyServiceStatisticsCluster-levelDetailEntry 16 }

affirmedServicesContentHttpProxyServiceStatisticsCluster-levelDetailClienthttprequestsizeavg OBJECT-TYPE
    SYNTAX      ConfdString
    MAX-ACCESS  read-only
    STATUS      current
    DESCRIPTION "Client HTTP Request Size Avg (Bytes)"
    ::= { affirmedServicesContentHttpProxyServiceStatisticsCluster-levelDetailEntry 17 }

affirmedServicesContentHttpProxyServiceStatisticsCluster-levelDetailClienthttprequestsizemax OBJECT-TYPE
    SYNTAX      ConfdString
    MAX-ACCESS  read-only
    STATUS      current
    DESCRIPTION "Client HTTP Request Size Max (Bytes)"
    ::= { affirmedServicesContentHttpProxyServiceStatisticsCluster-levelDetailEntry 18 }

affirmedServicesContentHttpProxyServiceStatisticsCluster-levelDetailClienthttpresponsesizemin OBJECT-TYPE
    SYNTAX      ConfdString
    MAX-ACCESS  read-only
    STATUS      current
    DESCRIPTION "Client HTTP Response Size Min (Bytes)"
    ::= { affirmedServicesContentHttpProxyServiceStatisticsCluster-levelDetailEntry 19 }

affirmedServicesContentHttpProxyServiceStatisticsCluster-levelDetailClienthttpresponsesizeavg OBJECT-TYPE
    SYNTAX      ConfdString
    MAX-ACCESS  read-only
    STATUS      current
    DESCRIPTION "Client HTTP Response Size Avg (Bytes)"
    ::= { affirmedServicesContentHttpProxyServiceStatisticsCluster-levelDetailEntry 20 }

affirmedServicesContentHttpProxyServiceStatisticsCluster-levelDetailClienthttpresponsesizemax OBJECT-TYPE
    SYNTAX      ConfdString
    MAX-ACCESS  read-only
    STATUS      current
    DESCRIPTION "Client HTTP Response Size Max (Bytes)"
    ::= { affirmedServicesContentHttpProxyServiceStatisticsCluster-levelDetailEntry 21 }

affirmedServicesContentHttpProxyServiceStatisticsCluster-levelDetailServicetimefromserveravg OBJECT-TYPE
    SYNTAX      ConfdString
    MAX-ACCESS  read-only
    STATUS      current
    DESCRIPTION "Client Average HTTP Request Service Time from Server"
    ::= { affirmedServicesContentHttpProxyServiceStatisticsCluster-levelDetailEntry 22 }

affirmedServicesContentHttpProxyServiceStatisticsCluster-levelDetailServicetimefromcacheavg OBJECT-TYPE
    SYNTAX      ConfdString
    MAX-ACCESS  read-only
    STATUS      current
    DESCRIPTION "Client Average HTTP Request Service Time from Cache"
    ::= { affirmedServicesContentHttpProxyServiceStatisticsCluster-levelDetailEntry 23 }

affirmedServicesContentHttpProxyServiceStatisticsCluster-levelDetailNumtotalclientrequestschunked OBJECT-TYPE
    SYNTAX      ConfdString
    MAX-ACCESS  read-only
    STATUS      current
    DESCRIPTION "Total number of chunked client requests received"
    ::= { affirmedServicesContentHttpProxyServiceStatisticsCluster-levelDetailEntry 24 }

affirmedServicesContentHttpProxyServiceStatisticsCluster-levelDetailNumsuccessclientrequestschunked OBJECT-TYPE
    SYNTAX      ConfdString
    MAX-ACCESS  read-only
    STATUS      current
    DESCRIPTION "Total number of chunked client requests processed successfully"
    ::= { affirmedServicesContentHttpProxyServiceStatisticsCluster-levelDetailEntry 25 }

affirmedServicesContentHttpProxyServiceStatisticsCluster-levelDetailNumproxyserviceattemptschunked OBJECT-TYPE
    SYNTAX      ConfdString
    MAX-ACCESS  read-only
    STATUS      current
    DESCRIPTION "Total number of chunked proxy service attempts"
    ::= { affirmedServicesContentHttpProxyServiceStatisticsCluster-levelDetailEntry 26 }

affirmedServicesContentHttpProxyServiceStatisticsCluster-levelDetailNumproxyservicesuccesscachedchunked OBJECT-TYPE
    SYNTAX      ConfdString
    MAX-ACCESS  read-only
    STATUS      current
    DESCRIPTION "Total number of proxy service success - cached chunked"
    ::= { affirmedServicesContentHttpProxyServiceStatisticsCluster-levelDetailEntry 27 }

affirmedServicesContentHttpProxyServiceStatisticsCluster-levelDetailNumproxyservicesuccesschunked OBJECT-TYPE
    SYNTAX      ConfdString
    MAX-ACCESS  read-only
    STATUS      current
    DESCRIPTION "Total number of chunked proxy service success"
    ::= { affirmedServicesContentHttpProxyServiceStatisticsCluster-levelDetailEntry 28 }

affirmedServicesContentHttpProxyServiceStatisticsCluster-levelDetailNumbytesclientrequestchunked OBJECT-TYPE
    SYNTAX      ConfdString
    MAX-ACCESS  read-only
    STATUS      current
    DESCRIPTION "Total number of Bytes from Chunked Client Request"
    ::= { affirmedServicesContentHttpProxyServiceStatisticsCluster-levelDetailEntry 29 }

affirmedServicesContentHttpProxyServiceStatisticsCluster-levelDetailNumbytesserverresponsechunked OBJECT-TYPE
    SYNTAX      ConfdString
    MAX-ACCESS  read-only
    STATUS      current
    DESCRIPTION "Total number of Bytes from Chunked Server Response"
    ::= { affirmedServicesContentHttpProxyServiceStatisticsCluster-levelDetailEntry 30 }

affirmedServicesContentHttpProxyServiceStatisticsCluster-levelDetailNumproxyserviceattemptschunkedvideo OBJECT-TYPE
    SYNTAX      ConfdString
    MAX-ACCESS  read-only
    STATUS      current
    DESCRIPTION "Total number of chunked video proxy service attempts"
    ::= { affirmedServicesContentHttpProxyServiceStatisticsCluster-levelDetailEntry 31 }

affirmedServicesContentHttpProxyServiceStatisticsCluster-levelDetailNumproxyservicesuccesschunkedvideo OBJECT-TYPE
    SYNTAX      ConfdString
    MAX-ACCESS  read-only
    STATUS      current
    DESCRIPTION "Total number of chunked video proxy service success"
    ::= { affirmedServicesContentHttpProxyServiceStatisticsCluster-levelDetailEntry 32 }

affirmedServicesContentHttpProxyServiceStatisticsCluster-levelDetailNumproxyservicesuccesscachedchunkedvideo OBJECT-TYPE
    SYNTAX      ConfdString
    MAX-ACCESS  read-only
    STATUS      current
    DESCRIPTION "Total number of proxy service success - cached chunked video"
    ::= { affirmedServicesContentHttpProxyServiceStatisticsCluster-levelDetailEntry 33 }

affirmedServicesContentHttpProxyServiceStatisticsCluster-levelDetailNumbytesserverresponsechunkedvideo OBJECT-TYPE
    SYNTAX      ConfdString
    MAX-ACCESS  read-only
    STATUS      current
    DESCRIPTION "Total number of Bytes from Chunked Video Server Response"
    ::= { affirmedServicesContentHttpProxyServiceStatisticsCluster-levelDetailEntry 34 }

affirmedServicesContentHttpProxyServiceStatisticsCluster-levelDetailNumconditionalclientrequests OBJECT-TYPE
    SYNTAX      ConfdString
    MAX-ACCESS  read-only
    STATUS      current
    DESCRIPTION "Total number of conditional client requests"
    ::= { affirmedServicesContentHttpProxyServiceStatisticsCluster-levelDetailEntry 35 }

affirmedServicesContentHttpProxyServiceStatisticsCluster-levelDetailNumproxyservicepreconditionfailed OBJECT-TYPE
    SYNTAX      ConfdString
    MAX-ACCESS  read-only
    STATUS      current
    DESCRIPTION "Total number of proxy service precondition failed"
    ::= { affirmedServicesContentHttpProxyServiceStatisticsCluster-levelDetailEntry 36 }

affirmedServicesContentHttpProxyServiceStatisticsCluster-levelDetailNumproxyservicepreconditionnotmodified OBJECT-TYPE
    SYNTAX      ConfdString
    MAX-ACCESS  read-only
    STATUS      current
    DESCRIPTION "Total number of proxy service precondition not modified"
    ::= { affirmedServicesContentHttpProxyServiceStatisticsCluster-levelDetailEntry 37 }

affirmedServicesContentHttpProxyServiceStatisticsCluster-levelDetailNumproxyservicepreconditionpartialcontentserved OBJECT-TYPE
    SYNTAX      ConfdString
    MAX-ACCESS  read-only
    STATUS      current
    DESCRIPTION "Total number of proxy service precondition partial content served"
    ::= { affirmedServicesContentHttpProxyServiceStatisticsCluster-levelDetailEntry 38 }

affirmedServicesContentHttpProxyServiceStatisticsCluster-levelDetailNumproxyservicepreconditionserved OBJECT-TYPE
    SYNTAX      ConfdString
    MAX-ACCESS  read-only
    STATUS      current
    DESCRIPTION "Total number of proxy service precondition served"
    ::= { affirmedServicesContentHttpProxyServiceStatisticsCluster-levelDetailEntry 39 }

affirmedServicesContentHttpProxyServiceStatisticsCluster-levelDetailNumproxyservicepreconditionforwarded OBJECT-TYPE
    SYNTAX      ConfdString
    MAX-ACCESS  read-only
    STATUS      current
    DESCRIPTION "Total number of proxy service precondition forwarded"
    ::= { affirmedServicesContentHttpProxyServiceStatisticsCluster-levelDetailEntry 40 }

affirmedServicesContentHttpProxyServiceStatisticsCluster-levelDetailNumbufferedrequests OBJECT-TYPE
    SYNTAX      ConfdString
    MAX-ACCESS  read-only
    STATUS      current
    DESCRIPTION "Total number of client requests delayed due to buffering"
    ::= { affirmedServicesContentHttpProxyServiceStatisticsCluster-levelDetailEntry 41 }

affirmedServicesContentHttpProxyServiceStatisticsCluster-levelDetailNumbufferedresponses OBJECT-TYPE
    SYNTAX      ConfdString
    MAX-ACCESS  read-only
    STATUS      current
    DESCRIPTION "Total number of server responses delayed due to buffering limit"
    ::= { affirmedServicesContentHttpProxyServiceStatisticsCluster-levelDetailEntry 42 }

affirmedServicesContentHttpProxyServiceStatisticsCluster-levelDetailNumtransparentproxyrequests OBJECT-TYPE
    SYNTAX      ConfdString
    MAX-ACCESS  read-only
    STATUS      current
    DESCRIPTION "Total number of client requests destined to transparent proxy"
    ::= { affirmedServicesContentHttpProxyServiceStatisticsCluster-levelDetailEntry 43 }

affirmedServicesContentHttpProxyServiceStatisticsCluster-levelDetailNumexplicitproxyrequests OBJECT-TYPE
    SYNTAX      ConfdString
    MAX-ACCESS  read-only
    STATUS      current
    DESCRIPTION "Total number of client requests destined to an explicit proxy"
    ::= { affirmedServicesContentHttpProxyServiceStatisticsCluster-levelDetailEntry 44 }

affirmedServicesContentHttpProxyServiceStatisticsCluster-levelDetailNumparsedlinuxrequests OBJECT-TYPE
    SYNTAX      ConfdString
    MAX-ACCESS  read-only
    STATUS      current
    DESCRIPTION "Total number of client requests parsed for Linux"
    ::= { affirmedServicesContentHttpProxyServiceStatisticsCluster-levelDetailEntry 45 }

affirmedServicesContentHttpProxyServiceStatisticsCluster-levelDetailNumparsedmacintoshrequests OBJECT-TYPE
    SYNTAX      ConfdString
    MAX-ACCESS  read-only
    STATUS      current
    DESCRIPTION "Total number of client requests parsed for Macintosh"
    ::= { affirmedServicesContentHttpProxyServiceStatisticsCluster-levelDetailEntry 46 }

affirmedServicesContentHttpProxyServiceStatisticsCluster-levelDetailNumparsedwindowsrequests OBJECT-TYPE
    SYNTAX      ConfdString
    MAX-ACCESS  read-only
    STATUS      current
    DESCRIPTION "Total number of client requests parsed for Windows"
    ::= { affirmedServicesContentHttpProxyServiceStatisticsCluster-levelDetailEntry 47 }

affirmedServicesContentHttpProxyServiceStatisticsCluster-levelDetailNumparsedotherosrequests OBJECT-TYPE
    SYNTAX      ConfdString
    MAX-ACCESS  read-only
    STATUS      current
    DESCRIPTION "Total number of client requests parsed for Other OS"
    ::= { affirmedServicesContentHttpProxyServiceStatisticsCluster-levelDetailEntry 48 }

affirmedServicesContentHttpProxyServiceStatisticsCluster-levelDetailNumparsedinternetexplorerrequests OBJECT-TYPE
    SYNTAX      ConfdString
    MAX-ACCESS  read-only
    STATUS      current
    DESCRIPTION "Total number of client requests parsed for InternetExplorer"
    ::= { affirmedServicesContentHttpProxyServiceStatisticsCluster-levelDetailEntry 49 }

affirmedServicesContentHttpProxyServiceStatisticsCluster-levelDetailNumparsedotherbrowserrequests OBJECT-TYPE
    SYNTAX      ConfdString
    MAX-ACCESS  read-only
    STATUS      current
    DESCRIPTION "Total number of client requests parsed for Other Browser"
    ::= { affirmedServicesContentHttpProxyServiceStatisticsCluster-levelDetailEntry 50 }

affirmedServicesContentHttpProxyServiceStatisticsCluster-levelDetailNumhttpproxyrequestpolicyappliedtotal OBJECT-TYPE
    SYNTAX      ConfdString
    MAX-ACCESS  read-only
    STATUS      current
    DESCRIPTION "Total number of request policy applied"
    ::= { affirmedServicesContentHttpProxyServiceStatisticsCluster-levelDetailEntry 51 }

affirmedServicesContentHttpProxyServiceStatisticsCluster-levelDetailNumhttpproxyresponsepolicyappliedtotal OBJECT-TYPE
    SYNTAX      ConfdString
    MAX-ACCESS  read-only
    STATUS      current
    DESCRIPTION "Total number of response policy applied"
    ::= { affirmedServicesContentHttpProxyServiceStatisticsCluster-levelDetailEntry 52 }

affirmedServicesContentHttpProxyServiceStatisticsCluster-levelDetailClienthttpresponsestatusinformation OBJECT-TYPE
    SYNTAX      ConfdString
    MAX-ACCESS  read-only
    STATUS      current
    DESCRIPTION "Client HTTP Response Status Information (1xx)"
    ::= { affirmedServicesContentHttpProxyServiceStatisticsCluster-levelDetailEntry 53 }

affirmedServicesContentHttpProxyServiceStatisticsCluster-levelDetailClienthttpresponsestatussuccessok OBJECT-TYPE
    SYNTAX      ConfdString
    MAX-ACCESS  read-only
    STATUS      current
    DESCRIPTION "Client HTTP Response Status Success OK (200)"
    ::= { affirmedServicesContentHttpProxyServiceStatisticsCluster-levelDetailEntry 54 }

affirmedServicesContentHttpProxyServiceStatisticsCluster-levelDetailClienthttpresponsestatussuccessother OBJECT-TYPE
    SYNTAX      ConfdString
    MAX-ACCESS  read-only
    STATUS      current
    DESCRIPTION "Client HTTP Response Status Success Other (2xx)"
    ::= { affirmedServicesContentHttpProxyServiceStatisticsCluster-levelDetailEntry 55 }

affirmedServicesContentHttpProxyServiceStatisticsCluster-levelDetailClienthttpresponsestatusredirection OBJECT-TYPE
    SYNTAX      ConfdString
    MAX-ACCESS  read-only
    STATUS      current
    DESCRIPTION "Client HTTP Response Status Redirection (3xx)"
    ::= { affirmedServicesContentHttpProxyServiceStatisticsCluster-levelDetailEntry 56 }

affirmedServicesContentHttpProxyServiceStatisticsCluster-levelDetailClienthttpresponsestatusclienterror OBJECT-TYPE
    SYNTAX      ConfdString
    MAX-ACCESS  read-only
    STATUS      current
    DESCRIPTION "Client HTTP Response Status Client Error (4xx)"
    ::= { affirmedServicesContentHttpProxyServiceStatisticsCluster-levelDetailEntry 57 }

affirmedServicesContentHttpProxyServiceStatisticsCluster-levelDetailClienthttpresponsestatusservererror OBJECT-TYPE
    SYNTAX      ConfdString
    MAX-ACCESS  read-only
    STATUS      current
    DESCRIPTION "Client HTTP Response Status Server Error (5xx)"
    ::= { affirmedServicesContentHttpProxyServiceStatisticsCluster-levelDetailEntry 58 }

affirmedServicesContentHttpProxyServiceStatisticsCluster-levelFailureTable OBJECT-TYPE
    SYNTAX      SEQUENCE OF AffirmedServicesContentHttpProxyServiceStatisticsCluster-levelFailureEntry
    MAX-ACCESS  not-accessible
    STATUS      current
    DESCRIPTION ""
    ::= { affirmedServicesContentHttpProxyServiceStatisticsCluster-level 4 }

affirmedServicesContentHttpProxyServiceStatisticsCluster-levelFailureEntry OBJECT-TYPE
    SYNTAX      AffirmedServicesContentHttpProxyServiceStatisticsCluster-levelFailureEntry
    MAX-ACCESS  not-accessible
    STATUS      current
    DESCRIPTION ""
    INDEX { affirmedServicesContentHttpProxyServiceStatisticsCluster-levelFailureChassis }
        ::= { affirmedServicesContentHttpProxyServiceStatisticsCluster-levelFailureTable 1 }

AffirmedServicesContentHttpProxyServiceStatisticsCluster-levelFailureEntry ::=
    SEQUENCE {
        affirmedServicesContentHttpProxyServiceStatisticsCluster-levelFailureChassis Unsigned32,
        affirmedServicesContentHttpProxyServiceStatisticsCluster-levelFailureNuminvalidclientrequestsoversizedheader ConfdString,
        affirmedServicesContentHttpProxyServiceStatisticsCluster-levelFailureNuminvalidclientrequestsbadrequestline ConfdString,
        affirmedServicesContentHttpProxyServiceStatisticsCluster-levelFailureNuminvalidclientrequestsbadheaders ConfdString,
        affirmedServicesContentHttpProxyServiceStatisticsCluster-levelFailureNuminvalidclientrequestsbadheaderattribute ConfdString,
        affirmedServicesContentHttpProxyServiceStatisticsCluster-levelFailureNuminvalidclientrequestsdupheaderattribute ConfdString,
        affirmedServicesContentHttpProxyServiceStatisticsCluster-levelFailureNuminvalidclientrequestsbadhostname ConfdString,
        affirmedServicesContentHttpProxyServiceStatisticsCluster-levelFailureNuminvalidclientrequestshostnotfound ConfdString,
        affirmedServicesContentHttpProxyServiceStatisticsCluster-levelFailureNuminvalidclientrequestsnotsupported ConfdString,
        affirmedServicesContentHttpProxyServiceStatisticsCluster-levelFailureNuminvalidclientrequestsexpectheadererror ConfdString,
        affirmedServicesContentHttpProxyServiceStatisticsCluster-levelFailureNuminvalidclientrequestsbodyreaderror ConfdString,
        affirmedServicesContentHttpProxyServiceStatisticsCluster-levelFailureNuminvalidclientrequestsidletimeout ConfdString,
        affirmedServicesContentHttpProxyServiceStatisticsCluster-levelFailureNumproxyservicefailedrequestcompileerror ConfdString,
        affirmedServicesContentHttpProxyServiceStatisticsCluster-levelFailureNumproxyservicefailedconnectioninitfailure ConfdString,
        affirmedServicesContentHttpProxyServiceStatisticsCluster-levelFailureNumproxyservicefailedoversizedresponseheader ConfdString,
        affirmedServicesContentHttpProxyServiceStatisticsCluster-levelFailureNumproxyservicefailedbadresponsestatusline ConfdString,
        affirmedServicesContentHttpProxyServiceStatisticsCluster-levelFailureNumproxyservicefailedbadresponseheader ConfdString,
        affirmedServicesContentHttpProxyServiceStatisticsCluster-levelFailureNumproxyservicefailedresponseprocessingfailure ConfdString,
        affirmedServicesContentHttpProxyServiceStatisticsCluster-levelFailureNumproxyservicefailedserverconnectionclose ConfdString,
        affirmedServicesContentHttpProxyServiceStatisticsCluster-levelFailureNumproxyservicefailedserverconnectiontimeout ConfdString,
        affirmedServicesContentHttpProxyServiceStatisticsCluster-levelFailureNumproxyservicefailedclientconnectiontimeout ConfdString,
        affirmedServicesContentHttpProxyServiceStatisticsCluster-levelFailureNumproxyservicefailedresourceunavailable ConfdString,
        affirmedServicesContentHttpProxyServiceStatisticsCluster-levelFailureNumproxyserviceredirected ConfdString,
        affirmedServicesContentHttpProxyServiceStatisticsCluster-levelFailureNumproxyserviceblocked ConfdString,
        affirmedServicesContentHttpProxyServiceStatisticsCluster-levelFailureNumcacheservicefailedresponsereaderror ConfdString,
        affirmedServicesContentHttpProxyServiceStatisticsCluster-levelFailureNumcacheservicefailedresponseheaderprocessing ConfdString,
        affirmedServicesContentHttpProxyServiceStatisticsCluster-levelFailureNumcacheservicefailedresponseoversizedheader ConfdString,
        affirmedServicesContentHttpProxyServiceStatisticsCluster-levelFailureNumcacheservicefailedservervalidationfailures ConfdString,
        affirmedServicesContentHttpProxyServiceStatisticsCluster-levelFailureNumcacheservicefailedmaintenanceconnectionclose ConfdString,
        affirmedServicesContentHttpProxyServiceStatisticsCluster-levelFailureNumproxyservicefailedmaintenanceconnectionclose ConfdString,
        affirmedServicesContentHttpProxyServiceStatisticsCluster-levelFailureNumproxyserviceabortedbyclient ConfdString,
        affirmedServicesContentHttpProxyServiceStatisticsCluster-levelFailureNumproxyserviceabortednorespfromserver ConfdString,
        affirmedServicesContentHttpProxyServiceStatisticsCluster-levelFailureNumproxyserviceabortedrequesttolocaladdr ConfdString,
        affirmedServicesContentHttpProxyServiceStatisticsCluster-levelFailureNumconnectionfailuresoverload ConfdString,
        affirmedServicesContentHttpProxyServiceStatisticsCluster-levelFailureNumconnectionfailuresinvalidmetadata ConfdString,
        affirmedServicesContentHttpProxyServiceStatisticsCluster-levelFailureNumconnectionfailuresproxyisnotready ConfdString,
        affirmedServicesContentHttpProxyServiceStatisticsCluster-levelFailureNumproxyserviceoutofbuffer ConfdString,
        affirmedServicesContentHttpProxyServiceStatisticsCluster-levelFailureNumconnectionfailuresfdlimitexceeded ConfdString,
        affirmedServicesContentHttpProxyServiceStatisticsCluster-levelFailureNumconnectionfailuresoutofresources ConfdString
    }

affirmedServicesContentHttpProxyServiceStatisticsCluster-levelFailureChassis OBJECT-TYPE
    SYNTAX      Unsigned32
    MAX-ACCESS  not-accessible
    STATUS      current
    DESCRIPTION "chassis ID"
    ::= { affirmedServicesContentHttpProxyServiceStatisticsCluster-levelFailureEntry 1 }

affirmedServicesContentHttpProxyServiceStatisticsCluster-levelFailureNuminvalidclientrequestsoversizedheader OBJECT-TYPE
    SYNTAX      ConfdString
    MAX-ACCESS  read-only
    STATUS      current
    DESCRIPTION "Total number of invalid client requests - Oversized Header"
    ::= { affirmedServicesContentHttpProxyServiceStatisticsCluster-levelFailureEntry 2 }

affirmedServicesContentHttpProxyServiceStatisticsCluster-levelFailureNuminvalidclientrequestsbadrequestline OBJECT-TYPE
    SYNTAX      ConfdString
    MAX-ACCESS  read-only
    STATUS      current
    DESCRIPTION "Total number of invalid client requests - Bad Request line"
    ::= { affirmedServicesContentHttpProxyServiceStatisticsCluster-levelFailureEntry 3 }

affirmedServicesContentHttpProxyServiceStatisticsCluster-levelFailureNuminvalidclientrequestsbadheaders OBJECT-TYPE
    SYNTAX      ConfdString
    MAX-ACCESS  read-only
    STATUS      current
    DESCRIPTION "Total number of invalid client requests - Bad Headers"
    ::= { affirmedServicesContentHttpProxyServiceStatisticsCluster-levelFailureEntry 4 }

affirmedServicesContentHttpProxyServiceStatisticsCluster-levelFailureNuminvalidclientrequestsbadheaderattribute OBJECT-TYPE
    SYNTAX      ConfdString
    MAX-ACCESS  read-only
    STATUS      current
    DESCRIPTION "Total number of invalid client requests - Bad Header Attribute"
    ::= { affirmedServicesContentHttpProxyServiceStatisticsCluster-levelFailureEntry 5 }

affirmedServicesContentHttpProxyServiceStatisticsCluster-levelFailureNuminvalidclientrequestsdupheaderattribute OBJECT-TYPE
    SYNTAX      ConfdString
    MAX-ACCESS  read-only
    STATUS      current
    DESCRIPTION "Total number of invalid client requests - Duplicated Header Attribute"
    ::= { affirmedServicesContentHttpProxyServiceStatisticsCluster-levelFailureEntry 6 }

affirmedServicesContentHttpProxyServiceStatisticsCluster-levelFailureNuminvalidclientrequestsbadhostname OBJECT-TYPE
    SYNTAX      ConfdString
    MAX-ACCESS  read-only
    STATUS      current
    DESCRIPTION "Total number of invalid client requests - Bad Host Name"
    ::= { affirmedServicesContentHttpProxyServiceStatisticsCluster-levelFailureEntry 7 }

affirmedServicesContentHttpProxyServiceStatisticsCluster-levelFailureNuminvalidclientrequestshostnotfound OBJECT-TYPE
    SYNTAX      ConfdString
    MAX-ACCESS  read-only
    STATUS      current
    DESCRIPTION "Total number of invalid client requests - Host Not Found"
    ::= { affirmedServicesContentHttpProxyServiceStatisticsCluster-levelFailureEntry 8 }

affirmedServicesContentHttpProxyServiceStatisticsCluster-levelFailureNuminvalidclientrequestsnotsupported OBJECT-TYPE
    SYNTAX      ConfdString
    MAX-ACCESS  read-only
    STATUS      current
    DESCRIPTION "Total number of invalid client requests - Not Supported"
    ::= { affirmedServicesContentHttpProxyServiceStatisticsCluster-levelFailureEntry 9 }

affirmedServicesContentHttpProxyServiceStatisticsCluster-levelFailureNuminvalidclientrequestsexpectheadererror OBJECT-TYPE
    SYNTAX      ConfdString
    MAX-ACCESS  read-only
    STATUS      current
    DESCRIPTION "Total number of invalid client requests - Expect Header Error"
    ::= { affirmedServicesContentHttpProxyServiceStatisticsCluster-levelFailureEntry 10 }

affirmedServicesContentHttpProxyServiceStatisticsCluster-levelFailureNuminvalidclientrequestsbodyreaderror OBJECT-TYPE
    SYNTAX      ConfdString
    MAX-ACCESS  read-only
    STATUS      current
    DESCRIPTION "Total number of invalid client requests - Body Read Error"
    ::= { affirmedServicesContentHttpProxyServiceStatisticsCluster-levelFailureEntry 11 }

affirmedServicesContentHttpProxyServiceStatisticsCluster-levelFailureNuminvalidclientrequestsidletimeout OBJECT-TYPE
    SYNTAX      ConfdString
    MAX-ACCESS  read-only
    STATUS      current
    DESCRIPTION "Total number of invalid client requests - Idle Timeout"
    ::= { affirmedServicesContentHttpProxyServiceStatisticsCluster-levelFailureEntry 12 }

affirmedServicesContentHttpProxyServiceStatisticsCluster-levelFailureNumproxyservicefailedrequestcompileerror OBJECT-TYPE
    SYNTAX      ConfdString
    MAX-ACCESS  read-only
    STATUS      current
    DESCRIPTION "Total number of proxy service failed - Request Compile Error"
    ::= { affirmedServicesContentHttpProxyServiceStatisticsCluster-levelFailureEntry 13 }

affirmedServicesContentHttpProxyServiceStatisticsCluster-levelFailureNumproxyservicefailedconnectioninitfailure OBJECT-TYPE
    SYNTAX      ConfdString
    MAX-ACCESS  read-only
    STATUS      current
    DESCRIPTION "Total number of proxy service failed - Connection Init Failure"
    ::= { affirmedServicesContentHttpProxyServiceStatisticsCluster-levelFailureEntry 14 }

affirmedServicesContentHttpProxyServiceStatisticsCluster-levelFailureNumproxyservicefailedoversizedresponseheader OBJECT-TYPE
    SYNTAX      ConfdString
    MAX-ACCESS  read-only
    STATUS      current
    DESCRIPTION "Total number of proxy service failed- Oversized Response Header"
    ::= { affirmedServicesContentHttpProxyServiceStatisticsCluster-levelFailureEntry 15 }

affirmedServicesContentHttpProxyServiceStatisticsCluster-levelFailureNumproxyservicefailedbadresponsestatusline OBJECT-TYPE
    SYNTAX      ConfdString
    MAX-ACCESS  read-only
    STATUS      current
    DESCRIPTION "Total number of proxy service failed - Bad Response Status Line"
    ::= { affirmedServicesContentHttpProxyServiceStatisticsCluster-levelFailureEntry 16 }

affirmedServicesContentHttpProxyServiceStatisticsCluster-levelFailureNumproxyservicefailedbadresponseheader OBJECT-TYPE
    SYNTAX      ConfdString
    MAX-ACCESS  read-only
    STATUS      current
    DESCRIPTION "Total number of proxy service failed - Bad Response Header"
    ::= { affirmedServicesContentHttpProxyServiceStatisticsCluster-levelFailureEntry 17 }

affirmedServicesContentHttpProxyServiceStatisticsCluster-levelFailureNumproxyservicefailedresponseprocessingfailure OBJECT-TYPE
    SYNTAX      ConfdString
    MAX-ACCESS  read-only
    STATUS      current
    DESCRIPTION "Total number of proxy service failed - Response Processing Failure"
    ::= { affirmedServicesContentHttpProxyServiceStatisticsCluster-levelFailureEntry 18 }

affirmedServicesContentHttpProxyServiceStatisticsCluster-levelFailureNumproxyservicefailedserverconnectionclose OBJECT-TYPE
    SYNTAX      ConfdString
    MAX-ACCESS  read-only
    STATUS      current
    DESCRIPTION "Total number of proxy service failed - Server Connection Close"
    ::= { affirmedServicesContentHttpProxyServiceStatisticsCluster-levelFailureEntry 19 }

affirmedServicesContentHttpProxyServiceStatisticsCluster-levelFailureNumproxyservicefailedserverconnectiontimeout OBJECT-TYPE
    SYNTAX      ConfdString
    MAX-ACCESS  read-only
    STATUS      current
    DESCRIPTION "Total number of proxy service failed - Server Connection Timeout"
    ::= { affirmedServicesContentHttpProxyServiceStatisticsCluster-levelFailureEntry 20 }

affirmedServicesContentHttpProxyServiceStatisticsCluster-levelFailureNumproxyservicefailedclientconnectiontimeout OBJECT-TYPE
    SYNTAX      ConfdString
    MAX-ACCESS  read-only
    STATUS      current
    DESCRIPTION "Total number of proxy service failed - Client Connection Timeout"
    ::= { affirmedServicesContentHttpProxyServiceStatisticsCluster-levelFailureEntry 21 }

affirmedServicesContentHttpProxyServiceStatisticsCluster-levelFailureNumproxyservicefailedresourceunavailable OBJECT-TYPE
    SYNTAX      ConfdString
    MAX-ACCESS  read-only
    STATUS      current
    DESCRIPTION "Total number of proxy service failed - Resources unavailable"
    ::= { affirmedServicesContentHttpProxyServiceStatisticsCluster-levelFailureEntry 22 }

affirmedServicesContentHttpProxyServiceStatisticsCluster-levelFailureNumproxyserviceredirected OBJECT-TYPE
    SYNTAX      ConfdString
    MAX-ACCESS  read-only
    STATUS      current
    DESCRIPTION "Total number of proxy service failed - Requests redirected"
    ::= { affirmedServicesContentHttpProxyServiceStatisticsCluster-levelFailureEntry 23 }

affirmedServicesContentHttpProxyServiceStatisticsCluster-levelFailureNumproxyserviceblocked OBJECT-TYPE
    SYNTAX      ConfdString
    MAX-ACCESS  read-only
    STATUS      current
    DESCRIPTION "Total number of proxy service failed - Requests blocked"
    ::= { affirmedServicesContentHttpProxyServiceStatisticsCluster-levelFailureEntry 24 }

affirmedServicesContentHttpProxyServiceStatisticsCluster-levelFailureNumcacheservicefailedresponsereaderror OBJECT-TYPE
    SYNTAX      ConfdString
    MAX-ACCESS  read-only
    STATUS      current
    DESCRIPTION "Total number of cache service failed - Response Read Error"
    ::= { affirmedServicesContentHttpProxyServiceStatisticsCluster-levelFailureEntry 25 }

affirmedServicesContentHttpProxyServiceStatisticsCluster-levelFailureNumcacheservicefailedresponseheaderprocessing OBJECT-TYPE
    SYNTAX      ConfdString
    MAX-ACCESS  read-only
    STATUS      current
    DESCRIPTION "Total number of cache service failed - Response Header Processing Failure"
    ::= { affirmedServicesContentHttpProxyServiceStatisticsCluster-levelFailureEntry 26 }

affirmedServicesContentHttpProxyServiceStatisticsCluster-levelFailureNumcacheservicefailedresponseoversizedheader OBJECT-TYPE
    SYNTAX      ConfdString
    MAX-ACCESS  read-only
    STATUS      current
    DESCRIPTION "Total number of cache service failed - Response Header Oversized"
    ::= { affirmedServicesContentHttpProxyServiceStatisticsCluster-levelFailureEntry 27 }

affirmedServicesContentHttpProxyServiceStatisticsCluster-levelFailureNumcacheservicefailedservervalidationfailures OBJECT-TYPE
    SYNTAX      ConfdString
    MAX-ACCESS  read-only
    STATUS      current
    DESCRIPTION "Total number of cache service failed - Server Validation Failures"
    ::= { affirmedServicesContentHttpProxyServiceStatisticsCluster-levelFailureEntry 28 }

affirmedServicesContentHttpProxyServiceStatisticsCluster-levelFailureNumcacheservicefailedmaintenanceconnectionclose OBJECT-TYPE
    SYNTAX      ConfdString
    MAX-ACCESS  read-only
    STATUS      current
    DESCRIPTION "Total number of cache service failed - Maintenance Connection Close"
    ::= { affirmedServicesContentHttpProxyServiceStatisticsCluster-levelFailureEntry 29 }

affirmedServicesContentHttpProxyServiceStatisticsCluster-levelFailureNumproxyservicefailedmaintenanceconnectionclose OBJECT-TYPE
    SYNTAX      ConfdString
    MAX-ACCESS  read-only
    STATUS      current
    DESCRIPTION "Total number of proxy service failed - Maintenance Connection Close"
    ::= { affirmedServicesContentHttpProxyServiceStatisticsCluster-levelFailureEntry 30 }

affirmedServicesContentHttpProxyServiceStatisticsCluster-levelFailureNumproxyserviceabortedbyclient OBJECT-TYPE
    SYNTAX      ConfdString
    MAX-ACCESS  read-only
    STATUS      current
    DESCRIPTION "Total number of proxy service aborted - Client Disconnected"
    ::= { affirmedServicesContentHttpProxyServiceStatisticsCluster-levelFailureEntry 31 }

affirmedServicesContentHttpProxyServiceStatisticsCluster-levelFailureNumproxyserviceabortednorespfromserver OBJECT-TYPE
    SYNTAX      ConfdString
    MAX-ACCESS  read-only
    STATUS      current
    DESCRIPTION "Total number of proxy service aborted - No Response from Server"
    ::= { affirmedServicesContentHttpProxyServiceStatisticsCluster-levelFailureEntry 32 }

affirmedServicesContentHttpProxyServiceStatisticsCluster-levelFailureNumproxyserviceabortedrequesttolocaladdr OBJECT-TYPE
    SYNTAX      ConfdString
    MAX-ACCESS  read-only
    STATUS      current
    DESCRIPTION "Total number of proxy service aborted - Request to Local Address"
    ::= { affirmedServicesContentHttpProxyServiceStatisticsCluster-levelFailureEntry 33 }

affirmedServicesContentHttpProxyServiceStatisticsCluster-levelFailureNumconnectionfailuresoverload OBJECT-TYPE
    SYNTAX      ConfdString
    MAX-ACCESS  read-only
    STATUS      current
    DESCRIPTION "Total number of client connection failures - Terminated due to Overload"
    ::= { affirmedServicesContentHttpProxyServiceStatisticsCluster-levelFailureEntry 34 }

affirmedServicesContentHttpProxyServiceStatisticsCluster-levelFailureNumconnectionfailuresinvalidmetadata OBJECT-TYPE
    SYNTAX      ConfdString
    MAX-ACCESS  read-only
    STATUS      current
    DESCRIPTION "Total number of client connection failures - Invalid Metadata"
    ::= { affirmedServicesContentHttpProxyServiceStatisticsCluster-levelFailureEntry 35 }

affirmedServicesContentHttpProxyServiceStatisticsCluster-levelFailureNumconnectionfailuresproxyisnotready OBJECT-TYPE
    SYNTAX      ConfdString
    MAX-ACCESS  read-only
    STATUS      current
    DESCRIPTION "Total number of client connection failures - Proxy is not Ready"
    ::= { affirmedServicesContentHttpProxyServiceStatisticsCluster-levelFailureEntry 36 }

affirmedServicesContentHttpProxyServiceStatisticsCluster-levelFailureNumproxyserviceoutofbuffer OBJECT-TYPE
    SYNTAX      ConfdString
    MAX-ACCESS  read-only
    STATUS      current
    DESCRIPTION "Total number of proxy service failed - Out of buffer"
    ::= { affirmedServicesContentHttpProxyServiceStatisticsCluster-levelFailureEntry 37 }

affirmedServicesContentHttpProxyServiceStatisticsCluster-levelFailureNumconnectionfailuresfdlimitexceeded OBJECT-TYPE
    SYNTAX      ConfdString
    MAX-ACCESS  read-only
    STATUS      current
    DESCRIPTION "Total number of client connection failures - FD limit exceeded"
    ::= { affirmedServicesContentHttpProxyServiceStatisticsCluster-levelFailureEntry 38 }

affirmedServicesContentHttpProxyServiceStatisticsCluster-levelFailureNumconnectionfailuresoutofresources OBJECT-TYPE
    SYNTAX      ConfdString
    MAX-ACCESS  read-only
    STATUS      current
    DESCRIPTION "Total number of client connection failures - Out of Resources"
    ::= { affirmedServicesContentHttpProxyServiceStatisticsCluster-levelFailureEntry 39 }

affirmedServicesContentHttpProxyServiceStatisticsCluster-levelRequestMethodTable OBJECT-TYPE
    SYNTAX      SEQUENCE OF AffirmedServicesContentHttpProxyServiceStatisticsCluster-levelRequestMethodEntry
    MAX-ACCESS  not-accessible
    STATUS      current
    DESCRIPTION ""
    ::= { affirmedServicesContentHttpProxyServiceStatisticsCluster-level 5 }

affirmedServicesContentHttpProxyServiceStatisticsCluster-levelRequestMethodEntry OBJECT-TYPE
    SYNTAX      AffirmedServicesContentHttpProxyServiceStatisticsCluster-levelRequestMethodEntry
    MAX-ACCESS  not-accessible
    STATUS      current
    DESCRIPTION ""
    INDEX { affirmedServicesContentHttpProxyServiceStatisticsCluster-levelRequestMethodChassis }
        ::= { affirmedServicesContentHttpProxyServiceStatisticsCluster-levelRequestMethodTable 1 }

AffirmedServicesContentHttpProxyServiceStatisticsCluster-levelRequestMethodEntry ::=
    SEQUENCE {
        affirmedServicesContentHttpProxyServiceStatisticsCluster-levelRequestMethodChassis Unsigned32,
        affirmedServicesContentHttpProxyServiceStatisticsCluster-levelRequestMethodMethodoptionsreceived ConfdString,
        affirmedServicesContentHttpProxyServiceStatisticsCluster-levelRequestMethodMethodoptionsaborted ConfdString,
        affirmedServicesContentHttpProxyServiceStatisticsCluster-levelRequestMethodMethodgetreceived ConfdString,
        affirmedServicesContentHttpProxyServiceStatisticsCluster-levelRequestMethodMethodgetaborted ConfdString,
        affirmedServicesContentHttpProxyServiceStatisticsCluster-levelRequestMethodMethodheadreceived ConfdString,
        affirmedServicesContentHttpProxyServiceStatisticsCluster-levelRequestMethodMethodheadaborted ConfdString,
        affirmedServicesContentHttpProxyServiceStatisticsCluster-levelRequestMethodMethodpostreceived ConfdString,
        affirmedServicesContentHttpProxyServiceStatisticsCluster-levelRequestMethodMethodpostaborted ConfdString,
        affirmedServicesContentHttpProxyServiceStatisticsCluster-levelRequestMethodMethodputreceived ConfdString,
        affirmedServicesContentHttpProxyServiceStatisticsCluster-levelRequestMethodMethodputaborted ConfdString,
        affirmedServicesContentHttpProxyServiceStatisticsCluster-levelRequestMethodMethoddeletereceived ConfdString,
        affirmedServicesContentHttpProxyServiceStatisticsCluster-levelRequestMethodMethoddeleteaborted ConfdString,
        affirmedServicesContentHttpProxyServiceStatisticsCluster-levelRequestMethodMethodtracereceived ConfdString,
        affirmedServicesContentHttpProxyServiceStatisticsCluster-levelRequestMethodMethodtraceaborted ConfdString,
        affirmedServicesContentHttpProxyServiceStatisticsCluster-levelRequestMethodMethodconnectreceived ConfdString,
        affirmedServicesContentHttpProxyServiceStatisticsCluster-levelRequestMethodMethodconnectaborted ConfdString,
        affirmedServicesContentHttpProxyServiceStatisticsCluster-levelRequestMethodMethodmkcolreceived ConfdString,
        affirmedServicesContentHttpProxyServiceStatisticsCluster-levelRequestMethodMethodmkcolaborted ConfdString,
        affirmedServicesContentHttpProxyServiceStatisticsCluster-levelRequestMethodMethodcopyreceived ConfdString,
        affirmedServicesContentHttpProxyServiceStatisticsCluster-levelRequestMethodMethodcopyaborted ConfdString,
        affirmedServicesContentHttpProxyServiceStatisticsCluster-levelRequestMethodMethodmovereceived ConfdString,
        affirmedServicesContentHttpProxyServiceStatisticsCluster-levelRequestMethodMethodmoveaborted ConfdString,
        affirmedServicesContentHttpProxyServiceStatisticsCluster-levelRequestMethodMethodpropfindreceived ConfdString,
        affirmedServicesContentHttpProxyServiceStatisticsCluster-levelRequestMethodMethodpropfindaborted ConfdString,
        affirmedServicesContentHttpProxyServiceStatisticsCluster-levelRequestMethodMethodproppatchreceived ConfdString,
        affirmedServicesContentHttpProxyServiceStatisticsCluster-levelRequestMethodMethodproppatchaborted ConfdString,
        affirmedServicesContentHttpProxyServiceStatisticsCluster-levelRequestMethodMethodlockreceived ConfdString,
        affirmedServicesContentHttpProxyServiceStatisticsCluster-levelRequestMethodMethodlockaborted ConfdString,
        affirmedServicesContentHttpProxyServiceStatisticsCluster-levelRequestMethodMethodunlockreceived ConfdString,
        affirmedServicesContentHttpProxyServiceStatisticsCluster-levelRequestMethodMethodunlockaborted ConfdString,
        affirmedServicesContentHttpProxyServiceStatisticsCluster-levelRequestMethodMethodpatchreceived ConfdString,
        affirmedServicesContentHttpProxyServiceStatisticsCluster-levelRequestMethodMethodpatchaborted ConfdString,
        affirmedServicesContentHttpProxyServiceStatisticsCluster-levelRequestMethodUnknownmethodreceived ConfdString,
        affirmedServicesContentHttpProxyServiceStatisticsCluster-levelRequestMethodUnknownmethodaborted ConfdString,
        affirmedServicesContentHttpProxyServiceStatisticsCluster-levelRequestMethodMethodaclreceived ConfdString,
        affirmedServicesContentHttpProxyServiceStatisticsCluster-levelRequestMethodMethodaclaborted ConfdString,
        affirmedServicesContentHttpProxyServiceStatisticsCluster-levelRequestMethodMethodbaselinecontrolreceived ConfdString,
        affirmedServicesContentHttpProxyServiceStatisticsCluster-levelRequestMethodMethodbaselinecontrolaborted ConfdString,
        affirmedServicesContentHttpProxyServiceStatisticsCluster-levelRequestMethodMethodbindreceived ConfdString,
        affirmedServicesContentHttpProxyServiceStatisticsCluster-levelRequestMethodMethodbindaborted ConfdString,
        affirmedServicesContentHttpProxyServiceStatisticsCluster-levelRequestMethodMethodcheckinreceived ConfdString,
        affirmedServicesContentHttpProxyServiceStatisticsCluster-levelRequestMethodMethodcheckinaborted ConfdString,
        affirmedServicesContentHttpProxyServiceStatisticsCluster-levelRequestMethodMethodcheckoutreceived ConfdString,
        affirmedServicesContentHttpProxyServiceStatisticsCluster-levelRequestMethodMethodcheckoutaborted ConfdString,
        affirmedServicesContentHttpProxyServiceStatisticsCluster-levelRequestMethodMethodlabelreceived ConfdString,
        affirmedServicesContentHttpProxyServiceStatisticsCluster-levelRequestMethodMethodlabelaborted ConfdString,
        affirmedServicesContentHttpProxyServiceStatisticsCluster-levelRequestMethodMethodlinkreceived ConfdString,
        affirmedServicesContentHttpProxyServiceStatisticsCluster-levelRequestMethodMethodlinkaborted ConfdString,
        affirmedServicesContentHttpProxyServiceStatisticsCluster-levelRequestMethodMethodmergereceived ConfdString,
        affirmedServicesContentHttpProxyServiceStatisticsCluster-levelRequestMethodMethodmergeaborted ConfdString,
        affirmedServicesContentHttpProxyServiceStatisticsCluster-levelRequestMethodMethodmkactivityreceived ConfdString,
        affirmedServicesContentHttpProxyServiceStatisticsCluster-levelRequestMethodMethodmkactivityaborted ConfdString,
        affirmedServicesContentHttpProxyServiceStatisticsCluster-levelRequestMethodMethodmkcalendarreceived ConfdString,
        affirmedServicesContentHttpProxyServiceStatisticsCluster-levelRequestMethodMethodmkcalendaraborted ConfdString,
        affirmedServicesContentHttpProxyServiceStatisticsCluster-levelRequestMethodMethodmkredirectrefreceived ConfdString,
        affirmedServicesContentHttpProxyServiceStatisticsCluster-levelRequestMethodMethodmkredirectrefaborted ConfdString,
        affirmedServicesContentHttpProxyServiceStatisticsCluster-levelRequestMethodMethodmkworkspacereceived ConfdString,
        affirmedServicesContentHttpProxyServiceStatisticsCluster-levelRequestMethodMethodmkworkspaceaborted ConfdString,
        affirmedServicesContentHttpProxyServiceStatisticsCluster-levelRequestMethodMethodorderpatchreceived ConfdString,
        affirmedServicesContentHttpProxyServiceStatisticsCluster-levelRequestMethodMethodorderpatchaborted ConfdString,
        affirmedServicesContentHttpProxyServiceStatisticsCluster-levelRequestMethodMethodprireceived ConfdString,
        affirmedServicesContentHttpProxyServiceStatisticsCluster-levelRequestMethodMethodpriaborted ConfdString,
        affirmedServicesContentHttpProxyServiceStatisticsCluster-levelRequestMethodMethodrebindreceived ConfdString,
        affirmedServicesContentHttpProxyServiceStatisticsCluster-levelRequestMethodMethodrebindaborted ConfdString,
        affirmedServicesContentHttpProxyServiceStatisticsCluster-levelRequestMethodMethodreportreceived ConfdString,
        affirmedServicesContentHttpProxyServiceStatisticsCluster-levelRequestMethodMethodreportaborted ConfdString,
        affirmedServicesContentHttpProxyServiceStatisticsCluster-levelRequestMethodMethodsearchreceived ConfdString,
        affirmedServicesContentHttpProxyServiceStatisticsCluster-levelRequestMethodMethodsearchaborted ConfdString,
        affirmedServicesContentHttpProxyServiceStatisticsCluster-levelRequestMethodMethodunbindreceived ConfdString,
        affirmedServicesContentHttpProxyServiceStatisticsCluster-levelRequestMethodMethodunbindaborted ConfdString,
        affirmedServicesContentHttpProxyServiceStatisticsCluster-levelRequestMethodMethoduncheckoutreceived ConfdString,
        affirmedServicesContentHttpProxyServiceStatisticsCluster-levelRequestMethodMethoduncheckoutaborted ConfdString,
        affirmedServicesContentHttpProxyServiceStatisticsCluster-levelRequestMethodMethodunlinkreceived ConfdString,
        affirmedServicesContentHttpProxyServiceStatisticsCluster-levelRequestMethodMethodunlinkaborted ConfdString,
        affirmedServicesContentHttpProxyServiceStatisticsCluster-levelRequestMethodMethodupdatereceived ConfdString,
        affirmedServicesContentHttpProxyServiceStatisticsCluster-levelRequestMethodMethodupdateaborted ConfdString,
        affirmedServicesContentHttpProxyServiceStatisticsCluster-levelRequestMethodMethodupdateredirectrefreceived ConfdString,
        affirmedServicesContentHttpProxyServiceStatisticsCluster-levelRequestMethodMethodupdateredirectrefaborted ConfdString,
        affirmedServicesContentHttpProxyServiceStatisticsCluster-levelRequestMethodMethodversioncontrolreceived ConfdString,
        affirmedServicesContentHttpProxyServiceStatisticsCluster-levelRequestMethodMethodversioncontrolaborted ConfdString,
        affirmedServicesContentHttpProxyServiceStatisticsCluster-levelRequestMethodUnsupportedmethodreceived ConfdString
    }

affirmedServicesContentHttpProxyServiceStatisticsCluster-levelRequestMethodChassis OBJECT-TYPE
    SYNTAX      Unsigned32
    MAX-ACCESS  not-accessible
    STATUS      current
    DESCRIPTION "chassis ID"
    ::= { affirmedServicesContentHttpProxyServiceStatisticsCluster-levelRequestMethodEntry 1 }

affirmedServicesContentHttpProxyServiceStatisticsCluster-levelRequestMethodMethodoptionsreceived OBJECT-TYPE
    SYNTAX      ConfdString
    MAX-ACCESS  read-only
    STATUS      current
    DESCRIPTION "Total number of OPTIONS request received"
    ::= { affirmedServicesContentHttpProxyServiceStatisticsCluster-levelRequestMethodEntry 2 }

affirmedServicesContentHttpProxyServiceStatisticsCluster-levelRequestMethodMethodoptionsaborted OBJECT-TYPE
    SYNTAX      ConfdString
    MAX-ACCESS  read-only
    STATUS      current
    DESCRIPTION "Total number of OPTIONS request aborted/failed"
    ::= { affirmedServicesContentHttpProxyServiceStatisticsCluster-levelRequestMethodEntry 3 }

affirmedServicesContentHttpProxyServiceStatisticsCluster-levelRequestMethodMethodgetreceived OBJECT-TYPE
    SYNTAX      ConfdString
    MAX-ACCESS  read-only
    STATUS      current
    DESCRIPTION "Total number of GET request received"
    ::= { affirmedServicesContentHttpProxyServiceStatisticsCluster-levelRequestMethodEntry 4 }

affirmedServicesContentHttpProxyServiceStatisticsCluster-levelRequestMethodMethodgetaborted OBJECT-TYPE
    SYNTAX      ConfdString
    MAX-ACCESS  read-only
    STATUS      current
    DESCRIPTION "Total number of GET request aborted/failed"
    ::= { affirmedServicesContentHttpProxyServiceStatisticsCluster-levelRequestMethodEntry 5 }

affirmedServicesContentHttpProxyServiceStatisticsCluster-levelRequestMethodMethodheadreceived OBJECT-TYPE
    SYNTAX      ConfdString
    MAX-ACCESS  read-only
    STATUS      current
    DESCRIPTION "Total number of HEAD request received"
    ::= { affirmedServicesContentHttpProxyServiceStatisticsCluster-levelRequestMethodEntry 6 }

affirmedServicesContentHttpProxyServiceStatisticsCluster-levelRequestMethodMethodheadaborted OBJECT-TYPE
    SYNTAX      ConfdString
    MAX-ACCESS  read-only
    STATUS      current
    DESCRIPTION "Total number of HEAD request aborted/failed"
    ::= { affirmedServicesContentHttpProxyServiceStatisticsCluster-levelRequestMethodEntry 7 }

affirmedServicesContentHttpProxyServiceStatisticsCluster-levelRequestMethodMethodpostreceived OBJECT-TYPE
    SYNTAX      ConfdString
    MAX-ACCESS  read-only
    STATUS      current
    DESCRIPTION "Total number of POST request received"
    ::= { affirmedServicesContentHttpProxyServiceStatisticsCluster-levelRequestMethodEntry 8 }

affirmedServicesContentHttpProxyServiceStatisticsCluster-levelRequestMethodMethodpostaborted OBJECT-TYPE
    SYNTAX      ConfdString
    MAX-ACCESS  read-only
    STATUS      current
    DESCRIPTION "Total number of POST request aborted/failed"
    ::= { affirmedServicesContentHttpProxyServiceStatisticsCluster-levelRequestMethodEntry 9 }

affirmedServicesContentHttpProxyServiceStatisticsCluster-levelRequestMethodMethodputreceived OBJECT-TYPE
    SYNTAX      ConfdString
    MAX-ACCESS  read-only
    STATUS      current
    DESCRIPTION "Total number of PUT request received"
    ::= { affirmedServicesContentHttpProxyServiceStatisticsCluster-levelRequestMethodEntry 10 }

affirmedServicesContentHttpProxyServiceStatisticsCluster-levelRequestMethodMethodputaborted OBJECT-TYPE
    SYNTAX      ConfdString
    MAX-ACCESS  read-only
    STATUS      current
    DESCRIPTION "Total number of PUT request aborted/failed"
    ::= { affirmedServicesContentHttpProxyServiceStatisticsCluster-levelRequestMethodEntry 11 }

affirmedServicesContentHttpProxyServiceStatisticsCluster-levelRequestMethodMethoddeletereceived OBJECT-TYPE
    SYNTAX      ConfdString
    MAX-ACCESS  read-only
    STATUS      current
    DESCRIPTION "Total number of DELETE request received"
    ::= { affirmedServicesContentHttpProxyServiceStatisticsCluster-levelRequestMethodEntry 12 }

affirmedServicesContentHttpProxyServiceStatisticsCluster-levelRequestMethodMethoddeleteaborted OBJECT-TYPE
    SYNTAX      ConfdString
    MAX-ACCESS  read-only
    STATUS      current
    DESCRIPTION "Total number of DELETE request aborted/failed"
    ::= { affirmedServicesContentHttpProxyServiceStatisticsCluster-levelRequestMethodEntry 13 }

affirmedServicesContentHttpProxyServiceStatisticsCluster-levelRequestMethodMethodtracereceived OBJECT-TYPE
    SYNTAX      ConfdString
    MAX-ACCESS  read-only
    STATUS      current
    DESCRIPTION "Total number of TRACE request received"
    ::= { affirmedServicesContentHttpProxyServiceStatisticsCluster-levelRequestMethodEntry 14 }

affirmedServicesContentHttpProxyServiceStatisticsCluster-levelRequestMethodMethodtraceaborted OBJECT-TYPE
    SYNTAX      ConfdString
    MAX-ACCESS  read-only
    STATUS      current
    DESCRIPTION "Total number of TRACE request aborted/failed"
    ::= { affirmedServicesContentHttpProxyServiceStatisticsCluster-levelRequestMethodEntry 15 }

affirmedServicesContentHttpProxyServiceStatisticsCluster-levelRequestMethodMethodconnectreceived OBJECT-TYPE
    SYNTAX      ConfdString
    MAX-ACCESS  read-only
    STATUS      current
    DESCRIPTION "Total number of CONNECT request received"
    ::= { affirmedServicesContentHttpProxyServiceStatisticsCluster-levelRequestMethodEntry 16 }

affirmedServicesContentHttpProxyServiceStatisticsCluster-levelRequestMethodMethodconnectaborted OBJECT-TYPE
    SYNTAX      ConfdString
    MAX-ACCESS  read-only
    STATUS      current
    DESCRIPTION "Total number of CONNECT request aborted/failed"
    ::= { affirmedServicesContentHttpProxyServiceStatisticsCluster-levelRequestMethodEntry 17 }

affirmedServicesContentHttpProxyServiceStatisticsCluster-levelRequestMethodMethodmkcolreceived OBJECT-TYPE
    SYNTAX      ConfdString
    MAX-ACCESS  read-only
    STATUS      current
    DESCRIPTION "Total number of MKCOL request received"
    ::= { affirmedServicesContentHttpProxyServiceStatisticsCluster-levelRequestMethodEntry 18 }

affirmedServicesContentHttpProxyServiceStatisticsCluster-levelRequestMethodMethodmkcolaborted OBJECT-TYPE
    SYNTAX      ConfdString
    MAX-ACCESS  read-only
    STATUS      current
    DESCRIPTION "Total number of MKCOL request aborted/failed"
    ::= { affirmedServicesContentHttpProxyServiceStatisticsCluster-levelRequestMethodEntry 19 }

affirmedServicesContentHttpProxyServiceStatisticsCluster-levelRequestMethodMethodcopyreceived OBJECT-TYPE
    SYNTAX      ConfdString
    MAX-ACCESS  read-only
    STATUS      current
    DESCRIPTION "Total number of COPY request received"
    ::= { affirmedServicesContentHttpProxyServiceStatisticsCluster-levelRequestMethodEntry 20 }

affirmedServicesContentHttpProxyServiceStatisticsCluster-levelRequestMethodMethodcopyaborted OBJECT-TYPE
    SYNTAX      ConfdString
    MAX-ACCESS  read-only
    STATUS      current
    DESCRIPTION "Total number of COPY request aborted/failed"
    ::= { affirmedServicesContentHttpProxyServiceStatisticsCluster-levelRequestMethodEntry 21 }

affirmedServicesContentHttpProxyServiceStatisticsCluster-levelRequestMethodMethodmovereceived OBJECT-TYPE
    SYNTAX      ConfdString
    MAX-ACCESS  read-only
    STATUS      current
    DESCRIPTION "Total number of MOVE request received"
    ::= { affirmedServicesContentHttpProxyServiceStatisticsCluster-levelRequestMethodEntry 22 }

affirmedServicesContentHttpProxyServiceStatisticsCluster-levelRequestMethodMethodmoveaborted OBJECT-TYPE
    SYNTAX      ConfdString
    MAX-ACCESS  read-only
    STATUS      current
    DESCRIPTION "Total number of MOVE request aborted/failed"
    ::= { affirmedServicesContentHttpProxyServiceStatisticsCluster-levelRequestMethodEntry 23 }

affirmedServicesContentHttpProxyServiceStatisticsCluster-levelRequestMethodMethodpropfindreceived OBJECT-TYPE
    SYNTAX      ConfdString
    MAX-ACCESS  read-only
    STATUS      current
    DESCRIPTION "Total number of PROPFIND request received"
    ::= { affirmedServicesContentHttpProxyServiceStatisticsCluster-levelRequestMethodEntry 24 }

affirmedServicesContentHttpProxyServiceStatisticsCluster-levelRequestMethodMethodpropfindaborted OBJECT-TYPE
    SYNTAX      ConfdString
    MAX-ACCESS  read-only
    STATUS      current
    DESCRIPTION "Total number of PROPFIND request aborted/failed"
    ::= { affirmedServicesContentHttpProxyServiceStatisticsCluster-levelRequestMethodEntry 25 }

affirmedServicesContentHttpProxyServiceStatisticsCluster-levelRequestMethodMethodproppatchreceived OBJECT-TYPE
    SYNTAX      ConfdString
    MAX-ACCESS  read-only
    STATUS      current
    DESCRIPTION "Total number of PROPPATCH request received"
    ::= { affirmedServicesContentHttpProxyServiceStatisticsCluster-levelRequestMethodEntry 26 }

affirmedServicesContentHttpProxyServiceStatisticsCluster-levelRequestMethodMethodproppatchaborted OBJECT-TYPE
    SYNTAX      ConfdString
    MAX-ACCESS  read-only
    STATUS      current
    DESCRIPTION "Total number of PROPPATCH request aborted/failed"
    ::= { affirmedServicesContentHttpProxyServiceStatisticsCluster-levelRequestMethodEntry 27 }

affirmedServicesContentHttpProxyServiceStatisticsCluster-levelRequestMethodMethodlockreceived OBJECT-TYPE
    SYNTAX      ConfdString
    MAX-ACCESS  read-only
    STATUS      current
    DESCRIPTION "Total number of LOCK request received"
    ::= { affirmedServicesContentHttpProxyServiceStatisticsCluster-levelRequestMethodEntry 28 }

affirmedServicesContentHttpProxyServiceStatisticsCluster-levelRequestMethodMethodlockaborted OBJECT-TYPE
    SYNTAX      ConfdString
    MAX-ACCESS  read-only
    STATUS      current
    DESCRIPTION "Total number of LOCK request aborted/failed"
    ::= { affirmedServicesContentHttpProxyServiceStatisticsCluster-levelRequestMethodEntry 29 }

affirmedServicesContentHttpProxyServiceStatisticsCluster-levelRequestMethodMethodunlockreceived OBJECT-TYPE
    SYNTAX      ConfdString
    MAX-ACCESS  read-only
    STATUS      current
    DESCRIPTION "Total number of UNLOCK request received"
    ::= { affirmedServicesContentHttpProxyServiceStatisticsCluster-levelRequestMethodEntry 30 }

affirmedServicesContentHttpProxyServiceStatisticsCluster-levelRequestMethodMethodunlockaborted OBJECT-TYPE
    SYNTAX      ConfdString
    MAX-ACCESS  read-only
    STATUS      current
    DESCRIPTION "Total number of UNLOCK request aborted/failed"
    ::= { affirmedServicesContentHttpProxyServiceStatisticsCluster-levelRequestMethodEntry 31 }

affirmedServicesContentHttpProxyServiceStatisticsCluster-levelRequestMethodMethodpatchreceived OBJECT-TYPE
    SYNTAX      ConfdString
    MAX-ACCESS  read-only
    STATUS      current
    DESCRIPTION "Total number of PATCH request received"
    ::= { affirmedServicesContentHttpProxyServiceStatisticsCluster-levelRequestMethodEntry 32 }

affirmedServicesContentHttpProxyServiceStatisticsCluster-levelRequestMethodMethodpatchaborted OBJECT-TYPE
    SYNTAX      ConfdString
    MAX-ACCESS  read-only
    STATUS      current
    DESCRIPTION "Total number of PATCH request aborted/failed"
    ::= { affirmedServicesContentHttpProxyServiceStatisticsCluster-levelRequestMethodEntry 33 }

affirmedServicesContentHttpProxyServiceStatisticsCluster-levelRequestMethodUnknownmethodreceived OBJECT-TYPE
    SYNTAX      ConfdString
    MAX-ACCESS  read-only
    STATUS      current
    DESCRIPTION "Total number of Unknown-Method request received"
    ::= { affirmedServicesContentHttpProxyServiceStatisticsCluster-levelRequestMethodEntry 34 }

affirmedServicesContentHttpProxyServiceStatisticsCluster-levelRequestMethodUnknownmethodaborted OBJECT-TYPE
    SYNTAX      ConfdString
    MAX-ACCESS  read-only
    STATUS      current
    DESCRIPTION "Total number of Unknown-Method request aborted/failed"
    ::= { affirmedServicesContentHttpProxyServiceStatisticsCluster-levelRequestMethodEntry 35 }

affirmedServicesContentHttpProxyServiceStatisticsCluster-levelRequestMethodMethodaclreceived OBJECT-TYPE
    SYNTAX      ConfdString
    MAX-ACCESS  read-only
    STATUS      current
    DESCRIPTION "Total number of ACL request received"
    ::= { affirmedServicesContentHttpProxyServiceStatisticsCluster-levelRequestMethodEntry 36 }

affirmedServicesContentHttpProxyServiceStatisticsCluster-levelRequestMethodMethodaclaborted OBJECT-TYPE
    SYNTAX      ConfdString
    MAX-ACCESS  read-only
    STATUS      current
    DESCRIPTION "Total number of ACL request aborted/failed"
    ::= { affirmedServicesContentHttpProxyServiceStatisticsCluster-levelRequestMethodEntry 37 }

affirmedServicesContentHttpProxyServiceStatisticsCluster-levelRequestMethodMethodbaselinecontrolreceived OBJECT-TYPE
    SYNTAX      ConfdString
    MAX-ACCESS  read-only
    STATUS      current
    DESCRIPTION "Total number of BASELINE-CONTROL request received"
    ::= { affirmedServicesContentHttpProxyServiceStatisticsCluster-levelRequestMethodEntry 38 }

affirmedServicesContentHttpProxyServiceStatisticsCluster-levelRequestMethodMethodbaselinecontrolaborted OBJECT-TYPE
    SYNTAX      ConfdString
    MAX-ACCESS  read-only
    STATUS      current
    DESCRIPTION "Total number of BASELINE-CONTROL request aborted/failed"
    ::= { affirmedServicesContentHttpProxyServiceStatisticsCluster-levelRequestMethodEntry 39 }

affirmedServicesContentHttpProxyServiceStatisticsCluster-levelRequestMethodMethodbindreceived OBJECT-TYPE
    SYNTAX      ConfdString
    MAX-ACCESS  read-only
    STATUS      current
    DESCRIPTION "Total number of BIND request received"
    ::= { affirmedServicesContentHttpProxyServiceStatisticsCluster-levelRequestMethodEntry 40 }

affirmedServicesContentHttpProxyServiceStatisticsCluster-levelRequestMethodMethodbindaborted OBJECT-TYPE
    SYNTAX      ConfdString
    MAX-ACCESS  read-only
    STATUS      current
    DESCRIPTION "Total number of BIND request aborted/failed"
    ::= { affirmedServicesContentHttpProxyServiceStatisticsCluster-levelRequestMethodEntry 41 }

affirmedServicesContentHttpProxyServiceStatisticsCluster-levelRequestMethodMethodcheckinreceived OBJECT-TYPE
    SYNTAX      ConfdString
    MAX-ACCESS  read-only
    STATUS      current
    DESCRIPTION "Total number of CHECKIN request received"
    ::= { affirmedServicesContentHttpProxyServiceStatisticsCluster-levelRequestMethodEntry 42 }

affirmedServicesContentHttpProxyServiceStatisticsCluster-levelRequestMethodMethodcheckinaborted OBJECT-TYPE
    SYNTAX      ConfdString
    MAX-ACCESS  read-only
    STATUS      current
    DESCRIPTION "Total number of CHECKIN request aborted/failed"
    ::= { affirmedServicesContentHttpProxyServiceStatisticsCluster-levelRequestMethodEntry 43 }

affirmedServicesContentHttpProxyServiceStatisticsCluster-levelRequestMethodMethodcheckoutreceived OBJECT-TYPE
    SYNTAX      ConfdString
    MAX-ACCESS  read-only
    STATUS      current
    DESCRIPTION "Total number of CHECKOUT request received"
    ::= { affirmedServicesContentHttpProxyServiceStatisticsCluster-levelRequestMethodEntry 44 }

affirmedServicesContentHttpProxyServiceStatisticsCluster-levelRequestMethodMethodcheckoutaborted OBJECT-TYPE
    SYNTAX      ConfdString
    MAX-ACCESS  read-only
    STATUS      current
    DESCRIPTION "Total number of CHECKOUT request aborted/failed"
    ::= { affirmedServicesContentHttpProxyServiceStatisticsCluster-levelRequestMethodEntry 45 }

affirmedServicesContentHttpProxyServiceStatisticsCluster-levelRequestMethodMethodlabelreceived OBJECT-TYPE
    SYNTAX      ConfdString
    MAX-ACCESS  read-only
    STATUS      current
    DESCRIPTION "Total number of LABEL request received"
    ::= { affirmedServicesContentHttpProxyServiceStatisticsCluster-levelRequestMethodEntry 46 }

affirmedServicesContentHttpProxyServiceStatisticsCluster-levelRequestMethodMethodlabelaborted OBJECT-TYPE
    SYNTAX      ConfdString
    MAX-ACCESS  read-only
    STATUS      current
    DESCRIPTION "Total number of LABEL request aborted/failed"
    ::= { affirmedServicesContentHttpProxyServiceStatisticsCluster-levelRequestMethodEntry 47 }

affirmedServicesContentHttpProxyServiceStatisticsCluster-levelRequestMethodMethodlinkreceived OBJECT-TYPE
    SYNTAX      ConfdString
    MAX-ACCESS  read-only
    STATUS      current
    DESCRIPTION "Total number of LINK request received"
    ::= { affirmedServicesContentHttpProxyServiceStatisticsCluster-levelRequestMethodEntry 48 }

affirmedServicesContentHttpProxyServiceStatisticsCluster-levelRequestMethodMethodlinkaborted OBJECT-TYPE
    SYNTAX      ConfdString
    MAX-ACCESS  read-only
    STATUS      current
    DESCRIPTION "Total number of LINK request aborted/failed"
    ::= { affirmedServicesContentHttpProxyServiceStatisticsCluster-levelRequestMethodEntry 49 }

affirmedServicesContentHttpProxyServiceStatisticsCluster-levelRequestMethodMethodmergereceived OBJECT-TYPE
    SYNTAX      ConfdString
    MAX-ACCESS  read-only
    STATUS      current
    DESCRIPTION "Total number of MERGE request received"
    ::= { affirmedServicesContentHttpProxyServiceStatisticsCluster-levelRequestMethodEntry 50 }

affirmedServicesContentHttpProxyServiceStatisticsCluster-levelRequestMethodMethodmergeaborted OBJECT-TYPE
    SYNTAX      ConfdString
    MAX-ACCESS  read-only
    STATUS      current
    DESCRIPTION "Total number of MERGE request aborted/failed"
    ::= { affirmedServicesContentHttpProxyServiceStatisticsCluster-levelRequestMethodEntry 51 }

affirmedServicesContentHttpProxyServiceStatisticsCluster-levelRequestMethodMethodmkactivityreceived OBJECT-TYPE
    SYNTAX      ConfdString
    MAX-ACCESS  read-only
    STATUS      current
    DESCRIPTION "Total number of MKACTIVITY request received"
    ::= { affirmedServicesContentHttpProxyServiceStatisticsCluster-levelRequestMethodEntry 52 }

affirmedServicesContentHttpProxyServiceStatisticsCluster-levelRequestMethodMethodmkactivityaborted OBJECT-TYPE
    SYNTAX      ConfdString
    MAX-ACCESS  read-only
    STATUS      current
    DESCRIPTION "Total number of MKACTIVITY request aborted/failed"
    ::= { affirmedServicesContentHttpProxyServiceStatisticsCluster-levelRequestMethodEntry 53 }

affirmedServicesContentHttpProxyServiceStatisticsCluster-levelRequestMethodMethodmkcalendarreceived OBJECT-TYPE
    SYNTAX      ConfdString
    MAX-ACCESS  read-only
    STATUS      current
    DESCRIPTION "Total number of MKCALENDAR request received"
    ::= { affirmedServicesContentHttpProxyServiceStatisticsCluster-levelRequestMethodEntry 54 }

affirmedServicesContentHttpProxyServiceStatisticsCluster-levelRequestMethodMethodmkcalendaraborted OBJECT-TYPE
    SYNTAX      ConfdString
    MAX-ACCESS  read-only
    STATUS      current
    DESCRIPTION "Total number of MKCALENDAR request aborted/failed"
    ::= { affirmedServicesContentHttpProxyServiceStatisticsCluster-levelRequestMethodEntry 55 }

affirmedServicesContentHttpProxyServiceStatisticsCluster-levelRequestMethodMethodmkredirectrefreceived OBJECT-TYPE
    SYNTAX      ConfdString
    MAX-ACCESS  read-only
    STATUS      current
    DESCRIPTION "Total number of MKREDIRECTREF request received"
    ::= { affirmedServicesContentHttpProxyServiceStatisticsCluster-levelRequestMethodEntry 56 }

affirmedServicesContentHttpProxyServiceStatisticsCluster-levelRequestMethodMethodmkredirectrefaborted OBJECT-TYPE
    SYNTAX      ConfdString
    MAX-ACCESS  read-only
    STATUS      current
    DESCRIPTION "Total number of MKREDIRECTREF request aborted/failed"
    ::= { affirmedServicesContentHttpProxyServiceStatisticsCluster-levelRequestMethodEntry 57 }

affirmedServicesContentHttpProxyServiceStatisticsCluster-levelRequestMethodMethodmkworkspacereceived OBJECT-TYPE
    SYNTAX      ConfdString
    MAX-ACCESS  read-only
    STATUS      current
    DESCRIPTION "Total number of MKWORKSPACE request received"
    ::= { affirmedServicesContentHttpProxyServiceStatisticsCluster-levelRequestMethodEntry 58 }

affirmedServicesContentHttpProxyServiceStatisticsCluster-levelRequestMethodMethodmkworkspaceaborted OBJECT-TYPE
    SYNTAX      ConfdString
    MAX-ACCESS  read-only
    STATUS      current
    DESCRIPTION "Total number of MKWORKSPACE request aborted/failed"
    ::= { affirmedServicesContentHttpProxyServiceStatisticsCluster-levelRequestMethodEntry 59 }

affirmedServicesContentHttpProxyServiceStatisticsCluster-levelRequestMethodMethodorderpatchreceived OBJECT-TYPE
    SYNTAX      ConfdString
    MAX-ACCESS  read-only
    STATUS      current
    DESCRIPTION "Total number of ORDERPATCH request received"
    ::= { affirmedServicesContentHttpProxyServiceStatisticsCluster-levelRequestMethodEntry 60 }

affirmedServicesContentHttpProxyServiceStatisticsCluster-levelRequestMethodMethodorderpatchaborted OBJECT-TYPE
    SYNTAX      ConfdString
    MAX-ACCESS  read-only
    STATUS      current
    DESCRIPTION "Total number of ORDERPATCH request aborted/failed"
    ::= { affirmedServicesContentHttpProxyServiceStatisticsCluster-levelRequestMethodEntry 61 }

affirmedServicesContentHttpProxyServiceStatisticsCluster-levelRequestMethodMethodprireceived OBJECT-TYPE
    SYNTAX      ConfdString
    MAX-ACCESS  read-only
    STATUS      current
    DESCRIPTION "Total number of PRI request received"
    ::= { affirmedServicesContentHttpProxyServiceStatisticsCluster-levelRequestMethodEntry 62 }

affirmedServicesContentHttpProxyServiceStatisticsCluster-levelRequestMethodMethodpriaborted OBJECT-TYPE
    SYNTAX      ConfdString
    MAX-ACCESS  read-only
    STATUS      current
    DESCRIPTION "Total number of PRI request aborted/failed"
    ::= { affirmedServicesContentHttpProxyServiceStatisticsCluster-levelRequestMethodEntry 63 }

affirmedServicesContentHttpProxyServiceStatisticsCluster-levelRequestMethodMethodrebindreceived OBJECT-TYPE
    SYNTAX      ConfdString
    MAX-ACCESS  read-only
    STATUS      current
    DESCRIPTION "Total number of REBIND request received"
    ::= { affirmedServicesContentHttpProxyServiceStatisticsCluster-levelRequestMethodEntry 64 }

affirmedServicesContentHttpProxyServiceStatisticsCluster-levelRequestMethodMethodrebindaborted OBJECT-TYPE
    SYNTAX      ConfdString
    MAX-ACCESS  read-only
    STATUS      current
    DESCRIPTION "Total number of REBIND request aborted/failed"
    ::= { affirmedServicesContentHttpProxyServiceStatisticsCluster-levelRequestMethodEntry 65 }

affirmedServicesContentHttpProxyServiceStatisticsCluster-levelRequestMethodMethodreportreceived OBJECT-TYPE
    SYNTAX      ConfdString
    MAX-ACCESS  read-only
    STATUS      current
    DESCRIPTION "Total number of REPORT request received"
    ::= { affirmedServicesContentHttpProxyServiceStatisticsCluster-levelRequestMethodEntry 66 }

affirmedServicesContentHttpProxyServiceStatisticsCluster-levelRequestMethodMethodreportaborted OBJECT-TYPE
    SYNTAX      ConfdString
    MAX-ACCESS  read-only
    STATUS      current
    DESCRIPTION "Total number of REPORT request aborted/failed"
    ::= { affirmedServicesContentHttpProxyServiceStatisticsCluster-levelRequestMethodEntry 67 }

affirmedServicesContentHttpProxyServiceStatisticsCluster-levelRequestMethodMethodsearchreceived OBJECT-TYPE
    SYNTAX      ConfdString
    MAX-ACCESS  read-only
    STATUS      current
    DESCRIPTION "Total number of SEARCH request received"
    ::= { affirmedServicesContentHttpProxyServiceStatisticsCluster-levelRequestMethodEntry 68 }

affirmedServicesContentHttpProxyServiceStatisticsCluster-levelRequestMethodMethodsearchaborted OBJECT-TYPE
    SYNTAX      ConfdString
    MAX-ACCESS  read-only
    STATUS      current
    DESCRIPTION "Total number of SEARCH request aborted/failed"
    ::= { affirmedServicesContentHttpProxyServiceStatisticsCluster-levelRequestMethodEntry 69 }

affirmedServicesContentHttpProxyServiceStatisticsCluster-levelRequestMethodMethodunbindreceived OBJECT-TYPE
    SYNTAX      ConfdString
    MAX-ACCESS  read-only
    STATUS      current
    DESCRIPTION "Total number of UNBIND request received"
    ::= { affirmedServicesContentHttpProxyServiceStatisticsCluster-levelRequestMethodEntry 70 }

affirmedServicesContentHttpProxyServiceStatisticsCluster-levelRequestMethodMethodunbindaborted OBJECT-TYPE
    SYNTAX      ConfdString
    MAX-ACCESS  read-only
    STATUS      current
    DESCRIPTION "Total number of UNBIND request aborted/failed"
    ::= { affirmedServicesContentHttpProxyServiceStatisticsCluster-levelRequestMethodEntry 71 }

affirmedServicesContentHttpProxyServiceStatisticsCluster-levelRequestMethodMethoduncheckoutreceived OBJECT-TYPE
    SYNTAX      ConfdString
    MAX-ACCESS  read-only
    STATUS      current
    DESCRIPTION "Total number of UNCHECKOUT request received"
    ::= { affirmedServicesContentHttpProxyServiceStatisticsCluster-levelRequestMethodEntry 72 }

affirmedServicesContentHttpProxyServiceStatisticsCluster-levelRequestMethodMethoduncheckoutaborted OBJECT-TYPE
    SYNTAX      ConfdString
    MAX-ACCESS  read-only
    STATUS      current
    DESCRIPTION "Total number of UNCHECKOUT request aborted/failed"
    ::= { affirmedServicesContentHttpProxyServiceStatisticsCluster-levelRequestMethodEntry 73 }

affirmedServicesContentHttpProxyServiceStatisticsCluster-levelRequestMethodMethodunlinkreceived OBJECT-TYPE
    SYNTAX      ConfdString
    MAX-ACCESS  read-only
    STATUS      current
    DESCRIPTION "Total number of UNLINK request received"
    ::= { affirmedServicesContentHttpProxyServiceStatisticsCluster-levelRequestMethodEntry 74 }

affirmedServicesContentHttpProxyServiceStatisticsCluster-levelRequestMethodMethodunlinkaborted OBJECT-TYPE
    SYNTAX      ConfdString
    MAX-ACCESS  read-only
    STATUS      current
    DESCRIPTION "Total number of UNLINK request aborted/failed"
    ::= { affirmedServicesContentHttpProxyServiceStatisticsCluster-levelRequestMethodEntry 75 }

affirmedServicesContentHttpProxyServiceStatisticsCluster-levelRequestMethodMethodupdatereceived OBJECT-TYPE
    SYNTAX      ConfdString
    MAX-ACCESS  read-only
    STATUS      current
    DESCRIPTION "Total number of UPDATE request received"
    ::= { affirmedServicesContentHttpProxyServiceStatisticsCluster-levelRequestMethodEntry 76 }

affirmedServicesContentHttpProxyServiceStatisticsCluster-levelRequestMethodMethodupdateaborted OBJECT-TYPE
    SYNTAX      ConfdString
    MAX-ACCESS  read-only
    STATUS      current
    DESCRIPTION "Total number of UPDATE request aborted/failed"
    ::= { affirmedServicesContentHttpProxyServiceStatisticsCluster-levelRequestMethodEntry 77 }

affirmedServicesContentHttpProxyServiceStatisticsCluster-levelRequestMethodMethodupdateredirectrefreceived OBJECT-TYPE
    SYNTAX      ConfdString
    MAX-ACCESS  read-only
    STATUS      current
    DESCRIPTION "Total number of UPDATEREDIRECTREF request received"
    ::= { affirmedServicesContentHttpProxyServiceStatisticsCluster-levelRequestMethodEntry 78 }

affirmedServicesContentHttpProxyServiceStatisticsCluster-levelRequestMethodMethodupdateredirectrefaborted OBJECT-TYPE
    SYNTAX      ConfdString
    MAX-ACCESS  read-only
    STATUS      current
    DESCRIPTION "Total number of UPDATEREDIRECTREF request aborted/failed"
    ::= { affirmedServicesContentHttpProxyServiceStatisticsCluster-levelRequestMethodEntry 79 }

affirmedServicesContentHttpProxyServiceStatisticsCluster-levelRequestMethodMethodversioncontrolreceived OBJECT-TYPE
    SYNTAX      ConfdString
    MAX-ACCESS  read-only
    STATUS      current
    DESCRIPTION "Total number of VERSION-CONTROL request received"
    ::= { affirmedServicesContentHttpProxyServiceStatisticsCluster-levelRequestMethodEntry 80 }

affirmedServicesContentHttpProxyServiceStatisticsCluster-levelRequestMethodMethodversioncontrolaborted OBJECT-TYPE
    SYNTAX      ConfdString
    MAX-ACCESS  read-only
    STATUS      current
    DESCRIPTION "Total number of VERSION-CONTROL request aborted/failed"
    ::= { affirmedServicesContentHttpProxyServiceStatisticsCluster-levelRequestMethodEntry 81 }

affirmedServicesContentHttpProxyServiceStatisticsCluster-levelRequestMethodUnsupportedmethodreceived OBJECT-TYPE
    SYNTAX      ConfdString
    MAX-ACCESS  read-only
    STATUS      current
    DESCRIPTION "Total number of Unsupported-Method request received"
    ::= { affirmedServicesContentHttpProxyServiceStatisticsCluster-levelRequestMethodEntry 82 }

affirmedServicesContentHttpProxyServiceStatisticsCluster-levelOverloadControlTable OBJECT-TYPE
    SYNTAX      SEQUENCE OF AffirmedServicesContentHttpProxyServiceStatisticsCluster-levelOverloadControlEntry
    MAX-ACCESS  not-accessible
    STATUS      current
    DESCRIPTION ""
    ::= { affirmedServicesContentHttpProxyServiceStatisticsCluster-level 6 }

affirmedServicesContentHttpProxyServiceStatisticsCluster-levelOverloadControlEntry OBJECT-TYPE
    SYNTAX      AffirmedServicesContentHttpProxyServiceStatisticsCluster-levelOverloadControlEntry
    MAX-ACCESS  not-accessible
    STATUS      current
    DESCRIPTION ""
    INDEX { affirmedServicesContentHttpProxyServiceStatisticsCluster-levelOverloadControlChassis }
        ::= { affirmedServicesContentHttpProxyServiceStatisticsCluster-levelOverloadControlTable 1 }

AffirmedServicesContentHttpProxyServiceStatisticsCluster-levelOverloadControlEntry ::=
    SEQUENCE {
        affirmedServicesContentHttpProxyServiceStatisticsCluster-levelOverloadControlChassis Unsigned32,
        affirmedServicesContentHttpProxyServiceStatisticsCluster-levelOverloadControlNumconnectionacceptsoc ConfdString,
        affirmedServicesContentHttpProxyServiceStatisticsCluster-levelOverloadControlNumconnectiondeniesoc ConfdString
    }

affirmedServicesContentHttpProxyServiceStatisticsCluster-levelOverloadControlChassis OBJECT-TYPE
    SYNTAX      Unsigned32
    MAX-ACCESS  not-accessible
    STATUS      current
    DESCRIPTION "chassis ID"
    ::= { affirmedServicesContentHttpProxyServiceStatisticsCluster-levelOverloadControlEntry 1 }

affirmedServicesContentHttpProxyServiceStatisticsCluster-levelOverloadControlNumconnectionacceptsoc OBJECT-TYPE
    SYNTAX      ConfdString
    MAX-ACCESS  read-only
    STATUS      current
    DESCRIPTION "Number of overload control connection accepts"
    ::= { affirmedServicesContentHttpProxyServiceStatisticsCluster-levelOverloadControlEntry 2 }

affirmedServicesContentHttpProxyServiceStatisticsCluster-levelOverloadControlNumconnectiondeniesoc OBJECT-TYPE
    SYNTAX      ConfdString
    MAX-ACCESS  read-only
    STATUS      current
    DESCRIPTION "Number of overload control connections denies"
    ::= { affirmedServicesContentHttpProxyServiceStatisticsCluster-levelOverloadControlEntry 3 }

affirmedServicesContentHttpProxyServiceStatisticsCluster-levelLatencyStatsTable OBJECT-TYPE
    SYNTAX      SEQUENCE OF AffirmedServicesContentHttpProxyServiceStatisticsCluster-levelLatencyStatsEntry
    MAX-ACCESS  not-accessible
    STATUS      current
    DESCRIPTION ""
    ::= { affirmedServicesContentHttpProxyServiceStatisticsCluster-level 7 }

affirmedServicesContentHttpProxyServiceStatisticsCluster-levelLatencyStatsEntry OBJECT-TYPE
    SYNTAX      AffirmedServicesContentHttpProxyServiceStatisticsCluster-levelLatencyStatsEntry
    MAX-ACCESS  not-accessible
    STATUS      current
    DESCRIPTION ""
    INDEX { affirmedServicesContentHttpProxyServiceStatisticsCluster-levelLatencyStatsChassis }
        ::= { affirmedServicesContentHttpProxyServiceStatisticsCluster-levelLatencyStatsTable 1 }

AffirmedServicesContentHttpProxyServiceStatisticsCluster-levelLatencyStatsEntry ::=
    SEQUENCE {
        affirmedServicesContentHttpProxyServiceStatisticsCluster-levelLatencyStatsChassis Unsigned32,
        affirmedServicesContentHttpProxyServiceStatisticsCluster-levelLatencyStatsLatencytnxtotal ConfdString,
        affirmedServicesContentHttpProxyServiceStatisticsCluster-levelLatencyStatsLatencytnxavg ConfdString,
        affirmedServicesContentHttpProxyServiceStatisticsCluster-levelLatencyStatsLatencytnxmax ConfdString,
        affirmedServicesContentHttpProxyServiceStatisticsCluster-levelLatencyStatsLatencytnx10 ConfdString,
        affirmedServicesContentHttpProxyServiceStatisticsCluster-levelLatencyStatsLatencytnx20 ConfdString,
        affirmedServicesContentHttpProxyServiceStatisticsCluster-levelLatencyStatsLatencytnx30 ConfdString,
        affirmedServicesContentHttpProxyServiceStatisticsCluster-levelLatencyStatsLatencytnx40 ConfdString,
        affirmedServicesContentHttpProxyServiceStatisticsCluster-levelLatencyStatsLatencytnx50 ConfdString,
        affirmedServicesContentHttpProxyServiceStatisticsCluster-levelLatencyStatsLatencytnx100 ConfdString,
        affirmedServicesContentHttpProxyServiceStatisticsCluster-levelLatencyStatsLatencytnx101 ConfdString,
        affirmedServicesContentHttpProxyServiceStatisticsCluster-levelLatencyStatsLatencyrequestavg ConfdString,
        affirmedServicesContentHttpProxyServiceStatisticsCluster-levelLatencyStatsLatencyrequestmax ConfdString,
        affirmedServicesContentHttpProxyServiceStatisticsCluster-levelLatencyStatsLatencyrequest10 ConfdString,
        affirmedServicesContentHttpProxyServiceStatisticsCluster-levelLatencyStatsLatencyrequest20 ConfdString,
        affirmedServicesContentHttpProxyServiceStatisticsCluster-levelLatencyStatsLatencyrequest30 ConfdString,
        affirmedServicesContentHttpProxyServiceStatisticsCluster-levelLatencyStatsLatencyrequest40 ConfdString,
        affirmedServicesContentHttpProxyServiceStatisticsCluster-levelLatencyStatsLatencyrequest50 ConfdString,
        affirmedServicesContentHttpProxyServiceStatisticsCluster-levelLatencyStatsLatencyrequest100 ConfdString,
        affirmedServicesContentHttpProxyServiceStatisticsCluster-levelLatencyStatsLatencyrequest101 ConfdString,
        affirmedServicesContentHttpProxyServiceStatisticsCluster-levelLatencyStatsLatencyresponseavg ConfdString,
        affirmedServicesContentHttpProxyServiceStatisticsCluster-levelLatencyStatsLatencyresponsemax ConfdString,
        affirmedServicesContentHttpProxyServiceStatisticsCluster-levelLatencyStatsLatencyresponse10 ConfdString,
        affirmedServicesContentHttpProxyServiceStatisticsCluster-levelLatencyStatsLatencyresponse20 ConfdString,
        affirmedServicesContentHttpProxyServiceStatisticsCluster-levelLatencyStatsLatencyresponse30 ConfdString,
        affirmedServicesContentHttpProxyServiceStatisticsCluster-levelLatencyStatsLatencyresponse40 ConfdString,
        affirmedServicesContentHttpProxyServiceStatisticsCluster-levelLatencyStatsLatencyresponse50 ConfdString,
        affirmedServicesContentHttpProxyServiceStatisticsCluster-levelLatencyStatsLatencyresponse100 ConfdString,
        affirmedServicesContentHttpProxyServiceStatisticsCluster-levelLatencyStatsLatencyresponse101 ConfdString,
        affirmedServicesContentHttpProxyServiceStatisticsCluster-levelLatencyStatsLatencyclientconntotal ConfdString,
        affirmedServicesContentHttpProxyServiceStatisticsCluster-levelLatencyStatsLatencyclientdatarxavg ConfdString,
        affirmedServicesContentHttpProxyServiceStatisticsCluster-levelLatencyStatsLatencyclientdatarxmax ConfdString,
        affirmedServicesContentHttpProxyServiceStatisticsCluster-levelLatencyStatsLatencyclientdatarx10 ConfdString,
        affirmedServicesContentHttpProxyServiceStatisticsCluster-levelLatencyStatsLatencyclientdatarx20 ConfdString,
        affirmedServicesContentHttpProxyServiceStatisticsCluster-levelLatencyStatsLatencyclientdatarx30 ConfdString,
        affirmedServicesContentHttpProxyServiceStatisticsCluster-levelLatencyStatsLatencyclientdatarx40 ConfdString,
        affirmedServicesContentHttpProxyServiceStatisticsCluster-levelLatencyStatsLatencyclientdatarx50 ConfdString,
        affirmedServicesContentHttpProxyServiceStatisticsCluster-levelLatencyStatsLatencyclientdatarx100 ConfdString,
        affirmedServicesContentHttpProxyServiceStatisticsCluster-levelLatencyStatsLatencyclientdatarx101 ConfdString,
        affirmedServicesContentHttpProxyServiceStatisticsCluster-levelLatencyStatsLatencyserverconntotal ConfdString,
        affirmedServicesContentHttpProxyServiceStatisticsCluster-levelLatencyStatsLatencyserverdatatxavg ConfdString,
        affirmedServicesContentHttpProxyServiceStatisticsCluster-levelLatencyStatsLatencyserverdatatxmax ConfdString,
        affirmedServicesContentHttpProxyServiceStatisticsCluster-levelLatencyStatsLatencyserverdatatx10 ConfdString,
        affirmedServicesContentHttpProxyServiceStatisticsCluster-levelLatencyStatsLatencyserverdatatx20 ConfdString,
        affirmedServicesContentHttpProxyServiceStatisticsCluster-levelLatencyStatsLatencyserverdatatx30 ConfdString,
        affirmedServicesContentHttpProxyServiceStatisticsCluster-levelLatencyStatsLatencyserverdatatx40 ConfdString,
        affirmedServicesContentHttpProxyServiceStatisticsCluster-levelLatencyStatsLatencyserverdatatx50 ConfdString,
        affirmedServicesContentHttpProxyServiceStatisticsCluster-levelLatencyStatsLatencyserverdatatx100 ConfdString,
        affirmedServicesContentHttpProxyServiceStatisticsCluster-levelLatencyStatsLatencyserverdatatx101 ConfdString
    }

affirmedServicesContentHttpProxyServiceStatisticsCluster-levelLatencyStatsChassis OBJECT-TYPE
    SYNTAX      Unsigned32
    MAX-ACCESS  not-accessible
    STATUS      current
    DESCRIPTION "chassis ID"
    ::= { affirmedServicesContentHttpProxyServiceStatisticsCluster-levelLatencyStatsEntry 1 }

affirmedServicesContentHttpProxyServiceStatisticsCluster-levelLatencyStatsLatencytnxtotal OBJECT-TYPE
    SYNTAX      ConfdString
    MAX-ACCESS  read-only
    STATUS      current
    DESCRIPTION "Total number of serviced HTTP transactions counted for latency calculation"
    ::= { affirmedServicesContentHttpProxyServiceStatisticsCluster-levelLatencyStatsEntry 2 }

affirmedServicesContentHttpProxyServiceStatisticsCluster-levelLatencyStatsLatencytnxavg OBJECT-TYPE
    SYNTAX      ConfdString
    MAX-ACCESS  read-only
    STATUS      current
    DESCRIPTION "HTTP Transaction Service Latency Cumulative Moving Average (ms)"
    ::= { affirmedServicesContentHttpProxyServiceStatisticsCluster-levelLatencyStatsEntry 3 }

affirmedServicesContentHttpProxyServiceStatisticsCluster-levelLatencyStatsLatencytnxmax OBJECT-TYPE
    SYNTAX      ConfdString
    MAX-ACCESS  read-only
    STATUS      current
    DESCRIPTION "HTTP Transaction Service Latency Maximum (ms)"
    ::= { affirmedServicesContentHttpProxyServiceStatisticsCluster-levelLatencyStatsEntry 4 }

affirmedServicesContentHttpProxyServiceStatisticsCluster-levelLatencyStatsLatencytnx10 OBJECT-TYPE
    SYNTAX      ConfdString
    MAX-ACCESS  read-only
    STATUS      current
    DESCRIPTION "HTTP Transaction with Latency 0-10 (ms)"
    ::= { affirmedServicesContentHttpProxyServiceStatisticsCluster-levelLatencyStatsEntry 5 }

affirmedServicesContentHttpProxyServiceStatisticsCluster-levelLatencyStatsLatencytnx20 OBJECT-TYPE
    SYNTAX      ConfdString
    MAX-ACCESS  read-only
    STATUS      current
    DESCRIPTION "HTTP Transaction with Latency 11-20 (ms)"
    ::= { affirmedServicesContentHttpProxyServiceStatisticsCluster-levelLatencyStatsEntry 6 }

affirmedServicesContentHttpProxyServiceStatisticsCluster-levelLatencyStatsLatencytnx30 OBJECT-TYPE
    SYNTAX      ConfdString
    MAX-ACCESS  read-only
    STATUS      current
    DESCRIPTION "HTTP Transaction with Latency 21-30 (ms)"
    ::= { affirmedServicesContentHttpProxyServiceStatisticsCluster-levelLatencyStatsEntry 7 }

affirmedServicesContentHttpProxyServiceStatisticsCluster-levelLatencyStatsLatencytnx40 OBJECT-TYPE
    SYNTAX      ConfdString
    MAX-ACCESS  read-only
    STATUS      current
    DESCRIPTION "HTTP Transaction with Latency 31-40 (ms)"
    ::= { affirmedServicesContentHttpProxyServiceStatisticsCluster-levelLatencyStatsEntry 8 }

affirmedServicesContentHttpProxyServiceStatisticsCluster-levelLatencyStatsLatencytnx50 OBJECT-TYPE
    SYNTAX      ConfdString
    MAX-ACCESS  read-only
    STATUS      current
    DESCRIPTION "HTTP Transaction with Latency 41-50 (ms)"
    ::= { affirmedServicesContentHttpProxyServiceStatisticsCluster-levelLatencyStatsEntry 9 }

affirmedServicesContentHttpProxyServiceStatisticsCluster-levelLatencyStatsLatencytnx100 OBJECT-TYPE
    SYNTAX      ConfdString
    MAX-ACCESS  read-only
    STATUS      current
    DESCRIPTION "HTTP Transaction with Latency 51-100 (ms)"
    ::= { affirmedServicesContentHttpProxyServiceStatisticsCluster-levelLatencyStatsEntry 10 }

affirmedServicesContentHttpProxyServiceStatisticsCluster-levelLatencyStatsLatencytnx101 OBJECT-TYPE
    SYNTAX      ConfdString
    MAX-ACCESS  read-only
    STATUS      current
    DESCRIPTION "HTTP Transaction with Latency 100+ (ms)"
    ::= { affirmedServicesContentHttpProxyServiceStatisticsCluster-levelLatencyStatsEntry 11 }

affirmedServicesContentHttpProxyServiceStatisticsCluster-levelLatencyStatsLatencyrequestavg OBJECT-TYPE
    SYNTAX      ConfdString
    MAX-ACCESS  read-only
    STATUS      current
    DESCRIPTION "HTTP Request Service Latency Cumulative Moving Average (ms)"
    ::= { affirmedServicesContentHttpProxyServiceStatisticsCluster-levelLatencyStatsEntry 12 }

affirmedServicesContentHttpProxyServiceStatisticsCluster-levelLatencyStatsLatencyrequestmax OBJECT-TYPE
    SYNTAX      ConfdString
    MAX-ACCESS  read-only
    STATUS      current
    DESCRIPTION "HTTP Request Service Latency Maximum (ms)"
    ::= { affirmedServicesContentHttpProxyServiceStatisticsCluster-levelLatencyStatsEntry 13 }

affirmedServicesContentHttpProxyServiceStatisticsCluster-levelLatencyStatsLatencyrequest10 OBJECT-TYPE
    SYNTAX      ConfdString
    MAX-ACCESS  read-only
    STATUS      current
    DESCRIPTION "HTTP Request Service with Latency 0-10 (ms)"
    ::= { affirmedServicesContentHttpProxyServiceStatisticsCluster-levelLatencyStatsEntry 14 }

affirmedServicesContentHttpProxyServiceStatisticsCluster-levelLatencyStatsLatencyrequest20 OBJECT-TYPE
    SYNTAX      ConfdString
    MAX-ACCESS  read-only
    STATUS      current
    DESCRIPTION "HTTP Request Service with Latency 11-20 (ms)"
    ::= { affirmedServicesContentHttpProxyServiceStatisticsCluster-levelLatencyStatsEntry 15 }

affirmedServicesContentHttpProxyServiceStatisticsCluster-levelLatencyStatsLatencyrequest30 OBJECT-TYPE
    SYNTAX      ConfdString
    MAX-ACCESS  read-only
    STATUS      current
    DESCRIPTION "HTTP Request Service with Latency 21-30 (ms)"
    ::= { affirmedServicesContentHttpProxyServiceStatisticsCluster-levelLatencyStatsEntry 16 }

affirmedServicesContentHttpProxyServiceStatisticsCluster-levelLatencyStatsLatencyrequest40 OBJECT-TYPE
    SYNTAX      ConfdString
    MAX-ACCESS  read-only
    STATUS      current
    DESCRIPTION "HTTP Request Service with Latency 31-40 (ms)"
    ::= { affirmedServicesContentHttpProxyServiceStatisticsCluster-levelLatencyStatsEntry 17 }

affirmedServicesContentHttpProxyServiceStatisticsCluster-levelLatencyStatsLatencyrequest50 OBJECT-TYPE
    SYNTAX      ConfdString
    MAX-ACCESS  read-only
    STATUS      current
    DESCRIPTION "HTTP Request Service with Latency 41-50 (ms)"
    ::= { affirmedServicesContentHttpProxyServiceStatisticsCluster-levelLatencyStatsEntry 18 }

affirmedServicesContentHttpProxyServiceStatisticsCluster-levelLatencyStatsLatencyrequest100 OBJECT-TYPE
    SYNTAX      ConfdString
    MAX-ACCESS  read-only
    STATUS      current
    DESCRIPTION "HTTP Request Service with Latency 51-100 (ms)"
    ::= { affirmedServicesContentHttpProxyServiceStatisticsCluster-levelLatencyStatsEntry 19 }

affirmedServicesContentHttpProxyServiceStatisticsCluster-levelLatencyStatsLatencyrequest101 OBJECT-TYPE
    SYNTAX      ConfdString
    MAX-ACCESS  read-only
    STATUS      current
    DESCRIPTION "HTTP Request Service with Latency 100+ (ms)"
    ::= { affirmedServicesContentHttpProxyServiceStatisticsCluster-levelLatencyStatsEntry 20 }

affirmedServicesContentHttpProxyServiceStatisticsCluster-levelLatencyStatsLatencyresponseavg OBJECT-TYPE
    SYNTAX      ConfdString
    MAX-ACCESS  read-only
    STATUS      current
    DESCRIPTION "HTTP Response Service Latency Cumulative Moving Average (ms)"
    ::= { affirmedServicesContentHttpProxyServiceStatisticsCluster-levelLatencyStatsEntry 21 }

affirmedServicesContentHttpProxyServiceStatisticsCluster-levelLatencyStatsLatencyresponsemax OBJECT-TYPE
    SYNTAX      ConfdString
    MAX-ACCESS  read-only
    STATUS      current
    DESCRIPTION "HTTP Response Service Latency Maximum (ms)"
    ::= { affirmedServicesContentHttpProxyServiceStatisticsCluster-levelLatencyStatsEntry 22 }

affirmedServicesContentHttpProxyServiceStatisticsCluster-levelLatencyStatsLatencyresponse10 OBJECT-TYPE
    SYNTAX      ConfdString
    MAX-ACCESS  read-only
    STATUS      current
    DESCRIPTION "HTTP Response Service with Latency 0-10 (ms)"
    ::= { affirmedServicesContentHttpProxyServiceStatisticsCluster-levelLatencyStatsEntry 23 }

affirmedServicesContentHttpProxyServiceStatisticsCluster-levelLatencyStatsLatencyresponse20 OBJECT-TYPE
    SYNTAX      ConfdString
    MAX-ACCESS  read-only
    STATUS      current
    DESCRIPTION "HTTP Response Service with Latency 11-20 (ms)"
    ::= { affirmedServicesContentHttpProxyServiceStatisticsCluster-levelLatencyStatsEntry 24 }

affirmedServicesContentHttpProxyServiceStatisticsCluster-levelLatencyStatsLatencyresponse30 OBJECT-TYPE
    SYNTAX      ConfdString
    MAX-ACCESS  read-only
    STATUS      current
    DESCRIPTION "HTTP Response Service with Latency 21-30 (ms)"
    ::= { affirmedServicesContentHttpProxyServiceStatisticsCluster-levelLatencyStatsEntry 25 }

affirmedServicesContentHttpProxyServiceStatisticsCluster-levelLatencyStatsLatencyresponse40 OBJECT-TYPE
    SYNTAX      ConfdString
    MAX-ACCESS  read-only
    STATUS      current
    DESCRIPTION "HTTP Response Service with Latency 31-40 (ms)"
    ::= { affirmedServicesContentHttpProxyServiceStatisticsCluster-levelLatencyStatsEntry 26 }

affirmedServicesContentHttpProxyServiceStatisticsCluster-levelLatencyStatsLatencyresponse50 OBJECT-TYPE
    SYNTAX      ConfdString
    MAX-ACCESS  read-only
    STATUS      current
    DESCRIPTION "HTTP Response Service with Latency 41-50 (ms)"
    ::= { affirmedServicesContentHttpProxyServiceStatisticsCluster-levelLatencyStatsEntry 27 }

affirmedServicesContentHttpProxyServiceStatisticsCluster-levelLatencyStatsLatencyresponse100 OBJECT-TYPE
    SYNTAX      ConfdString
    MAX-ACCESS  read-only
    STATUS      current
    DESCRIPTION "HTTP Response Service with Latency 51-100 (ms)"
    ::= { affirmedServicesContentHttpProxyServiceStatisticsCluster-levelLatencyStatsEntry 28 }

affirmedServicesContentHttpProxyServiceStatisticsCluster-levelLatencyStatsLatencyresponse101 OBJECT-TYPE
    SYNTAX      ConfdString
    MAX-ACCESS  read-only
    STATUS      current
    DESCRIPTION "HTTP Response Service with Latency 100+ (ms)"
    ::= { affirmedServicesContentHttpProxyServiceStatisticsCluster-levelLatencyStatsEntry 29 }

affirmedServicesContentHttpProxyServiceStatisticsCluster-levelLatencyStatsLatencyclientconntotal OBJECT-TYPE
    SYNTAX      ConfdString
    MAX-ACCESS  read-only
    STATUS      current
    DESCRIPTION "Total number of client connections counted for latency calculation"
    ::= { affirmedServicesContentHttpProxyServiceStatisticsCluster-levelLatencyStatsEntry 30 }

affirmedServicesContentHttpProxyServiceStatisticsCluster-levelLatencyStatsLatencyclientdatarxavg OBJECT-TYPE
    SYNTAX      ConfdString
    MAX-ACCESS  read-only
    STATUS      current
    DESCRIPTION "Client Connection Receiving Data Delay Average (ms)"
    ::= { affirmedServicesContentHttpProxyServiceStatisticsCluster-levelLatencyStatsEntry 31 }

affirmedServicesContentHttpProxyServiceStatisticsCluster-levelLatencyStatsLatencyclientdatarxmax OBJECT-TYPE
    SYNTAX      ConfdString
    MAX-ACCESS  read-only
    STATUS      current
    DESCRIPTION "Client Connection Receiving Data Delay Maximum (ms)"
    ::= { affirmedServicesContentHttpProxyServiceStatisticsCluster-levelLatencyStatsEntry 32 }

affirmedServicesContentHttpProxyServiceStatisticsCluster-levelLatencyStatsLatencyclientdatarx10 OBJECT-TYPE
    SYNTAX      ConfdString
    MAX-ACCESS  read-only
    STATUS      current
    DESCRIPTION "Client Connection with Receiving Data Delay 0-10 (ms)"
    ::= { affirmedServicesContentHttpProxyServiceStatisticsCluster-levelLatencyStatsEntry 33 }

affirmedServicesContentHttpProxyServiceStatisticsCluster-levelLatencyStatsLatencyclientdatarx20 OBJECT-TYPE
    SYNTAX      ConfdString
    MAX-ACCESS  read-only
    STATUS      current
    DESCRIPTION "Client Connection with Receiving Data Delay 11-20 (ms)"
    ::= { affirmedServicesContentHttpProxyServiceStatisticsCluster-levelLatencyStatsEntry 34 }

affirmedServicesContentHttpProxyServiceStatisticsCluster-levelLatencyStatsLatencyclientdatarx30 OBJECT-TYPE
    SYNTAX      ConfdString
    MAX-ACCESS  read-only
    STATUS      current
    DESCRIPTION "Client Connection with Receiving Data Delay 21-30 (ms)"
    ::= { affirmedServicesContentHttpProxyServiceStatisticsCluster-levelLatencyStatsEntry 35 }

affirmedServicesContentHttpProxyServiceStatisticsCluster-levelLatencyStatsLatencyclientdatarx40 OBJECT-TYPE
    SYNTAX      ConfdString
    MAX-ACCESS  read-only
    STATUS      current
    DESCRIPTION "Client Connection with Receiving Data Delay 31-40 (ms)"
    ::= { affirmedServicesContentHttpProxyServiceStatisticsCluster-levelLatencyStatsEntry 36 }

affirmedServicesContentHttpProxyServiceStatisticsCluster-levelLatencyStatsLatencyclientdatarx50 OBJECT-TYPE
    SYNTAX      ConfdString
    MAX-ACCESS  read-only
    STATUS      current
    DESCRIPTION "Client Connection with Receiving Data Delay 41-50 (ms)"
    ::= { affirmedServicesContentHttpProxyServiceStatisticsCluster-levelLatencyStatsEntry 37 }

affirmedServicesContentHttpProxyServiceStatisticsCluster-levelLatencyStatsLatencyclientdatarx100 OBJECT-TYPE
    SYNTAX      ConfdString
    MAX-ACCESS  read-only
    STATUS      current
    DESCRIPTION "Client Connection with Receiving Data Delay 51-100 (ms)"
    ::= { affirmedServicesContentHttpProxyServiceStatisticsCluster-levelLatencyStatsEntry 38 }

affirmedServicesContentHttpProxyServiceStatisticsCluster-levelLatencyStatsLatencyclientdatarx101 OBJECT-TYPE
    SYNTAX      ConfdString
    MAX-ACCESS  read-only
    STATUS      current
    DESCRIPTION "Client Connection with Receiving Data Delay 100+ (ms)"
    ::= { affirmedServicesContentHttpProxyServiceStatisticsCluster-levelLatencyStatsEntry 39 }

affirmedServicesContentHttpProxyServiceStatisticsCluster-levelLatencyStatsLatencyserverconntotal OBJECT-TYPE
    SYNTAX      ConfdString
    MAX-ACCESS  read-only
    STATUS      current
    DESCRIPTION "Total number of server connections counted for latency calculation"
    ::= { affirmedServicesContentHttpProxyServiceStatisticsCluster-levelLatencyStatsEntry 40 }

affirmedServicesContentHttpProxyServiceStatisticsCluster-levelLatencyStatsLatencyserverdatatxavg OBJECT-TYPE
    SYNTAX      ConfdString
    MAX-ACCESS  read-only
    STATUS      current
    DESCRIPTION "Server Connection Transmitting Data Delay Average (ms)"
    ::= { affirmedServicesContentHttpProxyServiceStatisticsCluster-levelLatencyStatsEntry 41 }

affirmedServicesContentHttpProxyServiceStatisticsCluster-levelLatencyStatsLatencyserverdatatxmax OBJECT-TYPE
    SYNTAX      ConfdString
    MAX-ACCESS  read-only
    STATUS      current
    DESCRIPTION "Server Connection Transmitting Data Delay Maximum (ms)"
    ::= { affirmedServicesContentHttpProxyServiceStatisticsCluster-levelLatencyStatsEntry 42 }

affirmedServicesContentHttpProxyServiceStatisticsCluster-levelLatencyStatsLatencyserverdatatx10 OBJECT-TYPE
    SYNTAX      ConfdString
    MAX-ACCESS  read-only
    STATUS      current
    DESCRIPTION "Server Connection with Transmitting Data Delay 0-10 (ms)"
    ::= { affirmedServicesContentHttpProxyServiceStatisticsCluster-levelLatencyStatsEntry 43 }

affirmedServicesContentHttpProxyServiceStatisticsCluster-levelLatencyStatsLatencyserverdatatx20 OBJECT-TYPE
    SYNTAX      ConfdString
    MAX-ACCESS  read-only
    STATUS      current
    DESCRIPTION "Server Connection with Transmitting Data Delay 11-20 (ms)"
    ::= { affirmedServicesContentHttpProxyServiceStatisticsCluster-levelLatencyStatsEntry 44 }

affirmedServicesContentHttpProxyServiceStatisticsCluster-levelLatencyStatsLatencyserverdatatx30 OBJECT-TYPE
    SYNTAX      ConfdString
    MAX-ACCESS  read-only
    STATUS      current
    DESCRIPTION "Server Connection with Transmitting Data Delay 21-30 (ms)"
    ::= { affirmedServicesContentHttpProxyServiceStatisticsCluster-levelLatencyStatsEntry 45 }

affirmedServicesContentHttpProxyServiceStatisticsCluster-levelLatencyStatsLatencyserverdatatx40 OBJECT-TYPE
    SYNTAX      ConfdString
    MAX-ACCESS  read-only
    STATUS      current
    DESCRIPTION "Server Connection with Transmitting Data Delay 31-40 (ms)"
    ::= { affirmedServicesContentHttpProxyServiceStatisticsCluster-levelLatencyStatsEntry 46 }

affirmedServicesContentHttpProxyServiceStatisticsCluster-levelLatencyStatsLatencyserverdatatx50 OBJECT-TYPE
    SYNTAX      ConfdString
    MAX-ACCESS  read-only
    STATUS      current
    DESCRIPTION "Server Connection with Transmitting Data Delay 41-50 (ms)"
    ::= { affirmedServicesContentHttpProxyServiceStatisticsCluster-levelLatencyStatsEntry 47 }

affirmedServicesContentHttpProxyServiceStatisticsCluster-levelLatencyStatsLatencyserverdatatx100 OBJECT-TYPE
    SYNTAX      ConfdString
    MAX-ACCESS  read-only
    STATUS      current
    DESCRIPTION "Server Connection with Transmitting Data Delay 51-100 (ms)"
    ::= { affirmedServicesContentHttpProxyServiceStatisticsCluster-levelLatencyStatsEntry 48 }

affirmedServicesContentHttpProxyServiceStatisticsCluster-levelLatencyStatsLatencyserverdatatx101 OBJECT-TYPE
    SYNTAX      ConfdString
    MAX-ACCESS  read-only
    STATUS      current
    DESCRIPTION "Server Connection with Transmitting Data Delay 100+ (ms)"
    ::= { affirmedServicesContentHttpProxyServiceStatisticsCluster-levelLatencyStatsEntry 49 }

affirmedServicesContentHttpProxyServiceStatisticsCluster-levelHeaderEnrichmentTable OBJECT-TYPE
    SYNTAX      SEQUENCE OF AffirmedServicesContentHttpProxyServiceStatisticsCluster-levelHeaderEnrichmentEntry
    MAX-ACCESS  not-accessible
    STATUS      current
    DESCRIPTION ""
    ::= { affirmedServicesContentHttpProxyServiceStatisticsCluster-level 1 }

affirmedServicesContentHttpProxyServiceStatisticsCluster-levelHeaderEnrichmentEntry OBJECT-TYPE
    SYNTAX      AffirmedServicesContentHttpProxyServiceStatisticsCluster-levelHeaderEnrichmentEntry
    MAX-ACCESS  not-accessible
    STATUS      current
    DESCRIPTION ""
    INDEX { affirmedServicesContentHttpProxyServiceStatisticsCluster-levelHeaderEnrichmentChassis }
        ::= { affirmedServicesContentHttpProxyServiceStatisticsCluster-levelHeaderEnrichmentTable 1 }

AffirmedServicesContentHttpProxyServiceStatisticsCluster-levelHeaderEnrichmentEntry ::=
    SEQUENCE {
        affirmedServicesContentHttpProxyServiceStatisticsCluster-levelHeaderEnrichmentChassis Unsigned32,
        affirmedServicesContentHttpProxyServiceStatisticsCluster-levelHeaderEnrichmentOther ConfdString,
        affirmedServicesContentHttpProxyServiceStatisticsCluster-levelHeaderEnrichmentImsi ConfdString,
        affirmedServicesContentHttpProxyServiceStatisticsCluster-levelHeaderEnrichmentImsimd5 ConfdString,
        affirmedServicesContentHttpProxyServiceStatisticsCluster-levelHeaderEnrichmentImei ConfdString,
        affirmedServicesContentHttpProxyServiceStatisticsCluster-levelHeaderEnrichmentImeimd5 ConfdString,
        affirmedServicesContentHttpProxyServiceStatisticsCluster-levelHeaderEnrichmentMsisdn ConfdString,
        affirmedServicesContentHttpProxyServiceStatisticsCluster-levelHeaderEnrichmentMsisdnmd5 ConfdString,
        affirmedServicesContentHttpProxyServiceStatisticsCluster-levelHeaderEnrichmentMsisdnstatenc ConfdString,
        affirmedServicesContentHttpProxyServiceStatisticsCluster-levelHeaderEnrichmentMsisdndynmenc ConfdString,
        affirmedServicesContentHttpProxyServiceStatisticsCluster-levelHeaderEnrichmentUeipaddr ConfdString,
        affirmedServicesContentHttpProxyServiceStatisticsCluster-levelHeaderEnrichmentRattype ConfdString,
        affirmedServicesContentHttpProxyServiceStatisticsCluster-levelHeaderEnrichmentChargingchar ConfdString,
        affirmedServicesContentHttpProxyServiceStatisticsCluster-levelHeaderEnrichmentServingplmnid ConfdString,
        affirmedServicesContentHttpProxyServiceStatisticsCluster-levelHeaderEnrichmentUlicgi ConfdString,
        affirmedServicesContentHttpProxyServiceStatisticsCluster-levelHeaderEnrichmentUeipaddrport ConfdString,
        affirmedServicesContentHttpProxyServiceStatisticsCluster-levelHeaderEnrichmentUeport ConfdString,
        affirmedServicesContentHttpProxyServiceStatisticsCluster-levelHeaderEnrichmentUeipv4mappedipv6addr ConfdString,
        affirmedServicesContentHttpProxyServiceStatisticsCluster-levelHeaderEnrichmentUehttpprotocol ConfdString,
        affirmedServicesContentHttpProxyServiceStatisticsCluster-levelHeaderEnrichmentSgwipaddr ConfdString,
        affirmedServicesContentHttpProxyServiceStatisticsCluster-levelHeaderEnrichmentOrigapn ConfdString,
        affirmedServicesContentHttpProxyServiceStatisticsCluster-levelHeaderEnrichmentMappedapn ConfdString,
        affirmedServicesContentHttpProxyServiceStatisticsCluster-levelHeaderEnrichmentLtmiplaintextid ConfdString,
        affirmedServicesContentHttpProxyServiceStatisticsCluster-levelHeaderEnrichmentLtmistatictrustedid ConfdString,
        affirmedServicesContentHttpProxyServiceStatisticsCluster-levelHeaderEnrichmentLtmidynamictrustedid ConfdString,
        affirmedServicesContentHttpProxyServiceStatisticsCluster-levelHeaderEnrichmentLtmiexternalid ConfdString,
        affirmedServicesContentHttpProxyServiceStatisticsCluster-levelHeaderEnrichmentResellerid ConfdString,
        affirmedServicesContentHttpProxyServiceStatisticsCluster-levelHeaderEnrichmentOriginalurl ConfdString,
        affirmedServicesContentHttpProxyServiceStatisticsCluster-levelHeaderEnrichmentHttpversion ConfdString,
        affirmedServicesContentHttpProxyServiceStatisticsCluster-levelHeaderEnrichmentOthermd5 ConfdString,
        affirmedServicesContentHttpProxyServiceStatisticsCluster-levelHeaderEnrichmentOtherencrypted ConfdString,
        affirmedServicesContentHttpProxyServiceStatisticsCluster-levelHeaderEnrichmentImsiencrypted ConfdString,
        affirmedServicesContentHttpProxyServiceStatisticsCluster-levelHeaderEnrichmentImeiencrypted ConfdString,
        affirmedServicesContentHttpProxyServiceStatisticsCluster-levelHeaderEnrichmentMsisdnencrypted ConfdString,
        affirmedServicesContentHttpProxyServiceStatisticsCluster-levelHeaderEnrichmentUeipaddrmd5 ConfdString,
        affirmedServicesContentHttpProxyServiceStatisticsCluster-levelHeaderEnrichmentUeipaddrencrypted ConfdString,
        affirmedServicesContentHttpProxyServiceStatisticsCluster-levelHeaderEnrichmentRattypemd5 ConfdString,
        affirmedServicesContentHttpProxyServiceStatisticsCluster-levelHeaderEnrichmentRattypeencrypted ConfdString,
        affirmedServicesContentHttpProxyServiceStatisticsCluster-levelHeaderEnrichmentChargingcharmd5 ConfdString,
        affirmedServicesContentHttpProxyServiceStatisticsCluster-levelHeaderEnrichmentChargingcharencrypted ConfdString,
        affirmedServicesContentHttpProxyServiceStatisticsCluster-levelHeaderEnrichmentServingplmnidmd5 ConfdString,
        affirmedServicesContentHttpProxyServiceStatisticsCluster-levelHeaderEnrichmentServingplmnidencrypted ConfdString,
        affirmedServicesContentHttpProxyServiceStatisticsCluster-levelHeaderEnrichmentUlicgimd5 ConfdString,
        affirmedServicesContentHttpProxyServiceStatisticsCluster-levelHeaderEnrichmentUlicgiencrypted ConfdString,
        affirmedServicesContentHttpProxyServiceStatisticsCluster-levelHeaderEnrichmentSgwipaddrmd5 ConfdString,
        affirmedServicesContentHttpProxyServiceStatisticsCluster-levelHeaderEnrichmentSgwipaddrencrypted ConfdString,
        affirmedServicesContentHttpProxyServiceStatisticsCluster-levelHeaderEnrichmentOrigapnmd5 ConfdString,
        affirmedServicesContentHttpProxyServiceStatisticsCluster-levelHeaderEnrichmentOrigapnencrypted ConfdString,
        affirmedServicesContentHttpProxyServiceStatisticsCluster-levelHeaderEnrichmentSgwipv6addr ConfdString,
        affirmedServicesContentHttpProxyServiceStatisticsCluster-levelHeaderEnrichmentSgwipv6addrmd5 ConfdString,
        affirmedServicesContentHttpProxyServiceStatisticsCluster-levelHeaderEnrichmentSgwipv6addrencrypted ConfdString,
        affirmedServicesContentHttpProxyServiceStatisticsCluster-levelHeaderEnrichmentMsisdnstatacr ConfdString,
        affirmedServicesContentHttpProxyServiceStatisticsCluster-levelHeaderEnrichmentMsisdndynmacr ConfdString,
        affirmedServicesContentHttpProxyServiceStatisticsCluster-levelHeaderEnrichmentTimezone ConfdString,
        affirmedServicesContentHttpProxyServiceStatisticsCluster-levelHeaderEnrichmentHttpversionmd5 ConfdString,
        affirmedServicesContentHttpProxyServiceStatisticsCluster-levelHeaderEnrichmentHttpversionencrypted ConfdString
    }

affirmedServicesContentHttpProxyServiceStatisticsCluster-levelHeaderEnrichmentChassis OBJECT-TYPE
    SYNTAX      Unsigned32
    MAX-ACCESS  not-accessible
    STATUS      current
    DESCRIPTION "chassis ID"
    ::= { affirmedServicesContentHttpProxyServiceStatisticsCluster-levelHeaderEnrichmentEntry 1 }

affirmedServicesContentHttpProxyServiceStatisticsCluster-levelHeaderEnrichmentOther OBJECT-TYPE
    SYNTAX      ConfdString
    MAX-ACCESS  read-only
    STATUS      current
    DESCRIPTION "Header Additions - Other"
    ::= { affirmedServicesContentHttpProxyServiceStatisticsCluster-levelHeaderEnrichmentEntry 2 }

affirmedServicesContentHttpProxyServiceStatisticsCluster-levelHeaderEnrichmentImsi OBJECT-TYPE
    SYNTAX      ConfdString
    MAX-ACCESS  read-only
    STATUS      current
    DESCRIPTION "Header Additions - IMSI"
    ::= { affirmedServicesContentHttpProxyServiceStatisticsCluster-levelHeaderEnrichmentEntry 3 }

affirmedServicesContentHttpProxyServiceStatisticsCluster-levelHeaderEnrichmentImsimd5 OBJECT-TYPE
    SYNTAX      ConfdString
    MAX-ACCESS  read-only
    STATUS      current
    DESCRIPTION "Header Additions - IMSI MD5"
    ::= { affirmedServicesContentHttpProxyServiceStatisticsCluster-levelHeaderEnrichmentEntry 4 }

affirmedServicesContentHttpProxyServiceStatisticsCluster-levelHeaderEnrichmentImei OBJECT-TYPE
    SYNTAX      ConfdString
    MAX-ACCESS  read-only
    STATUS      current
    DESCRIPTION "Header Additions - IMEI"
    ::= { affirmedServicesContentHttpProxyServiceStatisticsCluster-levelHeaderEnrichmentEntry 5 }

affirmedServicesContentHttpProxyServiceStatisticsCluster-levelHeaderEnrichmentImeimd5 OBJECT-TYPE
    SYNTAX      ConfdString
    MAX-ACCESS  read-only
    STATUS      current
    DESCRIPTION "Header Additions - IMEI MD5"
    ::= { affirmedServicesContentHttpProxyServiceStatisticsCluster-levelHeaderEnrichmentEntry 6 }

affirmedServicesContentHttpProxyServiceStatisticsCluster-levelHeaderEnrichmentMsisdn OBJECT-TYPE
    SYNTAX      ConfdString
    MAX-ACCESS  read-only
    STATUS      current
    DESCRIPTION "Header Additions - MSISDN"
    ::= { affirmedServicesContentHttpProxyServiceStatisticsCluster-levelHeaderEnrichmentEntry 7 }

affirmedServicesContentHttpProxyServiceStatisticsCluster-levelHeaderEnrichmentMsisdnmd5 OBJECT-TYPE
    SYNTAX      ConfdString
    MAX-ACCESS  read-only
    STATUS      current
    DESCRIPTION "Header Additions - MSISDN MD5"
    ::= { affirmedServicesContentHttpProxyServiceStatisticsCluster-levelHeaderEnrichmentEntry 8 }

affirmedServicesContentHttpProxyServiceStatisticsCluster-levelHeaderEnrichmentMsisdnstatenc OBJECT-TYPE
    SYNTAX      ConfdString
    MAX-ACCESS  read-only
    STATUS      current
    DESCRIPTION "Header Additions - MSISDN Static Encryption"
    ::= { affirmedServicesContentHttpProxyServiceStatisticsCluster-levelHeaderEnrichmentEntry 9 }

affirmedServicesContentHttpProxyServiceStatisticsCluster-levelHeaderEnrichmentMsisdndynmenc OBJECT-TYPE
    SYNTAX      ConfdString
    MAX-ACCESS  read-only
    STATUS      current
    DESCRIPTION "Header Additions - MSISDN Dynamic Encryption"
    ::= { affirmedServicesContentHttpProxyServiceStatisticsCluster-levelHeaderEnrichmentEntry 10 }

affirmedServicesContentHttpProxyServiceStatisticsCluster-levelHeaderEnrichmentUeipaddr OBJECT-TYPE
    SYNTAX      ConfdString
    MAX-ACCESS  read-only
    STATUS      current
    DESCRIPTION "Header Additions - UE IP Address"
    ::= { affirmedServicesContentHttpProxyServiceStatisticsCluster-levelHeaderEnrichmentEntry 11 }

affirmedServicesContentHttpProxyServiceStatisticsCluster-levelHeaderEnrichmentRattype OBJECT-TYPE
    SYNTAX      ConfdString
    MAX-ACCESS  read-only
    STATUS      current
    DESCRIPTION "Header Additions - RAT Type"
    ::= { affirmedServicesContentHttpProxyServiceStatisticsCluster-levelHeaderEnrichmentEntry 12 }

affirmedServicesContentHttpProxyServiceStatisticsCluster-levelHeaderEnrichmentChargingchar OBJECT-TYPE
    SYNTAX      ConfdString
    MAX-ACCESS  read-only
    STATUS      current
    DESCRIPTION "Header Additions - Charging Characteristic"
    ::= { affirmedServicesContentHttpProxyServiceStatisticsCluster-levelHeaderEnrichmentEntry 13 }

affirmedServicesContentHttpProxyServiceStatisticsCluster-levelHeaderEnrichmentServingplmnid OBJECT-TYPE
    SYNTAX      ConfdString
    MAX-ACCESS  read-only
    STATUS      current
    DESCRIPTION "Header Additions - Serving PLMNID"
    ::= { affirmedServicesContentHttpProxyServiceStatisticsCluster-levelHeaderEnrichmentEntry 14 }

affirmedServicesContentHttpProxyServiceStatisticsCluster-levelHeaderEnrichmentUlicgi OBJECT-TYPE
    SYNTAX      ConfdString
    MAX-ACCESS  read-only
    STATUS      current
    DESCRIPTION "Header Additions - ULI CGI"
    ::= { affirmedServicesContentHttpProxyServiceStatisticsCluster-levelHeaderEnrichmentEntry 15 }

affirmedServicesContentHttpProxyServiceStatisticsCluster-levelHeaderEnrichmentUeipaddrport OBJECT-TYPE
    SYNTAX      ConfdString
    MAX-ACCESS  read-only
    STATUS      current
    DESCRIPTION "Header Additions - UE IP Address and Port Number"
    ::= { affirmedServicesContentHttpProxyServiceStatisticsCluster-levelHeaderEnrichmentEntry 16 }

affirmedServicesContentHttpProxyServiceStatisticsCluster-levelHeaderEnrichmentUeport OBJECT-TYPE
    SYNTAX      ConfdString
    MAX-ACCESS  read-only
    STATUS      current
    DESCRIPTION "Header Additions - UE IP Port Number"
    ::= { affirmedServicesContentHttpProxyServiceStatisticsCluster-levelHeaderEnrichmentEntry 17 }

affirmedServicesContentHttpProxyServiceStatisticsCluster-levelHeaderEnrichmentUeipv4mappedipv6addr OBJECT-TYPE
    SYNTAX      ConfdString
    MAX-ACCESS  read-only
    STATUS      current
    DESCRIPTION "Header Additions - UE IPv4 Mapped IPv6 Address"
    ::= { affirmedServicesContentHttpProxyServiceStatisticsCluster-levelHeaderEnrichmentEntry 18 }

affirmedServicesContentHttpProxyServiceStatisticsCluster-levelHeaderEnrichmentUehttpprotocol OBJECT-TYPE
    SYNTAX      ConfdString
    MAX-ACCESS  read-only
    STATUS      current
    DESCRIPTION "Header Additions - UE Http Protocol"
    ::= { affirmedServicesContentHttpProxyServiceStatisticsCluster-levelHeaderEnrichmentEntry 19 }

affirmedServicesContentHttpProxyServiceStatisticsCluster-levelHeaderEnrichmentSgwipaddr OBJECT-TYPE
    SYNTAX      ConfdString
    MAX-ACCESS  read-only
    STATUS      current
    DESCRIPTION "Header Additions - SGW IPv4 Address"
    ::= { affirmedServicesContentHttpProxyServiceStatisticsCluster-levelHeaderEnrichmentEntry 20 }

affirmedServicesContentHttpProxyServiceStatisticsCluster-levelHeaderEnrichmentOrigapn OBJECT-TYPE
    SYNTAX      ConfdString
    MAX-ACCESS  read-only
    STATUS      current
    DESCRIPTION "Header Additions - Original APN"
    ::= { affirmedServicesContentHttpProxyServiceStatisticsCluster-levelHeaderEnrichmentEntry 21 }

affirmedServicesContentHttpProxyServiceStatisticsCluster-levelHeaderEnrichmentMappedapn OBJECT-TYPE
    SYNTAX      ConfdString
    MAX-ACCESS  read-only
    STATUS      current
    DESCRIPTION "Header Additions - Mapped APN"
    ::= { affirmedServicesContentHttpProxyServiceStatisticsCluster-levelHeaderEnrichmentEntry 22 }

affirmedServicesContentHttpProxyServiceStatisticsCluster-levelHeaderEnrichmentLtmiplaintextid OBJECT-TYPE
    SYNTAX      ConfdString
    MAX-ACCESS  read-only
    STATUS      current
    DESCRIPTION "Header Additions - Ltmi Plain Text ID"
    ::= { affirmedServicesContentHttpProxyServiceStatisticsCluster-levelHeaderEnrichmentEntry 23 }

affirmedServicesContentHttpProxyServiceStatisticsCluster-levelHeaderEnrichmentLtmistatictrustedid OBJECT-TYPE
    SYNTAX      ConfdString
    MAX-ACCESS  read-only
    STATUS      current
    DESCRIPTION "Header Additions - Ltmi Static Trusted ID"
    ::= { affirmedServicesContentHttpProxyServiceStatisticsCluster-levelHeaderEnrichmentEntry 24 }

affirmedServicesContentHttpProxyServiceStatisticsCluster-levelHeaderEnrichmentLtmidynamictrustedid OBJECT-TYPE
    SYNTAX      ConfdString
    MAX-ACCESS  read-only
    STATUS      current
    DESCRIPTION "Header Additions - Ltmi Dynamic Trusted ID"
    ::= { affirmedServicesContentHttpProxyServiceStatisticsCluster-levelHeaderEnrichmentEntry 25 }

affirmedServicesContentHttpProxyServiceStatisticsCluster-levelHeaderEnrichmentLtmiexternalid OBJECT-TYPE
    SYNTAX      ConfdString
    MAX-ACCESS  read-only
    STATUS      current
    DESCRIPTION "Header Additions - Ltmi External ID"
    ::= { affirmedServicesContentHttpProxyServiceStatisticsCluster-levelHeaderEnrichmentEntry 26 }

affirmedServicesContentHttpProxyServiceStatisticsCluster-levelHeaderEnrichmentResellerid OBJECT-TYPE
    SYNTAX      ConfdString
    MAX-ACCESS  read-only
    STATUS      current
    DESCRIPTION "Header Additions - Reseller ID"
    ::= { affirmedServicesContentHttpProxyServiceStatisticsCluster-levelHeaderEnrichmentEntry 27 }

affirmedServicesContentHttpProxyServiceStatisticsCluster-levelHeaderEnrichmentOriginalurl OBJECT-TYPE
    SYNTAX      ConfdString
    MAX-ACCESS  read-only
    STATUS      current
    DESCRIPTION "Header Additions - Original URL"
    ::= { affirmedServicesContentHttpProxyServiceStatisticsCluster-levelHeaderEnrichmentEntry 28 }

affirmedServicesContentHttpProxyServiceStatisticsCluster-levelHeaderEnrichmentHttpversion OBJECT-TYPE
    SYNTAX      ConfdString
    MAX-ACCESS  read-only
    STATUS      current
    DESCRIPTION "Header Additions - HTTPVersion"
    ::= { affirmedServicesContentHttpProxyServiceStatisticsCluster-levelHeaderEnrichmentEntry 29 }

affirmedServicesContentHttpProxyServiceStatisticsCluster-levelHeaderEnrichmentOthermd5 OBJECT-TYPE
    SYNTAX      ConfdString
    MAX-ACCESS  read-only
    STATUS      current
    DESCRIPTION "Header Additions - Other MD5"
    ::= { affirmedServicesContentHttpProxyServiceStatisticsCluster-levelHeaderEnrichmentEntry 30 }

affirmedServicesContentHttpProxyServiceStatisticsCluster-levelHeaderEnrichmentOtherencrypted OBJECT-TYPE
    SYNTAX      ConfdString
    MAX-ACCESS  read-only
    STATUS      current
    DESCRIPTION "Header Additions - Other Encrypted"
    ::= { affirmedServicesContentHttpProxyServiceStatisticsCluster-levelHeaderEnrichmentEntry 31 }

affirmedServicesContentHttpProxyServiceStatisticsCluster-levelHeaderEnrichmentImsiencrypted OBJECT-TYPE
    SYNTAX      ConfdString
    MAX-ACCESS  read-only
    STATUS      current
    DESCRIPTION "Header Additions - IMSI Encrypted"
    ::= { affirmedServicesContentHttpProxyServiceStatisticsCluster-levelHeaderEnrichmentEntry 32 }

affirmedServicesContentHttpProxyServiceStatisticsCluster-levelHeaderEnrichmentImeiencrypted OBJECT-TYPE
    SYNTAX      ConfdString
    MAX-ACCESS  read-only
    STATUS      current
    DESCRIPTION "Header Additions - IMEI Encrypted"
    ::= { affirmedServicesContentHttpProxyServiceStatisticsCluster-levelHeaderEnrichmentEntry 33 }

affirmedServicesContentHttpProxyServiceStatisticsCluster-levelHeaderEnrichmentMsisdnencrypted OBJECT-TYPE
    SYNTAX      ConfdString
    MAX-ACCESS  read-only
    STATUS      current
    DESCRIPTION "Header Additions - MSISDN Encrypted"
    ::= { affirmedServicesContentHttpProxyServiceStatisticsCluster-levelHeaderEnrichmentEntry 34 }

affirmedServicesContentHttpProxyServiceStatisticsCluster-levelHeaderEnrichmentUeipaddrmd5 OBJECT-TYPE
    SYNTAX      ConfdString
    MAX-ACCESS  read-only
    STATUS      current
    DESCRIPTION "Header Additions - UE IP Address MD5"
    ::= { affirmedServicesContentHttpProxyServiceStatisticsCluster-levelHeaderEnrichmentEntry 35 }

affirmedServicesContentHttpProxyServiceStatisticsCluster-levelHeaderEnrichmentUeipaddrencrypted OBJECT-TYPE
    SYNTAX      ConfdString
    MAX-ACCESS  read-only
    STATUS      current
    DESCRIPTION "Header Additions - UE IP Address Encrypted"
    ::= { affirmedServicesContentHttpProxyServiceStatisticsCluster-levelHeaderEnrichmentEntry 36 }

affirmedServicesContentHttpProxyServiceStatisticsCluster-levelHeaderEnrichmentRattypemd5 OBJECT-TYPE
    SYNTAX      ConfdString
    MAX-ACCESS  read-only
    STATUS      current
    DESCRIPTION "Header Additions - RAT Type MD5"
    ::= { affirmedServicesContentHttpProxyServiceStatisticsCluster-levelHeaderEnrichmentEntry 37 }

affirmedServicesContentHttpProxyServiceStatisticsCluster-levelHeaderEnrichmentRattypeencrypted OBJECT-TYPE
    SYNTAX      ConfdString
    MAX-ACCESS  read-only
    STATUS      current
    DESCRIPTION "Header Additions - RAT Type Encrypted"
    ::= { affirmedServicesContentHttpProxyServiceStatisticsCluster-levelHeaderEnrichmentEntry 38 }

affirmedServicesContentHttpProxyServiceStatisticsCluster-levelHeaderEnrichmentChargingcharmd5 OBJECT-TYPE
    SYNTAX      ConfdString
    MAX-ACCESS  read-only
    STATUS      current
    DESCRIPTION "Header Additions - Charging Characteristic MD5"
    ::= { affirmedServicesContentHttpProxyServiceStatisticsCluster-levelHeaderEnrichmentEntry 39 }

affirmedServicesContentHttpProxyServiceStatisticsCluster-levelHeaderEnrichmentChargingcharencrypted OBJECT-TYPE
    SYNTAX      ConfdString
    MAX-ACCESS  read-only
    STATUS      current
    DESCRIPTION "Header Additions - Charging Characteristic Encrypted"
    ::= { affirmedServicesContentHttpProxyServiceStatisticsCluster-levelHeaderEnrichmentEntry 40 }

affirmedServicesContentHttpProxyServiceStatisticsCluster-levelHeaderEnrichmentServingplmnidmd5 OBJECT-TYPE
    SYNTAX      ConfdString
    MAX-ACCESS  read-only
    STATUS      current
    DESCRIPTION "Header Additions - Serving PLMNID MD5"
    ::= { affirmedServicesContentHttpProxyServiceStatisticsCluster-levelHeaderEnrichmentEntry 41 }

affirmedServicesContentHttpProxyServiceStatisticsCluster-levelHeaderEnrichmentServingplmnidencrypted OBJECT-TYPE
    SYNTAX      ConfdString
    MAX-ACCESS  read-only
    STATUS      current
    DESCRIPTION "Header Additions - Serving PLMNID Encrypted"
    ::= { affirmedServicesContentHttpProxyServiceStatisticsCluster-levelHeaderEnrichmentEntry 42 }

affirmedServicesContentHttpProxyServiceStatisticsCluster-levelHeaderEnrichmentUlicgimd5 OBJECT-TYPE
    SYNTAX      ConfdString
    MAX-ACCESS  read-only
    STATUS      current
    DESCRIPTION "Header Additions - ULI CGI MD5"
    ::= { affirmedServicesContentHttpProxyServiceStatisticsCluster-levelHeaderEnrichmentEntry 43 }

affirmedServicesContentHttpProxyServiceStatisticsCluster-levelHeaderEnrichmentUlicgiencrypted OBJECT-TYPE
    SYNTAX      ConfdString
    MAX-ACCESS  read-only
    STATUS      current
    DESCRIPTION "Header Additions - ULI CGI Encrypted"
    ::= { affirmedServicesContentHttpProxyServiceStatisticsCluster-levelHeaderEnrichmentEntry 44 }

affirmedServicesContentHttpProxyServiceStatisticsCluster-levelHeaderEnrichmentSgwipaddrmd5 OBJECT-TYPE
    SYNTAX      ConfdString
    MAX-ACCESS  read-only
    STATUS      current
    DESCRIPTION "Header Additions - SGW IPv4 Address MD5"
    ::= { affirmedServicesContentHttpProxyServiceStatisticsCluster-levelHeaderEnrichmentEntry 45 }

affirmedServicesContentHttpProxyServiceStatisticsCluster-levelHeaderEnrichmentSgwipaddrencrypted OBJECT-TYPE
    SYNTAX      ConfdString
    MAX-ACCESS  read-only
    STATUS      current
    DESCRIPTION "Header Additions - SGW IPv4 Address Encrypted"
    ::= { affirmedServicesContentHttpProxyServiceStatisticsCluster-levelHeaderEnrichmentEntry 46 }

affirmedServicesContentHttpProxyServiceStatisticsCluster-levelHeaderEnrichmentOrigapnmd5 OBJECT-TYPE
    SYNTAX      ConfdString
    MAX-ACCESS  read-only
    STATUS      current
    DESCRIPTION "Header Additions - Original APN MD5"
    ::= { affirmedServicesContentHttpProxyServiceStatisticsCluster-levelHeaderEnrichmentEntry 47 }

affirmedServicesContentHttpProxyServiceStatisticsCluster-levelHeaderEnrichmentOrigapnencrypted OBJECT-TYPE
    SYNTAX      ConfdString
    MAX-ACCESS  read-only
    STATUS      current
    DESCRIPTION "Header Additions - Original APN Encrypted"
    ::= { affirmedServicesContentHttpProxyServiceStatisticsCluster-levelHeaderEnrichmentEntry 48 }

affirmedServicesContentHttpProxyServiceStatisticsCluster-levelHeaderEnrichmentSgwipv6addr OBJECT-TYPE
    SYNTAX      ConfdString
    MAX-ACCESS  read-only
    STATUS      current
    DESCRIPTION "Header Additions - SGW IPv6 Address"
    ::= { affirmedServicesContentHttpProxyServiceStatisticsCluster-levelHeaderEnrichmentEntry 49 }

affirmedServicesContentHttpProxyServiceStatisticsCluster-levelHeaderEnrichmentSgwipv6addrmd5 OBJECT-TYPE
    SYNTAX      ConfdString
    MAX-ACCESS  read-only
    STATUS      current
    DESCRIPTION "Header Additions - SGW IPv6 Address MD5"
    ::= { affirmedServicesContentHttpProxyServiceStatisticsCluster-levelHeaderEnrichmentEntry 50 }

affirmedServicesContentHttpProxyServiceStatisticsCluster-levelHeaderEnrichmentSgwipv6addrencrypted OBJECT-TYPE
    SYNTAX      ConfdString
    MAX-ACCESS  read-only
    STATUS      current
    DESCRIPTION "Header Additions - SGW IPv6 Address Encrypted"
    ::= { affirmedServicesContentHttpProxyServiceStatisticsCluster-levelHeaderEnrichmentEntry 51 }

affirmedServicesContentHttpProxyServiceStatisticsCluster-levelHeaderEnrichmentMsisdnstatacr OBJECT-TYPE
    SYNTAX      ConfdString
    MAX-ACCESS  read-only
    STATUS      current
    DESCRIPTION "Header Additions - MSISDN Static ACR"
    ::= { affirmedServicesContentHttpProxyServiceStatisticsCluster-levelHeaderEnrichmentEntry 52 }

affirmedServicesContentHttpProxyServiceStatisticsCluster-levelHeaderEnrichmentMsisdndynmacr OBJECT-TYPE
    SYNTAX      ConfdString
    MAX-ACCESS  read-only
    STATUS      current
    DESCRIPTION "Header Additions - MSISDN Dynamic ACR"
    ::= { affirmedServicesContentHttpProxyServiceStatisticsCluster-levelHeaderEnrichmentEntry 53 }

affirmedServicesContentHttpProxyServiceStatisticsCluster-levelHeaderEnrichmentTimezone OBJECT-TYPE
    SYNTAX      ConfdString
    MAX-ACCESS  read-only
    STATUS      current
    DESCRIPTION "Header Additions - Time Zone"
    ::= { affirmedServicesContentHttpProxyServiceStatisticsCluster-levelHeaderEnrichmentEntry 54 }

affirmedServicesContentHttpProxyServiceStatisticsCluster-levelHeaderEnrichmentHttpversionmd5 OBJECT-TYPE
    SYNTAX      ConfdString
    MAX-ACCESS  read-only
    STATUS      current
    DESCRIPTION "Header Additions - HTTPVersion"
    ::= { affirmedServicesContentHttpProxyServiceStatisticsCluster-levelHeaderEnrichmentEntry 55 }

affirmedServicesContentHttpProxyServiceStatisticsCluster-levelHeaderEnrichmentHttpversionencrypted OBJECT-TYPE
    SYNTAX      ConfdString
    MAX-ACCESS  read-only
    STATUS      current
    DESCRIPTION "Header Additions - HTTPVersion"
    ::= { affirmedServicesContentHttpProxyServiceStatisticsCluster-levelHeaderEnrichmentEntry 56 }

affirmedServicesContentHttpProxyServiceStatisticsCluster-levelSummaryTable OBJECT-TYPE
    SYNTAX      SEQUENCE OF AffirmedServicesContentHttpProxyServiceStatisticsCluster-levelSummaryEntry
    MAX-ACCESS  not-accessible
    STATUS      current
    DESCRIPTION ""
    ::= { affirmedServicesContentHttpProxyServiceStatisticsCluster-level 8 }

affirmedServicesContentHttpProxyServiceStatisticsCluster-levelSummaryEntry OBJECT-TYPE
    SYNTAX      AffirmedServicesContentHttpProxyServiceStatisticsCluster-levelSummaryEntry
    MAX-ACCESS  not-accessible
    STATUS      current
    DESCRIPTION ""
    INDEX { affirmedServicesContentHttpProxyServiceStatisticsCluster-levelSummaryChassis }
        ::= { affirmedServicesContentHttpProxyServiceStatisticsCluster-levelSummaryTable 1 }

AffirmedServicesContentHttpProxyServiceStatisticsCluster-levelSummaryEntry ::=
    SEQUENCE {
        affirmedServicesContentHttpProxyServiceStatisticsCluster-levelSummaryChassis Unsigned32,
        affirmedServicesContentHttpProxyServiceStatisticsCluster-levelSummaryNumproxyserviceattempts ConfdString,
        affirmedServicesContentHttpProxyServiceStatisticsCluster-levelSummaryNumproxyservicesuccess ConfdString,
        affirmedServicesContentHttpProxyServiceStatisticsCluster-levelSummaryNumproxyservicesuccesscached ConfdString,
        affirmedServicesContentHttpProxyServiceStatisticsCluster-levelSummaryNumproxyserviceabortedbyclient ConfdString,
        affirmedServicesContentHttpProxyServiceStatisticsCluster-levelSummaryNumproxyservicefailed ConfdString,
        affirmedServicesContentHttpProxyServiceStatisticsCluster-levelSummaryNumtotalclientrequests ConfdString,
        affirmedServicesContentHttpProxyServiceStatisticsCluster-levelSummaryNuminserviceclientrequests ConfdString,
        affirmedServicesContentHttpProxyServiceStatisticsCluster-levelSummaryNumsuccessclientrequests ConfdString,
        affirmedServicesContentHttpProxyServiceStatisticsCluster-levelSummaryNumclientabortrequests ConfdString,
        affirmedServicesContentHttpProxyServiceStatisticsCluster-levelSummaryNumfailedclientrequests ConfdString,
        affirmedServicesContentHttpProxyServiceStatisticsCluster-levelSummaryNumpipelinedroppedclientrequests ConfdString,
        affirmedServicesContentHttpProxyServiceStatisticsCluster-levelSummaryNuminvalidclientrequests ConfdString,
        affirmedServicesContentHttpProxyServiceStatisticsCluster-levelSummaryNumbytesclientrequest ConfdString,
        affirmedServicesContentHttpProxyServiceStatisticsCluster-levelSummaryNumbytesclientresponse ConfdString,
        affirmedServicesContentHttpProxyServiceStatisticsCluster-levelSummaryNumbytesserverrequest ConfdString,
        affirmedServicesContentHttpProxyServiceStatisticsCluster-levelSummaryNumbytesserverresponse ConfdString,
        affirmedServicesContentHttpProxyServiceStatisticsCluster-levelSummaryClienthttpservicetimemin ConfdString,
        affirmedServicesContentHttpProxyServiceStatisticsCluster-levelSummaryClienthttpservicetimeavg ConfdString,
        affirmedServicesContentHttpProxyServiceStatisticsCluster-levelSummaryClienthttpservicetimemax ConfdString,
        affirmedServicesContentHttpProxyServiceStatisticsCluster-levelSummaryServerhttpresponsestotal ConfdString,
        affirmedServicesContentHttpProxyServiceStatisticsCluster-levelSummaryServerhttpresponsetimemin ConfdString,
        affirmedServicesContentHttpProxyServiceStatisticsCluster-levelSummaryServerhttpresponsetimeavg ConfdString,
        affirmedServicesContentHttpProxyServiceStatisticsCluster-levelSummaryServerhttpresponsetimemax ConfdString,
        affirmedServicesContentHttpProxyServiceStatisticsCluster-levelSummaryLatencyrequestavg ConfdString,
        affirmedServicesContentHttpProxyServiceStatisticsCluster-levelSummaryLatencyresponseavg ConfdString,
        affirmedServicesContentHttpProxyServiceStatisticsCluster-levelSummaryLatencyavg ConfdString,
        affirmedServicesContentHttpProxyServiceStatisticsCluster-levelSummaryNumproxyclientcount ConfdString
    }

affirmedServicesContentHttpProxyServiceStatisticsCluster-levelSummaryChassis OBJECT-TYPE
    SYNTAX      Unsigned32
    MAX-ACCESS  not-accessible
    STATUS      current
    DESCRIPTION "chassis ID"
    ::= { affirmedServicesContentHttpProxyServiceStatisticsCluster-levelSummaryEntry 1 }

affirmedServicesContentHttpProxyServiceStatisticsCluster-levelSummaryNumproxyserviceattempts OBJECT-TYPE
    SYNTAX      ConfdString
    MAX-ACCESS  read-only
    STATUS      current
    DESCRIPTION "Total number of proxy service attempts"
    ::= { affirmedServicesContentHttpProxyServiceStatisticsCluster-levelSummaryEntry 2 }

affirmedServicesContentHttpProxyServiceStatisticsCluster-levelSummaryNumproxyservicesuccess OBJECT-TYPE
    SYNTAX      ConfdString
    MAX-ACCESS  read-only
    STATUS      current
    DESCRIPTION "Total number of proxy service success"
    ::= { affirmedServicesContentHttpProxyServiceStatisticsCluster-levelSummaryEntry 3 }

affirmedServicesContentHttpProxyServiceStatisticsCluster-levelSummaryNumproxyservicesuccesscached OBJECT-TYPE
    SYNTAX      ConfdString
    MAX-ACCESS  read-only
    STATUS      current
    DESCRIPTION "Total number of proxy service success - Cached"
    ::= { affirmedServicesContentHttpProxyServiceStatisticsCluster-levelSummaryEntry 4 }

affirmedServicesContentHttpProxyServiceStatisticsCluster-levelSummaryNumproxyserviceabortedbyclient OBJECT-TYPE
    SYNTAX      ConfdString
    MAX-ACCESS  read-only
    STATUS      current
    DESCRIPTION "Total number of proxy service aborted"
    ::= { affirmedServicesContentHttpProxyServiceStatisticsCluster-levelSummaryEntry 5 }

affirmedServicesContentHttpProxyServiceStatisticsCluster-levelSummaryNumproxyservicefailed OBJECT-TYPE
    SYNTAX      ConfdString
    MAX-ACCESS  read-only
    STATUS      current
    DESCRIPTION "Total number of proxy service failed"
    ::= { affirmedServicesContentHttpProxyServiceStatisticsCluster-levelSummaryEntry 6 }

affirmedServicesContentHttpProxyServiceStatisticsCluster-levelSummaryNumtotalclientrequests OBJECT-TYPE
    SYNTAX      ConfdString
    MAX-ACCESS  read-only
    STATUS      current
    DESCRIPTION "Total number of client requests received"
    ::= { affirmedServicesContentHttpProxyServiceStatisticsCluster-levelSummaryEntry 7 }

affirmedServicesContentHttpProxyServiceStatisticsCluster-levelSummaryNuminserviceclientrequests OBJECT-TYPE
    SYNTAX      ConfdString
    MAX-ACCESS  read-only
    STATUS      current
    DESCRIPTION "Total number of client requests currently in service"
    ::= { affirmedServicesContentHttpProxyServiceStatisticsCluster-levelSummaryEntry 8 }

affirmedServicesContentHttpProxyServiceStatisticsCluster-levelSummaryNumsuccessclientrequests OBJECT-TYPE
    SYNTAX      ConfdString
    MAX-ACCESS  read-only
    STATUS      current
    DESCRIPTION "Total number of client requests parsed successfully"
    ::= { affirmedServicesContentHttpProxyServiceStatisticsCluster-levelSummaryEntry 9 }

affirmedServicesContentHttpProxyServiceStatisticsCluster-levelSummaryNumclientabortrequests OBJECT-TYPE
    SYNTAX      ConfdString
    MAX-ACCESS  read-only
    STATUS      current
    DESCRIPTION "Total number of incomplete client requests"
    ::= { affirmedServicesContentHttpProxyServiceStatisticsCluster-levelSummaryEntry 10 }

affirmedServicesContentHttpProxyServiceStatisticsCluster-levelSummaryNumfailedclientrequests OBJECT-TYPE
    SYNTAX      ConfdString
    MAX-ACCESS  read-only
    STATUS      current
    DESCRIPTION "Total number of client requests processing failed"
    ::= { affirmedServicesContentHttpProxyServiceStatisticsCluster-levelSummaryEntry 11 }

affirmedServicesContentHttpProxyServiceStatisticsCluster-levelSummaryNumpipelinedroppedclientrequests OBJECT-TYPE
    SYNTAX      ConfdString
    MAX-ACCESS  read-only
    STATUS      current
    DESCRIPTION "Total number of client requests pipeline dropped"
    ::= { affirmedServicesContentHttpProxyServiceStatisticsCluster-levelSummaryEntry 12 }

affirmedServicesContentHttpProxyServiceStatisticsCluster-levelSummaryNuminvalidclientrequests OBJECT-TYPE
    SYNTAX      ConfdString
    MAX-ACCESS  read-only
    STATUS      current
    DESCRIPTION "Total number of invalid client requests"
    ::= { affirmedServicesContentHttpProxyServiceStatisticsCluster-levelSummaryEntry 13 }

affirmedServicesContentHttpProxyServiceStatisticsCluster-levelSummaryNumbytesclientrequest OBJECT-TYPE
    SYNTAX      ConfdString
    MAX-ACCESS  read-only
    STATUS      current
    DESCRIPTION "Total number of Bytes Client Request"
    ::= { affirmedServicesContentHttpProxyServiceStatisticsCluster-levelSummaryEntry 14 }

affirmedServicesContentHttpProxyServiceStatisticsCluster-levelSummaryNumbytesclientresponse OBJECT-TYPE
    SYNTAX      ConfdString
    MAX-ACCESS  read-only
    STATUS      current
    DESCRIPTION "Total number of Bytes Client Response"
    ::= { affirmedServicesContentHttpProxyServiceStatisticsCluster-levelSummaryEntry 15 }

affirmedServicesContentHttpProxyServiceStatisticsCluster-levelSummaryNumbytesserverrequest OBJECT-TYPE
    SYNTAX      ConfdString
    MAX-ACCESS  read-only
    STATUS      current
    DESCRIPTION "Total number of Bytes Server Request"
    ::= { affirmedServicesContentHttpProxyServiceStatisticsCluster-levelSummaryEntry 16 }

affirmedServicesContentHttpProxyServiceStatisticsCluster-levelSummaryNumbytesserverresponse OBJECT-TYPE
    SYNTAX      ConfdString
    MAX-ACCESS  read-only
    STATUS      current
    DESCRIPTION "Total number of Bytes Server Response"
    ::= { affirmedServicesContentHttpProxyServiceStatisticsCluster-levelSummaryEntry 17 }

affirmedServicesContentHttpProxyServiceStatisticsCluster-levelSummaryClienthttpservicetimemin OBJECT-TYPE
    SYNTAX      ConfdString
    MAX-ACCESS  read-only
    STATUS      current
    DESCRIPTION "Client HTTP Service Time Min (ms)"
    ::= { affirmedServicesContentHttpProxyServiceStatisticsCluster-levelSummaryEntry 18 }

affirmedServicesContentHttpProxyServiceStatisticsCluster-levelSummaryClienthttpservicetimeavg OBJECT-TYPE
    SYNTAX      ConfdString
    MAX-ACCESS  read-only
    STATUS      current
    DESCRIPTION "Client HTTP Service Time Avg (ms)"
    ::= { affirmedServicesContentHttpProxyServiceStatisticsCluster-levelSummaryEntry 19 }

affirmedServicesContentHttpProxyServiceStatisticsCluster-levelSummaryClienthttpservicetimemax OBJECT-TYPE
    SYNTAX      ConfdString
    MAX-ACCESS  read-only
    STATUS      current
    DESCRIPTION "Client HTTP Service Time Max (ms)"
    ::= { affirmedServicesContentHttpProxyServiceStatisticsCluster-levelSummaryEntry 20 }

affirmedServicesContentHttpProxyServiceStatisticsCluster-levelSummaryServerhttpresponsestotal OBJECT-TYPE
    SYNTAX      ConfdString
    MAX-ACCESS  read-only
    STATUS      current
    DESCRIPTION "Total number of HTTP server responses"
    ::= { affirmedServicesContentHttpProxyServiceStatisticsCluster-levelSummaryEntry 21 }

affirmedServicesContentHttpProxyServiceStatisticsCluster-levelSummaryServerhttpresponsetimemin OBJECT-TYPE
    SYNTAX      ConfdString
    MAX-ACCESS  read-only
    STATUS      current
    DESCRIPTION "Server HTTP Response Time Min (ms)"
    ::= { affirmedServicesContentHttpProxyServiceStatisticsCluster-levelSummaryEntry 22 }

affirmedServicesContentHttpProxyServiceStatisticsCluster-levelSummaryServerhttpresponsetimeavg OBJECT-TYPE
    SYNTAX      ConfdString
    MAX-ACCESS  read-only
    STATUS      current
    DESCRIPTION "Server HTTP Response Time Avg (ms)"
    ::= { affirmedServicesContentHttpProxyServiceStatisticsCluster-levelSummaryEntry 23 }

affirmedServicesContentHttpProxyServiceStatisticsCluster-levelSummaryServerhttpresponsetimemax OBJECT-TYPE
    SYNTAX      ConfdString
    MAX-ACCESS  read-only
    STATUS      current
    DESCRIPTION "Server HTTP Response Time Max (ms)"
    ::= { affirmedServicesContentHttpProxyServiceStatisticsCluster-levelSummaryEntry 24 }

affirmedServicesContentHttpProxyServiceStatisticsCluster-levelSummaryLatencyrequestavg OBJECT-TYPE
    SYNTAX      ConfdString
    MAX-ACCESS  read-only
    STATUS      current
    DESCRIPTION "HTTP Request Service Latency Average (ms)"
    ::= { affirmedServicesContentHttpProxyServiceStatisticsCluster-levelSummaryEntry 25 }

affirmedServicesContentHttpProxyServiceStatisticsCluster-levelSummaryLatencyresponseavg OBJECT-TYPE
    SYNTAX      ConfdString
    MAX-ACCESS  read-only
    STATUS      current
    DESCRIPTION "HTTP Response Service Latency Average (ms)"
    ::= { affirmedServicesContentHttpProxyServiceStatisticsCluster-levelSummaryEntry 26 }

affirmedServicesContentHttpProxyServiceStatisticsCluster-levelSummaryLatencyavg OBJECT-TYPE
    SYNTAX      ConfdString
    MAX-ACCESS  read-only
    STATUS      current
    DESCRIPTION "HTTP Service Latency Average (ms)"
    ::= { affirmedServicesContentHttpProxyServiceStatisticsCluster-levelSummaryEntry 27 }

affirmedServicesContentHttpProxyServiceStatisticsCluster-levelSummaryNumproxyclientcount OBJECT-TYPE
    SYNTAX      ConfdString
    MAX-ACCESS  read-only
    STATUS      current
    DESCRIPTION "Total number of current Proxy Sessions"
    ::= { affirmedServicesContentHttpProxyServiceStatisticsCluster-levelSummaryEntry 28 }

affirmedServicesContentHttpProxyServiceStatisticsNode-levelConnectionTable OBJECT-TYPE
    SYNTAX      SEQUENCE OF AffirmedServicesContentHttpProxyServiceStatisticsNode-levelConnectionEntry
    MAX-ACCESS  not-accessible
    STATUS      current
    DESCRIPTION ""
    ::= { affirmedServicesContentHttpProxyServiceStatisticsNode-level 2 }

affirmedServicesContentHttpProxyServiceStatisticsNode-levelConnectionEntry OBJECT-TYPE
    SYNTAX      AffirmedServicesContentHttpProxyServiceStatisticsNode-levelConnectionEntry
    MAX-ACCESS  not-accessible
    STATUS      current
    DESCRIPTION ""
    INDEX { affirmedServicesContentHttpProxyServiceStatisticsNode-levelConnectionChassis, affirmedServicesContentHttpProxyServiceStatisticsNode-levelConnectionSlot }
        ::= { affirmedServicesContentHttpProxyServiceStatisticsNode-levelConnectionTable 1 }

AffirmedServicesContentHttpProxyServiceStatisticsNode-levelConnectionEntry ::=
    SEQUENCE {
        affirmedServicesContentHttpProxyServiceStatisticsNode-levelConnectionChassis Unsigned32,
        affirmedServicesContentHttpProxyServiceStatisticsNode-levelConnectionSlot INTEGER,
        affirmedServicesContentHttpProxyServiceStatisticsNode-levelConnectionNumtotalclientconnections ConfdString,
        affirmedServicesContentHttpProxyServiceStatisticsNode-levelConnectionNumcurrentclientconnections ConfdString,
        affirmedServicesContentHttpProxyServiceStatisticsNode-levelConnectionNumkeepaliverequested ConfdString,
        affirmedServicesContentHttpProxyServiceStatisticsNode-levelConnectionNumpersistentclientconnections ConfdString,
        affirmedServicesContentHttpProxyServiceStatisticsNode-levelConnectionNumreusedclientconnections ConfdString,
        affirmedServicesContentHttpProxyServiceStatisticsNode-levelConnectionNumpipelinedclientconnections ConfdString,
        affirmedServicesContentHttpProxyServiceStatisticsNode-levelConnectionNumipv4clientconnections ConfdString,
        affirmedServicesContentHttpProxyServiceStatisticsNode-levelConnectionNumipv6clientconnections ConfdString,
        affirmedServicesContentHttpProxyServiceStatisticsNode-levelConnectionNumtotalserverconnections ConfdString,
        affirmedServicesContentHttpProxyServiceStatisticsNode-levelConnectionNumcurrentserverconnections ConfdString,
        affirmedServicesContentHttpProxyServiceStatisticsNode-levelConnectionNumipv4serverconnections ConfdString,
        affirmedServicesContentHttpProxyServiceStatisticsNode-levelConnectionNumipv6serverconnections ConfdString,
        affirmedServicesContentHttpProxyServiceStatisticsNode-levelConnectionNumcurrentlyidleserverconnections ConfdString,
        affirmedServicesContentHttpProxyServiceStatisticsNode-levelConnectionNumreusedsameclientserverconnections ConfdString,
        affirmedServicesContentHttpProxyServiceStatisticsNode-levelConnectionNumreusedserverconnections ConfdString,
        affirmedServicesContentHttpProxyServiceStatisticsNode-levelConnectionNumprefipfamilyusedserverconnections ConfdString,
        affirmedServicesContentHttpProxyServiceStatisticsNode-levelConnectionNumprefipfamilyunavailableserverconnections ConfdString,
        affirmedServicesContentHttpProxyServiceStatisticsNode-levelConnectionNumtotalsmppconnections ConfdString,
        affirmedServicesContentHttpProxyServiceStatisticsNode-levelConnectionNumcurrentsmppconnections ConfdString,
        affirmedServicesContentHttpProxyServiceStatisticsNode-levelConnectionNumipv4smppconnections ConfdString,
        affirmedServicesContentHttpProxyServiceStatisticsNode-levelConnectionNumipv6smppconnections ConfdString,
        affirmedServicesContentHttpProxyServiceStatisticsNode-levelConnectionNumcurrentlyidlesmppconnections ConfdString,
        affirmedServicesContentHttpProxyServiceStatisticsNode-levelConnectionNumreusedsameclientsmppconnections ConfdString,
        affirmedServicesContentHttpProxyServiceStatisticsNode-levelConnectionNumreusedsmppconnections ConfdString,
        affirmedServicesContentHttpProxyServiceStatisticsNode-levelConnectionNumconnectionerrorsmppconnections ConfdString,
        affirmedServicesContentHttpProxyServiceStatisticsNode-levelConnectionNumbinderrorsmppconnections ConfdString,
        affirmedServicesContentHttpProxyServiceStatisticsNode-levelConnectionNumsenderrorsmppconnections ConfdString,
        affirmedServicesContentHttpProxyServiceStatisticsNode-levelConnectionNumunbinderrorsmppconnections ConfdString,
        affirmedServicesContentHttpProxyServiceStatisticsNode-levelConnectionNumiptransparentserverconnections ConfdString,
        affirmedServicesContentHttpProxyServiceStatisticsNode-levelConnectionNumnonhttpclientconnections ConfdString,
        affirmedServicesContentHttpProxyServiceStatisticsNode-levelConnectionNumnorequestclientconnnections ConfdString,
        affirmedServicesContentHttpProxyServiceStatisticsNode-levelConnectionNumreversehandoffclientconnnections ConfdString,
        affirmedServicesContentHttpProxyServiceStatisticsNode-levelConnectionNumfailuresclientconnnections ConfdString,
        affirmedServicesContentHttpProxyServiceStatisticsNode-levelConnectionNumfastopenattempts ConfdString,
        affirmedServicesContentHttpProxyServiceStatisticsNode-levelConnectionNumfastopensuccesses ConfdString,
        affirmedServicesContentHttpProxyServiceStatisticsNode-levelConnectionNumfastopenfailureinitconn ConfdString,
        affirmedServicesContentHttpProxyServiceStatisticsNode-levelConnectionNumfastopenfailureduplicate ConfdString,
        affirmedServicesContentHttpProxyServiceStatisticsNode-levelConnectionNumfastopenfailurealreadycreated ConfdString,
        affirmedServicesContentHttpProxyServiceStatisticsNode-levelConnectionNumfastopenfailurepolicy ConfdString,
        affirmedServicesContentHttpProxyServiceStatisticsNode-levelConnectionNumfastopenfailureother ConfdString,
        affirmedServicesContentHttpProxyServiceStatisticsNode-levelConnectionNumfastopenlistfull ConfdString,
        affirmedServicesContentHttpProxyServiceStatisticsNode-levelConnectionNumfastopencurrentpendingconn ConfdString,
        affirmedServicesContentHttpProxyServiceStatisticsNode-levelConnectionNumfastopenaging ConfdString
    }

affirmedServicesContentHttpProxyServiceStatisticsNode-levelConnectionChassis OBJECT-TYPE
    SYNTAX      Unsigned32
    MAX-ACCESS  not-accessible
    STATUS      current
    DESCRIPTION "chassis ID"
    ::= { affirmedServicesContentHttpProxyServiceStatisticsNode-levelConnectionEntry 1 }

affirmedServicesContentHttpProxyServiceStatisticsNode-levelConnectionSlot OBJECT-TYPE
    SYNTAX      INTEGER {a1(1),a2(2),a3(3),a4(4),a5(5),a6(6),a7(7),a8(8),a9(9),a10(10),a11(11),a12(12),a13(13),a14(14),a15(15),a16(16),a17(17),a18(18),a19(19),a20(20),a21(21),a22(22),a23(23),a24(24),a25(25),a26(26),a27(27),a28(28),a29(29),a30(30),a31(31),a32(32),a33(33),a34(34),a35(35),a36(36),a37(37),a38(38),a39(39),a40(40),a41(41),a42(42),a43(43),a44(44),a45(45),a46(46),a47(47),a48(48),a49(49),a50(50),a51(51),a52(52),a53(53),a54(54),a55(55),a56(56),a57(57),a58(58),a59(59),a60(60),a61(61),a62(62),a63(63),a64(64),a65(65),a66(66),a67(67),a68(68),a69(69),a70(70),a71(71),a72(72),a73(73),a74(74),a75(75),a76(76),a77(77),a78(78),a79(79),a80(80),a81(81),a82(82),a83(83),a84(84),a85(85),a86(86),a87(87),a88(88),a89(89),a90(90),a91(91),a92(92),a93(93),a94(94),a95(95),a96(96),a97(97),a98(98),a99(99),a100(100),a101(101),a102(102),a103(103),a104(104),a105(105),a106(106),a107(107),a108(108),a109(109),a110(110),a111(111),a112(112),a113(113),a114(114),a115(115),a116(116),a117(117),a118(118),a119(119),a120(120),a121(121),a122(122),a123(123),a124(124),a125(125),a126(126),a127(127),a128(128)}
    MAX-ACCESS  not-accessible
    STATUS      current
    DESCRIPTION "slot number"
    ::= { affirmedServicesContentHttpProxyServiceStatisticsNode-levelConnectionEntry 2 }

affirmedServicesContentHttpProxyServiceStatisticsNode-levelConnectionNumtotalclientconnections OBJECT-TYPE
    SYNTAX      ConfdString
    MAX-ACCESS  read-only
    STATUS      current
    DESCRIPTION "Total number of client connections"
    ::= { affirmedServicesContentHttpProxyServiceStatisticsNode-levelConnectionEntry 3 }

affirmedServicesContentHttpProxyServiceStatisticsNode-levelConnectionNumcurrentclientconnections OBJECT-TYPE
    SYNTAX      ConfdString
    MAX-ACCESS  read-only
    STATUS      current
    DESCRIPTION "Total number of client connections currently in use"
    ::= { affirmedServicesContentHttpProxyServiceStatisticsNode-levelConnectionEntry 4 }

affirmedServicesContentHttpProxyServiceStatisticsNode-levelConnectionNumkeepaliverequested OBJECT-TYPE
    SYNTAX      ConfdString
    MAX-ACCESS  read-only
    STATUS      current
    DESCRIPTION "Total number of keep-alive requested from client"
    ::= { affirmedServicesContentHttpProxyServiceStatisticsNode-levelConnectionEntry 5 }

affirmedServicesContentHttpProxyServiceStatisticsNode-levelConnectionNumpersistentclientconnections OBJECT-TYPE
    SYNTAX      ConfdString
    MAX-ACCESS  read-only
    STATUS      current
    DESCRIPTION "Total number of persistent client connections"
    ::= { affirmedServicesContentHttpProxyServiceStatisticsNode-levelConnectionEntry 6 }

affirmedServicesContentHttpProxyServiceStatisticsNode-levelConnectionNumreusedclientconnections OBJECT-TYPE
    SYNTAX      ConfdString
    MAX-ACCESS  read-only
    STATUS      current
    DESCRIPTION "Total number of reused client connections"
    ::= { affirmedServicesContentHttpProxyServiceStatisticsNode-levelConnectionEntry 7 }

affirmedServicesContentHttpProxyServiceStatisticsNode-levelConnectionNumpipelinedclientconnections OBJECT-TYPE
    SYNTAX      ConfdString
    MAX-ACCESS  read-only
    STATUS      current
    DESCRIPTION "Total number of pipelined client connections"
    ::= { affirmedServicesContentHttpProxyServiceStatisticsNode-levelConnectionEntry 8 }

affirmedServicesContentHttpProxyServiceStatisticsNode-levelConnectionNumipv4clientconnections OBJECT-TYPE
    SYNTAX      ConfdString
    MAX-ACCESS  read-only
    STATUS      current
    DESCRIPTION "Total number of IPv4 client connections"
    ::= { affirmedServicesContentHttpProxyServiceStatisticsNode-levelConnectionEntry 9 }

affirmedServicesContentHttpProxyServiceStatisticsNode-levelConnectionNumipv6clientconnections OBJECT-TYPE
    SYNTAX      ConfdString
    MAX-ACCESS  read-only
    STATUS      current
    DESCRIPTION "Total number of IPv6 client connections"
    ::= { affirmedServicesContentHttpProxyServiceStatisticsNode-levelConnectionEntry 10 }

affirmedServicesContentHttpProxyServiceStatisticsNode-levelConnectionNumtotalserverconnections OBJECT-TYPE
    SYNTAX      ConfdString
    MAX-ACCESS  read-only
    STATUS      current
    DESCRIPTION "Total number of server connections"
    ::= { affirmedServicesContentHttpProxyServiceStatisticsNode-levelConnectionEntry 11 }

affirmedServicesContentHttpProxyServiceStatisticsNode-levelConnectionNumcurrentserverconnections OBJECT-TYPE
    SYNTAX      ConfdString
    MAX-ACCESS  read-only
    STATUS      current
    DESCRIPTION "Total number of server connections currently in use"
    ::= { affirmedServicesContentHttpProxyServiceStatisticsNode-levelConnectionEntry 12 }

affirmedServicesContentHttpProxyServiceStatisticsNode-levelConnectionNumipv4serverconnections OBJECT-TYPE
    SYNTAX      ConfdString
    MAX-ACCESS  read-only
    STATUS      current
    DESCRIPTION "Total number of IPv4 server connections"
    ::= { affirmedServicesContentHttpProxyServiceStatisticsNode-levelConnectionEntry 13 }

affirmedServicesContentHttpProxyServiceStatisticsNode-levelConnectionNumipv6serverconnections OBJECT-TYPE
    SYNTAX      ConfdString
    MAX-ACCESS  read-only
    STATUS      current
    DESCRIPTION "Total number of IPv6 server connections"
    ::= { affirmedServicesContentHttpProxyServiceStatisticsNode-levelConnectionEntry 14 }

affirmedServicesContentHttpProxyServiceStatisticsNode-levelConnectionNumcurrentlyidleserverconnections OBJECT-TYPE
    SYNTAX      ConfdString
    MAX-ACCESS  read-only
    STATUS      current
    DESCRIPTION "The number of idle server connections in the server connection pool"
    ::= { affirmedServicesContentHttpProxyServiceStatisticsNode-levelConnectionEntry 15 }

affirmedServicesContentHttpProxyServiceStatisticsNode-levelConnectionNumreusedsameclientserverconnections OBJECT-TYPE
    SYNTAX      ConfdString
    MAX-ACCESS  read-only
    STATUS      current
    DESCRIPTION "The number of times server connections were reused by same client connections"
    ::= { affirmedServicesContentHttpProxyServiceStatisticsNode-levelConnectionEntry 16 }

affirmedServicesContentHttpProxyServiceStatisticsNode-levelConnectionNumreusedserverconnections OBJECT-TYPE
    SYNTAX      ConfdString
    MAX-ACCESS  read-only
    STATUS      current
    DESCRIPTION "The number of times idle server connections were reused"
    ::= { affirmedServicesContentHttpProxyServiceStatisticsNode-levelConnectionEntry 17 }

affirmedServicesContentHttpProxyServiceStatisticsNode-levelConnectionNumprefipfamilyusedserverconnections OBJECT-TYPE
    SYNTAX      ConfdString
    MAX-ACCESS  read-only
    STATUS      current
    DESCRIPTION "Total number of preferred ip family used server connections"
    ::= { affirmedServicesContentHttpProxyServiceStatisticsNode-levelConnectionEntry 18 }

affirmedServicesContentHttpProxyServiceStatisticsNode-levelConnectionNumprefipfamilyunavailableserverconnections OBJECT-TYPE
    SYNTAX      ConfdString
    MAX-ACCESS  read-only
    STATUS      current
    DESCRIPTION "Total number of preferred ip family unavailable server connections"
    ::= { affirmedServicesContentHttpProxyServiceStatisticsNode-levelConnectionEntry 19 }

affirmedServicesContentHttpProxyServiceStatisticsNode-levelConnectionNumtotalsmppconnections OBJECT-TYPE
    SYNTAX      ConfdString
    MAX-ACCESS  read-only
    STATUS      current
    DESCRIPTION "Total number of smpp connections"
    ::= { affirmedServicesContentHttpProxyServiceStatisticsNode-levelConnectionEntry 20 }

affirmedServicesContentHttpProxyServiceStatisticsNode-levelConnectionNumcurrentsmppconnections OBJECT-TYPE
    SYNTAX      ConfdString
    MAX-ACCESS  read-only
    STATUS      current
    DESCRIPTION "Total number of smpp connections currently in use"
    ::= { affirmedServicesContentHttpProxyServiceStatisticsNode-levelConnectionEntry 21 }

affirmedServicesContentHttpProxyServiceStatisticsNode-levelConnectionNumipv4smppconnections OBJECT-TYPE
    SYNTAX      ConfdString
    MAX-ACCESS  read-only
    STATUS      current
    DESCRIPTION "Total number of IPv4 smpp connections"
    ::= { affirmedServicesContentHttpProxyServiceStatisticsNode-levelConnectionEntry 22 }

affirmedServicesContentHttpProxyServiceStatisticsNode-levelConnectionNumipv6smppconnections OBJECT-TYPE
    SYNTAX      ConfdString
    MAX-ACCESS  read-only
    STATUS      current
    DESCRIPTION "Total number of IPv6 smpp connections"
    ::= { affirmedServicesContentHttpProxyServiceStatisticsNode-levelConnectionEntry 23 }

affirmedServicesContentHttpProxyServiceStatisticsNode-levelConnectionNumcurrentlyidlesmppconnections OBJECT-TYPE
    SYNTAX      ConfdString
    MAX-ACCESS  read-only
    STATUS      current
    DESCRIPTION "The number of idle smpp connections in the server connection pool"
    ::= { affirmedServicesContentHttpProxyServiceStatisticsNode-levelConnectionEntry 24 }

affirmedServicesContentHttpProxyServiceStatisticsNode-levelConnectionNumreusedsameclientsmppconnections OBJECT-TYPE
    SYNTAX      ConfdString
    MAX-ACCESS  read-only
    STATUS      current
    DESCRIPTION "The number of times smpp connections were reused by same client connections"
    ::= { affirmedServicesContentHttpProxyServiceStatisticsNode-levelConnectionEntry 25 }

affirmedServicesContentHttpProxyServiceStatisticsNode-levelConnectionNumreusedsmppconnections OBJECT-TYPE
    SYNTAX      ConfdString
    MAX-ACCESS  read-only
    STATUS      current
    DESCRIPTION "The number of times idle smpp connections were reused"
    ::= { affirmedServicesContentHttpProxyServiceStatisticsNode-levelConnectionEntry 26 }

affirmedServicesContentHttpProxyServiceStatisticsNode-levelConnectionNumconnectionerrorsmppconnections OBJECT-TYPE
    SYNTAX      ConfdString
    MAX-ACCESS  read-only
    STATUS      current
    DESCRIPTION "The number of smpp connection errors"
    ::= { affirmedServicesContentHttpProxyServiceStatisticsNode-levelConnectionEntry 27 }

affirmedServicesContentHttpProxyServiceStatisticsNode-levelConnectionNumbinderrorsmppconnections OBJECT-TYPE
    SYNTAX      ConfdString
    MAX-ACCESS  read-only
    STATUS      current
    DESCRIPTION "The number of smpp bind errors"
    ::= { affirmedServicesContentHttpProxyServiceStatisticsNode-levelConnectionEntry 28 }

affirmedServicesContentHttpProxyServiceStatisticsNode-levelConnectionNumsenderrorsmppconnections OBJECT-TYPE
    SYNTAX      ConfdString
    MAX-ACCESS  read-only
    STATUS      current
    DESCRIPTION "The number of smpp send errors"
    ::= { affirmedServicesContentHttpProxyServiceStatisticsNode-levelConnectionEntry 29 }

affirmedServicesContentHttpProxyServiceStatisticsNode-levelConnectionNumunbinderrorsmppconnections OBJECT-TYPE
    SYNTAX      ConfdString
    MAX-ACCESS  read-only
    STATUS      current
    DESCRIPTION "The number of smpp unbind errors"
    ::= { affirmedServicesContentHttpProxyServiceStatisticsNode-levelConnectionEntry 30 }

affirmedServicesContentHttpProxyServiceStatisticsNode-levelConnectionNumiptransparentserverconnections OBJECT-TYPE
    SYNTAX      ConfdString
    MAX-ACCESS  read-only
    STATUS      current
    DESCRIPTION "Total number of IP transparent server connections"
    ::= { affirmedServicesContentHttpProxyServiceStatisticsNode-levelConnectionEntry 31 }

affirmedServicesContentHttpProxyServiceStatisticsNode-levelConnectionNumnonhttpclientconnections OBJECT-TYPE
    SYNTAX      ConfdString
    MAX-ACCESS  read-only
    STATUS      current
    DESCRIPTION "Total number of client connections with non-http request"
    ::= { affirmedServicesContentHttpProxyServiceStatisticsNode-levelConnectionEntry 32 }

affirmedServicesContentHttpProxyServiceStatisticsNode-levelConnectionNumnorequestclientconnnections OBJECT-TYPE
    SYNTAX      ConfdString
    MAX-ACCESS  read-only
    STATUS      current
    DESCRIPTION "Total number of client connections with request receive timeout"
    ::= { affirmedServicesContentHttpProxyServiceStatisticsNode-levelConnectionEntry 33 }

affirmedServicesContentHttpProxyServiceStatisticsNode-levelConnectionNumreversehandoffclientconnnections OBJECT-TYPE
    SYNTAX      ConfdString
    MAX-ACCESS  read-only
    STATUS      current
    DESCRIPTION "Total number of client connections from reverse handoff"
    ::= { affirmedServicesContentHttpProxyServiceStatisticsNode-levelConnectionEntry 34 }

affirmedServicesContentHttpProxyServiceStatisticsNode-levelConnectionNumfailuresclientconnnections OBJECT-TYPE
    SYNTAX      ConfdString
    MAX-ACCESS  read-only
    STATUS      current
    DESCRIPTION "Total number of client connection failures"
    ::= { affirmedServicesContentHttpProxyServiceStatisticsNode-levelConnectionEntry 35 }

affirmedServicesContentHttpProxyServiceStatisticsNode-levelConnectionNumfastopenattempts OBJECT-TYPE
    SYNTAX      ConfdString
    MAX-ACCESS  read-only
    STATUS      current
    DESCRIPTION "Total number of HTTP server connection fast open attempts"
    ::= { affirmedServicesContentHttpProxyServiceStatisticsNode-levelConnectionEntry 36 }

affirmedServicesContentHttpProxyServiceStatisticsNode-levelConnectionNumfastopensuccesses OBJECT-TYPE
    SYNTAX      ConfdString
    MAX-ACCESS  read-only
    STATUS      current
    DESCRIPTION "Total number of HTTP server connection fast open successes"
    ::= { affirmedServicesContentHttpProxyServiceStatisticsNode-levelConnectionEntry 37 }

affirmedServicesContentHttpProxyServiceStatisticsNode-levelConnectionNumfastopenfailureinitconn OBJECT-TYPE
    SYNTAX      ConfdString
    MAX-ACCESS  read-only
    STATUS      current
    DESCRIPTION "Total number of HTTP server connection fast open initialization failure"
    ::= { affirmedServicesContentHttpProxyServiceStatisticsNode-levelConnectionEntry 38 }

affirmedServicesContentHttpProxyServiceStatisticsNode-levelConnectionNumfastopenfailureduplicate OBJECT-TYPE
    SYNTAX      ConfdString
    MAX-ACCESS  read-only
    STATUS      current
    DESCRIPTION "Total number of HTTP server connection fast open duplicated connection"
    ::= { affirmedServicesContentHttpProxyServiceStatisticsNode-levelConnectionEntry 39 }

affirmedServicesContentHttpProxyServiceStatisticsNode-levelConnectionNumfastopenfailurealreadycreated OBJECT-TYPE
    SYNTAX      ConfdString
    MAX-ACCESS  read-only
    STATUS      current
    DESCRIPTION "Total number of HTTP server connection fast open already in the session"
    ::= { affirmedServicesContentHttpProxyServiceStatisticsNode-levelConnectionEntry 40 }

affirmedServicesContentHttpProxyServiceStatisticsNode-levelConnectionNumfastopenfailurepolicy OBJECT-TYPE
    SYNTAX      ConfdString
    MAX-ACCESS  read-only
    STATUS      current
    DESCRIPTION "Total number of HTTP server connection fast open policy reject"
    ::= { affirmedServicesContentHttpProxyServiceStatisticsNode-levelConnectionEntry 41 }

affirmedServicesContentHttpProxyServiceStatisticsNode-levelConnectionNumfastopenfailureother OBJECT-TYPE
    SYNTAX      ConfdString
    MAX-ACCESS  read-only
    STATUS      current
    DESCRIPTION "Total number of HTTP server connection fast open failure others"
    ::= { affirmedServicesContentHttpProxyServiceStatisticsNode-levelConnectionEntry 42 }

affirmedServicesContentHttpProxyServiceStatisticsNode-levelConnectionNumfastopenlistfull OBJECT-TYPE
    SYNTAX      ConfdString
    MAX-ACCESS  read-only
    STATUS      current
    DESCRIPTION "Total number of HTTP server connection fast open pending list full"
    ::= { affirmedServicesContentHttpProxyServiceStatisticsNode-levelConnectionEntry 43 }

affirmedServicesContentHttpProxyServiceStatisticsNode-levelConnectionNumfastopencurrentpendingconn OBJECT-TYPE
    SYNTAX      ConfdString
    MAX-ACCESS  read-only
    STATUS      current
    DESCRIPTION "Total number of HTTP server connection fast open in pending list"
    ::= { affirmedServicesContentHttpProxyServiceStatisticsNode-levelConnectionEntry 44 }

affirmedServicesContentHttpProxyServiceStatisticsNode-levelConnectionNumfastopenaging OBJECT-TYPE
    SYNTAX      ConfdString
    MAX-ACCESS  read-only
    STATUS      current
    DESCRIPTION "Total number of HTTP server connection fast open connection closed due to aging"
    ::= { affirmedServicesContentHttpProxyServiceStatisticsNode-levelConnectionEntry 45 }

affirmedServicesContentHttpProxyServiceStatisticsNode-levelDetailTable OBJECT-TYPE
    SYNTAX      SEQUENCE OF AffirmedServicesContentHttpProxyServiceStatisticsNode-levelDetailEntry
    MAX-ACCESS  not-accessible
    STATUS      current
    DESCRIPTION ""
    ::= { affirmedServicesContentHttpProxyServiceStatisticsNode-level 3 }

affirmedServicesContentHttpProxyServiceStatisticsNode-levelDetailEntry OBJECT-TYPE
    SYNTAX      AffirmedServicesContentHttpProxyServiceStatisticsNode-levelDetailEntry
    MAX-ACCESS  not-accessible
    STATUS      current
    DESCRIPTION ""
    INDEX { affirmedServicesContentHttpProxyServiceStatisticsNode-levelDetailChassis, affirmedServicesContentHttpProxyServiceStatisticsNode-levelDetailSlot }
        ::= { affirmedServicesContentHttpProxyServiceStatisticsNode-levelDetailTable 1 }

AffirmedServicesContentHttpProxyServiceStatisticsNode-levelDetailEntry ::=
    SEQUENCE {
        affirmedServicesContentHttpProxyServiceStatisticsNode-levelDetailChassis Unsigned32,
        affirmedServicesContentHttpProxyServiceStatisticsNode-levelDetailSlot INTEGER,
        affirmedServicesContentHttpProxyServiceStatisticsNode-levelDetailNumtotalrequestshttpv09 ConfdString,
        affirmedServicesContentHttpProxyServiceStatisticsNode-levelDetailNumtotalrequestshttpv10 ConfdString,
        affirmedServicesContentHttpProxyServiceStatisticsNode-levelDetailNumtotalrequestshttpv11 ConfdString,
        affirmedServicesContentHttpProxyServiceStatisticsNode-levelDetailNumpersistenclientrequests ConfdString,
        affirmedServicesContentHttpProxyServiceStatisticsNode-levelDetailNumpipelinedclientrequests ConfdString,
        affirmedServicesContentHttpProxyServiceStatisticsNode-levelDetailNumipv4clientrequests ConfdString,
        affirmedServicesContentHttpProxyServiceStatisticsNode-levelDetailNumipv6clientrequests ConfdString,
        affirmedServicesContentHttpProxyServiceStatisticsNode-levelDetailNumparsediosrequests ConfdString,
        affirmedServicesContentHttpProxyServiceStatisticsNode-levelDetailNumparsedandroidrequests ConfdString,
        affirmedServicesContentHttpProxyServiceStatisticsNode-levelDetailNumparsedmozillarequests ConfdString,
        affirmedServicesContentHttpProxyServiceStatisticsNode-levelDetailNumparsedsafarirequests ConfdString,
        affirmedServicesContentHttpProxyServiceStatisticsNode-levelDetailNumparsedchromerequests ConfdString,
        affirmedServicesContentHttpProxyServiceStatisticsNode-levelDetailServerhttpresponsesipv4 ConfdString,
        affirmedServicesContentHttpProxyServiceStatisticsNode-levelDetailServerhttpresponsesipv6 ConfdString,
        affirmedServicesContentHttpProxyServiceStatisticsNode-levelDetailClienthttprequestsizemin ConfdString,
        affirmedServicesContentHttpProxyServiceStatisticsNode-levelDetailClienthttprequestsizeavg ConfdString,
        affirmedServicesContentHttpProxyServiceStatisticsNode-levelDetailClienthttprequestsizemax ConfdString,
        affirmedServicesContentHttpProxyServiceStatisticsNode-levelDetailClienthttpresponsesizemin ConfdString,
        affirmedServicesContentHttpProxyServiceStatisticsNode-levelDetailClienthttpresponsesizeavg ConfdString,
        affirmedServicesContentHttpProxyServiceStatisticsNode-levelDetailClienthttpresponsesizemax ConfdString,
        affirmedServicesContentHttpProxyServiceStatisticsNode-levelDetailServicetimefromserveravg ConfdString,
        affirmedServicesContentHttpProxyServiceStatisticsNode-levelDetailServicetimefromcacheavg ConfdString,
        affirmedServicesContentHttpProxyServiceStatisticsNode-levelDetailNumtotalclientrequestschunked ConfdString,
        affirmedServicesContentHttpProxyServiceStatisticsNode-levelDetailNumsuccessclientrequestschunked ConfdString,
        affirmedServicesContentHttpProxyServiceStatisticsNode-levelDetailNumproxyserviceattemptschunked ConfdString,
        affirmedServicesContentHttpProxyServiceStatisticsNode-levelDetailNumproxyservicesuccesscachedchunked ConfdString,
        affirmedServicesContentHttpProxyServiceStatisticsNode-levelDetailNumproxyservicesuccesschunked ConfdString,
        affirmedServicesContentHttpProxyServiceStatisticsNode-levelDetailNumbytesclientrequestchunked ConfdString,
        affirmedServicesContentHttpProxyServiceStatisticsNode-levelDetailNumbytesserverresponsechunked ConfdString,
        affirmedServicesContentHttpProxyServiceStatisticsNode-levelDetailNumproxyserviceattemptschunkedvideo ConfdString,
        affirmedServicesContentHttpProxyServiceStatisticsNode-levelDetailNumproxyservicesuccesschunkedvideo ConfdString,
        affirmedServicesContentHttpProxyServiceStatisticsNode-levelDetailNumproxyservicesuccesscachedchunkedvideo ConfdString,
        affirmedServicesContentHttpProxyServiceStatisticsNode-levelDetailNumbytesserverresponsechunkedvideo ConfdString,
        affirmedServicesContentHttpProxyServiceStatisticsNode-levelDetailNumconditionalclientrequests ConfdString,
        affirmedServicesContentHttpProxyServiceStatisticsNode-levelDetailNumproxyservicepreconditionfailed ConfdString,
        affirmedServicesContentHttpProxyServiceStatisticsNode-levelDetailNumproxyservicepreconditionnotmodified ConfdString,
        affirmedServicesContentHttpProxyServiceStatisticsNode-levelDetailNumproxyservicepreconditionpartialcontentserved ConfdString,
        affirmedServicesContentHttpProxyServiceStatisticsNode-levelDetailNumproxyservicepreconditionserved ConfdString,
        affirmedServicesContentHttpProxyServiceStatisticsNode-levelDetailNumproxyservicepreconditionforwarded ConfdString,
        affirmedServicesContentHttpProxyServiceStatisticsNode-levelDetailNumbufferedrequests ConfdString,
        affirmedServicesContentHttpProxyServiceStatisticsNode-levelDetailNumbufferedresponses ConfdString,
        affirmedServicesContentHttpProxyServiceStatisticsNode-levelDetailNumtransparentproxyrequests ConfdString,
        affirmedServicesContentHttpProxyServiceStatisticsNode-levelDetailNumexplicitproxyrequests ConfdString,
        affirmedServicesContentHttpProxyServiceStatisticsNode-levelDetailNumparsedlinuxrequests ConfdString,
        affirmedServicesContentHttpProxyServiceStatisticsNode-levelDetailNumparsedmacintoshrequests ConfdString,
        affirmedServicesContentHttpProxyServiceStatisticsNode-levelDetailNumparsedwindowsrequests ConfdString,
        affirmedServicesContentHttpProxyServiceStatisticsNode-levelDetailNumparsedotherosrequests ConfdString,
        affirmedServicesContentHttpProxyServiceStatisticsNode-levelDetailNumparsedinternetexplorerrequests ConfdString,
        affirmedServicesContentHttpProxyServiceStatisticsNode-levelDetailNumparsedotherbrowserrequests ConfdString,
        affirmedServicesContentHttpProxyServiceStatisticsNode-levelDetailNumhttpproxyrequestpolicyappliedtotal ConfdString,
        affirmedServicesContentHttpProxyServiceStatisticsNode-levelDetailNumhttpproxyresponsepolicyappliedtotal ConfdString,
        affirmedServicesContentHttpProxyServiceStatisticsNode-levelDetailClienthttpresponsestatusinformation ConfdString,
        affirmedServicesContentHttpProxyServiceStatisticsNode-levelDetailClienthttpresponsestatussuccessok ConfdString,
        affirmedServicesContentHttpProxyServiceStatisticsNode-levelDetailClienthttpresponsestatussuccessother ConfdString,
        affirmedServicesContentHttpProxyServiceStatisticsNode-levelDetailClienthttpresponsestatusredirection ConfdString,
        affirmedServicesContentHttpProxyServiceStatisticsNode-levelDetailClienthttpresponsestatusclienterror ConfdString,
        affirmedServicesContentHttpProxyServiceStatisticsNode-levelDetailClienthttpresponsestatusservererror ConfdString
    }

affirmedServicesContentHttpProxyServiceStatisticsNode-levelDetailChassis OBJECT-TYPE
    SYNTAX      Unsigned32
    MAX-ACCESS  not-accessible
    STATUS      current
    DESCRIPTION "chassis ID"
    ::= { affirmedServicesContentHttpProxyServiceStatisticsNode-levelDetailEntry 1 }

affirmedServicesContentHttpProxyServiceStatisticsNode-levelDetailSlot OBJECT-TYPE
    SYNTAX      INTEGER {a1(1),a2(2),a3(3),a4(4),a5(5),a6(6),a7(7),a8(8),a9(9),a10(10),a11(11),a12(12),a13(13),a14(14),a15(15),a16(16),a17(17),a18(18),a19(19),a20(20),a21(21),a22(22),a23(23),a24(24),a25(25),a26(26),a27(27),a28(28),a29(29),a30(30),a31(31),a32(32),a33(33),a34(34),a35(35),a36(36),a37(37),a38(38),a39(39),a40(40),a41(41),a42(42),a43(43),a44(44),a45(45),a46(46),a47(47),a48(48),a49(49),a50(50),a51(51),a52(52),a53(53),a54(54),a55(55),a56(56),a57(57),a58(58),a59(59),a60(60),a61(61),a62(62),a63(63),a64(64),a65(65),a66(66),a67(67),a68(68),a69(69),a70(70),a71(71),a72(72),a73(73),a74(74),a75(75),a76(76),a77(77),a78(78),a79(79),a80(80),a81(81),a82(82),a83(83),a84(84),a85(85),a86(86),a87(87),a88(88),a89(89),a90(90),a91(91),a92(92),a93(93),a94(94),a95(95),a96(96),a97(97),a98(98),a99(99),a100(100),a101(101),a102(102),a103(103),a104(104),a105(105),a106(106),a107(107),a108(108),a109(109),a110(110),a111(111),a112(112),a113(113),a114(114),a115(115),a116(116),a117(117),a118(118),a119(119),a120(120),a121(121),a122(122),a123(123),a124(124),a125(125),a126(126),a127(127),a128(128)}
    MAX-ACCESS  not-accessible
    STATUS      current
    DESCRIPTION "slot number"
    ::= { affirmedServicesContentHttpProxyServiceStatisticsNode-levelDetailEntry 2 }

affirmedServicesContentHttpProxyServiceStatisticsNode-levelDetailNumtotalrequestshttpv09 OBJECT-TYPE
    SYNTAX      ConfdString
    MAX-ACCESS  read-only
    STATUS      current
    DESCRIPTION "Total number of Http V0.9 client requests received"
    ::= { affirmedServicesContentHttpProxyServiceStatisticsNode-levelDetailEntry 3 }

affirmedServicesContentHttpProxyServiceStatisticsNode-levelDetailNumtotalrequestshttpv10 OBJECT-TYPE
    SYNTAX      ConfdString
    MAX-ACCESS  read-only
    STATUS      current
    DESCRIPTION "Total number of Http V1.0 client requests received"
    ::= { affirmedServicesContentHttpProxyServiceStatisticsNode-levelDetailEntry 4 }

affirmedServicesContentHttpProxyServiceStatisticsNode-levelDetailNumtotalrequestshttpv11 OBJECT-TYPE
    SYNTAX      ConfdString
    MAX-ACCESS  read-only
    STATUS      current
    DESCRIPTION "Total number of Http V1.1 client requests received"
    ::= { affirmedServicesContentHttpProxyServiceStatisticsNode-levelDetailEntry 5 }

affirmedServicesContentHttpProxyServiceStatisticsNode-levelDetailNumpersistenclientrequests OBJECT-TYPE
    SYNTAX      ConfdString
    MAX-ACCESS  read-only
    STATUS      current
    DESCRIPTION "Total number of client requests persistent"
    ::= { affirmedServicesContentHttpProxyServiceStatisticsNode-levelDetailEntry 6 }

affirmedServicesContentHttpProxyServiceStatisticsNode-levelDetailNumpipelinedclientrequests OBJECT-TYPE
    SYNTAX      ConfdString
    MAX-ACCESS  read-only
    STATUS      current
    DESCRIPTION "Total number of pipelined client requests"
    ::= { affirmedServicesContentHttpProxyServiceStatisticsNode-levelDetailEntry 7 }

affirmedServicesContentHttpProxyServiceStatisticsNode-levelDetailNumipv4clientrequests OBJECT-TYPE
    SYNTAX      ConfdString
    MAX-ACCESS  read-only
    STATUS      current
    DESCRIPTION "Total number of IPv4 client requests"
    ::= { affirmedServicesContentHttpProxyServiceStatisticsNode-levelDetailEntry 8 }

affirmedServicesContentHttpProxyServiceStatisticsNode-levelDetailNumipv6clientrequests OBJECT-TYPE
    SYNTAX      ConfdString
    MAX-ACCESS  read-only
    STATUS      current
    DESCRIPTION "Total number of IPv6 client requests"
    ::= { affirmedServicesContentHttpProxyServiceStatisticsNode-levelDetailEntry 9 }

affirmedServicesContentHttpProxyServiceStatisticsNode-levelDetailNumparsediosrequests OBJECT-TYPE
    SYNTAX      ConfdString
    MAX-ACCESS  read-only
    STATUS      current
    DESCRIPTION "Total number of client requests parsed for iOS"
    ::= { affirmedServicesContentHttpProxyServiceStatisticsNode-levelDetailEntry 10 }

affirmedServicesContentHttpProxyServiceStatisticsNode-levelDetailNumparsedandroidrequests OBJECT-TYPE
    SYNTAX      ConfdString
    MAX-ACCESS  read-only
    STATUS      current
    DESCRIPTION "Total number of client requests parsed for Android"
    ::= { affirmedServicesContentHttpProxyServiceStatisticsNode-levelDetailEntry 11 }

affirmedServicesContentHttpProxyServiceStatisticsNode-levelDetailNumparsedmozillarequests OBJECT-TYPE
    SYNTAX      ConfdString
    MAX-ACCESS  read-only
    STATUS      current
    DESCRIPTION "Total number of client requests parsed for Firefox"
    ::= { affirmedServicesContentHttpProxyServiceStatisticsNode-levelDetailEntry 12 }

affirmedServicesContentHttpProxyServiceStatisticsNode-levelDetailNumparsedsafarirequests OBJECT-TYPE
    SYNTAX      ConfdString
    MAX-ACCESS  read-only
    STATUS      current
    DESCRIPTION "Total number of client requests parsed for Safari"
    ::= { affirmedServicesContentHttpProxyServiceStatisticsNode-levelDetailEntry 13 }

affirmedServicesContentHttpProxyServiceStatisticsNode-levelDetailNumparsedchromerequests OBJECT-TYPE
    SYNTAX      ConfdString
    MAX-ACCESS  read-only
    STATUS      current
    DESCRIPTION "Total number of client requests parsed for Chrome"
    ::= { affirmedServicesContentHttpProxyServiceStatisticsNode-levelDetailEntry 14 }

affirmedServicesContentHttpProxyServiceStatisticsNode-levelDetailServerhttpresponsesipv4 OBJECT-TYPE
    SYNTAX      ConfdString
    MAX-ACCESS  read-only
    STATUS      current
    DESCRIPTION "Total number of IPv4 server responses"
    ::= { affirmedServicesContentHttpProxyServiceStatisticsNode-levelDetailEntry 15 }

affirmedServicesContentHttpProxyServiceStatisticsNode-levelDetailServerhttpresponsesipv6 OBJECT-TYPE
    SYNTAX      ConfdString
    MAX-ACCESS  read-only
    STATUS      current
    DESCRIPTION "Total number of IPv6 server responses"
    ::= { affirmedServicesContentHttpProxyServiceStatisticsNode-levelDetailEntry 16 }

affirmedServicesContentHttpProxyServiceStatisticsNode-levelDetailClienthttprequestsizemin OBJECT-TYPE
    SYNTAX      ConfdString
    MAX-ACCESS  read-only
    STATUS      current
    DESCRIPTION "Client HTTP Request Size Min (Bytes)"
    ::= { affirmedServicesContentHttpProxyServiceStatisticsNode-levelDetailEntry 17 }

affirmedServicesContentHttpProxyServiceStatisticsNode-levelDetailClienthttprequestsizeavg OBJECT-TYPE
    SYNTAX      ConfdString
    MAX-ACCESS  read-only
    STATUS      current
    DESCRIPTION "Client HTTP Request Size Avg (Bytes)"
    ::= { affirmedServicesContentHttpProxyServiceStatisticsNode-levelDetailEntry 18 }

affirmedServicesContentHttpProxyServiceStatisticsNode-levelDetailClienthttprequestsizemax OBJECT-TYPE
    SYNTAX      ConfdString
    MAX-ACCESS  read-only
    STATUS      current
    DESCRIPTION "Client HTTP Request Size Max (Bytes)"
    ::= { affirmedServicesContentHttpProxyServiceStatisticsNode-levelDetailEntry 19 }

affirmedServicesContentHttpProxyServiceStatisticsNode-levelDetailClienthttpresponsesizemin OBJECT-TYPE
    SYNTAX      ConfdString
    MAX-ACCESS  read-only
    STATUS      current
    DESCRIPTION "Client HTTP Response Size Min (Bytes)"
    ::= { affirmedServicesContentHttpProxyServiceStatisticsNode-levelDetailEntry 20 }

affirmedServicesContentHttpProxyServiceStatisticsNode-levelDetailClienthttpresponsesizeavg OBJECT-TYPE
    SYNTAX      ConfdString
    MAX-ACCESS  read-only
    STATUS      current
    DESCRIPTION "Client HTTP Response Size Avg (Bytes)"
    ::= { affirmedServicesContentHttpProxyServiceStatisticsNode-levelDetailEntry 21 }

affirmedServicesContentHttpProxyServiceStatisticsNode-levelDetailClienthttpresponsesizemax OBJECT-TYPE
    SYNTAX      ConfdString
    MAX-ACCESS  read-only
    STATUS      current
    DESCRIPTION "Client HTTP Response Size Max (Bytes)"
    ::= { affirmedServicesContentHttpProxyServiceStatisticsNode-levelDetailEntry 22 }

affirmedServicesContentHttpProxyServiceStatisticsNode-levelDetailServicetimefromserveravg OBJECT-TYPE
    SYNTAX      ConfdString
    MAX-ACCESS  read-only
    STATUS      current
    DESCRIPTION "Client Average HTTP Request Service Time from Server"
    ::= { affirmedServicesContentHttpProxyServiceStatisticsNode-levelDetailEntry 23 }

affirmedServicesContentHttpProxyServiceStatisticsNode-levelDetailServicetimefromcacheavg OBJECT-TYPE
    SYNTAX      ConfdString
    MAX-ACCESS  read-only
    STATUS      current
    DESCRIPTION "Client Average HTTP Request Service Time from Cache"
    ::= { affirmedServicesContentHttpProxyServiceStatisticsNode-levelDetailEntry 24 }

affirmedServicesContentHttpProxyServiceStatisticsNode-levelDetailNumtotalclientrequestschunked OBJECT-TYPE
    SYNTAX      ConfdString
    MAX-ACCESS  read-only
    STATUS      current
    DESCRIPTION "Total number of chunked client requests received"
    ::= { affirmedServicesContentHttpProxyServiceStatisticsNode-levelDetailEntry 25 }

affirmedServicesContentHttpProxyServiceStatisticsNode-levelDetailNumsuccessclientrequestschunked OBJECT-TYPE
    SYNTAX      ConfdString
    MAX-ACCESS  read-only
    STATUS      current
    DESCRIPTION "Total number of chunked client requests processed successfully"
    ::= { affirmedServicesContentHttpProxyServiceStatisticsNode-levelDetailEntry 26 }

affirmedServicesContentHttpProxyServiceStatisticsNode-levelDetailNumproxyserviceattemptschunked OBJECT-TYPE
    SYNTAX      ConfdString
    MAX-ACCESS  read-only
    STATUS      current
    DESCRIPTION "Total number of chunked proxy service attempts"
    ::= { affirmedServicesContentHttpProxyServiceStatisticsNode-levelDetailEntry 27 }

affirmedServicesContentHttpProxyServiceStatisticsNode-levelDetailNumproxyservicesuccesscachedchunked OBJECT-TYPE
    SYNTAX      ConfdString
    MAX-ACCESS  read-only
    STATUS      current
    DESCRIPTION "Total number of proxy service success - cached chunked"
    ::= { affirmedServicesContentHttpProxyServiceStatisticsNode-levelDetailEntry 28 }

affirmedServicesContentHttpProxyServiceStatisticsNode-levelDetailNumproxyservicesuccesschunked OBJECT-TYPE
    SYNTAX      ConfdString
    MAX-ACCESS  read-only
    STATUS      current
    DESCRIPTION "Total number of chunked proxy service success"
    ::= { affirmedServicesContentHttpProxyServiceStatisticsNode-levelDetailEntry 29 }

affirmedServicesContentHttpProxyServiceStatisticsNode-levelDetailNumbytesclientrequestchunked OBJECT-TYPE
    SYNTAX      ConfdString
    MAX-ACCESS  read-only
    STATUS      current
    DESCRIPTION "Total number of Bytes from Chunked Client Request"
    ::= { affirmedServicesContentHttpProxyServiceStatisticsNode-levelDetailEntry 30 }

affirmedServicesContentHttpProxyServiceStatisticsNode-levelDetailNumbytesserverresponsechunked OBJECT-TYPE
    SYNTAX      ConfdString
    MAX-ACCESS  read-only
    STATUS      current
    DESCRIPTION "Total number of Bytes from Chunked Server Response"
    ::= { affirmedServicesContentHttpProxyServiceStatisticsNode-levelDetailEntry 31 }

affirmedServicesContentHttpProxyServiceStatisticsNode-levelDetailNumproxyserviceattemptschunkedvideo OBJECT-TYPE
    SYNTAX      ConfdString
    MAX-ACCESS  read-only
    STATUS      current
    DESCRIPTION "Total number of chunked video proxy service attempts"
    ::= { affirmedServicesContentHttpProxyServiceStatisticsNode-levelDetailEntry 32 }

affirmedServicesContentHttpProxyServiceStatisticsNode-levelDetailNumproxyservicesuccesschunkedvideo OBJECT-TYPE
    SYNTAX      ConfdString
    MAX-ACCESS  read-only
    STATUS      current
    DESCRIPTION "Total number of chunked video proxy service success"
    ::= { affirmedServicesContentHttpProxyServiceStatisticsNode-levelDetailEntry 33 }

affirmedServicesContentHttpProxyServiceStatisticsNode-levelDetailNumproxyservicesuccesscachedchunkedvideo OBJECT-TYPE
    SYNTAX      ConfdString
    MAX-ACCESS  read-only
    STATUS      current
    DESCRIPTION "Total number of proxy service success - cached chunked video"
    ::= { affirmedServicesContentHttpProxyServiceStatisticsNode-levelDetailEntry 34 }

affirmedServicesContentHttpProxyServiceStatisticsNode-levelDetailNumbytesserverresponsechunkedvideo OBJECT-TYPE
    SYNTAX      ConfdString
    MAX-ACCESS  read-only
    STATUS      current
    DESCRIPTION "Total number of Bytes from Chunked Video Server Response"
    ::= { affirmedServicesContentHttpProxyServiceStatisticsNode-levelDetailEntry 35 }

affirmedServicesContentHttpProxyServiceStatisticsNode-levelDetailNumconditionalclientrequests OBJECT-TYPE
    SYNTAX      ConfdString
    MAX-ACCESS  read-only
    STATUS      current
    DESCRIPTION "Total number of conditional client requests"
    ::= { affirmedServicesContentHttpProxyServiceStatisticsNode-levelDetailEntry 36 }

affirmedServicesContentHttpProxyServiceStatisticsNode-levelDetailNumproxyservicepreconditionfailed OBJECT-TYPE
    SYNTAX      ConfdString
    MAX-ACCESS  read-only
    STATUS      current
    DESCRIPTION "Total number of proxy service precondition failed"
    ::= { affirmedServicesContentHttpProxyServiceStatisticsNode-levelDetailEntry 37 }

affirmedServicesContentHttpProxyServiceStatisticsNode-levelDetailNumproxyservicepreconditionnotmodified OBJECT-TYPE
    SYNTAX      ConfdString
    MAX-ACCESS  read-only
    STATUS      current
    DESCRIPTION "Total number of proxy service precondition not modified"
    ::= { affirmedServicesContentHttpProxyServiceStatisticsNode-levelDetailEntry 38 }

affirmedServicesContentHttpProxyServiceStatisticsNode-levelDetailNumproxyservicepreconditionpartialcontentserved OBJECT-TYPE
    SYNTAX      ConfdString
    MAX-ACCESS  read-only
    STATUS      current
    DESCRIPTION "Total number of proxy service precondition partial content served"
    ::= { affirmedServicesContentHttpProxyServiceStatisticsNode-levelDetailEntry 39 }

affirmedServicesContentHttpProxyServiceStatisticsNode-levelDetailNumproxyservicepreconditionserved OBJECT-TYPE
    SYNTAX      ConfdString
    MAX-ACCESS  read-only
    STATUS      current
    DESCRIPTION "Total number of proxy service precondition served"
    ::= { affirmedServicesContentHttpProxyServiceStatisticsNode-levelDetailEntry 40 }

affirmedServicesContentHttpProxyServiceStatisticsNode-levelDetailNumproxyservicepreconditionforwarded OBJECT-TYPE
    SYNTAX      ConfdString
    MAX-ACCESS  read-only
    STATUS      current
    DESCRIPTION "Total number of proxy service precondition forwarded"
    ::= { affirmedServicesContentHttpProxyServiceStatisticsNode-levelDetailEntry 41 }

affirmedServicesContentHttpProxyServiceStatisticsNode-levelDetailNumbufferedrequests OBJECT-TYPE
    SYNTAX      ConfdString
    MAX-ACCESS  read-only
    STATUS      current
    DESCRIPTION "Total number of client requests delayed due to buffering"
    ::= { affirmedServicesContentHttpProxyServiceStatisticsNode-levelDetailEntry 42 }

affirmedServicesContentHttpProxyServiceStatisticsNode-levelDetailNumbufferedresponses OBJECT-TYPE
    SYNTAX      ConfdString
    MAX-ACCESS  read-only
    STATUS      current
    DESCRIPTION "Total number of server responses delayed due to buffering limit"
    ::= { affirmedServicesContentHttpProxyServiceStatisticsNode-levelDetailEntry 43 }

affirmedServicesContentHttpProxyServiceStatisticsNode-levelDetailNumtransparentproxyrequests OBJECT-TYPE
    SYNTAX      ConfdString
    MAX-ACCESS  read-only
    STATUS      current
    DESCRIPTION "Total number of client requests destined to transparent proxy"
    ::= { affirmedServicesContentHttpProxyServiceStatisticsNode-levelDetailEntry 44 }

affirmedServicesContentHttpProxyServiceStatisticsNode-levelDetailNumexplicitproxyrequests OBJECT-TYPE
    SYNTAX      ConfdString
    MAX-ACCESS  read-only
    STATUS      current
    DESCRIPTION "Total number of client requests destined to an explicit proxy"
    ::= { affirmedServicesContentHttpProxyServiceStatisticsNode-levelDetailEntry 45 }

affirmedServicesContentHttpProxyServiceStatisticsNode-levelDetailNumparsedlinuxrequests OBJECT-TYPE
    SYNTAX      ConfdString
    MAX-ACCESS  read-only
    STATUS      current
    DESCRIPTION "Total number of client requests parsed for Linux"
    ::= { affirmedServicesContentHttpProxyServiceStatisticsNode-levelDetailEntry 46 }

affirmedServicesContentHttpProxyServiceStatisticsNode-levelDetailNumparsedmacintoshrequests OBJECT-TYPE
    SYNTAX      ConfdString
    MAX-ACCESS  read-only
    STATUS      current
    DESCRIPTION "Total number of client requests parsed for Macintosh"
    ::= { affirmedServicesContentHttpProxyServiceStatisticsNode-levelDetailEntry 47 }

affirmedServicesContentHttpProxyServiceStatisticsNode-levelDetailNumparsedwindowsrequests OBJECT-TYPE
    SYNTAX      ConfdString
    MAX-ACCESS  read-only
    STATUS      current
    DESCRIPTION "Total number of client requests parsed for Windows"
    ::= { affirmedServicesContentHttpProxyServiceStatisticsNode-levelDetailEntry 48 }

affirmedServicesContentHttpProxyServiceStatisticsNode-levelDetailNumparsedotherosrequests OBJECT-TYPE
    SYNTAX      ConfdString
    MAX-ACCESS  read-only
    STATUS      current
    DESCRIPTION "Total number of client requests parsed for Other OS"
    ::= { affirmedServicesContentHttpProxyServiceStatisticsNode-levelDetailEntry 49 }

affirmedServicesContentHttpProxyServiceStatisticsNode-levelDetailNumparsedinternetexplorerrequests OBJECT-TYPE
    SYNTAX      ConfdString
    MAX-ACCESS  read-only
    STATUS      current
    DESCRIPTION "Total number of client requests parsed for InternetExplorer"
    ::= { affirmedServicesContentHttpProxyServiceStatisticsNode-levelDetailEntry 50 }

affirmedServicesContentHttpProxyServiceStatisticsNode-levelDetailNumparsedotherbrowserrequests OBJECT-TYPE
    SYNTAX      ConfdString
    MAX-ACCESS  read-only
    STATUS      current
    DESCRIPTION "Total number of client requests parsed for Other Browser"
    ::= { affirmedServicesContentHttpProxyServiceStatisticsNode-levelDetailEntry 51 }

affirmedServicesContentHttpProxyServiceStatisticsNode-levelDetailNumhttpproxyrequestpolicyappliedtotal OBJECT-TYPE
    SYNTAX      ConfdString
    MAX-ACCESS  read-only
    STATUS      current
    DESCRIPTION "Total number of request policy applied"
    ::= { affirmedServicesContentHttpProxyServiceStatisticsNode-levelDetailEntry 52 }

affirmedServicesContentHttpProxyServiceStatisticsNode-levelDetailNumhttpproxyresponsepolicyappliedtotal OBJECT-TYPE
    SYNTAX      ConfdString
    MAX-ACCESS  read-only
    STATUS      current
    DESCRIPTION "Total number of response policy applied"
    ::= { affirmedServicesContentHttpProxyServiceStatisticsNode-levelDetailEntry 53 }

affirmedServicesContentHttpProxyServiceStatisticsNode-levelDetailClienthttpresponsestatusinformation OBJECT-TYPE
    SYNTAX      ConfdString
    MAX-ACCESS  read-only
    STATUS      current
    DESCRIPTION "Client HTTP Response Status Information (1xx)"
    ::= { affirmedServicesContentHttpProxyServiceStatisticsNode-levelDetailEntry 54 }

affirmedServicesContentHttpProxyServiceStatisticsNode-levelDetailClienthttpresponsestatussuccessok OBJECT-TYPE
    SYNTAX      ConfdString
    MAX-ACCESS  read-only
    STATUS      current
    DESCRIPTION "Client HTTP Response Status Success OK (200)"
    ::= { affirmedServicesContentHttpProxyServiceStatisticsNode-levelDetailEntry 55 }

affirmedServicesContentHttpProxyServiceStatisticsNode-levelDetailClienthttpresponsestatussuccessother OBJECT-TYPE
    SYNTAX      ConfdString
    MAX-ACCESS  read-only
    STATUS      current
    DESCRIPTION "Client HTTP Response Status Success Other (2xx)"
    ::= { affirmedServicesContentHttpProxyServiceStatisticsNode-levelDetailEntry 56 }

affirmedServicesContentHttpProxyServiceStatisticsNode-levelDetailClienthttpresponsestatusredirection OBJECT-TYPE
    SYNTAX      ConfdString
    MAX-ACCESS  read-only
    STATUS      current
    DESCRIPTION "Client HTTP Response Status Redirection (3xx)"
    ::= { affirmedServicesContentHttpProxyServiceStatisticsNode-levelDetailEntry 57 }

affirmedServicesContentHttpProxyServiceStatisticsNode-levelDetailClienthttpresponsestatusclienterror OBJECT-TYPE
    SYNTAX      ConfdString
    MAX-ACCESS  read-only
    STATUS      current
    DESCRIPTION "Client HTTP Response Status Client Error (4xx)"
    ::= { affirmedServicesContentHttpProxyServiceStatisticsNode-levelDetailEntry 58 }

affirmedServicesContentHttpProxyServiceStatisticsNode-levelDetailClienthttpresponsestatusservererror OBJECT-TYPE
    SYNTAX      ConfdString
    MAX-ACCESS  read-only
    STATUS      current
    DESCRIPTION "Client HTTP Response Status Server Error (5xx)"
    ::= { affirmedServicesContentHttpProxyServiceStatisticsNode-levelDetailEntry 59 }

affirmedServicesContentHttpProxyServiceStatisticsNode-levelSummaryTable OBJECT-TYPE
    SYNTAX      SEQUENCE OF AffirmedServicesContentHttpProxyServiceStatisticsNode-levelSummaryEntry
    MAX-ACCESS  not-accessible
    STATUS      current
    DESCRIPTION ""
    ::= { affirmedServicesContentHttpProxyServiceStatisticsNode-level 4 }

affirmedServicesContentHttpProxyServiceStatisticsNode-levelSummaryEntry OBJECT-TYPE
    SYNTAX      AffirmedServicesContentHttpProxyServiceStatisticsNode-levelSummaryEntry
    MAX-ACCESS  not-accessible
    STATUS      current
    DESCRIPTION ""
    INDEX { affirmedServicesContentHttpProxyServiceStatisticsNode-levelSummaryChassis, affirmedServicesContentHttpProxyServiceStatisticsNode-levelSummarySlot }
        ::= { affirmedServicesContentHttpProxyServiceStatisticsNode-levelSummaryTable 1 }

AffirmedServicesContentHttpProxyServiceStatisticsNode-levelSummaryEntry ::=
    SEQUENCE {
        affirmedServicesContentHttpProxyServiceStatisticsNode-levelSummaryChassis Unsigned32,
        affirmedServicesContentHttpProxyServiceStatisticsNode-levelSummarySlot INTEGER,
        affirmedServicesContentHttpProxyServiceStatisticsNode-levelSummaryNumproxyserviceattempts ConfdString,
        affirmedServicesContentHttpProxyServiceStatisticsNode-levelSummaryNumproxyservicesuccess ConfdString,
        affirmedServicesContentHttpProxyServiceStatisticsNode-levelSummaryNumproxyservicesuccesscached ConfdString,
        affirmedServicesContentHttpProxyServiceStatisticsNode-levelSummaryNumproxyserviceabortedbyclient ConfdString,
        affirmedServicesContentHttpProxyServiceStatisticsNode-levelSummaryNumproxyservicefailed ConfdString,
        affirmedServicesContentHttpProxyServiceStatisticsNode-levelSummaryNumtotalclientrequests ConfdString,
        affirmedServicesContentHttpProxyServiceStatisticsNode-levelSummaryNuminserviceclientrequests ConfdString,
        affirmedServicesContentHttpProxyServiceStatisticsNode-levelSummaryNumsuccessclientrequests ConfdString,
        affirmedServicesContentHttpProxyServiceStatisticsNode-levelSummaryNumclientabortrequests ConfdString,
        affirmedServicesContentHttpProxyServiceStatisticsNode-levelSummaryNumfailedclientrequests ConfdString,
        affirmedServicesContentHttpProxyServiceStatisticsNode-levelSummaryNumpipelinedroppedclientrequests ConfdString,
        affirmedServicesContentHttpProxyServiceStatisticsNode-levelSummaryNuminvalidclientrequests ConfdString,
        affirmedServicesContentHttpProxyServiceStatisticsNode-levelSummaryNumbytesclientrequest ConfdString,
        affirmedServicesContentHttpProxyServiceStatisticsNode-levelSummaryNumbytesclientresponse ConfdString,
        affirmedServicesContentHttpProxyServiceStatisticsNode-levelSummaryNumbytesserverrequest ConfdString,
        affirmedServicesContentHttpProxyServiceStatisticsNode-levelSummaryNumbytesserverresponse ConfdString,
        affirmedServicesContentHttpProxyServiceStatisticsNode-levelSummaryClienthttpservicetimemin ConfdString,
        affirmedServicesContentHttpProxyServiceStatisticsNode-levelSummaryClienthttpservicetimeavg ConfdString,
        affirmedServicesContentHttpProxyServiceStatisticsNode-levelSummaryClienthttpservicetimemax ConfdString,
        affirmedServicesContentHttpProxyServiceStatisticsNode-levelSummaryServerhttpresponsestotal ConfdString,
        affirmedServicesContentHttpProxyServiceStatisticsNode-levelSummaryServerhttpresponsetimemin ConfdString,
        affirmedServicesContentHttpProxyServiceStatisticsNode-levelSummaryServerhttpresponsetimeavg ConfdString,
        affirmedServicesContentHttpProxyServiceStatisticsNode-levelSummaryServerhttpresponsetimemax ConfdString,
        affirmedServicesContentHttpProxyServiceStatisticsNode-levelSummaryLatencyrequestavg ConfdString,
        affirmedServicesContentHttpProxyServiceStatisticsNode-levelSummaryLatencyresponseavg ConfdString,
        affirmedServicesContentHttpProxyServiceStatisticsNode-levelSummaryLatencyavg ConfdString,
        affirmedServicesContentHttpProxyServiceStatisticsNode-levelSummaryNumproxyclientcount ConfdString
    }

affirmedServicesContentHttpProxyServiceStatisticsNode-levelSummaryChassis OBJECT-TYPE
    SYNTAX      Unsigned32
    MAX-ACCESS  not-accessible
    STATUS      current
    DESCRIPTION "chassis ID"
    ::= { affirmedServicesContentHttpProxyServiceStatisticsNode-levelSummaryEntry 1 }

affirmedServicesContentHttpProxyServiceStatisticsNode-levelSummarySlot OBJECT-TYPE
    SYNTAX      INTEGER {a1(1),a2(2),a3(3),a4(4),a5(5),a6(6),a7(7),a8(8),a9(9),a10(10),a11(11),a12(12),a13(13),a14(14),a15(15),a16(16),a17(17),a18(18),a19(19),a20(20),a21(21),a22(22),a23(23),a24(24),a25(25),a26(26),a27(27),a28(28),a29(29),a30(30),a31(31),a32(32),a33(33),a34(34),a35(35),a36(36),a37(37),a38(38),a39(39),a40(40),a41(41),a42(42),a43(43),a44(44),a45(45),a46(46),a47(47),a48(48),a49(49),a50(50),a51(51),a52(52),a53(53),a54(54),a55(55),a56(56),a57(57),a58(58),a59(59),a60(60),a61(61),a62(62),a63(63),a64(64),a65(65),a66(66),a67(67),a68(68),a69(69),a70(70),a71(71),a72(72),a73(73),a74(74),a75(75),a76(76),a77(77),a78(78),a79(79),a80(80),a81(81),a82(82),a83(83),a84(84),a85(85),a86(86),a87(87),a88(88),a89(89),a90(90),a91(91),a92(92),a93(93),a94(94),a95(95),a96(96),a97(97),a98(98),a99(99),a100(100),a101(101),a102(102),a103(103),a104(104),a105(105),a106(106),a107(107),a108(108),a109(109),a110(110),a111(111),a112(112),a113(113),a114(114),a115(115),a116(116),a117(117),a118(118),a119(119),a120(120),a121(121),a122(122),a123(123),a124(124),a125(125),a126(126),a127(127),a128(128)}
    MAX-ACCESS  not-accessible
    STATUS      current
    DESCRIPTION "slot number"
    ::= { affirmedServicesContentHttpProxyServiceStatisticsNode-levelSummaryEntry 2 }

affirmedServicesContentHttpProxyServiceStatisticsNode-levelSummaryNumproxyserviceattempts OBJECT-TYPE
    SYNTAX      ConfdString
    MAX-ACCESS  read-only
    STATUS      current
    DESCRIPTION "Total number of proxy service attempts"
    ::= { affirmedServicesContentHttpProxyServiceStatisticsNode-levelSummaryEntry 3 }

affirmedServicesContentHttpProxyServiceStatisticsNode-levelSummaryNumproxyservicesuccess OBJECT-TYPE
    SYNTAX      ConfdString
    MAX-ACCESS  read-only
    STATUS      current
    DESCRIPTION "Total number of proxy service success"
    ::= { affirmedServicesContentHttpProxyServiceStatisticsNode-levelSummaryEntry 4 }

affirmedServicesContentHttpProxyServiceStatisticsNode-levelSummaryNumproxyservicesuccesscached OBJECT-TYPE
    SYNTAX      ConfdString
    MAX-ACCESS  read-only
    STATUS      current
    DESCRIPTION "Total number of proxy service success - Cached"
    ::= { affirmedServicesContentHttpProxyServiceStatisticsNode-levelSummaryEntry 5 }

affirmedServicesContentHttpProxyServiceStatisticsNode-levelSummaryNumproxyserviceabortedbyclient OBJECT-TYPE
    SYNTAX      ConfdString
    MAX-ACCESS  read-only
    STATUS      current
    DESCRIPTION "Total number of proxy service aborted"
    ::= { affirmedServicesContentHttpProxyServiceStatisticsNode-levelSummaryEntry 6 }

affirmedServicesContentHttpProxyServiceStatisticsNode-levelSummaryNumproxyservicefailed OBJECT-TYPE
    SYNTAX      ConfdString
    MAX-ACCESS  read-only
    STATUS      current
    DESCRIPTION "Total number of proxy service failed"
    ::= { affirmedServicesContentHttpProxyServiceStatisticsNode-levelSummaryEntry 7 }

affirmedServicesContentHttpProxyServiceStatisticsNode-levelSummaryNumtotalclientrequests OBJECT-TYPE
    SYNTAX      ConfdString
    MAX-ACCESS  read-only
    STATUS      current
    DESCRIPTION "Total number of client requests received"
    ::= { affirmedServicesContentHttpProxyServiceStatisticsNode-levelSummaryEntry 8 }

affirmedServicesContentHttpProxyServiceStatisticsNode-levelSummaryNuminserviceclientrequests OBJECT-TYPE
    SYNTAX      ConfdString
    MAX-ACCESS  read-only
    STATUS      current
    DESCRIPTION "Total number of client requests currently in service"
    ::= { affirmedServicesContentHttpProxyServiceStatisticsNode-levelSummaryEntry 9 }

affirmedServicesContentHttpProxyServiceStatisticsNode-levelSummaryNumsuccessclientrequests OBJECT-TYPE
    SYNTAX      ConfdString
    MAX-ACCESS  read-only
    STATUS      current
    DESCRIPTION "Total number of client requests parsed successfully"
    ::= { affirmedServicesContentHttpProxyServiceStatisticsNode-levelSummaryEntry 10 }

affirmedServicesContentHttpProxyServiceStatisticsNode-levelSummaryNumclientabortrequests OBJECT-TYPE
    SYNTAX      ConfdString
    MAX-ACCESS  read-only
    STATUS      current
    DESCRIPTION "Total number of incomplete client requests"
    ::= { affirmedServicesContentHttpProxyServiceStatisticsNode-levelSummaryEntry 11 }

affirmedServicesContentHttpProxyServiceStatisticsNode-levelSummaryNumfailedclientrequests OBJECT-TYPE
    SYNTAX      ConfdString
    MAX-ACCESS  read-only
    STATUS      current
    DESCRIPTION "Total number of client requests processing failed"
    ::= { affirmedServicesContentHttpProxyServiceStatisticsNode-levelSummaryEntry 12 }

affirmedServicesContentHttpProxyServiceStatisticsNode-levelSummaryNumpipelinedroppedclientrequests OBJECT-TYPE
    SYNTAX      ConfdString
    MAX-ACCESS  read-only
    STATUS      current
    DESCRIPTION "Total number of client requests pipeline dropped"
    ::= { affirmedServicesContentHttpProxyServiceStatisticsNode-levelSummaryEntry 13 }

affirmedServicesContentHttpProxyServiceStatisticsNode-levelSummaryNuminvalidclientrequests OBJECT-TYPE
    SYNTAX      ConfdString
    MAX-ACCESS  read-only
    STATUS      current
    DESCRIPTION "Total number of invalid client requests"
    ::= { affirmedServicesContentHttpProxyServiceStatisticsNode-levelSummaryEntry 14 }

affirmedServicesContentHttpProxyServiceStatisticsNode-levelSummaryNumbytesclientrequest OBJECT-TYPE
    SYNTAX      ConfdString
    MAX-ACCESS  read-only
    STATUS      current
    DESCRIPTION "Total number of Bytes Client Request"
    ::= { affirmedServicesContentHttpProxyServiceStatisticsNode-levelSummaryEntry 15 }

affirmedServicesContentHttpProxyServiceStatisticsNode-levelSummaryNumbytesclientresponse OBJECT-TYPE
    SYNTAX      ConfdString
    MAX-ACCESS  read-only
    STATUS      current
    DESCRIPTION "Total number of Bytes Client Response"
    ::= { affirmedServicesContentHttpProxyServiceStatisticsNode-levelSummaryEntry 16 }

affirmedServicesContentHttpProxyServiceStatisticsNode-levelSummaryNumbytesserverrequest OBJECT-TYPE
    SYNTAX      ConfdString
    MAX-ACCESS  read-only
    STATUS      current
    DESCRIPTION "Total number of Bytes Server Request"
    ::= { affirmedServicesContentHttpProxyServiceStatisticsNode-levelSummaryEntry 17 }

affirmedServicesContentHttpProxyServiceStatisticsNode-levelSummaryNumbytesserverresponse OBJECT-TYPE
    SYNTAX      ConfdString
    MAX-ACCESS  read-only
    STATUS      current
    DESCRIPTION "Total number of Bytes Server Response"
    ::= { affirmedServicesContentHttpProxyServiceStatisticsNode-levelSummaryEntry 18 }

affirmedServicesContentHttpProxyServiceStatisticsNode-levelSummaryClienthttpservicetimemin OBJECT-TYPE
    SYNTAX      ConfdString
    MAX-ACCESS  read-only
    STATUS      current
    DESCRIPTION "Client HTTP Service Time Min (ms)"
    ::= { affirmedServicesContentHttpProxyServiceStatisticsNode-levelSummaryEntry 19 }

affirmedServicesContentHttpProxyServiceStatisticsNode-levelSummaryClienthttpservicetimeavg OBJECT-TYPE
    SYNTAX      ConfdString
    MAX-ACCESS  read-only
    STATUS      current
    DESCRIPTION "Client HTTP Service Time Avg (ms)"
    ::= { affirmedServicesContentHttpProxyServiceStatisticsNode-levelSummaryEntry 20 }

affirmedServicesContentHttpProxyServiceStatisticsNode-levelSummaryClienthttpservicetimemax OBJECT-TYPE
    SYNTAX      ConfdString
    MAX-ACCESS  read-only
    STATUS      current
    DESCRIPTION "Client HTTP Service Time Max (ms)"
    ::= { affirmedServicesContentHttpProxyServiceStatisticsNode-levelSummaryEntry 21 }

affirmedServicesContentHttpProxyServiceStatisticsNode-levelSummaryServerhttpresponsestotal OBJECT-TYPE
    SYNTAX      ConfdString
    MAX-ACCESS  read-only
    STATUS      current
    DESCRIPTION "Total number of HTTP server responses"
    ::= { affirmedServicesContentHttpProxyServiceStatisticsNode-levelSummaryEntry 22 }

affirmedServicesContentHttpProxyServiceStatisticsNode-levelSummaryServerhttpresponsetimemin OBJECT-TYPE
    SYNTAX      ConfdString
    MAX-ACCESS  read-only
    STATUS      current
    DESCRIPTION "Server HTTP Response Time Min (ms)"
    ::= { affirmedServicesContentHttpProxyServiceStatisticsNode-levelSummaryEntry 23 }

affirmedServicesContentHttpProxyServiceStatisticsNode-levelSummaryServerhttpresponsetimeavg OBJECT-TYPE
    SYNTAX      ConfdString
    MAX-ACCESS  read-only
    STATUS      current
    DESCRIPTION "Server HTTP Response Time Avg (ms)"
    ::= { affirmedServicesContentHttpProxyServiceStatisticsNode-levelSummaryEntry 24 }

affirmedServicesContentHttpProxyServiceStatisticsNode-levelSummaryServerhttpresponsetimemax OBJECT-TYPE
    SYNTAX      ConfdString
    MAX-ACCESS  read-only
    STATUS      current
    DESCRIPTION "Server HTTP Response Time Max (ms)"
    ::= { affirmedServicesContentHttpProxyServiceStatisticsNode-levelSummaryEntry 25 }

affirmedServicesContentHttpProxyServiceStatisticsNode-levelSummaryLatencyrequestavg OBJECT-TYPE
    SYNTAX      ConfdString
    MAX-ACCESS  read-only
    STATUS      current
    DESCRIPTION "HTTP Request Service Latency Average (ms)"
    ::= { affirmedServicesContentHttpProxyServiceStatisticsNode-levelSummaryEntry 26 }

affirmedServicesContentHttpProxyServiceStatisticsNode-levelSummaryLatencyresponseavg OBJECT-TYPE
    SYNTAX      ConfdString
    MAX-ACCESS  read-only
    STATUS      current
    DESCRIPTION "HTTP Response Service Latency Average (ms)"
    ::= { affirmedServicesContentHttpProxyServiceStatisticsNode-levelSummaryEntry 27 }

affirmedServicesContentHttpProxyServiceStatisticsNode-levelSummaryLatencyavg OBJECT-TYPE
    SYNTAX      ConfdString
    MAX-ACCESS  read-only
    STATUS      current
    DESCRIPTION "HTTP Service Latency Average (ms)"
    ::= { affirmedServicesContentHttpProxyServiceStatisticsNode-levelSummaryEntry 28 }

affirmedServicesContentHttpProxyServiceStatisticsNode-levelSummaryNumproxyclientcount OBJECT-TYPE
    SYNTAX      ConfdString
    MAX-ACCESS  read-only
    STATUS      current
    DESCRIPTION "Total number of current Proxy Sessions"
    ::= { affirmedServicesContentHttpProxyServiceStatisticsNode-levelSummaryEntry 29 }

affirmedServicesContentHttpProxyServiceStatisticsNode-levelFailureTable OBJECT-TYPE
    SYNTAX      SEQUENCE OF AffirmedServicesContentHttpProxyServiceStatisticsNode-levelFailureEntry
    MAX-ACCESS  not-accessible
    STATUS      current
    DESCRIPTION ""
    ::= { affirmedServicesContentHttpProxyServiceStatisticsNode-level 5 }

affirmedServicesContentHttpProxyServiceStatisticsNode-levelFailureEntry OBJECT-TYPE
    SYNTAX      AffirmedServicesContentHttpProxyServiceStatisticsNode-levelFailureEntry
    MAX-ACCESS  not-accessible
    STATUS      current
    DESCRIPTION ""
    INDEX { affirmedServicesContentHttpProxyServiceStatisticsNode-levelFailureChassis, affirmedServicesContentHttpProxyServiceStatisticsNode-levelFailureSlot }
        ::= { affirmedServicesContentHttpProxyServiceStatisticsNode-levelFailureTable 1 }

AffirmedServicesContentHttpProxyServiceStatisticsNode-levelFailureEntry ::=
    SEQUENCE {
        affirmedServicesContentHttpProxyServiceStatisticsNode-levelFailureChassis Unsigned32,
        affirmedServicesContentHttpProxyServiceStatisticsNode-levelFailureSlot INTEGER,
        affirmedServicesContentHttpProxyServiceStatisticsNode-levelFailureNuminvalidclientrequestsoversizedheader ConfdString,
        affirmedServicesContentHttpProxyServiceStatisticsNode-levelFailureNuminvalidclientrequestsbadrequestline ConfdString,
        affirmedServicesContentHttpProxyServiceStatisticsNode-levelFailureNuminvalidclientrequestsbadheaders ConfdString,
        affirmedServicesContentHttpProxyServiceStatisticsNode-levelFailureNuminvalidclientrequestsbadheaderattribute ConfdString,
        affirmedServicesContentHttpProxyServiceStatisticsNode-levelFailureNuminvalidclientrequestsdupheaderattribute ConfdString,
        affirmedServicesContentHttpProxyServiceStatisticsNode-levelFailureNuminvalidclientrequestsbadhostname ConfdString,
        affirmedServicesContentHttpProxyServiceStatisticsNode-levelFailureNuminvalidclientrequestshostnotfound ConfdString,
        affirmedServicesContentHttpProxyServiceStatisticsNode-levelFailureNuminvalidclientrequestsnotsupported ConfdString,
        affirmedServicesContentHttpProxyServiceStatisticsNode-levelFailureNuminvalidclientrequestsexpectheadererror ConfdString,
        affirmedServicesContentHttpProxyServiceStatisticsNode-levelFailureNuminvalidclientrequestsbodyreaderror ConfdString,
        affirmedServicesContentHttpProxyServiceStatisticsNode-levelFailureNuminvalidclientrequestsidletimeout ConfdString,
        affirmedServicesContentHttpProxyServiceStatisticsNode-levelFailureNumproxyservicefailedrequestcompileerror ConfdString,
        affirmedServicesContentHttpProxyServiceStatisticsNode-levelFailureNumproxyservicefailedconnectioninitfailure ConfdString,
        affirmedServicesContentHttpProxyServiceStatisticsNode-levelFailureNumproxyservicefailedoversizedresponseheader ConfdString,
        affirmedServicesContentHttpProxyServiceStatisticsNode-levelFailureNumproxyservicefailedbadresponsestatusline ConfdString,
        affirmedServicesContentHttpProxyServiceStatisticsNode-levelFailureNumproxyservicefailedbadresponseheader ConfdString,
        affirmedServicesContentHttpProxyServiceStatisticsNode-levelFailureNumproxyservicefailedresponseprocessingfailure ConfdString,
        affirmedServicesContentHttpProxyServiceStatisticsNode-levelFailureNumproxyservicefailedserverconnectionclose ConfdString,
        affirmedServicesContentHttpProxyServiceStatisticsNode-levelFailureNumproxyservicefailedserverconnectiontimeout ConfdString,
        affirmedServicesContentHttpProxyServiceStatisticsNode-levelFailureNumproxyservicefailedclientconnectiontimeout ConfdString,
        affirmedServicesContentHttpProxyServiceStatisticsNode-levelFailureNumproxyservicefailedresourceunavailable ConfdString,
        affirmedServicesContentHttpProxyServiceStatisticsNode-levelFailureNumproxyserviceredirected ConfdString,
        affirmedServicesContentHttpProxyServiceStatisticsNode-levelFailureNumproxyserviceblocked ConfdString,
        affirmedServicesContentHttpProxyServiceStatisticsNode-levelFailureNumcacheservicefailedresponsereaderror ConfdString,
        affirmedServicesContentHttpProxyServiceStatisticsNode-levelFailureNumcacheservicefailedresponseheaderprocessing ConfdString,
        affirmedServicesContentHttpProxyServiceStatisticsNode-levelFailureNumcacheservicefailedresponseoversizedheader ConfdString,
        affirmedServicesContentHttpProxyServiceStatisticsNode-levelFailureNumcacheservicefailedservervalidationfailures ConfdString,
        affirmedServicesContentHttpProxyServiceStatisticsNode-levelFailureNumcacheservicefailedmaintenanceconnectionclose ConfdString,
        affirmedServicesContentHttpProxyServiceStatisticsNode-levelFailureNumproxyservicefailedmaintenanceconnectionclose ConfdString,
        affirmedServicesContentHttpProxyServiceStatisticsNode-levelFailureNumproxyserviceabortedbyclient ConfdString,
        affirmedServicesContentHttpProxyServiceStatisticsNode-levelFailureNumproxyserviceabortednorespfromserver ConfdString,
        affirmedServicesContentHttpProxyServiceStatisticsNode-levelFailureNumproxyserviceabortedrequesttolocaladdr ConfdString,
        affirmedServicesContentHttpProxyServiceStatisticsNode-levelFailureNumconnectionfailuresoverload ConfdString,
        affirmedServicesContentHttpProxyServiceStatisticsNode-levelFailureNumconnectionfailuresinvalidmetadata ConfdString,
        affirmedServicesContentHttpProxyServiceStatisticsNode-levelFailureNumconnectionfailuresproxyisnotready ConfdString,
        affirmedServicesContentHttpProxyServiceStatisticsNode-levelFailureNumproxyserviceoutofbuffer ConfdString,
        affirmedServicesContentHttpProxyServiceStatisticsNode-levelFailureNumconnectionfailuresfdlimitexceeded ConfdString,
        affirmedServicesContentHttpProxyServiceStatisticsNode-levelFailureNumconnectionfailuresoutofresources ConfdString
    }

affirmedServicesContentHttpProxyServiceStatisticsNode-levelFailureChassis OBJECT-TYPE
    SYNTAX      Unsigned32
    MAX-ACCESS  not-accessible
    STATUS      current
    DESCRIPTION "chassis ID"
    ::= { affirmedServicesContentHttpProxyServiceStatisticsNode-levelFailureEntry 1 }

affirmedServicesContentHttpProxyServiceStatisticsNode-levelFailureSlot OBJECT-TYPE
    SYNTAX      INTEGER {a1(1),a2(2),a3(3),a4(4),a5(5),a6(6),a7(7),a8(8),a9(9),a10(10),a11(11),a12(12),a13(13),a14(14),a15(15),a16(16),a17(17),a18(18),a19(19),a20(20),a21(21),a22(22),a23(23),a24(24),a25(25),a26(26),a27(27),a28(28),a29(29),a30(30),a31(31),a32(32),a33(33),a34(34),a35(35),a36(36),a37(37),a38(38),a39(39),a40(40),a41(41),a42(42),a43(43),a44(44),a45(45),a46(46),a47(47),a48(48),a49(49),a50(50),a51(51),a52(52),a53(53),a54(54),a55(55),a56(56),a57(57),a58(58),a59(59),a60(60),a61(61),a62(62),a63(63),a64(64),a65(65),a66(66),a67(67),a68(68),a69(69),a70(70),a71(71),a72(72),a73(73),a74(74),a75(75),a76(76),a77(77),a78(78),a79(79),a80(80),a81(81),a82(82),a83(83),a84(84),a85(85),a86(86),a87(87),a88(88),a89(89),a90(90),a91(91),a92(92),a93(93),a94(94),a95(95),a96(96),a97(97),a98(98),a99(99),a100(100),a101(101),a102(102),a103(103),a104(104),a105(105),a106(106),a107(107),a108(108),a109(109),a110(110),a111(111),a112(112),a113(113),a114(114),a115(115),a116(116),a117(117),a118(118),a119(119),a120(120),a121(121),a122(122),a123(123),a124(124),a125(125),a126(126),a127(127),a128(128)}
    MAX-ACCESS  not-accessible
    STATUS      current
    DESCRIPTION "slot number"
    ::= { affirmedServicesContentHttpProxyServiceStatisticsNode-levelFailureEntry 2 }

affirmedServicesContentHttpProxyServiceStatisticsNode-levelFailureNuminvalidclientrequestsoversizedheader OBJECT-TYPE
    SYNTAX      ConfdString
    MAX-ACCESS  read-only
    STATUS      current
    DESCRIPTION "Total number of invalid client requests - Oversized Header"
    ::= { affirmedServicesContentHttpProxyServiceStatisticsNode-levelFailureEntry 3 }

affirmedServicesContentHttpProxyServiceStatisticsNode-levelFailureNuminvalidclientrequestsbadrequestline OBJECT-TYPE
    SYNTAX      ConfdString
    MAX-ACCESS  read-only
    STATUS      current
    DESCRIPTION "Total number of invalid client requests - Bad Request line"
    ::= { affirmedServicesContentHttpProxyServiceStatisticsNode-levelFailureEntry 4 }

affirmedServicesContentHttpProxyServiceStatisticsNode-levelFailureNuminvalidclientrequestsbadheaders OBJECT-TYPE
    SYNTAX      ConfdString
    MAX-ACCESS  read-only
    STATUS      current
    DESCRIPTION "Total number of invalid client requests - Bad Headers"
    ::= { affirmedServicesContentHttpProxyServiceStatisticsNode-levelFailureEntry 5 }

affirmedServicesContentHttpProxyServiceStatisticsNode-levelFailureNuminvalidclientrequestsbadheaderattribute OBJECT-TYPE
    SYNTAX      ConfdString
    MAX-ACCESS  read-only
    STATUS      current
    DESCRIPTION "Total number of invalid client requests - Bad Header Attribute"
    ::= { affirmedServicesContentHttpProxyServiceStatisticsNode-levelFailureEntry 6 }

affirmedServicesContentHttpProxyServiceStatisticsNode-levelFailureNuminvalidclientrequestsdupheaderattribute OBJECT-TYPE
    SYNTAX      ConfdString
    MAX-ACCESS  read-only
    STATUS      current
    DESCRIPTION "Total number of invalid client requests - Duplicated Header Attribute"
    ::= { affirmedServicesContentHttpProxyServiceStatisticsNode-levelFailureEntry 7 }

affirmedServicesContentHttpProxyServiceStatisticsNode-levelFailureNuminvalidclientrequestsbadhostname OBJECT-TYPE
    SYNTAX      ConfdString
    MAX-ACCESS  read-only
    STATUS      current
    DESCRIPTION "Total number of invalid client requests - Bad Host Name"
    ::= { affirmedServicesContentHttpProxyServiceStatisticsNode-levelFailureEntry 8 }

affirmedServicesContentHttpProxyServiceStatisticsNode-levelFailureNuminvalidclientrequestshostnotfound OBJECT-TYPE
    SYNTAX      ConfdString
    MAX-ACCESS  read-only
    STATUS      current
    DESCRIPTION "Total number of invalid client requests - Host Not Found"
    ::= { affirmedServicesContentHttpProxyServiceStatisticsNode-levelFailureEntry 9 }

affirmedServicesContentHttpProxyServiceStatisticsNode-levelFailureNuminvalidclientrequestsnotsupported OBJECT-TYPE
    SYNTAX      ConfdString
    MAX-ACCESS  read-only
    STATUS      current
    DESCRIPTION "Total number of invalid client requests - Not Supported"
    ::= { affirmedServicesContentHttpProxyServiceStatisticsNode-levelFailureEntry 10 }

affirmedServicesContentHttpProxyServiceStatisticsNode-levelFailureNuminvalidclientrequestsexpectheadererror OBJECT-TYPE
    SYNTAX      ConfdString
    MAX-ACCESS  read-only
    STATUS      current
    DESCRIPTION "Total number of invalid client requests - Expect Header Error"
    ::= { affirmedServicesContentHttpProxyServiceStatisticsNode-levelFailureEntry 11 }

affirmedServicesContentHttpProxyServiceStatisticsNode-levelFailureNuminvalidclientrequestsbodyreaderror OBJECT-TYPE
    SYNTAX      ConfdString
    MAX-ACCESS  read-only
    STATUS      current
    DESCRIPTION "Total number of invalid client requests - Body Read Error"
    ::= { affirmedServicesContentHttpProxyServiceStatisticsNode-levelFailureEntry 12 }

affirmedServicesContentHttpProxyServiceStatisticsNode-levelFailureNuminvalidclientrequestsidletimeout OBJECT-TYPE
    SYNTAX      ConfdString
    MAX-ACCESS  read-only
    STATUS      current
    DESCRIPTION "Total number of invalid client requests - Idle Timeout"
    ::= { affirmedServicesContentHttpProxyServiceStatisticsNode-levelFailureEntry 13 }

affirmedServicesContentHttpProxyServiceStatisticsNode-levelFailureNumproxyservicefailedrequestcompileerror OBJECT-TYPE
    SYNTAX      ConfdString
    MAX-ACCESS  read-only
    STATUS      current
    DESCRIPTION "Total number of proxy service failed - Request Compile Error"
    ::= { affirmedServicesContentHttpProxyServiceStatisticsNode-levelFailureEntry 14 }

affirmedServicesContentHttpProxyServiceStatisticsNode-levelFailureNumproxyservicefailedconnectioninitfailure OBJECT-TYPE
    SYNTAX      ConfdString
    MAX-ACCESS  read-only
    STATUS      current
    DESCRIPTION "Total number of proxy service failed - Connection Init Failure"
    ::= { affirmedServicesContentHttpProxyServiceStatisticsNode-levelFailureEntry 15 }

affirmedServicesContentHttpProxyServiceStatisticsNode-levelFailureNumproxyservicefailedoversizedresponseheader OBJECT-TYPE
    SYNTAX      ConfdString
    MAX-ACCESS  read-only
    STATUS      current
    DESCRIPTION "Total number of proxy service failed- Oversized Response Header"
    ::= { affirmedServicesContentHttpProxyServiceStatisticsNode-levelFailureEntry 16 }

affirmedServicesContentHttpProxyServiceStatisticsNode-levelFailureNumproxyservicefailedbadresponsestatusline OBJECT-TYPE
    SYNTAX      ConfdString
    MAX-ACCESS  read-only
    STATUS      current
    DESCRIPTION "Total number of proxy service failed - Bad Response Status Line"
    ::= { affirmedServicesContentHttpProxyServiceStatisticsNode-levelFailureEntry 17 }

affirmedServicesContentHttpProxyServiceStatisticsNode-levelFailureNumproxyservicefailedbadresponseheader OBJECT-TYPE
    SYNTAX      ConfdString
    MAX-ACCESS  read-only
    STATUS      current
    DESCRIPTION "Total number of proxy service failed - Bad Response Header"
    ::= { affirmedServicesContentHttpProxyServiceStatisticsNode-levelFailureEntry 18 }

affirmedServicesContentHttpProxyServiceStatisticsNode-levelFailureNumproxyservicefailedresponseprocessingfailure OBJECT-TYPE
    SYNTAX      ConfdString
    MAX-ACCESS  read-only
    STATUS      current
    DESCRIPTION "Total number of proxy service failed - Response Processing Failure"
    ::= { affirmedServicesContentHttpProxyServiceStatisticsNode-levelFailureEntry 19 }

affirmedServicesContentHttpProxyServiceStatisticsNode-levelFailureNumproxyservicefailedserverconnectionclose OBJECT-TYPE
    SYNTAX      ConfdString
    MAX-ACCESS  read-only
    STATUS      current
    DESCRIPTION "Total number of proxy service failed - Server Connection Close"
    ::= { affirmedServicesContentHttpProxyServiceStatisticsNode-levelFailureEntry 20 }

affirmedServicesContentHttpProxyServiceStatisticsNode-levelFailureNumproxyservicefailedserverconnectiontimeout OBJECT-TYPE
    SYNTAX      ConfdString
    MAX-ACCESS  read-only
    STATUS      current
    DESCRIPTION "Total number of proxy service failed - Server Connection Timeout"
    ::= { affirmedServicesContentHttpProxyServiceStatisticsNode-levelFailureEntry 21 }

affirmedServicesContentHttpProxyServiceStatisticsNode-levelFailureNumproxyservicefailedclientconnectiontimeout OBJECT-TYPE
    SYNTAX      ConfdString
    MAX-ACCESS  read-only
    STATUS      current
    DESCRIPTION "Total number of proxy service failed - Client Connection Timeout"
    ::= { affirmedServicesContentHttpProxyServiceStatisticsNode-levelFailureEntry 22 }

affirmedServicesContentHttpProxyServiceStatisticsNode-levelFailureNumproxyservicefailedresourceunavailable OBJECT-TYPE
    SYNTAX      ConfdString
    MAX-ACCESS  read-only
    STATUS      current
    DESCRIPTION "Total number of proxy service failed - Resources unavailable"
    ::= { affirmedServicesContentHttpProxyServiceStatisticsNode-levelFailureEntry 23 }

affirmedServicesContentHttpProxyServiceStatisticsNode-levelFailureNumproxyserviceredirected OBJECT-TYPE
    SYNTAX      ConfdString
    MAX-ACCESS  read-only
    STATUS      current
    DESCRIPTION "Total number of proxy service failed - Requests redirected"
    ::= { affirmedServicesContentHttpProxyServiceStatisticsNode-levelFailureEntry 24 }

affirmedServicesContentHttpProxyServiceStatisticsNode-levelFailureNumproxyserviceblocked OBJECT-TYPE
    SYNTAX      ConfdString
    MAX-ACCESS  read-only
    STATUS      current
    DESCRIPTION "Total number of proxy service failed - Requests blocked"
    ::= { affirmedServicesContentHttpProxyServiceStatisticsNode-levelFailureEntry 25 }

affirmedServicesContentHttpProxyServiceStatisticsNode-levelFailureNumcacheservicefailedresponsereaderror OBJECT-TYPE
    SYNTAX      ConfdString
    MAX-ACCESS  read-only
    STATUS      current
    DESCRIPTION "Total number of cache service failed - Response Read Error"
    ::= { affirmedServicesContentHttpProxyServiceStatisticsNode-levelFailureEntry 26 }

affirmedServicesContentHttpProxyServiceStatisticsNode-levelFailureNumcacheservicefailedresponseheaderprocessing OBJECT-TYPE
    SYNTAX      ConfdString
    MAX-ACCESS  read-only
    STATUS      current
    DESCRIPTION "Total number of cache service failed - Response Header Processing Failure"
    ::= { affirmedServicesContentHttpProxyServiceStatisticsNode-levelFailureEntry 27 }

affirmedServicesContentHttpProxyServiceStatisticsNode-levelFailureNumcacheservicefailedresponseoversizedheader OBJECT-TYPE
    SYNTAX      ConfdString
    MAX-ACCESS  read-only
    STATUS      current
    DESCRIPTION "Total number of cache service failed - Response Header Oversized"
    ::= { affirmedServicesContentHttpProxyServiceStatisticsNode-levelFailureEntry 28 }

affirmedServicesContentHttpProxyServiceStatisticsNode-levelFailureNumcacheservicefailedservervalidationfailures OBJECT-TYPE
    SYNTAX      ConfdString
    MAX-ACCESS  read-only
    STATUS      current
    DESCRIPTION "Total number of cache service failed - Server Validation Failures"
    ::= { affirmedServicesContentHttpProxyServiceStatisticsNode-levelFailureEntry 29 }

affirmedServicesContentHttpProxyServiceStatisticsNode-levelFailureNumcacheservicefailedmaintenanceconnectionclose OBJECT-TYPE
    SYNTAX      ConfdString
    MAX-ACCESS  read-only
    STATUS      current
    DESCRIPTION "Total number of cache service failed - Maintenance Connection Close"
    ::= { affirmedServicesContentHttpProxyServiceStatisticsNode-levelFailureEntry 30 }

affirmedServicesContentHttpProxyServiceStatisticsNode-levelFailureNumproxyservicefailedmaintenanceconnectionclose OBJECT-TYPE
    SYNTAX      ConfdString
    MAX-ACCESS  read-only
    STATUS      current
    DESCRIPTION "Total number of proxy service failed - Maintenance Connection Close"
    ::= { affirmedServicesContentHttpProxyServiceStatisticsNode-levelFailureEntry 31 }

affirmedServicesContentHttpProxyServiceStatisticsNode-levelFailureNumproxyserviceabortedbyclient OBJECT-TYPE
    SYNTAX      ConfdString
    MAX-ACCESS  read-only
    STATUS      current
    DESCRIPTION "Total number of proxy service aborted - Client Disconnected"
    ::= { affirmedServicesContentHttpProxyServiceStatisticsNode-levelFailureEntry 32 }

affirmedServicesContentHttpProxyServiceStatisticsNode-levelFailureNumproxyserviceabortednorespfromserver OBJECT-TYPE
    SYNTAX      ConfdString
    MAX-ACCESS  read-only
    STATUS      current
    DESCRIPTION "Total number of proxy service aborted - No Response from Server"
    ::= { affirmedServicesContentHttpProxyServiceStatisticsNode-levelFailureEntry 33 }

affirmedServicesContentHttpProxyServiceStatisticsNode-levelFailureNumproxyserviceabortedrequesttolocaladdr OBJECT-TYPE
    SYNTAX      ConfdString
    MAX-ACCESS  read-only
    STATUS      current
    DESCRIPTION "Total number of proxy service aborted - Request to Local Address"
    ::= { affirmedServicesContentHttpProxyServiceStatisticsNode-levelFailureEntry 34 }

affirmedServicesContentHttpProxyServiceStatisticsNode-levelFailureNumconnectionfailuresoverload OBJECT-TYPE
    SYNTAX      ConfdString
    MAX-ACCESS  read-only
    STATUS      current
    DESCRIPTION "Total number of client connection failures - Terminated due to Overload"
    ::= { affirmedServicesContentHttpProxyServiceStatisticsNode-levelFailureEntry 35 }

affirmedServicesContentHttpProxyServiceStatisticsNode-levelFailureNumconnectionfailuresinvalidmetadata OBJECT-TYPE
    SYNTAX      ConfdString
    MAX-ACCESS  read-only
    STATUS      current
    DESCRIPTION "Total number of client connection failures - Invalid Metadata"
    ::= { affirmedServicesContentHttpProxyServiceStatisticsNode-levelFailureEntry 36 }

affirmedServicesContentHttpProxyServiceStatisticsNode-levelFailureNumconnectionfailuresproxyisnotready OBJECT-TYPE
    SYNTAX      ConfdString
    MAX-ACCESS  read-only
    STATUS      current
    DESCRIPTION "Total number of client connection failures - Proxy is not Ready"
    ::= { affirmedServicesContentHttpProxyServiceStatisticsNode-levelFailureEntry 37 }

affirmedServicesContentHttpProxyServiceStatisticsNode-levelFailureNumproxyserviceoutofbuffer OBJECT-TYPE
    SYNTAX      ConfdString
    MAX-ACCESS  read-only
    STATUS      current
    DESCRIPTION "Total number of proxy service failed - Out of buffer"
    ::= { affirmedServicesContentHttpProxyServiceStatisticsNode-levelFailureEntry 38 }

affirmedServicesContentHttpProxyServiceStatisticsNode-levelFailureNumconnectionfailuresfdlimitexceeded OBJECT-TYPE
    SYNTAX      ConfdString
    MAX-ACCESS  read-only
    STATUS      current
    DESCRIPTION "Total number of client connection failures - FD limit exceeded"
    ::= { affirmedServicesContentHttpProxyServiceStatisticsNode-levelFailureEntry 39 }

affirmedServicesContentHttpProxyServiceStatisticsNode-levelFailureNumconnectionfailuresoutofresources OBJECT-TYPE
    SYNTAX      ConfdString
    MAX-ACCESS  read-only
    STATUS      current
    DESCRIPTION "Total number of client connection failures - Out of Resources"
    ::= { affirmedServicesContentHttpProxyServiceStatisticsNode-levelFailureEntry 40 }

affirmedServicesContentHttpProxyServiceStatisticsNode-levelRequestMethodTable OBJECT-TYPE
    SYNTAX      SEQUENCE OF AffirmedServicesContentHttpProxyServiceStatisticsNode-levelRequestMethodEntry
    MAX-ACCESS  not-accessible
    STATUS      current
    DESCRIPTION ""
    ::= { affirmedServicesContentHttpProxyServiceStatisticsNode-level 6 }

affirmedServicesContentHttpProxyServiceStatisticsNode-levelRequestMethodEntry OBJECT-TYPE
    SYNTAX      AffirmedServicesContentHttpProxyServiceStatisticsNode-levelRequestMethodEntry
    MAX-ACCESS  not-accessible
    STATUS      current
    DESCRIPTION ""
    INDEX { affirmedServicesContentHttpProxyServiceStatisticsNode-levelRequestMethodChassis, affirmedServicesContentHttpProxyServiceStatisticsNode-levelRequestMethodSlot }
        ::= { affirmedServicesContentHttpProxyServiceStatisticsNode-levelRequestMethodTable 1 }

AffirmedServicesContentHttpProxyServiceStatisticsNode-levelRequestMethodEntry ::=
    SEQUENCE {
        affirmedServicesContentHttpProxyServiceStatisticsNode-levelRequestMethodChassis Unsigned32,
        affirmedServicesContentHttpProxyServiceStatisticsNode-levelRequestMethodSlot INTEGER,
        affirmedServicesContentHttpProxyServiceStatisticsNode-levelRequestMethodMethodoptionsreceived ConfdString,
        affirmedServicesContentHttpProxyServiceStatisticsNode-levelRequestMethodMethodoptionsaborted ConfdString,
        affirmedServicesContentHttpProxyServiceStatisticsNode-levelRequestMethodMethodgetreceived ConfdString,
        affirmedServicesContentHttpProxyServiceStatisticsNode-levelRequestMethodMethodgetaborted ConfdString,
        affirmedServicesContentHttpProxyServiceStatisticsNode-levelRequestMethodMethodheadreceived ConfdString,
        affirmedServicesContentHttpProxyServiceStatisticsNode-levelRequestMethodMethodheadaborted ConfdString,
        affirmedServicesContentHttpProxyServiceStatisticsNode-levelRequestMethodMethodpostreceived ConfdString,
        affirmedServicesContentHttpProxyServiceStatisticsNode-levelRequestMethodMethodpostaborted ConfdString,
        affirmedServicesContentHttpProxyServiceStatisticsNode-levelRequestMethodMethodputreceived ConfdString,
        affirmedServicesContentHttpProxyServiceStatisticsNode-levelRequestMethodMethodputaborted ConfdString,
        affirmedServicesContentHttpProxyServiceStatisticsNode-levelRequestMethodMethoddeletereceived ConfdString,
        affirmedServicesContentHttpProxyServiceStatisticsNode-levelRequestMethodMethoddeleteaborted ConfdString,
        affirmedServicesContentHttpProxyServiceStatisticsNode-levelRequestMethodMethodtracereceived ConfdString,
        affirmedServicesContentHttpProxyServiceStatisticsNode-levelRequestMethodMethodtraceaborted ConfdString,
        affirmedServicesContentHttpProxyServiceStatisticsNode-levelRequestMethodMethodconnectreceived ConfdString,
        affirmedServicesContentHttpProxyServiceStatisticsNode-levelRequestMethodMethodconnectaborted ConfdString,
        affirmedServicesContentHttpProxyServiceStatisticsNode-levelRequestMethodMethodmkcolreceived ConfdString,
        affirmedServicesContentHttpProxyServiceStatisticsNode-levelRequestMethodMethodmkcolaborted ConfdString,
        affirmedServicesContentHttpProxyServiceStatisticsNode-levelRequestMethodMethodcopyreceived ConfdString,
        affirmedServicesContentHttpProxyServiceStatisticsNode-levelRequestMethodMethodcopyaborted ConfdString,
        affirmedServicesContentHttpProxyServiceStatisticsNode-levelRequestMethodMethodmovereceived ConfdString,
        affirmedServicesContentHttpProxyServiceStatisticsNode-levelRequestMethodMethodmoveaborted ConfdString,
        affirmedServicesContentHttpProxyServiceStatisticsNode-levelRequestMethodMethodpropfindreceived ConfdString,
        affirmedServicesContentHttpProxyServiceStatisticsNode-levelRequestMethodMethodpropfindaborted ConfdString,
        affirmedServicesContentHttpProxyServiceStatisticsNode-levelRequestMethodMethodproppatchreceived ConfdString,
        affirmedServicesContentHttpProxyServiceStatisticsNode-levelRequestMethodMethodproppatchaborted ConfdString,
        affirmedServicesContentHttpProxyServiceStatisticsNode-levelRequestMethodMethodlockreceived ConfdString,
        affirmedServicesContentHttpProxyServiceStatisticsNode-levelRequestMethodMethodlockaborted ConfdString,
        affirmedServicesContentHttpProxyServiceStatisticsNode-levelRequestMethodMethodunlockreceived ConfdString,
        affirmedServicesContentHttpProxyServiceStatisticsNode-levelRequestMethodMethodunlockaborted ConfdString,
        affirmedServicesContentHttpProxyServiceStatisticsNode-levelRequestMethodMethodpatchreceived ConfdString,
        affirmedServicesContentHttpProxyServiceStatisticsNode-levelRequestMethodMethodpatchaborted ConfdString,
        affirmedServicesContentHttpProxyServiceStatisticsNode-levelRequestMethodUnknownmethodreceived ConfdString,
        affirmedServicesContentHttpProxyServiceStatisticsNode-levelRequestMethodUnknownmethodaborted ConfdString,
        affirmedServicesContentHttpProxyServiceStatisticsNode-levelRequestMethodMethodaclreceived ConfdString,
        affirmedServicesContentHttpProxyServiceStatisticsNode-levelRequestMethodMethodaclaborted ConfdString,
        affirmedServicesContentHttpProxyServiceStatisticsNode-levelRequestMethodMethodbaselinecontrolreceived ConfdString,
        affirmedServicesContentHttpProxyServiceStatisticsNode-levelRequestMethodMethodbaselinecontrolaborted ConfdString,
        affirmedServicesContentHttpProxyServiceStatisticsNode-levelRequestMethodMethodbindreceived ConfdString,
        affirmedServicesContentHttpProxyServiceStatisticsNode-levelRequestMethodMethodbindaborted ConfdString,
        affirmedServicesContentHttpProxyServiceStatisticsNode-levelRequestMethodMethodcheckinreceived ConfdString,
        affirmedServicesContentHttpProxyServiceStatisticsNode-levelRequestMethodMethodcheckinaborted ConfdString,
        affirmedServicesContentHttpProxyServiceStatisticsNode-levelRequestMethodMethodcheckoutreceived ConfdString,
        affirmedServicesContentHttpProxyServiceStatisticsNode-levelRequestMethodMethodcheckoutaborted ConfdString,
        affirmedServicesContentHttpProxyServiceStatisticsNode-levelRequestMethodMethodlabelreceived ConfdString,
        affirmedServicesContentHttpProxyServiceStatisticsNode-levelRequestMethodMethodlabelaborted ConfdString,
        affirmedServicesContentHttpProxyServiceStatisticsNode-levelRequestMethodMethodlinkreceived ConfdString,
        affirmedServicesContentHttpProxyServiceStatisticsNode-levelRequestMethodMethodlinkaborted ConfdString,
        affirmedServicesContentHttpProxyServiceStatisticsNode-levelRequestMethodMethodmergereceived ConfdString,
        affirmedServicesContentHttpProxyServiceStatisticsNode-levelRequestMethodMethodmergeaborted ConfdString,
        affirmedServicesContentHttpProxyServiceStatisticsNode-levelRequestMethodMethodmkactivityreceived ConfdString,
        affirmedServicesContentHttpProxyServiceStatisticsNode-levelRequestMethodMethodmkactivityaborted ConfdString,
        affirmedServicesContentHttpProxyServiceStatisticsNode-levelRequestMethodMethodmkcalendarreceived ConfdString,
        affirmedServicesContentHttpProxyServiceStatisticsNode-levelRequestMethodMethodmkcalendaraborted ConfdString,
        affirmedServicesContentHttpProxyServiceStatisticsNode-levelRequestMethodMethodmkredirectrefreceived ConfdString,
        affirmedServicesContentHttpProxyServiceStatisticsNode-levelRequestMethodMethodmkredirectrefaborted ConfdString,
        affirmedServicesContentHttpProxyServiceStatisticsNode-levelRequestMethodMethodmkworkspacereceived ConfdString,
        affirmedServicesContentHttpProxyServiceStatisticsNode-levelRequestMethodMethodmkworkspaceaborted ConfdString,
        affirmedServicesContentHttpProxyServiceStatisticsNode-levelRequestMethodMethodorderpatchreceived ConfdString,
        affirmedServicesContentHttpProxyServiceStatisticsNode-levelRequestMethodMethodorderpatchaborted ConfdString,
        affirmedServicesContentHttpProxyServiceStatisticsNode-levelRequestMethodMethodprireceived ConfdString,
        affirmedServicesContentHttpProxyServiceStatisticsNode-levelRequestMethodMethodpriaborted ConfdString,
        affirmedServicesContentHttpProxyServiceStatisticsNode-levelRequestMethodMethodrebindreceived ConfdString,
        affirmedServicesContentHttpProxyServiceStatisticsNode-levelRequestMethodMethodrebindaborted ConfdString,
        affirmedServicesContentHttpProxyServiceStatisticsNode-levelRequestMethodMethodreportreceived ConfdString,
        affirmedServicesContentHttpProxyServiceStatisticsNode-levelRequestMethodMethodreportaborted ConfdString,
        affirmedServicesContentHttpProxyServiceStatisticsNode-levelRequestMethodMethodsearchreceived ConfdString,
        affirmedServicesContentHttpProxyServiceStatisticsNode-levelRequestMethodMethodsearchaborted ConfdString,
        affirmedServicesContentHttpProxyServiceStatisticsNode-levelRequestMethodMethodunbindreceived ConfdString,
        affirmedServicesContentHttpProxyServiceStatisticsNode-levelRequestMethodMethodunbindaborted ConfdString,
        affirmedServicesContentHttpProxyServiceStatisticsNode-levelRequestMethodMethoduncheckoutreceived ConfdString,
        affirmedServicesContentHttpProxyServiceStatisticsNode-levelRequestMethodMethoduncheckoutaborted ConfdString,
        affirmedServicesContentHttpProxyServiceStatisticsNode-levelRequestMethodMethodunlinkreceived ConfdString,
        affirmedServicesContentHttpProxyServiceStatisticsNode-levelRequestMethodMethodunlinkaborted ConfdString,
        affirmedServicesContentHttpProxyServiceStatisticsNode-levelRequestMethodMethodupdatereceived ConfdString,
        affirmedServicesContentHttpProxyServiceStatisticsNode-levelRequestMethodMethodupdateaborted ConfdString,
        affirmedServicesContentHttpProxyServiceStatisticsNode-levelRequestMethodMethodupdateredirectrefreceived ConfdString,
        affirmedServicesContentHttpProxyServiceStatisticsNode-levelRequestMethodMethodupdateredirectrefaborted ConfdString,
        affirmedServicesContentHttpProxyServiceStatisticsNode-levelRequestMethodMethodversioncontrolreceived ConfdString,
        affirmedServicesContentHttpProxyServiceStatisticsNode-levelRequestMethodMethodversioncontrolaborted ConfdString,
        affirmedServicesContentHttpProxyServiceStatisticsNode-levelRequestMethodUnsupportedmethodreceived ConfdString
    }

affirmedServicesContentHttpProxyServiceStatisticsNode-levelRequestMethodChassis OBJECT-TYPE
    SYNTAX      Unsigned32
    MAX-ACCESS  not-accessible
    STATUS      current
    DESCRIPTION "chassis ID"
    ::= { affirmedServicesContentHttpProxyServiceStatisticsNode-levelRequestMethodEntry 1 }

affirmedServicesContentHttpProxyServiceStatisticsNode-levelRequestMethodSlot OBJECT-TYPE
    SYNTAX      INTEGER {a1(1),a2(2),a3(3),a4(4),a5(5),a6(6),a7(7),a8(8),a9(9),a10(10),a11(11),a12(12),a13(13),a14(14),a15(15),a16(16),a17(17),a18(18),a19(19),a20(20),a21(21),a22(22),a23(23),a24(24),a25(25),a26(26),a27(27),a28(28),a29(29),a30(30),a31(31),a32(32),a33(33),a34(34),a35(35),a36(36),a37(37),a38(38),a39(39),a40(40),a41(41),a42(42),a43(43),a44(44),a45(45),a46(46),a47(47),a48(48),a49(49),a50(50),a51(51),a52(52),a53(53),a54(54),a55(55),a56(56),a57(57),a58(58),a59(59),a60(60),a61(61),a62(62),a63(63),a64(64),a65(65),a66(66),a67(67),a68(68),a69(69),a70(70),a71(71),a72(72),a73(73),a74(74),a75(75),a76(76),a77(77),a78(78),a79(79),a80(80),a81(81),a82(82),a83(83),a84(84),a85(85),a86(86),a87(87),a88(88),a89(89),a90(90),a91(91),a92(92),a93(93),a94(94),a95(95),a96(96),a97(97),a98(98),a99(99),a100(100),a101(101),a102(102),a103(103),a104(104),a105(105),a106(106),a107(107),a108(108),a109(109),a110(110),a111(111),a112(112),a113(113),a114(114),a115(115),a116(116),a117(117),a118(118),a119(119),a120(120),a121(121),a122(122),a123(123),a124(124),a125(125),a126(126),a127(127),a128(128)}
    MAX-ACCESS  not-accessible
    STATUS      current
    DESCRIPTION "slot number"
    ::= { affirmedServicesContentHttpProxyServiceStatisticsNode-levelRequestMethodEntry 2 }

affirmedServicesContentHttpProxyServiceStatisticsNode-levelRequestMethodMethodoptionsreceived OBJECT-TYPE
    SYNTAX      ConfdString
    MAX-ACCESS  read-only
    STATUS      current
    DESCRIPTION "Total number of OPTIONS request received"
    ::= { affirmedServicesContentHttpProxyServiceStatisticsNode-levelRequestMethodEntry 3 }

affirmedServicesContentHttpProxyServiceStatisticsNode-levelRequestMethodMethodoptionsaborted OBJECT-TYPE
    SYNTAX      ConfdString
    MAX-ACCESS  read-only
    STATUS      current
    DESCRIPTION "Total number of OPTIONS request aborted/failed"
    ::= { affirmedServicesContentHttpProxyServiceStatisticsNode-levelRequestMethodEntry 4 }

affirmedServicesContentHttpProxyServiceStatisticsNode-levelRequestMethodMethodgetreceived OBJECT-TYPE
    SYNTAX      ConfdString
    MAX-ACCESS  read-only
    STATUS      current
    DESCRIPTION "Total number of GET request received"
    ::= { affirmedServicesContentHttpProxyServiceStatisticsNode-levelRequestMethodEntry 5 }

affirmedServicesContentHttpProxyServiceStatisticsNode-levelRequestMethodMethodgetaborted OBJECT-TYPE
    SYNTAX      ConfdString
    MAX-ACCESS  read-only
    STATUS      current
    DESCRIPTION "Total number of GET request aborted/failed"
    ::= { affirmedServicesContentHttpProxyServiceStatisticsNode-levelRequestMethodEntry 6 }

affirmedServicesContentHttpProxyServiceStatisticsNode-levelRequestMethodMethodheadreceived OBJECT-TYPE
    SYNTAX      ConfdString
    MAX-ACCESS  read-only
    STATUS      current
    DESCRIPTION "Total number of HEAD request received"
    ::= { affirmedServicesContentHttpProxyServiceStatisticsNode-levelRequestMethodEntry 7 }

affirmedServicesContentHttpProxyServiceStatisticsNode-levelRequestMethodMethodheadaborted OBJECT-TYPE
    SYNTAX      ConfdString
    MAX-ACCESS  read-only
    STATUS      current
    DESCRIPTION "Total number of HEAD request aborted/failed"
    ::= { affirmedServicesContentHttpProxyServiceStatisticsNode-levelRequestMethodEntry 8 }

affirmedServicesContentHttpProxyServiceStatisticsNode-levelRequestMethodMethodpostreceived OBJECT-TYPE
    SYNTAX      ConfdString
    MAX-ACCESS  read-only
    STATUS      current
    DESCRIPTION "Total number of POST request received"
    ::= { affirmedServicesContentHttpProxyServiceStatisticsNode-levelRequestMethodEntry 9 }

affirmedServicesContentHttpProxyServiceStatisticsNode-levelRequestMethodMethodpostaborted OBJECT-TYPE
    SYNTAX      ConfdString
    MAX-ACCESS  read-only
    STATUS      current
    DESCRIPTION "Total number of POST request aborted/failed"
    ::= { affirmedServicesContentHttpProxyServiceStatisticsNode-levelRequestMethodEntry 10 }

affirmedServicesContentHttpProxyServiceStatisticsNode-levelRequestMethodMethodputreceived OBJECT-TYPE
    SYNTAX      ConfdString
    MAX-ACCESS  read-only
    STATUS      current
    DESCRIPTION "Total number of PUT request received"
    ::= { affirmedServicesContentHttpProxyServiceStatisticsNode-levelRequestMethodEntry 11 }

affirmedServicesContentHttpProxyServiceStatisticsNode-levelRequestMethodMethodputaborted OBJECT-TYPE
    SYNTAX      ConfdString
    MAX-ACCESS  read-only
    STATUS      current
    DESCRIPTION "Total number of PUT request aborted/failed"
    ::= { affirmedServicesContentHttpProxyServiceStatisticsNode-levelRequestMethodEntry 12 }

affirmedServicesContentHttpProxyServiceStatisticsNode-levelRequestMethodMethoddeletereceived OBJECT-TYPE
    SYNTAX      ConfdString
    MAX-ACCESS  read-only
    STATUS      current
    DESCRIPTION "Total number of DELETE request received"
    ::= { affirmedServicesContentHttpProxyServiceStatisticsNode-levelRequestMethodEntry 13 }

affirmedServicesContentHttpProxyServiceStatisticsNode-levelRequestMethodMethoddeleteaborted OBJECT-TYPE
    SYNTAX      ConfdString
    MAX-ACCESS  read-only
    STATUS      current
    DESCRIPTION "Total number of DELETE request aborted/failed"
    ::= { affirmedServicesContentHttpProxyServiceStatisticsNode-levelRequestMethodEntry 14 }

affirmedServicesContentHttpProxyServiceStatisticsNode-levelRequestMethodMethodtracereceived OBJECT-TYPE
    SYNTAX      ConfdString
    MAX-ACCESS  read-only
    STATUS      current
    DESCRIPTION "Total number of TRACE request received"
    ::= { affirmedServicesContentHttpProxyServiceStatisticsNode-levelRequestMethodEntry 15 }

affirmedServicesContentHttpProxyServiceStatisticsNode-levelRequestMethodMethodtraceaborted OBJECT-TYPE
    SYNTAX      ConfdString
    MAX-ACCESS  read-only
    STATUS      current
    DESCRIPTION "Total number of TRACE request aborted/failed"
    ::= { affirmedServicesContentHttpProxyServiceStatisticsNode-levelRequestMethodEntry 16 }

affirmedServicesContentHttpProxyServiceStatisticsNode-levelRequestMethodMethodconnectreceived OBJECT-TYPE
    SYNTAX      ConfdString
    MAX-ACCESS  read-only
    STATUS      current
    DESCRIPTION "Total number of CONNECT request received"
    ::= { affirmedServicesContentHttpProxyServiceStatisticsNode-levelRequestMethodEntry 17 }

affirmedServicesContentHttpProxyServiceStatisticsNode-levelRequestMethodMethodconnectaborted OBJECT-TYPE
    SYNTAX      ConfdString
    MAX-ACCESS  read-only
    STATUS      current
    DESCRIPTION "Total number of CONNECT request aborted/failed"
    ::= { affirmedServicesContentHttpProxyServiceStatisticsNode-levelRequestMethodEntry 18 }

affirmedServicesContentHttpProxyServiceStatisticsNode-levelRequestMethodMethodmkcolreceived OBJECT-TYPE
    SYNTAX      ConfdString
    MAX-ACCESS  read-only
    STATUS      current
    DESCRIPTION "Total number of MKCOL request received"
    ::= { affirmedServicesContentHttpProxyServiceStatisticsNode-levelRequestMethodEntry 19 }

affirmedServicesContentHttpProxyServiceStatisticsNode-levelRequestMethodMethodmkcolaborted OBJECT-TYPE
    SYNTAX      ConfdString
    MAX-ACCESS  read-only
    STATUS      current
    DESCRIPTION "Total number of MKCOL request aborted/failed"
    ::= { affirmedServicesContentHttpProxyServiceStatisticsNode-levelRequestMethodEntry 20 }

affirmedServicesContentHttpProxyServiceStatisticsNode-levelRequestMethodMethodcopyreceived OBJECT-TYPE
    SYNTAX      ConfdString
    MAX-ACCESS  read-only
    STATUS      current
    DESCRIPTION "Total number of COPY request received"
    ::= { affirmedServicesContentHttpProxyServiceStatisticsNode-levelRequestMethodEntry 21 }

affirmedServicesContentHttpProxyServiceStatisticsNode-levelRequestMethodMethodcopyaborted OBJECT-TYPE
    SYNTAX      ConfdString
    MAX-ACCESS  read-only
    STATUS      current
    DESCRIPTION "Total number of COPY request aborted/failed"
    ::= { affirmedServicesContentHttpProxyServiceStatisticsNode-levelRequestMethodEntry 22 }

affirmedServicesContentHttpProxyServiceStatisticsNode-levelRequestMethodMethodmovereceived OBJECT-TYPE
    SYNTAX      ConfdString
    MAX-ACCESS  read-only
    STATUS      current
    DESCRIPTION "Total number of MOVE request received"
    ::= { affirmedServicesContentHttpProxyServiceStatisticsNode-levelRequestMethodEntry 23 }

affirmedServicesContentHttpProxyServiceStatisticsNode-levelRequestMethodMethodmoveaborted OBJECT-TYPE
    SYNTAX      ConfdString
    MAX-ACCESS  read-only
    STATUS      current
    DESCRIPTION "Total number of MOVE request aborted/failed"
    ::= { affirmedServicesContentHttpProxyServiceStatisticsNode-levelRequestMethodEntry 24 }

affirmedServicesContentHttpProxyServiceStatisticsNode-levelRequestMethodMethodpropfindreceived OBJECT-TYPE
    SYNTAX      ConfdString
    MAX-ACCESS  read-only
    STATUS      current
    DESCRIPTION "Total number of PROPFIND request received"
    ::= { affirmedServicesContentHttpProxyServiceStatisticsNode-levelRequestMethodEntry 25 }

affirmedServicesContentHttpProxyServiceStatisticsNode-levelRequestMethodMethodpropfindaborted OBJECT-TYPE
    SYNTAX      ConfdString
    MAX-ACCESS  read-only
    STATUS      current
    DESCRIPTION "Total number of PROPFIND request aborted/failed"
    ::= { affirmedServicesContentHttpProxyServiceStatisticsNode-levelRequestMethodEntry 26 }

affirmedServicesContentHttpProxyServiceStatisticsNode-levelRequestMethodMethodproppatchreceived OBJECT-TYPE
    SYNTAX      ConfdString
    MAX-ACCESS  read-only
    STATUS      current
    DESCRIPTION "Total number of PROPPATCH request received"
    ::= { affirmedServicesContentHttpProxyServiceStatisticsNode-levelRequestMethodEntry 27 }

affirmedServicesContentHttpProxyServiceStatisticsNode-levelRequestMethodMethodproppatchaborted OBJECT-TYPE
    SYNTAX      ConfdString
    MAX-ACCESS  read-only
    STATUS      current
    DESCRIPTION "Total number of PROPPATCH request aborted/failed"
    ::= { affirmedServicesContentHttpProxyServiceStatisticsNode-levelRequestMethodEntry 28 }

affirmedServicesContentHttpProxyServiceStatisticsNode-levelRequestMethodMethodlockreceived OBJECT-TYPE
    SYNTAX      ConfdString
    MAX-ACCESS  read-only
    STATUS      current
    DESCRIPTION "Total number of LOCK request received"
    ::= { affirmedServicesContentHttpProxyServiceStatisticsNode-levelRequestMethodEntry 29 }

affirmedServicesContentHttpProxyServiceStatisticsNode-levelRequestMethodMethodlockaborted OBJECT-TYPE
    SYNTAX      ConfdString
    MAX-ACCESS  read-only
    STATUS      current
    DESCRIPTION "Total number of LOCK request aborted/failed"
    ::= { affirmedServicesContentHttpProxyServiceStatisticsNode-levelRequestMethodEntry 30 }

affirmedServicesContentHttpProxyServiceStatisticsNode-levelRequestMethodMethodunlockreceived OBJECT-TYPE
    SYNTAX      ConfdString
    MAX-ACCESS  read-only
    STATUS      current
    DESCRIPTION "Total number of UNLOCK request received"
    ::= { affirmedServicesContentHttpProxyServiceStatisticsNode-levelRequestMethodEntry 31 }

affirmedServicesContentHttpProxyServiceStatisticsNode-levelRequestMethodMethodunlockaborted OBJECT-TYPE
    SYNTAX      ConfdString
    MAX-ACCESS  read-only
    STATUS      current
    DESCRIPTION "Total number of UNLOCK request aborted/failed"
    ::= { affirmedServicesContentHttpProxyServiceStatisticsNode-levelRequestMethodEntry 32 }

affirmedServicesContentHttpProxyServiceStatisticsNode-levelRequestMethodMethodpatchreceived OBJECT-TYPE
    SYNTAX      ConfdString
    MAX-ACCESS  read-only
    STATUS      current
    DESCRIPTION "Total number of PATCH request received"
    ::= { affirmedServicesContentHttpProxyServiceStatisticsNode-levelRequestMethodEntry 33 }

affirmedServicesContentHttpProxyServiceStatisticsNode-levelRequestMethodMethodpatchaborted OBJECT-TYPE
    SYNTAX      ConfdString
    MAX-ACCESS  read-only
    STATUS      current
    DESCRIPTION "Total number of PATCH request aborted/failed"
    ::= { affirmedServicesContentHttpProxyServiceStatisticsNode-levelRequestMethodEntry 34 }

affirmedServicesContentHttpProxyServiceStatisticsNode-levelRequestMethodUnknownmethodreceived OBJECT-TYPE
    SYNTAX      ConfdString
    MAX-ACCESS  read-only
    STATUS      current
    DESCRIPTION "Total number of Unknown-Method request received"
    ::= { affirmedServicesContentHttpProxyServiceStatisticsNode-levelRequestMethodEntry 35 }

affirmedServicesContentHttpProxyServiceStatisticsNode-levelRequestMethodUnknownmethodaborted OBJECT-TYPE
    SYNTAX      ConfdString
    MAX-ACCESS  read-only
    STATUS      current
    DESCRIPTION "Total number of Unknown-Method request aborted/failed"
    ::= { affirmedServicesContentHttpProxyServiceStatisticsNode-levelRequestMethodEntry 36 }

affirmedServicesContentHttpProxyServiceStatisticsNode-levelRequestMethodMethodaclreceived OBJECT-TYPE
    SYNTAX      ConfdString
    MAX-ACCESS  read-only
    STATUS      current
    DESCRIPTION "Total number of ACL request received"
    ::= { affirmedServicesContentHttpProxyServiceStatisticsNode-levelRequestMethodEntry 37 }

affirmedServicesContentHttpProxyServiceStatisticsNode-levelRequestMethodMethodaclaborted OBJECT-TYPE
    SYNTAX      ConfdString
    MAX-ACCESS  read-only
    STATUS      current
    DESCRIPTION "Total number of ACL request aborted/failed"
    ::= { affirmedServicesContentHttpProxyServiceStatisticsNode-levelRequestMethodEntry 38 }

affirmedServicesContentHttpProxyServiceStatisticsNode-levelRequestMethodMethodbaselinecontrolreceived OBJECT-TYPE
    SYNTAX      ConfdString
    MAX-ACCESS  read-only
    STATUS      current
    DESCRIPTION "Total number of BASELINE-CONTROL request received"
    ::= { affirmedServicesContentHttpProxyServiceStatisticsNode-levelRequestMethodEntry 39 }

affirmedServicesContentHttpProxyServiceStatisticsNode-levelRequestMethodMethodbaselinecontrolaborted OBJECT-TYPE
    SYNTAX      ConfdString
    MAX-ACCESS  read-only
    STATUS      current
    DESCRIPTION "Total number of BASELINE-CONTROL request aborted/failed"
    ::= { affirmedServicesContentHttpProxyServiceStatisticsNode-levelRequestMethodEntry 40 }

affirmedServicesContentHttpProxyServiceStatisticsNode-levelRequestMethodMethodbindreceived OBJECT-TYPE
    SYNTAX      ConfdString
    MAX-ACCESS  read-only
    STATUS      current
    DESCRIPTION "Total number of BIND request received"
    ::= { affirmedServicesContentHttpProxyServiceStatisticsNode-levelRequestMethodEntry 41 }

affirmedServicesContentHttpProxyServiceStatisticsNode-levelRequestMethodMethodbindaborted OBJECT-TYPE
    SYNTAX      ConfdString
    MAX-ACCESS  read-only
    STATUS      current
    DESCRIPTION "Total number of BIND request aborted/failed"
    ::= { affirmedServicesContentHttpProxyServiceStatisticsNode-levelRequestMethodEntry 42 }

affirmedServicesContentHttpProxyServiceStatisticsNode-levelRequestMethodMethodcheckinreceived OBJECT-TYPE
    SYNTAX      ConfdString
    MAX-ACCESS  read-only
    STATUS      current
    DESCRIPTION "Total number of CHECKIN request received"
    ::= { affirmedServicesContentHttpProxyServiceStatisticsNode-levelRequestMethodEntry 43 }

affirmedServicesContentHttpProxyServiceStatisticsNode-levelRequestMethodMethodcheckinaborted OBJECT-TYPE
    SYNTAX      ConfdString
    MAX-ACCESS  read-only
    STATUS      current
    DESCRIPTION "Total number of CHECKIN request aborted/failed"
    ::= { affirmedServicesContentHttpProxyServiceStatisticsNode-levelRequestMethodEntry 44 }

affirmedServicesContentHttpProxyServiceStatisticsNode-levelRequestMethodMethodcheckoutreceived OBJECT-TYPE
    SYNTAX      ConfdString
    MAX-ACCESS  read-only
    STATUS      current
    DESCRIPTION "Total number of CHECKOUT request received"
    ::= { affirmedServicesContentHttpProxyServiceStatisticsNode-levelRequestMethodEntry 45 }

affirmedServicesContentHttpProxyServiceStatisticsNode-levelRequestMethodMethodcheckoutaborted OBJECT-TYPE
    SYNTAX      ConfdString
    MAX-ACCESS  read-only
    STATUS      current
    DESCRIPTION "Total number of CHECKOUT request aborted/failed"
    ::= { affirmedServicesContentHttpProxyServiceStatisticsNode-levelRequestMethodEntry 46 }

affirmedServicesContentHttpProxyServiceStatisticsNode-levelRequestMethodMethodlabelreceived OBJECT-TYPE
    SYNTAX      ConfdString
    MAX-ACCESS  read-only
    STATUS      current
    DESCRIPTION "Total number of LABEL request received"
    ::= { affirmedServicesContentHttpProxyServiceStatisticsNode-levelRequestMethodEntry 47 }

affirmedServicesContentHttpProxyServiceStatisticsNode-levelRequestMethodMethodlabelaborted OBJECT-TYPE
    SYNTAX      ConfdString
    MAX-ACCESS  read-only
    STATUS      current
    DESCRIPTION "Total number of LABEL request aborted/failed"
    ::= { affirmedServicesContentHttpProxyServiceStatisticsNode-levelRequestMethodEntry 48 }

affirmedServicesContentHttpProxyServiceStatisticsNode-levelRequestMethodMethodlinkreceived OBJECT-TYPE
    SYNTAX      ConfdString
    MAX-ACCESS  read-only
    STATUS      current
    DESCRIPTION "Total number of LINK request received"
    ::= { affirmedServicesContentHttpProxyServiceStatisticsNode-levelRequestMethodEntry 49 }

affirmedServicesContentHttpProxyServiceStatisticsNode-levelRequestMethodMethodlinkaborted OBJECT-TYPE
    SYNTAX      ConfdString
    MAX-ACCESS  read-only
    STATUS      current
    DESCRIPTION "Total number of LINK request aborted/failed"
    ::= { affirmedServicesContentHttpProxyServiceStatisticsNode-levelRequestMethodEntry 50 }

affirmedServicesContentHttpProxyServiceStatisticsNode-levelRequestMethodMethodmergereceived OBJECT-TYPE
    SYNTAX      ConfdString
    MAX-ACCESS  read-only
    STATUS      current
    DESCRIPTION "Total number of MERGE request received"
    ::= { affirmedServicesContentHttpProxyServiceStatisticsNode-levelRequestMethodEntry 51 }

affirmedServicesContentHttpProxyServiceStatisticsNode-levelRequestMethodMethodmergeaborted OBJECT-TYPE
    SYNTAX      ConfdString
    MAX-ACCESS  read-only
    STATUS      current
    DESCRIPTION "Total number of MERGE request aborted/failed"
    ::= { affirmedServicesContentHttpProxyServiceStatisticsNode-levelRequestMethodEntry 52 }

affirmedServicesContentHttpProxyServiceStatisticsNode-levelRequestMethodMethodmkactivityreceived OBJECT-TYPE
    SYNTAX      ConfdString
    MAX-ACCESS  read-only
    STATUS      current
    DESCRIPTION "Total number of MKACTIVITY request received"
    ::= { affirmedServicesContentHttpProxyServiceStatisticsNode-levelRequestMethodEntry 53 }

affirmedServicesContentHttpProxyServiceStatisticsNode-levelRequestMethodMethodmkactivityaborted OBJECT-TYPE
    SYNTAX      ConfdString
    MAX-ACCESS  read-only
    STATUS      current
    DESCRIPTION "Total number of MKACTIVITY request aborted/failed"
    ::= { affirmedServicesContentHttpProxyServiceStatisticsNode-levelRequestMethodEntry 54 }

affirmedServicesContentHttpProxyServiceStatisticsNode-levelRequestMethodMethodmkcalendarreceived OBJECT-TYPE
    SYNTAX      ConfdString
    MAX-ACCESS  read-only
    STATUS      current
    DESCRIPTION "Total number of MKCALENDAR request received"
    ::= { affirmedServicesContentHttpProxyServiceStatisticsNode-levelRequestMethodEntry 55 }

affirmedServicesContentHttpProxyServiceStatisticsNode-levelRequestMethodMethodmkcalendaraborted OBJECT-TYPE
    SYNTAX      ConfdString
    MAX-ACCESS  read-only
    STATUS      current
    DESCRIPTION "Total number of MKCALENDAR request aborted/failed"
    ::= { affirmedServicesContentHttpProxyServiceStatisticsNode-levelRequestMethodEntry 56 }

affirmedServicesContentHttpProxyServiceStatisticsNode-levelRequestMethodMethodmkredirectrefreceived OBJECT-TYPE
    SYNTAX      ConfdString
    MAX-ACCESS  read-only
    STATUS      current
    DESCRIPTION "Total number of MKREDIRECTREF request received"
    ::= { affirmedServicesContentHttpProxyServiceStatisticsNode-levelRequestMethodEntry 57 }

affirmedServicesContentHttpProxyServiceStatisticsNode-levelRequestMethodMethodmkredirectrefaborted OBJECT-TYPE
    SYNTAX      ConfdString
    MAX-ACCESS  read-only
    STATUS      current
    DESCRIPTION "Total number of MKREDIRECTREF request aborted/failed"
    ::= { affirmedServicesContentHttpProxyServiceStatisticsNode-levelRequestMethodEntry 58 }

affirmedServicesContentHttpProxyServiceStatisticsNode-levelRequestMethodMethodmkworkspacereceived OBJECT-TYPE
    SYNTAX      ConfdString
    MAX-ACCESS  read-only
    STATUS      current
    DESCRIPTION "Total number of MKWORKSPACE request received"
    ::= { affirmedServicesContentHttpProxyServiceStatisticsNode-levelRequestMethodEntry 59 }

affirmedServicesContentHttpProxyServiceStatisticsNode-levelRequestMethodMethodmkworkspaceaborted OBJECT-TYPE
    SYNTAX      ConfdString
    MAX-ACCESS  read-only
    STATUS      current
    DESCRIPTION "Total number of MKWORKSPACE request aborted/failed"
    ::= { affirmedServicesContentHttpProxyServiceStatisticsNode-levelRequestMethodEntry 60 }

affirmedServicesContentHttpProxyServiceStatisticsNode-levelRequestMethodMethodorderpatchreceived OBJECT-TYPE
    SYNTAX      ConfdString
    MAX-ACCESS  read-only
    STATUS      current
    DESCRIPTION "Total number of ORDERPATCH request received"
    ::= { affirmedServicesContentHttpProxyServiceStatisticsNode-levelRequestMethodEntry 61 }

affirmedServicesContentHttpProxyServiceStatisticsNode-levelRequestMethodMethodorderpatchaborted OBJECT-TYPE
    SYNTAX      ConfdString
    MAX-ACCESS  read-only
    STATUS      current
    DESCRIPTION "Total number of ORDERPATCH request aborted/failed"
    ::= { affirmedServicesContentHttpProxyServiceStatisticsNode-levelRequestMethodEntry 62 }

affirmedServicesContentHttpProxyServiceStatisticsNode-levelRequestMethodMethodprireceived OBJECT-TYPE
    SYNTAX      ConfdString
    MAX-ACCESS  read-only
    STATUS      current
    DESCRIPTION "Total number of PRI request received"
    ::= { affirmedServicesContentHttpProxyServiceStatisticsNode-levelRequestMethodEntry 63 }

affirmedServicesContentHttpProxyServiceStatisticsNode-levelRequestMethodMethodpriaborted OBJECT-TYPE
    SYNTAX      ConfdString
    MAX-ACCESS  read-only
    STATUS      current
    DESCRIPTION "Total number of PRI request aborted/failed"
    ::= { affirmedServicesContentHttpProxyServiceStatisticsNode-levelRequestMethodEntry 64 }

affirmedServicesContentHttpProxyServiceStatisticsNode-levelRequestMethodMethodrebindreceived OBJECT-TYPE
    SYNTAX      ConfdString
    MAX-ACCESS  read-only
    STATUS      current
    DESCRIPTION "Total number of REBIND request received"
    ::= { affirmedServicesContentHttpProxyServiceStatisticsNode-levelRequestMethodEntry 65 }

affirmedServicesContentHttpProxyServiceStatisticsNode-levelRequestMethodMethodrebindaborted OBJECT-TYPE
    SYNTAX      ConfdString
    MAX-ACCESS  read-only
    STATUS      current
    DESCRIPTION "Total number of REBIND request aborted/failed"
    ::= { affirmedServicesContentHttpProxyServiceStatisticsNode-levelRequestMethodEntry 66 }

affirmedServicesContentHttpProxyServiceStatisticsNode-levelRequestMethodMethodreportreceived OBJECT-TYPE
    SYNTAX      ConfdString
    MAX-ACCESS  read-only
    STATUS      current
    DESCRIPTION "Total number of REPORT request received"
    ::= { affirmedServicesContentHttpProxyServiceStatisticsNode-levelRequestMethodEntry 67 }

affirmedServicesContentHttpProxyServiceStatisticsNode-levelRequestMethodMethodreportaborted OBJECT-TYPE
    SYNTAX      ConfdString
    MAX-ACCESS  read-only
    STATUS      current
    DESCRIPTION "Total number of REPORT request aborted/failed"
    ::= { affirmedServicesContentHttpProxyServiceStatisticsNode-levelRequestMethodEntry 68 }

affirmedServicesContentHttpProxyServiceStatisticsNode-levelRequestMethodMethodsearchreceived OBJECT-TYPE
    SYNTAX      ConfdString
    MAX-ACCESS  read-only
    STATUS      current
    DESCRIPTION "Total number of SEARCH request received"
    ::= { affirmedServicesContentHttpProxyServiceStatisticsNode-levelRequestMethodEntry 69 }

affirmedServicesContentHttpProxyServiceStatisticsNode-levelRequestMethodMethodsearchaborted OBJECT-TYPE
    SYNTAX      ConfdString
    MAX-ACCESS  read-only
    STATUS      current
    DESCRIPTION "Total number of SEARCH request aborted/failed"
    ::= { affirmedServicesContentHttpProxyServiceStatisticsNode-levelRequestMethodEntry 70 }

affirmedServicesContentHttpProxyServiceStatisticsNode-levelRequestMethodMethodunbindreceived OBJECT-TYPE
    SYNTAX      ConfdString
    MAX-ACCESS  read-only
    STATUS      current
    DESCRIPTION "Total number of UNBIND request received"
    ::= { affirmedServicesContentHttpProxyServiceStatisticsNode-levelRequestMethodEntry 71 }

affirmedServicesContentHttpProxyServiceStatisticsNode-levelRequestMethodMethodunbindaborted OBJECT-TYPE
    SYNTAX      ConfdString
    MAX-ACCESS  read-only
    STATUS      current
    DESCRIPTION "Total number of UNBIND request aborted/failed"
    ::= { affirmedServicesContentHttpProxyServiceStatisticsNode-levelRequestMethodEntry 72 }

affirmedServicesContentHttpProxyServiceStatisticsNode-levelRequestMethodMethoduncheckoutreceived OBJECT-TYPE
    SYNTAX      ConfdString
    MAX-ACCESS  read-only
    STATUS      current
    DESCRIPTION "Total number of UNCHECKOUT request received"
    ::= { affirmedServicesContentHttpProxyServiceStatisticsNode-levelRequestMethodEntry 73 }

affirmedServicesContentHttpProxyServiceStatisticsNode-levelRequestMethodMethoduncheckoutaborted OBJECT-TYPE
    SYNTAX      ConfdString
    MAX-ACCESS  read-only
    STATUS      current
    DESCRIPTION "Total number of UNCHECKOUT request aborted/failed"
    ::= { affirmedServicesContentHttpProxyServiceStatisticsNode-levelRequestMethodEntry 74 }

affirmedServicesContentHttpProxyServiceStatisticsNode-levelRequestMethodMethodunlinkreceived OBJECT-TYPE
    SYNTAX      ConfdString
    MAX-ACCESS  read-only
    STATUS      current
    DESCRIPTION "Total number of UNLINK request received"
    ::= { affirmedServicesContentHttpProxyServiceStatisticsNode-levelRequestMethodEntry 75 }

affirmedServicesContentHttpProxyServiceStatisticsNode-levelRequestMethodMethodunlinkaborted OBJECT-TYPE
    SYNTAX      ConfdString
    MAX-ACCESS  read-only
    STATUS      current
    DESCRIPTION "Total number of UNLINK request aborted/failed"
    ::= { affirmedServicesContentHttpProxyServiceStatisticsNode-levelRequestMethodEntry 76 }

affirmedServicesContentHttpProxyServiceStatisticsNode-levelRequestMethodMethodupdatereceived OBJECT-TYPE
    SYNTAX      ConfdString
    MAX-ACCESS  read-only
    STATUS      current
    DESCRIPTION "Total number of UPDATE request received"
    ::= { affirmedServicesContentHttpProxyServiceStatisticsNode-levelRequestMethodEntry 77 }

affirmedServicesContentHttpProxyServiceStatisticsNode-levelRequestMethodMethodupdateaborted OBJECT-TYPE
    SYNTAX      ConfdString
    MAX-ACCESS  read-only
    STATUS      current
    DESCRIPTION "Total number of UPDATE request aborted/failed"
    ::= { affirmedServicesContentHttpProxyServiceStatisticsNode-levelRequestMethodEntry 78 }

affirmedServicesContentHttpProxyServiceStatisticsNode-levelRequestMethodMethodupdateredirectrefreceived OBJECT-TYPE
    SYNTAX      ConfdString
    MAX-ACCESS  read-only
    STATUS      current
    DESCRIPTION "Total number of UPDATEREDIRECTREF request received"
    ::= { affirmedServicesContentHttpProxyServiceStatisticsNode-levelRequestMethodEntry 79 }

affirmedServicesContentHttpProxyServiceStatisticsNode-levelRequestMethodMethodupdateredirectrefaborted OBJECT-TYPE
    SYNTAX      ConfdString
    MAX-ACCESS  read-only
    STATUS      current
    DESCRIPTION "Total number of UPDATEREDIRECTREF request aborted/failed"
    ::= { affirmedServicesContentHttpProxyServiceStatisticsNode-levelRequestMethodEntry 80 }

affirmedServicesContentHttpProxyServiceStatisticsNode-levelRequestMethodMethodversioncontrolreceived OBJECT-TYPE
    SYNTAX      ConfdString
    MAX-ACCESS  read-only
    STATUS      current
    DESCRIPTION "Total number of VERSION-CONTROL request received"
    ::= { affirmedServicesContentHttpProxyServiceStatisticsNode-levelRequestMethodEntry 81 }

affirmedServicesContentHttpProxyServiceStatisticsNode-levelRequestMethodMethodversioncontrolaborted OBJECT-TYPE
    SYNTAX      ConfdString
    MAX-ACCESS  read-only
    STATUS      current
    DESCRIPTION "Total number of VERSION-CONTROL request aborted/failed"
    ::= { affirmedServicesContentHttpProxyServiceStatisticsNode-levelRequestMethodEntry 82 }

affirmedServicesContentHttpProxyServiceStatisticsNode-levelRequestMethodUnsupportedmethodreceived OBJECT-TYPE
    SYNTAX      ConfdString
    MAX-ACCESS  read-only
    STATUS      current
    DESCRIPTION "Total number of Unsupported-Method request received"
    ::= { affirmedServicesContentHttpProxyServiceStatisticsNode-levelRequestMethodEntry 83 }

affirmedServicesContentHttpProxyServiceStatisticsNode-levelOverloadControlTable OBJECT-TYPE
    SYNTAX      SEQUENCE OF AffirmedServicesContentHttpProxyServiceStatisticsNode-levelOverloadControlEntry
    MAX-ACCESS  not-accessible
    STATUS      current
    DESCRIPTION ""
    ::= { affirmedServicesContentHttpProxyServiceStatisticsNode-level 7 }

affirmedServicesContentHttpProxyServiceStatisticsNode-levelOverloadControlEntry OBJECT-TYPE
    SYNTAX      AffirmedServicesContentHttpProxyServiceStatisticsNode-levelOverloadControlEntry
    MAX-ACCESS  not-accessible
    STATUS      current
    DESCRIPTION ""
    INDEX { affirmedServicesContentHttpProxyServiceStatisticsNode-levelOverloadControlChassis, affirmedServicesContentHttpProxyServiceStatisticsNode-levelOverloadControlSlot }
        ::= { affirmedServicesContentHttpProxyServiceStatisticsNode-levelOverloadControlTable 1 }

AffirmedServicesContentHttpProxyServiceStatisticsNode-levelOverloadControlEntry ::=
    SEQUENCE {
        affirmedServicesContentHttpProxyServiceStatisticsNode-levelOverloadControlChassis Unsigned32,
        affirmedServicesContentHttpProxyServiceStatisticsNode-levelOverloadControlSlot INTEGER,
        affirmedServicesContentHttpProxyServiceStatisticsNode-levelOverloadControlNumconnectionacceptsoc ConfdString,
        affirmedServicesContentHttpProxyServiceStatisticsNode-levelOverloadControlNumconnectiondeniesoc ConfdString
    }

affirmedServicesContentHttpProxyServiceStatisticsNode-levelOverloadControlChassis OBJECT-TYPE
    SYNTAX      Unsigned32
    MAX-ACCESS  not-accessible
    STATUS      current
    DESCRIPTION "chassis ID"
    ::= { affirmedServicesContentHttpProxyServiceStatisticsNode-levelOverloadControlEntry 1 }

affirmedServicesContentHttpProxyServiceStatisticsNode-levelOverloadControlSlot OBJECT-TYPE
    SYNTAX      INTEGER {a1(1),a2(2),a3(3),a4(4),a5(5),a6(6),a7(7),a8(8),a9(9),a10(10),a11(11),a12(12),a13(13),a14(14),a15(15),a16(16),a17(17),a18(18),a19(19),a20(20),a21(21),a22(22),a23(23),a24(24),a25(25),a26(26),a27(27),a28(28),a29(29),a30(30),a31(31),a32(32),a33(33),a34(34),a35(35),a36(36),a37(37),a38(38),a39(39),a40(40),a41(41),a42(42),a43(43),a44(44),a45(45),a46(46),a47(47),a48(48),a49(49),a50(50),a51(51),a52(52),a53(53),a54(54),a55(55),a56(56),a57(57),a58(58),a59(59),a60(60),a61(61),a62(62),a63(63),a64(64),a65(65),a66(66),a67(67),a68(68),a69(69),a70(70),a71(71),a72(72),a73(73),a74(74),a75(75),a76(76),a77(77),a78(78),a79(79),a80(80),a81(81),a82(82),a83(83),a84(84),a85(85),a86(86),a87(87),a88(88),a89(89),a90(90),a91(91),a92(92),a93(93),a94(94),a95(95),a96(96),a97(97),a98(98),a99(99),a100(100),a101(101),a102(102),a103(103),a104(104),a105(105),a106(106),a107(107),a108(108),a109(109),a110(110),a111(111),a112(112),a113(113),a114(114),a115(115),a116(116),a117(117),a118(118),a119(119),a120(120),a121(121),a122(122),a123(123),a124(124),a125(125),a126(126),a127(127),a128(128)}
    MAX-ACCESS  not-accessible
    STATUS      current
    DESCRIPTION "slot number"
    ::= { affirmedServicesContentHttpProxyServiceStatisticsNode-levelOverloadControlEntry 2 }

affirmedServicesContentHttpProxyServiceStatisticsNode-levelOverloadControlNumconnectionacceptsoc OBJECT-TYPE
    SYNTAX      ConfdString
    MAX-ACCESS  read-only
    STATUS      current
    DESCRIPTION "Number of overload control connection accepts"
    ::= { affirmedServicesContentHttpProxyServiceStatisticsNode-levelOverloadControlEntry 3 }

affirmedServicesContentHttpProxyServiceStatisticsNode-levelOverloadControlNumconnectiondeniesoc OBJECT-TYPE
    SYNTAX      ConfdString
    MAX-ACCESS  read-only
    STATUS      current
    DESCRIPTION "Number of overload control connections denies"
    ::= { affirmedServicesContentHttpProxyServiceStatisticsNode-levelOverloadControlEntry 4 }

affirmedServicesContentHttpProxyServiceStatisticsNode-levelLatencyStatsTable OBJECT-TYPE
    SYNTAX      SEQUENCE OF AffirmedServicesContentHttpProxyServiceStatisticsNode-levelLatencyStatsEntry
    MAX-ACCESS  not-accessible
    STATUS      current
    DESCRIPTION ""
    ::= { affirmedServicesContentHttpProxyServiceStatisticsNode-level 8 }

affirmedServicesContentHttpProxyServiceStatisticsNode-levelLatencyStatsEntry OBJECT-TYPE
    SYNTAX      AffirmedServicesContentHttpProxyServiceStatisticsNode-levelLatencyStatsEntry
    MAX-ACCESS  not-accessible
    STATUS      current
    DESCRIPTION ""
    INDEX { affirmedServicesContentHttpProxyServiceStatisticsNode-levelLatencyStatsChassis, affirmedServicesContentHttpProxyServiceStatisticsNode-levelLatencyStatsSlot }
        ::= { affirmedServicesContentHttpProxyServiceStatisticsNode-levelLatencyStatsTable 1 }

AffirmedServicesContentHttpProxyServiceStatisticsNode-levelLatencyStatsEntry ::=
    SEQUENCE {
        affirmedServicesContentHttpProxyServiceStatisticsNode-levelLatencyStatsChassis Unsigned32,
        affirmedServicesContentHttpProxyServiceStatisticsNode-levelLatencyStatsSlot INTEGER,
        affirmedServicesContentHttpProxyServiceStatisticsNode-levelLatencyStatsLatencytnxtotal ConfdString,
        affirmedServicesContentHttpProxyServiceStatisticsNode-levelLatencyStatsLatencytnxavg ConfdString,
        affirmedServicesContentHttpProxyServiceStatisticsNode-levelLatencyStatsLatencytnxmax ConfdString,
        affirmedServicesContentHttpProxyServiceStatisticsNode-levelLatencyStatsLatencytnx10 ConfdString,
        affirmedServicesContentHttpProxyServiceStatisticsNode-levelLatencyStatsLatencytnx20 ConfdString,
        affirmedServicesContentHttpProxyServiceStatisticsNode-levelLatencyStatsLatencytnx30 ConfdString,
        affirmedServicesContentHttpProxyServiceStatisticsNode-levelLatencyStatsLatencytnx40 ConfdString,
        affirmedServicesContentHttpProxyServiceStatisticsNode-levelLatencyStatsLatencytnx50 ConfdString,
        affirmedServicesContentHttpProxyServiceStatisticsNode-levelLatencyStatsLatencytnx100 ConfdString,
        affirmedServicesContentHttpProxyServiceStatisticsNode-levelLatencyStatsLatencytnx101 ConfdString,
        affirmedServicesContentHttpProxyServiceStatisticsNode-levelLatencyStatsLatencyrequestavg ConfdString,
        affirmedServicesContentHttpProxyServiceStatisticsNode-levelLatencyStatsLatencyrequestmax ConfdString,
        affirmedServicesContentHttpProxyServiceStatisticsNode-levelLatencyStatsLatencyrequest10 ConfdString,
        affirmedServicesContentHttpProxyServiceStatisticsNode-levelLatencyStatsLatencyrequest20 ConfdString,
        affirmedServicesContentHttpProxyServiceStatisticsNode-levelLatencyStatsLatencyrequest30 ConfdString,
        affirmedServicesContentHttpProxyServiceStatisticsNode-levelLatencyStatsLatencyrequest40 ConfdString,
        affirmedServicesContentHttpProxyServiceStatisticsNode-levelLatencyStatsLatencyrequest50 ConfdString,
        affirmedServicesContentHttpProxyServiceStatisticsNode-levelLatencyStatsLatencyrequest100 ConfdString,
        affirmedServicesContentHttpProxyServiceStatisticsNode-levelLatencyStatsLatencyrequest101 ConfdString,
        affirmedServicesContentHttpProxyServiceStatisticsNode-levelLatencyStatsLatencyresponseavg ConfdString,
        affirmedServicesContentHttpProxyServiceStatisticsNode-levelLatencyStatsLatencyresponsemax ConfdString,
        affirmedServicesContentHttpProxyServiceStatisticsNode-levelLatencyStatsLatencyresponse10 ConfdString,
        affirmedServicesContentHttpProxyServiceStatisticsNode-levelLatencyStatsLatencyresponse20 ConfdString,
        affirmedServicesContentHttpProxyServiceStatisticsNode-levelLatencyStatsLatencyresponse30 ConfdString,
        affirmedServicesContentHttpProxyServiceStatisticsNode-levelLatencyStatsLatencyresponse40 ConfdString,
        affirmedServicesContentHttpProxyServiceStatisticsNode-levelLatencyStatsLatencyresponse50 ConfdString,
        affirmedServicesContentHttpProxyServiceStatisticsNode-levelLatencyStatsLatencyresponse100 ConfdString,
        affirmedServicesContentHttpProxyServiceStatisticsNode-levelLatencyStatsLatencyresponse101 ConfdString,
        affirmedServicesContentHttpProxyServiceStatisticsNode-levelLatencyStatsLatencyclientconntotal ConfdString,
        affirmedServicesContentHttpProxyServiceStatisticsNode-levelLatencyStatsLatencyclientdatarxavg ConfdString,
        affirmedServicesContentHttpProxyServiceStatisticsNode-levelLatencyStatsLatencyclientdatarxmax ConfdString,
        affirmedServicesContentHttpProxyServiceStatisticsNode-levelLatencyStatsLatencyclientdatarx10 ConfdString,
        affirmedServicesContentHttpProxyServiceStatisticsNode-levelLatencyStatsLatencyclientdatarx20 ConfdString,
        affirmedServicesContentHttpProxyServiceStatisticsNode-levelLatencyStatsLatencyclientdatarx30 ConfdString,
        affirmedServicesContentHttpProxyServiceStatisticsNode-levelLatencyStatsLatencyclientdatarx40 ConfdString,
        affirmedServicesContentHttpProxyServiceStatisticsNode-levelLatencyStatsLatencyclientdatarx50 ConfdString,
        affirmedServicesContentHttpProxyServiceStatisticsNode-levelLatencyStatsLatencyclientdatarx100 ConfdString,
        affirmedServicesContentHttpProxyServiceStatisticsNode-levelLatencyStatsLatencyclientdatarx101 ConfdString,
        affirmedServicesContentHttpProxyServiceStatisticsNode-levelLatencyStatsLatencyserverconntotal ConfdString,
        affirmedServicesContentHttpProxyServiceStatisticsNode-levelLatencyStatsLatencyserverdatatxavg ConfdString,
        affirmedServicesContentHttpProxyServiceStatisticsNode-levelLatencyStatsLatencyserverdatatxmax ConfdString,
        affirmedServicesContentHttpProxyServiceStatisticsNode-levelLatencyStatsLatencyserverdatatx10 ConfdString,
        affirmedServicesContentHttpProxyServiceStatisticsNode-levelLatencyStatsLatencyserverdatatx20 ConfdString,
        affirmedServicesContentHttpProxyServiceStatisticsNode-levelLatencyStatsLatencyserverdatatx30 ConfdString,
        affirmedServicesContentHttpProxyServiceStatisticsNode-levelLatencyStatsLatencyserverdatatx40 ConfdString,
        affirmedServicesContentHttpProxyServiceStatisticsNode-levelLatencyStatsLatencyserverdatatx50 ConfdString,
        affirmedServicesContentHttpProxyServiceStatisticsNode-levelLatencyStatsLatencyserverdatatx100 ConfdString,
        affirmedServicesContentHttpProxyServiceStatisticsNode-levelLatencyStatsLatencyserverdatatx101 ConfdString
    }

affirmedServicesContentHttpProxyServiceStatisticsNode-levelLatencyStatsChassis OBJECT-TYPE
    SYNTAX      Unsigned32
    MAX-ACCESS  not-accessible
    STATUS      current
    DESCRIPTION "chassis ID"
    ::= { affirmedServicesContentHttpProxyServiceStatisticsNode-levelLatencyStatsEntry 1 }

affirmedServicesContentHttpProxyServiceStatisticsNode-levelLatencyStatsSlot OBJECT-TYPE
    SYNTAX      INTEGER {a1(1),a2(2),a3(3),a4(4),a5(5),a6(6),a7(7),a8(8),a9(9),a10(10),a11(11),a12(12),a13(13),a14(14),a15(15),a16(16),a17(17),a18(18),a19(19),a20(20),a21(21),a22(22),a23(23),a24(24),a25(25),a26(26),a27(27),a28(28),a29(29),a30(30),a31(31),a32(32),a33(33),a34(34),a35(35),a36(36),a37(37),a38(38),a39(39),a40(40),a41(41),a42(42),a43(43),a44(44),a45(45),a46(46),a47(47),a48(48),a49(49),a50(50),a51(51),a52(52),a53(53),a54(54),a55(55),a56(56),a57(57),a58(58),a59(59),a60(60),a61(61),a62(62),a63(63),a64(64),a65(65),a66(66),a67(67),a68(68),a69(69),a70(70),a71(71),a72(72),a73(73),a74(74),a75(75),a76(76),a77(77),a78(78),a79(79),a80(80),a81(81),a82(82),a83(83),a84(84),a85(85),a86(86),a87(87),a88(88),a89(89),a90(90),a91(91),a92(92),a93(93),a94(94),a95(95),a96(96),a97(97),a98(98),a99(99),a100(100),a101(101),a102(102),a103(103),a104(104),a105(105),a106(106),a107(107),a108(108),a109(109),a110(110),a111(111),a112(112),a113(113),a114(114),a115(115),a116(116),a117(117),a118(118),a119(119),a120(120),a121(121),a122(122),a123(123),a124(124),a125(125),a126(126),a127(127),a128(128)}
    MAX-ACCESS  not-accessible
    STATUS      current
    DESCRIPTION "slot number"
    ::= { affirmedServicesContentHttpProxyServiceStatisticsNode-levelLatencyStatsEntry 2 }

affirmedServicesContentHttpProxyServiceStatisticsNode-levelLatencyStatsLatencytnxtotal OBJECT-TYPE
    SYNTAX      ConfdString
    MAX-ACCESS  read-only
    STATUS      current
    DESCRIPTION "Total number of serviced HTTP transactions counted for latency calculation"
    ::= { affirmedServicesContentHttpProxyServiceStatisticsNode-levelLatencyStatsEntry 3 }

affirmedServicesContentHttpProxyServiceStatisticsNode-levelLatencyStatsLatencytnxavg OBJECT-TYPE
    SYNTAX      ConfdString
    MAX-ACCESS  read-only
    STATUS      current
    DESCRIPTION "HTTP Transaction Service Latency Cumulative Moving Average (ms)"
    ::= { affirmedServicesContentHttpProxyServiceStatisticsNode-levelLatencyStatsEntry 4 }

affirmedServicesContentHttpProxyServiceStatisticsNode-levelLatencyStatsLatencytnxmax OBJECT-TYPE
    SYNTAX      ConfdString
    MAX-ACCESS  read-only
    STATUS      current
    DESCRIPTION "HTTP Transaction Service Latency Maximum (ms)"
    ::= { affirmedServicesContentHttpProxyServiceStatisticsNode-levelLatencyStatsEntry 5 }

affirmedServicesContentHttpProxyServiceStatisticsNode-levelLatencyStatsLatencytnx10 OBJECT-TYPE
    SYNTAX      ConfdString
    MAX-ACCESS  read-only
    STATUS      current
    DESCRIPTION "HTTP Transaction with Latency 0-10 (ms)"
    ::= { affirmedServicesContentHttpProxyServiceStatisticsNode-levelLatencyStatsEntry 6 }

affirmedServicesContentHttpProxyServiceStatisticsNode-levelLatencyStatsLatencytnx20 OBJECT-TYPE
    SYNTAX      ConfdString
    MAX-ACCESS  read-only
    STATUS      current
    DESCRIPTION "HTTP Transaction with Latency 11-20 (ms)"
    ::= { affirmedServicesContentHttpProxyServiceStatisticsNode-levelLatencyStatsEntry 7 }

affirmedServicesContentHttpProxyServiceStatisticsNode-levelLatencyStatsLatencytnx30 OBJECT-TYPE
    SYNTAX      ConfdString
    MAX-ACCESS  read-only
    STATUS      current
    DESCRIPTION "HTTP Transaction with Latency 21-30 (ms)"
    ::= { affirmedServicesContentHttpProxyServiceStatisticsNode-levelLatencyStatsEntry 8 }

affirmedServicesContentHttpProxyServiceStatisticsNode-levelLatencyStatsLatencytnx40 OBJECT-TYPE
    SYNTAX      ConfdString
    MAX-ACCESS  read-only
    STATUS      current
    DESCRIPTION "HTTP Transaction with Latency 31-40 (ms)"
    ::= { affirmedServicesContentHttpProxyServiceStatisticsNode-levelLatencyStatsEntry 9 }

affirmedServicesContentHttpProxyServiceStatisticsNode-levelLatencyStatsLatencytnx50 OBJECT-TYPE
    SYNTAX      ConfdString
    MAX-ACCESS  read-only
    STATUS      current
    DESCRIPTION "HTTP Transaction with Latency 41-50 (ms)"
    ::= { affirmedServicesContentHttpProxyServiceStatisticsNode-levelLatencyStatsEntry 10 }

affirmedServicesContentHttpProxyServiceStatisticsNode-levelLatencyStatsLatencytnx100 OBJECT-TYPE
    SYNTAX      ConfdString
    MAX-ACCESS  read-only
    STATUS      current
    DESCRIPTION "HTTP Transaction with Latency 51-100 (ms)"
    ::= { affirmedServicesContentHttpProxyServiceStatisticsNode-levelLatencyStatsEntry 11 }

affirmedServicesContentHttpProxyServiceStatisticsNode-levelLatencyStatsLatencytnx101 OBJECT-TYPE
    SYNTAX      ConfdString
    MAX-ACCESS  read-only
    STATUS      current
    DESCRIPTION "HTTP Transaction with Latency 100+ (ms)"
    ::= { affirmedServicesContentHttpProxyServiceStatisticsNode-levelLatencyStatsEntry 12 }

affirmedServicesContentHttpProxyServiceStatisticsNode-levelLatencyStatsLatencyrequestavg OBJECT-TYPE
    SYNTAX      ConfdString
    MAX-ACCESS  read-only
    STATUS      current
    DESCRIPTION "HTTP Request Service Latency Cumulative Moving Average (ms)"
    ::= { affirmedServicesContentHttpProxyServiceStatisticsNode-levelLatencyStatsEntry 13 }

affirmedServicesContentHttpProxyServiceStatisticsNode-levelLatencyStatsLatencyrequestmax OBJECT-TYPE
    SYNTAX      ConfdString
    MAX-ACCESS  read-only
    STATUS      current
    DESCRIPTION "HTTP Request Service Latency Maximum (ms)"
    ::= { affirmedServicesContentHttpProxyServiceStatisticsNode-levelLatencyStatsEntry 14 }

affirmedServicesContentHttpProxyServiceStatisticsNode-levelLatencyStatsLatencyrequest10 OBJECT-TYPE
    SYNTAX      ConfdString
    MAX-ACCESS  read-only
    STATUS      current
    DESCRIPTION "HTTP Request Service with Latency 0-10 (ms)"
    ::= { affirmedServicesContentHttpProxyServiceStatisticsNode-levelLatencyStatsEntry 15 }

affirmedServicesContentHttpProxyServiceStatisticsNode-levelLatencyStatsLatencyrequest20 OBJECT-TYPE
    SYNTAX      ConfdString
    MAX-ACCESS  read-only
    STATUS      current
    DESCRIPTION "HTTP Request Service with Latency 11-20 (ms)"
    ::= { affirmedServicesContentHttpProxyServiceStatisticsNode-levelLatencyStatsEntry 16 }

affirmedServicesContentHttpProxyServiceStatisticsNode-levelLatencyStatsLatencyrequest30 OBJECT-TYPE
    SYNTAX      ConfdString
    MAX-ACCESS  read-only
    STATUS      current
    DESCRIPTION "HTTP Request Service with Latency 21-30 (ms)"
    ::= { affirmedServicesContentHttpProxyServiceStatisticsNode-levelLatencyStatsEntry 17 }

affirmedServicesContentHttpProxyServiceStatisticsNode-levelLatencyStatsLatencyrequest40 OBJECT-TYPE
    SYNTAX      ConfdString
    MAX-ACCESS  read-only
    STATUS      current
    DESCRIPTION "HTTP Request Service with Latency 31-40 (ms)"
    ::= { affirmedServicesContentHttpProxyServiceStatisticsNode-levelLatencyStatsEntry 18 }

affirmedServicesContentHttpProxyServiceStatisticsNode-levelLatencyStatsLatencyrequest50 OBJECT-TYPE
    SYNTAX      ConfdString
    MAX-ACCESS  read-only
    STATUS      current
    DESCRIPTION "HTTP Request Service with Latency 41-50 (ms)"
    ::= { affirmedServicesContentHttpProxyServiceStatisticsNode-levelLatencyStatsEntry 19 }

affirmedServicesContentHttpProxyServiceStatisticsNode-levelLatencyStatsLatencyrequest100 OBJECT-TYPE
    SYNTAX      ConfdString
    MAX-ACCESS  read-only
    STATUS      current
    DESCRIPTION "HTTP Request Service with Latency 51-100 (ms)"
    ::= { affirmedServicesContentHttpProxyServiceStatisticsNode-levelLatencyStatsEntry 20 }

affirmedServicesContentHttpProxyServiceStatisticsNode-levelLatencyStatsLatencyrequest101 OBJECT-TYPE
    SYNTAX      ConfdString
    MAX-ACCESS  read-only
    STATUS      current
    DESCRIPTION "HTTP Request Service with Latency 100+ (ms)"
    ::= { affirmedServicesContentHttpProxyServiceStatisticsNode-levelLatencyStatsEntry 21 }

affirmedServicesContentHttpProxyServiceStatisticsNode-levelLatencyStatsLatencyresponseavg OBJECT-TYPE
    SYNTAX      ConfdString
    MAX-ACCESS  read-only
    STATUS      current
    DESCRIPTION "HTTP Response Service Latency Cumulative Moving Average (ms)"
    ::= { affirmedServicesContentHttpProxyServiceStatisticsNode-levelLatencyStatsEntry 22 }

affirmedServicesContentHttpProxyServiceStatisticsNode-levelLatencyStatsLatencyresponsemax OBJECT-TYPE
    SYNTAX      ConfdString
    MAX-ACCESS  read-only
    STATUS      current
    DESCRIPTION "HTTP Response Service Latency Maximum (ms)"
    ::= { affirmedServicesContentHttpProxyServiceStatisticsNode-levelLatencyStatsEntry 23 }

affirmedServicesContentHttpProxyServiceStatisticsNode-levelLatencyStatsLatencyresponse10 OBJECT-TYPE
    SYNTAX      ConfdString
    MAX-ACCESS  read-only
    STATUS      current
    DESCRIPTION "HTTP Response Service with Latency 0-10 (ms)"
    ::= { affirmedServicesContentHttpProxyServiceStatisticsNode-levelLatencyStatsEntry 24 }

affirmedServicesContentHttpProxyServiceStatisticsNode-levelLatencyStatsLatencyresponse20 OBJECT-TYPE
    SYNTAX      ConfdString
    MAX-ACCESS  read-only
    STATUS      current
    DESCRIPTION "HTTP Response Service with Latency 11-20 (ms)"
    ::= { affirmedServicesContentHttpProxyServiceStatisticsNode-levelLatencyStatsEntry 25 }

affirmedServicesContentHttpProxyServiceStatisticsNode-levelLatencyStatsLatencyresponse30 OBJECT-TYPE
    SYNTAX      ConfdString
    MAX-ACCESS  read-only
    STATUS      current
    DESCRIPTION "HTTP Response Service with Latency 21-30 (ms)"
    ::= { affirmedServicesContentHttpProxyServiceStatisticsNode-levelLatencyStatsEntry 26 }

affirmedServicesContentHttpProxyServiceStatisticsNode-levelLatencyStatsLatencyresponse40 OBJECT-TYPE
    SYNTAX      ConfdString
    MAX-ACCESS  read-only
    STATUS      current
    DESCRIPTION "HTTP Response Service with Latency 31-40 (ms)"
    ::= { affirmedServicesContentHttpProxyServiceStatisticsNode-levelLatencyStatsEntry 27 }

affirmedServicesContentHttpProxyServiceStatisticsNode-levelLatencyStatsLatencyresponse50 OBJECT-TYPE
    SYNTAX      ConfdString
    MAX-ACCESS  read-only
    STATUS      current
    DESCRIPTION "HTTP Response Service with Latency 41-50 (ms)"
    ::= { affirmedServicesContentHttpProxyServiceStatisticsNode-levelLatencyStatsEntry 28 }

affirmedServicesContentHttpProxyServiceStatisticsNode-levelLatencyStatsLatencyresponse100 OBJECT-TYPE
    SYNTAX      ConfdString
    MAX-ACCESS  read-only
    STATUS      current
    DESCRIPTION "HTTP Response Service with Latency 51-100 (ms)"
    ::= { affirmedServicesContentHttpProxyServiceStatisticsNode-levelLatencyStatsEntry 29 }

affirmedServicesContentHttpProxyServiceStatisticsNode-levelLatencyStatsLatencyresponse101 OBJECT-TYPE
    SYNTAX      ConfdString
    MAX-ACCESS  read-only
    STATUS      current
    DESCRIPTION "HTTP Response Service with Latency 100+ (ms)"
    ::= { affirmedServicesContentHttpProxyServiceStatisticsNode-levelLatencyStatsEntry 30 }

affirmedServicesContentHttpProxyServiceStatisticsNode-levelLatencyStatsLatencyclientconntotal OBJECT-TYPE
    SYNTAX      ConfdString
    MAX-ACCESS  read-only
    STATUS      current
    DESCRIPTION "Total number of client connections counted for latency calculation"
    ::= { affirmedServicesContentHttpProxyServiceStatisticsNode-levelLatencyStatsEntry 31 }

affirmedServicesContentHttpProxyServiceStatisticsNode-levelLatencyStatsLatencyclientdatarxavg OBJECT-TYPE
    SYNTAX      ConfdString
    MAX-ACCESS  read-only
    STATUS      current
    DESCRIPTION "Client Connection Receiving Data Delay Average (ms)"
    ::= { affirmedServicesContentHttpProxyServiceStatisticsNode-levelLatencyStatsEntry 32 }

affirmedServicesContentHttpProxyServiceStatisticsNode-levelLatencyStatsLatencyclientdatarxmax OBJECT-TYPE
    SYNTAX      ConfdString
    MAX-ACCESS  read-only
    STATUS      current
    DESCRIPTION "Client Connection Receiving Data Delay Maximum (ms)"
    ::= { affirmedServicesContentHttpProxyServiceStatisticsNode-levelLatencyStatsEntry 33 }

affirmedServicesContentHttpProxyServiceStatisticsNode-levelLatencyStatsLatencyclientdatarx10 OBJECT-TYPE
    SYNTAX      ConfdString
    MAX-ACCESS  read-only
    STATUS      current
    DESCRIPTION "Client Connection with Receiving Data Delay 0-10 (ms)"
    ::= { affirmedServicesContentHttpProxyServiceStatisticsNode-levelLatencyStatsEntry 34 }

affirmedServicesContentHttpProxyServiceStatisticsNode-levelLatencyStatsLatencyclientdatarx20 OBJECT-TYPE
    SYNTAX      ConfdString
    MAX-ACCESS  read-only
    STATUS      current
    DESCRIPTION "Client Connection with Receiving Data Delay 11-20 (ms)"
    ::= { affirmedServicesContentHttpProxyServiceStatisticsNode-levelLatencyStatsEntry 35 }

affirmedServicesContentHttpProxyServiceStatisticsNode-levelLatencyStatsLatencyclientdatarx30 OBJECT-TYPE
    SYNTAX      ConfdString
    MAX-ACCESS  read-only
    STATUS      current
    DESCRIPTION "Client Connection with Receiving Data Delay 21-30 (ms)"
    ::= { affirmedServicesContentHttpProxyServiceStatisticsNode-levelLatencyStatsEntry 36 }

affirmedServicesContentHttpProxyServiceStatisticsNode-levelLatencyStatsLatencyclientdatarx40 OBJECT-TYPE
    SYNTAX      ConfdString
    MAX-ACCESS  read-only
    STATUS      current
    DESCRIPTION "Client Connection with Receiving Data Delay 31-40 (ms)"
    ::= { affirmedServicesContentHttpProxyServiceStatisticsNode-levelLatencyStatsEntry 37 }

affirmedServicesContentHttpProxyServiceStatisticsNode-levelLatencyStatsLatencyclientdatarx50 OBJECT-TYPE
    SYNTAX      ConfdString
    MAX-ACCESS  read-only
    STATUS      current
    DESCRIPTION "Client Connection with Receiving Data Delay 41-50 (ms)"
    ::= { affirmedServicesContentHttpProxyServiceStatisticsNode-levelLatencyStatsEntry 38 }

affirmedServicesContentHttpProxyServiceStatisticsNode-levelLatencyStatsLatencyclientdatarx100 OBJECT-TYPE
    SYNTAX      ConfdString
    MAX-ACCESS  read-only
    STATUS      current
    DESCRIPTION "Client Connection with Receiving Data Delay 51-100 (ms)"
    ::= { affirmedServicesContentHttpProxyServiceStatisticsNode-levelLatencyStatsEntry 39 }

affirmedServicesContentHttpProxyServiceStatisticsNode-levelLatencyStatsLatencyclientdatarx101 OBJECT-TYPE
    SYNTAX      ConfdString
    MAX-ACCESS  read-only
    STATUS      current
    DESCRIPTION "Client Connection with Receiving Data Delay 100+ (ms)"
    ::= { affirmedServicesContentHttpProxyServiceStatisticsNode-levelLatencyStatsEntry 40 }

affirmedServicesContentHttpProxyServiceStatisticsNode-levelLatencyStatsLatencyserverconntotal OBJECT-TYPE
    SYNTAX      ConfdString
    MAX-ACCESS  read-only
    STATUS      current
    DESCRIPTION "Total number of server connections counted for latency calculation"
    ::= { affirmedServicesContentHttpProxyServiceStatisticsNode-levelLatencyStatsEntry 41 }

affirmedServicesContentHttpProxyServiceStatisticsNode-levelLatencyStatsLatencyserverdatatxavg OBJECT-TYPE
    SYNTAX      ConfdString
    MAX-ACCESS  read-only
    STATUS      current
    DESCRIPTION "Server Connection Transmitting Data Delay Average (ms)"
    ::= { affirmedServicesContentHttpProxyServiceStatisticsNode-levelLatencyStatsEntry 42 }

affirmedServicesContentHttpProxyServiceStatisticsNode-levelLatencyStatsLatencyserverdatatxmax OBJECT-TYPE
    SYNTAX      ConfdString
    MAX-ACCESS  read-only
    STATUS      current
    DESCRIPTION "Server Connection Transmitting Data Delay Maximum (ms)"
    ::= { affirmedServicesContentHttpProxyServiceStatisticsNode-levelLatencyStatsEntry 43 }

affirmedServicesContentHttpProxyServiceStatisticsNode-levelLatencyStatsLatencyserverdatatx10 OBJECT-TYPE
    SYNTAX      ConfdString
    MAX-ACCESS  read-only
    STATUS      current
    DESCRIPTION "Server Connection with Transmitting Data Delay 0-10 (ms)"
    ::= { affirmedServicesContentHttpProxyServiceStatisticsNode-levelLatencyStatsEntry 44 }

affirmedServicesContentHttpProxyServiceStatisticsNode-levelLatencyStatsLatencyserverdatatx20 OBJECT-TYPE
    SYNTAX      ConfdString
    MAX-ACCESS  read-only
    STATUS      current
    DESCRIPTION "Server Connection with Transmitting Data Delay 11-20 (ms)"
    ::= { affirmedServicesContentHttpProxyServiceStatisticsNode-levelLatencyStatsEntry 45 }

affirmedServicesContentHttpProxyServiceStatisticsNode-levelLatencyStatsLatencyserverdatatx30 OBJECT-TYPE
    SYNTAX      ConfdString
    MAX-ACCESS  read-only
    STATUS      current
    DESCRIPTION "Server Connection with Transmitting Data Delay 21-30 (ms)"
    ::= { affirmedServicesContentHttpProxyServiceStatisticsNode-levelLatencyStatsEntry 46 }

affirmedServicesContentHttpProxyServiceStatisticsNode-levelLatencyStatsLatencyserverdatatx40 OBJECT-TYPE
    SYNTAX      ConfdString
    MAX-ACCESS  read-only
    STATUS      current
    DESCRIPTION "Server Connection with Transmitting Data Delay 31-40 (ms)"
    ::= { affirmedServicesContentHttpProxyServiceStatisticsNode-levelLatencyStatsEntry 47 }

affirmedServicesContentHttpProxyServiceStatisticsNode-levelLatencyStatsLatencyserverdatatx50 OBJECT-TYPE
    SYNTAX      ConfdString
    MAX-ACCESS  read-only
    STATUS      current
    DESCRIPTION "Server Connection with Transmitting Data Delay 41-50 (ms)"
    ::= { affirmedServicesContentHttpProxyServiceStatisticsNode-levelLatencyStatsEntry 48 }

affirmedServicesContentHttpProxyServiceStatisticsNode-levelLatencyStatsLatencyserverdatatx100 OBJECT-TYPE
    SYNTAX      ConfdString
    MAX-ACCESS  read-only
    STATUS      current
    DESCRIPTION "Server Connection with Transmitting Data Delay 51-100 (ms)"
    ::= { affirmedServicesContentHttpProxyServiceStatisticsNode-levelLatencyStatsEntry 49 }

affirmedServicesContentHttpProxyServiceStatisticsNode-levelLatencyStatsLatencyserverdatatx101 OBJECT-TYPE
    SYNTAX      ConfdString
    MAX-ACCESS  read-only
    STATUS      current
    DESCRIPTION "Server Connection with Transmitting Data Delay 100+ (ms)"
    ::= { affirmedServicesContentHttpProxyServiceStatisticsNode-levelLatencyStatsEntry 50 }

affirmedServicesContentHttpProxyServiceStatisticsNode-levelHeaderEnrichmentTable OBJECT-TYPE
    SYNTAX      SEQUENCE OF AffirmedServicesContentHttpProxyServiceStatisticsNode-levelHeaderEnrichmentEntry
    MAX-ACCESS  not-accessible
    STATUS      current
    DESCRIPTION ""
    ::= { affirmedServicesContentHttpProxyServiceStatisticsNode-level 1 }

affirmedServicesContentHttpProxyServiceStatisticsNode-levelHeaderEnrichmentEntry OBJECT-TYPE
    SYNTAX      AffirmedServicesContentHttpProxyServiceStatisticsNode-levelHeaderEnrichmentEntry
    MAX-ACCESS  not-accessible
    STATUS      current
    DESCRIPTION ""
    INDEX { affirmedServicesContentHttpProxyServiceStatisticsNode-levelHeaderEnrichmentChassis, affirmedServicesContentHttpProxyServiceStatisticsNode-levelHeaderEnrichmentSlot }
        ::= { affirmedServicesContentHttpProxyServiceStatisticsNode-levelHeaderEnrichmentTable 1 }

AffirmedServicesContentHttpProxyServiceStatisticsNode-levelHeaderEnrichmentEntry ::=
    SEQUENCE {
        affirmedServicesContentHttpProxyServiceStatisticsNode-levelHeaderEnrichmentChassis Unsigned32,
        affirmedServicesContentHttpProxyServiceStatisticsNode-levelHeaderEnrichmentSlot INTEGER,
        affirmedServicesContentHttpProxyServiceStatisticsNode-levelHeaderEnrichmentOther ConfdString,
        affirmedServicesContentHttpProxyServiceStatisticsNode-levelHeaderEnrichmentImsi ConfdString,
        affirmedServicesContentHttpProxyServiceStatisticsNode-levelHeaderEnrichmentImsimd5 ConfdString,
        affirmedServicesContentHttpProxyServiceStatisticsNode-levelHeaderEnrichmentImei ConfdString,
        affirmedServicesContentHttpProxyServiceStatisticsNode-levelHeaderEnrichmentImeimd5 ConfdString,
        affirmedServicesContentHttpProxyServiceStatisticsNode-levelHeaderEnrichmentMsisdn ConfdString,
        affirmedServicesContentHttpProxyServiceStatisticsNode-levelHeaderEnrichmentMsisdnmd5 ConfdString,
        affirmedServicesContentHttpProxyServiceStatisticsNode-levelHeaderEnrichmentMsisdnstatenc ConfdString,
        affirmedServicesContentHttpProxyServiceStatisticsNode-levelHeaderEnrichmentMsisdndynmenc ConfdString,
        affirmedServicesContentHttpProxyServiceStatisticsNode-levelHeaderEnrichmentUeipaddr ConfdString,
        affirmedServicesContentHttpProxyServiceStatisticsNode-levelHeaderEnrichmentRattype ConfdString,
        affirmedServicesContentHttpProxyServiceStatisticsNode-levelHeaderEnrichmentChargingchar ConfdString,
        affirmedServicesContentHttpProxyServiceStatisticsNode-levelHeaderEnrichmentServingplmnid ConfdString,
        affirmedServicesContentHttpProxyServiceStatisticsNode-levelHeaderEnrichmentUlicgi ConfdString,
        affirmedServicesContentHttpProxyServiceStatisticsNode-levelHeaderEnrichmentUeipaddrport ConfdString,
        affirmedServicesContentHttpProxyServiceStatisticsNode-levelHeaderEnrichmentUeport ConfdString,
        affirmedServicesContentHttpProxyServiceStatisticsNode-levelHeaderEnrichmentUeipv4mappedipv6addr ConfdString,
        affirmedServicesContentHttpProxyServiceStatisticsNode-levelHeaderEnrichmentUehttpprotocol ConfdString,
        affirmedServicesContentHttpProxyServiceStatisticsNode-levelHeaderEnrichmentSgwipaddr ConfdString,
        affirmedServicesContentHttpProxyServiceStatisticsNode-levelHeaderEnrichmentOrigapn ConfdString,
        affirmedServicesContentHttpProxyServiceStatisticsNode-levelHeaderEnrichmentMappedapn ConfdString,
        affirmedServicesContentHttpProxyServiceStatisticsNode-levelHeaderEnrichmentLtmiplaintextid ConfdString,
        affirmedServicesContentHttpProxyServiceStatisticsNode-levelHeaderEnrichmentLtmistatictrustedid ConfdString,
        affirmedServicesContentHttpProxyServiceStatisticsNode-levelHeaderEnrichmentLtmidynamictrustedid ConfdString,
        affirmedServicesContentHttpProxyServiceStatisticsNode-levelHeaderEnrichmentLtmiexternalid ConfdString,
        affirmedServicesContentHttpProxyServiceStatisticsNode-levelHeaderEnrichmentResellerid ConfdString,
        affirmedServicesContentHttpProxyServiceStatisticsNode-levelHeaderEnrichmentOriginalurl ConfdString,
        affirmedServicesContentHttpProxyServiceStatisticsNode-levelHeaderEnrichmentHttpversion ConfdString,
        affirmedServicesContentHttpProxyServiceStatisticsNode-levelHeaderEnrichmentOthermd5 ConfdString,
        affirmedServicesContentHttpProxyServiceStatisticsNode-levelHeaderEnrichmentOtherencrypted ConfdString,
        affirmedServicesContentHttpProxyServiceStatisticsNode-levelHeaderEnrichmentImsiencrypted ConfdString,
        affirmedServicesContentHttpProxyServiceStatisticsNode-levelHeaderEnrichmentImeiencrypted ConfdString,
        affirmedServicesContentHttpProxyServiceStatisticsNode-levelHeaderEnrichmentMsisdnencrypted ConfdString,
        affirmedServicesContentHttpProxyServiceStatisticsNode-levelHeaderEnrichmentUeipaddrmd5 ConfdString,
        affirmedServicesContentHttpProxyServiceStatisticsNode-levelHeaderEnrichmentUeipaddrencrypted ConfdString,
        affirmedServicesContentHttpProxyServiceStatisticsNode-levelHeaderEnrichmentRattypemd5 ConfdString,
        affirmedServicesContentHttpProxyServiceStatisticsNode-levelHeaderEnrichmentRattypeencrypted ConfdString,
        affirmedServicesContentHttpProxyServiceStatisticsNode-levelHeaderEnrichmentChargingcharmd5 ConfdString,
        affirmedServicesContentHttpProxyServiceStatisticsNode-levelHeaderEnrichmentChargingcharencrypted ConfdString,
        affirmedServicesContentHttpProxyServiceStatisticsNode-levelHeaderEnrichmentServingplmnidmd5 ConfdString,
        affirmedServicesContentHttpProxyServiceStatisticsNode-levelHeaderEnrichmentServingplmnidencrypted ConfdString,
        affirmedServicesContentHttpProxyServiceStatisticsNode-levelHeaderEnrichmentUlicgimd5 ConfdString,
        affirmedServicesContentHttpProxyServiceStatisticsNode-levelHeaderEnrichmentUlicgiencrypted ConfdString,
        affirmedServicesContentHttpProxyServiceStatisticsNode-levelHeaderEnrichmentSgwipaddrmd5 ConfdString,
        affirmedServicesContentHttpProxyServiceStatisticsNode-levelHeaderEnrichmentSgwipaddrencrypted ConfdString,
        affirmedServicesContentHttpProxyServiceStatisticsNode-levelHeaderEnrichmentOrigapnmd5 ConfdString,
        affirmedServicesContentHttpProxyServiceStatisticsNode-levelHeaderEnrichmentOrigapnencrypted ConfdString,
        affirmedServicesContentHttpProxyServiceStatisticsNode-levelHeaderEnrichmentSgwipv6addr ConfdString,
        affirmedServicesContentHttpProxyServiceStatisticsNode-levelHeaderEnrichmentSgwipv6addrmd5 ConfdString,
        affirmedServicesContentHttpProxyServiceStatisticsNode-levelHeaderEnrichmentSgwipv6addrencrypted ConfdString,
        affirmedServicesContentHttpProxyServiceStatisticsNode-levelHeaderEnrichmentMsisdnstatacr ConfdString,
        affirmedServicesContentHttpProxyServiceStatisticsNode-levelHeaderEnrichmentMsisdndynmacr ConfdString,
        affirmedServicesContentHttpProxyServiceStatisticsNode-levelHeaderEnrichmentTimezone ConfdString,
        affirmedServicesContentHttpProxyServiceStatisticsNode-levelHeaderEnrichmentHttpversionmd5 ConfdString,
        affirmedServicesContentHttpProxyServiceStatisticsNode-levelHeaderEnrichmentHttpversionencrypted ConfdString
    }

affirmedServicesContentHttpProxyServiceStatisticsNode-levelHeaderEnrichmentChassis OBJECT-TYPE
    SYNTAX      Unsigned32
    MAX-ACCESS  not-accessible
    STATUS      current
    DESCRIPTION "chassis ID"
    ::= { affirmedServicesContentHttpProxyServiceStatisticsNode-levelHeaderEnrichmentEntry 1 }

affirmedServicesContentHttpProxyServiceStatisticsNode-levelHeaderEnrichmentSlot OBJECT-TYPE
    SYNTAX      INTEGER {a1(1),a2(2),a3(3),a4(4),a5(5),a6(6),a7(7),a8(8),a9(9),a10(10),a11(11),a12(12),a13(13),a14(14),a15(15),a16(16),a17(17),a18(18),a19(19),a20(20),a21(21),a22(22),a23(23),a24(24),a25(25),a26(26),a27(27),a28(28),a29(29),a30(30),a31(31),a32(32),a33(33),a34(34),a35(35),a36(36),a37(37),a38(38),a39(39),a40(40),a41(41),a42(42),a43(43),a44(44),a45(45),a46(46),a47(47),a48(48),a49(49),a50(50),a51(51),a52(52),a53(53),a54(54),a55(55),a56(56),a57(57),a58(58),a59(59),a60(60),a61(61),a62(62),a63(63),a64(64),a65(65),a66(66),a67(67),a68(68),a69(69),a70(70),a71(71),a72(72),a73(73),a74(74),a75(75),a76(76),a77(77),a78(78),a79(79),a80(80),a81(81),a82(82),a83(83),a84(84),a85(85),a86(86),a87(87),a88(88),a89(89),a90(90),a91(91),a92(92),a93(93),a94(94),a95(95),a96(96),a97(97),a98(98),a99(99),a100(100),a101(101),a102(102),a103(103),a104(104),a105(105),a106(106),a107(107),a108(108),a109(109),a110(110),a111(111),a112(112),a113(113),a114(114),a115(115),a116(116),a117(117),a118(118),a119(119),a120(120),a121(121),a122(122),a123(123),a124(124),a125(125),a126(126),a127(127),a128(128)}
    MAX-ACCESS  not-accessible
    STATUS      current
    DESCRIPTION "slot number"
    ::= { affirmedServicesContentHttpProxyServiceStatisticsNode-levelHeaderEnrichmentEntry 2 }

affirmedServicesContentHttpProxyServiceStatisticsNode-levelHeaderEnrichmentOther OBJECT-TYPE
    SYNTAX      ConfdString
    MAX-ACCESS  read-only
    STATUS      current
    DESCRIPTION "Header Additions - Other"
    ::= { affirmedServicesContentHttpProxyServiceStatisticsNode-levelHeaderEnrichmentEntry 3 }

affirmedServicesContentHttpProxyServiceStatisticsNode-levelHeaderEnrichmentImsi OBJECT-TYPE
    SYNTAX      ConfdString
    MAX-ACCESS  read-only
    STATUS      current
    DESCRIPTION "Header Additions - IMSI"
    ::= { affirmedServicesContentHttpProxyServiceStatisticsNode-levelHeaderEnrichmentEntry 4 }

affirmedServicesContentHttpProxyServiceStatisticsNode-levelHeaderEnrichmentImsimd5 OBJECT-TYPE
    SYNTAX      ConfdString
    MAX-ACCESS  read-only
    STATUS      current
    DESCRIPTION "Header Additions - IMSI MD5"
    ::= { affirmedServicesContentHttpProxyServiceStatisticsNode-levelHeaderEnrichmentEntry 5 }

affirmedServicesContentHttpProxyServiceStatisticsNode-levelHeaderEnrichmentImei OBJECT-TYPE
    SYNTAX      ConfdString
    MAX-ACCESS  read-only
    STATUS      current
    DESCRIPTION "Header Additions - IMEI"
    ::= { affirmedServicesContentHttpProxyServiceStatisticsNode-levelHeaderEnrichmentEntry 6 }

affirmedServicesContentHttpProxyServiceStatisticsNode-levelHeaderEnrichmentImeimd5 OBJECT-TYPE
    SYNTAX      ConfdString
    MAX-ACCESS  read-only
    STATUS      current
    DESCRIPTION "Header Additions - IMEI MD5"
    ::= { affirmedServicesContentHttpProxyServiceStatisticsNode-levelHeaderEnrichmentEntry 7 }

affirmedServicesContentHttpProxyServiceStatisticsNode-levelHeaderEnrichmentMsisdn OBJECT-TYPE
    SYNTAX      ConfdString
    MAX-ACCESS  read-only
    STATUS      current
    DESCRIPTION "Header Additions - MSISDN"
    ::= { affirmedServicesContentHttpProxyServiceStatisticsNode-levelHeaderEnrichmentEntry 8 }

affirmedServicesContentHttpProxyServiceStatisticsNode-levelHeaderEnrichmentMsisdnmd5 OBJECT-TYPE
    SYNTAX      ConfdString
    MAX-ACCESS  read-only
    STATUS      current
    DESCRIPTION "Header Additions - MSISDN MD5"
    ::= { affirmedServicesContentHttpProxyServiceStatisticsNode-levelHeaderEnrichmentEntry 9 }

affirmedServicesContentHttpProxyServiceStatisticsNode-levelHeaderEnrichmentMsisdnstatenc OBJECT-TYPE
    SYNTAX      ConfdString
    MAX-ACCESS  read-only
    STATUS      current
    DESCRIPTION "Header Additions - MSISDN Static Encryption"
    ::= { affirmedServicesContentHttpProxyServiceStatisticsNode-levelHeaderEnrichmentEntry 10 }

affirmedServicesContentHttpProxyServiceStatisticsNode-levelHeaderEnrichmentMsisdndynmenc OBJECT-TYPE
    SYNTAX      ConfdString
    MAX-ACCESS  read-only
    STATUS      current
    DESCRIPTION "Header Additions - MSISDN Dynamic Encryption"
    ::= { affirmedServicesContentHttpProxyServiceStatisticsNode-levelHeaderEnrichmentEntry 11 }

affirmedServicesContentHttpProxyServiceStatisticsNode-levelHeaderEnrichmentUeipaddr OBJECT-TYPE
    SYNTAX      ConfdString
    MAX-ACCESS  read-only
    STATUS      current
    DESCRIPTION "Header Additions - UE IP Address"
    ::= { affirmedServicesContentHttpProxyServiceStatisticsNode-levelHeaderEnrichmentEntry 12 }

affirmedServicesContentHttpProxyServiceStatisticsNode-levelHeaderEnrichmentRattype OBJECT-TYPE
    SYNTAX      ConfdString
    MAX-ACCESS  read-only
    STATUS      current
    DESCRIPTION "Header Additions - RAT Type"
    ::= { affirmedServicesContentHttpProxyServiceStatisticsNode-levelHeaderEnrichmentEntry 13 }

affirmedServicesContentHttpProxyServiceStatisticsNode-levelHeaderEnrichmentChargingchar OBJECT-TYPE
    SYNTAX      ConfdString
    MAX-ACCESS  read-only
    STATUS      current
    DESCRIPTION "Header Additions - Charging Characteristic"
    ::= { affirmedServicesContentHttpProxyServiceStatisticsNode-levelHeaderEnrichmentEntry 14 }

affirmedServicesContentHttpProxyServiceStatisticsNode-levelHeaderEnrichmentServingplmnid OBJECT-TYPE
    SYNTAX      ConfdString
    MAX-ACCESS  read-only
    STATUS      current
    DESCRIPTION "Header Additions - Serving PLMNID"
    ::= { affirmedServicesContentHttpProxyServiceStatisticsNode-levelHeaderEnrichmentEntry 15 }

affirmedServicesContentHttpProxyServiceStatisticsNode-levelHeaderEnrichmentUlicgi OBJECT-TYPE
    SYNTAX      ConfdString
    MAX-ACCESS  read-only
    STATUS      current
    DESCRIPTION "Header Additions - ULI CGI"
    ::= { affirmedServicesContentHttpProxyServiceStatisticsNode-levelHeaderEnrichmentEntry 16 }

affirmedServicesContentHttpProxyServiceStatisticsNode-levelHeaderEnrichmentUeipaddrport OBJECT-TYPE
    SYNTAX      ConfdString
    MAX-ACCESS  read-only
    STATUS      current
    DESCRIPTION "Header Additions - UE IP Address and Port Number"
    ::= { affirmedServicesContentHttpProxyServiceStatisticsNode-levelHeaderEnrichmentEntry 17 }

affirmedServicesContentHttpProxyServiceStatisticsNode-levelHeaderEnrichmentUeport OBJECT-TYPE
    SYNTAX      ConfdString
    MAX-ACCESS  read-only
    STATUS      current
    DESCRIPTION "Header Additions - UE IP Port Number"
    ::= { affirmedServicesContentHttpProxyServiceStatisticsNode-levelHeaderEnrichmentEntry 18 }

affirmedServicesContentHttpProxyServiceStatisticsNode-levelHeaderEnrichmentUeipv4mappedipv6addr OBJECT-TYPE
    SYNTAX      ConfdString
    MAX-ACCESS  read-only
    STATUS      current
    DESCRIPTION "Header Additions - UE IPv4 Mapped IPv6 Address"
    ::= { affirmedServicesContentHttpProxyServiceStatisticsNode-levelHeaderEnrichmentEntry 19 }

affirmedServicesContentHttpProxyServiceStatisticsNode-levelHeaderEnrichmentUehttpprotocol OBJECT-TYPE
    SYNTAX      ConfdString
    MAX-ACCESS  read-only
    STATUS      current
    DESCRIPTION "Header Additions - UE Http Protocol"
    ::= { affirmedServicesContentHttpProxyServiceStatisticsNode-levelHeaderEnrichmentEntry 20 }

affirmedServicesContentHttpProxyServiceStatisticsNode-levelHeaderEnrichmentSgwipaddr OBJECT-TYPE
    SYNTAX      ConfdString
    MAX-ACCESS  read-only
    STATUS      current
    DESCRIPTION "Header Additions - SGW IPv4 Address"
    ::= { affirmedServicesContentHttpProxyServiceStatisticsNode-levelHeaderEnrichmentEntry 21 }

affirmedServicesContentHttpProxyServiceStatisticsNode-levelHeaderEnrichmentOrigapn OBJECT-TYPE
    SYNTAX      ConfdString
    MAX-ACCESS  read-only
    STATUS      current
    DESCRIPTION "Header Additions - Original APN"
    ::= { affirmedServicesContentHttpProxyServiceStatisticsNode-levelHeaderEnrichmentEntry 22 }

affirmedServicesContentHttpProxyServiceStatisticsNode-levelHeaderEnrichmentMappedapn OBJECT-TYPE
    SYNTAX      ConfdString
    MAX-ACCESS  read-only
    STATUS      current
    DESCRIPTION "Header Additions - Mapped APN"
    ::= { affirmedServicesContentHttpProxyServiceStatisticsNode-levelHeaderEnrichmentEntry 23 }

affirmedServicesContentHttpProxyServiceStatisticsNode-levelHeaderEnrichmentLtmiplaintextid OBJECT-TYPE
    SYNTAX      ConfdString
    MAX-ACCESS  read-only
    STATUS      current
    DESCRIPTION "Header Additions - Ltmi Plain Text ID"
    ::= { affirmedServicesContentHttpProxyServiceStatisticsNode-levelHeaderEnrichmentEntry 24 }

affirmedServicesContentHttpProxyServiceStatisticsNode-levelHeaderEnrichmentLtmistatictrustedid OBJECT-TYPE
    SYNTAX      ConfdString
    MAX-ACCESS  read-only
    STATUS      current
    DESCRIPTION "Header Additions - Ltmi Static Trusted ID"
    ::= { affirmedServicesContentHttpProxyServiceStatisticsNode-levelHeaderEnrichmentEntry 25 }

affirmedServicesContentHttpProxyServiceStatisticsNode-levelHeaderEnrichmentLtmidynamictrustedid OBJECT-TYPE
    SYNTAX      ConfdString
    MAX-ACCESS  read-only
    STATUS      current
    DESCRIPTION "Header Additions - Ltmi Dynamic Trusted ID"
    ::= { affirmedServicesContentHttpProxyServiceStatisticsNode-levelHeaderEnrichmentEntry 26 }

affirmedServicesContentHttpProxyServiceStatisticsNode-levelHeaderEnrichmentLtmiexternalid OBJECT-TYPE
    SYNTAX      ConfdString
    MAX-ACCESS  read-only
    STATUS      current
    DESCRIPTION "Header Additions - Ltmi External ID"
    ::= { affirmedServicesContentHttpProxyServiceStatisticsNode-levelHeaderEnrichmentEntry 27 }

affirmedServicesContentHttpProxyServiceStatisticsNode-levelHeaderEnrichmentResellerid OBJECT-TYPE
    SYNTAX      ConfdString
    MAX-ACCESS  read-only
    STATUS      current
    DESCRIPTION "Header Additions - Reseller ID"
    ::= { affirmedServicesContentHttpProxyServiceStatisticsNode-levelHeaderEnrichmentEntry 28 }

affirmedServicesContentHttpProxyServiceStatisticsNode-levelHeaderEnrichmentOriginalurl OBJECT-TYPE
    SYNTAX      ConfdString
    MAX-ACCESS  read-only
    STATUS      current
    DESCRIPTION "Header Additions - Original URL"
    ::= { affirmedServicesContentHttpProxyServiceStatisticsNode-levelHeaderEnrichmentEntry 29 }

affirmedServicesContentHttpProxyServiceStatisticsNode-levelHeaderEnrichmentHttpversion OBJECT-TYPE
    SYNTAX      ConfdString
    MAX-ACCESS  read-only
    STATUS      current
    DESCRIPTION "Header Additions - HTTPVersion"
    ::= { affirmedServicesContentHttpProxyServiceStatisticsNode-levelHeaderEnrichmentEntry 30 }

affirmedServicesContentHttpProxyServiceStatisticsNode-levelHeaderEnrichmentOthermd5 OBJECT-TYPE
    SYNTAX      ConfdString
    MAX-ACCESS  read-only
    STATUS      current
    DESCRIPTION "Header Additions - Other MD5"
    ::= { affirmedServicesContentHttpProxyServiceStatisticsNode-levelHeaderEnrichmentEntry 31 }

affirmedServicesContentHttpProxyServiceStatisticsNode-levelHeaderEnrichmentOtherencrypted OBJECT-TYPE
    SYNTAX      ConfdString
    MAX-ACCESS  read-only
    STATUS      current
    DESCRIPTION "Header Additions - Other Encrypted"
    ::= { affirmedServicesContentHttpProxyServiceStatisticsNode-levelHeaderEnrichmentEntry 32 }

affirmedServicesContentHttpProxyServiceStatisticsNode-levelHeaderEnrichmentImsiencrypted OBJECT-TYPE
    SYNTAX      ConfdString
    MAX-ACCESS  read-only
    STATUS      current
    DESCRIPTION "Header Additions - IMSI Encrypted"
    ::= { affirmedServicesContentHttpProxyServiceStatisticsNode-levelHeaderEnrichmentEntry 33 }

affirmedServicesContentHttpProxyServiceStatisticsNode-levelHeaderEnrichmentImeiencrypted OBJECT-TYPE
    SYNTAX      ConfdString
    MAX-ACCESS  read-only
    STATUS      current
    DESCRIPTION "Header Additions - IMEI Encrypted"
    ::= { affirmedServicesContentHttpProxyServiceStatisticsNode-levelHeaderEnrichmentEntry 34 }

affirmedServicesContentHttpProxyServiceStatisticsNode-levelHeaderEnrichmentMsisdnencrypted OBJECT-TYPE
    SYNTAX      ConfdString
    MAX-ACCESS  read-only
    STATUS      current
    DESCRIPTION "Header Additions - MSISDN Encrypted"
    ::= { affirmedServicesContentHttpProxyServiceStatisticsNode-levelHeaderEnrichmentEntry 35 }

affirmedServicesContentHttpProxyServiceStatisticsNode-levelHeaderEnrichmentUeipaddrmd5 OBJECT-TYPE
    SYNTAX      ConfdString
    MAX-ACCESS  read-only
    STATUS      current
    DESCRIPTION "Header Additions - UE IP Address MD5"
    ::= { affirmedServicesContentHttpProxyServiceStatisticsNode-levelHeaderEnrichmentEntry 36 }

affirmedServicesContentHttpProxyServiceStatisticsNode-levelHeaderEnrichmentUeipaddrencrypted OBJECT-TYPE
    SYNTAX      ConfdString
    MAX-ACCESS  read-only
    STATUS      current
    DESCRIPTION "Header Additions - UE IP Address Encrypted"
    ::= { affirmedServicesContentHttpProxyServiceStatisticsNode-levelHeaderEnrichmentEntry 37 }

affirmedServicesContentHttpProxyServiceStatisticsNode-levelHeaderEnrichmentRattypemd5 OBJECT-TYPE
    SYNTAX      ConfdString
    MAX-ACCESS  read-only
    STATUS      current
    DESCRIPTION "Header Additions - RAT Type MD5"
    ::= { affirmedServicesContentHttpProxyServiceStatisticsNode-levelHeaderEnrichmentEntry 38 }

affirmedServicesContentHttpProxyServiceStatisticsNode-levelHeaderEnrichmentRattypeencrypted OBJECT-TYPE
    SYNTAX      ConfdString
    MAX-ACCESS  read-only
    STATUS      current
    DESCRIPTION "Header Additions - RAT Type Encrypted"
    ::= { affirmedServicesContentHttpProxyServiceStatisticsNode-levelHeaderEnrichmentEntry 39 }

affirmedServicesContentHttpProxyServiceStatisticsNode-levelHeaderEnrichmentChargingcharmd5 OBJECT-TYPE
    SYNTAX      ConfdString
    MAX-ACCESS  read-only
    STATUS      current
    DESCRIPTION "Header Additions - Charging Characteristic MD5"
    ::= { affirmedServicesContentHttpProxyServiceStatisticsNode-levelHeaderEnrichmentEntry 40 }

affirmedServicesContentHttpProxyServiceStatisticsNode-levelHeaderEnrichmentChargingcharencrypted OBJECT-TYPE
    SYNTAX      ConfdString
    MAX-ACCESS  read-only
    STATUS      current
    DESCRIPTION "Header Additions - Charging Characteristic Encrypted"
    ::= { affirmedServicesContentHttpProxyServiceStatisticsNode-levelHeaderEnrichmentEntry 41 }

affirmedServicesContentHttpProxyServiceStatisticsNode-levelHeaderEnrichmentServingplmnidmd5 OBJECT-TYPE
    SYNTAX      ConfdString
    MAX-ACCESS  read-only
    STATUS      current
    DESCRIPTION "Header Additions - Serving PLMNID MD5"
    ::= { affirmedServicesContentHttpProxyServiceStatisticsNode-levelHeaderEnrichmentEntry 42 }

affirmedServicesContentHttpProxyServiceStatisticsNode-levelHeaderEnrichmentServingplmnidencrypted OBJECT-TYPE
    SYNTAX      ConfdString
    MAX-ACCESS  read-only
    STATUS      current
    DESCRIPTION "Header Additions - Serving PLMNID Encrypted"
    ::= { affirmedServicesContentHttpProxyServiceStatisticsNode-levelHeaderEnrichmentEntry 43 }

affirmedServicesContentHttpProxyServiceStatisticsNode-levelHeaderEnrichmentUlicgimd5 OBJECT-TYPE
    SYNTAX      ConfdString
    MAX-ACCESS  read-only
    STATUS      current
    DESCRIPTION "Header Additions - ULI CGI MD5"
    ::= { affirmedServicesContentHttpProxyServiceStatisticsNode-levelHeaderEnrichmentEntry 44 }

affirmedServicesContentHttpProxyServiceStatisticsNode-levelHeaderEnrichmentUlicgiencrypted OBJECT-TYPE
    SYNTAX      ConfdString
    MAX-ACCESS  read-only
    STATUS      current
    DESCRIPTION "Header Additions - ULI CGI Encrypted"
    ::= { affirmedServicesContentHttpProxyServiceStatisticsNode-levelHeaderEnrichmentEntry 45 }

affirmedServicesContentHttpProxyServiceStatisticsNode-levelHeaderEnrichmentSgwipaddrmd5 OBJECT-TYPE
    SYNTAX      ConfdString
    MAX-ACCESS  read-only
    STATUS      current
    DESCRIPTION "Header Additions - SGW IPv4 Address MD5"
    ::= { affirmedServicesContentHttpProxyServiceStatisticsNode-levelHeaderEnrichmentEntry 46 }

affirmedServicesContentHttpProxyServiceStatisticsNode-levelHeaderEnrichmentSgwipaddrencrypted OBJECT-TYPE
    SYNTAX      ConfdString
    MAX-ACCESS  read-only
    STATUS      current
    DESCRIPTION "Header Additions - SGW IPv4 Address Encrypted"
    ::= { affirmedServicesContentHttpProxyServiceStatisticsNode-levelHeaderEnrichmentEntry 47 }

affirmedServicesContentHttpProxyServiceStatisticsNode-levelHeaderEnrichmentOrigapnmd5 OBJECT-TYPE
    SYNTAX      ConfdString
    MAX-ACCESS  read-only
    STATUS      current
    DESCRIPTION "Header Additions - Original APN MD5"
    ::= { affirmedServicesContentHttpProxyServiceStatisticsNode-levelHeaderEnrichmentEntry 48 }

affirmedServicesContentHttpProxyServiceStatisticsNode-levelHeaderEnrichmentOrigapnencrypted OBJECT-TYPE
    SYNTAX      ConfdString
    MAX-ACCESS  read-only
    STATUS      current
    DESCRIPTION "Header Additions - Original APN Encrypted"
    ::= { affirmedServicesContentHttpProxyServiceStatisticsNode-levelHeaderEnrichmentEntry 49 }

affirmedServicesContentHttpProxyServiceStatisticsNode-levelHeaderEnrichmentSgwipv6addr OBJECT-TYPE
    SYNTAX      ConfdString
    MAX-ACCESS  read-only
    STATUS      current
    DESCRIPTION "Header Additions - SGW IPv6 Address"
    ::= { affirmedServicesContentHttpProxyServiceStatisticsNode-levelHeaderEnrichmentEntry 50 }

affirmedServicesContentHttpProxyServiceStatisticsNode-levelHeaderEnrichmentSgwipv6addrmd5 OBJECT-TYPE
    SYNTAX      ConfdString
    MAX-ACCESS  read-only
    STATUS      current
    DESCRIPTION "Header Additions - SGW IPv6 Address MD5"
    ::= { affirmedServicesContentHttpProxyServiceStatisticsNode-levelHeaderEnrichmentEntry 51 }

affirmedServicesContentHttpProxyServiceStatisticsNode-levelHeaderEnrichmentSgwipv6addrencrypted OBJECT-TYPE
    SYNTAX      ConfdString
    MAX-ACCESS  read-only
    STATUS      current
    DESCRIPTION "Header Additions - SGW IPv6 Address Encrypted"
    ::= { affirmedServicesContentHttpProxyServiceStatisticsNode-levelHeaderEnrichmentEntry 52 }

affirmedServicesContentHttpProxyServiceStatisticsNode-levelHeaderEnrichmentMsisdnstatacr OBJECT-TYPE
    SYNTAX      ConfdString
    MAX-ACCESS  read-only
    STATUS      current
    DESCRIPTION "Header Additions - MSISDN Static ACR"
    ::= { affirmedServicesContentHttpProxyServiceStatisticsNode-levelHeaderEnrichmentEntry 53 }

affirmedServicesContentHttpProxyServiceStatisticsNode-levelHeaderEnrichmentMsisdndynmacr OBJECT-TYPE
    SYNTAX      ConfdString
    MAX-ACCESS  read-only
    STATUS      current
    DESCRIPTION "Header Additions - MSISDN Dynamic ACR"
    ::= { affirmedServicesContentHttpProxyServiceStatisticsNode-levelHeaderEnrichmentEntry 54 }

affirmedServicesContentHttpProxyServiceStatisticsNode-levelHeaderEnrichmentTimezone OBJECT-TYPE
    SYNTAX      ConfdString
    MAX-ACCESS  read-only
    STATUS      current
    DESCRIPTION "Header Additions - Time Zone"
    ::= { affirmedServicesContentHttpProxyServiceStatisticsNode-levelHeaderEnrichmentEntry 55 }

affirmedServicesContentHttpProxyServiceStatisticsNode-levelHeaderEnrichmentHttpversionmd5 OBJECT-TYPE
    SYNTAX      ConfdString
    MAX-ACCESS  read-only
    STATUS      current
    DESCRIPTION "Header Additions - HTTPVersion"
    ::= { affirmedServicesContentHttpProxyServiceStatisticsNode-levelHeaderEnrichmentEntry 56 }

affirmedServicesContentHttpProxyServiceStatisticsNode-levelHeaderEnrichmentHttpversionencrypted OBJECT-TYPE
    SYNTAX      ConfdString
    MAX-ACCESS  read-only
    STATUS      current
    DESCRIPTION "Header Additions - HTTPVersion"
    ::= { affirmedServicesContentHttpProxyServiceStatisticsNode-levelHeaderEnrichmentEntry 57 }

affirmedServicesContentHttpProxyServiceStatisticsGridLevelVideoPacingSummaryTable OBJECT-TYPE
    SYNTAX      SEQUENCE OF AffirmedServicesContentHttpProxyServiceStatisticsGridLevelVideoPacingSummaryEntry
    MAX-ACCESS  not-accessible
    STATUS      current
    DESCRIPTION ""
    ::= { affirmedServicesContentHttpProxyServiceStatisticsGridLevelVideoPacing 1 }

affirmedServicesContentHttpProxyServiceStatisticsGridLevelVideoPacingSummaryEntry OBJECT-TYPE
    SYNTAX      AffirmedServicesContentHttpProxyServiceStatisticsGridLevelVideoPacingSummaryEntry
    MAX-ACCESS  not-accessible
    STATUS      current
    DESCRIPTION ""
    INDEX { affirmedServicesContentHttpProxyServiceStatisticsGridLevelVideoPacingSummaryGrid }
        ::= { affirmedServicesContentHttpProxyServiceStatisticsGridLevelVideoPacingSummaryTable 1 }

AffirmedServicesContentHttpProxyServiceStatisticsGridLevelVideoPacingSummaryEntry ::=
    SEQUENCE {
        affirmedServicesContentHttpProxyServiceStatisticsGridLevelVideoPacingSummaryGrid Unsigned32,
        affirmedServicesContentHttpProxyServiceStatisticsGridLevelVideoPacingSummaryVideopacingattempts ConfdString,
        affirmedServicesContentHttpProxyServiceStatisticsGridLevelVideoPacingSummaryVideopacingsuccesses ConfdString,
        affirmedServicesContentHttpProxyServiceStatisticsGridLevelVideoPacingSummaryVideopacingfailures ConfdString,
        affirmedServicesContentHttpProxyServiceStatisticsGridLevelVideoPacingSummaryVideopacingstalls ConfdString,
        affirmedServicesContentHttpProxyServiceStatisticsGridLevelVideoPacingSummaryVideopacingcurrents ConfdString,
        affirmedServicesContentHttpProxyServiceStatisticsGridLevelVideoPacingSummaryVideopacingserverrsp ConfdString,
        affirmedServicesContentHttpProxyServiceStatisticsGridLevelVideoPacingSummaryVideopacingclientrsp ConfdString,
        affirmedServicesContentHttpProxyServiceStatisticsGridLevelVideoPacingSummaryVideodurationmin ConfdString,
        affirmedServicesContentHttpProxyServiceStatisticsGridLevelVideoPacingSummaryVideodurationmax ConfdString,
        affirmedServicesContentHttpProxyServiceStatisticsGridLevelVideoPacingSummaryVideodurationaverage ConfdString,
        affirmedServicesContentHttpProxyServiceStatisticsGridLevelVideoPacingSummaryVideodurationtotal ConfdString,
        affirmedServicesContentHttpProxyServiceStatisticsGridLevelVideoPacingSummaryVideoservingdurationmin ConfdString,
        affirmedServicesContentHttpProxyServiceStatisticsGridLevelVideoPacingSummaryVideoservingdurationmax ConfdString,
        affirmedServicesContentHttpProxyServiceStatisticsGridLevelVideoPacingSummaryVideoservingdurationaverage ConfdString,
        affirmedServicesContentHttpProxyServiceStatisticsGridLevelVideoPacingSummaryVideoservingdurationtotal ConfdString,
        affirmedServicesContentHttpProxyServiceStatisticsGridLevelVideoPacingSummaryVideostalldurationmin ConfdString,
        affirmedServicesContentHttpProxyServiceStatisticsGridLevelVideoPacingSummaryVideostalldurationmax ConfdString,
        affirmedServicesContentHttpProxyServiceStatisticsGridLevelVideoPacingSummaryVideostalldurationaverage ConfdString,
        affirmedServicesContentHttpProxyServiceStatisticsGridLevelVideoPacingSummaryVideostalldurationtotal ConfdString,
        affirmedServicesContentHttpProxyServiceStatisticsGridLevelVideoPacingSummaryVideobitratemin ConfdString,
        affirmedServicesContentHttpProxyServiceStatisticsGridLevelVideoPacingSummaryVideobitratemax ConfdString,
        affirmedServicesContentHttpProxyServiceStatisticsGridLevelVideoPacingSummaryVideobitrateaverage ConfdString
    }

affirmedServicesContentHttpProxyServiceStatisticsGridLevelVideoPacingSummaryGrid OBJECT-TYPE
    SYNTAX      Unsigned32
    MAX-ACCESS  not-accessible
    STATUS      current
    DESCRIPTION ""
    ::= { affirmedServicesContentHttpProxyServiceStatisticsGridLevelVideoPacingSummaryEntry 1 }

affirmedServicesContentHttpProxyServiceStatisticsGridLevelVideoPacingSummaryVideopacingattempts OBJECT-TYPE
    SYNTAX      ConfdString
    MAX-ACCESS  read-only
    STATUS      deprecated
    DESCRIPTION "Number of video pacing attempts"
    ::= { affirmedServicesContentHttpProxyServiceStatisticsGridLevelVideoPacingSummaryEntry 2 }

affirmedServicesContentHttpProxyServiceStatisticsGridLevelVideoPacingSummaryVideopacingsuccesses OBJECT-TYPE
    SYNTAX      ConfdString
    MAX-ACCESS  read-only
    STATUS      deprecated
    DESCRIPTION "Number of video pacing successes"
    ::= { affirmedServicesContentHttpProxyServiceStatisticsGridLevelVideoPacingSummaryEntry 3 }

affirmedServicesContentHttpProxyServiceStatisticsGridLevelVideoPacingSummaryVideopacingfailures OBJECT-TYPE
    SYNTAX      ConfdString
    MAX-ACCESS  read-only
    STATUS      deprecated
    DESCRIPTION "Number of video pacing failures"
    ::= { affirmedServicesContentHttpProxyServiceStatisticsGridLevelVideoPacingSummaryEntry 4 }

affirmedServicesContentHttpProxyServiceStatisticsGridLevelVideoPacingSummaryVideopacingstalls OBJECT-TYPE
    SYNTAX      ConfdString
    MAX-ACCESS  read-only
    STATUS      deprecated
    DESCRIPTION "Number of video pacing stalls"
    ::= { affirmedServicesContentHttpProxyServiceStatisticsGridLevelVideoPacingSummaryEntry 5 }

affirmedServicesContentHttpProxyServiceStatisticsGridLevelVideoPacingSummaryVideopacingcurrents OBJECT-TYPE
    SYNTAX      ConfdString
    MAX-ACCESS  read-only
    STATUS      deprecated
    DESCRIPTION "Number of video pacing currently paced"
    ::= { affirmedServicesContentHttpProxyServiceStatisticsGridLevelVideoPacingSummaryEntry 6 }

affirmedServicesContentHttpProxyServiceStatisticsGridLevelVideoPacingSummaryVideopacingserverrsp OBJECT-TYPE
    SYNTAX      ConfdString
    MAX-ACCESS  read-only
    STATUS      deprecated
    DESCRIPTION "Number of Bytes from Server Response"
    ::= { affirmedServicesContentHttpProxyServiceStatisticsGridLevelVideoPacingSummaryEntry 7 }

affirmedServicesContentHttpProxyServiceStatisticsGridLevelVideoPacingSummaryVideopacingclientrsp OBJECT-TYPE
    SYNTAX      ConfdString
    MAX-ACCESS  read-only
    STATUS      deprecated
    DESCRIPTION "Number of Bytes from Client Response"
    ::= { affirmedServicesContentHttpProxyServiceStatisticsGridLevelVideoPacingSummaryEntry 8 }

affirmedServicesContentHttpProxyServiceStatisticsGridLevelVideoPacingSummaryVideodurationmin OBJECT-TYPE
    SYNTAX      ConfdString
    MAX-ACCESS  read-only
    STATUS      deprecated
    DESCRIPTION "Minimum video duration in seconds"
    ::= { affirmedServicesContentHttpProxyServiceStatisticsGridLevelVideoPacingSummaryEntry 9 }

affirmedServicesContentHttpProxyServiceStatisticsGridLevelVideoPacingSummaryVideodurationmax OBJECT-TYPE
    SYNTAX      ConfdString
    MAX-ACCESS  read-only
    STATUS      deprecated
    DESCRIPTION "Maximum video duration in seconds"
    ::= { affirmedServicesContentHttpProxyServiceStatisticsGridLevelVideoPacingSummaryEntry 10 }

affirmedServicesContentHttpProxyServiceStatisticsGridLevelVideoPacingSummaryVideodurationaverage OBJECT-TYPE
    SYNTAX      ConfdString
    MAX-ACCESS  read-only
    STATUS      deprecated
    DESCRIPTION "Average video duration in seconds"
    ::= { affirmedServicesContentHttpProxyServiceStatisticsGridLevelVideoPacingSummaryEntry 11 }

affirmedServicesContentHttpProxyServiceStatisticsGridLevelVideoPacingSummaryVideodurationtotal OBJECT-TYPE
    SYNTAX      ConfdString
    MAX-ACCESS  read-only
    STATUS      deprecated
    DESCRIPTION "Total video duration in seconds"
    ::= { affirmedServicesContentHttpProxyServiceStatisticsGridLevelVideoPacingSummaryEntry 12 }

affirmedServicesContentHttpProxyServiceStatisticsGridLevelVideoPacingSummaryVideoservingdurationmin OBJECT-TYPE
    SYNTAX      ConfdString
    MAX-ACCESS  read-only
    STATUS      deprecated
    DESCRIPTION "Minimum video serving duration in seconds"
    ::= { affirmedServicesContentHttpProxyServiceStatisticsGridLevelVideoPacingSummaryEntry 13 }

affirmedServicesContentHttpProxyServiceStatisticsGridLevelVideoPacingSummaryVideoservingdurationmax OBJECT-TYPE
    SYNTAX      ConfdString
    MAX-ACCESS  read-only
    STATUS      deprecated
    DESCRIPTION "Maximum video serving duration in seconds"
    ::= { affirmedServicesContentHttpProxyServiceStatisticsGridLevelVideoPacingSummaryEntry 14 }

affirmedServicesContentHttpProxyServiceStatisticsGridLevelVideoPacingSummaryVideoservingdurationaverage OBJECT-TYPE
    SYNTAX      ConfdString
    MAX-ACCESS  read-only
    STATUS      deprecated
    DESCRIPTION "Average video serving duration in seconds"
    ::= { affirmedServicesContentHttpProxyServiceStatisticsGridLevelVideoPacingSummaryEntry 15 }

affirmedServicesContentHttpProxyServiceStatisticsGridLevelVideoPacingSummaryVideoservingdurationtotal OBJECT-TYPE
    SYNTAX      ConfdString
    MAX-ACCESS  read-only
    STATUS      deprecated
    DESCRIPTION "Total video serving duration in seconds"
    ::= { affirmedServicesContentHttpProxyServiceStatisticsGridLevelVideoPacingSummaryEntry 16 }

affirmedServicesContentHttpProxyServiceStatisticsGridLevelVideoPacingSummaryVideostalldurationmin OBJECT-TYPE
    SYNTAX      ConfdString
    MAX-ACCESS  read-only
    STATUS      deprecated
    DESCRIPTION "Minimum video pacing stall duration in seconds"
    ::= { affirmedServicesContentHttpProxyServiceStatisticsGridLevelVideoPacingSummaryEntry 17 }

affirmedServicesContentHttpProxyServiceStatisticsGridLevelVideoPacingSummaryVideostalldurationmax OBJECT-TYPE
    SYNTAX      ConfdString
    MAX-ACCESS  read-only
    STATUS      deprecated
    DESCRIPTION "Maximum video pacing stall duration in seconds"
    ::= { affirmedServicesContentHttpProxyServiceStatisticsGridLevelVideoPacingSummaryEntry 18 }

affirmedServicesContentHttpProxyServiceStatisticsGridLevelVideoPacingSummaryVideostalldurationaverage OBJECT-TYPE
    SYNTAX      ConfdString
    MAX-ACCESS  read-only
    STATUS      deprecated
    DESCRIPTION "Average video pacing stall duration in seconds"
    ::= { affirmedServicesContentHttpProxyServiceStatisticsGridLevelVideoPacingSummaryEntry 19 }

affirmedServicesContentHttpProxyServiceStatisticsGridLevelVideoPacingSummaryVideostalldurationtotal OBJECT-TYPE
    SYNTAX      ConfdString
    MAX-ACCESS  read-only
    STATUS      deprecated
    DESCRIPTION "Total video pacing stall duration in seconds"
    ::= { affirmedServicesContentHttpProxyServiceStatisticsGridLevelVideoPacingSummaryEntry 20 }

affirmedServicesContentHttpProxyServiceStatisticsGridLevelVideoPacingSummaryVideobitratemin OBJECT-TYPE
    SYNTAX      ConfdString
    MAX-ACCESS  read-only
    STATUS      deprecated
    DESCRIPTION "Minimum video bitrate in kbps"
    ::= { affirmedServicesContentHttpProxyServiceStatisticsGridLevelVideoPacingSummaryEntry 21 }

affirmedServicesContentHttpProxyServiceStatisticsGridLevelVideoPacingSummaryVideobitratemax OBJECT-TYPE
    SYNTAX      ConfdString
    MAX-ACCESS  read-only
    STATUS      deprecated
    DESCRIPTION "Maximum video bitrate in kbps"
    ::= { affirmedServicesContentHttpProxyServiceStatisticsGridLevelVideoPacingSummaryEntry 22 }

affirmedServicesContentHttpProxyServiceStatisticsGridLevelVideoPacingSummaryVideobitrateaverage OBJECT-TYPE
    SYNTAX      ConfdString
    MAX-ACCESS  read-only
    STATUS      deprecated
    DESCRIPTION "Average video bitrate in kbps"
    ::= { affirmedServicesContentHttpProxyServiceStatisticsGridLevelVideoPacingSummaryEntry 23 }

affirmedServicesContentHttpProxyServiceStatisticsGridLevelVideoPacingDetailMp4Table OBJECT-TYPE
    SYNTAX      SEQUENCE OF AffirmedServicesContentHttpProxyServiceStatisticsGridLevelVideoPacingDetailMp4Entry
    MAX-ACCESS  not-accessible
    STATUS      current
    DESCRIPTION ""
    ::= { affirmedServicesContentHttpProxyServiceStatisticsGridLevelVideoPacingDetail 1 }

affirmedServicesContentHttpProxyServiceStatisticsGridLevelVideoPacingDetailMp4Entry OBJECT-TYPE
    SYNTAX      AffirmedServicesContentHttpProxyServiceStatisticsGridLevelVideoPacingDetailMp4Entry
    MAX-ACCESS  not-accessible
    STATUS      current
    DESCRIPTION ""
    INDEX { affirmedServicesContentHttpProxyServiceStatisticsGridLevelVideoPacingDetailMp4Grid }
        ::= { affirmedServicesContentHttpProxyServiceStatisticsGridLevelVideoPacingDetailMp4Table 1 }

AffirmedServicesContentHttpProxyServiceStatisticsGridLevelVideoPacingDetailMp4Entry ::=
    SEQUENCE {
        affirmedServicesContentHttpProxyServiceStatisticsGridLevelVideoPacingDetailMp4Grid Unsigned32,
        affirmedServicesContentHttpProxyServiceStatisticsGridLevelVideoPacingDetailMp4Videopacingattempts ConfdString,
        affirmedServicesContentHttpProxyServiceStatisticsGridLevelVideoPacingDetailMp4Videopacingsuccesses ConfdString,
        affirmedServicesContentHttpProxyServiceStatisticsGridLevelVideoPacingDetailMp4Videopacingfailures ConfdString,
        affirmedServicesContentHttpProxyServiceStatisticsGridLevelVideoPacingDetailMp4Videopacingserverrsp ConfdString,
        affirmedServicesContentHttpProxyServiceStatisticsGridLevelVideoPacingDetailMp4Videopacingclientrsp ConfdString,
        affirmedServicesContentHttpProxyServiceStatisticsGridLevelVideoPacingDetailMp4Videodurationmin ConfdString,
        affirmedServicesContentHttpProxyServiceStatisticsGridLevelVideoPacingDetailMp4Videodurationmax ConfdString,
        affirmedServicesContentHttpProxyServiceStatisticsGridLevelVideoPacingDetailMp4Videodurationaverage ConfdString,
        affirmedServicesContentHttpProxyServiceStatisticsGridLevelVideoPacingDetailMp4Videodurationtotal ConfdString,
        affirmedServicesContentHttpProxyServiceStatisticsGridLevelVideoPacingDetailMp4Videoservingdurationmin ConfdString,
        affirmedServicesContentHttpProxyServiceStatisticsGridLevelVideoPacingDetailMp4Videoservingdurationmax ConfdString,
        affirmedServicesContentHttpProxyServiceStatisticsGridLevelVideoPacingDetailMp4Videoservingdurationaverage ConfdString,
        affirmedServicesContentHttpProxyServiceStatisticsGridLevelVideoPacingDetailMp4Videoservingdurationtotal ConfdString,
        affirmedServicesContentHttpProxyServiceStatisticsGridLevelVideoPacingDetailMp4Videobitratemin ConfdString,
        affirmedServicesContentHttpProxyServiceStatisticsGridLevelVideoPacingDetailMp4Videobitratemax ConfdString,
        affirmedServicesContentHttpProxyServiceStatisticsGridLevelVideoPacingDetailMp4Videobitrateaverage ConfdString
    }

affirmedServicesContentHttpProxyServiceStatisticsGridLevelVideoPacingDetailMp4Grid OBJECT-TYPE
    SYNTAX      Unsigned32
    MAX-ACCESS  not-accessible
    STATUS      current
    DESCRIPTION ""
    ::= { affirmedServicesContentHttpProxyServiceStatisticsGridLevelVideoPacingDetailMp4Entry 1 }

affirmedServicesContentHttpProxyServiceStatisticsGridLevelVideoPacingDetailMp4Videopacingattempts OBJECT-TYPE
    SYNTAX      ConfdString
    MAX-ACCESS  read-only
    STATUS      deprecated
    DESCRIPTION "Number of video pacing attempts"
    ::= { affirmedServicesContentHttpProxyServiceStatisticsGridLevelVideoPacingDetailMp4Entry 2 }

affirmedServicesContentHttpProxyServiceStatisticsGridLevelVideoPacingDetailMp4Videopacingsuccesses OBJECT-TYPE
    SYNTAX      ConfdString
    MAX-ACCESS  read-only
    STATUS      deprecated
    DESCRIPTION "Number of video pacing successes"
    ::= { affirmedServicesContentHttpProxyServiceStatisticsGridLevelVideoPacingDetailMp4Entry 3 }

affirmedServicesContentHttpProxyServiceStatisticsGridLevelVideoPacingDetailMp4Videopacingfailures OBJECT-TYPE
    SYNTAX      ConfdString
    MAX-ACCESS  read-only
    STATUS      deprecated
    DESCRIPTION "Number of video pacing failures"
    ::= { affirmedServicesContentHttpProxyServiceStatisticsGridLevelVideoPacingDetailMp4Entry 4 }

affirmedServicesContentHttpProxyServiceStatisticsGridLevelVideoPacingDetailMp4Videopacingserverrsp OBJECT-TYPE
    SYNTAX      ConfdString
    MAX-ACCESS  read-only
    STATUS      deprecated
    DESCRIPTION "Number of Bytes from Server Response"
    ::= { affirmedServicesContentHttpProxyServiceStatisticsGridLevelVideoPacingDetailMp4Entry 5 }

affirmedServicesContentHttpProxyServiceStatisticsGridLevelVideoPacingDetailMp4Videopacingclientrsp OBJECT-TYPE
    SYNTAX      ConfdString
    MAX-ACCESS  read-only
    STATUS      deprecated
    DESCRIPTION "Number of Bytes from Client Response"
    ::= { affirmedServicesContentHttpProxyServiceStatisticsGridLevelVideoPacingDetailMp4Entry 6 }

affirmedServicesContentHttpProxyServiceStatisticsGridLevelVideoPacingDetailMp4Videodurationmin OBJECT-TYPE
    SYNTAX      ConfdString
    MAX-ACCESS  read-only
    STATUS      deprecated
    DESCRIPTION "Minimum video duration in seconds"
    ::= { affirmedServicesContentHttpProxyServiceStatisticsGridLevelVideoPacingDetailMp4Entry 7 }

affirmedServicesContentHttpProxyServiceStatisticsGridLevelVideoPacingDetailMp4Videodurationmax OBJECT-TYPE
    SYNTAX      ConfdString
    MAX-ACCESS  read-only
    STATUS      deprecated
    DESCRIPTION "Maximum video duration in seconds"
    ::= { affirmedServicesContentHttpProxyServiceStatisticsGridLevelVideoPacingDetailMp4Entry 8 }

affirmedServicesContentHttpProxyServiceStatisticsGridLevelVideoPacingDetailMp4Videodurationaverage OBJECT-TYPE
    SYNTAX      ConfdString
    MAX-ACCESS  read-only
    STATUS      deprecated
    DESCRIPTION "Average video duration in seconds"
    ::= { affirmedServicesContentHttpProxyServiceStatisticsGridLevelVideoPacingDetailMp4Entry 9 }

affirmedServicesContentHttpProxyServiceStatisticsGridLevelVideoPacingDetailMp4Videodurationtotal OBJECT-TYPE
    SYNTAX      ConfdString
    MAX-ACCESS  read-only
    STATUS      deprecated
    DESCRIPTION "Total video duration in seconds"
    ::= { affirmedServicesContentHttpProxyServiceStatisticsGridLevelVideoPacingDetailMp4Entry 10 }

affirmedServicesContentHttpProxyServiceStatisticsGridLevelVideoPacingDetailMp4Videoservingdurationmin OBJECT-TYPE
    SYNTAX      ConfdString
    MAX-ACCESS  read-only
    STATUS      deprecated
    DESCRIPTION "Minimum video serving duration in seconds"
    ::= { affirmedServicesContentHttpProxyServiceStatisticsGridLevelVideoPacingDetailMp4Entry 11 }

affirmedServicesContentHttpProxyServiceStatisticsGridLevelVideoPacingDetailMp4Videoservingdurationmax OBJECT-TYPE
    SYNTAX      ConfdString
    MAX-ACCESS  read-only
    STATUS      deprecated
    DESCRIPTION "Maximum video serving duration in seconds"
    ::= { affirmedServicesContentHttpProxyServiceStatisticsGridLevelVideoPacingDetailMp4Entry 12 }

affirmedServicesContentHttpProxyServiceStatisticsGridLevelVideoPacingDetailMp4Videoservingdurationaverage OBJECT-TYPE
    SYNTAX      ConfdString
    MAX-ACCESS  read-only
    STATUS      deprecated
    DESCRIPTION "Average video serving duration in seconds"
    ::= { affirmedServicesContentHttpProxyServiceStatisticsGridLevelVideoPacingDetailMp4Entry 13 }

affirmedServicesContentHttpProxyServiceStatisticsGridLevelVideoPacingDetailMp4Videoservingdurationtotal OBJECT-TYPE
    SYNTAX      ConfdString
    MAX-ACCESS  read-only
    STATUS      deprecated
    DESCRIPTION "Total video serving duration in seconds"
    ::= { affirmedServicesContentHttpProxyServiceStatisticsGridLevelVideoPacingDetailMp4Entry 14 }

affirmedServicesContentHttpProxyServiceStatisticsGridLevelVideoPacingDetailMp4Videobitratemin OBJECT-TYPE
    SYNTAX      ConfdString
    MAX-ACCESS  read-only
    STATUS      deprecated
    DESCRIPTION "Minimum video bitrate in kbps"
    ::= { affirmedServicesContentHttpProxyServiceStatisticsGridLevelVideoPacingDetailMp4Entry 15 }

affirmedServicesContentHttpProxyServiceStatisticsGridLevelVideoPacingDetailMp4Videobitratemax OBJECT-TYPE
    SYNTAX      ConfdString
    MAX-ACCESS  read-only
    STATUS      deprecated
    DESCRIPTION "Maximum video bitrate in kbps"
    ::= { affirmedServicesContentHttpProxyServiceStatisticsGridLevelVideoPacingDetailMp4Entry 16 }

affirmedServicesContentHttpProxyServiceStatisticsGridLevelVideoPacingDetailMp4Videobitrateaverage OBJECT-TYPE
    SYNTAX      ConfdString
    MAX-ACCESS  read-only
    STATUS      deprecated
    DESCRIPTION "Average video bitrate in kbps"
    ::= { affirmedServicesContentHttpProxyServiceStatisticsGridLevelVideoPacingDetailMp4Entry 17 }

affirmedServicesContentHttpProxyServiceStatisticsGridLevelVideoPacingDetailFlvTable OBJECT-TYPE
    SYNTAX      SEQUENCE OF AffirmedServicesContentHttpProxyServiceStatisticsGridLevelVideoPacingDetailFlvEntry
    MAX-ACCESS  not-accessible
    STATUS      current
    DESCRIPTION ""
    ::= { affirmedServicesContentHttpProxyServiceStatisticsGridLevelVideoPacingDetail 2 }

affirmedServicesContentHttpProxyServiceStatisticsGridLevelVideoPacingDetailFlvEntry OBJECT-TYPE
    SYNTAX      AffirmedServicesContentHttpProxyServiceStatisticsGridLevelVideoPacingDetailFlvEntry
    MAX-ACCESS  not-accessible
    STATUS      current
    DESCRIPTION ""
    INDEX { affirmedServicesContentHttpProxyServiceStatisticsGridLevelVideoPacingDetailFlvGrid }
        ::= { affirmedServicesContentHttpProxyServiceStatisticsGridLevelVideoPacingDetailFlvTable 1 }

AffirmedServicesContentHttpProxyServiceStatisticsGridLevelVideoPacingDetailFlvEntry ::=
    SEQUENCE {
        affirmedServicesContentHttpProxyServiceStatisticsGridLevelVideoPacingDetailFlvGrid Unsigned32,
        affirmedServicesContentHttpProxyServiceStatisticsGridLevelVideoPacingDetailFlvVideopacingattempts ConfdString,
        affirmedServicesContentHttpProxyServiceStatisticsGridLevelVideoPacingDetailFlvVideopacingsuccesses ConfdString,
        affirmedServicesContentHttpProxyServiceStatisticsGridLevelVideoPacingDetailFlvVideopacingfailures ConfdString,
        affirmedServicesContentHttpProxyServiceStatisticsGridLevelVideoPacingDetailFlvVideopacingserverrsp ConfdString,
        affirmedServicesContentHttpProxyServiceStatisticsGridLevelVideoPacingDetailFlvVideopacingclientrsp ConfdString,
        affirmedServicesContentHttpProxyServiceStatisticsGridLevelVideoPacingDetailFlvVideodurationmin ConfdString,
        affirmedServicesContentHttpProxyServiceStatisticsGridLevelVideoPacingDetailFlvVideodurationmax ConfdString,
        affirmedServicesContentHttpProxyServiceStatisticsGridLevelVideoPacingDetailFlvVideodurationaverage ConfdString,
        affirmedServicesContentHttpProxyServiceStatisticsGridLevelVideoPacingDetailFlvVideodurationtotal ConfdString,
        affirmedServicesContentHttpProxyServiceStatisticsGridLevelVideoPacingDetailFlvVideoservingdurationmin ConfdString,
        affirmedServicesContentHttpProxyServiceStatisticsGridLevelVideoPacingDetailFlvVideoservingdurationmax ConfdString,
        affirmedServicesContentHttpProxyServiceStatisticsGridLevelVideoPacingDetailFlvVideoservingdurationaverage ConfdString,
        affirmedServicesContentHttpProxyServiceStatisticsGridLevelVideoPacingDetailFlvVideoservingdurationtotal ConfdString,
        affirmedServicesContentHttpProxyServiceStatisticsGridLevelVideoPacingDetailFlvVideobitratemin ConfdString,
        affirmedServicesContentHttpProxyServiceStatisticsGridLevelVideoPacingDetailFlvVideobitratemax ConfdString,
        affirmedServicesContentHttpProxyServiceStatisticsGridLevelVideoPacingDetailFlvVideobitrateaverage ConfdString
    }

affirmedServicesContentHttpProxyServiceStatisticsGridLevelVideoPacingDetailFlvGrid OBJECT-TYPE
    SYNTAX      Unsigned32
    MAX-ACCESS  not-accessible
    STATUS      current
    DESCRIPTION ""
    ::= { affirmedServicesContentHttpProxyServiceStatisticsGridLevelVideoPacingDetailFlvEntry 1 }

affirmedServicesContentHttpProxyServiceStatisticsGridLevelVideoPacingDetailFlvVideopacingattempts OBJECT-TYPE
    SYNTAX      ConfdString
    MAX-ACCESS  read-only
    STATUS      deprecated
    DESCRIPTION "Number of video pacing attempts"
    ::= { affirmedServicesContentHttpProxyServiceStatisticsGridLevelVideoPacingDetailFlvEntry 2 }

affirmedServicesContentHttpProxyServiceStatisticsGridLevelVideoPacingDetailFlvVideopacingsuccesses OBJECT-TYPE
    SYNTAX      ConfdString
    MAX-ACCESS  read-only
    STATUS      deprecated
    DESCRIPTION "Number of video pacing successes"
    ::= { affirmedServicesContentHttpProxyServiceStatisticsGridLevelVideoPacingDetailFlvEntry 3 }

affirmedServicesContentHttpProxyServiceStatisticsGridLevelVideoPacingDetailFlvVideopacingfailures OBJECT-TYPE
    SYNTAX      ConfdString
    MAX-ACCESS  read-only
    STATUS      deprecated
    DESCRIPTION "Number of video pacing failures"
    ::= { affirmedServicesContentHttpProxyServiceStatisticsGridLevelVideoPacingDetailFlvEntry 4 }

affirmedServicesContentHttpProxyServiceStatisticsGridLevelVideoPacingDetailFlvVideopacingserverrsp OBJECT-TYPE
    SYNTAX      ConfdString
    MAX-ACCESS  read-only
    STATUS      deprecated
    DESCRIPTION "Number of Bytes from Server Response"
    ::= { affirmedServicesContentHttpProxyServiceStatisticsGridLevelVideoPacingDetailFlvEntry 5 }

affirmedServicesContentHttpProxyServiceStatisticsGridLevelVideoPacingDetailFlvVideopacingclientrsp OBJECT-TYPE
    SYNTAX      ConfdString
    MAX-ACCESS  read-only
    STATUS      deprecated
    DESCRIPTION "Number of Bytes from Client Response"
    ::= { affirmedServicesContentHttpProxyServiceStatisticsGridLevelVideoPacingDetailFlvEntry 6 }

affirmedServicesContentHttpProxyServiceStatisticsGridLevelVideoPacingDetailFlvVideodurationmin OBJECT-TYPE
    SYNTAX      ConfdString
    MAX-ACCESS  read-only
    STATUS      deprecated
    DESCRIPTION "Minimum video duration in seconds"
    ::= { affirmedServicesContentHttpProxyServiceStatisticsGridLevelVideoPacingDetailFlvEntry 7 }

affirmedServicesContentHttpProxyServiceStatisticsGridLevelVideoPacingDetailFlvVideodurationmax OBJECT-TYPE
    SYNTAX      ConfdString
    MAX-ACCESS  read-only
    STATUS      deprecated
    DESCRIPTION "Maximum video duration in seconds"
    ::= { affirmedServicesContentHttpProxyServiceStatisticsGridLevelVideoPacingDetailFlvEntry 8 }

affirmedServicesContentHttpProxyServiceStatisticsGridLevelVideoPacingDetailFlvVideodurationaverage OBJECT-TYPE
    SYNTAX      ConfdString
    MAX-ACCESS  read-only
    STATUS      deprecated
    DESCRIPTION "Average video duration in seconds"
    ::= { affirmedServicesContentHttpProxyServiceStatisticsGridLevelVideoPacingDetailFlvEntry 9 }

affirmedServicesContentHttpProxyServiceStatisticsGridLevelVideoPacingDetailFlvVideodurationtotal OBJECT-TYPE
    SYNTAX      ConfdString
    MAX-ACCESS  read-only
    STATUS      deprecated
    DESCRIPTION "Total video duration in seconds"
    ::= { affirmedServicesContentHttpProxyServiceStatisticsGridLevelVideoPacingDetailFlvEntry 10 }

affirmedServicesContentHttpProxyServiceStatisticsGridLevelVideoPacingDetailFlvVideoservingdurationmin OBJECT-TYPE
    SYNTAX      ConfdString
    MAX-ACCESS  read-only
    STATUS      deprecated
    DESCRIPTION "Minimum video serving duration in seconds"
    ::= { affirmedServicesContentHttpProxyServiceStatisticsGridLevelVideoPacingDetailFlvEntry 11 }

affirmedServicesContentHttpProxyServiceStatisticsGridLevelVideoPacingDetailFlvVideoservingdurationmax OBJECT-TYPE
    SYNTAX      ConfdString
    MAX-ACCESS  read-only
    STATUS      deprecated
    DESCRIPTION "Maximum video serving duration in seconds"
    ::= { affirmedServicesContentHttpProxyServiceStatisticsGridLevelVideoPacingDetailFlvEntry 12 }

affirmedServicesContentHttpProxyServiceStatisticsGridLevelVideoPacingDetailFlvVideoservingdurationaverage OBJECT-TYPE
    SYNTAX      ConfdString
    MAX-ACCESS  read-only
    STATUS      deprecated
    DESCRIPTION "Average video serving duration in seconds"
    ::= { affirmedServicesContentHttpProxyServiceStatisticsGridLevelVideoPacingDetailFlvEntry 13 }

affirmedServicesContentHttpProxyServiceStatisticsGridLevelVideoPacingDetailFlvVideoservingdurationtotal OBJECT-TYPE
    SYNTAX      ConfdString
    MAX-ACCESS  read-only
    STATUS      deprecated
    DESCRIPTION "Total video serving duration in seconds"
    ::= { affirmedServicesContentHttpProxyServiceStatisticsGridLevelVideoPacingDetailFlvEntry 14 }

affirmedServicesContentHttpProxyServiceStatisticsGridLevelVideoPacingDetailFlvVideobitratemin OBJECT-TYPE
    SYNTAX      ConfdString
    MAX-ACCESS  read-only
    STATUS      deprecated
    DESCRIPTION "Minimum video bitrate in kbps"
    ::= { affirmedServicesContentHttpProxyServiceStatisticsGridLevelVideoPacingDetailFlvEntry 15 }

affirmedServicesContentHttpProxyServiceStatisticsGridLevelVideoPacingDetailFlvVideobitratemax OBJECT-TYPE
    SYNTAX      ConfdString
    MAX-ACCESS  read-only
    STATUS      deprecated
    DESCRIPTION "Maximum video bitrate in kbps"
    ::= { affirmedServicesContentHttpProxyServiceStatisticsGridLevelVideoPacingDetailFlvEntry 16 }

affirmedServicesContentHttpProxyServiceStatisticsGridLevelVideoPacingDetailFlvVideobitrateaverage OBJECT-TYPE
    SYNTAX      ConfdString
    MAX-ACCESS  read-only
    STATUS      deprecated
    DESCRIPTION "Average video bitrate in kbps"
    ::= { affirmedServicesContentHttpProxyServiceStatisticsGridLevelVideoPacingDetailFlvEntry 17 }

affirmedServicesContentHttpProxyServiceStatisticsGridLevelVideoPacingDetailWebmTable OBJECT-TYPE
    SYNTAX      SEQUENCE OF AffirmedServicesContentHttpProxyServiceStatisticsGridLevelVideoPacingDetailWebmEntry
    MAX-ACCESS  not-accessible
    STATUS      current
    DESCRIPTION ""
    ::= { affirmedServicesContentHttpProxyServiceStatisticsGridLevelVideoPacingDetail 3 }

affirmedServicesContentHttpProxyServiceStatisticsGridLevelVideoPacingDetailWebmEntry OBJECT-TYPE
    SYNTAX      AffirmedServicesContentHttpProxyServiceStatisticsGridLevelVideoPacingDetailWebmEntry
    MAX-ACCESS  not-accessible
    STATUS      current
    DESCRIPTION ""
    INDEX { affirmedServicesContentHttpProxyServiceStatisticsGridLevelVideoPacingDetailWebmGrid }
        ::= { affirmedServicesContentHttpProxyServiceStatisticsGridLevelVideoPacingDetailWebmTable 1 }

AffirmedServicesContentHttpProxyServiceStatisticsGridLevelVideoPacingDetailWebmEntry ::=
    SEQUENCE {
        affirmedServicesContentHttpProxyServiceStatisticsGridLevelVideoPacingDetailWebmGrid Unsigned32,
        affirmedServicesContentHttpProxyServiceStatisticsGridLevelVideoPacingDetailWebmVideopacingattempts ConfdString,
        affirmedServicesContentHttpProxyServiceStatisticsGridLevelVideoPacingDetailWebmVideopacingsuccesses ConfdString,
        affirmedServicesContentHttpProxyServiceStatisticsGridLevelVideoPacingDetailWebmVideopacingfailures ConfdString,
        affirmedServicesContentHttpProxyServiceStatisticsGridLevelVideoPacingDetailWebmVideopacingserverrsp ConfdString,
        affirmedServicesContentHttpProxyServiceStatisticsGridLevelVideoPacingDetailWebmVideopacingclientrsp ConfdString,
        affirmedServicesContentHttpProxyServiceStatisticsGridLevelVideoPacingDetailWebmVideodurationmin ConfdString,
        affirmedServicesContentHttpProxyServiceStatisticsGridLevelVideoPacingDetailWebmVideodurationmax ConfdString,
        affirmedServicesContentHttpProxyServiceStatisticsGridLevelVideoPacingDetailWebmVideodurationaverage ConfdString,
        affirmedServicesContentHttpProxyServiceStatisticsGridLevelVideoPacingDetailWebmVideodurationtotal ConfdString,
        affirmedServicesContentHttpProxyServiceStatisticsGridLevelVideoPacingDetailWebmVideoservingdurationmin ConfdString,
        affirmedServicesContentHttpProxyServiceStatisticsGridLevelVideoPacingDetailWebmVideoservingdurationmax ConfdString,
        affirmedServicesContentHttpProxyServiceStatisticsGridLevelVideoPacingDetailWebmVideoservingdurationaverage ConfdString,
        affirmedServicesContentHttpProxyServiceStatisticsGridLevelVideoPacingDetailWebmVideoservingdurationtotal ConfdString,
        affirmedServicesContentHttpProxyServiceStatisticsGridLevelVideoPacingDetailWebmVideobitratemin ConfdString,
        affirmedServicesContentHttpProxyServiceStatisticsGridLevelVideoPacingDetailWebmVideobitratemax ConfdString,
        affirmedServicesContentHttpProxyServiceStatisticsGridLevelVideoPacingDetailWebmVideobitrateaverage ConfdString
    }

affirmedServicesContentHttpProxyServiceStatisticsGridLevelVideoPacingDetailWebmGrid OBJECT-TYPE
    SYNTAX      Unsigned32
    MAX-ACCESS  not-accessible
    STATUS      current
    DESCRIPTION ""
    ::= { affirmedServicesContentHttpProxyServiceStatisticsGridLevelVideoPacingDetailWebmEntry 1 }

affirmedServicesContentHttpProxyServiceStatisticsGridLevelVideoPacingDetailWebmVideopacingattempts OBJECT-TYPE
    SYNTAX      ConfdString
    MAX-ACCESS  read-only
    STATUS      deprecated
    DESCRIPTION "Number of video pacing attempts"
    ::= { affirmedServicesContentHttpProxyServiceStatisticsGridLevelVideoPacingDetailWebmEntry 2 }

affirmedServicesContentHttpProxyServiceStatisticsGridLevelVideoPacingDetailWebmVideopacingsuccesses OBJECT-TYPE
    SYNTAX      ConfdString
    MAX-ACCESS  read-only
    STATUS      deprecated
    DESCRIPTION "Number of video pacing successes"
    ::= { affirmedServicesContentHttpProxyServiceStatisticsGridLevelVideoPacingDetailWebmEntry 3 }

affirmedServicesContentHttpProxyServiceStatisticsGridLevelVideoPacingDetailWebmVideopacingfailures OBJECT-TYPE
    SYNTAX      ConfdString
    MAX-ACCESS  read-only
    STATUS      deprecated
    DESCRIPTION "Number of video pacing failures"
    ::= { affirmedServicesContentHttpProxyServiceStatisticsGridLevelVideoPacingDetailWebmEntry 4 }

affirmedServicesContentHttpProxyServiceStatisticsGridLevelVideoPacingDetailWebmVideopacingserverrsp OBJECT-TYPE
    SYNTAX      ConfdString
    MAX-ACCESS  read-only
    STATUS      deprecated
    DESCRIPTION "Number of Bytes from Server Response"
    ::= { affirmedServicesContentHttpProxyServiceStatisticsGridLevelVideoPacingDetailWebmEntry 5 }

affirmedServicesContentHttpProxyServiceStatisticsGridLevelVideoPacingDetailWebmVideopacingclientrsp OBJECT-TYPE
    SYNTAX      ConfdString
    MAX-ACCESS  read-only
    STATUS      deprecated
    DESCRIPTION "Number of Bytes from Client Response"
    ::= { affirmedServicesContentHttpProxyServiceStatisticsGridLevelVideoPacingDetailWebmEntry 6 }

affirmedServicesContentHttpProxyServiceStatisticsGridLevelVideoPacingDetailWebmVideodurationmin OBJECT-TYPE
    SYNTAX      ConfdString
    MAX-ACCESS  read-only
    STATUS      deprecated
    DESCRIPTION "Minimum video duration in seconds"
    ::= { affirmedServicesContentHttpProxyServiceStatisticsGridLevelVideoPacingDetailWebmEntry 7 }

affirmedServicesContentHttpProxyServiceStatisticsGridLevelVideoPacingDetailWebmVideodurationmax OBJECT-TYPE
    SYNTAX      ConfdString
    MAX-ACCESS  read-only
    STATUS      deprecated
    DESCRIPTION "Maximum video duration in seconds"
    ::= { affirmedServicesContentHttpProxyServiceStatisticsGridLevelVideoPacingDetailWebmEntry 8 }

affirmedServicesContentHttpProxyServiceStatisticsGridLevelVideoPacingDetailWebmVideodurationaverage OBJECT-TYPE
    SYNTAX      ConfdString
    MAX-ACCESS  read-only
    STATUS      deprecated
    DESCRIPTION "Average video duration in seconds"
    ::= { affirmedServicesContentHttpProxyServiceStatisticsGridLevelVideoPacingDetailWebmEntry 9 }

affirmedServicesContentHttpProxyServiceStatisticsGridLevelVideoPacingDetailWebmVideodurationtotal OBJECT-TYPE
    SYNTAX      ConfdString
    MAX-ACCESS  read-only
    STATUS      deprecated
    DESCRIPTION "Total video duration in seconds"
    ::= { affirmedServicesContentHttpProxyServiceStatisticsGridLevelVideoPacingDetailWebmEntry 10 }

affirmedServicesContentHttpProxyServiceStatisticsGridLevelVideoPacingDetailWebmVideoservingdurationmin OBJECT-TYPE
    SYNTAX      ConfdString
    MAX-ACCESS  read-only
    STATUS      deprecated
    DESCRIPTION "Minimum video serving duration in seconds"
    ::= { affirmedServicesContentHttpProxyServiceStatisticsGridLevelVideoPacingDetailWebmEntry 11 }

affirmedServicesContentHttpProxyServiceStatisticsGridLevelVideoPacingDetailWebmVideoservingdurationmax OBJECT-TYPE
    SYNTAX      ConfdString
    MAX-ACCESS  read-only
    STATUS      deprecated
    DESCRIPTION "Maximum video serving duration in seconds"
    ::= { affirmedServicesContentHttpProxyServiceStatisticsGridLevelVideoPacingDetailWebmEntry 12 }

affirmedServicesContentHttpProxyServiceStatisticsGridLevelVideoPacingDetailWebmVideoservingdurationaverage OBJECT-TYPE
    SYNTAX      ConfdString
    MAX-ACCESS  read-only
    STATUS      deprecated
    DESCRIPTION "Average video serving duration in seconds"
    ::= { affirmedServicesContentHttpProxyServiceStatisticsGridLevelVideoPacingDetailWebmEntry 13 }

affirmedServicesContentHttpProxyServiceStatisticsGridLevelVideoPacingDetailWebmVideoservingdurationtotal OBJECT-TYPE
    SYNTAX      ConfdString
    MAX-ACCESS  read-only
    STATUS      deprecated
    DESCRIPTION "Total video serving duration in seconds"
    ::= { affirmedServicesContentHttpProxyServiceStatisticsGridLevelVideoPacingDetailWebmEntry 14 }

affirmedServicesContentHttpProxyServiceStatisticsGridLevelVideoPacingDetailWebmVideobitratemin OBJECT-TYPE
    SYNTAX      ConfdString
    MAX-ACCESS  read-only
    STATUS      deprecated
    DESCRIPTION "Minimum video bitrate in kbps"
    ::= { affirmedServicesContentHttpProxyServiceStatisticsGridLevelVideoPacingDetailWebmEntry 15 }

affirmedServicesContentHttpProxyServiceStatisticsGridLevelVideoPacingDetailWebmVideobitratemax OBJECT-TYPE
    SYNTAX      ConfdString
    MAX-ACCESS  read-only
    STATUS      deprecated
    DESCRIPTION "Maximum video bitrate in kbps"
    ::= { affirmedServicesContentHttpProxyServiceStatisticsGridLevelVideoPacingDetailWebmEntry 16 }

affirmedServicesContentHttpProxyServiceStatisticsGridLevelVideoPacingDetailWebmVideobitrateaverage OBJECT-TYPE
    SYNTAX      ConfdString
    MAX-ACCESS  read-only
    STATUS      deprecated
    DESCRIPTION "Average video bitrate in kbps"
    ::= { affirmedServicesContentHttpProxyServiceStatisticsGridLevelVideoPacingDetailWebmEntry 17 }

affirmedServicesContentHttpProxyServiceStatisticsGridLevelVideoPacingFailureTable OBJECT-TYPE
    SYNTAX      SEQUENCE OF AffirmedServicesContentHttpProxyServiceStatisticsGridLevelVideoPacingFailureEntry
    MAX-ACCESS  not-accessible
    STATUS      current
    DESCRIPTION ""
    ::= { affirmedServicesContentHttpProxyServiceStatisticsGridLevelVideoPacing 3 }

affirmedServicesContentHttpProxyServiceStatisticsGridLevelVideoPacingFailureEntry OBJECT-TYPE
    SYNTAX      AffirmedServicesContentHttpProxyServiceStatisticsGridLevelVideoPacingFailureEntry
    MAX-ACCESS  not-accessible
    STATUS      current
    DESCRIPTION ""
    INDEX { affirmedServicesContentHttpProxyServiceStatisticsGridLevelVideoPacingFailureGrid }
        ::= { affirmedServicesContentHttpProxyServiceStatisticsGridLevelVideoPacingFailureTable 1 }

AffirmedServicesContentHttpProxyServiceStatisticsGridLevelVideoPacingFailureEntry ::=
    SEQUENCE {
        affirmedServicesContentHttpProxyServiceStatisticsGridLevelVideoPacingFailureGrid Unsigned32,
        affirmedServicesContentHttpProxyServiceStatisticsGridLevelVideoPacingFailureVideopacingfailureunknownmediatype ConfdString,
        affirmedServicesContentHttpProxyServiceStatisticsGridLevelVideoPacingFailureVideopacingfailureparsingmp4 ConfdString,
        affirmedServicesContentHttpProxyServiceStatisticsGridLevelVideoPacingFailureVideopacingfailureparsingflv ConfdString,
        affirmedServicesContentHttpProxyServiceStatisticsGridLevelVideoPacingFailureVideopacingfailureparsingwebm ConfdString,
        affirmedServicesContentHttpProxyServiceStatisticsGridLevelVideoPacingFailureVideopacingfailureothers ConfdString
    }

affirmedServicesContentHttpProxyServiceStatisticsGridLevelVideoPacingFailureGrid OBJECT-TYPE
    SYNTAX      Unsigned32
    MAX-ACCESS  not-accessible
    STATUS      current
    DESCRIPTION ""
    ::= { affirmedServicesContentHttpProxyServiceStatisticsGridLevelVideoPacingFailureEntry 1 }

affirmedServicesContentHttpProxyServiceStatisticsGridLevelVideoPacingFailureVideopacingfailureunknownmediatype OBJECT-TYPE
    SYNTAX      ConfdString
    MAX-ACCESS  read-only
    STATUS      deprecated
    DESCRIPTION "Number of Video Pacing Failure Unknown Media Type"
    ::= { affirmedServicesContentHttpProxyServiceStatisticsGridLevelVideoPacingFailureEntry 2 }

affirmedServicesContentHttpProxyServiceStatisticsGridLevelVideoPacingFailureVideopacingfailureparsingmp4 OBJECT-TYPE
    SYNTAX      ConfdString
    MAX-ACCESS  read-only
    STATUS      deprecated
    DESCRIPTION "Number of Video Pacing Failure Parsing MP4"
    ::= { affirmedServicesContentHttpProxyServiceStatisticsGridLevelVideoPacingFailureEntry 3 }

affirmedServicesContentHttpProxyServiceStatisticsGridLevelVideoPacingFailureVideopacingfailureparsingflv OBJECT-TYPE
    SYNTAX      ConfdString
    MAX-ACCESS  read-only
    STATUS      deprecated
    DESCRIPTION "Number of Video Pacing Failure Parsing FLV"
    ::= { affirmedServicesContentHttpProxyServiceStatisticsGridLevelVideoPacingFailureEntry 4 }

affirmedServicesContentHttpProxyServiceStatisticsGridLevelVideoPacingFailureVideopacingfailureparsingwebm OBJECT-TYPE
    SYNTAX      ConfdString
    MAX-ACCESS  read-only
    STATUS      deprecated
    DESCRIPTION "Number of Video Pacing Failure Parsing WEBM"
    ::= { affirmedServicesContentHttpProxyServiceStatisticsGridLevelVideoPacingFailureEntry 5 }

affirmedServicesContentHttpProxyServiceStatisticsGridLevelVideoPacingFailureVideopacingfailureothers OBJECT-TYPE
    SYNTAX      ConfdString
    MAX-ACCESS  read-only
    STATUS      deprecated
    DESCRIPTION "Number of Video Pacing Failure Others"
    ::= { affirmedServicesContentHttpProxyServiceStatisticsGridLevelVideoPacingFailureEntry 6 }

affirmedServicesContentHttpProxyServiceStatisticsGridLevelPVideoPacingSummaryTable OBJECT-TYPE
    SYNTAX      SEQUENCE OF AffirmedServicesContentHttpProxyServiceStatisticsGridLevelPVideoPacingSummaryEntry
    MAX-ACCESS  not-accessible
    STATUS      current
    DESCRIPTION ""
    ::= { affirmedServicesContentHttpProxyServiceStatisticsGridLevelPVideoPacing 1 }

affirmedServicesContentHttpProxyServiceStatisticsGridLevelPVideoPacingSummaryEntry OBJECT-TYPE
    SYNTAX      AffirmedServicesContentHttpProxyServiceStatisticsGridLevelPVideoPacingSummaryEntry
    MAX-ACCESS  not-accessible
    STATUS      current
    DESCRIPTION ""
    INDEX { affirmedServicesContentHttpProxyServiceStatisticsGridLevelPVideoPacingSummaryGrid }
        ::= { affirmedServicesContentHttpProxyServiceStatisticsGridLevelPVideoPacingSummaryTable 1 }

AffirmedServicesContentHttpProxyServiceStatisticsGridLevelPVideoPacingSummaryEntry ::=
    SEQUENCE {
        affirmedServicesContentHttpProxyServiceStatisticsGridLevelPVideoPacingSummaryGrid Unsigned32,
        affirmedServicesContentHttpProxyServiceStatisticsGridLevelPVideoPacingSummaryVideopacingattempts ConfdString,
        affirmedServicesContentHttpProxyServiceStatisticsGridLevelPVideoPacingSummaryVideopacingsuccesses ConfdString,
        affirmedServicesContentHttpProxyServiceStatisticsGridLevelPVideoPacingSummaryVideopacingfailures ConfdString,
        affirmedServicesContentHttpProxyServiceStatisticsGridLevelPVideoPacingSummaryVideopacingstalls ConfdString,
        affirmedServicesContentHttpProxyServiceStatisticsGridLevelPVideoPacingSummaryVideopacingcurrents ConfdString,
        affirmedServicesContentHttpProxyServiceStatisticsGridLevelPVideoPacingSummaryVideopacingserverrsp ConfdString,
        affirmedServicesContentHttpProxyServiceStatisticsGridLevelPVideoPacingSummaryVideopacingclientrsp ConfdString,
        affirmedServicesContentHttpProxyServiceStatisticsGridLevelPVideoPacingSummaryVideodurationmin ConfdString,
        affirmedServicesContentHttpProxyServiceStatisticsGridLevelPVideoPacingSummaryVideodurationmax ConfdString,
        affirmedServicesContentHttpProxyServiceStatisticsGridLevelPVideoPacingSummaryVideodurationaverage ConfdString,
        affirmedServicesContentHttpProxyServiceStatisticsGridLevelPVideoPacingSummaryVideodurationtotal ConfdString,
        affirmedServicesContentHttpProxyServiceStatisticsGridLevelPVideoPacingSummaryVideoservingdurationmin ConfdString,
        affirmedServicesContentHttpProxyServiceStatisticsGridLevelPVideoPacingSummaryVideoservingdurationmax ConfdString,
        affirmedServicesContentHttpProxyServiceStatisticsGridLevelPVideoPacingSummaryVideoservingdurationaverage ConfdString,
        affirmedServicesContentHttpProxyServiceStatisticsGridLevelPVideoPacingSummaryVideoservingdurationtotal ConfdString,
        affirmedServicesContentHttpProxyServiceStatisticsGridLevelPVideoPacingSummaryVideostalldurationmin ConfdString,
        affirmedServicesContentHttpProxyServiceStatisticsGridLevelPVideoPacingSummaryVideostalldurationmax ConfdString,
        affirmedServicesContentHttpProxyServiceStatisticsGridLevelPVideoPacingSummaryVideostalldurationaverage ConfdString,
        affirmedServicesContentHttpProxyServiceStatisticsGridLevelPVideoPacingSummaryVideostalldurationtotal ConfdString,
        affirmedServicesContentHttpProxyServiceStatisticsGridLevelPVideoPacingSummaryVideobitratemin ConfdString,
        affirmedServicesContentHttpProxyServiceStatisticsGridLevelPVideoPacingSummaryVideobitratemax ConfdString,
        affirmedServicesContentHttpProxyServiceStatisticsGridLevelPVideoPacingSummaryVideobitrateaverage ConfdString,
        affirmedServicesContentHttpProxyServiceStatisticsGridLevelPVideoPacingSummaryVideopacingaborts ConfdString,
        affirmedServicesContentHttpProxyServiceStatisticsGridLevelPVideoPacingSummaryVideosessiondurationmin ConfdString,
        affirmedServicesContentHttpProxyServiceStatisticsGridLevelPVideoPacingSummaryVideosessiondurationaverage ConfdString,
        affirmedServicesContentHttpProxyServiceStatisticsGridLevelPVideoPacingSummaryVideosessiondurationmax ConfdString,
        affirmedServicesContentHttpProxyServiceStatisticsGridLevelPVideoPacingSummaryVideosessiondurationtotal ConfdString,
        affirmedServicesContentHttpProxyServiceStatisticsGridLevelPVideoPacingSummaryVideopacingoptedoutbysubscriber ConfdString
    }

affirmedServicesContentHttpProxyServiceStatisticsGridLevelPVideoPacingSummaryGrid OBJECT-TYPE
    SYNTAX      Unsigned32
    MAX-ACCESS  not-accessible
    STATUS      current
    DESCRIPTION "grid ID"
    ::= { affirmedServicesContentHttpProxyServiceStatisticsGridLevelPVideoPacingSummaryEntry 1 }

affirmedServicesContentHttpProxyServiceStatisticsGridLevelPVideoPacingSummaryVideopacingattempts OBJECT-TYPE
    SYNTAX      ConfdString
    MAX-ACCESS  read-only
    STATUS      current
    DESCRIPTION "Number of video pacing attempts"
    ::= { affirmedServicesContentHttpProxyServiceStatisticsGridLevelPVideoPacingSummaryEntry 2 }

affirmedServicesContentHttpProxyServiceStatisticsGridLevelPVideoPacingSummaryVideopacingsuccesses OBJECT-TYPE
    SYNTAX      ConfdString
    MAX-ACCESS  read-only
    STATUS      current
    DESCRIPTION "Number of video pacing successes"
    ::= { affirmedServicesContentHttpProxyServiceStatisticsGridLevelPVideoPacingSummaryEntry 3 }

affirmedServicesContentHttpProxyServiceStatisticsGridLevelPVideoPacingSummaryVideopacingfailures OBJECT-TYPE
    SYNTAX      ConfdString
    MAX-ACCESS  read-only
    STATUS      current
    DESCRIPTION "Number of video pacing failures"
    ::= { affirmedServicesContentHttpProxyServiceStatisticsGridLevelPVideoPacingSummaryEntry 4 }

affirmedServicesContentHttpProxyServiceStatisticsGridLevelPVideoPacingSummaryVideopacingstalls OBJECT-TYPE
    SYNTAX      ConfdString
    MAX-ACCESS  read-only
    STATUS      current
    DESCRIPTION "Number of video pacing stalls"
    ::= { affirmedServicesContentHttpProxyServiceStatisticsGridLevelPVideoPacingSummaryEntry 5 }

affirmedServicesContentHttpProxyServiceStatisticsGridLevelPVideoPacingSummaryVideopacingcurrents OBJECT-TYPE
    SYNTAX      ConfdString
    MAX-ACCESS  read-only
    STATUS      current
    DESCRIPTION "Number of video pacing currently paced"
    ::= { affirmedServicesContentHttpProxyServiceStatisticsGridLevelPVideoPacingSummaryEntry 6 }

affirmedServicesContentHttpProxyServiceStatisticsGridLevelPVideoPacingSummaryVideopacingserverrsp OBJECT-TYPE
    SYNTAX      ConfdString
    MAX-ACCESS  read-only
    STATUS      current
    DESCRIPTION "Number of Bytes from Server Response"
    ::= { affirmedServicesContentHttpProxyServiceStatisticsGridLevelPVideoPacingSummaryEntry 7 }

affirmedServicesContentHttpProxyServiceStatisticsGridLevelPVideoPacingSummaryVideopacingclientrsp OBJECT-TYPE
    SYNTAX      ConfdString
    MAX-ACCESS  read-only
    STATUS      current
    DESCRIPTION "Number of Bytes from Client Response"
    ::= { affirmedServicesContentHttpProxyServiceStatisticsGridLevelPVideoPacingSummaryEntry 8 }

affirmedServicesContentHttpProxyServiceStatisticsGridLevelPVideoPacingSummaryVideodurationmin OBJECT-TYPE
    SYNTAX      ConfdString
    MAX-ACCESS  read-only
    STATUS      current
    DESCRIPTION "Minimum video file duration in seconds"
    ::= { affirmedServicesContentHttpProxyServiceStatisticsGridLevelPVideoPacingSummaryEntry 9 }

affirmedServicesContentHttpProxyServiceStatisticsGridLevelPVideoPacingSummaryVideodurationmax OBJECT-TYPE
    SYNTAX      ConfdString
    MAX-ACCESS  read-only
    STATUS      current
    DESCRIPTION "Maximum video file duration in seconds"
    ::= { affirmedServicesContentHttpProxyServiceStatisticsGridLevelPVideoPacingSummaryEntry 10 }

affirmedServicesContentHttpProxyServiceStatisticsGridLevelPVideoPacingSummaryVideodurationaverage OBJECT-TYPE
    SYNTAX      ConfdString
    MAX-ACCESS  read-only
    STATUS      current
    DESCRIPTION "Average video file duration in seconds"
    ::= { affirmedServicesContentHttpProxyServiceStatisticsGridLevelPVideoPacingSummaryEntry 11 }

affirmedServicesContentHttpProxyServiceStatisticsGridLevelPVideoPacingSummaryVideodurationtotal OBJECT-TYPE
    SYNTAX      ConfdString
    MAX-ACCESS  read-only
    STATUS      current
    DESCRIPTION "Total video file duration in seconds"
    ::= { affirmedServicesContentHttpProxyServiceStatisticsGridLevelPVideoPacingSummaryEntry 12 }

affirmedServicesContentHttpProxyServiceStatisticsGridLevelPVideoPacingSummaryVideoservingdurationmin OBJECT-TYPE
    SYNTAX      ConfdString
    MAX-ACCESS  read-only
    STATUS      current
    DESCRIPTION "Minimum served video duration in seconds"
    ::= { affirmedServicesContentHttpProxyServiceStatisticsGridLevelPVideoPacingSummaryEntry 13 }

affirmedServicesContentHttpProxyServiceStatisticsGridLevelPVideoPacingSummaryVideoservingdurationmax OBJECT-TYPE
    SYNTAX      ConfdString
    MAX-ACCESS  read-only
    STATUS      current
    DESCRIPTION "Maximum served video duration in seconds"
    ::= { affirmedServicesContentHttpProxyServiceStatisticsGridLevelPVideoPacingSummaryEntry 14 }

affirmedServicesContentHttpProxyServiceStatisticsGridLevelPVideoPacingSummaryVideoservingdurationaverage OBJECT-TYPE
    SYNTAX      ConfdString
    MAX-ACCESS  read-only
    STATUS      current
    DESCRIPTION "Average served video duration in seconds"
    ::= { affirmedServicesContentHttpProxyServiceStatisticsGridLevelPVideoPacingSummaryEntry 15 }

affirmedServicesContentHttpProxyServiceStatisticsGridLevelPVideoPacingSummaryVideoservingdurationtotal OBJECT-TYPE
    SYNTAX      ConfdString
    MAX-ACCESS  read-only
    STATUS      current
    DESCRIPTION "Total served video duration in seconds"
    ::= { affirmedServicesContentHttpProxyServiceStatisticsGridLevelPVideoPacingSummaryEntry 16 }

affirmedServicesContentHttpProxyServiceStatisticsGridLevelPVideoPacingSummaryVideostalldurationmin OBJECT-TYPE
    SYNTAX      ConfdString
    MAX-ACCESS  read-only
    STATUS      current
    DESCRIPTION "Minimum video pacing stall duration in seconds"
    ::= { affirmedServicesContentHttpProxyServiceStatisticsGridLevelPVideoPacingSummaryEntry 17 }

affirmedServicesContentHttpProxyServiceStatisticsGridLevelPVideoPacingSummaryVideostalldurationmax OBJECT-TYPE
    SYNTAX      ConfdString
    MAX-ACCESS  read-only
    STATUS      current
    DESCRIPTION "Maximum video pacing stall duration in seconds"
    ::= { affirmedServicesContentHttpProxyServiceStatisticsGridLevelPVideoPacingSummaryEntry 18 }

affirmedServicesContentHttpProxyServiceStatisticsGridLevelPVideoPacingSummaryVideostalldurationaverage OBJECT-TYPE
    SYNTAX      ConfdString
    MAX-ACCESS  read-only
    STATUS      current
    DESCRIPTION "Average video pacing stall duration in seconds"
    ::= { affirmedServicesContentHttpProxyServiceStatisticsGridLevelPVideoPacingSummaryEntry 19 }

affirmedServicesContentHttpProxyServiceStatisticsGridLevelPVideoPacingSummaryVideostalldurationtotal OBJECT-TYPE
    SYNTAX      ConfdString
    MAX-ACCESS  read-only
    STATUS      current
    DESCRIPTION "Total video pacing stall duration in seconds"
    ::= { affirmedServicesContentHttpProxyServiceStatisticsGridLevelPVideoPacingSummaryEntry 20 }

affirmedServicesContentHttpProxyServiceStatisticsGridLevelPVideoPacingSummaryVideobitratemin OBJECT-TYPE
    SYNTAX      ConfdString
    MAX-ACCESS  read-only
    STATUS      current
    DESCRIPTION "Minimum video bitrate in kbps"
    ::= { affirmedServicesContentHttpProxyServiceStatisticsGridLevelPVideoPacingSummaryEntry 21 }

affirmedServicesContentHttpProxyServiceStatisticsGridLevelPVideoPacingSummaryVideobitratemax OBJECT-TYPE
    SYNTAX      ConfdString
    MAX-ACCESS  read-only
    STATUS      current
    DESCRIPTION "Maximum video bitrate in kbps"
    ::= { affirmedServicesContentHttpProxyServiceStatisticsGridLevelPVideoPacingSummaryEntry 22 }

affirmedServicesContentHttpProxyServiceStatisticsGridLevelPVideoPacingSummaryVideobitrateaverage OBJECT-TYPE
    SYNTAX      ConfdString
    MAX-ACCESS  read-only
    STATUS      current
    DESCRIPTION "Average video bitrate in kbps"
    ::= { affirmedServicesContentHttpProxyServiceStatisticsGridLevelPVideoPacingSummaryEntry 23 }

affirmedServicesContentHttpProxyServiceStatisticsGridLevelPVideoPacingSummaryVideopacingaborts OBJECT-TYPE
    SYNTAX      ConfdString
    MAX-ACCESS  read-only
    STATUS      current
    DESCRIPTION "Number of video pacing aborted by client"
    ::= { affirmedServicesContentHttpProxyServiceStatisticsGridLevelPVideoPacingSummaryEntry 24 }

affirmedServicesContentHttpProxyServiceStatisticsGridLevelPVideoPacingSummaryVideosessiondurationmin OBJECT-TYPE
    SYNTAX      ConfdString
    MAX-ACCESS  read-only
    STATUS      current
    DESCRIPTION "Minimum video service time in seconds"
    ::= { affirmedServicesContentHttpProxyServiceStatisticsGridLevelPVideoPacingSummaryEntry 25 }

affirmedServicesContentHttpProxyServiceStatisticsGridLevelPVideoPacingSummaryVideosessiondurationaverage OBJECT-TYPE
    SYNTAX      ConfdString
    MAX-ACCESS  read-only
    STATUS      current
    DESCRIPTION "Average video service time in seconds"
    ::= { affirmedServicesContentHttpProxyServiceStatisticsGridLevelPVideoPacingSummaryEntry 26 }

affirmedServicesContentHttpProxyServiceStatisticsGridLevelPVideoPacingSummaryVideosessiondurationmax OBJECT-TYPE
    SYNTAX      ConfdString
    MAX-ACCESS  read-only
    STATUS      current
    DESCRIPTION "Maximum video service time in seconds"
    ::= { affirmedServicesContentHttpProxyServiceStatisticsGridLevelPVideoPacingSummaryEntry 27 }

affirmedServicesContentHttpProxyServiceStatisticsGridLevelPVideoPacingSummaryVideosessiondurationtotal OBJECT-TYPE
    SYNTAX      ConfdString
    MAX-ACCESS  read-only
    STATUS      current
    DESCRIPTION "Total video service time in seconds"
    ::= { affirmedServicesContentHttpProxyServiceStatisticsGridLevelPVideoPacingSummaryEntry 28 }

affirmedServicesContentHttpProxyServiceStatisticsGridLevelPVideoPacingSummaryVideopacingoptedoutbysubscriber OBJECT-TYPE
    SYNTAX      ConfdString
    MAX-ACCESS  read-only
    STATUS      current
    DESCRIPTION "Number of video pacing bypass - Opted Out by Subscriber"
    ::= { affirmedServicesContentHttpProxyServiceStatisticsGridLevelPVideoPacingSummaryEntry 29 }

affirmedServicesContentHttpProxyServiceStatisticsGridLevelPVideoPacingDetailMp4Table OBJECT-TYPE
    SYNTAX      SEQUENCE OF AffirmedServicesContentHttpProxyServiceStatisticsGridLevelPVideoPacingDetailMp4Entry
    MAX-ACCESS  not-accessible
    STATUS      current
    DESCRIPTION ""
    ::= { affirmedServicesContentHttpProxyServiceStatisticsGridLevelPVideoPacingDetail 1 }

affirmedServicesContentHttpProxyServiceStatisticsGridLevelPVideoPacingDetailMp4Entry OBJECT-TYPE
    SYNTAX      AffirmedServicesContentHttpProxyServiceStatisticsGridLevelPVideoPacingDetailMp4Entry
    MAX-ACCESS  not-accessible
    STATUS      current
    DESCRIPTION ""
    INDEX { affirmedServicesContentHttpProxyServiceStatisticsGridLevelPVideoPacingDetailMp4Grid }
        ::= { affirmedServicesContentHttpProxyServiceStatisticsGridLevelPVideoPacingDetailMp4Table 1 }

AffirmedServicesContentHttpProxyServiceStatisticsGridLevelPVideoPacingDetailMp4Entry ::=
    SEQUENCE {
        affirmedServicesContentHttpProxyServiceStatisticsGridLevelPVideoPacingDetailMp4Grid Unsigned32,
        affirmedServicesContentHttpProxyServiceStatisticsGridLevelPVideoPacingDetailMp4Videopacingattempts ConfdString,
        affirmedServicesContentHttpProxyServiceStatisticsGridLevelPVideoPacingDetailMp4Videopacingsuccesses ConfdString,
        affirmedServicesContentHttpProxyServiceStatisticsGridLevelPVideoPacingDetailMp4Videopacingfailures ConfdString,
        affirmedServicesContentHttpProxyServiceStatisticsGridLevelPVideoPacingDetailMp4Videopacingserverrsp ConfdString,
        affirmedServicesContentHttpProxyServiceStatisticsGridLevelPVideoPacingDetailMp4Videopacingclientrsp ConfdString,
        affirmedServicesContentHttpProxyServiceStatisticsGridLevelPVideoPacingDetailMp4Videodurationmin ConfdString,
        affirmedServicesContentHttpProxyServiceStatisticsGridLevelPVideoPacingDetailMp4Videodurationmax ConfdString,
        affirmedServicesContentHttpProxyServiceStatisticsGridLevelPVideoPacingDetailMp4Videodurationaverage ConfdString,
        affirmedServicesContentHttpProxyServiceStatisticsGridLevelPVideoPacingDetailMp4Videodurationtotal ConfdString,
        affirmedServicesContentHttpProxyServiceStatisticsGridLevelPVideoPacingDetailMp4Videoservingdurationmin ConfdString,
        affirmedServicesContentHttpProxyServiceStatisticsGridLevelPVideoPacingDetailMp4Videoservingdurationmax ConfdString,
        affirmedServicesContentHttpProxyServiceStatisticsGridLevelPVideoPacingDetailMp4Videoservingdurationaverage ConfdString,
        affirmedServicesContentHttpProxyServiceStatisticsGridLevelPVideoPacingDetailMp4Videoservingdurationtotal ConfdString,
        affirmedServicesContentHttpProxyServiceStatisticsGridLevelPVideoPacingDetailMp4Videobitratemin ConfdString,
        affirmedServicesContentHttpProxyServiceStatisticsGridLevelPVideoPacingDetailMp4Videobitratemax ConfdString,
        affirmedServicesContentHttpProxyServiceStatisticsGridLevelPVideoPacingDetailMp4Videobitrateaverage ConfdString,
        affirmedServicesContentHttpProxyServiceStatisticsGridLevelPVideoPacingDetailMp4Videopacingaborts ConfdString,
        affirmedServicesContentHttpProxyServiceStatisticsGridLevelPVideoPacingDetailMp4Videosessiondurationmin ConfdString,
        affirmedServicesContentHttpProxyServiceStatisticsGridLevelPVideoPacingDetailMp4Videosessiondurationaverage ConfdString,
        affirmedServicesContentHttpProxyServiceStatisticsGridLevelPVideoPacingDetailMp4Videosessiondurationmax ConfdString,
        affirmedServicesContentHttpProxyServiceStatisticsGridLevelPVideoPacingDetailMp4Videosessiondurationtotal ConfdString,
        affirmedServicesContentHttpProxyServiceStatisticsGridLevelPVideoPacingDetailMp4Videopacingoptedoutbysubscriber ConfdString
    }

affirmedServicesContentHttpProxyServiceStatisticsGridLevelPVideoPacingDetailMp4Grid OBJECT-TYPE
    SYNTAX      Unsigned32
    MAX-ACCESS  not-accessible
    STATUS      current
    DESCRIPTION "grid ID"
    ::= { affirmedServicesContentHttpProxyServiceStatisticsGridLevelPVideoPacingDetailMp4Entry 1 }

affirmedServicesContentHttpProxyServiceStatisticsGridLevelPVideoPacingDetailMp4Videopacingattempts OBJECT-TYPE
    SYNTAX      ConfdString
    MAX-ACCESS  read-only
    STATUS      current
    DESCRIPTION "Number of video pacing attempts"
    ::= { affirmedServicesContentHttpProxyServiceStatisticsGridLevelPVideoPacingDetailMp4Entry 2 }

affirmedServicesContentHttpProxyServiceStatisticsGridLevelPVideoPacingDetailMp4Videopacingsuccesses OBJECT-TYPE
    SYNTAX      ConfdString
    MAX-ACCESS  read-only
    STATUS      current
    DESCRIPTION "Number of video pacing successes"
    ::= { affirmedServicesContentHttpProxyServiceStatisticsGridLevelPVideoPacingDetailMp4Entry 3 }

affirmedServicesContentHttpProxyServiceStatisticsGridLevelPVideoPacingDetailMp4Videopacingfailures OBJECT-TYPE
    SYNTAX      ConfdString
    MAX-ACCESS  read-only
    STATUS      current
    DESCRIPTION "Number of video pacing failures"
    ::= { affirmedServicesContentHttpProxyServiceStatisticsGridLevelPVideoPacingDetailMp4Entry 4 }

affirmedServicesContentHttpProxyServiceStatisticsGridLevelPVideoPacingDetailMp4Videopacingserverrsp OBJECT-TYPE
    SYNTAX      ConfdString
    MAX-ACCESS  read-only
    STATUS      current
    DESCRIPTION "Number of Bytes from Server Response"
    ::= { affirmedServicesContentHttpProxyServiceStatisticsGridLevelPVideoPacingDetailMp4Entry 5 }

affirmedServicesContentHttpProxyServiceStatisticsGridLevelPVideoPacingDetailMp4Videopacingclientrsp OBJECT-TYPE
    SYNTAX      ConfdString
    MAX-ACCESS  read-only
    STATUS      current
    DESCRIPTION "Number of Bytes from Client Response"
    ::= { affirmedServicesContentHttpProxyServiceStatisticsGridLevelPVideoPacingDetailMp4Entry 6 }

affirmedServicesContentHttpProxyServiceStatisticsGridLevelPVideoPacingDetailMp4Videodurationmin OBJECT-TYPE
    SYNTAX      ConfdString
    MAX-ACCESS  read-only
    STATUS      current
    DESCRIPTION "Minimum video file duration in seconds"
    ::= { affirmedServicesContentHttpProxyServiceStatisticsGridLevelPVideoPacingDetailMp4Entry 7 }

affirmedServicesContentHttpProxyServiceStatisticsGridLevelPVideoPacingDetailMp4Videodurationmax OBJECT-TYPE
    SYNTAX      ConfdString
    MAX-ACCESS  read-only
    STATUS      current
    DESCRIPTION "Maximum video file duration in seconds"
    ::= { affirmedServicesContentHttpProxyServiceStatisticsGridLevelPVideoPacingDetailMp4Entry 8 }

affirmedServicesContentHttpProxyServiceStatisticsGridLevelPVideoPacingDetailMp4Videodurationaverage OBJECT-TYPE
    SYNTAX      ConfdString
    MAX-ACCESS  read-only
    STATUS      current
    DESCRIPTION "Average video file duration in seconds"
    ::= { affirmedServicesContentHttpProxyServiceStatisticsGridLevelPVideoPacingDetailMp4Entry 9 }

affirmedServicesContentHttpProxyServiceStatisticsGridLevelPVideoPacingDetailMp4Videodurationtotal OBJECT-TYPE
    SYNTAX      ConfdString
    MAX-ACCESS  read-only
    STATUS      current
    DESCRIPTION "Total video file duration in seconds"
    ::= { affirmedServicesContentHttpProxyServiceStatisticsGridLevelPVideoPacingDetailMp4Entry 10 }

affirmedServicesContentHttpProxyServiceStatisticsGridLevelPVideoPacingDetailMp4Videoservingdurationmin OBJECT-TYPE
    SYNTAX      ConfdString
    MAX-ACCESS  read-only
    STATUS      current
    DESCRIPTION "Minimum served video duration in seconds"
    ::= { affirmedServicesContentHttpProxyServiceStatisticsGridLevelPVideoPacingDetailMp4Entry 11 }

affirmedServicesContentHttpProxyServiceStatisticsGridLevelPVideoPacingDetailMp4Videoservingdurationmax OBJECT-TYPE
    SYNTAX      ConfdString
    MAX-ACCESS  read-only
    STATUS      current
    DESCRIPTION "Maximum served video duration in seconds"
    ::= { affirmedServicesContentHttpProxyServiceStatisticsGridLevelPVideoPacingDetailMp4Entry 12 }

affirmedServicesContentHttpProxyServiceStatisticsGridLevelPVideoPacingDetailMp4Videoservingdurationaverage OBJECT-TYPE
    SYNTAX      ConfdString
    MAX-ACCESS  read-only
    STATUS      current
    DESCRIPTION "Average served video duration in seconds"
    ::= { affirmedServicesContentHttpProxyServiceStatisticsGridLevelPVideoPacingDetailMp4Entry 13 }

affirmedServicesContentHttpProxyServiceStatisticsGridLevelPVideoPacingDetailMp4Videoservingdurationtotal OBJECT-TYPE
    SYNTAX      ConfdString
    MAX-ACCESS  read-only
    STATUS      current
    DESCRIPTION "Total served video duration in seconds"
    ::= { affirmedServicesContentHttpProxyServiceStatisticsGridLevelPVideoPacingDetailMp4Entry 14 }

affirmedServicesContentHttpProxyServiceStatisticsGridLevelPVideoPacingDetailMp4Videobitratemin OBJECT-TYPE
    SYNTAX      ConfdString
    MAX-ACCESS  read-only
    STATUS      current
    DESCRIPTION "Minimum video bitrate in kbps"
    ::= { affirmedServicesContentHttpProxyServiceStatisticsGridLevelPVideoPacingDetailMp4Entry 15 }

affirmedServicesContentHttpProxyServiceStatisticsGridLevelPVideoPacingDetailMp4Videobitratemax OBJECT-TYPE
    SYNTAX      ConfdString
    MAX-ACCESS  read-only
    STATUS      current
    DESCRIPTION "Maximum video bitrate in kbps"
    ::= { affirmedServicesContentHttpProxyServiceStatisticsGridLevelPVideoPacingDetailMp4Entry 16 }

affirmedServicesContentHttpProxyServiceStatisticsGridLevelPVideoPacingDetailMp4Videobitrateaverage OBJECT-TYPE
    SYNTAX      ConfdString
    MAX-ACCESS  read-only
    STATUS      current
    DESCRIPTION "Average video bitrate in kbps"
    ::= { affirmedServicesContentHttpProxyServiceStatisticsGridLevelPVideoPacingDetailMp4Entry 17 }

affirmedServicesContentHttpProxyServiceStatisticsGridLevelPVideoPacingDetailMp4Videopacingaborts OBJECT-TYPE
    SYNTAX      ConfdString
    MAX-ACCESS  read-only
    STATUS      current
    DESCRIPTION "Number of video pacing aborted by client"
    ::= { affirmedServicesContentHttpProxyServiceStatisticsGridLevelPVideoPacingDetailMp4Entry 18 }

affirmedServicesContentHttpProxyServiceStatisticsGridLevelPVideoPacingDetailMp4Videosessiondurationmin OBJECT-TYPE
    SYNTAX      ConfdString
    MAX-ACCESS  read-only
    STATUS      current
    DESCRIPTION "Minimum video service time in seconds"
    ::= { affirmedServicesContentHttpProxyServiceStatisticsGridLevelPVideoPacingDetailMp4Entry 19 }

affirmedServicesContentHttpProxyServiceStatisticsGridLevelPVideoPacingDetailMp4Videosessiondurationaverage OBJECT-TYPE
    SYNTAX      ConfdString
    MAX-ACCESS  read-only
    STATUS      current
    DESCRIPTION "Average video service time in seconds"
    ::= { affirmedServicesContentHttpProxyServiceStatisticsGridLevelPVideoPacingDetailMp4Entry 20 }

affirmedServicesContentHttpProxyServiceStatisticsGridLevelPVideoPacingDetailMp4Videosessiondurationmax OBJECT-TYPE
    SYNTAX      ConfdString
    MAX-ACCESS  read-only
    STATUS      current
    DESCRIPTION "Maximum video service time in seconds"
    ::= { affirmedServicesContentHttpProxyServiceStatisticsGridLevelPVideoPacingDetailMp4Entry 21 }

affirmedServicesContentHttpProxyServiceStatisticsGridLevelPVideoPacingDetailMp4Videosessiondurationtotal OBJECT-TYPE
    SYNTAX      ConfdString
    MAX-ACCESS  read-only
    STATUS      current
    DESCRIPTION "Total video service time in seconds"
    ::= { affirmedServicesContentHttpProxyServiceStatisticsGridLevelPVideoPacingDetailMp4Entry 22 }

affirmedServicesContentHttpProxyServiceStatisticsGridLevelPVideoPacingDetailMp4Videopacingoptedoutbysubscriber OBJECT-TYPE
    SYNTAX      ConfdString
    MAX-ACCESS  read-only
    STATUS      current
    DESCRIPTION "Number of video pacing bypass - Opted Out by Subscriber"
    ::= { affirmedServicesContentHttpProxyServiceStatisticsGridLevelPVideoPacingDetailMp4Entry 23 }

affirmedServicesContentHttpProxyServiceStatisticsGridLevelPVideoPacingDetailFlvTable OBJECT-TYPE
    SYNTAX      SEQUENCE OF AffirmedServicesContentHttpProxyServiceStatisticsGridLevelPVideoPacingDetailFlvEntry
    MAX-ACCESS  not-accessible
    STATUS      current
    DESCRIPTION ""
    ::= { affirmedServicesContentHttpProxyServiceStatisticsGridLevelPVideoPacingDetail 2 }

affirmedServicesContentHttpProxyServiceStatisticsGridLevelPVideoPacingDetailFlvEntry OBJECT-TYPE
    SYNTAX      AffirmedServicesContentHttpProxyServiceStatisticsGridLevelPVideoPacingDetailFlvEntry
    MAX-ACCESS  not-accessible
    STATUS      current
    DESCRIPTION ""
    INDEX { affirmedServicesContentHttpProxyServiceStatisticsGridLevelPVideoPacingDetailFlvGrid }
        ::= { affirmedServicesContentHttpProxyServiceStatisticsGridLevelPVideoPacingDetailFlvTable 1 }

AffirmedServicesContentHttpProxyServiceStatisticsGridLevelPVideoPacingDetailFlvEntry ::=
    SEQUENCE {
        affirmedServicesContentHttpProxyServiceStatisticsGridLevelPVideoPacingDetailFlvGrid Unsigned32,
        affirmedServicesContentHttpProxyServiceStatisticsGridLevelPVideoPacingDetailFlvVideopacingattempts ConfdString,
        affirmedServicesContentHttpProxyServiceStatisticsGridLevelPVideoPacingDetailFlvVideopacingsuccesses ConfdString,
        affirmedServicesContentHttpProxyServiceStatisticsGridLevelPVideoPacingDetailFlvVideopacingfailures ConfdString,
        affirmedServicesContentHttpProxyServiceStatisticsGridLevelPVideoPacingDetailFlvVideopacingserverrsp ConfdString,
        affirmedServicesContentHttpProxyServiceStatisticsGridLevelPVideoPacingDetailFlvVideopacingclientrsp ConfdString,
        affirmedServicesContentHttpProxyServiceStatisticsGridLevelPVideoPacingDetailFlvVideodurationmin ConfdString,
        affirmedServicesContentHttpProxyServiceStatisticsGridLevelPVideoPacingDetailFlvVideodurationmax ConfdString,
        affirmedServicesContentHttpProxyServiceStatisticsGridLevelPVideoPacingDetailFlvVideodurationaverage ConfdString,
        affirmedServicesContentHttpProxyServiceStatisticsGridLevelPVideoPacingDetailFlvVideodurationtotal ConfdString,
        affirmedServicesContentHttpProxyServiceStatisticsGridLevelPVideoPacingDetailFlvVideoservingdurationmin ConfdString,
        affirmedServicesContentHttpProxyServiceStatisticsGridLevelPVideoPacingDetailFlvVideoservingdurationmax ConfdString,
        affirmedServicesContentHttpProxyServiceStatisticsGridLevelPVideoPacingDetailFlvVideoservingdurationaverage ConfdString,
        affirmedServicesContentHttpProxyServiceStatisticsGridLevelPVideoPacingDetailFlvVideoservingdurationtotal ConfdString,
        affirmedServicesContentHttpProxyServiceStatisticsGridLevelPVideoPacingDetailFlvVideobitratemin ConfdString,
        affirmedServicesContentHttpProxyServiceStatisticsGridLevelPVideoPacingDetailFlvVideobitratemax ConfdString,
        affirmedServicesContentHttpProxyServiceStatisticsGridLevelPVideoPacingDetailFlvVideobitrateaverage ConfdString,
        affirmedServicesContentHttpProxyServiceStatisticsGridLevelPVideoPacingDetailFlvVideopacingaborts ConfdString,
        affirmedServicesContentHttpProxyServiceStatisticsGridLevelPVideoPacingDetailFlvVideosessiondurationmin ConfdString,
        affirmedServicesContentHttpProxyServiceStatisticsGridLevelPVideoPacingDetailFlvVideosessiondurationaverage ConfdString,
        affirmedServicesContentHttpProxyServiceStatisticsGridLevelPVideoPacingDetailFlvVideosessiondurationmax ConfdString,
        affirmedServicesContentHttpProxyServiceStatisticsGridLevelPVideoPacingDetailFlvVideosessiondurationtotal ConfdString,
        affirmedServicesContentHttpProxyServiceStatisticsGridLevelPVideoPacingDetailFlvVideopacingoptedoutbysubscriber ConfdString
    }

affirmedServicesContentHttpProxyServiceStatisticsGridLevelPVideoPacingDetailFlvGrid OBJECT-TYPE
    SYNTAX      Unsigned32
    MAX-ACCESS  not-accessible
    STATUS      current
    DESCRIPTION "grid ID"
    ::= { affirmedServicesContentHttpProxyServiceStatisticsGridLevelPVideoPacingDetailFlvEntry 1 }

affirmedServicesContentHttpProxyServiceStatisticsGridLevelPVideoPacingDetailFlvVideopacingattempts OBJECT-TYPE
    SYNTAX      ConfdString
    MAX-ACCESS  read-only
    STATUS      current
    DESCRIPTION "Number of video pacing attempts"
    ::= { affirmedServicesContentHttpProxyServiceStatisticsGridLevelPVideoPacingDetailFlvEntry 2 }

affirmedServicesContentHttpProxyServiceStatisticsGridLevelPVideoPacingDetailFlvVideopacingsuccesses OBJECT-TYPE
    SYNTAX      ConfdString
    MAX-ACCESS  read-only
    STATUS      current
    DESCRIPTION "Number of video pacing successes"
    ::= { affirmedServicesContentHttpProxyServiceStatisticsGridLevelPVideoPacingDetailFlvEntry 3 }

affirmedServicesContentHttpProxyServiceStatisticsGridLevelPVideoPacingDetailFlvVideopacingfailures OBJECT-TYPE
    SYNTAX      ConfdString
    MAX-ACCESS  read-only
    STATUS      current
    DESCRIPTION "Number of video pacing failures"
    ::= { affirmedServicesContentHttpProxyServiceStatisticsGridLevelPVideoPacingDetailFlvEntry 4 }

affirmedServicesContentHttpProxyServiceStatisticsGridLevelPVideoPacingDetailFlvVideopacingserverrsp OBJECT-TYPE
    SYNTAX      ConfdString
    MAX-ACCESS  read-only
    STATUS      current
    DESCRIPTION "Number of Bytes from Server Response"
    ::= { affirmedServicesContentHttpProxyServiceStatisticsGridLevelPVideoPacingDetailFlvEntry 5 }

affirmedServicesContentHttpProxyServiceStatisticsGridLevelPVideoPacingDetailFlvVideopacingclientrsp OBJECT-TYPE
    SYNTAX      ConfdString
    MAX-ACCESS  read-only
    STATUS      current
    DESCRIPTION "Number of Bytes from Client Response"
    ::= { affirmedServicesContentHttpProxyServiceStatisticsGridLevelPVideoPacingDetailFlvEntry 6 }

affirmedServicesContentHttpProxyServiceStatisticsGridLevelPVideoPacingDetailFlvVideodurationmin OBJECT-TYPE
    SYNTAX      ConfdString
    MAX-ACCESS  read-only
    STATUS      current
    DESCRIPTION "Minimum video file duration in seconds"
    ::= { affirmedServicesContentHttpProxyServiceStatisticsGridLevelPVideoPacingDetailFlvEntry 7 }

affirmedServicesContentHttpProxyServiceStatisticsGridLevelPVideoPacingDetailFlvVideodurationmax OBJECT-TYPE
    SYNTAX      ConfdString
    MAX-ACCESS  read-only
    STATUS      current
    DESCRIPTION "Maximum video file duration in seconds"
    ::= { affirmedServicesContentHttpProxyServiceStatisticsGridLevelPVideoPacingDetailFlvEntry 8 }

affirmedServicesContentHttpProxyServiceStatisticsGridLevelPVideoPacingDetailFlvVideodurationaverage OBJECT-TYPE
    SYNTAX      ConfdString
    MAX-ACCESS  read-only
    STATUS      current
    DESCRIPTION "Average video file duration in seconds"
    ::= { affirmedServicesContentHttpProxyServiceStatisticsGridLevelPVideoPacingDetailFlvEntry 9 }

affirmedServicesContentHttpProxyServiceStatisticsGridLevelPVideoPacingDetailFlvVideodurationtotal OBJECT-TYPE
    SYNTAX      ConfdString
    MAX-ACCESS  read-only
    STATUS      current
    DESCRIPTION "Total video file duration in seconds"
    ::= { affirmedServicesContentHttpProxyServiceStatisticsGridLevelPVideoPacingDetailFlvEntry 10 }

affirmedServicesContentHttpProxyServiceStatisticsGridLevelPVideoPacingDetailFlvVideoservingdurationmin OBJECT-TYPE
    SYNTAX      ConfdString
    MAX-ACCESS  read-only
    STATUS      current
    DESCRIPTION "Minimum served video duration in seconds"
    ::= { affirmedServicesContentHttpProxyServiceStatisticsGridLevelPVideoPacingDetailFlvEntry 11 }

affirmedServicesContentHttpProxyServiceStatisticsGridLevelPVideoPacingDetailFlvVideoservingdurationmax OBJECT-TYPE
    SYNTAX      ConfdString
    MAX-ACCESS  read-only
    STATUS      current
    DESCRIPTION "Maximum served video duration in seconds"
    ::= { affirmedServicesContentHttpProxyServiceStatisticsGridLevelPVideoPacingDetailFlvEntry 12 }

affirmedServicesContentHttpProxyServiceStatisticsGridLevelPVideoPacingDetailFlvVideoservingdurationaverage OBJECT-TYPE
    SYNTAX      ConfdString
    MAX-ACCESS  read-only
    STATUS      current
    DESCRIPTION "Average served video duration in seconds"
    ::= { affirmedServicesContentHttpProxyServiceStatisticsGridLevelPVideoPacingDetailFlvEntry 13 }

affirmedServicesContentHttpProxyServiceStatisticsGridLevelPVideoPacingDetailFlvVideoservingdurationtotal OBJECT-TYPE
    SYNTAX      ConfdString
    MAX-ACCESS  read-only
    STATUS      current
    DESCRIPTION "Total served video duration in seconds"
    ::= { affirmedServicesContentHttpProxyServiceStatisticsGridLevelPVideoPacingDetailFlvEntry 14 }

affirmedServicesContentHttpProxyServiceStatisticsGridLevelPVideoPacingDetailFlvVideobitratemin OBJECT-TYPE
    SYNTAX      ConfdString
    MAX-ACCESS  read-only
    STATUS      current
    DESCRIPTION "Minimum video bitrate in kbps"
    ::= { affirmedServicesContentHttpProxyServiceStatisticsGridLevelPVideoPacingDetailFlvEntry 15 }

affirmedServicesContentHttpProxyServiceStatisticsGridLevelPVideoPacingDetailFlvVideobitratemax OBJECT-TYPE
    SYNTAX      ConfdString
    MAX-ACCESS  read-only
    STATUS      current
    DESCRIPTION "Maximum video bitrate in kbps"
    ::= { affirmedServicesContentHttpProxyServiceStatisticsGridLevelPVideoPacingDetailFlvEntry 16 }

affirmedServicesContentHttpProxyServiceStatisticsGridLevelPVideoPacingDetailFlvVideobitrateaverage OBJECT-TYPE
    SYNTAX      ConfdString
    MAX-ACCESS  read-only
    STATUS      current
    DESCRIPTION "Average video bitrate in kbps"
    ::= { affirmedServicesContentHttpProxyServiceStatisticsGridLevelPVideoPacingDetailFlvEntry 17 }

affirmedServicesContentHttpProxyServiceStatisticsGridLevelPVideoPacingDetailFlvVideopacingaborts OBJECT-TYPE
    SYNTAX      ConfdString
    MAX-ACCESS  read-only
    STATUS      current
    DESCRIPTION "Number of video pacing aborted by client"
    ::= { affirmedServicesContentHttpProxyServiceStatisticsGridLevelPVideoPacingDetailFlvEntry 18 }

affirmedServicesContentHttpProxyServiceStatisticsGridLevelPVideoPacingDetailFlvVideosessiondurationmin OBJECT-TYPE
    SYNTAX      ConfdString
    MAX-ACCESS  read-only
    STATUS      current
    DESCRIPTION "Minimum video service time in seconds"
    ::= { affirmedServicesContentHttpProxyServiceStatisticsGridLevelPVideoPacingDetailFlvEntry 19 }

affirmedServicesContentHttpProxyServiceStatisticsGridLevelPVideoPacingDetailFlvVideosessiondurationaverage OBJECT-TYPE
    SYNTAX      ConfdString
    MAX-ACCESS  read-only
    STATUS      current
    DESCRIPTION "Average video service time in seconds"
    ::= { affirmedServicesContentHttpProxyServiceStatisticsGridLevelPVideoPacingDetailFlvEntry 20 }

affirmedServicesContentHttpProxyServiceStatisticsGridLevelPVideoPacingDetailFlvVideosessiondurationmax OBJECT-TYPE
    SYNTAX      ConfdString
    MAX-ACCESS  read-only
    STATUS      current
    DESCRIPTION "Maximum video service time in seconds"
    ::= { affirmedServicesContentHttpProxyServiceStatisticsGridLevelPVideoPacingDetailFlvEntry 21 }

affirmedServicesContentHttpProxyServiceStatisticsGridLevelPVideoPacingDetailFlvVideosessiondurationtotal OBJECT-TYPE
    SYNTAX      ConfdString
    MAX-ACCESS  read-only
    STATUS      current
    DESCRIPTION "Total video service time in seconds"
    ::= { affirmedServicesContentHttpProxyServiceStatisticsGridLevelPVideoPacingDetailFlvEntry 22 }

affirmedServicesContentHttpProxyServiceStatisticsGridLevelPVideoPacingDetailFlvVideopacingoptedoutbysubscriber OBJECT-TYPE
    SYNTAX      ConfdString
    MAX-ACCESS  read-only
    STATUS      current
    DESCRIPTION "Number of video pacing bypass - Opted Out by Subscriber"
    ::= { affirmedServicesContentHttpProxyServiceStatisticsGridLevelPVideoPacingDetailFlvEntry 23 }

affirmedServicesContentHttpProxyServiceStatisticsGridLevelPVideoPacingDetailWebmTable OBJECT-TYPE
    SYNTAX      SEQUENCE OF AffirmedServicesContentHttpProxyServiceStatisticsGridLevelPVideoPacingDetailWebmEntry
    MAX-ACCESS  not-accessible
    STATUS      current
    DESCRIPTION ""
    ::= { affirmedServicesContentHttpProxyServiceStatisticsGridLevelPVideoPacingDetail 3 }

affirmedServicesContentHttpProxyServiceStatisticsGridLevelPVideoPacingDetailWebmEntry OBJECT-TYPE
    SYNTAX      AffirmedServicesContentHttpProxyServiceStatisticsGridLevelPVideoPacingDetailWebmEntry
    MAX-ACCESS  not-accessible
    STATUS      current
    DESCRIPTION ""
    INDEX { affirmedServicesContentHttpProxyServiceStatisticsGridLevelPVideoPacingDetailWebmGrid }
        ::= { affirmedServicesContentHttpProxyServiceStatisticsGridLevelPVideoPacingDetailWebmTable 1 }

AffirmedServicesContentHttpProxyServiceStatisticsGridLevelPVideoPacingDetailWebmEntry ::=
    SEQUENCE {
        affirmedServicesContentHttpProxyServiceStatisticsGridLevelPVideoPacingDetailWebmGrid Unsigned32,
        affirmedServicesContentHttpProxyServiceStatisticsGridLevelPVideoPacingDetailWebmVideopacingattempts ConfdString,
        affirmedServicesContentHttpProxyServiceStatisticsGridLevelPVideoPacingDetailWebmVideopacingsuccesses ConfdString,
        affirmedServicesContentHttpProxyServiceStatisticsGridLevelPVideoPacingDetailWebmVideopacingfailures ConfdString,
        affirmedServicesContentHttpProxyServiceStatisticsGridLevelPVideoPacingDetailWebmVideopacingserverrsp ConfdString,
        affirmedServicesContentHttpProxyServiceStatisticsGridLevelPVideoPacingDetailWebmVideopacingclientrsp ConfdString,
        affirmedServicesContentHttpProxyServiceStatisticsGridLevelPVideoPacingDetailWebmVideodurationmin ConfdString,
        affirmedServicesContentHttpProxyServiceStatisticsGridLevelPVideoPacingDetailWebmVideodurationmax ConfdString,
        affirmedServicesContentHttpProxyServiceStatisticsGridLevelPVideoPacingDetailWebmVideodurationaverage ConfdString,
        affirmedServicesContentHttpProxyServiceStatisticsGridLevelPVideoPacingDetailWebmVideodurationtotal ConfdString,
        affirmedServicesContentHttpProxyServiceStatisticsGridLevelPVideoPacingDetailWebmVideoservingdurationmin ConfdString,
        affirmedServicesContentHttpProxyServiceStatisticsGridLevelPVideoPacingDetailWebmVideoservingdurationmax ConfdString,
        affirmedServicesContentHttpProxyServiceStatisticsGridLevelPVideoPacingDetailWebmVideoservingdurationaverage ConfdString,
        affirmedServicesContentHttpProxyServiceStatisticsGridLevelPVideoPacingDetailWebmVideoservingdurationtotal ConfdString,
        affirmedServicesContentHttpProxyServiceStatisticsGridLevelPVideoPacingDetailWebmVideobitratemin ConfdString,
        affirmedServicesContentHttpProxyServiceStatisticsGridLevelPVideoPacingDetailWebmVideobitratemax ConfdString,
        affirmedServicesContentHttpProxyServiceStatisticsGridLevelPVideoPacingDetailWebmVideobitrateaverage ConfdString,
        affirmedServicesContentHttpProxyServiceStatisticsGridLevelPVideoPacingDetailWebmVideopacingaborts ConfdString,
        affirmedServicesContentHttpProxyServiceStatisticsGridLevelPVideoPacingDetailWebmVideosessiondurationmin ConfdString,
        affirmedServicesContentHttpProxyServiceStatisticsGridLevelPVideoPacingDetailWebmVideosessiondurationaverage ConfdString,
        affirmedServicesContentHttpProxyServiceStatisticsGridLevelPVideoPacingDetailWebmVideosessiondurationmax ConfdString,
        affirmedServicesContentHttpProxyServiceStatisticsGridLevelPVideoPacingDetailWebmVideosessiondurationtotal ConfdString,
        affirmedServicesContentHttpProxyServiceStatisticsGridLevelPVideoPacingDetailWebmVideopacingoptedoutbysubscriber ConfdString
    }

affirmedServicesContentHttpProxyServiceStatisticsGridLevelPVideoPacingDetailWebmGrid OBJECT-TYPE
    SYNTAX      Unsigned32
    MAX-ACCESS  not-accessible
    STATUS      current
    DESCRIPTION "grid ID"
    ::= { affirmedServicesContentHttpProxyServiceStatisticsGridLevelPVideoPacingDetailWebmEntry 1 }

affirmedServicesContentHttpProxyServiceStatisticsGridLevelPVideoPacingDetailWebmVideopacingattempts OBJECT-TYPE
    SYNTAX      ConfdString
    MAX-ACCESS  read-only
    STATUS      current
    DESCRIPTION "Number of video pacing attempts"
    ::= { affirmedServicesContentHttpProxyServiceStatisticsGridLevelPVideoPacingDetailWebmEntry 2 }

affirmedServicesContentHttpProxyServiceStatisticsGridLevelPVideoPacingDetailWebmVideopacingsuccesses OBJECT-TYPE
    SYNTAX      ConfdString
    MAX-ACCESS  read-only
    STATUS      current
    DESCRIPTION "Number of video pacing successes"
    ::= { affirmedServicesContentHttpProxyServiceStatisticsGridLevelPVideoPacingDetailWebmEntry 3 }

affirmedServicesContentHttpProxyServiceStatisticsGridLevelPVideoPacingDetailWebmVideopacingfailures OBJECT-TYPE
    SYNTAX      ConfdString
    MAX-ACCESS  read-only
    STATUS      current
    DESCRIPTION "Number of video pacing failures"
    ::= { affirmedServicesContentHttpProxyServiceStatisticsGridLevelPVideoPacingDetailWebmEntry 4 }

affirmedServicesContentHttpProxyServiceStatisticsGridLevelPVideoPacingDetailWebmVideopacingserverrsp OBJECT-TYPE
    SYNTAX      ConfdString
    MAX-ACCESS  read-only
    STATUS      current
    DESCRIPTION "Number of Bytes from Server Response"
    ::= { affirmedServicesContentHttpProxyServiceStatisticsGridLevelPVideoPacingDetailWebmEntry 5 }

affirmedServicesContentHttpProxyServiceStatisticsGridLevelPVideoPacingDetailWebmVideopacingclientrsp OBJECT-TYPE
    SYNTAX      ConfdString
    MAX-ACCESS  read-only
    STATUS      current
    DESCRIPTION "Number of Bytes from Client Response"
    ::= { affirmedServicesContentHttpProxyServiceStatisticsGridLevelPVideoPacingDetailWebmEntry 6 }

affirmedServicesContentHttpProxyServiceStatisticsGridLevelPVideoPacingDetailWebmVideodurationmin OBJECT-TYPE
    SYNTAX      ConfdString
    MAX-ACCESS  read-only
    STATUS      current
    DESCRIPTION "Minimum video file duration in seconds"
    ::= { affirmedServicesContentHttpProxyServiceStatisticsGridLevelPVideoPacingDetailWebmEntry 7 }

affirmedServicesContentHttpProxyServiceStatisticsGridLevelPVideoPacingDetailWebmVideodurationmax OBJECT-TYPE
    SYNTAX      ConfdString
    MAX-ACCESS  read-only
    STATUS      current
    DESCRIPTION "Maximum video file duration in seconds"
    ::= { affirmedServicesContentHttpProxyServiceStatisticsGridLevelPVideoPacingDetailWebmEntry 8 }

affirmedServicesContentHttpProxyServiceStatisticsGridLevelPVideoPacingDetailWebmVideodurationaverage OBJECT-TYPE
    SYNTAX      ConfdString
    MAX-ACCESS  read-only
    STATUS      current
    DESCRIPTION "Average video file duration in seconds"
    ::= { affirmedServicesContentHttpProxyServiceStatisticsGridLevelPVideoPacingDetailWebmEntry 9 }

affirmedServicesContentHttpProxyServiceStatisticsGridLevelPVideoPacingDetailWebmVideodurationtotal OBJECT-TYPE
    SYNTAX      ConfdString
    MAX-ACCESS  read-only
    STATUS      current
    DESCRIPTION "Total video file duration in seconds"
    ::= { affirmedServicesContentHttpProxyServiceStatisticsGridLevelPVideoPacingDetailWebmEntry 10 }

affirmedServicesContentHttpProxyServiceStatisticsGridLevelPVideoPacingDetailWebmVideoservingdurationmin OBJECT-TYPE
    SYNTAX      ConfdString
    MAX-ACCESS  read-only
    STATUS      current
    DESCRIPTION "Minimum served video duration in seconds"
    ::= { affirmedServicesContentHttpProxyServiceStatisticsGridLevelPVideoPacingDetailWebmEntry 11 }

affirmedServicesContentHttpProxyServiceStatisticsGridLevelPVideoPacingDetailWebmVideoservingdurationmax OBJECT-TYPE
    SYNTAX      ConfdString
    MAX-ACCESS  read-only
    STATUS      current
    DESCRIPTION "Maximum served video duration in seconds"
    ::= { affirmedServicesContentHttpProxyServiceStatisticsGridLevelPVideoPacingDetailWebmEntry 12 }

affirmedServicesContentHttpProxyServiceStatisticsGridLevelPVideoPacingDetailWebmVideoservingdurationaverage OBJECT-TYPE
    SYNTAX      ConfdString
    MAX-ACCESS  read-only
    STATUS      current
    DESCRIPTION "Average served video duration in seconds"
    ::= { affirmedServicesContentHttpProxyServiceStatisticsGridLevelPVideoPacingDetailWebmEntry 13 }

affirmedServicesContentHttpProxyServiceStatisticsGridLevelPVideoPacingDetailWebmVideoservingdurationtotal OBJECT-TYPE
    SYNTAX      ConfdString
    MAX-ACCESS  read-only
    STATUS      current
    DESCRIPTION "Total served video duration in seconds"
    ::= { affirmedServicesContentHttpProxyServiceStatisticsGridLevelPVideoPacingDetailWebmEntry 14 }

affirmedServicesContentHttpProxyServiceStatisticsGridLevelPVideoPacingDetailWebmVideobitratemin OBJECT-TYPE
    SYNTAX      ConfdString
    MAX-ACCESS  read-only
    STATUS      current
    DESCRIPTION "Minimum video bitrate in kbps"
    ::= { affirmedServicesContentHttpProxyServiceStatisticsGridLevelPVideoPacingDetailWebmEntry 15 }

affirmedServicesContentHttpProxyServiceStatisticsGridLevelPVideoPacingDetailWebmVideobitratemax OBJECT-TYPE
    SYNTAX      ConfdString
    MAX-ACCESS  read-only
    STATUS      current
    DESCRIPTION "Maximum video bitrate in kbps"
    ::= { affirmedServicesContentHttpProxyServiceStatisticsGridLevelPVideoPacingDetailWebmEntry 16 }

affirmedServicesContentHttpProxyServiceStatisticsGridLevelPVideoPacingDetailWebmVideobitrateaverage OBJECT-TYPE
    SYNTAX      ConfdString
    MAX-ACCESS  read-only
    STATUS      current
    DESCRIPTION "Average video bitrate in kbps"
    ::= { affirmedServicesContentHttpProxyServiceStatisticsGridLevelPVideoPacingDetailWebmEntry 17 }

affirmedServicesContentHttpProxyServiceStatisticsGridLevelPVideoPacingDetailWebmVideopacingaborts OBJECT-TYPE
    SYNTAX      ConfdString
    MAX-ACCESS  read-only
    STATUS      current
    DESCRIPTION "Number of video pacing aborted by client"
    ::= { affirmedServicesContentHttpProxyServiceStatisticsGridLevelPVideoPacingDetailWebmEntry 18 }

affirmedServicesContentHttpProxyServiceStatisticsGridLevelPVideoPacingDetailWebmVideosessiondurationmin OBJECT-TYPE
    SYNTAX      ConfdString
    MAX-ACCESS  read-only
    STATUS      current
    DESCRIPTION "Minimum video service time in seconds"
    ::= { affirmedServicesContentHttpProxyServiceStatisticsGridLevelPVideoPacingDetailWebmEntry 19 }

affirmedServicesContentHttpProxyServiceStatisticsGridLevelPVideoPacingDetailWebmVideosessiondurationaverage OBJECT-TYPE
    SYNTAX      ConfdString
    MAX-ACCESS  read-only
    STATUS      current
    DESCRIPTION "Average video service time in seconds"
    ::= { affirmedServicesContentHttpProxyServiceStatisticsGridLevelPVideoPacingDetailWebmEntry 20 }

affirmedServicesContentHttpProxyServiceStatisticsGridLevelPVideoPacingDetailWebmVideosessiondurationmax OBJECT-TYPE
    SYNTAX      ConfdString
    MAX-ACCESS  read-only
    STATUS      current
    DESCRIPTION "Maximum video service time in seconds"
    ::= { affirmedServicesContentHttpProxyServiceStatisticsGridLevelPVideoPacingDetailWebmEntry 21 }

affirmedServicesContentHttpProxyServiceStatisticsGridLevelPVideoPacingDetailWebmVideosessiondurationtotal OBJECT-TYPE
    SYNTAX      ConfdString
    MAX-ACCESS  read-only
    STATUS      current
    DESCRIPTION "Total video service time in seconds"
    ::= { affirmedServicesContentHttpProxyServiceStatisticsGridLevelPVideoPacingDetailWebmEntry 22 }

affirmedServicesContentHttpProxyServiceStatisticsGridLevelPVideoPacingDetailWebmVideopacingoptedoutbysubscriber OBJECT-TYPE
    SYNTAX      ConfdString
    MAX-ACCESS  read-only
    STATUS      current
    DESCRIPTION "Number of video pacing bypass - Opted Out by Subscriber"
    ::= { affirmedServicesContentHttpProxyServiceStatisticsGridLevelPVideoPacingDetailWebmEntry 23 }

affirmedServicesContentHttpProxyServiceStatisticsGridLevelPVideoPacingFailureTable OBJECT-TYPE
    SYNTAX      SEQUENCE OF AffirmedServicesContentHttpProxyServiceStatisticsGridLevelPVideoPacingFailureEntry
    MAX-ACCESS  not-accessible
    STATUS      current
    DESCRIPTION ""
    ::= { affirmedServicesContentHttpProxyServiceStatisticsGridLevelPVideoPacing 3 }

affirmedServicesContentHttpProxyServiceStatisticsGridLevelPVideoPacingFailureEntry OBJECT-TYPE
    SYNTAX      AffirmedServicesContentHttpProxyServiceStatisticsGridLevelPVideoPacingFailureEntry
    MAX-ACCESS  not-accessible
    STATUS      current
    DESCRIPTION ""
    INDEX { affirmedServicesContentHttpProxyServiceStatisticsGridLevelPVideoPacingFailureGrid }
        ::= { affirmedServicesContentHttpProxyServiceStatisticsGridLevelPVideoPacingFailureTable 1 }

AffirmedServicesContentHttpProxyServiceStatisticsGridLevelPVideoPacingFailureEntry ::=
    SEQUENCE {
        affirmedServicesContentHttpProxyServiceStatisticsGridLevelPVideoPacingFailureGrid Unsigned32,
        affirmedServicesContentHttpProxyServiceStatisticsGridLevelPVideoPacingFailureVideopacingfailureunknownmediatype ConfdString,
        affirmedServicesContentHttpProxyServiceStatisticsGridLevelPVideoPacingFailureVideopacingfailureparsingmp4 ConfdString,
        affirmedServicesContentHttpProxyServiceStatisticsGridLevelPVideoPacingFailureVideopacingfailureparsingflv ConfdString,
        affirmedServicesContentHttpProxyServiceStatisticsGridLevelPVideoPacingFailureVideopacingfailureparsingwebm ConfdString,
        affirmedServicesContentHttpProxyServiceStatisticsGridLevelPVideoPacingFailureVideopacingfailureothers ConfdString,
        affirmedServicesContentHttpProxyServiceStatisticsGridLevelPVideoPacingFailureVideopacingcancelcontenttypemismatches ConfdString
    }

affirmedServicesContentHttpProxyServiceStatisticsGridLevelPVideoPacingFailureGrid OBJECT-TYPE
    SYNTAX      Unsigned32
    MAX-ACCESS  not-accessible
    STATUS      current
    DESCRIPTION "grid ID"
    ::= { affirmedServicesContentHttpProxyServiceStatisticsGridLevelPVideoPacingFailureEntry 1 }

affirmedServicesContentHttpProxyServiceStatisticsGridLevelPVideoPacingFailureVideopacingfailureunknownmediatype OBJECT-TYPE
    SYNTAX      ConfdString
    MAX-ACCESS  read-only
    STATUS      current
    DESCRIPTION "Number of Video Pacing Failure Unknown Media Type"
    ::= { affirmedServicesContentHttpProxyServiceStatisticsGridLevelPVideoPacingFailureEntry 2 }

affirmedServicesContentHttpProxyServiceStatisticsGridLevelPVideoPacingFailureVideopacingfailureparsingmp4 OBJECT-TYPE
    SYNTAX      ConfdString
    MAX-ACCESS  read-only
    STATUS      current
    DESCRIPTION "Number of Video Pacing Failure Parsing MP4"
    ::= { affirmedServicesContentHttpProxyServiceStatisticsGridLevelPVideoPacingFailureEntry 3 }

affirmedServicesContentHttpProxyServiceStatisticsGridLevelPVideoPacingFailureVideopacingfailureparsingflv OBJECT-TYPE
    SYNTAX      ConfdString
    MAX-ACCESS  read-only
    STATUS      current
    DESCRIPTION "Number of Video Pacing Failure Parsing FLV"
    ::= { affirmedServicesContentHttpProxyServiceStatisticsGridLevelPVideoPacingFailureEntry 4 }

affirmedServicesContentHttpProxyServiceStatisticsGridLevelPVideoPacingFailureVideopacingfailureparsingwebm OBJECT-TYPE
    SYNTAX      ConfdString
    MAX-ACCESS  read-only
    STATUS      current
    DESCRIPTION "Number of Video Pacing Failure Parsing WEBM"
    ::= { affirmedServicesContentHttpProxyServiceStatisticsGridLevelPVideoPacingFailureEntry 5 }

affirmedServicesContentHttpProxyServiceStatisticsGridLevelPVideoPacingFailureVideopacingfailureothers OBJECT-TYPE
    SYNTAX      ConfdString
    MAX-ACCESS  read-only
    STATUS      current
    DESCRIPTION "Number of Video Pacing Failure Others"
    ::= { affirmedServicesContentHttpProxyServiceStatisticsGridLevelPVideoPacingFailureEntry 6 }

affirmedServicesContentHttpProxyServiceStatisticsGridLevelPVideoPacingFailureVideopacingcancelcontenttypemismatches OBJECT-TYPE
    SYNTAX      ConfdString
    MAX-ACCESS  read-only
    STATUS      current
    DESCRIPTION "Number of Video Pacing Cancel Content-Type Mismatches"
    ::= { affirmedServicesContentHttpProxyServiceStatisticsGridLevelPVideoPacingFailureEntry 7 }

affirmedServicesContentHttpProxyServiceStatisticsChassisLevelVideoPacingSummaryTable OBJECT-TYPE
    SYNTAX      SEQUENCE OF AffirmedServicesContentHttpProxyServiceStatisticsChassisLevelVideoPacingSummaryEntry
    MAX-ACCESS  not-accessible
    STATUS      current
    DESCRIPTION ""
    ::= { affirmedServicesContentHttpProxyServiceStatisticsChassisLevelVideoPacing 1 }

affirmedServicesContentHttpProxyServiceStatisticsChassisLevelVideoPacingSummaryEntry OBJECT-TYPE
    SYNTAX      AffirmedServicesContentHttpProxyServiceStatisticsChassisLevelVideoPacingSummaryEntry
    MAX-ACCESS  not-accessible
    STATUS      current
    DESCRIPTION ""
    INDEX { affirmedServicesContentHttpProxyServiceStatisticsChassisLevelVideoPacingSummaryChassis }
        ::= { affirmedServicesContentHttpProxyServiceStatisticsChassisLevelVideoPacingSummaryTable 1 }

AffirmedServicesContentHttpProxyServiceStatisticsChassisLevelVideoPacingSummaryEntry ::=
    SEQUENCE {
        affirmedServicesContentHttpProxyServiceStatisticsChassisLevelVideoPacingSummaryChassis Unsigned32,
        affirmedServicesContentHttpProxyServiceStatisticsChassisLevelVideoPacingSummaryVideopacingattempts ConfdString,
        affirmedServicesContentHttpProxyServiceStatisticsChassisLevelVideoPacingSummaryVideopacingsuccesses ConfdString,
        affirmedServicesContentHttpProxyServiceStatisticsChassisLevelVideoPacingSummaryVideopacingfailures ConfdString,
        affirmedServicesContentHttpProxyServiceStatisticsChassisLevelVideoPacingSummaryVideopacingstalls ConfdString,
        affirmedServicesContentHttpProxyServiceStatisticsChassisLevelVideoPacingSummaryVideopacingcurrents ConfdString,
        affirmedServicesContentHttpProxyServiceStatisticsChassisLevelVideoPacingSummaryVideopacingserverrsp ConfdString,
        affirmedServicesContentHttpProxyServiceStatisticsChassisLevelVideoPacingSummaryVideopacingclientrsp ConfdString,
        affirmedServicesContentHttpProxyServiceStatisticsChassisLevelVideoPacingSummaryVideodurationmin ConfdString,
        affirmedServicesContentHttpProxyServiceStatisticsChassisLevelVideoPacingSummaryVideodurationmax ConfdString,
        affirmedServicesContentHttpProxyServiceStatisticsChassisLevelVideoPacingSummaryVideodurationaverage ConfdString,
        affirmedServicesContentHttpProxyServiceStatisticsChassisLevelVideoPacingSummaryVideodurationtotal ConfdString,
        affirmedServicesContentHttpProxyServiceStatisticsChassisLevelVideoPacingSummaryVideoservingdurationmin ConfdString,
        affirmedServicesContentHttpProxyServiceStatisticsChassisLevelVideoPacingSummaryVideoservingdurationmax ConfdString,
        affirmedServicesContentHttpProxyServiceStatisticsChassisLevelVideoPacingSummaryVideoservingdurationaverage ConfdString,
        affirmedServicesContentHttpProxyServiceStatisticsChassisLevelVideoPacingSummaryVideoservingdurationtotal ConfdString,
        affirmedServicesContentHttpProxyServiceStatisticsChassisLevelVideoPacingSummaryVideostalldurationmin ConfdString,
        affirmedServicesContentHttpProxyServiceStatisticsChassisLevelVideoPacingSummaryVideostalldurationmax ConfdString,
        affirmedServicesContentHttpProxyServiceStatisticsChassisLevelVideoPacingSummaryVideostalldurationaverage ConfdString,
        affirmedServicesContentHttpProxyServiceStatisticsChassisLevelVideoPacingSummaryVideostalldurationtotal ConfdString,
        affirmedServicesContentHttpProxyServiceStatisticsChassisLevelVideoPacingSummaryVideobitratemin ConfdString,
        affirmedServicesContentHttpProxyServiceStatisticsChassisLevelVideoPacingSummaryVideobitratemax ConfdString,
        affirmedServicesContentHttpProxyServiceStatisticsChassisLevelVideoPacingSummaryVideobitrateaverage ConfdString
    }

affirmedServicesContentHttpProxyServiceStatisticsChassisLevelVideoPacingSummaryChassis OBJECT-TYPE
    SYNTAX      Unsigned32
    MAX-ACCESS  not-accessible
    STATUS      current
    DESCRIPTION ""
    ::= { affirmedServicesContentHttpProxyServiceStatisticsChassisLevelVideoPacingSummaryEntry 1 }

affirmedServicesContentHttpProxyServiceStatisticsChassisLevelVideoPacingSummaryVideopacingattempts OBJECT-TYPE
    SYNTAX      ConfdString
    MAX-ACCESS  read-only
    STATUS      deprecated
    DESCRIPTION "Number of video pacing attempts"
    ::= { affirmedServicesContentHttpProxyServiceStatisticsChassisLevelVideoPacingSummaryEntry 2 }

affirmedServicesContentHttpProxyServiceStatisticsChassisLevelVideoPacingSummaryVideopacingsuccesses OBJECT-TYPE
    SYNTAX      ConfdString
    MAX-ACCESS  read-only
    STATUS      deprecated
    DESCRIPTION "Number of video pacing successes"
    ::= { affirmedServicesContentHttpProxyServiceStatisticsChassisLevelVideoPacingSummaryEntry 3 }

affirmedServicesContentHttpProxyServiceStatisticsChassisLevelVideoPacingSummaryVideopacingfailures OBJECT-TYPE
    SYNTAX      ConfdString
    MAX-ACCESS  read-only
    STATUS      deprecated
    DESCRIPTION "Number of video pacing failures"
    ::= { affirmedServicesContentHttpProxyServiceStatisticsChassisLevelVideoPacingSummaryEntry 4 }

affirmedServicesContentHttpProxyServiceStatisticsChassisLevelVideoPacingSummaryVideopacingstalls OBJECT-TYPE
    SYNTAX      ConfdString
    MAX-ACCESS  read-only
    STATUS      deprecated
    DESCRIPTION "Number of video pacing stalls"
    ::= { affirmedServicesContentHttpProxyServiceStatisticsChassisLevelVideoPacingSummaryEntry 5 }

affirmedServicesContentHttpProxyServiceStatisticsChassisLevelVideoPacingSummaryVideopacingcurrents OBJECT-TYPE
    SYNTAX      ConfdString
    MAX-ACCESS  read-only
    STATUS      deprecated
    DESCRIPTION "Number of video pacing currently paced"
    ::= { affirmedServicesContentHttpProxyServiceStatisticsChassisLevelVideoPacingSummaryEntry 6 }

affirmedServicesContentHttpProxyServiceStatisticsChassisLevelVideoPacingSummaryVideopacingserverrsp OBJECT-TYPE
    SYNTAX      ConfdString
    MAX-ACCESS  read-only
    STATUS      deprecated
    DESCRIPTION "Number of Bytes from Server Response"
    ::= { affirmedServicesContentHttpProxyServiceStatisticsChassisLevelVideoPacingSummaryEntry 7 }

affirmedServicesContentHttpProxyServiceStatisticsChassisLevelVideoPacingSummaryVideopacingclientrsp OBJECT-TYPE
    SYNTAX      ConfdString
    MAX-ACCESS  read-only
    STATUS      deprecated
    DESCRIPTION "Number of Bytes from Client Response"
    ::= { affirmedServicesContentHttpProxyServiceStatisticsChassisLevelVideoPacingSummaryEntry 8 }

affirmedServicesContentHttpProxyServiceStatisticsChassisLevelVideoPacingSummaryVideodurationmin OBJECT-TYPE
    SYNTAX      ConfdString
    MAX-ACCESS  read-only
    STATUS      deprecated
    DESCRIPTION "Minimum video duration in seconds"
    ::= { affirmedServicesContentHttpProxyServiceStatisticsChassisLevelVideoPacingSummaryEntry 9 }

affirmedServicesContentHttpProxyServiceStatisticsChassisLevelVideoPacingSummaryVideodurationmax OBJECT-TYPE
    SYNTAX      ConfdString
    MAX-ACCESS  read-only
    STATUS      deprecated
    DESCRIPTION "Maximum video duration in seconds"
    ::= { affirmedServicesContentHttpProxyServiceStatisticsChassisLevelVideoPacingSummaryEntry 10 }

affirmedServicesContentHttpProxyServiceStatisticsChassisLevelVideoPacingSummaryVideodurationaverage OBJECT-TYPE
    SYNTAX      ConfdString
    MAX-ACCESS  read-only
    STATUS      deprecated
    DESCRIPTION "Average video duration in seconds"
    ::= { affirmedServicesContentHttpProxyServiceStatisticsChassisLevelVideoPacingSummaryEntry 11 }

affirmedServicesContentHttpProxyServiceStatisticsChassisLevelVideoPacingSummaryVideodurationtotal OBJECT-TYPE
    SYNTAX      ConfdString
    MAX-ACCESS  read-only
    STATUS      deprecated
    DESCRIPTION "Total video duration in seconds"
    ::= { affirmedServicesContentHttpProxyServiceStatisticsChassisLevelVideoPacingSummaryEntry 12 }

affirmedServicesContentHttpProxyServiceStatisticsChassisLevelVideoPacingSummaryVideoservingdurationmin OBJECT-TYPE
    SYNTAX      ConfdString
    MAX-ACCESS  read-only
    STATUS      deprecated
    DESCRIPTION "Minimum video serving duration in seconds"
    ::= { affirmedServicesContentHttpProxyServiceStatisticsChassisLevelVideoPacingSummaryEntry 13 }

affirmedServicesContentHttpProxyServiceStatisticsChassisLevelVideoPacingSummaryVideoservingdurationmax OBJECT-TYPE
    SYNTAX      ConfdString
    MAX-ACCESS  read-only
    STATUS      deprecated
    DESCRIPTION "Maximum video serving duration in seconds"
    ::= { affirmedServicesContentHttpProxyServiceStatisticsChassisLevelVideoPacingSummaryEntry 14 }

affirmedServicesContentHttpProxyServiceStatisticsChassisLevelVideoPacingSummaryVideoservingdurationaverage OBJECT-TYPE
    SYNTAX      ConfdString
    MAX-ACCESS  read-only
    STATUS      deprecated
    DESCRIPTION "Average video serving duration in seconds"
    ::= { affirmedServicesContentHttpProxyServiceStatisticsChassisLevelVideoPacingSummaryEntry 15 }

affirmedServicesContentHttpProxyServiceStatisticsChassisLevelVideoPacingSummaryVideoservingdurationtotal OBJECT-TYPE
    SYNTAX      ConfdString
    MAX-ACCESS  read-only
    STATUS      deprecated
    DESCRIPTION "Total video serving duration in seconds"
    ::= { affirmedServicesContentHttpProxyServiceStatisticsChassisLevelVideoPacingSummaryEntry 16 }

affirmedServicesContentHttpProxyServiceStatisticsChassisLevelVideoPacingSummaryVideostalldurationmin OBJECT-TYPE
    SYNTAX      ConfdString
    MAX-ACCESS  read-only
    STATUS      deprecated
    DESCRIPTION "Minimum video pacing stall duration in seconds"
    ::= { affirmedServicesContentHttpProxyServiceStatisticsChassisLevelVideoPacingSummaryEntry 17 }

affirmedServicesContentHttpProxyServiceStatisticsChassisLevelVideoPacingSummaryVideostalldurationmax OBJECT-TYPE
    SYNTAX      ConfdString
    MAX-ACCESS  read-only
    STATUS      deprecated
    DESCRIPTION "Maximum video pacing stall duration in seconds"
    ::= { affirmedServicesContentHttpProxyServiceStatisticsChassisLevelVideoPacingSummaryEntry 18 }

affirmedServicesContentHttpProxyServiceStatisticsChassisLevelVideoPacingSummaryVideostalldurationaverage OBJECT-TYPE
    SYNTAX      ConfdString
    MAX-ACCESS  read-only
    STATUS      deprecated
    DESCRIPTION "Average video pacing stall duration in seconds"
    ::= { affirmedServicesContentHttpProxyServiceStatisticsChassisLevelVideoPacingSummaryEntry 19 }

affirmedServicesContentHttpProxyServiceStatisticsChassisLevelVideoPacingSummaryVideostalldurationtotal OBJECT-TYPE
    SYNTAX      ConfdString
    MAX-ACCESS  read-only
    STATUS      deprecated
    DESCRIPTION "Total video pacing stall duration in seconds"
    ::= { affirmedServicesContentHttpProxyServiceStatisticsChassisLevelVideoPacingSummaryEntry 20 }

affirmedServicesContentHttpProxyServiceStatisticsChassisLevelVideoPacingSummaryVideobitratemin OBJECT-TYPE
    SYNTAX      ConfdString
    MAX-ACCESS  read-only
    STATUS      deprecated
    DESCRIPTION "Minimum video bitrate in kbps"
    ::= { affirmedServicesContentHttpProxyServiceStatisticsChassisLevelVideoPacingSummaryEntry 21 }

affirmedServicesContentHttpProxyServiceStatisticsChassisLevelVideoPacingSummaryVideobitratemax OBJECT-TYPE
    SYNTAX      ConfdString
    MAX-ACCESS  read-only
    STATUS      deprecated
    DESCRIPTION "Maximum video bitrate in kbps"
    ::= { affirmedServicesContentHttpProxyServiceStatisticsChassisLevelVideoPacingSummaryEntry 22 }

affirmedServicesContentHttpProxyServiceStatisticsChassisLevelVideoPacingSummaryVideobitrateaverage OBJECT-TYPE
    SYNTAX      ConfdString
    MAX-ACCESS  read-only
    STATUS      deprecated
    DESCRIPTION "Average video bitrate in kbps"
    ::= { affirmedServicesContentHttpProxyServiceStatisticsChassisLevelVideoPacingSummaryEntry 23 }

affirmedServicesContentHttpProxyServiceStatisticsChassisLevelVideoPacingDetailMp4Table OBJECT-TYPE
    SYNTAX      SEQUENCE OF AffirmedServicesContentHttpProxyServiceStatisticsChassisLevelVideoPacingDetailMp4Entry
    MAX-ACCESS  not-accessible
    STATUS      current
    DESCRIPTION ""
    ::= { affirmedServicesContentHttpProxyServiceStatisticsChassisLevelVideoPacingDetail 1 }

affirmedServicesContentHttpProxyServiceStatisticsChassisLevelVideoPacingDetailMp4Entry OBJECT-TYPE
    SYNTAX      AffirmedServicesContentHttpProxyServiceStatisticsChassisLevelVideoPacingDetailMp4Entry
    MAX-ACCESS  not-accessible
    STATUS      current
    DESCRIPTION ""
    INDEX { affirmedServicesContentHttpProxyServiceStatisticsChassisLevelVideoPacingDetailMp4Chassis }
        ::= { affirmedServicesContentHttpProxyServiceStatisticsChassisLevelVideoPacingDetailMp4Table 1 }

AffirmedServicesContentHttpProxyServiceStatisticsChassisLevelVideoPacingDetailMp4Entry ::=
    SEQUENCE {
        affirmedServicesContentHttpProxyServiceStatisticsChassisLevelVideoPacingDetailMp4Chassis Unsigned32,
        affirmedServicesContentHttpProxyServiceStatisticsChassisLevelVideoPacingDetailMp4Videopacingattempts ConfdString,
        affirmedServicesContentHttpProxyServiceStatisticsChassisLevelVideoPacingDetailMp4Videopacingsuccesses ConfdString,
        affirmedServicesContentHttpProxyServiceStatisticsChassisLevelVideoPacingDetailMp4Videopacingfailures ConfdString,
        affirmedServicesContentHttpProxyServiceStatisticsChassisLevelVideoPacingDetailMp4Videopacingserverrsp ConfdString,
        affirmedServicesContentHttpProxyServiceStatisticsChassisLevelVideoPacingDetailMp4Videopacingclientrsp ConfdString,
        affirmedServicesContentHttpProxyServiceStatisticsChassisLevelVideoPacingDetailMp4Videodurationmin ConfdString,
        affirmedServicesContentHttpProxyServiceStatisticsChassisLevelVideoPacingDetailMp4Videodurationmax ConfdString,
        affirmedServicesContentHttpProxyServiceStatisticsChassisLevelVideoPacingDetailMp4Videodurationaverage ConfdString,
        affirmedServicesContentHttpProxyServiceStatisticsChassisLevelVideoPacingDetailMp4Videodurationtotal ConfdString,
        affirmedServicesContentHttpProxyServiceStatisticsChassisLevelVideoPacingDetailMp4Videoservingdurationmin ConfdString,
        affirmedServicesContentHttpProxyServiceStatisticsChassisLevelVideoPacingDetailMp4Videoservingdurationmax ConfdString,
        affirmedServicesContentHttpProxyServiceStatisticsChassisLevelVideoPacingDetailMp4Videoservingdurationaverage ConfdString,
        affirmedServicesContentHttpProxyServiceStatisticsChassisLevelVideoPacingDetailMp4Videoservingdurationtotal ConfdString,
        affirmedServicesContentHttpProxyServiceStatisticsChassisLevelVideoPacingDetailMp4Videobitratemin ConfdString,
        affirmedServicesContentHttpProxyServiceStatisticsChassisLevelVideoPacingDetailMp4Videobitratemax ConfdString,
        affirmedServicesContentHttpProxyServiceStatisticsChassisLevelVideoPacingDetailMp4Videobitrateaverage ConfdString
    }

affirmedServicesContentHttpProxyServiceStatisticsChassisLevelVideoPacingDetailMp4Chassis OBJECT-TYPE
    SYNTAX      Unsigned32
    MAX-ACCESS  not-accessible
    STATUS      current
    DESCRIPTION ""
    ::= { affirmedServicesContentHttpProxyServiceStatisticsChassisLevelVideoPacingDetailMp4Entry 1 }

affirmedServicesContentHttpProxyServiceStatisticsChassisLevelVideoPacingDetailMp4Videopacingattempts OBJECT-TYPE
    SYNTAX      ConfdString
    MAX-ACCESS  read-only
    STATUS      deprecated
    DESCRIPTION "Number of video pacing attempts"
    ::= { affirmedServicesContentHttpProxyServiceStatisticsChassisLevelVideoPacingDetailMp4Entry 2 }

affirmedServicesContentHttpProxyServiceStatisticsChassisLevelVideoPacingDetailMp4Videopacingsuccesses OBJECT-TYPE
    SYNTAX      ConfdString
    MAX-ACCESS  read-only
    STATUS      deprecated
    DESCRIPTION "Number of video pacing successes"
    ::= { affirmedServicesContentHttpProxyServiceStatisticsChassisLevelVideoPacingDetailMp4Entry 3 }

affirmedServicesContentHttpProxyServiceStatisticsChassisLevelVideoPacingDetailMp4Videopacingfailures OBJECT-TYPE
    SYNTAX      ConfdString
    MAX-ACCESS  read-only
    STATUS      deprecated
    DESCRIPTION "Number of video pacing failures"
    ::= { affirmedServicesContentHttpProxyServiceStatisticsChassisLevelVideoPacingDetailMp4Entry 4 }

affirmedServicesContentHttpProxyServiceStatisticsChassisLevelVideoPacingDetailMp4Videopacingserverrsp OBJECT-TYPE
    SYNTAX      ConfdString
    MAX-ACCESS  read-only
    STATUS      deprecated
    DESCRIPTION "Number of Bytes from Server Response"
    ::= { affirmedServicesContentHttpProxyServiceStatisticsChassisLevelVideoPacingDetailMp4Entry 5 }

affirmedServicesContentHttpProxyServiceStatisticsChassisLevelVideoPacingDetailMp4Videopacingclientrsp OBJECT-TYPE
    SYNTAX      ConfdString
    MAX-ACCESS  read-only
    STATUS      deprecated
    DESCRIPTION "Number of Bytes from Client Response"
    ::= { affirmedServicesContentHttpProxyServiceStatisticsChassisLevelVideoPacingDetailMp4Entry 6 }

affirmedServicesContentHttpProxyServiceStatisticsChassisLevelVideoPacingDetailMp4Videodurationmin OBJECT-TYPE
    SYNTAX      ConfdString
    MAX-ACCESS  read-only
    STATUS      deprecated
    DESCRIPTION "Minimum video duration in seconds"
    ::= { affirmedServicesContentHttpProxyServiceStatisticsChassisLevelVideoPacingDetailMp4Entry 7 }

affirmedServicesContentHttpProxyServiceStatisticsChassisLevelVideoPacingDetailMp4Videodurationmax OBJECT-TYPE
    SYNTAX      ConfdString
    MAX-ACCESS  read-only
    STATUS      deprecated
    DESCRIPTION "Maximum video duration in seconds"
    ::= { affirmedServicesContentHttpProxyServiceStatisticsChassisLevelVideoPacingDetailMp4Entry 8 }

affirmedServicesContentHttpProxyServiceStatisticsChassisLevelVideoPacingDetailMp4Videodurationaverage OBJECT-TYPE
    SYNTAX      ConfdString
    MAX-ACCESS  read-only
    STATUS      deprecated
    DESCRIPTION "Average video duration in seconds"
    ::= { affirmedServicesContentHttpProxyServiceStatisticsChassisLevelVideoPacingDetailMp4Entry 9 }

affirmedServicesContentHttpProxyServiceStatisticsChassisLevelVideoPacingDetailMp4Videodurationtotal OBJECT-TYPE
    SYNTAX      ConfdString
    MAX-ACCESS  read-only
    STATUS      deprecated
    DESCRIPTION "Total video duration in seconds"
    ::= { affirmedServicesContentHttpProxyServiceStatisticsChassisLevelVideoPacingDetailMp4Entry 10 }

affirmedServicesContentHttpProxyServiceStatisticsChassisLevelVideoPacingDetailMp4Videoservingdurationmin OBJECT-TYPE
    SYNTAX      ConfdString
    MAX-ACCESS  read-only
    STATUS      deprecated
    DESCRIPTION "Minimum video serving duration in seconds"
    ::= { affirmedServicesContentHttpProxyServiceStatisticsChassisLevelVideoPacingDetailMp4Entry 11 }

affirmedServicesContentHttpProxyServiceStatisticsChassisLevelVideoPacingDetailMp4Videoservingdurationmax OBJECT-TYPE
    SYNTAX      ConfdString
    MAX-ACCESS  read-only
    STATUS      deprecated
    DESCRIPTION "Maximum video serving duration in seconds"
    ::= { affirmedServicesContentHttpProxyServiceStatisticsChassisLevelVideoPacingDetailMp4Entry 12 }

affirmedServicesContentHttpProxyServiceStatisticsChassisLevelVideoPacingDetailMp4Videoservingdurationaverage OBJECT-TYPE
    SYNTAX      ConfdString
    MAX-ACCESS  read-only
    STATUS      deprecated
    DESCRIPTION "Average video serving duration in seconds"
    ::= { affirmedServicesContentHttpProxyServiceStatisticsChassisLevelVideoPacingDetailMp4Entry 13 }

affirmedServicesContentHttpProxyServiceStatisticsChassisLevelVideoPacingDetailMp4Videoservingdurationtotal OBJECT-TYPE
    SYNTAX      ConfdString
    MAX-ACCESS  read-only
    STATUS      deprecated
    DESCRIPTION "Total video serving duration in seconds"
    ::= { affirmedServicesContentHttpProxyServiceStatisticsChassisLevelVideoPacingDetailMp4Entry 14 }

affirmedServicesContentHttpProxyServiceStatisticsChassisLevelVideoPacingDetailMp4Videobitratemin OBJECT-TYPE
    SYNTAX      ConfdString
    MAX-ACCESS  read-only
    STATUS      deprecated
    DESCRIPTION "Minimum video bitrate in kbps"
    ::= { affirmedServicesContentHttpProxyServiceStatisticsChassisLevelVideoPacingDetailMp4Entry 15 }

affirmedServicesContentHttpProxyServiceStatisticsChassisLevelVideoPacingDetailMp4Videobitratemax OBJECT-TYPE
    SYNTAX      ConfdString
    MAX-ACCESS  read-only
    STATUS      deprecated
    DESCRIPTION "Maximum video bitrate in kbps"
    ::= { affirmedServicesContentHttpProxyServiceStatisticsChassisLevelVideoPacingDetailMp4Entry 16 }

affirmedServicesContentHttpProxyServiceStatisticsChassisLevelVideoPacingDetailMp4Videobitrateaverage OBJECT-TYPE
    SYNTAX      ConfdString
    MAX-ACCESS  read-only
    STATUS      deprecated
    DESCRIPTION "Average video bitrate in kbps"
    ::= { affirmedServicesContentHttpProxyServiceStatisticsChassisLevelVideoPacingDetailMp4Entry 17 }

affirmedServicesContentHttpProxyServiceStatisticsChassisLevelVideoPacingDetailFlvTable OBJECT-TYPE
    SYNTAX      SEQUENCE OF AffirmedServicesContentHttpProxyServiceStatisticsChassisLevelVideoPacingDetailFlvEntry
    MAX-ACCESS  not-accessible
    STATUS      current
    DESCRIPTION ""
    ::= { affirmedServicesContentHttpProxyServiceStatisticsChassisLevelVideoPacingDetail 2 }

affirmedServicesContentHttpProxyServiceStatisticsChassisLevelVideoPacingDetailFlvEntry OBJECT-TYPE
    SYNTAX      AffirmedServicesContentHttpProxyServiceStatisticsChassisLevelVideoPacingDetailFlvEntry
    MAX-ACCESS  not-accessible
    STATUS      current
    DESCRIPTION ""
    INDEX { affirmedServicesContentHttpProxyServiceStatisticsChassisLevelVideoPacingDetailFlvChassis }
        ::= { affirmedServicesContentHttpProxyServiceStatisticsChassisLevelVideoPacingDetailFlvTable 1 }

AffirmedServicesContentHttpProxyServiceStatisticsChassisLevelVideoPacingDetailFlvEntry ::=
    SEQUENCE {
        affirmedServicesContentHttpProxyServiceStatisticsChassisLevelVideoPacingDetailFlvChassis Unsigned32,
        affirmedServicesContentHttpProxyServiceStatisticsChassisLevelVideoPacingDetailFlvVideopacingattempts ConfdString,
        affirmedServicesContentHttpProxyServiceStatisticsChassisLevelVideoPacingDetailFlvVideopacingsuccesses ConfdString,
        affirmedServicesContentHttpProxyServiceStatisticsChassisLevelVideoPacingDetailFlvVideopacingfailures ConfdString,
        affirmedServicesContentHttpProxyServiceStatisticsChassisLevelVideoPacingDetailFlvVideopacingserverrsp ConfdString,
        affirmedServicesContentHttpProxyServiceStatisticsChassisLevelVideoPacingDetailFlvVideopacingclientrsp ConfdString,
        affirmedServicesContentHttpProxyServiceStatisticsChassisLevelVideoPacingDetailFlvVideodurationmin ConfdString,
        affirmedServicesContentHttpProxyServiceStatisticsChassisLevelVideoPacingDetailFlvVideodurationmax ConfdString,
        affirmedServicesContentHttpProxyServiceStatisticsChassisLevelVideoPacingDetailFlvVideodurationaverage ConfdString,
        affirmedServicesContentHttpProxyServiceStatisticsChassisLevelVideoPacingDetailFlvVideodurationtotal ConfdString,
        affirmedServicesContentHttpProxyServiceStatisticsChassisLevelVideoPacingDetailFlvVideoservingdurationmin ConfdString,
        affirmedServicesContentHttpProxyServiceStatisticsChassisLevelVideoPacingDetailFlvVideoservingdurationmax ConfdString,
        affirmedServicesContentHttpProxyServiceStatisticsChassisLevelVideoPacingDetailFlvVideoservingdurationaverage ConfdString,
        affirmedServicesContentHttpProxyServiceStatisticsChassisLevelVideoPacingDetailFlvVideoservingdurationtotal ConfdString,
        affirmedServicesContentHttpProxyServiceStatisticsChassisLevelVideoPacingDetailFlvVideobitratemin ConfdString,
        affirmedServicesContentHttpProxyServiceStatisticsChassisLevelVideoPacingDetailFlvVideobitratemax ConfdString,
        affirmedServicesContentHttpProxyServiceStatisticsChassisLevelVideoPacingDetailFlvVideobitrateaverage ConfdString
    }

affirmedServicesContentHttpProxyServiceStatisticsChassisLevelVideoPacingDetailFlvChassis OBJECT-TYPE
    SYNTAX      Unsigned32
    MAX-ACCESS  not-accessible
    STATUS      current
    DESCRIPTION ""
    ::= { affirmedServicesContentHttpProxyServiceStatisticsChassisLevelVideoPacingDetailFlvEntry 1 }

affirmedServicesContentHttpProxyServiceStatisticsChassisLevelVideoPacingDetailFlvVideopacingattempts OBJECT-TYPE
    SYNTAX      ConfdString
    MAX-ACCESS  read-only
    STATUS      deprecated
    DESCRIPTION "Number of video pacing attempts"
    ::= { affirmedServicesContentHttpProxyServiceStatisticsChassisLevelVideoPacingDetailFlvEntry 2 }

affirmedServicesContentHttpProxyServiceStatisticsChassisLevelVideoPacingDetailFlvVideopacingsuccesses OBJECT-TYPE
    SYNTAX      ConfdString
    MAX-ACCESS  read-only
    STATUS      deprecated
    DESCRIPTION "Number of video pacing successes"
    ::= { affirmedServicesContentHttpProxyServiceStatisticsChassisLevelVideoPacingDetailFlvEntry 3 }

affirmedServicesContentHttpProxyServiceStatisticsChassisLevelVideoPacingDetailFlvVideopacingfailures OBJECT-TYPE
    SYNTAX      ConfdString
    MAX-ACCESS  read-only
    STATUS      deprecated
    DESCRIPTION "Number of video pacing failures"
    ::= { affirmedServicesContentHttpProxyServiceStatisticsChassisLevelVideoPacingDetailFlvEntry 4 }

affirmedServicesContentHttpProxyServiceStatisticsChassisLevelVideoPacingDetailFlvVideopacingserverrsp OBJECT-TYPE
    SYNTAX      ConfdString
    MAX-ACCESS  read-only
    STATUS      deprecated
    DESCRIPTION "Number of Bytes from Server Response"
    ::= { affirmedServicesContentHttpProxyServiceStatisticsChassisLevelVideoPacingDetailFlvEntry 5 }

affirmedServicesContentHttpProxyServiceStatisticsChassisLevelVideoPacingDetailFlvVideopacingclientrsp OBJECT-TYPE
    SYNTAX      ConfdString
    MAX-ACCESS  read-only
    STATUS      deprecated
    DESCRIPTION "Number of Bytes from Client Response"
    ::= { affirmedServicesContentHttpProxyServiceStatisticsChassisLevelVideoPacingDetailFlvEntry 6 }

affirmedServicesContentHttpProxyServiceStatisticsChassisLevelVideoPacingDetailFlvVideodurationmin OBJECT-TYPE
    SYNTAX      ConfdString
    MAX-ACCESS  read-only
    STATUS      deprecated
    DESCRIPTION "Minimum video duration in seconds"
    ::= { affirmedServicesContentHttpProxyServiceStatisticsChassisLevelVideoPacingDetailFlvEntry 7 }

affirmedServicesContentHttpProxyServiceStatisticsChassisLevelVideoPacingDetailFlvVideodurationmax OBJECT-TYPE
    SYNTAX      ConfdString
    MAX-ACCESS  read-only
    STATUS      deprecated
    DESCRIPTION "Maximum video duration in seconds"
    ::= { affirmedServicesContentHttpProxyServiceStatisticsChassisLevelVideoPacingDetailFlvEntry 8 }

affirmedServicesContentHttpProxyServiceStatisticsChassisLevelVideoPacingDetailFlvVideodurationaverage OBJECT-TYPE
    SYNTAX      ConfdString
    MAX-ACCESS  read-only
    STATUS      deprecated
    DESCRIPTION "Average video duration in seconds"
    ::= { affirmedServicesContentHttpProxyServiceStatisticsChassisLevelVideoPacingDetailFlvEntry 9 }

affirmedServicesContentHttpProxyServiceStatisticsChassisLevelVideoPacingDetailFlvVideodurationtotal OBJECT-TYPE
    SYNTAX      ConfdString
    MAX-ACCESS  read-only
    STATUS      deprecated
    DESCRIPTION "Total video duration in seconds"
    ::= { affirmedServicesContentHttpProxyServiceStatisticsChassisLevelVideoPacingDetailFlvEntry 10 }

affirmedServicesContentHttpProxyServiceStatisticsChassisLevelVideoPacingDetailFlvVideoservingdurationmin OBJECT-TYPE
    SYNTAX      ConfdString
    MAX-ACCESS  read-only
    STATUS      deprecated
    DESCRIPTION "Minimum video serving duration in seconds"
    ::= { affirmedServicesContentHttpProxyServiceStatisticsChassisLevelVideoPacingDetailFlvEntry 11 }

affirmedServicesContentHttpProxyServiceStatisticsChassisLevelVideoPacingDetailFlvVideoservingdurationmax OBJECT-TYPE
    SYNTAX      ConfdString
    MAX-ACCESS  read-only
    STATUS      deprecated
    DESCRIPTION "Maximum video serving duration in seconds"
    ::= { affirmedServicesContentHttpProxyServiceStatisticsChassisLevelVideoPacingDetailFlvEntry 12 }

affirmedServicesContentHttpProxyServiceStatisticsChassisLevelVideoPacingDetailFlvVideoservingdurationaverage OBJECT-TYPE
    SYNTAX      ConfdString
    MAX-ACCESS  read-only
    STATUS      deprecated
    DESCRIPTION "Average video serving duration in seconds"
    ::= { affirmedServicesContentHttpProxyServiceStatisticsChassisLevelVideoPacingDetailFlvEntry 13 }

affirmedServicesContentHttpProxyServiceStatisticsChassisLevelVideoPacingDetailFlvVideoservingdurationtotal OBJECT-TYPE
    SYNTAX      ConfdString
    MAX-ACCESS  read-only
    STATUS      deprecated
    DESCRIPTION "Total video serving duration in seconds"
    ::= { affirmedServicesContentHttpProxyServiceStatisticsChassisLevelVideoPacingDetailFlvEntry 14 }

affirmedServicesContentHttpProxyServiceStatisticsChassisLevelVideoPacingDetailFlvVideobitratemin OBJECT-TYPE
    SYNTAX      ConfdString
    MAX-ACCESS  read-only
    STATUS      deprecated
    DESCRIPTION "Minimum video bitrate in kbps"
    ::= { affirmedServicesContentHttpProxyServiceStatisticsChassisLevelVideoPacingDetailFlvEntry 15 }

affirmedServicesContentHttpProxyServiceStatisticsChassisLevelVideoPacingDetailFlvVideobitratemax OBJECT-TYPE
    SYNTAX      ConfdString
    MAX-ACCESS  read-only
    STATUS      deprecated
    DESCRIPTION "Maximum video bitrate in kbps"
    ::= { affirmedServicesContentHttpProxyServiceStatisticsChassisLevelVideoPacingDetailFlvEntry 16 }

affirmedServicesContentHttpProxyServiceStatisticsChassisLevelVideoPacingDetailFlvVideobitrateaverage OBJECT-TYPE
    SYNTAX      ConfdString
    MAX-ACCESS  read-only
    STATUS      deprecated
    DESCRIPTION "Average video bitrate in kbps"
    ::= { affirmedServicesContentHttpProxyServiceStatisticsChassisLevelVideoPacingDetailFlvEntry 17 }

affirmedServicesContentHttpProxyServiceStatisticsChassisLevelVideoPacingDetailWebmTable OBJECT-TYPE
    SYNTAX      SEQUENCE OF AffirmedServicesContentHttpProxyServiceStatisticsChassisLevelVideoPacingDetailWebmEntry
    MAX-ACCESS  not-accessible
    STATUS      current
    DESCRIPTION ""
    ::= { affirmedServicesContentHttpProxyServiceStatisticsChassisLevelVideoPacingDetail 3 }

affirmedServicesContentHttpProxyServiceStatisticsChassisLevelVideoPacingDetailWebmEntry OBJECT-TYPE
    SYNTAX      AffirmedServicesContentHttpProxyServiceStatisticsChassisLevelVideoPacingDetailWebmEntry
    MAX-ACCESS  not-accessible
    STATUS      current
    DESCRIPTION ""
    INDEX { affirmedServicesContentHttpProxyServiceStatisticsChassisLevelVideoPacingDetailWebmChassis }
        ::= { affirmedServicesContentHttpProxyServiceStatisticsChassisLevelVideoPacingDetailWebmTable 1 }

AffirmedServicesContentHttpProxyServiceStatisticsChassisLevelVideoPacingDetailWebmEntry ::=
    SEQUENCE {
        affirmedServicesContentHttpProxyServiceStatisticsChassisLevelVideoPacingDetailWebmChassis Unsigned32,
        affirmedServicesContentHttpProxyServiceStatisticsChassisLevelVideoPacingDetailWebmVideopacingattempts ConfdString,
        affirmedServicesContentHttpProxyServiceStatisticsChassisLevelVideoPacingDetailWebmVideopacingsuccesses ConfdString,
        affirmedServicesContentHttpProxyServiceStatisticsChassisLevelVideoPacingDetailWebmVideopacingfailures ConfdString,
        affirmedServicesContentHttpProxyServiceStatisticsChassisLevelVideoPacingDetailWebmVideopacingserverrsp ConfdString,
        affirmedServicesContentHttpProxyServiceStatisticsChassisLevelVideoPacingDetailWebmVideopacingclientrsp ConfdString,
        affirmedServicesContentHttpProxyServiceStatisticsChassisLevelVideoPacingDetailWebmVideodurationmin ConfdString,
        affirmedServicesContentHttpProxyServiceStatisticsChassisLevelVideoPacingDetailWebmVideodurationmax ConfdString,
        affirmedServicesContentHttpProxyServiceStatisticsChassisLevelVideoPacingDetailWebmVideodurationaverage ConfdString,
        affirmedServicesContentHttpProxyServiceStatisticsChassisLevelVideoPacingDetailWebmVideodurationtotal ConfdString,
        affirmedServicesContentHttpProxyServiceStatisticsChassisLevelVideoPacingDetailWebmVideoservingdurationmin ConfdString,
        affirmedServicesContentHttpProxyServiceStatisticsChassisLevelVideoPacingDetailWebmVideoservingdurationmax ConfdString,
        affirmedServicesContentHttpProxyServiceStatisticsChassisLevelVideoPacingDetailWebmVideoservingdurationaverage ConfdString,
        affirmedServicesContentHttpProxyServiceStatisticsChassisLevelVideoPacingDetailWebmVideoservingdurationtotal ConfdString,
        affirmedServicesContentHttpProxyServiceStatisticsChassisLevelVideoPacingDetailWebmVideobitratemin ConfdString,
        affirmedServicesContentHttpProxyServiceStatisticsChassisLevelVideoPacingDetailWebmVideobitratemax ConfdString,
        affirmedServicesContentHttpProxyServiceStatisticsChassisLevelVideoPacingDetailWebmVideobitrateaverage ConfdString
    }

affirmedServicesContentHttpProxyServiceStatisticsChassisLevelVideoPacingDetailWebmChassis OBJECT-TYPE
    SYNTAX      Unsigned32
    MAX-ACCESS  not-accessible
    STATUS      current
    DESCRIPTION ""
    ::= { affirmedServicesContentHttpProxyServiceStatisticsChassisLevelVideoPacingDetailWebmEntry 1 }

affirmedServicesContentHttpProxyServiceStatisticsChassisLevelVideoPacingDetailWebmVideopacingattempts OBJECT-TYPE
    SYNTAX      ConfdString
    MAX-ACCESS  read-only
    STATUS      deprecated
    DESCRIPTION "Number of video pacing attempts"
    ::= { affirmedServicesContentHttpProxyServiceStatisticsChassisLevelVideoPacingDetailWebmEntry 2 }

affirmedServicesContentHttpProxyServiceStatisticsChassisLevelVideoPacingDetailWebmVideopacingsuccesses OBJECT-TYPE
    SYNTAX      ConfdString
    MAX-ACCESS  read-only
    STATUS      deprecated
    DESCRIPTION "Number of video pacing successes"
    ::= { affirmedServicesContentHttpProxyServiceStatisticsChassisLevelVideoPacingDetailWebmEntry 3 }

affirmedServicesContentHttpProxyServiceStatisticsChassisLevelVideoPacingDetailWebmVideopacingfailures OBJECT-TYPE
    SYNTAX      ConfdString
    MAX-ACCESS  read-only
    STATUS      deprecated
    DESCRIPTION "Number of video pacing failures"
    ::= { affirmedServicesContentHttpProxyServiceStatisticsChassisLevelVideoPacingDetailWebmEntry 4 }

affirmedServicesContentHttpProxyServiceStatisticsChassisLevelVideoPacingDetailWebmVideopacingserverrsp OBJECT-TYPE
    SYNTAX      ConfdString
    MAX-ACCESS  read-only
    STATUS      deprecated
    DESCRIPTION "Number of Bytes from Server Response"
    ::= { affirmedServicesContentHttpProxyServiceStatisticsChassisLevelVideoPacingDetailWebmEntry 5 }

affirmedServicesContentHttpProxyServiceStatisticsChassisLevelVideoPacingDetailWebmVideopacingclientrsp OBJECT-TYPE
    SYNTAX      ConfdString
    MAX-ACCESS  read-only
    STATUS      deprecated
    DESCRIPTION "Number of Bytes from Client Response"
    ::= { affirmedServicesContentHttpProxyServiceStatisticsChassisLevelVideoPacingDetailWebmEntry 6 }

affirmedServicesContentHttpProxyServiceStatisticsChassisLevelVideoPacingDetailWebmVideodurationmin OBJECT-TYPE
    SYNTAX      ConfdString
    MAX-ACCESS  read-only
    STATUS      deprecated
    DESCRIPTION "Minimum video duration in seconds"
    ::= { affirmedServicesContentHttpProxyServiceStatisticsChassisLevelVideoPacingDetailWebmEntry 7 }

affirmedServicesContentHttpProxyServiceStatisticsChassisLevelVideoPacingDetailWebmVideodurationmax OBJECT-TYPE
    SYNTAX      ConfdString
    MAX-ACCESS  read-only
    STATUS      deprecated
    DESCRIPTION "Maximum video duration in seconds"
    ::= { affirmedServicesContentHttpProxyServiceStatisticsChassisLevelVideoPacingDetailWebmEntry 8 }

affirmedServicesContentHttpProxyServiceStatisticsChassisLevelVideoPacingDetailWebmVideodurationaverage OBJECT-TYPE
    SYNTAX      ConfdString
    MAX-ACCESS  read-only
    STATUS      deprecated
    DESCRIPTION "Average video duration in seconds"
    ::= { affirmedServicesContentHttpProxyServiceStatisticsChassisLevelVideoPacingDetailWebmEntry 9 }

affirmedServicesContentHttpProxyServiceStatisticsChassisLevelVideoPacingDetailWebmVideodurationtotal OBJECT-TYPE
    SYNTAX      ConfdString
    MAX-ACCESS  read-only
    STATUS      deprecated
    DESCRIPTION "Total video duration in seconds"
    ::= { affirmedServicesContentHttpProxyServiceStatisticsChassisLevelVideoPacingDetailWebmEntry 10 }

affirmedServicesContentHttpProxyServiceStatisticsChassisLevelVideoPacingDetailWebmVideoservingdurationmin OBJECT-TYPE
    SYNTAX      ConfdString
    MAX-ACCESS  read-only
    STATUS      deprecated
    DESCRIPTION "Minimum video serving duration in seconds"
    ::= { affirmedServicesContentHttpProxyServiceStatisticsChassisLevelVideoPacingDetailWebmEntry 11 }

affirmedServicesContentHttpProxyServiceStatisticsChassisLevelVideoPacingDetailWebmVideoservingdurationmax OBJECT-TYPE
    SYNTAX      ConfdString
    MAX-ACCESS  read-only
    STATUS      deprecated
    DESCRIPTION "Maximum video serving duration in seconds"
    ::= { affirmedServicesContentHttpProxyServiceStatisticsChassisLevelVideoPacingDetailWebmEntry 12 }

affirmedServicesContentHttpProxyServiceStatisticsChassisLevelVideoPacingDetailWebmVideoservingdurationaverage OBJECT-TYPE
    SYNTAX      ConfdString
    MAX-ACCESS  read-only
    STATUS      deprecated
    DESCRIPTION "Average video serving duration in seconds"
    ::= { affirmedServicesContentHttpProxyServiceStatisticsChassisLevelVideoPacingDetailWebmEntry 13 }

affirmedServicesContentHttpProxyServiceStatisticsChassisLevelVideoPacingDetailWebmVideoservingdurationtotal OBJECT-TYPE
    SYNTAX      ConfdString
    MAX-ACCESS  read-only
    STATUS      deprecated
    DESCRIPTION "Total video serving duration in seconds"
    ::= { affirmedServicesContentHttpProxyServiceStatisticsChassisLevelVideoPacingDetailWebmEntry 14 }

affirmedServicesContentHttpProxyServiceStatisticsChassisLevelVideoPacingDetailWebmVideobitratemin OBJECT-TYPE
    SYNTAX      ConfdString
    MAX-ACCESS  read-only
    STATUS      deprecated
    DESCRIPTION "Minimum video bitrate in kbps"
    ::= { affirmedServicesContentHttpProxyServiceStatisticsChassisLevelVideoPacingDetailWebmEntry 15 }

affirmedServicesContentHttpProxyServiceStatisticsChassisLevelVideoPacingDetailWebmVideobitratemax OBJECT-TYPE
    SYNTAX      ConfdString
    MAX-ACCESS  read-only
    STATUS      deprecated
    DESCRIPTION "Maximum video bitrate in kbps"
    ::= { affirmedServicesContentHttpProxyServiceStatisticsChassisLevelVideoPacingDetailWebmEntry 16 }

affirmedServicesContentHttpProxyServiceStatisticsChassisLevelVideoPacingDetailWebmVideobitrateaverage OBJECT-TYPE
    SYNTAX      ConfdString
    MAX-ACCESS  read-only
    STATUS      deprecated
    DESCRIPTION "Average video bitrate in kbps"
    ::= { affirmedServicesContentHttpProxyServiceStatisticsChassisLevelVideoPacingDetailWebmEntry 17 }

affirmedServicesContentHttpProxyServiceStatisticsChassisLevelVideoPacingFailureTable OBJECT-TYPE
    SYNTAX      SEQUENCE OF AffirmedServicesContentHttpProxyServiceStatisticsChassisLevelVideoPacingFailureEntry
    MAX-ACCESS  not-accessible
    STATUS      current
    DESCRIPTION ""
    ::= { affirmedServicesContentHttpProxyServiceStatisticsChassisLevelVideoPacing 3 }

affirmedServicesContentHttpProxyServiceStatisticsChassisLevelVideoPacingFailureEntry OBJECT-TYPE
    SYNTAX      AffirmedServicesContentHttpProxyServiceStatisticsChassisLevelVideoPacingFailureEntry
    MAX-ACCESS  not-accessible
    STATUS      current
    DESCRIPTION ""
    INDEX { affirmedServicesContentHttpProxyServiceStatisticsChassisLevelVideoPacingFailureChassis }
        ::= { affirmedServicesContentHttpProxyServiceStatisticsChassisLevelVideoPacingFailureTable 1 }

AffirmedServicesContentHttpProxyServiceStatisticsChassisLevelVideoPacingFailureEntry ::=
    SEQUENCE {
        affirmedServicesContentHttpProxyServiceStatisticsChassisLevelVideoPacingFailureChassis Unsigned32,
        affirmedServicesContentHttpProxyServiceStatisticsChassisLevelVideoPacingFailureVideopacingfailureunknownmediatype ConfdString,
        affirmedServicesContentHttpProxyServiceStatisticsChassisLevelVideoPacingFailureVideopacingfailureparsingmp4 ConfdString,
        affirmedServicesContentHttpProxyServiceStatisticsChassisLevelVideoPacingFailureVideopacingfailureparsingflv ConfdString,
        affirmedServicesContentHttpProxyServiceStatisticsChassisLevelVideoPacingFailureVideopacingfailureparsingwebm ConfdString,
        affirmedServicesContentHttpProxyServiceStatisticsChassisLevelVideoPacingFailureVideopacingfailureothers ConfdString
    }

affirmedServicesContentHttpProxyServiceStatisticsChassisLevelVideoPacingFailureChassis OBJECT-TYPE
    SYNTAX      Unsigned32
    MAX-ACCESS  not-accessible
    STATUS      current
    DESCRIPTION ""
    ::= { affirmedServicesContentHttpProxyServiceStatisticsChassisLevelVideoPacingFailureEntry 1 }

affirmedServicesContentHttpProxyServiceStatisticsChassisLevelVideoPacingFailureVideopacingfailureunknownmediatype OBJECT-TYPE
    SYNTAX      ConfdString
    MAX-ACCESS  read-only
    STATUS      deprecated
    DESCRIPTION "Number of Video Pacing Failure Unknown Media Type"
    ::= { affirmedServicesContentHttpProxyServiceStatisticsChassisLevelVideoPacingFailureEntry 2 }

affirmedServicesContentHttpProxyServiceStatisticsChassisLevelVideoPacingFailureVideopacingfailureparsingmp4 OBJECT-TYPE
    SYNTAX      ConfdString
    MAX-ACCESS  read-only
    STATUS      deprecated
    DESCRIPTION "Number of Video Pacing Failure Parsing MP4"
    ::= { affirmedServicesContentHttpProxyServiceStatisticsChassisLevelVideoPacingFailureEntry 3 }

affirmedServicesContentHttpProxyServiceStatisticsChassisLevelVideoPacingFailureVideopacingfailureparsingflv OBJECT-TYPE
    SYNTAX      ConfdString
    MAX-ACCESS  read-only
    STATUS      deprecated
    DESCRIPTION "Number of Video Pacing Failure Parsing FLV"
    ::= { affirmedServicesContentHttpProxyServiceStatisticsChassisLevelVideoPacingFailureEntry 4 }

affirmedServicesContentHttpProxyServiceStatisticsChassisLevelVideoPacingFailureVideopacingfailureparsingwebm OBJECT-TYPE
    SYNTAX      ConfdString
    MAX-ACCESS  read-only
    STATUS      deprecated
    DESCRIPTION "Number of Video Pacing Failure Parsing WEBM"
    ::= { affirmedServicesContentHttpProxyServiceStatisticsChassisLevelVideoPacingFailureEntry 5 }

affirmedServicesContentHttpProxyServiceStatisticsChassisLevelVideoPacingFailureVideopacingfailureothers OBJECT-TYPE
    SYNTAX      ConfdString
    MAX-ACCESS  read-only
    STATUS      deprecated
    DESCRIPTION "Number of Video Pacing Failure Others"
    ::= { affirmedServicesContentHttpProxyServiceStatisticsChassisLevelVideoPacingFailureEntry 6 }

affirmedServicesContentHttpProxyServiceStatisticsChassisLevelPVideoPacingSummaryTable OBJECT-TYPE
    SYNTAX      SEQUENCE OF AffirmedServicesContentHttpProxyServiceStatisticsChassisLevelPVideoPacingSummaryEntry
    MAX-ACCESS  not-accessible
    STATUS      current
    DESCRIPTION ""
    ::= { affirmedServicesContentHttpProxyServiceStatisticsChassisLevelPVideoPacing 1 }

affirmedServicesContentHttpProxyServiceStatisticsChassisLevelPVideoPacingSummaryEntry OBJECT-TYPE
    SYNTAX      AffirmedServicesContentHttpProxyServiceStatisticsChassisLevelPVideoPacingSummaryEntry
    MAX-ACCESS  not-accessible
    STATUS      current
    DESCRIPTION ""
    INDEX { affirmedServicesContentHttpProxyServiceStatisticsChassisLevelPVideoPacingSummaryChassis }
        ::= { affirmedServicesContentHttpProxyServiceStatisticsChassisLevelPVideoPacingSummaryTable 1 }

AffirmedServicesContentHttpProxyServiceStatisticsChassisLevelPVideoPacingSummaryEntry ::=
    SEQUENCE {
        affirmedServicesContentHttpProxyServiceStatisticsChassisLevelPVideoPacingSummaryChassis Unsigned32,
        affirmedServicesContentHttpProxyServiceStatisticsChassisLevelPVideoPacingSummaryVideopacingattempts ConfdString,
        affirmedServicesContentHttpProxyServiceStatisticsChassisLevelPVideoPacingSummaryVideopacingsuccesses ConfdString,
        affirmedServicesContentHttpProxyServiceStatisticsChassisLevelPVideoPacingSummaryVideopacingfailures ConfdString,
        affirmedServicesContentHttpProxyServiceStatisticsChassisLevelPVideoPacingSummaryVideopacingstalls ConfdString,
        affirmedServicesContentHttpProxyServiceStatisticsChassisLevelPVideoPacingSummaryVideopacingcurrents ConfdString,
        affirmedServicesContentHttpProxyServiceStatisticsChassisLevelPVideoPacingSummaryVideopacingserverrsp ConfdString,
        affirmedServicesContentHttpProxyServiceStatisticsChassisLevelPVideoPacingSummaryVideopacingclientrsp ConfdString,
        affirmedServicesContentHttpProxyServiceStatisticsChassisLevelPVideoPacingSummaryVideodurationmin ConfdString,
        affirmedServicesContentHttpProxyServiceStatisticsChassisLevelPVideoPacingSummaryVideodurationmax ConfdString,
        affirmedServicesContentHttpProxyServiceStatisticsChassisLevelPVideoPacingSummaryVideodurationaverage ConfdString,
        affirmedServicesContentHttpProxyServiceStatisticsChassisLevelPVideoPacingSummaryVideodurationtotal ConfdString,
        affirmedServicesContentHttpProxyServiceStatisticsChassisLevelPVideoPacingSummaryVideoservingdurationmin ConfdString,
        affirmedServicesContentHttpProxyServiceStatisticsChassisLevelPVideoPacingSummaryVideoservingdurationmax ConfdString,
        affirmedServicesContentHttpProxyServiceStatisticsChassisLevelPVideoPacingSummaryVideoservingdurationaverage ConfdString,
        affirmedServicesContentHttpProxyServiceStatisticsChassisLevelPVideoPacingSummaryVideoservingdurationtotal ConfdString,
        affirmedServicesContentHttpProxyServiceStatisticsChassisLevelPVideoPacingSummaryVideostalldurationmin ConfdString,
        affirmedServicesContentHttpProxyServiceStatisticsChassisLevelPVideoPacingSummaryVideostalldurationmax ConfdString,
        affirmedServicesContentHttpProxyServiceStatisticsChassisLevelPVideoPacingSummaryVideostalldurationaverage ConfdString,
        affirmedServicesContentHttpProxyServiceStatisticsChassisLevelPVideoPacingSummaryVideostalldurationtotal ConfdString,
        affirmedServicesContentHttpProxyServiceStatisticsChassisLevelPVideoPacingSummaryVideobitratemin ConfdString,
        affirmedServicesContentHttpProxyServiceStatisticsChassisLevelPVideoPacingSummaryVideobitratemax ConfdString,
        affirmedServicesContentHttpProxyServiceStatisticsChassisLevelPVideoPacingSummaryVideobitrateaverage ConfdString,
        affirmedServicesContentHttpProxyServiceStatisticsChassisLevelPVideoPacingSummaryVideopacingaborts ConfdString,
        affirmedServicesContentHttpProxyServiceStatisticsChassisLevelPVideoPacingSummaryVideosessiondurationmin ConfdString,
        affirmedServicesContentHttpProxyServiceStatisticsChassisLevelPVideoPacingSummaryVideosessiondurationaverage ConfdString,
        affirmedServicesContentHttpProxyServiceStatisticsChassisLevelPVideoPacingSummaryVideosessiondurationmax ConfdString,
        affirmedServicesContentHttpProxyServiceStatisticsChassisLevelPVideoPacingSummaryVideosessiondurationtotal ConfdString,
        affirmedServicesContentHttpProxyServiceStatisticsChassisLevelPVideoPacingSummaryVideopacingoptedoutbysubscriber ConfdString
    }

affirmedServicesContentHttpProxyServiceStatisticsChassisLevelPVideoPacingSummaryChassis OBJECT-TYPE
    SYNTAX      Unsigned32
    MAX-ACCESS  not-accessible
    STATUS      current
    DESCRIPTION "chassis ID"
    ::= { affirmedServicesContentHttpProxyServiceStatisticsChassisLevelPVideoPacingSummaryEntry 1 }

affirmedServicesContentHttpProxyServiceStatisticsChassisLevelPVideoPacingSummaryVideopacingattempts OBJECT-TYPE
    SYNTAX      ConfdString
    MAX-ACCESS  read-only
    STATUS      current
    DESCRIPTION "Number of video pacing attempts"
    ::= { affirmedServicesContentHttpProxyServiceStatisticsChassisLevelPVideoPacingSummaryEntry 2 }

affirmedServicesContentHttpProxyServiceStatisticsChassisLevelPVideoPacingSummaryVideopacingsuccesses OBJECT-TYPE
    SYNTAX      ConfdString
    MAX-ACCESS  read-only
    STATUS      current
    DESCRIPTION "Number of video pacing successes"
    ::= { affirmedServicesContentHttpProxyServiceStatisticsChassisLevelPVideoPacingSummaryEntry 3 }

affirmedServicesContentHttpProxyServiceStatisticsChassisLevelPVideoPacingSummaryVideopacingfailures OBJECT-TYPE
    SYNTAX      ConfdString
    MAX-ACCESS  read-only
    STATUS      current
    DESCRIPTION "Number of video pacing failures"
    ::= { affirmedServicesContentHttpProxyServiceStatisticsChassisLevelPVideoPacingSummaryEntry 4 }

affirmedServicesContentHttpProxyServiceStatisticsChassisLevelPVideoPacingSummaryVideopacingstalls OBJECT-TYPE
    SYNTAX      ConfdString
    MAX-ACCESS  read-only
    STATUS      current
    DESCRIPTION "Number of video pacing stalls"
    ::= { affirmedServicesContentHttpProxyServiceStatisticsChassisLevelPVideoPacingSummaryEntry 5 }

affirmedServicesContentHttpProxyServiceStatisticsChassisLevelPVideoPacingSummaryVideopacingcurrents OBJECT-TYPE
    SYNTAX      ConfdString
    MAX-ACCESS  read-only
    STATUS      current
    DESCRIPTION "Number of video pacing currently paced"
    ::= { affirmedServicesContentHttpProxyServiceStatisticsChassisLevelPVideoPacingSummaryEntry 6 }

affirmedServicesContentHttpProxyServiceStatisticsChassisLevelPVideoPacingSummaryVideopacingserverrsp OBJECT-TYPE
    SYNTAX      ConfdString
    MAX-ACCESS  read-only
    STATUS      current
    DESCRIPTION "Number of Bytes from Server Response"
    ::= { affirmedServicesContentHttpProxyServiceStatisticsChassisLevelPVideoPacingSummaryEntry 7 }

affirmedServicesContentHttpProxyServiceStatisticsChassisLevelPVideoPacingSummaryVideopacingclientrsp OBJECT-TYPE
    SYNTAX      ConfdString
    MAX-ACCESS  read-only
    STATUS      current
    DESCRIPTION "Number of Bytes from Client Response"
    ::= { affirmedServicesContentHttpProxyServiceStatisticsChassisLevelPVideoPacingSummaryEntry 8 }

affirmedServicesContentHttpProxyServiceStatisticsChassisLevelPVideoPacingSummaryVideodurationmin OBJECT-TYPE
    SYNTAX      ConfdString
    MAX-ACCESS  read-only
    STATUS      current
    DESCRIPTION "Minimum video file duration in seconds"
    ::= { affirmedServicesContentHttpProxyServiceStatisticsChassisLevelPVideoPacingSummaryEntry 9 }

affirmedServicesContentHttpProxyServiceStatisticsChassisLevelPVideoPacingSummaryVideodurationmax OBJECT-TYPE
    SYNTAX      ConfdString
    MAX-ACCESS  read-only
    STATUS      current
    DESCRIPTION "Maximum video file duration in seconds"
    ::= { affirmedServicesContentHttpProxyServiceStatisticsChassisLevelPVideoPacingSummaryEntry 10 }

affirmedServicesContentHttpProxyServiceStatisticsChassisLevelPVideoPacingSummaryVideodurationaverage OBJECT-TYPE
    SYNTAX      ConfdString
    MAX-ACCESS  read-only
    STATUS      current
    DESCRIPTION "Average video file duration in seconds"
    ::= { affirmedServicesContentHttpProxyServiceStatisticsChassisLevelPVideoPacingSummaryEntry 11 }

affirmedServicesContentHttpProxyServiceStatisticsChassisLevelPVideoPacingSummaryVideodurationtotal OBJECT-TYPE
    SYNTAX      ConfdString
    MAX-ACCESS  read-only
    STATUS      current
    DESCRIPTION "Total video file duration in seconds"
    ::= { affirmedServicesContentHttpProxyServiceStatisticsChassisLevelPVideoPacingSummaryEntry 12 }

affirmedServicesContentHttpProxyServiceStatisticsChassisLevelPVideoPacingSummaryVideoservingdurationmin OBJECT-TYPE
    SYNTAX      ConfdString
    MAX-ACCESS  read-only
    STATUS      current
    DESCRIPTION "Minimum served video duration in seconds"
    ::= { affirmedServicesContentHttpProxyServiceStatisticsChassisLevelPVideoPacingSummaryEntry 13 }

affirmedServicesContentHttpProxyServiceStatisticsChassisLevelPVideoPacingSummaryVideoservingdurationmax OBJECT-TYPE
    SYNTAX      ConfdString
    MAX-ACCESS  read-only
    STATUS      current
    DESCRIPTION "Maximum served video duration in seconds"
    ::= { affirmedServicesContentHttpProxyServiceStatisticsChassisLevelPVideoPacingSummaryEntry 14 }

affirmedServicesContentHttpProxyServiceStatisticsChassisLevelPVideoPacingSummaryVideoservingdurationaverage OBJECT-TYPE
    SYNTAX      ConfdString
    MAX-ACCESS  read-only
    STATUS      current
    DESCRIPTION "Average served video duration in seconds"
    ::= { affirmedServicesContentHttpProxyServiceStatisticsChassisLevelPVideoPacingSummaryEntry 15 }

affirmedServicesContentHttpProxyServiceStatisticsChassisLevelPVideoPacingSummaryVideoservingdurationtotal OBJECT-TYPE
    SYNTAX      ConfdString
    MAX-ACCESS  read-only
    STATUS      current
    DESCRIPTION "Total served video duration in seconds"
    ::= { affirmedServicesContentHttpProxyServiceStatisticsChassisLevelPVideoPacingSummaryEntry 16 }

affirmedServicesContentHttpProxyServiceStatisticsChassisLevelPVideoPacingSummaryVideostalldurationmin OBJECT-TYPE
    SYNTAX      ConfdString
    MAX-ACCESS  read-only
    STATUS      current
    DESCRIPTION "Minimum video pacing stall duration in seconds"
    ::= { affirmedServicesContentHttpProxyServiceStatisticsChassisLevelPVideoPacingSummaryEntry 17 }

affirmedServicesContentHttpProxyServiceStatisticsChassisLevelPVideoPacingSummaryVideostalldurationmax OBJECT-TYPE
    SYNTAX      ConfdString
    MAX-ACCESS  read-only
    STATUS      current
    DESCRIPTION "Maximum video pacing stall duration in seconds"
    ::= { affirmedServicesContentHttpProxyServiceStatisticsChassisLevelPVideoPacingSummaryEntry 18 }

affirmedServicesContentHttpProxyServiceStatisticsChassisLevelPVideoPacingSummaryVideostalldurationaverage OBJECT-TYPE
    SYNTAX      ConfdString
    MAX-ACCESS  read-only
    STATUS      current
    DESCRIPTION "Average video pacing stall duration in seconds"
    ::= { affirmedServicesContentHttpProxyServiceStatisticsChassisLevelPVideoPacingSummaryEntry 19 }

affirmedServicesContentHttpProxyServiceStatisticsChassisLevelPVideoPacingSummaryVideostalldurationtotal OBJECT-TYPE
    SYNTAX      ConfdString
    MAX-ACCESS  read-only
    STATUS      current
    DESCRIPTION "Total video pacing stall duration in seconds"
    ::= { affirmedServicesContentHttpProxyServiceStatisticsChassisLevelPVideoPacingSummaryEntry 20 }

affirmedServicesContentHttpProxyServiceStatisticsChassisLevelPVideoPacingSummaryVideobitratemin OBJECT-TYPE
    SYNTAX      ConfdString
    MAX-ACCESS  read-only
    STATUS      current
    DESCRIPTION "Minimum video bitrate in kbps"
    ::= { affirmedServicesContentHttpProxyServiceStatisticsChassisLevelPVideoPacingSummaryEntry 21 }

affirmedServicesContentHttpProxyServiceStatisticsChassisLevelPVideoPacingSummaryVideobitratemax OBJECT-TYPE
    SYNTAX      ConfdString
    MAX-ACCESS  read-only
    STATUS      current
    DESCRIPTION "Maximum video bitrate in kbps"
    ::= { affirmedServicesContentHttpProxyServiceStatisticsChassisLevelPVideoPacingSummaryEntry 22 }

affirmedServicesContentHttpProxyServiceStatisticsChassisLevelPVideoPacingSummaryVideobitrateaverage OBJECT-TYPE
    SYNTAX      ConfdString
    MAX-ACCESS  read-only
    STATUS      current
    DESCRIPTION "Average video bitrate in kbps"
    ::= { affirmedServicesContentHttpProxyServiceStatisticsChassisLevelPVideoPacingSummaryEntry 23 }

affirmedServicesContentHttpProxyServiceStatisticsChassisLevelPVideoPacingSummaryVideopacingaborts OBJECT-TYPE
    SYNTAX      ConfdString
    MAX-ACCESS  read-only
    STATUS      current
    DESCRIPTION "Number of video pacing aborted by client"
    ::= { affirmedServicesContentHttpProxyServiceStatisticsChassisLevelPVideoPacingSummaryEntry 24 }

affirmedServicesContentHttpProxyServiceStatisticsChassisLevelPVideoPacingSummaryVideosessiondurationmin OBJECT-TYPE
    SYNTAX      ConfdString
    MAX-ACCESS  read-only
    STATUS      current
    DESCRIPTION "Minimum video service time in seconds"
    ::= { affirmedServicesContentHttpProxyServiceStatisticsChassisLevelPVideoPacingSummaryEntry 25 }

affirmedServicesContentHttpProxyServiceStatisticsChassisLevelPVideoPacingSummaryVideosessiondurationaverage OBJECT-TYPE
    SYNTAX      ConfdString
    MAX-ACCESS  read-only
    STATUS      current
    DESCRIPTION "Average video service time in seconds"
    ::= { affirmedServicesContentHttpProxyServiceStatisticsChassisLevelPVideoPacingSummaryEntry 26 }

affirmedServicesContentHttpProxyServiceStatisticsChassisLevelPVideoPacingSummaryVideosessiondurationmax OBJECT-TYPE
    SYNTAX      ConfdString
    MAX-ACCESS  read-only
    STATUS      current
    DESCRIPTION "Maximum video service time in seconds"
    ::= { affirmedServicesContentHttpProxyServiceStatisticsChassisLevelPVideoPacingSummaryEntry 27 }

affirmedServicesContentHttpProxyServiceStatisticsChassisLevelPVideoPacingSummaryVideosessiondurationtotal OBJECT-TYPE
    SYNTAX      ConfdString
    MAX-ACCESS  read-only
    STATUS      current
    DESCRIPTION "Total video service time in seconds"
    ::= { affirmedServicesContentHttpProxyServiceStatisticsChassisLevelPVideoPacingSummaryEntry 28 }

affirmedServicesContentHttpProxyServiceStatisticsChassisLevelPVideoPacingSummaryVideopacingoptedoutbysubscriber OBJECT-TYPE
    SYNTAX      ConfdString
    MAX-ACCESS  read-only
    STATUS      current
    DESCRIPTION "Number of video pacing bypass - Opted Out by Subscriber"
    ::= { affirmedServicesContentHttpProxyServiceStatisticsChassisLevelPVideoPacingSummaryEntry 29 }

affirmedServicesContentHttpProxyServiceStatisticsChassisLevelPVideoPacingDetailMp4Table OBJECT-TYPE
    SYNTAX      SEQUENCE OF AffirmedServicesContentHttpProxyServiceStatisticsChassisLevelPVideoPacingDetailMp4Entry
    MAX-ACCESS  not-accessible
    STATUS      current
    DESCRIPTION ""
    ::= { affirmedServicesContentHttpProxyServiceStatisticsChassisLevelPVideoPacingDetail 1 }

affirmedServicesContentHttpProxyServiceStatisticsChassisLevelPVideoPacingDetailMp4Entry OBJECT-TYPE
    SYNTAX      AffirmedServicesContentHttpProxyServiceStatisticsChassisLevelPVideoPacingDetailMp4Entry
    MAX-ACCESS  not-accessible
    STATUS      current
    DESCRIPTION ""
    INDEX { affirmedServicesContentHttpProxyServiceStatisticsChassisLevelPVideoPacingDetailMp4Chassis }
        ::= { affirmedServicesContentHttpProxyServiceStatisticsChassisLevelPVideoPacingDetailMp4Table 1 }

AffirmedServicesContentHttpProxyServiceStatisticsChassisLevelPVideoPacingDetailMp4Entry ::=
    SEQUENCE {
        affirmedServicesContentHttpProxyServiceStatisticsChassisLevelPVideoPacingDetailMp4Chassis Unsigned32,
        affirmedServicesContentHttpProxyServiceStatisticsChassisLevelPVideoPacingDetailMp4Videopacingattempts ConfdString,
        affirmedServicesContentHttpProxyServiceStatisticsChassisLevelPVideoPacingDetailMp4Videopacingsuccesses ConfdString,
        affirmedServicesContentHttpProxyServiceStatisticsChassisLevelPVideoPacingDetailMp4Videopacingfailures ConfdString,
        affirmedServicesContentHttpProxyServiceStatisticsChassisLevelPVideoPacingDetailMp4Videopacingserverrsp ConfdString,
        affirmedServicesContentHttpProxyServiceStatisticsChassisLevelPVideoPacingDetailMp4Videopacingclientrsp ConfdString,
        affirmedServicesContentHttpProxyServiceStatisticsChassisLevelPVideoPacingDetailMp4Videodurationmin ConfdString,
        affirmedServicesContentHttpProxyServiceStatisticsChassisLevelPVideoPacingDetailMp4Videodurationmax ConfdString,
        affirmedServicesContentHttpProxyServiceStatisticsChassisLevelPVideoPacingDetailMp4Videodurationaverage ConfdString,
        affirmedServicesContentHttpProxyServiceStatisticsChassisLevelPVideoPacingDetailMp4Videodurationtotal ConfdString,
        affirmedServicesContentHttpProxyServiceStatisticsChassisLevelPVideoPacingDetailMp4Videoservingdurationmin ConfdString,
        affirmedServicesContentHttpProxyServiceStatisticsChassisLevelPVideoPacingDetailMp4Videoservingdurationmax ConfdString,
        affirmedServicesContentHttpProxyServiceStatisticsChassisLevelPVideoPacingDetailMp4Videoservingdurationaverage ConfdString,
        affirmedServicesContentHttpProxyServiceStatisticsChassisLevelPVideoPacingDetailMp4Videoservingdurationtotal ConfdString,
        affirmedServicesContentHttpProxyServiceStatisticsChassisLevelPVideoPacingDetailMp4Videobitratemin ConfdString,
        affirmedServicesContentHttpProxyServiceStatisticsChassisLevelPVideoPacingDetailMp4Videobitratemax ConfdString,
        affirmedServicesContentHttpProxyServiceStatisticsChassisLevelPVideoPacingDetailMp4Videobitrateaverage ConfdString,
        affirmedServicesContentHttpProxyServiceStatisticsChassisLevelPVideoPacingDetailMp4Videopacingaborts ConfdString,
        affirmedServicesContentHttpProxyServiceStatisticsChassisLevelPVideoPacingDetailMp4Videosessiondurationmin ConfdString,
        affirmedServicesContentHttpProxyServiceStatisticsChassisLevelPVideoPacingDetailMp4Videosessiondurationaverage ConfdString,
        affirmedServicesContentHttpProxyServiceStatisticsChassisLevelPVideoPacingDetailMp4Videosessiondurationmax ConfdString,
        affirmedServicesContentHttpProxyServiceStatisticsChassisLevelPVideoPacingDetailMp4Videosessiondurationtotal ConfdString,
        affirmedServicesContentHttpProxyServiceStatisticsChassisLevelPVideoPacingDetailMp4Videopacingoptedoutbysubscriber ConfdString
    }

affirmedServicesContentHttpProxyServiceStatisticsChassisLevelPVideoPacingDetailMp4Chassis OBJECT-TYPE
    SYNTAX      Unsigned32
    MAX-ACCESS  not-accessible
    STATUS      current
    DESCRIPTION "chassis ID"
    ::= { affirmedServicesContentHttpProxyServiceStatisticsChassisLevelPVideoPacingDetailMp4Entry 1 }

affirmedServicesContentHttpProxyServiceStatisticsChassisLevelPVideoPacingDetailMp4Videopacingattempts OBJECT-TYPE
    SYNTAX      ConfdString
    MAX-ACCESS  read-only
    STATUS      current
    DESCRIPTION "Number of video pacing attempts"
    ::= { affirmedServicesContentHttpProxyServiceStatisticsChassisLevelPVideoPacingDetailMp4Entry 2 }

affirmedServicesContentHttpProxyServiceStatisticsChassisLevelPVideoPacingDetailMp4Videopacingsuccesses OBJECT-TYPE
    SYNTAX      ConfdString
    MAX-ACCESS  read-only
    STATUS      current
    DESCRIPTION "Number of video pacing successes"
    ::= { affirmedServicesContentHttpProxyServiceStatisticsChassisLevelPVideoPacingDetailMp4Entry 3 }

affirmedServicesContentHttpProxyServiceStatisticsChassisLevelPVideoPacingDetailMp4Videopacingfailures OBJECT-TYPE
    SYNTAX      ConfdString
    MAX-ACCESS  read-only
    STATUS      current
    DESCRIPTION "Number of video pacing failures"
    ::= { affirmedServicesContentHttpProxyServiceStatisticsChassisLevelPVideoPacingDetailMp4Entry 4 }

affirmedServicesContentHttpProxyServiceStatisticsChassisLevelPVideoPacingDetailMp4Videopacingserverrsp OBJECT-TYPE
    SYNTAX      ConfdString
    MAX-ACCESS  read-only
    STATUS      current
    DESCRIPTION "Number of Bytes from Server Response"
    ::= { affirmedServicesContentHttpProxyServiceStatisticsChassisLevelPVideoPacingDetailMp4Entry 5 }

affirmedServicesContentHttpProxyServiceStatisticsChassisLevelPVideoPacingDetailMp4Videopacingclientrsp OBJECT-TYPE
    SYNTAX      ConfdString
    MAX-ACCESS  read-only
    STATUS      current
    DESCRIPTION "Number of Bytes from Client Response"
    ::= { affirmedServicesContentHttpProxyServiceStatisticsChassisLevelPVideoPacingDetailMp4Entry 6 }

affirmedServicesContentHttpProxyServiceStatisticsChassisLevelPVideoPacingDetailMp4Videodurationmin OBJECT-TYPE
    SYNTAX      ConfdString
    MAX-ACCESS  read-only
    STATUS      current
    DESCRIPTION "Minimum video file duration in seconds"
    ::= { affirmedServicesContentHttpProxyServiceStatisticsChassisLevelPVideoPacingDetailMp4Entry 7 }

affirmedServicesContentHttpProxyServiceStatisticsChassisLevelPVideoPacingDetailMp4Videodurationmax OBJECT-TYPE
    SYNTAX      ConfdString
    MAX-ACCESS  read-only
    STATUS      current
    DESCRIPTION "Maximum video file duration in seconds"
    ::= { affirmedServicesContentHttpProxyServiceStatisticsChassisLevelPVideoPacingDetailMp4Entry 8 }

affirmedServicesContentHttpProxyServiceStatisticsChassisLevelPVideoPacingDetailMp4Videodurationaverage OBJECT-TYPE
    SYNTAX      ConfdString
    MAX-ACCESS  read-only
    STATUS      current
    DESCRIPTION "Average video file duration in seconds"
    ::= { affirmedServicesContentHttpProxyServiceStatisticsChassisLevelPVideoPacingDetailMp4Entry 9 }

affirmedServicesContentHttpProxyServiceStatisticsChassisLevelPVideoPacingDetailMp4Videodurationtotal OBJECT-TYPE
    SYNTAX      ConfdString
    MAX-ACCESS  read-only
    STATUS      current
    DESCRIPTION "Total video file duration in seconds"
    ::= { affirmedServicesContentHttpProxyServiceStatisticsChassisLevelPVideoPacingDetailMp4Entry 10 }

affirmedServicesContentHttpProxyServiceStatisticsChassisLevelPVideoPacingDetailMp4Videoservingdurationmin OBJECT-TYPE
    SYNTAX      ConfdString
    MAX-ACCESS  read-only
    STATUS      current
    DESCRIPTION "Minimum served video duration in seconds"
    ::= { affirmedServicesContentHttpProxyServiceStatisticsChassisLevelPVideoPacingDetailMp4Entry 11 }

affirmedServicesContentHttpProxyServiceStatisticsChassisLevelPVideoPacingDetailMp4Videoservingdurationmax OBJECT-TYPE
    SYNTAX      ConfdString
    MAX-ACCESS  read-only
    STATUS      current
    DESCRIPTION "Maximum served video duration in seconds"
    ::= { affirmedServicesContentHttpProxyServiceStatisticsChassisLevelPVideoPacingDetailMp4Entry 12 }

affirmedServicesContentHttpProxyServiceStatisticsChassisLevelPVideoPacingDetailMp4Videoservingdurationaverage OBJECT-TYPE
    SYNTAX      ConfdString
    MAX-ACCESS  read-only
    STATUS      current
    DESCRIPTION "Average served video duration in seconds"
    ::= { affirmedServicesContentHttpProxyServiceStatisticsChassisLevelPVideoPacingDetailMp4Entry 13 }

affirmedServicesContentHttpProxyServiceStatisticsChassisLevelPVideoPacingDetailMp4Videoservingdurationtotal OBJECT-TYPE
    SYNTAX      ConfdString
    MAX-ACCESS  read-only
    STATUS      current
    DESCRIPTION "Total served video duration in seconds"
    ::= { affirmedServicesContentHttpProxyServiceStatisticsChassisLevelPVideoPacingDetailMp4Entry 14 }

affirmedServicesContentHttpProxyServiceStatisticsChassisLevelPVideoPacingDetailMp4Videobitratemin OBJECT-TYPE
    SYNTAX      ConfdString
    MAX-ACCESS  read-only
    STATUS      current
    DESCRIPTION "Minimum video bitrate in kbps"
    ::= { affirmedServicesContentHttpProxyServiceStatisticsChassisLevelPVideoPacingDetailMp4Entry 15 }

affirmedServicesContentHttpProxyServiceStatisticsChassisLevelPVideoPacingDetailMp4Videobitratemax OBJECT-TYPE
    SYNTAX      ConfdString
    MAX-ACCESS  read-only
    STATUS      current
    DESCRIPTION "Maximum video bitrate in kbps"
    ::= { affirmedServicesContentHttpProxyServiceStatisticsChassisLevelPVideoPacingDetailMp4Entry 16 }

affirmedServicesContentHttpProxyServiceStatisticsChassisLevelPVideoPacingDetailMp4Videobitrateaverage OBJECT-TYPE
    SYNTAX      ConfdString
    MAX-ACCESS  read-only
    STATUS      current
    DESCRIPTION "Average video bitrate in kbps"
    ::= { affirmedServicesContentHttpProxyServiceStatisticsChassisLevelPVideoPacingDetailMp4Entry 17 }

affirmedServicesContentHttpProxyServiceStatisticsChassisLevelPVideoPacingDetailMp4Videopacingaborts OBJECT-TYPE
    SYNTAX      ConfdString
    MAX-ACCESS  read-only
    STATUS      current
    DESCRIPTION "Number of video pacing aborted by client"
    ::= { affirmedServicesContentHttpProxyServiceStatisticsChassisLevelPVideoPacingDetailMp4Entry 18 }

affirmedServicesContentHttpProxyServiceStatisticsChassisLevelPVideoPacingDetailMp4Videosessiondurationmin OBJECT-TYPE
    SYNTAX      ConfdString
    MAX-ACCESS  read-only
    STATUS      current
    DESCRIPTION "Minimum video service time in seconds"
    ::= { affirmedServicesContentHttpProxyServiceStatisticsChassisLevelPVideoPacingDetailMp4Entry 19 }

affirmedServicesContentHttpProxyServiceStatisticsChassisLevelPVideoPacingDetailMp4Videosessiondurationaverage OBJECT-TYPE
    SYNTAX      ConfdString
    MAX-ACCESS  read-only
    STATUS      current
    DESCRIPTION "Average video service time in seconds"
    ::= { affirmedServicesContentHttpProxyServiceStatisticsChassisLevelPVideoPacingDetailMp4Entry 20 }

affirmedServicesContentHttpProxyServiceStatisticsChassisLevelPVideoPacingDetailMp4Videosessiondurationmax OBJECT-TYPE
    SYNTAX      ConfdString
    MAX-ACCESS  read-only
    STATUS      current
    DESCRIPTION "Maximum video service time in seconds"
    ::= { affirmedServicesContentHttpProxyServiceStatisticsChassisLevelPVideoPacingDetailMp4Entry 21 }

affirmedServicesContentHttpProxyServiceStatisticsChassisLevelPVideoPacingDetailMp4Videosessiondurationtotal OBJECT-TYPE
    SYNTAX      ConfdString
    MAX-ACCESS  read-only
    STATUS      current
    DESCRIPTION "Total video service time in seconds"
    ::= { affirmedServicesContentHttpProxyServiceStatisticsChassisLevelPVideoPacingDetailMp4Entry 22 }

affirmedServicesContentHttpProxyServiceStatisticsChassisLevelPVideoPacingDetailMp4Videopacingoptedoutbysubscriber OBJECT-TYPE
    SYNTAX      ConfdString
    MAX-ACCESS  read-only
    STATUS      current
    DESCRIPTION "Number of video pacing bypass - Opted Out by Subscriber"
    ::= { affirmedServicesContentHttpProxyServiceStatisticsChassisLevelPVideoPacingDetailMp4Entry 23 }

affirmedServicesContentHttpProxyServiceStatisticsChassisLevelPVideoPacingDetailFlvTable OBJECT-TYPE
    SYNTAX      SEQUENCE OF AffirmedServicesContentHttpProxyServiceStatisticsChassisLevelPVideoPacingDetailFlvEntry
    MAX-ACCESS  not-accessible
    STATUS      current
    DESCRIPTION ""
    ::= { affirmedServicesContentHttpProxyServiceStatisticsChassisLevelPVideoPacingDetail 2 }

affirmedServicesContentHttpProxyServiceStatisticsChassisLevelPVideoPacingDetailFlvEntry OBJECT-TYPE
    SYNTAX      AffirmedServicesContentHttpProxyServiceStatisticsChassisLevelPVideoPacingDetailFlvEntry
    MAX-ACCESS  not-accessible
    STATUS      current
    DESCRIPTION ""
    INDEX { affirmedServicesContentHttpProxyServiceStatisticsChassisLevelPVideoPacingDetailFlvChassis }
        ::= { affirmedServicesContentHttpProxyServiceStatisticsChassisLevelPVideoPacingDetailFlvTable 1 }

AffirmedServicesContentHttpProxyServiceStatisticsChassisLevelPVideoPacingDetailFlvEntry ::=
    SEQUENCE {
        affirmedServicesContentHttpProxyServiceStatisticsChassisLevelPVideoPacingDetailFlvChassis Unsigned32,
        affirmedServicesContentHttpProxyServiceStatisticsChassisLevelPVideoPacingDetailFlvVideopacingattempts ConfdString,
        affirmedServicesContentHttpProxyServiceStatisticsChassisLevelPVideoPacingDetailFlvVideopacingsuccesses ConfdString,
        affirmedServicesContentHttpProxyServiceStatisticsChassisLevelPVideoPacingDetailFlvVideopacingfailures ConfdString,
        affirmedServicesContentHttpProxyServiceStatisticsChassisLevelPVideoPacingDetailFlvVideopacingserverrsp ConfdString,
        affirmedServicesContentHttpProxyServiceStatisticsChassisLevelPVideoPacingDetailFlvVideopacingclientrsp ConfdString,
        affirmedServicesContentHttpProxyServiceStatisticsChassisLevelPVideoPacingDetailFlvVideodurationmin ConfdString,
        affirmedServicesContentHttpProxyServiceStatisticsChassisLevelPVideoPacingDetailFlvVideodurationmax ConfdString,
        affirmedServicesContentHttpProxyServiceStatisticsChassisLevelPVideoPacingDetailFlvVideodurationaverage ConfdString,
        affirmedServicesContentHttpProxyServiceStatisticsChassisLevelPVideoPacingDetailFlvVideodurationtotal ConfdString,
        affirmedServicesContentHttpProxyServiceStatisticsChassisLevelPVideoPacingDetailFlvVideoservingdurationmin ConfdString,
        affirmedServicesContentHttpProxyServiceStatisticsChassisLevelPVideoPacingDetailFlvVideoservingdurationmax ConfdString,
        affirmedServicesContentHttpProxyServiceStatisticsChassisLevelPVideoPacingDetailFlvVideoservingdurationaverage ConfdString,
        affirmedServicesContentHttpProxyServiceStatisticsChassisLevelPVideoPacingDetailFlvVideoservingdurationtotal ConfdString,
        affirmedServicesContentHttpProxyServiceStatisticsChassisLevelPVideoPacingDetailFlvVideobitratemin ConfdString,
        affirmedServicesContentHttpProxyServiceStatisticsChassisLevelPVideoPacingDetailFlvVideobitratemax ConfdString,
        affirmedServicesContentHttpProxyServiceStatisticsChassisLevelPVideoPacingDetailFlvVideobitrateaverage ConfdString,
        affirmedServicesContentHttpProxyServiceStatisticsChassisLevelPVideoPacingDetailFlvVideopacingaborts ConfdString,
        affirmedServicesContentHttpProxyServiceStatisticsChassisLevelPVideoPacingDetailFlvVideosessiondurationmin ConfdString,
        affirmedServicesContentHttpProxyServiceStatisticsChassisLevelPVideoPacingDetailFlvVideosessiondurationaverage ConfdString,
        affirmedServicesContentHttpProxyServiceStatisticsChassisLevelPVideoPacingDetailFlvVideosessiondurationmax ConfdString,
        affirmedServicesContentHttpProxyServiceStatisticsChassisLevelPVideoPacingDetailFlvVideosessiondurationtotal ConfdString,
        affirmedServicesContentHttpProxyServiceStatisticsChassisLevelPVideoPacingDetailFlvVideopacingoptedoutbysubscriber ConfdString
    }

affirmedServicesContentHttpProxyServiceStatisticsChassisLevelPVideoPacingDetailFlvChassis OBJECT-TYPE
    SYNTAX      Unsigned32
    MAX-ACCESS  not-accessible
    STATUS      current
    DESCRIPTION "chassis ID"
    ::= { affirmedServicesContentHttpProxyServiceStatisticsChassisLevelPVideoPacingDetailFlvEntry 1 }

affirmedServicesContentHttpProxyServiceStatisticsChassisLevelPVideoPacingDetailFlvVideopacingattempts OBJECT-TYPE
    SYNTAX      ConfdString
    MAX-ACCESS  read-only
    STATUS      current
    DESCRIPTION "Number of video pacing attempts"
    ::= { affirmedServicesContentHttpProxyServiceStatisticsChassisLevelPVideoPacingDetailFlvEntry 2 }

affirmedServicesContentHttpProxyServiceStatisticsChassisLevelPVideoPacingDetailFlvVideopacingsuccesses OBJECT-TYPE
    SYNTAX      ConfdString
    MAX-ACCESS  read-only
    STATUS      current
    DESCRIPTION "Number of video pacing successes"
    ::= { affirmedServicesContentHttpProxyServiceStatisticsChassisLevelPVideoPacingDetailFlvEntry 3 }

affirmedServicesContentHttpProxyServiceStatisticsChassisLevelPVideoPacingDetailFlvVideopacingfailures OBJECT-TYPE
    SYNTAX      ConfdString
    MAX-ACCESS  read-only
    STATUS      current
    DESCRIPTION "Number of video pacing failures"
    ::= { affirmedServicesContentHttpProxyServiceStatisticsChassisLevelPVideoPacingDetailFlvEntry 4 }

affirmedServicesContentHttpProxyServiceStatisticsChassisLevelPVideoPacingDetailFlvVideopacingserverrsp OBJECT-TYPE
    SYNTAX      ConfdString
    MAX-ACCESS  read-only
    STATUS      current
    DESCRIPTION "Number of Bytes from Server Response"
    ::= { affirmedServicesContentHttpProxyServiceStatisticsChassisLevelPVideoPacingDetailFlvEntry 5 }

affirmedServicesContentHttpProxyServiceStatisticsChassisLevelPVideoPacingDetailFlvVideopacingclientrsp OBJECT-TYPE
    SYNTAX      ConfdString
    MAX-ACCESS  read-only
    STATUS      current
    DESCRIPTION "Number of Bytes from Client Response"
    ::= { affirmedServicesContentHttpProxyServiceStatisticsChassisLevelPVideoPacingDetailFlvEntry 6 }

affirmedServicesContentHttpProxyServiceStatisticsChassisLevelPVideoPacingDetailFlvVideodurationmin OBJECT-TYPE
    SYNTAX      ConfdString
    MAX-ACCESS  read-only
    STATUS      current
    DESCRIPTION "Minimum video file duration in seconds"
    ::= { affirmedServicesContentHttpProxyServiceStatisticsChassisLevelPVideoPacingDetailFlvEntry 7 }

affirmedServicesContentHttpProxyServiceStatisticsChassisLevelPVideoPacingDetailFlvVideodurationmax OBJECT-TYPE
    SYNTAX      ConfdString
    MAX-ACCESS  read-only
    STATUS      current
    DESCRIPTION "Maximum video file duration in seconds"
    ::= { affirmedServicesContentHttpProxyServiceStatisticsChassisLevelPVideoPacingDetailFlvEntry 8 }

affirmedServicesContentHttpProxyServiceStatisticsChassisLevelPVideoPacingDetailFlvVideodurationaverage OBJECT-TYPE
    SYNTAX      ConfdString
    MAX-ACCESS  read-only
    STATUS      current
    DESCRIPTION "Average video file duration in seconds"
    ::= { affirmedServicesContentHttpProxyServiceStatisticsChassisLevelPVideoPacingDetailFlvEntry 9 }

affirmedServicesContentHttpProxyServiceStatisticsChassisLevelPVideoPacingDetailFlvVideodurationtotal OBJECT-TYPE
    SYNTAX      ConfdString
    MAX-ACCESS  read-only
    STATUS      current
    DESCRIPTION "Total video file duration in seconds"
    ::= { affirmedServicesContentHttpProxyServiceStatisticsChassisLevelPVideoPacingDetailFlvEntry 10 }

affirmedServicesContentHttpProxyServiceStatisticsChassisLevelPVideoPacingDetailFlvVideoservingdurationmin OBJECT-TYPE
    SYNTAX      ConfdString
    MAX-ACCESS  read-only
    STATUS      current
    DESCRIPTION "Minimum served video duration in seconds"
    ::= { affirmedServicesContentHttpProxyServiceStatisticsChassisLevelPVideoPacingDetailFlvEntry 11 }

affirmedServicesContentHttpProxyServiceStatisticsChassisLevelPVideoPacingDetailFlvVideoservingdurationmax OBJECT-TYPE
    SYNTAX      ConfdString
    MAX-ACCESS  read-only
    STATUS      current
    DESCRIPTION "Maximum served video duration in seconds"
    ::= { affirmedServicesContentHttpProxyServiceStatisticsChassisLevelPVideoPacingDetailFlvEntry 12 }

affirmedServicesContentHttpProxyServiceStatisticsChassisLevelPVideoPacingDetailFlvVideoservingdurationaverage OBJECT-TYPE
    SYNTAX      ConfdString
    MAX-ACCESS  read-only
    STATUS      current
    DESCRIPTION "Average served video duration in seconds"
    ::= { affirmedServicesContentHttpProxyServiceStatisticsChassisLevelPVideoPacingDetailFlvEntry 13 }

affirmedServicesContentHttpProxyServiceStatisticsChassisLevelPVideoPacingDetailFlvVideoservingdurationtotal OBJECT-TYPE
    SYNTAX      ConfdString
    MAX-ACCESS  read-only
    STATUS      current
    DESCRIPTION "Total served video duration in seconds"
    ::= { affirmedServicesContentHttpProxyServiceStatisticsChassisLevelPVideoPacingDetailFlvEntry 14 }

affirmedServicesContentHttpProxyServiceStatisticsChassisLevelPVideoPacingDetailFlvVideobitratemin OBJECT-TYPE
    SYNTAX      ConfdString
    MAX-ACCESS  read-only
    STATUS      current
    DESCRIPTION "Minimum video bitrate in kbps"
    ::= { affirmedServicesContentHttpProxyServiceStatisticsChassisLevelPVideoPacingDetailFlvEntry 15 }

affirmedServicesContentHttpProxyServiceStatisticsChassisLevelPVideoPacingDetailFlvVideobitratemax OBJECT-TYPE
    SYNTAX      ConfdString
    MAX-ACCESS  read-only
    STATUS      current
    DESCRIPTION "Maximum video bitrate in kbps"
    ::= { affirmedServicesContentHttpProxyServiceStatisticsChassisLevelPVideoPacingDetailFlvEntry 16 }

affirmedServicesContentHttpProxyServiceStatisticsChassisLevelPVideoPacingDetailFlvVideobitrateaverage OBJECT-TYPE
    SYNTAX      ConfdString
    MAX-ACCESS  read-only
    STATUS      current
    DESCRIPTION "Average video bitrate in kbps"
    ::= { affirmedServicesContentHttpProxyServiceStatisticsChassisLevelPVideoPacingDetailFlvEntry 17 }

affirmedServicesContentHttpProxyServiceStatisticsChassisLevelPVideoPacingDetailFlvVideopacingaborts OBJECT-TYPE
    SYNTAX      ConfdString
    MAX-ACCESS  read-only
    STATUS      current
    DESCRIPTION "Number of video pacing aborted by client"
    ::= { affirmedServicesContentHttpProxyServiceStatisticsChassisLevelPVideoPacingDetailFlvEntry 18 }

affirmedServicesContentHttpProxyServiceStatisticsChassisLevelPVideoPacingDetailFlvVideosessiondurationmin OBJECT-TYPE
    SYNTAX      ConfdString
    MAX-ACCESS  read-only
    STATUS      current
    DESCRIPTION "Minimum video service time in seconds"
    ::= { affirmedServicesContentHttpProxyServiceStatisticsChassisLevelPVideoPacingDetailFlvEntry 19 }

affirmedServicesContentHttpProxyServiceStatisticsChassisLevelPVideoPacingDetailFlvVideosessiondurationaverage OBJECT-TYPE
    SYNTAX      ConfdString
    MAX-ACCESS  read-only
    STATUS      current
    DESCRIPTION "Average video service time in seconds"
    ::= { affirmedServicesContentHttpProxyServiceStatisticsChassisLevelPVideoPacingDetailFlvEntry 20 }

affirmedServicesContentHttpProxyServiceStatisticsChassisLevelPVideoPacingDetailFlvVideosessiondurationmax OBJECT-TYPE
    SYNTAX      ConfdString
    MAX-ACCESS  read-only
    STATUS      current
    DESCRIPTION "Maximum video service time in seconds"
    ::= { affirmedServicesContentHttpProxyServiceStatisticsChassisLevelPVideoPacingDetailFlvEntry 21 }

affirmedServicesContentHttpProxyServiceStatisticsChassisLevelPVideoPacingDetailFlvVideosessiondurationtotal OBJECT-TYPE
    SYNTAX      ConfdString
    MAX-ACCESS  read-only
    STATUS      current
    DESCRIPTION "Total video service time in seconds"
    ::= { affirmedServicesContentHttpProxyServiceStatisticsChassisLevelPVideoPacingDetailFlvEntry 22 }

affirmedServicesContentHttpProxyServiceStatisticsChassisLevelPVideoPacingDetailFlvVideopacingoptedoutbysubscriber OBJECT-TYPE
    SYNTAX      ConfdString
    MAX-ACCESS  read-only
    STATUS      current
    DESCRIPTION "Number of video pacing bypass - Opted Out by Subscriber"
    ::= { affirmedServicesContentHttpProxyServiceStatisticsChassisLevelPVideoPacingDetailFlvEntry 23 }

affirmedServicesContentHttpProxyServiceStatisticsChassisLevelPVideoPacingDetailWebmTable OBJECT-TYPE
    SYNTAX      SEQUENCE OF AffirmedServicesContentHttpProxyServiceStatisticsChassisLevelPVideoPacingDetailWebmEntry
    MAX-ACCESS  not-accessible
    STATUS      current
    DESCRIPTION ""
    ::= { affirmedServicesContentHttpProxyServiceStatisticsChassisLevelPVideoPacingDetail 3 }

affirmedServicesContentHttpProxyServiceStatisticsChassisLevelPVideoPacingDetailWebmEntry OBJECT-TYPE
    SYNTAX      AffirmedServicesContentHttpProxyServiceStatisticsChassisLevelPVideoPacingDetailWebmEntry
    MAX-ACCESS  not-accessible
    STATUS      current
    DESCRIPTION ""
    INDEX { affirmedServicesContentHttpProxyServiceStatisticsChassisLevelPVideoPacingDetailWebmChassis }
        ::= { affirmedServicesContentHttpProxyServiceStatisticsChassisLevelPVideoPacingDetailWebmTable 1 }

AffirmedServicesContentHttpProxyServiceStatisticsChassisLevelPVideoPacingDetailWebmEntry ::=
    SEQUENCE {
        affirmedServicesContentHttpProxyServiceStatisticsChassisLevelPVideoPacingDetailWebmChassis Unsigned32,
        affirmedServicesContentHttpProxyServiceStatisticsChassisLevelPVideoPacingDetailWebmVideopacingattempts ConfdString,
        affirmedServicesContentHttpProxyServiceStatisticsChassisLevelPVideoPacingDetailWebmVideopacingsuccesses ConfdString,
        affirmedServicesContentHttpProxyServiceStatisticsChassisLevelPVideoPacingDetailWebmVideopacingfailures ConfdString,
        affirmedServicesContentHttpProxyServiceStatisticsChassisLevelPVideoPacingDetailWebmVideopacingserverrsp ConfdString,
        affirmedServicesContentHttpProxyServiceStatisticsChassisLevelPVideoPacingDetailWebmVideopacingclientrsp ConfdString,
        affirmedServicesContentHttpProxyServiceStatisticsChassisLevelPVideoPacingDetailWebmVideodurationmin ConfdString,
        affirmedServicesContentHttpProxyServiceStatisticsChassisLevelPVideoPacingDetailWebmVideodurationmax ConfdString,
        affirmedServicesContentHttpProxyServiceStatisticsChassisLevelPVideoPacingDetailWebmVideodurationaverage ConfdString,
        affirmedServicesContentHttpProxyServiceStatisticsChassisLevelPVideoPacingDetailWebmVideodurationtotal ConfdString,
        affirmedServicesContentHttpProxyServiceStatisticsChassisLevelPVideoPacingDetailWebmVideoservingdurationmin ConfdString,
        affirmedServicesContentHttpProxyServiceStatisticsChassisLevelPVideoPacingDetailWebmVideoservingdurationmax ConfdString,
        affirmedServicesContentHttpProxyServiceStatisticsChassisLevelPVideoPacingDetailWebmVideoservingdurationaverage ConfdString,
        affirmedServicesContentHttpProxyServiceStatisticsChassisLevelPVideoPacingDetailWebmVideoservingdurationtotal ConfdString,
        affirmedServicesContentHttpProxyServiceStatisticsChassisLevelPVideoPacingDetailWebmVideobitratemin ConfdString,
        affirmedServicesContentHttpProxyServiceStatisticsChassisLevelPVideoPacingDetailWebmVideobitratemax ConfdString,
        affirmedServicesContentHttpProxyServiceStatisticsChassisLevelPVideoPacingDetailWebmVideobitrateaverage ConfdString,
        affirmedServicesContentHttpProxyServiceStatisticsChassisLevelPVideoPacingDetailWebmVideopacingaborts ConfdString,
        affirmedServicesContentHttpProxyServiceStatisticsChassisLevelPVideoPacingDetailWebmVideosessiondurationmin ConfdString,
        affirmedServicesContentHttpProxyServiceStatisticsChassisLevelPVideoPacingDetailWebmVideosessiondurationaverage ConfdString,
        affirmedServicesContentHttpProxyServiceStatisticsChassisLevelPVideoPacingDetailWebmVideosessiondurationmax ConfdString,
        affirmedServicesContentHttpProxyServiceStatisticsChassisLevelPVideoPacingDetailWebmVideosessiondurationtotal ConfdString,
        affirmedServicesContentHttpProxyServiceStatisticsChassisLevelPVideoPacingDetailWebmVideopacingoptedoutbysubscriber ConfdString
    }

affirmedServicesContentHttpProxyServiceStatisticsChassisLevelPVideoPacingDetailWebmChassis OBJECT-TYPE
    SYNTAX      Unsigned32
    MAX-ACCESS  not-accessible
    STATUS      current
    DESCRIPTION "chassis ID"
    ::= { affirmedServicesContentHttpProxyServiceStatisticsChassisLevelPVideoPacingDetailWebmEntry 1 }

affirmedServicesContentHttpProxyServiceStatisticsChassisLevelPVideoPacingDetailWebmVideopacingattempts OBJECT-TYPE
    SYNTAX      ConfdString
    MAX-ACCESS  read-only
    STATUS      current
    DESCRIPTION "Number of video pacing attempts"
    ::= { affirmedServicesContentHttpProxyServiceStatisticsChassisLevelPVideoPacingDetailWebmEntry 2 }

affirmedServicesContentHttpProxyServiceStatisticsChassisLevelPVideoPacingDetailWebmVideopacingsuccesses OBJECT-TYPE
    SYNTAX      ConfdString
    MAX-ACCESS  read-only
    STATUS      current
    DESCRIPTION "Number of video pacing successes"
    ::= { affirmedServicesContentHttpProxyServiceStatisticsChassisLevelPVideoPacingDetailWebmEntry 3 }

affirmedServicesContentHttpProxyServiceStatisticsChassisLevelPVideoPacingDetailWebmVideopacingfailures OBJECT-TYPE
    SYNTAX      ConfdString
    MAX-ACCESS  read-only
    STATUS      current
    DESCRIPTION "Number of video pacing failures"
    ::= { affirmedServicesContentHttpProxyServiceStatisticsChassisLevelPVideoPacingDetailWebmEntry 4 }

affirmedServicesContentHttpProxyServiceStatisticsChassisLevelPVideoPacingDetailWebmVideopacingserverrsp OBJECT-TYPE
    SYNTAX      ConfdString
    MAX-ACCESS  read-only
    STATUS      current
    DESCRIPTION "Number of Bytes from Server Response"
    ::= { affirmedServicesContentHttpProxyServiceStatisticsChassisLevelPVideoPacingDetailWebmEntry 5 }

affirmedServicesContentHttpProxyServiceStatisticsChassisLevelPVideoPacingDetailWebmVideopacingclientrsp OBJECT-TYPE
    SYNTAX      ConfdString
    MAX-ACCESS  read-only
    STATUS      current
    DESCRIPTION "Number of Bytes from Client Response"
    ::= { affirmedServicesContentHttpProxyServiceStatisticsChassisLevelPVideoPacingDetailWebmEntry 6 }

affirmedServicesContentHttpProxyServiceStatisticsChassisLevelPVideoPacingDetailWebmVideodurationmin OBJECT-TYPE
    SYNTAX      ConfdString
    MAX-ACCESS  read-only
    STATUS      current
    DESCRIPTION "Minimum video file duration in seconds"
    ::= { affirmedServicesContentHttpProxyServiceStatisticsChassisLevelPVideoPacingDetailWebmEntry 7 }

affirmedServicesContentHttpProxyServiceStatisticsChassisLevelPVideoPacingDetailWebmVideodurationmax OBJECT-TYPE
    SYNTAX      ConfdString
    MAX-ACCESS  read-only
    STATUS      current
    DESCRIPTION "Maximum video file duration in seconds"
    ::= { affirmedServicesContentHttpProxyServiceStatisticsChassisLevelPVideoPacingDetailWebmEntry 8 }

affirmedServicesContentHttpProxyServiceStatisticsChassisLevelPVideoPacingDetailWebmVideodurationaverage OBJECT-TYPE
    SYNTAX      ConfdString
    MAX-ACCESS  read-only
    STATUS      current
    DESCRIPTION "Average video file duration in seconds"
    ::= { affirmedServicesContentHttpProxyServiceStatisticsChassisLevelPVideoPacingDetailWebmEntry 9 }

affirmedServicesContentHttpProxyServiceStatisticsChassisLevelPVideoPacingDetailWebmVideodurationtotal OBJECT-TYPE
    SYNTAX      ConfdString
    MAX-ACCESS  read-only
    STATUS      current
    DESCRIPTION "Total video file duration in seconds"
    ::= { affirmedServicesContentHttpProxyServiceStatisticsChassisLevelPVideoPacingDetailWebmEntry 10 }

affirmedServicesContentHttpProxyServiceStatisticsChassisLevelPVideoPacingDetailWebmVideoservingdurationmin OBJECT-TYPE
    SYNTAX      ConfdString
    MAX-ACCESS  read-only
    STATUS      current
    DESCRIPTION "Minimum served video duration in seconds"
    ::= { affirmedServicesContentHttpProxyServiceStatisticsChassisLevelPVideoPacingDetailWebmEntry 11 }

affirmedServicesContentHttpProxyServiceStatisticsChassisLevelPVideoPacingDetailWebmVideoservingdurationmax OBJECT-TYPE
    SYNTAX      ConfdString
    MAX-ACCESS  read-only
    STATUS      current
    DESCRIPTION "Maximum served video duration in seconds"
    ::= { affirmedServicesContentHttpProxyServiceStatisticsChassisLevelPVideoPacingDetailWebmEntry 12 }

affirmedServicesContentHttpProxyServiceStatisticsChassisLevelPVideoPacingDetailWebmVideoservingdurationaverage OBJECT-TYPE
    SYNTAX      ConfdString
    MAX-ACCESS  read-only
    STATUS      current
    DESCRIPTION "Average served video duration in seconds"
    ::= { affirmedServicesContentHttpProxyServiceStatisticsChassisLevelPVideoPacingDetailWebmEntry 13 }

affirmedServicesContentHttpProxyServiceStatisticsChassisLevelPVideoPacingDetailWebmVideoservingdurationtotal OBJECT-TYPE
    SYNTAX      ConfdString
    MAX-ACCESS  read-only
    STATUS      current
    DESCRIPTION "Total served video duration in seconds"
    ::= { affirmedServicesContentHttpProxyServiceStatisticsChassisLevelPVideoPacingDetailWebmEntry 14 }

affirmedServicesContentHttpProxyServiceStatisticsChassisLevelPVideoPacingDetailWebmVideobitratemin OBJECT-TYPE
    SYNTAX      ConfdString
    MAX-ACCESS  read-only
    STATUS      current
    DESCRIPTION "Minimum video bitrate in kbps"
    ::= { affirmedServicesContentHttpProxyServiceStatisticsChassisLevelPVideoPacingDetailWebmEntry 15 }

affirmedServicesContentHttpProxyServiceStatisticsChassisLevelPVideoPacingDetailWebmVideobitratemax OBJECT-TYPE
    SYNTAX      ConfdString
    MAX-ACCESS  read-only
    STATUS      current
    DESCRIPTION "Maximum video bitrate in kbps"
    ::= { affirmedServicesContentHttpProxyServiceStatisticsChassisLevelPVideoPacingDetailWebmEntry 16 }

affirmedServicesContentHttpProxyServiceStatisticsChassisLevelPVideoPacingDetailWebmVideobitrateaverage OBJECT-TYPE
    SYNTAX      ConfdString
    MAX-ACCESS  read-only
    STATUS      current
    DESCRIPTION "Average video bitrate in kbps"
    ::= { affirmedServicesContentHttpProxyServiceStatisticsChassisLevelPVideoPacingDetailWebmEntry 17 }

affirmedServicesContentHttpProxyServiceStatisticsChassisLevelPVideoPacingDetailWebmVideopacingaborts OBJECT-TYPE
    SYNTAX      ConfdString
    MAX-ACCESS  read-only
    STATUS      current
    DESCRIPTION "Number of video pacing aborted by client"
    ::= { affirmedServicesContentHttpProxyServiceStatisticsChassisLevelPVideoPacingDetailWebmEntry 18 }

affirmedServicesContentHttpProxyServiceStatisticsChassisLevelPVideoPacingDetailWebmVideosessiondurationmin OBJECT-TYPE
    SYNTAX      ConfdString
    MAX-ACCESS  read-only
    STATUS      current
    DESCRIPTION "Minimum video service time in seconds"
    ::= { affirmedServicesContentHttpProxyServiceStatisticsChassisLevelPVideoPacingDetailWebmEntry 19 }

affirmedServicesContentHttpProxyServiceStatisticsChassisLevelPVideoPacingDetailWebmVideosessiondurationaverage OBJECT-TYPE
    SYNTAX      ConfdString
    MAX-ACCESS  read-only
    STATUS      current
    DESCRIPTION "Average video service time in seconds"
    ::= { affirmedServicesContentHttpProxyServiceStatisticsChassisLevelPVideoPacingDetailWebmEntry 20 }

affirmedServicesContentHttpProxyServiceStatisticsChassisLevelPVideoPacingDetailWebmVideosessiondurationmax OBJECT-TYPE
    SYNTAX      ConfdString
    MAX-ACCESS  read-only
    STATUS      current
    DESCRIPTION "Maximum video service time in seconds"
    ::= { affirmedServicesContentHttpProxyServiceStatisticsChassisLevelPVideoPacingDetailWebmEntry 21 }

affirmedServicesContentHttpProxyServiceStatisticsChassisLevelPVideoPacingDetailWebmVideosessiondurationtotal OBJECT-TYPE
    SYNTAX      ConfdString
    MAX-ACCESS  read-only
    STATUS      current
    DESCRIPTION "Total video service time in seconds"
    ::= { affirmedServicesContentHttpProxyServiceStatisticsChassisLevelPVideoPacingDetailWebmEntry 22 }

affirmedServicesContentHttpProxyServiceStatisticsChassisLevelPVideoPacingDetailWebmVideopacingoptedoutbysubscriber OBJECT-TYPE
    SYNTAX      ConfdString
    MAX-ACCESS  read-only
    STATUS      current
    DESCRIPTION "Number of video pacing bypass - Opted Out by Subscriber"
    ::= { affirmedServicesContentHttpProxyServiceStatisticsChassisLevelPVideoPacingDetailWebmEntry 23 }

affirmedServicesContentHttpProxyServiceStatisticsChassisLevelPVideoPacingFailureTable OBJECT-TYPE
    SYNTAX      SEQUENCE OF AffirmedServicesContentHttpProxyServiceStatisticsChassisLevelPVideoPacingFailureEntry
    MAX-ACCESS  not-accessible
    STATUS      current
    DESCRIPTION ""
    ::= { affirmedServicesContentHttpProxyServiceStatisticsChassisLevelPVideoPacing 3 }

affirmedServicesContentHttpProxyServiceStatisticsChassisLevelPVideoPacingFailureEntry OBJECT-TYPE
    SYNTAX      AffirmedServicesContentHttpProxyServiceStatisticsChassisLevelPVideoPacingFailureEntry
    MAX-ACCESS  not-accessible
    STATUS      current
    DESCRIPTION ""
    INDEX { affirmedServicesContentHttpProxyServiceStatisticsChassisLevelPVideoPacingFailureChassis }
        ::= { affirmedServicesContentHttpProxyServiceStatisticsChassisLevelPVideoPacingFailureTable 1 }

AffirmedServicesContentHttpProxyServiceStatisticsChassisLevelPVideoPacingFailureEntry ::=
    SEQUENCE {
        affirmedServicesContentHttpProxyServiceStatisticsChassisLevelPVideoPacingFailureChassis Unsigned32,
        affirmedServicesContentHttpProxyServiceStatisticsChassisLevelPVideoPacingFailureVideopacingfailureunknownmediatype ConfdString,
        affirmedServicesContentHttpProxyServiceStatisticsChassisLevelPVideoPacingFailureVideopacingfailureparsingmp4 ConfdString,
        affirmedServicesContentHttpProxyServiceStatisticsChassisLevelPVideoPacingFailureVideopacingfailureparsingflv ConfdString,
        affirmedServicesContentHttpProxyServiceStatisticsChassisLevelPVideoPacingFailureVideopacingfailureparsingwebm ConfdString,
        affirmedServicesContentHttpProxyServiceStatisticsChassisLevelPVideoPacingFailureVideopacingfailureothers ConfdString,
        affirmedServicesContentHttpProxyServiceStatisticsChassisLevelPVideoPacingFailureVideopacingcancelcontenttypemismatches ConfdString
    }

affirmedServicesContentHttpProxyServiceStatisticsChassisLevelPVideoPacingFailureChassis OBJECT-TYPE
    SYNTAX      Unsigned32
    MAX-ACCESS  not-accessible
    STATUS      current
    DESCRIPTION "chassis ID"
    ::= { affirmedServicesContentHttpProxyServiceStatisticsChassisLevelPVideoPacingFailureEntry 1 }

affirmedServicesContentHttpProxyServiceStatisticsChassisLevelPVideoPacingFailureVideopacingfailureunknownmediatype OBJECT-TYPE
    SYNTAX      ConfdString
    MAX-ACCESS  read-only
    STATUS      current
    DESCRIPTION "Number of Video Pacing Failure Unknown Media Type"
    ::= { affirmedServicesContentHttpProxyServiceStatisticsChassisLevelPVideoPacingFailureEntry 2 }

affirmedServicesContentHttpProxyServiceStatisticsChassisLevelPVideoPacingFailureVideopacingfailureparsingmp4 OBJECT-TYPE
    SYNTAX      ConfdString
    MAX-ACCESS  read-only
    STATUS      current
    DESCRIPTION "Number of Video Pacing Failure Parsing MP4"
    ::= { affirmedServicesContentHttpProxyServiceStatisticsChassisLevelPVideoPacingFailureEntry 3 }

affirmedServicesContentHttpProxyServiceStatisticsChassisLevelPVideoPacingFailureVideopacingfailureparsingflv OBJECT-TYPE
    SYNTAX      ConfdString
    MAX-ACCESS  read-only
    STATUS      current
    DESCRIPTION "Number of Video Pacing Failure Parsing FLV"
    ::= { affirmedServicesContentHttpProxyServiceStatisticsChassisLevelPVideoPacingFailureEntry 4 }

affirmedServicesContentHttpProxyServiceStatisticsChassisLevelPVideoPacingFailureVideopacingfailureparsingwebm OBJECT-TYPE
    SYNTAX      ConfdString
    MAX-ACCESS  read-only
    STATUS      current
    DESCRIPTION "Number of Video Pacing Failure Parsing WEBM"
    ::= { affirmedServicesContentHttpProxyServiceStatisticsChassisLevelPVideoPacingFailureEntry 5 }

affirmedServicesContentHttpProxyServiceStatisticsChassisLevelPVideoPacingFailureVideopacingfailureothers OBJECT-TYPE
    SYNTAX      ConfdString
    MAX-ACCESS  read-only
    STATUS      current
    DESCRIPTION "Number of Video Pacing Failure Others"
    ::= { affirmedServicesContentHttpProxyServiceStatisticsChassisLevelPVideoPacingFailureEntry 6 }

affirmedServicesContentHttpProxyServiceStatisticsChassisLevelPVideoPacingFailureVideopacingcancelcontenttypemismatches OBJECT-TYPE
    SYNTAX      ConfdString
    MAX-ACCESS  read-only
    STATUS      current
    DESCRIPTION "Number of Video Pacing Cancel Content-Type Mismatches"
    ::= { affirmedServicesContentHttpProxyServiceStatisticsChassisLevelPVideoPacingFailureEntry 7 }

affirmedServicesContentHttpProxyServiceStatisticsChassisLevelOptimizationSavingsOptzsavingsTable OBJECT-TYPE
    SYNTAX      SEQUENCE OF AffirmedServicesContentHttpProxyServiceStatisticsChassisLevelOptimizationSavingsOptzsavingsEntry
    MAX-ACCESS  not-accessible
    STATUS      current
    DESCRIPTION ""
    ::= { affirmedServicesContentHttpProxyServiceStatisticsChassisLevelOptimizationSavings 1 }

affirmedServicesContentHttpProxyServiceStatisticsChassisLevelOptimizationSavingsOptzsavingsEntry OBJECT-TYPE
    SYNTAX      AffirmedServicesContentHttpProxyServiceStatisticsChassisLevelOptimizationSavingsOptzsavingsEntry
    MAX-ACCESS  not-accessible
    STATUS      current
    DESCRIPTION ""
    INDEX { affirmedServicesContentHttpProxyServiceStatisticsChassisLevelOptimizationSavingsOptzsavingsChassis }
        ::= { affirmedServicesContentHttpProxyServiceStatisticsChassisLevelOptimizationSavingsOptzsavingsTable 1 }

AffirmedServicesContentHttpProxyServiceStatisticsChassisLevelOptimizationSavingsOptzsavingsEntry ::=
    SEQUENCE {
        affirmedServicesContentHttpProxyServiceStatisticsChassisLevelOptimizationSavingsOptzsavingsChassis Unsigned32,
        affirmedServicesContentHttpProxyServiceStatisticsChassisLevelOptimizationSavingsOptzsavingsVideopacingtotalbytessaved ConfdString,
        affirmedServicesContentHttpProxyServiceStatisticsChassisLevelOptimizationSavingsOptzsavingsVideopacingflvbytessaved ConfdString,
        affirmedServicesContentHttpProxyServiceStatisticsChassisLevelOptimizationSavingsOptzsavingsVideopacingmp4bytessaved ConfdString,
        affirmedServicesContentHttpProxyServiceStatisticsChassisLevelOptimizationSavingsOptzsavingsVideopacingwebmbytessaved ConfdString,
        affirmedServicesContentHttpProxyServiceStatisticsChassisLevelOptimizationSavingsOptzsavingsOnlinevideoxcodingtotalbytessaved ConfdString,
        affirmedServicesContentHttpProxyServiceStatisticsChassisLevelOptimizationSavingsOptzsavingsOnlinevideoxcodingflvbytessaved ConfdString,
        affirmedServicesContentHttpProxyServiceStatisticsChassisLevelOptimizationSavingsOptzsavingsOnlinevideoxcodingmp4bytessaved ConfdString,
        affirmedServicesContentHttpProxyServiceStatisticsChassisLevelOptimizationSavingsOptzsavingsOnlinevideoxcodingwebmbytessaved ConfdString,
        affirmedServicesContentHttpProxyServiceStatisticsChassisLevelOptimizationSavingsOptzsavingsOfflinevideoxcodingtotalbytessaved ConfdString,
        affirmedServicesContentHttpProxyServiceStatisticsChassisLevelOptimizationSavingsOptzsavingsOfflinevideoxcodingflvbytessaved ConfdString,
        affirmedServicesContentHttpProxyServiceStatisticsChassisLevelOptimizationSavingsOptzsavingsOfflinevideoxcodingmp4bytessaved ConfdString,
        affirmedServicesContentHttpProxyServiceStatisticsChassisLevelOptimizationSavingsOptzsavingsOfflinevideoxcodingwebmbytessaved ConfdString,
        affirmedServicesContentHttpProxyServiceStatisticsChassisLevelOptimizationSavingsOptzsavingsMinifytotalbytessaved ConfdString,
        affirmedServicesContentHttpProxyServiceStatisticsChassisLevelOptimizationSavingsOptzsavingsMinifycssbytessaved ConfdString,
        affirmedServicesContentHttpProxyServiceStatisticsChassisLevelOptimizationSavingsOptzsavingsMinifyhtmlbytessaved ConfdString,
        affirmedServicesContentHttpProxyServiceStatisticsChassisLevelOptimizationSavingsOptzsavingsMinifyjavascriptbytessaved ConfdString,
        affirmedServicesContentHttpProxyServiceStatisticsChassisLevelOptimizationSavingsOptzsavingsWebimageoptimizationtotalbytessaved ConfdString,
        affirmedServicesContentHttpProxyServiceStatisticsChassisLevelOptimizationSavingsOptzsavingsWebimageoptimizationgifbytessaved ConfdString,
        affirmedServicesContentHttpProxyServiceStatisticsChassisLevelOptimizationSavingsOptzsavingsWebimageoptimizationpngbytessaved ConfdString,
        affirmedServicesContentHttpProxyServiceStatisticsChassisLevelOptimizationSavingsOptzsavingsWebimageoptimizationjpegbytessaved ConfdString,
        affirmedServicesContentHttpProxyServiceStatisticsChassisLevelOptimizationSavingsOptzsavingsCompressionbytessaved ConfdString,
        affirmedServicesContentHttpProxyServiceStatisticsChassisLevelOptimizationSavingsOptzsavingsHls-bytes-saved ConfdString,
        affirmedServicesContentHttpProxyServiceStatisticsChassisLevelOptimizationSavingsOptzsavingsDash-bytes-saved ConfdString,
        affirmedServicesContentHttpProxyServiceStatisticsChassisLevelOptimizationSavingsOptzsavingsHds-bytes-saved ConfdString,
        affirmedServicesContentHttpProxyServiceStatisticsChassisLevelOptimizationSavingsOptzsavingsAbrratelimitingtotalbytessaved ConfdString,
        affirmedServicesContentHttpProxyServiceStatisticsChassisLevelOptimizationSavingsOptzsavingsTcprlbytessaved ConfdString,
        affirmedServicesContentHttpProxyServiceStatisticsChassisLevelOptimizationSavingsOptzsavingsQuicrlbytessaved ConfdString
    }

affirmedServicesContentHttpProxyServiceStatisticsChassisLevelOptimizationSavingsOptzsavingsChassis OBJECT-TYPE
    SYNTAX      Unsigned32
    MAX-ACCESS  not-accessible
    STATUS      current
    DESCRIPTION "chassis ID"
    ::= { affirmedServicesContentHttpProxyServiceStatisticsChassisLevelOptimizationSavingsOptzsavingsEntry 1 }

affirmedServicesContentHttpProxyServiceStatisticsChassisLevelOptimizationSavingsOptzsavingsVideopacingtotalbytessaved OBJECT-TYPE
    SYNTAX      ConfdString
    MAX-ACCESS  read-only
    STATUS      current
    DESCRIPTION "Total Number of Video Pacing Bytes Saved."
    ::= { affirmedServicesContentHttpProxyServiceStatisticsChassisLevelOptimizationSavingsOptzsavingsEntry 2 }

affirmedServicesContentHttpProxyServiceStatisticsChassisLevelOptimizationSavingsOptzsavingsVideopacingflvbytessaved OBJECT-TYPE
    SYNTAX      ConfdString
    MAX-ACCESS  read-only
    STATUS      current
    DESCRIPTION "Number of FLV Video Pacing Bytes Saved."
    ::= { affirmedServicesContentHttpProxyServiceStatisticsChassisLevelOptimizationSavingsOptzsavingsEntry 3 }

affirmedServicesContentHttpProxyServiceStatisticsChassisLevelOptimizationSavingsOptzsavingsVideopacingmp4bytessaved OBJECT-TYPE
    SYNTAX      ConfdString
    MAX-ACCESS  read-only
    STATUS      current
    DESCRIPTION "Number of MP4 Video Pacing Bytes Saved."
    ::= { affirmedServicesContentHttpProxyServiceStatisticsChassisLevelOptimizationSavingsOptzsavingsEntry 4 }

affirmedServicesContentHttpProxyServiceStatisticsChassisLevelOptimizationSavingsOptzsavingsVideopacingwebmbytessaved OBJECT-TYPE
    SYNTAX      ConfdString
    MAX-ACCESS  read-only
    STATUS      current
    DESCRIPTION "Number of WEBM Video Pacing Bytes Saved."
    ::= { affirmedServicesContentHttpProxyServiceStatisticsChassisLevelOptimizationSavingsOptzsavingsEntry 5 }

affirmedServicesContentHttpProxyServiceStatisticsChassisLevelOptimizationSavingsOptzsavingsOnlinevideoxcodingtotalbytessaved OBJECT-TYPE
    SYNTAX      ConfdString
    MAX-ACCESS  read-only
    STATUS      current
    DESCRIPTION "Total Number of Online Video Transcoding Bytes Saved."
    ::= { affirmedServicesContentHttpProxyServiceStatisticsChassisLevelOptimizationSavingsOptzsavingsEntry 6 }

affirmedServicesContentHttpProxyServiceStatisticsChassisLevelOptimizationSavingsOptzsavingsOnlinevideoxcodingflvbytessaved OBJECT-TYPE
    SYNTAX      ConfdString
    MAX-ACCESS  read-only
    STATUS      current
    DESCRIPTION "Number of Online FLV Video Transcoding Bytes Saved."
    ::= { affirmedServicesContentHttpProxyServiceStatisticsChassisLevelOptimizationSavingsOptzsavingsEntry 7 }

affirmedServicesContentHttpProxyServiceStatisticsChassisLevelOptimizationSavingsOptzsavingsOnlinevideoxcodingmp4bytessaved OBJECT-TYPE
    SYNTAX      ConfdString
    MAX-ACCESS  read-only
    STATUS      current
    DESCRIPTION "Number of Online MP4 Video Transcoding Bytes Saved."
    ::= { affirmedServicesContentHttpProxyServiceStatisticsChassisLevelOptimizationSavingsOptzsavingsEntry 8 }

affirmedServicesContentHttpProxyServiceStatisticsChassisLevelOptimizationSavingsOptzsavingsOnlinevideoxcodingwebmbytessaved OBJECT-TYPE
    SYNTAX      ConfdString
    MAX-ACCESS  read-only
    STATUS      current
    DESCRIPTION "Number of Online WEBM Video Transcoding Bytes Saved."
    ::= { affirmedServicesContentHttpProxyServiceStatisticsChassisLevelOptimizationSavingsOptzsavingsEntry 9 }

affirmedServicesContentHttpProxyServiceStatisticsChassisLevelOptimizationSavingsOptzsavingsOfflinevideoxcodingtotalbytessaved OBJECT-TYPE
    SYNTAX      ConfdString
    MAX-ACCESS  read-only
    STATUS      current
    DESCRIPTION "Total Number of Offline Video Transcoding Bytes Saved."
    ::= { affirmedServicesContentHttpProxyServiceStatisticsChassisLevelOptimizationSavingsOptzsavingsEntry 10 }

affirmedServicesContentHttpProxyServiceStatisticsChassisLevelOptimizationSavingsOptzsavingsOfflinevideoxcodingflvbytessaved OBJECT-TYPE
    SYNTAX      ConfdString
    MAX-ACCESS  read-only
    STATUS      current
    DESCRIPTION "Number of Offline FLV Video Transcoding Bytes Saved."
    ::= { affirmedServicesContentHttpProxyServiceStatisticsChassisLevelOptimizationSavingsOptzsavingsEntry 11 }

affirmedServicesContentHttpProxyServiceStatisticsChassisLevelOptimizationSavingsOptzsavingsOfflinevideoxcodingmp4bytessaved OBJECT-TYPE
    SYNTAX      ConfdString
    MAX-ACCESS  read-only
    STATUS      current
    DESCRIPTION "Number of Offline MP4 Video Transcoding Bytes Saved."
    ::= { affirmedServicesContentHttpProxyServiceStatisticsChassisLevelOptimizationSavingsOptzsavingsEntry 12 }

affirmedServicesContentHttpProxyServiceStatisticsChassisLevelOptimizationSavingsOptzsavingsOfflinevideoxcodingwebmbytessaved OBJECT-TYPE
    SYNTAX      ConfdString
    MAX-ACCESS  read-only
    STATUS      current
    DESCRIPTION "Number of Offline WEBM Video Transcoding Bytes Saved."
    ::= { affirmedServicesContentHttpProxyServiceStatisticsChassisLevelOptimizationSavingsOptzsavingsEntry 13 }

affirmedServicesContentHttpProxyServiceStatisticsChassisLevelOptimizationSavingsOptzsavingsMinifytotalbytessaved OBJECT-TYPE
    SYNTAX      ConfdString
    MAX-ACCESS  read-only
    STATUS      deprecated
    DESCRIPTION "Total Number of Minify Bytes Saved."
    ::= { affirmedServicesContentHttpProxyServiceStatisticsChassisLevelOptimizationSavingsOptzsavingsEntry 14 }

affirmedServicesContentHttpProxyServiceStatisticsChassisLevelOptimizationSavingsOptzsavingsMinifycssbytessaved OBJECT-TYPE
    SYNTAX      ConfdString
    MAX-ACCESS  read-only
    STATUS      deprecated
    DESCRIPTION "Number of Minify CSS Bytes Saved."
    ::= { affirmedServicesContentHttpProxyServiceStatisticsChassisLevelOptimizationSavingsOptzsavingsEntry 15 }

affirmedServicesContentHttpProxyServiceStatisticsChassisLevelOptimizationSavingsOptzsavingsMinifyhtmlbytessaved OBJECT-TYPE
    SYNTAX      ConfdString
    MAX-ACCESS  read-only
    STATUS      deprecated
    DESCRIPTION "Number of Minify HTML Bytes Saved."
    ::= { affirmedServicesContentHttpProxyServiceStatisticsChassisLevelOptimizationSavingsOptzsavingsEntry 16 }

affirmedServicesContentHttpProxyServiceStatisticsChassisLevelOptimizationSavingsOptzsavingsMinifyjavascriptbytessaved OBJECT-TYPE
    SYNTAX      ConfdString
    MAX-ACCESS  read-only
    STATUS      deprecated
    DESCRIPTION "Number of Minify Javascript Bytes Saved."
    ::= { affirmedServicesContentHttpProxyServiceStatisticsChassisLevelOptimizationSavingsOptzsavingsEntry 17 }

affirmedServicesContentHttpProxyServiceStatisticsChassisLevelOptimizationSavingsOptzsavingsWebimageoptimizationtotalbytessaved OBJECT-TYPE
    SYNTAX      ConfdString
    MAX-ACCESS  read-only
    STATUS      current
    DESCRIPTION "Total Number of Web Image Optimization Bytes Saved."
    ::= { affirmedServicesContentHttpProxyServiceStatisticsChassisLevelOptimizationSavingsOptzsavingsEntry 18 }

affirmedServicesContentHttpProxyServiceStatisticsChassisLevelOptimizationSavingsOptzsavingsWebimageoptimizationgifbytessaved OBJECT-TYPE
    SYNTAX      ConfdString
    MAX-ACCESS  read-only
    STATUS      current
    DESCRIPTION "Number of Web Image Optimization GIF Bytes Saved."
    ::= { affirmedServicesContentHttpProxyServiceStatisticsChassisLevelOptimizationSavingsOptzsavingsEntry 19 }

affirmedServicesContentHttpProxyServiceStatisticsChassisLevelOptimizationSavingsOptzsavingsWebimageoptimizationpngbytessaved OBJECT-TYPE
    SYNTAX      ConfdString
    MAX-ACCESS  read-only
    STATUS      current
    DESCRIPTION "Number of Web Image Optimization PNG Bytes Saved."
    ::= { affirmedServicesContentHttpProxyServiceStatisticsChassisLevelOptimizationSavingsOptzsavingsEntry 20 }

affirmedServicesContentHttpProxyServiceStatisticsChassisLevelOptimizationSavingsOptzsavingsWebimageoptimizationjpegbytessaved OBJECT-TYPE
    SYNTAX      ConfdString
    MAX-ACCESS  read-only
    STATUS      current
    DESCRIPTION "Number of Web Image Optimization JPEG Bytes Saved."
    ::= { affirmedServicesContentHttpProxyServiceStatisticsChassisLevelOptimizationSavingsOptzsavingsEntry 21 }

affirmedServicesContentHttpProxyServiceStatisticsChassisLevelOptimizationSavingsOptzsavingsCompressionbytessaved OBJECT-TYPE
    SYNTAX      ConfdString
    MAX-ACCESS  read-only
    STATUS      current
    DESCRIPTION "Number of Compression Bytes Saved."
    ::= { affirmedServicesContentHttpProxyServiceStatisticsChassisLevelOptimizationSavingsOptzsavingsEntry 22 }

affirmedServicesContentHttpProxyServiceStatisticsChassisLevelOptimizationSavingsOptzsavingsHls-bytes-saved OBJECT-TYPE
    SYNTAX      ConfdString
    MAX-ACCESS  read-only
    STATUS      current
    DESCRIPTION "Number of ABR Rate Limiting Bytes Saved for HLS"
    ::= { affirmedServicesContentHttpProxyServiceStatisticsChassisLevelOptimizationSavingsOptzsavingsEntry 23 }

affirmedServicesContentHttpProxyServiceStatisticsChassisLevelOptimizationSavingsOptzsavingsDash-bytes-saved OBJECT-TYPE
    SYNTAX      ConfdString
    MAX-ACCESS  read-only
    STATUS      current
    DESCRIPTION "Number of ABR Rate Limiting Bytes Saved for DASH"
    ::= { affirmedServicesContentHttpProxyServiceStatisticsChassisLevelOptimizationSavingsOptzsavingsEntry 24 }

affirmedServicesContentHttpProxyServiceStatisticsChassisLevelOptimizationSavingsOptzsavingsHds-bytes-saved OBJECT-TYPE
    SYNTAX      ConfdString
    MAX-ACCESS  read-only
    STATUS      current
    DESCRIPTION "Number of ABR Rate Limiting Bytes Saved for HDS"
    ::= { affirmedServicesContentHttpProxyServiceStatisticsChassisLevelOptimizationSavingsOptzsavingsEntry 25 }

affirmedServicesContentHttpProxyServiceStatisticsChassisLevelOptimizationSavingsOptzsavingsAbrratelimitingtotalbytessaved OBJECT-TYPE
    SYNTAX      ConfdString
    MAX-ACCESS  read-only
    STATUS      current
    DESCRIPTION "Total Number of ABR Rate Limiting Bytes Saved."
    ::= { affirmedServicesContentHttpProxyServiceStatisticsChassisLevelOptimizationSavingsOptzsavingsEntry 26 }

affirmedServicesContentHttpProxyServiceStatisticsChassisLevelOptimizationSavingsOptzsavingsTcprlbytessaved OBJECT-TYPE
    SYNTAX      ConfdString
    MAX-ACCESS  read-only
    STATUS      current
    DESCRIPTION "Number of bytes saved due to TCP Rate Limiting"
    ::= { affirmedServicesContentHttpProxyServiceStatisticsChassisLevelOptimizationSavingsOptzsavingsEntry 27 }

affirmedServicesContentHttpProxyServiceStatisticsChassisLevelOptimizationSavingsOptzsavingsQuicrlbytessaved OBJECT-TYPE
    SYNTAX      ConfdString
    MAX-ACCESS  read-only
    STATUS      current
    DESCRIPTION "Number of bytes saved due to QUIC Rate Limiting"
    ::= { affirmedServicesContentHttpProxyServiceStatisticsChassisLevelOptimizationSavingsOptzsavingsEntry 28 }

affirmedServicesContentHttpProxyServiceStatisticsChassisLevelContentInsertionScriptLinkTable OBJECT-TYPE
    SYNTAX      SEQUENCE OF AffirmedServicesContentHttpProxyServiceStatisticsChassisLevelContentInsertionScriptLinkEntry
    MAX-ACCESS  not-accessible
    STATUS      current
    DESCRIPTION ""
    ::= { affirmedServicesContentHttpProxyServiceStatisticsChassisLevelContentInsertion 1 }

affirmedServicesContentHttpProxyServiceStatisticsChassisLevelContentInsertionScriptLinkEntry OBJECT-TYPE
    SYNTAX      AffirmedServicesContentHttpProxyServiceStatisticsChassisLevelContentInsertionScriptLinkEntry
    MAX-ACCESS  not-accessible
    STATUS      current
    DESCRIPTION ""
    INDEX { affirmedServicesContentHttpProxyServiceStatisticsChassisLevelContentInsertionScriptLinkChassis }
        ::= { affirmedServicesContentHttpProxyServiceStatisticsChassisLevelContentInsertionScriptLinkTable 1 }

AffirmedServicesContentHttpProxyServiceStatisticsChassisLevelContentInsertionScriptLinkEntry ::=
    SEQUENCE {
        affirmedServicesContentHttpProxyServiceStatisticsChassisLevelContentInsertionScriptLinkChassis Unsigned32,
        affirmedServicesContentHttpProxyServiceStatisticsChassisLevelContentInsertionScriptLinkScriptlinkinsertionattempts ConfdString,
        affirmedServicesContentHttpProxyServiceStatisticsChassisLevelContentInsertionScriptLinkScriptlinkinsertionsuccesses ConfdString,
        affirmedServicesContentHttpProxyServiceStatisticsChassisLevelContentInsertionScriptLinkScriptlinkinsertioncancels ConfdString,
        affirmedServicesContentHttpProxyServiceStatisticsChassisLevelContentInsertionScriptLinkScriptlinkinsertionfailures ConfdString,
        affirmedServicesContentHttpProxyServiceStatisticsChassisLevelContentInsertionScriptLinkScriptlinkinsertionaborts ConfdString,
        affirmedServicesContentHttpProxyServiceStatisticsChassisLevelContentInsertionScriptLinkScriptlinkinsertioncancelnonokstatus ConfdString,
        affirmedServicesContentHttpProxyServiceStatisticsChassisLevelContentInsertionScriptLinkScriptlinkinsertioncancelpagetoobig ConfdString,
        affirmedServicesContentHttpProxyServiceStatisticsChassisLevelContentInsertionScriptLinkScriptlinkinsertionfailureunsupportedhtml ConfdString,
        affirmedServicesContentHttpProxyServiceStatisticsChassisLevelContentInsertionScriptLinkScriptlinkinsertionfailureinvalidhtml ConfdString
    }

affirmedServicesContentHttpProxyServiceStatisticsChassisLevelContentInsertionScriptLinkChassis OBJECT-TYPE
    SYNTAX      Unsigned32
    MAX-ACCESS  not-accessible
    STATUS      current
    DESCRIPTION "chassis ID"
    ::= { affirmedServicesContentHttpProxyServiceStatisticsChassisLevelContentInsertionScriptLinkEntry 1 }

affirmedServicesContentHttpProxyServiceStatisticsChassisLevelContentInsertionScriptLinkScriptlinkinsertionattempts OBJECT-TYPE
    SYNTAX      ConfdString
    MAX-ACCESS  read-only
    STATUS      current
    DESCRIPTION "Number of Script-Link Insertion Attempts"
    ::= { affirmedServicesContentHttpProxyServiceStatisticsChassisLevelContentInsertionScriptLinkEntry 2 }

affirmedServicesContentHttpProxyServiceStatisticsChassisLevelContentInsertionScriptLinkScriptlinkinsertionsuccesses OBJECT-TYPE
    SYNTAX      ConfdString
    MAX-ACCESS  read-only
    STATUS      current
    DESCRIPTION "Number of Script-Link Insertion Successes"
    ::= { affirmedServicesContentHttpProxyServiceStatisticsChassisLevelContentInsertionScriptLinkEntry 3 }

affirmedServicesContentHttpProxyServiceStatisticsChassisLevelContentInsertionScriptLinkScriptlinkinsertioncancels OBJECT-TYPE
    SYNTAX      ConfdString
    MAX-ACCESS  read-only
    STATUS      current
    DESCRIPTION "Number of Script-Link Insertion Cancels"
    ::= { affirmedServicesContentHttpProxyServiceStatisticsChassisLevelContentInsertionScriptLinkEntry 4 }

affirmedServicesContentHttpProxyServiceStatisticsChassisLevelContentInsertionScriptLinkScriptlinkinsertionfailures OBJECT-TYPE
    SYNTAX      ConfdString
    MAX-ACCESS  read-only
    STATUS      current
    DESCRIPTION "Number of Script-Link Insertion Failures"
    ::= { affirmedServicesContentHttpProxyServiceStatisticsChassisLevelContentInsertionScriptLinkEntry 5 }

affirmedServicesContentHttpProxyServiceStatisticsChassisLevelContentInsertionScriptLinkScriptlinkinsertionaborts OBJECT-TYPE
    SYNTAX      ConfdString
    MAX-ACCESS  read-only
    STATUS      current
    DESCRIPTION "Number of Script-Link Insertion Aborts"
    ::= { affirmedServicesContentHttpProxyServiceStatisticsChassisLevelContentInsertionScriptLinkEntry 6 }

affirmedServicesContentHttpProxyServiceStatisticsChassisLevelContentInsertionScriptLinkScriptlinkinsertioncancelnonokstatus OBJECT-TYPE
    SYNTAX      ConfdString
    MAX-ACCESS  read-only
    STATUS      current
    DESCRIPTION "Number of Script-Link Insertion Cancels Due to Non-OK Response Status"
    ::= { affirmedServicesContentHttpProxyServiceStatisticsChassisLevelContentInsertionScriptLinkEntry 7 }

affirmedServicesContentHttpProxyServiceStatisticsChassisLevelContentInsertionScriptLinkScriptlinkinsertioncancelpagetoobig OBJECT-TYPE
    SYNTAX      ConfdString
    MAX-ACCESS  read-only
    STATUS      current
    DESCRIPTION "Number of Script-Link Insertion Cancels Due to Respnose Page Too Big"
    ::= { affirmedServicesContentHttpProxyServiceStatisticsChassisLevelContentInsertionScriptLinkEntry 8 }

affirmedServicesContentHttpProxyServiceStatisticsChassisLevelContentInsertionScriptLinkScriptlinkinsertionfailureunsupportedhtml OBJECT-TYPE
    SYNTAX      ConfdString
    MAX-ACCESS  read-only
    STATUS      current
    DESCRIPTION "Number of Script-Link Insertion Failures Due to Unsupported HTML"
    ::= { affirmedServicesContentHttpProxyServiceStatisticsChassisLevelContentInsertionScriptLinkEntry 9 }

affirmedServicesContentHttpProxyServiceStatisticsChassisLevelContentInsertionScriptLinkScriptlinkinsertionfailureinvalidhtml OBJECT-TYPE
    SYNTAX      ConfdString
    MAX-ACCESS  read-only
    STATUS      current
    DESCRIPTION "Number of Script-Link Insertion Failures Due to Invalid HTML Format"
    ::= { affirmedServicesContentHttpProxyServiceStatisticsChassisLevelContentInsertionScriptLinkEntry 10 }

affirmedServicesContentHttpProxyServiceStatisticsChassisLevelTollFreeDataSummaryTable OBJECT-TYPE
    SYNTAX      SEQUENCE OF AffirmedServicesContentHttpProxyServiceStatisticsChassisLevelTollFreeDataSummaryEntry
    MAX-ACCESS  not-accessible
    STATUS      current
    DESCRIPTION ""
    ::= { affirmedServicesContentHttpProxyServiceStatisticsChassisLevelTollFreeData 1 }

affirmedServicesContentHttpProxyServiceStatisticsChassisLevelTollFreeDataSummaryEntry OBJECT-TYPE
    SYNTAX      AffirmedServicesContentHttpProxyServiceStatisticsChassisLevelTollFreeDataSummaryEntry
    MAX-ACCESS  not-accessible
    STATUS      current
    DESCRIPTION ""
    INDEX { affirmedServicesContentHttpProxyServiceStatisticsChassisLevelTollFreeDataSummaryChassis }
        ::= { affirmedServicesContentHttpProxyServiceStatisticsChassisLevelTollFreeDataSummaryTable 1 }

AffirmedServicesContentHttpProxyServiceStatisticsChassisLevelTollFreeDataSummaryEntry ::=
    SEQUENCE {
        affirmedServicesContentHttpProxyServiceStatisticsChassisLevelTollFreeDataSummaryChassis Unsigned32,
        affirmedServicesContentHttpProxyServiceStatisticsChassisLevelTollFreeDataSummaryNumtotaltfdattempts ConfdString,
        affirmedServicesContentHttpProxyServiceStatisticsChassisLevelTollFreeDataSummaryNumtotaltfdsuccesses ConfdString,
        affirmedServicesContentHttpProxyServiceStatisticsChassisLevelTollFreeDataSummaryNumtotaltfdrejects ConfdString,
        affirmedServicesContentHttpProxyServiceStatisticsChassisLevelTollFreeDataSummaryNumtotaltfdhttpattempts ConfdString,
        affirmedServicesContentHttpProxyServiceStatisticsChassisLevelTollFreeDataSummaryNumtotaltfdhttpsuccesses ConfdString,
        affirmedServicesContentHttpProxyServiceStatisticsChassisLevelTollFreeDataSummaryNumtotaltfdhttprejects ConfdString,
        affirmedServicesContentHttpProxyServiceStatisticsChassisLevelTollFreeDataSummaryNumtotaltfdhttpsattempts ConfdString,
        affirmedServicesContentHttpProxyServiceStatisticsChassisLevelTollFreeDataSummaryNumtotaltfdhttpssuccesses ConfdString,
        affirmedServicesContentHttpProxyServiceStatisticsChassisLevelTollFreeDataSummaryNumtotaltfdhttpsrejects ConfdString,
        affirmedServicesContentHttpProxyServiceStatisticsChassisLevelTollFreeDataSummaryNumtotaltfdconnectattempts ConfdString,
        affirmedServicesContentHttpProxyServiceStatisticsChassisLevelTollFreeDataSummaryNumtotaltfdconnectsuccesses ConfdString,
        affirmedServicesContentHttpProxyServiceStatisticsChassisLevelTollFreeDataSummaryNumtotaltfdconnectrejects ConfdString,
        affirmedServicesContentHttpProxyServiceStatisticsChassisLevelTollFreeDataSummaryNumtotaltfdwebsocketattempts ConfdString,
        affirmedServicesContentHttpProxyServiceStatisticsChassisLevelTollFreeDataSummaryNumtotaltfdwebsocketsuccesses ConfdString,
        affirmedServicesContentHttpProxyServiceStatisticsChassisLevelTollFreeDataSummaryNumtotaltfdwebsocketrejects ConfdString,
        affirmedServicesContentHttpProxyServiceStatisticsChassisLevelTollFreeDataSummaryNumtotaltfdhttpserrorcallbacks ConfdString,
        affirmedServicesContentHttpProxyServiceStatisticsChassisLevelTollFreeDataSummaryNumtotaltfdconnecterrorcallbacks ConfdString
    }

affirmedServicesContentHttpProxyServiceStatisticsChassisLevelTollFreeDataSummaryChassis OBJECT-TYPE
    SYNTAX      Unsigned32
    MAX-ACCESS  not-accessible
    STATUS      current
    DESCRIPTION "chassis ID"
    ::= { affirmedServicesContentHttpProxyServiceStatisticsChassisLevelTollFreeDataSummaryEntry 1 }

affirmedServicesContentHttpProxyServiceStatisticsChassisLevelTollFreeDataSummaryNumtotaltfdattempts OBJECT-TYPE
    SYNTAX      ConfdString
    MAX-ACCESS  read-only
    STATUS      current
    DESCRIPTION "Total number of Toll Free Data Attempts"
    ::= { affirmedServicesContentHttpProxyServiceStatisticsChassisLevelTollFreeDataSummaryEntry 2 }

affirmedServicesContentHttpProxyServiceStatisticsChassisLevelTollFreeDataSummaryNumtotaltfdsuccesses OBJECT-TYPE
    SYNTAX      ConfdString
    MAX-ACCESS  read-only
    STATUS      current
    DESCRIPTION "Total number of Toll Free Data Successes"
    ::= { affirmedServicesContentHttpProxyServiceStatisticsChassisLevelTollFreeDataSummaryEntry 3 }

affirmedServicesContentHttpProxyServiceStatisticsChassisLevelTollFreeDataSummaryNumtotaltfdrejects OBJECT-TYPE
    SYNTAX      ConfdString
    MAX-ACCESS  read-only
    STATUS      current
    DESCRIPTION "Total number of Toll Free Data Rejects"
    ::= { affirmedServicesContentHttpProxyServiceStatisticsChassisLevelTollFreeDataSummaryEntry 4 }

affirmedServicesContentHttpProxyServiceStatisticsChassisLevelTollFreeDataSummaryNumtotaltfdhttpattempts OBJECT-TYPE
    SYNTAX      ConfdString
    MAX-ACCESS  read-only
    STATUS      current
    DESCRIPTION "Total number of HTTP Toll Free Data Attempts"
    ::= { affirmedServicesContentHttpProxyServiceStatisticsChassisLevelTollFreeDataSummaryEntry 5 }

affirmedServicesContentHttpProxyServiceStatisticsChassisLevelTollFreeDataSummaryNumtotaltfdhttpsuccesses OBJECT-TYPE
    SYNTAX      ConfdString
    MAX-ACCESS  read-only
    STATUS      current
    DESCRIPTION "Total number of HTTP Toll Free Data Successes"
    ::= { affirmedServicesContentHttpProxyServiceStatisticsChassisLevelTollFreeDataSummaryEntry 6 }

affirmedServicesContentHttpProxyServiceStatisticsChassisLevelTollFreeDataSummaryNumtotaltfdhttprejects OBJECT-TYPE
    SYNTAX      ConfdString
    MAX-ACCESS  read-only
    STATUS      current
    DESCRIPTION "Total number of HTTP Toll Free Data Rejects"
    ::= { affirmedServicesContentHttpProxyServiceStatisticsChassisLevelTollFreeDataSummaryEntry 7 }

affirmedServicesContentHttpProxyServiceStatisticsChassisLevelTollFreeDataSummaryNumtotaltfdhttpsattempts OBJECT-TYPE
    SYNTAX      ConfdString
    MAX-ACCESS  read-only
    STATUS      current
    DESCRIPTION "Total number of HTTPS Toll Free Data Attempts"
    ::= { affirmedServicesContentHttpProxyServiceStatisticsChassisLevelTollFreeDataSummaryEntry 8 }

affirmedServicesContentHttpProxyServiceStatisticsChassisLevelTollFreeDataSummaryNumtotaltfdhttpssuccesses OBJECT-TYPE
    SYNTAX      ConfdString
    MAX-ACCESS  read-only
    STATUS      current
    DESCRIPTION "Total number of HTTPS Toll Free Data Successes"
    ::= { affirmedServicesContentHttpProxyServiceStatisticsChassisLevelTollFreeDataSummaryEntry 9 }

affirmedServicesContentHttpProxyServiceStatisticsChassisLevelTollFreeDataSummaryNumtotaltfdhttpsrejects OBJECT-TYPE
    SYNTAX      ConfdString
    MAX-ACCESS  read-only
    STATUS      current
    DESCRIPTION "Total number of HTTPS Toll Free Data Rejects"
    ::= { affirmedServicesContentHttpProxyServiceStatisticsChassisLevelTollFreeDataSummaryEntry 10 }

affirmedServicesContentHttpProxyServiceStatisticsChassisLevelTollFreeDataSummaryNumtotaltfdconnectattempts OBJECT-TYPE
    SYNTAX      ConfdString
    MAX-ACCESS  read-only
    STATUS      current
    DESCRIPTION "Total number of CONNECT Toll Free Data Attempts"
    ::= { affirmedServicesContentHttpProxyServiceStatisticsChassisLevelTollFreeDataSummaryEntry 11 }

affirmedServicesContentHttpProxyServiceStatisticsChassisLevelTollFreeDataSummaryNumtotaltfdconnectsuccesses OBJECT-TYPE
    SYNTAX      ConfdString
    MAX-ACCESS  read-only
    STATUS      current
    DESCRIPTION "Total number of CONNECT Toll Free Data Successes"
    ::= { affirmedServicesContentHttpProxyServiceStatisticsChassisLevelTollFreeDataSummaryEntry 12 }

affirmedServicesContentHttpProxyServiceStatisticsChassisLevelTollFreeDataSummaryNumtotaltfdconnectrejects OBJECT-TYPE
    SYNTAX      ConfdString
    MAX-ACCESS  read-only
    STATUS      current
    DESCRIPTION "Total number of CONNECT Toll Free Data Rejects"
    ::= { affirmedServicesContentHttpProxyServiceStatisticsChassisLevelTollFreeDataSummaryEntry 13 }

affirmedServicesContentHttpProxyServiceStatisticsChassisLevelTollFreeDataSummaryNumtotaltfdwebsocketattempts OBJECT-TYPE
    SYNTAX      ConfdString
    MAX-ACCESS  read-only
    STATUS      current
    DESCRIPTION "Total number of Web Socket Toll Free Data Attempts"
    ::= { affirmedServicesContentHttpProxyServiceStatisticsChassisLevelTollFreeDataSummaryEntry 14 }

affirmedServicesContentHttpProxyServiceStatisticsChassisLevelTollFreeDataSummaryNumtotaltfdwebsocketsuccesses OBJECT-TYPE
    SYNTAX      ConfdString
    MAX-ACCESS  read-only
    STATUS      current
    DESCRIPTION "Total number of Web Socket Toll Free Data Successes"
    ::= { affirmedServicesContentHttpProxyServiceStatisticsChassisLevelTollFreeDataSummaryEntry 15 }

affirmedServicesContentHttpProxyServiceStatisticsChassisLevelTollFreeDataSummaryNumtotaltfdwebsocketrejects OBJECT-TYPE
    SYNTAX      ConfdString
    MAX-ACCESS  read-only
    STATUS      current
    DESCRIPTION "Total number of Web Socket Toll Free Data Rejects"
    ::= { affirmedServicesContentHttpProxyServiceStatisticsChassisLevelTollFreeDataSummaryEntry 16 }

affirmedServicesContentHttpProxyServiceStatisticsChassisLevelTollFreeDataSummaryNumtotaltfdhttpserrorcallbacks OBJECT-TYPE
    SYNTAX      ConfdString
    MAX-ACCESS  read-only
    STATUS      current
    DESCRIPTION "Total number of HTTPS Toll Free Data Error Callbacks sent"
    ::= { affirmedServicesContentHttpProxyServiceStatisticsChassisLevelTollFreeDataSummaryEntry 17 }

affirmedServicesContentHttpProxyServiceStatisticsChassisLevelTollFreeDataSummaryNumtotaltfdconnecterrorcallbacks OBJECT-TYPE
    SYNTAX      ConfdString
    MAX-ACCESS  read-only
    STATUS      current
    DESCRIPTION "Total number of CONNECT Toll Free Data Error Callbacks sent"
    ::= { affirmedServicesContentHttpProxyServiceStatisticsChassisLevelTollFreeDataSummaryEntry 18 }

affirmedServicesContentHttpProxyServiceStatisticsChassisLevelTollFreeDataDetailTable OBJECT-TYPE
    SYNTAX      SEQUENCE OF AffirmedServicesContentHttpProxyServiceStatisticsChassisLevelTollFreeDataDetailEntry
    MAX-ACCESS  not-accessible
    STATUS      current
    DESCRIPTION ""
    ::= { affirmedServicesContentHttpProxyServiceStatisticsChassisLevelTollFreeData 2 }

affirmedServicesContentHttpProxyServiceStatisticsChassisLevelTollFreeDataDetailEntry OBJECT-TYPE
    SYNTAX      AffirmedServicesContentHttpProxyServiceStatisticsChassisLevelTollFreeDataDetailEntry
    MAX-ACCESS  not-accessible
    STATUS      current
    DESCRIPTION ""
    INDEX { affirmedServicesContentHttpProxyServiceStatisticsChassisLevelTollFreeDataDetailChassis }
        ::= { affirmedServicesContentHttpProxyServiceStatisticsChassisLevelTollFreeDataDetailTable 1 }

AffirmedServicesContentHttpProxyServiceStatisticsChassisLevelTollFreeDataDetailEntry ::=
    SEQUENCE {
        affirmedServicesContentHttpProxyServiceStatisticsChassisLevelTollFreeDataDetailChassis Unsigned32,
        affirmedServicesContentHttpProxyServiceStatisticsChassisLevelTollFreeDataDetailNumtotaltfdcertdownloads ConfdString,
        affirmedServicesContentHttpProxyServiceStatisticsChassisLevelTollFreeDataDetailNumtotaltfdcertdownloadsuccess ConfdString,
        affirmedServicesContentHttpProxyServiceStatisticsChassisLevelTollFreeDataDetailNumtotaltfdcertdownloaderrors ConfdString,
        affirmedServicesContentHttpProxyServiceStatisticsChassisLevelTollFreeDataDetailNumtotaltfdcertinvalid ConfdString,
        affirmedServicesContentHttpProxyServiceStatisticsChassisLevelTollFreeDataDetailNumtotaltfdcertrevoked ConfdString,
        affirmedServicesContentHttpProxyServiceStatisticsChassisLevelTollFreeDataDetailNumtotaltfdcertcrldownloads ConfdString,
        affirmedServicesContentHttpProxyServiceStatisticsChassisLevelTollFreeDataDetailNumtotalmanifestrecvd ConfdString,
        affirmedServicesContentHttpProxyServiceStatisticsChassisLevelTollFreeDataDetailNumtotalmanifestvalid ConfdString,
        affirmedServicesContentHttpProxyServiceStatisticsChassisLevelTollFreeDataDetailNumtotalmanifesterror ConfdString,
        affirmedServicesContentHttpProxyServiceStatisticsChassisLevelTollFreeDataDetailNumtotalmanifestbase64decodeerror ConfdString,
        affirmedServicesContentHttpProxyServiceStatisticsChassisLevelTollFreeDataDetailNumtotalmanifestcmsdecodeerror ConfdString,
        affirmedServicesContentHttpProxyServiceStatisticsChassisLevelTollFreeDataDetailNumtotalmanifestjsonparsingerror ConfdString,
        affirmedServicesContentHttpProxyServiceStatisticsChassisLevelTollFreeDataDetailNumtotalhttpbytesupstream ConfdString,
        affirmedServicesContentHttpProxyServiceStatisticsChassisLevelTollFreeDataDetailNumtotalhttpbytesdownstream ConfdString,
        affirmedServicesContentHttpProxyServiceStatisticsChassisLevelTollFreeDataDetailNumtotalhttpsbytesupstream ConfdString,
        affirmedServicesContentHttpProxyServiceStatisticsChassisLevelTollFreeDataDetailNumtotalhttpsbytesdownstream ConfdString,
        affirmedServicesContentHttpProxyServiceStatisticsChassisLevelTollFreeDataDetailNumtotalconnectbytesupstream ConfdString,
        affirmedServicesContentHttpProxyServiceStatisticsChassisLevelTollFreeDataDetailNumtotalconnectbytesdownstream ConfdString,
        affirmedServicesContentHttpProxyServiceStatisticsChassisLevelTollFreeDataDetailNumtotalwebsocketbytesupstream ConfdString,
        affirmedServicesContentHttpProxyServiceStatisticsChassisLevelTollFreeDataDetailNumtotalwebsocketbytesdownstream ConfdString,
        affirmedServicesContentHttpProxyServiceStatisticsChassisLevelTollFreeDataDetailNumtotalrejectintlroaming ConfdString,
        affirmedServicesContentHttpProxyServiceStatisticsChassisLevelTollFreeDataDetailNumtotalrejectoptout ConfdString,
        affirmedServicesContentHttpProxyServiceStatisticsChassisLevelTollFreeDataDetailNumtotalrejectineligible ConfdString,
        affirmedServicesContentHttpProxyServiceStatisticsChassisLevelTollFreeDataDetailNumtotalrejectcontentprovider ConfdString,
        affirmedServicesContentHttpProxyServiceStatisticsChassisLevelTollFreeDataDetailNumtotalrejectmissingsni ConfdString,
        affirmedServicesContentHttpProxyServiceStatisticsChassisLevelTollFreeDataDetailNumtotalrejectmanifestnomatch ConfdString,
        affirmedServicesContentHttpProxyServiceStatisticsChassisLevelTollFreeDataDetailNumtotalrejectinvalidprofile ConfdString,
        affirmedServicesContentHttpProxyServiceStatisticsChassisLevelTollFreeDataDetailNumtotalrejectinvalidrequest ConfdString,
        affirmedServicesContentHttpProxyServiceStatisticsChassisLevelTollFreeDataDetailNumtotalmanifestinvalidheaderformat ConfdString,
        affirmedServicesContentHttpProxyServiceStatisticsChassisLevelTollFreeDataDetailNumtotalmanifestcertificateerror ConfdString,
        affirmedServicesContentHttpProxyServiceStatisticsChassisLevelTollFreeDataDetailNumtotalmanifesturllisterror ConfdString,
        affirmedServicesContentHttpProxyServiceStatisticsChassisLevelTollFreeDataDetailNumtotalmanifestvalidationerror ConfdString,
        affirmedServicesContentHttpProxyServiceStatisticsChassisLevelTollFreeDataDetailNumtotalmanifestinternalerror ConfdString,
        affirmedServicesContentHttpProxyServiceStatisticsChassisLevelTollFreeDataDetailNumtotalrejectstatusunknown ConfdString,
        affirmedServicesContentHttpProxyServiceStatisticsChassisLevelTollFreeDataDetailNumtotaltfdcertcrldownloadsuccess ConfdString,
        affirmedServicesContentHttpProxyServiceStatisticsChassisLevelTollFreeDataDetailNumtotaltfdcertcrldownloaderror ConfdString
    }

affirmedServicesContentHttpProxyServiceStatisticsChassisLevelTollFreeDataDetailChassis OBJECT-TYPE
    SYNTAX      Unsigned32
    MAX-ACCESS  not-accessible
    STATUS      current
    DESCRIPTION "chassis ID"
    ::= { affirmedServicesContentHttpProxyServiceStatisticsChassisLevelTollFreeDataDetailEntry 1 }

affirmedServicesContentHttpProxyServiceStatisticsChassisLevelTollFreeDataDetailNumtotaltfdcertdownloads OBJECT-TYPE
    SYNTAX      ConfdString
    MAX-ACCESS  read-only
    STATUS      current
    DESCRIPTION "Total number of Toll Free Data Certificate Download Attempts"
    ::= { affirmedServicesContentHttpProxyServiceStatisticsChassisLevelTollFreeDataDetailEntry 2 }

affirmedServicesContentHttpProxyServiceStatisticsChassisLevelTollFreeDataDetailNumtotaltfdcertdownloadsuccess OBJECT-TYPE
    SYNTAX      ConfdString
    MAX-ACCESS  read-only
    STATUS      current
    DESCRIPTION "Total number of Toll Free Data Certificate Download Successes"
    ::= { affirmedServicesContentHttpProxyServiceStatisticsChassisLevelTollFreeDataDetailEntry 3 }

affirmedServicesContentHttpProxyServiceStatisticsChassisLevelTollFreeDataDetailNumtotaltfdcertdownloaderrors OBJECT-TYPE
    SYNTAX      ConfdString
    MAX-ACCESS  read-only
    STATUS      current
    DESCRIPTION "Total number of Toll Free Data Certificate Download Errors"
    ::= { affirmedServicesContentHttpProxyServiceStatisticsChassisLevelTollFreeDataDetailEntry 4 }

affirmedServicesContentHttpProxyServiceStatisticsChassisLevelTollFreeDataDetailNumtotaltfdcertinvalid OBJECT-TYPE
    SYNTAX      ConfdString
    MAX-ACCESS  read-only
    STATUS      current
    DESCRIPTION "Total number of Invalid Toll Free Data Certificate"
    ::= { affirmedServicesContentHttpProxyServiceStatisticsChassisLevelTollFreeDataDetailEntry 5 }

affirmedServicesContentHttpProxyServiceStatisticsChassisLevelTollFreeDataDetailNumtotaltfdcertrevoked OBJECT-TYPE
    SYNTAX      ConfdString
    MAX-ACCESS  read-only
    STATUS      current
    DESCRIPTION "Total number of Revoked Toll Free Data Certificate"
    ::= { affirmedServicesContentHttpProxyServiceStatisticsChassisLevelTollFreeDataDetailEntry 6 }

affirmedServicesContentHttpProxyServiceStatisticsChassisLevelTollFreeDataDetailNumtotaltfdcertcrldownloads OBJECT-TYPE
    SYNTAX      ConfdString
    MAX-ACCESS  read-only
    STATUS      current
    DESCRIPTION "Total number of Toll Free Data Certificate CRL Download Attempts"
    ::= { affirmedServicesContentHttpProxyServiceStatisticsChassisLevelTollFreeDataDetailEntry 7 }

affirmedServicesContentHttpProxyServiceStatisticsChassisLevelTollFreeDataDetailNumtotalmanifestrecvd OBJECT-TYPE
    SYNTAX      ConfdString
    MAX-ACCESS  read-only
    STATUS      current
    DESCRIPTION "Total number of Toll Free Data Manifests Received"
    ::= { affirmedServicesContentHttpProxyServiceStatisticsChassisLevelTollFreeDataDetailEntry 8 }

affirmedServicesContentHttpProxyServiceStatisticsChassisLevelTollFreeDataDetailNumtotalmanifestvalid OBJECT-TYPE
    SYNTAX      ConfdString
    MAX-ACCESS  read-only
    STATUS      current
    DESCRIPTION "Total number of Toll Free Data Manifests that are valid"
    ::= { affirmedServicesContentHttpProxyServiceStatisticsChassisLevelTollFreeDataDetailEntry 9 }

affirmedServicesContentHttpProxyServiceStatisticsChassisLevelTollFreeDataDetailNumtotalmanifesterror OBJECT-TYPE
    SYNTAX      ConfdString
    MAX-ACCESS  read-only
    STATUS      current
    DESCRIPTION "Total number of Toll Free Data Manifests that warranted error callbacks"
    ::= { affirmedServicesContentHttpProxyServiceStatisticsChassisLevelTollFreeDataDetailEntry 10 }

affirmedServicesContentHttpProxyServiceStatisticsChassisLevelTollFreeDataDetailNumtotalmanifestbase64decodeerror OBJECT-TYPE
    SYNTAX      ConfdString
    MAX-ACCESS  read-only
    STATUS      current
    DESCRIPTION "Total number of Toll Free Data Manifests that have base64 decode errors"
    ::= { affirmedServicesContentHttpProxyServiceStatisticsChassisLevelTollFreeDataDetailEntry 11 }

affirmedServicesContentHttpProxyServiceStatisticsChassisLevelTollFreeDataDetailNumtotalmanifestcmsdecodeerror OBJECT-TYPE
    SYNTAX      ConfdString
    MAX-ACCESS  read-only
    STATUS      current
    DESCRIPTION "Total number of Toll Free Data Manifests that have CMS decode failures"
    ::= { affirmedServicesContentHttpProxyServiceStatisticsChassisLevelTollFreeDataDetailEntry 12 }

affirmedServicesContentHttpProxyServiceStatisticsChassisLevelTollFreeDataDetailNumtotalmanifestjsonparsingerror OBJECT-TYPE
    SYNTAX      ConfdString
    MAX-ACCESS  read-only
    STATUS      current
    DESCRIPTION "Total number of Toll Free Data Manifests that have JSON parsing errors"
    ::= { affirmedServicesContentHttpProxyServiceStatisticsChassisLevelTollFreeDataDetailEntry 13 }

affirmedServicesContentHttpProxyServiceStatisticsChassisLevelTollFreeDataDetailNumtotalhttpbytesupstream OBJECT-TYPE
    SYNTAX      ConfdString
    MAX-ACCESS  read-only
    STATUS      current
    DESCRIPTION "Total number of Toll Free Data HTTP Bytes Allowed Upstream"
    ::= { affirmedServicesContentHttpProxyServiceStatisticsChassisLevelTollFreeDataDetailEntry 14 }

affirmedServicesContentHttpProxyServiceStatisticsChassisLevelTollFreeDataDetailNumtotalhttpbytesdownstream OBJECT-TYPE
    SYNTAX      ConfdString
    MAX-ACCESS  read-only
    STATUS      current
    DESCRIPTION "Total number of Toll Free Data HTTP Bytes Allowed Downstream"
    ::= { affirmedServicesContentHttpProxyServiceStatisticsChassisLevelTollFreeDataDetailEntry 15 }

affirmedServicesContentHttpProxyServiceStatisticsChassisLevelTollFreeDataDetailNumtotalhttpsbytesupstream OBJECT-TYPE
    SYNTAX      ConfdString
    MAX-ACCESS  read-only
    STATUS      current
    DESCRIPTION "Total number of Toll Free Data HTTPS Bytes Allowed Upstream"
    ::= { affirmedServicesContentHttpProxyServiceStatisticsChassisLevelTollFreeDataDetailEntry 16 }

affirmedServicesContentHttpProxyServiceStatisticsChassisLevelTollFreeDataDetailNumtotalhttpsbytesdownstream OBJECT-TYPE
    SYNTAX      ConfdString
    MAX-ACCESS  read-only
    STATUS      current
    DESCRIPTION "Total number of Toll Free Data HTTPS Bytes Allowed Downstream"
    ::= { affirmedServicesContentHttpProxyServiceStatisticsChassisLevelTollFreeDataDetailEntry 17 }

affirmedServicesContentHttpProxyServiceStatisticsChassisLevelTollFreeDataDetailNumtotalconnectbytesupstream OBJECT-TYPE
    SYNTAX      ConfdString
    MAX-ACCESS  read-only
    STATUS      current
    DESCRIPTION "Total number of Toll Free Data CONNECT Bytes Allowed Upstream"
    ::= { affirmedServicesContentHttpProxyServiceStatisticsChassisLevelTollFreeDataDetailEntry 18 }

affirmedServicesContentHttpProxyServiceStatisticsChassisLevelTollFreeDataDetailNumtotalconnectbytesdownstream OBJECT-TYPE
    SYNTAX      ConfdString
    MAX-ACCESS  read-only
    STATUS      current
    DESCRIPTION "Total number of Toll Free Data CONNECT Bytes Allowed Downstream"
    ::= { affirmedServicesContentHttpProxyServiceStatisticsChassisLevelTollFreeDataDetailEntry 19 }

affirmedServicesContentHttpProxyServiceStatisticsChassisLevelTollFreeDataDetailNumtotalwebsocketbytesupstream OBJECT-TYPE
    SYNTAX      ConfdString
    MAX-ACCESS  read-only
    STATUS      current
    DESCRIPTION "Total number of Toll Free Data Web Socket Bytes Allowed Upstream"
    ::= { affirmedServicesContentHttpProxyServiceStatisticsChassisLevelTollFreeDataDetailEntry 20 }

affirmedServicesContentHttpProxyServiceStatisticsChassisLevelTollFreeDataDetailNumtotalwebsocketbytesdownstream OBJECT-TYPE
    SYNTAX      ConfdString
    MAX-ACCESS  read-only
    STATUS      current
    DESCRIPTION "Total number of Toll Free Data Web Socket Bytes Allowed Downstream"
    ::= { affirmedServicesContentHttpProxyServiceStatisticsChassisLevelTollFreeDataDetailEntry 21 }

affirmedServicesContentHttpProxyServiceStatisticsChassisLevelTollFreeDataDetailNumtotalrejectintlroaming OBJECT-TYPE
    SYNTAX      ConfdString
    MAX-ACCESS  read-only
    STATUS      current
    DESCRIPTION "Total number of Toll Free Data rejects due to the subscriber being International Roaming"
    ::= { affirmedServicesContentHttpProxyServiceStatisticsChassisLevelTollFreeDataDetailEntry 22 }

affirmedServicesContentHttpProxyServiceStatisticsChassisLevelTollFreeDataDetailNumtotalrejectoptout OBJECT-TYPE
    SYNTAX      ConfdString
    MAX-ACCESS  read-only
    STATUS      current
    DESCRIPTION "Total number of Toll Free Data rejects due to subscriber opting out"
    ::= { affirmedServicesContentHttpProxyServiceStatisticsChassisLevelTollFreeDataDetailEntry 23 }

affirmedServicesContentHttpProxyServiceStatisticsChassisLevelTollFreeDataDetailNumtotalrejectineligible OBJECT-TYPE
    SYNTAX      ConfdString
    MAX-ACCESS  read-only
    STATUS      current
    DESCRIPTION "Total number of Toll Free Data rejects due to the subscriber being Ineligible for the plan"
    ::= { affirmedServicesContentHttpProxyServiceStatisticsChassisLevelTollFreeDataDetailEntry 24 }

affirmedServicesContentHttpProxyServiceStatisticsChassisLevelTollFreeDataDetailNumtotalrejectcontentprovider OBJECT-TYPE
    SYNTAX      ConfdString
    MAX-ACCESS  read-only
    STATUS      current
    DESCRIPTION "Total number of Toll Free Data rejected by the Content Provider"
    ::= { affirmedServicesContentHttpProxyServiceStatisticsChassisLevelTollFreeDataDetailEntry 25 }

affirmedServicesContentHttpProxyServiceStatisticsChassisLevelTollFreeDataDetailNumtotalrejectmissingsni OBJECT-TYPE
    SYNTAX      ConfdString
    MAX-ACCESS  read-only
    STATUS      current
    DESCRIPTION "Total number of Toll Free Data rejected because of missing Server Name Indication"
    ::= { affirmedServicesContentHttpProxyServiceStatisticsChassisLevelTollFreeDataDetailEntry 26 }

affirmedServicesContentHttpProxyServiceStatisticsChassisLevelTollFreeDataDetailNumtotalrejectmanifestnomatch OBJECT-TYPE
    SYNTAX      ConfdString
    MAX-ACCESS  read-only
    STATUS      current
    DESCRIPTION "Total number of Toll Free Data rejected because the manifest URL did not match"
    ::= { affirmedServicesContentHttpProxyServiceStatisticsChassisLevelTollFreeDataDetailEntry 27 }

affirmedServicesContentHttpProxyServiceStatisticsChassisLevelTollFreeDataDetailNumtotalrejectinvalidprofile OBJECT-TYPE
    SYNTAX      ConfdString
    MAX-ACCESS  read-only
    STATUS      current
    DESCRIPTION "Total number of Toll Free Data rejected because of invalid toll-free-profile configuration"
    ::= { affirmedServicesContentHttpProxyServiceStatisticsChassisLevelTollFreeDataDetailEntry 28 }

affirmedServicesContentHttpProxyServiceStatisticsChassisLevelTollFreeDataDetailNumtotalrejectinvalidrequest OBJECT-TYPE
    SYNTAX      ConfdString
    MAX-ACCESS  read-only
    STATUS      current
    DESCRIPTION "Total number of Toll Free Data rejected because the request was not a HTTPS/TLS request"
    ::= { affirmedServicesContentHttpProxyServiceStatisticsChassisLevelTollFreeDataDetailEntry 29 }

affirmedServicesContentHttpProxyServiceStatisticsChassisLevelTollFreeDataDetailNumtotalmanifestinvalidheaderformat OBJECT-TYPE
    SYNTAX      ConfdString
    MAX-ACCESS  read-only
    STATUS      current
    DESCRIPTION "Total number of Toll Free Data Manifests with invalid header format"
    ::= { affirmedServicesContentHttpProxyServiceStatisticsChassisLevelTollFreeDataDetailEntry 30 }

affirmedServicesContentHttpProxyServiceStatisticsChassisLevelTollFreeDataDetailNumtotalmanifestcertificateerror OBJECT-TYPE
    SYNTAX      ConfdString
    MAX-ACCESS  read-only
    STATUS      current
    DESCRIPTION "Total number of Toll Free Data Manifests with certificate error during signature verification"
    ::= { affirmedServicesContentHttpProxyServiceStatisticsChassisLevelTollFreeDataDetailEntry 31 }

affirmedServicesContentHttpProxyServiceStatisticsChassisLevelTollFreeDataDetailNumtotalmanifesturllisterror OBJECT-TYPE
    SYNTAX      ConfdString
    MAX-ACCESS  read-only
    STATUS      current
    DESCRIPTION "Total number of Toll Free Data Manifests with URL list errors"
    ::= { affirmedServicesContentHttpProxyServiceStatisticsChassisLevelTollFreeDataDetailEntry 32 }

affirmedServicesContentHttpProxyServiceStatisticsChassisLevelTollFreeDataDetailNumtotalmanifestvalidationerror OBJECT-TYPE
    SYNTAX      ConfdString
    MAX-ACCESS  read-only
    STATUS      current
    DESCRIPTION "Total number of Toll Free Data Manifests with validation errors"
    ::= { affirmedServicesContentHttpProxyServiceStatisticsChassisLevelTollFreeDataDetailEntry 33 }

affirmedServicesContentHttpProxyServiceStatisticsChassisLevelTollFreeDataDetailNumtotalmanifestinternalerror OBJECT-TYPE
    SYNTAX      ConfdString
    MAX-ACCESS  read-only
    STATUS      current
    DESCRIPTION "Total number of Toll Free Data Manifests with internal handling errors"
    ::= { affirmedServicesContentHttpProxyServiceStatisticsChassisLevelTollFreeDataDetailEntry 34 }

affirmedServicesContentHttpProxyServiceStatisticsChassisLevelTollFreeDataDetailNumtotalrejectstatusunknown OBJECT-TYPE
    SYNTAX      ConfdString
    MAX-ACCESS  read-only
    STATUS      current
    DESCRIPTION "Total number of Toll Free Data rejected because the PCRF state is unknown"
    ::= { affirmedServicesContentHttpProxyServiceStatisticsChassisLevelTollFreeDataDetailEntry 35 }

affirmedServicesContentHttpProxyServiceStatisticsChassisLevelTollFreeDataDetailNumtotaltfdcertcrldownloadsuccess OBJECT-TYPE
    SYNTAX      ConfdString
    MAX-ACCESS  read-only
    STATUS      current
    DESCRIPTION "Total number of Toll Free Data Certificate CRL Download Successes"
    ::= { affirmedServicesContentHttpProxyServiceStatisticsChassisLevelTollFreeDataDetailEntry 36 }

affirmedServicesContentHttpProxyServiceStatisticsChassisLevelTollFreeDataDetailNumtotaltfdcertcrldownloaderror OBJECT-TYPE
    SYNTAX      ConfdString
    MAX-ACCESS  read-only
    STATUS      current
    DESCRIPTION "Total number of Toll Free Data Certificate CRL Download Errors"
    ::= { affirmedServicesContentHttpProxyServiceStatisticsChassisLevelTollFreeDataDetailEntry 37 }

affirmedServicesContentHttpProxyServiceStatisticsChassisLevelAbrRateLimitingSessionTable OBJECT-TYPE
    SYNTAX      SEQUENCE OF AffirmedServicesContentHttpProxyServiceStatisticsChassisLevelAbrRateLimitingSessionEntry
    MAX-ACCESS  not-accessible
    STATUS      current
    DESCRIPTION ""
    ::= { affirmedServicesContentHttpProxyServiceStatisticsChassisLevelAbrRateLimiting 1 }

affirmedServicesContentHttpProxyServiceStatisticsChassisLevelAbrRateLimitingSessionEntry OBJECT-TYPE
    SYNTAX      AffirmedServicesContentHttpProxyServiceStatisticsChassisLevelAbrRateLimitingSessionEntry
    MAX-ACCESS  not-accessible
    STATUS      current
    DESCRIPTION ""
    INDEX { affirmedServicesContentHttpProxyServiceStatisticsChassisLevelAbrRateLimitingSessionChassis }
        ::= { affirmedServicesContentHttpProxyServiceStatisticsChassisLevelAbrRateLimitingSessionTable 1 }

AffirmedServicesContentHttpProxyServiceStatisticsChassisLevelAbrRateLimitingSessionEntry ::=
    SEQUENCE {
        affirmedServicesContentHttpProxyServiceStatisticsChassisLevelAbrRateLimitingSessionChassis Unsigned32,
        affirmedServicesContentHttpProxyServiceStatisticsChassisLevelAbrRateLimitingSessionSession-total ConfdString,
        affirmedServicesContentHttpProxyServiceStatisticsChassisLevelAbrRateLimitingSessionSession-total-hls ConfdString,
        affirmedServicesContentHttpProxyServiceStatisticsChassisLevelAbrRateLimitingSessionSession-total-dash ConfdString,
        affirmedServicesContentHttpProxyServiceStatisticsChassisLevelAbrRateLimitingSessionSession-total-hds ConfdString,
        affirmedServicesContentHttpProxyServiceStatisticsChassisLevelAbrRateLimitingSessionSession-total-other ConfdString,
        affirmedServicesContentHttpProxyServiceStatisticsChassisLevelAbrRateLimitingSessionDuration-min ConfdString,
        affirmedServicesContentHttpProxyServiceStatisticsChassisLevelAbrRateLimitingSessionDuration-avg ConfdString,
        affirmedServicesContentHttpProxyServiceStatisticsChassisLevelAbrRateLimitingSessionDuration-max ConfdString,
        affirmedServicesContentHttpProxyServiceStatisticsChassisLevelAbrRateLimitingSessionSession-bytes-total ConfdString,
        affirmedServicesContentHttpProxyServiceStatisticsChassisLevelAbrRateLimitingSessionSession-bytes-hls ConfdString,
        affirmedServicesContentHttpProxyServiceStatisticsChassisLevelAbrRateLimitingSessionSession-bytes-dash ConfdString,
        affirmedServicesContentHttpProxyServiceStatisticsChassisLevelAbrRateLimitingSessionSession-bytes-hds ConfdString,
        affirmedServicesContentHttpProxyServiceStatisticsChassisLevelAbrRateLimitingSessionSession-bytes-other ConfdString,
        affirmedServicesContentHttpProxyServiceStatisticsChassisLevelAbrRateLimitingSessionSession-bitrate-0-500 ConfdString,
        affirmedServicesContentHttpProxyServiceStatisticsChassisLevelAbrRateLimitingSessionSession-bitrate-500-1000 ConfdString,
        affirmedServicesContentHttpProxyServiceStatisticsChassisLevelAbrRateLimitingSessionSession-bitrate-1000-2500 ConfdString,
        affirmedServicesContentHttpProxyServiceStatisticsChassisLevelAbrRateLimitingSessionSession-bitrate-2500-more ConfdString,
        affirmedServicesContentHttpProxyServiceStatisticsChassisLevelAbrRateLimitingSessionSession-current ConfdString,
        affirmedServicesContentHttpProxyServiceStatisticsChassisLevelAbrRateLimitingSessionSession-bypass-savings-estimation ConfdString
    }

affirmedServicesContentHttpProxyServiceStatisticsChassisLevelAbrRateLimitingSessionChassis OBJECT-TYPE
    SYNTAX      Unsigned32
    MAX-ACCESS  not-accessible
    STATUS      current
    DESCRIPTION "chassis ID"
    ::= { affirmedServicesContentHttpProxyServiceStatisticsChassisLevelAbrRateLimitingSessionEntry 1 }

affirmedServicesContentHttpProxyServiceStatisticsChassisLevelAbrRateLimitingSessionSession-total OBJECT-TYPE
    SYNTAX      ConfdString
    MAX-ACCESS  read-only
    STATUS      current
    DESCRIPTION "Number of Total ABR Session"
    ::= { affirmedServicesContentHttpProxyServiceStatisticsChassisLevelAbrRateLimitingSessionEntry 2 }

affirmedServicesContentHttpProxyServiceStatisticsChassisLevelAbrRateLimitingSessionSession-total-hls OBJECT-TYPE
    SYNTAX      ConfdString
    MAX-ACCESS  read-only
    STATUS      current
    DESCRIPTION "Number of Total HLS ABR Sessions"
    ::= { affirmedServicesContentHttpProxyServiceStatisticsChassisLevelAbrRateLimitingSessionEntry 3 }

affirmedServicesContentHttpProxyServiceStatisticsChassisLevelAbrRateLimitingSessionSession-total-dash OBJECT-TYPE
    SYNTAX      ConfdString
    MAX-ACCESS  read-only
    STATUS      current
    DESCRIPTION "Number of Total DASH ABR Sessions"
    ::= { affirmedServicesContentHttpProxyServiceStatisticsChassisLevelAbrRateLimitingSessionEntry 4 }

affirmedServicesContentHttpProxyServiceStatisticsChassisLevelAbrRateLimitingSessionSession-total-hds OBJECT-TYPE
    SYNTAX      ConfdString
    MAX-ACCESS  read-only
    STATUS      current
    DESCRIPTION "Number of Total HDS ABR Sessions"
    ::= { affirmedServicesContentHttpProxyServiceStatisticsChassisLevelAbrRateLimitingSessionEntry 5 }

affirmedServicesContentHttpProxyServiceStatisticsChassisLevelAbrRateLimitingSessionSession-total-other OBJECT-TYPE
    SYNTAX      ConfdString
    MAX-ACCESS  read-only
    STATUS      current
    DESCRIPTION "Number of Total Other ABR Sessions"
    ::= { affirmedServicesContentHttpProxyServiceStatisticsChassisLevelAbrRateLimitingSessionEntry 6 }

affirmedServicesContentHttpProxyServiceStatisticsChassisLevelAbrRateLimitingSessionDuration-min OBJECT-TYPE
    SYNTAX      ConfdString
    MAX-ACCESS  read-only
    STATUS      current
    DESCRIPTION "Minimum ABR video duration in seconds"
    ::= { affirmedServicesContentHttpProxyServiceStatisticsChassisLevelAbrRateLimitingSessionEntry 7 }

affirmedServicesContentHttpProxyServiceStatisticsChassisLevelAbrRateLimitingSessionDuration-avg OBJECT-TYPE
    SYNTAX      ConfdString
    MAX-ACCESS  read-only
    STATUS      current
    DESCRIPTION "Average ABR video duration in seconds"
    ::= { affirmedServicesContentHttpProxyServiceStatisticsChassisLevelAbrRateLimitingSessionEntry 8 }

affirmedServicesContentHttpProxyServiceStatisticsChassisLevelAbrRateLimitingSessionDuration-max OBJECT-TYPE
    SYNTAX      ConfdString
    MAX-ACCESS  read-only
    STATUS      current
    DESCRIPTION "Maximum ABR video duration in seconds"
    ::= { affirmedServicesContentHttpProxyServiceStatisticsChassisLevelAbrRateLimitingSessionEntry 9 }

affirmedServicesContentHttpProxyServiceStatisticsChassisLevelAbrRateLimitingSessionSession-bytes-total OBJECT-TYPE
    SYNTAX      ConfdString
    MAX-ACCESS  read-only
    STATUS      current
    DESCRIPTION "Total Bytes of ABR Sessions"
    ::= { affirmedServicesContentHttpProxyServiceStatisticsChassisLevelAbrRateLimitingSessionEntry 10 }

affirmedServicesContentHttpProxyServiceStatisticsChassisLevelAbrRateLimitingSessionSession-bytes-hls OBJECT-TYPE
    SYNTAX      ConfdString
    MAX-ACCESS  read-only
    STATUS      current
    DESCRIPTION "Total Bytes of HLS ABR Sessions"
    ::= { affirmedServicesContentHttpProxyServiceStatisticsChassisLevelAbrRateLimitingSessionEntry 11 }

affirmedServicesContentHttpProxyServiceStatisticsChassisLevelAbrRateLimitingSessionSession-bytes-dash OBJECT-TYPE
    SYNTAX      ConfdString
    MAX-ACCESS  read-only
    STATUS      current
    DESCRIPTION "Total Bytes of DASH ABR Sessions"
    ::= { affirmedServicesContentHttpProxyServiceStatisticsChassisLevelAbrRateLimitingSessionEntry 12 }

affirmedServicesContentHttpProxyServiceStatisticsChassisLevelAbrRateLimitingSessionSession-bytes-hds OBJECT-TYPE
    SYNTAX      ConfdString
    MAX-ACCESS  read-only
    STATUS      current
    DESCRIPTION "Total Bytes of HDS ABR Sessions"
    ::= { affirmedServicesContentHttpProxyServiceStatisticsChassisLevelAbrRateLimitingSessionEntry 13 }

affirmedServicesContentHttpProxyServiceStatisticsChassisLevelAbrRateLimitingSessionSession-bytes-other OBJECT-TYPE
    SYNTAX      ConfdString
    MAX-ACCESS  read-only
    STATUS      current
    DESCRIPTION "Total Bytes of Other Sessions"
    ::= { affirmedServicesContentHttpProxyServiceStatisticsChassisLevelAbrRateLimitingSessionEntry 14 }

affirmedServicesContentHttpProxyServiceStatisticsChassisLevelAbrRateLimitingSessionSession-bitrate-0-500 OBJECT-TYPE
    SYNTAX      ConfdString
    MAX-ACCESS  read-only
    STATUS      current
    DESCRIPTION "Total ABR video bitrate from 0 to 500 kbps"
    ::= { affirmedServicesContentHttpProxyServiceStatisticsChassisLevelAbrRateLimitingSessionEntry 15 }

affirmedServicesContentHttpProxyServiceStatisticsChassisLevelAbrRateLimitingSessionSession-bitrate-500-1000 OBJECT-TYPE
    SYNTAX      ConfdString
    MAX-ACCESS  read-only
    STATUS      current
    DESCRIPTION "Total ABR video bitrate from 500 to 1,000 kbps"
    ::= { affirmedServicesContentHttpProxyServiceStatisticsChassisLevelAbrRateLimitingSessionEntry 16 }

affirmedServicesContentHttpProxyServiceStatisticsChassisLevelAbrRateLimitingSessionSession-bitrate-1000-2500 OBJECT-TYPE
    SYNTAX      ConfdString
    MAX-ACCESS  read-only
    STATUS      current
    DESCRIPTION "Total ABR video bitrate from 1,000 to 2,500 kbps"
    ::= { affirmedServicesContentHttpProxyServiceStatisticsChassisLevelAbrRateLimitingSessionEntry 17 }

affirmedServicesContentHttpProxyServiceStatisticsChassisLevelAbrRateLimitingSessionSession-bitrate-2500-more OBJECT-TYPE
    SYNTAX      ConfdString
    MAX-ACCESS  read-only
    STATUS      current
    DESCRIPTION "Total ABR video bitrate greater than 2,500 kbps"
    ::= { affirmedServicesContentHttpProxyServiceStatisticsChassisLevelAbrRateLimitingSessionEntry 18 }

affirmedServicesContentHttpProxyServiceStatisticsChassisLevelAbrRateLimitingSessionSession-current OBJECT-TYPE
    SYNTAX      ConfdString
    MAX-ACCESS  read-only
    STATUS      current
    DESCRIPTION "Total ABR Session currently rate limited"
    ::= { affirmedServicesContentHttpProxyServiceStatisticsChassisLevelAbrRateLimitingSessionEntry 19 }

affirmedServicesContentHttpProxyServiceStatisticsChassisLevelAbrRateLimitingSessionSession-bypass-savings-estimation OBJECT-TYPE
    SYNTAX      ConfdString
    MAX-ACCESS  read-only
    STATUS      current
    DESCRIPTION "Total ABR video segment bypass because of savings estimation process"
    ::= { affirmedServicesContentHttpProxyServiceStatisticsChassisLevelAbrRateLimitingSessionEntry 20 }

affirmedServicesContentHttpProxyServiceStatisticsChassisLevelAbrRateLimitingSegmentTable OBJECT-TYPE
    SYNTAX      SEQUENCE OF AffirmedServicesContentHttpProxyServiceStatisticsChassisLevelAbrRateLimitingSegmentEntry
    MAX-ACCESS  not-accessible
    STATUS      current
    DESCRIPTION ""
    ::= { affirmedServicesContentHttpProxyServiceStatisticsChassisLevelAbrRateLimiting 2 }

affirmedServicesContentHttpProxyServiceStatisticsChassisLevelAbrRateLimitingSegmentEntry OBJECT-TYPE
    SYNTAX      AffirmedServicesContentHttpProxyServiceStatisticsChassisLevelAbrRateLimitingSegmentEntry
    MAX-ACCESS  not-accessible
    STATUS      current
    DESCRIPTION ""
    INDEX { affirmedServicesContentHttpProxyServiceStatisticsChassisLevelAbrRateLimitingSegmentChassis }
        ::= { affirmedServicesContentHttpProxyServiceStatisticsChassisLevelAbrRateLimitingSegmentTable 1 }

AffirmedServicesContentHttpProxyServiceStatisticsChassisLevelAbrRateLimitingSegmentEntry ::=
    SEQUENCE {
        affirmedServicesContentHttpProxyServiceStatisticsChassisLevelAbrRateLimitingSegmentChassis Unsigned32,
        affirmedServicesContentHttpProxyServiceStatisticsChassisLevelAbrRateLimitingSegmentSegment-total ConfdString,
        affirmedServicesContentHttpProxyServiceStatisticsChassisLevelAbrRateLimitingSegmentSegment-total-hls ConfdString,
        affirmedServicesContentHttpProxyServiceStatisticsChassisLevelAbrRateLimitingSegmentSegment-total-dash ConfdString,
        affirmedServicesContentHttpProxyServiceStatisticsChassisLevelAbrRateLimitingSegmentSegment-total-hds ConfdString,
        affirmedServicesContentHttpProxyServiceStatisticsChassisLevelAbrRateLimitingSegmentSegment-total-other ConfdString,
        affirmedServicesContentHttpProxyServiceStatisticsChassisLevelAbrRateLimitingSegmentSegment-bitrate-0-500 ConfdString,
        affirmedServicesContentHttpProxyServiceStatisticsChassisLevelAbrRateLimitingSegmentSegment-bitrate-500-1000 ConfdString,
        affirmedServicesContentHttpProxyServiceStatisticsChassisLevelAbrRateLimitingSegmentSegment-bitrate-1000-2500 ConfdString,
        affirmedServicesContentHttpProxyServiceStatisticsChassisLevelAbrRateLimitingSegmentSegment-bitrate-2500-more ConfdString,
        affirmedServicesContentHttpProxyServiceStatisticsChassisLevelAbrRateLimitingSegmentSegment-bitrate-enforced ConfdString,
        affirmedServicesContentHttpProxyServiceStatisticsChassisLevelAbrRateLimitingSegmentSubscriber-opt-out ConfdString,
        affirmedServicesContentHttpProxyServiceStatisticsChassisLevelAbrRateLimitingSegmentNo-matching-policy ConfdString,
        affirmedServicesContentHttpProxyServiceStatisticsChassisLevelAbrRateLimitingSegmentSegment-current ConfdString,
        affirmedServicesContentHttpProxyServiceStatisticsChassisLevelAbrRateLimitingSegmentSubscriber-opt-in-rate-limiting-req-not-met ConfdString,
        affirmedServicesContentHttpProxyServiceStatisticsChassisLevelAbrRateLimitingSegmentNo-maxrate-cp-manifest ConfdString,
        affirmedServicesContentHttpProxyServiceStatisticsChassisLevelAbrRateLimitingSegmentCp-manifest-with-maxrate ConfdString,
        affirmedServicesContentHttpProxyServiceStatisticsChassisLevelAbrRateLimitingSegmentInvalid-maxrate-cp-manifest ConfdString,
        affirmedServicesContentHttpProxyServiceStatisticsChassisLevelAbrRateLimitingSegmentSegment-bypass-savings-estimation ConfdString,
        affirmedServicesContentHttpProxyServiceStatisticsChassisLevelAbrRateLimitingSegmentSegment-bypass-short-response ConfdString,
        affirmedServicesContentHttpProxyServiceStatisticsChassisLevelAbrRateLimitingSegmentAggregation-bypass ConfdString
    }

affirmedServicesContentHttpProxyServiceStatisticsChassisLevelAbrRateLimitingSegmentChassis OBJECT-TYPE
    SYNTAX      Unsigned32
    MAX-ACCESS  not-accessible
    STATUS      current
    DESCRIPTION "chassis ID"
    ::= { affirmedServicesContentHttpProxyServiceStatisticsChassisLevelAbrRateLimitingSegmentEntry 1 }

affirmedServicesContentHttpProxyServiceStatisticsChassisLevelAbrRateLimitingSegmentSegment-total OBJECT-TYPE
    SYNTAX      ConfdString
    MAX-ACCESS  read-only
    STATUS      current
    DESCRIPTION "Number of Total ABR Segment"
    ::= { affirmedServicesContentHttpProxyServiceStatisticsChassisLevelAbrRateLimitingSegmentEntry 2 }

affirmedServicesContentHttpProxyServiceStatisticsChassisLevelAbrRateLimitingSegmentSegment-total-hls OBJECT-TYPE
    SYNTAX      ConfdString
    MAX-ACCESS  read-only
    STATUS      current
    DESCRIPTION "Number of Total HLS ABR Segment"
    ::= { affirmedServicesContentHttpProxyServiceStatisticsChassisLevelAbrRateLimitingSegmentEntry 3 }

affirmedServicesContentHttpProxyServiceStatisticsChassisLevelAbrRateLimitingSegmentSegment-total-dash OBJECT-TYPE
    SYNTAX      ConfdString
    MAX-ACCESS  read-only
    STATUS      current
    DESCRIPTION "Number of Total DASH ABR Segment"
    ::= { affirmedServicesContentHttpProxyServiceStatisticsChassisLevelAbrRateLimitingSegmentEntry 4 }

affirmedServicesContentHttpProxyServiceStatisticsChassisLevelAbrRateLimitingSegmentSegment-total-hds OBJECT-TYPE
    SYNTAX      ConfdString
    MAX-ACCESS  read-only
    STATUS      current
    DESCRIPTION "Number of Total HDS ABR Segment"
    ::= { affirmedServicesContentHttpProxyServiceStatisticsChassisLevelAbrRateLimitingSegmentEntry 5 }

affirmedServicesContentHttpProxyServiceStatisticsChassisLevelAbrRateLimitingSegmentSegment-total-other OBJECT-TYPE
    SYNTAX      ConfdString
    MAX-ACCESS  read-only
    STATUS      current
    DESCRIPTION "Number of Total Other ABR Segment"
    ::= { affirmedServicesContentHttpProxyServiceStatisticsChassisLevelAbrRateLimitingSegmentEntry 6 }

affirmedServicesContentHttpProxyServiceStatisticsChassisLevelAbrRateLimitingSegmentSegment-bitrate-0-500 OBJECT-TYPE
    SYNTAX      ConfdString
    MAX-ACCESS  read-only
    STATUS      current
    DESCRIPTION "Total ABR video bitrate from 0 to 1,000 kbps"
    ::= { affirmedServicesContentHttpProxyServiceStatisticsChassisLevelAbrRateLimitingSegmentEntry 7 }

affirmedServicesContentHttpProxyServiceStatisticsChassisLevelAbrRateLimitingSegmentSegment-bitrate-500-1000 OBJECT-TYPE
    SYNTAX      ConfdString
    MAX-ACCESS  read-only
    STATUS      current
    DESCRIPTION "Total ABR Segment bitrate from 500 to 1,000 kbps"
    ::= { affirmedServicesContentHttpProxyServiceStatisticsChassisLevelAbrRateLimitingSegmentEntry 8 }

affirmedServicesContentHttpProxyServiceStatisticsChassisLevelAbrRateLimitingSegmentSegment-bitrate-1000-2500 OBJECT-TYPE
    SYNTAX      ConfdString
    MAX-ACCESS  read-only
    STATUS      current
    DESCRIPTION "Total ABR Segment bitrate from 1,000 to 2,500 kbps"
    ::= { affirmedServicesContentHttpProxyServiceStatisticsChassisLevelAbrRateLimitingSegmentEntry 9 }

affirmedServicesContentHttpProxyServiceStatisticsChassisLevelAbrRateLimitingSegmentSegment-bitrate-2500-more OBJECT-TYPE
    SYNTAX      ConfdString
    MAX-ACCESS  read-only
    STATUS      current
    DESCRIPTION "Total ABR Segment bitrate greater than 2,500 kbps"
    ::= { affirmedServicesContentHttpProxyServiceStatisticsChassisLevelAbrRateLimitingSegmentEntry 10 }

affirmedServicesContentHttpProxyServiceStatisticsChassisLevelAbrRateLimitingSegmentSegment-bitrate-enforced OBJECT-TYPE
    SYNTAX      ConfdString
    MAX-ACCESS  read-only
    STATUS      current
    DESCRIPTION "Total ABR Segment that bitrate is enforced lower than media bitrate"
    ::= { affirmedServicesContentHttpProxyServiceStatisticsChassisLevelAbrRateLimitingSegmentEntry 11 }

affirmedServicesContentHttpProxyServiceStatisticsChassisLevelAbrRateLimitingSegmentSubscriber-opt-out OBJECT-TYPE
    SYNTAX      ConfdString
    MAX-ACCESS  read-only
    STATUS      current
    DESCRIPTION "Total ABR Segment bypass because of subsscriber opt out"
    ::= { affirmedServicesContentHttpProxyServiceStatisticsChassisLevelAbrRateLimitingSegmentEntry 12 }

affirmedServicesContentHttpProxyServiceStatisticsChassisLevelAbrRateLimitingSegmentNo-matching-policy OBJECT-TYPE
    SYNTAX      ConfdString
    MAX-ACCESS  read-only
    STATUS      current
    DESCRIPTION "Total ABR Segment bypass because applied response policy without ABR optimization"
    ::= { affirmedServicesContentHttpProxyServiceStatisticsChassisLevelAbrRateLimitingSegmentEntry 13 }

affirmedServicesContentHttpProxyServiceStatisticsChassisLevelAbrRateLimitingSegmentSegment-current OBJECT-TYPE
    SYNTAX      ConfdString
    MAX-ACCESS  read-only
    STATUS      current
    DESCRIPTION "Total ABR Segment currently rate limited"
    ::= { affirmedServicesContentHttpProxyServiceStatisticsChassisLevelAbrRateLimitingSegmentEntry 14 }

affirmedServicesContentHttpProxyServiceStatisticsChassisLevelAbrRateLimitingSegmentSubscriber-opt-in-rate-limiting-req-not-met OBJECT-TYPE
    SYNTAX      ConfdString
    MAX-ACCESS  read-only
    STATUS      current
    DESCRIPTION "Total ABR Segment bypass because of subscriber opt in requirements do not meet"
    ::= { affirmedServicesContentHttpProxyServiceStatisticsChassisLevelAbrRateLimitingSegmentEntry 15 }

affirmedServicesContentHttpProxyServiceStatisticsChassisLevelAbrRateLimitingSegmentNo-maxrate-cp-manifest OBJECT-TYPE
    SYNTAX      ConfdString
    MAX-ACCESS  read-only
    STATUS      current
    DESCRIPTION "Total ABR video segment bypass because no Max-Rate in the CP Manifest"
    ::= { affirmedServicesContentHttpProxyServiceStatisticsChassisLevelAbrRateLimitingSegmentEntry 16 }

affirmedServicesContentHttpProxyServiceStatisticsChassisLevelAbrRateLimitingSegmentCp-manifest-with-maxrate OBJECT-TYPE
    SYNTAX      ConfdString
    MAX-ACCESS  read-only
    STATUS      current
    DESCRIPTION "Total ABR video segment when Max-Rate in the CP Manifest"
    ::= { affirmedServicesContentHttpProxyServiceStatisticsChassisLevelAbrRateLimitingSegmentEntry 17 }

affirmedServicesContentHttpProxyServiceStatisticsChassisLevelAbrRateLimitingSegmentInvalid-maxrate-cp-manifest OBJECT-TYPE
    SYNTAX      ConfdString
    MAX-ACCESS  read-only
    STATUS      current
    DESCRIPTION "Total ABR video segment bypass because of invalid Max-Rate in the CP Manifest"
    ::= { affirmedServicesContentHttpProxyServiceStatisticsChassisLevelAbrRateLimitingSegmentEntry 18 }

affirmedServicesContentHttpProxyServiceStatisticsChassisLevelAbrRateLimitingSegmentSegment-bypass-savings-estimation OBJECT-TYPE
    SYNTAX      ConfdString
    MAX-ACCESS  read-only
    STATUS      current
    DESCRIPTION "Total ABR video segment bypass because of savings estimation process"
    ::= { affirmedServicesContentHttpProxyServiceStatisticsChassisLevelAbrRateLimitingSegmentEntry 19 }

affirmedServicesContentHttpProxyServiceStatisticsChassisLevelAbrRateLimitingSegmentSegment-bypass-short-response OBJECT-TYPE
    SYNTAX      ConfdString
    MAX-ACCESS  read-only
    STATUS      current
    DESCRIPTION "Total ABR video segment bypass because of short response"
    ::= { affirmedServicesContentHttpProxyServiceStatisticsChassisLevelAbrRateLimitingSegmentEntry 20 }

affirmedServicesContentHttpProxyServiceStatisticsChassisLevelAbrRateLimitingSegmentAggregation-bypass OBJECT-TYPE
    SYNTAX      ConfdString
    MAX-ACCESS  read-only
    STATUS      current
    DESCRIPTION "Total ABR video segment with aggregation bypass"
    ::= { affirmedServicesContentHttpProxyServiceStatisticsChassisLevelAbrRateLimitingSegmentEntry 21 }

affirmedServicesContentHttpProxyServiceStatisticsChassisLevelTcpSplicingRateLimitingTable OBJECT-TYPE
    SYNTAX      SEQUENCE OF AffirmedServicesContentHttpProxyServiceStatisticsChassisLevelTcpSplicingRateLimitingEntry
    MAX-ACCESS  not-accessible
    STATUS      current
    DESCRIPTION ""
    ::= { affirmedServicesContentHttpProxyServiceStatisticsChassisLevelTcpSplicing 1 }

affirmedServicesContentHttpProxyServiceStatisticsChassisLevelTcpSplicingRateLimitingEntry OBJECT-TYPE
    SYNTAX      AffirmedServicesContentHttpProxyServiceStatisticsChassisLevelTcpSplicingRateLimitingEntry
    MAX-ACCESS  not-accessible
    STATUS      current
    DESCRIPTION ""
    INDEX { affirmedServicesContentHttpProxyServiceStatisticsChassisLevelTcpSplicingRateLimitingChassis }
        ::= { affirmedServicesContentHttpProxyServiceStatisticsChassisLevelTcpSplicingRateLimitingTable 1 }

AffirmedServicesContentHttpProxyServiceStatisticsChassisLevelTcpSplicingRateLimitingEntry ::=
    SEQUENCE {
        affirmedServicesContentHttpProxyServiceStatisticsChassisLevelTcpSplicingRateLimitingChassis Unsigned32,
        affirmedServicesContentHttpProxyServiceStatisticsChassisLevelTcpSplicingRateLimitingNumratelimitingsummaryattempts ConfdString,
        affirmedServicesContentHttpProxyServiceStatisticsChassisLevelTcpSplicingRateLimitingNumratelimitingsummarysuccesses ConfdString,
        affirmedServicesContentHttpProxyServiceStatisticsChassisLevelTcpSplicingRateLimitingNumratelimitingsummarycancels ConfdString,
        affirmedServicesContentHttpProxyServiceStatisticsChassisLevelTcpSplicingRateLimitingNumratelimitingbytes ConfdString,
        affirmedServicesContentHttpProxyServiceStatisticsChassisLevelTcpSplicingRateLimitingNumratelimitingconnectionscurrent ConfdString,
        affirmedServicesContentHttpProxyServiceStatisticsChassisLevelTcpSplicingRateLimitingNumratelimitingcancelsrsptooshort ConfdString,
        affirmedServicesContentHttpProxyServiceStatisticsChassisLevelTcpSplicingRateLimitingNumratelimitingoptedoutbysubscriber ConfdString,
        affirmedServicesContentHttpProxyServiceStatisticsChassisLevelTcpSplicingRateLimitingNumratelimitingdisabled ConfdString,
        affirmedServicesContentHttpProxyServiceStatisticsChassisLevelTcpSplicingRateLimitingNumratelimitingoptedinreqnotmet ConfdString,
        affirmedServicesContentHttpProxyServiceStatisticsChassisLevelTcpSplicingRateLimitingNumratelimitingnomaxrateincpmanifest ConfdString,
        affirmedServicesContentHttpProxyServiceStatisticsChassisLevelTcpSplicingRateLimitingNumratelimitingsummarycpmanifestwithmaxrate ConfdString,
        affirmedServicesContentHttpProxyServiceStatisticsChassisLevelTcpSplicingRateLimitingNumratelimitinginvalidmaxrateincpmanifest ConfdString,
        affirmedServicesContentHttpProxyServiceStatisticsChassisLevelTcpSplicingRateLimitingNumratelimitingsessions250500 ConfdString,
        affirmedServicesContentHttpProxyServiceStatisticsChassisLevelTcpSplicingRateLimitingNumratelimitingsessions5001500 ConfdString,
        affirmedServicesContentHttpProxyServiceStatisticsChassisLevelTcpSplicingRateLimitingNumratelimitingsessions15003000 ConfdString,
        affirmedServicesContentHttpProxyServiceStatisticsChassisLevelTcpSplicingRateLimitingNumratelimitingsessions30006000 ConfdString,
        affirmedServicesContentHttpProxyServiceStatisticsChassisLevelTcpSplicingRateLimitingNumratelimitingsessions6000more ConfdString,
        affirmedServicesContentHttpProxyServiceStatisticsChassisLevelTcpSplicingRateLimitingNumratelimitedbytesld ConfdString,
        affirmedServicesContentHttpProxyServiceStatisticsChassisLevelTcpSplicingRateLimitingNumratelimitedbytessd ConfdString,
        affirmedServicesContentHttpProxyServiceStatisticsChassisLevelTcpSplicingRateLimitingNumratelimitedbyteshd ConfdString,
        affirmedServicesContentHttpProxyServiceStatisticsChassisLevelTcpSplicingRateLimitingNumratelimitedbytesfullhd ConfdString,
        affirmedServicesContentHttpProxyServiceStatisticsChassisLevelTcpSplicingRateLimitingNumratelimitedbytesuhd ConfdString,
        affirmedServicesContentHttpProxyServiceStatisticsChassisLevelTcpSplicingRateLimitingNumratelimitingbypasssavingsestimation ConfdString,
        affirmedServicesContentHttpProxyServiceStatisticsChassisLevelTcpSplicingRateLimitingNumratelimitingsessioncounttotal ConfdString,
        affirmedServicesContentHttpProxyServiceStatisticsChassisLevelTcpSplicingRateLimitingNumratelimitingsessionaverageflowcount ConfdString,
        affirmedServicesContentHttpProxyServiceStatisticsChassisLevelTcpSplicingRateLimitingNumratelimitingsessionaverageduration ConfdString,
        affirmedServicesContentHttpProxyServiceStatisticsChassisLevelTcpSplicingRateLimitingNumratelimitingbypassoverload ConfdString,
        affirmedServicesContentHttpProxyServiceStatisticsChassisLevelTcpSplicingRateLimitingNumratelimitingsessionaggregationbypass ConfdString
    }

affirmedServicesContentHttpProxyServiceStatisticsChassisLevelTcpSplicingRateLimitingChassis OBJECT-TYPE
    SYNTAX      Unsigned32
    MAX-ACCESS  not-accessible
    STATUS      current
    DESCRIPTION "chassis ID"
    ::= { affirmedServicesContentHttpProxyServiceStatisticsChassisLevelTcpSplicingRateLimitingEntry 1 }

affirmedServicesContentHttpProxyServiceStatisticsChassisLevelTcpSplicingRateLimitingNumratelimitingsummaryattempts OBJECT-TYPE
    SYNTAX      ConfdString
    MAX-ACCESS  read-only
    STATUS      current
    DESCRIPTION "Total number of Rate Limiting Summary Attempts"
    ::= { affirmedServicesContentHttpProxyServiceStatisticsChassisLevelTcpSplicingRateLimitingEntry 2 }

affirmedServicesContentHttpProxyServiceStatisticsChassisLevelTcpSplicingRateLimitingNumratelimitingsummarysuccesses OBJECT-TYPE
    SYNTAX      ConfdString
    MAX-ACCESS  read-only
    STATUS      current
    DESCRIPTION "Total number of Rate Limiting Summary Successes"
    ::= { affirmedServicesContentHttpProxyServiceStatisticsChassisLevelTcpSplicingRateLimitingEntry 3 }

affirmedServicesContentHttpProxyServiceStatisticsChassisLevelTcpSplicingRateLimitingNumratelimitingsummarycancels OBJECT-TYPE
    SYNTAX      ConfdString
    MAX-ACCESS  read-only
    STATUS      current
    DESCRIPTION "Total number of Rate Limiting Summary Cancels"
    ::= { affirmedServicesContentHttpProxyServiceStatisticsChassisLevelTcpSplicingRateLimitingEntry 4 }

affirmedServicesContentHttpProxyServiceStatisticsChassisLevelTcpSplicingRateLimitingNumratelimitingbytes OBJECT-TYPE
    SYNTAX      ConfdString
    MAX-ACCESS  read-only
    STATUS      current
    DESCRIPTION "Total number of Rate Limiting Bytes"
    ::= { affirmedServicesContentHttpProxyServiceStatisticsChassisLevelTcpSplicingRateLimitingEntry 5 }

affirmedServicesContentHttpProxyServiceStatisticsChassisLevelTcpSplicingRateLimitingNumratelimitingconnectionscurrent OBJECT-TYPE
    SYNTAX      ConfdString
    MAX-ACCESS  read-only
    STATUS      current
    DESCRIPTION "Total number of Rate Limiting Connections Current"
    ::= { affirmedServicesContentHttpProxyServiceStatisticsChassisLevelTcpSplicingRateLimitingEntry 6 }

affirmedServicesContentHttpProxyServiceStatisticsChassisLevelTcpSplicingRateLimitingNumratelimitingcancelsrsptooshort OBJECT-TYPE
    SYNTAX      ConfdString
    MAX-ACCESS  read-only
    STATUS      current
    DESCRIPTION "Total number of Rate Limiting Response Too Short"
    ::= { affirmedServicesContentHttpProxyServiceStatisticsChassisLevelTcpSplicingRateLimitingEntry 7 }

affirmedServicesContentHttpProxyServiceStatisticsChassisLevelTcpSplicingRateLimitingNumratelimitingoptedoutbysubscriber OBJECT-TYPE
    SYNTAX      ConfdString
    MAX-ACCESS  read-only
    STATUS      current
    DESCRIPTION "Total number of Rate Limiting Opted Out by Subscriber"
    ::= { affirmedServicesContentHttpProxyServiceStatisticsChassisLevelTcpSplicingRateLimitingEntry 8 }

affirmedServicesContentHttpProxyServiceStatisticsChassisLevelTcpSplicingRateLimitingNumratelimitingdisabled OBJECT-TYPE
    SYNTAX      ConfdString
    MAX-ACCESS  read-only
    STATUS      current
    DESCRIPTION "Total number of Rate Limiting Disabled"
    ::= { affirmedServicesContentHttpProxyServiceStatisticsChassisLevelTcpSplicingRateLimitingEntry 9 }

affirmedServicesContentHttpProxyServiceStatisticsChassisLevelTcpSplicingRateLimitingNumratelimitingoptedinreqnotmet OBJECT-TYPE
    SYNTAX      ConfdString
    MAX-ACCESS  read-only
    STATUS      current
    DESCRIPTION "Total number of Rate Limiting Opted by Subscriber but Requirements not met"
    ::= { affirmedServicesContentHttpProxyServiceStatisticsChassisLevelTcpSplicingRateLimitingEntry 10 }

affirmedServicesContentHttpProxyServiceStatisticsChassisLevelTcpSplicingRateLimitingNumratelimitingnomaxrateincpmanifest OBJECT-TYPE
    SYNTAX      ConfdString
    MAX-ACCESS  read-only
    STATUS      current
    DESCRIPTION "Total number of Rate Limiting No Max-Rate in the CP Manifest"
    ::= { affirmedServicesContentHttpProxyServiceStatisticsChassisLevelTcpSplicingRateLimitingEntry 11 }

affirmedServicesContentHttpProxyServiceStatisticsChassisLevelTcpSplicingRateLimitingNumratelimitingsummarycpmanifestwithmaxrate OBJECT-TYPE
    SYNTAX      ConfdString
    MAX-ACCESS  read-only
    STATUS      current
    DESCRIPTION "Total number of Rate Limiting Summary- CP Manifest with Max-Rate"
    ::= { affirmedServicesContentHttpProxyServiceStatisticsChassisLevelTcpSplicingRateLimitingEntry 12 }

affirmedServicesContentHttpProxyServiceStatisticsChassisLevelTcpSplicingRateLimitingNumratelimitinginvalidmaxrateincpmanifest OBJECT-TYPE
    SYNTAX      ConfdString
    MAX-ACCESS  read-only
    STATUS      current
    DESCRIPTION "Total number of Rate Limiting Invalid Max-Rate in the CP Manifest"
    ::= { affirmedServicesContentHttpProxyServiceStatisticsChassisLevelTcpSplicingRateLimitingEntry 13 }

affirmedServicesContentHttpProxyServiceStatisticsChassisLevelTcpSplicingRateLimitingNumratelimitingsessions250500 OBJECT-TYPE
    SYNTAX      ConfdString
    MAX-ACCESS  read-only
    STATUS      current
    DESCRIPTION "Total number of Rate Limiting Sessions from 250 to 500kbps (LD)"
    ::= { affirmedServicesContentHttpProxyServiceStatisticsChassisLevelTcpSplicingRateLimitingEntry 14 }

affirmedServicesContentHttpProxyServiceStatisticsChassisLevelTcpSplicingRateLimitingNumratelimitingsessions5001500 OBJECT-TYPE
    SYNTAX      ConfdString
    MAX-ACCESS  read-only
    STATUS      current
    DESCRIPTION "Total number of Rate Limiting Sessions from 500 to 1500kbps (SD)"
    ::= { affirmedServicesContentHttpProxyServiceStatisticsChassisLevelTcpSplicingRateLimitingEntry 15 }

affirmedServicesContentHttpProxyServiceStatisticsChassisLevelTcpSplicingRateLimitingNumratelimitingsessions15003000 OBJECT-TYPE
    SYNTAX      ConfdString
    MAX-ACCESS  read-only
    STATUS      current
    DESCRIPTION "Total number of Rate Limiting Sessions from 1500 to 3000kbps (HD)"
    ::= { affirmedServicesContentHttpProxyServiceStatisticsChassisLevelTcpSplicingRateLimitingEntry 16 }

affirmedServicesContentHttpProxyServiceStatisticsChassisLevelTcpSplicingRateLimitingNumratelimitingsessions30006000 OBJECT-TYPE
    SYNTAX      ConfdString
    MAX-ACCESS  read-only
    STATUS      current
    DESCRIPTION "Total number of Rate Limiting Sessions from 3000 to 6000kbps (Full HD)"
    ::= { affirmedServicesContentHttpProxyServiceStatisticsChassisLevelTcpSplicingRateLimitingEntry 17 }

affirmedServicesContentHttpProxyServiceStatisticsChassisLevelTcpSplicingRateLimitingNumratelimitingsessions6000more OBJECT-TYPE
    SYNTAX      ConfdString
    MAX-ACCESS  read-only
    STATUS      current
    DESCRIPTION "Total number of Rate Limiting Sessions greater than 6000kbps (UHD)"
    ::= { affirmedServicesContentHttpProxyServiceStatisticsChassisLevelTcpSplicingRateLimitingEntry 18 }

affirmedServicesContentHttpProxyServiceStatisticsChassisLevelTcpSplicingRateLimitingNumratelimitedbytesld OBJECT-TYPE
    SYNTAX      ConfdString
    MAX-ACCESS  read-only
    STATUS      current
    DESCRIPTION "Total number of Rate Limited Bytes - LD"
    ::= { affirmedServicesContentHttpProxyServiceStatisticsChassisLevelTcpSplicingRateLimitingEntry 19 }

affirmedServicesContentHttpProxyServiceStatisticsChassisLevelTcpSplicingRateLimitingNumratelimitedbytessd OBJECT-TYPE
    SYNTAX      ConfdString
    MAX-ACCESS  read-only
    STATUS      current
    DESCRIPTION "Total number of Rate Limited Bytes - SD"
    ::= { affirmedServicesContentHttpProxyServiceStatisticsChassisLevelTcpSplicingRateLimitingEntry 20 }

affirmedServicesContentHttpProxyServiceStatisticsChassisLevelTcpSplicingRateLimitingNumratelimitedbyteshd OBJECT-TYPE
    SYNTAX      ConfdString
    MAX-ACCESS  read-only
    STATUS      current
    DESCRIPTION "Total number of Rate Limited Bytes - HD"
    ::= { affirmedServicesContentHttpProxyServiceStatisticsChassisLevelTcpSplicingRateLimitingEntry 21 }

affirmedServicesContentHttpProxyServiceStatisticsChassisLevelTcpSplicingRateLimitingNumratelimitedbytesfullhd OBJECT-TYPE
    SYNTAX      ConfdString
    MAX-ACCESS  read-only
    STATUS      current
    DESCRIPTION "Total number of Rate Limited Bytes - Full HD"
    ::= { affirmedServicesContentHttpProxyServiceStatisticsChassisLevelTcpSplicingRateLimitingEntry 22 }

affirmedServicesContentHttpProxyServiceStatisticsChassisLevelTcpSplicingRateLimitingNumratelimitedbytesuhd OBJECT-TYPE
    SYNTAX      ConfdString
    MAX-ACCESS  read-only
    STATUS      current
    DESCRIPTION "Total number of Rate Limited Bytes - UHD"
    ::= { affirmedServicesContentHttpProxyServiceStatisticsChassisLevelTcpSplicingRateLimitingEntry 23 }

affirmedServicesContentHttpProxyServiceStatisticsChassisLevelTcpSplicingRateLimitingNumratelimitingbypasssavingsestimation OBJECT-TYPE
    SYNTAX      ConfdString
    MAX-ACCESS  read-only
    STATUS      current
    DESCRIPTION "Total number of Rate Limiting Bypass due to Savings Estimation"
    ::= { affirmedServicesContentHttpProxyServiceStatisticsChassisLevelTcpSplicingRateLimitingEntry 24 }

affirmedServicesContentHttpProxyServiceStatisticsChassisLevelTcpSplicingRateLimitingNumratelimitingsessioncounttotal OBJECT-TYPE
    SYNTAX      ConfdString
    MAX-ACCESS  read-only
    STATUS      current
    DESCRIPTION "Total number of Rate Limiting sessions"
    ::= { affirmedServicesContentHttpProxyServiceStatisticsChassisLevelTcpSplicingRateLimitingEntry 25 }

affirmedServicesContentHttpProxyServiceStatisticsChassisLevelTcpSplicingRateLimitingNumratelimitingsessionaverageflowcount OBJECT-TYPE
    SYNTAX      ConfdString
    MAX-ACCESS  read-only
    STATUS      current
    DESCRIPTION "Average number of Rate Limiting Flows/Session"
    ::= { affirmedServicesContentHttpProxyServiceStatisticsChassisLevelTcpSplicingRateLimitingEntry 26 }

affirmedServicesContentHttpProxyServiceStatisticsChassisLevelTcpSplicingRateLimitingNumratelimitingsessionaverageduration OBJECT-TYPE
    SYNTAX      ConfdString
    MAX-ACCESS  read-only
    STATUS      current
    DESCRIPTION "Average duration of Rate Limiting Sessions"
    ::= { affirmedServicesContentHttpProxyServiceStatisticsChassisLevelTcpSplicingRateLimitingEntry 27 }

affirmedServicesContentHttpProxyServiceStatisticsChassisLevelTcpSplicingRateLimitingNumratelimitingbypassoverload OBJECT-TYPE
    SYNTAX      ConfdString
    MAX-ACCESS  read-only
    STATUS      current
    DESCRIPTION "Total number of Rate Limiting Bypass due to Overload"
    ::= { affirmedServicesContentHttpProxyServiceStatisticsChassisLevelTcpSplicingRateLimitingEntry 28 }

affirmedServicesContentHttpProxyServiceStatisticsChassisLevelTcpSplicingRateLimitingNumratelimitingsessionaggregationbypass OBJECT-TYPE
    SYNTAX      ConfdString
    MAX-ACCESS  read-only
    STATUS      current
    DESCRIPTION "Total number of Rate Limiting sessions aggregation bypass"
    ::= { affirmedServicesContentHttpProxyServiceStatisticsChassisLevelTcpSplicingRateLimitingEntry 29 }

affirmedServicesContentHttpProxyServiceStatisticsChassisLevelTcpSplicingSummaryTable OBJECT-TYPE
    SYNTAX      SEQUENCE OF AffirmedServicesContentHttpProxyServiceStatisticsChassisLevelTcpSplicingSummaryEntry
    MAX-ACCESS  not-accessible
    STATUS      current
    DESCRIPTION ""
    ::= { affirmedServicesContentHttpProxyServiceStatisticsChassisLevelTcpSplicing 2 }

affirmedServicesContentHttpProxyServiceStatisticsChassisLevelTcpSplicingSummaryEntry OBJECT-TYPE
    SYNTAX      AffirmedServicesContentHttpProxyServiceStatisticsChassisLevelTcpSplicingSummaryEntry
    MAX-ACCESS  not-accessible
    STATUS      current
    DESCRIPTION ""
    INDEX { affirmedServicesContentHttpProxyServiceStatisticsChassisLevelTcpSplicingSummaryChassis }
        ::= { affirmedServicesContentHttpProxyServiceStatisticsChassisLevelTcpSplicingSummaryTable 1 }

AffirmedServicesContentHttpProxyServiceStatisticsChassisLevelTcpSplicingSummaryEntry ::=
    SEQUENCE {
        affirmedServicesContentHttpProxyServiceStatisticsChassisLevelTcpSplicingSummaryChassis Unsigned32,
        affirmedServicesContentHttpProxyServiceStatisticsChassisLevelTcpSplicingSummaryNumtcpsplicingsummaryattempts ConfdString,
        affirmedServicesContentHttpProxyServiceStatisticsChassisLevelTcpSplicingSummaryNumtcpsplicingsummarysuccesses ConfdString,
        affirmedServicesContentHttpProxyServiceStatisticsChassisLevelTcpSplicingSummaryNumtcpsplicingsummaryaborts ConfdString,
        affirmedServicesContentHttpProxyServiceStatisticsChassisLevelTcpSplicingSummaryNumtcpsplicingsummaryfailures ConfdString,
        affirmedServicesContentHttpProxyServiceStatisticsChassisLevelTcpSplicingSummaryNumtcpservicedurationminseconds ConfdString,
        affirmedServicesContentHttpProxyServiceStatisticsChassisLevelTcpSplicingSummaryNumtcpservicedurationmaxseconds ConfdString,
        affirmedServicesContentHttpProxyServiceStatisticsChassisLevelTcpSplicingSummaryNumtcpservicedurationtotalseconds ConfdString,
        affirmedServicesContentHttpProxyServiceStatisticsChassisLevelTcpSplicingSummaryNumtcpservicedurationaverageseconds ConfdString,
        affirmedServicesContentHttpProxyServiceStatisticsChassisLevelTcpSplicingSummaryNumtcpservicedurationmin ConfdString,
        affirmedServicesContentHttpProxyServiceStatisticsChassisLevelTcpSplicingSummaryNumtcpservicedurationmax ConfdString,
        affirmedServicesContentHttpProxyServiceStatisticsChassisLevelTcpSplicingSummaryNumtcpservicedurationavg ConfdString
    }

affirmedServicesContentHttpProxyServiceStatisticsChassisLevelTcpSplicingSummaryChassis OBJECT-TYPE
    SYNTAX      Unsigned32
    MAX-ACCESS  not-accessible
    STATUS      current
    DESCRIPTION "chassis ID"
    ::= { affirmedServicesContentHttpProxyServiceStatisticsChassisLevelTcpSplicingSummaryEntry 1 }

affirmedServicesContentHttpProxyServiceStatisticsChassisLevelTcpSplicingSummaryNumtcpsplicingsummaryattempts OBJECT-TYPE
    SYNTAX      ConfdString
    MAX-ACCESS  read-only
    STATUS      current
    DESCRIPTION "Number of tcp splicing summary attempts"
    ::= { affirmedServicesContentHttpProxyServiceStatisticsChassisLevelTcpSplicingSummaryEntry 2 }

affirmedServicesContentHttpProxyServiceStatisticsChassisLevelTcpSplicingSummaryNumtcpsplicingsummarysuccesses OBJECT-TYPE
    SYNTAX      ConfdString
    MAX-ACCESS  read-only
    STATUS      current
    DESCRIPTION "Number of tcp splicing summary successes"
    ::= { affirmedServicesContentHttpProxyServiceStatisticsChassisLevelTcpSplicingSummaryEntry 3 }

affirmedServicesContentHttpProxyServiceStatisticsChassisLevelTcpSplicingSummaryNumtcpsplicingsummaryaborts OBJECT-TYPE
    SYNTAX      ConfdString
    MAX-ACCESS  read-only
    STATUS      current
    DESCRIPTION "Number of tcp splicing summary aborts"
    ::= { affirmedServicesContentHttpProxyServiceStatisticsChassisLevelTcpSplicingSummaryEntry 4 }

affirmedServicesContentHttpProxyServiceStatisticsChassisLevelTcpSplicingSummaryNumtcpsplicingsummaryfailures OBJECT-TYPE
    SYNTAX      ConfdString
    MAX-ACCESS  read-only
    STATUS      current
    DESCRIPTION "Number of tcp splicing summary failures"
    ::= { affirmedServicesContentHttpProxyServiceStatisticsChassisLevelTcpSplicingSummaryEntry 5 }

affirmedServicesContentHttpProxyServiceStatisticsChassisLevelTcpSplicingSummaryNumtcpservicedurationminseconds OBJECT-TYPE
    SYNTAX      ConfdString
    MAX-ACCESS  read-only
    STATUS      deprecated
    DESCRIPTION "Number of tcp service duration min seconds"
    ::= { affirmedServicesContentHttpProxyServiceStatisticsChassisLevelTcpSplicingSummaryEntry 6 }

affirmedServicesContentHttpProxyServiceStatisticsChassisLevelTcpSplicingSummaryNumtcpservicedurationmaxseconds OBJECT-TYPE
    SYNTAX      ConfdString
    MAX-ACCESS  read-only
    STATUS      deprecated
    DESCRIPTION "Number of tcp service duration max seconds"
    ::= { affirmedServicesContentHttpProxyServiceStatisticsChassisLevelTcpSplicingSummaryEntry 7 }

affirmedServicesContentHttpProxyServiceStatisticsChassisLevelTcpSplicingSummaryNumtcpservicedurationtotalseconds OBJECT-TYPE
    SYNTAX      ConfdString
    MAX-ACCESS  read-only
    STATUS      current
    DESCRIPTION "Number of tcp service duration total"
    ::= { affirmedServicesContentHttpProxyServiceStatisticsChassisLevelTcpSplicingSummaryEntry 8 }

affirmedServicesContentHttpProxyServiceStatisticsChassisLevelTcpSplicingSummaryNumtcpservicedurationaverageseconds OBJECT-TYPE
    SYNTAX      ConfdString
    MAX-ACCESS  read-only
    STATUS      deprecated
    DESCRIPTION "Number of tcp service duration average seconds"
    ::= { affirmedServicesContentHttpProxyServiceStatisticsChassisLevelTcpSplicingSummaryEntry 9 }

affirmedServicesContentHttpProxyServiceStatisticsChassisLevelTcpSplicingSummaryNumtcpservicedurationmin OBJECT-TYPE
    SYNTAX      ConfdString
    MAX-ACCESS  read-only
    STATUS      current
    DESCRIPTION "Number of tcp service duration min seconds"
    ::= { affirmedServicesContentHttpProxyServiceStatisticsChassisLevelTcpSplicingSummaryEntry 10 }

affirmedServicesContentHttpProxyServiceStatisticsChassisLevelTcpSplicingSummaryNumtcpservicedurationmax OBJECT-TYPE
    SYNTAX      ConfdString
    MAX-ACCESS  read-only
    STATUS      current
    DESCRIPTION "Number of tcp service duration max seconds"
    ::= { affirmedServicesContentHttpProxyServiceStatisticsChassisLevelTcpSplicingSummaryEntry 11 }

affirmedServicesContentHttpProxyServiceStatisticsChassisLevelTcpSplicingSummaryNumtcpservicedurationavg OBJECT-TYPE
    SYNTAX      ConfdString
    MAX-ACCESS  read-only
    STATUS      current
    DESCRIPTION "Number of tcp service duration average seconds"
    ::= { affirmedServicesContentHttpProxyServiceStatisticsChassisLevelTcpSplicingSummaryEntry 12 }

affirmedServicesContentHttpProxyServiceStatisticsChassisLevelTcpSplicingDetailTable OBJECT-TYPE
    SYNTAX      SEQUENCE OF AffirmedServicesContentHttpProxyServiceStatisticsChassisLevelTcpSplicingDetailEntry
    MAX-ACCESS  not-accessible
    STATUS      current
    DESCRIPTION ""
    ::= { affirmedServicesContentHttpProxyServiceStatisticsChassisLevelTcpSplicing 3 }

affirmedServicesContentHttpProxyServiceStatisticsChassisLevelTcpSplicingDetailEntry OBJECT-TYPE
    SYNTAX      AffirmedServicesContentHttpProxyServiceStatisticsChassisLevelTcpSplicingDetailEntry
    MAX-ACCESS  not-accessible
    STATUS      current
    DESCRIPTION ""
    INDEX { affirmedServicesContentHttpProxyServiceStatisticsChassisLevelTcpSplicingDetailChassis }
        ::= { affirmedServicesContentHttpProxyServiceStatisticsChassisLevelTcpSplicingDetailTable 1 }

AffirmedServicesContentHttpProxyServiceStatisticsChassisLevelTcpSplicingDetailEntry ::=
    SEQUENCE {
        affirmedServicesContentHttpProxyServiceStatisticsChassisLevelTcpSplicingDetailChassis Unsigned32,
        affirmedServicesContentHttpProxyServiceStatisticsChassisLevelTcpSplicingDetailNumtcpservicehandoffreversehandoffs ConfdString,
        affirmedServicesContentHttpProxyServiceStatisticsChassisLevelTcpSplicingDetailNumtcpsplicingprotocolhttp1xovertls ConfdString,
        affirmedServicesContentHttpProxyServiceStatisticsChassisLevelTcpSplicingDetailNumtcpsplicingprotocolhttp20 ConfdString,
        affirmedServicesContentHttpProxyServiceStatisticsChassisLevelTcpSplicingDetailNumtcpsplicingprotocolhttp20overtls ConfdString,
        affirmedServicesContentHttpProxyServiceStatisticsChassisLevelTcpSplicingDetailNumtcpsplicingprotocolwebsocket ConfdString,
        affirmedServicesContentHttpProxyServiceStatisticsChassisLevelTcpSplicingDetailNumtcpsplicingprotocolothers ConfdString,
        affirmedServicesContentHttpProxyServiceStatisticsChassisLevelTcpSplicingDetailNumtcpsplicingprotocolhttp ConfdString,
        affirmedServicesContentHttpProxyServiceStatisticsChassisLevelTcpSplicingDetailNumtcpsplicingreasonhttpscredentialsnotavailable ConfdString,
        affirmedServicesContentHttpProxyServiceStatisticsChassisLevelTcpSplicingDetailNumtcpsplicingreasonhttpconnectionupgrade ConfdString,
        affirmedServicesContentHttpProxyServiceStatisticsChassisLevelTcpSplicingDetailNumtcpsplicingreasontcpipflow ConfdString,
        affirmedServicesContentHttpProxyServiceStatisticsChassisLevelTcpSplicingDetailNumtcpsplicingreasonnonhttp ConfdString,
        affirmedServicesContentHttpProxyServiceStatisticsChassisLevelTcpSplicingDetailNumtcpsplicingreasonhttprequestreceivetimeout ConfdString,
        affirmedServicesContentHttpProxyServiceStatisticsChassisLevelTcpSplicingDetailNumtcpsplicingreasonhttpconnect ConfdString,
        affirmedServicesContentHttpProxyServiceStatisticsChassisLevelTcpSplicingDetailNumtcpsplicingreasonbypasshttpproxy ConfdString,
        affirmedServicesContentHttpProxyServiceStatisticsChassisLevelTcpSplicingDetailNumtcpsplicingprofileactionallowed ConfdString,
        affirmedServicesContentHttpProxyServiceStatisticsChassisLevelTcpSplicingDetailNumtcpsplicingprofileactionblocked ConfdString,
        affirmedServicesContentHttpProxyServiceStatisticsChassisLevelTcpSplicingDetailNumtcpsplicingprofilesteeredtoip ConfdString,
        affirmedServicesContentHttpProxyServiceStatisticsChassisLevelTcpSplicingDetailNumtcpsplicingprofilesteeredtohost ConfdString,
        affirmedServicesContentHttpProxyServiceStatisticsChassisLevelTcpSplicingDetailNumtcpsplicingpolicyevaluated ConfdString,
        affirmedServicesContentHttpProxyServiceStatisticsChassisLevelTcpSplicingDetailNumtcpsplicingpolicymatched ConfdString,
        affirmedServicesContentHttpProxyServiceStatisticsChassisLevelTcpSplicingDetailNumtcpsplicingpolicyignored ConfdString,
        affirmedServicesContentHttpProxyServiceStatisticsChassisLevelTcpSplicingDetailNumtcpsplicingpolicynotavailable ConfdString,
        affirmedServicesContentHttpProxyServiceStatisticsChassisLevelTcpSplicingDetailNumtcpsplicingpolicyreevaluated ConfdString,
        affirmedServicesContentHttpProxyServiceStatisticsChassisLevelTcpSplicingDetailNumtcpsplicingpolicymatchedafterreevaluation ConfdString,
        affirmedServicesContentHttpProxyServiceStatisticsChassisLevelTcpSplicingDetailNumtcpsplicingpolicynotavailableafterreevaluation ConfdString,
        affirmedServicesContentHttpProxyServiceStatisticsChassisLevelTcpSplicingDetailNumtcpsplicingprotocolwebrtc ConfdString,
        affirmedServicesContentHttpProxyServiceStatisticsChassisLevelTcpSplicingDetailNumtcpsplicingprotocolfacebookzero ConfdString
    }

affirmedServicesContentHttpProxyServiceStatisticsChassisLevelTcpSplicingDetailChassis OBJECT-TYPE
    SYNTAX      Unsigned32
    MAX-ACCESS  not-accessible
    STATUS      current
    DESCRIPTION "chassis ID"
    ::= { affirmedServicesContentHttpProxyServiceStatisticsChassisLevelTcpSplicingDetailEntry 1 }

affirmedServicesContentHttpProxyServiceStatisticsChassisLevelTcpSplicingDetailNumtcpservicehandoffreversehandoffs OBJECT-TYPE
    SYNTAX      ConfdString
    MAX-ACCESS  read-only
    STATUS      current
    DESCRIPTION "Number of tcp service handoff reverse handoffs"
    ::= { affirmedServicesContentHttpProxyServiceStatisticsChassisLevelTcpSplicingDetailEntry 2 }

affirmedServicesContentHttpProxyServiceStatisticsChassisLevelTcpSplicingDetailNumtcpsplicingprotocolhttp1xovertls OBJECT-TYPE
    SYNTAX      ConfdString
    MAX-ACCESS  read-only
    STATUS      current
    DESCRIPTION "Number of tcp splicing protocol http1x over tls"
    ::= { affirmedServicesContentHttpProxyServiceStatisticsChassisLevelTcpSplicingDetailEntry 3 }

affirmedServicesContentHttpProxyServiceStatisticsChassisLevelTcpSplicingDetailNumtcpsplicingprotocolhttp20 OBJECT-TYPE
    SYNTAX      ConfdString
    MAX-ACCESS  read-only
    STATUS      current
    DESCRIPTION "Number of tcp splicing protocol http20"
    ::= { affirmedServicesContentHttpProxyServiceStatisticsChassisLevelTcpSplicingDetailEntry 4 }

affirmedServicesContentHttpProxyServiceStatisticsChassisLevelTcpSplicingDetailNumtcpsplicingprotocolhttp20overtls OBJECT-TYPE
    SYNTAX      ConfdString
    MAX-ACCESS  read-only
    STATUS      current
    DESCRIPTION "Number of tcp splicing protocol http20 over tls"
    ::= { affirmedServicesContentHttpProxyServiceStatisticsChassisLevelTcpSplicingDetailEntry 5 }

affirmedServicesContentHttpProxyServiceStatisticsChassisLevelTcpSplicingDetailNumtcpsplicingprotocolwebsocket OBJECT-TYPE
    SYNTAX      ConfdString
    MAX-ACCESS  read-only
    STATUS      current
    DESCRIPTION "Number of tcp splicing protocol websocket"
    ::= { affirmedServicesContentHttpProxyServiceStatisticsChassisLevelTcpSplicingDetailEntry 6 }

affirmedServicesContentHttpProxyServiceStatisticsChassisLevelTcpSplicingDetailNumtcpsplicingprotocolothers OBJECT-TYPE
    SYNTAX      ConfdString
    MAX-ACCESS  read-only
    STATUS      current
    DESCRIPTION "Number of tcp splicing protocol others"
    ::= { affirmedServicesContentHttpProxyServiceStatisticsChassisLevelTcpSplicingDetailEntry 7 }

affirmedServicesContentHttpProxyServiceStatisticsChassisLevelTcpSplicingDetailNumtcpsplicingprotocolhttp OBJECT-TYPE
    SYNTAX      ConfdString
    MAX-ACCESS  read-only
    STATUS      current
    DESCRIPTION "Number of tcp splicing protocol http"
    ::= { affirmedServicesContentHttpProxyServiceStatisticsChassisLevelTcpSplicingDetailEntry 8 }

affirmedServicesContentHttpProxyServiceStatisticsChassisLevelTcpSplicingDetailNumtcpsplicingreasonhttpscredentialsnotavailable OBJECT-TYPE
    SYNTAX      ConfdString
    MAX-ACCESS  read-only
    STATUS      current
    DESCRIPTION "Number of tcp splicing reason https credentials not available"
    ::= { affirmedServicesContentHttpProxyServiceStatisticsChassisLevelTcpSplicingDetailEntry 9 }

affirmedServicesContentHttpProxyServiceStatisticsChassisLevelTcpSplicingDetailNumtcpsplicingreasonhttpconnectionupgrade OBJECT-TYPE
    SYNTAX      ConfdString
    MAX-ACCESS  read-only
    STATUS      current
    DESCRIPTION "Number of tcp splicing reason http connection upgrade"
    ::= { affirmedServicesContentHttpProxyServiceStatisticsChassisLevelTcpSplicingDetailEntry 10 }

affirmedServicesContentHttpProxyServiceStatisticsChassisLevelTcpSplicingDetailNumtcpsplicingreasontcpipflow OBJECT-TYPE
    SYNTAX      ConfdString
    MAX-ACCESS  read-only
    STATUS      current
    DESCRIPTION "Number of tcp splicing reason tcp ip flow"
    ::= { affirmedServicesContentHttpProxyServiceStatisticsChassisLevelTcpSplicingDetailEntry 11 }

affirmedServicesContentHttpProxyServiceStatisticsChassisLevelTcpSplicingDetailNumtcpsplicingreasonnonhttp OBJECT-TYPE
    SYNTAX      ConfdString
    MAX-ACCESS  read-only
    STATUS      current
    DESCRIPTION "Number of tcp splicing reason nonhttp"
    ::= { affirmedServicesContentHttpProxyServiceStatisticsChassisLevelTcpSplicingDetailEntry 12 }

affirmedServicesContentHttpProxyServiceStatisticsChassisLevelTcpSplicingDetailNumtcpsplicingreasonhttprequestreceivetimeout OBJECT-TYPE
    SYNTAX      ConfdString
    MAX-ACCESS  read-only
    STATUS      current
    DESCRIPTION "Number of tcp splicing reason http request receive timeout"
    ::= { affirmedServicesContentHttpProxyServiceStatisticsChassisLevelTcpSplicingDetailEntry 13 }

affirmedServicesContentHttpProxyServiceStatisticsChassisLevelTcpSplicingDetailNumtcpsplicingreasonhttpconnect OBJECT-TYPE
    SYNTAX      ConfdString
    MAX-ACCESS  read-only
    STATUS      current
    DESCRIPTION "Number of tcp splicing reason http connect"
    ::= { affirmedServicesContentHttpProxyServiceStatisticsChassisLevelTcpSplicingDetailEntry 14 }

affirmedServicesContentHttpProxyServiceStatisticsChassisLevelTcpSplicingDetailNumtcpsplicingreasonbypasshttpproxy OBJECT-TYPE
    SYNTAX      ConfdString
    MAX-ACCESS  read-only
    STATUS      current
    DESCRIPTION "Number of tcp splicing reason bypass http proxy"
    ::= { affirmedServicesContentHttpProxyServiceStatisticsChassisLevelTcpSplicingDetailEntry 15 }

affirmedServicesContentHttpProxyServiceStatisticsChassisLevelTcpSplicingDetailNumtcpsplicingprofileactionallowed OBJECT-TYPE
    SYNTAX      ConfdString
    MAX-ACCESS  read-only
    STATUS      current
    DESCRIPTION "Number of tcp splicing profile action allowed"
    ::= { affirmedServicesContentHttpProxyServiceStatisticsChassisLevelTcpSplicingDetailEntry 16 }

affirmedServicesContentHttpProxyServiceStatisticsChassisLevelTcpSplicingDetailNumtcpsplicingprofileactionblocked OBJECT-TYPE
    SYNTAX      ConfdString
    MAX-ACCESS  read-only
    STATUS      current
    DESCRIPTION "Number of tcp splicing profile action blocked"
    ::= { affirmedServicesContentHttpProxyServiceStatisticsChassisLevelTcpSplicingDetailEntry 17 }

affirmedServicesContentHttpProxyServiceStatisticsChassisLevelTcpSplicingDetailNumtcpsplicingprofilesteeredtoip OBJECT-TYPE
    SYNTAX      ConfdString
    MAX-ACCESS  read-only
    STATUS      current
    DESCRIPTION "Number of tcp splicing profile steered to ip"
    ::= { affirmedServicesContentHttpProxyServiceStatisticsChassisLevelTcpSplicingDetailEntry 18 }

affirmedServicesContentHttpProxyServiceStatisticsChassisLevelTcpSplicingDetailNumtcpsplicingprofilesteeredtohost OBJECT-TYPE
    SYNTAX      ConfdString
    MAX-ACCESS  read-only
    STATUS      current
    DESCRIPTION "Number of tcp splicing profile steered to host"
    ::= { affirmedServicesContentHttpProxyServiceStatisticsChassisLevelTcpSplicingDetailEntry 19 }

affirmedServicesContentHttpProxyServiceStatisticsChassisLevelTcpSplicingDetailNumtcpsplicingpolicyevaluated OBJECT-TYPE
    SYNTAX      ConfdString
    MAX-ACCESS  read-only
    STATUS      current
    DESCRIPTION "Number of tcp splicing policy evaluated"
    ::= { affirmedServicesContentHttpProxyServiceStatisticsChassisLevelTcpSplicingDetailEntry 20 }

affirmedServicesContentHttpProxyServiceStatisticsChassisLevelTcpSplicingDetailNumtcpsplicingpolicymatched OBJECT-TYPE
    SYNTAX      ConfdString
    MAX-ACCESS  read-only
    STATUS      current
    DESCRIPTION "Number of tcp splicing policy matched"
    ::= { affirmedServicesContentHttpProxyServiceStatisticsChassisLevelTcpSplicingDetailEntry 21 }

affirmedServicesContentHttpProxyServiceStatisticsChassisLevelTcpSplicingDetailNumtcpsplicingpolicyignored OBJECT-TYPE
    SYNTAX      ConfdString
    MAX-ACCESS  read-only
    STATUS      current
    DESCRIPTION "Number of tcp splicing policy ignored"
    ::= { affirmedServicesContentHttpProxyServiceStatisticsChassisLevelTcpSplicingDetailEntry 22 }

affirmedServicesContentHttpProxyServiceStatisticsChassisLevelTcpSplicingDetailNumtcpsplicingpolicynotavailable OBJECT-TYPE
    SYNTAX      ConfdString
    MAX-ACCESS  read-only
    STATUS      current
    DESCRIPTION "Number of tcp splicing policy not available"
    ::= { affirmedServicesContentHttpProxyServiceStatisticsChassisLevelTcpSplicingDetailEntry 23 }

affirmedServicesContentHttpProxyServiceStatisticsChassisLevelTcpSplicingDetailNumtcpsplicingpolicyreevaluated OBJECT-TYPE
    SYNTAX      ConfdString
    MAX-ACCESS  read-only
    STATUS      current
    DESCRIPTION "Number of tcp splicing policy reevaluated"
    ::= { affirmedServicesContentHttpProxyServiceStatisticsChassisLevelTcpSplicingDetailEntry 24 }

affirmedServicesContentHttpProxyServiceStatisticsChassisLevelTcpSplicingDetailNumtcpsplicingpolicymatchedafterreevaluation OBJECT-TYPE
    SYNTAX      ConfdString
    MAX-ACCESS  read-only
    STATUS      current
    DESCRIPTION "Number of tcp splicing policy matched after reevaluation"
    ::= { affirmedServicesContentHttpProxyServiceStatisticsChassisLevelTcpSplicingDetailEntry 25 }

affirmedServicesContentHttpProxyServiceStatisticsChassisLevelTcpSplicingDetailNumtcpsplicingpolicynotavailableafterreevaluation OBJECT-TYPE
    SYNTAX      ConfdString
    MAX-ACCESS  read-only
    STATUS      current
    DESCRIPTION "Number of tcp splicing policy not available after reevaluation"
    ::= { affirmedServicesContentHttpProxyServiceStatisticsChassisLevelTcpSplicingDetailEntry 26 }

affirmedServicesContentHttpProxyServiceStatisticsChassisLevelTcpSplicingDetailNumtcpsplicingprotocolwebrtc OBJECT-TYPE
    SYNTAX      ConfdString
    MAX-ACCESS  read-only
    STATUS      current
    DESCRIPTION "Number of tcp splicing protocol webRTC"
    ::= { affirmedServicesContentHttpProxyServiceStatisticsChassisLevelTcpSplicingDetailEntry 27 }

affirmedServicesContentHttpProxyServiceStatisticsChassisLevelTcpSplicingDetailNumtcpsplicingprotocolfacebookzero OBJECT-TYPE
    SYNTAX      ConfdString
    MAX-ACCESS  read-only
    STATUS      current
    DESCRIPTION "Number of tcp splicing protocol FacebookZero"
    ::= { affirmedServicesContentHttpProxyServiceStatisticsChassisLevelTcpSplicingDetailEntry 28 }

affirmedServicesContentHttpProxyServiceStatisticsChassisLevelTcpSplicingFailureTable OBJECT-TYPE
    SYNTAX      SEQUENCE OF AffirmedServicesContentHttpProxyServiceStatisticsChassisLevelTcpSplicingFailureEntry
    MAX-ACCESS  not-accessible
    STATUS      current
    DESCRIPTION ""
    ::= { affirmedServicesContentHttpProxyServiceStatisticsChassisLevelTcpSplicing 4 }

affirmedServicesContentHttpProxyServiceStatisticsChassisLevelTcpSplicingFailureEntry OBJECT-TYPE
    SYNTAX      AffirmedServicesContentHttpProxyServiceStatisticsChassisLevelTcpSplicingFailureEntry
    MAX-ACCESS  not-accessible
    STATUS      current
    DESCRIPTION ""
    INDEX { affirmedServicesContentHttpProxyServiceStatisticsChassisLevelTcpSplicingFailureChassis }
        ::= { affirmedServicesContentHttpProxyServiceStatisticsChassisLevelTcpSplicingFailureTable 1 }

AffirmedServicesContentHttpProxyServiceStatisticsChassisLevelTcpSplicingFailureEntry ::=
    SEQUENCE {
        affirmedServicesContentHttpProxyServiceStatisticsChassisLevelTcpSplicingFailureChassis Unsigned32,
        affirmedServicesContentHttpProxyServiceStatisticsChassisLevelTcpSplicingFailureNumtcpsplicingabortsclientabort ConfdString,
        affirmedServicesContentHttpProxyServiceStatisticsChassisLevelTcpSplicingFailureNumtcpsplicingabortsserverabort ConfdString,
        affirmedServicesContentHttpProxyServiceStatisticsChassisLevelTcpSplicingFailureNumtcpsplicingabortsidletimeout ConfdString,
        affirmedServicesContentHttpProxyServiceStatisticsChassisLevelTcpSplicingFailureNumtcpsplicingabortsclientsocketerror ConfdString,
        affirmedServicesContentHttpProxyServiceStatisticsChassisLevelTcpSplicingFailureNumtcpsplicingabortsserversocketerror ConfdString,
        affirmedServicesContentHttpProxyServiceStatisticsChassisLevelTcpSplicingFailureNumtcpsplicingabortsclientreaderror ConfdString,
        affirmedServicesContentHttpProxyServiceStatisticsChassisLevelTcpSplicingFailureNumtcpsplicingabortsclientwriteerror ConfdString,
        affirmedServicesContentHttpProxyServiceStatisticsChassisLevelTcpSplicingFailureNumtcpsplicingabortsserverreaderror ConfdString,
        affirmedServicesContentHttpProxyServiceStatisticsChassisLevelTcpSplicingFailureNumtcpsplicingabortsserverwriteerror ConfdString,
        affirmedServicesContentHttpProxyServiceStatisticsChassisLevelTcpSplicingFailureNumtcpsplicingabortsnodatainconnection ConfdString,
        affirmedServicesContentHttpProxyServiceStatisticsChassisLevelTcpSplicingFailureNumtcpsplicingabortsclienterror ConfdString,
        affirmedServicesContentHttpProxyServiceStatisticsChassisLevelTcpSplicingFailureNumtcpsplicingabortsservererror ConfdString,
        affirmedServicesContentHttpProxyServiceStatisticsChassisLevelTcpSplicingFailureNumtcpsplicingfailuresoutofbuffers ConfdString,
        affirmedServicesContentHttpProxyServiceStatisticsChassisLevelTcpSplicingFailureNumtcpsplicingfailuresserverconnectionfailure ConfdString,
        affirmedServicesContentHttpProxyServiceStatisticsChassisLevelTcpSplicingFailureNumtcpsplicingfailuresdnsrequestfailure ConfdString,
        affirmedServicesContentHttpProxyServiceStatisticsChassisLevelTcpSplicingFailureNumtcpsplicingfailuresdnsresponsefailure ConfdString,
        affirmedServicesContentHttpProxyServiceStatisticsChassisLevelTcpSplicingFailureNumtcpsplicingfailurespolicyreject ConfdString,
        affirmedServicesContentHttpProxyServiceStatisticsChassisLevelTcpSplicingFailureNumtcpsplicingfailurestfdreject ConfdString,
        affirmedServicesContentHttpProxyServiceStatisticsChassisLevelTcpSplicingFailureNumtcpsplicingfailuresoutofsocket ConfdString
    }

affirmedServicesContentHttpProxyServiceStatisticsChassisLevelTcpSplicingFailureChassis OBJECT-TYPE
    SYNTAX      Unsigned32
    MAX-ACCESS  not-accessible
    STATUS      current
    DESCRIPTION "chassis ID"
    ::= { affirmedServicesContentHttpProxyServiceStatisticsChassisLevelTcpSplicingFailureEntry 1 }

affirmedServicesContentHttpProxyServiceStatisticsChassisLevelTcpSplicingFailureNumtcpsplicingabortsclientabort OBJECT-TYPE
    SYNTAX      ConfdString
    MAX-ACCESS  read-only
    STATUS      current
    DESCRIPTION "Number of tcp splicing aborts client abort"
    ::= { affirmedServicesContentHttpProxyServiceStatisticsChassisLevelTcpSplicingFailureEntry 2 }

affirmedServicesContentHttpProxyServiceStatisticsChassisLevelTcpSplicingFailureNumtcpsplicingabortsserverabort OBJECT-TYPE
    SYNTAX      ConfdString
    MAX-ACCESS  read-only
    STATUS      current
    DESCRIPTION "Number of tcp splicing aborts serverabort"
    ::= { affirmedServicesContentHttpProxyServiceStatisticsChassisLevelTcpSplicingFailureEntry 3 }

affirmedServicesContentHttpProxyServiceStatisticsChassisLevelTcpSplicingFailureNumtcpsplicingabortsidletimeout OBJECT-TYPE
    SYNTAX      ConfdString
    MAX-ACCESS  read-only
    STATUS      current
    DESCRIPTION "Number of tcp splicing aborts idle timeout"
    ::= { affirmedServicesContentHttpProxyServiceStatisticsChassisLevelTcpSplicingFailureEntry 4 }

affirmedServicesContentHttpProxyServiceStatisticsChassisLevelTcpSplicingFailureNumtcpsplicingabortsclientsocketerror OBJECT-TYPE
    SYNTAX      ConfdString
    MAX-ACCESS  read-only
    STATUS      current
    DESCRIPTION "Number of tcp splicing aborts client socket error"
    ::= { affirmedServicesContentHttpProxyServiceStatisticsChassisLevelTcpSplicingFailureEntry 5 }

affirmedServicesContentHttpProxyServiceStatisticsChassisLevelTcpSplicingFailureNumtcpsplicingabortsserversocketerror OBJECT-TYPE
    SYNTAX      ConfdString
    MAX-ACCESS  read-only
    STATUS      current
    DESCRIPTION "Number of tcp splicing aborts server socket error"
    ::= { affirmedServicesContentHttpProxyServiceStatisticsChassisLevelTcpSplicingFailureEntry 6 }

affirmedServicesContentHttpProxyServiceStatisticsChassisLevelTcpSplicingFailureNumtcpsplicingabortsclientreaderror OBJECT-TYPE
    SYNTAX      ConfdString
    MAX-ACCESS  read-only
    STATUS      current
    DESCRIPTION "Number of tcp splicing aborts client read error"
    ::= { affirmedServicesContentHttpProxyServiceStatisticsChassisLevelTcpSplicingFailureEntry 7 }

affirmedServicesContentHttpProxyServiceStatisticsChassisLevelTcpSplicingFailureNumtcpsplicingabortsclientwriteerror OBJECT-TYPE
    SYNTAX      ConfdString
    MAX-ACCESS  read-only
    STATUS      current
    DESCRIPTION "Number of tcp splicing aborts client write error"
    ::= { affirmedServicesContentHttpProxyServiceStatisticsChassisLevelTcpSplicingFailureEntry 8 }

affirmedServicesContentHttpProxyServiceStatisticsChassisLevelTcpSplicingFailureNumtcpsplicingabortsserverreaderror OBJECT-TYPE
    SYNTAX      ConfdString
    MAX-ACCESS  read-only
    STATUS      current
    DESCRIPTION "Number of tcp splicing aborts server read error"
    ::= { affirmedServicesContentHttpProxyServiceStatisticsChassisLevelTcpSplicingFailureEntry 9 }

affirmedServicesContentHttpProxyServiceStatisticsChassisLevelTcpSplicingFailureNumtcpsplicingabortsserverwriteerror OBJECT-TYPE
    SYNTAX      ConfdString
    MAX-ACCESS  read-only
    STATUS      current
    DESCRIPTION "Number of tcp splicing aborts server write error"
    ::= { affirmedServicesContentHttpProxyServiceStatisticsChassisLevelTcpSplicingFailureEntry 10 }

affirmedServicesContentHttpProxyServiceStatisticsChassisLevelTcpSplicingFailureNumtcpsplicingabortsnodatainconnection OBJECT-TYPE
    SYNTAX      ConfdString
    MAX-ACCESS  read-only
    STATUS      current
    DESCRIPTION "Number of tcp splicing aborts no data in connection"
    ::= { affirmedServicesContentHttpProxyServiceStatisticsChassisLevelTcpSplicingFailureEntry 11 }

affirmedServicesContentHttpProxyServiceStatisticsChassisLevelTcpSplicingFailureNumtcpsplicingabortsclienterror OBJECT-TYPE
    SYNTAX      ConfdString
    MAX-ACCESS  read-only
    STATUS      current
    DESCRIPTION "Number of tcp splicing aborts client error"
    ::= { affirmedServicesContentHttpProxyServiceStatisticsChassisLevelTcpSplicingFailureEntry 12 }

affirmedServicesContentHttpProxyServiceStatisticsChassisLevelTcpSplicingFailureNumtcpsplicingabortsservererror OBJECT-TYPE
    SYNTAX      ConfdString
    MAX-ACCESS  read-only
    STATUS      current
    DESCRIPTION "Number of tcp splicing aborts server error"
    ::= { affirmedServicesContentHttpProxyServiceStatisticsChassisLevelTcpSplicingFailureEntry 13 }

affirmedServicesContentHttpProxyServiceStatisticsChassisLevelTcpSplicingFailureNumtcpsplicingfailuresoutofbuffers OBJECT-TYPE
    SYNTAX      ConfdString
    MAX-ACCESS  read-only
    STATUS      current
    DESCRIPTION "Number of tcp splicing failures out of buffers"
    ::= { affirmedServicesContentHttpProxyServiceStatisticsChassisLevelTcpSplicingFailureEntry 14 }

affirmedServicesContentHttpProxyServiceStatisticsChassisLevelTcpSplicingFailureNumtcpsplicingfailuresserverconnectionfailure OBJECT-TYPE
    SYNTAX      ConfdString
    MAX-ACCESS  read-only
    STATUS      current
    DESCRIPTION "Number of tcp splicing failures server connection failure"
    ::= { affirmedServicesContentHttpProxyServiceStatisticsChassisLevelTcpSplicingFailureEntry 15 }

affirmedServicesContentHttpProxyServiceStatisticsChassisLevelTcpSplicingFailureNumtcpsplicingfailuresdnsrequestfailure OBJECT-TYPE
    SYNTAX      ConfdString
    MAX-ACCESS  read-only
    STATUS      current
    DESCRIPTION "Number of tcp splicing failures dns request failure"
    ::= { affirmedServicesContentHttpProxyServiceStatisticsChassisLevelTcpSplicingFailureEntry 16 }

affirmedServicesContentHttpProxyServiceStatisticsChassisLevelTcpSplicingFailureNumtcpsplicingfailuresdnsresponsefailure OBJECT-TYPE
    SYNTAX      ConfdString
    MAX-ACCESS  read-only
    STATUS      current
    DESCRIPTION "Number of tcp splicing failures dns response failure"
    ::= { affirmedServicesContentHttpProxyServiceStatisticsChassisLevelTcpSplicingFailureEntry 17 }

affirmedServicesContentHttpProxyServiceStatisticsChassisLevelTcpSplicingFailureNumtcpsplicingfailurespolicyreject OBJECT-TYPE
    SYNTAX      ConfdString
    MAX-ACCESS  read-only
    STATUS      current
    DESCRIPTION "Number of tcp splicing failures policy reject"
    ::= { affirmedServicesContentHttpProxyServiceStatisticsChassisLevelTcpSplicingFailureEntry 18 }

affirmedServicesContentHttpProxyServiceStatisticsChassisLevelTcpSplicingFailureNumtcpsplicingfailurestfdreject OBJECT-TYPE
    SYNTAX      ConfdString
    MAX-ACCESS  read-only
    STATUS      current
    DESCRIPTION "Number of tcp splicing failures tfd reject"
    ::= { affirmedServicesContentHttpProxyServiceStatisticsChassisLevelTcpSplicingFailureEntry 19 }

affirmedServicesContentHttpProxyServiceStatisticsChassisLevelTcpSplicingFailureNumtcpsplicingfailuresoutofsocket OBJECT-TYPE
    SYNTAX      ConfdString
    MAX-ACCESS  read-only
    STATUS      current
    DESCRIPTION "Number of tcp splicing failures out of socket"
    ::= { affirmedServicesContentHttpProxyServiceStatisticsChassisLevelTcpSplicingFailureEntry 20 }

affirmedServicesContentHttpProxyServiceStatisticsChassisLevelTcpSplicingConnectionTable OBJECT-TYPE
    SYNTAX      SEQUENCE OF AffirmedServicesContentHttpProxyServiceStatisticsChassisLevelTcpSplicingConnectionEntry
    MAX-ACCESS  not-accessible
    STATUS      current
    DESCRIPTION ""
    ::= { affirmedServicesContentHttpProxyServiceStatisticsChassisLevelTcpSplicing 5 }

affirmedServicesContentHttpProxyServiceStatisticsChassisLevelTcpSplicingConnectionEntry OBJECT-TYPE
    SYNTAX      AffirmedServicesContentHttpProxyServiceStatisticsChassisLevelTcpSplicingConnectionEntry
    MAX-ACCESS  not-accessible
    STATUS      current
    DESCRIPTION ""
    INDEX { affirmedServicesContentHttpProxyServiceStatisticsChassisLevelTcpSplicingConnectionChassis }
        ::= { affirmedServicesContentHttpProxyServiceStatisticsChassisLevelTcpSplicingConnectionTable 1 }

AffirmedServicesContentHttpProxyServiceStatisticsChassisLevelTcpSplicingConnectionEntry ::=
    SEQUENCE {
        affirmedServicesContentHttpProxyServiceStatisticsChassisLevelTcpSplicingConnectionChassis Unsigned32,
        affirmedServicesContentHttpProxyServiceStatisticsChassisLevelTcpSplicingConnectionNumtcpsplicingclientconnectionstotal ConfdString,
        affirmedServicesContentHttpProxyServiceStatisticsChassisLevelTcpSplicingConnectionNumtcpsplicingclientconnectionscurrentlyinuse ConfdString,
        affirmedServicesContentHttpProxyServiceStatisticsChassisLevelTcpSplicingConnectionNumtcpsplicingclientconnectionsipv4 ConfdString,
        affirmedServicesContentHttpProxyServiceStatisticsChassisLevelTcpSplicingConnectionNumtcpsplicingclientconnectionsipv6 ConfdString,
        affirmedServicesContentHttpProxyServiceStatisticsChassisLevelTcpSplicingConnectionNumtcpsplicingclientconnectionsbytesreceived ConfdString,
        affirmedServicesContentHttpProxyServiceStatisticsChassisLevelTcpSplicingConnectionNumtcpsplicingclientconnectionsbytessent ConfdString,
        affirmedServicesContentHttpProxyServiceStatisticsChassisLevelTcpSplicingConnectionNumtcpsplicingclientconnectionsreadfailure ConfdString,
        affirmedServicesContentHttpProxyServiceStatisticsChassisLevelTcpSplicingConnectionNumtcpsplicingclientconnectionswritefailure ConfdString,
        affirmedServicesContentHttpProxyServiceStatisticsChassisLevelTcpSplicingConnectionNumtcpsplicingclientconnectionswriteincomplete ConfdString,
        affirmedServicesContentHttpProxyServiceStatisticsChassisLevelTcpSplicingConnectionNumtcpsplicingserverconnectionstotal ConfdString,
        affirmedServicesContentHttpProxyServiceStatisticsChassisLevelTcpSplicingConnectionNumtcpsplicingserverconnectionscurrentlyinuse ConfdString,
        affirmedServicesContentHttpProxyServiceStatisticsChassisLevelTcpSplicingConnectionNumtcpsplicingserverconnectionsipv4 ConfdString,
        affirmedServicesContentHttpProxyServiceStatisticsChassisLevelTcpSplicingConnectionNumtcpsplicingserverconnectionsipv6 ConfdString,
        affirmedServicesContentHttpProxyServiceStatisticsChassisLevelTcpSplicingConnectionNumtcpsplicingserverconnectionsiptransparent ConfdString,
        affirmedServicesContentHttpProxyServiceStatisticsChassisLevelTcpSplicingConnectionNumtcpsplicingserverconnectionsbytesreceived ConfdString,
        affirmedServicesContentHttpProxyServiceStatisticsChassisLevelTcpSplicingConnectionNumtcpsplicingserverconnectionsbytessent ConfdString,
        affirmedServicesContentHttpProxyServiceStatisticsChassisLevelTcpSplicingConnectionNumtcpsplicingserverconnectionsreadfailure ConfdString,
        affirmedServicesContentHttpProxyServiceStatisticsChassisLevelTcpSplicingConnectionNumtcpsplicingserverconnectionswritefailure ConfdString,
        affirmedServicesContentHttpProxyServiceStatisticsChassisLevelTcpSplicingConnectionNumtcpsplicingserverconnectionswriteincomplete ConfdString,
        affirmedServicesContentHttpProxyServiceStatisticsChassisLevelTcpSplicingConnectionNumtcpsplicingserverconnectionsconnectfailed ConfdString,
        affirmedServicesContentHttpProxyServiceStatisticsChassisLevelTcpSplicingConnectionNumtcpsplicingclientconnectionscurrentinuse ConfdString,
        affirmedServicesContentHttpProxyServiceStatisticsChassisLevelTcpSplicingConnectionNumtcpsplicingserverconnectionscurrentinuse ConfdString,
        affirmedServicesContentHttpProxyServiceStatisticsChassisLevelTcpSplicingConnectionNumfastopenattempts ConfdString,
        affirmedServicesContentHttpProxyServiceStatisticsChassisLevelTcpSplicingConnectionNumfastopensuccesses ConfdString,
        affirmedServicesContentHttpProxyServiceStatisticsChassisLevelTcpSplicingConnectionNumfastopenfailureinitconn ConfdString,
        affirmedServicesContentHttpProxyServiceStatisticsChassisLevelTcpSplicingConnectionNumfastopenfailureduplicate ConfdString,
        affirmedServicesContentHttpProxyServiceStatisticsChassisLevelTcpSplicingConnectionNumfastopenfailurealreadycreated ConfdString,
        affirmedServicesContentHttpProxyServiceStatisticsChassisLevelTcpSplicingConnectionNumfastopenfailurepolicy ConfdString,
        affirmedServicesContentHttpProxyServiceStatisticsChassisLevelTcpSplicingConnectionNumfastopenfailureother ConfdString,
        affirmedServicesContentHttpProxyServiceStatisticsChassisLevelTcpSplicingConnectionNumfastopenlistfull ConfdString,
        affirmedServicesContentHttpProxyServiceStatisticsChassisLevelTcpSplicingConnectionNumfastopencurrentpendingconn ConfdString,
        affirmedServicesContentHttpProxyServiceStatisticsChassisLevelTcpSplicingConnectionNumfastopenaging ConfdString,
        affirmedServicesContentHttpProxyServiceStatisticsChassisLevelTcpSplicingConnectionNumtcpsplicingdpiupdates ConfdString,
        affirmedServicesContentHttpProxyServiceStatisticsChassisLevelTcpSplicingConnectionNumtcpsplicingdpiupdatefailures ConfdString
    }

affirmedServicesContentHttpProxyServiceStatisticsChassisLevelTcpSplicingConnectionChassis OBJECT-TYPE
    SYNTAX      Unsigned32
    MAX-ACCESS  not-accessible
    STATUS      current
    DESCRIPTION "chassis ID"
    ::= { affirmedServicesContentHttpProxyServiceStatisticsChassisLevelTcpSplicingConnectionEntry 1 }

affirmedServicesContentHttpProxyServiceStatisticsChassisLevelTcpSplicingConnectionNumtcpsplicingclientconnectionstotal OBJECT-TYPE
    SYNTAX      ConfdString
    MAX-ACCESS  read-only
    STATUS      current
    DESCRIPTION "Number of tcp splicing client connections total"
    ::= { affirmedServicesContentHttpProxyServiceStatisticsChassisLevelTcpSplicingConnectionEntry 2 }

affirmedServicesContentHttpProxyServiceStatisticsChassisLevelTcpSplicingConnectionNumtcpsplicingclientconnectionscurrentlyinuse OBJECT-TYPE
    SYNTAX      ConfdString
    MAX-ACCESS  read-only
    STATUS      deprecated
    DESCRIPTION "Number of tcp splicing client connections currently in use"
    ::= { affirmedServicesContentHttpProxyServiceStatisticsChassisLevelTcpSplicingConnectionEntry 3 }

affirmedServicesContentHttpProxyServiceStatisticsChassisLevelTcpSplicingConnectionNumtcpsplicingclientconnectionsipv4 OBJECT-TYPE
    SYNTAX      ConfdString
    MAX-ACCESS  read-only
    STATUS      current
    DESCRIPTION "Number of tcp splicing client connections ipv4"
    ::= { affirmedServicesContentHttpProxyServiceStatisticsChassisLevelTcpSplicingConnectionEntry 4 }

affirmedServicesContentHttpProxyServiceStatisticsChassisLevelTcpSplicingConnectionNumtcpsplicingclientconnectionsipv6 OBJECT-TYPE
    SYNTAX      ConfdString
    MAX-ACCESS  read-only
    STATUS      current
    DESCRIPTION "Number of tcp splicing client connections ipv6"
    ::= { affirmedServicesContentHttpProxyServiceStatisticsChassisLevelTcpSplicingConnectionEntry 5 }

affirmedServicesContentHttpProxyServiceStatisticsChassisLevelTcpSplicingConnectionNumtcpsplicingclientconnectionsbytesreceived OBJECT-TYPE
    SYNTAX      ConfdString
    MAX-ACCESS  read-only
    STATUS      current
    DESCRIPTION "Number of tcp splicing client connections bytes received"
    ::= { affirmedServicesContentHttpProxyServiceStatisticsChassisLevelTcpSplicingConnectionEntry 6 }

affirmedServicesContentHttpProxyServiceStatisticsChassisLevelTcpSplicingConnectionNumtcpsplicingclientconnectionsbytessent OBJECT-TYPE
    SYNTAX      ConfdString
    MAX-ACCESS  read-only
    STATUS      current
    DESCRIPTION "Number of tcp splicing client connections bytes sent"
    ::= { affirmedServicesContentHttpProxyServiceStatisticsChassisLevelTcpSplicingConnectionEntry 7 }

affirmedServicesContentHttpProxyServiceStatisticsChassisLevelTcpSplicingConnectionNumtcpsplicingclientconnectionsreadfailure OBJECT-TYPE
    SYNTAX      ConfdString
    MAX-ACCESS  read-only
    STATUS      current
    DESCRIPTION "Number of tcp splicing client connections read failure"
    ::= { affirmedServicesContentHttpProxyServiceStatisticsChassisLevelTcpSplicingConnectionEntry 8 }

affirmedServicesContentHttpProxyServiceStatisticsChassisLevelTcpSplicingConnectionNumtcpsplicingclientconnectionswritefailure OBJECT-TYPE
    SYNTAX      ConfdString
    MAX-ACCESS  read-only
    STATUS      current
    DESCRIPTION "Number of tcp splicing client connections write failure"
    ::= { affirmedServicesContentHttpProxyServiceStatisticsChassisLevelTcpSplicingConnectionEntry 9 }

affirmedServicesContentHttpProxyServiceStatisticsChassisLevelTcpSplicingConnectionNumtcpsplicingclientconnectionswriteincomplete OBJECT-TYPE
    SYNTAX      ConfdString
    MAX-ACCESS  read-only
    STATUS      current
    DESCRIPTION "Number of tcp splicing client connections write incomplete"
    ::= { affirmedServicesContentHttpProxyServiceStatisticsChassisLevelTcpSplicingConnectionEntry 10 }

affirmedServicesContentHttpProxyServiceStatisticsChassisLevelTcpSplicingConnectionNumtcpsplicingserverconnectionstotal OBJECT-TYPE
    SYNTAX      ConfdString
    MAX-ACCESS  read-only
    STATUS      current
    DESCRIPTION "Number of tcp splicing server connections total"
    ::= { affirmedServicesContentHttpProxyServiceStatisticsChassisLevelTcpSplicingConnectionEntry 11 }

affirmedServicesContentHttpProxyServiceStatisticsChassisLevelTcpSplicingConnectionNumtcpsplicingserverconnectionscurrentlyinuse OBJECT-TYPE
    SYNTAX      ConfdString
    MAX-ACCESS  read-only
    STATUS      deprecated
    DESCRIPTION "Number of tcp splicing server connections currently in use"
    ::= { affirmedServicesContentHttpProxyServiceStatisticsChassisLevelTcpSplicingConnectionEntry 12 }

affirmedServicesContentHttpProxyServiceStatisticsChassisLevelTcpSplicingConnectionNumtcpsplicingserverconnectionsipv4 OBJECT-TYPE
    SYNTAX      ConfdString
    MAX-ACCESS  read-only
    STATUS      current
    DESCRIPTION "Number of tcp splicing server connections ipv4"
    ::= { affirmedServicesContentHttpProxyServiceStatisticsChassisLevelTcpSplicingConnectionEntry 13 }

affirmedServicesContentHttpProxyServiceStatisticsChassisLevelTcpSplicingConnectionNumtcpsplicingserverconnectionsipv6 OBJECT-TYPE
    SYNTAX      ConfdString
    MAX-ACCESS  read-only
    STATUS      current
    DESCRIPTION "Number of tcp splicing server connections ipv6"
    ::= { affirmedServicesContentHttpProxyServiceStatisticsChassisLevelTcpSplicingConnectionEntry 14 }

affirmedServicesContentHttpProxyServiceStatisticsChassisLevelTcpSplicingConnectionNumtcpsplicingserverconnectionsiptransparent OBJECT-TYPE
    SYNTAX      ConfdString
    MAX-ACCESS  read-only
    STATUS      current
    DESCRIPTION "Number of tcp splicing server connections ip transparent"
    ::= { affirmedServicesContentHttpProxyServiceStatisticsChassisLevelTcpSplicingConnectionEntry 15 }

affirmedServicesContentHttpProxyServiceStatisticsChassisLevelTcpSplicingConnectionNumtcpsplicingserverconnectionsbytesreceived OBJECT-TYPE
    SYNTAX      ConfdString
    MAX-ACCESS  read-only
    STATUS      current
    DESCRIPTION "Number of tcp splicing server connections bytes received"
    ::= { affirmedServicesContentHttpProxyServiceStatisticsChassisLevelTcpSplicingConnectionEntry 16 }

affirmedServicesContentHttpProxyServiceStatisticsChassisLevelTcpSplicingConnectionNumtcpsplicingserverconnectionsbytessent OBJECT-TYPE
    SYNTAX      ConfdString
    MAX-ACCESS  read-only
    STATUS      current
    DESCRIPTION "Number of tcp splicing server connections bytes sent"
    ::= { affirmedServicesContentHttpProxyServiceStatisticsChassisLevelTcpSplicingConnectionEntry 17 }

affirmedServicesContentHttpProxyServiceStatisticsChassisLevelTcpSplicingConnectionNumtcpsplicingserverconnectionsreadfailure OBJECT-TYPE
    SYNTAX      ConfdString
    MAX-ACCESS  read-only
    STATUS      current
    DESCRIPTION "Number of tcp splicing server connections read failure"
    ::= { affirmedServicesContentHttpProxyServiceStatisticsChassisLevelTcpSplicingConnectionEntry 18 }

affirmedServicesContentHttpProxyServiceStatisticsChassisLevelTcpSplicingConnectionNumtcpsplicingserverconnectionswritefailure OBJECT-TYPE
    SYNTAX      ConfdString
    MAX-ACCESS  read-only
    STATUS      current
    DESCRIPTION "Number of tcp splicing server connections write failure"
    ::= { affirmedServicesContentHttpProxyServiceStatisticsChassisLevelTcpSplicingConnectionEntry 19 }

affirmedServicesContentHttpProxyServiceStatisticsChassisLevelTcpSplicingConnectionNumtcpsplicingserverconnectionswriteincomplete OBJECT-TYPE
    SYNTAX      ConfdString
    MAX-ACCESS  read-only
    STATUS      current
    DESCRIPTION "Number of tcp splicing server connections write incomplete"
    ::= { affirmedServicesContentHttpProxyServiceStatisticsChassisLevelTcpSplicingConnectionEntry 20 }

affirmedServicesContentHttpProxyServiceStatisticsChassisLevelTcpSplicingConnectionNumtcpsplicingserverconnectionsconnectfailed OBJECT-TYPE
    SYNTAX      ConfdString
    MAX-ACCESS  read-only
    STATUS      current
    DESCRIPTION "Number of tcp splicing server connections connect failed"
    ::= { affirmedServicesContentHttpProxyServiceStatisticsChassisLevelTcpSplicingConnectionEntry 21 }

affirmedServicesContentHttpProxyServiceStatisticsChassisLevelTcpSplicingConnectionNumtcpsplicingclientconnectionscurrentinuse OBJECT-TYPE
    SYNTAX      ConfdString
    MAX-ACCESS  read-only
    STATUS      current
    DESCRIPTION "Number of tcp splicing client connections currently in use"
    ::= { affirmedServicesContentHttpProxyServiceStatisticsChassisLevelTcpSplicingConnectionEntry 22 }

affirmedServicesContentHttpProxyServiceStatisticsChassisLevelTcpSplicingConnectionNumtcpsplicingserverconnectionscurrentinuse OBJECT-TYPE
    SYNTAX      ConfdString
    MAX-ACCESS  read-only
    STATUS      current
    DESCRIPTION "Number of tcp splicing server connections currently in use"
    ::= { affirmedServicesContentHttpProxyServiceStatisticsChassisLevelTcpSplicingConnectionEntry 23 }

affirmedServicesContentHttpProxyServiceStatisticsChassisLevelTcpSplicingConnectionNumfastopenattempts OBJECT-TYPE
    SYNTAX      ConfdString
    MAX-ACCESS  read-only
    STATUS      current
    DESCRIPTION "Total number of HTTPS server connection fast open attempts"
    ::= { affirmedServicesContentHttpProxyServiceStatisticsChassisLevelTcpSplicingConnectionEntry 24 }

affirmedServicesContentHttpProxyServiceStatisticsChassisLevelTcpSplicingConnectionNumfastopensuccesses OBJECT-TYPE
    SYNTAX      ConfdString
    MAX-ACCESS  read-only
    STATUS      current
    DESCRIPTION "Total number of HTTPS server connection fast open successes"
    ::= { affirmedServicesContentHttpProxyServiceStatisticsChassisLevelTcpSplicingConnectionEntry 25 }

affirmedServicesContentHttpProxyServiceStatisticsChassisLevelTcpSplicingConnectionNumfastopenfailureinitconn OBJECT-TYPE
    SYNTAX      ConfdString
    MAX-ACCESS  read-only
    STATUS      current
    DESCRIPTION "Total number of HTTPS server connection fast open initialization failure"
    ::= { affirmedServicesContentHttpProxyServiceStatisticsChassisLevelTcpSplicingConnectionEntry 26 }

affirmedServicesContentHttpProxyServiceStatisticsChassisLevelTcpSplicingConnectionNumfastopenfailureduplicate OBJECT-TYPE
    SYNTAX      ConfdString
    MAX-ACCESS  read-only
    STATUS      current
    DESCRIPTION "Total number of HTTPS server connection fast open duplicated connection"
    ::= { affirmedServicesContentHttpProxyServiceStatisticsChassisLevelTcpSplicingConnectionEntry 27 }

affirmedServicesContentHttpProxyServiceStatisticsChassisLevelTcpSplicingConnectionNumfastopenfailurealreadycreated OBJECT-TYPE
    SYNTAX      ConfdString
    MAX-ACCESS  read-only
    STATUS      current
    DESCRIPTION "Total number of HTTPS server connection fast open already in the session"
    ::= { affirmedServicesContentHttpProxyServiceStatisticsChassisLevelTcpSplicingConnectionEntry 28 }

affirmedServicesContentHttpProxyServiceStatisticsChassisLevelTcpSplicingConnectionNumfastopenfailurepolicy OBJECT-TYPE
    SYNTAX      ConfdString
    MAX-ACCESS  read-only
    STATUS      current
    DESCRIPTION "Total number of HTTPS server connection fast open policy reject"
    ::= { affirmedServicesContentHttpProxyServiceStatisticsChassisLevelTcpSplicingConnectionEntry 29 }

affirmedServicesContentHttpProxyServiceStatisticsChassisLevelTcpSplicingConnectionNumfastopenfailureother OBJECT-TYPE
    SYNTAX      ConfdString
    MAX-ACCESS  read-only
    STATUS      current
    DESCRIPTION "Total number of HTTPS server connection fast open failure others"
    ::= { affirmedServicesContentHttpProxyServiceStatisticsChassisLevelTcpSplicingConnectionEntry 30 }

affirmedServicesContentHttpProxyServiceStatisticsChassisLevelTcpSplicingConnectionNumfastopenlistfull OBJECT-TYPE
    SYNTAX      ConfdString
    MAX-ACCESS  read-only
    STATUS      current
    DESCRIPTION "Total number of HTTPS server connection fast open pending list full"
    ::= { affirmedServicesContentHttpProxyServiceStatisticsChassisLevelTcpSplicingConnectionEntry 31 }

affirmedServicesContentHttpProxyServiceStatisticsChassisLevelTcpSplicingConnectionNumfastopencurrentpendingconn OBJECT-TYPE
    SYNTAX      ConfdString
    MAX-ACCESS  read-only
    STATUS      current
    DESCRIPTION "Total number of HTTPS server connection fast open in pending list"
    ::= { affirmedServicesContentHttpProxyServiceStatisticsChassisLevelTcpSplicingConnectionEntry 32 }

affirmedServicesContentHttpProxyServiceStatisticsChassisLevelTcpSplicingConnectionNumfastopenaging OBJECT-TYPE
    SYNTAX      ConfdString
    MAX-ACCESS  read-only
    STATUS      current
    DESCRIPTION "Total number of HTTPS server connection fast open connection closed due to aging"
    ::= { affirmedServicesContentHttpProxyServiceStatisticsChassisLevelTcpSplicingConnectionEntry 33 }

affirmedServicesContentHttpProxyServiceStatisticsChassisLevelTcpSplicingConnectionNumtcpsplicingdpiupdates OBJECT-TYPE
    SYNTAX      ConfdString
    MAX-ACCESS  read-only
    STATUS      current
    DESCRIPTION "Total Number of tcp splicing DPI Updates"
    ::= { affirmedServicesContentHttpProxyServiceStatisticsChassisLevelTcpSplicingConnectionEntry 34 }

affirmedServicesContentHttpProxyServiceStatisticsChassisLevelTcpSplicingConnectionNumtcpsplicingdpiupdatefailures OBJECT-TYPE
    SYNTAX      ConfdString
    MAX-ACCESS  read-only
    STATUS      current
    DESCRIPTION "Total Number of tcp splicing DPI Update Failures"
    ::= { affirmedServicesContentHttpProxyServiceStatisticsChassisLevelTcpSplicingConnectionEntry 35 }

affirmedServicesContentHttpProxyServiceStatisticsChassisLevelTcpSplicingDnsTable OBJECT-TYPE
    SYNTAX      SEQUENCE OF AffirmedServicesContentHttpProxyServiceStatisticsChassisLevelTcpSplicingDnsEntry
    MAX-ACCESS  not-accessible
    STATUS      current
    DESCRIPTION ""
    ::= { affirmedServicesContentHttpProxyServiceStatisticsChassisLevelTcpSplicing 6 }

affirmedServicesContentHttpProxyServiceStatisticsChassisLevelTcpSplicingDnsEntry OBJECT-TYPE
    SYNTAX      AffirmedServicesContentHttpProxyServiceStatisticsChassisLevelTcpSplicingDnsEntry
    MAX-ACCESS  not-accessible
    STATUS      current
    DESCRIPTION ""
    INDEX { affirmedServicesContentHttpProxyServiceStatisticsChassisLevelTcpSplicingDnsChassis }
        ::= { affirmedServicesContentHttpProxyServiceStatisticsChassisLevelTcpSplicingDnsTable 1 }

AffirmedServicesContentHttpProxyServiceStatisticsChassisLevelTcpSplicingDnsEntry ::=
    SEQUENCE {
        affirmedServicesContentHttpProxyServiceStatisticsChassisLevelTcpSplicingDnsChassis Unsigned32,
        affirmedServicesContentHttpProxyServiceStatisticsChassisLevelTcpSplicingDnsNumtcpsplicingdnsqueriessent ConfdString,
        affirmedServicesContentHttpProxyServiceStatisticsChassisLevelTcpSplicingDnsNumtcpsplicingdnsqueriesfailed ConfdString,
        affirmedServicesContentHttpProxyServiceStatisticsChassisLevelTcpSplicingDnsNumtcpsplicingdnsqueriescanceled ConfdString,
        affirmedServicesContentHttpProxyServiceStatisticsChassisLevelTcpSplicingDnsNumtcpsplicingdnsrepliessuccess ConfdString,
        affirmedServicesContentHttpProxyServiceStatisticsChassisLevelTcpSplicingDnsNumtcpsplicingdnsrepliesfailure ConfdString,
        affirmedServicesContentHttpProxyServiceStatisticsChassisLevelTcpSplicingDnsNumtcpsplicingdnsrepliesstale ConfdString,
        affirmedServicesContentHttpProxyServiceStatisticsChassisLevelTcpSplicingDnsNumtcpsplicingdnsrepliesfromcache ConfdString
    }

affirmedServicesContentHttpProxyServiceStatisticsChassisLevelTcpSplicingDnsChassis OBJECT-TYPE
    SYNTAX      Unsigned32
    MAX-ACCESS  not-accessible
    STATUS      current
    DESCRIPTION "chassis ID"
    ::= { affirmedServicesContentHttpProxyServiceStatisticsChassisLevelTcpSplicingDnsEntry 1 }

affirmedServicesContentHttpProxyServiceStatisticsChassisLevelTcpSplicingDnsNumtcpsplicingdnsqueriessent OBJECT-TYPE
    SYNTAX      ConfdString
    MAX-ACCESS  read-only
    STATUS      current
    DESCRIPTION "Number of tcp splicing dns queries sent"
    ::= { affirmedServicesContentHttpProxyServiceStatisticsChassisLevelTcpSplicingDnsEntry 2 }

affirmedServicesContentHttpProxyServiceStatisticsChassisLevelTcpSplicingDnsNumtcpsplicingdnsqueriesfailed OBJECT-TYPE
    SYNTAX      ConfdString
    MAX-ACCESS  read-only
    STATUS      current
    DESCRIPTION "Number of tcp splicing dns queries failed"
    ::= { affirmedServicesContentHttpProxyServiceStatisticsChassisLevelTcpSplicingDnsEntry 3 }

affirmedServicesContentHttpProxyServiceStatisticsChassisLevelTcpSplicingDnsNumtcpsplicingdnsqueriescanceled OBJECT-TYPE
    SYNTAX      ConfdString
    MAX-ACCESS  read-only
    STATUS      current
    DESCRIPTION "Number of tcp splicing dns queries canceled"
    ::= { affirmedServicesContentHttpProxyServiceStatisticsChassisLevelTcpSplicingDnsEntry 4 }

affirmedServicesContentHttpProxyServiceStatisticsChassisLevelTcpSplicingDnsNumtcpsplicingdnsrepliessuccess OBJECT-TYPE
    SYNTAX      ConfdString
    MAX-ACCESS  read-only
    STATUS      current
    DESCRIPTION "Number of tcp splicing dns replies success"
    ::= { affirmedServicesContentHttpProxyServiceStatisticsChassisLevelTcpSplicingDnsEntry 5 }

affirmedServicesContentHttpProxyServiceStatisticsChassisLevelTcpSplicingDnsNumtcpsplicingdnsrepliesfailure OBJECT-TYPE
    SYNTAX      ConfdString
    MAX-ACCESS  read-only
    STATUS      current
    DESCRIPTION "Number of tcp splicing dns replies failure"
    ::= { affirmedServicesContentHttpProxyServiceStatisticsChassisLevelTcpSplicingDnsEntry 6 }

affirmedServicesContentHttpProxyServiceStatisticsChassisLevelTcpSplicingDnsNumtcpsplicingdnsrepliesstale OBJECT-TYPE
    SYNTAX      ConfdString
    MAX-ACCESS  read-only
    STATUS      current
    DESCRIPTION "Number of tcp splicing dns replies stale"
    ::= { affirmedServicesContentHttpProxyServiceStatisticsChassisLevelTcpSplicingDnsEntry 7 }

affirmedServicesContentHttpProxyServiceStatisticsChassisLevelTcpSplicingDnsNumtcpsplicingdnsrepliesfromcache OBJECT-TYPE
    SYNTAX      ConfdString
    MAX-ACCESS  read-only
    STATUS      current
    DESCRIPTION "Number of tcp splicing dns replies from cache"
    ::= { affirmedServicesContentHttpProxyServiceStatisticsChassisLevelTcpSplicingDnsEntry 8 }

affirmedServicesContentHttpProxyServiceStatisticsChassisLevelBufferBufferTable OBJECT-TYPE
    SYNTAX      SEQUENCE OF AffirmedServicesContentHttpProxyServiceStatisticsChassisLevelBufferBufferEntry
    MAX-ACCESS  not-accessible
    STATUS      deprecated
    DESCRIPTION ""
    ::= { affirmedServicesContentHttpProxyServiceStatisticsChassisLevelBuffer 1 }

affirmedServicesContentHttpProxyServiceStatisticsChassisLevelBufferBufferEntry OBJECT-TYPE
    SYNTAX      AffirmedServicesContentHttpProxyServiceStatisticsChassisLevelBufferBufferEntry
    MAX-ACCESS  not-accessible
    STATUS      deprecated
    DESCRIPTION ""
    INDEX { affirmedServicesContentHttpProxyServiceStatisticsChassisLevelBufferBufferChassis }
        ::= { affirmedServicesContentHttpProxyServiceStatisticsChassisLevelBufferBufferTable 1 }

AffirmedServicesContentHttpProxyServiceStatisticsChassisLevelBufferBufferEntry ::=
    SEQUENCE {
        affirmedServicesContentHttpProxyServiceStatisticsChassisLevelBufferBufferChassis Unsigned32,
        affirmedServicesContentHttpProxyServiceStatisticsChassisLevelBufferBufferPbuf-allocated ConfdString,
        affirmedServicesContentHttpProxyServiceStatisticsChassisLevelBufferBufferPbuf-5min-peak ConfdString,
        affirmedServicesContentHttpProxyServiceStatisticsChassisLevelBufferBufferPbuf-total ConfdString,
        affirmedServicesContentHttpProxyServiceStatisticsChassisLevelBufferBufferBuffer-4k-allocated ConfdString,
        affirmedServicesContentHttpProxyServiceStatisticsChassisLevelBufferBufferBuffer-4k-5min-peak ConfdString,
        affirmedServicesContentHttpProxyServiceStatisticsChassisLevelBufferBufferBuffer-4k-total ConfdString,
        affirmedServicesContentHttpProxyServiceStatisticsChassisLevelBufferBufferBuffer-8k-allocated ConfdString,
        affirmedServicesContentHttpProxyServiceStatisticsChassisLevelBufferBufferBuffer-8k-5min-peak ConfdString,
        affirmedServicesContentHttpProxyServiceStatisticsChassisLevelBufferBufferBuffer-8k-total ConfdString,
        affirmedServicesContentHttpProxyServiceStatisticsChassisLevelBufferBufferBuffer-64k-allocated ConfdString,
        affirmedServicesContentHttpProxyServiceStatisticsChassisLevelBufferBufferBuffer-64k-5min-peak ConfdString,
        affirmedServicesContentHttpProxyServiceStatisticsChassisLevelBufferBufferBuffer-64k-total ConfdString,
        affirmedServicesContentHttpProxyServiceStatisticsChassisLevelBufferBufferBuffer-128k-allocated ConfdString,
        affirmedServicesContentHttpProxyServiceStatisticsChassisLevelBufferBufferBuffer-128k-5min-peak ConfdString,
        affirmedServicesContentHttpProxyServiceStatisticsChassisLevelBufferBufferBuffer-128k-total ConfdString,
        affirmedServicesContentHttpProxyServiceStatisticsChassisLevelBufferBufferBuffer-256k-allocated ConfdString,
        affirmedServicesContentHttpProxyServiceStatisticsChassisLevelBufferBufferBuffer-256k-5min-peak ConfdString,
        affirmedServicesContentHttpProxyServiceStatisticsChassisLevelBufferBufferBuffer-256k-total ConfdString,
        affirmedServicesContentHttpProxyServiceStatisticsChassisLevelBufferBufferBuffer-512k-allocated ConfdString,
        affirmedServicesContentHttpProxyServiceStatisticsChassisLevelBufferBufferBuffer-512k-5min-peak ConfdString,
        affirmedServicesContentHttpProxyServiceStatisticsChassisLevelBufferBufferBuffer-512k-total ConfdString
    }

affirmedServicesContentHttpProxyServiceStatisticsChassisLevelBufferBufferChassis OBJECT-TYPE
    SYNTAX      Unsigned32
    MAX-ACCESS  not-accessible
    STATUS      current
    DESCRIPTION "chassis ID"
    ::= { affirmedServicesContentHttpProxyServiceStatisticsChassisLevelBufferBufferEntry 1 }

affirmedServicesContentHttpProxyServiceStatisticsChassisLevelBufferBufferPbuf-allocated OBJECT-TYPE
    SYNTAX      ConfdString
    MAX-ACCESS  read-only
    STATUS      current
    DESCRIPTION "Number of packet buffers currently allocated"
    ::= { affirmedServicesContentHttpProxyServiceStatisticsChassisLevelBufferBufferEntry 2 }

affirmedServicesContentHttpProxyServiceStatisticsChassisLevelBufferBufferPbuf-5min-peak OBJECT-TYPE
    SYNTAX      ConfdString
    MAX-ACCESS  read-only
    STATUS      current
    DESCRIPTION "Max number of packet buffers allocated in last 5 minutes"
    ::= { affirmedServicesContentHttpProxyServiceStatisticsChassisLevelBufferBufferEntry 3 }

affirmedServicesContentHttpProxyServiceStatisticsChassisLevelBufferBufferPbuf-total OBJECT-TYPE
    SYNTAX      ConfdString
    MAX-ACCESS  read-only
    STATUS      current
    DESCRIPTION "Total packet buffers in the pool"
    ::= { affirmedServicesContentHttpProxyServiceStatisticsChassisLevelBufferBufferEntry 4 }

affirmedServicesContentHttpProxyServiceStatisticsChassisLevelBufferBufferBuffer-4k-allocated OBJECT-TYPE
    SYNTAX      ConfdString
    MAX-ACCESS  read-only
    STATUS      current
    DESCRIPTION "Number of 4K buffers currently allocated"
    ::= { affirmedServicesContentHttpProxyServiceStatisticsChassisLevelBufferBufferEntry 5 }

affirmedServicesContentHttpProxyServiceStatisticsChassisLevelBufferBufferBuffer-4k-5min-peak OBJECT-TYPE
    SYNTAX      ConfdString
    MAX-ACCESS  read-only
    STATUS      current
    DESCRIPTION "Max number of 4K buffers allocated in last 5 minutes"
    ::= { affirmedServicesContentHttpProxyServiceStatisticsChassisLevelBufferBufferEntry 6 }

affirmedServicesContentHttpProxyServiceStatisticsChassisLevelBufferBufferBuffer-4k-total OBJECT-TYPE
    SYNTAX      ConfdString
    MAX-ACCESS  read-only
    STATUS      current
    DESCRIPTION "Total 4K buffers in the pool"
    ::= { affirmedServicesContentHttpProxyServiceStatisticsChassisLevelBufferBufferEntry 7 }

affirmedServicesContentHttpProxyServiceStatisticsChassisLevelBufferBufferBuffer-8k-allocated OBJECT-TYPE
    SYNTAX      ConfdString
    MAX-ACCESS  read-only
    STATUS      current
    DESCRIPTION "Number of 8K buffers currently allocated"
    ::= { affirmedServicesContentHttpProxyServiceStatisticsChassisLevelBufferBufferEntry 8 }

affirmedServicesContentHttpProxyServiceStatisticsChassisLevelBufferBufferBuffer-8k-5min-peak OBJECT-TYPE
    SYNTAX      ConfdString
    MAX-ACCESS  read-only
    STATUS      current
    DESCRIPTION "Max number of 8K buffers allocated in last 5 minutes"
    ::= { affirmedServicesContentHttpProxyServiceStatisticsChassisLevelBufferBufferEntry 9 }

affirmedServicesContentHttpProxyServiceStatisticsChassisLevelBufferBufferBuffer-8k-total OBJECT-TYPE
    SYNTAX      ConfdString
    MAX-ACCESS  read-only
    STATUS      current
    DESCRIPTION "Total 8K buffers in the pool"
    ::= { affirmedServicesContentHttpProxyServiceStatisticsChassisLevelBufferBufferEntry 10 }

affirmedServicesContentHttpProxyServiceStatisticsChassisLevelBufferBufferBuffer-64k-allocated OBJECT-TYPE
    SYNTAX      ConfdString
    MAX-ACCESS  read-only
    STATUS      current
    DESCRIPTION "Number of 64K buffers currently allocated"
    ::= { affirmedServicesContentHttpProxyServiceStatisticsChassisLevelBufferBufferEntry 11 }

affirmedServicesContentHttpProxyServiceStatisticsChassisLevelBufferBufferBuffer-64k-5min-peak OBJECT-TYPE
    SYNTAX      ConfdString
    MAX-ACCESS  read-only
    STATUS      current
    DESCRIPTION "Max number of 64K buffers allocated in last 5 minutes"
    ::= { affirmedServicesContentHttpProxyServiceStatisticsChassisLevelBufferBufferEntry 12 }

affirmedServicesContentHttpProxyServiceStatisticsChassisLevelBufferBufferBuffer-64k-total OBJECT-TYPE
    SYNTAX      ConfdString
    MAX-ACCESS  read-only
    STATUS      current
    DESCRIPTION "Total 64K buffers in the pool"
    ::= { affirmedServicesContentHttpProxyServiceStatisticsChassisLevelBufferBufferEntry 13 }

affirmedServicesContentHttpProxyServiceStatisticsChassisLevelBufferBufferBuffer-128k-allocated OBJECT-TYPE
    SYNTAX      ConfdString
    MAX-ACCESS  read-only
    STATUS      current
    DESCRIPTION "Number of 128K buffers currently allocated"
    ::= { affirmedServicesContentHttpProxyServiceStatisticsChassisLevelBufferBufferEntry 14 }

affirmedServicesContentHttpProxyServiceStatisticsChassisLevelBufferBufferBuffer-128k-5min-peak OBJECT-TYPE
    SYNTAX      ConfdString
    MAX-ACCESS  read-only
    STATUS      current
    DESCRIPTION "Max number of 128K buffers allocated in last 5 minutes"
    ::= { affirmedServicesContentHttpProxyServiceStatisticsChassisLevelBufferBufferEntry 15 }

affirmedServicesContentHttpProxyServiceStatisticsChassisLevelBufferBufferBuffer-128k-total OBJECT-TYPE
    SYNTAX      ConfdString
    MAX-ACCESS  read-only
    STATUS      current
    DESCRIPTION "Total 128K buffers in the pool"
    ::= { affirmedServicesContentHttpProxyServiceStatisticsChassisLevelBufferBufferEntry 16 }

affirmedServicesContentHttpProxyServiceStatisticsChassisLevelBufferBufferBuffer-256k-allocated OBJECT-TYPE
    SYNTAX      ConfdString
    MAX-ACCESS  read-only
    STATUS      current
    DESCRIPTION "Number of 256K buffers currently allocated"
    ::= { affirmedServicesContentHttpProxyServiceStatisticsChassisLevelBufferBufferEntry 17 }

affirmedServicesContentHttpProxyServiceStatisticsChassisLevelBufferBufferBuffer-256k-5min-peak OBJECT-TYPE
    SYNTAX      ConfdString
    MAX-ACCESS  read-only
    STATUS      current
    DESCRIPTION "Max number of 256K buffers allocated in last 5 minutes"
    ::= { affirmedServicesContentHttpProxyServiceStatisticsChassisLevelBufferBufferEntry 18 }

affirmedServicesContentHttpProxyServiceStatisticsChassisLevelBufferBufferBuffer-256k-total OBJECT-TYPE
    SYNTAX      ConfdString
    MAX-ACCESS  read-only
    STATUS      current
    DESCRIPTION "Total 256K buffers in the pool"
    ::= { affirmedServicesContentHttpProxyServiceStatisticsChassisLevelBufferBufferEntry 19 }

affirmedServicesContentHttpProxyServiceStatisticsChassisLevelBufferBufferBuffer-512k-allocated OBJECT-TYPE
    SYNTAX      ConfdString
    MAX-ACCESS  read-only
    STATUS      current
    DESCRIPTION "Number of 512K buffers currently allocated"
    ::= { affirmedServicesContentHttpProxyServiceStatisticsChassisLevelBufferBufferEntry 20 }

affirmedServicesContentHttpProxyServiceStatisticsChassisLevelBufferBufferBuffer-512k-5min-peak OBJECT-TYPE
    SYNTAX      ConfdString
    MAX-ACCESS  read-only
    STATUS      current
    DESCRIPTION "Max number of 512K buffers allocated in last 5 minutes"
    ::= { affirmedServicesContentHttpProxyServiceStatisticsChassisLevelBufferBufferEntry 21 }

affirmedServicesContentHttpProxyServiceStatisticsChassisLevelBufferBufferBuffer-512k-total OBJECT-TYPE
    SYNTAX      ConfdString
    MAX-ACCESS  read-only
    STATUS      current
    DESCRIPTION "Total 512K buffers in the pool"
    ::= { affirmedServicesContentHttpProxyServiceStatisticsChassisLevelBufferBufferEntry 22 }

affirmedServicesContentHttpProxyServiceStatisticsChassisLevelBufferSummaryTable OBJECT-TYPE
    SYNTAX      SEQUENCE OF AffirmedServicesContentHttpProxyServiceStatisticsChassisLevelBufferSummaryEntry
    MAX-ACCESS  not-accessible
    STATUS      deprecated
    DESCRIPTION ""
    ::= { affirmedServicesContentHttpProxyServiceStatisticsChassisLevelBuffer 2 }

affirmedServicesContentHttpProxyServiceStatisticsChassisLevelBufferSummaryEntry OBJECT-TYPE
    SYNTAX      AffirmedServicesContentHttpProxyServiceStatisticsChassisLevelBufferSummaryEntry
    MAX-ACCESS  not-accessible
    STATUS      deprecated
    DESCRIPTION ""
    INDEX { affirmedServicesContentHttpProxyServiceStatisticsChassisLevelBufferSummaryChassis }
        ::= { affirmedServicesContentHttpProxyServiceStatisticsChassisLevelBufferSummaryTable 1 }

AffirmedServicesContentHttpProxyServiceStatisticsChassisLevelBufferSummaryEntry ::=
    SEQUENCE {
        affirmedServicesContentHttpProxyServiceStatisticsChassisLevelBufferSummaryChassis Unsigned32,
        affirmedServicesContentHttpProxyServiceStatisticsChassisLevelBufferSummaryPbuf-allocated ConfdString,
        affirmedServicesContentHttpProxyServiceStatisticsChassisLevelBufferSummaryPbuf-5min-peak ConfdString,
        affirmedServicesContentHttpProxyServiceStatisticsChassisLevelBufferSummaryPbuf-total ConfdString,
        affirmedServicesContentHttpProxyServiceStatisticsChassisLevelBufferSummaryBuffer-4k-allocated ConfdString,
        affirmedServicesContentHttpProxyServiceStatisticsChassisLevelBufferSummaryBuffer-4k-5min-peak ConfdString,
        affirmedServicesContentHttpProxyServiceStatisticsChassisLevelBufferSummaryBuffer-4k-total ConfdString,
        affirmedServicesContentHttpProxyServiceStatisticsChassisLevelBufferSummaryBuffer-8k-allocated ConfdString,
        affirmedServicesContentHttpProxyServiceStatisticsChassisLevelBufferSummaryBuffer-8k-5min-peak ConfdString,
        affirmedServicesContentHttpProxyServiceStatisticsChassisLevelBufferSummaryBuffer-8k-total ConfdString,
        affirmedServicesContentHttpProxyServiceStatisticsChassisLevelBufferSummaryBuffer-64k-allocated ConfdString,
        affirmedServicesContentHttpProxyServiceStatisticsChassisLevelBufferSummaryBuffer-64k-5min-peak ConfdString,
        affirmedServicesContentHttpProxyServiceStatisticsChassisLevelBufferSummaryBuffer-64k-total ConfdString,
        affirmedServicesContentHttpProxyServiceStatisticsChassisLevelBufferSummaryBuffer-128k-allocated ConfdString,
        affirmedServicesContentHttpProxyServiceStatisticsChassisLevelBufferSummaryBuffer-128k-5min-peak ConfdString,
        affirmedServicesContentHttpProxyServiceStatisticsChassisLevelBufferSummaryBuffer-128k-total ConfdString,
        affirmedServicesContentHttpProxyServiceStatisticsChassisLevelBufferSummaryBuffer-256k-allocated ConfdString,
        affirmedServicesContentHttpProxyServiceStatisticsChassisLevelBufferSummaryBuffer-256k-5min-peak ConfdString,
        affirmedServicesContentHttpProxyServiceStatisticsChassisLevelBufferSummaryBuffer-256k-total ConfdString,
        affirmedServicesContentHttpProxyServiceStatisticsChassisLevelBufferSummaryBuffer-512k-allocated ConfdString,
        affirmedServicesContentHttpProxyServiceStatisticsChassisLevelBufferSummaryBuffer-512k-5min-peak ConfdString,
        affirmedServicesContentHttpProxyServiceStatisticsChassisLevelBufferSummaryBuffer-512k-total ConfdString,
        affirmedServicesContentHttpProxyServiceStatisticsChassisLevelBufferSummaryBuffer-2k-allocated ConfdString,
        affirmedServicesContentHttpProxyServiceStatisticsChassisLevelBufferSummaryBuffer-2k-5min-peak ConfdString,
        affirmedServicesContentHttpProxyServiceStatisticsChassisLevelBufferSummaryBuffer-2k-total ConfdString
    }

affirmedServicesContentHttpProxyServiceStatisticsChassisLevelBufferSummaryChassis OBJECT-TYPE
    SYNTAX      Unsigned32
    MAX-ACCESS  not-accessible
    STATUS      current
    DESCRIPTION "chassis ID"
    ::= { affirmedServicesContentHttpProxyServiceStatisticsChassisLevelBufferSummaryEntry 1 }

affirmedServicesContentHttpProxyServiceStatisticsChassisLevelBufferSummaryPbuf-allocated OBJECT-TYPE
    SYNTAX      ConfdString
    MAX-ACCESS  read-only
    STATUS      current
    DESCRIPTION "Number of packet buffers currently allocated"
    ::= { affirmedServicesContentHttpProxyServiceStatisticsChassisLevelBufferSummaryEntry 2 }

affirmedServicesContentHttpProxyServiceStatisticsChassisLevelBufferSummaryPbuf-5min-peak OBJECT-TYPE
    SYNTAX      ConfdString
    MAX-ACCESS  read-only
    STATUS      current
    DESCRIPTION "Max number of packet buffers allocated in last 5 minutes"
    ::= { affirmedServicesContentHttpProxyServiceStatisticsChassisLevelBufferSummaryEntry 3 }

affirmedServicesContentHttpProxyServiceStatisticsChassisLevelBufferSummaryPbuf-total OBJECT-TYPE
    SYNTAX      ConfdString
    MAX-ACCESS  read-only
    STATUS      current
    DESCRIPTION "Total packet buffers in the pool"
    ::= { affirmedServicesContentHttpProxyServiceStatisticsChassisLevelBufferSummaryEntry 4 }

affirmedServicesContentHttpProxyServiceStatisticsChassisLevelBufferSummaryBuffer-4k-allocated OBJECT-TYPE
    SYNTAX      ConfdString
    MAX-ACCESS  read-only
    STATUS      current
    DESCRIPTION "Number of 4K buffers currently allocated"
    ::= { affirmedServicesContentHttpProxyServiceStatisticsChassisLevelBufferSummaryEntry 5 }

affirmedServicesContentHttpProxyServiceStatisticsChassisLevelBufferSummaryBuffer-4k-5min-peak OBJECT-TYPE
    SYNTAX      ConfdString
    MAX-ACCESS  read-only
    STATUS      current
    DESCRIPTION "Max number of 4K buffers allocated in last 5 minutes"
    ::= { affirmedServicesContentHttpProxyServiceStatisticsChassisLevelBufferSummaryEntry 6 }

affirmedServicesContentHttpProxyServiceStatisticsChassisLevelBufferSummaryBuffer-4k-total OBJECT-TYPE
    SYNTAX      ConfdString
    MAX-ACCESS  read-only
    STATUS      current
    DESCRIPTION "Total 4K buffers in the pool"
    ::= { affirmedServicesContentHttpProxyServiceStatisticsChassisLevelBufferSummaryEntry 7 }

affirmedServicesContentHttpProxyServiceStatisticsChassisLevelBufferSummaryBuffer-8k-allocated OBJECT-TYPE
    SYNTAX      ConfdString
    MAX-ACCESS  read-only
    STATUS      current
    DESCRIPTION "Number of 8K buffers currently allocated"
    ::= { affirmedServicesContentHttpProxyServiceStatisticsChassisLevelBufferSummaryEntry 8 }

affirmedServicesContentHttpProxyServiceStatisticsChassisLevelBufferSummaryBuffer-8k-5min-peak OBJECT-TYPE
    SYNTAX      ConfdString
    MAX-ACCESS  read-only
    STATUS      current
    DESCRIPTION "Max number of 8K buffers allocated in last 5 minutes"
    ::= { affirmedServicesContentHttpProxyServiceStatisticsChassisLevelBufferSummaryEntry 9 }

affirmedServicesContentHttpProxyServiceStatisticsChassisLevelBufferSummaryBuffer-8k-total OBJECT-TYPE
    SYNTAX      ConfdString
    MAX-ACCESS  read-only
    STATUS      current
    DESCRIPTION "Total 8K buffers in the pool"
    ::= { affirmedServicesContentHttpProxyServiceStatisticsChassisLevelBufferSummaryEntry 10 }

affirmedServicesContentHttpProxyServiceStatisticsChassisLevelBufferSummaryBuffer-64k-allocated OBJECT-TYPE
    SYNTAX      ConfdString
    MAX-ACCESS  read-only
    STATUS      current
    DESCRIPTION "Number of 64K buffers currently allocated"
    ::= { affirmedServicesContentHttpProxyServiceStatisticsChassisLevelBufferSummaryEntry 11 }

affirmedServicesContentHttpProxyServiceStatisticsChassisLevelBufferSummaryBuffer-64k-5min-peak OBJECT-TYPE
    SYNTAX      ConfdString
    MAX-ACCESS  read-only
    STATUS      current
    DESCRIPTION "Max number of 64K buffers allocated in last 5 minutes"
    ::= { affirmedServicesContentHttpProxyServiceStatisticsChassisLevelBufferSummaryEntry 12 }

affirmedServicesContentHttpProxyServiceStatisticsChassisLevelBufferSummaryBuffer-64k-total OBJECT-TYPE
    SYNTAX      ConfdString
    MAX-ACCESS  read-only
    STATUS      current
    DESCRIPTION "Total 64K buffers in the pool"
    ::= { affirmedServicesContentHttpProxyServiceStatisticsChassisLevelBufferSummaryEntry 13 }

affirmedServicesContentHttpProxyServiceStatisticsChassisLevelBufferSummaryBuffer-128k-allocated OBJECT-TYPE
    SYNTAX      ConfdString
    MAX-ACCESS  read-only
    STATUS      current
    DESCRIPTION "Number of 128K buffers currently allocated"
    ::= { affirmedServicesContentHttpProxyServiceStatisticsChassisLevelBufferSummaryEntry 14 }

affirmedServicesContentHttpProxyServiceStatisticsChassisLevelBufferSummaryBuffer-128k-5min-peak OBJECT-TYPE
    SYNTAX      ConfdString
    MAX-ACCESS  read-only
    STATUS      current
    DESCRIPTION "Max number of 128K buffers allocated in last 5 minutes"
    ::= { affirmedServicesContentHttpProxyServiceStatisticsChassisLevelBufferSummaryEntry 15 }

affirmedServicesContentHttpProxyServiceStatisticsChassisLevelBufferSummaryBuffer-128k-total OBJECT-TYPE
    SYNTAX      ConfdString
    MAX-ACCESS  read-only
    STATUS      current
    DESCRIPTION "Total 128K buffers in the pool"
    ::= { affirmedServicesContentHttpProxyServiceStatisticsChassisLevelBufferSummaryEntry 16 }

affirmedServicesContentHttpProxyServiceStatisticsChassisLevelBufferSummaryBuffer-256k-allocated OBJECT-TYPE
    SYNTAX      ConfdString
    MAX-ACCESS  read-only
    STATUS      current
    DESCRIPTION "Number of 256K buffers currently allocated"
    ::= { affirmedServicesContentHttpProxyServiceStatisticsChassisLevelBufferSummaryEntry 17 }

affirmedServicesContentHttpProxyServiceStatisticsChassisLevelBufferSummaryBuffer-256k-5min-peak OBJECT-TYPE
    SYNTAX      ConfdString
    MAX-ACCESS  read-only
    STATUS      current
    DESCRIPTION "Max number of 256K buffers allocated in last 5 minutes"
    ::= { affirmedServicesContentHttpProxyServiceStatisticsChassisLevelBufferSummaryEntry 18 }

affirmedServicesContentHttpProxyServiceStatisticsChassisLevelBufferSummaryBuffer-256k-total OBJECT-TYPE
    SYNTAX      ConfdString
    MAX-ACCESS  read-only
    STATUS      current
    DESCRIPTION "Total 256K buffers in the pool"
    ::= { affirmedServicesContentHttpProxyServiceStatisticsChassisLevelBufferSummaryEntry 19 }

affirmedServicesContentHttpProxyServiceStatisticsChassisLevelBufferSummaryBuffer-512k-allocated OBJECT-TYPE
    SYNTAX      ConfdString
    MAX-ACCESS  read-only
    STATUS      current
    DESCRIPTION "Number of 512K buffers currently allocated"
    ::= { affirmedServicesContentHttpProxyServiceStatisticsChassisLevelBufferSummaryEntry 20 }

affirmedServicesContentHttpProxyServiceStatisticsChassisLevelBufferSummaryBuffer-512k-5min-peak OBJECT-TYPE
    SYNTAX      ConfdString
    MAX-ACCESS  read-only
    STATUS      current
    DESCRIPTION "Max number of 512K buffers allocated in last 5 minutes"
    ::= { affirmedServicesContentHttpProxyServiceStatisticsChassisLevelBufferSummaryEntry 21 }

affirmedServicesContentHttpProxyServiceStatisticsChassisLevelBufferSummaryBuffer-512k-total OBJECT-TYPE
    SYNTAX      ConfdString
    MAX-ACCESS  read-only
    STATUS      current
    DESCRIPTION "Total 512K buffers in the pool"
    ::= { affirmedServicesContentHttpProxyServiceStatisticsChassisLevelBufferSummaryEntry 22 }

affirmedServicesContentHttpProxyServiceStatisticsChassisLevelBufferSummaryBuffer-2k-allocated OBJECT-TYPE
    SYNTAX      ConfdString
    MAX-ACCESS  read-only
    STATUS      current
    DESCRIPTION "Number of 2K buffers currently allocated"
    ::= { affirmedServicesContentHttpProxyServiceStatisticsChassisLevelBufferSummaryEntry 23 }

affirmedServicesContentHttpProxyServiceStatisticsChassisLevelBufferSummaryBuffer-2k-5min-peak OBJECT-TYPE
    SYNTAX      ConfdString
    MAX-ACCESS  read-only
    STATUS      current
    DESCRIPTION "Max number of 2K buffers allocated in last 5 minutes"
    ::= { affirmedServicesContentHttpProxyServiceStatisticsChassisLevelBufferSummaryEntry 24 }

affirmedServicesContentHttpProxyServiceStatisticsChassisLevelBufferSummaryBuffer-2k-total OBJECT-TYPE
    SYNTAX      ConfdString
    MAX-ACCESS  read-only
    STATUS      current
    DESCRIPTION "Total 2K buffers in the pool"
    ::= { affirmedServicesContentHttpProxyServiceStatisticsChassisLevelBufferSummaryEntry 25 }

affirmedServicesContentHttpProxyServiceStatisticsChassisLevelTcpMeasurementMeasurementTable OBJECT-TYPE
    SYNTAX      SEQUENCE OF AffirmedServicesContentHttpProxyServiceStatisticsChassisLevelTcpMeasurementMeasurementEntry
    MAX-ACCESS  not-accessible
    STATUS      current
    DESCRIPTION ""
    ::= { affirmedServicesContentHttpProxyServiceStatisticsChassisLevelTcpMeasurement 1 }

affirmedServicesContentHttpProxyServiceStatisticsChassisLevelTcpMeasurementMeasurementEntry OBJECT-TYPE
    SYNTAX      AffirmedServicesContentHttpProxyServiceStatisticsChassisLevelTcpMeasurementMeasurementEntry
    MAX-ACCESS  not-accessible
    STATUS      current
    DESCRIPTION ""
    INDEX { affirmedServicesContentHttpProxyServiceStatisticsChassisLevelTcpMeasurementMeasurementChassis }
        ::= { affirmedServicesContentHttpProxyServiceStatisticsChassisLevelTcpMeasurementMeasurementTable 1 }

AffirmedServicesContentHttpProxyServiceStatisticsChassisLevelTcpMeasurementMeasurementEntry ::=
    SEQUENCE {
        affirmedServicesContentHttpProxyServiceStatisticsChassisLevelTcpMeasurementMeasurementChassis Unsigned32,
        affirmedServicesContentHttpProxyServiceStatisticsChassisLevelTcpMeasurementMeasurementMinrtt ConfdString,
        affirmedServicesContentHttpProxyServiceStatisticsChassisLevelTcpMeasurementMeasurementAvgrtt ConfdString,
        affirmedServicesContentHttpProxyServiceStatisticsChassisLevelTcpMeasurementMeasurementMaxrtt ConfdString,
        affirmedServicesContentHttpProxyServiceStatisticsChassisLevelTcpMeasurementMeasurementMinmssdl ConfdString,
        affirmedServicesContentHttpProxyServiceStatisticsChassisLevelTcpMeasurementMeasurementAvgmssdl ConfdString,
        affirmedServicesContentHttpProxyServiceStatisticsChassisLevelTcpMeasurementMeasurementMaxmssdl ConfdString,
        affirmedServicesContentHttpProxyServiceStatisticsChassisLevelTcpMeasurementMeasurementMincwnddl ConfdString,
        affirmedServicesContentHttpProxyServiceStatisticsChassisLevelTcpMeasurementMeasurementAvgcwnddl ConfdString,
        affirmedServicesContentHttpProxyServiceStatisticsChassisLevelTcpMeasurementMeasurementMaxcwnddl ConfdString,
        affirmedServicesContentHttpProxyServiceStatisticsChassisLevelTcpMeasurementMeasurementMinthroughputdl ConfdString,
        affirmedServicesContentHttpProxyServiceStatisticsChassisLevelTcpMeasurementMeasurementAvgthroughputdl ConfdString,
        affirmedServicesContentHttpProxyServiceStatisticsChassisLevelTcpMeasurementMeasurementMaxthroughputdl ConfdString,
        affirmedServicesContentHttpProxyServiceStatisticsChassisLevelTcpMeasurementMeasurementNumtotalsegmentslostdl ConfdString,
        affirmedServicesContentHttpProxyServiceStatisticsChassisLevelTcpMeasurementMeasurementNumtotalsegmentsretransdl ConfdString,
        affirmedServicesContentHttpProxyServiceStatisticsChassisLevelTcpMeasurementMeasurementNumtotalestimatedsegmentsdl ConfdString
    }

affirmedServicesContentHttpProxyServiceStatisticsChassisLevelTcpMeasurementMeasurementChassis OBJECT-TYPE
    SYNTAX      Unsigned32
    MAX-ACCESS  not-accessible
    STATUS      current
    DESCRIPTION "chassis ID"
    ::= { affirmedServicesContentHttpProxyServiceStatisticsChassisLevelTcpMeasurementMeasurementEntry 1 }

affirmedServicesContentHttpProxyServiceStatisticsChassisLevelTcpMeasurementMeasurementMinrtt OBJECT-TYPE
    SYNTAX      ConfdString
    MAX-ACCESS  read-only
    STATUS      current
    DESCRIPTION "Minimum RTT(us)"
    ::= { affirmedServicesContentHttpProxyServiceStatisticsChassisLevelTcpMeasurementMeasurementEntry 2 }

affirmedServicesContentHttpProxyServiceStatisticsChassisLevelTcpMeasurementMeasurementAvgrtt OBJECT-TYPE
    SYNTAX      ConfdString
    MAX-ACCESS  read-only
    STATUS      current
    DESCRIPTION "Average RTT(us) in Last 1 min"
    ::= { affirmedServicesContentHttpProxyServiceStatisticsChassisLevelTcpMeasurementMeasurementEntry 3 }

affirmedServicesContentHttpProxyServiceStatisticsChassisLevelTcpMeasurementMeasurementMaxrtt OBJECT-TYPE
    SYNTAX      ConfdString
    MAX-ACCESS  read-only
    STATUS      current
    DESCRIPTION "Maximum RTT(us)"
    ::= { affirmedServicesContentHttpProxyServiceStatisticsChassisLevelTcpMeasurementMeasurementEntry 4 }

affirmedServicesContentHttpProxyServiceStatisticsChassisLevelTcpMeasurementMeasurementMinmssdl OBJECT-TYPE
    SYNTAX      ConfdString
    MAX-ACCESS  read-only
    STATUS      current
    DESCRIPTION "Minimum Downstream MSS"
    ::= { affirmedServicesContentHttpProxyServiceStatisticsChassisLevelTcpMeasurementMeasurementEntry 5 }

affirmedServicesContentHttpProxyServiceStatisticsChassisLevelTcpMeasurementMeasurementAvgmssdl OBJECT-TYPE
    SYNTAX      ConfdString
    MAX-ACCESS  read-only
    STATUS      current
    DESCRIPTION "Average Downstream MSS"
    ::= { affirmedServicesContentHttpProxyServiceStatisticsChassisLevelTcpMeasurementMeasurementEntry 6 }

affirmedServicesContentHttpProxyServiceStatisticsChassisLevelTcpMeasurementMeasurementMaxmssdl OBJECT-TYPE
    SYNTAX      ConfdString
    MAX-ACCESS  read-only
    STATUS      current
    DESCRIPTION "Maximum Downstream MSS"
    ::= { affirmedServicesContentHttpProxyServiceStatisticsChassisLevelTcpMeasurementMeasurementEntry 7 }

affirmedServicesContentHttpProxyServiceStatisticsChassisLevelTcpMeasurementMeasurementMincwnddl OBJECT-TYPE
    SYNTAX      ConfdString
    MAX-ACCESS  read-only
    STATUS      current
    DESCRIPTION "Minimum Downstream CWND"
    ::= { affirmedServicesContentHttpProxyServiceStatisticsChassisLevelTcpMeasurementMeasurementEntry 8 }

affirmedServicesContentHttpProxyServiceStatisticsChassisLevelTcpMeasurementMeasurementAvgcwnddl OBJECT-TYPE
    SYNTAX      ConfdString
    MAX-ACCESS  read-only
    STATUS      current
    DESCRIPTION "Average Downstream CWND"
    ::= { affirmedServicesContentHttpProxyServiceStatisticsChassisLevelTcpMeasurementMeasurementEntry 9 }

affirmedServicesContentHttpProxyServiceStatisticsChassisLevelTcpMeasurementMeasurementMaxcwnddl OBJECT-TYPE
    SYNTAX      ConfdString
    MAX-ACCESS  read-only
    STATUS      current
    DESCRIPTION "Maximum Downstream CWND"
    ::= { affirmedServicesContentHttpProxyServiceStatisticsChassisLevelTcpMeasurementMeasurementEntry 10 }

affirmedServicesContentHttpProxyServiceStatisticsChassisLevelTcpMeasurementMeasurementMinthroughputdl OBJECT-TYPE
    SYNTAX      ConfdString
    MAX-ACCESS  read-only
    STATUS      current
    DESCRIPTION "Minimum Available Downstream Throughput of all Active Proxy Connections (Kbps)"
    ::= { affirmedServicesContentHttpProxyServiceStatisticsChassisLevelTcpMeasurementMeasurementEntry 11 }

affirmedServicesContentHttpProxyServiceStatisticsChassisLevelTcpMeasurementMeasurementAvgthroughputdl OBJECT-TYPE
    SYNTAX      ConfdString
    MAX-ACCESS  read-only
    STATUS      current
    DESCRIPTION "Average Available Downstream Throughput of all Active Proxy Connections (Kbps)"
    ::= { affirmedServicesContentHttpProxyServiceStatisticsChassisLevelTcpMeasurementMeasurementEntry 12 }

affirmedServicesContentHttpProxyServiceStatisticsChassisLevelTcpMeasurementMeasurementMaxthroughputdl OBJECT-TYPE
    SYNTAX      ConfdString
    MAX-ACCESS  read-only
    STATUS      current
    DESCRIPTION "Maximum Available Downstream Throughput of all Active Proxy Connections (Kbps)"
    ::= { affirmedServicesContentHttpProxyServiceStatisticsChassisLevelTcpMeasurementMeasurementEntry 13 }

affirmedServicesContentHttpProxyServiceStatisticsChassisLevelTcpMeasurementMeasurementNumtotalsegmentslostdl OBJECT-TYPE
    SYNTAX      ConfdString
    MAX-ACCESS  read-only
    STATUS      deprecated
    DESCRIPTION "Downstream Segments Lost"
    ::= { affirmedServicesContentHttpProxyServiceStatisticsChassisLevelTcpMeasurementMeasurementEntry 14 }

affirmedServicesContentHttpProxyServiceStatisticsChassisLevelTcpMeasurementMeasurementNumtotalsegmentsretransdl OBJECT-TYPE
    SYNTAX      ConfdString
    MAX-ACCESS  read-only
    STATUS      deprecated
    DESCRIPTION "Downstream Segments Retransmitted"
    ::= { affirmedServicesContentHttpProxyServiceStatisticsChassisLevelTcpMeasurementMeasurementEntry 15 }

affirmedServicesContentHttpProxyServiceStatisticsChassisLevelTcpMeasurementMeasurementNumtotalestimatedsegmentsdl OBJECT-TYPE
    SYNTAX      ConfdString
    MAX-ACCESS  read-only
    STATUS      deprecated
    DESCRIPTION "Estimated Downstream Segments"
    ::= { affirmedServicesContentHttpProxyServiceStatisticsChassisLevelTcpMeasurementMeasurementEntry 16 }

affirmedServicesContentHttpProxyServiceStatisticsChassisLevelTcpMeasurementsSummaryTable OBJECT-TYPE
    SYNTAX      SEQUENCE OF AffirmedServicesContentHttpProxyServiceStatisticsChassisLevelTcpMeasurementsSummaryEntry
    MAX-ACCESS  not-accessible
    STATUS      current
    DESCRIPTION ""
    ::= { affirmedServicesContentHttpProxyServiceStatisticsChassisLevelTcpMeasurements 1 }

affirmedServicesContentHttpProxyServiceStatisticsChassisLevelTcpMeasurementsSummaryEntry OBJECT-TYPE
    SYNTAX      AffirmedServicesContentHttpProxyServiceStatisticsChassisLevelTcpMeasurementsSummaryEntry
    MAX-ACCESS  not-accessible
    STATUS      current
    DESCRIPTION ""
    INDEX { affirmedServicesContentHttpProxyServiceStatisticsChassisLevelTcpMeasurementsSummaryChassis }
        ::= { affirmedServicesContentHttpProxyServiceStatisticsChassisLevelTcpMeasurementsSummaryTable 1 }

AffirmedServicesContentHttpProxyServiceStatisticsChassisLevelTcpMeasurementsSummaryEntry ::=
    SEQUENCE {
        affirmedServicesContentHttpProxyServiceStatisticsChassisLevelTcpMeasurementsSummaryChassis Unsigned32,
        affirmedServicesContentHttpProxyServiceStatisticsChassisLevelTcpMeasurementsSummaryMinrtt ConfdString,
        affirmedServicesContentHttpProxyServiceStatisticsChassisLevelTcpMeasurementsSummaryAvgrtt ConfdString,
        affirmedServicesContentHttpProxyServiceStatisticsChassisLevelTcpMeasurementsSummaryMaxrtt ConfdString,
        affirmedServicesContentHttpProxyServiceStatisticsChassisLevelTcpMeasurementsSummaryMinmssdl ConfdString,
        affirmedServicesContentHttpProxyServiceStatisticsChassisLevelTcpMeasurementsSummaryAvgmssdl ConfdString,
        affirmedServicesContentHttpProxyServiceStatisticsChassisLevelTcpMeasurementsSummaryMaxmssdl ConfdString,
        affirmedServicesContentHttpProxyServiceStatisticsChassisLevelTcpMeasurementsSummaryMincwnddl ConfdString,
        affirmedServicesContentHttpProxyServiceStatisticsChassisLevelTcpMeasurementsSummaryAvgcwnddl ConfdString,
        affirmedServicesContentHttpProxyServiceStatisticsChassisLevelTcpMeasurementsSummaryMaxcwnddl ConfdString,
        affirmedServicesContentHttpProxyServiceStatisticsChassisLevelTcpMeasurementsSummaryMinthroughputdl ConfdString,
        affirmedServicesContentHttpProxyServiceStatisticsChassisLevelTcpMeasurementsSummaryAvgthroughputdl ConfdString,
        affirmedServicesContentHttpProxyServiceStatisticsChassisLevelTcpMeasurementsSummaryMaxthroughputdl ConfdString,
        affirmedServicesContentHttpProxyServiceStatisticsChassisLevelTcpMeasurementsSummaryNumtotalsegmentslostdl ConfdString,
        affirmedServicesContentHttpProxyServiceStatisticsChassisLevelTcpMeasurementsSummaryNumtotalsegmentsretransdl ConfdString,
        affirmedServicesContentHttpProxyServiceStatisticsChassisLevelTcpMeasurementsSummaryNumtotalestimatedsegmentsdl ConfdString,
        affirmedServicesContentHttpProxyServiceStatisticsChassisLevelTcpMeasurementsSummaryNumtotalsegslostdl ConfdString,
        affirmedServicesContentHttpProxyServiceStatisticsChassisLevelTcpMeasurementsSummaryNumtotalsegsretransdl ConfdString,
        affirmedServicesContentHttpProxyServiceStatisticsChassisLevelTcpMeasurementsSummaryNumtotalestimatedsegsdl ConfdString,
        affirmedServicesContentHttpProxyServiceStatisticsChassisLevelTcpMeasurementsSummaryNumsessionscongestionmild ConfdString,
        affirmedServicesContentHttpProxyServiceStatisticsChassisLevelTcpMeasurementsSummaryNumsessionscongestionmoderate ConfdString,
        affirmedServicesContentHttpProxyServiceStatisticsChassisLevelTcpMeasurementsSummaryNumsessionscongestionsevere ConfdString,
        affirmedServicesContentHttpProxyServiceStatisticsChassisLevelTcpMeasurementsSummaryNumsessionstotal ConfdString
    }

affirmedServicesContentHttpProxyServiceStatisticsChassisLevelTcpMeasurementsSummaryChassis OBJECT-TYPE
    SYNTAX      Unsigned32
    MAX-ACCESS  not-accessible
    STATUS      current
    DESCRIPTION "chassis ID"
    ::= { affirmedServicesContentHttpProxyServiceStatisticsChassisLevelTcpMeasurementsSummaryEntry 1 }

affirmedServicesContentHttpProxyServiceStatisticsChassisLevelTcpMeasurementsSummaryMinrtt OBJECT-TYPE
    SYNTAX      ConfdString
    MAX-ACCESS  read-only
    STATUS      current
    DESCRIPTION "Minimum RTT(us)"
    ::= { affirmedServicesContentHttpProxyServiceStatisticsChassisLevelTcpMeasurementsSummaryEntry 2 }

affirmedServicesContentHttpProxyServiceStatisticsChassisLevelTcpMeasurementsSummaryAvgrtt OBJECT-TYPE
    SYNTAX      ConfdString
    MAX-ACCESS  read-only
    STATUS      current
    DESCRIPTION "Average RTT(us) in Last 1 min"
    ::= { affirmedServicesContentHttpProxyServiceStatisticsChassisLevelTcpMeasurementsSummaryEntry 3 }

affirmedServicesContentHttpProxyServiceStatisticsChassisLevelTcpMeasurementsSummaryMaxrtt OBJECT-TYPE
    SYNTAX      ConfdString
    MAX-ACCESS  read-only
    STATUS      current
    DESCRIPTION "Maximum RTT(us)"
    ::= { affirmedServicesContentHttpProxyServiceStatisticsChassisLevelTcpMeasurementsSummaryEntry 4 }

affirmedServicesContentHttpProxyServiceStatisticsChassisLevelTcpMeasurementsSummaryMinmssdl OBJECT-TYPE
    SYNTAX      ConfdString
    MAX-ACCESS  read-only
    STATUS      current
    DESCRIPTION "Minimum Downstream MSS"
    ::= { affirmedServicesContentHttpProxyServiceStatisticsChassisLevelTcpMeasurementsSummaryEntry 5 }

affirmedServicesContentHttpProxyServiceStatisticsChassisLevelTcpMeasurementsSummaryAvgmssdl OBJECT-TYPE
    SYNTAX      ConfdString
    MAX-ACCESS  read-only
    STATUS      current
    DESCRIPTION "Average Downstream MSS"
    ::= { affirmedServicesContentHttpProxyServiceStatisticsChassisLevelTcpMeasurementsSummaryEntry 6 }

affirmedServicesContentHttpProxyServiceStatisticsChassisLevelTcpMeasurementsSummaryMaxmssdl OBJECT-TYPE
    SYNTAX      ConfdString
    MAX-ACCESS  read-only
    STATUS      current
    DESCRIPTION "Maximum Downstream MSS"
    ::= { affirmedServicesContentHttpProxyServiceStatisticsChassisLevelTcpMeasurementsSummaryEntry 7 }

affirmedServicesContentHttpProxyServiceStatisticsChassisLevelTcpMeasurementsSummaryMincwnddl OBJECT-TYPE
    SYNTAX      ConfdString
    MAX-ACCESS  read-only
    STATUS      current
    DESCRIPTION "Minimum Downstream CWND"
    ::= { affirmedServicesContentHttpProxyServiceStatisticsChassisLevelTcpMeasurementsSummaryEntry 8 }

affirmedServicesContentHttpProxyServiceStatisticsChassisLevelTcpMeasurementsSummaryAvgcwnddl OBJECT-TYPE
    SYNTAX      ConfdString
    MAX-ACCESS  read-only
    STATUS      current
    DESCRIPTION "Average Downstream CWND"
    ::= { affirmedServicesContentHttpProxyServiceStatisticsChassisLevelTcpMeasurementsSummaryEntry 9 }

affirmedServicesContentHttpProxyServiceStatisticsChassisLevelTcpMeasurementsSummaryMaxcwnddl OBJECT-TYPE
    SYNTAX      ConfdString
    MAX-ACCESS  read-only
    STATUS      current
    DESCRIPTION "Maximum Downstream CWND"
    ::= { affirmedServicesContentHttpProxyServiceStatisticsChassisLevelTcpMeasurementsSummaryEntry 10 }

affirmedServicesContentHttpProxyServiceStatisticsChassisLevelTcpMeasurementsSummaryMinthroughputdl OBJECT-TYPE
    SYNTAX      ConfdString
    MAX-ACCESS  read-only
    STATUS      current
    DESCRIPTION "Minimum Available Downstream Throughput of all Active Proxy Connections (Kbps)"
    ::= { affirmedServicesContentHttpProxyServiceStatisticsChassisLevelTcpMeasurementsSummaryEntry 11 }

affirmedServicesContentHttpProxyServiceStatisticsChassisLevelTcpMeasurementsSummaryAvgthroughputdl OBJECT-TYPE
    SYNTAX      ConfdString
    MAX-ACCESS  read-only
    STATUS      current
    DESCRIPTION "Average Available Downstream Throughput of all Active Proxy Connections (Kbps)"
    ::= { affirmedServicesContentHttpProxyServiceStatisticsChassisLevelTcpMeasurementsSummaryEntry 12 }

affirmedServicesContentHttpProxyServiceStatisticsChassisLevelTcpMeasurementsSummaryMaxthroughputdl OBJECT-TYPE
    SYNTAX      ConfdString
    MAX-ACCESS  read-only
    STATUS      current
    DESCRIPTION "Maximum Available Downstream Throughput of all Active Proxy Connections (Kbps)"
    ::= { affirmedServicesContentHttpProxyServiceStatisticsChassisLevelTcpMeasurementsSummaryEntry 13 }

affirmedServicesContentHttpProxyServiceStatisticsChassisLevelTcpMeasurementsSummaryNumtotalsegmentslostdl OBJECT-TYPE
    SYNTAX      ConfdString
    MAX-ACCESS  read-only
    STATUS      deprecated
    DESCRIPTION "Downstream Segments Lost"
    ::= { affirmedServicesContentHttpProxyServiceStatisticsChassisLevelTcpMeasurementsSummaryEntry 14 }

affirmedServicesContentHttpProxyServiceStatisticsChassisLevelTcpMeasurementsSummaryNumtotalsegmentsretransdl OBJECT-TYPE
    SYNTAX      ConfdString
    MAX-ACCESS  read-only
    STATUS      deprecated
    DESCRIPTION "Downstream Segments Retransmitted"
    ::= { affirmedServicesContentHttpProxyServiceStatisticsChassisLevelTcpMeasurementsSummaryEntry 15 }

affirmedServicesContentHttpProxyServiceStatisticsChassisLevelTcpMeasurementsSummaryNumtotalestimatedsegmentsdl OBJECT-TYPE
    SYNTAX      ConfdString
    MAX-ACCESS  read-only
    STATUS      deprecated
    DESCRIPTION "Estimated Downstream Segments"
    ::= { affirmedServicesContentHttpProxyServiceStatisticsChassisLevelTcpMeasurementsSummaryEntry 16 }

affirmedServicesContentHttpProxyServiceStatisticsChassisLevelTcpMeasurementsSummaryNumtotalsegslostdl OBJECT-TYPE
    SYNTAX      ConfdString
    MAX-ACCESS  read-only
    STATUS      deprecated
    DESCRIPTION "Downstream Segments Lost"
    ::= { affirmedServicesContentHttpProxyServiceStatisticsChassisLevelTcpMeasurementsSummaryEntry 17 }

affirmedServicesContentHttpProxyServiceStatisticsChassisLevelTcpMeasurementsSummaryNumtotalsegsretransdl OBJECT-TYPE
    SYNTAX      ConfdString
    MAX-ACCESS  read-only
    STATUS      current
    DESCRIPTION "Downstream Segments Retransmitted"
    ::= { affirmedServicesContentHttpProxyServiceStatisticsChassisLevelTcpMeasurementsSummaryEntry 18 }

affirmedServicesContentHttpProxyServiceStatisticsChassisLevelTcpMeasurementsSummaryNumtotalestimatedsegsdl OBJECT-TYPE
    SYNTAX      ConfdString
    MAX-ACCESS  read-only
    STATUS      current
    DESCRIPTION "Estimated Downstream Segments"
    ::= { affirmedServicesContentHttpProxyServiceStatisticsChassisLevelTcpMeasurementsSummaryEntry 19 }

affirmedServicesContentHttpProxyServiceStatisticsChassisLevelTcpMeasurementsSummaryNumsessionscongestionmild OBJECT-TYPE
    SYNTAX      ConfdString
    MAX-ACCESS  read-only
    STATUS      current
    DESCRIPTION "Congested Sessions - Mild"
    ::= { affirmedServicesContentHttpProxyServiceStatisticsChassisLevelTcpMeasurementsSummaryEntry 20 }

affirmedServicesContentHttpProxyServiceStatisticsChassisLevelTcpMeasurementsSummaryNumsessionscongestionmoderate OBJECT-TYPE
    SYNTAX      ConfdString
    MAX-ACCESS  read-only
    STATUS      current
    DESCRIPTION "Congested Sessions - Moderate"
    ::= { affirmedServicesContentHttpProxyServiceStatisticsChassisLevelTcpMeasurementsSummaryEntry 21 }

affirmedServicesContentHttpProxyServiceStatisticsChassisLevelTcpMeasurementsSummaryNumsessionscongestionsevere OBJECT-TYPE
    SYNTAX      ConfdString
    MAX-ACCESS  read-only
    STATUS      current
    DESCRIPTION "Congested Sessions - Severe"
    ::= { affirmedServicesContentHttpProxyServiceStatisticsChassisLevelTcpMeasurementsSummaryEntry 22 }

affirmedServicesContentHttpProxyServiceStatisticsChassisLevelTcpMeasurementsSummaryNumsessionstotal OBJECT-TYPE
    SYNTAX      ConfdString
    MAX-ACCESS  read-only
    STATUS      current
    DESCRIPTION "Current Sessions"
    ::= { affirmedServicesContentHttpProxyServiceStatisticsChassisLevelTcpMeasurementsSummaryEntry 23 }

affirmedServicesContentHttpProxyServiceStatisticsChassisLevelTcpMeasurementsServer-sideTable OBJECT-TYPE
    SYNTAX      SEQUENCE OF AffirmedServicesContentHttpProxyServiceStatisticsChassisLevelTcpMeasurementsServer-sideEntry
    MAX-ACCESS  not-accessible
    STATUS      current
    DESCRIPTION ""
    ::= { affirmedServicesContentHttpProxyServiceStatisticsChassisLevelTcpMeasurements 2 }

affirmedServicesContentHttpProxyServiceStatisticsChassisLevelTcpMeasurementsServer-sideEntry OBJECT-TYPE
    SYNTAX      AffirmedServicesContentHttpProxyServiceStatisticsChassisLevelTcpMeasurementsServer-sideEntry
    MAX-ACCESS  not-accessible
    STATUS      current
    DESCRIPTION ""
    INDEX { affirmedServicesContentHttpProxyServiceStatisticsChassisLevelTcpMeasurementsServer-sideChassis }
        ::= { affirmedServicesContentHttpProxyServiceStatisticsChassisLevelTcpMeasurementsServer-sideTable 1 }

AffirmedServicesContentHttpProxyServiceStatisticsChassisLevelTcpMeasurementsServer-sideEntry ::=
    SEQUENCE {
        affirmedServicesContentHttpProxyServiceStatisticsChassisLevelTcpMeasurementsServer-sideChassis Unsigned32,
        affirmedServicesContentHttpProxyServiceStatisticsChassisLevelTcpMeasurementsServer-sideMinrtt ConfdString,
        affirmedServicesContentHttpProxyServiceStatisticsChassisLevelTcpMeasurementsServer-sideAvgrtt ConfdString,
        affirmedServicesContentHttpProxyServiceStatisticsChassisLevelTcpMeasurementsServer-sideMaxrtt ConfdString,
        affirmedServicesContentHttpProxyServiceStatisticsChassisLevelTcpMeasurementsServer-sideNumretransin ConfdString,
        affirmedServicesContentHttpProxyServiceStatisticsChassisLevelTcpMeasurementsServer-sideNumoooin ConfdString
    }

affirmedServicesContentHttpProxyServiceStatisticsChassisLevelTcpMeasurementsServer-sideChassis OBJECT-TYPE
    SYNTAX      Unsigned32
    MAX-ACCESS  not-accessible
    STATUS      current
    DESCRIPTION "chassis ID"
    ::= { affirmedServicesContentHttpProxyServiceStatisticsChassisLevelTcpMeasurementsServer-sideEntry 1 }

affirmedServicesContentHttpProxyServiceStatisticsChassisLevelTcpMeasurementsServer-sideMinrtt OBJECT-TYPE
    SYNTAX      ConfdString
    MAX-ACCESS  read-only
    STATUS      current
    DESCRIPTION "Minimum RTT(us)"
    ::= { affirmedServicesContentHttpProxyServiceStatisticsChassisLevelTcpMeasurementsServer-sideEntry 2 }

affirmedServicesContentHttpProxyServiceStatisticsChassisLevelTcpMeasurementsServer-sideAvgrtt OBJECT-TYPE
    SYNTAX      ConfdString
    MAX-ACCESS  read-only
    STATUS      current
    DESCRIPTION "Average RTT(us) in Last 1 min"
    ::= { affirmedServicesContentHttpProxyServiceStatisticsChassisLevelTcpMeasurementsServer-sideEntry 3 }

affirmedServicesContentHttpProxyServiceStatisticsChassisLevelTcpMeasurementsServer-sideMaxrtt OBJECT-TYPE
    SYNTAX      ConfdString
    MAX-ACCESS  read-only
    STATUS      current
    DESCRIPTION "Maximum RTT(us)"
    ::= { affirmedServicesContentHttpProxyServiceStatisticsChassisLevelTcpMeasurementsServer-sideEntry 4 }

affirmedServicesContentHttpProxyServiceStatisticsChassisLevelTcpMeasurementsServer-sideNumretransin OBJECT-TYPE
    SYNTAX      ConfdString
    MAX-ACCESS  read-only
    STATUS      current
    DESCRIPTION "Number of Packets Retransmitted"
    ::= { affirmedServicesContentHttpProxyServiceStatisticsChassisLevelTcpMeasurementsServer-sideEntry 5 }

affirmedServicesContentHttpProxyServiceStatisticsChassisLevelTcpMeasurementsServer-sideNumoooin OBJECT-TYPE
    SYNTAX      ConfdString
    MAX-ACCESS  read-only
    STATUS      current
    DESCRIPTION "Number of Packets Out of Order"
    ::= { affirmedServicesContentHttpProxyServiceStatisticsChassisLevelTcpMeasurementsServer-sideEntry 6 }

affirmedServicesContentHttpProxyServiceStatisticsChassisLevelTcpMeasurementsTacTable OBJECT-TYPE
    SYNTAX      SEQUENCE OF AffirmedServicesContentHttpProxyServiceStatisticsChassisLevelTcpMeasurementsTacEntry
    MAX-ACCESS  not-accessible
    STATUS      current
    DESCRIPTION ""
    ::= { affirmedServicesContentHttpProxyServiceStatisticsChassisLevelTcpMeasurements 3 }

affirmedServicesContentHttpProxyServiceStatisticsChassisLevelTcpMeasurementsTacEntry OBJECT-TYPE
    SYNTAX      AffirmedServicesContentHttpProxyServiceStatisticsChassisLevelTcpMeasurementsTacEntry
    MAX-ACCESS  not-accessible
    STATUS      current
    DESCRIPTION ""
    INDEX { affirmedServicesContentHttpProxyServiceStatisticsChassisLevelTcpMeasurementsTacTac, affirmedServicesContentHttpProxyServiceStatisticsChassisLevelTcpMeasurementsTacChassis }
        ::= { affirmedServicesContentHttpProxyServiceStatisticsChassisLevelTcpMeasurementsTacTable 1 }

AffirmedServicesContentHttpProxyServiceStatisticsChassisLevelTcpMeasurementsTacEntry ::=
    SEQUENCE {
        affirmedServicesContentHttpProxyServiceStatisticsChassisLevelTcpMeasurementsTacTac Unsigned32,
        affirmedServicesContentHttpProxyServiceStatisticsChassisLevelTcpMeasurementsTacChassis Unsigned32,
        affirmedServicesContentHttpProxyServiceStatisticsChassisLevelTcpMeasurementsTacNumsessionscongestionmild ConfdString,
        affirmedServicesContentHttpProxyServiceStatisticsChassisLevelTcpMeasurementsTacNumsessionscongestionmoderate ConfdString,
        affirmedServicesContentHttpProxyServiceStatisticsChassisLevelTcpMeasurementsTacNumsessionscongestionsevere ConfdString,
        affirmedServicesContentHttpProxyServiceStatisticsChassisLevelTcpMeasurementsTacNumsessionstotal ConfdString
    }

affirmedServicesContentHttpProxyServiceStatisticsChassisLevelTcpMeasurementsTacTac OBJECT-TYPE
    SYNTAX      Unsigned32
    MAX-ACCESS  not-accessible
    STATUS      current
    DESCRIPTION "high byte of TAC"
    ::= { affirmedServicesContentHttpProxyServiceStatisticsChassisLevelTcpMeasurementsTacEntry 1 }

affirmedServicesContentHttpProxyServiceStatisticsChassisLevelTcpMeasurementsTacChassis OBJECT-TYPE
    SYNTAX      Unsigned32
    MAX-ACCESS  not-accessible
    STATUS      current
    DESCRIPTION "chassis ID"
    ::= { affirmedServicesContentHttpProxyServiceStatisticsChassisLevelTcpMeasurementsTacEntry 2 }

affirmedServicesContentHttpProxyServiceStatisticsChassisLevelTcpMeasurementsTacNumsessionscongestionmild OBJECT-TYPE
    SYNTAX      ConfdString
    MAX-ACCESS  read-only
    STATUS      current
    DESCRIPTION "Congested Sessions - Mild"
    ::= { affirmedServicesContentHttpProxyServiceStatisticsChassisLevelTcpMeasurementsTacEntry 3 }

affirmedServicesContentHttpProxyServiceStatisticsChassisLevelTcpMeasurementsTacNumsessionscongestionmoderate OBJECT-TYPE
    SYNTAX      ConfdString
    MAX-ACCESS  read-only
    STATUS      current
    DESCRIPTION "Congested Sessions - Moderate"
    ::= { affirmedServicesContentHttpProxyServiceStatisticsChassisLevelTcpMeasurementsTacEntry 4 }

affirmedServicesContentHttpProxyServiceStatisticsChassisLevelTcpMeasurementsTacNumsessionscongestionsevere OBJECT-TYPE
    SYNTAX      ConfdString
    MAX-ACCESS  read-only
    STATUS      current
    DESCRIPTION "Congested Sessions - Severe"
    ::= { affirmedServicesContentHttpProxyServiceStatisticsChassisLevelTcpMeasurementsTacEntry 5 }

affirmedServicesContentHttpProxyServiceStatisticsChassisLevelTcpMeasurementsTacNumsessionstotal OBJECT-TYPE
    SYNTAX      ConfdString
    MAX-ACCESS  read-only
    STATUS      current
    DESCRIPTION "Current Sessions"
    ::= { affirmedServicesContentHttpProxyServiceStatisticsChassisLevelTcpMeasurementsTacEntry 6 }

affirmedServicesContentHttpProxyServiceStatisticsChassisLevelUdpProxySummaryTable OBJECT-TYPE
    SYNTAX      SEQUENCE OF AffirmedServicesContentHttpProxyServiceStatisticsChassisLevelUdpProxySummaryEntry
    MAX-ACCESS  not-accessible
    STATUS      current
    DESCRIPTION ""
    ::= { affirmedServicesContentHttpProxyServiceStatisticsChassisLevelUdpProxy 1 }

affirmedServicesContentHttpProxyServiceStatisticsChassisLevelUdpProxySummaryEntry OBJECT-TYPE
    SYNTAX      AffirmedServicesContentHttpProxyServiceStatisticsChassisLevelUdpProxySummaryEntry
    MAX-ACCESS  not-accessible
    STATUS      current
    DESCRIPTION ""
    INDEX { affirmedServicesContentHttpProxyServiceStatisticsChassisLevelUdpProxySummaryChassis }
        ::= { affirmedServicesContentHttpProxyServiceStatisticsChassisLevelUdpProxySummaryTable 1 }

AffirmedServicesContentHttpProxyServiceStatisticsChassisLevelUdpProxySummaryEntry ::=
    SEQUENCE {
        affirmedServicesContentHttpProxyServiceStatisticsChassisLevelUdpProxySummaryChassis Unsigned32,
        affirmedServicesContentHttpProxyServiceStatisticsChassisLevelUdpProxySummaryNumudpproxysummaryattempts ConfdString,
        affirmedServicesContentHttpProxyServiceStatisticsChassisLevelUdpProxySummaryNumudpproxysummarysuccesses ConfdString,
        affirmedServicesContentHttpProxyServiceStatisticsChassisLevelUdpProxySummaryNumudpproxysummaryaborts ConfdString,
        affirmedServicesContentHttpProxyServiceStatisticsChassisLevelUdpProxySummaryNumudpproxysummaryfailures ConfdString,
        affirmedServicesContentHttpProxyServiceStatisticsChassisLevelUdpProxySummaryNumudpproxydurationminseconds ConfdString,
        affirmedServicesContentHttpProxyServiceStatisticsChassisLevelUdpProxySummaryNumudpproxydurationmaxseconds ConfdString,
        affirmedServicesContentHttpProxyServiceStatisticsChassisLevelUdpProxySummaryNumudpproxydurationavgseconds ConfdString
    }

affirmedServicesContentHttpProxyServiceStatisticsChassisLevelUdpProxySummaryChassis OBJECT-TYPE
    SYNTAX      Unsigned32
    MAX-ACCESS  not-accessible
    STATUS      current
    DESCRIPTION "chassis ID"
    ::= { affirmedServicesContentHttpProxyServiceStatisticsChassisLevelUdpProxySummaryEntry 1 }

affirmedServicesContentHttpProxyServiceStatisticsChassisLevelUdpProxySummaryNumudpproxysummaryattempts OBJECT-TYPE
    SYNTAX      ConfdString
    MAX-ACCESS  read-only
    STATUS      current
    DESCRIPTION "Number of UDP Proxy summary attempts"
    ::= { affirmedServicesContentHttpProxyServiceStatisticsChassisLevelUdpProxySummaryEntry 2 }

affirmedServicesContentHttpProxyServiceStatisticsChassisLevelUdpProxySummaryNumudpproxysummarysuccesses OBJECT-TYPE
    SYNTAX      ConfdString
    MAX-ACCESS  read-only
    STATUS      current
    DESCRIPTION "Number of UDP Proxy summary successes"
    ::= { affirmedServicesContentHttpProxyServiceStatisticsChassisLevelUdpProxySummaryEntry 3 }

affirmedServicesContentHttpProxyServiceStatisticsChassisLevelUdpProxySummaryNumudpproxysummaryaborts OBJECT-TYPE
    SYNTAX      ConfdString
    MAX-ACCESS  read-only
    STATUS      current
    DESCRIPTION "Number of UDP Proxy summary aborts"
    ::= { affirmedServicesContentHttpProxyServiceStatisticsChassisLevelUdpProxySummaryEntry 4 }

affirmedServicesContentHttpProxyServiceStatisticsChassisLevelUdpProxySummaryNumudpproxysummaryfailures OBJECT-TYPE
    SYNTAX      ConfdString
    MAX-ACCESS  read-only
    STATUS      current
    DESCRIPTION "Number of UDP Proxy summary failures"
    ::= { affirmedServicesContentHttpProxyServiceStatisticsChassisLevelUdpProxySummaryEntry 5 }

affirmedServicesContentHttpProxyServiceStatisticsChassisLevelUdpProxySummaryNumudpproxydurationminseconds OBJECT-TYPE
    SYNTAX      ConfdString
    MAX-ACCESS  read-only
    STATUS      current
    DESCRIPTION "Number of Minimum UDP Proxy duration in milliseconds"
    ::= { affirmedServicesContentHttpProxyServiceStatisticsChassisLevelUdpProxySummaryEntry 6 }

affirmedServicesContentHttpProxyServiceStatisticsChassisLevelUdpProxySummaryNumudpproxydurationmaxseconds OBJECT-TYPE
    SYNTAX      ConfdString
    MAX-ACCESS  read-only
    STATUS      current
    DESCRIPTION "Number of Maximum UDP Proxy duration in milliseconds"
    ::= { affirmedServicesContentHttpProxyServiceStatisticsChassisLevelUdpProxySummaryEntry 7 }

affirmedServicesContentHttpProxyServiceStatisticsChassisLevelUdpProxySummaryNumudpproxydurationavgseconds OBJECT-TYPE
    SYNTAX      ConfdString
    MAX-ACCESS  read-only
    STATUS      current
    DESCRIPTION "Number of Average UDP Proxy duration in milliseconds"
    ::= { affirmedServicesContentHttpProxyServiceStatisticsChassisLevelUdpProxySummaryEntry 8 }

affirmedServicesContentHttpProxyServiceStatisticsChassisLevelUdpProxyDetailTable OBJECT-TYPE
    SYNTAX      SEQUENCE OF AffirmedServicesContentHttpProxyServiceStatisticsChassisLevelUdpProxyDetailEntry
    MAX-ACCESS  not-accessible
    STATUS      current
    DESCRIPTION ""
    ::= { affirmedServicesContentHttpProxyServiceStatisticsChassisLevelUdpProxy 2 }

affirmedServicesContentHttpProxyServiceStatisticsChassisLevelUdpProxyDetailEntry OBJECT-TYPE
    SYNTAX      AffirmedServicesContentHttpProxyServiceStatisticsChassisLevelUdpProxyDetailEntry
    MAX-ACCESS  not-accessible
    STATUS      current
    DESCRIPTION ""
    INDEX { affirmedServicesContentHttpProxyServiceStatisticsChassisLevelUdpProxyDetailChassis }
        ::= { affirmedServicesContentHttpProxyServiceStatisticsChassisLevelUdpProxyDetailTable 1 }

AffirmedServicesContentHttpProxyServiceStatisticsChassisLevelUdpProxyDetailEntry ::=
    SEQUENCE {
        affirmedServicesContentHttpProxyServiceStatisticsChassisLevelUdpProxyDetailChassis Unsigned32,
        affirmedServicesContentHttpProxyServiceStatisticsChassisLevelUdpProxyDetailNumudpproxypolicyevaluated ConfdString,
        affirmedServicesContentHttpProxyServiceStatisticsChassisLevelUdpProxyDetailNumudpproxypolicymatched ConfdString,
        affirmedServicesContentHttpProxyServiceStatisticsChassisLevelUdpProxyDetailNumudpproxypolicyignored ConfdString,
        affirmedServicesContentHttpProxyServiceStatisticsChassisLevelUdpProxyDetailNumudpproxypolicynotavailable ConfdString,
        affirmedServicesContentHttpProxyServiceStatisticsChassisLevelUdpProxyDetailNumudpproxyprofileactionallowed ConfdString,
        affirmedServicesContentHttpProxyServiceStatisticsChassisLevelUdpProxyDetailNumudpproxyprofilesteeredtoip ConfdString,
        affirmedServicesContentHttpProxyServiceStatisticsChassisLevelUdpProxyDetailNumudpproxyprofilesteeredtohost ConfdString,
        affirmedServicesContentHttpProxyServiceStatisticsChassisLevelUdpProxyDetailNumudpproxypolicyreevaluated ConfdString,
        affirmedServicesContentHttpProxyServiceStatisticsChassisLevelUdpProxyDetailNumudpproxypolicyrematched ConfdString,
        affirmedServicesContentHttpProxyServiceStatisticsChassisLevelUdpProxyDetailNumudpproxypolicynotavailablereeval ConfdString
    }

affirmedServicesContentHttpProxyServiceStatisticsChassisLevelUdpProxyDetailChassis OBJECT-TYPE
    SYNTAX      Unsigned32
    MAX-ACCESS  not-accessible
    STATUS      current
    DESCRIPTION "chassis ID"
    ::= { affirmedServicesContentHttpProxyServiceStatisticsChassisLevelUdpProxyDetailEntry 1 }

affirmedServicesContentHttpProxyServiceStatisticsChassisLevelUdpProxyDetailNumudpproxypolicyevaluated OBJECT-TYPE
    SYNTAX      ConfdString
    MAX-ACCESS  read-only
    STATUS      current
    DESCRIPTION "Number of UDP Proxy Policies evaluated"
    ::= { affirmedServicesContentHttpProxyServiceStatisticsChassisLevelUdpProxyDetailEntry 2 }

affirmedServicesContentHttpProxyServiceStatisticsChassisLevelUdpProxyDetailNumudpproxypolicymatched OBJECT-TYPE
    SYNTAX      ConfdString
    MAX-ACCESS  read-only
    STATUS      current
    DESCRIPTION "Number of UDP Proxy Policies Matched"
    ::= { affirmedServicesContentHttpProxyServiceStatisticsChassisLevelUdpProxyDetailEntry 3 }

affirmedServicesContentHttpProxyServiceStatisticsChassisLevelUdpProxyDetailNumudpproxypolicyignored OBJECT-TYPE
    SYNTAX      ConfdString
    MAX-ACCESS  read-only
    STATUS      current
    DESCRIPTION "Number of UDP Proxy Policies Ignored"
    ::= { affirmedServicesContentHttpProxyServiceStatisticsChassisLevelUdpProxyDetailEntry 4 }

affirmedServicesContentHttpProxyServiceStatisticsChassisLevelUdpProxyDetailNumudpproxypolicynotavailable OBJECT-TYPE
    SYNTAX      ConfdString
    MAX-ACCESS  read-only
    STATUS      current
    DESCRIPTION "Number of UDP Proxy Policies Not Available"
    ::= { affirmedServicesContentHttpProxyServiceStatisticsChassisLevelUdpProxyDetailEntry 5 }

affirmedServicesContentHttpProxyServiceStatisticsChassisLevelUdpProxyDetailNumudpproxyprofileactionallowed OBJECT-TYPE
    SYNTAX      ConfdString
    MAX-ACCESS  read-only
    STATUS      current
    DESCRIPTION "Number of Traffic Control Profile Action Allow Applied"
    ::= { affirmedServicesContentHttpProxyServiceStatisticsChassisLevelUdpProxyDetailEntry 6 }

affirmedServicesContentHttpProxyServiceStatisticsChassisLevelUdpProxyDetailNumudpproxyprofilesteeredtoip OBJECT-TYPE
    SYNTAX      ConfdString
    MAX-ACCESS  read-only
    STATUS      current
    DESCRIPTION "Number of tcp splicing profile steering-destination IP applied"
    ::= { affirmedServicesContentHttpProxyServiceStatisticsChassisLevelUdpProxyDetailEntry 7 }

affirmedServicesContentHttpProxyServiceStatisticsChassisLevelUdpProxyDetailNumudpproxyprofilesteeredtohost OBJECT-TYPE
    SYNTAX      ConfdString
    MAX-ACCESS  read-only
    STATUS      current
    DESCRIPTION "Number of tcp splicing profile steering-destination host applied"
    ::= { affirmedServicesContentHttpProxyServiceStatisticsChassisLevelUdpProxyDetailEntry 8 }

affirmedServicesContentHttpProxyServiceStatisticsChassisLevelUdpProxyDetailNumudpproxypolicyreevaluated OBJECT-TYPE
    SYNTAX      ConfdString
    MAX-ACCESS  read-only
    STATUS      current
    DESCRIPTION "Policy - Re-evaluations"
    ::= { affirmedServicesContentHttpProxyServiceStatisticsChassisLevelUdpProxyDetailEntry 9 }

affirmedServicesContentHttpProxyServiceStatisticsChassisLevelUdpProxyDetailNumudpproxypolicyrematched OBJECT-TYPE
    SYNTAX      ConfdString
    MAX-ACCESS  read-only
    STATUS      current
    DESCRIPTION "Policy - Matches after Re-evaluation"
    ::= { affirmedServicesContentHttpProxyServiceStatisticsChassisLevelUdpProxyDetailEntry 10 }

affirmedServicesContentHttpProxyServiceStatisticsChassisLevelUdpProxyDetailNumudpproxypolicynotavailablereeval OBJECT-TYPE
    SYNTAX      ConfdString
    MAX-ACCESS  read-only
    STATUS      current
    DESCRIPTION "Policy - No Policy Available after Re-evaluation"
    ::= { affirmedServicesContentHttpProxyServiceStatisticsChassisLevelUdpProxyDetailEntry 11 }

affirmedServicesContentHttpProxyServiceStatisticsChassisLevelUdpProxyFailureTable OBJECT-TYPE
    SYNTAX      SEQUENCE OF AffirmedServicesContentHttpProxyServiceStatisticsChassisLevelUdpProxyFailureEntry
    MAX-ACCESS  not-accessible
    STATUS      current
    DESCRIPTION ""
    ::= { affirmedServicesContentHttpProxyServiceStatisticsChassisLevelUdpProxy 3 }

affirmedServicesContentHttpProxyServiceStatisticsChassisLevelUdpProxyFailureEntry OBJECT-TYPE
    SYNTAX      AffirmedServicesContentHttpProxyServiceStatisticsChassisLevelUdpProxyFailureEntry
    MAX-ACCESS  not-accessible
    STATUS      current
    DESCRIPTION ""
    INDEX { affirmedServicesContentHttpProxyServiceStatisticsChassisLevelUdpProxyFailureChassis }
        ::= { affirmedServicesContentHttpProxyServiceStatisticsChassisLevelUdpProxyFailureTable 1 }

AffirmedServicesContentHttpProxyServiceStatisticsChassisLevelUdpProxyFailureEntry ::=
    SEQUENCE {
        affirmedServicesContentHttpProxyServiceStatisticsChassisLevelUdpProxyFailureChassis Unsigned32,
        affirmedServicesContentHttpProxyServiceStatisticsChassisLevelUdpProxyFailureNumudpproxyabortsclientsocketerror ConfdString,
        affirmedServicesContentHttpProxyServiceStatisticsChassisLevelUdpProxyFailureNumudpproxyabortsserversocketerror ConfdString,
        affirmedServicesContentHttpProxyServiceStatisticsChassisLevelUdpProxyFailureNumudpproxyfailuresserverconnectioninitfailure ConfdString,
        affirmedServicesContentHttpProxyServiceStatisticsChassisLevelUdpProxyFailureNumudpproxyfailuresoutofsocket ConfdString,
        affirmedServicesContentHttpProxyServiceStatisticsChassisLevelUdpProxyFailureNumudpproxyabortsnoresponsefromserver ConfdString
    }

affirmedServicesContentHttpProxyServiceStatisticsChassisLevelUdpProxyFailureChassis OBJECT-TYPE
    SYNTAX      Unsigned32
    MAX-ACCESS  not-accessible
    STATUS      current
    DESCRIPTION "chassis ID"
    ::= { affirmedServicesContentHttpProxyServiceStatisticsChassisLevelUdpProxyFailureEntry 1 }

affirmedServicesContentHttpProxyServiceStatisticsChassisLevelUdpProxyFailureNumudpproxyabortsclientsocketerror OBJECT-TYPE
    SYNTAX      ConfdString
    MAX-ACCESS  read-only
    STATUS      current
    DESCRIPTION "Number of UDP Proxy Aborts Client Socket Error"
    ::= { affirmedServicesContentHttpProxyServiceStatisticsChassisLevelUdpProxyFailureEntry 2 }

affirmedServicesContentHttpProxyServiceStatisticsChassisLevelUdpProxyFailureNumudpproxyabortsserversocketerror OBJECT-TYPE
    SYNTAX      ConfdString
    MAX-ACCESS  read-only
    STATUS      current
    DESCRIPTION "Number of UDP Proxy Aborts Server Socket Error"
    ::= { affirmedServicesContentHttpProxyServiceStatisticsChassisLevelUdpProxyFailureEntry 3 }

affirmedServicesContentHttpProxyServiceStatisticsChassisLevelUdpProxyFailureNumudpproxyfailuresserverconnectioninitfailure OBJECT-TYPE
    SYNTAX      ConfdString
    MAX-ACCESS  read-only
    STATUS      current
    DESCRIPTION "Number of UDP Proxy Failures Server Connection Init Failure"
    ::= { affirmedServicesContentHttpProxyServiceStatisticsChassisLevelUdpProxyFailureEntry 4 }

affirmedServicesContentHttpProxyServiceStatisticsChassisLevelUdpProxyFailureNumudpproxyfailuresoutofsocket OBJECT-TYPE
    SYNTAX      ConfdString
    MAX-ACCESS  read-only
    STATUS      current
    DESCRIPTION "Number of UDP Proxy Failures Out of Socket"
    ::= { affirmedServicesContentHttpProxyServiceStatisticsChassisLevelUdpProxyFailureEntry 5 }

affirmedServicesContentHttpProxyServiceStatisticsChassisLevelUdpProxyFailureNumudpproxyabortsnoresponsefromserver OBJECT-TYPE
    SYNTAX      ConfdString
    MAX-ACCESS  read-only
    STATUS      current
    DESCRIPTION "Number of UDP Proxy Aborts No Response From Server"
    ::= { affirmedServicesContentHttpProxyServiceStatisticsChassisLevelUdpProxyFailureEntry 6 }

affirmedServicesContentHttpProxyServiceStatisticsChassisLevelUdpProxyConnectionTable OBJECT-TYPE
    SYNTAX      SEQUENCE OF AffirmedServicesContentHttpProxyServiceStatisticsChassisLevelUdpProxyConnectionEntry
    MAX-ACCESS  not-accessible
    STATUS      current
    DESCRIPTION ""
    ::= { affirmedServicesContentHttpProxyServiceStatisticsChassisLevelUdpProxy 4 }

affirmedServicesContentHttpProxyServiceStatisticsChassisLevelUdpProxyConnectionEntry OBJECT-TYPE
    SYNTAX      AffirmedServicesContentHttpProxyServiceStatisticsChassisLevelUdpProxyConnectionEntry
    MAX-ACCESS  not-accessible
    STATUS      current
    DESCRIPTION ""
    INDEX { affirmedServicesContentHttpProxyServiceStatisticsChassisLevelUdpProxyConnectionChassis }
        ::= { affirmedServicesContentHttpProxyServiceStatisticsChassisLevelUdpProxyConnectionTable 1 }

AffirmedServicesContentHttpProxyServiceStatisticsChassisLevelUdpProxyConnectionEntry ::=
    SEQUENCE {
        affirmedServicesContentHttpProxyServiceStatisticsChassisLevelUdpProxyConnectionChassis Unsigned32,
        affirmedServicesContentHttpProxyServiceStatisticsChassisLevelUdpProxyConnectionNumudpproxyclientconnectionstotal ConfdString,
        affirmedServicesContentHttpProxyServiceStatisticsChassisLevelUdpProxyConnectionNumudpproxyclientconnectionscurrentlyinuse ConfdString,
        affirmedServicesContentHttpProxyServiceStatisticsChassisLevelUdpProxyConnectionNumudpproxyclientconnectionsipv4 ConfdString,
        affirmedServicesContentHttpProxyServiceStatisticsChassisLevelUdpProxyConnectionNumudpproxyclientconnectionsipv6 ConfdString,
        affirmedServicesContentHttpProxyServiceStatisticsChassisLevelUdpProxyConnectionNumudpproxyclientconnectionsbytesreceived ConfdString,
        affirmedServicesContentHttpProxyServiceStatisticsChassisLevelUdpProxyConnectionNumudpproxyclientconnectionsbytessent ConfdString,
        affirmedServicesContentHttpProxyServiceStatisticsChassisLevelUdpProxyConnectionNumudpproxyclientconnectionspacketsreceived ConfdString,
        affirmedServicesContentHttpProxyServiceStatisticsChassisLevelUdpProxyConnectionNumudpproxyclientconnectionspacketssent ConfdString,
        affirmedServicesContentHttpProxyServiceStatisticsChassisLevelUdpProxyConnectionNumudpproxyserverconnectionstotal ConfdString,
        affirmedServicesContentHttpProxyServiceStatisticsChassisLevelUdpProxyConnectionNumudpproxyserverconnectionscurrentlyinuse ConfdString,
        affirmedServicesContentHttpProxyServiceStatisticsChassisLevelUdpProxyConnectionNumudpproxyserverconnectionsipv4 ConfdString,
        affirmedServicesContentHttpProxyServiceStatisticsChassisLevelUdpProxyConnectionNumudpproxyserverconnectionsipv6 ConfdString,
        affirmedServicesContentHttpProxyServiceStatisticsChassisLevelUdpProxyConnectionNumudpproxyserverconnectionsiptransparent ConfdString,
        affirmedServicesContentHttpProxyServiceStatisticsChassisLevelUdpProxyConnectionNumudpproxyserverconnectionsbytesreceived ConfdString,
        affirmedServicesContentHttpProxyServiceStatisticsChassisLevelUdpProxyConnectionNumudpproxyserverconnectionsbytessent ConfdString,
        affirmedServicesContentHttpProxyServiceStatisticsChassisLevelUdpProxyConnectionNumudpproxyserverconnectionspacketsreceived ConfdString,
        affirmedServicesContentHttpProxyServiceStatisticsChassisLevelUdpProxyConnectionNumudpproxyserverconnectionspacketssent ConfdString,
        affirmedServicesContentHttpProxyServiceStatisticsChassisLevelUdpProxyConnectionNumudpproxydpiupdates ConfdString,
        affirmedServicesContentHttpProxyServiceStatisticsChassisLevelUdpProxyConnectionNumudpproxydpiupdatefailures ConfdString
    }

affirmedServicesContentHttpProxyServiceStatisticsChassisLevelUdpProxyConnectionChassis OBJECT-TYPE
    SYNTAX      Unsigned32
    MAX-ACCESS  not-accessible
    STATUS      current
    DESCRIPTION "chassis ID"
    ::= { affirmedServicesContentHttpProxyServiceStatisticsChassisLevelUdpProxyConnectionEntry 1 }

affirmedServicesContentHttpProxyServiceStatisticsChassisLevelUdpProxyConnectionNumudpproxyclientconnectionstotal OBJECT-TYPE
    SYNTAX      ConfdString
    MAX-ACCESS  read-only
    STATUS      current
    DESCRIPTION "Number of Total UDP Proxy Client Connections"
    ::= { affirmedServicesContentHttpProxyServiceStatisticsChassisLevelUdpProxyConnectionEntry 2 }

affirmedServicesContentHttpProxyServiceStatisticsChassisLevelUdpProxyConnectionNumudpproxyclientconnectionscurrentlyinuse OBJECT-TYPE
    SYNTAX      ConfdString
    MAX-ACCESS  read-only
    STATUS      current
    DESCRIPTION "Number of UDP Proxy Client Connections Currently In Use"
    ::= { affirmedServicesContentHttpProxyServiceStatisticsChassisLevelUdpProxyConnectionEntry 3 }

affirmedServicesContentHttpProxyServiceStatisticsChassisLevelUdpProxyConnectionNumudpproxyclientconnectionsipv4 OBJECT-TYPE
    SYNTAX      ConfdString
    MAX-ACCESS  read-only
    STATUS      current
    DESCRIPTION "Number of UDP Proxy Client Connections - IPv4"
    ::= { affirmedServicesContentHttpProxyServiceStatisticsChassisLevelUdpProxyConnectionEntry 4 }

affirmedServicesContentHttpProxyServiceStatisticsChassisLevelUdpProxyConnectionNumudpproxyclientconnectionsipv6 OBJECT-TYPE
    SYNTAX      ConfdString
    MAX-ACCESS  read-only
    STATUS      current
    DESCRIPTION "Number of UDP Proxy Client Connections - IPv6"
    ::= { affirmedServicesContentHttpProxyServiceStatisticsChassisLevelUdpProxyConnectionEntry 5 }

affirmedServicesContentHttpProxyServiceStatisticsChassisLevelUdpProxyConnectionNumudpproxyclientconnectionsbytesreceived OBJECT-TYPE
    SYNTAX      ConfdString
    MAX-ACCESS  read-only
    STATUS      current
    DESCRIPTION "UDP Proxy Client Connections - Number of Bytes Received"
    ::= { affirmedServicesContentHttpProxyServiceStatisticsChassisLevelUdpProxyConnectionEntry 6 }

affirmedServicesContentHttpProxyServiceStatisticsChassisLevelUdpProxyConnectionNumudpproxyclientconnectionsbytessent OBJECT-TYPE
    SYNTAX      ConfdString
    MAX-ACCESS  read-only
    STATUS      current
    DESCRIPTION "UDP Proxy Client Connections - Number of Bytes Sent"
    ::= { affirmedServicesContentHttpProxyServiceStatisticsChassisLevelUdpProxyConnectionEntry 7 }

affirmedServicesContentHttpProxyServiceStatisticsChassisLevelUdpProxyConnectionNumudpproxyclientconnectionspacketsreceived OBJECT-TYPE
    SYNTAX      ConfdString
    MAX-ACCESS  read-only
    STATUS      current
    DESCRIPTION "UDP Proxy Client Connections - Number of Packets Received"
    ::= { affirmedServicesContentHttpProxyServiceStatisticsChassisLevelUdpProxyConnectionEntry 8 }

affirmedServicesContentHttpProxyServiceStatisticsChassisLevelUdpProxyConnectionNumudpproxyclientconnectionspacketssent OBJECT-TYPE
    SYNTAX      ConfdString
    MAX-ACCESS  read-only
    STATUS      current
    DESCRIPTION "UDP Proxy Client Connections - Number of Packets Sent"
    ::= { affirmedServicesContentHttpProxyServiceStatisticsChassisLevelUdpProxyConnectionEntry 9 }

affirmedServicesContentHttpProxyServiceStatisticsChassisLevelUdpProxyConnectionNumudpproxyserverconnectionstotal OBJECT-TYPE
    SYNTAX      ConfdString
    MAX-ACCESS  read-only
    STATUS      current
    DESCRIPTION "Number of Total UDP Proxy Server Connections"
    ::= { affirmedServicesContentHttpProxyServiceStatisticsChassisLevelUdpProxyConnectionEntry 10 }

affirmedServicesContentHttpProxyServiceStatisticsChassisLevelUdpProxyConnectionNumudpproxyserverconnectionscurrentlyinuse OBJECT-TYPE
    SYNTAX      ConfdString
    MAX-ACCESS  read-only
    STATUS      current
    DESCRIPTION "Number of UDP Proxy Server Connections Currently In Use"
    ::= { affirmedServicesContentHttpProxyServiceStatisticsChassisLevelUdpProxyConnectionEntry 11 }

affirmedServicesContentHttpProxyServiceStatisticsChassisLevelUdpProxyConnectionNumudpproxyserverconnectionsipv4 OBJECT-TYPE
    SYNTAX      ConfdString
    MAX-ACCESS  read-only
    STATUS      current
    DESCRIPTION "Number of UDP Proxy Server Connections - IPv4"
    ::= { affirmedServicesContentHttpProxyServiceStatisticsChassisLevelUdpProxyConnectionEntry 12 }

affirmedServicesContentHttpProxyServiceStatisticsChassisLevelUdpProxyConnectionNumudpproxyserverconnectionsipv6 OBJECT-TYPE
    SYNTAX      ConfdString
    MAX-ACCESS  read-only
    STATUS      current
    DESCRIPTION "Number of UDP Proxy Server Connections - IPv6"
    ::= { affirmedServicesContentHttpProxyServiceStatisticsChassisLevelUdpProxyConnectionEntry 13 }

affirmedServicesContentHttpProxyServiceStatisticsChassisLevelUdpProxyConnectionNumudpproxyserverconnectionsiptransparent OBJECT-TYPE
    SYNTAX      ConfdString
    MAX-ACCESS  read-only
    STATUS      current
    DESCRIPTION "UDP Proxy Server Connections - Number of IP Transparent Flows"
    ::= { affirmedServicesContentHttpProxyServiceStatisticsChassisLevelUdpProxyConnectionEntry 14 }

affirmedServicesContentHttpProxyServiceStatisticsChassisLevelUdpProxyConnectionNumudpproxyserverconnectionsbytesreceived OBJECT-TYPE
    SYNTAX      ConfdString
    MAX-ACCESS  read-only
    STATUS      current
    DESCRIPTION "UDP Proxy Server Connections - Number of Bytes Received"
    ::= { affirmedServicesContentHttpProxyServiceStatisticsChassisLevelUdpProxyConnectionEntry 15 }

affirmedServicesContentHttpProxyServiceStatisticsChassisLevelUdpProxyConnectionNumudpproxyserverconnectionsbytessent OBJECT-TYPE
    SYNTAX      ConfdString
    MAX-ACCESS  read-only
    STATUS      current
    DESCRIPTION "UDP Proxy Server Connections - Number of Bytes Sent"
    ::= { affirmedServicesContentHttpProxyServiceStatisticsChassisLevelUdpProxyConnectionEntry 16 }

affirmedServicesContentHttpProxyServiceStatisticsChassisLevelUdpProxyConnectionNumudpproxyserverconnectionspacketsreceived OBJECT-TYPE
    SYNTAX      ConfdString
    MAX-ACCESS  read-only
    STATUS      current
    DESCRIPTION "UDP Proxy Server Connections - Number of Packets Received"
    ::= { affirmedServicesContentHttpProxyServiceStatisticsChassisLevelUdpProxyConnectionEntry 17 }

affirmedServicesContentHttpProxyServiceStatisticsChassisLevelUdpProxyConnectionNumudpproxyserverconnectionspacketssent OBJECT-TYPE
    SYNTAX      ConfdString
    MAX-ACCESS  read-only
    STATUS      current
    DESCRIPTION "UDP Proxy Server Connections - Number of Packets Sent"
    ::= { affirmedServicesContentHttpProxyServiceStatisticsChassisLevelUdpProxyConnectionEntry 18 }

affirmedServicesContentHttpProxyServiceStatisticsChassisLevelUdpProxyConnectionNumudpproxydpiupdates OBJECT-TYPE
    SYNTAX      ConfdString
    MAX-ACCESS  read-only
    STATUS      current
    DESCRIPTION "Total Number of UDP Proxy DPI Updates"
    ::= { affirmedServicesContentHttpProxyServiceStatisticsChassisLevelUdpProxyConnectionEntry 19 }

affirmedServicesContentHttpProxyServiceStatisticsChassisLevelUdpProxyConnectionNumudpproxydpiupdatefailures OBJECT-TYPE
    SYNTAX      ConfdString
    MAX-ACCESS  read-only
    STATUS      current
    DESCRIPTION "Total Number of UDP Proxy DPI Update Failures"
    ::= { affirmedServicesContentHttpProxyServiceStatisticsChassisLevelUdpProxyConnectionEntry 20 }

affirmedServicesContentHttpProxyServiceStatisticsChassisLevelUdpProxyQuicTable OBJECT-TYPE
    SYNTAX      SEQUENCE OF AffirmedServicesContentHttpProxyServiceStatisticsChassisLevelUdpProxyQuicEntry
    MAX-ACCESS  not-accessible
    STATUS      current
    DESCRIPTION ""
    ::= { affirmedServicesContentHttpProxyServiceStatisticsChassisLevelUdpProxy 5 }

affirmedServicesContentHttpProxyServiceStatisticsChassisLevelUdpProxyQuicEntry OBJECT-TYPE
    SYNTAX      AffirmedServicesContentHttpProxyServiceStatisticsChassisLevelUdpProxyQuicEntry
    MAX-ACCESS  not-accessible
    STATUS      current
    DESCRIPTION ""
    INDEX { affirmedServicesContentHttpProxyServiceStatisticsChassisLevelUdpProxyQuicChassis }
        ::= { affirmedServicesContentHttpProxyServiceStatisticsChassisLevelUdpProxyQuicTable 1 }

AffirmedServicesContentHttpProxyServiceStatisticsChassisLevelUdpProxyQuicEntry ::=
    SEQUENCE {
        affirmedServicesContentHttpProxyServiceStatisticsChassisLevelUdpProxyQuicChassis Unsigned32,
        affirmedServicesContentHttpProxyServiceStatisticsChassisLevelUdpProxyQuicNumudpproxyquicclienthello ConfdString,
        affirmedServicesContentHttpProxyServiceStatisticsChassisLevelUdpProxyQuicNumudpproxyquicserverhello ConfdString,
        affirmedServicesContentHttpProxyServiceStatisticsChassisLevelUdpProxyQuicNumudpproxyquicotherpackets ConfdString,
        affirmedServicesContentHttpProxyServiceStatisticsChassisLevelUdpProxyQuicNumudpproxyquicserverreset ConfdString,
        affirmedServicesContentHttpProxyServiceStatisticsChassisLevelUdpProxyQuicNumudpproxyquicclientreset ConfdString,
        affirmedServicesContentHttpProxyServiceStatisticsChassisLevelUdpProxyQuicNumudpproxyquicbytesdownstream ConfdString,
        affirmedServicesContentHttpProxyServiceStatisticsChassisLevelUdpProxyQuicNumudpproxyquicbytesupstream ConfdString,
        affirmedServicesContentHttpProxyServiceStatisticsChassisLevelUdpProxyQuicNumudpproxyquicconnections ConfdString
    }

affirmedServicesContentHttpProxyServiceStatisticsChassisLevelUdpProxyQuicChassis OBJECT-TYPE
    SYNTAX      Unsigned32
    MAX-ACCESS  not-accessible
    STATUS      current
    DESCRIPTION "chassis ID"
    ::= { affirmedServicesContentHttpProxyServiceStatisticsChassisLevelUdpProxyQuicEntry 1 }

affirmedServicesContentHttpProxyServiceStatisticsChassisLevelUdpProxyQuicNumudpproxyquicclienthello OBJECT-TYPE
    SYNTAX      ConfdString
    MAX-ACCESS  read-only
    STATUS      current
    DESCRIPTION "UDP Proxy QUIC - Number of Client Hello"
    ::= { affirmedServicesContentHttpProxyServiceStatisticsChassisLevelUdpProxyQuicEntry 2 }

affirmedServicesContentHttpProxyServiceStatisticsChassisLevelUdpProxyQuicNumudpproxyquicserverhello OBJECT-TYPE
    SYNTAX      ConfdString
    MAX-ACCESS  read-only
    STATUS      deprecated
    DESCRIPTION "UDP Proxy QUIC - Number of Server Rejects"
    ::= { affirmedServicesContentHttpProxyServiceStatisticsChassisLevelUdpProxyQuicEntry 3 }

affirmedServicesContentHttpProxyServiceStatisticsChassisLevelUdpProxyQuicNumudpproxyquicotherpackets OBJECT-TYPE
    SYNTAX      ConfdString
    MAX-ACCESS  read-only
    STATUS      current
    DESCRIPTION "UDP Proxy QUIC - Number of Other packets"
    ::= { affirmedServicesContentHttpProxyServiceStatisticsChassisLevelUdpProxyQuicEntry 4 }

affirmedServicesContentHttpProxyServiceStatisticsChassisLevelUdpProxyQuicNumudpproxyquicserverreset OBJECT-TYPE
    SYNTAX      ConfdString
    MAX-ACCESS  read-only
    STATUS      current
    DESCRIPTION "UDP Proxy QUIC - Number of Server Resets"
    ::= { affirmedServicesContentHttpProxyServiceStatisticsChassisLevelUdpProxyQuicEntry 5 }

affirmedServicesContentHttpProxyServiceStatisticsChassisLevelUdpProxyQuicNumudpproxyquicclientreset OBJECT-TYPE
    SYNTAX      ConfdString
    MAX-ACCESS  read-only
    STATUS      current
    DESCRIPTION "UDP Proxy QUIC - Number of Client Resets"
    ::= { affirmedServicesContentHttpProxyServiceStatisticsChassisLevelUdpProxyQuicEntry 6 }

affirmedServicesContentHttpProxyServiceStatisticsChassisLevelUdpProxyQuicNumudpproxyquicbytesdownstream OBJECT-TYPE
    SYNTAX      ConfdString
    MAX-ACCESS  read-only
    STATUS      current
    DESCRIPTION "UDP Proxy QUIC - Number of Downstream Bytes"
    ::= { affirmedServicesContentHttpProxyServiceStatisticsChassisLevelUdpProxyQuicEntry 7 }

affirmedServicesContentHttpProxyServiceStatisticsChassisLevelUdpProxyQuicNumudpproxyquicbytesupstream OBJECT-TYPE
    SYNTAX      ConfdString
    MAX-ACCESS  read-only
    STATUS      current
    DESCRIPTION "UDP Proxy QUIC - Number of Upstream Bytes"
    ::= { affirmedServicesContentHttpProxyServiceStatisticsChassisLevelUdpProxyQuicEntry 8 }

affirmedServicesContentHttpProxyServiceStatisticsChassisLevelUdpProxyQuicNumudpproxyquicconnections OBJECT-TYPE
    SYNTAX      ConfdString
    MAX-ACCESS  read-only
    STATUS      current
    DESCRIPTION "UDP Proxy QUIC - Number of Connections"
    ::= { affirmedServicesContentHttpProxyServiceStatisticsChassisLevelUdpProxyQuicEntry 9 }

affirmedServicesContentHttpProxyServiceStatisticsChassisLevelUdpProxyRateLimitingTable OBJECT-TYPE
    SYNTAX      SEQUENCE OF AffirmedServicesContentHttpProxyServiceStatisticsChassisLevelUdpProxyRateLimitingEntry
    MAX-ACCESS  not-accessible
    STATUS      current
    DESCRIPTION ""
    ::= { affirmedServicesContentHttpProxyServiceStatisticsChassisLevelUdpProxy 6 }

affirmedServicesContentHttpProxyServiceStatisticsChassisLevelUdpProxyRateLimitingEntry OBJECT-TYPE
    SYNTAX      AffirmedServicesContentHttpProxyServiceStatisticsChassisLevelUdpProxyRateLimitingEntry
    MAX-ACCESS  not-accessible
    STATUS      current
    DESCRIPTION ""
    INDEX { affirmedServicesContentHttpProxyServiceStatisticsChassisLevelUdpProxyRateLimitingChassis }
        ::= { affirmedServicesContentHttpProxyServiceStatisticsChassisLevelUdpProxyRateLimitingTable 1 }

AffirmedServicesContentHttpProxyServiceStatisticsChassisLevelUdpProxyRateLimitingEntry ::=
    SEQUENCE {
        affirmedServicesContentHttpProxyServiceStatisticsChassisLevelUdpProxyRateLimitingChassis Unsigned32,
        affirmedServicesContentHttpProxyServiceStatisticsChassisLevelUdpProxyRateLimitingNumudpproxyratelimitingsummaryattempts ConfdString,
        affirmedServicesContentHttpProxyServiceStatisticsChassisLevelUdpProxyRateLimitingNumudpproxyratelimitingsummarysuccesses ConfdString,
        affirmedServicesContentHttpProxyServiceStatisticsChassisLevelUdpProxyRateLimitingNumudpproxyratelimitingbytes ConfdString,
        affirmedServicesContentHttpProxyServiceStatisticsChassisLevelUdpProxyRateLimitingNumudpproxyratelimitingcurrent ConfdString,
        affirmedServicesContentHttpProxyServiceStatisticsChassisLevelUdpProxyRateLimitingNumudpproxyratelimitingbypassesdisabled ConfdString,
        affirmedServicesContentHttpProxyServiceStatisticsChassisLevelUdpProxyRateLimitingNumudpproxyratelimitingbypassesnotquic ConfdString,
        affirmedServicesContentHttpProxyServiceStatisticsChassisLevelUdpProxyRateLimitingNumudpproxyratelimitingoptedoutbysubscriber ConfdString,
        affirmedServicesContentHttpProxyServiceStatisticsChassisLevelUdpProxyRateLimitingNumudpproxyratelimitingoptedinreqnotmet ConfdString,
        affirmedServicesContentHttpProxyServiceStatisticsChassisLevelUdpProxyRateLimitingNumudpproxyratelimitingsavingsestimation ConfdString,
        affirmedServicesContentHttpProxyServiceStatisticsChassisLevelUdpProxyRateLimitingNumudpproxyratelimitingaggregationbypass ConfdString,
        affirmedServicesContentHttpProxyServiceStatisticsChassisLevelUdpProxyRateLimitingNumudpproxyratelimitingcanceltooshort ConfdString,
        affirmedServicesContentHttpProxyServiceStatisticsChassisLevelUdpProxyRateLimitingNumudpproxyratelimitingbytessavingsestimation ConfdString
    }

affirmedServicesContentHttpProxyServiceStatisticsChassisLevelUdpProxyRateLimitingChassis OBJECT-TYPE
    SYNTAX      Unsigned32
    MAX-ACCESS  not-accessible
    STATUS      current
    DESCRIPTION "chassis ID"
    ::= { affirmedServicesContentHttpProxyServiceStatisticsChassisLevelUdpProxyRateLimitingEntry 1 }

affirmedServicesContentHttpProxyServiceStatisticsChassisLevelUdpProxyRateLimitingNumudpproxyratelimitingsummaryattempts OBJECT-TYPE
    SYNTAX      ConfdString
    MAX-ACCESS  read-only
    STATUS      current
    DESCRIPTION "Total number of Rate Limiting Summary Attempts"
    ::= { affirmedServicesContentHttpProxyServiceStatisticsChassisLevelUdpProxyRateLimitingEntry 2 }

affirmedServicesContentHttpProxyServiceStatisticsChassisLevelUdpProxyRateLimitingNumudpproxyratelimitingsummarysuccesses OBJECT-TYPE
    SYNTAX      ConfdString
    MAX-ACCESS  read-only
    STATUS      current
    DESCRIPTION "Total number of Rate Limiting Summary Successes"
    ::= { affirmedServicesContentHttpProxyServiceStatisticsChassisLevelUdpProxyRateLimitingEntry 3 }

affirmedServicesContentHttpProxyServiceStatisticsChassisLevelUdpProxyRateLimitingNumudpproxyratelimitingbytes OBJECT-TYPE
    SYNTAX      ConfdString
    MAX-ACCESS  read-only
    STATUS      current
    DESCRIPTION "Total number of Rate Limiting Bytes"
    ::= { affirmedServicesContentHttpProxyServiceStatisticsChassisLevelUdpProxyRateLimitingEntry 4 }

affirmedServicesContentHttpProxyServiceStatisticsChassisLevelUdpProxyRateLimitingNumudpproxyratelimitingcurrent OBJECT-TYPE
    SYNTAX      ConfdString
    MAX-ACCESS  read-only
    STATUS      current
    DESCRIPTION "Total number of Current Rate Limiting Flows"
    ::= { affirmedServicesContentHttpProxyServiceStatisticsChassisLevelUdpProxyRateLimitingEntry 5 }

affirmedServicesContentHttpProxyServiceStatisticsChassisLevelUdpProxyRateLimitingNumudpproxyratelimitingbypassesdisabled OBJECT-TYPE
    SYNTAX      ConfdString
    MAX-ACCESS  read-only
    STATUS      current
    DESCRIPTION "Total number of Rate Limiting Disabled Flows"
    ::= { affirmedServicesContentHttpProxyServiceStatisticsChassisLevelUdpProxyRateLimitingEntry 6 }

affirmedServicesContentHttpProxyServiceStatisticsChassisLevelUdpProxyRateLimitingNumudpproxyratelimitingbypassesnotquic OBJECT-TYPE
    SYNTAX      ConfdString
    MAX-ACCESS  read-only
    STATUS      current
    DESCRIPTION "Total number of Rate Limiting Bypassed Flow, Not QUIC"
    ::= { affirmedServicesContentHttpProxyServiceStatisticsChassisLevelUdpProxyRateLimitingEntry 7 }

affirmedServicesContentHttpProxyServiceStatisticsChassisLevelUdpProxyRateLimitingNumudpproxyratelimitingoptedoutbysubscriber OBJECT-TYPE
    SYNTAX      ConfdString
    MAX-ACCESS  read-only
    STATUS      current
    DESCRIPTION "Total number of Rate Limiting Flows Opted Out by Subscriber"
    ::= { affirmedServicesContentHttpProxyServiceStatisticsChassisLevelUdpProxyRateLimitingEntry 8 }

affirmedServicesContentHttpProxyServiceStatisticsChassisLevelUdpProxyRateLimitingNumudpproxyratelimitingoptedinreqnotmet OBJECT-TYPE
    SYNTAX      ConfdString
    MAX-ACCESS  read-only
    STATUS      current
    DESCRIPTION "Total number of Rate Limiting Flows Opted In by Subscriber but Requirements Not Met"
    ::= { affirmedServicesContentHttpProxyServiceStatisticsChassisLevelUdpProxyRateLimitingEntry 9 }

affirmedServicesContentHttpProxyServiceStatisticsChassisLevelUdpProxyRateLimitingNumudpproxyratelimitingsavingsestimation OBJECT-TYPE
    SYNTAX      ConfdString
    MAX-ACCESS  read-only
    STATUS      current
    DESCRIPTION "Total number of Rate Limiting Bypassed Flow, Savings Estimation"
    ::= { affirmedServicesContentHttpProxyServiceStatisticsChassisLevelUdpProxyRateLimitingEntry 10 }

affirmedServicesContentHttpProxyServiceStatisticsChassisLevelUdpProxyRateLimitingNumudpproxyratelimitingaggregationbypass OBJECT-TYPE
    SYNTAX      ConfdString
    MAX-ACCESS  read-only
    STATUS      current
    DESCRIPTION "Total number of Rate Limiting Flows Aggregation Bypass"
    ::= { affirmedServicesContentHttpProxyServiceStatisticsChassisLevelUdpProxyRateLimitingEntry 11 }

affirmedServicesContentHttpProxyServiceStatisticsChassisLevelUdpProxyRateLimitingNumudpproxyratelimitingcanceltooshort OBJECT-TYPE
    SYNTAX      ConfdString
    MAX-ACCESS  read-only
    STATUS      current
    DESCRIPTION "Total number of Rate Limiting Cancel flows, Too short"
    ::= { affirmedServicesContentHttpProxyServiceStatisticsChassisLevelUdpProxyRateLimitingEntry 12 }

affirmedServicesContentHttpProxyServiceStatisticsChassisLevelUdpProxyRateLimitingNumudpproxyratelimitingbytessavingsestimation OBJECT-TYPE
    SYNTAX      ConfdString
    MAX-ACCESS  read-only
    STATUS      current
    DESCRIPTION "Total number of Rate Limiting Bypassed Bytes, Savings Estimation"
    ::= { affirmedServicesContentHttpProxyServiceStatisticsChassisLevelUdpProxyRateLimitingEntry 13 }

affirmedServicesContentHttpProxyServiceStatisticsChassisLevelUdpProxyDnsTable OBJECT-TYPE
    SYNTAX      SEQUENCE OF AffirmedServicesContentHttpProxyServiceStatisticsChassisLevelUdpProxyDnsEntry
    MAX-ACCESS  not-accessible
    STATUS      current
    DESCRIPTION ""
    ::= { affirmedServicesContentHttpProxyServiceStatisticsChassisLevelUdpProxy 7 }

affirmedServicesContentHttpProxyServiceStatisticsChassisLevelUdpProxyDnsEntry OBJECT-TYPE
    SYNTAX      AffirmedServicesContentHttpProxyServiceStatisticsChassisLevelUdpProxyDnsEntry
    MAX-ACCESS  not-accessible
    STATUS      current
    DESCRIPTION ""
    INDEX { affirmedServicesContentHttpProxyServiceStatisticsChassisLevelUdpProxyDnsChassis }
        ::= { affirmedServicesContentHttpProxyServiceStatisticsChassisLevelUdpProxyDnsTable 1 }

AffirmedServicesContentHttpProxyServiceStatisticsChassisLevelUdpProxyDnsEntry ::=
    SEQUENCE {
        affirmedServicesContentHttpProxyServiceStatisticsChassisLevelUdpProxyDnsChassis Unsigned32,
        affirmedServicesContentHttpProxyServiceStatisticsChassisLevelUdpProxyDnsNumudpproxydnsqueriessent ConfdString,
        affirmedServicesContentHttpProxyServiceStatisticsChassisLevelUdpProxyDnsNumudpproxydnsqueriesfailed ConfdString,
        affirmedServicesContentHttpProxyServiceStatisticsChassisLevelUdpProxyDnsNumudpproxydnsqueriescanceled ConfdString,
        affirmedServicesContentHttpProxyServiceStatisticsChassisLevelUdpProxyDnsNumudpproxydnsrepliessuccess ConfdString,
        affirmedServicesContentHttpProxyServiceStatisticsChassisLevelUdpProxyDnsNumudpproxydnsrepliesfailure ConfdString,
        affirmedServicesContentHttpProxyServiceStatisticsChassisLevelUdpProxyDnsNumudpproxydnsrepliesstale ConfdString,
        affirmedServicesContentHttpProxyServiceStatisticsChassisLevelUdpProxyDnsNumudpproxydnsrepliesfromcache ConfdString
    }

affirmedServicesContentHttpProxyServiceStatisticsChassisLevelUdpProxyDnsChassis OBJECT-TYPE
    SYNTAX      Unsigned32
    MAX-ACCESS  not-accessible
    STATUS      current
    DESCRIPTION "chassis ID"
    ::= { affirmedServicesContentHttpProxyServiceStatisticsChassisLevelUdpProxyDnsEntry 1 }

affirmedServicesContentHttpProxyServiceStatisticsChassisLevelUdpProxyDnsNumudpproxydnsqueriessent OBJECT-TYPE
    SYNTAX      ConfdString
    MAX-ACCESS  read-only
    STATUS      current
    DESCRIPTION "Number of UDP Proxy DNS Queries Sent"
    ::= { affirmedServicesContentHttpProxyServiceStatisticsChassisLevelUdpProxyDnsEntry 2 }

affirmedServicesContentHttpProxyServiceStatisticsChassisLevelUdpProxyDnsNumudpproxydnsqueriesfailed OBJECT-TYPE
    SYNTAX      ConfdString
    MAX-ACCESS  read-only
    STATUS      current
    DESCRIPTION "Number of UDP Proxy DNS Queries Failed"
    ::= { affirmedServicesContentHttpProxyServiceStatisticsChassisLevelUdpProxyDnsEntry 3 }

affirmedServicesContentHttpProxyServiceStatisticsChassisLevelUdpProxyDnsNumudpproxydnsqueriescanceled OBJECT-TYPE
    SYNTAX      ConfdString
    MAX-ACCESS  read-only
    STATUS      current
    DESCRIPTION "Number of UDP Proxy DNS Queries Canceled"
    ::= { affirmedServicesContentHttpProxyServiceStatisticsChassisLevelUdpProxyDnsEntry 4 }

affirmedServicesContentHttpProxyServiceStatisticsChassisLevelUdpProxyDnsNumudpproxydnsrepliessuccess OBJECT-TYPE
    SYNTAX      ConfdString
    MAX-ACCESS  read-only
    STATUS      current
    DESCRIPTION "Number of UDP Proxy DNS Replies Succeded"
    ::= { affirmedServicesContentHttpProxyServiceStatisticsChassisLevelUdpProxyDnsEntry 5 }

affirmedServicesContentHttpProxyServiceStatisticsChassisLevelUdpProxyDnsNumudpproxydnsrepliesfailure OBJECT-TYPE
    SYNTAX      ConfdString
    MAX-ACCESS  read-only
    STATUS      current
    DESCRIPTION "Number of UDP Proxy DNS Replies Failed"
    ::= { affirmedServicesContentHttpProxyServiceStatisticsChassisLevelUdpProxyDnsEntry 6 }

affirmedServicesContentHttpProxyServiceStatisticsChassisLevelUdpProxyDnsNumudpproxydnsrepliesstale OBJECT-TYPE
    SYNTAX      ConfdString
    MAX-ACCESS  read-only
    STATUS      current
    DESCRIPTION "Number of UDP Proxy DNS Stale Replies"
    ::= { affirmedServicesContentHttpProxyServiceStatisticsChassisLevelUdpProxyDnsEntry 7 }

affirmedServicesContentHttpProxyServiceStatisticsChassisLevelUdpProxyDnsNumudpproxydnsrepliesfromcache OBJECT-TYPE
    SYNTAX      ConfdString
    MAX-ACCESS  read-only
    STATUS      current
    DESCRIPTION "Number of UDP Proxy DNS Replies from Cache"
    ::= { affirmedServicesContentHttpProxyServiceStatisticsChassisLevelUdpProxyDnsEntry 8 }

affirmedServicesContentHttpProxyServiceStatisticsChassisLevelMinifyTable OBJECT-TYPE
    SYNTAX      SEQUENCE OF AffirmedServicesContentHttpProxyServiceStatisticsChassisLevelMinifyEntry
    MAX-ACCESS  not-accessible
    STATUS      deprecated
    DESCRIPTION ""
    ::= { affirmedServicesContentHttpProxyServiceStatisticsChassisLevel 12 }

affirmedServicesContentHttpProxyServiceStatisticsChassisLevelMinifyEntry OBJECT-TYPE
    SYNTAX      AffirmedServicesContentHttpProxyServiceStatisticsChassisLevelMinifyEntry
    MAX-ACCESS  not-accessible
    STATUS      deprecated
    DESCRIPTION ""
    INDEX { affirmedServicesContentHttpProxyServiceStatisticsChassisLevelMinifyChassis }
        ::= { affirmedServicesContentHttpProxyServiceStatisticsChassisLevelMinifyTable 1 }

AffirmedServicesContentHttpProxyServiceStatisticsChassisLevelMinifyEntry ::=
    SEQUENCE {
        affirmedServicesContentHttpProxyServiceStatisticsChassisLevelMinifyChassis Unsigned32,
        affirmedServicesContentHttpProxyServiceStatisticsChassisLevelMinifyNumminifycssattempts ConfdString,
        affirmedServicesContentHttpProxyServiceStatisticsChassisLevelMinifyNumminifycsssuccesses ConfdString,
        affirmedServicesContentHttpProxyServiceStatisticsChassisLevelMinifyNumminifycssfailures ConfdString,
        affirmedServicesContentHttpProxyServiceStatisticsChassisLevelMinifyNumminifycssbytesattempt ConfdString,
        affirmedServicesContentHttpProxyServiceStatisticsChassisLevelMinifyNumminifycssbytesminified ConfdString,
        affirmedServicesContentHttpProxyServiceStatisticsChassisLevelMinifyNumminifycssbytesnotminified ConfdString,
        affirmedServicesContentHttpProxyServiceStatisticsChassisLevelMinifyNumminifyhtmlattempts ConfdString,
        affirmedServicesContentHttpProxyServiceStatisticsChassisLevelMinifyNumminifyhtmlsuccesses ConfdString,
        affirmedServicesContentHttpProxyServiceStatisticsChassisLevelMinifyNumminifyhtmlfailures ConfdString,
        affirmedServicesContentHttpProxyServiceStatisticsChassisLevelMinifyNumminifyhtmlbytesattempt ConfdString,
        affirmedServicesContentHttpProxyServiceStatisticsChassisLevelMinifyNumminifyhtmlbytesminified ConfdString,
        affirmedServicesContentHttpProxyServiceStatisticsChassisLevelMinifyNumminifyhtmlbytesnotminified ConfdString,
        affirmedServicesContentHttpProxyServiceStatisticsChassisLevelMinifyNumminifyjsattempts ConfdString,
        affirmedServicesContentHttpProxyServiceStatisticsChassisLevelMinifyNumminifyjssuccesses ConfdString,
        affirmedServicesContentHttpProxyServiceStatisticsChassisLevelMinifyNumminifyjsfailures ConfdString,
        affirmedServicesContentHttpProxyServiceStatisticsChassisLevelMinifyNumminifyjsbytesattempt ConfdString,
        affirmedServicesContentHttpProxyServiceStatisticsChassisLevelMinifyNumminifyjsbytesminified ConfdString,
        affirmedServicesContentHttpProxyServiceStatisticsChassisLevelMinifyNumminifyjsbytesnotminified ConfdString,
        affirmedServicesContentHttpProxyServiceStatisticsChassisLevelMinifyNumminifycancelcontenttypemismatches ConfdString
    }

affirmedServicesContentHttpProxyServiceStatisticsChassisLevelMinifyChassis OBJECT-TYPE
    SYNTAX      Unsigned32
    MAX-ACCESS  not-accessible
    STATUS      current
    DESCRIPTION "chassis ID"
    ::= { affirmedServicesContentHttpProxyServiceStatisticsChassisLevelMinifyEntry 1 }

affirmedServicesContentHttpProxyServiceStatisticsChassisLevelMinifyNumminifycssattempts OBJECT-TYPE
    SYNTAX      ConfdString
    MAX-ACCESS  read-only
    STATUS      current
    DESCRIPTION "Total number of Minify CSS attempts"
    ::= { affirmedServicesContentHttpProxyServiceStatisticsChassisLevelMinifyEntry 2 }

affirmedServicesContentHttpProxyServiceStatisticsChassisLevelMinifyNumminifycsssuccesses OBJECT-TYPE
    SYNTAX      ConfdString
    MAX-ACCESS  read-only
    STATUS      current
    DESCRIPTION "Total number of Minify CSS successes"
    ::= { affirmedServicesContentHttpProxyServiceStatisticsChassisLevelMinifyEntry 3 }

affirmedServicesContentHttpProxyServiceStatisticsChassisLevelMinifyNumminifycssfailures OBJECT-TYPE
    SYNTAX      ConfdString
    MAX-ACCESS  read-only
    STATUS      current
    DESCRIPTION "Total number of Minify CSS failures"
    ::= { affirmedServicesContentHttpProxyServiceStatisticsChassisLevelMinifyEntry 4 }

affirmedServicesContentHttpProxyServiceStatisticsChassisLevelMinifyNumminifycssbytesattempt OBJECT-TYPE
    SYNTAX      ConfdString
    MAX-ACCESS  read-only
    STATUS      current
    DESCRIPTION "Total number of Minify CSS bytes attempt"
    ::= { affirmedServicesContentHttpProxyServiceStatisticsChassisLevelMinifyEntry 5 }

affirmedServicesContentHttpProxyServiceStatisticsChassisLevelMinifyNumminifycssbytesminified OBJECT-TYPE
    SYNTAX      ConfdString
    MAX-ACCESS  read-only
    STATUS      current
    DESCRIPTION "Total number of Minify CSS bytes minified"
    ::= { affirmedServicesContentHttpProxyServiceStatisticsChassisLevelMinifyEntry 6 }

affirmedServicesContentHttpProxyServiceStatisticsChassisLevelMinifyNumminifycssbytesnotminified OBJECT-TYPE
    SYNTAX      ConfdString
    MAX-ACCESS  read-only
    STATUS      current
    DESCRIPTION "Total number of Minify CSS bytes not minified"
    ::= { affirmedServicesContentHttpProxyServiceStatisticsChassisLevelMinifyEntry 7 }

affirmedServicesContentHttpProxyServiceStatisticsChassisLevelMinifyNumminifyhtmlattempts OBJECT-TYPE
    SYNTAX      ConfdString
    MAX-ACCESS  read-only
    STATUS      current
    DESCRIPTION "Total number of Minify HTML attempts"
    ::= { affirmedServicesContentHttpProxyServiceStatisticsChassisLevelMinifyEntry 8 }

affirmedServicesContentHttpProxyServiceStatisticsChassisLevelMinifyNumminifyhtmlsuccesses OBJECT-TYPE
    SYNTAX      ConfdString
    MAX-ACCESS  read-only
    STATUS      current
    DESCRIPTION "Total number of Minify HTML successes"
    ::= { affirmedServicesContentHttpProxyServiceStatisticsChassisLevelMinifyEntry 9 }

affirmedServicesContentHttpProxyServiceStatisticsChassisLevelMinifyNumminifyhtmlfailures OBJECT-TYPE
    SYNTAX      ConfdString
    MAX-ACCESS  read-only
    STATUS      current
    DESCRIPTION "Total number of Minify HTML failures"
    ::= { affirmedServicesContentHttpProxyServiceStatisticsChassisLevelMinifyEntry 10 }

affirmedServicesContentHttpProxyServiceStatisticsChassisLevelMinifyNumminifyhtmlbytesattempt OBJECT-TYPE
    SYNTAX      ConfdString
    MAX-ACCESS  read-only
    STATUS      current
    DESCRIPTION "Total number of Minify HTML bytes attempt"
    ::= { affirmedServicesContentHttpProxyServiceStatisticsChassisLevelMinifyEntry 11 }

affirmedServicesContentHttpProxyServiceStatisticsChassisLevelMinifyNumminifyhtmlbytesminified OBJECT-TYPE
    SYNTAX      ConfdString
    MAX-ACCESS  read-only
    STATUS      current
    DESCRIPTION "Total number of Minify HTML bytes minified"
    ::= { affirmedServicesContentHttpProxyServiceStatisticsChassisLevelMinifyEntry 12 }

affirmedServicesContentHttpProxyServiceStatisticsChassisLevelMinifyNumminifyhtmlbytesnotminified OBJECT-TYPE
    SYNTAX      ConfdString
    MAX-ACCESS  read-only
    STATUS      current
    DESCRIPTION "Total number of Minify HTML bytes not minified"
    ::= { affirmedServicesContentHttpProxyServiceStatisticsChassisLevelMinifyEntry 13 }

affirmedServicesContentHttpProxyServiceStatisticsChassisLevelMinifyNumminifyjsattempts OBJECT-TYPE
    SYNTAX      ConfdString
    MAX-ACCESS  read-only
    STATUS      current
    DESCRIPTION "Total number of Minify Javascript attempts"
    ::= { affirmedServicesContentHttpProxyServiceStatisticsChassisLevelMinifyEntry 14 }

affirmedServicesContentHttpProxyServiceStatisticsChassisLevelMinifyNumminifyjssuccesses OBJECT-TYPE
    SYNTAX      ConfdString
    MAX-ACCESS  read-only
    STATUS      current
    DESCRIPTION "Total number of Minify Javascript successes"
    ::= { affirmedServicesContentHttpProxyServiceStatisticsChassisLevelMinifyEntry 15 }

affirmedServicesContentHttpProxyServiceStatisticsChassisLevelMinifyNumminifyjsfailures OBJECT-TYPE
    SYNTAX      ConfdString
    MAX-ACCESS  read-only
    STATUS      current
    DESCRIPTION "Total number of Minify Javascript failures"
    ::= { affirmedServicesContentHttpProxyServiceStatisticsChassisLevelMinifyEntry 16 }

affirmedServicesContentHttpProxyServiceStatisticsChassisLevelMinifyNumminifyjsbytesattempt OBJECT-TYPE
    SYNTAX      ConfdString
    MAX-ACCESS  read-only
    STATUS      current
    DESCRIPTION "Total number of Minify Javascript bytes attempt"
    ::= { affirmedServicesContentHttpProxyServiceStatisticsChassisLevelMinifyEntry 17 }

affirmedServicesContentHttpProxyServiceStatisticsChassisLevelMinifyNumminifyjsbytesminified OBJECT-TYPE
    SYNTAX      ConfdString
    MAX-ACCESS  read-only
    STATUS      current
    DESCRIPTION "Total number of Minify Javascript bytes minified"
    ::= { affirmedServicesContentHttpProxyServiceStatisticsChassisLevelMinifyEntry 18 }

affirmedServicesContentHttpProxyServiceStatisticsChassisLevelMinifyNumminifyjsbytesnotminified OBJECT-TYPE
    SYNTAX      ConfdString
    MAX-ACCESS  read-only
    STATUS      current
    DESCRIPTION "Total number of Minify Javascript bytes not minified"
    ::= { affirmedServicesContentHttpProxyServiceStatisticsChassisLevelMinifyEntry 19 }

affirmedServicesContentHttpProxyServiceStatisticsChassisLevelMinifyNumminifycancelcontenttypemismatches OBJECT-TYPE
    SYNTAX      ConfdString
    MAX-ACCESS  read-only
    STATUS      current
    DESCRIPTION "Total number of Minify Cancels because Content-Type mismatches"
    ::= { affirmedServicesContentHttpProxyServiceStatisticsChassisLevelMinifyEntry 20 }

affirmedServicesContentHttpProxyServiceStatisticsChassisLevelCompressionTable OBJECT-TYPE
    SYNTAX      SEQUENCE OF AffirmedServicesContentHttpProxyServiceStatisticsChassisLevelCompressionEntry
    MAX-ACCESS  not-accessible
    STATUS      current
    DESCRIPTION ""
    ::= { affirmedServicesContentHttpProxyServiceStatisticsChassisLevel 13 }

affirmedServicesContentHttpProxyServiceStatisticsChassisLevelCompressionEntry OBJECT-TYPE
    SYNTAX      AffirmedServicesContentHttpProxyServiceStatisticsChassisLevelCompressionEntry
    MAX-ACCESS  not-accessible
    STATUS      current
    DESCRIPTION ""
    INDEX { affirmedServicesContentHttpProxyServiceStatisticsChassisLevelCompressionChassis }
        ::= { affirmedServicesContentHttpProxyServiceStatisticsChassisLevelCompressionTable 1 }

AffirmedServicesContentHttpProxyServiceStatisticsChassisLevelCompressionEntry ::=
    SEQUENCE {
        affirmedServicesContentHttpProxyServiceStatisticsChassisLevelCompressionChassis Unsigned32,
        affirmedServicesContentHttpProxyServiceStatisticsChassisLevelCompressionNumrspnotcompressedbyserver ConfdString,
        affirmedServicesContentHttpProxyServiceStatisticsChassisLevelCompressionNumrspcompressedbyserver ConfdString,
        affirmedServicesContentHttpProxyServiceStatisticsChassisLevelCompressionNumrspcompressedbyproxy ConfdString,
        affirmedServicesContentHttpProxyServiceStatisticsChassisLevelCompressionNumrspforcedcompressbyproxy ConfdString,
        affirmedServicesContentHttpProxyServiceStatisticsChassisLevelCompressionNumbytesnotcompressedbyserver ConfdString,
        affirmedServicesContentHttpProxyServiceStatisticsChassisLevelCompressionNumbytescompressedbyserver ConfdString,
        affirmedServicesContentHttpProxyServiceStatisticsChassisLevelCompressionNumbytescompressedbyproxy ConfdString,
        affirmedServicesContentHttpProxyServiceStatisticsChassisLevelCompressionNumbytesforcedcompressbyproxy ConfdString,
        affirmedServicesContentHttpProxyServiceStatisticsChassisLevelCompressionNumrspcancelcontenttypemismatches ConfdString
    }

affirmedServicesContentHttpProxyServiceStatisticsChassisLevelCompressionChassis OBJECT-TYPE
    SYNTAX      Unsigned32
    MAX-ACCESS  not-accessible
    STATUS      current
    DESCRIPTION "chassis ID"
    ::= { affirmedServicesContentHttpProxyServiceStatisticsChassisLevelCompressionEntry 1 }

affirmedServicesContentHttpProxyServiceStatisticsChassisLevelCompressionNumrspnotcompressedbyserver OBJECT-TYPE
    SYNTAX      ConfdString
    MAX-ACCESS  read-only
    STATUS      current
    DESCRIPTION "Total number of responses that were not compressed by the server"
    ::= { affirmedServicesContentHttpProxyServiceStatisticsChassisLevelCompressionEntry 2 }

affirmedServicesContentHttpProxyServiceStatisticsChassisLevelCompressionNumrspcompressedbyserver OBJECT-TYPE
    SYNTAX      ConfdString
    MAX-ACCESS  read-only
    STATUS      current
    DESCRIPTION "Total number of responses that were compressed by the server"
    ::= { affirmedServicesContentHttpProxyServiceStatisticsChassisLevelCompressionEntry 3 }

affirmedServicesContentHttpProxyServiceStatisticsChassisLevelCompressionNumrspcompressedbyproxy OBJECT-TYPE
    SYNTAX      ConfdString
    MAX-ACCESS  read-only
    STATUS      current
    DESCRIPTION "Total number of responses that were compressed by proxy"
    ::= { affirmedServicesContentHttpProxyServiceStatisticsChassisLevelCompressionEntry 4 }

affirmedServicesContentHttpProxyServiceStatisticsChassisLevelCompressionNumrspforcedcompressbyproxy OBJECT-TYPE
    SYNTAX      ConfdString
    MAX-ACCESS  read-only
    STATUS      current
    DESCRIPTION "Total number of responses that were forced to compress by proxy"
    ::= { affirmedServicesContentHttpProxyServiceStatisticsChassisLevelCompressionEntry 5 }

affirmedServicesContentHttpProxyServiceStatisticsChassisLevelCompressionNumbytesnotcompressedbyserver OBJECT-TYPE
    SYNTAX      ConfdString
    MAX-ACCESS  read-only
    STATUS      current
    DESCRIPTION "Total number of bytes that were not compressed by the server"
    ::= { affirmedServicesContentHttpProxyServiceStatisticsChassisLevelCompressionEntry 6 }

affirmedServicesContentHttpProxyServiceStatisticsChassisLevelCompressionNumbytescompressedbyserver OBJECT-TYPE
    SYNTAX      ConfdString
    MAX-ACCESS  read-only
    STATUS      current
    DESCRIPTION "Total number of bytes that were compressed by the server"
    ::= { affirmedServicesContentHttpProxyServiceStatisticsChassisLevelCompressionEntry 7 }

affirmedServicesContentHttpProxyServiceStatisticsChassisLevelCompressionNumbytescompressedbyproxy OBJECT-TYPE
    SYNTAX      ConfdString
    MAX-ACCESS  read-only
    STATUS      current
    DESCRIPTION "Total number of bytes that were compressed by proxy"
    ::= { affirmedServicesContentHttpProxyServiceStatisticsChassisLevelCompressionEntry 8 }

affirmedServicesContentHttpProxyServiceStatisticsChassisLevelCompressionNumbytesforcedcompressbyproxy OBJECT-TYPE
    SYNTAX      ConfdString
    MAX-ACCESS  read-only
    STATUS      current
    DESCRIPTION "Total number of bytes that were forced to compress by proxy"
    ::= { affirmedServicesContentHttpProxyServiceStatisticsChassisLevelCompressionEntry 9 }

affirmedServicesContentHttpProxyServiceStatisticsChassisLevelCompressionNumrspcancelcontenttypemismatches OBJECT-TYPE
    SYNTAX      ConfdString
    MAX-ACCESS  read-only
    STATUS      current
    DESCRIPTION "Total number of responses that were cancel because content-type mismatches"
    ::= { affirmedServicesContentHttpProxyServiceStatisticsChassisLevelCompressionEntry 10 }

affirmedServicesContentHttpProxyServiceStatisticsChassisLevelWebImageOptSummaryTable OBJECT-TYPE
    SYNTAX      SEQUENCE OF AffirmedServicesContentHttpProxyServiceStatisticsChassisLevelWebImageOptSummaryEntry
    MAX-ACCESS  not-accessible
    STATUS      current
    DESCRIPTION ""
    ::= { affirmedServicesContentHttpProxyServiceStatisticsChassisLevelWebImageOpt 1 }

affirmedServicesContentHttpProxyServiceStatisticsChassisLevelWebImageOptSummaryEntry OBJECT-TYPE
    SYNTAX      AffirmedServicesContentHttpProxyServiceStatisticsChassisLevelWebImageOptSummaryEntry
    MAX-ACCESS  not-accessible
    STATUS      current
    DESCRIPTION ""
    INDEX { affirmedServicesContentHttpProxyServiceStatisticsChassisLevelWebImageOptSummaryChassis }
        ::= { affirmedServicesContentHttpProxyServiceStatisticsChassisLevelWebImageOptSummaryTable 1 }

AffirmedServicesContentHttpProxyServiceStatisticsChassisLevelWebImageOptSummaryEntry ::=
    SEQUENCE {
        affirmedServicesContentHttpProxyServiceStatisticsChassisLevelWebImageOptSummaryChassis Unsigned32,
        affirmedServicesContentHttpProxyServiceStatisticsChassisLevelWebImageOptSummaryNumwebimageoptattempts ConfdString,
        affirmedServicesContentHttpProxyServiceStatisticsChassisLevelWebImageOptSummaryNumwebimageoptsuccesses ConfdString,
        affirmedServicesContentHttpProxyServiceStatisticsChassisLevelWebImageOptSummaryNumwebimageoptcancels ConfdString,
        affirmedServicesContentHttpProxyServiceStatisticsChassisLevelWebImageOptSummaryNumwebimageoptfailures ConfdString,
        affirmedServicesContentHttpProxyServiceStatisticsChassisLevelWebImageOptSummaryNumwebimageoptbytesattempt ConfdString,
        affirmedServicesContentHttpProxyServiceStatisticsChassisLevelWebImageOptSummaryNumwebimageoptbytesnotadapted ConfdString,
        affirmedServicesContentHttpProxyServiceStatisticsChassisLevelWebImageOptSummaryNumwebimageoptbytesadapted ConfdString,
        affirmedServicesContentHttpProxyServiceStatisticsChassisLevelWebImageOptSummaryWebimagesizemax ConfdString,
        affirmedServicesContentHttpProxyServiceStatisticsChassisLevelWebImageOptSummaryWebimagesizemin ConfdString,
        affirmedServicesContentHttpProxyServiceStatisticsChassisLevelWebImageOptSummaryWebimagesizeavg ConfdString,
        affirmedServicesContentHttpProxyServiceStatisticsChassisLevelWebImageOptSummaryWebimageadaptedsizemax ConfdString,
        affirmedServicesContentHttpProxyServiceStatisticsChassisLevelWebImageOptSummaryWebimageadaptedsizemin ConfdString,
        affirmedServicesContentHttpProxyServiceStatisticsChassisLevelWebImageOptSummaryWebimageadaptedsizeavg ConfdString,
        affirmedServicesContentHttpProxyServiceStatisticsChassisLevelWebImageOptSummaryNumwebimageoptaborts ConfdString
    }

affirmedServicesContentHttpProxyServiceStatisticsChassisLevelWebImageOptSummaryChassis OBJECT-TYPE
    SYNTAX      Unsigned32
    MAX-ACCESS  not-accessible
    STATUS      current
    DESCRIPTION "chassis ID"
    ::= { affirmedServicesContentHttpProxyServiceStatisticsChassisLevelWebImageOptSummaryEntry 1 }

affirmedServicesContentHttpProxyServiceStatisticsChassisLevelWebImageOptSummaryNumwebimageoptattempts OBJECT-TYPE
    SYNTAX      ConfdString
    MAX-ACCESS  read-only
    STATUS      current
    DESCRIPTION "Total number of Web Image Optimization attempts"
    ::= { affirmedServicesContentHttpProxyServiceStatisticsChassisLevelWebImageOptSummaryEntry 2 }

affirmedServicesContentHttpProxyServiceStatisticsChassisLevelWebImageOptSummaryNumwebimageoptsuccesses OBJECT-TYPE
    SYNTAX      ConfdString
    MAX-ACCESS  read-only
    STATUS      current
    DESCRIPTION "Total number of Web Image Optimization successes"
    ::= { affirmedServicesContentHttpProxyServiceStatisticsChassisLevelWebImageOptSummaryEntry 3 }

affirmedServicesContentHttpProxyServiceStatisticsChassisLevelWebImageOptSummaryNumwebimageoptcancels OBJECT-TYPE
    SYNTAX      ConfdString
    MAX-ACCESS  read-only
    STATUS      current
    DESCRIPTION "Total number of Web Image Optimization cancels"
    ::= { affirmedServicesContentHttpProxyServiceStatisticsChassisLevelWebImageOptSummaryEntry 4 }

affirmedServicesContentHttpProxyServiceStatisticsChassisLevelWebImageOptSummaryNumwebimageoptfailures OBJECT-TYPE
    SYNTAX      ConfdString
    MAX-ACCESS  read-only
    STATUS      current
    DESCRIPTION "Total number of Web Image Optimization failures"
    ::= { affirmedServicesContentHttpProxyServiceStatisticsChassisLevelWebImageOptSummaryEntry 5 }

affirmedServicesContentHttpProxyServiceStatisticsChassisLevelWebImageOptSummaryNumwebimageoptbytesattempt OBJECT-TYPE
    SYNTAX      ConfdString
    MAX-ACCESS  read-only
    STATUS      current
    DESCRIPTION "Total number of Web Image Optimization bytes attempt to adapt"
    ::= { affirmedServicesContentHttpProxyServiceStatisticsChassisLevelWebImageOptSummaryEntry 6 }

affirmedServicesContentHttpProxyServiceStatisticsChassisLevelWebImageOptSummaryNumwebimageoptbytesnotadapted OBJECT-TYPE
    SYNTAX      ConfdString
    MAX-ACCESS  read-only
    STATUS      current
    DESCRIPTION "Total number of Web Image Optimization bytes not adapted"
    ::= { affirmedServicesContentHttpProxyServiceStatisticsChassisLevelWebImageOptSummaryEntry 7 }

affirmedServicesContentHttpProxyServiceStatisticsChassisLevelWebImageOptSummaryNumwebimageoptbytesadapted OBJECT-TYPE
    SYNTAX      ConfdString
    MAX-ACCESS  read-only
    STATUS      current
    DESCRIPTION "Total number of Web Image Optimization bytes adapted"
    ::= { affirmedServicesContentHttpProxyServiceStatisticsChassisLevelWebImageOptSummaryEntry 8 }

affirmedServicesContentHttpProxyServiceStatisticsChassisLevelWebImageOptSummaryWebimagesizemax OBJECT-TYPE
    SYNTAX      ConfdString
    MAX-ACCESS  read-only
    STATUS      current
    DESCRIPTION "Web Image Size Max (Bytes)"
    ::= { affirmedServicesContentHttpProxyServiceStatisticsChassisLevelWebImageOptSummaryEntry 9 }

affirmedServicesContentHttpProxyServiceStatisticsChassisLevelWebImageOptSummaryWebimagesizemin OBJECT-TYPE
    SYNTAX      ConfdString
    MAX-ACCESS  read-only
    STATUS      current
    DESCRIPTION "Web Image Size Min (Bytes)"
    ::= { affirmedServicesContentHttpProxyServiceStatisticsChassisLevelWebImageOptSummaryEntry 10 }

affirmedServicesContentHttpProxyServiceStatisticsChassisLevelWebImageOptSummaryWebimagesizeavg OBJECT-TYPE
    SYNTAX      ConfdString
    MAX-ACCESS  read-only
    STATUS      current
    DESCRIPTION "Web Image Size Average (Bytes)"
    ::= { affirmedServicesContentHttpProxyServiceStatisticsChassisLevelWebImageOptSummaryEntry 11 }

affirmedServicesContentHttpProxyServiceStatisticsChassisLevelWebImageOptSummaryWebimageadaptedsizemax OBJECT-TYPE
    SYNTAX      ConfdString
    MAX-ACCESS  read-only
    STATUS      current
    DESCRIPTION "Web Image Adapted Size Max (Bytes)"
    ::= { affirmedServicesContentHttpProxyServiceStatisticsChassisLevelWebImageOptSummaryEntry 12 }

affirmedServicesContentHttpProxyServiceStatisticsChassisLevelWebImageOptSummaryWebimageadaptedsizemin OBJECT-TYPE
    SYNTAX      ConfdString
    MAX-ACCESS  read-only
    STATUS      current
    DESCRIPTION "Web Image Adapted Size Min (Bytes)"
    ::= { affirmedServicesContentHttpProxyServiceStatisticsChassisLevelWebImageOptSummaryEntry 13 }

affirmedServicesContentHttpProxyServiceStatisticsChassisLevelWebImageOptSummaryWebimageadaptedsizeavg OBJECT-TYPE
    SYNTAX      ConfdString
    MAX-ACCESS  read-only
    STATUS      current
    DESCRIPTION "Web Image Adapted Size Average (Bytes)"
    ::= { affirmedServicesContentHttpProxyServiceStatisticsChassisLevelWebImageOptSummaryEntry 14 }

affirmedServicesContentHttpProxyServiceStatisticsChassisLevelWebImageOptSummaryNumwebimageoptaborts OBJECT-TYPE
    SYNTAX      ConfdString
    MAX-ACCESS  read-only
    STATUS      current
    DESCRIPTION "Total number of Web Image Optimization Aborts"
    ::= { affirmedServicesContentHttpProxyServiceStatisticsChassisLevelWebImageOptSummaryEntry 15 }

affirmedServicesContentHttpProxyServiceStatisticsChassisLevelWebImageOptDetailTable OBJECT-TYPE
    SYNTAX      SEQUENCE OF AffirmedServicesContentHttpProxyServiceStatisticsChassisLevelWebImageOptDetailEntry
    MAX-ACCESS  not-accessible
    STATUS      current
    DESCRIPTION ""
    ::= { affirmedServicesContentHttpProxyServiceStatisticsChassisLevelWebImageOpt 2 }

affirmedServicesContentHttpProxyServiceStatisticsChassisLevelWebImageOptDetailEntry OBJECT-TYPE
    SYNTAX      AffirmedServicesContentHttpProxyServiceStatisticsChassisLevelWebImageOptDetailEntry
    MAX-ACCESS  not-accessible
    STATUS      current
    DESCRIPTION ""
    INDEX { affirmedServicesContentHttpProxyServiceStatisticsChassisLevelWebImageOptDetailChassis }
        ::= { affirmedServicesContentHttpProxyServiceStatisticsChassisLevelWebImageOptDetailTable 1 }

AffirmedServicesContentHttpProxyServiceStatisticsChassisLevelWebImageOptDetailEntry ::=
    SEQUENCE {
        affirmedServicesContentHttpProxyServiceStatisticsChassisLevelWebImageOptDetailChassis Unsigned32,
        affirmedServicesContentHttpProxyServiceStatisticsChassisLevelWebImageOptDetailNumwebimageoptbelowsrcsizethresh ConfdString,
        affirmedServicesContentHttpProxyServiceStatisticsChassisLevelWebImageOptDetailNumwebimageoptbelowpercentsavingthresh ConfdString,
        affirmedServicesContentHttpProxyServiceStatisticsChassisLevelWebImageOptDetailNumwebimageopttgtmaxsizeexceeded ConfdString,
        affirmedServicesContentHttpProxyServiceStatisticsChassisLevelWebImageOptDetailNumwebimageoptformatnotsupported ConfdString,
        affirmedServicesContentHttpProxyServiceStatisticsChassisLevelWebImageOptDetailNumwebimageoptcompressnotallowed ConfdString,
        affirmedServicesContentHttpProxyServiceStatisticsChassisLevelWebImageOptDetailNumwebimageoptdecompressimagefailed ConfdString,
        affirmedServicesContentHttpProxyServiceStatisticsChassisLevelWebImageOptDetailNumwebimageoptcompressimagefailed ConfdString,
        affirmedServicesContentHttpProxyServiceStatisticsChassisLevelWebImageOptDetailNumwebimageoptquantizeimagefailed ConfdString,
        affirmedServicesContentHttpProxyServiceStatisticsChassisLevelWebImageOptDetailNumwebimageoptremovemetadatafailed ConfdString,
        affirmedServicesContentHttpProxyServiceStatisticsChassisLevelWebImageOptDetailNumwebimageoptresizeimagefailed ConfdString,
        affirmedServicesContentHttpProxyServiceStatisticsChassisLevelWebImageOptDetailNumwebimageoptalphablendimagefailed ConfdString,
        affirmedServicesContentHttpProxyServiceStatisticsChassisLevelWebImageOptDetailNumwebimageoptgetsrcimageformatfailed ConfdString,
        affirmedServicesContentHttpProxyServiceStatisticsChassisLevelWebImageOptDetailNumwebimageoptgettgtimageformatfailed ConfdString,
        affirmedServicesContentHttpProxyServiceStatisticsChassisLevelWebImageOptDetailNumwebimageoptjpegattempts ConfdString,
        affirmedServicesContentHttpProxyServiceStatisticsChassisLevelWebImageOptDetailNumwebimageoptjpegsuccesses ConfdString,
        affirmedServicesContentHttpProxyServiceStatisticsChassisLevelWebImageOptDetailNumwebimageoptjpegbytesattempt ConfdString,
        affirmedServicesContentHttpProxyServiceStatisticsChassisLevelWebImageOptDetailNumwebimageoptjpegbytesnotadapted ConfdString,
        affirmedServicesContentHttpProxyServiceStatisticsChassisLevelWebImageOptDetailNumwebimageoptjpegbytesadapted ConfdString,
        affirmedServicesContentHttpProxyServiceStatisticsChassisLevelWebImageOptDetailNumwebimageoptgifattempts ConfdString,
        affirmedServicesContentHttpProxyServiceStatisticsChassisLevelWebImageOptDetailNumwebimageoptgifsuccesses ConfdString,
        affirmedServicesContentHttpProxyServiceStatisticsChassisLevelWebImageOptDetailNumwebimageoptgifbytesattempt ConfdString,
        affirmedServicesContentHttpProxyServiceStatisticsChassisLevelWebImageOptDetailNumwebimageoptgifbytesnotadapted ConfdString,
        affirmedServicesContentHttpProxyServiceStatisticsChassisLevelWebImageOptDetailNumwebimageoptgifbytesadapted ConfdString,
        affirmedServicesContentHttpProxyServiceStatisticsChassisLevelWebImageOptDetailNumwebimageoptpngattempts ConfdString,
        affirmedServicesContentHttpProxyServiceStatisticsChassisLevelWebImageOptDetailNumwebimageoptpngsuccesses ConfdString,
        affirmedServicesContentHttpProxyServiceStatisticsChassisLevelWebImageOptDetailNumwebimageoptpngbytesattempt ConfdString,
        affirmedServicesContentHttpProxyServiceStatisticsChassisLevelWebImageOptDetailNumwebimageoptpngbytesnotadapted ConfdString,
        affirmedServicesContentHttpProxyServiceStatisticsChassisLevelWebImageOptDetailNumwebimageoptpngbytesadapted ConfdString,
        affirmedServicesContentHttpProxyServiceStatisticsChassisLevelWebImageOptDetailNumwebimageoptsrcmaxsizeexceeded ConfdString,
        affirmedServicesContentHttpProxyServiceStatisticsChassisLevelWebImageOptDetailNumwebimageoptcontenttypemismatches ConfdString,
        affirmedServicesContentHttpProxyServiceStatisticsChassisLevelWebImageOptDetailNumwebimageoptcpuoverload ConfdString
    }

affirmedServicesContentHttpProxyServiceStatisticsChassisLevelWebImageOptDetailChassis OBJECT-TYPE
    SYNTAX      Unsigned32
    MAX-ACCESS  not-accessible
    STATUS      current
    DESCRIPTION "chassis ID"
    ::= { affirmedServicesContentHttpProxyServiceStatisticsChassisLevelWebImageOptDetailEntry 1 }

affirmedServicesContentHttpProxyServiceStatisticsChassisLevelWebImageOptDetailNumwebimageoptbelowsrcsizethresh OBJECT-TYPE
    SYNTAX      ConfdString
    MAX-ACCESS  read-only
    STATUS      current
    DESCRIPTION "Total number of Web Image Optimization below source size threshold"
    ::= { affirmedServicesContentHttpProxyServiceStatisticsChassisLevelWebImageOptDetailEntry 2 }

affirmedServicesContentHttpProxyServiceStatisticsChassisLevelWebImageOptDetailNumwebimageoptbelowpercentsavingthresh OBJECT-TYPE
    SYNTAX      ConfdString
    MAX-ACCESS  read-only
    STATUS      current
    DESCRIPTION "Total number of Web Image Optimization below percentage savings threshold"
    ::= { affirmedServicesContentHttpProxyServiceStatisticsChassisLevelWebImageOptDetailEntry 3 }

affirmedServicesContentHttpProxyServiceStatisticsChassisLevelWebImageOptDetailNumwebimageopttgtmaxsizeexceeded OBJECT-TYPE
    SYNTAX      ConfdString
    MAX-ACCESS  read-only
    STATUS      current
    DESCRIPTION "Total number of Web Image Optimization target max size exceeded"
    ::= { affirmedServicesContentHttpProxyServiceStatisticsChassisLevelWebImageOptDetailEntry 4 }

affirmedServicesContentHttpProxyServiceStatisticsChassisLevelWebImageOptDetailNumwebimageoptformatnotsupported OBJECT-TYPE
    SYNTAX      ConfdString
    MAX-ACCESS  read-only
    STATUS      current
    DESCRIPTION "Total number of Web Image Optimization format not supported"
    ::= { affirmedServicesContentHttpProxyServiceStatisticsChassisLevelWebImageOptDetailEntry 5 }

affirmedServicesContentHttpProxyServiceStatisticsChassisLevelWebImageOptDetailNumwebimageoptcompressnotallowed OBJECT-TYPE
    SYNTAX      ConfdString
    MAX-ACCESS  read-only
    STATUS      current
    DESCRIPTION "Total number of Web Image Optimization compressing not allowed"
    ::= { affirmedServicesContentHttpProxyServiceStatisticsChassisLevelWebImageOptDetailEntry 6 }

affirmedServicesContentHttpProxyServiceStatisticsChassisLevelWebImageOptDetailNumwebimageoptdecompressimagefailed OBJECT-TYPE
    SYNTAX      ConfdString
    MAX-ACCESS  read-only
    STATUS      current
    DESCRIPTION "Total number of Web Image Optimization decompressing image failed"
    ::= { affirmedServicesContentHttpProxyServiceStatisticsChassisLevelWebImageOptDetailEntry 7 }

affirmedServicesContentHttpProxyServiceStatisticsChassisLevelWebImageOptDetailNumwebimageoptcompressimagefailed OBJECT-TYPE
    SYNTAX      ConfdString
    MAX-ACCESS  read-only
    STATUS      current
    DESCRIPTION "Total number of Web Image Optimization compressing image failed"
    ::= { affirmedServicesContentHttpProxyServiceStatisticsChassisLevelWebImageOptDetailEntry 8 }

affirmedServicesContentHttpProxyServiceStatisticsChassisLevelWebImageOptDetailNumwebimageoptquantizeimagefailed OBJECT-TYPE
    SYNTAX      ConfdString
    MAX-ACCESS  read-only
    STATUS      current
    DESCRIPTION "Total number of Web Image Optimization quantizing image failed"
    ::= { affirmedServicesContentHttpProxyServiceStatisticsChassisLevelWebImageOptDetailEntry 9 }

affirmedServicesContentHttpProxyServiceStatisticsChassisLevelWebImageOptDetailNumwebimageoptremovemetadatafailed OBJECT-TYPE
    SYNTAX      ConfdString
    MAX-ACCESS  read-only
    STATUS      current
    DESCRIPTION "Total number of Web Image Optimization removing metadata failed"
    ::= { affirmedServicesContentHttpProxyServiceStatisticsChassisLevelWebImageOptDetailEntry 10 }

affirmedServicesContentHttpProxyServiceStatisticsChassisLevelWebImageOptDetailNumwebimageoptresizeimagefailed OBJECT-TYPE
    SYNTAX      ConfdString
    MAX-ACCESS  read-only
    STATUS      current
    DESCRIPTION "Total number of Web Image Optimization resizing image failed"
    ::= { affirmedServicesContentHttpProxyServiceStatisticsChassisLevelWebImageOptDetailEntry 11 }

affirmedServicesContentHttpProxyServiceStatisticsChassisLevelWebImageOptDetailNumwebimageoptalphablendimagefailed OBJECT-TYPE
    SYNTAX      ConfdString
    MAX-ACCESS  read-only
    STATUS      current
    DESCRIPTION "Total number of Web Image Optimization alpha blend image failed"
    ::= { affirmedServicesContentHttpProxyServiceStatisticsChassisLevelWebImageOptDetailEntry 12 }

affirmedServicesContentHttpProxyServiceStatisticsChassisLevelWebImageOptDetailNumwebimageoptgetsrcimageformatfailed OBJECT-TYPE
    SYNTAX      ConfdString
    MAX-ACCESS  read-only
    STATUS      current
    DESCRIPTION "Total number of Web Image Optimization getting source image format failed"
    ::= { affirmedServicesContentHttpProxyServiceStatisticsChassisLevelWebImageOptDetailEntry 13 }

affirmedServicesContentHttpProxyServiceStatisticsChassisLevelWebImageOptDetailNumwebimageoptgettgtimageformatfailed OBJECT-TYPE
    SYNTAX      ConfdString
    MAX-ACCESS  read-only
    STATUS      current
    DESCRIPTION "Total number of Web Image Optimization getting target image format failed"
    ::= { affirmedServicesContentHttpProxyServiceStatisticsChassisLevelWebImageOptDetailEntry 14 }

affirmedServicesContentHttpProxyServiceStatisticsChassisLevelWebImageOptDetailNumwebimageoptjpegattempts OBJECT-TYPE
    SYNTAX      ConfdString
    MAX-ACCESS  read-only
    STATUS      current
    DESCRIPTION "Total number of Web Image Optimization JPEG Attempts"
    ::= { affirmedServicesContentHttpProxyServiceStatisticsChassisLevelWebImageOptDetailEntry 15 }

affirmedServicesContentHttpProxyServiceStatisticsChassisLevelWebImageOptDetailNumwebimageoptjpegsuccesses OBJECT-TYPE
    SYNTAX      ConfdString
    MAX-ACCESS  read-only
    STATUS      current
    DESCRIPTION "Total number of Web Image Optimization JPEG successes"
    ::= { affirmedServicesContentHttpProxyServiceStatisticsChassisLevelWebImageOptDetailEntry 16 }

affirmedServicesContentHttpProxyServiceStatisticsChassisLevelWebImageOptDetailNumwebimageoptjpegbytesattempt OBJECT-TYPE
    SYNTAX      ConfdString
    MAX-ACCESS  read-only
    STATUS      current
    DESCRIPTION "Total number of Web Image Optimization JPEG bytes attempt to adapt"
    ::= { affirmedServicesContentHttpProxyServiceStatisticsChassisLevelWebImageOptDetailEntry 17 }

affirmedServicesContentHttpProxyServiceStatisticsChassisLevelWebImageOptDetailNumwebimageoptjpegbytesnotadapted OBJECT-TYPE
    SYNTAX      ConfdString
    MAX-ACCESS  read-only
    STATUS      current
    DESCRIPTION "Total number of Web Image Optimization JPEG bytes not adapted"
    ::= { affirmedServicesContentHttpProxyServiceStatisticsChassisLevelWebImageOptDetailEntry 18 }

affirmedServicesContentHttpProxyServiceStatisticsChassisLevelWebImageOptDetailNumwebimageoptjpegbytesadapted OBJECT-TYPE
    SYNTAX      ConfdString
    MAX-ACCESS  read-only
    STATUS      current
    DESCRIPTION "Total number of Web Image Optimization JPEG bytes adapted"
    ::= { affirmedServicesContentHttpProxyServiceStatisticsChassisLevelWebImageOptDetailEntry 19 }

affirmedServicesContentHttpProxyServiceStatisticsChassisLevelWebImageOptDetailNumwebimageoptgifattempts OBJECT-TYPE
    SYNTAX      ConfdString
    MAX-ACCESS  read-only
    STATUS      current
    DESCRIPTION "Total number of Web Image Optimization GIF Attempts"
    ::= { affirmedServicesContentHttpProxyServiceStatisticsChassisLevelWebImageOptDetailEntry 20 }

affirmedServicesContentHttpProxyServiceStatisticsChassisLevelWebImageOptDetailNumwebimageoptgifsuccesses OBJECT-TYPE
    SYNTAX      ConfdString
    MAX-ACCESS  read-only
    STATUS      current
    DESCRIPTION "Total number of Web Image Optimization GIF successes"
    ::= { affirmedServicesContentHttpProxyServiceStatisticsChassisLevelWebImageOptDetailEntry 21 }

affirmedServicesContentHttpProxyServiceStatisticsChassisLevelWebImageOptDetailNumwebimageoptgifbytesattempt OBJECT-TYPE
    SYNTAX      ConfdString
    MAX-ACCESS  read-only
    STATUS      current
    DESCRIPTION "Total number of Web Image Optimization GIF bytes attempt to adapt"
    ::= { affirmedServicesContentHttpProxyServiceStatisticsChassisLevelWebImageOptDetailEntry 22 }

affirmedServicesContentHttpProxyServiceStatisticsChassisLevelWebImageOptDetailNumwebimageoptgifbytesnotadapted OBJECT-TYPE
    SYNTAX      ConfdString
    MAX-ACCESS  read-only
    STATUS      current
    DESCRIPTION "Total number of Web Image Optimization GIF bytes not adapted"
    ::= { affirmedServicesContentHttpProxyServiceStatisticsChassisLevelWebImageOptDetailEntry 23 }

affirmedServicesContentHttpProxyServiceStatisticsChassisLevelWebImageOptDetailNumwebimageoptgifbytesadapted OBJECT-TYPE
    SYNTAX      ConfdString
    MAX-ACCESS  read-only
    STATUS      current
    DESCRIPTION "Total number of Web Image Optimization GIF bytes adapted"
    ::= { affirmedServicesContentHttpProxyServiceStatisticsChassisLevelWebImageOptDetailEntry 24 }

affirmedServicesContentHttpProxyServiceStatisticsChassisLevelWebImageOptDetailNumwebimageoptpngattempts OBJECT-TYPE
    SYNTAX      ConfdString
    MAX-ACCESS  read-only
    STATUS      current
    DESCRIPTION "Total number of Web Image Optimization PNG Attempts"
    ::= { affirmedServicesContentHttpProxyServiceStatisticsChassisLevelWebImageOptDetailEntry 25 }

affirmedServicesContentHttpProxyServiceStatisticsChassisLevelWebImageOptDetailNumwebimageoptpngsuccesses OBJECT-TYPE
    SYNTAX      ConfdString
    MAX-ACCESS  read-only
    STATUS      current
    DESCRIPTION "Total number of Web Image Optimization PNG successes"
    ::= { affirmedServicesContentHttpProxyServiceStatisticsChassisLevelWebImageOptDetailEntry 26 }

affirmedServicesContentHttpProxyServiceStatisticsChassisLevelWebImageOptDetailNumwebimageoptpngbytesattempt OBJECT-TYPE
    SYNTAX      ConfdString
    MAX-ACCESS  read-only
    STATUS      current
    DESCRIPTION "Total number of Web Image Optimization PNG bytes attempt to adapt"
    ::= { affirmedServicesContentHttpProxyServiceStatisticsChassisLevelWebImageOptDetailEntry 27 }

affirmedServicesContentHttpProxyServiceStatisticsChassisLevelWebImageOptDetailNumwebimageoptpngbytesnotadapted OBJECT-TYPE
    SYNTAX      ConfdString
    MAX-ACCESS  read-only
    STATUS      current
    DESCRIPTION "Total number of Web Image Optimization PNG bytes not adapted"
    ::= { affirmedServicesContentHttpProxyServiceStatisticsChassisLevelWebImageOptDetailEntry 28 }

affirmedServicesContentHttpProxyServiceStatisticsChassisLevelWebImageOptDetailNumwebimageoptpngbytesadapted OBJECT-TYPE
    SYNTAX      ConfdString
    MAX-ACCESS  read-only
    STATUS      current
    DESCRIPTION "Total number of Web Image Optimization PNG bytes adapted"
    ::= { affirmedServicesContentHttpProxyServiceStatisticsChassisLevelWebImageOptDetailEntry 29 }

affirmedServicesContentHttpProxyServiceStatisticsChassisLevelWebImageOptDetailNumwebimageoptsrcmaxsizeexceeded OBJECT-TYPE
    SYNTAX      ConfdString
    MAX-ACCESS  read-only
    STATUS      current
    DESCRIPTION "Total number of Web Image Optimization source max size exceeded"
    ::= { affirmedServicesContentHttpProxyServiceStatisticsChassisLevelWebImageOptDetailEntry 30 }

affirmedServicesContentHttpProxyServiceStatisticsChassisLevelWebImageOptDetailNumwebimageoptcontenttypemismatches OBJECT-TYPE
    SYNTAX      ConfdString
    MAX-ACCESS  read-only
    STATUS      current
    DESCRIPTION "Total number of Web Image Optimization with Content-type mismatches"
    ::= { affirmedServicesContentHttpProxyServiceStatisticsChassisLevelWebImageOptDetailEntry 31 }

affirmedServicesContentHttpProxyServiceStatisticsChassisLevelWebImageOptDetailNumwebimageoptcpuoverload OBJECT-TYPE
    SYNTAX      ConfdString
    MAX-ACCESS  read-only
    STATUS      current
    DESCRIPTION "Total number of Web Image Optimization CPU overload"
    ::= { affirmedServicesContentHttpProxyServiceStatisticsChassisLevelWebImageOptDetailEntry 32 }

affirmedServicesContentHttpProxyServiceStatisticsChassisLevelTcpOptzTable OBJECT-TYPE
    SYNTAX      SEQUENCE OF AffirmedServicesContentHttpProxyServiceStatisticsChassisLevelTcpOptzEntry
    MAX-ACCESS  not-accessible
    STATUS      current
    DESCRIPTION ""
    ::= { affirmedServicesContentHttpProxyServiceStatisticsChassisLevel 15 }

affirmedServicesContentHttpProxyServiceStatisticsChassisLevelTcpOptzEntry OBJECT-TYPE
    SYNTAX      AffirmedServicesContentHttpProxyServiceStatisticsChassisLevelTcpOptzEntry
    MAX-ACCESS  not-accessible
    STATUS      current
    DESCRIPTION ""
    INDEX { affirmedServicesContentHttpProxyServiceStatisticsChassisLevelTcpOptzChassis }
        ::= { affirmedServicesContentHttpProxyServiceStatisticsChassisLevelTcpOptzTable 1 }

AffirmedServicesContentHttpProxyServiceStatisticsChassisLevelTcpOptzEntry ::=
    SEQUENCE {
        affirmedServicesContentHttpProxyServiceStatisticsChassisLevelTcpOptzChassis Unsigned32,
        affirmedServicesContentHttpProxyServiceStatisticsChassisLevelTcpOptzNumtotalclientconnections ConfdString,
        affirmedServicesContentHttpProxyServiceStatisticsChassisLevelTcpOptzNumactiveclientconnections ConfdString,
        affirmedServicesContentHttpProxyServiceStatisticsChassisLevelTcpOptzNumservicedclientconnections ConfdString,
        affirmedServicesContentHttpProxyServiceStatisticsChassisLevelTcpOptzNumfailedservicedclientconnections ConfdString,
        affirmedServicesContentHttpProxyServiceStatisticsChassisLevelTcpOptzNumtotalserverconnections ConfdString,
        affirmedServicesContentHttpProxyServiceStatisticsChassisLevelTcpOptzNumactiveserverconnections ConfdString,
        affirmedServicesContentHttpProxyServiceStatisticsChassisLevelTcpOptzNumservicedserverconnections ConfdString,
        affirmedServicesContentHttpProxyServiceStatisticsChassisLevelTcpOptzNumfailedservicedserverconnections ConfdString,
        affirmedServicesContentHttpProxyServiceStatisticsChassisLevelTcpOptzNumintelligentbufferingapplied ConfdString
    }

affirmedServicesContentHttpProxyServiceStatisticsChassisLevelTcpOptzChassis OBJECT-TYPE
    SYNTAX      Unsigned32
    MAX-ACCESS  not-accessible
    STATUS      current
    DESCRIPTION "chassis ID"
    ::= { affirmedServicesContentHttpProxyServiceStatisticsChassisLevelTcpOptzEntry 1 }

affirmedServicesContentHttpProxyServiceStatisticsChassisLevelTcpOptzNumtotalclientconnections OBJECT-TYPE
    SYNTAX      ConfdString
    MAX-ACCESS  read-only
    STATUS      current
    DESCRIPTION "Total number of TCP client connections"
    ::= { affirmedServicesContentHttpProxyServiceStatisticsChassisLevelTcpOptzEntry 2 }

affirmedServicesContentHttpProxyServiceStatisticsChassisLevelTcpOptzNumactiveclientconnections OBJECT-TYPE
    SYNTAX      ConfdString
    MAX-ACCESS  read-only
    STATUS      current
    DESCRIPTION "Number of active TCP client connections"
    ::= { affirmedServicesContentHttpProxyServiceStatisticsChassisLevelTcpOptzEntry 3 }

affirmedServicesContentHttpProxyServiceStatisticsChassisLevelTcpOptzNumservicedclientconnections OBJECT-TYPE
    SYNTAX      ConfdString
    MAX-ACCESS  read-only
    STATUS      current
    DESCRIPTION "Number of client connections that TCP Optimization Service applied"
    ::= { affirmedServicesContentHttpProxyServiceStatisticsChassisLevelTcpOptzEntry 4 }

affirmedServicesContentHttpProxyServiceStatisticsChassisLevelTcpOptzNumfailedservicedclientconnections OBJECT-TYPE
    SYNTAX      ConfdString
    MAX-ACCESS  read-only
    STATUS      current
    DESCRIPTION "Number of tcp client connections that failed applying TCP Optimization service"
    ::= { affirmedServicesContentHttpProxyServiceStatisticsChassisLevelTcpOptzEntry 5 }

affirmedServicesContentHttpProxyServiceStatisticsChassisLevelTcpOptzNumtotalserverconnections OBJECT-TYPE
    SYNTAX      ConfdString
    MAX-ACCESS  read-only
    STATUS      current
    DESCRIPTION "Total number of TCP server connections"
    ::= { affirmedServicesContentHttpProxyServiceStatisticsChassisLevelTcpOptzEntry 6 }

affirmedServicesContentHttpProxyServiceStatisticsChassisLevelTcpOptzNumactiveserverconnections OBJECT-TYPE
    SYNTAX      ConfdString
    MAX-ACCESS  read-only
    STATUS      current
    DESCRIPTION "Number of active TCP server connections"
    ::= { affirmedServicesContentHttpProxyServiceStatisticsChassisLevelTcpOptzEntry 7 }

affirmedServicesContentHttpProxyServiceStatisticsChassisLevelTcpOptzNumservicedserverconnections OBJECT-TYPE
    SYNTAX      ConfdString
    MAX-ACCESS  read-only
    STATUS      current
    DESCRIPTION "Number of server connections that TCP Optimization Service applied"
    ::= { affirmedServicesContentHttpProxyServiceStatisticsChassisLevelTcpOptzEntry 8 }

affirmedServicesContentHttpProxyServiceStatisticsChassisLevelTcpOptzNumfailedservicedserverconnections OBJECT-TYPE
    SYNTAX      ConfdString
    MAX-ACCESS  read-only
    STATUS      current
    DESCRIPTION "Number of tcp server connections that failed applying TCP Optimization service"
    ::= { affirmedServicesContentHttpProxyServiceStatisticsChassisLevelTcpOptzEntry 9 }

affirmedServicesContentHttpProxyServiceStatisticsChassisLevelTcpOptzNumintelligentbufferingapplied OBJECT-TYPE
    SYNTAX      ConfdString
    MAX-ACCESS  read-only
    STATUS      current
    DESCRIPTION "Number of tcp server connections that applied intelligent buffering service"
    ::= { affirmedServicesContentHttpProxyServiceStatisticsChassisLevelTcpOptzEntry 10 }

affirmedServicesContentHttpProxyServiceStatisticsChassisLevelDnsResolutionTable OBJECT-TYPE
    SYNTAX      SEQUENCE OF AffirmedServicesContentHttpProxyServiceStatisticsChassisLevelDnsResolutionEntry
    MAX-ACCESS  not-accessible
    STATUS      current
    DESCRIPTION ""
    ::= { affirmedServicesContentHttpProxyServiceStatisticsChassisLevel 16 }

affirmedServicesContentHttpProxyServiceStatisticsChassisLevelDnsResolutionEntry OBJECT-TYPE
    SYNTAX      AffirmedServicesContentHttpProxyServiceStatisticsChassisLevelDnsResolutionEntry
    MAX-ACCESS  not-accessible
    STATUS      current
    DESCRIPTION ""
    INDEX { affirmedServicesContentHttpProxyServiceStatisticsChassisLevelDnsResolutionChassis }
        ::= { affirmedServicesContentHttpProxyServiceStatisticsChassisLevelDnsResolutionTable 1 }

AffirmedServicesContentHttpProxyServiceStatisticsChassisLevelDnsResolutionEntry ::=
    SEQUENCE {
        affirmedServicesContentHttpProxyServiceStatisticsChassisLevelDnsResolutionChassis Unsigned32,
        affirmedServicesContentHttpProxyServiceStatisticsChassisLevelDnsResolutionNumdnsresolutiontotal ConfdString,
        affirmedServicesContentHttpProxyServiceStatisticsChassisLevelDnsResolutionNumdnsresolutioncurrent ConfdString,
        affirmedServicesContentHttpProxyServiceStatisticsChassisLevelDnsResolutionNumdnsresolutionsuccess ConfdString,
        affirmedServicesContentHttpProxyServiceStatisticsChassisLevelDnsResolutionNumdnsresolutionfail ConfdString,
        affirmedServicesContentHttpProxyServiceStatisticsChassisLevelDnsResolutionNumdnsresolutionv4attempts ConfdString,
        affirmedServicesContentHttpProxyServiceStatisticsChassisLevelDnsResolutionNumdnsresolutionv6attempts ConfdString,
        affirmedServicesContentHttpProxyServiceStatisticsChassisLevelDnsResolutionNumdnsresolutionv4v6attempts ConfdString,
        affirmedServicesContentHttpProxyServiceStatisticsChassisLevelDnsResolutionNumdnsresolutioncached ConfdString,
        affirmedServicesContentHttpProxyServiceStatisticsChassisLevelDnsResolutionNumdnsresolutionv4results ConfdString,
        affirmedServicesContentHttpProxyServiceStatisticsChassisLevelDnsResolutionNumdnsresolutionv6results ConfdString,
        affirmedServicesContentHttpProxyServiceStatisticsChassisLevelDnsResolutionNumdnsresolutionv4v6results ConfdString,
        affirmedServicesContentHttpProxyServiceStatisticsChassisLevelDnsResolutionNumdnsresolutiondropped ConfdString,
        affirmedServicesContentHttpProxyServiceStatisticsChassisLevelDnsResolutionNumdnsresolutioncanceled ConfdString,
        affirmedServicesContentHttpProxyServiceStatisticsChassisLevelDnsResolutionNumdnsresolutionnoreach ConfdString,
        affirmedServicesContentHttpProxyServiceStatisticsChassisLevelDnsResolutionNumdnsresolutiontimeout ConfdString,
        affirmedServicesContentHttpProxyServiceStatisticsChassisLevelDnsResolutionNumdnsresolutionnodata ConfdString,
        affirmedServicesContentHttpProxyServiceStatisticsChassisLevelDnsResolutionNumdnsresolutionnotfound ConfdString,
        affirmedServicesContentHttpProxyServiceStatisticsChassisLevelDnsResolutionNumdnsresolutionrefused ConfdString,
        affirmedServicesContentHttpProxyServiceStatisticsChassisLevelDnsResolutionNumdnsresolutionothers ConfdString
    }

affirmedServicesContentHttpProxyServiceStatisticsChassisLevelDnsResolutionChassis OBJECT-TYPE
    SYNTAX      Unsigned32
    MAX-ACCESS  not-accessible
    STATUS      current
    DESCRIPTION "chassis ID"
    ::= { affirmedServicesContentHttpProxyServiceStatisticsChassisLevelDnsResolutionEntry 1 }

affirmedServicesContentHttpProxyServiceStatisticsChassisLevelDnsResolutionNumdnsresolutiontotal OBJECT-TYPE
    SYNTAX      ConfdString
    MAX-ACCESS  read-only
    STATUS      current
    DESCRIPTION "Total number of DNS Resolution Query Attempts"
    ::= { affirmedServicesContentHttpProxyServiceStatisticsChassisLevelDnsResolutionEntry 2 }

affirmedServicesContentHttpProxyServiceStatisticsChassisLevelDnsResolutionNumdnsresolutioncurrent OBJECT-TYPE
    SYNTAX      ConfdString
    MAX-ACCESS  read-only
    STATUS      current
    DESCRIPTION "Current number of DNS Resolution Query IPv4 Attempts"
    ::= { affirmedServicesContentHttpProxyServiceStatisticsChassisLevelDnsResolutionEntry 3 }

affirmedServicesContentHttpProxyServiceStatisticsChassisLevelDnsResolutionNumdnsresolutionsuccess OBJECT-TYPE
    SYNTAX      ConfdString
    MAX-ACCESS  read-only
    STATUS      current
    DESCRIPTION "Total number of DNS Resolution Query Success"
    ::= { affirmedServicesContentHttpProxyServiceStatisticsChassisLevelDnsResolutionEntry 4 }

affirmedServicesContentHttpProxyServiceStatisticsChassisLevelDnsResolutionNumdnsresolutionfail OBJECT-TYPE
    SYNTAX      ConfdString
    MAX-ACCESS  read-only
    STATUS      current
    DESCRIPTION "Total number of DNS Resolution Query Failures"
    ::= { affirmedServicesContentHttpProxyServiceStatisticsChassisLevelDnsResolutionEntry 5 }

affirmedServicesContentHttpProxyServiceStatisticsChassisLevelDnsResolutionNumdnsresolutionv4attempts OBJECT-TYPE
    SYNTAX      ConfdString
    MAX-ACCESS  read-only
    STATUS      current
    DESCRIPTION "Total number of DNS Resolution Query IPv4 Requests"
    ::= { affirmedServicesContentHttpProxyServiceStatisticsChassisLevelDnsResolutionEntry 6 }

affirmedServicesContentHttpProxyServiceStatisticsChassisLevelDnsResolutionNumdnsresolutionv6attempts OBJECT-TYPE
    SYNTAX      ConfdString
    MAX-ACCESS  read-only
    STATUS      current
    DESCRIPTION "Total number of DNS Resolution Query IPv6 Requests"
    ::= { affirmedServicesContentHttpProxyServiceStatisticsChassisLevelDnsResolutionEntry 7 }

affirmedServicesContentHttpProxyServiceStatisticsChassisLevelDnsResolutionNumdnsresolutionv4v6attempts OBJECT-TYPE
    SYNTAX      ConfdString
    MAX-ACCESS  read-only
    STATUS      current
    DESCRIPTION "Total number of DNS Resolution Query IPv4v6 Requests"
    ::= { affirmedServicesContentHttpProxyServiceStatisticsChassisLevelDnsResolutionEntry 8 }

affirmedServicesContentHttpProxyServiceStatisticsChassisLevelDnsResolutionNumdnsresolutioncached OBJECT-TYPE
    SYNTAX      ConfdString
    MAX-ACCESS  read-only
    STATUS      current
    DESCRIPTION "Total number of DNS Resolution Query Cache Hit Results"
    ::= { affirmedServicesContentHttpProxyServiceStatisticsChassisLevelDnsResolutionEntry 9 }

affirmedServicesContentHttpProxyServiceStatisticsChassisLevelDnsResolutionNumdnsresolutionv4results OBJECT-TYPE
    SYNTAX      ConfdString
    MAX-ACCESS  read-only
    STATUS      current
    DESCRIPTION "Total number of DNS Resolution Query IPv4 Results"
    ::= { affirmedServicesContentHttpProxyServiceStatisticsChassisLevelDnsResolutionEntry 10 }

affirmedServicesContentHttpProxyServiceStatisticsChassisLevelDnsResolutionNumdnsresolutionv6results OBJECT-TYPE
    SYNTAX      ConfdString
    MAX-ACCESS  read-only
    STATUS      current
    DESCRIPTION "Total number of DNS Resolution Query IPv6 Results"
    ::= { affirmedServicesContentHttpProxyServiceStatisticsChassisLevelDnsResolutionEntry 11 }

affirmedServicesContentHttpProxyServiceStatisticsChassisLevelDnsResolutionNumdnsresolutionv4v6results OBJECT-TYPE
    SYNTAX      ConfdString
    MAX-ACCESS  read-only
    STATUS      current
    DESCRIPTION "Total number of DNS Resolution Query IPv4v6 Results"
    ::= { affirmedServicesContentHttpProxyServiceStatisticsChassisLevelDnsResolutionEntry 12 }

affirmedServicesContentHttpProxyServiceStatisticsChassisLevelDnsResolutionNumdnsresolutiondropped OBJECT-TYPE
    SYNTAX      ConfdString
    MAX-ACCESS  read-only
    STATUS      current
    DESCRIPTION "Total number of DNS Resolution Query Dropped, Not Sent"
    ::= { affirmedServicesContentHttpProxyServiceStatisticsChassisLevelDnsResolutionEntry 13 }

affirmedServicesContentHttpProxyServiceStatisticsChassisLevelDnsResolutionNumdnsresolutioncanceled OBJECT-TYPE
    SYNTAX      ConfdString
    MAX-ACCESS  read-only
    STATUS      current
    DESCRIPTION "Total number of DNS Resolution Query Canceled"
    ::= { affirmedServicesContentHttpProxyServiceStatisticsChassisLevelDnsResolutionEntry 14 }

affirmedServicesContentHttpProxyServiceStatisticsChassisLevelDnsResolutionNumdnsresolutionnoreach OBJECT-TYPE
    SYNTAX      ConfdString
    MAX-ACCESS  read-only
    STATUS      current
    DESCRIPTION "Total number of DNS Resolution Server Not-Reachable"
    ::= { affirmedServicesContentHttpProxyServiceStatisticsChassisLevelDnsResolutionEntry 15 }

affirmedServicesContentHttpProxyServiceStatisticsChassisLevelDnsResolutionNumdnsresolutiontimeout OBJECT-TYPE
    SYNTAX      ConfdString
    MAX-ACCESS  read-only
    STATUS      current
    DESCRIPTION "Total number of DNS Resolution Response Timeout"
    ::= { affirmedServicesContentHttpProxyServiceStatisticsChassisLevelDnsResolutionEntry 16 }

affirmedServicesContentHttpProxyServiceStatisticsChassisLevelDnsResolutionNumdnsresolutionnodata OBJECT-TYPE
    SYNTAX      ConfdString
    MAX-ACCESS  read-only
    STATUS      current
    DESCRIPTION "Total number of DNS Resolution Response No Data"
    ::= { affirmedServicesContentHttpProxyServiceStatisticsChassisLevelDnsResolutionEntry 17 }

affirmedServicesContentHttpProxyServiceStatisticsChassisLevelDnsResolutionNumdnsresolutionnotfound OBJECT-TYPE
    SYNTAX      ConfdString
    MAX-ACCESS  read-only
    STATUS      current
    DESCRIPTION "Total number of DNS Resolution Response Name Not Found"
    ::= { affirmedServicesContentHttpProxyServiceStatisticsChassisLevelDnsResolutionEntry 18 }

affirmedServicesContentHttpProxyServiceStatisticsChassisLevelDnsResolutionNumdnsresolutionrefused OBJECT-TYPE
    SYNTAX      ConfdString
    MAX-ACCESS  read-only
    STATUS      current
    DESCRIPTION "Total number of DNS Resolution Response Server Refused"
    ::= { affirmedServicesContentHttpProxyServiceStatisticsChassisLevelDnsResolutionEntry 19 }

affirmedServicesContentHttpProxyServiceStatisticsChassisLevelDnsResolutionNumdnsresolutionothers OBJECT-TYPE
    SYNTAX      ConfdString
    MAX-ACCESS  read-only
    STATUS      current
    DESCRIPTION "Total number of DNS Resolution Response Dailure With Other Reason"
    ::= { affirmedServicesContentHttpProxyServiceStatisticsChassisLevelDnsResolutionEntry 20 }

affirmedServicesContentHttpProxyServiceStatisticsChassisLevelTlsTable OBJECT-TYPE
    SYNTAX      SEQUENCE OF AffirmedServicesContentHttpProxyServiceStatisticsChassisLevelTlsEntry
    MAX-ACCESS  not-accessible
    STATUS      current
    DESCRIPTION ""
    ::= { affirmedServicesContentHttpProxyServiceStatisticsChassisLevel 17 }

affirmedServicesContentHttpProxyServiceStatisticsChassisLevelTlsEntry OBJECT-TYPE
    SYNTAX      AffirmedServicesContentHttpProxyServiceStatisticsChassisLevelTlsEntry
    MAX-ACCESS  not-accessible
    STATUS      current
    DESCRIPTION ""
    INDEX { affirmedServicesContentHttpProxyServiceStatisticsChassisLevelTlsChassis }
        ::= { affirmedServicesContentHttpProxyServiceStatisticsChassisLevelTlsTable 1 }

AffirmedServicesContentHttpProxyServiceStatisticsChassisLevelTlsEntry ::=
    SEQUENCE {
        affirmedServicesContentHttpProxyServiceStatisticsChassisLevelTlsChassis Unsigned32,
        affirmedServicesContentHttpProxyServiceStatisticsChassisLevelTlsNumtotalclientconnections ConfdString,
        affirmedServicesContentHttpProxyServiceStatisticsChassisLevelTlsNumcurrentclientconnections ConfdString,
        affirmedServicesContentHttpProxyServiceStatisticsChassisLevelTlsNumtermclientconnections ConfdString,
        affirmedServicesContentHttpProxyServiceStatisticsChassisLevelTlsNumipv4clientconnections ConfdString,
        affirmedServicesContentHttpProxyServiceStatisticsChassisLevelTlsNumipv6clientconnections ConfdString,
        affirmedServicesContentHttpProxyServiceStatisticsChassisLevelTlsNumclientbytesrecvd ConfdString,
        affirmedServicesContentHttpProxyServiceStatisticsChassisLevelTlsNumclientbytessent ConfdString,
        affirmedServicesContentHttpProxyServiceStatisticsChassisLevelTlsNumclientprototlsv10 ConfdString,
        affirmedServicesContentHttpProxyServiceStatisticsChassisLevelTlsNumclientprototlsv11 ConfdString,
        affirmedServicesContentHttpProxyServiceStatisticsChassisLevelTlsNumclientprototlsv12 ConfdString,
        affirmedServicesContentHttpProxyServiceStatisticsChassisLevelTlsNumclienttlserrors ConfdString,
        affirmedServicesContentHttpProxyServiceStatisticsChassisLevelTlsNumclientfderrors ConfdString,
        affirmedServicesContentHttpProxyServiceStatisticsChassisLevelTlsNumclienthandshakeerrors ConfdString,
        affirmedServicesContentHttpProxyServiceStatisticsChassisLevelTlsNumclientreaderrors ConfdString,
        affirmedServicesContentHttpProxyServiceStatisticsChassisLevelTlsNumclientwriteerrors ConfdString,
        affirmedServicesContentHttpProxyServiceStatisticsChassisLevelTlsNumtotalserverconnections ConfdString,
        affirmedServicesContentHttpProxyServiceStatisticsChassisLevelTlsNumcurrentserverconnections ConfdString,
        affirmedServicesContentHttpProxyServiceStatisticsChassisLevelTlsNumorigserverconnections ConfdString,
        affirmedServicesContentHttpProxyServiceStatisticsChassisLevelTlsNumipv4serverconnections ConfdString,
        affirmedServicesContentHttpProxyServiceStatisticsChassisLevelTlsNumipv6serverconnections ConfdString,
        affirmedServicesContentHttpProxyServiceStatisticsChassisLevelTlsNumserverbytesrecvd ConfdString,
        affirmedServicesContentHttpProxyServiceStatisticsChassisLevelTlsNumserverbytessent ConfdString,
        affirmedServicesContentHttpProxyServiceStatisticsChassisLevelTlsNumservertlsv10 ConfdString,
        affirmedServicesContentHttpProxyServiceStatisticsChassisLevelTlsNumservertlsv11 ConfdString,
        affirmedServicesContentHttpProxyServiceStatisticsChassisLevelTlsNumservertlsv12 ConfdString,
        affirmedServicesContentHttpProxyServiceStatisticsChassisLevelTlsNumservertlserror ConfdString,
        affirmedServicesContentHttpProxyServiceStatisticsChassisLevelTlsNumserverfderrors ConfdString,
        affirmedServicesContentHttpProxyServiceStatisticsChassisLevelTlsNumserverhandshakeerrors ConfdString,
        affirmedServicesContentHttpProxyServiceStatisticsChassisLevelTlsNumserverautherrors ConfdString,
        affirmedServicesContentHttpProxyServiceStatisticsChassisLevelTlsNumserverreaderrors ConfdString,
        affirmedServicesContentHttpProxyServiceStatisticsChassisLevelTlsNumserverwriteerrors ConfdString
    }

affirmedServicesContentHttpProxyServiceStatisticsChassisLevelTlsChassis OBJECT-TYPE
    SYNTAX      Unsigned32
    MAX-ACCESS  not-accessible
    STATUS      current
    DESCRIPTION "chassis ID"
    ::= { affirmedServicesContentHttpProxyServiceStatisticsChassisLevelTlsEntry 1 }

affirmedServicesContentHttpProxyServiceStatisticsChassisLevelTlsNumtotalclientconnections OBJECT-TYPE
    SYNTAX      ConfdString
    MAX-ACCESS  read-only
    STATUS      current
    DESCRIPTION "Total number of client connections"
    ::= { affirmedServicesContentHttpProxyServiceStatisticsChassisLevelTlsEntry 2 }

affirmedServicesContentHttpProxyServiceStatisticsChassisLevelTlsNumcurrentclientconnections OBJECT-TYPE
    SYNTAX      ConfdString
    MAX-ACCESS  read-only
    STATUS      current
    DESCRIPTION "Total number of client connections currently in use"
    ::= { affirmedServicesContentHttpProxyServiceStatisticsChassisLevelTlsEntry 3 }

affirmedServicesContentHttpProxyServiceStatisticsChassisLevelTlsNumtermclientconnections OBJECT-TYPE
    SYNTAX      ConfdString
    MAX-ACCESS  read-only
    STATUS      current
    DESCRIPTION "Total number of terminated connections"
    ::= { affirmedServicesContentHttpProxyServiceStatisticsChassisLevelTlsEntry 4 }

affirmedServicesContentHttpProxyServiceStatisticsChassisLevelTlsNumipv4clientconnections OBJECT-TYPE
    SYNTAX      ConfdString
    MAX-ACCESS  read-only
    STATUS      current
    DESCRIPTION "Total number of IPv4 client connections"
    ::= { affirmedServicesContentHttpProxyServiceStatisticsChassisLevelTlsEntry 5 }

affirmedServicesContentHttpProxyServiceStatisticsChassisLevelTlsNumipv6clientconnections OBJECT-TYPE
    SYNTAX      ConfdString
    MAX-ACCESS  read-only
    STATUS      current
    DESCRIPTION "Total number of IPv6 client connections"
    ::= { affirmedServicesContentHttpProxyServiceStatisticsChassisLevelTlsEntry 6 }

affirmedServicesContentHttpProxyServiceStatisticsChassisLevelTlsNumclientbytesrecvd OBJECT-TYPE
    SYNTAX      ConfdString
    MAX-ACCESS  read-only
    STATUS      current
    DESCRIPTION "Total number of bytes received from client"
    ::= { affirmedServicesContentHttpProxyServiceStatisticsChassisLevelTlsEntry 7 }

affirmedServicesContentHttpProxyServiceStatisticsChassisLevelTlsNumclientbytessent OBJECT-TYPE
    SYNTAX      ConfdString
    MAX-ACCESS  read-only
    STATUS      current
    DESCRIPTION "Total number of bytes sent to client"
    ::= { affirmedServicesContentHttpProxyServiceStatisticsChassisLevelTlsEntry 8 }

affirmedServicesContentHttpProxyServiceStatisticsChassisLevelTlsNumclientprototlsv10 OBJECT-TYPE
    SYNTAX      ConfdString
    MAX-ACCESS  read-only
    STATUS      current
    DESCRIPTION "Total number of TLS1.0 client requests received"
    ::= { affirmedServicesContentHttpProxyServiceStatisticsChassisLevelTlsEntry 9 }

affirmedServicesContentHttpProxyServiceStatisticsChassisLevelTlsNumclientprototlsv11 OBJECT-TYPE
    SYNTAX      ConfdString
    MAX-ACCESS  read-only
    STATUS      current
    DESCRIPTION "Total number of TLS1.1 client requests received"
    ::= { affirmedServicesContentHttpProxyServiceStatisticsChassisLevelTlsEntry 10 }

affirmedServicesContentHttpProxyServiceStatisticsChassisLevelTlsNumclientprototlsv12 OBJECT-TYPE
    SYNTAX      ConfdString
    MAX-ACCESS  read-only
    STATUS      current
    DESCRIPTION "Total number of TLS1.2 client requests received"
    ::= { affirmedServicesContentHttpProxyServiceStatisticsChassisLevelTlsEntry 11 }

affirmedServicesContentHttpProxyServiceStatisticsChassisLevelTlsNumclienttlserrors OBJECT-TYPE
    SYNTAX      ConfdString
    MAX-ACCESS  read-only
    STATUS      current
    DESCRIPTION "Total number of Client TLS Errors"
    ::= { affirmedServicesContentHttpProxyServiceStatisticsChassisLevelTlsEntry 12 }

affirmedServicesContentHttpProxyServiceStatisticsChassisLevelTlsNumclientfderrors OBJECT-TYPE
    SYNTAX      ConfdString
    MAX-ACCESS  read-only
    STATUS      current
    DESCRIPTION "Total number of Client set FD Errors"
    ::= { affirmedServicesContentHttpProxyServiceStatisticsChassisLevelTlsEntry 13 }

affirmedServicesContentHttpProxyServiceStatisticsChassisLevelTlsNumclienthandshakeerrors OBJECT-TYPE
    SYNTAX      ConfdString
    MAX-ACCESS  read-only
    STATUS      current
    DESCRIPTION "Total number of Client handshake Errors"
    ::= { affirmedServicesContentHttpProxyServiceStatisticsChassisLevelTlsEntry 14 }

affirmedServicesContentHttpProxyServiceStatisticsChassisLevelTlsNumclientreaderrors OBJECT-TYPE
    SYNTAX      ConfdString
    MAX-ACCESS  read-only
    STATUS      current
    DESCRIPTION "Total number of Client read Errors"
    ::= { affirmedServicesContentHttpProxyServiceStatisticsChassisLevelTlsEntry 15 }

affirmedServicesContentHttpProxyServiceStatisticsChassisLevelTlsNumclientwriteerrors OBJECT-TYPE
    SYNTAX      ConfdString
    MAX-ACCESS  read-only
    STATUS      current
    DESCRIPTION "Total number of Client write Errors"
    ::= { affirmedServicesContentHttpProxyServiceStatisticsChassisLevelTlsEntry 16 }

affirmedServicesContentHttpProxyServiceStatisticsChassisLevelTlsNumtotalserverconnections OBJECT-TYPE
    SYNTAX      ConfdString
    MAX-ACCESS  read-only
    STATUS      current
    DESCRIPTION "Total number of server connections"
    ::= { affirmedServicesContentHttpProxyServiceStatisticsChassisLevelTlsEntry 17 }

affirmedServicesContentHttpProxyServiceStatisticsChassisLevelTlsNumcurrentserverconnections OBJECT-TYPE
    SYNTAX      ConfdString
    MAX-ACCESS  read-only
    STATUS      current
    DESCRIPTION "Total number of server connections currently in use"
    ::= { affirmedServicesContentHttpProxyServiceStatisticsChassisLevelTlsEntry 18 }

affirmedServicesContentHttpProxyServiceStatisticsChassisLevelTlsNumorigserverconnections OBJECT-TYPE
    SYNTAX      ConfdString
    MAX-ACCESS  read-only
    STATUS      current
    DESCRIPTION "Total number of originated connections"
    ::= { affirmedServicesContentHttpProxyServiceStatisticsChassisLevelTlsEntry 19 }

affirmedServicesContentHttpProxyServiceStatisticsChassisLevelTlsNumipv4serverconnections OBJECT-TYPE
    SYNTAX      ConfdString
    MAX-ACCESS  read-only
    STATUS      current
    DESCRIPTION "Total number of IPv4 server connections"
    ::= { affirmedServicesContentHttpProxyServiceStatisticsChassisLevelTlsEntry 20 }

affirmedServicesContentHttpProxyServiceStatisticsChassisLevelTlsNumipv6serverconnections OBJECT-TYPE
    SYNTAX      ConfdString
    MAX-ACCESS  read-only
    STATUS      current
    DESCRIPTION "Total number of IPv6 server connections"
    ::= { affirmedServicesContentHttpProxyServiceStatisticsChassisLevelTlsEntry 21 }

affirmedServicesContentHttpProxyServiceStatisticsChassisLevelTlsNumserverbytesrecvd OBJECT-TYPE
    SYNTAX      ConfdString
    MAX-ACCESS  read-only
    STATUS      current
    DESCRIPTION "Total number of bytes received from server"
    ::= { affirmedServicesContentHttpProxyServiceStatisticsChassisLevelTlsEntry 22 }

affirmedServicesContentHttpProxyServiceStatisticsChassisLevelTlsNumserverbytessent OBJECT-TYPE
    SYNTAX      ConfdString
    MAX-ACCESS  read-only
    STATUS      current
    DESCRIPTION "Total number of bytes sent to server"
    ::= { affirmedServicesContentHttpProxyServiceStatisticsChassisLevelTlsEntry 23 }

affirmedServicesContentHttpProxyServiceStatisticsChassisLevelTlsNumservertlsv10 OBJECT-TYPE
    SYNTAX      ConfdString
    MAX-ACCESS  read-only
    STATUS      current
    DESCRIPTION "Total number of TLS1.0 server requests sent"
    ::= { affirmedServicesContentHttpProxyServiceStatisticsChassisLevelTlsEntry 24 }

affirmedServicesContentHttpProxyServiceStatisticsChassisLevelTlsNumservertlsv11 OBJECT-TYPE
    SYNTAX      ConfdString
    MAX-ACCESS  read-only
    STATUS      current
    DESCRIPTION "Total number of TLS1.1 server requests sent"
    ::= { affirmedServicesContentHttpProxyServiceStatisticsChassisLevelTlsEntry 25 }

affirmedServicesContentHttpProxyServiceStatisticsChassisLevelTlsNumservertlsv12 OBJECT-TYPE
    SYNTAX      ConfdString
    MAX-ACCESS  read-only
    STATUS      current
    DESCRIPTION "Total number of TLS1.2 server requests sent"
    ::= { affirmedServicesContentHttpProxyServiceStatisticsChassisLevelTlsEntry 26 }

affirmedServicesContentHttpProxyServiceStatisticsChassisLevelTlsNumservertlserror OBJECT-TYPE
    SYNTAX      ConfdString
    MAX-ACCESS  read-only
    STATUS      current
    DESCRIPTION "Total number of Server TLS Errors"
    ::= { affirmedServicesContentHttpProxyServiceStatisticsChassisLevelTlsEntry 27 }

affirmedServicesContentHttpProxyServiceStatisticsChassisLevelTlsNumserverfderrors OBJECT-TYPE
    SYNTAX      ConfdString
    MAX-ACCESS  read-only
    STATUS      current
    DESCRIPTION "Total number of Server set FD Errors"
    ::= { affirmedServicesContentHttpProxyServiceStatisticsChassisLevelTlsEntry 28 }

affirmedServicesContentHttpProxyServiceStatisticsChassisLevelTlsNumserverhandshakeerrors OBJECT-TYPE
    SYNTAX      ConfdString
    MAX-ACCESS  read-only
    STATUS      current
    DESCRIPTION "Total number of server handshake Errors"
    ::= { affirmedServicesContentHttpProxyServiceStatisticsChassisLevelTlsEntry 29 }

affirmedServicesContentHttpProxyServiceStatisticsChassisLevelTlsNumserverautherrors OBJECT-TYPE
    SYNTAX      ConfdString
    MAX-ACCESS  read-only
    STATUS      current
    DESCRIPTION "Total number of server authentication Errors"
    ::= { affirmedServicesContentHttpProxyServiceStatisticsChassisLevelTlsEntry 30 }

affirmedServicesContentHttpProxyServiceStatisticsChassisLevelTlsNumserverreaderrors OBJECT-TYPE
    SYNTAX      ConfdString
    MAX-ACCESS  read-only
    STATUS      current
    DESCRIPTION "Total number of Server read Errors"
    ::= { affirmedServicesContentHttpProxyServiceStatisticsChassisLevelTlsEntry 31 }

affirmedServicesContentHttpProxyServiceStatisticsChassisLevelTlsNumserverwriteerrors OBJECT-TYPE
    SYNTAX      ConfdString
    MAX-ACCESS  read-only
    STATUS      current
    DESCRIPTION "Total number of Server write Errors"
    ::= { affirmedServicesContentHttpProxyServiceStatisticsChassisLevelTlsEntry 32 }

affirmedServicesContentHttpProxyServiceStatisticsChassisLevelUrlRWTable OBJECT-TYPE
    SYNTAX      SEQUENCE OF AffirmedServicesContentHttpProxyServiceStatisticsChassisLevelUrlRWEntry
    MAX-ACCESS  not-accessible
    STATUS      current
    DESCRIPTION ""
    ::= { affirmedServicesContentHttpProxyServiceStatisticsChassisLevel 18 }

affirmedServicesContentHttpProxyServiceStatisticsChassisLevelUrlRWEntry OBJECT-TYPE
    SYNTAX      AffirmedServicesContentHttpProxyServiceStatisticsChassisLevelUrlRWEntry
    MAX-ACCESS  not-accessible
    STATUS      current
    DESCRIPTION ""
    INDEX { affirmedServicesContentHttpProxyServiceStatisticsChassisLevelUrlRWChassis }
        ::= { affirmedServicesContentHttpProxyServiceStatisticsChassisLevelUrlRWTable 1 }

AffirmedServicesContentHttpProxyServiceStatisticsChassisLevelUrlRWEntry ::=
    SEQUENCE {
        affirmedServicesContentHttpProxyServiceStatisticsChassisLevelUrlRWChassis Unsigned32,
        affirmedServicesContentHttpProxyServiceStatisticsChassisLevelUrlRWNumurlrwattempts ConfdString,
        affirmedServicesContentHttpProxyServiceStatisticsChassisLevelUrlRWNumurlrwsuccess ConfdString,
        affirmedServicesContentHttpProxyServiceStatisticsChassisLevelUrlRWNumurlrwdnslkupv4attempts ConfdString,
        affirmedServicesContentHttpProxyServiceStatisticsChassisLevelUrlRWNumurlrwdnslkupv6attempts ConfdString,
        affirmedServicesContentHttpProxyServiceStatisticsChassisLevelUrlRWNumurlrwdnslkupv4success ConfdString,
        affirmedServicesContentHttpProxyServiceStatisticsChassisLevelUrlRWNumurlrwdnslkupv6success ConfdString,
        affirmedServicesContentHttpProxyServiceStatisticsChassisLevelUrlRWNumurlrwdnslkupv4v6attempts ConfdString
    }

affirmedServicesContentHttpProxyServiceStatisticsChassisLevelUrlRWChassis OBJECT-TYPE
    SYNTAX      Unsigned32
    MAX-ACCESS  not-accessible
    STATUS      current
    DESCRIPTION "chassis ID"
    ::= { affirmedServicesContentHttpProxyServiceStatisticsChassisLevelUrlRWEntry 1 }

affirmedServicesContentHttpProxyServiceStatisticsChassisLevelUrlRWNumurlrwattempts OBJECT-TYPE
    SYNTAX      ConfdString
    MAX-ACCESS  read-only
    STATUS      current
    DESCRIPTION "Total number of url-rewrite attempts"
    ::= { affirmedServicesContentHttpProxyServiceStatisticsChassisLevelUrlRWEntry 2 }

affirmedServicesContentHttpProxyServiceStatisticsChassisLevelUrlRWNumurlrwsuccess OBJECT-TYPE
    SYNTAX      ConfdString
    MAX-ACCESS  read-only
    STATUS      current
    DESCRIPTION "Total number of url-rewrite Successes"
    ::= { affirmedServicesContentHttpProxyServiceStatisticsChassisLevelUrlRWEntry 3 }

affirmedServicesContentHttpProxyServiceStatisticsChassisLevelUrlRWNumurlrwdnslkupv4attempts OBJECT-TYPE
    SYNTAX      ConfdString
    MAX-ACCESS  read-only
    STATUS      current
    DESCRIPTION "Total number of url-rewrite DNS lookup IPv4 attempts"
    ::= { affirmedServicesContentHttpProxyServiceStatisticsChassisLevelUrlRWEntry 4 }

affirmedServicesContentHttpProxyServiceStatisticsChassisLevelUrlRWNumurlrwdnslkupv6attempts OBJECT-TYPE
    SYNTAX      ConfdString
    MAX-ACCESS  read-only
    STATUS      current
    DESCRIPTION "Total number of url-rewrite DNS lookup IPv6 attempts"
    ::= { affirmedServicesContentHttpProxyServiceStatisticsChassisLevelUrlRWEntry 5 }

affirmedServicesContentHttpProxyServiceStatisticsChassisLevelUrlRWNumurlrwdnslkupv4success OBJECT-TYPE
    SYNTAX      ConfdString
    MAX-ACCESS  read-only
    STATUS      current
    DESCRIPTION "Total number of url-rewrite DNS lookup IPv4 success"
    ::= { affirmedServicesContentHttpProxyServiceStatisticsChassisLevelUrlRWEntry 6 }

affirmedServicesContentHttpProxyServiceStatisticsChassisLevelUrlRWNumurlrwdnslkupv6success OBJECT-TYPE
    SYNTAX      ConfdString
    MAX-ACCESS  read-only
    STATUS      current
    DESCRIPTION "Total number of url-rewrite DNS lookup IPv6 success"
    ::= { affirmedServicesContentHttpProxyServiceStatisticsChassisLevelUrlRWEntry 7 }

affirmedServicesContentHttpProxyServiceStatisticsChassisLevelUrlRWNumurlrwdnslkupv4v6attempts OBJECT-TYPE
    SYNTAX      ConfdString
    MAX-ACCESS  read-only
    STATUS      current
    DESCRIPTION "Total number of url-rewrite DNS lookup IPv4v6 attempts"
    ::= { affirmedServicesContentHttpProxyServiceStatisticsChassisLevelUrlRWEntry 8 }

affirmedServicesContentHttpProxyServiceStatisticsChassisLevelBefTable OBJECT-TYPE
    SYNTAX      SEQUENCE OF AffirmedServicesContentHttpProxyServiceStatisticsChassisLevelBefEntry
    MAX-ACCESS  not-accessible
    STATUS      current
    DESCRIPTION ""
    ::= { affirmedServicesContentHttpProxyServiceStatisticsChassisLevel 19 }

affirmedServicesContentHttpProxyServiceStatisticsChassisLevelBefEntry OBJECT-TYPE
    SYNTAX      AffirmedServicesContentHttpProxyServiceStatisticsChassisLevelBefEntry
    MAX-ACCESS  not-accessible
    STATUS      current
    DESCRIPTION ""
    INDEX { affirmedServicesContentHttpProxyServiceStatisticsChassisLevelBefChassis }
        ::= { affirmedServicesContentHttpProxyServiceStatisticsChassisLevelBefTable 1 }

AffirmedServicesContentHttpProxyServiceStatisticsChassisLevelBefEntry ::=
    SEQUENCE {
        affirmedServicesContentHttpProxyServiceStatisticsChassisLevelBefChassis Unsigned32,
        affirmedServicesContentHttpProxyServiceStatisticsChassisLevelBefNumbefrequestprocessedlocally ConfdString,
        affirmedServicesContentHttpProxyServiceStatisticsChassisLevelBefNumbefrequestredirectsuccess ConfdString,
        affirmedServicesContentHttpProxyServiceStatisticsChassisLevelBefNumbefrequestredirectfail ConfdString,
        affirmedServicesContentHttpProxyServiceStatisticsChassisLevelBefNumbefrequestredirectreceived ConfdString,
        affirmedServicesContentHttpProxyServiceStatisticsChassisLevelBefNumbefresponseredirectsuccess ConfdString,
        affirmedServicesContentHttpProxyServiceStatisticsChassisLevelBefNumbefresponseredirectfail ConfdString,
        affirmedServicesContentHttpProxyServiceStatisticsChassisLevelBefNumbefresponseredirectreceived ConfdString,
        affirmedServicesContentHttpProxyServiceStatisticsChassisLevelBefNumbefcurrentlyidleconnections ConfdString,
        affirmedServicesContentHttpProxyServiceStatisticsChassisLevelBefNumbefreusedconnections ConfdString
    }

affirmedServicesContentHttpProxyServiceStatisticsChassisLevelBefChassis OBJECT-TYPE
    SYNTAX      Unsigned32
    MAX-ACCESS  not-accessible
    STATUS      current
    DESCRIPTION "chassis ID"
    ::= { affirmedServicesContentHttpProxyServiceStatisticsChassisLevelBefEntry 1 }

affirmedServicesContentHttpProxyServiceStatisticsChassisLevelBefNumbefrequestprocessedlocally OBJECT-TYPE
    SYNTAX      ConfdString
    MAX-ACCESS  read-only
    STATUS      current
    DESCRIPTION "Total number of requests not redirected but processed locally"
    ::= { affirmedServicesContentHttpProxyServiceStatisticsChassisLevelBefEntry 2 }

affirmedServicesContentHttpProxyServiceStatisticsChassisLevelBefNumbefrequestredirectsuccess OBJECT-TYPE
    SYNTAX      ConfdString
    MAX-ACCESS  read-only
    STATUS      current
    DESCRIPTION "Total number of back-end forwarding request redirection successes"
    ::= { affirmedServicesContentHttpProxyServiceStatisticsChassisLevelBefEntry 3 }

affirmedServicesContentHttpProxyServiceStatisticsChassisLevelBefNumbefrequestredirectfail OBJECT-TYPE
    SYNTAX      ConfdString
    MAX-ACCESS  read-only
    STATUS      current
    DESCRIPTION "Total number of back-end forwarding request redirection failures"
    ::= { affirmedServicesContentHttpProxyServiceStatisticsChassisLevelBefEntry 4 }

affirmedServicesContentHttpProxyServiceStatisticsChassisLevelBefNumbefrequestredirectreceived OBJECT-TYPE
    SYNTAX      ConfdString
    MAX-ACCESS  read-only
    STATUS      current
    DESCRIPTION "Total number of back-end forwarding request redirections received"
    ::= { affirmedServicesContentHttpProxyServiceStatisticsChassisLevelBefEntry 5 }

affirmedServicesContentHttpProxyServiceStatisticsChassisLevelBefNumbefresponseredirectsuccess OBJECT-TYPE
    SYNTAX      ConfdString
    MAX-ACCESS  read-only
    STATUS      current
    DESCRIPTION "Total number of back-end forwarding response redirection successes"
    ::= { affirmedServicesContentHttpProxyServiceStatisticsChassisLevelBefEntry 6 }

affirmedServicesContentHttpProxyServiceStatisticsChassisLevelBefNumbefresponseredirectfail OBJECT-TYPE
    SYNTAX      ConfdString
    MAX-ACCESS  read-only
    STATUS      current
    DESCRIPTION "Total number of back-end forwarding response redirection failures"
    ::= { affirmedServicesContentHttpProxyServiceStatisticsChassisLevelBefEntry 7 }

affirmedServicesContentHttpProxyServiceStatisticsChassisLevelBefNumbefresponseredirectreceived OBJECT-TYPE
    SYNTAX      ConfdString
    MAX-ACCESS  read-only
    STATUS      current
    DESCRIPTION "Total number of back-end forwarding response redirections received"
    ::= { affirmedServicesContentHttpProxyServiceStatisticsChassisLevelBefEntry 8 }

affirmedServicesContentHttpProxyServiceStatisticsChassisLevelBefNumbefcurrentlyidleconnections OBJECT-TYPE
    SYNTAX      ConfdString
    MAX-ACCESS  read-only
    STATUS      current
    DESCRIPTION "The number of BEF connections in the idle connection pool"
    ::= { affirmedServicesContentHttpProxyServiceStatisticsChassisLevelBefEntry 9 }

affirmedServicesContentHttpProxyServiceStatisticsChassisLevelBefNumbefreusedconnections OBJECT-TYPE
    SYNTAX      ConfdString
    MAX-ACCESS  read-only
    STATUS      current
    DESCRIPTION "The number of times idle BEF connections were reused"
    ::= { affirmedServicesContentHttpProxyServiceStatisticsChassisLevelBefEntry 10 }

affirmedServicesContentHttpProxyServiceStatisticsChassisLevelPremptDnsTable OBJECT-TYPE
    SYNTAX      SEQUENCE OF AffirmedServicesContentHttpProxyServiceStatisticsChassisLevelPremptDnsEntry
    MAX-ACCESS  not-accessible
    STATUS      current
    DESCRIPTION ""
    ::= { affirmedServicesContentHttpProxyServiceStatisticsChassisLevel 20 }

affirmedServicesContentHttpProxyServiceStatisticsChassisLevelPremptDnsEntry OBJECT-TYPE
    SYNTAX      AffirmedServicesContentHttpProxyServiceStatisticsChassisLevelPremptDnsEntry
    MAX-ACCESS  not-accessible
    STATUS      current
    DESCRIPTION ""
    INDEX { affirmedServicesContentHttpProxyServiceStatisticsChassisLevelPremptDnsChassis }
        ::= { affirmedServicesContentHttpProxyServiceStatisticsChassisLevelPremptDnsTable 1 }

AffirmedServicesContentHttpProxyServiceStatisticsChassisLevelPremptDnsEntry ::=
    SEQUENCE {
        affirmedServicesContentHttpProxyServiceStatisticsChassisLevelPremptDnsChassis Unsigned32,
        affirmedServicesContentHttpProxyServiceStatisticsChassisLevelPremptDnsNumpremptdnsrsptotal ConfdString,
        affirmedServicesContentHttpProxyServiceStatisticsChassisLevelPremptDnsNumpremptdnsrspurlrwtotal ConfdString,
        affirmedServicesContentHttpProxyServiceStatisticsChassisLevelPremptDnsNumpremptdnsrspbypass ConfdString,
        affirmedServicesContentHttpProxyServiceStatisticsChassisLevelPremptDnsNumpremptdnsrspchunked ConfdString,
        affirmedServicesContentHttpProxyServiceStatisticsChassisLevelPremptDnsNumpremptdnsreqrecvdtotal ConfdString,
        affirmedServicesContentHttpProxyServiceStatisticsChassisLevelPremptDnsNumpremptdnsreqsrvdtotal ConfdString,
        affirmedServicesContentHttpProxyServiceStatisticsChassisLevelPremptDnsNumpremptdnsreqfailtotal ConfdString
    }

affirmedServicesContentHttpProxyServiceStatisticsChassisLevelPremptDnsChassis OBJECT-TYPE
    SYNTAX      Unsigned32
    MAX-ACCESS  not-accessible
    STATUS      current
    DESCRIPTION "chassis ID"
    ::= { affirmedServicesContentHttpProxyServiceStatisticsChassisLevelPremptDnsEntry 1 }

affirmedServicesContentHttpProxyServiceStatisticsChassisLevelPremptDnsNumpremptdnsrsptotal OBJECT-TYPE
    SYNTAX      ConfdString
    MAX-ACCESS  read-only
    STATUS      current
    DESCRIPTION "Total number of HTTP Response applied preemptive-dns"
    ::= { affirmedServicesContentHttpProxyServiceStatisticsChassisLevelPremptDnsEntry 2 }

affirmedServicesContentHttpProxyServiceStatisticsChassisLevelPremptDnsNumpremptdnsrspurlrwtotal OBJECT-TYPE
    SYNTAX      ConfdString
    MAX-ACCESS  read-only
    STATUS      current
    DESCRIPTION "Total number URL rewrote in HTTP Response"
    ::= { affirmedServicesContentHttpProxyServiceStatisticsChassisLevelPremptDnsEntry 3 }

affirmedServicesContentHttpProxyServiceStatisticsChassisLevelPremptDnsNumpremptdnsrspbypass OBJECT-TYPE
    SYNTAX      ConfdString
    MAX-ACCESS  read-only
    STATUS      current
    DESCRIPTION "Total number of Responses dropping content-length header"
    ::= { affirmedServicesContentHttpProxyServiceStatisticsChassisLevelPremptDnsEntry 4 }

affirmedServicesContentHttpProxyServiceStatisticsChassisLevelPremptDnsNumpremptdnsrspchunked OBJECT-TYPE
    SYNTAX      ConfdString
    MAX-ACCESS  read-only
    STATUS      current
    DESCRIPTION "Total number of Responses got chunked"
    ::= { affirmedServicesContentHttpProxyServiceStatisticsChassisLevelPremptDnsEntry 5 }

affirmedServicesContentHttpProxyServiceStatisticsChassisLevelPremptDnsNumpremptdnsreqrecvdtotal OBJECT-TYPE
    SYNTAX      ConfdString
    MAX-ACCESS  read-only
    STATUS      current
    DESCRIPTION "Total number of Updated Requests Received"
    ::= { affirmedServicesContentHttpProxyServiceStatisticsChassisLevelPremptDnsEntry 6 }

affirmedServicesContentHttpProxyServiceStatisticsChassisLevelPremptDnsNumpremptdnsreqsrvdtotal OBJECT-TYPE
    SYNTAX      ConfdString
    MAX-ACCESS  read-only
    STATUS      current
    DESCRIPTION "Total number of Updated Requests Serviced"
    ::= { affirmedServicesContentHttpProxyServiceStatisticsChassisLevelPremptDnsEntry 7 }

affirmedServicesContentHttpProxyServiceStatisticsChassisLevelPremptDnsNumpremptdnsreqfailtotal OBJECT-TYPE
    SYNTAX      ConfdString
    MAX-ACCESS  read-only
    STATUS      current
    DESCRIPTION "Total number of Updated Requests Failed Service"
    ::= { affirmedServicesContentHttpProxyServiceStatisticsChassisLevelPremptDnsEntry 8 }

affirmedServicesContentHttpProxyServiceStatisticsChassisLevelFraudDetectionTable OBJECT-TYPE
    SYNTAX      SEQUENCE OF AffirmedServicesContentHttpProxyServiceStatisticsChassisLevelFraudDetectionEntry
    MAX-ACCESS  not-accessible
    STATUS      current
    DESCRIPTION ""
    ::= { affirmedServicesContentHttpProxyServiceStatisticsChassisLevel 21 }

affirmedServicesContentHttpProxyServiceStatisticsChassisLevelFraudDetectionEntry OBJECT-TYPE
    SYNTAX      AffirmedServicesContentHttpProxyServiceStatisticsChassisLevelFraudDetectionEntry
    MAX-ACCESS  not-accessible
    STATUS      current
    DESCRIPTION ""
    INDEX { affirmedServicesContentHttpProxyServiceStatisticsChassisLevelFraudDetectionChassis }
        ::= { affirmedServicesContentHttpProxyServiceStatisticsChassisLevelFraudDetectionTable 1 }

AffirmedServicesContentHttpProxyServiceStatisticsChassisLevelFraudDetectionEntry ::=
    SEQUENCE {
        affirmedServicesContentHttpProxyServiceStatisticsChassisLevelFraudDetectionChassis Unsigned32,
        affirmedServicesContentHttpProxyServiceStatisticsChassisLevelFraudDetectionNumfrauddetectionreq ConfdString,
        affirmedServicesContentHttpProxyServiceStatisticsChassisLevelFraudDetectionNumfrauddetectionreqnonfraud ConfdString,
        affirmedServicesContentHttpProxyServiceStatisticsChassisLevelFraudDetectionNumfrauddetectionreqfraud ConfdString,
        affirmedServicesContentHttpProxyServiceStatisticsChassisLevelFraudDetectionNumfrauddetectionreqfraudheader ConfdString,
        affirmedServicesContentHttpProxyServiceStatisticsChassisLevelFraudDetectionNumfrauddetectionreqfrauddns ConfdString,
        affirmedServicesContentHttpProxyServiceStatisticsChassisLevelFraudDetectionNumfrauddetectionreqfraudallowed ConfdString,
        affirmedServicesContentHttpProxyServiceStatisticsChassisLevelFraudDetectionNumfrauddetectionreqfraudblocked ConfdString
    }

affirmedServicesContentHttpProxyServiceStatisticsChassisLevelFraudDetectionChassis OBJECT-TYPE
    SYNTAX      Unsigned32
    MAX-ACCESS  not-accessible
    STATUS      current
    DESCRIPTION "chassis ID"
    ::= { affirmedServicesContentHttpProxyServiceStatisticsChassisLevelFraudDetectionEntry 1 }

affirmedServicesContentHttpProxyServiceStatisticsChassisLevelFraudDetectionNumfrauddetectionreq OBJECT-TYPE
    SYNTAX      ConfdString
    MAX-ACCESS  read-only
    STATUS      current
    DESCRIPTION "Total number of Request Validation Attempts"
    ::= { affirmedServicesContentHttpProxyServiceStatisticsChassisLevelFraudDetectionEntry 2 }

affirmedServicesContentHttpProxyServiceStatisticsChassisLevelFraudDetectionNumfrauddetectionreqnonfraud OBJECT-TYPE
    SYNTAX      ConfdString
    MAX-ACCESS  read-only
    STATUS      current
    DESCRIPTION "Total number of Non-Fraudulent Requests"
    ::= { affirmedServicesContentHttpProxyServiceStatisticsChassisLevelFraudDetectionEntry 3 }

affirmedServicesContentHttpProxyServiceStatisticsChassisLevelFraudDetectionNumfrauddetectionreqfraud OBJECT-TYPE
    SYNTAX      ConfdString
    MAX-ACCESS  read-only
    STATUS      current
    DESCRIPTION "Total number of Fraudulent Requests"
    ::= { affirmedServicesContentHttpProxyServiceStatisticsChassisLevelFraudDetectionEntry 4 }

affirmedServicesContentHttpProxyServiceStatisticsChassisLevelFraudDetectionNumfrauddetectionreqfraudheader OBJECT-TYPE
    SYNTAX      ConfdString
    MAX-ACCESS  read-only
    STATUS      current
    DESCRIPTION "Total number of Request Header Consistency Check Failures"
    ::= { affirmedServicesContentHttpProxyServiceStatisticsChassisLevelFraudDetectionEntry 5 }

affirmedServicesContentHttpProxyServiceStatisticsChassisLevelFraudDetectionNumfrauddetectionreqfrauddns OBJECT-TYPE
    SYNTAX      ConfdString
    MAX-ACCESS  read-only
    STATUS      current
    DESCRIPTION "Total number of Request DNS Check Failures"
    ::= { affirmedServicesContentHttpProxyServiceStatisticsChassisLevelFraudDetectionEntry 6 }

affirmedServicesContentHttpProxyServiceStatisticsChassisLevelFraudDetectionNumfrauddetectionreqfraudallowed OBJECT-TYPE
    SYNTAX      ConfdString
    MAX-ACCESS  read-only
    STATUS      current
    DESCRIPTION "Total number of Fraudulent Requests Allowed"
    ::= { affirmedServicesContentHttpProxyServiceStatisticsChassisLevelFraudDetectionEntry 7 }

affirmedServicesContentHttpProxyServiceStatisticsChassisLevelFraudDetectionNumfrauddetectionreqfraudblocked OBJECT-TYPE
    SYNTAX      ConfdString
    MAX-ACCESS  read-only
    STATUS      current
    DESCRIPTION "Total number of Fraudulent Requests Blocked"
    ::= { affirmedServicesContentHttpProxyServiceStatisticsChassisLevelFraudDetectionEntry 8 }

affirmedServicesContentHttpProxyServiceStatisticsChassisLevelVideoTable OBJECT-TYPE
    SYNTAX      SEQUENCE OF AffirmedServicesContentHttpProxyServiceStatisticsChassisLevelVideoEntry
    MAX-ACCESS  not-accessible
    STATUS      current
    DESCRIPTION ""
    ::= { affirmedServicesContentHttpProxyServiceStatisticsChassisLevel 22 }

affirmedServicesContentHttpProxyServiceStatisticsChassisLevelVideoEntry OBJECT-TYPE
    SYNTAX      AffirmedServicesContentHttpProxyServiceStatisticsChassisLevelVideoEntry
    MAX-ACCESS  not-accessible
    STATUS      current
    DESCRIPTION ""
    INDEX { affirmedServicesContentHttpProxyServiceStatisticsChassisLevelVideoChassis }
        ::= { affirmedServicesContentHttpProxyServiceStatisticsChassisLevelVideoTable 1 }

AffirmedServicesContentHttpProxyServiceStatisticsChassisLevelVideoEntry ::=
    SEQUENCE {
        affirmedServicesContentHttpProxyServiceStatisticsChassisLevelVideoChassis Unsigned32,
        affirmedServicesContentHttpProxyServiceStatisticsChassisLevelVideoVideoattempts ConfdString,
        affirmedServicesContentHttpProxyServiceStatisticsChassisLevelVideoVideosuccesses ConfdString,
        affirmedServicesContentHttpProxyServiceStatisticsChassisLevelVideoVideosuccessescached ConfdString,
        affirmedServicesContentHttpProxyServiceStatisticsChassisLevelVideoVideoservedfromcache ConfdString,
        affirmedServicesContentHttpProxyServiceStatisticsChassisLevelVideoVideoaborts ConfdString,
        affirmedServicesContentHttpProxyServiceStatisticsChassisLevelVideoVideofailures ConfdString,
        affirmedServicesContentHttpProxyServiceStatisticsChassisLevelVideoVideoseekrequests ConfdString,
        affirmedServicesContentHttpProxyServiceStatisticsChassisLevelVideoFlvvideosuccesses ConfdString,
        affirmedServicesContentHttpProxyServiceStatisticsChassisLevelVideoFlvvideosuccessescached ConfdString,
        affirmedServicesContentHttpProxyServiceStatisticsChassisLevelVideoFlvvideoservedfromcache ConfdString,
        affirmedServicesContentHttpProxyServiceStatisticsChassisLevelVideoFlvvideoaborts ConfdString,
        affirmedServicesContentHttpProxyServiceStatisticsChassisLevelVideoMp4videosuccesses ConfdString,
        affirmedServicesContentHttpProxyServiceStatisticsChassisLevelVideoMp4videosuccessescached ConfdString,
        affirmedServicesContentHttpProxyServiceStatisticsChassisLevelVideoMp4videoservedfromcache ConfdString,
        affirmedServicesContentHttpProxyServiceStatisticsChassisLevelVideoMp4videoaborts ConfdString,
        affirmedServicesContentHttpProxyServiceStatisticsChassisLevelVideoDailymotionvideosuccesses ConfdString,
        affirmedServicesContentHttpProxyServiceStatisticsChassisLevelVideoDailymotionvideosuccessescached ConfdString,
        affirmedServicesContentHttpProxyServiceStatisticsChassisLevelVideoDailymotionvideoservedfromcache ConfdString,
        affirmedServicesContentHttpProxyServiceStatisticsChassisLevelVideoDailymotionvideoaborts ConfdString,
        affirmedServicesContentHttpProxyServiceStatisticsChassisLevelVideoMetacafevideosuccesses ConfdString,
        affirmedServicesContentHttpProxyServiceStatisticsChassisLevelVideoMetacafevideosuccessescached ConfdString,
        affirmedServicesContentHttpProxyServiceStatisticsChassisLevelVideoMetacafevideoservedfromcache ConfdString,
        affirmedServicesContentHttpProxyServiceStatisticsChassisLevelVideoMetacafevideoaborts ConfdString,
        affirmedServicesContentHttpProxyServiceStatisticsChassisLevelVideoVideosizemin ConfdString,
        affirmedServicesContentHttpProxyServiceStatisticsChassisLevelVideoVideosizemax ConfdString,
        affirmedServicesContentHttpProxyServiceStatisticsChassisLevelVideoVideosizeaverage ConfdString,
        affirmedServicesContentHttpProxyServiceStatisticsChassisLevelVideoVideosizetotal ConfdString,
        affirmedServicesContentHttpProxyServiceStatisticsChassisLevelVideoFlvvideosizemin ConfdString,
        affirmedServicesContentHttpProxyServiceStatisticsChassisLevelVideoFlvvideosizemax ConfdString,
        affirmedServicesContentHttpProxyServiceStatisticsChassisLevelVideoFlvvideosizeaverage ConfdString,
        affirmedServicesContentHttpProxyServiceStatisticsChassisLevelVideoFlvvideosizetotal ConfdString,
        affirmedServicesContentHttpProxyServiceStatisticsChassisLevelVideoMp4videosizemin ConfdString,
        affirmedServicesContentHttpProxyServiceStatisticsChassisLevelVideoMp4videosizemax ConfdString,
        affirmedServicesContentHttpProxyServiceStatisticsChassisLevelVideoMp4videosizeaverage ConfdString,
        affirmedServicesContentHttpProxyServiceStatisticsChassisLevelVideoMp4videosizetotal ConfdString,
        affirmedServicesContentHttpProxyServiceStatisticsChassisLevelVideoFlvvideodurationmin ConfdString,
        affirmedServicesContentHttpProxyServiceStatisticsChassisLevelVideoFlvvideodurationmax ConfdString,
        affirmedServicesContentHttpProxyServiceStatisticsChassisLevelVideoFlvvideodurationaverage ConfdString,
        affirmedServicesContentHttpProxyServiceStatisticsChassisLevelVideoFlvvideodurationtotal ConfdString,
        affirmedServicesContentHttpProxyServiceStatisticsChassisLevelVideoMp4videodurationmin ConfdString,
        affirmedServicesContentHttpProxyServiceStatisticsChassisLevelVideoMp4videodurationmax ConfdString,
        affirmedServicesContentHttpProxyServiceStatisticsChassisLevelVideoMp4videodurationaverage ConfdString,
        affirmedServicesContentHttpProxyServiceStatisticsChassisLevelVideoMp4videodurationtotal ConfdString,
        affirmedServicesContentHttpProxyServiceStatisticsChassisLevelVideoVideoservedbytesfromcache ConfdString,
        affirmedServicesContentHttpProxyServiceStatisticsChassisLevelVideoVideopacedrequests ConfdString,
        affirmedServicesContentHttpProxyServiceStatisticsChassisLevelVideoVideosizepacedtotal ConfdString,
        affirmedServicesContentHttpProxyServiceStatisticsChassisLevelVideoVideosizepacedsent ConfdString,
        affirmedServicesContentHttpProxyServiceStatisticsChassisLevelVideoWebmvideosuccesses ConfdString,
        affirmedServicesContentHttpProxyServiceStatisticsChassisLevelVideoWebmvideosuccessescached ConfdString,
        affirmedServicesContentHttpProxyServiceStatisticsChassisLevelVideoWebmvideoservedfromcache ConfdString,
        affirmedServicesContentHttpProxyServiceStatisticsChassisLevelVideoWebmvideoaborts ConfdString,
        affirmedServicesContentHttpProxyServiceStatisticsChassisLevelVideoWebmvideosizemin ConfdString,
        affirmedServicesContentHttpProxyServiceStatisticsChassisLevelVideoWebmvideosizemax ConfdString,
        affirmedServicesContentHttpProxyServiceStatisticsChassisLevelVideoWebmvideosizeaverage ConfdString,
        affirmedServicesContentHttpProxyServiceStatisticsChassisLevelVideoWebmvideosizetotal ConfdString,
        affirmedServicesContentHttpProxyServiceStatisticsChassisLevelVideoWebmvideodurationmin ConfdString,
        affirmedServicesContentHttpProxyServiceStatisticsChassisLevelVideoWebmvideodurationmax ConfdString,
        affirmedServicesContentHttpProxyServiceStatisticsChassisLevelVideoWebmvideodurationaverage ConfdString,
        affirmedServicesContentHttpProxyServiceStatisticsChassisLevelVideoWebmvideodurationtotal ConfdString
    }

affirmedServicesContentHttpProxyServiceStatisticsChassisLevelVideoChassis OBJECT-TYPE
    SYNTAX      Unsigned32
    MAX-ACCESS  not-accessible
    STATUS      current
    DESCRIPTION "chassis ID"
    ::= { affirmedServicesContentHttpProxyServiceStatisticsChassisLevelVideoEntry 1 }

affirmedServicesContentHttpProxyServiceStatisticsChassisLevelVideoVideoattempts OBJECT-TYPE
    SYNTAX      ConfdString
    MAX-ACCESS  read-only
    STATUS      current
    DESCRIPTION "Number of video attempts"
    ::= { affirmedServicesContentHttpProxyServiceStatisticsChassisLevelVideoEntry 2 }

affirmedServicesContentHttpProxyServiceStatisticsChassisLevelVideoVideosuccesses OBJECT-TYPE
    SYNTAX      ConfdString
    MAX-ACCESS  read-only
    STATUS      current
    DESCRIPTION "Number of video successes"
    ::= { affirmedServicesContentHttpProxyServiceStatisticsChassisLevelVideoEntry 3 }

affirmedServicesContentHttpProxyServiceStatisticsChassisLevelVideoVideosuccessescached OBJECT-TYPE
    SYNTAX      ConfdString
    MAX-ACCESS  read-only
    STATUS      current
    DESCRIPTION "Number of video successes cached"
    ::= { affirmedServicesContentHttpProxyServiceStatisticsChassisLevelVideoEntry 4 }

affirmedServicesContentHttpProxyServiceStatisticsChassisLevelVideoVideoservedfromcache OBJECT-TYPE
    SYNTAX      ConfdString
    MAX-ACCESS  read-only
    STATUS      current
    DESCRIPTION "Number of video served from cache"
    ::= { affirmedServicesContentHttpProxyServiceStatisticsChassisLevelVideoEntry 5 }

affirmedServicesContentHttpProxyServiceStatisticsChassisLevelVideoVideoaborts OBJECT-TYPE
    SYNTAX      ConfdString
    MAX-ACCESS  read-only
    STATUS      current
    DESCRIPTION "Number of video aborts"
    ::= { affirmedServicesContentHttpProxyServiceStatisticsChassisLevelVideoEntry 6 }

affirmedServicesContentHttpProxyServiceStatisticsChassisLevelVideoVideofailures OBJECT-TYPE
    SYNTAX      ConfdString
    MAX-ACCESS  read-only
    STATUS      current
    DESCRIPTION "Number of video failures"
    ::= { affirmedServicesContentHttpProxyServiceStatisticsChassisLevelVideoEntry 7 }

affirmedServicesContentHttpProxyServiceStatisticsChassisLevelVideoVideoseekrequests OBJECT-TYPE
    SYNTAX      ConfdString
    MAX-ACCESS  read-only
    STATUS      current
    DESCRIPTION "Number of video seek requests"
    ::= { affirmedServicesContentHttpProxyServiceStatisticsChassisLevelVideoEntry 8 }

affirmedServicesContentHttpProxyServiceStatisticsChassisLevelVideoFlvvideosuccesses OBJECT-TYPE
    SYNTAX      ConfdString
    MAX-ACCESS  read-only
    STATUS      current
    DESCRIPTION "Number of FLV video successes"
    ::= { affirmedServicesContentHttpProxyServiceStatisticsChassisLevelVideoEntry 9 }

affirmedServicesContentHttpProxyServiceStatisticsChassisLevelVideoFlvvideosuccessescached OBJECT-TYPE
    SYNTAX      ConfdString
    MAX-ACCESS  read-only
    STATUS      current
    DESCRIPTION "Number of FLV video successes cached"
    ::= { affirmedServicesContentHttpProxyServiceStatisticsChassisLevelVideoEntry 10 }

affirmedServicesContentHttpProxyServiceStatisticsChassisLevelVideoFlvvideoservedfromcache OBJECT-TYPE
    SYNTAX      ConfdString
    MAX-ACCESS  read-only
    STATUS      current
    DESCRIPTION "Number of FLV video served from cache"
    ::= { affirmedServicesContentHttpProxyServiceStatisticsChassisLevelVideoEntry 11 }

affirmedServicesContentHttpProxyServiceStatisticsChassisLevelVideoFlvvideoaborts OBJECT-TYPE
    SYNTAX      ConfdString
    MAX-ACCESS  read-only
    STATUS      current
    DESCRIPTION "Number of FLV video aborts"
    ::= { affirmedServicesContentHttpProxyServiceStatisticsChassisLevelVideoEntry 12 }

affirmedServicesContentHttpProxyServiceStatisticsChassisLevelVideoMp4videosuccesses OBJECT-TYPE
    SYNTAX      ConfdString
    MAX-ACCESS  read-only
    STATUS      current
    DESCRIPTION "Number of MP4 video successes"
    ::= { affirmedServicesContentHttpProxyServiceStatisticsChassisLevelVideoEntry 13 }

affirmedServicesContentHttpProxyServiceStatisticsChassisLevelVideoMp4videosuccessescached OBJECT-TYPE
    SYNTAX      ConfdString
    MAX-ACCESS  read-only
    STATUS      current
    DESCRIPTION "Number of MP4 video successes cached"
    ::= { affirmedServicesContentHttpProxyServiceStatisticsChassisLevelVideoEntry 14 }

affirmedServicesContentHttpProxyServiceStatisticsChassisLevelVideoMp4videoservedfromcache OBJECT-TYPE
    SYNTAX      ConfdString
    MAX-ACCESS  read-only
    STATUS      current
    DESCRIPTION "Number of MP4 video served from cache"
    ::= { affirmedServicesContentHttpProxyServiceStatisticsChassisLevelVideoEntry 15 }

affirmedServicesContentHttpProxyServiceStatisticsChassisLevelVideoMp4videoaborts OBJECT-TYPE
    SYNTAX      ConfdString
    MAX-ACCESS  read-only
    STATUS      current
    DESCRIPTION "Number of MP4 video aborts"
    ::= { affirmedServicesContentHttpProxyServiceStatisticsChassisLevelVideoEntry 16 }

affirmedServicesContentHttpProxyServiceStatisticsChassisLevelVideoDailymotionvideosuccesses OBJECT-TYPE
    SYNTAX      ConfdString
    MAX-ACCESS  read-only
    STATUS      current
    DESCRIPTION "Number of success video served by Dailymotion"
    ::= { affirmedServicesContentHttpProxyServiceStatisticsChassisLevelVideoEntry 17 }

affirmedServicesContentHttpProxyServiceStatisticsChassisLevelVideoDailymotionvideosuccessescached OBJECT-TYPE
    SYNTAX      ConfdString
    MAX-ACCESS  read-only
    STATUS      current
    DESCRIPTION "Number of success cached video served by Dailymotion"
    ::= { affirmedServicesContentHttpProxyServiceStatisticsChassisLevelVideoEntry 18 }

affirmedServicesContentHttpProxyServiceStatisticsChassisLevelVideoDailymotionvideoservedfromcache OBJECT-TYPE
    SYNTAX      ConfdString
    MAX-ACCESS  read-only
    STATUS      current
    DESCRIPTION "Number of Dailymotion videos served from cache"
    ::= { affirmedServicesContentHttpProxyServiceStatisticsChassisLevelVideoEntry 19 }

affirmedServicesContentHttpProxyServiceStatisticsChassisLevelVideoDailymotionvideoaborts OBJECT-TYPE
    SYNTAX      ConfdString
    MAX-ACCESS  read-only
    STATUS      current
    DESCRIPTION "Number of abort video served by Dailymotion"
    ::= { affirmedServicesContentHttpProxyServiceStatisticsChassisLevelVideoEntry 20 }

affirmedServicesContentHttpProxyServiceStatisticsChassisLevelVideoMetacafevideosuccesses OBJECT-TYPE
    SYNTAX      ConfdString
    MAX-ACCESS  read-only
    STATUS      current
    DESCRIPTION "Number of success video served by Metacafe"
    ::= { affirmedServicesContentHttpProxyServiceStatisticsChassisLevelVideoEntry 21 }

affirmedServicesContentHttpProxyServiceStatisticsChassisLevelVideoMetacafevideosuccessescached OBJECT-TYPE
    SYNTAX      ConfdString
    MAX-ACCESS  read-only
    STATUS      current
    DESCRIPTION "Number of success cached video served by Metacafe"
    ::= { affirmedServicesContentHttpProxyServiceStatisticsChassisLevelVideoEntry 22 }

affirmedServicesContentHttpProxyServiceStatisticsChassisLevelVideoMetacafevideoservedfromcache OBJECT-TYPE
    SYNTAX      ConfdString
    MAX-ACCESS  read-only
    STATUS      current
    DESCRIPTION "Number of Metacafe videos served from cache"
    ::= { affirmedServicesContentHttpProxyServiceStatisticsChassisLevelVideoEntry 23 }

affirmedServicesContentHttpProxyServiceStatisticsChassisLevelVideoMetacafevideoaborts OBJECT-TYPE
    SYNTAX      ConfdString
    MAX-ACCESS  read-only
    STATUS      current
    DESCRIPTION "Number of abort video served by Metacafe"
    ::= { affirmedServicesContentHttpProxyServiceStatisticsChassisLevelVideoEntry 24 }

affirmedServicesContentHttpProxyServiceStatisticsChassisLevelVideoVideosizemin OBJECT-TYPE
    SYNTAX      ConfdString
    MAX-ACCESS  read-only
    STATUS      current
    DESCRIPTION "Minimum video size in bytes"
    ::= { affirmedServicesContentHttpProxyServiceStatisticsChassisLevelVideoEntry 25 }

affirmedServicesContentHttpProxyServiceStatisticsChassisLevelVideoVideosizemax OBJECT-TYPE
    SYNTAX      ConfdString
    MAX-ACCESS  read-only
    STATUS      current
    DESCRIPTION "Maximum video size in bytes"
    ::= { affirmedServicesContentHttpProxyServiceStatisticsChassisLevelVideoEntry 26 }

affirmedServicesContentHttpProxyServiceStatisticsChassisLevelVideoVideosizeaverage OBJECT-TYPE
    SYNTAX      ConfdString
    MAX-ACCESS  read-only
    STATUS      current
    DESCRIPTION "Average video size in bytes"
    ::= { affirmedServicesContentHttpProxyServiceStatisticsChassisLevelVideoEntry 27 }

affirmedServicesContentHttpProxyServiceStatisticsChassisLevelVideoVideosizetotal OBJECT-TYPE
    SYNTAX      ConfdString
    MAX-ACCESS  read-only
    STATUS      current
    DESCRIPTION "Total video size in bytes"
    ::= { affirmedServicesContentHttpProxyServiceStatisticsChassisLevelVideoEntry 28 }

affirmedServicesContentHttpProxyServiceStatisticsChassisLevelVideoFlvvideosizemin OBJECT-TYPE
    SYNTAX      ConfdString
    MAX-ACCESS  read-only
    STATUS      current
    DESCRIPTION "Minimum FLV video size in bytes"
    ::= { affirmedServicesContentHttpProxyServiceStatisticsChassisLevelVideoEntry 29 }

affirmedServicesContentHttpProxyServiceStatisticsChassisLevelVideoFlvvideosizemax OBJECT-TYPE
    SYNTAX      ConfdString
    MAX-ACCESS  read-only
    STATUS      current
    DESCRIPTION "Maximum FLV video size in bytes"
    ::= { affirmedServicesContentHttpProxyServiceStatisticsChassisLevelVideoEntry 30 }

affirmedServicesContentHttpProxyServiceStatisticsChassisLevelVideoFlvvideosizeaverage OBJECT-TYPE
    SYNTAX      ConfdString
    MAX-ACCESS  read-only
    STATUS      current
    DESCRIPTION "Average FLV video size in bytes"
    ::= { affirmedServicesContentHttpProxyServiceStatisticsChassisLevelVideoEntry 31 }

affirmedServicesContentHttpProxyServiceStatisticsChassisLevelVideoFlvvideosizetotal OBJECT-TYPE
    SYNTAX      ConfdString
    MAX-ACCESS  read-only
    STATUS      current
    DESCRIPTION "Total FLV video size in bytes"
    ::= { affirmedServicesContentHttpProxyServiceStatisticsChassisLevelVideoEntry 32 }

affirmedServicesContentHttpProxyServiceStatisticsChassisLevelVideoMp4videosizemin OBJECT-TYPE
    SYNTAX      ConfdString
    MAX-ACCESS  read-only
    STATUS      current
    DESCRIPTION "Minimum MP4 video size in bytes"
    ::= { affirmedServicesContentHttpProxyServiceStatisticsChassisLevelVideoEntry 33 }

affirmedServicesContentHttpProxyServiceStatisticsChassisLevelVideoMp4videosizemax OBJECT-TYPE
    SYNTAX      ConfdString
    MAX-ACCESS  read-only
    STATUS      current
    DESCRIPTION "Maximum MP4 video size in bytes"
    ::= { affirmedServicesContentHttpProxyServiceStatisticsChassisLevelVideoEntry 34 }

affirmedServicesContentHttpProxyServiceStatisticsChassisLevelVideoMp4videosizeaverage OBJECT-TYPE
    SYNTAX      ConfdString
    MAX-ACCESS  read-only
    STATUS      current
    DESCRIPTION "Average MP4 video size in bytes"
    ::= { affirmedServicesContentHttpProxyServiceStatisticsChassisLevelVideoEntry 35 }

affirmedServicesContentHttpProxyServiceStatisticsChassisLevelVideoMp4videosizetotal OBJECT-TYPE
    SYNTAX      ConfdString
    MAX-ACCESS  read-only
    STATUS      current
    DESCRIPTION "Total MP4 video size in bytes"
    ::= { affirmedServicesContentHttpProxyServiceStatisticsChassisLevelVideoEntry 36 }

affirmedServicesContentHttpProxyServiceStatisticsChassisLevelVideoFlvvideodurationmin OBJECT-TYPE
    SYNTAX      ConfdString
    MAX-ACCESS  read-only
    STATUS      current
    DESCRIPTION "Minimum FLV video duration in seconds"
    ::= { affirmedServicesContentHttpProxyServiceStatisticsChassisLevelVideoEntry 37 }

affirmedServicesContentHttpProxyServiceStatisticsChassisLevelVideoFlvvideodurationmax OBJECT-TYPE
    SYNTAX      ConfdString
    MAX-ACCESS  read-only
    STATUS      current
    DESCRIPTION "Maximum FLV video duration in seconds"
    ::= { affirmedServicesContentHttpProxyServiceStatisticsChassisLevelVideoEntry 38 }

affirmedServicesContentHttpProxyServiceStatisticsChassisLevelVideoFlvvideodurationaverage OBJECT-TYPE
    SYNTAX      ConfdString
    MAX-ACCESS  read-only
    STATUS      current
    DESCRIPTION "Average FLV video duration in seconds"
    ::= { affirmedServicesContentHttpProxyServiceStatisticsChassisLevelVideoEntry 39 }

affirmedServicesContentHttpProxyServiceStatisticsChassisLevelVideoFlvvideodurationtotal OBJECT-TYPE
    SYNTAX      ConfdString
    MAX-ACCESS  read-only
    STATUS      current
    DESCRIPTION "Total FLV video duration in seconds"
    ::= { affirmedServicesContentHttpProxyServiceStatisticsChassisLevelVideoEntry 40 }

affirmedServicesContentHttpProxyServiceStatisticsChassisLevelVideoMp4videodurationmin OBJECT-TYPE
    SYNTAX      ConfdString
    MAX-ACCESS  read-only
    STATUS      current
    DESCRIPTION "Minimum MP4 video duration in seconds"
    ::= { affirmedServicesContentHttpProxyServiceStatisticsChassisLevelVideoEntry 41 }

affirmedServicesContentHttpProxyServiceStatisticsChassisLevelVideoMp4videodurationmax OBJECT-TYPE
    SYNTAX      ConfdString
    MAX-ACCESS  read-only
    STATUS      current
    DESCRIPTION "Maximum MP4 video duration in seconds"
    ::= { affirmedServicesContentHttpProxyServiceStatisticsChassisLevelVideoEntry 42 }

affirmedServicesContentHttpProxyServiceStatisticsChassisLevelVideoMp4videodurationaverage OBJECT-TYPE
    SYNTAX      ConfdString
    MAX-ACCESS  read-only
    STATUS      current
    DESCRIPTION "Average MP4 video duration in seconds"
    ::= { affirmedServicesContentHttpProxyServiceStatisticsChassisLevelVideoEntry 43 }

affirmedServicesContentHttpProxyServiceStatisticsChassisLevelVideoMp4videodurationtotal OBJECT-TYPE
    SYNTAX      ConfdString
    MAX-ACCESS  read-only
    STATUS      current
    DESCRIPTION "Total MP4 video duration in seconds"
    ::= { affirmedServicesContentHttpProxyServiceStatisticsChassisLevelVideoEntry 44 }

affirmedServicesContentHttpProxyServiceStatisticsChassisLevelVideoVideoservedbytesfromcache OBJECT-TYPE
    SYNTAX      ConfdString
    MAX-ACCESS  read-only
    STATUS      current
    DESCRIPTION "Number of video (bytes) served from cache"
    ::= { affirmedServicesContentHttpProxyServiceStatisticsChassisLevelVideoEntry 45 }

affirmedServicesContentHttpProxyServiceStatisticsChassisLevelVideoVideopacedrequests OBJECT-TYPE
    SYNTAX      ConfdString
    MAX-ACCESS  read-only
    STATUS      current
    DESCRIPTION "Number of videos for which video-pacing was applied"
    ::= { affirmedServicesContentHttpProxyServiceStatisticsChassisLevelVideoEntry 46 }

affirmedServicesContentHttpProxyServiceStatisticsChassisLevelVideoVideosizepacedtotal OBJECT-TYPE
    SYNTAX      ConfdString
    MAX-ACCESS  read-only
    STATUS      current
    DESCRIPTION "Length in bytes of videos for which pacing is applied"
    ::= { affirmedServicesContentHttpProxyServiceStatisticsChassisLevelVideoEntry 47 }

affirmedServicesContentHttpProxyServiceStatisticsChassisLevelVideoVideosizepacedsent OBJECT-TYPE
    SYNTAX      ConfdString
    MAX-ACCESS  read-only
    STATUS      current
    DESCRIPTION "Number of bytes of paced videos delivered"
    ::= { affirmedServicesContentHttpProxyServiceStatisticsChassisLevelVideoEntry 48 }

affirmedServicesContentHttpProxyServiceStatisticsChassisLevelVideoWebmvideosuccesses OBJECT-TYPE
    SYNTAX      ConfdString
    MAX-ACCESS  read-only
    STATUS      current
    DESCRIPTION "Number of WEBM video successes"
    ::= { affirmedServicesContentHttpProxyServiceStatisticsChassisLevelVideoEntry 49 }

affirmedServicesContentHttpProxyServiceStatisticsChassisLevelVideoWebmvideosuccessescached OBJECT-TYPE
    SYNTAX      ConfdString
    MAX-ACCESS  read-only
    STATUS      current
    DESCRIPTION "Number of WEBM video successes cached"
    ::= { affirmedServicesContentHttpProxyServiceStatisticsChassisLevelVideoEntry 50 }

affirmedServicesContentHttpProxyServiceStatisticsChassisLevelVideoWebmvideoservedfromcache OBJECT-TYPE
    SYNTAX      ConfdString
    MAX-ACCESS  read-only
    STATUS      current
    DESCRIPTION "Number of WEBM video served from cache"
    ::= { affirmedServicesContentHttpProxyServiceStatisticsChassisLevelVideoEntry 51 }

affirmedServicesContentHttpProxyServiceStatisticsChassisLevelVideoWebmvideoaborts OBJECT-TYPE
    SYNTAX      ConfdString
    MAX-ACCESS  read-only
    STATUS      current
    DESCRIPTION "Number of WEBM video aborts"
    ::= { affirmedServicesContentHttpProxyServiceStatisticsChassisLevelVideoEntry 52 }

affirmedServicesContentHttpProxyServiceStatisticsChassisLevelVideoWebmvideosizemin OBJECT-TYPE
    SYNTAX      ConfdString
    MAX-ACCESS  read-only
    STATUS      current
    DESCRIPTION "Minimum WEBM video size in bytes"
    ::= { affirmedServicesContentHttpProxyServiceStatisticsChassisLevelVideoEntry 53 }

affirmedServicesContentHttpProxyServiceStatisticsChassisLevelVideoWebmvideosizemax OBJECT-TYPE
    SYNTAX      ConfdString
    MAX-ACCESS  read-only
    STATUS      current
    DESCRIPTION "Maximum WEBM video size in bytes"
    ::= { affirmedServicesContentHttpProxyServiceStatisticsChassisLevelVideoEntry 54 }

affirmedServicesContentHttpProxyServiceStatisticsChassisLevelVideoWebmvideosizeaverage OBJECT-TYPE
    SYNTAX      ConfdString
    MAX-ACCESS  read-only
    STATUS      current
    DESCRIPTION "Average WEBM video size in bytes"
    ::= { affirmedServicesContentHttpProxyServiceStatisticsChassisLevelVideoEntry 55 }

affirmedServicesContentHttpProxyServiceStatisticsChassisLevelVideoWebmvideosizetotal OBJECT-TYPE
    SYNTAX      ConfdString
    MAX-ACCESS  read-only
    STATUS      current
    DESCRIPTION "Total WEBM video size in bytes"
    ::= { affirmedServicesContentHttpProxyServiceStatisticsChassisLevelVideoEntry 56 }

affirmedServicesContentHttpProxyServiceStatisticsChassisLevelVideoWebmvideodurationmin OBJECT-TYPE
    SYNTAX      ConfdString
    MAX-ACCESS  read-only
    STATUS      current
    DESCRIPTION "Minimum WEBM video duration in seconds"
    ::= { affirmedServicesContentHttpProxyServiceStatisticsChassisLevelVideoEntry 57 }

affirmedServicesContentHttpProxyServiceStatisticsChassisLevelVideoWebmvideodurationmax OBJECT-TYPE
    SYNTAX      ConfdString
    MAX-ACCESS  read-only
    STATUS      current
    DESCRIPTION "Maximum WEBM video duration in seconds"
    ::= { affirmedServicesContentHttpProxyServiceStatisticsChassisLevelVideoEntry 58 }

affirmedServicesContentHttpProxyServiceStatisticsChassisLevelVideoWebmvideodurationaverage OBJECT-TYPE
    SYNTAX      ConfdString
    MAX-ACCESS  read-only
    STATUS      current
    DESCRIPTION "Average WEBM video duration in seconds"
    ::= { affirmedServicesContentHttpProxyServiceStatisticsChassisLevelVideoEntry 59 }

affirmedServicesContentHttpProxyServiceStatisticsChassisLevelVideoWebmvideodurationtotal OBJECT-TYPE
    SYNTAX      ConfdString
    MAX-ACCESS  read-only
    STATUS      current
    DESCRIPTION "Total WEBM video duration in seconds"
    ::= { affirmedServicesContentHttpProxyServiceStatisticsChassisLevelVideoEntry 60 }

affirmedServicesContentHttpProxyServiceStatisticsChassisLevelMediaTypeResponsesTable OBJECT-TYPE
    SYNTAX      SEQUENCE OF AffirmedServicesContentHttpProxyServiceStatisticsChassisLevelMediaTypeResponsesEntry
    MAX-ACCESS  not-accessible
    STATUS      current
    DESCRIPTION ""
    ::= { affirmedServicesContentHttpProxyServiceStatisticsChassisLevelMediaType 1 }

affirmedServicesContentHttpProxyServiceStatisticsChassisLevelMediaTypeResponsesEntry OBJECT-TYPE
    SYNTAX      AffirmedServicesContentHttpProxyServiceStatisticsChassisLevelMediaTypeResponsesEntry
    MAX-ACCESS  not-accessible
    STATUS      current
    DESCRIPTION ""
    INDEX { affirmedServicesContentHttpProxyServiceStatisticsChassisLevelMediaTypeResponsesChassis }
        ::= { affirmedServicesContentHttpProxyServiceStatisticsChassisLevelMediaTypeResponsesTable 1 }

AffirmedServicesContentHttpProxyServiceStatisticsChassisLevelMediaTypeResponsesEntry ::=
    SEQUENCE {
        affirmedServicesContentHttpProxyServiceStatisticsChassisLevelMediaTypeResponsesChassis Unsigned32,
        affirmedServicesContentHttpProxyServiceStatisticsChassisLevelMediaTypeResponsesNumtextresphtml ConfdString,
        affirmedServicesContentHttpProxyServiceStatisticsChassisLevelMediaTypeResponsesNumtextrespxml ConfdString,
        affirmedServicesContentHttpProxyServiceStatisticsChassisLevelMediaTypeResponsesNumtextrespcss ConfdString,
        affirmedServicesContentHttpProxyServiceStatisticsChassisLevelMediaTypeResponsesNumtextrespjs ConfdString,
        affirmedServicesContentHttpProxyServiceStatisticsChassisLevelMediaTypeResponsesNumtextrespjson ConfdString,
        affirmedServicesContentHttpProxyServiceStatisticsChassisLevelMediaTypeResponsesNumtextrespplain ConfdString,
        affirmedServicesContentHttpProxyServiceStatisticsChassisLevelMediaTypeResponsesNumimagerespjpeg ConfdString,
        affirmedServicesContentHttpProxyServiceStatisticsChassisLevelMediaTypeResponsesNumimageresppng ConfdString,
        affirmedServicesContentHttpProxyServiceStatisticsChassisLevelMediaTypeResponsesNumimagerespgif ConfdString,
        affirmedServicesContentHttpProxyServiceStatisticsChassisLevelMediaTypeResponsesNumimagerespbmp ConfdString,
        affirmedServicesContentHttpProxyServiceStatisticsChassisLevelMediaTypeResponsesNumvideorespmp4 ConfdString,
        affirmedServicesContentHttpProxyServiceStatisticsChassisLevelMediaTypeResponsesNumvideorespflv ConfdString,
        affirmedServicesContentHttpProxyServiceStatisticsChassisLevelMediaTypeResponsesNumvideorespwebm ConfdString,
        affirmedServicesContentHttpProxyServiceStatisticsChassisLevelMediaTypeResponsesNumvideoresphls ConfdString,
        affirmedServicesContentHttpProxyServiceStatisticsChassisLevelMediaTypeResponsesNumvideorespdash ConfdString,
        affirmedServicesContentHttpProxyServiceStatisticsChassisLevelMediaTypeResponsesNumvideoresphds ConfdString,
        affirmedServicesContentHttpProxyServiceStatisticsChassisLevelMediaTypeResponsesNumotherrespbinary ConfdString,
        affirmedServicesContentHttpProxyServiceStatisticsChassisLevelMediaTypeResponsesNumotherrespunrecog ConfdString
    }

affirmedServicesContentHttpProxyServiceStatisticsChassisLevelMediaTypeResponsesChassis OBJECT-TYPE
    SYNTAX      Unsigned32
    MAX-ACCESS  not-accessible
    STATUS      current
    DESCRIPTION "chassis ID"
    ::= { affirmedServicesContentHttpProxyServiceStatisticsChassisLevelMediaTypeResponsesEntry 1 }

affirmedServicesContentHttpProxyServiceStatisticsChassisLevelMediaTypeResponsesNumtextresphtml OBJECT-TYPE
    SYNTAX      ConfdString
    MAX-ACCESS  read-only
    STATUS      current
    DESCRIPTION "Number of HTML Text Responses"
    ::= { affirmedServicesContentHttpProxyServiceStatisticsChassisLevelMediaTypeResponsesEntry 2 }

affirmedServicesContentHttpProxyServiceStatisticsChassisLevelMediaTypeResponsesNumtextrespxml OBJECT-TYPE
    SYNTAX      ConfdString
    MAX-ACCESS  read-only
    STATUS      current
    DESCRIPTION "Number of XML Text Responses"
    ::= { affirmedServicesContentHttpProxyServiceStatisticsChassisLevelMediaTypeResponsesEntry 3 }

affirmedServicesContentHttpProxyServiceStatisticsChassisLevelMediaTypeResponsesNumtextrespcss OBJECT-TYPE
    SYNTAX      ConfdString
    MAX-ACCESS  read-only
    STATUS      current
    DESCRIPTION "Number of CSS Text Responses"
    ::= { affirmedServicesContentHttpProxyServiceStatisticsChassisLevelMediaTypeResponsesEntry 4 }

affirmedServicesContentHttpProxyServiceStatisticsChassisLevelMediaTypeResponsesNumtextrespjs OBJECT-TYPE
    SYNTAX      ConfdString
    MAX-ACCESS  read-only
    STATUS      current
    DESCRIPTION "Number of Javascript Text Responses"
    ::= { affirmedServicesContentHttpProxyServiceStatisticsChassisLevelMediaTypeResponsesEntry 5 }

affirmedServicesContentHttpProxyServiceStatisticsChassisLevelMediaTypeResponsesNumtextrespjson OBJECT-TYPE
    SYNTAX      ConfdString
    MAX-ACCESS  read-only
    STATUS      current
    DESCRIPTION "Number of JSON Text Responses"
    ::= { affirmedServicesContentHttpProxyServiceStatisticsChassisLevelMediaTypeResponsesEntry 6 }

affirmedServicesContentHttpProxyServiceStatisticsChassisLevelMediaTypeResponsesNumtextrespplain OBJECT-TYPE
    SYNTAX      ConfdString
    MAX-ACCESS  read-only
    STATUS      current
    DESCRIPTION "Number of Plain Text Responses"
    ::= { affirmedServicesContentHttpProxyServiceStatisticsChassisLevelMediaTypeResponsesEntry 7 }

affirmedServicesContentHttpProxyServiceStatisticsChassisLevelMediaTypeResponsesNumimagerespjpeg OBJECT-TYPE
    SYNTAX      ConfdString
    MAX-ACCESS  read-only
    STATUS      current
    DESCRIPTION "Number of JPEG Image Responses"
    ::= { affirmedServicesContentHttpProxyServiceStatisticsChassisLevelMediaTypeResponsesEntry 8 }

affirmedServicesContentHttpProxyServiceStatisticsChassisLevelMediaTypeResponsesNumimageresppng OBJECT-TYPE
    SYNTAX      ConfdString
    MAX-ACCESS  read-only
    STATUS      current
    DESCRIPTION "Number of PNG Image Responses"
    ::= { affirmedServicesContentHttpProxyServiceStatisticsChassisLevelMediaTypeResponsesEntry 9 }

affirmedServicesContentHttpProxyServiceStatisticsChassisLevelMediaTypeResponsesNumimagerespgif OBJECT-TYPE
    SYNTAX      ConfdString
    MAX-ACCESS  read-only
    STATUS      current
    DESCRIPTION "Number of GIF Image Responses"
    ::= { affirmedServicesContentHttpProxyServiceStatisticsChassisLevelMediaTypeResponsesEntry 10 }

affirmedServicesContentHttpProxyServiceStatisticsChassisLevelMediaTypeResponsesNumimagerespbmp OBJECT-TYPE
    SYNTAX      ConfdString
    MAX-ACCESS  read-only
    STATUS      current
    DESCRIPTION "Number of BMP Image Responses"
    ::= { affirmedServicesContentHttpProxyServiceStatisticsChassisLevelMediaTypeResponsesEntry 11 }

affirmedServicesContentHttpProxyServiceStatisticsChassisLevelMediaTypeResponsesNumvideorespmp4 OBJECT-TYPE
    SYNTAX      ConfdString
    MAX-ACCESS  read-only
    STATUS      current
    DESCRIPTION "Number of MP4 Video Responses"
    ::= { affirmedServicesContentHttpProxyServiceStatisticsChassisLevelMediaTypeResponsesEntry 12 }

affirmedServicesContentHttpProxyServiceStatisticsChassisLevelMediaTypeResponsesNumvideorespflv OBJECT-TYPE
    SYNTAX      ConfdString
    MAX-ACCESS  read-only
    STATUS      current
    DESCRIPTION "Number of FLV Video Responses"
    ::= { affirmedServicesContentHttpProxyServiceStatisticsChassisLevelMediaTypeResponsesEntry 13 }

affirmedServicesContentHttpProxyServiceStatisticsChassisLevelMediaTypeResponsesNumvideorespwebm OBJECT-TYPE
    SYNTAX      ConfdString
    MAX-ACCESS  read-only
    STATUS      current
    DESCRIPTION "Number of WEBM Video Responses"
    ::= { affirmedServicesContentHttpProxyServiceStatisticsChassisLevelMediaTypeResponsesEntry 14 }

affirmedServicesContentHttpProxyServiceStatisticsChassisLevelMediaTypeResponsesNumvideoresphls OBJECT-TYPE
    SYNTAX      ConfdString
    MAX-ACCESS  read-only
    STATUS      current
    DESCRIPTION "Number of HLS Video Responses"
    ::= { affirmedServicesContentHttpProxyServiceStatisticsChassisLevelMediaTypeResponsesEntry 15 }

affirmedServicesContentHttpProxyServiceStatisticsChassisLevelMediaTypeResponsesNumvideorespdash OBJECT-TYPE
    SYNTAX      ConfdString
    MAX-ACCESS  read-only
    STATUS      current
    DESCRIPTION "Number of DASH Video Responses"
    ::= { affirmedServicesContentHttpProxyServiceStatisticsChassisLevelMediaTypeResponsesEntry 16 }

affirmedServicesContentHttpProxyServiceStatisticsChassisLevelMediaTypeResponsesNumvideoresphds OBJECT-TYPE
    SYNTAX      ConfdString
    MAX-ACCESS  read-only
    STATUS      current
    DESCRIPTION "Number of HDS Video Responses"
    ::= { affirmedServicesContentHttpProxyServiceStatisticsChassisLevelMediaTypeResponsesEntry 17 }

affirmedServicesContentHttpProxyServiceStatisticsChassisLevelMediaTypeResponsesNumotherrespbinary OBJECT-TYPE
    SYNTAX      ConfdString
    MAX-ACCESS  read-only
    STATUS      current
    DESCRIPTION "Number of Binary Responses"
    ::= { affirmedServicesContentHttpProxyServiceStatisticsChassisLevelMediaTypeResponsesEntry 18 }

affirmedServicesContentHttpProxyServiceStatisticsChassisLevelMediaTypeResponsesNumotherrespunrecog OBJECT-TYPE
    SYNTAX      ConfdString
    MAX-ACCESS  read-only
    STATUS      current
    DESCRIPTION "Number of Unrecognized Responses"
    ::= { affirmedServicesContentHttpProxyServiceStatisticsChassisLevelMediaTypeResponsesEntry 19 }

affirmedServicesContentHttpProxyServiceStatisticsChassisLevelMediaTypeBytesTable OBJECT-TYPE
    SYNTAX      SEQUENCE OF AffirmedServicesContentHttpProxyServiceStatisticsChassisLevelMediaTypeBytesEntry
    MAX-ACCESS  not-accessible
    STATUS      current
    DESCRIPTION ""
    ::= { affirmedServicesContentHttpProxyServiceStatisticsChassisLevelMediaType 2 }

affirmedServicesContentHttpProxyServiceStatisticsChassisLevelMediaTypeBytesEntry OBJECT-TYPE
    SYNTAX      AffirmedServicesContentHttpProxyServiceStatisticsChassisLevelMediaTypeBytesEntry
    MAX-ACCESS  not-accessible
    STATUS      current
    DESCRIPTION ""
    INDEX { affirmedServicesContentHttpProxyServiceStatisticsChassisLevelMediaTypeBytesChassis }
        ::= { affirmedServicesContentHttpProxyServiceStatisticsChassisLevelMediaTypeBytesTable 1 }

AffirmedServicesContentHttpProxyServiceStatisticsChassisLevelMediaTypeBytesEntry ::=
    SEQUENCE {
        affirmedServicesContentHttpProxyServiceStatisticsChassisLevelMediaTypeBytesChassis Unsigned32,
        affirmedServicesContentHttpProxyServiceStatisticsChassisLevelMediaTypeBytesNumtextbyteshtml ConfdString,
        affirmedServicesContentHttpProxyServiceStatisticsChassisLevelMediaTypeBytesNumtextbytesxml ConfdString,
        affirmedServicesContentHttpProxyServiceStatisticsChassisLevelMediaTypeBytesNumtextbytescss ConfdString,
        affirmedServicesContentHttpProxyServiceStatisticsChassisLevelMediaTypeBytesNumtextbytesjs ConfdString,
        affirmedServicesContentHttpProxyServiceStatisticsChassisLevelMediaTypeBytesNumtextbytesjson ConfdString,
        affirmedServicesContentHttpProxyServiceStatisticsChassisLevelMediaTypeBytesNumtextbytesplain ConfdString,
        affirmedServicesContentHttpProxyServiceStatisticsChassisLevelMediaTypeBytesNumimagebytesjpeg ConfdString,
        affirmedServicesContentHttpProxyServiceStatisticsChassisLevelMediaTypeBytesNumimagebytespng ConfdString,
        affirmedServicesContentHttpProxyServiceStatisticsChassisLevelMediaTypeBytesNumimagebytesgif ConfdString,
        affirmedServicesContentHttpProxyServiceStatisticsChassisLevelMediaTypeBytesNumimagebytesbmp ConfdString,
        affirmedServicesContentHttpProxyServiceStatisticsChassisLevelMediaTypeBytesNumvideobytesmp4 ConfdString,
        affirmedServicesContentHttpProxyServiceStatisticsChassisLevelMediaTypeBytesNumvideobytesflv ConfdString,
        affirmedServicesContentHttpProxyServiceStatisticsChassisLevelMediaTypeBytesNumvideobyteswebm ConfdString,
        affirmedServicesContentHttpProxyServiceStatisticsChassisLevelMediaTypeBytesNumvideobyteshls ConfdString,
        affirmedServicesContentHttpProxyServiceStatisticsChassisLevelMediaTypeBytesNumvideobytesdash ConfdString,
        affirmedServicesContentHttpProxyServiceStatisticsChassisLevelMediaTypeBytesNumvideobyteshds ConfdString,
        affirmedServicesContentHttpProxyServiceStatisticsChassisLevelMediaTypeBytesNumotherbytesbinary ConfdString,
        affirmedServicesContentHttpProxyServiceStatisticsChassisLevelMediaTypeBytesNumotherbytesunrecog ConfdString
    }

affirmedServicesContentHttpProxyServiceStatisticsChassisLevelMediaTypeBytesChassis OBJECT-TYPE
    SYNTAX      Unsigned32
    MAX-ACCESS  not-accessible
    STATUS      current
    DESCRIPTION "chassis ID"
    ::= { affirmedServicesContentHttpProxyServiceStatisticsChassisLevelMediaTypeBytesEntry 1 }

affirmedServicesContentHttpProxyServiceStatisticsChassisLevelMediaTypeBytesNumtextbyteshtml OBJECT-TYPE
    SYNTAX      ConfdString
    MAX-ACCESS  read-only
    STATUS      current
    DESCRIPTION "Number of HTML Text Bytes"
    ::= { affirmedServicesContentHttpProxyServiceStatisticsChassisLevelMediaTypeBytesEntry 2 }

affirmedServicesContentHttpProxyServiceStatisticsChassisLevelMediaTypeBytesNumtextbytesxml OBJECT-TYPE
    SYNTAX      ConfdString
    MAX-ACCESS  read-only
    STATUS      current
    DESCRIPTION "Number of XML Text Bytes"
    ::= { affirmedServicesContentHttpProxyServiceStatisticsChassisLevelMediaTypeBytesEntry 3 }

affirmedServicesContentHttpProxyServiceStatisticsChassisLevelMediaTypeBytesNumtextbytescss OBJECT-TYPE
    SYNTAX      ConfdString
    MAX-ACCESS  read-only
    STATUS      current
    DESCRIPTION "Number of CSS Text Bytes"
    ::= { affirmedServicesContentHttpProxyServiceStatisticsChassisLevelMediaTypeBytesEntry 4 }

affirmedServicesContentHttpProxyServiceStatisticsChassisLevelMediaTypeBytesNumtextbytesjs OBJECT-TYPE
    SYNTAX      ConfdString
    MAX-ACCESS  read-only
    STATUS      current
    DESCRIPTION "Number of Javascript Text Bytes"
    ::= { affirmedServicesContentHttpProxyServiceStatisticsChassisLevelMediaTypeBytesEntry 5 }

affirmedServicesContentHttpProxyServiceStatisticsChassisLevelMediaTypeBytesNumtextbytesjson OBJECT-TYPE
    SYNTAX      ConfdString
    MAX-ACCESS  read-only
    STATUS      current
    DESCRIPTION "Number of JSON Text Bytes"
    ::= { affirmedServicesContentHttpProxyServiceStatisticsChassisLevelMediaTypeBytesEntry 6 }

affirmedServicesContentHttpProxyServiceStatisticsChassisLevelMediaTypeBytesNumtextbytesplain OBJECT-TYPE
    SYNTAX      ConfdString
    MAX-ACCESS  read-only
    STATUS      current
    DESCRIPTION "Number of Plain Text Bytes"
    ::= { affirmedServicesContentHttpProxyServiceStatisticsChassisLevelMediaTypeBytesEntry 7 }

affirmedServicesContentHttpProxyServiceStatisticsChassisLevelMediaTypeBytesNumimagebytesjpeg OBJECT-TYPE
    SYNTAX      ConfdString
    MAX-ACCESS  read-only
    STATUS      current
    DESCRIPTION "Number of JPEG Image Bytes"
    ::= { affirmedServicesContentHttpProxyServiceStatisticsChassisLevelMediaTypeBytesEntry 8 }

affirmedServicesContentHttpProxyServiceStatisticsChassisLevelMediaTypeBytesNumimagebytespng OBJECT-TYPE
    SYNTAX      ConfdString
    MAX-ACCESS  read-only
    STATUS      current
    DESCRIPTION "Number of PNG Image Bytes"
    ::= { affirmedServicesContentHttpProxyServiceStatisticsChassisLevelMediaTypeBytesEntry 9 }

affirmedServicesContentHttpProxyServiceStatisticsChassisLevelMediaTypeBytesNumimagebytesgif OBJECT-TYPE
    SYNTAX      ConfdString
    MAX-ACCESS  read-only
    STATUS      current
    DESCRIPTION "Number of GIF Image Bytes"
    ::= { affirmedServicesContentHttpProxyServiceStatisticsChassisLevelMediaTypeBytesEntry 10 }

affirmedServicesContentHttpProxyServiceStatisticsChassisLevelMediaTypeBytesNumimagebytesbmp OBJECT-TYPE
    SYNTAX      ConfdString
    MAX-ACCESS  read-only
    STATUS      current
    DESCRIPTION "Number of BMP Image Bytes"
    ::= { affirmedServicesContentHttpProxyServiceStatisticsChassisLevelMediaTypeBytesEntry 11 }

affirmedServicesContentHttpProxyServiceStatisticsChassisLevelMediaTypeBytesNumvideobytesmp4 OBJECT-TYPE
    SYNTAX      ConfdString
    MAX-ACCESS  read-only
    STATUS      current
    DESCRIPTION "Number of MP4 Video Bytes"
    ::= { affirmedServicesContentHttpProxyServiceStatisticsChassisLevelMediaTypeBytesEntry 12 }

affirmedServicesContentHttpProxyServiceStatisticsChassisLevelMediaTypeBytesNumvideobytesflv OBJECT-TYPE
    SYNTAX      ConfdString
    MAX-ACCESS  read-only
    STATUS      current
    DESCRIPTION "Number of FLV Video Bytes"
    ::= { affirmedServicesContentHttpProxyServiceStatisticsChassisLevelMediaTypeBytesEntry 13 }

affirmedServicesContentHttpProxyServiceStatisticsChassisLevelMediaTypeBytesNumvideobyteswebm OBJECT-TYPE
    SYNTAX      ConfdString
    MAX-ACCESS  read-only
    STATUS      current
    DESCRIPTION "Number of WEBM Video Bytes"
    ::= { affirmedServicesContentHttpProxyServiceStatisticsChassisLevelMediaTypeBytesEntry 14 }

affirmedServicesContentHttpProxyServiceStatisticsChassisLevelMediaTypeBytesNumvideobyteshls OBJECT-TYPE
    SYNTAX      ConfdString
    MAX-ACCESS  read-only
    STATUS      current
    DESCRIPTION "Number of HLS Video Bytes"
    ::= { affirmedServicesContentHttpProxyServiceStatisticsChassisLevelMediaTypeBytesEntry 15 }

affirmedServicesContentHttpProxyServiceStatisticsChassisLevelMediaTypeBytesNumvideobytesdash OBJECT-TYPE
    SYNTAX      ConfdString
    MAX-ACCESS  read-only
    STATUS      current
    DESCRIPTION "Number of DASH Video Bytes"
    ::= { affirmedServicesContentHttpProxyServiceStatisticsChassisLevelMediaTypeBytesEntry 16 }

affirmedServicesContentHttpProxyServiceStatisticsChassisLevelMediaTypeBytesNumvideobyteshds OBJECT-TYPE
    SYNTAX      ConfdString
    MAX-ACCESS  read-only
    STATUS      current
    DESCRIPTION "Number of HDS Video Bytes"
    ::= { affirmedServicesContentHttpProxyServiceStatisticsChassisLevelMediaTypeBytesEntry 17 }

affirmedServicesContentHttpProxyServiceStatisticsChassisLevelMediaTypeBytesNumotherbytesbinary OBJECT-TYPE
    SYNTAX      ConfdString
    MAX-ACCESS  read-only
    STATUS      current
    DESCRIPTION "Number of Binary Bytes"
    ::= { affirmedServicesContentHttpProxyServiceStatisticsChassisLevelMediaTypeBytesEntry 18 }

affirmedServicesContentHttpProxyServiceStatisticsChassisLevelMediaTypeBytesNumotherbytesunrecog OBJECT-TYPE
    SYNTAX      ConfdString
    MAX-ACCESS  read-only
    STATUS      current
    DESCRIPTION "Number of Unrecognized Bytes"
    ::= { affirmedServicesContentHttpProxyServiceStatisticsChassisLevelMediaTypeBytesEntry 19 }

affirmedServicesContentHttpProxyServiceStatisticsSlotLevelContentInsertionScriptLinkTable OBJECT-TYPE
    SYNTAX      SEQUENCE OF AffirmedServicesContentHttpProxyServiceStatisticsSlotLevelContentInsertionScriptLinkEntry
    MAX-ACCESS  not-accessible
    STATUS      current
    DESCRIPTION ""
    ::= { affirmedServicesContentHttpProxyServiceStatisticsSlotLevelContentInsertion 1 }

affirmedServicesContentHttpProxyServiceStatisticsSlotLevelContentInsertionScriptLinkEntry OBJECT-TYPE
    SYNTAX      AffirmedServicesContentHttpProxyServiceStatisticsSlotLevelContentInsertionScriptLinkEntry
    MAX-ACCESS  not-accessible
    STATUS      current
    DESCRIPTION ""
    INDEX { affirmedServicesContentHttpProxyServiceStatisticsSlotLevelContentInsertionScriptLinkChassis, affirmedServicesContentHttpProxyServiceStatisticsSlotLevelContentInsertionScriptLinkSlot }
        ::= { affirmedServicesContentHttpProxyServiceStatisticsSlotLevelContentInsertionScriptLinkTable 1 }

AffirmedServicesContentHttpProxyServiceStatisticsSlotLevelContentInsertionScriptLinkEntry ::=
    SEQUENCE {
        affirmedServicesContentHttpProxyServiceStatisticsSlotLevelContentInsertionScriptLinkChassis Unsigned32,
        affirmedServicesContentHttpProxyServiceStatisticsSlotLevelContentInsertionScriptLinkSlot INTEGER,
        affirmedServicesContentHttpProxyServiceStatisticsSlotLevelContentInsertionScriptLinkScriptlinkinsertionattempts ConfdString,
        affirmedServicesContentHttpProxyServiceStatisticsSlotLevelContentInsertionScriptLinkScriptlinkinsertionsuccesses ConfdString,
        affirmedServicesContentHttpProxyServiceStatisticsSlotLevelContentInsertionScriptLinkScriptlinkinsertioncancels ConfdString,
        affirmedServicesContentHttpProxyServiceStatisticsSlotLevelContentInsertionScriptLinkScriptlinkinsertionfailures ConfdString,
        affirmedServicesContentHttpProxyServiceStatisticsSlotLevelContentInsertionScriptLinkScriptlinkinsertionaborts ConfdString,
        affirmedServicesContentHttpProxyServiceStatisticsSlotLevelContentInsertionScriptLinkScriptlinkinsertioncancelnonokstatus ConfdString,
        affirmedServicesContentHttpProxyServiceStatisticsSlotLevelContentInsertionScriptLinkScriptlinkinsertioncancelpagetoobig ConfdString,
        affirmedServicesContentHttpProxyServiceStatisticsSlotLevelContentInsertionScriptLinkScriptlinkinsertionfailureunsupportedhtml ConfdString,
        affirmedServicesContentHttpProxyServiceStatisticsSlotLevelContentInsertionScriptLinkScriptlinkinsertionfailureinvalidhtml ConfdString
    }

affirmedServicesContentHttpProxyServiceStatisticsSlotLevelContentInsertionScriptLinkChassis OBJECT-TYPE
    SYNTAX      Unsigned32
    MAX-ACCESS  not-accessible
    STATUS      current
    DESCRIPTION "chassis ID"
    ::= { affirmedServicesContentHttpProxyServiceStatisticsSlotLevelContentInsertionScriptLinkEntry 1 }

affirmedServicesContentHttpProxyServiceStatisticsSlotLevelContentInsertionScriptLinkSlot OBJECT-TYPE
    SYNTAX      INTEGER {a1(1),a2(2),a3(3),a4(4),a5(5),a6(6),a7(7),a8(8),a9(9),a10(10),a11(11),a12(12),a13(13),a14(14),a15(15),a16(16),a17(17),a18(18),a19(19),a20(20),a21(21),a22(22),a23(23),a24(24),a25(25),a26(26),a27(27),a28(28),a29(29),a30(30),a31(31),a32(32),a33(33),a34(34),a35(35),a36(36),a37(37),a38(38),a39(39),a40(40),a41(41),a42(42),a43(43),a44(44),a45(45),a46(46),a47(47),a48(48),a49(49),a50(50),a51(51),a52(52),a53(53),a54(54),a55(55),a56(56),a57(57),a58(58),a59(59),a60(60),a61(61),a62(62),a63(63),a64(64),a65(65),a66(66),a67(67),a68(68),a69(69),a70(70),a71(71),a72(72),a73(73),a74(74),a75(75),a76(76),a77(77),a78(78),a79(79),a80(80),a81(81),a82(82),a83(83),a84(84),a85(85),a86(86),a87(87),a88(88),a89(89),a90(90),a91(91),a92(92),a93(93),a94(94),a95(95),a96(96),a97(97),a98(98),a99(99),a100(100),a101(101),a102(102),a103(103),a104(104),a105(105),a106(106),a107(107),a108(108),a109(109),a110(110),a111(111),a112(112),a113(113),a114(114),a115(115),a116(116),a117(117),a118(118),a119(119),a120(120),a121(121),a122(122),a123(123),a124(124),a125(125),a126(126),a127(127),a128(128)}
    MAX-ACCESS  not-accessible
    STATUS      current
    DESCRIPTION "slot number"
    ::= { affirmedServicesContentHttpProxyServiceStatisticsSlotLevelContentInsertionScriptLinkEntry 2 }

affirmedServicesContentHttpProxyServiceStatisticsSlotLevelContentInsertionScriptLinkScriptlinkinsertionattempts OBJECT-TYPE
    SYNTAX      ConfdString
    MAX-ACCESS  read-only
    STATUS      current
    DESCRIPTION "Number of Script-Link Insertion Attempts"
    ::= { affirmedServicesContentHttpProxyServiceStatisticsSlotLevelContentInsertionScriptLinkEntry 3 }

affirmedServicesContentHttpProxyServiceStatisticsSlotLevelContentInsertionScriptLinkScriptlinkinsertionsuccesses OBJECT-TYPE
    SYNTAX      ConfdString
    MAX-ACCESS  read-only
    STATUS      current
    DESCRIPTION "Number of Script-Link Insertion Successes"
    ::= { affirmedServicesContentHttpProxyServiceStatisticsSlotLevelContentInsertionScriptLinkEntry 4 }

affirmedServicesContentHttpProxyServiceStatisticsSlotLevelContentInsertionScriptLinkScriptlinkinsertioncancels OBJECT-TYPE
    SYNTAX      ConfdString
    MAX-ACCESS  read-only
    STATUS      current
    DESCRIPTION "Number of Script-Link Insertion Cancels"
    ::= { affirmedServicesContentHttpProxyServiceStatisticsSlotLevelContentInsertionScriptLinkEntry 5 }

affirmedServicesContentHttpProxyServiceStatisticsSlotLevelContentInsertionScriptLinkScriptlinkinsertionfailures OBJECT-TYPE
    SYNTAX      ConfdString
    MAX-ACCESS  read-only
    STATUS      current
    DESCRIPTION "Number of Script-Link Insertion Failures"
    ::= { affirmedServicesContentHttpProxyServiceStatisticsSlotLevelContentInsertionScriptLinkEntry 6 }

affirmedServicesContentHttpProxyServiceStatisticsSlotLevelContentInsertionScriptLinkScriptlinkinsertionaborts OBJECT-TYPE
    SYNTAX      ConfdString
    MAX-ACCESS  read-only
    STATUS      current
    DESCRIPTION "Number of Script-Link Insertion Aborts"
    ::= { affirmedServicesContentHttpProxyServiceStatisticsSlotLevelContentInsertionScriptLinkEntry 7 }

affirmedServicesContentHttpProxyServiceStatisticsSlotLevelContentInsertionScriptLinkScriptlinkinsertioncancelnonokstatus OBJECT-TYPE
    SYNTAX      ConfdString
    MAX-ACCESS  read-only
    STATUS      current
    DESCRIPTION "Number of Script-Link Insertion Cancels Due to Non-OK Response Status"
    ::= { affirmedServicesContentHttpProxyServiceStatisticsSlotLevelContentInsertionScriptLinkEntry 8 }

affirmedServicesContentHttpProxyServiceStatisticsSlotLevelContentInsertionScriptLinkScriptlinkinsertioncancelpagetoobig OBJECT-TYPE
    SYNTAX      ConfdString
    MAX-ACCESS  read-only
    STATUS      current
    DESCRIPTION "Number of Script-Link Insertion Cancels Due to Respnose Page Too Big"
    ::= { affirmedServicesContentHttpProxyServiceStatisticsSlotLevelContentInsertionScriptLinkEntry 9 }

affirmedServicesContentHttpProxyServiceStatisticsSlotLevelContentInsertionScriptLinkScriptlinkinsertionfailureunsupportedhtml OBJECT-TYPE
    SYNTAX      ConfdString
    MAX-ACCESS  read-only
    STATUS      current
    DESCRIPTION "Number of Script-Link Insertion Failures Due to Unsupported HTML"
    ::= { affirmedServicesContentHttpProxyServiceStatisticsSlotLevelContentInsertionScriptLinkEntry 10 }

affirmedServicesContentHttpProxyServiceStatisticsSlotLevelContentInsertionScriptLinkScriptlinkinsertionfailureinvalidhtml OBJECT-TYPE
    SYNTAX      ConfdString
    MAX-ACCESS  read-only
    STATUS      current
    DESCRIPTION "Number of Script-Link Insertion Failures Due to Invalid HTML Format"
    ::= { affirmedServicesContentHttpProxyServiceStatisticsSlotLevelContentInsertionScriptLinkEntry 11 }

affirmedServicesContentHttpProxyServiceStatisticsSlotLevelTollFreeDataSummaryTable OBJECT-TYPE
    SYNTAX      SEQUENCE OF AffirmedServicesContentHttpProxyServiceStatisticsSlotLevelTollFreeDataSummaryEntry
    MAX-ACCESS  not-accessible
    STATUS      current
    DESCRIPTION ""
    ::= { affirmedServicesContentHttpProxyServiceStatisticsSlotLevelTollFreeData 1 }

affirmedServicesContentHttpProxyServiceStatisticsSlotLevelTollFreeDataSummaryEntry OBJECT-TYPE
    SYNTAX      AffirmedServicesContentHttpProxyServiceStatisticsSlotLevelTollFreeDataSummaryEntry
    MAX-ACCESS  not-accessible
    STATUS      current
    DESCRIPTION ""
    INDEX { affirmedServicesContentHttpProxyServiceStatisticsSlotLevelTollFreeDataSummaryChassis, affirmedServicesContentHttpProxyServiceStatisticsSlotLevelTollFreeDataSummarySlot }
        ::= { affirmedServicesContentHttpProxyServiceStatisticsSlotLevelTollFreeDataSummaryTable 1 }

AffirmedServicesContentHttpProxyServiceStatisticsSlotLevelTollFreeDataSummaryEntry ::=
    SEQUENCE {
        affirmedServicesContentHttpProxyServiceStatisticsSlotLevelTollFreeDataSummaryChassis Unsigned32,
        affirmedServicesContentHttpProxyServiceStatisticsSlotLevelTollFreeDataSummarySlot INTEGER,
        affirmedServicesContentHttpProxyServiceStatisticsSlotLevelTollFreeDataSummaryNumtotaltfdattempts ConfdString,
        affirmedServicesContentHttpProxyServiceStatisticsSlotLevelTollFreeDataSummaryNumtotaltfdsuccesses ConfdString,
        affirmedServicesContentHttpProxyServiceStatisticsSlotLevelTollFreeDataSummaryNumtotaltfdrejects ConfdString,
        affirmedServicesContentHttpProxyServiceStatisticsSlotLevelTollFreeDataSummaryNumtotaltfdhttpattempts ConfdString,
        affirmedServicesContentHttpProxyServiceStatisticsSlotLevelTollFreeDataSummaryNumtotaltfdhttpsuccesses ConfdString,
        affirmedServicesContentHttpProxyServiceStatisticsSlotLevelTollFreeDataSummaryNumtotaltfdhttprejects ConfdString,
        affirmedServicesContentHttpProxyServiceStatisticsSlotLevelTollFreeDataSummaryNumtotaltfdhttpsattempts ConfdString,
        affirmedServicesContentHttpProxyServiceStatisticsSlotLevelTollFreeDataSummaryNumtotaltfdhttpssuccesses ConfdString,
        affirmedServicesContentHttpProxyServiceStatisticsSlotLevelTollFreeDataSummaryNumtotaltfdhttpsrejects ConfdString,
        affirmedServicesContentHttpProxyServiceStatisticsSlotLevelTollFreeDataSummaryNumtotaltfdconnectattempts ConfdString,
        affirmedServicesContentHttpProxyServiceStatisticsSlotLevelTollFreeDataSummaryNumtotaltfdconnectsuccesses ConfdString,
        affirmedServicesContentHttpProxyServiceStatisticsSlotLevelTollFreeDataSummaryNumtotaltfdconnectrejects ConfdString,
        affirmedServicesContentHttpProxyServiceStatisticsSlotLevelTollFreeDataSummaryNumtotaltfdwebsocketattempts ConfdString,
        affirmedServicesContentHttpProxyServiceStatisticsSlotLevelTollFreeDataSummaryNumtotaltfdwebsocketsuccesses ConfdString,
        affirmedServicesContentHttpProxyServiceStatisticsSlotLevelTollFreeDataSummaryNumtotaltfdwebsocketrejects ConfdString,
        affirmedServicesContentHttpProxyServiceStatisticsSlotLevelTollFreeDataSummaryNumtotaltfdhttpserrorcallbacks ConfdString,
        affirmedServicesContentHttpProxyServiceStatisticsSlotLevelTollFreeDataSummaryNumtotaltfdconnecterrorcallbacks ConfdString
    }

affirmedServicesContentHttpProxyServiceStatisticsSlotLevelTollFreeDataSummaryChassis OBJECT-TYPE
    SYNTAX      Unsigned32
    MAX-ACCESS  not-accessible
    STATUS      current
    DESCRIPTION "chassis ID"
    ::= { affirmedServicesContentHttpProxyServiceStatisticsSlotLevelTollFreeDataSummaryEntry 1 }

affirmedServicesContentHttpProxyServiceStatisticsSlotLevelTollFreeDataSummarySlot OBJECT-TYPE
    SYNTAX      INTEGER {a1(1),a2(2),a3(3),a4(4),a5(5),a6(6),a7(7),a8(8),a9(9),a10(10),a11(11),a12(12),a13(13),a14(14),a15(15),a16(16),a17(17),a18(18),a19(19),a20(20),a21(21),a22(22),a23(23),a24(24),a25(25),a26(26),a27(27),a28(28),a29(29),a30(30),a31(31),a32(32),a33(33),a34(34),a35(35),a36(36),a37(37),a38(38),a39(39),a40(40),a41(41),a42(42),a43(43),a44(44),a45(45),a46(46),a47(47),a48(48),a49(49),a50(50),a51(51),a52(52),a53(53),a54(54),a55(55),a56(56),a57(57),a58(58),a59(59),a60(60),a61(61),a62(62),a63(63),a64(64),a65(65),a66(66),a67(67),a68(68),a69(69),a70(70),a71(71),a72(72),a73(73),a74(74),a75(75),a76(76),a77(77),a78(78),a79(79),a80(80),a81(81),a82(82),a83(83),a84(84),a85(85),a86(86),a87(87),a88(88),a89(89),a90(90),a91(91),a92(92),a93(93),a94(94),a95(95),a96(96),a97(97),a98(98),a99(99),a100(100),a101(101),a102(102),a103(103),a104(104),a105(105),a106(106),a107(107),a108(108),a109(109),a110(110),a111(111),a112(112),a113(113),a114(114),a115(115),a116(116),a117(117),a118(118),a119(119),a120(120),a121(121),a122(122),a123(123),a124(124),a125(125),a126(126),a127(127),a128(128)}
    MAX-ACCESS  not-accessible
    STATUS      current
    DESCRIPTION "slot number"
    ::= { affirmedServicesContentHttpProxyServiceStatisticsSlotLevelTollFreeDataSummaryEntry 2 }

affirmedServicesContentHttpProxyServiceStatisticsSlotLevelTollFreeDataSummaryNumtotaltfdattempts OBJECT-TYPE
    SYNTAX      ConfdString
    MAX-ACCESS  read-only
    STATUS      current
    DESCRIPTION "Total number of Toll Free Data Attempts"
    ::= { affirmedServicesContentHttpProxyServiceStatisticsSlotLevelTollFreeDataSummaryEntry 3 }

affirmedServicesContentHttpProxyServiceStatisticsSlotLevelTollFreeDataSummaryNumtotaltfdsuccesses OBJECT-TYPE
    SYNTAX      ConfdString
    MAX-ACCESS  read-only
    STATUS      current
    DESCRIPTION "Total number of Toll Free Data Successes"
    ::= { affirmedServicesContentHttpProxyServiceStatisticsSlotLevelTollFreeDataSummaryEntry 4 }

affirmedServicesContentHttpProxyServiceStatisticsSlotLevelTollFreeDataSummaryNumtotaltfdrejects OBJECT-TYPE
    SYNTAX      ConfdString
    MAX-ACCESS  read-only
    STATUS      current
    DESCRIPTION "Total number of Toll Free Data Rejects"
    ::= { affirmedServicesContentHttpProxyServiceStatisticsSlotLevelTollFreeDataSummaryEntry 5 }

affirmedServicesContentHttpProxyServiceStatisticsSlotLevelTollFreeDataSummaryNumtotaltfdhttpattempts OBJECT-TYPE
    SYNTAX      ConfdString
    MAX-ACCESS  read-only
    STATUS      current
    DESCRIPTION "Total number of HTTP Toll Free Data Attempts"
    ::= { affirmedServicesContentHttpProxyServiceStatisticsSlotLevelTollFreeDataSummaryEntry 6 }

affirmedServicesContentHttpProxyServiceStatisticsSlotLevelTollFreeDataSummaryNumtotaltfdhttpsuccesses OBJECT-TYPE
    SYNTAX      ConfdString
    MAX-ACCESS  read-only
    STATUS      current
    DESCRIPTION "Total number of HTTP Toll Free Data Successes"
    ::= { affirmedServicesContentHttpProxyServiceStatisticsSlotLevelTollFreeDataSummaryEntry 7 }

affirmedServicesContentHttpProxyServiceStatisticsSlotLevelTollFreeDataSummaryNumtotaltfdhttprejects OBJECT-TYPE
    SYNTAX      ConfdString
    MAX-ACCESS  read-only
    STATUS      current
    DESCRIPTION "Total number of HTTP Toll Free Data Rejects"
    ::= { affirmedServicesContentHttpProxyServiceStatisticsSlotLevelTollFreeDataSummaryEntry 8 }

affirmedServicesContentHttpProxyServiceStatisticsSlotLevelTollFreeDataSummaryNumtotaltfdhttpsattempts OBJECT-TYPE
    SYNTAX      ConfdString
    MAX-ACCESS  read-only
    STATUS      current
    DESCRIPTION "Total number of HTTPS Toll Free Data Attempts"
    ::= { affirmedServicesContentHttpProxyServiceStatisticsSlotLevelTollFreeDataSummaryEntry 9 }

affirmedServicesContentHttpProxyServiceStatisticsSlotLevelTollFreeDataSummaryNumtotaltfdhttpssuccesses OBJECT-TYPE
    SYNTAX      ConfdString
    MAX-ACCESS  read-only
    STATUS      current
    DESCRIPTION "Total number of HTTPS Toll Free Data Successes"
    ::= { affirmedServicesContentHttpProxyServiceStatisticsSlotLevelTollFreeDataSummaryEntry 10 }

affirmedServicesContentHttpProxyServiceStatisticsSlotLevelTollFreeDataSummaryNumtotaltfdhttpsrejects OBJECT-TYPE
    SYNTAX      ConfdString
    MAX-ACCESS  read-only
    STATUS      current
    DESCRIPTION "Total number of HTTPS Toll Free Data Rejects"
    ::= { affirmedServicesContentHttpProxyServiceStatisticsSlotLevelTollFreeDataSummaryEntry 11 }

affirmedServicesContentHttpProxyServiceStatisticsSlotLevelTollFreeDataSummaryNumtotaltfdconnectattempts OBJECT-TYPE
    SYNTAX      ConfdString
    MAX-ACCESS  read-only
    STATUS      current
    DESCRIPTION "Total number of CONNECT Toll Free Data Attempts"
    ::= { affirmedServicesContentHttpProxyServiceStatisticsSlotLevelTollFreeDataSummaryEntry 12 }

affirmedServicesContentHttpProxyServiceStatisticsSlotLevelTollFreeDataSummaryNumtotaltfdconnectsuccesses OBJECT-TYPE
    SYNTAX      ConfdString
    MAX-ACCESS  read-only
    STATUS      current
    DESCRIPTION "Total number of CONNECT Toll Free Data Successes"
    ::= { affirmedServicesContentHttpProxyServiceStatisticsSlotLevelTollFreeDataSummaryEntry 13 }

affirmedServicesContentHttpProxyServiceStatisticsSlotLevelTollFreeDataSummaryNumtotaltfdconnectrejects OBJECT-TYPE
    SYNTAX      ConfdString
    MAX-ACCESS  read-only
    STATUS      current
    DESCRIPTION "Total number of CONNECT Toll Free Data Rejects"
    ::= { affirmedServicesContentHttpProxyServiceStatisticsSlotLevelTollFreeDataSummaryEntry 14 }

affirmedServicesContentHttpProxyServiceStatisticsSlotLevelTollFreeDataSummaryNumtotaltfdwebsocketattempts OBJECT-TYPE
    SYNTAX      ConfdString
    MAX-ACCESS  read-only
    STATUS      current
    DESCRIPTION "Total number of Web Socket Toll Free Data Attempts"
    ::= { affirmedServicesContentHttpProxyServiceStatisticsSlotLevelTollFreeDataSummaryEntry 15 }

affirmedServicesContentHttpProxyServiceStatisticsSlotLevelTollFreeDataSummaryNumtotaltfdwebsocketsuccesses OBJECT-TYPE
    SYNTAX      ConfdString
    MAX-ACCESS  read-only
    STATUS      current
    DESCRIPTION "Total number of Web Socket Toll Free Data Successes"
    ::= { affirmedServicesContentHttpProxyServiceStatisticsSlotLevelTollFreeDataSummaryEntry 16 }

affirmedServicesContentHttpProxyServiceStatisticsSlotLevelTollFreeDataSummaryNumtotaltfdwebsocketrejects OBJECT-TYPE
    SYNTAX      ConfdString
    MAX-ACCESS  read-only
    STATUS      current
    DESCRIPTION "Total number of Web Socket Toll Free Data Rejects"
    ::= { affirmedServicesContentHttpProxyServiceStatisticsSlotLevelTollFreeDataSummaryEntry 17 }

affirmedServicesContentHttpProxyServiceStatisticsSlotLevelTollFreeDataSummaryNumtotaltfdhttpserrorcallbacks OBJECT-TYPE
    SYNTAX      ConfdString
    MAX-ACCESS  read-only
    STATUS      current
    DESCRIPTION "Total number of HTTPS Toll Free Data Error Callbacks sent"
    ::= { affirmedServicesContentHttpProxyServiceStatisticsSlotLevelTollFreeDataSummaryEntry 18 }

affirmedServicesContentHttpProxyServiceStatisticsSlotLevelTollFreeDataSummaryNumtotaltfdconnecterrorcallbacks OBJECT-TYPE
    SYNTAX      ConfdString
    MAX-ACCESS  read-only
    STATUS      current
    DESCRIPTION "Total number of CONNECT Toll Free Data Error Callbacks sent"
    ::= { affirmedServicesContentHttpProxyServiceStatisticsSlotLevelTollFreeDataSummaryEntry 19 }

affirmedServicesContentHttpProxyServiceStatisticsSlotLevelTollFreeDataDetailTable OBJECT-TYPE
    SYNTAX      SEQUENCE OF AffirmedServicesContentHttpProxyServiceStatisticsSlotLevelTollFreeDataDetailEntry
    MAX-ACCESS  not-accessible
    STATUS      current
    DESCRIPTION ""
    ::= { affirmedServicesContentHttpProxyServiceStatisticsSlotLevelTollFreeData 2 }

affirmedServicesContentHttpProxyServiceStatisticsSlotLevelTollFreeDataDetailEntry OBJECT-TYPE
    SYNTAX      AffirmedServicesContentHttpProxyServiceStatisticsSlotLevelTollFreeDataDetailEntry
    MAX-ACCESS  not-accessible
    STATUS      current
    DESCRIPTION ""
    INDEX { affirmedServicesContentHttpProxyServiceStatisticsSlotLevelTollFreeDataDetailChassis, affirmedServicesContentHttpProxyServiceStatisticsSlotLevelTollFreeDataDetailSlot }
        ::= { affirmedServicesContentHttpProxyServiceStatisticsSlotLevelTollFreeDataDetailTable 1 }

AffirmedServicesContentHttpProxyServiceStatisticsSlotLevelTollFreeDataDetailEntry ::=
    SEQUENCE {
        affirmedServicesContentHttpProxyServiceStatisticsSlotLevelTollFreeDataDetailChassis Unsigned32,
        affirmedServicesContentHttpProxyServiceStatisticsSlotLevelTollFreeDataDetailSlot INTEGER,
        affirmedServicesContentHttpProxyServiceStatisticsSlotLevelTollFreeDataDetailNumtotaltfdcertdownloads ConfdString,
        affirmedServicesContentHttpProxyServiceStatisticsSlotLevelTollFreeDataDetailNumtotaltfdcertdownloadsuccess ConfdString,
        affirmedServicesContentHttpProxyServiceStatisticsSlotLevelTollFreeDataDetailNumtotaltfdcertdownloaderrors ConfdString,
        affirmedServicesContentHttpProxyServiceStatisticsSlotLevelTollFreeDataDetailNumtotaltfdcertinvalid ConfdString,
        affirmedServicesContentHttpProxyServiceStatisticsSlotLevelTollFreeDataDetailNumtotaltfdcertrevoked ConfdString,
        affirmedServicesContentHttpProxyServiceStatisticsSlotLevelTollFreeDataDetailNumtotaltfdcertcrldownloads ConfdString,
        affirmedServicesContentHttpProxyServiceStatisticsSlotLevelTollFreeDataDetailNumtotalmanifestrecvd ConfdString,
        affirmedServicesContentHttpProxyServiceStatisticsSlotLevelTollFreeDataDetailNumtotalmanifestvalid ConfdString,
        affirmedServicesContentHttpProxyServiceStatisticsSlotLevelTollFreeDataDetailNumtotalmanifesterror ConfdString,
        affirmedServicesContentHttpProxyServiceStatisticsSlotLevelTollFreeDataDetailNumtotalmanifestbase64decodeerror ConfdString,
        affirmedServicesContentHttpProxyServiceStatisticsSlotLevelTollFreeDataDetailNumtotalmanifestcmsdecodeerror ConfdString,
        affirmedServicesContentHttpProxyServiceStatisticsSlotLevelTollFreeDataDetailNumtotalmanifestjsonparsingerror ConfdString,
        affirmedServicesContentHttpProxyServiceStatisticsSlotLevelTollFreeDataDetailNumtotalhttpbytesupstream ConfdString,
        affirmedServicesContentHttpProxyServiceStatisticsSlotLevelTollFreeDataDetailNumtotalhttpbytesdownstream ConfdString,
        affirmedServicesContentHttpProxyServiceStatisticsSlotLevelTollFreeDataDetailNumtotalhttpsbytesupstream ConfdString,
        affirmedServicesContentHttpProxyServiceStatisticsSlotLevelTollFreeDataDetailNumtotalhttpsbytesdownstream ConfdString,
        affirmedServicesContentHttpProxyServiceStatisticsSlotLevelTollFreeDataDetailNumtotalconnectbytesupstream ConfdString,
        affirmedServicesContentHttpProxyServiceStatisticsSlotLevelTollFreeDataDetailNumtotalconnectbytesdownstream ConfdString,
        affirmedServicesContentHttpProxyServiceStatisticsSlotLevelTollFreeDataDetailNumtotalwebsocketbytesupstream ConfdString,
        affirmedServicesContentHttpProxyServiceStatisticsSlotLevelTollFreeDataDetailNumtotalwebsocketbytesdownstream ConfdString,
        affirmedServicesContentHttpProxyServiceStatisticsSlotLevelTollFreeDataDetailNumtotalrejectintlroaming ConfdString,
        affirmedServicesContentHttpProxyServiceStatisticsSlotLevelTollFreeDataDetailNumtotalrejectoptout ConfdString,
        affirmedServicesContentHttpProxyServiceStatisticsSlotLevelTollFreeDataDetailNumtotalrejectineligible ConfdString,
        affirmedServicesContentHttpProxyServiceStatisticsSlotLevelTollFreeDataDetailNumtotalrejectcontentprovider ConfdString,
        affirmedServicesContentHttpProxyServiceStatisticsSlotLevelTollFreeDataDetailNumtotalrejectmissingsni ConfdString,
        affirmedServicesContentHttpProxyServiceStatisticsSlotLevelTollFreeDataDetailNumtotalrejectmanifestnomatch ConfdString,
        affirmedServicesContentHttpProxyServiceStatisticsSlotLevelTollFreeDataDetailNumtotalrejectinvalidprofile ConfdString,
        affirmedServicesContentHttpProxyServiceStatisticsSlotLevelTollFreeDataDetailNumtotalrejectinvalidrequest ConfdString,
        affirmedServicesContentHttpProxyServiceStatisticsSlotLevelTollFreeDataDetailNumtotalmanifestinvalidheaderformat ConfdString,
        affirmedServicesContentHttpProxyServiceStatisticsSlotLevelTollFreeDataDetailNumtotalmanifestcertificateerror ConfdString,
        affirmedServicesContentHttpProxyServiceStatisticsSlotLevelTollFreeDataDetailNumtotalmanifesturllisterror ConfdString,
        affirmedServicesContentHttpProxyServiceStatisticsSlotLevelTollFreeDataDetailNumtotalmanifestvalidationerror ConfdString,
        affirmedServicesContentHttpProxyServiceStatisticsSlotLevelTollFreeDataDetailNumtotalmanifestinternalerror ConfdString,
        affirmedServicesContentHttpProxyServiceStatisticsSlotLevelTollFreeDataDetailNumtotalrejectstatusunknown ConfdString,
        affirmedServicesContentHttpProxyServiceStatisticsSlotLevelTollFreeDataDetailNumtotaltfdcertcrldownloadsuccess ConfdString,
        affirmedServicesContentHttpProxyServiceStatisticsSlotLevelTollFreeDataDetailNumtotaltfdcertcrldownloaderror ConfdString
    }

affirmedServicesContentHttpProxyServiceStatisticsSlotLevelTollFreeDataDetailChassis OBJECT-TYPE
    SYNTAX      Unsigned32
    MAX-ACCESS  not-accessible
    STATUS      current
    DESCRIPTION "chassis ID"
    ::= { affirmedServicesContentHttpProxyServiceStatisticsSlotLevelTollFreeDataDetailEntry 1 }

affirmedServicesContentHttpProxyServiceStatisticsSlotLevelTollFreeDataDetailSlot OBJECT-TYPE
    SYNTAX      INTEGER {a1(1),a2(2),a3(3),a4(4),a5(5),a6(6),a7(7),a8(8),a9(9),a10(10),a11(11),a12(12),a13(13),a14(14),a15(15),a16(16),a17(17),a18(18),a19(19),a20(20),a21(21),a22(22),a23(23),a24(24),a25(25),a26(26),a27(27),a28(28),a29(29),a30(30),a31(31),a32(32),a33(33),a34(34),a35(35),a36(36),a37(37),a38(38),a39(39),a40(40),a41(41),a42(42),a43(43),a44(44),a45(45),a46(46),a47(47),a48(48),a49(49),a50(50),a51(51),a52(52),a53(53),a54(54),a55(55),a56(56),a57(57),a58(58),a59(59),a60(60),a61(61),a62(62),a63(63),a64(64),a65(65),a66(66),a67(67),a68(68),a69(69),a70(70),a71(71),a72(72),a73(73),a74(74),a75(75),a76(76),a77(77),a78(78),a79(79),a80(80),a81(81),a82(82),a83(83),a84(84),a85(85),a86(86),a87(87),a88(88),a89(89),a90(90),a91(91),a92(92),a93(93),a94(94),a95(95),a96(96),a97(97),a98(98),a99(99),a100(100),a101(101),a102(102),a103(103),a104(104),a105(105),a106(106),a107(107),a108(108),a109(109),a110(110),a111(111),a112(112),a113(113),a114(114),a115(115),a116(116),a117(117),a118(118),a119(119),a120(120),a121(121),a122(122),a123(123),a124(124),a125(125),a126(126),a127(127),a128(128)}
    MAX-ACCESS  not-accessible
    STATUS      current
    DESCRIPTION "slot number"
    ::= { affirmedServicesContentHttpProxyServiceStatisticsSlotLevelTollFreeDataDetailEntry 2 }

affirmedServicesContentHttpProxyServiceStatisticsSlotLevelTollFreeDataDetailNumtotaltfdcertdownloads OBJECT-TYPE
    SYNTAX      ConfdString
    MAX-ACCESS  read-only
    STATUS      current
    DESCRIPTION "Total number of Toll Free Data Certificate Download Attempts"
    ::= { affirmedServicesContentHttpProxyServiceStatisticsSlotLevelTollFreeDataDetailEntry 3 }

affirmedServicesContentHttpProxyServiceStatisticsSlotLevelTollFreeDataDetailNumtotaltfdcertdownloadsuccess OBJECT-TYPE
    SYNTAX      ConfdString
    MAX-ACCESS  read-only
    STATUS      current
    DESCRIPTION "Total number of Toll Free Data Certificate Download Successes"
    ::= { affirmedServicesContentHttpProxyServiceStatisticsSlotLevelTollFreeDataDetailEntry 4 }

affirmedServicesContentHttpProxyServiceStatisticsSlotLevelTollFreeDataDetailNumtotaltfdcertdownloaderrors OBJECT-TYPE
    SYNTAX      ConfdString
    MAX-ACCESS  read-only
    STATUS      current
    DESCRIPTION "Total number of Toll Free Data Certificate Download Errors"
    ::= { affirmedServicesContentHttpProxyServiceStatisticsSlotLevelTollFreeDataDetailEntry 5 }

affirmedServicesContentHttpProxyServiceStatisticsSlotLevelTollFreeDataDetailNumtotaltfdcertinvalid OBJECT-TYPE
    SYNTAX      ConfdString
    MAX-ACCESS  read-only
    STATUS      current
    DESCRIPTION "Total number of Invalid Toll Free Data Certificate"
    ::= { affirmedServicesContentHttpProxyServiceStatisticsSlotLevelTollFreeDataDetailEntry 6 }

affirmedServicesContentHttpProxyServiceStatisticsSlotLevelTollFreeDataDetailNumtotaltfdcertrevoked OBJECT-TYPE
    SYNTAX      ConfdString
    MAX-ACCESS  read-only
    STATUS      current
    DESCRIPTION "Total number of Revoked Toll Free Data Certificate"
    ::= { affirmedServicesContentHttpProxyServiceStatisticsSlotLevelTollFreeDataDetailEntry 7 }

affirmedServicesContentHttpProxyServiceStatisticsSlotLevelTollFreeDataDetailNumtotaltfdcertcrldownloads OBJECT-TYPE
    SYNTAX      ConfdString
    MAX-ACCESS  read-only
    STATUS      current
    DESCRIPTION "Total number of Toll Free Data Certificate CRL Download Attempts"
    ::= { affirmedServicesContentHttpProxyServiceStatisticsSlotLevelTollFreeDataDetailEntry 8 }

affirmedServicesContentHttpProxyServiceStatisticsSlotLevelTollFreeDataDetailNumtotalmanifestrecvd OBJECT-TYPE
    SYNTAX      ConfdString
    MAX-ACCESS  read-only
    STATUS      current
    DESCRIPTION "Total number of Toll Free Data Manifests Received"
    ::= { affirmedServicesContentHttpProxyServiceStatisticsSlotLevelTollFreeDataDetailEntry 9 }

affirmedServicesContentHttpProxyServiceStatisticsSlotLevelTollFreeDataDetailNumtotalmanifestvalid OBJECT-TYPE
    SYNTAX      ConfdString
    MAX-ACCESS  read-only
    STATUS      current
    DESCRIPTION "Total number of Toll Free Data Manifests that are valid"
    ::= { affirmedServicesContentHttpProxyServiceStatisticsSlotLevelTollFreeDataDetailEntry 10 }

affirmedServicesContentHttpProxyServiceStatisticsSlotLevelTollFreeDataDetailNumtotalmanifesterror OBJECT-TYPE
    SYNTAX      ConfdString
    MAX-ACCESS  read-only
    STATUS      current
    DESCRIPTION "Total number of Toll Free Data Manifests that warranted error callbacks"
    ::= { affirmedServicesContentHttpProxyServiceStatisticsSlotLevelTollFreeDataDetailEntry 11 }

affirmedServicesContentHttpProxyServiceStatisticsSlotLevelTollFreeDataDetailNumtotalmanifestbase64decodeerror OBJECT-TYPE
    SYNTAX      ConfdString
    MAX-ACCESS  read-only
    STATUS      current
    DESCRIPTION "Total number of Toll Free Data Manifests that have base64 decode errors"
    ::= { affirmedServicesContentHttpProxyServiceStatisticsSlotLevelTollFreeDataDetailEntry 12 }

affirmedServicesContentHttpProxyServiceStatisticsSlotLevelTollFreeDataDetailNumtotalmanifestcmsdecodeerror OBJECT-TYPE
    SYNTAX      ConfdString
    MAX-ACCESS  read-only
    STATUS      current
    DESCRIPTION "Total number of Toll Free Data Manifests that have CMS decode failures"
    ::= { affirmedServicesContentHttpProxyServiceStatisticsSlotLevelTollFreeDataDetailEntry 13 }

affirmedServicesContentHttpProxyServiceStatisticsSlotLevelTollFreeDataDetailNumtotalmanifestjsonparsingerror OBJECT-TYPE
    SYNTAX      ConfdString
    MAX-ACCESS  read-only
    STATUS      current
    DESCRIPTION "Total number of Toll Free Data Manifests that have JSON parsing errors"
    ::= { affirmedServicesContentHttpProxyServiceStatisticsSlotLevelTollFreeDataDetailEntry 14 }

affirmedServicesContentHttpProxyServiceStatisticsSlotLevelTollFreeDataDetailNumtotalhttpbytesupstream OBJECT-TYPE
    SYNTAX      ConfdString
    MAX-ACCESS  read-only
    STATUS      current
    DESCRIPTION "Total number of Toll Free Data HTTP Bytes Allowed Upstream"
    ::= { affirmedServicesContentHttpProxyServiceStatisticsSlotLevelTollFreeDataDetailEntry 15 }

affirmedServicesContentHttpProxyServiceStatisticsSlotLevelTollFreeDataDetailNumtotalhttpbytesdownstream OBJECT-TYPE
    SYNTAX      ConfdString
    MAX-ACCESS  read-only
    STATUS      current
    DESCRIPTION "Total number of Toll Free Data HTTP Bytes Allowed Downstream"
    ::= { affirmedServicesContentHttpProxyServiceStatisticsSlotLevelTollFreeDataDetailEntry 16 }

affirmedServicesContentHttpProxyServiceStatisticsSlotLevelTollFreeDataDetailNumtotalhttpsbytesupstream OBJECT-TYPE
    SYNTAX      ConfdString
    MAX-ACCESS  read-only
    STATUS      current
    DESCRIPTION "Total number of Toll Free Data HTTPS Bytes Allowed Upstream"
    ::= { affirmedServicesContentHttpProxyServiceStatisticsSlotLevelTollFreeDataDetailEntry 17 }

affirmedServicesContentHttpProxyServiceStatisticsSlotLevelTollFreeDataDetailNumtotalhttpsbytesdownstream OBJECT-TYPE
    SYNTAX      ConfdString
    MAX-ACCESS  read-only
    STATUS      current
    DESCRIPTION "Total number of Toll Free Data HTTPS Bytes Allowed Downstream"
    ::= { affirmedServicesContentHttpProxyServiceStatisticsSlotLevelTollFreeDataDetailEntry 18 }

affirmedServicesContentHttpProxyServiceStatisticsSlotLevelTollFreeDataDetailNumtotalconnectbytesupstream OBJECT-TYPE
    SYNTAX      ConfdString
    MAX-ACCESS  read-only
    STATUS      current
    DESCRIPTION "Total number of Toll Free Data CONNECT Bytes Allowed Upstream"
    ::= { affirmedServicesContentHttpProxyServiceStatisticsSlotLevelTollFreeDataDetailEntry 19 }

affirmedServicesContentHttpProxyServiceStatisticsSlotLevelTollFreeDataDetailNumtotalconnectbytesdownstream OBJECT-TYPE
    SYNTAX      ConfdString
    MAX-ACCESS  read-only
    STATUS      current
    DESCRIPTION "Total number of Toll Free Data CONNECT Bytes Allowed Downstream"
    ::= { affirmedServicesContentHttpProxyServiceStatisticsSlotLevelTollFreeDataDetailEntry 20 }

affirmedServicesContentHttpProxyServiceStatisticsSlotLevelTollFreeDataDetailNumtotalwebsocketbytesupstream OBJECT-TYPE
    SYNTAX      ConfdString
    MAX-ACCESS  read-only
    STATUS      current
    DESCRIPTION "Total number of Toll Free Data Web Socket Bytes Allowed Upstream"
    ::= { affirmedServicesContentHttpProxyServiceStatisticsSlotLevelTollFreeDataDetailEntry 21 }

affirmedServicesContentHttpProxyServiceStatisticsSlotLevelTollFreeDataDetailNumtotalwebsocketbytesdownstream OBJECT-TYPE
    SYNTAX      ConfdString
    MAX-ACCESS  read-only
    STATUS      current
    DESCRIPTION "Total number of Toll Free Data Web Socket Bytes Allowed Downstream"
    ::= { affirmedServicesContentHttpProxyServiceStatisticsSlotLevelTollFreeDataDetailEntry 22 }

affirmedServicesContentHttpProxyServiceStatisticsSlotLevelTollFreeDataDetailNumtotalrejectintlroaming OBJECT-TYPE
    SYNTAX      ConfdString
    MAX-ACCESS  read-only
    STATUS      current
    DESCRIPTION "Total number of Toll Free Data rejects due to the subscriber being International Roaming"
    ::= { affirmedServicesContentHttpProxyServiceStatisticsSlotLevelTollFreeDataDetailEntry 23 }

affirmedServicesContentHttpProxyServiceStatisticsSlotLevelTollFreeDataDetailNumtotalrejectoptout OBJECT-TYPE
    SYNTAX      ConfdString
    MAX-ACCESS  read-only
    STATUS      current
    DESCRIPTION "Total number of Toll Free Data rejects due to subscriber opting out"
    ::= { affirmedServicesContentHttpProxyServiceStatisticsSlotLevelTollFreeDataDetailEntry 24 }

affirmedServicesContentHttpProxyServiceStatisticsSlotLevelTollFreeDataDetailNumtotalrejectineligible OBJECT-TYPE
    SYNTAX      ConfdString
    MAX-ACCESS  read-only
    STATUS      current
    DESCRIPTION "Total number of Toll Free Data rejects due to the subscriber being Ineligible for the plan"
    ::= { affirmedServicesContentHttpProxyServiceStatisticsSlotLevelTollFreeDataDetailEntry 25 }

affirmedServicesContentHttpProxyServiceStatisticsSlotLevelTollFreeDataDetailNumtotalrejectcontentprovider OBJECT-TYPE
    SYNTAX      ConfdString
    MAX-ACCESS  read-only
    STATUS      current
    DESCRIPTION "Total number of Toll Free Data rejected by the Content Provider"
    ::= { affirmedServicesContentHttpProxyServiceStatisticsSlotLevelTollFreeDataDetailEntry 26 }

affirmedServicesContentHttpProxyServiceStatisticsSlotLevelTollFreeDataDetailNumtotalrejectmissingsni OBJECT-TYPE
    SYNTAX      ConfdString
    MAX-ACCESS  read-only
    STATUS      current
    DESCRIPTION "Total number of Toll Free Data rejected because of missing Server Name Indication"
    ::= { affirmedServicesContentHttpProxyServiceStatisticsSlotLevelTollFreeDataDetailEntry 27 }

affirmedServicesContentHttpProxyServiceStatisticsSlotLevelTollFreeDataDetailNumtotalrejectmanifestnomatch OBJECT-TYPE
    SYNTAX      ConfdString
    MAX-ACCESS  read-only
    STATUS      current
    DESCRIPTION "Total number of Toll Free Data rejected because the manifest URL did not match"
    ::= { affirmedServicesContentHttpProxyServiceStatisticsSlotLevelTollFreeDataDetailEntry 28 }

affirmedServicesContentHttpProxyServiceStatisticsSlotLevelTollFreeDataDetailNumtotalrejectinvalidprofile OBJECT-TYPE
    SYNTAX      ConfdString
    MAX-ACCESS  read-only
    STATUS      current
    DESCRIPTION "Total number of Toll Free Data rejected because of invalid toll-free-profile configuration"
    ::= { affirmedServicesContentHttpProxyServiceStatisticsSlotLevelTollFreeDataDetailEntry 29 }

affirmedServicesContentHttpProxyServiceStatisticsSlotLevelTollFreeDataDetailNumtotalrejectinvalidrequest OBJECT-TYPE
    SYNTAX      ConfdString
    MAX-ACCESS  read-only
    STATUS      current
    DESCRIPTION "Total number of Toll Free Data rejected because the request was not a HTTPS/TLS request"
    ::= { affirmedServicesContentHttpProxyServiceStatisticsSlotLevelTollFreeDataDetailEntry 30 }

affirmedServicesContentHttpProxyServiceStatisticsSlotLevelTollFreeDataDetailNumtotalmanifestinvalidheaderformat OBJECT-TYPE
    SYNTAX      ConfdString
    MAX-ACCESS  read-only
    STATUS      current
    DESCRIPTION "Total number of Toll Free Data Manifests with invalid header format"
    ::= { affirmedServicesContentHttpProxyServiceStatisticsSlotLevelTollFreeDataDetailEntry 31 }

affirmedServicesContentHttpProxyServiceStatisticsSlotLevelTollFreeDataDetailNumtotalmanifestcertificateerror OBJECT-TYPE
    SYNTAX      ConfdString
    MAX-ACCESS  read-only
    STATUS      current
    DESCRIPTION "Total number of Toll Free Data Manifests with certificate error during signature verification"
    ::= { affirmedServicesContentHttpProxyServiceStatisticsSlotLevelTollFreeDataDetailEntry 32 }

affirmedServicesContentHttpProxyServiceStatisticsSlotLevelTollFreeDataDetailNumtotalmanifesturllisterror OBJECT-TYPE
    SYNTAX      ConfdString
    MAX-ACCESS  read-only
    STATUS      current
    DESCRIPTION "Total number of Toll Free Data Manifests with URL list errors"
    ::= { affirmedServicesContentHttpProxyServiceStatisticsSlotLevelTollFreeDataDetailEntry 33 }

affirmedServicesContentHttpProxyServiceStatisticsSlotLevelTollFreeDataDetailNumtotalmanifestvalidationerror OBJECT-TYPE
    SYNTAX      ConfdString
    MAX-ACCESS  read-only
    STATUS      current
    DESCRIPTION "Total number of Toll Free Data Manifests with validation errors"
    ::= { affirmedServicesContentHttpProxyServiceStatisticsSlotLevelTollFreeDataDetailEntry 34 }

affirmedServicesContentHttpProxyServiceStatisticsSlotLevelTollFreeDataDetailNumtotalmanifestinternalerror OBJECT-TYPE
    SYNTAX      ConfdString
    MAX-ACCESS  read-only
    STATUS      current
    DESCRIPTION "Total number of Toll Free Data Manifests with internal handling errors"
    ::= { affirmedServicesContentHttpProxyServiceStatisticsSlotLevelTollFreeDataDetailEntry 35 }

affirmedServicesContentHttpProxyServiceStatisticsSlotLevelTollFreeDataDetailNumtotalrejectstatusunknown OBJECT-TYPE
    SYNTAX      ConfdString
    MAX-ACCESS  read-only
    STATUS      current
    DESCRIPTION "Total number of Toll Free Data rejected because the PCRF state is unknown"
    ::= { affirmedServicesContentHttpProxyServiceStatisticsSlotLevelTollFreeDataDetailEntry 36 }

affirmedServicesContentHttpProxyServiceStatisticsSlotLevelTollFreeDataDetailNumtotaltfdcertcrldownloadsuccess OBJECT-TYPE
    SYNTAX      ConfdString
    MAX-ACCESS  read-only
    STATUS      current
    DESCRIPTION "Total number of Toll Free Data Certificate CRL Download Successes"
    ::= { affirmedServicesContentHttpProxyServiceStatisticsSlotLevelTollFreeDataDetailEntry 37 }

affirmedServicesContentHttpProxyServiceStatisticsSlotLevelTollFreeDataDetailNumtotaltfdcertcrldownloaderror OBJECT-TYPE
    SYNTAX      ConfdString
    MAX-ACCESS  read-only
    STATUS      current
    DESCRIPTION "Total number of Toll Free Data Certificate CRL Download Errors"
    ::= { affirmedServicesContentHttpProxyServiceStatisticsSlotLevelTollFreeDataDetailEntry 38 }

affirmedServicesContentHttpProxyServiceStatisticsSlotLevelTcpSplicingRateLimitingTable OBJECT-TYPE
    SYNTAX      SEQUENCE OF AffirmedServicesContentHttpProxyServiceStatisticsSlotLevelTcpSplicingRateLimitingEntry
    MAX-ACCESS  not-accessible
    STATUS      current
    DESCRIPTION ""
    ::= { affirmedServicesContentHttpProxyServiceStatisticsSlotLevelTcpSplicing 1 }

affirmedServicesContentHttpProxyServiceStatisticsSlotLevelTcpSplicingRateLimitingEntry OBJECT-TYPE
    SYNTAX      AffirmedServicesContentHttpProxyServiceStatisticsSlotLevelTcpSplicingRateLimitingEntry
    MAX-ACCESS  not-accessible
    STATUS      current
    DESCRIPTION ""
    INDEX { affirmedServicesContentHttpProxyServiceStatisticsSlotLevelTcpSplicingRateLimitingChassis, affirmedServicesContentHttpProxyServiceStatisticsSlotLevelTcpSplicingRateLimitingSlot }
        ::= { affirmedServicesContentHttpProxyServiceStatisticsSlotLevelTcpSplicingRateLimitingTable 1 }

AffirmedServicesContentHttpProxyServiceStatisticsSlotLevelTcpSplicingRateLimitingEntry ::=
    SEQUENCE {
        affirmedServicesContentHttpProxyServiceStatisticsSlotLevelTcpSplicingRateLimitingChassis Unsigned32,
        affirmedServicesContentHttpProxyServiceStatisticsSlotLevelTcpSplicingRateLimitingSlot INTEGER,
        affirmedServicesContentHttpProxyServiceStatisticsSlotLevelTcpSplicingRateLimitingNumratelimitingsummaryattempts ConfdString,
        affirmedServicesContentHttpProxyServiceStatisticsSlotLevelTcpSplicingRateLimitingNumratelimitingsummarysuccesses ConfdString,
        affirmedServicesContentHttpProxyServiceStatisticsSlotLevelTcpSplicingRateLimitingNumratelimitingsummarycancels ConfdString,
        affirmedServicesContentHttpProxyServiceStatisticsSlotLevelTcpSplicingRateLimitingNumratelimitingbytes ConfdString,
        affirmedServicesContentHttpProxyServiceStatisticsSlotLevelTcpSplicingRateLimitingNumratelimitingconnectionscurrent ConfdString,
        affirmedServicesContentHttpProxyServiceStatisticsSlotLevelTcpSplicingRateLimitingNumratelimitingcancelsrsptooshort ConfdString,
        affirmedServicesContentHttpProxyServiceStatisticsSlotLevelTcpSplicingRateLimitingNumratelimitingoptedoutbysubscriber ConfdString,
        affirmedServicesContentHttpProxyServiceStatisticsSlotLevelTcpSplicingRateLimitingNumratelimitingdisabled ConfdString,
        affirmedServicesContentHttpProxyServiceStatisticsSlotLevelTcpSplicingRateLimitingNumratelimitingoptedinreqnotmet ConfdString,
        affirmedServicesContentHttpProxyServiceStatisticsSlotLevelTcpSplicingRateLimitingNumratelimitingnomaxrateincpmanifest ConfdString,
        affirmedServicesContentHttpProxyServiceStatisticsSlotLevelTcpSplicingRateLimitingNumratelimitingsummarycpmanifestwithmaxrate ConfdString,
        affirmedServicesContentHttpProxyServiceStatisticsSlotLevelTcpSplicingRateLimitingNumratelimitinginvalidmaxrateincpmanifest ConfdString,
        affirmedServicesContentHttpProxyServiceStatisticsSlotLevelTcpSplicingRateLimitingNumratelimitingsessions250500 ConfdString,
        affirmedServicesContentHttpProxyServiceStatisticsSlotLevelTcpSplicingRateLimitingNumratelimitingsessions5001500 ConfdString,
        affirmedServicesContentHttpProxyServiceStatisticsSlotLevelTcpSplicingRateLimitingNumratelimitingsessions15003000 ConfdString,
        affirmedServicesContentHttpProxyServiceStatisticsSlotLevelTcpSplicingRateLimitingNumratelimitingsessions30006000 ConfdString,
        affirmedServicesContentHttpProxyServiceStatisticsSlotLevelTcpSplicingRateLimitingNumratelimitingsessions6000more ConfdString,
        affirmedServicesContentHttpProxyServiceStatisticsSlotLevelTcpSplicingRateLimitingNumratelimitedbytesld ConfdString,
        affirmedServicesContentHttpProxyServiceStatisticsSlotLevelTcpSplicingRateLimitingNumratelimitedbytessd ConfdString,
        affirmedServicesContentHttpProxyServiceStatisticsSlotLevelTcpSplicingRateLimitingNumratelimitedbyteshd ConfdString,
        affirmedServicesContentHttpProxyServiceStatisticsSlotLevelTcpSplicingRateLimitingNumratelimitedbytesfullhd ConfdString,
        affirmedServicesContentHttpProxyServiceStatisticsSlotLevelTcpSplicingRateLimitingNumratelimitedbytesuhd ConfdString,
        affirmedServicesContentHttpProxyServiceStatisticsSlotLevelTcpSplicingRateLimitingNumratelimitingbypasssavingsestimation ConfdString,
        affirmedServicesContentHttpProxyServiceStatisticsSlotLevelTcpSplicingRateLimitingNumratelimitingsessioncounttotal ConfdString,
        affirmedServicesContentHttpProxyServiceStatisticsSlotLevelTcpSplicingRateLimitingNumratelimitingsessionaverageflowcount ConfdString,
        affirmedServicesContentHttpProxyServiceStatisticsSlotLevelTcpSplicingRateLimitingNumratelimitingsessionaverageduration ConfdString,
        affirmedServicesContentHttpProxyServiceStatisticsSlotLevelTcpSplicingRateLimitingNumratelimitingbypassoverload ConfdString,
        affirmedServicesContentHttpProxyServiceStatisticsSlotLevelTcpSplicingRateLimitingNumratelimitingsessionaggregationbypass ConfdString
    }

affirmedServicesContentHttpProxyServiceStatisticsSlotLevelTcpSplicingRateLimitingChassis OBJECT-TYPE
    SYNTAX      Unsigned32
    MAX-ACCESS  not-accessible
    STATUS      current
    DESCRIPTION "chassis ID"
    ::= { affirmedServicesContentHttpProxyServiceStatisticsSlotLevelTcpSplicingRateLimitingEntry 1 }

affirmedServicesContentHttpProxyServiceStatisticsSlotLevelTcpSplicingRateLimitingSlot OBJECT-TYPE
    SYNTAX      INTEGER {a1(1),a2(2),a3(3),a4(4),a5(5),a6(6),a7(7),a8(8),a9(9),a10(10),a11(11),a12(12),a13(13),a14(14),a15(15),a16(16),a17(17),a18(18),a19(19),a20(20),a21(21),a22(22),a23(23),a24(24),a25(25),a26(26),a27(27),a28(28),a29(29),a30(30),a31(31),a32(32),a33(33),a34(34),a35(35),a36(36),a37(37),a38(38),a39(39),a40(40),a41(41),a42(42),a43(43),a44(44),a45(45),a46(46),a47(47),a48(48),a49(49),a50(50),a51(51),a52(52),a53(53),a54(54),a55(55),a56(56),a57(57),a58(58),a59(59),a60(60),a61(61),a62(62),a63(63),a64(64),a65(65),a66(66),a67(67),a68(68),a69(69),a70(70),a71(71),a72(72),a73(73),a74(74),a75(75),a76(76),a77(77),a78(78),a79(79),a80(80),a81(81),a82(82),a83(83),a84(84),a85(85),a86(86),a87(87),a88(88),a89(89),a90(90),a91(91),a92(92),a93(93),a94(94),a95(95),a96(96),a97(97),a98(98),a99(99),a100(100),a101(101),a102(102),a103(103),a104(104),a105(105),a106(106),a107(107),a108(108),a109(109),a110(110),a111(111),a112(112),a113(113),a114(114),a115(115),a116(116),a117(117),a118(118),a119(119),a120(120),a121(121),a122(122),a123(123),a124(124),a125(125),a126(126),a127(127),a128(128)}
    MAX-ACCESS  not-accessible
    STATUS      current
    DESCRIPTION "slot number"
    ::= { affirmedServicesContentHttpProxyServiceStatisticsSlotLevelTcpSplicingRateLimitingEntry 2 }

affirmedServicesContentHttpProxyServiceStatisticsSlotLevelTcpSplicingRateLimitingNumratelimitingsummaryattempts OBJECT-TYPE
    SYNTAX      ConfdString
    MAX-ACCESS  read-only
    STATUS      current
    DESCRIPTION "Total number of Rate Limiting Summary Attempts"
    ::= { affirmedServicesContentHttpProxyServiceStatisticsSlotLevelTcpSplicingRateLimitingEntry 3 }

affirmedServicesContentHttpProxyServiceStatisticsSlotLevelTcpSplicingRateLimitingNumratelimitingsummarysuccesses OBJECT-TYPE
    SYNTAX      ConfdString
    MAX-ACCESS  read-only
    STATUS      current
    DESCRIPTION "Total number of Rate Limiting Summary Successes"
    ::= { affirmedServicesContentHttpProxyServiceStatisticsSlotLevelTcpSplicingRateLimitingEntry 4 }

affirmedServicesContentHttpProxyServiceStatisticsSlotLevelTcpSplicingRateLimitingNumratelimitingsummarycancels OBJECT-TYPE
    SYNTAX      ConfdString
    MAX-ACCESS  read-only
    STATUS      current
    DESCRIPTION "Total number of Rate Limiting Summary Cancels"
    ::= { affirmedServicesContentHttpProxyServiceStatisticsSlotLevelTcpSplicingRateLimitingEntry 5 }

affirmedServicesContentHttpProxyServiceStatisticsSlotLevelTcpSplicingRateLimitingNumratelimitingbytes OBJECT-TYPE
    SYNTAX      ConfdString
    MAX-ACCESS  read-only
    STATUS      current
    DESCRIPTION "Total number of Rate Limiting Bytes"
    ::= { affirmedServicesContentHttpProxyServiceStatisticsSlotLevelTcpSplicingRateLimitingEntry 6 }

affirmedServicesContentHttpProxyServiceStatisticsSlotLevelTcpSplicingRateLimitingNumratelimitingconnectionscurrent OBJECT-TYPE
    SYNTAX      ConfdString
    MAX-ACCESS  read-only
    STATUS      current
    DESCRIPTION "Total number of Rate Limiting Connections Current"
    ::= { affirmedServicesContentHttpProxyServiceStatisticsSlotLevelTcpSplicingRateLimitingEntry 7 }

affirmedServicesContentHttpProxyServiceStatisticsSlotLevelTcpSplicingRateLimitingNumratelimitingcancelsrsptooshort OBJECT-TYPE
    SYNTAX      ConfdString
    MAX-ACCESS  read-only
    STATUS      current
    DESCRIPTION "Total number of Rate Limiting Response Too Short"
    ::= { affirmedServicesContentHttpProxyServiceStatisticsSlotLevelTcpSplicingRateLimitingEntry 8 }

affirmedServicesContentHttpProxyServiceStatisticsSlotLevelTcpSplicingRateLimitingNumratelimitingoptedoutbysubscriber OBJECT-TYPE
    SYNTAX      ConfdString
    MAX-ACCESS  read-only
    STATUS      current
    DESCRIPTION "Total number of Rate Limiting Opted Out by Subscriber"
    ::= { affirmedServicesContentHttpProxyServiceStatisticsSlotLevelTcpSplicingRateLimitingEntry 9 }

affirmedServicesContentHttpProxyServiceStatisticsSlotLevelTcpSplicingRateLimitingNumratelimitingdisabled OBJECT-TYPE
    SYNTAX      ConfdString
    MAX-ACCESS  read-only
    STATUS      current
    DESCRIPTION "Total number of Rate Limiting Disabled"
    ::= { affirmedServicesContentHttpProxyServiceStatisticsSlotLevelTcpSplicingRateLimitingEntry 10 }

affirmedServicesContentHttpProxyServiceStatisticsSlotLevelTcpSplicingRateLimitingNumratelimitingoptedinreqnotmet OBJECT-TYPE
    SYNTAX      ConfdString
    MAX-ACCESS  read-only
    STATUS      current
    DESCRIPTION "Total number of Rate Limiting Opted by Subscriber but Requirements not met"
    ::= { affirmedServicesContentHttpProxyServiceStatisticsSlotLevelTcpSplicingRateLimitingEntry 11 }

affirmedServicesContentHttpProxyServiceStatisticsSlotLevelTcpSplicingRateLimitingNumratelimitingnomaxrateincpmanifest OBJECT-TYPE
    SYNTAX      ConfdString
    MAX-ACCESS  read-only
    STATUS      current
    DESCRIPTION "Total number of Rate Limiting No Max-Rate in the CP Manifest"
    ::= { affirmedServicesContentHttpProxyServiceStatisticsSlotLevelTcpSplicingRateLimitingEntry 12 }

affirmedServicesContentHttpProxyServiceStatisticsSlotLevelTcpSplicingRateLimitingNumratelimitingsummarycpmanifestwithmaxrate OBJECT-TYPE
    SYNTAX      ConfdString
    MAX-ACCESS  read-only
    STATUS      current
    DESCRIPTION "Total number of Rate Limiting Summary- CP Manifest with Max-Rate"
    ::= { affirmedServicesContentHttpProxyServiceStatisticsSlotLevelTcpSplicingRateLimitingEntry 13 }

affirmedServicesContentHttpProxyServiceStatisticsSlotLevelTcpSplicingRateLimitingNumratelimitinginvalidmaxrateincpmanifest OBJECT-TYPE
    SYNTAX      ConfdString
    MAX-ACCESS  read-only
    STATUS      current
    DESCRIPTION "Total number of Rate Limiting Invalid Max-Rate in the CP Manifest"
    ::= { affirmedServicesContentHttpProxyServiceStatisticsSlotLevelTcpSplicingRateLimitingEntry 14 }

affirmedServicesContentHttpProxyServiceStatisticsSlotLevelTcpSplicingRateLimitingNumratelimitingsessions250500 OBJECT-TYPE
    SYNTAX      ConfdString
    MAX-ACCESS  read-only
    STATUS      current
    DESCRIPTION "Total number of Rate Limiting Sessions from 250 to 500kbps (LD)"
    ::= { affirmedServicesContentHttpProxyServiceStatisticsSlotLevelTcpSplicingRateLimitingEntry 15 }

affirmedServicesContentHttpProxyServiceStatisticsSlotLevelTcpSplicingRateLimitingNumratelimitingsessions5001500 OBJECT-TYPE
    SYNTAX      ConfdString
    MAX-ACCESS  read-only
    STATUS      current
    DESCRIPTION "Total number of Rate Limiting Sessions from 500 to 1500kbps (SD)"
    ::= { affirmedServicesContentHttpProxyServiceStatisticsSlotLevelTcpSplicingRateLimitingEntry 16 }

affirmedServicesContentHttpProxyServiceStatisticsSlotLevelTcpSplicingRateLimitingNumratelimitingsessions15003000 OBJECT-TYPE
    SYNTAX      ConfdString
    MAX-ACCESS  read-only
    STATUS      current
    DESCRIPTION "Total number of Rate Limiting Sessions from 1500 to 3000kbps (HD)"
    ::= { affirmedServicesContentHttpProxyServiceStatisticsSlotLevelTcpSplicingRateLimitingEntry 17 }

affirmedServicesContentHttpProxyServiceStatisticsSlotLevelTcpSplicingRateLimitingNumratelimitingsessions30006000 OBJECT-TYPE
    SYNTAX      ConfdString
    MAX-ACCESS  read-only
    STATUS      current
    DESCRIPTION "Total number of Rate Limiting Sessions from 3000 to 6000kbps (Full HD)"
    ::= { affirmedServicesContentHttpProxyServiceStatisticsSlotLevelTcpSplicingRateLimitingEntry 18 }

affirmedServicesContentHttpProxyServiceStatisticsSlotLevelTcpSplicingRateLimitingNumratelimitingsessions6000more OBJECT-TYPE
    SYNTAX      ConfdString
    MAX-ACCESS  read-only
    STATUS      current
    DESCRIPTION "Total number of Rate Limiting Sessions greater than 6000kbps (UHD)"
    ::= { affirmedServicesContentHttpProxyServiceStatisticsSlotLevelTcpSplicingRateLimitingEntry 19 }

affirmedServicesContentHttpProxyServiceStatisticsSlotLevelTcpSplicingRateLimitingNumratelimitedbytesld OBJECT-TYPE
    SYNTAX      ConfdString
    MAX-ACCESS  read-only
    STATUS      current
    DESCRIPTION "Total number of Rate Limited Bytes - LD"
    ::= { affirmedServicesContentHttpProxyServiceStatisticsSlotLevelTcpSplicingRateLimitingEntry 20 }

affirmedServicesContentHttpProxyServiceStatisticsSlotLevelTcpSplicingRateLimitingNumratelimitedbytessd OBJECT-TYPE
    SYNTAX      ConfdString
    MAX-ACCESS  read-only
    STATUS      current
    DESCRIPTION "Total number of Rate Limited Bytes - SD"
    ::= { affirmedServicesContentHttpProxyServiceStatisticsSlotLevelTcpSplicingRateLimitingEntry 21 }

affirmedServicesContentHttpProxyServiceStatisticsSlotLevelTcpSplicingRateLimitingNumratelimitedbyteshd OBJECT-TYPE
    SYNTAX      ConfdString
    MAX-ACCESS  read-only
    STATUS      current
    DESCRIPTION "Total number of Rate Limited Bytes - HD"
    ::= { affirmedServicesContentHttpProxyServiceStatisticsSlotLevelTcpSplicingRateLimitingEntry 22 }

affirmedServicesContentHttpProxyServiceStatisticsSlotLevelTcpSplicingRateLimitingNumratelimitedbytesfullhd OBJECT-TYPE
    SYNTAX      ConfdString
    MAX-ACCESS  read-only
    STATUS      current
    DESCRIPTION "Total number of Rate Limited Bytes - Full HD"
    ::= { affirmedServicesContentHttpProxyServiceStatisticsSlotLevelTcpSplicingRateLimitingEntry 23 }

affirmedServicesContentHttpProxyServiceStatisticsSlotLevelTcpSplicingRateLimitingNumratelimitedbytesuhd OBJECT-TYPE
    SYNTAX      ConfdString
    MAX-ACCESS  read-only
    STATUS      current
    DESCRIPTION "Total number of Rate Limited Bytes - UHD"
    ::= { affirmedServicesContentHttpProxyServiceStatisticsSlotLevelTcpSplicingRateLimitingEntry 24 }

affirmedServicesContentHttpProxyServiceStatisticsSlotLevelTcpSplicingRateLimitingNumratelimitingbypasssavingsestimation OBJECT-TYPE
    SYNTAX      ConfdString
    MAX-ACCESS  read-only
    STATUS      current
    DESCRIPTION "Total number of Rate Limiting Bypass due to Savings Estimation"
    ::= { affirmedServicesContentHttpProxyServiceStatisticsSlotLevelTcpSplicingRateLimitingEntry 25 }

affirmedServicesContentHttpProxyServiceStatisticsSlotLevelTcpSplicingRateLimitingNumratelimitingsessioncounttotal OBJECT-TYPE
    SYNTAX      ConfdString
    MAX-ACCESS  read-only
    STATUS      current
    DESCRIPTION "Total number of Rate Limiting sessions"
    ::= { affirmedServicesContentHttpProxyServiceStatisticsSlotLevelTcpSplicingRateLimitingEntry 26 }

affirmedServicesContentHttpProxyServiceStatisticsSlotLevelTcpSplicingRateLimitingNumratelimitingsessionaverageflowcount OBJECT-TYPE
    SYNTAX      ConfdString
    MAX-ACCESS  read-only
    STATUS      current
    DESCRIPTION "Average number of Rate Limiting Flows/Session"
    ::= { affirmedServicesContentHttpProxyServiceStatisticsSlotLevelTcpSplicingRateLimitingEntry 27 }

affirmedServicesContentHttpProxyServiceStatisticsSlotLevelTcpSplicingRateLimitingNumratelimitingsessionaverageduration OBJECT-TYPE
    SYNTAX      ConfdString
    MAX-ACCESS  read-only
    STATUS      current
    DESCRIPTION "Average duration of Rate Limiting Sessions"
    ::= { affirmedServicesContentHttpProxyServiceStatisticsSlotLevelTcpSplicingRateLimitingEntry 28 }

affirmedServicesContentHttpProxyServiceStatisticsSlotLevelTcpSplicingRateLimitingNumratelimitingbypassoverload OBJECT-TYPE
    SYNTAX      ConfdString
    MAX-ACCESS  read-only
    STATUS      current
    DESCRIPTION "Total number of Rate Limiting Bypass due to Overload"
    ::= { affirmedServicesContentHttpProxyServiceStatisticsSlotLevelTcpSplicingRateLimitingEntry 29 }

affirmedServicesContentHttpProxyServiceStatisticsSlotLevelTcpSplicingRateLimitingNumratelimitingsessionaggregationbypass OBJECT-TYPE
    SYNTAX      ConfdString
    MAX-ACCESS  read-only
    STATUS      current
    DESCRIPTION "Total number of Rate Limiting sessions aggregation bypass"
    ::= { affirmedServicesContentHttpProxyServiceStatisticsSlotLevelTcpSplicingRateLimitingEntry 30 }

affirmedServicesContentHttpProxyServiceStatisticsSlotLevelTcpSplicingSummaryTable OBJECT-TYPE
    SYNTAX      SEQUENCE OF AffirmedServicesContentHttpProxyServiceStatisticsSlotLevelTcpSplicingSummaryEntry
    MAX-ACCESS  not-accessible
    STATUS      current
    DESCRIPTION ""
    ::= { affirmedServicesContentHttpProxyServiceStatisticsSlotLevelTcpSplicing 2 }

affirmedServicesContentHttpProxyServiceStatisticsSlotLevelTcpSplicingSummaryEntry OBJECT-TYPE
    SYNTAX      AffirmedServicesContentHttpProxyServiceStatisticsSlotLevelTcpSplicingSummaryEntry
    MAX-ACCESS  not-accessible
    STATUS      current
    DESCRIPTION ""
    INDEX { affirmedServicesContentHttpProxyServiceStatisticsSlotLevelTcpSplicingSummaryChassis, affirmedServicesContentHttpProxyServiceStatisticsSlotLevelTcpSplicingSummarySlot }
        ::= { affirmedServicesContentHttpProxyServiceStatisticsSlotLevelTcpSplicingSummaryTable 1 }

AffirmedServicesContentHttpProxyServiceStatisticsSlotLevelTcpSplicingSummaryEntry ::=
    SEQUENCE {
        affirmedServicesContentHttpProxyServiceStatisticsSlotLevelTcpSplicingSummaryChassis Unsigned32,
        affirmedServicesContentHttpProxyServiceStatisticsSlotLevelTcpSplicingSummarySlot INTEGER,
        affirmedServicesContentHttpProxyServiceStatisticsSlotLevelTcpSplicingSummaryNumtcpsplicingsummaryattempts ConfdString,
        affirmedServicesContentHttpProxyServiceStatisticsSlotLevelTcpSplicingSummaryNumtcpsplicingsummarysuccesses ConfdString,
        affirmedServicesContentHttpProxyServiceStatisticsSlotLevelTcpSplicingSummaryNumtcpsplicingsummaryaborts ConfdString,
        affirmedServicesContentHttpProxyServiceStatisticsSlotLevelTcpSplicingSummaryNumtcpsplicingsummaryfailures ConfdString,
        affirmedServicesContentHttpProxyServiceStatisticsSlotLevelTcpSplicingSummaryNumtcpservicedurationminseconds ConfdString,
        affirmedServicesContentHttpProxyServiceStatisticsSlotLevelTcpSplicingSummaryNumtcpservicedurationmaxseconds ConfdString,
        affirmedServicesContentHttpProxyServiceStatisticsSlotLevelTcpSplicingSummaryNumtcpservicedurationtotalseconds ConfdString,
        affirmedServicesContentHttpProxyServiceStatisticsSlotLevelTcpSplicingSummaryNumtcpservicedurationaverageseconds ConfdString,
        affirmedServicesContentHttpProxyServiceStatisticsSlotLevelTcpSplicingSummaryNumtcpservicedurationmin ConfdString,
        affirmedServicesContentHttpProxyServiceStatisticsSlotLevelTcpSplicingSummaryNumtcpservicedurationmax ConfdString,
        affirmedServicesContentHttpProxyServiceStatisticsSlotLevelTcpSplicingSummaryNumtcpservicedurationavg ConfdString
    }

affirmedServicesContentHttpProxyServiceStatisticsSlotLevelTcpSplicingSummaryChassis OBJECT-TYPE
    SYNTAX      Unsigned32
    MAX-ACCESS  not-accessible
    STATUS      current
    DESCRIPTION "chassis ID"
    ::= { affirmedServicesContentHttpProxyServiceStatisticsSlotLevelTcpSplicingSummaryEntry 1 }

affirmedServicesContentHttpProxyServiceStatisticsSlotLevelTcpSplicingSummarySlot OBJECT-TYPE
    SYNTAX      INTEGER {a1(1),a2(2),a3(3),a4(4),a5(5),a6(6),a7(7),a8(8),a9(9),a10(10),a11(11),a12(12),a13(13),a14(14),a15(15),a16(16),a17(17),a18(18),a19(19),a20(20),a21(21),a22(22),a23(23),a24(24),a25(25),a26(26),a27(27),a28(28),a29(29),a30(30),a31(31),a32(32),a33(33),a34(34),a35(35),a36(36),a37(37),a38(38),a39(39),a40(40),a41(41),a42(42),a43(43),a44(44),a45(45),a46(46),a47(47),a48(48),a49(49),a50(50),a51(51),a52(52),a53(53),a54(54),a55(55),a56(56),a57(57),a58(58),a59(59),a60(60),a61(61),a62(62),a63(63),a64(64),a65(65),a66(66),a67(67),a68(68),a69(69),a70(70),a71(71),a72(72),a73(73),a74(74),a75(75),a76(76),a77(77),a78(78),a79(79),a80(80),a81(81),a82(82),a83(83),a84(84),a85(85),a86(86),a87(87),a88(88),a89(89),a90(90),a91(91),a92(92),a93(93),a94(94),a95(95),a96(96),a97(97),a98(98),a99(99),a100(100),a101(101),a102(102),a103(103),a104(104),a105(105),a106(106),a107(107),a108(108),a109(109),a110(110),a111(111),a112(112),a113(113),a114(114),a115(115),a116(116),a117(117),a118(118),a119(119),a120(120),a121(121),a122(122),a123(123),a124(124),a125(125),a126(126),a127(127),a128(128)}
    MAX-ACCESS  not-accessible
    STATUS      current
    DESCRIPTION "slot number"
    ::= { affirmedServicesContentHttpProxyServiceStatisticsSlotLevelTcpSplicingSummaryEntry 2 }

affirmedServicesContentHttpProxyServiceStatisticsSlotLevelTcpSplicingSummaryNumtcpsplicingsummaryattempts OBJECT-TYPE
    SYNTAX      ConfdString
    MAX-ACCESS  read-only
    STATUS      current
    DESCRIPTION "Number of tcp splicing summary attempts"
    ::= { affirmedServicesContentHttpProxyServiceStatisticsSlotLevelTcpSplicingSummaryEntry 3 }

affirmedServicesContentHttpProxyServiceStatisticsSlotLevelTcpSplicingSummaryNumtcpsplicingsummarysuccesses OBJECT-TYPE
    SYNTAX      ConfdString
    MAX-ACCESS  read-only
    STATUS      current
    DESCRIPTION "Number of tcp splicing summary successes"
    ::= { affirmedServicesContentHttpProxyServiceStatisticsSlotLevelTcpSplicingSummaryEntry 4 }

affirmedServicesContentHttpProxyServiceStatisticsSlotLevelTcpSplicingSummaryNumtcpsplicingsummaryaborts OBJECT-TYPE
    SYNTAX      ConfdString
    MAX-ACCESS  read-only
    STATUS      current
    DESCRIPTION "Number of tcp splicing summary aborts"
    ::= { affirmedServicesContentHttpProxyServiceStatisticsSlotLevelTcpSplicingSummaryEntry 5 }

affirmedServicesContentHttpProxyServiceStatisticsSlotLevelTcpSplicingSummaryNumtcpsplicingsummaryfailures OBJECT-TYPE
    SYNTAX      ConfdString
    MAX-ACCESS  read-only
    STATUS      current
    DESCRIPTION "Number of tcp splicing summary failures"
    ::= { affirmedServicesContentHttpProxyServiceStatisticsSlotLevelTcpSplicingSummaryEntry 6 }

affirmedServicesContentHttpProxyServiceStatisticsSlotLevelTcpSplicingSummaryNumtcpservicedurationminseconds OBJECT-TYPE
    SYNTAX      ConfdString
    MAX-ACCESS  read-only
    STATUS      deprecated
    DESCRIPTION "Number of tcp service duration min seconds"
    ::= { affirmedServicesContentHttpProxyServiceStatisticsSlotLevelTcpSplicingSummaryEntry 7 }

affirmedServicesContentHttpProxyServiceStatisticsSlotLevelTcpSplicingSummaryNumtcpservicedurationmaxseconds OBJECT-TYPE
    SYNTAX      ConfdString
    MAX-ACCESS  read-only
    STATUS      deprecated
    DESCRIPTION "Number of tcp service duration max seconds"
    ::= { affirmedServicesContentHttpProxyServiceStatisticsSlotLevelTcpSplicingSummaryEntry 8 }

affirmedServicesContentHttpProxyServiceStatisticsSlotLevelTcpSplicingSummaryNumtcpservicedurationtotalseconds OBJECT-TYPE
    SYNTAX      ConfdString
    MAX-ACCESS  read-only
    STATUS      current
    DESCRIPTION "Number of tcp service duration total"
    ::= { affirmedServicesContentHttpProxyServiceStatisticsSlotLevelTcpSplicingSummaryEntry 9 }

affirmedServicesContentHttpProxyServiceStatisticsSlotLevelTcpSplicingSummaryNumtcpservicedurationaverageseconds OBJECT-TYPE
    SYNTAX      ConfdString
    MAX-ACCESS  read-only
    STATUS      deprecated
    DESCRIPTION "Number of tcp service duration average seconds"
    ::= { affirmedServicesContentHttpProxyServiceStatisticsSlotLevelTcpSplicingSummaryEntry 10 }

affirmedServicesContentHttpProxyServiceStatisticsSlotLevelTcpSplicingSummaryNumtcpservicedurationmin OBJECT-TYPE
    SYNTAX      ConfdString
    MAX-ACCESS  read-only
    STATUS      current
    DESCRIPTION "Number of tcp service duration min seconds"
    ::= { affirmedServicesContentHttpProxyServiceStatisticsSlotLevelTcpSplicingSummaryEntry 11 }

affirmedServicesContentHttpProxyServiceStatisticsSlotLevelTcpSplicingSummaryNumtcpservicedurationmax OBJECT-TYPE
    SYNTAX      ConfdString
    MAX-ACCESS  read-only
    STATUS      current
    DESCRIPTION "Number of tcp service duration max seconds"
    ::= { affirmedServicesContentHttpProxyServiceStatisticsSlotLevelTcpSplicingSummaryEntry 12 }

affirmedServicesContentHttpProxyServiceStatisticsSlotLevelTcpSplicingSummaryNumtcpservicedurationavg OBJECT-TYPE
    SYNTAX      ConfdString
    MAX-ACCESS  read-only
    STATUS      current
    DESCRIPTION "Number of tcp service duration average seconds"
    ::= { affirmedServicesContentHttpProxyServiceStatisticsSlotLevelTcpSplicingSummaryEntry 13 }

affirmedServicesContentHttpProxyServiceStatisticsSlotLevelTcpSplicingDetailTable OBJECT-TYPE
    SYNTAX      SEQUENCE OF AffirmedServicesContentHttpProxyServiceStatisticsSlotLevelTcpSplicingDetailEntry
    MAX-ACCESS  not-accessible
    STATUS      current
    DESCRIPTION ""
    ::= { affirmedServicesContentHttpProxyServiceStatisticsSlotLevelTcpSplicing 3 }

affirmedServicesContentHttpProxyServiceStatisticsSlotLevelTcpSplicingDetailEntry OBJECT-TYPE
    SYNTAX      AffirmedServicesContentHttpProxyServiceStatisticsSlotLevelTcpSplicingDetailEntry
    MAX-ACCESS  not-accessible
    STATUS      current
    DESCRIPTION ""
    INDEX { affirmedServicesContentHttpProxyServiceStatisticsSlotLevelTcpSplicingDetailChassis, affirmedServicesContentHttpProxyServiceStatisticsSlotLevelTcpSplicingDetailSlot }
        ::= { affirmedServicesContentHttpProxyServiceStatisticsSlotLevelTcpSplicingDetailTable 1 }

AffirmedServicesContentHttpProxyServiceStatisticsSlotLevelTcpSplicingDetailEntry ::=
    SEQUENCE {
        affirmedServicesContentHttpProxyServiceStatisticsSlotLevelTcpSplicingDetailChassis Unsigned32,
        affirmedServicesContentHttpProxyServiceStatisticsSlotLevelTcpSplicingDetailSlot INTEGER,
        affirmedServicesContentHttpProxyServiceStatisticsSlotLevelTcpSplicingDetailNumtcpservicehandoffreversehandoffs ConfdString,
        affirmedServicesContentHttpProxyServiceStatisticsSlotLevelTcpSplicingDetailNumtcpsplicingprotocolhttp1xovertls ConfdString,
        affirmedServicesContentHttpProxyServiceStatisticsSlotLevelTcpSplicingDetailNumtcpsplicingprotocolhttp20 ConfdString,
        affirmedServicesContentHttpProxyServiceStatisticsSlotLevelTcpSplicingDetailNumtcpsplicingprotocolhttp20overtls ConfdString,
        affirmedServicesContentHttpProxyServiceStatisticsSlotLevelTcpSplicingDetailNumtcpsplicingprotocolwebsocket ConfdString,
        affirmedServicesContentHttpProxyServiceStatisticsSlotLevelTcpSplicingDetailNumtcpsplicingprotocolothers ConfdString,
        affirmedServicesContentHttpProxyServiceStatisticsSlotLevelTcpSplicingDetailNumtcpsplicingprotocolhttp ConfdString,
        affirmedServicesContentHttpProxyServiceStatisticsSlotLevelTcpSplicingDetailNumtcpsplicingreasonhttpscredentialsnotavailable ConfdString,
        affirmedServicesContentHttpProxyServiceStatisticsSlotLevelTcpSplicingDetailNumtcpsplicingreasonhttpconnectionupgrade ConfdString,
        affirmedServicesContentHttpProxyServiceStatisticsSlotLevelTcpSplicingDetailNumtcpsplicingreasontcpipflow ConfdString,
        affirmedServicesContentHttpProxyServiceStatisticsSlotLevelTcpSplicingDetailNumtcpsplicingreasonnonhttp ConfdString,
        affirmedServicesContentHttpProxyServiceStatisticsSlotLevelTcpSplicingDetailNumtcpsplicingreasonhttprequestreceivetimeout ConfdString,
        affirmedServicesContentHttpProxyServiceStatisticsSlotLevelTcpSplicingDetailNumtcpsplicingreasonhttpconnect ConfdString,
        affirmedServicesContentHttpProxyServiceStatisticsSlotLevelTcpSplicingDetailNumtcpsplicingreasonbypasshttpproxy ConfdString,
        affirmedServicesContentHttpProxyServiceStatisticsSlotLevelTcpSplicingDetailNumtcpsplicingprofileactionallowed ConfdString,
        affirmedServicesContentHttpProxyServiceStatisticsSlotLevelTcpSplicingDetailNumtcpsplicingprofileactionblocked ConfdString,
        affirmedServicesContentHttpProxyServiceStatisticsSlotLevelTcpSplicingDetailNumtcpsplicingprofilesteeredtoip ConfdString,
        affirmedServicesContentHttpProxyServiceStatisticsSlotLevelTcpSplicingDetailNumtcpsplicingprofilesteeredtohost ConfdString,
        affirmedServicesContentHttpProxyServiceStatisticsSlotLevelTcpSplicingDetailNumtcpsplicingpolicyevaluated ConfdString,
        affirmedServicesContentHttpProxyServiceStatisticsSlotLevelTcpSplicingDetailNumtcpsplicingpolicymatched ConfdString,
        affirmedServicesContentHttpProxyServiceStatisticsSlotLevelTcpSplicingDetailNumtcpsplicingpolicyignored ConfdString,
        affirmedServicesContentHttpProxyServiceStatisticsSlotLevelTcpSplicingDetailNumtcpsplicingpolicynotavailable ConfdString,
        affirmedServicesContentHttpProxyServiceStatisticsSlotLevelTcpSplicingDetailNumtcpsplicingpolicyreevaluated ConfdString,
        affirmedServicesContentHttpProxyServiceStatisticsSlotLevelTcpSplicingDetailNumtcpsplicingpolicymatchedafterreevaluation ConfdString,
        affirmedServicesContentHttpProxyServiceStatisticsSlotLevelTcpSplicingDetailNumtcpsplicingpolicynotavailableafterreevaluation ConfdString,
        affirmedServicesContentHttpProxyServiceStatisticsSlotLevelTcpSplicingDetailNumtcpsplicingprotocolwebrtc ConfdString,
        affirmedServicesContentHttpProxyServiceStatisticsSlotLevelTcpSplicingDetailNumtcpsplicingprotocolfacebookzero ConfdString
    }

affirmedServicesContentHttpProxyServiceStatisticsSlotLevelTcpSplicingDetailChassis OBJECT-TYPE
    SYNTAX      Unsigned32
    MAX-ACCESS  not-accessible
    STATUS      current
    DESCRIPTION "chassis ID"
    ::= { affirmedServicesContentHttpProxyServiceStatisticsSlotLevelTcpSplicingDetailEntry 1 }

affirmedServicesContentHttpProxyServiceStatisticsSlotLevelTcpSplicingDetailSlot OBJECT-TYPE
    SYNTAX      INTEGER {a1(1),a2(2),a3(3),a4(4),a5(5),a6(6),a7(7),a8(8),a9(9),a10(10),a11(11),a12(12),a13(13),a14(14),a15(15),a16(16),a17(17),a18(18),a19(19),a20(20),a21(21),a22(22),a23(23),a24(24),a25(25),a26(26),a27(27),a28(28),a29(29),a30(30),a31(31),a32(32),a33(33),a34(34),a35(35),a36(36),a37(37),a38(38),a39(39),a40(40),a41(41),a42(42),a43(43),a44(44),a45(45),a46(46),a47(47),a48(48),a49(49),a50(50),a51(51),a52(52),a53(53),a54(54),a55(55),a56(56),a57(57),a58(58),a59(59),a60(60),a61(61),a62(62),a63(63),a64(64),a65(65),a66(66),a67(67),a68(68),a69(69),a70(70),a71(71),a72(72),a73(73),a74(74),a75(75),a76(76),a77(77),a78(78),a79(79),a80(80),a81(81),a82(82),a83(83),a84(84),a85(85),a86(86),a87(87),a88(88),a89(89),a90(90),a91(91),a92(92),a93(93),a94(94),a95(95),a96(96),a97(97),a98(98),a99(99),a100(100),a101(101),a102(102),a103(103),a104(104),a105(105),a106(106),a107(107),a108(108),a109(109),a110(110),a111(111),a112(112),a113(113),a114(114),a115(115),a116(116),a117(117),a118(118),a119(119),a120(120),a121(121),a122(122),a123(123),a124(124),a125(125),a126(126),a127(127),a128(128)}
    MAX-ACCESS  not-accessible
    STATUS      current
    DESCRIPTION "slot number"
    ::= { affirmedServicesContentHttpProxyServiceStatisticsSlotLevelTcpSplicingDetailEntry 2 }

affirmedServicesContentHttpProxyServiceStatisticsSlotLevelTcpSplicingDetailNumtcpservicehandoffreversehandoffs OBJECT-TYPE
    SYNTAX      ConfdString
    MAX-ACCESS  read-only
    STATUS      current
    DESCRIPTION "Number of tcp service handoff reverse handoffs"
    ::= { affirmedServicesContentHttpProxyServiceStatisticsSlotLevelTcpSplicingDetailEntry 3 }

affirmedServicesContentHttpProxyServiceStatisticsSlotLevelTcpSplicingDetailNumtcpsplicingprotocolhttp1xovertls OBJECT-TYPE
    SYNTAX      ConfdString
    MAX-ACCESS  read-only
    STATUS      current
    DESCRIPTION "Number of tcp splicing protocol http1x over tls"
    ::= { affirmedServicesContentHttpProxyServiceStatisticsSlotLevelTcpSplicingDetailEntry 4 }

affirmedServicesContentHttpProxyServiceStatisticsSlotLevelTcpSplicingDetailNumtcpsplicingprotocolhttp20 OBJECT-TYPE
    SYNTAX      ConfdString
    MAX-ACCESS  read-only
    STATUS      current
    DESCRIPTION "Number of tcp splicing protocol http20"
    ::= { affirmedServicesContentHttpProxyServiceStatisticsSlotLevelTcpSplicingDetailEntry 5 }

affirmedServicesContentHttpProxyServiceStatisticsSlotLevelTcpSplicingDetailNumtcpsplicingprotocolhttp20overtls OBJECT-TYPE
    SYNTAX      ConfdString
    MAX-ACCESS  read-only
    STATUS      current
    DESCRIPTION "Number of tcp splicing protocol http20 over tls"
    ::= { affirmedServicesContentHttpProxyServiceStatisticsSlotLevelTcpSplicingDetailEntry 6 }

affirmedServicesContentHttpProxyServiceStatisticsSlotLevelTcpSplicingDetailNumtcpsplicingprotocolwebsocket OBJECT-TYPE
    SYNTAX      ConfdString
    MAX-ACCESS  read-only
    STATUS      current
    DESCRIPTION "Number of tcp splicing protocol websocket"
    ::= { affirmedServicesContentHttpProxyServiceStatisticsSlotLevelTcpSplicingDetailEntry 7 }

affirmedServicesContentHttpProxyServiceStatisticsSlotLevelTcpSplicingDetailNumtcpsplicingprotocolothers OBJECT-TYPE
    SYNTAX      ConfdString
    MAX-ACCESS  read-only
    STATUS      current
    DESCRIPTION "Number of tcp splicing protocol others"
    ::= { affirmedServicesContentHttpProxyServiceStatisticsSlotLevelTcpSplicingDetailEntry 8 }

affirmedServicesContentHttpProxyServiceStatisticsSlotLevelTcpSplicingDetailNumtcpsplicingprotocolhttp OBJECT-TYPE
    SYNTAX      ConfdString
    MAX-ACCESS  read-only
    STATUS      current
    DESCRIPTION "Number of tcp splicing protocol http"
    ::= { affirmedServicesContentHttpProxyServiceStatisticsSlotLevelTcpSplicingDetailEntry 9 }

affirmedServicesContentHttpProxyServiceStatisticsSlotLevelTcpSplicingDetailNumtcpsplicingreasonhttpscredentialsnotavailable OBJECT-TYPE
    SYNTAX      ConfdString
    MAX-ACCESS  read-only
    STATUS      current
    DESCRIPTION "Number of tcp splicing reason https credentials not available"
    ::= { affirmedServicesContentHttpProxyServiceStatisticsSlotLevelTcpSplicingDetailEntry 10 }

affirmedServicesContentHttpProxyServiceStatisticsSlotLevelTcpSplicingDetailNumtcpsplicingreasonhttpconnectionupgrade OBJECT-TYPE
    SYNTAX      ConfdString
    MAX-ACCESS  read-only
    STATUS      current
    DESCRIPTION "Number of tcp splicing reason http connection upgrade"
    ::= { affirmedServicesContentHttpProxyServiceStatisticsSlotLevelTcpSplicingDetailEntry 11 }

affirmedServicesContentHttpProxyServiceStatisticsSlotLevelTcpSplicingDetailNumtcpsplicingreasontcpipflow OBJECT-TYPE
    SYNTAX      ConfdString
    MAX-ACCESS  read-only
    STATUS      current
    DESCRIPTION "Number of tcp splicing reason tcp ip flow"
    ::= { affirmedServicesContentHttpProxyServiceStatisticsSlotLevelTcpSplicingDetailEntry 12 }

affirmedServicesContentHttpProxyServiceStatisticsSlotLevelTcpSplicingDetailNumtcpsplicingreasonnonhttp OBJECT-TYPE
    SYNTAX      ConfdString
    MAX-ACCESS  read-only
    STATUS      current
    DESCRIPTION "Number of tcp splicing reason nonhttp"
    ::= { affirmedServicesContentHttpProxyServiceStatisticsSlotLevelTcpSplicingDetailEntry 13 }

affirmedServicesContentHttpProxyServiceStatisticsSlotLevelTcpSplicingDetailNumtcpsplicingreasonhttprequestreceivetimeout OBJECT-TYPE
    SYNTAX      ConfdString
    MAX-ACCESS  read-only
    STATUS      current
    DESCRIPTION "Number of tcp splicing reason http request receive timeout"
    ::= { affirmedServicesContentHttpProxyServiceStatisticsSlotLevelTcpSplicingDetailEntry 14 }

affirmedServicesContentHttpProxyServiceStatisticsSlotLevelTcpSplicingDetailNumtcpsplicingreasonhttpconnect OBJECT-TYPE
    SYNTAX      ConfdString
    MAX-ACCESS  read-only
    STATUS      current
    DESCRIPTION "Number of tcp splicing reason http connect"
    ::= { affirmedServicesContentHttpProxyServiceStatisticsSlotLevelTcpSplicingDetailEntry 15 }

affirmedServicesContentHttpProxyServiceStatisticsSlotLevelTcpSplicingDetailNumtcpsplicingreasonbypasshttpproxy OBJECT-TYPE
    SYNTAX      ConfdString
    MAX-ACCESS  read-only
    STATUS      current
    DESCRIPTION "Number of tcp splicing reason bypass http proxy"
    ::= { affirmedServicesContentHttpProxyServiceStatisticsSlotLevelTcpSplicingDetailEntry 16 }

affirmedServicesContentHttpProxyServiceStatisticsSlotLevelTcpSplicingDetailNumtcpsplicingprofileactionallowed OBJECT-TYPE
    SYNTAX      ConfdString
    MAX-ACCESS  read-only
    STATUS      current
    DESCRIPTION "Number of tcp splicing profile action allowed"
    ::= { affirmedServicesContentHttpProxyServiceStatisticsSlotLevelTcpSplicingDetailEntry 17 }

affirmedServicesContentHttpProxyServiceStatisticsSlotLevelTcpSplicingDetailNumtcpsplicingprofileactionblocked OBJECT-TYPE
    SYNTAX      ConfdString
    MAX-ACCESS  read-only
    STATUS      current
    DESCRIPTION "Number of tcp splicing profile action blocked"
    ::= { affirmedServicesContentHttpProxyServiceStatisticsSlotLevelTcpSplicingDetailEntry 18 }

affirmedServicesContentHttpProxyServiceStatisticsSlotLevelTcpSplicingDetailNumtcpsplicingprofilesteeredtoip OBJECT-TYPE
    SYNTAX      ConfdString
    MAX-ACCESS  read-only
    STATUS      current
    DESCRIPTION "Number of tcp splicing profile steered to ip"
    ::= { affirmedServicesContentHttpProxyServiceStatisticsSlotLevelTcpSplicingDetailEntry 19 }

affirmedServicesContentHttpProxyServiceStatisticsSlotLevelTcpSplicingDetailNumtcpsplicingprofilesteeredtohost OBJECT-TYPE
    SYNTAX      ConfdString
    MAX-ACCESS  read-only
    STATUS      current
    DESCRIPTION "Number of tcp splicing profile steered to host"
    ::= { affirmedServicesContentHttpProxyServiceStatisticsSlotLevelTcpSplicingDetailEntry 20 }

affirmedServicesContentHttpProxyServiceStatisticsSlotLevelTcpSplicingDetailNumtcpsplicingpolicyevaluated OBJECT-TYPE
    SYNTAX      ConfdString
    MAX-ACCESS  read-only
    STATUS      current
    DESCRIPTION "Number of tcp splicing policy evaluated"
    ::= { affirmedServicesContentHttpProxyServiceStatisticsSlotLevelTcpSplicingDetailEntry 21 }

affirmedServicesContentHttpProxyServiceStatisticsSlotLevelTcpSplicingDetailNumtcpsplicingpolicymatched OBJECT-TYPE
    SYNTAX      ConfdString
    MAX-ACCESS  read-only
    STATUS      current
    DESCRIPTION "Number of tcp splicing policy matched"
    ::= { affirmedServicesContentHttpProxyServiceStatisticsSlotLevelTcpSplicingDetailEntry 22 }

affirmedServicesContentHttpProxyServiceStatisticsSlotLevelTcpSplicingDetailNumtcpsplicingpolicyignored OBJECT-TYPE
    SYNTAX      ConfdString
    MAX-ACCESS  read-only
    STATUS      current
    DESCRIPTION "Number of tcp splicing policy ignored"
    ::= { affirmedServicesContentHttpProxyServiceStatisticsSlotLevelTcpSplicingDetailEntry 23 }

affirmedServicesContentHttpProxyServiceStatisticsSlotLevelTcpSplicingDetailNumtcpsplicingpolicynotavailable OBJECT-TYPE
    SYNTAX      ConfdString
    MAX-ACCESS  read-only
    STATUS      current
    DESCRIPTION "Number of tcp splicing policy not available"
    ::= { affirmedServicesContentHttpProxyServiceStatisticsSlotLevelTcpSplicingDetailEntry 24 }

affirmedServicesContentHttpProxyServiceStatisticsSlotLevelTcpSplicingDetailNumtcpsplicingpolicyreevaluated OBJECT-TYPE
    SYNTAX      ConfdString
    MAX-ACCESS  read-only
    STATUS      current
    DESCRIPTION "Number of tcp splicing policy reevaluated"
    ::= { affirmedServicesContentHttpProxyServiceStatisticsSlotLevelTcpSplicingDetailEntry 25 }

affirmedServicesContentHttpProxyServiceStatisticsSlotLevelTcpSplicingDetailNumtcpsplicingpolicymatchedafterreevaluation OBJECT-TYPE
    SYNTAX      ConfdString
    MAX-ACCESS  read-only
    STATUS      current
    DESCRIPTION "Number of tcp splicing policy matched after reevaluation"
    ::= { affirmedServicesContentHttpProxyServiceStatisticsSlotLevelTcpSplicingDetailEntry 26 }

affirmedServicesContentHttpProxyServiceStatisticsSlotLevelTcpSplicingDetailNumtcpsplicingpolicynotavailableafterreevaluation OBJECT-TYPE
    SYNTAX      ConfdString
    MAX-ACCESS  read-only
    STATUS      current
    DESCRIPTION "Number of tcp splicing policy not available after reevaluation"
    ::= { affirmedServicesContentHttpProxyServiceStatisticsSlotLevelTcpSplicingDetailEntry 27 }

affirmedServicesContentHttpProxyServiceStatisticsSlotLevelTcpSplicingDetailNumtcpsplicingprotocolwebrtc OBJECT-TYPE
    SYNTAX      ConfdString
    MAX-ACCESS  read-only
    STATUS      current
    DESCRIPTION "Number of tcp splicing protocol webRTC"
    ::= { affirmedServicesContentHttpProxyServiceStatisticsSlotLevelTcpSplicingDetailEntry 28 }

affirmedServicesContentHttpProxyServiceStatisticsSlotLevelTcpSplicingDetailNumtcpsplicingprotocolfacebookzero OBJECT-TYPE
    SYNTAX      ConfdString
    MAX-ACCESS  read-only
    STATUS      current
    DESCRIPTION "Number of tcp splicing protocol FacebookZero"
    ::= { affirmedServicesContentHttpProxyServiceStatisticsSlotLevelTcpSplicingDetailEntry 29 }

affirmedServicesContentHttpProxyServiceStatisticsSlotLevelTcpSplicingFailureTable OBJECT-TYPE
    SYNTAX      SEQUENCE OF AffirmedServicesContentHttpProxyServiceStatisticsSlotLevelTcpSplicingFailureEntry
    MAX-ACCESS  not-accessible
    STATUS      current
    DESCRIPTION ""
    ::= { affirmedServicesContentHttpProxyServiceStatisticsSlotLevelTcpSplicing 4 }

affirmedServicesContentHttpProxyServiceStatisticsSlotLevelTcpSplicingFailureEntry OBJECT-TYPE
    SYNTAX      AffirmedServicesContentHttpProxyServiceStatisticsSlotLevelTcpSplicingFailureEntry
    MAX-ACCESS  not-accessible
    STATUS      current
    DESCRIPTION ""
    INDEX { affirmedServicesContentHttpProxyServiceStatisticsSlotLevelTcpSplicingFailureChassis, affirmedServicesContentHttpProxyServiceStatisticsSlotLevelTcpSplicingFailureSlot }
        ::= { affirmedServicesContentHttpProxyServiceStatisticsSlotLevelTcpSplicingFailureTable 1 }

AffirmedServicesContentHttpProxyServiceStatisticsSlotLevelTcpSplicingFailureEntry ::=
    SEQUENCE {
        affirmedServicesContentHttpProxyServiceStatisticsSlotLevelTcpSplicingFailureChassis Unsigned32,
        affirmedServicesContentHttpProxyServiceStatisticsSlotLevelTcpSplicingFailureSlot INTEGER,
        affirmedServicesContentHttpProxyServiceStatisticsSlotLevelTcpSplicingFailureNumtcpsplicingabortsclientabort ConfdString,
        affirmedServicesContentHttpProxyServiceStatisticsSlotLevelTcpSplicingFailureNumtcpsplicingabortsserverabort ConfdString,
        affirmedServicesContentHttpProxyServiceStatisticsSlotLevelTcpSplicingFailureNumtcpsplicingabortsidletimeout ConfdString,
        affirmedServicesContentHttpProxyServiceStatisticsSlotLevelTcpSplicingFailureNumtcpsplicingabortsclientsocketerror ConfdString,
        affirmedServicesContentHttpProxyServiceStatisticsSlotLevelTcpSplicingFailureNumtcpsplicingabortsserversocketerror ConfdString,
        affirmedServicesContentHttpProxyServiceStatisticsSlotLevelTcpSplicingFailureNumtcpsplicingabortsclientreaderror ConfdString,
        affirmedServicesContentHttpProxyServiceStatisticsSlotLevelTcpSplicingFailureNumtcpsplicingabortsclientwriteerror ConfdString,
        affirmedServicesContentHttpProxyServiceStatisticsSlotLevelTcpSplicingFailureNumtcpsplicingabortsserverreaderror ConfdString,
        affirmedServicesContentHttpProxyServiceStatisticsSlotLevelTcpSplicingFailureNumtcpsplicingabortsserverwriteerror ConfdString,
        affirmedServicesContentHttpProxyServiceStatisticsSlotLevelTcpSplicingFailureNumtcpsplicingabortsnodatainconnection ConfdString,
        affirmedServicesContentHttpProxyServiceStatisticsSlotLevelTcpSplicingFailureNumtcpsplicingabortsclienterror ConfdString,
        affirmedServicesContentHttpProxyServiceStatisticsSlotLevelTcpSplicingFailureNumtcpsplicingabortsservererror ConfdString,
        affirmedServicesContentHttpProxyServiceStatisticsSlotLevelTcpSplicingFailureNumtcpsplicingfailuresoutofbuffers ConfdString,
        affirmedServicesContentHttpProxyServiceStatisticsSlotLevelTcpSplicingFailureNumtcpsplicingfailuresserverconnectionfailure ConfdString,
        affirmedServicesContentHttpProxyServiceStatisticsSlotLevelTcpSplicingFailureNumtcpsplicingfailuresdnsrequestfailure ConfdString,
        affirmedServicesContentHttpProxyServiceStatisticsSlotLevelTcpSplicingFailureNumtcpsplicingfailuresdnsresponsefailure ConfdString,
        affirmedServicesContentHttpProxyServiceStatisticsSlotLevelTcpSplicingFailureNumtcpsplicingfailurespolicyreject ConfdString,
        affirmedServicesContentHttpProxyServiceStatisticsSlotLevelTcpSplicingFailureNumtcpsplicingfailurestfdreject ConfdString,
        affirmedServicesContentHttpProxyServiceStatisticsSlotLevelTcpSplicingFailureNumtcpsplicingfailuresoutofsocket ConfdString
    }

affirmedServicesContentHttpProxyServiceStatisticsSlotLevelTcpSplicingFailureChassis OBJECT-TYPE
    SYNTAX      Unsigned32
    MAX-ACCESS  not-accessible
    STATUS      current
    DESCRIPTION "chassis ID"
    ::= { affirmedServicesContentHttpProxyServiceStatisticsSlotLevelTcpSplicingFailureEntry 1 }

affirmedServicesContentHttpProxyServiceStatisticsSlotLevelTcpSplicingFailureSlot OBJECT-TYPE
    SYNTAX      INTEGER {a1(1),a2(2),a3(3),a4(4),a5(5),a6(6),a7(7),a8(8),a9(9),a10(10),a11(11),a12(12),a13(13),a14(14),a15(15),a16(16),a17(17),a18(18),a19(19),a20(20),a21(21),a22(22),a23(23),a24(24),a25(25),a26(26),a27(27),a28(28),a29(29),a30(30),a31(31),a32(32),a33(33),a34(34),a35(35),a36(36),a37(37),a38(38),a39(39),a40(40),a41(41),a42(42),a43(43),a44(44),a45(45),a46(46),a47(47),a48(48),a49(49),a50(50),a51(51),a52(52),a53(53),a54(54),a55(55),a56(56),a57(57),a58(58),a59(59),a60(60),a61(61),a62(62),a63(63),a64(64),a65(65),a66(66),a67(67),a68(68),a69(69),a70(70),a71(71),a72(72),a73(73),a74(74),a75(75),a76(76),a77(77),a78(78),a79(79),a80(80),a81(81),a82(82),a83(83),a84(84),a85(85),a86(86),a87(87),a88(88),a89(89),a90(90),a91(91),a92(92),a93(93),a94(94),a95(95),a96(96),a97(97),a98(98),a99(99),a100(100),a101(101),a102(102),a103(103),a104(104),a105(105),a106(106),a107(107),a108(108),a109(109),a110(110),a111(111),a112(112),a113(113),a114(114),a115(115),a116(116),a117(117),a118(118),a119(119),a120(120),a121(121),a122(122),a123(123),a124(124),a125(125),a126(126),a127(127),a128(128)}
    MAX-ACCESS  not-accessible
    STATUS      current
    DESCRIPTION "slot number"
    ::= { affirmedServicesContentHttpProxyServiceStatisticsSlotLevelTcpSplicingFailureEntry 2 }

affirmedServicesContentHttpProxyServiceStatisticsSlotLevelTcpSplicingFailureNumtcpsplicingabortsclientabort OBJECT-TYPE
    SYNTAX      ConfdString
    MAX-ACCESS  read-only
    STATUS      current
    DESCRIPTION "Number of tcp splicing aborts client abort"
    ::= { affirmedServicesContentHttpProxyServiceStatisticsSlotLevelTcpSplicingFailureEntry 3 }

affirmedServicesContentHttpProxyServiceStatisticsSlotLevelTcpSplicingFailureNumtcpsplicingabortsserverabort OBJECT-TYPE
    SYNTAX      ConfdString
    MAX-ACCESS  read-only
    STATUS      current
    DESCRIPTION "Number of tcp splicing aborts serverabort"
    ::= { affirmedServicesContentHttpProxyServiceStatisticsSlotLevelTcpSplicingFailureEntry 4 }

affirmedServicesContentHttpProxyServiceStatisticsSlotLevelTcpSplicingFailureNumtcpsplicingabortsidletimeout OBJECT-TYPE
    SYNTAX      ConfdString
    MAX-ACCESS  read-only
    STATUS      current
    DESCRIPTION "Number of tcp splicing aborts idle timeout"
    ::= { affirmedServicesContentHttpProxyServiceStatisticsSlotLevelTcpSplicingFailureEntry 5 }

affirmedServicesContentHttpProxyServiceStatisticsSlotLevelTcpSplicingFailureNumtcpsplicingabortsclientsocketerror OBJECT-TYPE
    SYNTAX      ConfdString
    MAX-ACCESS  read-only
    STATUS      current
    DESCRIPTION "Number of tcp splicing aborts client socket error"
    ::= { affirmedServicesContentHttpProxyServiceStatisticsSlotLevelTcpSplicingFailureEntry 6 }

affirmedServicesContentHttpProxyServiceStatisticsSlotLevelTcpSplicingFailureNumtcpsplicingabortsserversocketerror OBJECT-TYPE
    SYNTAX      ConfdString
    MAX-ACCESS  read-only
    STATUS      current
    DESCRIPTION "Number of tcp splicing aborts server socket error"
    ::= { affirmedServicesContentHttpProxyServiceStatisticsSlotLevelTcpSplicingFailureEntry 7 }

affirmedServicesContentHttpProxyServiceStatisticsSlotLevelTcpSplicingFailureNumtcpsplicingabortsclientreaderror OBJECT-TYPE
    SYNTAX      ConfdString
    MAX-ACCESS  read-only
    STATUS      current
    DESCRIPTION "Number of tcp splicing aborts client read error"
    ::= { affirmedServicesContentHttpProxyServiceStatisticsSlotLevelTcpSplicingFailureEntry 8 }

affirmedServicesContentHttpProxyServiceStatisticsSlotLevelTcpSplicingFailureNumtcpsplicingabortsclientwriteerror OBJECT-TYPE
    SYNTAX      ConfdString
    MAX-ACCESS  read-only
    STATUS      current
    DESCRIPTION "Number of tcp splicing aborts client write error"
    ::= { affirmedServicesContentHttpProxyServiceStatisticsSlotLevelTcpSplicingFailureEntry 9 }

affirmedServicesContentHttpProxyServiceStatisticsSlotLevelTcpSplicingFailureNumtcpsplicingabortsserverreaderror OBJECT-TYPE
    SYNTAX      ConfdString
    MAX-ACCESS  read-only
    STATUS      current
    DESCRIPTION "Number of tcp splicing aborts server read error"
    ::= { affirmedServicesContentHttpProxyServiceStatisticsSlotLevelTcpSplicingFailureEntry 10 }

affirmedServicesContentHttpProxyServiceStatisticsSlotLevelTcpSplicingFailureNumtcpsplicingabortsserverwriteerror OBJECT-TYPE
    SYNTAX      ConfdString
    MAX-ACCESS  read-only
    STATUS      current
    DESCRIPTION "Number of tcp splicing aborts server write error"
    ::= { affirmedServicesContentHttpProxyServiceStatisticsSlotLevelTcpSplicingFailureEntry 11 }

affirmedServicesContentHttpProxyServiceStatisticsSlotLevelTcpSplicingFailureNumtcpsplicingabortsnodatainconnection OBJECT-TYPE
    SYNTAX      ConfdString
    MAX-ACCESS  read-only
    STATUS      current
    DESCRIPTION "Number of tcp splicing aborts no data in connection"
    ::= { affirmedServicesContentHttpProxyServiceStatisticsSlotLevelTcpSplicingFailureEntry 12 }

affirmedServicesContentHttpProxyServiceStatisticsSlotLevelTcpSplicingFailureNumtcpsplicingabortsclienterror OBJECT-TYPE
    SYNTAX      ConfdString
    MAX-ACCESS  read-only
    STATUS      current
    DESCRIPTION "Number of tcp splicing aborts client error"
    ::= { affirmedServicesContentHttpProxyServiceStatisticsSlotLevelTcpSplicingFailureEntry 13 }

affirmedServicesContentHttpProxyServiceStatisticsSlotLevelTcpSplicingFailureNumtcpsplicingabortsservererror OBJECT-TYPE
    SYNTAX      ConfdString
    MAX-ACCESS  read-only
    STATUS      current
    DESCRIPTION "Number of tcp splicing aborts server error"
    ::= { affirmedServicesContentHttpProxyServiceStatisticsSlotLevelTcpSplicingFailureEntry 14 }

affirmedServicesContentHttpProxyServiceStatisticsSlotLevelTcpSplicingFailureNumtcpsplicingfailuresoutofbuffers OBJECT-TYPE
    SYNTAX      ConfdString
    MAX-ACCESS  read-only
    STATUS      current
    DESCRIPTION "Number of tcp splicing failures out of buffers"
    ::= { affirmedServicesContentHttpProxyServiceStatisticsSlotLevelTcpSplicingFailureEntry 15 }

affirmedServicesContentHttpProxyServiceStatisticsSlotLevelTcpSplicingFailureNumtcpsplicingfailuresserverconnectionfailure OBJECT-TYPE
    SYNTAX      ConfdString
    MAX-ACCESS  read-only
    STATUS      current
    DESCRIPTION "Number of tcp splicing failures server connection failure"
    ::= { affirmedServicesContentHttpProxyServiceStatisticsSlotLevelTcpSplicingFailureEntry 16 }

affirmedServicesContentHttpProxyServiceStatisticsSlotLevelTcpSplicingFailureNumtcpsplicingfailuresdnsrequestfailure OBJECT-TYPE
    SYNTAX      ConfdString
    MAX-ACCESS  read-only
    STATUS      current
    DESCRIPTION "Number of tcp splicing failures dns request failure"
    ::= { affirmedServicesContentHttpProxyServiceStatisticsSlotLevelTcpSplicingFailureEntry 17 }

affirmedServicesContentHttpProxyServiceStatisticsSlotLevelTcpSplicingFailureNumtcpsplicingfailuresdnsresponsefailure OBJECT-TYPE
    SYNTAX      ConfdString
    MAX-ACCESS  read-only
    STATUS      current
    DESCRIPTION "Number of tcp splicing failures dns response failure"
    ::= { affirmedServicesContentHttpProxyServiceStatisticsSlotLevelTcpSplicingFailureEntry 18 }

affirmedServicesContentHttpProxyServiceStatisticsSlotLevelTcpSplicingFailureNumtcpsplicingfailurespolicyreject OBJECT-TYPE
    SYNTAX      ConfdString
    MAX-ACCESS  read-only
    STATUS      current
    DESCRIPTION "Number of tcp splicing failures policy reject"
    ::= { affirmedServicesContentHttpProxyServiceStatisticsSlotLevelTcpSplicingFailureEntry 19 }

affirmedServicesContentHttpProxyServiceStatisticsSlotLevelTcpSplicingFailureNumtcpsplicingfailurestfdreject OBJECT-TYPE
    SYNTAX      ConfdString
    MAX-ACCESS  read-only
    STATUS      current
    DESCRIPTION "Number of tcp splicing failures tfd reject"
    ::= { affirmedServicesContentHttpProxyServiceStatisticsSlotLevelTcpSplicingFailureEntry 20 }

affirmedServicesContentHttpProxyServiceStatisticsSlotLevelTcpSplicingFailureNumtcpsplicingfailuresoutofsocket OBJECT-TYPE
    SYNTAX      ConfdString
    MAX-ACCESS  read-only
    STATUS      current
    DESCRIPTION "Number of tcp splicing failures out of socket"
    ::= { affirmedServicesContentHttpProxyServiceStatisticsSlotLevelTcpSplicingFailureEntry 21 }

affirmedServicesContentHttpProxyServiceStatisticsSlotLevelTcpSplicingConnectionTable OBJECT-TYPE
    SYNTAX      SEQUENCE OF AffirmedServicesContentHttpProxyServiceStatisticsSlotLevelTcpSplicingConnectionEntry
    MAX-ACCESS  not-accessible
    STATUS      current
    DESCRIPTION ""
    ::= { affirmedServicesContentHttpProxyServiceStatisticsSlotLevelTcpSplicing 5 }

affirmedServicesContentHttpProxyServiceStatisticsSlotLevelTcpSplicingConnectionEntry OBJECT-TYPE
    SYNTAX      AffirmedServicesContentHttpProxyServiceStatisticsSlotLevelTcpSplicingConnectionEntry
    MAX-ACCESS  not-accessible
    STATUS      current
    DESCRIPTION ""
    INDEX { affirmedServicesContentHttpProxyServiceStatisticsSlotLevelTcpSplicingConnectionChassis, affirmedServicesContentHttpProxyServiceStatisticsSlotLevelTcpSplicingConnectionSlot }
        ::= { affirmedServicesContentHttpProxyServiceStatisticsSlotLevelTcpSplicingConnectionTable 1 }

AffirmedServicesContentHttpProxyServiceStatisticsSlotLevelTcpSplicingConnectionEntry ::=
    SEQUENCE {
        affirmedServicesContentHttpProxyServiceStatisticsSlotLevelTcpSplicingConnectionChassis Unsigned32,
        affirmedServicesContentHttpProxyServiceStatisticsSlotLevelTcpSplicingConnectionSlot INTEGER,
        affirmedServicesContentHttpProxyServiceStatisticsSlotLevelTcpSplicingConnectionNumtcpsplicingclientconnectionstotal ConfdString,
        affirmedServicesContentHttpProxyServiceStatisticsSlotLevelTcpSplicingConnectionNumtcpsplicingclientconnectionscurrentlyinuse ConfdString,
        affirmedServicesContentHttpProxyServiceStatisticsSlotLevelTcpSplicingConnectionNumtcpsplicingclientconnectionsipv4 ConfdString,
        affirmedServicesContentHttpProxyServiceStatisticsSlotLevelTcpSplicingConnectionNumtcpsplicingclientconnectionsipv6 ConfdString,
        affirmedServicesContentHttpProxyServiceStatisticsSlotLevelTcpSplicingConnectionNumtcpsplicingclientconnectionsbytesreceived ConfdString,
        affirmedServicesContentHttpProxyServiceStatisticsSlotLevelTcpSplicingConnectionNumtcpsplicingclientconnectionsbytessent ConfdString,
        affirmedServicesContentHttpProxyServiceStatisticsSlotLevelTcpSplicingConnectionNumtcpsplicingclientconnectionsreadfailure ConfdString,
        affirmedServicesContentHttpProxyServiceStatisticsSlotLevelTcpSplicingConnectionNumtcpsplicingclientconnectionswritefailure ConfdString,
        affirmedServicesContentHttpProxyServiceStatisticsSlotLevelTcpSplicingConnectionNumtcpsplicingclientconnectionswriteincomplete ConfdString,
        affirmedServicesContentHttpProxyServiceStatisticsSlotLevelTcpSplicingConnectionNumtcpsplicingserverconnectionstotal ConfdString,
        affirmedServicesContentHttpProxyServiceStatisticsSlotLevelTcpSplicingConnectionNumtcpsplicingserverconnectionscurrentlyinuse ConfdString,
        affirmedServicesContentHttpProxyServiceStatisticsSlotLevelTcpSplicingConnectionNumtcpsplicingserverconnectionsipv4 ConfdString,
        affirmedServicesContentHttpProxyServiceStatisticsSlotLevelTcpSplicingConnectionNumtcpsplicingserverconnectionsipv6 ConfdString,
        affirmedServicesContentHttpProxyServiceStatisticsSlotLevelTcpSplicingConnectionNumtcpsplicingserverconnectionsiptransparent ConfdString,
        affirmedServicesContentHttpProxyServiceStatisticsSlotLevelTcpSplicingConnectionNumtcpsplicingserverconnectionsbytesreceived ConfdString,
        affirmedServicesContentHttpProxyServiceStatisticsSlotLevelTcpSplicingConnectionNumtcpsplicingserverconnectionsbytessent ConfdString,
        affirmedServicesContentHttpProxyServiceStatisticsSlotLevelTcpSplicingConnectionNumtcpsplicingserverconnectionsreadfailure ConfdString,
        affirmedServicesContentHttpProxyServiceStatisticsSlotLevelTcpSplicingConnectionNumtcpsplicingserverconnectionswritefailure ConfdString,
        affirmedServicesContentHttpProxyServiceStatisticsSlotLevelTcpSplicingConnectionNumtcpsplicingserverconnectionswriteincomplete ConfdString,
        affirmedServicesContentHttpProxyServiceStatisticsSlotLevelTcpSplicingConnectionNumtcpsplicingserverconnectionsconnectfailed ConfdString,
        affirmedServicesContentHttpProxyServiceStatisticsSlotLevelTcpSplicingConnectionNumtcpsplicingclientconnectionscurrentinuse ConfdString,
        affirmedServicesContentHttpProxyServiceStatisticsSlotLevelTcpSplicingConnectionNumtcpsplicingserverconnectionscurrentinuse ConfdString,
        affirmedServicesContentHttpProxyServiceStatisticsSlotLevelTcpSplicingConnectionNumfastopenattempts ConfdString,
        affirmedServicesContentHttpProxyServiceStatisticsSlotLevelTcpSplicingConnectionNumfastopensuccesses ConfdString,
        affirmedServicesContentHttpProxyServiceStatisticsSlotLevelTcpSplicingConnectionNumfastopenfailureinitconn ConfdString,
        affirmedServicesContentHttpProxyServiceStatisticsSlotLevelTcpSplicingConnectionNumfastopenfailureduplicate ConfdString,
        affirmedServicesContentHttpProxyServiceStatisticsSlotLevelTcpSplicingConnectionNumfastopenfailurealreadycreated ConfdString,
        affirmedServicesContentHttpProxyServiceStatisticsSlotLevelTcpSplicingConnectionNumfastopenfailurepolicy ConfdString,
        affirmedServicesContentHttpProxyServiceStatisticsSlotLevelTcpSplicingConnectionNumfastopenfailureother ConfdString,
        affirmedServicesContentHttpProxyServiceStatisticsSlotLevelTcpSplicingConnectionNumfastopenlistfull ConfdString,
        affirmedServicesContentHttpProxyServiceStatisticsSlotLevelTcpSplicingConnectionNumfastopencurrentpendingconn ConfdString,
        affirmedServicesContentHttpProxyServiceStatisticsSlotLevelTcpSplicingConnectionNumfastopenaging ConfdString,
        affirmedServicesContentHttpProxyServiceStatisticsSlotLevelTcpSplicingConnectionNumtcpsplicingdpiupdates ConfdString,
        affirmedServicesContentHttpProxyServiceStatisticsSlotLevelTcpSplicingConnectionNumtcpsplicingdpiupdatefailures ConfdString
    }

affirmedServicesContentHttpProxyServiceStatisticsSlotLevelTcpSplicingConnectionChassis OBJECT-TYPE
    SYNTAX      Unsigned32
    MAX-ACCESS  not-accessible
    STATUS      current
    DESCRIPTION "chassis ID"
    ::= { affirmedServicesContentHttpProxyServiceStatisticsSlotLevelTcpSplicingConnectionEntry 1 }

affirmedServicesContentHttpProxyServiceStatisticsSlotLevelTcpSplicingConnectionSlot OBJECT-TYPE
    SYNTAX      INTEGER {a1(1),a2(2),a3(3),a4(4),a5(5),a6(6),a7(7),a8(8),a9(9),a10(10),a11(11),a12(12),a13(13),a14(14),a15(15),a16(16),a17(17),a18(18),a19(19),a20(20),a21(21),a22(22),a23(23),a24(24),a25(25),a26(26),a27(27),a28(28),a29(29),a30(30),a31(31),a32(32),a33(33),a34(34),a35(35),a36(36),a37(37),a38(38),a39(39),a40(40),a41(41),a42(42),a43(43),a44(44),a45(45),a46(46),a47(47),a48(48),a49(49),a50(50),a51(51),a52(52),a53(53),a54(54),a55(55),a56(56),a57(57),a58(58),a59(59),a60(60),a61(61),a62(62),a63(63),a64(64),a65(65),a66(66),a67(67),a68(68),a69(69),a70(70),a71(71),a72(72),a73(73),a74(74),a75(75),a76(76),a77(77),a78(78),a79(79),a80(80),a81(81),a82(82),a83(83),a84(84),a85(85),a86(86),a87(87),a88(88),a89(89),a90(90),a91(91),a92(92),a93(93),a94(94),a95(95),a96(96),a97(97),a98(98),a99(99),a100(100),a101(101),a102(102),a103(103),a104(104),a105(105),a106(106),a107(107),a108(108),a109(109),a110(110),a111(111),a112(112),a113(113),a114(114),a115(115),a116(116),a117(117),a118(118),a119(119),a120(120),a121(121),a122(122),a123(123),a124(124),a125(125),a126(126),a127(127),a128(128)}
    MAX-ACCESS  not-accessible
    STATUS      current
    DESCRIPTION "slot number"
    ::= { affirmedServicesContentHttpProxyServiceStatisticsSlotLevelTcpSplicingConnectionEntry 2 }

affirmedServicesContentHttpProxyServiceStatisticsSlotLevelTcpSplicingConnectionNumtcpsplicingclientconnectionstotal OBJECT-TYPE
    SYNTAX      ConfdString
    MAX-ACCESS  read-only
    STATUS      current
    DESCRIPTION "Number of tcp splicing client connections total"
    ::= { affirmedServicesContentHttpProxyServiceStatisticsSlotLevelTcpSplicingConnectionEntry 3 }

affirmedServicesContentHttpProxyServiceStatisticsSlotLevelTcpSplicingConnectionNumtcpsplicingclientconnectionscurrentlyinuse OBJECT-TYPE
    SYNTAX      ConfdString
    MAX-ACCESS  read-only
    STATUS      deprecated
    DESCRIPTION "Number of tcp splicing client connections currently in use"
    ::= { affirmedServicesContentHttpProxyServiceStatisticsSlotLevelTcpSplicingConnectionEntry 4 }

affirmedServicesContentHttpProxyServiceStatisticsSlotLevelTcpSplicingConnectionNumtcpsplicingclientconnectionsipv4 OBJECT-TYPE
    SYNTAX      ConfdString
    MAX-ACCESS  read-only
    STATUS      current
    DESCRIPTION "Number of tcp splicing client connections ipv4"
    ::= { affirmedServicesContentHttpProxyServiceStatisticsSlotLevelTcpSplicingConnectionEntry 5 }

affirmedServicesContentHttpProxyServiceStatisticsSlotLevelTcpSplicingConnectionNumtcpsplicingclientconnectionsipv6 OBJECT-TYPE
    SYNTAX      ConfdString
    MAX-ACCESS  read-only
    STATUS      current
    DESCRIPTION "Number of tcp splicing client connections ipv6"
    ::= { affirmedServicesContentHttpProxyServiceStatisticsSlotLevelTcpSplicingConnectionEntry 6 }

affirmedServicesContentHttpProxyServiceStatisticsSlotLevelTcpSplicingConnectionNumtcpsplicingclientconnectionsbytesreceived OBJECT-TYPE
    SYNTAX      ConfdString
    MAX-ACCESS  read-only
    STATUS      current
    DESCRIPTION "Number of tcp splicing client connections bytes received"
    ::= { affirmedServicesContentHttpProxyServiceStatisticsSlotLevelTcpSplicingConnectionEntry 7 }

affirmedServicesContentHttpProxyServiceStatisticsSlotLevelTcpSplicingConnectionNumtcpsplicingclientconnectionsbytessent OBJECT-TYPE
    SYNTAX      ConfdString
    MAX-ACCESS  read-only
    STATUS      current
    DESCRIPTION "Number of tcp splicing client connections bytes sent"
    ::= { affirmedServicesContentHttpProxyServiceStatisticsSlotLevelTcpSplicingConnectionEntry 8 }

affirmedServicesContentHttpProxyServiceStatisticsSlotLevelTcpSplicingConnectionNumtcpsplicingclientconnectionsreadfailure OBJECT-TYPE
    SYNTAX      ConfdString
    MAX-ACCESS  read-only
    STATUS      current
    DESCRIPTION "Number of tcp splicing client connections read failure"
    ::= { affirmedServicesContentHttpProxyServiceStatisticsSlotLevelTcpSplicingConnectionEntry 9 }

affirmedServicesContentHttpProxyServiceStatisticsSlotLevelTcpSplicingConnectionNumtcpsplicingclientconnectionswritefailure OBJECT-TYPE
    SYNTAX      ConfdString
    MAX-ACCESS  read-only
    STATUS      current
    DESCRIPTION "Number of tcp splicing client connections write failure"
    ::= { affirmedServicesContentHttpProxyServiceStatisticsSlotLevelTcpSplicingConnectionEntry 10 }

affirmedServicesContentHttpProxyServiceStatisticsSlotLevelTcpSplicingConnectionNumtcpsplicingclientconnectionswriteincomplete OBJECT-TYPE
    SYNTAX      ConfdString
    MAX-ACCESS  read-only
    STATUS      current
    DESCRIPTION "Number of tcp splicing client connections write incomplete"
    ::= { affirmedServicesContentHttpProxyServiceStatisticsSlotLevelTcpSplicingConnectionEntry 11 }

affirmedServicesContentHttpProxyServiceStatisticsSlotLevelTcpSplicingConnectionNumtcpsplicingserverconnectionstotal OBJECT-TYPE
    SYNTAX      ConfdString
    MAX-ACCESS  read-only
    STATUS      current
    DESCRIPTION "Number of tcp splicing server connections total"
    ::= { affirmedServicesContentHttpProxyServiceStatisticsSlotLevelTcpSplicingConnectionEntry 12 }

affirmedServicesContentHttpProxyServiceStatisticsSlotLevelTcpSplicingConnectionNumtcpsplicingserverconnectionscurrentlyinuse OBJECT-TYPE
    SYNTAX      ConfdString
    MAX-ACCESS  read-only
    STATUS      deprecated
    DESCRIPTION "Number of tcp splicing server connections currently in use"
    ::= { affirmedServicesContentHttpProxyServiceStatisticsSlotLevelTcpSplicingConnectionEntry 13 }

affirmedServicesContentHttpProxyServiceStatisticsSlotLevelTcpSplicingConnectionNumtcpsplicingserverconnectionsipv4 OBJECT-TYPE
    SYNTAX      ConfdString
    MAX-ACCESS  read-only
    STATUS      current
    DESCRIPTION "Number of tcp splicing server connections ipv4"
    ::= { affirmedServicesContentHttpProxyServiceStatisticsSlotLevelTcpSplicingConnectionEntry 14 }

affirmedServicesContentHttpProxyServiceStatisticsSlotLevelTcpSplicingConnectionNumtcpsplicingserverconnectionsipv6 OBJECT-TYPE
    SYNTAX      ConfdString
    MAX-ACCESS  read-only
    STATUS      current
    DESCRIPTION "Number of tcp splicing server connections ipv6"
    ::= { affirmedServicesContentHttpProxyServiceStatisticsSlotLevelTcpSplicingConnectionEntry 15 }

affirmedServicesContentHttpProxyServiceStatisticsSlotLevelTcpSplicingConnectionNumtcpsplicingserverconnectionsiptransparent OBJECT-TYPE
    SYNTAX      ConfdString
    MAX-ACCESS  read-only
    STATUS      current
    DESCRIPTION "Number of tcp splicing server connections ip transparent"
    ::= { affirmedServicesContentHttpProxyServiceStatisticsSlotLevelTcpSplicingConnectionEntry 16 }

affirmedServicesContentHttpProxyServiceStatisticsSlotLevelTcpSplicingConnectionNumtcpsplicingserverconnectionsbytesreceived OBJECT-TYPE
    SYNTAX      ConfdString
    MAX-ACCESS  read-only
    STATUS      current
    DESCRIPTION "Number of tcp splicing server connections bytes received"
    ::= { affirmedServicesContentHttpProxyServiceStatisticsSlotLevelTcpSplicingConnectionEntry 17 }

affirmedServicesContentHttpProxyServiceStatisticsSlotLevelTcpSplicingConnectionNumtcpsplicingserverconnectionsbytessent OBJECT-TYPE
    SYNTAX      ConfdString
    MAX-ACCESS  read-only
    STATUS      current
    DESCRIPTION "Number of tcp splicing server connections bytes sent"
    ::= { affirmedServicesContentHttpProxyServiceStatisticsSlotLevelTcpSplicingConnectionEntry 18 }

affirmedServicesContentHttpProxyServiceStatisticsSlotLevelTcpSplicingConnectionNumtcpsplicingserverconnectionsreadfailure OBJECT-TYPE
    SYNTAX      ConfdString
    MAX-ACCESS  read-only
    STATUS      current
    DESCRIPTION "Number of tcp splicing server connections read failure"
    ::= { affirmedServicesContentHttpProxyServiceStatisticsSlotLevelTcpSplicingConnectionEntry 19 }

affirmedServicesContentHttpProxyServiceStatisticsSlotLevelTcpSplicingConnectionNumtcpsplicingserverconnectionswritefailure OBJECT-TYPE
    SYNTAX      ConfdString
    MAX-ACCESS  read-only
    STATUS      current
    DESCRIPTION "Number of tcp splicing server connections write failure"
    ::= { affirmedServicesContentHttpProxyServiceStatisticsSlotLevelTcpSplicingConnectionEntry 20 }

affirmedServicesContentHttpProxyServiceStatisticsSlotLevelTcpSplicingConnectionNumtcpsplicingserverconnectionswriteincomplete OBJECT-TYPE
    SYNTAX      ConfdString
    MAX-ACCESS  read-only
    STATUS      current
    DESCRIPTION "Number of tcp splicing server connections write incomplete"
    ::= { affirmedServicesContentHttpProxyServiceStatisticsSlotLevelTcpSplicingConnectionEntry 21 }

affirmedServicesContentHttpProxyServiceStatisticsSlotLevelTcpSplicingConnectionNumtcpsplicingserverconnectionsconnectfailed OBJECT-TYPE
    SYNTAX      ConfdString
    MAX-ACCESS  read-only
    STATUS      current
    DESCRIPTION "Number of tcp splicing server connections connect failed"
    ::= { affirmedServicesContentHttpProxyServiceStatisticsSlotLevelTcpSplicingConnectionEntry 22 }

affirmedServicesContentHttpProxyServiceStatisticsSlotLevelTcpSplicingConnectionNumtcpsplicingclientconnectionscurrentinuse OBJECT-TYPE
    SYNTAX      ConfdString
    MAX-ACCESS  read-only
    STATUS      current
    DESCRIPTION "Number of tcp splicing client connections currently in use"
    ::= { affirmedServicesContentHttpProxyServiceStatisticsSlotLevelTcpSplicingConnectionEntry 23 }

affirmedServicesContentHttpProxyServiceStatisticsSlotLevelTcpSplicingConnectionNumtcpsplicingserverconnectionscurrentinuse OBJECT-TYPE
    SYNTAX      ConfdString
    MAX-ACCESS  read-only
    STATUS      current
    DESCRIPTION "Number of tcp splicing server connections currently in use"
    ::= { affirmedServicesContentHttpProxyServiceStatisticsSlotLevelTcpSplicingConnectionEntry 24 }

affirmedServicesContentHttpProxyServiceStatisticsSlotLevelTcpSplicingConnectionNumfastopenattempts OBJECT-TYPE
    SYNTAX      ConfdString
    MAX-ACCESS  read-only
    STATUS      current
    DESCRIPTION "Total number of HTTPS server connection fast open attempts"
    ::= { affirmedServicesContentHttpProxyServiceStatisticsSlotLevelTcpSplicingConnectionEntry 25 }

affirmedServicesContentHttpProxyServiceStatisticsSlotLevelTcpSplicingConnectionNumfastopensuccesses OBJECT-TYPE
    SYNTAX      ConfdString
    MAX-ACCESS  read-only
    STATUS      current
    DESCRIPTION "Total number of HTTPS server connection fast open successes"
    ::= { affirmedServicesContentHttpProxyServiceStatisticsSlotLevelTcpSplicingConnectionEntry 26 }

affirmedServicesContentHttpProxyServiceStatisticsSlotLevelTcpSplicingConnectionNumfastopenfailureinitconn OBJECT-TYPE
    SYNTAX      ConfdString
    MAX-ACCESS  read-only
    STATUS      current
    DESCRIPTION "Total number of HTTPS server connection fast open initialization failure"
    ::= { affirmedServicesContentHttpProxyServiceStatisticsSlotLevelTcpSplicingConnectionEntry 27 }

affirmedServicesContentHttpProxyServiceStatisticsSlotLevelTcpSplicingConnectionNumfastopenfailureduplicate OBJECT-TYPE
    SYNTAX      ConfdString
    MAX-ACCESS  read-only
    STATUS      current
    DESCRIPTION "Total number of HTTPS server connection fast open duplicated connection"
    ::= { affirmedServicesContentHttpProxyServiceStatisticsSlotLevelTcpSplicingConnectionEntry 28 }

affirmedServicesContentHttpProxyServiceStatisticsSlotLevelTcpSplicingConnectionNumfastopenfailurealreadycreated OBJECT-TYPE
    SYNTAX      ConfdString
    MAX-ACCESS  read-only
    STATUS      current
    DESCRIPTION "Total number of HTTPS server connection fast open already in the session"
    ::= { affirmedServicesContentHttpProxyServiceStatisticsSlotLevelTcpSplicingConnectionEntry 29 }

affirmedServicesContentHttpProxyServiceStatisticsSlotLevelTcpSplicingConnectionNumfastopenfailurepolicy OBJECT-TYPE
    SYNTAX      ConfdString
    MAX-ACCESS  read-only
    STATUS      current
    DESCRIPTION "Total number of HTTPS server connection fast open policy reject"
    ::= { affirmedServicesContentHttpProxyServiceStatisticsSlotLevelTcpSplicingConnectionEntry 30 }

affirmedServicesContentHttpProxyServiceStatisticsSlotLevelTcpSplicingConnectionNumfastopenfailureother OBJECT-TYPE
    SYNTAX      ConfdString
    MAX-ACCESS  read-only
    STATUS      current
    DESCRIPTION "Total number of HTTPS server connection fast open failure others"
    ::= { affirmedServicesContentHttpProxyServiceStatisticsSlotLevelTcpSplicingConnectionEntry 31 }

affirmedServicesContentHttpProxyServiceStatisticsSlotLevelTcpSplicingConnectionNumfastopenlistfull OBJECT-TYPE
    SYNTAX      ConfdString
    MAX-ACCESS  read-only
    STATUS      current
    DESCRIPTION "Total number of HTTPS server connection fast open pending list full"
    ::= { affirmedServicesContentHttpProxyServiceStatisticsSlotLevelTcpSplicingConnectionEntry 32 }

affirmedServicesContentHttpProxyServiceStatisticsSlotLevelTcpSplicingConnectionNumfastopencurrentpendingconn OBJECT-TYPE
    SYNTAX      ConfdString
    MAX-ACCESS  read-only
    STATUS      current
    DESCRIPTION "Total number of HTTPS server connection fast open in pending list"
    ::= { affirmedServicesContentHttpProxyServiceStatisticsSlotLevelTcpSplicingConnectionEntry 33 }

affirmedServicesContentHttpProxyServiceStatisticsSlotLevelTcpSplicingConnectionNumfastopenaging OBJECT-TYPE
    SYNTAX      ConfdString
    MAX-ACCESS  read-only
    STATUS      current
    DESCRIPTION "Total number of HTTPS server connection fast open connection closed due to aging"
    ::= { affirmedServicesContentHttpProxyServiceStatisticsSlotLevelTcpSplicingConnectionEntry 34 }

affirmedServicesContentHttpProxyServiceStatisticsSlotLevelTcpSplicingConnectionNumtcpsplicingdpiupdates OBJECT-TYPE
    SYNTAX      ConfdString
    MAX-ACCESS  read-only
    STATUS      current
    DESCRIPTION "Total Number of tcp splicing DPI Updates"
    ::= { affirmedServicesContentHttpProxyServiceStatisticsSlotLevelTcpSplicingConnectionEntry 35 }

affirmedServicesContentHttpProxyServiceStatisticsSlotLevelTcpSplicingConnectionNumtcpsplicingdpiupdatefailures OBJECT-TYPE
    SYNTAX      ConfdString
    MAX-ACCESS  read-only
    STATUS      current
    DESCRIPTION "Total Number of tcp splicing DPI Update Failures"
    ::= { affirmedServicesContentHttpProxyServiceStatisticsSlotLevelTcpSplicingConnectionEntry 36 }

affirmedServicesContentHttpProxyServiceStatisticsSlotLevelTcpSplicingDnsTable OBJECT-TYPE
    SYNTAX      SEQUENCE OF AffirmedServicesContentHttpProxyServiceStatisticsSlotLevelTcpSplicingDnsEntry
    MAX-ACCESS  not-accessible
    STATUS      current
    DESCRIPTION ""
    ::= { affirmedServicesContentHttpProxyServiceStatisticsSlotLevelTcpSplicing 6 }

affirmedServicesContentHttpProxyServiceStatisticsSlotLevelTcpSplicingDnsEntry OBJECT-TYPE
    SYNTAX      AffirmedServicesContentHttpProxyServiceStatisticsSlotLevelTcpSplicingDnsEntry
    MAX-ACCESS  not-accessible
    STATUS      current
    DESCRIPTION ""
    INDEX { affirmedServicesContentHttpProxyServiceStatisticsSlotLevelTcpSplicingDnsChassis, affirmedServicesContentHttpProxyServiceStatisticsSlotLevelTcpSplicingDnsSlot }
        ::= { affirmedServicesContentHttpProxyServiceStatisticsSlotLevelTcpSplicingDnsTable 1 }

AffirmedServicesContentHttpProxyServiceStatisticsSlotLevelTcpSplicingDnsEntry ::=
    SEQUENCE {
        affirmedServicesContentHttpProxyServiceStatisticsSlotLevelTcpSplicingDnsChassis Unsigned32,
        affirmedServicesContentHttpProxyServiceStatisticsSlotLevelTcpSplicingDnsSlot INTEGER,
        affirmedServicesContentHttpProxyServiceStatisticsSlotLevelTcpSplicingDnsNumtcpsplicingdnsqueriessent ConfdString,
        affirmedServicesContentHttpProxyServiceStatisticsSlotLevelTcpSplicingDnsNumtcpsplicingdnsqueriesfailed ConfdString,
        affirmedServicesContentHttpProxyServiceStatisticsSlotLevelTcpSplicingDnsNumtcpsplicingdnsqueriescanceled ConfdString,
        affirmedServicesContentHttpProxyServiceStatisticsSlotLevelTcpSplicingDnsNumtcpsplicingdnsrepliessuccess ConfdString,
        affirmedServicesContentHttpProxyServiceStatisticsSlotLevelTcpSplicingDnsNumtcpsplicingdnsrepliesfailure ConfdString,
        affirmedServicesContentHttpProxyServiceStatisticsSlotLevelTcpSplicingDnsNumtcpsplicingdnsrepliesstale ConfdString,
        affirmedServicesContentHttpProxyServiceStatisticsSlotLevelTcpSplicingDnsNumtcpsplicingdnsrepliesfromcache ConfdString
    }

affirmedServicesContentHttpProxyServiceStatisticsSlotLevelTcpSplicingDnsChassis OBJECT-TYPE
    SYNTAX      Unsigned32
    MAX-ACCESS  not-accessible
    STATUS      current
    DESCRIPTION "chassis ID"
    ::= { affirmedServicesContentHttpProxyServiceStatisticsSlotLevelTcpSplicingDnsEntry 1 }

affirmedServicesContentHttpProxyServiceStatisticsSlotLevelTcpSplicingDnsSlot OBJECT-TYPE
    SYNTAX      INTEGER {a1(1),a2(2),a3(3),a4(4),a5(5),a6(6),a7(7),a8(8),a9(9),a10(10),a11(11),a12(12),a13(13),a14(14),a15(15),a16(16),a17(17),a18(18),a19(19),a20(20),a21(21),a22(22),a23(23),a24(24),a25(25),a26(26),a27(27),a28(28),a29(29),a30(30),a31(31),a32(32),a33(33),a34(34),a35(35),a36(36),a37(37),a38(38),a39(39),a40(40),a41(41),a42(42),a43(43),a44(44),a45(45),a46(46),a47(47),a48(48),a49(49),a50(50),a51(51),a52(52),a53(53),a54(54),a55(55),a56(56),a57(57),a58(58),a59(59),a60(60),a61(61),a62(62),a63(63),a64(64),a65(65),a66(66),a67(67),a68(68),a69(69),a70(70),a71(71),a72(72),a73(73),a74(74),a75(75),a76(76),a77(77),a78(78),a79(79),a80(80),a81(81),a82(82),a83(83),a84(84),a85(85),a86(86),a87(87),a88(88),a89(89),a90(90),a91(91),a92(92),a93(93),a94(94),a95(95),a96(96),a97(97),a98(98),a99(99),a100(100),a101(101),a102(102),a103(103),a104(104),a105(105),a106(106),a107(107),a108(108),a109(109),a110(110),a111(111),a112(112),a113(113),a114(114),a115(115),a116(116),a117(117),a118(118),a119(119),a120(120),a121(121),a122(122),a123(123),a124(124),a125(125),a126(126),a127(127),a128(128)}
    MAX-ACCESS  not-accessible
    STATUS      current
    DESCRIPTION "slot number"
    ::= { affirmedServicesContentHttpProxyServiceStatisticsSlotLevelTcpSplicingDnsEntry 2 }

affirmedServicesContentHttpProxyServiceStatisticsSlotLevelTcpSplicingDnsNumtcpsplicingdnsqueriessent OBJECT-TYPE
    SYNTAX      ConfdString
    MAX-ACCESS  read-only
    STATUS      current
    DESCRIPTION "Number of tcp splicing dns queries sent"
    ::= { affirmedServicesContentHttpProxyServiceStatisticsSlotLevelTcpSplicingDnsEntry 3 }

affirmedServicesContentHttpProxyServiceStatisticsSlotLevelTcpSplicingDnsNumtcpsplicingdnsqueriesfailed OBJECT-TYPE
    SYNTAX      ConfdString
    MAX-ACCESS  read-only
    STATUS      current
    DESCRIPTION "Number of tcp splicing dns queries failed"
    ::= { affirmedServicesContentHttpProxyServiceStatisticsSlotLevelTcpSplicingDnsEntry 4 }

affirmedServicesContentHttpProxyServiceStatisticsSlotLevelTcpSplicingDnsNumtcpsplicingdnsqueriescanceled OBJECT-TYPE
    SYNTAX      ConfdString
    MAX-ACCESS  read-only
    STATUS      current
    DESCRIPTION "Number of tcp splicing dns queries canceled"
    ::= { affirmedServicesContentHttpProxyServiceStatisticsSlotLevelTcpSplicingDnsEntry 5 }

affirmedServicesContentHttpProxyServiceStatisticsSlotLevelTcpSplicingDnsNumtcpsplicingdnsrepliessuccess OBJECT-TYPE
    SYNTAX      ConfdString
    MAX-ACCESS  read-only
    STATUS      current
    DESCRIPTION "Number of tcp splicing dns replies success"
    ::= { affirmedServicesContentHttpProxyServiceStatisticsSlotLevelTcpSplicingDnsEntry 6 }

affirmedServicesContentHttpProxyServiceStatisticsSlotLevelTcpSplicingDnsNumtcpsplicingdnsrepliesfailure OBJECT-TYPE
    SYNTAX      ConfdString
    MAX-ACCESS  read-only
    STATUS      current
    DESCRIPTION "Number of tcp splicing dns replies failure"
    ::= { affirmedServicesContentHttpProxyServiceStatisticsSlotLevelTcpSplicingDnsEntry 7 }

affirmedServicesContentHttpProxyServiceStatisticsSlotLevelTcpSplicingDnsNumtcpsplicingdnsrepliesstale OBJECT-TYPE
    SYNTAX      ConfdString
    MAX-ACCESS  read-only
    STATUS      current
    DESCRIPTION "Number of tcp splicing dns replies stale"
    ::= { affirmedServicesContentHttpProxyServiceStatisticsSlotLevelTcpSplicingDnsEntry 8 }

affirmedServicesContentHttpProxyServiceStatisticsSlotLevelTcpSplicingDnsNumtcpsplicingdnsrepliesfromcache OBJECT-TYPE
    SYNTAX      ConfdString
    MAX-ACCESS  read-only
    STATUS      current
    DESCRIPTION "Number of tcp splicing dns replies from cache"
    ::= { affirmedServicesContentHttpProxyServiceStatisticsSlotLevelTcpSplicingDnsEntry 9 }

affirmedServicesContentHttpProxyServiceStatisticsSlotLevelAbrRateLimitingSessionTable OBJECT-TYPE
    SYNTAX      SEQUENCE OF AffirmedServicesContentHttpProxyServiceStatisticsSlotLevelAbrRateLimitingSessionEntry
    MAX-ACCESS  not-accessible
    STATUS      current
    DESCRIPTION ""
    ::= { affirmedServicesContentHttpProxyServiceStatisticsSlotLevelAbrRateLimiting 1 }

affirmedServicesContentHttpProxyServiceStatisticsSlotLevelAbrRateLimitingSessionEntry OBJECT-TYPE
    SYNTAX      AffirmedServicesContentHttpProxyServiceStatisticsSlotLevelAbrRateLimitingSessionEntry
    MAX-ACCESS  not-accessible
    STATUS      current
    DESCRIPTION ""
    INDEX { affirmedServicesContentHttpProxyServiceStatisticsSlotLevelAbrRateLimitingSessionChassis, affirmedServicesContentHttpProxyServiceStatisticsSlotLevelAbrRateLimitingSessionSlot }
        ::= { affirmedServicesContentHttpProxyServiceStatisticsSlotLevelAbrRateLimitingSessionTable 1 }

AffirmedServicesContentHttpProxyServiceStatisticsSlotLevelAbrRateLimitingSessionEntry ::=
    SEQUENCE {
        affirmedServicesContentHttpProxyServiceStatisticsSlotLevelAbrRateLimitingSessionChassis Unsigned32,
        affirmedServicesContentHttpProxyServiceStatisticsSlotLevelAbrRateLimitingSessionSlot INTEGER,
        affirmedServicesContentHttpProxyServiceStatisticsSlotLevelAbrRateLimitingSessionSession-total ConfdString,
        affirmedServicesContentHttpProxyServiceStatisticsSlotLevelAbrRateLimitingSessionSession-total-hls ConfdString,
        affirmedServicesContentHttpProxyServiceStatisticsSlotLevelAbrRateLimitingSessionSession-total-dash ConfdString,
        affirmedServicesContentHttpProxyServiceStatisticsSlotLevelAbrRateLimitingSessionSession-total-hds ConfdString,
        affirmedServicesContentHttpProxyServiceStatisticsSlotLevelAbrRateLimitingSessionSession-total-other ConfdString,
        affirmedServicesContentHttpProxyServiceStatisticsSlotLevelAbrRateLimitingSessionDuration-min ConfdString,
        affirmedServicesContentHttpProxyServiceStatisticsSlotLevelAbrRateLimitingSessionDuration-avg ConfdString,
        affirmedServicesContentHttpProxyServiceStatisticsSlotLevelAbrRateLimitingSessionDuration-max ConfdString,
        affirmedServicesContentHttpProxyServiceStatisticsSlotLevelAbrRateLimitingSessionSession-bytes-total ConfdString,
        affirmedServicesContentHttpProxyServiceStatisticsSlotLevelAbrRateLimitingSessionSession-bytes-hls ConfdString,
        affirmedServicesContentHttpProxyServiceStatisticsSlotLevelAbrRateLimitingSessionSession-bytes-dash ConfdString,
        affirmedServicesContentHttpProxyServiceStatisticsSlotLevelAbrRateLimitingSessionSession-bytes-hds ConfdString,
        affirmedServicesContentHttpProxyServiceStatisticsSlotLevelAbrRateLimitingSessionSession-bytes-other ConfdString,
        affirmedServicesContentHttpProxyServiceStatisticsSlotLevelAbrRateLimitingSessionSession-bitrate-0-500 ConfdString,
        affirmedServicesContentHttpProxyServiceStatisticsSlotLevelAbrRateLimitingSessionSession-bitrate-500-1000 ConfdString,
        affirmedServicesContentHttpProxyServiceStatisticsSlotLevelAbrRateLimitingSessionSession-bitrate-1000-2500 ConfdString,
        affirmedServicesContentHttpProxyServiceStatisticsSlotLevelAbrRateLimitingSessionSession-bitrate-2500-more ConfdString,
        affirmedServicesContentHttpProxyServiceStatisticsSlotLevelAbrRateLimitingSessionSession-current ConfdString,
        affirmedServicesContentHttpProxyServiceStatisticsSlotLevelAbrRateLimitingSessionSession-bypass-savings-estimation ConfdString
    }

affirmedServicesContentHttpProxyServiceStatisticsSlotLevelAbrRateLimitingSessionChassis OBJECT-TYPE
    SYNTAX      Unsigned32
    MAX-ACCESS  not-accessible
    STATUS      current
    DESCRIPTION "chassis ID"
    ::= { affirmedServicesContentHttpProxyServiceStatisticsSlotLevelAbrRateLimitingSessionEntry 1 }

affirmedServicesContentHttpProxyServiceStatisticsSlotLevelAbrRateLimitingSessionSlot OBJECT-TYPE
    SYNTAX      INTEGER {a1(1),a2(2),a3(3),a4(4),a5(5),a6(6),a7(7),a8(8),a9(9),a10(10),a11(11),a12(12),a13(13),a14(14),a15(15),a16(16),a17(17),a18(18),a19(19),a20(20),a21(21),a22(22),a23(23),a24(24),a25(25),a26(26),a27(27),a28(28),a29(29),a30(30),a31(31),a32(32),a33(33),a34(34),a35(35),a36(36),a37(37),a38(38),a39(39),a40(40),a41(41),a42(42),a43(43),a44(44),a45(45),a46(46),a47(47),a48(48),a49(49),a50(50),a51(51),a52(52),a53(53),a54(54),a55(55),a56(56),a57(57),a58(58),a59(59),a60(60),a61(61),a62(62),a63(63),a64(64),a65(65),a66(66),a67(67),a68(68),a69(69),a70(70),a71(71),a72(72),a73(73),a74(74),a75(75),a76(76),a77(77),a78(78),a79(79),a80(80),a81(81),a82(82),a83(83),a84(84),a85(85),a86(86),a87(87),a88(88),a89(89),a90(90),a91(91),a92(92),a93(93),a94(94),a95(95),a96(96),a97(97),a98(98),a99(99),a100(100),a101(101),a102(102),a103(103),a104(104),a105(105),a106(106),a107(107),a108(108),a109(109),a110(110),a111(111),a112(112),a113(113),a114(114),a115(115),a116(116),a117(117),a118(118),a119(119),a120(120),a121(121),a122(122),a123(123),a124(124),a125(125),a126(126),a127(127),a128(128)}
    MAX-ACCESS  not-accessible
    STATUS      current
    DESCRIPTION "slot number"
    ::= { affirmedServicesContentHttpProxyServiceStatisticsSlotLevelAbrRateLimitingSessionEntry 2 }

affirmedServicesContentHttpProxyServiceStatisticsSlotLevelAbrRateLimitingSessionSession-total OBJECT-TYPE
    SYNTAX      ConfdString
    MAX-ACCESS  read-only
    STATUS      current
    DESCRIPTION "Number of Total ABR Session"
    ::= { affirmedServicesContentHttpProxyServiceStatisticsSlotLevelAbrRateLimitingSessionEntry 3 }

affirmedServicesContentHttpProxyServiceStatisticsSlotLevelAbrRateLimitingSessionSession-total-hls OBJECT-TYPE
    SYNTAX      ConfdString
    MAX-ACCESS  read-only
    STATUS      current
    DESCRIPTION "Number of Total HLS ABR Sessions"
    ::= { affirmedServicesContentHttpProxyServiceStatisticsSlotLevelAbrRateLimitingSessionEntry 4 }

affirmedServicesContentHttpProxyServiceStatisticsSlotLevelAbrRateLimitingSessionSession-total-dash OBJECT-TYPE
    SYNTAX      ConfdString
    MAX-ACCESS  read-only
    STATUS      current
    DESCRIPTION "Number of Total DASH ABR Sessions"
    ::= { affirmedServicesContentHttpProxyServiceStatisticsSlotLevelAbrRateLimitingSessionEntry 5 }

affirmedServicesContentHttpProxyServiceStatisticsSlotLevelAbrRateLimitingSessionSession-total-hds OBJECT-TYPE
    SYNTAX      ConfdString
    MAX-ACCESS  read-only
    STATUS      current
    DESCRIPTION "Number of Total HDS ABR Sessions"
    ::= { affirmedServicesContentHttpProxyServiceStatisticsSlotLevelAbrRateLimitingSessionEntry 6 }

affirmedServicesContentHttpProxyServiceStatisticsSlotLevelAbrRateLimitingSessionSession-total-other OBJECT-TYPE
    SYNTAX      ConfdString
    MAX-ACCESS  read-only
    STATUS      current
    DESCRIPTION "Number of Total Other ABR Sessions"
    ::= { affirmedServicesContentHttpProxyServiceStatisticsSlotLevelAbrRateLimitingSessionEntry 7 }

affirmedServicesContentHttpProxyServiceStatisticsSlotLevelAbrRateLimitingSessionDuration-min OBJECT-TYPE
    SYNTAX      ConfdString
    MAX-ACCESS  read-only
    STATUS      current
    DESCRIPTION "Minimum ABR video duration in seconds"
    ::= { affirmedServicesContentHttpProxyServiceStatisticsSlotLevelAbrRateLimitingSessionEntry 8 }

affirmedServicesContentHttpProxyServiceStatisticsSlotLevelAbrRateLimitingSessionDuration-avg OBJECT-TYPE
    SYNTAX      ConfdString
    MAX-ACCESS  read-only
    STATUS      current
    DESCRIPTION "Average ABR video duration in seconds"
    ::= { affirmedServicesContentHttpProxyServiceStatisticsSlotLevelAbrRateLimitingSessionEntry 9 }

affirmedServicesContentHttpProxyServiceStatisticsSlotLevelAbrRateLimitingSessionDuration-max OBJECT-TYPE
    SYNTAX      ConfdString
    MAX-ACCESS  read-only
    STATUS      current
    DESCRIPTION "Maximum ABR video duration in seconds"
    ::= { affirmedServicesContentHttpProxyServiceStatisticsSlotLevelAbrRateLimitingSessionEntry 10 }

affirmedServicesContentHttpProxyServiceStatisticsSlotLevelAbrRateLimitingSessionSession-bytes-total OBJECT-TYPE
    SYNTAX      ConfdString
    MAX-ACCESS  read-only
    STATUS      current
    DESCRIPTION "Total Bytes of ABR Sessions"
    ::= { affirmedServicesContentHttpProxyServiceStatisticsSlotLevelAbrRateLimitingSessionEntry 11 }

affirmedServicesContentHttpProxyServiceStatisticsSlotLevelAbrRateLimitingSessionSession-bytes-hls OBJECT-TYPE
    SYNTAX      ConfdString
    MAX-ACCESS  read-only
    STATUS      current
    DESCRIPTION "Total Bytes of HLS ABR Sessions"
    ::= { affirmedServicesContentHttpProxyServiceStatisticsSlotLevelAbrRateLimitingSessionEntry 12 }

affirmedServicesContentHttpProxyServiceStatisticsSlotLevelAbrRateLimitingSessionSession-bytes-dash OBJECT-TYPE
    SYNTAX      ConfdString
    MAX-ACCESS  read-only
    STATUS      current
    DESCRIPTION "Total Bytes of DASH ABR Sessions"
    ::= { affirmedServicesContentHttpProxyServiceStatisticsSlotLevelAbrRateLimitingSessionEntry 13 }

affirmedServicesContentHttpProxyServiceStatisticsSlotLevelAbrRateLimitingSessionSession-bytes-hds OBJECT-TYPE
    SYNTAX      ConfdString
    MAX-ACCESS  read-only
    STATUS      current
    DESCRIPTION "Total Bytes of HDS ABR Sessions"
    ::= { affirmedServicesContentHttpProxyServiceStatisticsSlotLevelAbrRateLimitingSessionEntry 14 }

affirmedServicesContentHttpProxyServiceStatisticsSlotLevelAbrRateLimitingSessionSession-bytes-other OBJECT-TYPE
    SYNTAX      ConfdString
    MAX-ACCESS  read-only
    STATUS      current
    DESCRIPTION "Total Bytes of Other Sessions"
    ::= { affirmedServicesContentHttpProxyServiceStatisticsSlotLevelAbrRateLimitingSessionEntry 15 }

affirmedServicesContentHttpProxyServiceStatisticsSlotLevelAbrRateLimitingSessionSession-bitrate-0-500 OBJECT-TYPE
    SYNTAX      ConfdString
    MAX-ACCESS  read-only
    STATUS      current
    DESCRIPTION "Total ABR video bitrate from 0 to 500 kbps"
    ::= { affirmedServicesContentHttpProxyServiceStatisticsSlotLevelAbrRateLimitingSessionEntry 16 }

affirmedServicesContentHttpProxyServiceStatisticsSlotLevelAbrRateLimitingSessionSession-bitrate-500-1000 OBJECT-TYPE
    SYNTAX      ConfdString
    MAX-ACCESS  read-only
    STATUS      current
    DESCRIPTION "Total ABR video bitrate from 500 to 1,000 kbps"
    ::= { affirmedServicesContentHttpProxyServiceStatisticsSlotLevelAbrRateLimitingSessionEntry 17 }

affirmedServicesContentHttpProxyServiceStatisticsSlotLevelAbrRateLimitingSessionSession-bitrate-1000-2500 OBJECT-TYPE
    SYNTAX      ConfdString
    MAX-ACCESS  read-only
    STATUS      current
    DESCRIPTION "Total ABR video bitrate from 1,000 to 2,500 kbps"
    ::= { affirmedServicesContentHttpProxyServiceStatisticsSlotLevelAbrRateLimitingSessionEntry 18 }

affirmedServicesContentHttpProxyServiceStatisticsSlotLevelAbrRateLimitingSessionSession-bitrate-2500-more OBJECT-TYPE
    SYNTAX      ConfdString
    MAX-ACCESS  read-only
    STATUS      current
    DESCRIPTION "Total ABR video bitrate greater than 2,500 kbps"
    ::= { affirmedServicesContentHttpProxyServiceStatisticsSlotLevelAbrRateLimitingSessionEntry 19 }

affirmedServicesContentHttpProxyServiceStatisticsSlotLevelAbrRateLimitingSessionSession-current OBJECT-TYPE
    SYNTAX      ConfdString
    MAX-ACCESS  read-only
    STATUS      current
    DESCRIPTION "Total ABR Session currently rate limited"
    ::= { affirmedServicesContentHttpProxyServiceStatisticsSlotLevelAbrRateLimitingSessionEntry 20 }

affirmedServicesContentHttpProxyServiceStatisticsSlotLevelAbrRateLimitingSessionSession-bypass-savings-estimation OBJECT-TYPE
    SYNTAX      ConfdString
    MAX-ACCESS  read-only
    STATUS      current
    DESCRIPTION "Total ABR video segment bypass because of savings estimation process"
    ::= { affirmedServicesContentHttpProxyServiceStatisticsSlotLevelAbrRateLimitingSessionEntry 21 }

affirmedServicesContentHttpProxyServiceStatisticsSlotLevelAbrRateLimitingSegmentTable OBJECT-TYPE
    SYNTAX      SEQUENCE OF AffirmedServicesContentHttpProxyServiceStatisticsSlotLevelAbrRateLimitingSegmentEntry
    MAX-ACCESS  not-accessible
    STATUS      current
    DESCRIPTION ""
    ::= { affirmedServicesContentHttpProxyServiceStatisticsSlotLevelAbrRateLimiting 2 }

affirmedServicesContentHttpProxyServiceStatisticsSlotLevelAbrRateLimitingSegmentEntry OBJECT-TYPE
    SYNTAX      AffirmedServicesContentHttpProxyServiceStatisticsSlotLevelAbrRateLimitingSegmentEntry
    MAX-ACCESS  not-accessible
    STATUS      current
    DESCRIPTION ""
    INDEX { affirmedServicesContentHttpProxyServiceStatisticsSlotLevelAbrRateLimitingSegmentChassis, affirmedServicesContentHttpProxyServiceStatisticsSlotLevelAbrRateLimitingSegmentSlot }
        ::= { affirmedServicesContentHttpProxyServiceStatisticsSlotLevelAbrRateLimitingSegmentTable 1 }

AffirmedServicesContentHttpProxyServiceStatisticsSlotLevelAbrRateLimitingSegmentEntry ::=
    SEQUENCE {
        affirmedServicesContentHttpProxyServiceStatisticsSlotLevelAbrRateLimitingSegmentChassis Unsigned32,
        affirmedServicesContentHttpProxyServiceStatisticsSlotLevelAbrRateLimitingSegmentSlot INTEGER,
        affirmedServicesContentHttpProxyServiceStatisticsSlotLevelAbrRateLimitingSegmentSegment-total ConfdString,
        affirmedServicesContentHttpProxyServiceStatisticsSlotLevelAbrRateLimitingSegmentSegment-total-hls ConfdString,
        affirmedServicesContentHttpProxyServiceStatisticsSlotLevelAbrRateLimitingSegmentSegment-total-dash ConfdString,
        affirmedServicesContentHttpProxyServiceStatisticsSlotLevelAbrRateLimitingSegmentSegment-total-hds ConfdString,
        affirmedServicesContentHttpProxyServiceStatisticsSlotLevelAbrRateLimitingSegmentSegment-total-other ConfdString,
        affirmedServicesContentHttpProxyServiceStatisticsSlotLevelAbrRateLimitingSegmentSegment-bitrate-0-500 ConfdString,
        affirmedServicesContentHttpProxyServiceStatisticsSlotLevelAbrRateLimitingSegmentSegment-bitrate-500-1000 ConfdString,
        affirmedServicesContentHttpProxyServiceStatisticsSlotLevelAbrRateLimitingSegmentSegment-bitrate-1000-2500 ConfdString,
        affirmedServicesContentHttpProxyServiceStatisticsSlotLevelAbrRateLimitingSegmentSegment-bitrate-2500-more ConfdString,
        affirmedServicesContentHttpProxyServiceStatisticsSlotLevelAbrRateLimitingSegmentSegment-bitrate-enforced ConfdString,
        affirmedServicesContentHttpProxyServiceStatisticsSlotLevelAbrRateLimitingSegmentSubscriber-opt-out ConfdString,
        affirmedServicesContentHttpProxyServiceStatisticsSlotLevelAbrRateLimitingSegmentNo-matching-policy ConfdString,
        affirmedServicesContentHttpProxyServiceStatisticsSlotLevelAbrRateLimitingSegmentSegment-current ConfdString,
        affirmedServicesContentHttpProxyServiceStatisticsSlotLevelAbrRateLimitingSegmentSubscriber-opt-in-rate-limiting-req-not-met ConfdString,
        affirmedServicesContentHttpProxyServiceStatisticsSlotLevelAbrRateLimitingSegmentNo-maxrate-cp-manifest ConfdString,
        affirmedServicesContentHttpProxyServiceStatisticsSlotLevelAbrRateLimitingSegmentCp-manifest-with-maxrate ConfdString,
        affirmedServicesContentHttpProxyServiceStatisticsSlotLevelAbrRateLimitingSegmentInvalid-maxrate-cp-manifest ConfdString,
        affirmedServicesContentHttpProxyServiceStatisticsSlotLevelAbrRateLimitingSegmentSegment-bypass-savings-estimation ConfdString,
        affirmedServicesContentHttpProxyServiceStatisticsSlotLevelAbrRateLimitingSegmentSegment-bypass-short-response ConfdString,
        affirmedServicesContentHttpProxyServiceStatisticsSlotLevelAbrRateLimitingSegmentAggregation-bypass ConfdString
    }

affirmedServicesContentHttpProxyServiceStatisticsSlotLevelAbrRateLimitingSegmentChassis OBJECT-TYPE
    SYNTAX      Unsigned32
    MAX-ACCESS  not-accessible
    STATUS      current
    DESCRIPTION "chassis ID"
    ::= { affirmedServicesContentHttpProxyServiceStatisticsSlotLevelAbrRateLimitingSegmentEntry 1 }

affirmedServicesContentHttpProxyServiceStatisticsSlotLevelAbrRateLimitingSegmentSlot OBJECT-TYPE
    SYNTAX      INTEGER {a1(1),a2(2),a3(3),a4(4),a5(5),a6(6),a7(7),a8(8),a9(9),a10(10),a11(11),a12(12),a13(13),a14(14),a15(15),a16(16),a17(17),a18(18),a19(19),a20(20),a21(21),a22(22),a23(23),a24(24),a25(25),a26(26),a27(27),a28(28),a29(29),a30(30),a31(31),a32(32),a33(33),a34(34),a35(35),a36(36),a37(37),a38(38),a39(39),a40(40),a41(41),a42(42),a43(43),a44(44),a45(45),a46(46),a47(47),a48(48),a49(49),a50(50),a51(51),a52(52),a53(53),a54(54),a55(55),a56(56),a57(57),a58(58),a59(59),a60(60),a61(61),a62(62),a63(63),a64(64),a65(65),a66(66),a67(67),a68(68),a69(69),a70(70),a71(71),a72(72),a73(73),a74(74),a75(75),a76(76),a77(77),a78(78),a79(79),a80(80),a81(81),a82(82),a83(83),a84(84),a85(85),a86(86),a87(87),a88(88),a89(89),a90(90),a91(91),a92(92),a93(93),a94(94),a95(95),a96(96),a97(97),a98(98),a99(99),a100(100),a101(101),a102(102),a103(103),a104(104),a105(105),a106(106),a107(107),a108(108),a109(109),a110(110),a111(111),a112(112),a113(113),a114(114),a115(115),a116(116),a117(117),a118(118),a119(119),a120(120),a121(121),a122(122),a123(123),a124(124),a125(125),a126(126),a127(127),a128(128)}
    MAX-ACCESS  not-accessible
    STATUS      current
    DESCRIPTION "slot number"
    ::= { affirmedServicesContentHttpProxyServiceStatisticsSlotLevelAbrRateLimitingSegmentEntry 2 }

affirmedServicesContentHttpProxyServiceStatisticsSlotLevelAbrRateLimitingSegmentSegment-total OBJECT-TYPE
    SYNTAX      ConfdString
    MAX-ACCESS  read-only
    STATUS      current
    DESCRIPTION "Number of Total ABR Segment"
    ::= { affirmedServicesContentHttpProxyServiceStatisticsSlotLevelAbrRateLimitingSegmentEntry 3 }

affirmedServicesContentHttpProxyServiceStatisticsSlotLevelAbrRateLimitingSegmentSegment-total-hls OBJECT-TYPE
    SYNTAX      ConfdString
    MAX-ACCESS  read-only
    STATUS      current
    DESCRIPTION "Number of Total HLS ABR Segment"
    ::= { affirmedServicesContentHttpProxyServiceStatisticsSlotLevelAbrRateLimitingSegmentEntry 4 }

affirmedServicesContentHttpProxyServiceStatisticsSlotLevelAbrRateLimitingSegmentSegment-total-dash OBJECT-TYPE
    SYNTAX      ConfdString
    MAX-ACCESS  read-only
    STATUS      current
    DESCRIPTION "Number of Total DASH ABR Segment"
    ::= { affirmedServicesContentHttpProxyServiceStatisticsSlotLevelAbrRateLimitingSegmentEntry 5 }

affirmedServicesContentHttpProxyServiceStatisticsSlotLevelAbrRateLimitingSegmentSegment-total-hds OBJECT-TYPE
    SYNTAX      ConfdString
    MAX-ACCESS  read-only
    STATUS      current
    DESCRIPTION "Number of Total HDS ABR Segment"
    ::= { affirmedServicesContentHttpProxyServiceStatisticsSlotLevelAbrRateLimitingSegmentEntry 6 }

affirmedServicesContentHttpProxyServiceStatisticsSlotLevelAbrRateLimitingSegmentSegment-total-other OBJECT-TYPE
    SYNTAX      ConfdString
    MAX-ACCESS  read-only
    STATUS      current
    DESCRIPTION "Number of Total Other ABR Segment"
    ::= { affirmedServicesContentHttpProxyServiceStatisticsSlotLevelAbrRateLimitingSegmentEntry 7 }

affirmedServicesContentHttpProxyServiceStatisticsSlotLevelAbrRateLimitingSegmentSegment-bitrate-0-500 OBJECT-TYPE
    SYNTAX      ConfdString
    MAX-ACCESS  read-only
    STATUS      current
    DESCRIPTION "Total ABR video bitrate from 0 to 1,000 kbps"
    ::= { affirmedServicesContentHttpProxyServiceStatisticsSlotLevelAbrRateLimitingSegmentEntry 8 }

affirmedServicesContentHttpProxyServiceStatisticsSlotLevelAbrRateLimitingSegmentSegment-bitrate-500-1000 OBJECT-TYPE
    SYNTAX      ConfdString
    MAX-ACCESS  read-only
    STATUS      current
    DESCRIPTION "Total ABR Segment bitrate from 500 to 1,000 kbps"
    ::= { affirmedServicesContentHttpProxyServiceStatisticsSlotLevelAbrRateLimitingSegmentEntry 9 }

affirmedServicesContentHttpProxyServiceStatisticsSlotLevelAbrRateLimitingSegmentSegment-bitrate-1000-2500 OBJECT-TYPE
    SYNTAX      ConfdString
    MAX-ACCESS  read-only
    STATUS      current
    DESCRIPTION "Total ABR Segment bitrate from 1,000 to 2,500 kbps"
    ::= { affirmedServicesContentHttpProxyServiceStatisticsSlotLevelAbrRateLimitingSegmentEntry 10 }

affirmedServicesContentHttpProxyServiceStatisticsSlotLevelAbrRateLimitingSegmentSegment-bitrate-2500-more OBJECT-TYPE
    SYNTAX      ConfdString
    MAX-ACCESS  read-only
    STATUS      current
    DESCRIPTION "Total ABR Segment bitrate greater than 2,500 kbps"
    ::= { affirmedServicesContentHttpProxyServiceStatisticsSlotLevelAbrRateLimitingSegmentEntry 11 }

affirmedServicesContentHttpProxyServiceStatisticsSlotLevelAbrRateLimitingSegmentSegment-bitrate-enforced OBJECT-TYPE
    SYNTAX      ConfdString
    MAX-ACCESS  read-only
    STATUS      current
    DESCRIPTION "Total ABR Segment that bitrate is enforced lower than media bitrate"
    ::= { affirmedServicesContentHttpProxyServiceStatisticsSlotLevelAbrRateLimitingSegmentEntry 12 }

affirmedServicesContentHttpProxyServiceStatisticsSlotLevelAbrRateLimitingSegmentSubscriber-opt-out OBJECT-TYPE
    SYNTAX      ConfdString
    MAX-ACCESS  read-only
    STATUS      current
    DESCRIPTION "Total ABR Segment bypass because of subsscriber opt out"
    ::= { affirmedServicesContentHttpProxyServiceStatisticsSlotLevelAbrRateLimitingSegmentEntry 13 }

affirmedServicesContentHttpProxyServiceStatisticsSlotLevelAbrRateLimitingSegmentNo-matching-policy OBJECT-TYPE
    SYNTAX      ConfdString
    MAX-ACCESS  read-only
    STATUS      current
    DESCRIPTION "Total ABR Segment bypass because applied response policy without ABR optimization"
    ::= { affirmedServicesContentHttpProxyServiceStatisticsSlotLevelAbrRateLimitingSegmentEntry 14 }

affirmedServicesContentHttpProxyServiceStatisticsSlotLevelAbrRateLimitingSegmentSegment-current OBJECT-TYPE
    SYNTAX      ConfdString
    MAX-ACCESS  read-only
    STATUS      current
    DESCRIPTION "Total ABR Segment currently rate limited"
    ::= { affirmedServicesContentHttpProxyServiceStatisticsSlotLevelAbrRateLimitingSegmentEntry 15 }

affirmedServicesContentHttpProxyServiceStatisticsSlotLevelAbrRateLimitingSegmentSubscriber-opt-in-rate-limiting-req-not-met OBJECT-TYPE
    SYNTAX      ConfdString
    MAX-ACCESS  read-only
    STATUS      current
    DESCRIPTION "Total ABR Segment bypass because of subscriber opt in requirements do not meet"
    ::= { affirmedServicesContentHttpProxyServiceStatisticsSlotLevelAbrRateLimitingSegmentEntry 16 }

affirmedServicesContentHttpProxyServiceStatisticsSlotLevelAbrRateLimitingSegmentNo-maxrate-cp-manifest OBJECT-TYPE
    SYNTAX      ConfdString
    MAX-ACCESS  read-only
    STATUS      current
    DESCRIPTION "Total ABR video segment bypass because no Max-Rate in the CP Manifest"
    ::= { affirmedServicesContentHttpProxyServiceStatisticsSlotLevelAbrRateLimitingSegmentEntry 17 }

affirmedServicesContentHttpProxyServiceStatisticsSlotLevelAbrRateLimitingSegmentCp-manifest-with-maxrate OBJECT-TYPE
    SYNTAX      ConfdString
    MAX-ACCESS  read-only
    STATUS      current
    DESCRIPTION "Total ABR video segment when Max-Rate in the CP Manifest"
    ::= { affirmedServicesContentHttpProxyServiceStatisticsSlotLevelAbrRateLimitingSegmentEntry 18 }

affirmedServicesContentHttpProxyServiceStatisticsSlotLevelAbrRateLimitingSegmentInvalid-maxrate-cp-manifest OBJECT-TYPE
    SYNTAX      ConfdString
    MAX-ACCESS  read-only
    STATUS      current
    DESCRIPTION "Total ABR video segment bypass because of invalid Max-Rate in the CP Manifest"
    ::= { affirmedServicesContentHttpProxyServiceStatisticsSlotLevelAbrRateLimitingSegmentEntry 19 }

affirmedServicesContentHttpProxyServiceStatisticsSlotLevelAbrRateLimitingSegmentSegment-bypass-savings-estimation OBJECT-TYPE
    SYNTAX      ConfdString
    MAX-ACCESS  read-only
    STATUS      current
    DESCRIPTION "Total ABR video segment bypass because of savings estimation process"
    ::= { affirmedServicesContentHttpProxyServiceStatisticsSlotLevelAbrRateLimitingSegmentEntry 20 }

affirmedServicesContentHttpProxyServiceStatisticsSlotLevelAbrRateLimitingSegmentSegment-bypass-short-response OBJECT-TYPE
    SYNTAX      ConfdString
    MAX-ACCESS  read-only
    STATUS      current
    DESCRIPTION "Total ABR video segment bypass because of short response"
    ::= { affirmedServicesContentHttpProxyServiceStatisticsSlotLevelAbrRateLimitingSegmentEntry 21 }

affirmedServicesContentHttpProxyServiceStatisticsSlotLevelAbrRateLimitingSegmentAggregation-bypass OBJECT-TYPE
    SYNTAX      ConfdString
    MAX-ACCESS  read-only
    STATUS      current
    DESCRIPTION "Total ABR video segment with aggregation bypass"
    ::= { affirmedServicesContentHttpProxyServiceStatisticsSlotLevelAbrRateLimitingSegmentEntry 22 }

affirmedServicesContentHttpProxyServiceStatisticsSlotLevelBufferBufferTable OBJECT-TYPE
    SYNTAX      SEQUENCE OF AffirmedServicesContentHttpProxyServiceStatisticsSlotLevelBufferBufferEntry
    MAX-ACCESS  not-accessible
    STATUS      deprecated
    DESCRIPTION ""
    ::= { affirmedServicesContentHttpProxyServiceStatisticsSlotLevelBuffer 1 }

affirmedServicesContentHttpProxyServiceStatisticsSlotLevelBufferBufferEntry OBJECT-TYPE
    SYNTAX      AffirmedServicesContentHttpProxyServiceStatisticsSlotLevelBufferBufferEntry
    MAX-ACCESS  not-accessible
    STATUS      deprecated
    DESCRIPTION ""
    INDEX { affirmedServicesContentHttpProxyServiceStatisticsSlotLevelBufferBufferChassis, affirmedServicesContentHttpProxyServiceStatisticsSlotLevelBufferBufferSlot }
        ::= { affirmedServicesContentHttpProxyServiceStatisticsSlotLevelBufferBufferTable 1 }

AffirmedServicesContentHttpProxyServiceStatisticsSlotLevelBufferBufferEntry ::=
    SEQUENCE {
        affirmedServicesContentHttpProxyServiceStatisticsSlotLevelBufferBufferChassis Unsigned32,
        affirmedServicesContentHttpProxyServiceStatisticsSlotLevelBufferBufferSlot INTEGER,
        affirmedServicesContentHttpProxyServiceStatisticsSlotLevelBufferBufferPbuf-allocated ConfdString,
        affirmedServicesContentHttpProxyServiceStatisticsSlotLevelBufferBufferPbuf-5min-peak ConfdString,
        affirmedServicesContentHttpProxyServiceStatisticsSlotLevelBufferBufferPbuf-total ConfdString,
        affirmedServicesContentHttpProxyServiceStatisticsSlotLevelBufferBufferBuffer-4k-allocated ConfdString,
        affirmedServicesContentHttpProxyServiceStatisticsSlotLevelBufferBufferBuffer-4k-5min-peak ConfdString,
        affirmedServicesContentHttpProxyServiceStatisticsSlotLevelBufferBufferBuffer-4k-total ConfdString,
        affirmedServicesContentHttpProxyServiceStatisticsSlotLevelBufferBufferBuffer-8k-allocated ConfdString,
        affirmedServicesContentHttpProxyServiceStatisticsSlotLevelBufferBufferBuffer-8k-5min-peak ConfdString,
        affirmedServicesContentHttpProxyServiceStatisticsSlotLevelBufferBufferBuffer-8k-total ConfdString,
        affirmedServicesContentHttpProxyServiceStatisticsSlotLevelBufferBufferBuffer-64k-allocated ConfdString,
        affirmedServicesContentHttpProxyServiceStatisticsSlotLevelBufferBufferBuffer-64k-5min-peak ConfdString,
        affirmedServicesContentHttpProxyServiceStatisticsSlotLevelBufferBufferBuffer-64k-total ConfdString,
        affirmedServicesContentHttpProxyServiceStatisticsSlotLevelBufferBufferBuffer-128k-allocated ConfdString,
        affirmedServicesContentHttpProxyServiceStatisticsSlotLevelBufferBufferBuffer-128k-5min-peak ConfdString,
        affirmedServicesContentHttpProxyServiceStatisticsSlotLevelBufferBufferBuffer-128k-total ConfdString,
        affirmedServicesContentHttpProxyServiceStatisticsSlotLevelBufferBufferBuffer-256k-allocated ConfdString,
        affirmedServicesContentHttpProxyServiceStatisticsSlotLevelBufferBufferBuffer-256k-5min-peak ConfdString,
        affirmedServicesContentHttpProxyServiceStatisticsSlotLevelBufferBufferBuffer-256k-total ConfdString,
        affirmedServicesContentHttpProxyServiceStatisticsSlotLevelBufferBufferBuffer-512k-allocated ConfdString,
        affirmedServicesContentHttpProxyServiceStatisticsSlotLevelBufferBufferBuffer-512k-5min-peak ConfdString,
        affirmedServicesContentHttpProxyServiceStatisticsSlotLevelBufferBufferBuffer-512k-total ConfdString
    }

affirmedServicesContentHttpProxyServiceStatisticsSlotLevelBufferBufferChassis OBJECT-TYPE
    SYNTAX      Unsigned32
    MAX-ACCESS  not-accessible
    STATUS      current
    DESCRIPTION "chassis ID"
    ::= { affirmedServicesContentHttpProxyServiceStatisticsSlotLevelBufferBufferEntry 1 }

affirmedServicesContentHttpProxyServiceStatisticsSlotLevelBufferBufferSlot OBJECT-TYPE
    SYNTAX      INTEGER {a1(1),a2(2),a3(3),a4(4),a5(5),a6(6),a7(7),a8(8),a9(9),a10(10),a11(11),a12(12),a13(13),a14(14),a15(15),a16(16),a17(17),a18(18),a19(19),a20(20),a21(21),a22(22),a23(23),a24(24),a25(25),a26(26),a27(27),a28(28),a29(29),a30(30),a31(31),a32(32),a33(33),a34(34),a35(35),a36(36),a37(37),a38(38),a39(39),a40(40),a41(41),a42(42),a43(43),a44(44),a45(45),a46(46),a47(47),a48(48),a49(49),a50(50),a51(51),a52(52),a53(53),a54(54),a55(55),a56(56),a57(57),a58(58),a59(59),a60(60),a61(61),a62(62),a63(63),a64(64),a65(65),a66(66),a67(67),a68(68),a69(69),a70(70),a71(71),a72(72),a73(73),a74(74),a75(75),a76(76),a77(77),a78(78),a79(79),a80(80),a81(81),a82(82),a83(83),a84(84),a85(85),a86(86),a87(87),a88(88),a89(89),a90(90),a91(91),a92(92),a93(93),a94(94),a95(95),a96(96),a97(97),a98(98),a99(99),a100(100),a101(101),a102(102),a103(103),a104(104),a105(105),a106(106),a107(107),a108(108),a109(109),a110(110),a111(111),a112(112),a113(113),a114(114),a115(115),a116(116),a117(117),a118(118),a119(119),a120(120),a121(121),a122(122),a123(123),a124(124),a125(125),a126(126),a127(127),a128(128)}
    MAX-ACCESS  not-accessible
    STATUS      current
    DESCRIPTION "slot number"
    ::= { affirmedServicesContentHttpProxyServiceStatisticsSlotLevelBufferBufferEntry 2 }

affirmedServicesContentHttpProxyServiceStatisticsSlotLevelBufferBufferPbuf-allocated OBJECT-TYPE
    SYNTAX      ConfdString
    MAX-ACCESS  read-only
    STATUS      current
    DESCRIPTION "Number of packet buffers currently allocated"
    ::= { affirmedServicesContentHttpProxyServiceStatisticsSlotLevelBufferBufferEntry 3 }

affirmedServicesContentHttpProxyServiceStatisticsSlotLevelBufferBufferPbuf-5min-peak OBJECT-TYPE
    SYNTAX      ConfdString
    MAX-ACCESS  read-only
    STATUS      current
    DESCRIPTION "Max number of packet buffers allocated in last 5 minutes"
    ::= { affirmedServicesContentHttpProxyServiceStatisticsSlotLevelBufferBufferEntry 4 }

affirmedServicesContentHttpProxyServiceStatisticsSlotLevelBufferBufferPbuf-total OBJECT-TYPE
    SYNTAX      ConfdString
    MAX-ACCESS  read-only
    STATUS      current
    DESCRIPTION "Total packet buffers in the pool"
    ::= { affirmedServicesContentHttpProxyServiceStatisticsSlotLevelBufferBufferEntry 5 }

affirmedServicesContentHttpProxyServiceStatisticsSlotLevelBufferBufferBuffer-4k-allocated OBJECT-TYPE
    SYNTAX      ConfdString
    MAX-ACCESS  read-only
    STATUS      current
    DESCRIPTION "Number of 4K buffers currently allocated"
    ::= { affirmedServicesContentHttpProxyServiceStatisticsSlotLevelBufferBufferEntry 6 }

affirmedServicesContentHttpProxyServiceStatisticsSlotLevelBufferBufferBuffer-4k-5min-peak OBJECT-TYPE
    SYNTAX      ConfdString
    MAX-ACCESS  read-only
    STATUS      current
    DESCRIPTION "Max number of 4K buffers allocated in last 5 minutes"
    ::= { affirmedServicesContentHttpProxyServiceStatisticsSlotLevelBufferBufferEntry 7 }

affirmedServicesContentHttpProxyServiceStatisticsSlotLevelBufferBufferBuffer-4k-total OBJECT-TYPE
    SYNTAX      ConfdString
    MAX-ACCESS  read-only
    STATUS      current
    DESCRIPTION "Total 4K buffers in the pool"
    ::= { affirmedServicesContentHttpProxyServiceStatisticsSlotLevelBufferBufferEntry 8 }

affirmedServicesContentHttpProxyServiceStatisticsSlotLevelBufferBufferBuffer-8k-allocated OBJECT-TYPE
    SYNTAX      ConfdString
    MAX-ACCESS  read-only
    STATUS      current
    DESCRIPTION "Number of 8K buffers currently allocated"
    ::= { affirmedServicesContentHttpProxyServiceStatisticsSlotLevelBufferBufferEntry 9 }

affirmedServicesContentHttpProxyServiceStatisticsSlotLevelBufferBufferBuffer-8k-5min-peak OBJECT-TYPE
    SYNTAX      ConfdString
    MAX-ACCESS  read-only
    STATUS      current
    DESCRIPTION "Max number of 8K buffers allocated in last 5 minutes"
    ::= { affirmedServicesContentHttpProxyServiceStatisticsSlotLevelBufferBufferEntry 10 }

affirmedServicesContentHttpProxyServiceStatisticsSlotLevelBufferBufferBuffer-8k-total OBJECT-TYPE
    SYNTAX      ConfdString
    MAX-ACCESS  read-only
    STATUS      current
    DESCRIPTION "Total 8K buffers in the pool"
    ::= { affirmedServicesContentHttpProxyServiceStatisticsSlotLevelBufferBufferEntry 11 }

affirmedServicesContentHttpProxyServiceStatisticsSlotLevelBufferBufferBuffer-64k-allocated OBJECT-TYPE
    SYNTAX      ConfdString
    MAX-ACCESS  read-only
    STATUS      current
    DESCRIPTION "Number of 64K buffers currently allocated"
    ::= { affirmedServicesContentHttpProxyServiceStatisticsSlotLevelBufferBufferEntry 12 }

affirmedServicesContentHttpProxyServiceStatisticsSlotLevelBufferBufferBuffer-64k-5min-peak OBJECT-TYPE
    SYNTAX      ConfdString
    MAX-ACCESS  read-only
    STATUS      current
    DESCRIPTION "Max number of 64K buffers allocated in last 5 minutes"
    ::= { affirmedServicesContentHttpProxyServiceStatisticsSlotLevelBufferBufferEntry 13 }

affirmedServicesContentHttpProxyServiceStatisticsSlotLevelBufferBufferBuffer-64k-total OBJECT-TYPE
    SYNTAX      ConfdString
    MAX-ACCESS  read-only
    STATUS      current
    DESCRIPTION "Total 64K buffers in the pool"
    ::= { affirmedServicesContentHttpProxyServiceStatisticsSlotLevelBufferBufferEntry 14 }

affirmedServicesContentHttpProxyServiceStatisticsSlotLevelBufferBufferBuffer-128k-allocated OBJECT-TYPE
    SYNTAX      ConfdString
    MAX-ACCESS  read-only
    STATUS      current
    DESCRIPTION "Number of 128K buffers currently allocated"
    ::= { affirmedServicesContentHttpProxyServiceStatisticsSlotLevelBufferBufferEntry 15 }

affirmedServicesContentHttpProxyServiceStatisticsSlotLevelBufferBufferBuffer-128k-5min-peak OBJECT-TYPE
    SYNTAX      ConfdString
    MAX-ACCESS  read-only
    STATUS      current
    DESCRIPTION "Max number of 128K buffers allocated in last 5 minutes"
    ::= { affirmedServicesContentHttpProxyServiceStatisticsSlotLevelBufferBufferEntry 16 }

affirmedServicesContentHttpProxyServiceStatisticsSlotLevelBufferBufferBuffer-128k-total OBJECT-TYPE
    SYNTAX      ConfdString
    MAX-ACCESS  read-only
    STATUS      current
    DESCRIPTION "Total 128K buffers in the pool"
    ::= { affirmedServicesContentHttpProxyServiceStatisticsSlotLevelBufferBufferEntry 17 }

affirmedServicesContentHttpProxyServiceStatisticsSlotLevelBufferBufferBuffer-256k-allocated OBJECT-TYPE
    SYNTAX      ConfdString
    MAX-ACCESS  read-only
    STATUS      current
    DESCRIPTION "Number of 256K buffers currently allocated"
    ::= { affirmedServicesContentHttpProxyServiceStatisticsSlotLevelBufferBufferEntry 18 }

affirmedServicesContentHttpProxyServiceStatisticsSlotLevelBufferBufferBuffer-256k-5min-peak OBJECT-TYPE
    SYNTAX      ConfdString
    MAX-ACCESS  read-only
    STATUS      current
    DESCRIPTION "Max number of 256K buffers allocated in last 5 minutes"
    ::= { affirmedServicesContentHttpProxyServiceStatisticsSlotLevelBufferBufferEntry 19 }

affirmedServicesContentHttpProxyServiceStatisticsSlotLevelBufferBufferBuffer-256k-total OBJECT-TYPE
    SYNTAX      ConfdString
    MAX-ACCESS  read-only
    STATUS      current
    DESCRIPTION "Total 256K buffers in the pool"
    ::= { affirmedServicesContentHttpProxyServiceStatisticsSlotLevelBufferBufferEntry 20 }

affirmedServicesContentHttpProxyServiceStatisticsSlotLevelBufferBufferBuffer-512k-allocated OBJECT-TYPE
    SYNTAX      ConfdString
    MAX-ACCESS  read-only
    STATUS      current
    DESCRIPTION "Number of 512K buffers currently allocated"
    ::= { affirmedServicesContentHttpProxyServiceStatisticsSlotLevelBufferBufferEntry 21 }

affirmedServicesContentHttpProxyServiceStatisticsSlotLevelBufferBufferBuffer-512k-5min-peak OBJECT-TYPE
    SYNTAX      ConfdString
    MAX-ACCESS  read-only
    STATUS      current
    DESCRIPTION "Max number of 512K buffers allocated in last 5 minutes"
    ::= { affirmedServicesContentHttpProxyServiceStatisticsSlotLevelBufferBufferEntry 22 }

affirmedServicesContentHttpProxyServiceStatisticsSlotLevelBufferBufferBuffer-512k-total OBJECT-TYPE
    SYNTAX      ConfdString
    MAX-ACCESS  read-only
    STATUS      current
    DESCRIPTION "Total 512K buffers in the pool"
    ::= { affirmedServicesContentHttpProxyServiceStatisticsSlotLevelBufferBufferEntry 23 }

affirmedServicesContentHttpProxyServiceStatisticsSlotLevelBufferSummaryTable OBJECT-TYPE
    SYNTAX      SEQUENCE OF AffirmedServicesContentHttpProxyServiceStatisticsSlotLevelBufferSummaryEntry
    MAX-ACCESS  not-accessible
    STATUS      deprecated
    DESCRIPTION ""
    ::= { affirmedServicesContentHttpProxyServiceStatisticsSlotLevelBuffer 2 }

affirmedServicesContentHttpProxyServiceStatisticsSlotLevelBufferSummaryEntry OBJECT-TYPE
    SYNTAX      AffirmedServicesContentHttpProxyServiceStatisticsSlotLevelBufferSummaryEntry
    MAX-ACCESS  not-accessible
    STATUS      deprecated
    DESCRIPTION ""
    INDEX { affirmedServicesContentHttpProxyServiceStatisticsSlotLevelBufferSummaryChassis, affirmedServicesContentHttpProxyServiceStatisticsSlotLevelBufferSummarySlot }
        ::= { affirmedServicesContentHttpProxyServiceStatisticsSlotLevelBufferSummaryTable 1 }

AffirmedServicesContentHttpProxyServiceStatisticsSlotLevelBufferSummaryEntry ::=
    SEQUENCE {
        affirmedServicesContentHttpProxyServiceStatisticsSlotLevelBufferSummaryChassis Unsigned32,
        affirmedServicesContentHttpProxyServiceStatisticsSlotLevelBufferSummarySlot INTEGER,
        affirmedServicesContentHttpProxyServiceStatisticsSlotLevelBufferSummaryPbuf-allocated ConfdString,
        affirmedServicesContentHttpProxyServiceStatisticsSlotLevelBufferSummaryPbuf-5min-peak ConfdString,
        affirmedServicesContentHttpProxyServiceStatisticsSlotLevelBufferSummaryPbuf-total ConfdString,
        affirmedServicesContentHttpProxyServiceStatisticsSlotLevelBufferSummaryBuffer-4k-allocated ConfdString,
        affirmedServicesContentHttpProxyServiceStatisticsSlotLevelBufferSummaryBuffer-4k-5min-peak ConfdString,
        affirmedServicesContentHttpProxyServiceStatisticsSlotLevelBufferSummaryBuffer-4k-total ConfdString,
        affirmedServicesContentHttpProxyServiceStatisticsSlotLevelBufferSummaryBuffer-8k-allocated ConfdString,
        affirmedServicesContentHttpProxyServiceStatisticsSlotLevelBufferSummaryBuffer-8k-5min-peak ConfdString,
        affirmedServicesContentHttpProxyServiceStatisticsSlotLevelBufferSummaryBuffer-8k-total ConfdString,
        affirmedServicesContentHttpProxyServiceStatisticsSlotLevelBufferSummaryBuffer-64k-allocated ConfdString,
        affirmedServicesContentHttpProxyServiceStatisticsSlotLevelBufferSummaryBuffer-64k-5min-peak ConfdString,
        affirmedServicesContentHttpProxyServiceStatisticsSlotLevelBufferSummaryBuffer-64k-total ConfdString,
        affirmedServicesContentHttpProxyServiceStatisticsSlotLevelBufferSummaryBuffer-128k-allocated ConfdString,
        affirmedServicesContentHttpProxyServiceStatisticsSlotLevelBufferSummaryBuffer-128k-5min-peak ConfdString,
        affirmedServicesContentHttpProxyServiceStatisticsSlotLevelBufferSummaryBuffer-128k-total ConfdString,
        affirmedServicesContentHttpProxyServiceStatisticsSlotLevelBufferSummaryBuffer-256k-allocated ConfdString,
        affirmedServicesContentHttpProxyServiceStatisticsSlotLevelBufferSummaryBuffer-256k-5min-peak ConfdString,
        affirmedServicesContentHttpProxyServiceStatisticsSlotLevelBufferSummaryBuffer-256k-total ConfdString,
        affirmedServicesContentHttpProxyServiceStatisticsSlotLevelBufferSummaryBuffer-512k-allocated ConfdString,
        affirmedServicesContentHttpProxyServiceStatisticsSlotLevelBufferSummaryBuffer-512k-5min-peak ConfdString,
        affirmedServicesContentHttpProxyServiceStatisticsSlotLevelBufferSummaryBuffer-512k-total ConfdString,
        affirmedServicesContentHttpProxyServiceStatisticsSlotLevelBufferSummaryBuffer-2k-allocated ConfdString,
        affirmedServicesContentHttpProxyServiceStatisticsSlotLevelBufferSummaryBuffer-2k-5min-peak ConfdString,
        affirmedServicesContentHttpProxyServiceStatisticsSlotLevelBufferSummaryBuffer-2k-total ConfdString
    }

affirmedServicesContentHttpProxyServiceStatisticsSlotLevelBufferSummaryChassis OBJECT-TYPE
    SYNTAX      Unsigned32
    MAX-ACCESS  not-accessible
    STATUS      current
    DESCRIPTION "chassis ID"
    ::= { affirmedServicesContentHttpProxyServiceStatisticsSlotLevelBufferSummaryEntry 1 }

affirmedServicesContentHttpProxyServiceStatisticsSlotLevelBufferSummarySlot OBJECT-TYPE
    SYNTAX      INTEGER {a1(1),a2(2),a3(3),a4(4),a5(5),a6(6),a7(7),a8(8),a9(9),a10(10),a11(11),a12(12),a13(13),a14(14),a15(15),a16(16),a17(17),a18(18),a19(19),a20(20),a21(21),a22(22),a23(23),a24(24),a25(25),a26(26),a27(27),a28(28),a29(29),a30(30),a31(31),a32(32),a33(33),a34(34),a35(35),a36(36),a37(37),a38(38),a39(39),a40(40),a41(41),a42(42),a43(43),a44(44),a45(45),a46(46),a47(47),a48(48),a49(49),a50(50),a51(51),a52(52),a53(53),a54(54),a55(55),a56(56),a57(57),a58(58),a59(59),a60(60),a61(61),a62(62),a63(63),a64(64),a65(65),a66(66),a67(67),a68(68),a69(69),a70(70),a71(71),a72(72),a73(73),a74(74),a75(75),a76(76),a77(77),a78(78),a79(79),a80(80),a81(81),a82(82),a83(83),a84(84),a85(85),a86(86),a87(87),a88(88),a89(89),a90(90),a91(91),a92(92),a93(93),a94(94),a95(95),a96(96),a97(97),a98(98),a99(99),a100(100),a101(101),a102(102),a103(103),a104(104),a105(105),a106(106),a107(107),a108(108),a109(109),a110(110),a111(111),a112(112),a113(113),a114(114),a115(115),a116(116),a117(117),a118(118),a119(119),a120(120),a121(121),a122(122),a123(123),a124(124),a125(125),a126(126),a127(127),a128(128)}
    MAX-ACCESS  not-accessible
    STATUS      current
    DESCRIPTION "slot number"
    ::= { affirmedServicesContentHttpProxyServiceStatisticsSlotLevelBufferSummaryEntry 2 }

affirmedServicesContentHttpProxyServiceStatisticsSlotLevelBufferSummaryPbuf-allocated OBJECT-TYPE
    SYNTAX      ConfdString
    MAX-ACCESS  read-only
    STATUS      current
    DESCRIPTION "Number of packet buffers currently allocated"
    ::= { affirmedServicesContentHttpProxyServiceStatisticsSlotLevelBufferSummaryEntry 3 }

affirmedServicesContentHttpProxyServiceStatisticsSlotLevelBufferSummaryPbuf-5min-peak OBJECT-TYPE
    SYNTAX      ConfdString
    MAX-ACCESS  read-only
    STATUS      current
    DESCRIPTION "Max number of packet buffers allocated in last 5 minutes"
    ::= { affirmedServicesContentHttpProxyServiceStatisticsSlotLevelBufferSummaryEntry 4 }

affirmedServicesContentHttpProxyServiceStatisticsSlotLevelBufferSummaryPbuf-total OBJECT-TYPE
    SYNTAX      ConfdString
    MAX-ACCESS  read-only
    STATUS      current
    DESCRIPTION "Total packet buffers in the pool"
    ::= { affirmedServicesContentHttpProxyServiceStatisticsSlotLevelBufferSummaryEntry 5 }

affirmedServicesContentHttpProxyServiceStatisticsSlotLevelBufferSummaryBuffer-4k-allocated OBJECT-TYPE
    SYNTAX      ConfdString
    MAX-ACCESS  read-only
    STATUS      current
    DESCRIPTION "Number of 4K buffers currently allocated"
    ::= { affirmedServicesContentHttpProxyServiceStatisticsSlotLevelBufferSummaryEntry 6 }

affirmedServicesContentHttpProxyServiceStatisticsSlotLevelBufferSummaryBuffer-4k-5min-peak OBJECT-TYPE
    SYNTAX      ConfdString
    MAX-ACCESS  read-only
    STATUS      current
    DESCRIPTION "Max number of 4K buffers allocated in last 5 minutes"
    ::= { affirmedServicesContentHttpProxyServiceStatisticsSlotLevelBufferSummaryEntry 7 }

affirmedServicesContentHttpProxyServiceStatisticsSlotLevelBufferSummaryBuffer-4k-total OBJECT-TYPE
    SYNTAX      ConfdString
    MAX-ACCESS  read-only
    STATUS      current
    DESCRIPTION "Total 4K buffers in the pool"
    ::= { affirmedServicesContentHttpProxyServiceStatisticsSlotLevelBufferSummaryEntry 8 }

affirmedServicesContentHttpProxyServiceStatisticsSlotLevelBufferSummaryBuffer-8k-allocated OBJECT-TYPE
    SYNTAX      ConfdString
    MAX-ACCESS  read-only
    STATUS      current
    DESCRIPTION "Number of 8K buffers currently allocated"
    ::= { affirmedServicesContentHttpProxyServiceStatisticsSlotLevelBufferSummaryEntry 9 }

affirmedServicesContentHttpProxyServiceStatisticsSlotLevelBufferSummaryBuffer-8k-5min-peak OBJECT-TYPE
    SYNTAX      ConfdString
    MAX-ACCESS  read-only
    STATUS      current
    DESCRIPTION "Max number of 8K buffers allocated in last 5 minutes"
    ::= { affirmedServicesContentHttpProxyServiceStatisticsSlotLevelBufferSummaryEntry 10 }

affirmedServicesContentHttpProxyServiceStatisticsSlotLevelBufferSummaryBuffer-8k-total OBJECT-TYPE
    SYNTAX      ConfdString
    MAX-ACCESS  read-only
    STATUS      current
    DESCRIPTION "Total 8K buffers in the pool"
    ::= { affirmedServicesContentHttpProxyServiceStatisticsSlotLevelBufferSummaryEntry 11 }

affirmedServicesContentHttpProxyServiceStatisticsSlotLevelBufferSummaryBuffer-64k-allocated OBJECT-TYPE
    SYNTAX      ConfdString
    MAX-ACCESS  read-only
    STATUS      current
    DESCRIPTION "Number of 64K buffers currently allocated"
    ::= { affirmedServicesContentHttpProxyServiceStatisticsSlotLevelBufferSummaryEntry 12 }

affirmedServicesContentHttpProxyServiceStatisticsSlotLevelBufferSummaryBuffer-64k-5min-peak OBJECT-TYPE
    SYNTAX      ConfdString
    MAX-ACCESS  read-only
    STATUS      current
    DESCRIPTION "Max number of 64K buffers allocated in last 5 minutes"
    ::= { affirmedServicesContentHttpProxyServiceStatisticsSlotLevelBufferSummaryEntry 13 }

affirmedServicesContentHttpProxyServiceStatisticsSlotLevelBufferSummaryBuffer-64k-total OBJECT-TYPE
    SYNTAX      ConfdString
    MAX-ACCESS  read-only
    STATUS      current
    DESCRIPTION "Total 64K buffers in the pool"
    ::= { affirmedServicesContentHttpProxyServiceStatisticsSlotLevelBufferSummaryEntry 14 }

affirmedServicesContentHttpProxyServiceStatisticsSlotLevelBufferSummaryBuffer-128k-allocated OBJECT-TYPE
    SYNTAX      ConfdString
    MAX-ACCESS  read-only
    STATUS      current
    DESCRIPTION "Number of 128K buffers currently allocated"
    ::= { affirmedServicesContentHttpProxyServiceStatisticsSlotLevelBufferSummaryEntry 15 }

affirmedServicesContentHttpProxyServiceStatisticsSlotLevelBufferSummaryBuffer-128k-5min-peak OBJECT-TYPE
    SYNTAX      ConfdString
    MAX-ACCESS  read-only
    STATUS      current
    DESCRIPTION "Max number of 128K buffers allocated in last 5 minutes"
    ::= { affirmedServicesContentHttpProxyServiceStatisticsSlotLevelBufferSummaryEntry 16 }

affirmedServicesContentHttpProxyServiceStatisticsSlotLevelBufferSummaryBuffer-128k-total OBJECT-TYPE
    SYNTAX      ConfdString
    MAX-ACCESS  read-only
    STATUS      current
    DESCRIPTION "Total 128K buffers in the pool"
    ::= { affirmedServicesContentHttpProxyServiceStatisticsSlotLevelBufferSummaryEntry 17 }

affirmedServicesContentHttpProxyServiceStatisticsSlotLevelBufferSummaryBuffer-256k-allocated OBJECT-TYPE
    SYNTAX      ConfdString
    MAX-ACCESS  read-only
    STATUS      current
    DESCRIPTION "Number of 256K buffers currently allocated"
    ::= { affirmedServicesContentHttpProxyServiceStatisticsSlotLevelBufferSummaryEntry 18 }

affirmedServicesContentHttpProxyServiceStatisticsSlotLevelBufferSummaryBuffer-256k-5min-peak OBJECT-TYPE
    SYNTAX      ConfdString
    MAX-ACCESS  read-only
    STATUS      current
    DESCRIPTION "Max number of 256K buffers allocated in last 5 minutes"
    ::= { affirmedServicesContentHttpProxyServiceStatisticsSlotLevelBufferSummaryEntry 19 }

affirmedServicesContentHttpProxyServiceStatisticsSlotLevelBufferSummaryBuffer-256k-total OBJECT-TYPE
    SYNTAX      ConfdString
    MAX-ACCESS  read-only
    STATUS      current
    DESCRIPTION "Total 256K buffers in the pool"
    ::= { affirmedServicesContentHttpProxyServiceStatisticsSlotLevelBufferSummaryEntry 20 }

affirmedServicesContentHttpProxyServiceStatisticsSlotLevelBufferSummaryBuffer-512k-allocated OBJECT-TYPE
    SYNTAX      ConfdString
    MAX-ACCESS  read-only
    STATUS      current
    DESCRIPTION "Number of 512K buffers currently allocated"
    ::= { affirmedServicesContentHttpProxyServiceStatisticsSlotLevelBufferSummaryEntry 21 }

affirmedServicesContentHttpProxyServiceStatisticsSlotLevelBufferSummaryBuffer-512k-5min-peak OBJECT-TYPE
    SYNTAX      ConfdString
    MAX-ACCESS  read-only
    STATUS      current
    DESCRIPTION "Max number of 512K buffers allocated in last 5 minutes"
    ::= { affirmedServicesContentHttpProxyServiceStatisticsSlotLevelBufferSummaryEntry 22 }

affirmedServicesContentHttpProxyServiceStatisticsSlotLevelBufferSummaryBuffer-512k-total OBJECT-TYPE
    SYNTAX      ConfdString
    MAX-ACCESS  read-only
    STATUS      current
    DESCRIPTION "Total 512K buffers in the pool"
    ::= { affirmedServicesContentHttpProxyServiceStatisticsSlotLevelBufferSummaryEntry 23 }

affirmedServicesContentHttpProxyServiceStatisticsSlotLevelBufferSummaryBuffer-2k-allocated OBJECT-TYPE
    SYNTAX      ConfdString
    MAX-ACCESS  read-only
    STATUS      current
    DESCRIPTION "Number of 2K buffers currently allocated"
    ::= { affirmedServicesContentHttpProxyServiceStatisticsSlotLevelBufferSummaryEntry 24 }

affirmedServicesContentHttpProxyServiceStatisticsSlotLevelBufferSummaryBuffer-2k-5min-peak OBJECT-TYPE
    SYNTAX      ConfdString
    MAX-ACCESS  read-only
    STATUS      current
    DESCRIPTION "Max number of 2K buffers allocated in last 5 minutes"
    ::= { affirmedServicesContentHttpProxyServiceStatisticsSlotLevelBufferSummaryEntry 25 }

affirmedServicesContentHttpProxyServiceStatisticsSlotLevelBufferSummaryBuffer-2k-total OBJECT-TYPE
    SYNTAX      ConfdString
    MAX-ACCESS  read-only
    STATUS      current
    DESCRIPTION "Total 2K buffers in the pool"
    ::= { affirmedServicesContentHttpProxyServiceStatisticsSlotLevelBufferSummaryEntry 26 }

affirmedServicesContentHttpProxyServiceStatisticsSlotLevelTcpMeasurementMeasurementTable OBJECT-TYPE
    SYNTAX      SEQUENCE OF AffirmedServicesContentHttpProxyServiceStatisticsSlotLevelTcpMeasurementMeasurementEntry
    MAX-ACCESS  not-accessible
    STATUS      current
    DESCRIPTION ""
    ::= { affirmedServicesContentHttpProxyServiceStatisticsSlotLevelTcpMeasurement 1 }

affirmedServicesContentHttpProxyServiceStatisticsSlotLevelTcpMeasurementMeasurementEntry OBJECT-TYPE
    SYNTAX      AffirmedServicesContentHttpProxyServiceStatisticsSlotLevelTcpMeasurementMeasurementEntry
    MAX-ACCESS  not-accessible
    STATUS      current
    DESCRIPTION ""
    INDEX { affirmedServicesContentHttpProxyServiceStatisticsSlotLevelTcpMeasurementMeasurementChassis, affirmedServicesContentHttpProxyServiceStatisticsSlotLevelTcpMeasurementMeasurementSlot }
        ::= { affirmedServicesContentHttpProxyServiceStatisticsSlotLevelTcpMeasurementMeasurementTable 1 }

AffirmedServicesContentHttpProxyServiceStatisticsSlotLevelTcpMeasurementMeasurementEntry ::=
    SEQUENCE {
        affirmedServicesContentHttpProxyServiceStatisticsSlotLevelTcpMeasurementMeasurementChassis Unsigned32,
        affirmedServicesContentHttpProxyServiceStatisticsSlotLevelTcpMeasurementMeasurementSlot INTEGER,
        affirmedServicesContentHttpProxyServiceStatisticsSlotLevelTcpMeasurementMeasurementMinrtt ConfdString,
        affirmedServicesContentHttpProxyServiceStatisticsSlotLevelTcpMeasurementMeasurementAvgrtt ConfdString,
        affirmedServicesContentHttpProxyServiceStatisticsSlotLevelTcpMeasurementMeasurementMaxrtt ConfdString,
        affirmedServicesContentHttpProxyServiceStatisticsSlotLevelTcpMeasurementMeasurementMinmssdl ConfdString,
        affirmedServicesContentHttpProxyServiceStatisticsSlotLevelTcpMeasurementMeasurementAvgmssdl ConfdString,
        affirmedServicesContentHttpProxyServiceStatisticsSlotLevelTcpMeasurementMeasurementMaxmssdl ConfdString,
        affirmedServicesContentHttpProxyServiceStatisticsSlotLevelTcpMeasurementMeasurementMincwnddl ConfdString,
        affirmedServicesContentHttpProxyServiceStatisticsSlotLevelTcpMeasurementMeasurementAvgcwnddl ConfdString,
        affirmedServicesContentHttpProxyServiceStatisticsSlotLevelTcpMeasurementMeasurementMaxcwnddl ConfdString,
        affirmedServicesContentHttpProxyServiceStatisticsSlotLevelTcpMeasurementMeasurementMinthroughputdl ConfdString,
        affirmedServicesContentHttpProxyServiceStatisticsSlotLevelTcpMeasurementMeasurementAvgthroughputdl ConfdString,
        affirmedServicesContentHttpProxyServiceStatisticsSlotLevelTcpMeasurementMeasurementMaxthroughputdl ConfdString,
        affirmedServicesContentHttpProxyServiceStatisticsSlotLevelTcpMeasurementMeasurementNumtotalsegmentslostdl ConfdString,
        affirmedServicesContentHttpProxyServiceStatisticsSlotLevelTcpMeasurementMeasurementNumtotalsegmentsretransdl ConfdString,
        affirmedServicesContentHttpProxyServiceStatisticsSlotLevelTcpMeasurementMeasurementNumtotalestimatedsegmentsdl ConfdString
    }

affirmedServicesContentHttpProxyServiceStatisticsSlotLevelTcpMeasurementMeasurementChassis OBJECT-TYPE
    SYNTAX      Unsigned32
    MAX-ACCESS  not-accessible
    STATUS      current
    DESCRIPTION "chassis ID"
    ::= { affirmedServicesContentHttpProxyServiceStatisticsSlotLevelTcpMeasurementMeasurementEntry 1 }

affirmedServicesContentHttpProxyServiceStatisticsSlotLevelTcpMeasurementMeasurementSlot OBJECT-TYPE
    SYNTAX      INTEGER {a1(1),a2(2),a3(3),a4(4),a5(5),a6(6),a7(7),a8(8),a9(9),a10(10),a11(11),a12(12),a13(13),a14(14),a15(15),a16(16),a17(17),a18(18),a19(19),a20(20),a21(21),a22(22),a23(23),a24(24),a25(25),a26(26),a27(27),a28(28),a29(29),a30(30),a31(31),a32(32),a33(33),a34(34),a35(35),a36(36),a37(37),a38(38),a39(39),a40(40),a41(41),a42(42),a43(43),a44(44),a45(45),a46(46),a47(47),a48(48),a49(49),a50(50),a51(51),a52(52),a53(53),a54(54),a55(55),a56(56),a57(57),a58(58),a59(59),a60(60),a61(61),a62(62),a63(63),a64(64),a65(65),a66(66),a67(67),a68(68),a69(69),a70(70),a71(71),a72(72),a73(73),a74(74),a75(75),a76(76),a77(77),a78(78),a79(79),a80(80),a81(81),a82(82),a83(83),a84(84),a85(85),a86(86),a87(87),a88(88),a89(89),a90(90),a91(91),a92(92),a93(93),a94(94),a95(95),a96(96),a97(97),a98(98),a99(99),a100(100),a101(101),a102(102),a103(103),a104(104),a105(105),a106(106),a107(107),a108(108),a109(109),a110(110),a111(111),a112(112),a113(113),a114(114),a115(115),a116(116),a117(117),a118(118),a119(119),a120(120),a121(121),a122(122),a123(123),a124(124),a125(125),a126(126),a127(127),a128(128)}
    MAX-ACCESS  not-accessible
    STATUS      current
    DESCRIPTION "slot number"
    ::= { affirmedServicesContentHttpProxyServiceStatisticsSlotLevelTcpMeasurementMeasurementEntry 2 }

affirmedServicesContentHttpProxyServiceStatisticsSlotLevelTcpMeasurementMeasurementMinrtt OBJECT-TYPE
    SYNTAX      ConfdString
    MAX-ACCESS  read-only
    STATUS      current
    DESCRIPTION "Minimum RTT(us)"
    ::= { affirmedServicesContentHttpProxyServiceStatisticsSlotLevelTcpMeasurementMeasurementEntry 3 }

affirmedServicesContentHttpProxyServiceStatisticsSlotLevelTcpMeasurementMeasurementAvgrtt OBJECT-TYPE
    SYNTAX      ConfdString
    MAX-ACCESS  read-only
    STATUS      current
    DESCRIPTION "Average RTT(us) in Last 1 min"
    ::= { affirmedServicesContentHttpProxyServiceStatisticsSlotLevelTcpMeasurementMeasurementEntry 4 }

affirmedServicesContentHttpProxyServiceStatisticsSlotLevelTcpMeasurementMeasurementMaxrtt OBJECT-TYPE
    SYNTAX      ConfdString
    MAX-ACCESS  read-only
    STATUS      current
    DESCRIPTION "Maximum RTT(us)"
    ::= { affirmedServicesContentHttpProxyServiceStatisticsSlotLevelTcpMeasurementMeasurementEntry 5 }

affirmedServicesContentHttpProxyServiceStatisticsSlotLevelTcpMeasurementMeasurementMinmssdl OBJECT-TYPE
    SYNTAX      ConfdString
    MAX-ACCESS  read-only
    STATUS      current
    DESCRIPTION "Minimum Downstream MSS"
    ::= { affirmedServicesContentHttpProxyServiceStatisticsSlotLevelTcpMeasurementMeasurementEntry 6 }

affirmedServicesContentHttpProxyServiceStatisticsSlotLevelTcpMeasurementMeasurementAvgmssdl OBJECT-TYPE
    SYNTAX      ConfdString
    MAX-ACCESS  read-only
    STATUS      current
    DESCRIPTION "Average Downstream MSS"
    ::= { affirmedServicesContentHttpProxyServiceStatisticsSlotLevelTcpMeasurementMeasurementEntry 7 }

affirmedServicesContentHttpProxyServiceStatisticsSlotLevelTcpMeasurementMeasurementMaxmssdl OBJECT-TYPE
    SYNTAX      ConfdString
    MAX-ACCESS  read-only
    STATUS      current
    DESCRIPTION "Maximum Downstream MSS"
    ::= { affirmedServicesContentHttpProxyServiceStatisticsSlotLevelTcpMeasurementMeasurementEntry 8 }

affirmedServicesContentHttpProxyServiceStatisticsSlotLevelTcpMeasurementMeasurementMincwnddl OBJECT-TYPE
    SYNTAX      ConfdString
    MAX-ACCESS  read-only
    STATUS      current
    DESCRIPTION "Minimum Downstream CWND"
    ::= { affirmedServicesContentHttpProxyServiceStatisticsSlotLevelTcpMeasurementMeasurementEntry 9 }

affirmedServicesContentHttpProxyServiceStatisticsSlotLevelTcpMeasurementMeasurementAvgcwnddl OBJECT-TYPE
    SYNTAX      ConfdString
    MAX-ACCESS  read-only
    STATUS      current
    DESCRIPTION "Average Downstream CWND"
    ::= { affirmedServicesContentHttpProxyServiceStatisticsSlotLevelTcpMeasurementMeasurementEntry 10 }

affirmedServicesContentHttpProxyServiceStatisticsSlotLevelTcpMeasurementMeasurementMaxcwnddl OBJECT-TYPE
    SYNTAX      ConfdString
    MAX-ACCESS  read-only
    STATUS      current
    DESCRIPTION "Maximum Downstream CWND"
    ::= { affirmedServicesContentHttpProxyServiceStatisticsSlotLevelTcpMeasurementMeasurementEntry 11 }

affirmedServicesContentHttpProxyServiceStatisticsSlotLevelTcpMeasurementMeasurementMinthroughputdl OBJECT-TYPE
    SYNTAX      ConfdString
    MAX-ACCESS  read-only
    STATUS      current
    DESCRIPTION "Minimum Available Downstream Throughput of all Active Proxy Connections (Kbps)"
    ::= { affirmedServicesContentHttpProxyServiceStatisticsSlotLevelTcpMeasurementMeasurementEntry 12 }

affirmedServicesContentHttpProxyServiceStatisticsSlotLevelTcpMeasurementMeasurementAvgthroughputdl OBJECT-TYPE
    SYNTAX      ConfdString
    MAX-ACCESS  read-only
    STATUS      current
    DESCRIPTION "Average Available Downstream Throughput of all Active Proxy Connections (Kbps)"
    ::= { affirmedServicesContentHttpProxyServiceStatisticsSlotLevelTcpMeasurementMeasurementEntry 13 }

affirmedServicesContentHttpProxyServiceStatisticsSlotLevelTcpMeasurementMeasurementMaxthroughputdl OBJECT-TYPE
    SYNTAX      ConfdString
    MAX-ACCESS  read-only
    STATUS      current
    DESCRIPTION "Maximum Available Downstream Throughput of all Active Proxy Connections (Kbps)"
    ::= { affirmedServicesContentHttpProxyServiceStatisticsSlotLevelTcpMeasurementMeasurementEntry 14 }

affirmedServicesContentHttpProxyServiceStatisticsSlotLevelTcpMeasurementMeasurementNumtotalsegmentslostdl OBJECT-TYPE
    SYNTAX      ConfdString
    MAX-ACCESS  read-only
    STATUS      deprecated
    DESCRIPTION "Downstream Segments Lost"
    ::= { affirmedServicesContentHttpProxyServiceStatisticsSlotLevelTcpMeasurementMeasurementEntry 15 }

affirmedServicesContentHttpProxyServiceStatisticsSlotLevelTcpMeasurementMeasurementNumtotalsegmentsretransdl OBJECT-TYPE
    SYNTAX      ConfdString
    MAX-ACCESS  read-only
    STATUS      deprecated
    DESCRIPTION "Downstream Segments Retransmitted"
    ::= { affirmedServicesContentHttpProxyServiceStatisticsSlotLevelTcpMeasurementMeasurementEntry 16 }

affirmedServicesContentHttpProxyServiceStatisticsSlotLevelTcpMeasurementMeasurementNumtotalestimatedsegmentsdl OBJECT-TYPE
    SYNTAX      ConfdString
    MAX-ACCESS  read-only
    STATUS      deprecated
    DESCRIPTION "Estimated Downstream Segments"
    ::= { affirmedServicesContentHttpProxyServiceStatisticsSlotLevelTcpMeasurementMeasurementEntry 17 }

affirmedServicesContentHttpProxyServiceStatisticsSlotLevelTcpMeasurementsSummaryTable OBJECT-TYPE
    SYNTAX      SEQUENCE OF AffirmedServicesContentHttpProxyServiceStatisticsSlotLevelTcpMeasurementsSummaryEntry
    MAX-ACCESS  not-accessible
    STATUS      current
    DESCRIPTION ""
    ::= { affirmedServicesContentHttpProxyServiceStatisticsSlotLevelTcpMeasurements 1 }

affirmedServicesContentHttpProxyServiceStatisticsSlotLevelTcpMeasurementsSummaryEntry OBJECT-TYPE
    SYNTAX      AffirmedServicesContentHttpProxyServiceStatisticsSlotLevelTcpMeasurementsSummaryEntry
    MAX-ACCESS  not-accessible
    STATUS      current
    DESCRIPTION ""
    INDEX { affirmedServicesContentHttpProxyServiceStatisticsSlotLevelTcpMeasurementsSummaryChassis, affirmedServicesContentHttpProxyServiceStatisticsSlotLevelTcpMeasurementsSummarySlot }
        ::= { affirmedServicesContentHttpProxyServiceStatisticsSlotLevelTcpMeasurementsSummaryTable 1 }

AffirmedServicesContentHttpProxyServiceStatisticsSlotLevelTcpMeasurementsSummaryEntry ::=
    SEQUENCE {
        affirmedServicesContentHttpProxyServiceStatisticsSlotLevelTcpMeasurementsSummaryChassis Unsigned32,
        affirmedServicesContentHttpProxyServiceStatisticsSlotLevelTcpMeasurementsSummarySlot INTEGER,
        affirmedServicesContentHttpProxyServiceStatisticsSlotLevelTcpMeasurementsSummaryMinrtt ConfdString,
        affirmedServicesContentHttpProxyServiceStatisticsSlotLevelTcpMeasurementsSummaryAvgrtt ConfdString,
        affirmedServicesContentHttpProxyServiceStatisticsSlotLevelTcpMeasurementsSummaryMaxrtt ConfdString,
        affirmedServicesContentHttpProxyServiceStatisticsSlotLevelTcpMeasurementsSummaryMinmssdl ConfdString,
        affirmedServicesContentHttpProxyServiceStatisticsSlotLevelTcpMeasurementsSummaryAvgmssdl ConfdString,
        affirmedServicesContentHttpProxyServiceStatisticsSlotLevelTcpMeasurementsSummaryMaxmssdl ConfdString,
        affirmedServicesContentHttpProxyServiceStatisticsSlotLevelTcpMeasurementsSummaryMincwnddl ConfdString,
        affirmedServicesContentHttpProxyServiceStatisticsSlotLevelTcpMeasurementsSummaryAvgcwnddl ConfdString,
        affirmedServicesContentHttpProxyServiceStatisticsSlotLevelTcpMeasurementsSummaryMaxcwnddl ConfdString,
        affirmedServicesContentHttpProxyServiceStatisticsSlotLevelTcpMeasurementsSummaryMinthroughputdl ConfdString,
        affirmedServicesContentHttpProxyServiceStatisticsSlotLevelTcpMeasurementsSummaryAvgthroughputdl ConfdString,
        affirmedServicesContentHttpProxyServiceStatisticsSlotLevelTcpMeasurementsSummaryMaxthroughputdl ConfdString,
        affirmedServicesContentHttpProxyServiceStatisticsSlotLevelTcpMeasurementsSummaryNumtotalsegmentslostdl ConfdString,
        affirmedServicesContentHttpProxyServiceStatisticsSlotLevelTcpMeasurementsSummaryNumtotalsegmentsretransdl ConfdString,
        affirmedServicesContentHttpProxyServiceStatisticsSlotLevelTcpMeasurementsSummaryNumtotalestimatedsegmentsdl ConfdString,
        affirmedServicesContentHttpProxyServiceStatisticsSlotLevelTcpMeasurementsSummaryNumtotalsegslostdl ConfdString,
        affirmedServicesContentHttpProxyServiceStatisticsSlotLevelTcpMeasurementsSummaryNumtotalsegsretransdl ConfdString,
        affirmedServicesContentHttpProxyServiceStatisticsSlotLevelTcpMeasurementsSummaryNumtotalestimatedsegsdl ConfdString,
        affirmedServicesContentHttpProxyServiceStatisticsSlotLevelTcpMeasurementsSummaryNumsessionscongestionmild ConfdString,
        affirmedServicesContentHttpProxyServiceStatisticsSlotLevelTcpMeasurementsSummaryNumsessionscongestionmoderate ConfdString,
        affirmedServicesContentHttpProxyServiceStatisticsSlotLevelTcpMeasurementsSummaryNumsessionscongestionsevere ConfdString,
        affirmedServicesContentHttpProxyServiceStatisticsSlotLevelTcpMeasurementsSummaryNumsessionstotal ConfdString
    }

affirmedServicesContentHttpProxyServiceStatisticsSlotLevelTcpMeasurementsSummaryChassis OBJECT-TYPE
    SYNTAX      Unsigned32
    MAX-ACCESS  not-accessible
    STATUS      current
    DESCRIPTION "chassis ID"
    ::= { affirmedServicesContentHttpProxyServiceStatisticsSlotLevelTcpMeasurementsSummaryEntry 1 }

affirmedServicesContentHttpProxyServiceStatisticsSlotLevelTcpMeasurementsSummarySlot OBJECT-TYPE
    SYNTAX      INTEGER {a1(1),a2(2),a3(3),a4(4),a5(5),a6(6),a7(7),a8(8),a9(9),a10(10),a11(11),a12(12),a13(13),a14(14),a15(15),a16(16),a17(17),a18(18),a19(19),a20(20),a21(21),a22(22),a23(23),a24(24),a25(25),a26(26),a27(27),a28(28),a29(29),a30(30),a31(31),a32(32),a33(33),a34(34),a35(35),a36(36),a37(37),a38(38),a39(39),a40(40),a41(41),a42(42),a43(43),a44(44),a45(45),a46(46),a47(47),a48(48),a49(49),a50(50),a51(51),a52(52),a53(53),a54(54),a55(55),a56(56),a57(57),a58(58),a59(59),a60(60),a61(61),a62(62),a63(63),a64(64),a65(65),a66(66),a67(67),a68(68),a69(69),a70(70),a71(71),a72(72),a73(73),a74(74),a75(75),a76(76),a77(77),a78(78),a79(79),a80(80),a81(81),a82(82),a83(83),a84(84),a85(85),a86(86),a87(87),a88(88),a89(89),a90(90),a91(91),a92(92),a93(93),a94(94),a95(95),a96(96),a97(97),a98(98),a99(99),a100(100),a101(101),a102(102),a103(103),a104(104),a105(105),a106(106),a107(107),a108(108),a109(109),a110(110),a111(111),a112(112),a113(113),a114(114),a115(115),a116(116),a117(117),a118(118),a119(119),a120(120),a121(121),a122(122),a123(123),a124(124),a125(125),a126(126),a127(127),a128(128)}
    MAX-ACCESS  not-accessible
    STATUS      current
    DESCRIPTION "slot number"
    ::= { affirmedServicesContentHttpProxyServiceStatisticsSlotLevelTcpMeasurementsSummaryEntry 2 }

affirmedServicesContentHttpProxyServiceStatisticsSlotLevelTcpMeasurementsSummaryMinrtt OBJECT-TYPE
    SYNTAX      ConfdString
    MAX-ACCESS  read-only
    STATUS      current
    DESCRIPTION "Minimum RTT(us)"
    ::= { affirmedServicesContentHttpProxyServiceStatisticsSlotLevelTcpMeasurementsSummaryEntry 3 }

affirmedServicesContentHttpProxyServiceStatisticsSlotLevelTcpMeasurementsSummaryAvgrtt OBJECT-TYPE
    SYNTAX      ConfdString
    MAX-ACCESS  read-only
    STATUS      current
    DESCRIPTION "Average RTT(us) in Last 1 min"
    ::= { affirmedServicesContentHttpProxyServiceStatisticsSlotLevelTcpMeasurementsSummaryEntry 4 }

affirmedServicesContentHttpProxyServiceStatisticsSlotLevelTcpMeasurementsSummaryMaxrtt OBJECT-TYPE
    SYNTAX      ConfdString
    MAX-ACCESS  read-only
    STATUS      current
    DESCRIPTION "Maximum RTT(us)"
    ::= { affirmedServicesContentHttpProxyServiceStatisticsSlotLevelTcpMeasurementsSummaryEntry 5 }

affirmedServicesContentHttpProxyServiceStatisticsSlotLevelTcpMeasurementsSummaryMinmssdl OBJECT-TYPE
    SYNTAX      ConfdString
    MAX-ACCESS  read-only
    STATUS      current
    DESCRIPTION "Minimum Downstream MSS"
    ::= { affirmedServicesContentHttpProxyServiceStatisticsSlotLevelTcpMeasurementsSummaryEntry 6 }

affirmedServicesContentHttpProxyServiceStatisticsSlotLevelTcpMeasurementsSummaryAvgmssdl OBJECT-TYPE
    SYNTAX      ConfdString
    MAX-ACCESS  read-only
    STATUS      current
    DESCRIPTION "Average Downstream MSS"
    ::= { affirmedServicesContentHttpProxyServiceStatisticsSlotLevelTcpMeasurementsSummaryEntry 7 }

affirmedServicesContentHttpProxyServiceStatisticsSlotLevelTcpMeasurementsSummaryMaxmssdl OBJECT-TYPE
    SYNTAX      ConfdString
    MAX-ACCESS  read-only
    STATUS      current
    DESCRIPTION "Maximum Downstream MSS"
    ::= { affirmedServicesContentHttpProxyServiceStatisticsSlotLevelTcpMeasurementsSummaryEntry 8 }

affirmedServicesContentHttpProxyServiceStatisticsSlotLevelTcpMeasurementsSummaryMincwnddl OBJECT-TYPE
    SYNTAX      ConfdString
    MAX-ACCESS  read-only
    STATUS      current
    DESCRIPTION "Minimum Downstream CWND"
    ::= { affirmedServicesContentHttpProxyServiceStatisticsSlotLevelTcpMeasurementsSummaryEntry 9 }

affirmedServicesContentHttpProxyServiceStatisticsSlotLevelTcpMeasurementsSummaryAvgcwnddl OBJECT-TYPE
    SYNTAX      ConfdString
    MAX-ACCESS  read-only
    STATUS      current
    DESCRIPTION "Average Downstream CWND"
    ::= { affirmedServicesContentHttpProxyServiceStatisticsSlotLevelTcpMeasurementsSummaryEntry 10 }

affirmedServicesContentHttpProxyServiceStatisticsSlotLevelTcpMeasurementsSummaryMaxcwnddl OBJECT-TYPE
    SYNTAX      ConfdString
    MAX-ACCESS  read-only
    STATUS      current
    DESCRIPTION "Maximum Downstream CWND"
    ::= { affirmedServicesContentHttpProxyServiceStatisticsSlotLevelTcpMeasurementsSummaryEntry 11 }

affirmedServicesContentHttpProxyServiceStatisticsSlotLevelTcpMeasurementsSummaryMinthroughputdl OBJECT-TYPE
    SYNTAX      ConfdString
    MAX-ACCESS  read-only
    STATUS      current
    DESCRIPTION "Minimum Available Downstream Throughput of all Active Proxy Connections (Kbps)"
    ::= { affirmedServicesContentHttpProxyServiceStatisticsSlotLevelTcpMeasurementsSummaryEntry 12 }

affirmedServicesContentHttpProxyServiceStatisticsSlotLevelTcpMeasurementsSummaryAvgthroughputdl OBJECT-TYPE
    SYNTAX      ConfdString
    MAX-ACCESS  read-only
    STATUS      current
    DESCRIPTION "Average Available Downstream Throughput of all Active Proxy Connections (Kbps)"
    ::= { affirmedServicesContentHttpProxyServiceStatisticsSlotLevelTcpMeasurementsSummaryEntry 13 }

affirmedServicesContentHttpProxyServiceStatisticsSlotLevelTcpMeasurementsSummaryMaxthroughputdl OBJECT-TYPE
    SYNTAX      ConfdString
    MAX-ACCESS  read-only
    STATUS      current
    DESCRIPTION "Maximum Available Downstream Throughput of all Active Proxy Connections (Kbps)"
    ::= { affirmedServicesContentHttpProxyServiceStatisticsSlotLevelTcpMeasurementsSummaryEntry 14 }

affirmedServicesContentHttpProxyServiceStatisticsSlotLevelTcpMeasurementsSummaryNumtotalsegmentslostdl OBJECT-TYPE
    SYNTAX      ConfdString
    MAX-ACCESS  read-only
    STATUS      deprecated
    DESCRIPTION "Downstream Segments Lost"
    ::= { affirmedServicesContentHttpProxyServiceStatisticsSlotLevelTcpMeasurementsSummaryEntry 15 }

affirmedServicesContentHttpProxyServiceStatisticsSlotLevelTcpMeasurementsSummaryNumtotalsegmentsretransdl OBJECT-TYPE
    SYNTAX      ConfdString
    MAX-ACCESS  read-only
    STATUS      deprecated
    DESCRIPTION "Downstream Segments Retransmitted"
    ::= { affirmedServicesContentHttpProxyServiceStatisticsSlotLevelTcpMeasurementsSummaryEntry 16 }

affirmedServicesContentHttpProxyServiceStatisticsSlotLevelTcpMeasurementsSummaryNumtotalestimatedsegmentsdl OBJECT-TYPE
    SYNTAX      ConfdString
    MAX-ACCESS  read-only
    STATUS      deprecated
    DESCRIPTION "Estimated Downstream Segments"
    ::= { affirmedServicesContentHttpProxyServiceStatisticsSlotLevelTcpMeasurementsSummaryEntry 17 }

affirmedServicesContentHttpProxyServiceStatisticsSlotLevelTcpMeasurementsSummaryNumtotalsegslostdl OBJECT-TYPE
    SYNTAX      ConfdString
    MAX-ACCESS  read-only
    STATUS      deprecated
    DESCRIPTION "Downstream Segments Lost"
    ::= { affirmedServicesContentHttpProxyServiceStatisticsSlotLevelTcpMeasurementsSummaryEntry 18 }

affirmedServicesContentHttpProxyServiceStatisticsSlotLevelTcpMeasurementsSummaryNumtotalsegsretransdl OBJECT-TYPE
    SYNTAX      ConfdString
    MAX-ACCESS  read-only
    STATUS      current
    DESCRIPTION "Downstream Segments Retransmitted"
    ::= { affirmedServicesContentHttpProxyServiceStatisticsSlotLevelTcpMeasurementsSummaryEntry 19 }

affirmedServicesContentHttpProxyServiceStatisticsSlotLevelTcpMeasurementsSummaryNumtotalestimatedsegsdl OBJECT-TYPE
    SYNTAX      ConfdString
    MAX-ACCESS  read-only
    STATUS      current
    DESCRIPTION "Estimated Downstream Segments"
    ::= { affirmedServicesContentHttpProxyServiceStatisticsSlotLevelTcpMeasurementsSummaryEntry 20 }

affirmedServicesContentHttpProxyServiceStatisticsSlotLevelTcpMeasurementsSummaryNumsessionscongestionmild OBJECT-TYPE
    SYNTAX      ConfdString
    MAX-ACCESS  read-only
    STATUS      current
    DESCRIPTION "Congested Sessions - Mild"
    ::= { affirmedServicesContentHttpProxyServiceStatisticsSlotLevelTcpMeasurementsSummaryEntry 21 }

affirmedServicesContentHttpProxyServiceStatisticsSlotLevelTcpMeasurementsSummaryNumsessionscongestionmoderate OBJECT-TYPE
    SYNTAX      ConfdString
    MAX-ACCESS  read-only
    STATUS      current
    DESCRIPTION "Congested Sessions - Moderate"
    ::= { affirmedServicesContentHttpProxyServiceStatisticsSlotLevelTcpMeasurementsSummaryEntry 22 }

affirmedServicesContentHttpProxyServiceStatisticsSlotLevelTcpMeasurementsSummaryNumsessionscongestionsevere OBJECT-TYPE
    SYNTAX      ConfdString
    MAX-ACCESS  read-only
    STATUS      current
    DESCRIPTION "Congested Sessions - Severe"
    ::= { affirmedServicesContentHttpProxyServiceStatisticsSlotLevelTcpMeasurementsSummaryEntry 23 }

affirmedServicesContentHttpProxyServiceStatisticsSlotLevelTcpMeasurementsSummaryNumsessionstotal OBJECT-TYPE
    SYNTAX      ConfdString
    MAX-ACCESS  read-only
    STATUS      current
    DESCRIPTION "Current Sessions"
    ::= { affirmedServicesContentHttpProxyServiceStatisticsSlotLevelTcpMeasurementsSummaryEntry 24 }

affirmedServicesContentHttpProxyServiceStatisticsSlotLevelTcpMeasurementsServer-sideTable OBJECT-TYPE
    SYNTAX      SEQUENCE OF AffirmedServicesContentHttpProxyServiceStatisticsSlotLevelTcpMeasurementsServer-sideEntry
    MAX-ACCESS  not-accessible
    STATUS      current
    DESCRIPTION ""
    ::= { affirmedServicesContentHttpProxyServiceStatisticsSlotLevelTcpMeasurements 2 }

affirmedServicesContentHttpProxyServiceStatisticsSlotLevelTcpMeasurementsServer-sideEntry OBJECT-TYPE
    SYNTAX      AffirmedServicesContentHttpProxyServiceStatisticsSlotLevelTcpMeasurementsServer-sideEntry
    MAX-ACCESS  not-accessible
    STATUS      current
    DESCRIPTION ""
    INDEX { affirmedServicesContentHttpProxyServiceStatisticsSlotLevelTcpMeasurementsServer-sideChassis, affirmedServicesContentHttpProxyServiceStatisticsSlotLevelTcpMeasurementsServer-sideSlot }
        ::= { affirmedServicesContentHttpProxyServiceStatisticsSlotLevelTcpMeasurementsServer-sideTable 1 }

AffirmedServicesContentHttpProxyServiceStatisticsSlotLevelTcpMeasurementsServer-sideEntry ::=
    SEQUENCE {
        affirmedServicesContentHttpProxyServiceStatisticsSlotLevelTcpMeasurementsServer-sideChassis Unsigned32,
        affirmedServicesContentHttpProxyServiceStatisticsSlotLevelTcpMeasurementsServer-sideSlot INTEGER,
        affirmedServicesContentHttpProxyServiceStatisticsSlotLevelTcpMeasurementsServer-sideMinrtt ConfdString,
        affirmedServicesContentHttpProxyServiceStatisticsSlotLevelTcpMeasurementsServer-sideAvgrtt ConfdString,
        affirmedServicesContentHttpProxyServiceStatisticsSlotLevelTcpMeasurementsServer-sideMaxrtt ConfdString,
        affirmedServicesContentHttpProxyServiceStatisticsSlotLevelTcpMeasurementsServer-sideNumretransin ConfdString,
        affirmedServicesContentHttpProxyServiceStatisticsSlotLevelTcpMeasurementsServer-sideNumoooin ConfdString
    }

affirmedServicesContentHttpProxyServiceStatisticsSlotLevelTcpMeasurementsServer-sideChassis OBJECT-TYPE
    SYNTAX      Unsigned32
    MAX-ACCESS  not-accessible
    STATUS      current
    DESCRIPTION "chassis ID"
    ::= { affirmedServicesContentHttpProxyServiceStatisticsSlotLevelTcpMeasurementsServer-sideEntry 1 }

affirmedServicesContentHttpProxyServiceStatisticsSlotLevelTcpMeasurementsServer-sideSlot OBJECT-TYPE
    SYNTAX      INTEGER {a1(1),a2(2),a3(3),a4(4),a5(5),a6(6),a7(7),a8(8),a9(9),a10(10),a11(11),a12(12),a13(13),a14(14),a15(15),a16(16),a17(17),a18(18),a19(19),a20(20),a21(21),a22(22),a23(23),a24(24),a25(25),a26(26),a27(27),a28(28),a29(29),a30(30),a31(31),a32(32),a33(33),a34(34),a35(35),a36(36),a37(37),a38(38),a39(39),a40(40),a41(41),a42(42),a43(43),a44(44),a45(45),a46(46),a47(47),a48(48),a49(49),a50(50),a51(51),a52(52),a53(53),a54(54),a55(55),a56(56),a57(57),a58(58),a59(59),a60(60),a61(61),a62(62),a63(63),a64(64),a65(65),a66(66),a67(67),a68(68),a69(69),a70(70),a71(71),a72(72),a73(73),a74(74),a75(75),a76(76),a77(77),a78(78),a79(79),a80(80),a81(81),a82(82),a83(83),a84(84),a85(85),a86(86),a87(87),a88(88),a89(89),a90(90),a91(91),a92(92),a93(93),a94(94),a95(95),a96(96),a97(97),a98(98),a99(99),a100(100),a101(101),a102(102),a103(103),a104(104),a105(105),a106(106),a107(107),a108(108),a109(109),a110(110),a111(111),a112(112),a113(113),a114(114),a115(115),a116(116),a117(117),a118(118),a119(119),a120(120),a121(121),a122(122),a123(123),a124(124),a125(125),a126(126),a127(127),a128(128)}
    MAX-ACCESS  not-accessible
    STATUS      current
    DESCRIPTION "slot number"
    ::= { affirmedServicesContentHttpProxyServiceStatisticsSlotLevelTcpMeasurementsServer-sideEntry 2 }

affirmedServicesContentHttpProxyServiceStatisticsSlotLevelTcpMeasurementsServer-sideMinrtt OBJECT-TYPE
    SYNTAX      ConfdString
    MAX-ACCESS  read-only
    STATUS      current
    DESCRIPTION "Minimum RTT(us)"
    ::= { affirmedServicesContentHttpProxyServiceStatisticsSlotLevelTcpMeasurementsServer-sideEntry 3 }

affirmedServicesContentHttpProxyServiceStatisticsSlotLevelTcpMeasurementsServer-sideAvgrtt OBJECT-TYPE
    SYNTAX      ConfdString
    MAX-ACCESS  read-only
    STATUS      current
    DESCRIPTION "Average RTT(us) in Last 1 min"
    ::= { affirmedServicesContentHttpProxyServiceStatisticsSlotLevelTcpMeasurementsServer-sideEntry 4 }

affirmedServicesContentHttpProxyServiceStatisticsSlotLevelTcpMeasurementsServer-sideMaxrtt OBJECT-TYPE
    SYNTAX      ConfdString
    MAX-ACCESS  read-only
    STATUS      current
    DESCRIPTION "Maximum RTT(us)"
    ::= { affirmedServicesContentHttpProxyServiceStatisticsSlotLevelTcpMeasurementsServer-sideEntry 5 }

affirmedServicesContentHttpProxyServiceStatisticsSlotLevelTcpMeasurementsServer-sideNumretransin OBJECT-TYPE
    SYNTAX      ConfdString
    MAX-ACCESS  read-only
    STATUS      current
    DESCRIPTION "Number of Packets Retransmitted"
    ::= { affirmedServicesContentHttpProxyServiceStatisticsSlotLevelTcpMeasurementsServer-sideEntry 6 }

affirmedServicesContentHttpProxyServiceStatisticsSlotLevelTcpMeasurementsServer-sideNumoooin OBJECT-TYPE
    SYNTAX      ConfdString
    MAX-ACCESS  read-only
    STATUS      current
    DESCRIPTION "Number of Packets Out of Order"
    ::= { affirmedServicesContentHttpProxyServiceStatisticsSlotLevelTcpMeasurementsServer-sideEntry 7 }

affirmedServicesContentHttpProxyServiceStatisticsSlotLevelUdpProxySummaryTable OBJECT-TYPE
    SYNTAX      SEQUENCE OF AffirmedServicesContentHttpProxyServiceStatisticsSlotLevelUdpProxySummaryEntry
    MAX-ACCESS  not-accessible
    STATUS      current
    DESCRIPTION ""
    ::= { affirmedServicesContentHttpProxyServiceStatisticsSlotLevelUdpProxy 1 }

affirmedServicesContentHttpProxyServiceStatisticsSlotLevelUdpProxySummaryEntry OBJECT-TYPE
    SYNTAX      AffirmedServicesContentHttpProxyServiceStatisticsSlotLevelUdpProxySummaryEntry
    MAX-ACCESS  not-accessible
    STATUS      current
    DESCRIPTION ""
    INDEX { affirmedServicesContentHttpProxyServiceStatisticsSlotLevelUdpProxySummaryChassis, affirmedServicesContentHttpProxyServiceStatisticsSlotLevelUdpProxySummarySlot }
        ::= { affirmedServicesContentHttpProxyServiceStatisticsSlotLevelUdpProxySummaryTable 1 }

AffirmedServicesContentHttpProxyServiceStatisticsSlotLevelUdpProxySummaryEntry ::=
    SEQUENCE {
        affirmedServicesContentHttpProxyServiceStatisticsSlotLevelUdpProxySummaryChassis Unsigned32,
        affirmedServicesContentHttpProxyServiceStatisticsSlotLevelUdpProxySummarySlot INTEGER,
        affirmedServicesContentHttpProxyServiceStatisticsSlotLevelUdpProxySummaryNumudpproxysummaryattempts ConfdString,
        affirmedServicesContentHttpProxyServiceStatisticsSlotLevelUdpProxySummaryNumudpproxysummarysuccesses ConfdString,
        affirmedServicesContentHttpProxyServiceStatisticsSlotLevelUdpProxySummaryNumudpproxysummaryaborts ConfdString,
        affirmedServicesContentHttpProxyServiceStatisticsSlotLevelUdpProxySummaryNumudpproxysummaryfailures ConfdString,
        affirmedServicesContentHttpProxyServiceStatisticsSlotLevelUdpProxySummaryNumudpproxydurationminseconds ConfdString,
        affirmedServicesContentHttpProxyServiceStatisticsSlotLevelUdpProxySummaryNumudpproxydurationmaxseconds ConfdString,
        affirmedServicesContentHttpProxyServiceStatisticsSlotLevelUdpProxySummaryNumudpproxydurationavgseconds ConfdString
    }

affirmedServicesContentHttpProxyServiceStatisticsSlotLevelUdpProxySummaryChassis OBJECT-TYPE
    SYNTAX      Unsigned32
    MAX-ACCESS  not-accessible
    STATUS      current
    DESCRIPTION "chassis ID"
    ::= { affirmedServicesContentHttpProxyServiceStatisticsSlotLevelUdpProxySummaryEntry 1 }

affirmedServicesContentHttpProxyServiceStatisticsSlotLevelUdpProxySummarySlot OBJECT-TYPE
    SYNTAX      INTEGER {a1(1),a2(2),a3(3),a4(4),a5(5),a6(6),a7(7),a8(8),a9(9),a10(10),a11(11),a12(12),a13(13),a14(14),a15(15),a16(16),a17(17),a18(18),a19(19),a20(20),a21(21),a22(22),a23(23),a24(24),a25(25),a26(26),a27(27),a28(28),a29(29),a30(30),a31(31),a32(32),a33(33),a34(34),a35(35),a36(36),a37(37),a38(38),a39(39),a40(40),a41(41),a42(42),a43(43),a44(44),a45(45),a46(46),a47(47),a48(48),a49(49),a50(50),a51(51),a52(52),a53(53),a54(54),a55(55),a56(56),a57(57),a58(58),a59(59),a60(60),a61(61),a62(62),a63(63),a64(64),a65(65),a66(66),a67(67),a68(68),a69(69),a70(70),a71(71),a72(72),a73(73),a74(74),a75(75),a76(76),a77(77),a78(78),a79(79),a80(80),a81(81),a82(82),a83(83),a84(84),a85(85),a86(86),a87(87),a88(88),a89(89),a90(90),a91(91),a92(92),a93(93),a94(94),a95(95),a96(96),a97(97),a98(98),a99(99),a100(100),a101(101),a102(102),a103(103),a104(104),a105(105),a106(106),a107(107),a108(108),a109(109),a110(110),a111(111),a112(112),a113(113),a114(114),a115(115),a116(116),a117(117),a118(118),a119(119),a120(120),a121(121),a122(122),a123(123),a124(124),a125(125),a126(126),a127(127),a128(128)}
    MAX-ACCESS  not-accessible
    STATUS      current
    DESCRIPTION "slot number"
    ::= { affirmedServicesContentHttpProxyServiceStatisticsSlotLevelUdpProxySummaryEntry 2 }

affirmedServicesContentHttpProxyServiceStatisticsSlotLevelUdpProxySummaryNumudpproxysummaryattempts OBJECT-TYPE
    SYNTAX      ConfdString
    MAX-ACCESS  read-only
    STATUS      current
    DESCRIPTION "Number of UDP Proxy summary attempts"
    ::= { affirmedServicesContentHttpProxyServiceStatisticsSlotLevelUdpProxySummaryEntry 3 }

affirmedServicesContentHttpProxyServiceStatisticsSlotLevelUdpProxySummaryNumudpproxysummarysuccesses OBJECT-TYPE
    SYNTAX      ConfdString
    MAX-ACCESS  read-only
    STATUS      current
    DESCRIPTION "Number of UDP Proxy summary successes"
    ::= { affirmedServicesContentHttpProxyServiceStatisticsSlotLevelUdpProxySummaryEntry 4 }

affirmedServicesContentHttpProxyServiceStatisticsSlotLevelUdpProxySummaryNumudpproxysummaryaborts OBJECT-TYPE
    SYNTAX      ConfdString
    MAX-ACCESS  read-only
    STATUS      current
    DESCRIPTION "Number of UDP Proxy summary aborts"
    ::= { affirmedServicesContentHttpProxyServiceStatisticsSlotLevelUdpProxySummaryEntry 5 }

affirmedServicesContentHttpProxyServiceStatisticsSlotLevelUdpProxySummaryNumudpproxysummaryfailures OBJECT-TYPE
    SYNTAX      ConfdString
    MAX-ACCESS  read-only
    STATUS      current
    DESCRIPTION "Number of UDP Proxy summary failures"
    ::= { affirmedServicesContentHttpProxyServiceStatisticsSlotLevelUdpProxySummaryEntry 6 }

affirmedServicesContentHttpProxyServiceStatisticsSlotLevelUdpProxySummaryNumudpproxydurationminseconds OBJECT-TYPE
    SYNTAX      ConfdString
    MAX-ACCESS  read-only
    STATUS      current
    DESCRIPTION "Number of Minimum UDP Proxy duration in milliseconds"
    ::= { affirmedServicesContentHttpProxyServiceStatisticsSlotLevelUdpProxySummaryEntry 7 }

affirmedServicesContentHttpProxyServiceStatisticsSlotLevelUdpProxySummaryNumudpproxydurationmaxseconds OBJECT-TYPE
    SYNTAX      ConfdString
    MAX-ACCESS  read-only
    STATUS      current
    DESCRIPTION "Number of Maximum UDP Proxy duration in milliseconds"
    ::= { affirmedServicesContentHttpProxyServiceStatisticsSlotLevelUdpProxySummaryEntry 8 }

affirmedServicesContentHttpProxyServiceStatisticsSlotLevelUdpProxySummaryNumudpproxydurationavgseconds OBJECT-TYPE
    SYNTAX      ConfdString
    MAX-ACCESS  read-only
    STATUS      current
    DESCRIPTION "Number of Average UDP Proxy duration in milliseconds"
    ::= { affirmedServicesContentHttpProxyServiceStatisticsSlotLevelUdpProxySummaryEntry 9 }

affirmedServicesContentHttpProxyServiceStatisticsSlotLevelUdpProxyDetailTable OBJECT-TYPE
    SYNTAX      SEQUENCE OF AffirmedServicesContentHttpProxyServiceStatisticsSlotLevelUdpProxyDetailEntry
    MAX-ACCESS  not-accessible
    STATUS      current
    DESCRIPTION ""
    ::= { affirmedServicesContentHttpProxyServiceStatisticsSlotLevelUdpProxy 2 }

affirmedServicesContentHttpProxyServiceStatisticsSlotLevelUdpProxyDetailEntry OBJECT-TYPE
    SYNTAX      AffirmedServicesContentHttpProxyServiceStatisticsSlotLevelUdpProxyDetailEntry
    MAX-ACCESS  not-accessible
    STATUS      current
    DESCRIPTION ""
    INDEX { affirmedServicesContentHttpProxyServiceStatisticsSlotLevelUdpProxyDetailChassis, affirmedServicesContentHttpProxyServiceStatisticsSlotLevelUdpProxyDetailSlot }
        ::= { affirmedServicesContentHttpProxyServiceStatisticsSlotLevelUdpProxyDetailTable 1 }

AffirmedServicesContentHttpProxyServiceStatisticsSlotLevelUdpProxyDetailEntry ::=
    SEQUENCE {
        affirmedServicesContentHttpProxyServiceStatisticsSlotLevelUdpProxyDetailChassis Unsigned32,
        affirmedServicesContentHttpProxyServiceStatisticsSlotLevelUdpProxyDetailSlot INTEGER,
        affirmedServicesContentHttpProxyServiceStatisticsSlotLevelUdpProxyDetailNumudpproxypolicyevaluated ConfdString,
        affirmedServicesContentHttpProxyServiceStatisticsSlotLevelUdpProxyDetailNumudpproxypolicymatched ConfdString,
        affirmedServicesContentHttpProxyServiceStatisticsSlotLevelUdpProxyDetailNumudpproxypolicyignored ConfdString,
        affirmedServicesContentHttpProxyServiceStatisticsSlotLevelUdpProxyDetailNumudpproxypolicynotavailable ConfdString,
        affirmedServicesContentHttpProxyServiceStatisticsSlotLevelUdpProxyDetailNumudpproxyprofileactionallowed ConfdString,
        affirmedServicesContentHttpProxyServiceStatisticsSlotLevelUdpProxyDetailNumudpproxyprofilesteeredtoip ConfdString,
        affirmedServicesContentHttpProxyServiceStatisticsSlotLevelUdpProxyDetailNumudpproxyprofilesteeredtohost ConfdString,
        affirmedServicesContentHttpProxyServiceStatisticsSlotLevelUdpProxyDetailNumudpproxypolicyreevaluated ConfdString,
        affirmedServicesContentHttpProxyServiceStatisticsSlotLevelUdpProxyDetailNumudpproxypolicyrematched ConfdString,
        affirmedServicesContentHttpProxyServiceStatisticsSlotLevelUdpProxyDetailNumudpproxypolicynotavailablereeval ConfdString
    }

affirmedServicesContentHttpProxyServiceStatisticsSlotLevelUdpProxyDetailChassis OBJECT-TYPE
    SYNTAX      Unsigned32
    MAX-ACCESS  not-accessible
    STATUS      current
    DESCRIPTION "chassis ID"
    ::= { affirmedServicesContentHttpProxyServiceStatisticsSlotLevelUdpProxyDetailEntry 1 }

affirmedServicesContentHttpProxyServiceStatisticsSlotLevelUdpProxyDetailSlot OBJECT-TYPE
    SYNTAX      INTEGER {a1(1),a2(2),a3(3),a4(4),a5(5),a6(6),a7(7),a8(8),a9(9),a10(10),a11(11),a12(12),a13(13),a14(14),a15(15),a16(16),a17(17),a18(18),a19(19),a20(20),a21(21),a22(22),a23(23),a24(24),a25(25),a26(26),a27(27),a28(28),a29(29),a30(30),a31(31),a32(32),a33(33),a34(34),a35(35),a36(36),a37(37),a38(38),a39(39),a40(40),a41(41),a42(42),a43(43),a44(44),a45(45),a46(46),a47(47),a48(48),a49(49),a50(50),a51(51),a52(52),a53(53),a54(54),a55(55),a56(56),a57(57),a58(58),a59(59),a60(60),a61(61),a62(62),a63(63),a64(64),a65(65),a66(66),a67(67),a68(68),a69(69),a70(70),a71(71),a72(72),a73(73),a74(74),a75(75),a76(76),a77(77),a78(78),a79(79),a80(80),a81(81),a82(82),a83(83),a84(84),a85(85),a86(86),a87(87),a88(88),a89(89),a90(90),a91(91),a92(92),a93(93),a94(94),a95(95),a96(96),a97(97),a98(98),a99(99),a100(100),a101(101),a102(102),a103(103),a104(104),a105(105),a106(106),a107(107),a108(108),a109(109),a110(110),a111(111),a112(112),a113(113),a114(114),a115(115),a116(116),a117(117),a118(118),a119(119),a120(120),a121(121),a122(122),a123(123),a124(124),a125(125),a126(126),a127(127),a128(128)}
    MAX-ACCESS  not-accessible
    STATUS      current
    DESCRIPTION "slot number"
    ::= { affirmedServicesContentHttpProxyServiceStatisticsSlotLevelUdpProxyDetailEntry 2 }

affirmedServicesContentHttpProxyServiceStatisticsSlotLevelUdpProxyDetailNumudpproxypolicyevaluated OBJECT-TYPE
    SYNTAX      ConfdString
    MAX-ACCESS  read-only
    STATUS      current
    DESCRIPTION "Number of UDP Proxy Policies evaluated"
    ::= { affirmedServicesContentHttpProxyServiceStatisticsSlotLevelUdpProxyDetailEntry 3 }

affirmedServicesContentHttpProxyServiceStatisticsSlotLevelUdpProxyDetailNumudpproxypolicymatched OBJECT-TYPE
    SYNTAX      ConfdString
    MAX-ACCESS  read-only
    STATUS      current
    DESCRIPTION "Number of UDP Proxy Policies Matched"
    ::= { affirmedServicesContentHttpProxyServiceStatisticsSlotLevelUdpProxyDetailEntry 4 }

affirmedServicesContentHttpProxyServiceStatisticsSlotLevelUdpProxyDetailNumudpproxypolicyignored OBJECT-TYPE
    SYNTAX      ConfdString
    MAX-ACCESS  read-only
    STATUS      current
    DESCRIPTION "Number of UDP Proxy Policies Ignored"
    ::= { affirmedServicesContentHttpProxyServiceStatisticsSlotLevelUdpProxyDetailEntry 5 }

affirmedServicesContentHttpProxyServiceStatisticsSlotLevelUdpProxyDetailNumudpproxypolicynotavailable OBJECT-TYPE
    SYNTAX      ConfdString
    MAX-ACCESS  read-only
    STATUS      current
    DESCRIPTION "Number of UDP Proxy Policies Not Available"
    ::= { affirmedServicesContentHttpProxyServiceStatisticsSlotLevelUdpProxyDetailEntry 6 }

affirmedServicesContentHttpProxyServiceStatisticsSlotLevelUdpProxyDetailNumudpproxyprofileactionallowed OBJECT-TYPE
    SYNTAX      ConfdString
    MAX-ACCESS  read-only
    STATUS      current
    DESCRIPTION "Number of Traffic Control Profile Action Allow Applied"
    ::= { affirmedServicesContentHttpProxyServiceStatisticsSlotLevelUdpProxyDetailEntry 7 }

affirmedServicesContentHttpProxyServiceStatisticsSlotLevelUdpProxyDetailNumudpproxyprofilesteeredtoip OBJECT-TYPE
    SYNTAX      ConfdString
    MAX-ACCESS  read-only
    STATUS      current
    DESCRIPTION "Number of tcp splicing profile steering-destination IP applied"
    ::= { affirmedServicesContentHttpProxyServiceStatisticsSlotLevelUdpProxyDetailEntry 8 }

affirmedServicesContentHttpProxyServiceStatisticsSlotLevelUdpProxyDetailNumudpproxyprofilesteeredtohost OBJECT-TYPE
    SYNTAX      ConfdString
    MAX-ACCESS  read-only
    STATUS      current
    DESCRIPTION "Number of tcp splicing profile steering-destination host applied"
    ::= { affirmedServicesContentHttpProxyServiceStatisticsSlotLevelUdpProxyDetailEntry 9 }

affirmedServicesContentHttpProxyServiceStatisticsSlotLevelUdpProxyDetailNumudpproxypolicyreevaluated OBJECT-TYPE
    SYNTAX      ConfdString
    MAX-ACCESS  read-only
    STATUS      current
    DESCRIPTION "Policy - Re-evaluations"
    ::= { affirmedServicesContentHttpProxyServiceStatisticsSlotLevelUdpProxyDetailEntry 10 }

affirmedServicesContentHttpProxyServiceStatisticsSlotLevelUdpProxyDetailNumudpproxypolicyrematched OBJECT-TYPE
    SYNTAX      ConfdString
    MAX-ACCESS  read-only
    STATUS      current
    DESCRIPTION "Policy - Matches after Re-evaluation"
    ::= { affirmedServicesContentHttpProxyServiceStatisticsSlotLevelUdpProxyDetailEntry 11 }

affirmedServicesContentHttpProxyServiceStatisticsSlotLevelUdpProxyDetailNumudpproxypolicynotavailablereeval OBJECT-TYPE
    SYNTAX      ConfdString
    MAX-ACCESS  read-only
    STATUS      current
    DESCRIPTION "Policy - No Policy Available after Re-evaluation"
    ::= { affirmedServicesContentHttpProxyServiceStatisticsSlotLevelUdpProxyDetailEntry 12 }

affirmedServicesContentHttpProxyServiceStatisticsSlotLevelUdpProxyFailureTable OBJECT-TYPE
    SYNTAX      SEQUENCE OF AffirmedServicesContentHttpProxyServiceStatisticsSlotLevelUdpProxyFailureEntry
    MAX-ACCESS  not-accessible
    STATUS      current
    DESCRIPTION ""
    ::= { affirmedServicesContentHttpProxyServiceStatisticsSlotLevelUdpProxy 3 }

affirmedServicesContentHttpProxyServiceStatisticsSlotLevelUdpProxyFailureEntry OBJECT-TYPE
    SYNTAX      AffirmedServicesContentHttpProxyServiceStatisticsSlotLevelUdpProxyFailureEntry
    MAX-ACCESS  not-accessible
    STATUS      current
    DESCRIPTION ""
    INDEX { affirmedServicesContentHttpProxyServiceStatisticsSlotLevelUdpProxyFailureChassis, affirmedServicesContentHttpProxyServiceStatisticsSlotLevelUdpProxyFailureSlot }
        ::= { affirmedServicesContentHttpProxyServiceStatisticsSlotLevelUdpProxyFailureTable 1 }

AffirmedServicesContentHttpProxyServiceStatisticsSlotLevelUdpProxyFailureEntry ::=
    SEQUENCE {
        affirmedServicesContentHttpProxyServiceStatisticsSlotLevelUdpProxyFailureChassis Unsigned32,
        affirmedServicesContentHttpProxyServiceStatisticsSlotLevelUdpProxyFailureSlot INTEGER,
        affirmedServicesContentHttpProxyServiceStatisticsSlotLevelUdpProxyFailureNumudpproxyabortsclientsocketerror ConfdString,
        affirmedServicesContentHttpProxyServiceStatisticsSlotLevelUdpProxyFailureNumudpproxyabortsserversocketerror ConfdString,
        affirmedServicesContentHttpProxyServiceStatisticsSlotLevelUdpProxyFailureNumudpproxyfailuresserverconnectioninitfailure ConfdString,
        affirmedServicesContentHttpProxyServiceStatisticsSlotLevelUdpProxyFailureNumudpproxyfailuresoutofsocket ConfdString,
        affirmedServicesContentHttpProxyServiceStatisticsSlotLevelUdpProxyFailureNumudpproxyabortsnoresponsefromserver ConfdString
    }

affirmedServicesContentHttpProxyServiceStatisticsSlotLevelUdpProxyFailureChassis OBJECT-TYPE
    SYNTAX      Unsigned32
    MAX-ACCESS  not-accessible
    STATUS      current
    DESCRIPTION "chassis ID"
    ::= { affirmedServicesContentHttpProxyServiceStatisticsSlotLevelUdpProxyFailureEntry 1 }

affirmedServicesContentHttpProxyServiceStatisticsSlotLevelUdpProxyFailureSlot OBJECT-TYPE
    SYNTAX      INTEGER {a1(1),a2(2),a3(3),a4(4),a5(5),a6(6),a7(7),a8(8),a9(9),a10(10),a11(11),a12(12),a13(13),a14(14),a15(15),a16(16),a17(17),a18(18),a19(19),a20(20),a21(21),a22(22),a23(23),a24(24),a25(25),a26(26),a27(27),a28(28),a29(29),a30(30),a31(31),a32(32),a33(33),a34(34),a35(35),a36(36),a37(37),a38(38),a39(39),a40(40),a41(41),a42(42),a43(43),a44(44),a45(45),a46(46),a47(47),a48(48),a49(49),a50(50),a51(51),a52(52),a53(53),a54(54),a55(55),a56(56),a57(57),a58(58),a59(59),a60(60),a61(61),a62(62),a63(63),a64(64),a65(65),a66(66),a67(67),a68(68),a69(69),a70(70),a71(71),a72(72),a73(73),a74(74),a75(75),a76(76),a77(77),a78(78),a79(79),a80(80),a81(81),a82(82),a83(83),a84(84),a85(85),a86(86),a87(87),a88(88),a89(89),a90(90),a91(91),a92(92),a93(93),a94(94),a95(95),a96(96),a97(97),a98(98),a99(99),a100(100),a101(101),a102(102),a103(103),a104(104),a105(105),a106(106),a107(107),a108(108),a109(109),a110(110),a111(111),a112(112),a113(113),a114(114),a115(115),a116(116),a117(117),a118(118),a119(119),a120(120),a121(121),a122(122),a123(123),a124(124),a125(125),a126(126),a127(127),a128(128)}
    MAX-ACCESS  not-accessible
    STATUS      current
    DESCRIPTION "slot number"
    ::= { affirmedServicesContentHttpProxyServiceStatisticsSlotLevelUdpProxyFailureEntry 2 }

affirmedServicesContentHttpProxyServiceStatisticsSlotLevelUdpProxyFailureNumudpproxyabortsclientsocketerror OBJECT-TYPE
    SYNTAX      ConfdString
    MAX-ACCESS  read-only
    STATUS      current
    DESCRIPTION "Number of UDP Proxy Aborts Client Socket Error"
    ::= { affirmedServicesContentHttpProxyServiceStatisticsSlotLevelUdpProxyFailureEntry 3 }

affirmedServicesContentHttpProxyServiceStatisticsSlotLevelUdpProxyFailureNumudpproxyabortsserversocketerror OBJECT-TYPE
    SYNTAX      ConfdString
    MAX-ACCESS  read-only
    STATUS      current
    DESCRIPTION "Number of UDP Proxy Aborts Server Socket Error"
    ::= { affirmedServicesContentHttpProxyServiceStatisticsSlotLevelUdpProxyFailureEntry 4 }

affirmedServicesContentHttpProxyServiceStatisticsSlotLevelUdpProxyFailureNumudpproxyfailuresserverconnectioninitfailure OBJECT-TYPE
    SYNTAX      ConfdString
    MAX-ACCESS  read-only
    STATUS      current
    DESCRIPTION "Number of UDP Proxy Failures Server Connection Init Failure"
    ::= { affirmedServicesContentHttpProxyServiceStatisticsSlotLevelUdpProxyFailureEntry 5 }

affirmedServicesContentHttpProxyServiceStatisticsSlotLevelUdpProxyFailureNumudpproxyfailuresoutofsocket OBJECT-TYPE
    SYNTAX      ConfdString
    MAX-ACCESS  read-only
    STATUS      current
    DESCRIPTION "Number of UDP Proxy Failures Out of Socket"
    ::= { affirmedServicesContentHttpProxyServiceStatisticsSlotLevelUdpProxyFailureEntry 6 }

affirmedServicesContentHttpProxyServiceStatisticsSlotLevelUdpProxyFailureNumudpproxyabortsnoresponsefromserver OBJECT-TYPE
    SYNTAX      ConfdString
    MAX-ACCESS  read-only
    STATUS      current
    DESCRIPTION "Number of UDP Proxy Aborts No Response From Server"
    ::= { affirmedServicesContentHttpProxyServiceStatisticsSlotLevelUdpProxyFailureEntry 7 }

affirmedServicesContentHttpProxyServiceStatisticsSlotLevelUdpProxyConnectionTable OBJECT-TYPE
    SYNTAX      SEQUENCE OF AffirmedServicesContentHttpProxyServiceStatisticsSlotLevelUdpProxyConnectionEntry
    MAX-ACCESS  not-accessible
    STATUS      current
    DESCRIPTION ""
    ::= { affirmedServicesContentHttpProxyServiceStatisticsSlotLevelUdpProxy 4 }

affirmedServicesContentHttpProxyServiceStatisticsSlotLevelUdpProxyConnectionEntry OBJECT-TYPE
    SYNTAX      AffirmedServicesContentHttpProxyServiceStatisticsSlotLevelUdpProxyConnectionEntry
    MAX-ACCESS  not-accessible
    STATUS      current
    DESCRIPTION ""
    INDEX { affirmedServicesContentHttpProxyServiceStatisticsSlotLevelUdpProxyConnectionChassis, affirmedServicesContentHttpProxyServiceStatisticsSlotLevelUdpProxyConnectionSlot }
        ::= { affirmedServicesContentHttpProxyServiceStatisticsSlotLevelUdpProxyConnectionTable 1 }

AffirmedServicesContentHttpProxyServiceStatisticsSlotLevelUdpProxyConnectionEntry ::=
    SEQUENCE {
        affirmedServicesContentHttpProxyServiceStatisticsSlotLevelUdpProxyConnectionChassis Unsigned32,
        affirmedServicesContentHttpProxyServiceStatisticsSlotLevelUdpProxyConnectionSlot INTEGER,
        affirmedServicesContentHttpProxyServiceStatisticsSlotLevelUdpProxyConnectionNumudpproxyclientconnectionstotal ConfdString,
        affirmedServicesContentHttpProxyServiceStatisticsSlotLevelUdpProxyConnectionNumudpproxyclientconnectionscurrentlyinuse ConfdString,
        affirmedServicesContentHttpProxyServiceStatisticsSlotLevelUdpProxyConnectionNumudpproxyclientconnectionsipv4 ConfdString,
        affirmedServicesContentHttpProxyServiceStatisticsSlotLevelUdpProxyConnectionNumudpproxyclientconnectionsipv6 ConfdString,
        affirmedServicesContentHttpProxyServiceStatisticsSlotLevelUdpProxyConnectionNumudpproxyclientconnectionsbytesreceived ConfdString,
        affirmedServicesContentHttpProxyServiceStatisticsSlotLevelUdpProxyConnectionNumudpproxyclientconnectionsbytessent ConfdString,
        affirmedServicesContentHttpProxyServiceStatisticsSlotLevelUdpProxyConnectionNumudpproxyclientconnectionspacketsreceived ConfdString,
        affirmedServicesContentHttpProxyServiceStatisticsSlotLevelUdpProxyConnectionNumudpproxyclientconnectionspacketssent ConfdString,
        affirmedServicesContentHttpProxyServiceStatisticsSlotLevelUdpProxyConnectionNumudpproxyserverconnectionstotal ConfdString,
        affirmedServicesContentHttpProxyServiceStatisticsSlotLevelUdpProxyConnectionNumudpproxyserverconnectionscurrentlyinuse ConfdString,
        affirmedServicesContentHttpProxyServiceStatisticsSlotLevelUdpProxyConnectionNumudpproxyserverconnectionsipv4 ConfdString,
        affirmedServicesContentHttpProxyServiceStatisticsSlotLevelUdpProxyConnectionNumudpproxyserverconnectionsipv6 ConfdString,
        affirmedServicesContentHttpProxyServiceStatisticsSlotLevelUdpProxyConnectionNumudpproxyserverconnectionsiptransparent ConfdString,
        affirmedServicesContentHttpProxyServiceStatisticsSlotLevelUdpProxyConnectionNumudpproxyserverconnectionsbytesreceived ConfdString,
        affirmedServicesContentHttpProxyServiceStatisticsSlotLevelUdpProxyConnectionNumudpproxyserverconnectionsbytessent ConfdString,
        affirmedServicesContentHttpProxyServiceStatisticsSlotLevelUdpProxyConnectionNumudpproxyserverconnectionspacketsreceived ConfdString,
        affirmedServicesContentHttpProxyServiceStatisticsSlotLevelUdpProxyConnectionNumudpproxyserverconnectionspacketssent ConfdString,
        affirmedServicesContentHttpProxyServiceStatisticsSlotLevelUdpProxyConnectionNumudpproxydpiupdates ConfdString,
        affirmedServicesContentHttpProxyServiceStatisticsSlotLevelUdpProxyConnectionNumudpproxydpiupdatefailures ConfdString
    }

affirmedServicesContentHttpProxyServiceStatisticsSlotLevelUdpProxyConnectionChassis OBJECT-TYPE
    SYNTAX      Unsigned32
    MAX-ACCESS  not-accessible
    STATUS      current
    DESCRIPTION "chassis ID"
    ::= { affirmedServicesContentHttpProxyServiceStatisticsSlotLevelUdpProxyConnectionEntry 1 }

affirmedServicesContentHttpProxyServiceStatisticsSlotLevelUdpProxyConnectionSlot OBJECT-TYPE
    SYNTAX      INTEGER {a1(1),a2(2),a3(3),a4(4),a5(5),a6(6),a7(7),a8(8),a9(9),a10(10),a11(11),a12(12),a13(13),a14(14),a15(15),a16(16),a17(17),a18(18),a19(19),a20(20),a21(21),a22(22),a23(23),a24(24),a25(25),a26(26),a27(27),a28(28),a29(29),a30(30),a31(31),a32(32),a33(33),a34(34),a35(35),a36(36),a37(37),a38(38),a39(39),a40(40),a41(41),a42(42),a43(43),a44(44),a45(45),a46(46),a47(47),a48(48),a49(49),a50(50),a51(51),a52(52),a53(53),a54(54),a55(55),a56(56),a57(57),a58(58),a59(59),a60(60),a61(61),a62(62),a63(63),a64(64),a65(65),a66(66),a67(67),a68(68),a69(69),a70(70),a71(71),a72(72),a73(73),a74(74),a75(75),a76(76),a77(77),a78(78),a79(79),a80(80),a81(81),a82(82),a83(83),a84(84),a85(85),a86(86),a87(87),a88(88),a89(89),a90(90),a91(91),a92(92),a93(93),a94(94),a95(95),a96(96),a97(97),a98(98),a99(99),a100(100),a101(101),a102(102),a103(103),a104(104),a105(105),a106(106),a107(107),a108(108),a109(109),a110(110),a111(111),a112(112),a113(113),a114(114),a115(115),a116(116),a117(117),a118(118),a119(119),a120(120),a121(121),a122(122),a123(123),a124(124),a125(125),a126(126),a127(127),a128(128)}
    MAX-ACCESS  not-accessible
    STATUS      current
    DESCRIPTION "slot number"
    ::= { affirmedServicesContentHttpProxyServiceStatisticsSlotLevelUdpProxyConnectionEntry 2 }

affirmedServicesContentHttpProxyServiceStatisticsSlotLevelUdpProxyConnectionNumudpproxyclientconnectionstotal OBJECT-TYPE
    SYNTAX      ConfdString
    MAX-ACCESS  read-only
    STATUS      current
    DESCRIPTION "Number of Total UDP Proxy Client Connections"
    ::= { affirmedServicesContentHttpProxyServiceStatisticsSlotLevelUdpProxyConnectionEntry 3 }

affirmedServicesContentHttpProxyServiceStatisticsSlotLevelUdpProxyConnectionNumudpproxyclientconnectionscurrentlyinuse OBJECT-TYPE
    SYNTAX      ConfdString
    MAX-ACCESS  read-only
    STATUS      current
    DESCRIPTION "Number of UDP Proxy Client Connections Currently In Use"
    ::= { affirmedServicesContentHttpProxyServiceStatisticsSlotLevelUdpProxyConnectionEntry 4 }

affirmedServicesContentHttpProxyServiceStatisticsSlotLevelUdpProxyConnectionNumudpproxyclientconnectionsipv4 OBJECT-TYPE
    SYNTAX      ConfdString
    MAX-ACCESS  read-only
    STATUS      current
    DESCRIPTION "Number of UDP Proxy Client Connections - IPv4"
    ::= { affirmedServicesContentHttpProxyServiceStatisticsSlotLevelUdpProxyConnectionEntry 5 }

affirmedServicesContentHttpProxyServiceStatisticsSlotLevelUdpProxyConnectionNumudpproxyclientconnectionsipv6 OBJECT-TYPE
    SYNTAX      ConfdString
    MAX-ACCESS  read-only
    STATUS      current
    DESCRIPTION "Number of UDP Proxy Client Connections - IPv6"
    ::= { affirmedServicesContentHttpProxyServiceStatisticsSlotLevelUdpProxyConnectionEntry 6 }

affirmedServicesContentHttpProxyServiceStatisticsSlotLevelUdpProxyConnectionNumudpproxyclientconnectionsbytesreceived OBJECT-TYPE
    SYNTAX      ConfdString
    MAX-ACCESS  read-only
    STATUS      current
    DESCRIPTION "UDP Proxy Client Connections - Number of Bytes Received"
    ::= { affirmedServicesContentHttpProxyServiceStatisticsSlotLevelUdpProxyConnectionEntry 7 }

affirmedServicesContentHttpProxyServiceStatisticsSlotLevelUdpProxyConnectionNumudpproxyclientconnectionsbytessent OBJECT-TYPE
    SYNTAX      ConfdString
    MAX-ACCESS  read-only
    STATUS      current
    DESCRIPTION "UDP Proxy Client Connections - Number of Bytes Sent"
    ::= { affirmedServicesContentHttpProxyServiceStatisticsSlotLevelUdpProxyConnectionEntry 8 }

affirmedServicesContentHttpProxyServiceStatisticsSlotLevelUdpProxyConnectionNumudpproxyclientconnectionspacketsreceived OBJECT-TYPE
    SYNTAX      ConfdString
    MAX-ACCESS  read-only
    STATUS      current
    DESCRIPTION "UDP Proxy Client Connections - Number of Packets Received"
    ::= { affirmedServicesContentHttpProxyServiceStatisticsSlotLevelUdpProxyConnectionEntry 9 }

affirmedServicesContentHttpProxyServiceStatisticsSlotLevelUdpProxyConnectionNumudpproxyclientconnectionspacketssent OBJECT-TYPE
    SYNTAX      ConfdString
    MAX-ACCESS  read-only
    STATUS      current
    DESCRIPTION "UDP Proxy Client Connections - Number of Packets Sent"
    ::= { affirmedServicesContentHttpProxyServiceStatisticsSlotLevelUdpProxyConnectionEntry 10 }

affirmedServicesContentHttpProxyServiceStatisticsSlotLevelUdpProxyConnectionNumudpproxyserverconnectionstotal OBJECT-TYPE
    SYNTAX      ConfdString
    MAX-ACCESS  read-only
    STATUS      current
    DESCRIPTION "Number of Total UDP Proxy Server Connections"
    ::= { affirmedServicesContentHttpProxyServiceStatisticsSlotLevelUdpProxyConnectionEntry 11 }

affirmedServicesContentHttpProxyServiceStatisticsSlotLevelUdpProxyConnectionNumudpproxyserverconnectionscurrentlyinuse OBJECT-TYPE
    SYNTAX      ConfdString
    MAX-ACCESS  read-only
    STATUS      current
    DESCRIPTION "Number of UDP Proxy Server Connections Currently In Use"
    ::= { affirmedServicesContentHttpProxyServiceStatisticsSlotLevelUdpProxyConnectionEntry 12 }

affirmedServicesContentHttpProxyServiceStatisticsSlotLevelUdpProxyConnectionNumudpproxyserverconnectionsipv4 OBJECT-TYPE
    SYNTAX      ConfdString
    MAX-ACCESS  read-only
    STATUS      current
    DESCRIPTION "Number of UDP Proxy Server Connections - IPv4"
    ::= { affirmedServicesContentHttpProxyServiceStatisticsSlotLevelUdpProxyConnectionEntry 13 }

affirmedServicesContentHttpProxyServiceStatisticsSlotLevelUdpProxyConnectionNumudpproxyserverconnectionsipv6 OBJECT-TYPE
    SYNTAX      ConfdString
    MAX-ACCESS  read-only
    STATUS      current
    DESCRIPTION "Number of UDP Proxy Server Connections - IPv6"
    ::= { affirmedServicesContentHttpProxyServiceStatisticsSlotLevelUdpProxyConnectionEntry 14 }

affirmedServicesContentHttpProxyServiceStatisticsSlotLevelUdpProxyConnectionNumudpproxyserverconnectionsiptransparent OBJECT-TYPE
    SYNTAX      ConfdString
    MAX-ACCESS  read-only
    STATUS      current
    DESCRIPTION "UDP Proxy Server Connections - Number of IP Transparent Flows"
    ::= { affirmedServicesContentHttpProxyServiceStatisticsSlotLevelUdpProxyConnectionEntry 15 }

affirmedServicesContentHttpProxyServiceStatisticsSlotLevelUdpProxyConnectionNumudpproxyserverconnectionsbytesreceived OBJECT-TYPE
    SYNTAX      ConfdString
    MAX-ACCESS  read-only
    STATUS      current
    DESCRIPTION "UDP Proxy Server Connections - Number of Bytes Received"
    ::= { affirmedServicesContentHttpProxyServiceStatisticsSlotLevelUdpProxyConnectionEntry 16 }

affirmedServicesContentHttpProxyServiceStatisticsSlotLevelUdpProxyConnectionNumudpproxyserverconnectionsbytessent OBJECT-TYPE
    SYNTAX      ConfdString
    MAX-ACCESS  read-only
    STATUS      current
    DESCRIPTION "UDP Proxy Server Connections - Number of Bytes Sent"
    ::= { affirmedServicesContentHttpProxyServiceStatisticsSlotLevelUdpProxyConnectionEntry 17 }

affirmedServicesContentHttpProxyServiceStatisticsSlotLevelUdpProxyConnectionNumudpproxyserverconnectionspacketsreceived OBJECT-TYPE
    SYNTAX      ConfdString
    MAX-ACCESS  read-only
    STATUS      current
    DESCRIPTION "UDP Proxy Server Connections - Number of Packets Received"
    ::= { affirmedServicesContentHttpProxyServiceStatisticsSlotLevelUdpProxyConnectionEntry 18 }

affirmedServicesContentHttpProxyServiceStatisticsSlotLevelUdpProxyConnectionNumudpproxyserverconnectionspacketssent OBJECT-TYPE
    SYNTAX      ConfdString
    MAX-ACCESS  read-only
    STATUS      current
    DESCRIPTION "UDP Proxy Server Connections - Number of Packets Sent"
    ::= { affirmedServicesContentHttpProxyServiceStatisticsSlotLevelUdpProxyConnectionEntry 19 }

affirmedServicesContentHttpProxyServiceStatisticsSlotLevelUdpProxyConnectionNumudpproxydpiupdates OBJECT-TYPE
    SYNTAX      ConfdString
    MAX-ACCESS  read-only
    STATUS      current
    DESCRIPTION "Total Number of UDP Proxy DPI Updates"
    ::= { affirmedServicesContentHttpProxyServiceStatisticsSlotLevelUdpProxyConnectionEntry 20 }

affirmedServicesContentHttpProxyServiceStatisticsSlotLevelUdpProxyConnectionNumudpproxydpiupdatefailures OBJECT-TYPE
    SYNTAX      ConfdString
    MAX-ACCESS  read-only
    STATUS      current
    DESCRIPTION "Total Number of UDP Proxy DPI Update Failures"
    ::= { affirmedServicesContentHttpProxyServiceStatisticsSlotLevelUdpProxyConnectionEntry 21 }

affirmedServicesContentHttpProxyServiceStatisticsSlotLevelUdpProxyQuicTable OBJECT-TYPE
    SYNTAX      SEQUENCE OF AffirmedServicesContentHttpProxyServiceStatisticsSlotLevelUdpProxyQuicEntry
    MAX-ACCESS  not-accessible
    STATUS      current
    DESCRIPTION ""
    ::= { affirmedServicesContentHttpProxyServiceStatisticsSlotLevelUdpProxy 5 }

affirmedServicesContentHttpProxyServiceStatisticsSlotLevelUdpProxyQuicEntry OBJECT-TYPE
    SYNTAX      AffirmedServicesContentHttpProxyServiceStatisticsSlotLevelUdpProxyQuicEntry
    MAX-ACCESS  not-accessible
    STATUS      current
    DESCRIPTION ""
    INDEX { affirmedServicesContentHttpProxyServiceStatisticsSlotLevelUdpProxyQuicChassis, affirmedServicesContentHttpProxyServiceStatisticsSlotLevelUdpProxyQuicSlot }
        ::= { affirmedServicesContentHttpProxyServiceStatisticsSlotLevelUdpProxyQuicTable 1 }

AffirmedServicesContentHttpProxyServiceStatisticsSlotLevelUdpProxyQuicEntry ::=
    SEQUENCE {
        affirmedServicesContentHttpProxyServiceStatisticsSlotLevelUdpProxyQuicChassis Unsigned32,
        affirmedServicesContentHttpProxyServiceStatisticsSlotLevelUdpProxyQuicSlot INTEGER,
        affirmedServicesContentHttpProxyServiceStatisticsSlotLevelUdpProxyQuicNumudpproxyquicclienthello ConfdString,
        affirmedServicesContentHttpProxyServiceStatisticsSlotLevelUdpProxyQuicNumudpproxyquicserverhello ConfdString,
        affirmedServicesContentHttpProxyServiceStatisticsSlotLevelUdpProxyQuicNumudpproxyquicotherpackets ConfdString,
        affirmedServicesContentHttpProxyServiceStatisticsSlotLevelUdpProxyQuicNumudpproxyquicserverreset ConfdString,
        affirmedServicesContentHttpProxyServiceStatisticsSlotLevelUdpProxyQuicNumudpproxyquicclientreset ConfdString,
        affirmedServicesContentHttpProxyServiceStatisticsSlotLevelUdpProxyQuicNumudpproxyquicbytesdownstream ConfdString,
        affirmedServicesContentHttpProxyServiceStatisticsSlotLevelUdpProxyQuicNumudpproxyquicbytesupstream ConfdString,
        affirmedServicesContentHttpProxyServiceStatisticsSlotLevelUdpProxyQuicNumudpproxyquicconnections ConfdString
    }

affirmedServicesContentHttpProxyServiceStatisticsSlotLevelUdpProxyQuicChassis OBJECT-TYPE
    SYNTAX      Unsigned32
    MAX-ACCESS  not-accessible
    STATUS      current
    DESCRIPTION "chassis ID"
    ::= { affirmedServicesContentHttpProxyServiceStatisticsSlotLevelUdpProxyQuicEntry 1 }

affirmedServicesContentHttpProxyServiceStatisticsSlotLevelUdpProxyQuicSlot OBJECT-TYPE
    SYNTAX      INTEGER {a1(1),a2(2),a3(3),a4(4),a5(5),a6(6),a7(7),a8(8),a9(9),a10(10),a11(11),a12(12),a13(13),a14(14),a15(15),a16(16),a17(17),a18(18),a19(19),a20(20),a21(21),a22(22),a23(23),a24(24),a25(25),a26(26),a27(27),a28(28),a29(29),a30(30),a31(31),a32(32),a33(33),a34(34),a35(35),a36(36),a37(37),a38(38),a39(39),a40(40),a41(41),a42(42),a43(43),a44(44),a45(45),a46(46),a47(47),a48(48),a49(49),a50(50),a51(51),a52(52),a53(53),a54(54),a55(55),a56(56),a57(57),a58(58),a59(59),a60(60),a61(61),a62(62),a63(63),a64(64),a65(65),a66(66),a67(67),a68(68),a69(69),a70(70),a71(71),a72(72),a73(73),a74(74),a75(75),a76(76),a77(77),a78(78),a79(79),a80(80),a81(81),a82(82),a83(83),a84(84),a85(85),a86(86),a87(87),a88(88),a89(89),a90(90),a91(91),a92(92),a93(93),a94(94),a95(95),a96(96),a97(97),a98(98),a99(99),a100(100),a101(101),a102(102),a103(103),a104(104),a105(105),a106(106),a107(107),a108(108),a109(109),a110(110),a111(111),a112(112),a113(113),a114(114),a115(115),a116(116),a117(117),a118(118),a119(119),a120(120),a121(121),a122(122),a123(123),a124(124),a125(125),a126(126),a127(127),a128(128)}
    MAX-ACCESS  not-accessible
    STATUS      current
    DESCRIPTION "slot number"
    ::= { affirmedServicesContentHttpProxyServiceStatisticsSlotLevelUdpProxyQuicEntry 2 }

affirmedServicesContentHttpProxyServiceStatisticsSlotLevelUdpProxyQuicNumudpproxyquicclienthello OBJECT-TYPE
    SYNTAX      ConfdString
    MAX-ACCESS  read-only
    STATUS      current
    DESCRIPTION "UDP Proxy QUIC - Number of Client Hello"
    ::= { affirmedServicesContentHttpProxyServiceStatisticsSlotLevelUdpProxyQuicEntry 3 }

affirmedServicesContentHttpProxyServiceStatisticsSlotLevelUdpProxyQuicNumudpproxyquicserverhello OBJECT-TYPE
    SYNTAX      ConfdString
    MAX-ACCESS  read-only
    STATUS      deprecated
    DESCRIPTION "UDP Proxy QUIC - Number of Server Rejects"
    ::= { affirmedServicesContentHttpProxyServiceStatisticsSlotLevelUdpProxyQuicEntry 4 }

affirmedServicesContentHttpProxyServiceStatisticsSlotLevelUdpProxyQuicNumudpproxyquicotherpackets OBJECT-TYPE
    SYNTAX      ConfdString
    MAX-ACCESS  read-only
    STATUS      current
    DESCRIPTION "UDP Proxy QUIC - Number of Other packets"
    ::= { affirmedServicesContentHttpProxyServiceStatisticsSlotLevelUdpProxyQuicEntry 5 }

affirmedServicesContentHttpProxyServiceStatisticsSlotLevelUdpProxyQuicNumudpproxyquicserverreset OBJECT-TYPE
    SYNTAX      ConfdString
    MAX-ACCESS  read-only
    STATUS      current
    DESCRIPTION "UDP Proxy QUIC - Number of Server Resets"
    ::= { affirmedServicesContentHttpProxyServiceStatisticsSlotLevelUdpProxyQuicEntry 6 }

affirmedServicesContentHttpProxyServiceStatisticsSlotLevelUdpProxyQuicNumudpproxyquicclientreset OBJECT-TYPE
    SYNTAX      ConfdString
    MAX-ACCESS  read-only
    STATUS      current
    DESCRIPTION "UDP Proxy QUIC - Number of Client Resets"
    ::= { affirmedServicesContentHttpProxyServiceStatisticsSlotLevelUdpProxyQuicEntry 7 }

affirmedServicesContentHttpProxyServiceStatisticsSlotLevelUdpProxyQuicNumudpproxyquicbytesdownstream OBJECT-TYPE
    SYNTAX      ConfdString
    MAX-ACCESS  read-only
    STATUS      current
    DESCRIPTION "UDP Proxy QUIC - Number of Downstream Bytes"
    ::= { affirmedServicesContentHttpProxyServiceStatisticsSlotLevelUdpProxyQuicEntry 8 }

affirmedServicesContentHttpProxyServiceStatisticsSlotLevelUdpProxyQuicNumudpproxyquicbytesupstream OBJECT-TYPE
    SYNTAX      ConfdString
    MAX-ACCESS  read-only
    STATUS      current
    DESCRIPTION "UDP Proxy QUIC - Number of Upstream Bytes"
    ::= { affirmedServicesContentHttpProxyServiceStatisticsSlotLevelUdpProxyQuicEntry 9 }

affirmedServicesContentHttpProxyServiceStatisticsSlotLevelUdpProxyQuicNumudpproxyquicconnections OBJECT-TYPE
    SYNTAX      ConfdString
    MAX-ACCESS  read-only
    STATUS      current
    DESCRIPTION "UDP Proxy QUIC - Number of Connections"
    ::= { affirmedServicesContentHttpProxyServiceStatisticsSlotLevelUdpProxyQuicEntry 10 }

affirmedServicesContentHttpProxyServiceStatisticsSlotLevelUdpProxyRateLimitingTable OBJECT-TYPE
    SYNTAX      SEQUENCE OF AffirmedServicesContentHttpProxyServiceStatisticsSlotLevelUdpProxyRateLimitingEntry
    MAX-ACCESS  not-accessible
    STATUS      current
    DESCRIPTION ""
    ::= { affirmedServicesContentHttpProxyServiceStatisticsSlotLevelUdpProxy 6 }

affirmedServicesContentHttpProxyServiceStatisticsSlotLevelUdpProxyRateLimitingEntry OBJECT-TYPE
    SYNTAX      AffirmedServicesContentHttpProxyServiceStatisticsSlotLevelUdpProxyRateLimitingEntry
    MAX-ACCESS  not-accessible
    STATUS      current
    DESCRIPTION ""
    INDEX { affirmedServicesContentHttpProxyServiceStatisticsSlotLevelUdpProxyRateLimitingChassis, affirmedServicesContentHttpProxyServiceStatisticsSlotLevelUdpProxyRateLimitingSlot }
        ::= { affirmedServicesContentHttpProxyServiceStatisticsSlotLevelUdpProxyRateLimitingTable 1 }

AffirmedServicesContentHttpProxyServiceStatisticsSlotLevelUdpProxyRateLimitingEntry ::=
    SEQUENCE {
        affirmedServicesContentHttpProxyServiceStatisticsSlotLevelUdpProxyRateLimitingChassis Unsigned32,
        affirmedServicesContentHttpProxyServiceStatisticsSlotLevelUdpProxyRateLimitingSlot INTEGER,
        affirmedServicesContentHttpProxyServiceStatisticsSlotLevelUdpProxyRateLimitingNumudpproxyratelimitingsummaryattempts ConfdString,
        affirmedServicesContentHttpProxyServiceStatisticsSlotLevelUdpProxyRateLimitingNumudpproxyratelimitingsummarysuccesses ConfdString,
        affirmedServicesContentHttpProxyServiceStatisticsSlotLevelUdpProxyRateLimitingNumudpproxyratelimitingbytes ConfdString,
        affirmedServicesContentHttpProxyServiceStatisticsSlotLevelUdpProxyRateLimitingNumudpproxyratelimitingcurrent ConfdString,
        affirmedServicesContentHttpProxyServiceStatisticsSlotLevelUdpProxyRateLimitingNumudpproxyratelimitingbypassesdisabled ConfdString,
        affirmedServicesContentHttpProxyServiceStatisticsSlotLevelUdpProxyRateLimitingNumudpproxyratelimitingbypassesnotquic ConfdString,
        affirmedServicesContentHttpProxyServiceStatisticsSlotLevelUdpProxyRateLimitingNumudpproxyratelimitingoptedoutbysubscriber ConfdString,
        affirmedServicesContentHttpProxyServiceStatisticsSlotLevelUdpProxyRateLimitingNumudpproxyratelimitingoptedinreqnotmet ConfdString,
        affirmedServicesContentHttpProxyServiceStatisticsSlotLevelUdpProxyRateLimitingNumudpproxyratelimitingsavingsestimation ConfdString,
        affirmedServicesContentHttpProxyServiceStatisticsSlotLevelUdpProxyRateLimitingNumudpproxyratelimitingaggregationbypass ConfdString,
        affirmedServicesContentHttpProxyServiceStatisticsSlotLevelUdpProxyRateLimitingNumudpproxyratelimitingcanceltooshort ConfdString,
        affirmedServicesContentHttpProxyServiceStatisticsSlotLevelUdpProxyRateLimitingNumudpproxyratelimitingbytessavingsestimation ConfdString
    }

affirmedServicesContentHttpProxyServiceStatisticsSlotLevelUdpProxyRateLimitingChassis OBJECT-TYPE
    SYNTAX      Unsigned32
    MAX-ACCESS  not-accessible
    STATUS      current
    DESCRIPTION "chassis ID"
    ::= { affirmedServicesContentHttpProxyServiceStatisticsSlotLevelUdpProxyRateLimitingEntry 1 }

affirmedServicesContentHttpProxyServiceStatisticsSlotLevelUdpProxyRateLimitingSlot OBJECT-TYPE
    SYNTAX      INTEGER {a1(1),a2(2),a3(3),a4(4),a5(5),a6(6),a7(7),a8(8),a9(9),a10(10),a11(11),a12(12),a13(13),a14(14),a15(15),a16(16),a17(17),a18(18),a19(19),a20(20),a21(21),a22(22),a23(23),a24(24),a25(25),a26(26),a27(27),a28(28),a29(29),a30(30),a31(31),a32(32),a33(33),a34(34),a35(35),a36(36),a37(37),a38(38),a39(39),a40(40),a41(41),a42(42),a43(43),a44(44),a45(45),a46(46),a47(47),a48(48),a49(49),a50(50),a51(51),a52(52),a53(53),a54(54),a55(55),a56(56),a57(57),a58(58),a59(59),a60(60),a61(61),a62(62),a63(63),a64(64),a65(65),a66(66),a67(67),a68(68),a69(69),a70(70),a71(71),a72(72),a73(73),a74(74),a75(75),a76(76),a77(77),a78(78),a79(79),a80(80),a81(81),a82(82),a83(83),a84(84),a85(85),a86(86),a87(87),a88(88),a89(89),a90(90),a91(91),a92(92),a93(93),a94(94),a95(95),a96(96),a97(97),a98(98),a99(99),a100(100),a101(101),a102(102),a103(103),a104(104),a105(105),a106(106),a107(107),a108(108),a109(109),a110(110),a111(111),a112(112),a113(113),a114(114),a115(115),a116(116),a117(117),a118(118),a119(119),a120(120),a121(121),a122(122),a123(123),a124(124),a125(125),a126(126),a127(127),a128(128)}
    MAX-ACCESS  not-accessible
    STATUS      current
    DESCRIPTION "slot number"
    ::= { affirmedServicesContentHttpProxyServiceStatisticsSlotLevelUdpProxyRateLimitingEntry 2 }

affirmedServicesContentHttpProxyServiceStatisticsSlotLevelUdpProxyRateLimitingNumudpproxyratelimitingsummaryattempts OBJECT-TYPE
    SYNTAX      ConfdString
    MAX-ACCESS  read-only
    STATUS      current
    DESCRIPTION "Total number of Rate Limiting Summary Attempts"
    ::= { affirmedServicesContentHttpProxyServiceStatisticsSlotLevelUdpProxyRateLimitingEntry 3 }

affirmedServicesContentHttpProxyServiceStatisticsSlotLevelUdpProxyRateLimitingNumudpproxyratelimitingsummarysuccesses OBJECT-TYPE
    SYNTAX      ConfdString
    MAX-ACCESS  read-only
    STATUS      current
    DESCRIPTION "Total number of Rate Limiting Summary Successes"
    ::= { affirmedServicesContentHttpProxyServiceStatisticsSlotLevelUdpProxyRateLimitingEntry 4 }

affirmedServicesContentHttpProxyServiceStatisticsSlotLevelUdpProxyRateLimitingNumudpproxyratelimitingbytes OBJECT-TYPE
    SYNTAX      ConfdString
    MAX-ACCESS  read-only
    STATUS      current
    DESCRIPTION "Total number of Rate Limiting Bytes"
    ::= { affirmedServicesContentHttpProxyServiceStatisticsSlotLevelUdpProxyRateLimitingEntry 5 }

affirmedServicesContentHttpProxyServiceStatisticsSlotLevelUdpProxyRateLimitingNumudpproxyratelimitingcurrent OBJECT-TYPE
    SYNTAX      ConfdString
    MAX-ACCESS  read-only
    STATUS      current
    DESCRIPTION "Total number of Current Rate Limiting Flows"
    ::= { affirmedServicesContentHttpProxyServiceStatisticsSlotLevelUdpProxyRateLimitingEntry 6 }

affirmedServicesContentHttpProxyServiceStatisticsSlotLevelUdpProxyRateLimitingNumudpproxyratelimitingbypassesdisabled OBJECT-TYPE
    SYNTAX      ConfdString
    MAX-ACCESS  read-only
    STATUS      current
    DESCRIPTION "Total number of Rate Limiting Disabled Flows"
    ::= { affirmedServicesContentHttpProxyServiceStatisticsSlotLevelUdpProxyRateLimitingEntry 7 }

affirmedServicesContentHttpProxyServiceStatisticsSlotLevelUdpProxyRateLimitingNumudpproxyratelimitingbypassesnotquic OBJECT-TYPE
    SYNTAX      ConfdString
    MAX-ACCESS  read-only
    STATUS      current
    DESCRIPTION "Total number of Rate Limiting Bypassed Flow, Not QUIC"
    ::= { affirmedServicesContentHttpProxyServiceStatisticsSlotLevelUdpProxyRateLimitingEntry 8 }

affirmedServicesContentHttpProxyServiceStatisticsSlotLevelUdpProxyRateLimitingNumudpproxyratelimitingoptedoutbysubscriber OBJECT-TYPE
    SYNTAX      ConfdString
    MAX-ACCESS  read-only
    STATUS      current
    DESCRIPTION "Total number of Rate Limiting Flows Opted Out by Subscriber"
    ::= { affirmedServicesContentHttpProxyServiceStatisticsSlotLevelUdpProxyRateLimitingEntry 9 }

affirmedServicesContentHttpProxyServiceStatisticsSlotLevelUdpProxyRateLimitingNumudpproxyratelimitingoptedinreqnotmet OBJECT-TYPE
    SYNTAX      ConfdString
    MAX-ACCESS  read-only
    STATUS      current
    DESCRIPTION "Total number of Rate Limiting Flows Opted In by Subscriber but Requirements Not Met"
    ::= { affirmedServicesContentHttpProxyServiceStatisticsSlotLevelUdpProxyRateLimitingEntry 10 }

affirmedServicesContentHttpProxyServiceStatisticsSlotLevelUdpProxyRateLimitingNumudpproxyratelimitingsavingsestimation OBJECT-TYPE
    SYNTAX      ConfdString
    MAX-ACCESS  read-only
    STATUS      current
    DESCRIPTION "Total number of Rate Limiting Bypassed Flow, Savings Estimation"
    ::= { affirmedServicesContentHttpProxyServiceStatisticsSlotLevelUdpProxyRateLimitingEntry 11 }

affirmedServicesContentHttpProxyServiceStatisticsSlotLevelUdpProxyRateLimitingNumudpproxyratelimitingaggregationbypass OBJECT-TYPE
    SYNTAX      ConfdString
    MAX-ACCESS  read-only
    STATUS      current
    DESCRIPTION "Total number of Rate Limiting Flows Aggregation Bypass"
    ::= { affirmedServicesContentHttpProxyServiceStatisticsSlotLevelUdpProxyRateLimitingEntry 12 }

affirmedServicesContentHttpProxyServiceStatisticsSlotLevelUdpProxyRateLimitingNumudpproxyratelimitingcanceltooshort OBJECT-TYPE
    SYNTAX      ConfdString
    MAX-ACCESS  read-only
    STATUS      current
    DESCRIPTION "Total number of Rate Limiting Cancel flows, Too short"
    ::= { affirmedServicesContentHttpProxyServiceStatisticsSlotLevelUdpProxyRateLimitingEntry 13 }

affirmedServicesContentHttpProxyServiceStatisticsSlotLevelUdpProxyRateLimitingNumudpproxyratelimitingbytessavingsestimation OBJECT-TYPE
    SYNTAX      ConfdString
    MAX-ACCESS  read-only
    STATUS      current
    DESCRIPTION "Total number of Rate Limiting Bypassed Bytes, Savings Estimation"
    ::= { affirmedServicesContentHttpProxyServiceStatisticsSlotLevelUdpProxyRateLimitingEntry 14 }

affirmedServicesContentHttpProxyServiceStatisticsSlotLevelUdpProxyDnsTable OBJECT-TYPE
    SYNTAX      SEQUENCE OF AffirmedServicesContentHttpProxyServiceStatisticsSlotLevelUdpProxyDnsEntry
    MAX-ACCESS  not-accessible
    STATUS      current
    DESCRIPTION ""
    ::= { affirmedServicesContentHttpProxyServiceStatisticsSlotLevelUdpProxy 7 }

affirmedServicesContentHttpProxyServiceStatisticsSlotLevelUdpProxyDnsEntry OBJECT-TYPE
    SYNTAX      AffirmedServicesContentHttpProxyServiceStatisticsSlotLevelUdpProxyDnsEntry
    MAX-ACCESS  not-accessible
    STATUS      current
    DESCRIPTION ""
    INDEX { affirmedServicesContentHttpProxyServiceStatisticsSlotLevelUdpProxyDnsChassis, affirmedServicesContentHttpProxyServiceStatisticsSlotLevelUdpProxyDnsSlot }
        ::= { affirmedServicesContentHttpProxyServiceStatisticsSlotLevelUdpProxyDnsTable 1 }

AffirmedServicesContentHttpProxyServiceStatisticsSlotLevelUdpProxyDnsEntry ::=
    SEQUENCE {
        affirmedServicesContentHttpProxyServiceStatisticsSlotLevelUdpProxyDnsChassis Unsigned32,
        affirmedServicesContentHttpProxyServiceStatisticsSlotLevelUdpProxyDnsSlot INTEGER,
        affirmedServicesContentHttpProxyServiceStatisticsSlotLevelUdpProxyDnsNumudpproxydnsqueriessent ConfdString,
        affirmedServicesContentHttpProxyServiceStatisticsSlotLevelUdpProxyDnsNumudpproxydnsqueriesfailed ConfdString,
        affirmedServicesContentHttpProxyServiceStatisticsSlotLevelUdpProxyDnsNumudpproxydnsqueriescanceled ConfdString,
        affirmedServicesContentHttpProxyServiceStatisticsSlotLevelUdpProxyDnsNumudpproxydnsrepliessuccess ConfdString,
        affirmedServicesContentHttpProxyServiceStatisticsSlotLevelUdpProxyDnsNumudpproxydnsrepliesfailure ConfdString,
        affirmedServicesContentHttpProxyServiceStatisticsSlotLevelUdpProxyDnsNumudpproxydnsrepliesstale ConfdString,
        affirmedServicesContentHttpProxyServiceStatisticsSlotLevelUdpProxyDnsNumudpproxydnsrepliesfromcache ConfdString
    }

affirmedServicesContentHttpProxyServiceStatisticsSlotLevelUdpProxyDnsChassis OBJECT-TYPE
    SYNTAX      Unsigned32
    MAX-ACCESS  not-accessible
    STATUS      current
    DESCRIPTION "chassis ID"
    ::= { affirmedServicesContentHttpProxyServiceStatisticsSlotLevelUdpProxyDnsEntry 1 }

affirmedServicesContentHttpProxyServiceStatisticsSlotLevelUdpProxyDnsSlot OBJECT-TYPE
    SYNTAX      INTEGER {a1(1),a2(2),a3(3),a4(4),a5(5),a6(6),a7(7),a8(8),a9(9),a10(10),a11(11),a12(12),a13(13),a14(14),a15(15),a16(16),a17(17),a18(18),a19(19),a20(20),a21(21),a22(22),a23(23),a24(24),a25(25),a26(26),a27(27),a28(28),a29(29),a30(30),a31(31),a32(32),a33(33),a34(34),a35(35),a36(36),a37(37),a38(38),a39(39),a40(40),a41(41),a42(42),a43(43),a44(44),a45(45),a46(46),a47(47),a48(48),a49(49),a50(50),a51(51),a52(52),a53(53),a54(54),a55(55),a56(56),a57(57),a58(58),a59(59),a60(60),a61(61),a62(62),a63(63),a64(64),a65(65),a66(66),a67(67),a68(68),a69(69),a70(70),a71(71),a72(72),a73(73),a74(74),a75(75),a76(76),a77(77),a78(78),a79(79),a80(80),a81(81),a82(82),a83(83),a84(84),a85(85),a86(86),a87(87),a88(88),a89(89),a90(90),a91(91),a92(92),a93(93),a94(94),a95(95),a96(96),a97(97),a98(98),a99(99),a100(100),a101(101),a102(102),a103(103),a104(104),a105(105),a106(106),a107(107),a108(108),a109(109),a110(110),a111(111),a112(112),a113(113),a114(114),a115(115),a116(116),a117(117),a118(118),a119(119),a120(120),a121(121),a122(122),a123(123),a124(124),a125(125),a126(126),a127(127),a128(128)}
    MAX-ACCESS  not-accessible
    STATUS      current
    DESCRIPTION "slot number"
    ::= { affirmedServicesContentHttpProxyServiceStatisticsSlotLevelUdpProxyDnsEntry 2 }

affirmedServicesContentHttpProxyServiceStatisticsSlotLevelUdpProxyDnsNumudpproxydnsqueriessent OBJECT-TYPE
    SYNTAX      ConfdString
    MAX-ACCESS  read-only
    STATUS      current
    DESCRIPTION "Number of UDP Proxy DNS Queries Sent"
    ::= { affirmedServicesContentHttpProxyServiceStatisticsSlotLevelUdpProxyDnsEntry 3 }

affirmedServicesContentHttpProxyServiceStatisticsSlotLevelUdpProxyDnsNumudpproxydnsqueriesfailed OBJECT-TYPE
    SYNTAX      ConfdString
    MAX-ACCESS  read-only
    STATUS      current
    DESCRIPTION "Number of UDP Proxy DNS Queries Failed"
    ::= { affirmedServicesContentHttpProxyServiceStatisticsSlotLevelUdpProxyDnsEntry 4 }

affirmedServicesContentHttpProxyServiceStatisticsSlotLevelUdpProxyDnsNumudpproxydnsqueriescanceled OBJECT-TYPE
    SYNTAX      ConfdString
    MAX-ACCESS  read-only
    STATUS      current
    DESCRIPTION "Number of UDP Proxy DNS Queries Canceled"
    ::= { affirmedServicesContentHttpProxyServiceStatisticsSlotLevelUdpProxyDnsEntry 5 }

affirmedServicesContentHttpProxyServiceStatisticsSlotLevelUdpProxyDnsNumudpproxydnsrepliessuccess OBJECT-TYPE
    SYNTAX      ConfdString
    MAX-ACCESS  read-only
    STATUS      current
    DESCRIPTION "Number of UDP Proxy DNS Replies Succeded"
    ::= { affirmedServicesContentHttpProxyServiceStatisticsSlotLevelUdpProxyDnsEntry 6 }

affirmedServicesContentHttpProxyServiceStatisticsSlotLevelUdpProxyDnsNumudpproxydnsrepliesfailure OBJECT-TYPE
    SYNTAX      ConfdString
    MAX-ACCESS  read-only
    STATUS      current
    DESCRIPTION "Number of UDP Proxy DNS Replies Failed"
    ::= { affirmedServicesContentHttpProxyServiceStatisticsSlotLevelUdpProxyDnsEntry 7 }

affirmedServicesContentHttpProxyServiceStatisticsSlotLevelUdpProxyDnsNumudpproxydnsrepliesstale OBJECT-TYPE
    SYNTAX      ConfdString
    MAX-ACCESS  read-only
    STATUS      current
    DESCRIPTION "Number of UDP Proxy DNS Stale Replies"
    ::= { affirmedServicesContentHttpProxyServiceStatisticsSlotLevelUdpProxyDnsEntry 8 }

affirmedServicesContentHttpProxyServiceStatisticsSlotLevelUdpProxyDnsNumudpproxydnsrepliesfromcache OBJECT-TYPE
    SYNTAX      ConfdString
    MAX-ACCESS  read-only
    STATUS      current
    DESCRIPTION "Number of UDP Proxy DNS Replies from Cache"
    ::= { affirmedServicesContentHttpProxyServiceStatisticsSlotLevelUdpProxyDnsEntry 9 }

affirmedServicesContentHttpProxyServiceStatisticsSlotLevelMinifyTable OBJECT-TYPE
    SYNTAX      SEQUENCE OF AffirmedServicesContentHttpProxyServiceStatisticsSlotLevelMinifyEntry
    MAX-ACCESS  not-accessible
    STATUS      deprecated
    DESCRIPTION ""
    ::= { affirmedServicesContentHttpProxyServiceStatisticsSlotLevel 9 }

affirmedServicesContentHttpProxyServiceStatisticsSlotLevelMinifyEntry OBJECT-TYPE
    SYNTAX      AffirmedServicesContentHttpProxyServiceStatisticsSlotLevelMinifyEntry
    MAX-ACCESS  not-accessible
    STATUS      deprecated
    DESCRIPTION ""
    INDEX { affirmedServicesContentHttpProxyServiceStatisticsSlotLevelMinifyChassis, affirmedServicesContentHttpProxyServiceStatisticsSlotLevelMinifySlot }
        ::= { affirmedServicesContentHttpProxyServiceStatisticsSlotLevelMinifyTable 1 }

AffirmedServicesContentHttpProxyServiceStatisticsSlotLevelMinifyEntry ::=
    SEQUENCE {
        affirmedServicesContentHttpProxyServiceStatisticsSlotLevelMinifyChassis Unsigned32,
        affirmedServicesContentHttpProxyServiceStatisticsSlotLevelMinifySlot Unsigned32,
        affirmedServicesContentHttpProxyServiceStatisticsSlotLevelMinifyNumminifycssattempts ConfdString,
        affirmedServicesContentHttpProxyServiceStatisticsSlotLevelMinifyNumminifycsssuccesses ConfdString,
        affirmedServicesContentHttpProxyServiceStatisticsSlotLevelMinifyNumminifycssfailures ConfdString,
        affirmedServicesContentHttpProxyServiceStatisticsSlotLevelMinifyNumminifycssbytesattempt ConfdString,
        affirmedServicesContentHttpProxyServiceStatisticsSlotLevelMinifyNumminifycssbytesminified ConfdString,
        affirmedServicesContentHttpProxyServiceStatisticsSlotLevelMinifyNumminifycssbytesnotminified ConfdString,
        affirmedServicesContentHttpProxyServiceStatisticsSlotLevelMinifyNumminifyhtmlattempts ConfdString,
        affirmedServicesContentHttpProxyServiceStatisticsSlotLevelMinifyNumminifyhtmlsuccesses ConfdString,
        affirmedServicesContentHttpProxyServiceStatisticsSlotLevelMinifyNumminifyhtmlfailures ConfdString,
        affirmedServicesContentHttpProxyServiceStatisticsSlotLevelMinifyNumminifyhtmlbytesattempt ConfdString,
        affirmedServicesContentHttpProxyServiceStatisticsSlotLevelMinifyNumminifyhtmlbytesminified ConfdString,
        affirmedServicesContentHttpProxyServiceStatisticsSlotLevelMinifyNumminifyhtmlbytesnotminified ConfdString,
        affirmedServicesContentHttpProxyServiceStatisticsSlotLevelMinifyNumminifyjsattempts ConfdString,
        affirmedServicesContentHttpProxyServiceStatisticsSlotLevelMinifyNumminifyjssuccesses ConfdString,
        affirmedServicesContentHttpProxyServiceStatisticsSlotLevelMinifyNumminifyjsfailures ConfdString,
        affirmedServicesContentHttpProxyServiceStatisticsSlotLevelMinifyNumminifyjsbytesattempt ConfdString,
        affirmedServicesContentHttpProxyServiceStatisticsSlotLevelMinifyNumminifyjsbytesminified ConfdString,
        affirmedServicesContentHttpProxyServiceStatisticsSlotLevelMinifyNumminifyjsbytesnotminified ConfdString,
        affirmedServicesContentHttpProxyServiceStatisticsSlotLevelMinifyNumminifycancelcontenttypemismatches ConfdString
    }

affirmedServicesContentHttpProxyServiceStatisticsSlotLevelMinifyChassis OBJECT-TYPE
    SYNTAX      Unsigned32
    MAX-ACCESS  not-accessible
    STATUS      current
    DESCRIPTION "chassis ID"
    ::= { affirmedServicesContentHttpProxyServiceStatisticsSlotLevelMinifyEntry 1 }

affirmedServicesContentHttpProxyServiceStatisticsSlotLevelMinifySlot OBJECT-TYPE
    SYNTAX      Unsigned32
    MAX-ACCESS  not-accessible
    STATUS      current
    DESCRIPTION "slot number"
    ::= { affirmedServicesContentHttpProxyServiceStatisticsSlotLevelMinifyEntry 2 }

affirmedServicesContentHttpProxyServiceStatisticsSlotLevelMinifyNumminifycssattempts OBJECT-TYPE
    SYNTAX      ConfdString
    MAX-ACCESS  read-only
    STATUS      current
    DESCRIPTION "Total number of Minify CSS attempts"
    ::= { affirmedServicesContentHttpProxyServiceStatisticsSlotLevelMinifyEntry 3 }

affirmedServicesContentHttpProxyServiceStatisticsSlotLevelMinifyNumminifycsssuccesses OBJECT-TYPE
    SYNTAX      ConfdString
    MAX-ACCESS  read-only
    STATUS      current
    DESCRIPTION "Total number of Minify CSS successes"
    ::= { affirmedServicesContentHttpProxyServiceStatisticsSlotLevelMinifyEntry 4 }

affirmedServicesContentHttpProxyServiceStatisticsSlotLevelMinifyNumminifycssfailures OBJECT-TYPE
    SYNTAX      ConfdString
    MAX-ACCESS  read-only
    STATUS      current
    DESCRIPTION "Total number of Minify CSS failures"
    ::= { affirmedServicesContentHttpProxyServiceStatisticsSlotLevelMinifyEntry 5 }

affirmedServicesContentHttpProxyServiceStatisticsSlotLevelMinifyNumminifycssbytesattempt OBJECT-TYPE
    SYNTAX      ConfdString
    MAX-ACCESS  read-only
    STATUS      current
    DESCRIPTION "Total number of Minify CSS bytes attempt"
    ::= { affirmedServicesContentHttpProxyServiceStatisticsSlotLevelMinifyEntry 6 }

affirmedServicesContentHttpProxyServiceStatisticsSlotLevelMinifyNumminifycssbytesminified OBJECT-TYPE
    SYNTAX      ConfdString
    MAX-ACCESS  read-only
    STATUS      current
    DESCRIPTION "Total number of Minify CSS bytes minified"
    ::= { affirmedServicesContentHttpProxyServiceStatisticsSlotLevelMinifyEntry 7 }

affirmedServicesContentHttpProxyServiceStatisticsSlotLevelMinifyNumminifycssbytesnotminified OBJECT-TYPE
    SYNTAX      ConfdString
    MAX-ACCESS  read-only
    STATUS      current
    DESCRIPTION "Total number of Minify CSS bytes not minified"
    ::= { affirmedServicesContentHttpProxyServiceStatisticsSlotLevelMinifyEntry 8 }

affirmedServicesContentHttpProxyServiceStatisticsSlotLevelMinifyNumminifyhtmlattempts OBJECT-TYPE
    SYNTAX      ConfdString
    MAX-ACCESS  read-only
    STATUS      current
    DESCRIPTION "Total number of Minify HTML attempts"
    ::= { affirmedServicesContentHttpProxyServiceStatisticsSlotLevelMinifyEntry 9 }

affirmedServicesContentHttpProxyServiceStatisticsSlotLevelMinifyNumminifyhtmlsuccesses OBJECT-TYPE
    SYNTAX      ConfdString
    MAX-ACCESS  read-only
    STATUS      current
    DESCRIPTION "Total number of Minify HTML successes"
    ::= { affirmedServicesContentHttpProxyServiceStatisticsSlotLevelMinifyEntry 10 }

affirmedServicesContentHttpProxyServiceStatisticsSlotLevelMinifyNumminifyhtmlfailures OBJECT-TYPE
    SYNTAX      ConfdString
    MAX-ACCESS  read-only
    STATUS      current
    DESCRIPTION "Total number of Minify HTML failures"
    ::= { affirmedServicesContentHttpProxyServiceStatisticsSlotLevelMinifyEntry 11 }

affirmedServicesContentHttpProxyServiceStatisticsSlotLevelMinifyNumminifyhtmlbytesattempt OBJECT-TYPE
    SYNTAX      ConfdString
    MAX-ACCESS  read-only
    STATUS      current
    DESCRIPTION "Total number of Minify HTML bytes attempt"
    ::= { affirmedServicesContentHttpProxyServiceStatisticsSlotLevelMinifyEntry 12 }

affirmedServicesContentHttpProxyServiceStatisticsSlotLevelMinifyNumminifyhtmlbytesminified OBJECT-TYPE
    SYNTAX      ConfdString
    MAX-ACCESS  read-only
    STATUS      current
    DESCRIPTION "Total number of Minify HTML bytes minified"
    ::= { affirmedServicesContentHttpProxyServiceStatisticsSlotLevelMinifyEntry 13 }

affirmedServicesContentHttpProxyServiceStatisticsSlotLevelMinifyNumminifyhtmlbytesnotminified OBJECT-TYPE
    SYNTAX      ConfdString
    MAX-ACCESS  read-only
    STATUS      current
    DESCRIPTION "Total number of Minify HTML bytes not minified"
    ::= { affirmedServicesContentHttpProxyServiceStatisticsSlotLevelMinifyEntry 14 }

affirmedServicesContentHttpProxyServiceStatisticsSlotLevelMinifyNumminifyjsattempts OBJECT-TYPE
    SYNTAX      ConfdString
    MAX-ACCESS  read-only
    STATUS      current
    DESCRIPTION "Total number of Minify Javascript attempts"
    ::= { affirmedServicesContentHttpProxyServiceStatisticsSlotLevelMinifyEntry 15 }

affirmedServicesContentHttpProxyServiceStatisticsSlotLevelMinifyNumminifyjssuccesses OBJECT-TYPE
    SYNTAX      ConfdString
    MAX-ACCESS  read-only
    STATUS      current
    DESCRIPTION "Total number of Minify Javascript successes"
    ::= { affirmedServicesContentHttpProxyServiceStatisticsSlotLevelMinifyEntry 16 }

affirmedServicesContentHttpProxyServiceStatisticsSlotLevelMinifyNumminifyjsfailures OBJECT-TYPE
    SYNTAX      ConfdString
    MAX-ACCESS  read-only
    STATUS      current
    DESCRIPTION "Total number of Minify Javascript failures"
    ::= { affirmedServicesContentHttpProxyServiceStatisticsSlotLevelMinifyEntry 17 }

affirmedServicesContentHttpProxyServiceStatisticsSlotLevelMinifyNumminifyjsbytesattempt OBJECT-TYPE
    SYNTAX      ConfdString
    MAX-ACCESS  read-only
    STATUS      current
    DESCRIPTION "Total number of Minify Javascript bytes attempt"
    ::= { affirmedServicesContentHttpProxyServiceStatisticsSlotLevelMinifyEntry 18 }

affirmedServicesContentHttpProxyServiceStatisticsSlotLevelMinifyNumminifyjsbytesminified OBJECT-TYPE
    SYNTAX      ConfdString
    MAX-ACCESS  read-only
    STATUS      current
    DESCRIPTION "Total number of Minify Javascript bytes minified"
    ::= { affirmedServicesContentHttpProxyServiceStatisticsSlotLevelMinifyEntry 19 }

affirmedServicesContentHttpProxyServiceStatisticsSlotLevelMinifyNumminifyjsbytesnotminified OBJECT-TYPE
    SYNTAX      ConfdString
    MAX-ACCESS  read-only
    STATUS      current
    DESCRIPTION "Total number of Minify Javascript bytes not minified"
    ::= { affirmedServicesContentHttpProxyServiceStatisticsSlotLevelMinifyEntry 20 }

affirmedServicesContentHttpProxyServiceStatisticsSlotLevelMinifyNumminifycancelcontenttypemismatches OBJECT-TYPE
    SYNTAX      ConfdString
    MAX-ACCESS  read-only
    STATUS      current
    DESCRIPTION "Total number of Minify Cancels because Content-Type mismatches"
    ::= { affirmedServicesContentHttpProxyServiceStatisticsSlotLevelMinifyEntry 21 }

affirmedServicesContentHttpProxyServiceStatisticsSlotLevelCompressionTable OBJECT-TYPE
    SYNTAX      SEQUENCE OF AffirmedServicesContentHttpProxyServiceStatisticsSlotLevelCompressionEntry
    MAX-ACCESS  not-accessible
    STATUS      current
    DESCRIPTION ""
    ::= { affirmedServicesContentHttpProxyServiceStatisticsSlotLevel 10 }

affirmedServicesContentHttpProxyServiceStatisticsSlotLevelCompressionEntry OBJECT-TYPE
    SYNTAX      AffirmedServicesContentHttpProxyServiceStatisticsSlotLevelCompressionEntry
    MAX-ACCESS  not-accessible
    STATUS      current
    DESCRIPTION ""
    INDEX { affirmedServicesContentHttpProxyServiceStatisticsSlotLevelCompressionChassis, affirmedServicesContentHttpProxyServiceStatisticsSlotLevelCompressionSlot }
        ::= { affirmedServicesContentHttpProxyServiceStatisticsSlotLevelCompressionTable 1 }

AffirmedServicesContentHttpProxyServiceStatisticsSlotLevelCompressionEntry ::=
    SEQUENCE {
        affirmedServicesContentHttpProxyServiceStatisticsSlotLevelCompressionChassis Unsigned32,
        affirmedServicesContentHttpProxyServiceStatisticsSlotLevelCompressionSlot Unsigned32,
        affirmedServicesContentHttpProxyServiceStatisticsSlotLevelCompressionNumrspnotcompressedbyserver ConfdString,
        affirmedServicesContentHttpProxyServiceStatisticsSlotLevelCompressionNumrspcompressedbyserver ConfdString,
        affirmedServicesContentHttpProxyServiceStatisticsSlotLevelCompressionNumrspcompressedbyproxy ConfdString,
        affirmedServicesContentHttpProxyServiceStatisticsSlotLevelCompressionNumrspforcedcompressbyproxy ConfdString,
        affirmedServicesContentHttpProxyServiceStatisticsSlotLevelCompressionNumbytesnotcompressedbyserver ConfdString,
        affirmedServicesContentHttpProxyServiceStatisticsSlotLevelCompressionNumbytescompressedbyserver ConfdString,
        affirmedServicesContentHttpProxyServiceStatisticsSlotLevelCompressionNumbytescompressedbyproxy ConfdString,
        affirmedServicesContentHttpProxyServiceStatisticsSlotLevelCompressionNumbytesforcedcompressbyproxy ConfdString,
        affirmedServicesContentHttpProxyServiceStatisticsSlotLevelCompressionNumrspcancelcontenttypemismatches ConfdString
    }

affirmedServicesContentHttpProxyServiceStatisticsSlotLevelCompressionChassis OBJECT-TYPE
    SYNTAX      Unsigned32
    MAX-ACCESS  not-accessible
    STATUS      current
    DESCRIPTION "chassis ID"
    ::= { affirmedServicesContentHttpProxyServiceStatisticsSlotLevelCompressionEntry 1 }

affirmedServicesContentHttpProxyServiceStatisticsSlotLevelCompressionSlot OBJECT-TYPE
    SYNTAX      Unsigned32
    MAX-ACCESS  not-accessible
    STATUS      current
    DESCRIPTION "slot number"
    ::= { affirmedServicesContentHttpProxyServiceStatisticsSlotLevelCompressionEntry 2 }

affirmedServicesContentHttpProxyServiceStatisticsSlotLevelCompressionNumrspnotcompressedbyserver OBJECT-TYPE
    SYNTAX      ConfdString
    MAX-ACCESS  read-only
    STATUS      current
    DESCRIPTION "Total number of responses that were not compressed by the server"
    ::= { affirmedServicesContentHttpProxyServiceStatisticsSlotLevelCompressionEntry 3 }

affirmedServicesContentHttpProxyServiceStatisticsSlotLevelCompressionNumrspcompressedbyserver OBJECT-TYPE
    SYNTAX      ConfdString
    MAX-ACCESS  read-only
    STATUS      current
    DESCRIPTION "Total number of responses that were compressed by the server"
    ::= { affirmedServicesContentHttpProxyServiceStatisticsSlotLevelCompressionEntry 4 }

affirmedServicesContentHttpProxyServiceStatisticsSlotLevelCompressionNumrspcompressedbyproxy OBJECT-TYPE
    SYNTAX      ConfdString
    MAX-ACCESS  read-only
    STATUS      current
    DESCRIPTION "Total number of responses that were compressed by proxy"
    ::= { affirmedServicesContentHttpProxyServiceStatisticsSlotLevelCompressionEntry 5 }

affirmedServicesContentHttpProxyServiceStatisticsSlotLevelCompressionNumrspforcedcompressbyproxy OBJECT-TYPE
    SYNTAX      ConfdString
    MAX-ACCESS  read-only
    STATUS      current
    DESCRIPTION "Total number of responses that were forced to compress by proxy"
    ::= { affirmedServicesContentHttpProxyServiceStatisticsSlotLevelCompressionEntry 6 }

affirmedServicesContentHttpProxyServiceStatisticsSlotLevelCompressionNumbytesnotcompressedbyserver OBJECT-TYPE
    SYNTAX      ConfdString
    MAX-ACCESS  read-only
    STATUS      current
    DESCRIPTION "Total number of bytes that were not compressed by the server"
    ::= { affirmedServicesContentHttpProxyServiceStatisticsSlotLevelCompressionEntry 7 }

affirmedServicesContentHttpProxyServiceStatisticsSlotLevelCompressionNumbytescompressedbyserver OBJECT-TYPE
    SYNTAX      ConfdString
    MAX-ACCESS  read-only
    STATUS      current
    DESCRIPTION "Total number of bytes that were compressed by the server"
    ::= { affirmedServicesContentHttpProxyServiceStatisticsSlotLevelCompressionEntry 8 }

affirmedServicesContentHttpProxyServiceStatisticsSlotLevelCompressionNumbytescompressedbyproxy OBJECT-TYPE
    SYNTAX      ConfdString
    MAX-ACCESS  read-only
    STATUS      current
    DESCRIPTION "Total number of bytes that were compressed by proxy"
    ::= { affirmedServicesContentHttpProxyServiceStatisticsSlotLevelCompressionEntry 9 }

affirmedServicesContentHttpProxyServiceStatisticsSlotLevelCompressionNumbytesforcedcompressbyproxy OBJECT-TYPE
    SYNTAX      ConfdString
    MAX-ACCESS  read-only
    STATUS      current
    DESCRIPTION "Total number of bytes that were forced to compress by proxy"
    ::= { affirmedServicesContentHttpProxyServiceStatisticsSlotLevelCompressionEntry 10 }

affirmedServicesContentHttpProxyServiceStatisticsSlotLevelCompressionNumrspcancelcontenttypemismatches OBJECT-TYPE
    SYNTAX      ConfdString
    MAX-ACCESS  read-only
    STATUS      current
    DESCRIPTION "Total number of responses that were cancel because content-type mismatches"
    ::= { affirmedServicesContentHttpProxyServiceStatisticsSlotLevelCompressionEntry 11 }

affirmedServicesContentHttpProxyServiceStatisticsSlotLevelWebImageOptSummaryTable OBJECT-TYPE
    SYNTAX      SEQUENCE OF AffirmedServicesContentHttpProxyServiceStatisticsSlotLevelWebImageOptSummaryEntry
    MAX-ACCESS  not-accessible
    STATUS      current
    DESCRIPTION ""
    ::= { affirmedServicesContentHttpProxyServiceStatisticsSlotLevelWebImageOpt 1 }

affirmedServicesContentHttpProxyServiceStatisticsSlotLevelWebImageOptSummaryEntry OBJECT-TYPE
    SYNTAX      AffirmedServicesContentHttpProxyServiceStatisticsSlotLevelWebImageOptSummaryEntry
    MAX-ACCESS  not-accessible
    STATUS      current
    DESCRIPTION ""
    INDEX { affirmedServicesContentHttpProxyServiceStatisticsSlotLevelWebImageOptSummaryChassis, affirmedServicesContentHttpProxyServiceStatisticsSlotLevelWebImageOptSummarySlot }
        ::= { affirmedServicesContentHttpProxyServiceStatisticsSlotLevelWebImageOptSummaryTable 1 }

AffirmedServicesContentHttpProxyServiceStatisticsSlotLevelWebImageOptSummaryEntry ::=
    SEQUENCE {
        affirmedServicesContentHttpProxyServiceStatisticsSlotLevelWebImageOptSummaryChassis Unsigned32,
        affirmedServicesContentHttpProxyServiceStatisticsSlotLevelWebImageOptSummarySlot Unsigned32,
        affirmedServicesContentHttpProxyServiceStatisticsSlotLevelWebImageOptSummaryNumwebimageoptattempts ConfdString,
        affirmedServicesContentHttpProxyServiceStatisticsSlotLevelWebImageOptSummaryNumwebimageoptsuccesses ConfdString,
        affirmedServicesContentHttpProxyServiceStatisticsSlotLevelWebImageOptSummaryNumwebimageoptcancels ConfdString,
        affirmedServicesContentHttpProxyServiceStatisticsSlotLevelWebImageOptSummaryNumwebimageoptfailures ConfdString,
        affirmedServicesContentHttpProxyServiceStatisticsSlotLevelWebImageOptSummaryNumwebimageoptbytesattempt ConfdString,
        affirmedServicesContentHttpProxyServiceStatisticsSlotLevelWebImageOptSummaryNumwebimageoptbytesnotadapted ConfdString,
        affirmedServicesContentHttpProxyServiceStatisticsSlotLevelWebImageOptSummaryNumwebimageoptbytesadapted ConfdString,
        affirmedServicesContentHttpProxyServiceStatisticsSlotLevelWebImageOptSummaryWebimagesizemax ConfdString,
        affirmedServicesContentHttpProxyServiceStatisticsSlotLevelWebImageOptSummaryWebimagesizemin ConfdString,
        affirmedServicesContentHttpProxyServiceStatisticsSlotLevelWebImageOptSummaryWebimagesizeavg ConfdString,
        affirmedServicesContentHttpProxyServiceStatisticsSlotLevelWebImageOptSummaryWebimageadaptedsizemax ConfdString,
        affirmedServicesContentHttpProxyServiceStatisticsSlotLevelWebImageOptSummaryWebimageadaptedsizemin ConfdString,
        affirmedServicesContentHttpProxyServiceStatisticsSlotLevelWebImageOptSummaryWebimageadaptedsizeavg ConfdString,
        affirmedServicesContentHttpProxyServiceStatisticsSlotLevelWebImageOptSummaryNumwebimageoptaborts ConfdString
    }

affirmedServicesContentHttpProxyServiceStatisticsSlotLevelWebImageOptSummaryChassis OBJECT-TYPE
    SYNTAX      Unsigned32
    MAX-ACCESS  not-accessible
    STATUS      current
    DESCRIPTION "chassis ID"
    ::= { affirmedServicesContentHttpProxyServiceStatisticsSlotLevelWebImageOptSummaryEntry 1 }

affirmedServicesContentHttpProxyServiceStatisticsSlotLevelWebImageOptSummarySlot OBJECT-TYPE
    SYNTAX      Unsigned32
    MAX-ACCESS  not-accessible
    STATUS      current
    DESCRIPTION "slot number"
    ::= { affirmedServicesContentHttpProxyServiceStatisticsSlotLevelWebImageOptSummaryEntry 2 }

affirmedServicesContentHttpProxyServiceStatisticsSlotLevelWebImageOptSummaryNumwebimageoptattempts OBJECT-TYPE
    SYNTAX      ConfdString
    MAX-ACCESS  read-only
    STATUS      current
    DESCRIPTION "Total number of Web Image Optimization attempts"
    ::= { affirmedServicesContentHttpProxyServiceStatisticsSlotLevelWebImageOptSummaryEntry 3 }

affirmedServicesContentHttpProxyServiceStatisticsSlotLevelWebImageOptSummaryNumwebimageoptsuccesses OBJECT-TYPE
    SYNTAX      ConfdString
    MAX-ACCESS  read-only
    STATUS      current
    DESCRIPTION "Total number of Web Image Optimization successes"
    ::= { affirmedServicesContentHttpProxyServiceStatisticsSlotLevelWebImageOptSummaryEntry 4 }

affirmedServicesContentHttpProxyServiceStatisticsSlotLevelWebImageOptSummaryNumwebimageoptcancels OBJECT-TYPE
    SYNTAX      ConfdString
    MAX-ACCESS  read-only
    STATUS      current
    DESCRIPTION "Total number of Web Image Optimization cancels"
    ::= { affirmedServicesContentHttpProxyServiceStatisticsSlotLevelWebImageOptSummaryEntry 5 }

affirmedServicesContentHttpProxyServiceStatisticsSlotLevelWebImageOptSummaryNumwebimageoptfailures OBJECT-TYPE
    SYNTAX      ConfdString
    MAX-ACCESS  read-only
    STATUS      current
    DESCRIPTION "Total number of Web Image Optimization failures"
    ::= { affirmedServicesContentHttpProxyServiceStatisticsSlotLevelWebImageOptSummaryEntry 6 }

affirmedServicesContentHttpProxyServiceStatisticsSlotLevelWebImageOptSummaryNumwebimageoptbytesattempt OBJECT-TYPE
    SYNTAX      ConfdString
    MAX-ACCESS  read-only
    STATUS      current
    DESCRIPTION "Total number of Web Image Optimization bytes attempt to adapt"
    ::= { affirmedServicesContentHttpProxyServiceStatisticsSlotLevelWebImageOptSummaryEntry 7 }

affirmedServicesContentHttpProxyServiceStatisticsSlotLevelWebImageOptSummaryNumwebimageoptbytesnotadapted OBJECT-TYPE
    SYNTAX      ConfdString
    MAX-ACCESS  read-only
    STATUS      current
    DESCRIPTION "Total number of Web Image Optimization bytes not adapted"
    ::= { affirmedServicesContentHttpProxyServiceStatisticsSlotLevelWebImageOptSummaryEntry 8 }

affirmedServicesContentHttpProxyServiceStatisticsSlotLevelWebImageOptSummaryNumwebimageoptbytesadapted OBJECT-TYPE
    SYNTAX      ConfdString
    MAX-ACCESS  read-only
    STATUS      current
    DESCRIPTION "Total number of Web Image Optimization bytes adapted"
    ::= { affirmedServicesContentHttpProxyServiceStatisticsSlotLevelWebImageOptSummaryEntry 9 }

affirmedServicesContentHttpProxyServiceStatisticsSlotLevelWebImageOptSummaryWebimagesizemax OBJECT-TYPE
    SYNTAX      ConfdString
    MAX-ACCESS  read-only
    STATUS      current
    DESCRIPTION "Web Image Size Max (Bytes)"
    ::= { affirmedServicesContentHttpProxyServiceStatisticsSlotLevelWebImageOptSummaryEntry 10 }

affirmedServicesContentHttpProxyServiceStatisticsSlotLevelWebImageOptSummaryWebimagesizemin OBJECT-TYPE
    SYNTAX      ConfdString
    MAX-ACCESS  read-only
    STATUS      current
    DESCRIPTION "Web Image Size Min (Bytes)"
    ::= { affirmedServicesContentHttpProxyServiceStatisticsSlotLevelWebImageOptSummaryEntry 11 }

affirmedServicesContentHttpProxyServiceStatisticsSlotLevelWebImageOptSummaryWebimagesizeavg OBJECT-TYPE
    SYNTAX      ConfdString
    MAX-ACCESS  read-only
    STATUS      current
    DESCRIPTION "Web Image Size Average (Bytes)"
    ::= { affirmedServicesContentHttpProxyServiceStatisticsSlotLevelWebImageOptSummaryEntry 12 }

affirmedServicesContentHttpProxyServiceStatisticsSlotLevelWebImageOptSummaryWebimageadaptedsizemax OBJECT-TYPE
    SYNTAX      ConfdString
    MAX-ACCESS  read-only
    STATUS      current
    DESCRIPTION "Web Image Adapted Size Max (Bytes)"
    ::= { affirmedServicesContentHttpProxyServiceStatisticsSlotLevelWebImageOptSummaryEntry 13 }

affirmedServicesContentHttpProxyServiceStatisticsSlotLevelWebImageOptSummaryWebimageadaptedsizemin OBJECT-TYPE
    SYNTAX      ConfdString
    MAX-ACCESS  read-only
    STATUS      current
    DESCRIPTION "Web Image Adapted Size Min (Bytes)"
    ::= { affirmedServicesContentHttpProxyServiceStatisticsSlotLevelWebImageOptSummaryEntry 14 }

affirmedServicesContentHttpProxyServiceStatisticsSlotLevelWebImageOptSummaryWebimageadaptedsizeavg OBJECT-TYPE
    SYNTAX      ConfdString
    MAX-ACCESS  read-only
    STATUS      current
    DESCRIPTION "Web Image Adapted Size Average (Bytes)"
    ::= { affirmedServicesContentHttpProxyServiceStatisticsSlotLevelWebImageOptSummaryEntry 15 }

affirmedServicesContentHttpProxyServiceStatisticsSlotLevelWebImageOptSummaryNumwebimageoptaborts OBJECT-TYPE
    SYNTAX      ConfdString
    MAX-ACCESS  read-only
    STATUS      current
    DESCRIPTION "Total number of Web Image Optimization Aborts"
    ::= { affirmedServicesContentHttpProxyServiceStatisticsSlotLevelWebImageOptSummaryEntry 16 }

affirmedServicesContentHttpProxyServiceStatisticsSlotLevelWebImageOptDetailTable OBJECT-TYPE
    SYNTAX      SEQUENCE OF AffirmedServicesContentHttpProxyServiceStatisticsSlotLevelWebImageOptDetailEntry
    MAX-ACCESS  not-accessible
    STATUS      current
    DESCRIPTION ""
    ::= { affirmedServicesContentHttpProxyServiceStatisticsSlotLevelWebImageOpt 2 }

affirmedServicesContentHttpProxyServiceStatisticsSlotLevelWebImageOptDetailEntry OBJECT-TYPE
    SYNTAX      AffirmedServicesContentHttpProxyServiceStatisticsSlotLevelWebImageOptDetailEntry
    MAX-ACCESS  not-accessible
    STATUS      current
    DESCRIPTION ""
    INDEX { affirmedServicesContentHttpProxyServiceStatisticsSlotLevelWebImageOptDetailChassis, affirmedServicesContentHttpProxyServiceStatisticsSlotLevelWebImageOptDetailSlot }
        ::= { affirmedServicesContentHttpProxyServiceStatisticsSlotLevelWebImageOptDetailTable 1 }

AffirmedServicesContentHttpProxyServiceStatisticsSlotLevelWebImageOptDetailEntry ::=
    SEQUENCE {
        affirmedServicesContentHttpProxyServiceStatisticsSlotLevelWebImageOptDetailChassis Unsigned32,
        affirmedServicesContentHttpProxyServiceStatisticsSlotLevelWebImageOptDetailSlot Unsigned32,
        affirmedServicesContentHttpProxyServiceStatisticsSlotLevelWebImageOptDetailNumwebimageoptbelowsrcsizethresh ConfdString,
        affirmedServicesContentHttpProxyServiceStatisticsSlotLevelWebImageOptDetailNumwebimageoptbelowpercentsavingthresh ConfdString,
        affirmedServicesContentHttpProxyServiceStatisticsSlotLevelWebImageOptDetailNumwebimageopttgtmaxsizeexceeded ConfdString,
        affirmedServicesContentHttpProxyServiceStatisticsSlotLevelWebImageOptDetailNumwebimageoptformatnotsupported ConfdString,
        affirmedServicesContentHttpProxyServiceStatisticsSlotLevelWebImageOptDetailNumwebimageoptcompressnotallowed ConfdString,
        affirmedServicesContentHttpProxyServiceStatisticsSlotLevelWebImageOptDetailNumwebimageoptdecompressimagefailed ConfdString,
        affirmedServicesContentHttpProxyServiceStatisticsSlotLevelWebImageOptDetailNumwebimageoptcompressimagefailed ConfdString,
        affirmedServicesContentHttpProxyServiceStatisticsSlotLevelWebImageOptDetailNumwebimageoptquantizeimagefailed ConfdString,
        affirmedServicesContentHttpProxyServiceStatisticsSlotLevelWebImageOptDetailNumwebimageoptremovemetadatafailed ConfdString,
        affirmedServicesContentHttpProxyServiceStatisticsSlotLevelWebImageOptDetailNumwebimageoptresizeimagefailed ConfdString,
        affirmedServicesContentHttpProxyServiceStatisticsSlotLevelWebImageOptDetailNumwebimageoptalphablendimagefailed ConfdString,
        affirmedServicesContentHttpProxyServiceStatisticsSlotLevelWebImageOptDetailNumwebimageoptgetsrcimageformatfailed ConfdString,
        affirmedServicesContentHttpProxyServiceStatisticsSlotLevelWebImageOptDetailNumwebimageoptgettgtimageformatfailed ConfdString,
        affirmedServicesContentHttpProxyServiceStatisticsSlotLevelWebImageOptDetailNumwebimageoptjpegattempts ConfdString,
        affirmedServicesContentHttpProxyServiceStatisticsSlotLevelWebImageOptDetailNumwebimageoptjpegsuccesses ConfdString,
        affirmedServicesContentHttpProxyServiceStatisticsSlotLevelWebImageOptDetailNumwebimageoptjpegbytesattempt ConfdString,
        affirmedServicesContentHttpProxyServiceStatisticsSlotLevelWebImageOptDetailNumwebimageoptjpegbytesnotadapted ConfdString,
        affirmedServicesContentHttpProxyServiceStatisticsSlotLevelWebImageOptDetailNumwebimageoptjpegbytesadapted ConfdString,
        affirmedServicesContentHttpProxyServiceStatisticsSlotLevelWebImageOptDetailNumwebimageoptgifattempts ConfdString,
        affirmedServicesContentHttpProxyServiceStatisticsSlotLevelWebImageOptDetailNumwebimageoptgifsuccesses ConfdString,
        affirmedServicesContentHttpProxyServiceStatisticsSlotLevelWebImageOptDetailNumwebimageoptgifbytesattempt ConfdString,
        affirmedServicesContentHttpProxyServiceStatisticsSlotLevelWebImageOptDetailNumwebimageoptgifbytesnotadapted ConfdString,
        affirmedServicesContentHttpProxyServiceStatisticsSlotLevelWebImageOptDetailNumwebimageoptgifbytesadapted ConfdString,
        affirmedServicesContentHttpProxyServiceStatisticsSlotLevelWebImageOptDetailNumwebimageoptpngattempts ConfdString,
        affirmedServicesContentHttpProxyServiceStatisticsSlotLevelWebImageOptDetailNumwebimageoptpngsuccesses ConfdString,
        affirmedServicesContentHttpProxyServiceStatisticsSlotLevelWebImageOptDetailNumwebimageoptpngbytesattempt ConfdString,
        affirmedServicesContentHttpProxyServiceStatisticsSlotLevelWebImageOptDetailNumwebimageoptpngbytesnotadapted ConfdString,
        affirmedServicesContentHttpProxyServiceStatisticsSlotLevelWebImageOptDetailNumwebimageoptpngbytesadapted ConfdString,
        affirmedServicesContentHttpProxyServiceStatisticsSlotLevelWebImageOptDetailNumwebimageoptsrcmaxsizeexceeded ConfdString,
        affirmedServicesContentHttpProxyServiceStatisticsSlotLevelWebImageOptDetailNumwebimageoptcontenttypemismatches ConfdString,
        affirmedServicesContentHttpProxyServiceStatisticsSlotLevelWebImageOptDetailNumwebimageoptcpuoverload ConfdString
    }

affirmedServicesContentHttpProxyServiceStatisticsSlotLevelWebImageOptDetailChassis OBJECT-TYPE
    SYNTAX      Unsigned32
    MAX-ACCESS  not-accessible
    STATUS      current
    DESCRIPTION "chassis ID"
    ::= { affirmedServicesContentHttpProxyServiceStatisticsSlotLevelWebImageOptDetailEntry 1 }

affirmedServicesContentHttpProxyServiceStatisticsSlotLevelWebImageOptDetailSlot OBJECT-TYPE
    SYNTAX      Unsigned32
    MAX-ACCESS  not-accessible
    STATUS      current
    DESCRIPTION "slot number"
    ::= { affirmedServicesContentHttpProxyServiceStatisticsSlotLevelWebImageOptDetailEntry 2 }

affirmedServicesContentHttpProxyServiceStatisticsSlotLevelWebImageOptDetailNumwebimageoptbelowsrcsizethresh OBJECT-TYPE
    SYNTAX      ConfdString
    MAX-ACCESS  read-only
    STATUS      current
    DESCRIPTION "Total number of Web Image Optimization below source size threshold"
    ::= { affirmedServicesContentHttpProxyServiceStatisticsSlotLevelWebImageOptDetailEntry 3 }

affirmedServicesContentHttpProxyServiceStatisticsSlotLevelWebImageOptDetailNumwebimageoptbelowpercentsavingthresh OBJECT-TYPE
    SYNTAX      ConfdString
    MAX-ACCESS  read-only
    STATUS      current
    DESCRIPTION "Total number of Web Image Optimization below percentage savings threshold"
    ::= { affirmedServicesContentHttpProxyServiceStatisticsSlotLevelWebImageOptDetailEntry 4 }

affirmedServicesContentHttpProxyServiceStatisticsSlotLevelWebImageOptDetailNumwebimageopttgtmaxsizeexceeded OBJECT-TYPE
    SYNTAX      ConfdString
    MAX-ACCESS  read-only
    STATUS      current
    DESCRIPTION "Total number of Web Image Optimization target max size exceeded"
    ::= { affirmedServicesContentHttpProxyServiceStatisticsSlotLevelWebImageOptDetailEntry 5 }

affirmedServicesContentHttpProxyServiceStatisticsSlotLevelWebImageOptDetailNumwebimageoptformatnotsupported OBJECT-TYPE
    SYNTAX      ConfdString
    MAX-ACCESS  read-only
    STATUS      current
    DESCRIPTION "Total number of Web Image Optimization format not supported"
    ::= { affirmedServicesContentHttpProxyServiceStatisticsSlotLevelWebImageOptDetailEntry 6 }

affirmedServicesContentHttpProxyServiceStatisticsSlotLevelWebImageOptDetailNumwebimageoptcompressnotallowed OBJECT-TYPE
    SYNTAX      ConfdString
    MAX-ACCESS  read-only
    STATUS      current
    DESCRIPTION "Total number of Web Image Optimization compressing not allowed"
    ::= { affirmedServicesContentHttpProxyServiceStatisticsSlotLevelWebImageOptDetailEntry 7 }

affirmedServicesContentHttpProxyServiceStatisticsSlotLevelWebImageOptDetailNumwebimageoptdecompressimagefailed OBJECT-TYPE
    SYNTAX      ConfdString
    MAX-ACCESS  read-only
    STATUS      current
    DESCRIPTION "Total number of Web Image Optimization decompressing image failed"
    ::= { affirmedServicesContentHttpProxyServiceStatisticsSlotLevelWebImageOptDetailEntry 8 }

affirmedServicesContentHttpProxyServiceStatisticsSlotLevelWebImageOptDetailNumwebimageoptcompressimagefailed OBJECT-TYPE
    SYNTAX      ConfdString
    MAX-ACCESS  read-only
    STATUS      current
    DESCRIPTION "Total number of Web Image Optimization compressing image failed"
    ::= { affirmedServicesContentHttpProxyServiceStatisticsSlotLevelWebImageOptDetailEntry 9 }

affirmedServicesContentHttpProxyServiceStatisticsSlotLevelWebImageOptDetailNumwebimageoptquantizeimagefailed OBJECT-TYPE
    SYNTAX      ConfdString
    MAX-ACCESS  read-only
    STATUS      current
    DESCRIPTION "Total number of Web Image Optimization quantizing image failed"
    ::= { affirmedServicesContentHttpProxyServiceStatisticsSlotLevelWebImageOptDetailEntry 10 }

affirmedServicesContentHttpProxyServiceStatisticsSlotLevelWebImageOptDetailNumwebimageoptremovemetadatafailed OBJECT-TYPE
    SYNTAX      ConfdString
    MAX-ACCESS  read-only
    STATUS      current
    DESCRIPTION "Total number of Web Image Optimization removing metadata failed"
    ::= { affirmedServicesContentHttpProxyServiceStatisticsSlotLevelWebImageOptDetailEntry 11 }

affirmedServicesContentHttpProxyServiceStatisticsSlotLevelWebImageOptDetailNumwebimageoptresizeimagefailed OBJECT-TYPE
    SYNTAX      ConfdString
    MAX-ACCESS  read-only
    STATUS      current
    DESCRIPTION "Total number of Web Image Optimization resizing image failed"
    ::= { affirmedServicesContentHttpProxyServiceStatisticsSlotLevelWebImageOptDetailEntry 12 }

affirmedServicesContentHttpProxyServiceStatisticsSlotLevelWebImageOptDetailNumwebimageoptalphablendimagefailed OBJECT-TYPE
    SYNTAX      ConfdString
    MAX-ACCESS  read-only
    STATUS      current
    DESCRIPTION "Total number of Web Image Optimization alpha blend image failed"
    ::= { affirmedServicesContentHttpProxyServiceStatisticsSlotLevelWebImageOptDetailEntry 13 }

affirmedServicesContentHttpProxyServiceStatisticsSlotLevelWebImageOptDetailNumwebimageoptgetsrcimageformatfailed OBJECT-TYPE
    SYNTAX      ConfdString
    MAX-ACCESS  read-only
    STATUS      current
    DESCRIPTION "Total number of Web Image Optimization getting source image format failed"
    ::= { affirmedServicesContentHttpProxyServiceStatisticsSlotLevelWebImageOptDetailEntry 14 }

affirmedServicesContentHttpProxyServiceStatisticsSlotLevelWebImageOptDetailNumwebimageoptgettgtimageformatfailed OBJECT-TYPE
    SYNTAX      ConfdString
    MAX-ACCESS  read-only
    STATUS      current
    DESCRIPTION "Total number of Web Image Optimization getting target image format failed"
    ::= { affirmedServicesContentHttpProxyServiceStatisticsSlotLevelWebImageOptDetailEntry 15 }

affirmedServicesContentHttpProxyServiceStatisticsSlotLevelWebImageOptDetailNumwebimageoptjpegattempts OBJECT-TYPE
    SYNTAX      ConfdString
    MAX-ACCESS  read-only
    STATUS      current
    DESCRIPTION "Total number of Web Image Optimization JPEG Attempts"
    ::= { affirmedServicesContentHttpProxyServiceStatisticsSlotLevelWebImageOptDetailEntry 16 }

affirmedServicesContentHttpProxyServiceStatisticsSlotLevelWebImageOptDetailNumwebimageoptjpegsuccesses OBJECT-TYPE
    SYNTAX      ConfdString
    MAX-ACCESS  read-only
    STATUS      current
    DESCRIPTION "Total number of Web Image Optimization JPEG successes"
    ::= { affirmedServicesContentHttpProxyServiceStatisticsSlotLevelWebImageOptDetailEntry 17 }

affirmedServicesContentHttpProxyServiceStatisticsSlotLevelWebImageOptDetailNumwebimageoptjpegbytesattempt OBJECT-TYPE
    SYNTAX      ConfdString
    MAX-ACCESS  read-only
    STATUS      current
    DESCRIPTION "Total number of Web Image Optimization JPEG bytes attempt to adapt"
    ::= { affirmedServicesContentHttpProxyServiceStatisticsSlotLevelWebImageOptDetailEntry 18 }

affirmedServicesContentHttpProxyServiceStatisticsSlotLevelWebImageOptDetailNumwebimageoptjpegbytesnotadapted OBJECT-TYPE
    SYNTAX      ConfdString
    MAX-ACCESS  read-only
    STATUS      current
    DESCRIPTION "Total number of Web Image Optimization JPEG bytes not adapted"
    ::= { affirmedServicesContentHttpProxyServiceStatisticsSlotLevelWebImageOptDetailEntry 19 }

affirmedServicesContentHttpProxyServiceStatisticsSlotLevelWebImageOptDetailNumwebimageoptjpegbytesadapted OBJECT-TYPE
    SYNTAX      ConfdString
    MAX-ACCESS  read-only
    STATUS      current
    DESCRIPTION "Total number of Web Image Optimization JPEG bytes adapted"
    ::= { affirmedServicesContentHttpProxyServiceStatisticsSlotLevelWebImageOptDetailEntry 20 }

affirmedServicesContentHttpProxyServiceStatisticsSlotLevelWebImageOptDetailNumwebimageoptgifattempts OBJECT-TYPE
    SYNTAX      ConfdString
    MAX-ACCESS  read-only
    STATUS      current
    DESCRIPTION "Total number of Web Image Optimization GIF Attempts"
    ::= { affirmedServicesContentHttpProxyServiceStatisticsSlotLevelWebImageOptDetailEntry 21 }

affirmedServicesContentHttpProxyServiceStatisticsSlotLevelWebImageOptDetailNumwebimageoptgifsuccesses OBJECT-TYPE
    SYNTAX      ConfdString
    MAX-ACCESS  read-only
    STATUS      current
    DESCRIPTION "Total number of Web Image Optimization GIF successes"
    ::= { affirmedServicesContentHttpProxyServiceStatisticsSlotLevelWebImageOptDetailEntry 22 }

affirmedServicesContentHttpProxyServiceStatisticsSlotLevelWebImageOptDetailNumwebimageoptgifbytesattempt OBJECT-TYPE
    SYNTAX      ConfdString
    MAX-ACCESS  read-only
    STATUS      current
    DESCRIPTION "Total number of Web Image Optimization GIF bytes attempt to adapt"
    ::= { affirmedServicesContentHttpProxyServiceStatisticsSlotLevelWebImageOptDetailEntry 23 }

affirmedServicesContentHttpProxyServiceStatisticsSlotLevelWebImageOptDetailNumwebimageoptgifbytesnotadapted OBJECT-TYPE
    SYNTAX      ConfdString
    MAX-ACCESS  read-only
    STATUS      current
    DESCRIPTION "Total number of Web Image Optimization GIF bytes not adapted"
    ::= { affirmedServicesContentHttpProxyServiceStatisticsSlotLevelWebImageOptDetailEntry 24 }

affirmedServicesContentHttpProxyServiceStatisticsSlotLevelWebImageOptDetailNumwebimageoptgifbytesadapted OBJECT-TYPE
    SYNTAX      ConfdString
    MAX-ACCESS  read-only
    STATUS      current
    DESCRIPTION "Total number of Web Image Optimization GIF bytes adapted"
    ::= { affirmedServicesContentHttpProxyServiceStatisticsSlotLevelWebImageOptDetailEntry 25 }

affirmedServicesContentHttpProxyServiceStatisticsSlotLevelWebImageOptDetailNumwebimageoptpngattempts OBJECT-TYPE
    SYNTAX      ConfdString
    MAX-ACCESS  read-only
    STATUS      current
    DESCRIPTION "Total number of Web Image Optimization PNG Attempts"
    ::= { affirmedServicesContentHttpProxyServiceStatisticsSlotLevelWebImageOptDetailEntry 26 }

affirmedServicesContentHttpProxyServiceStatisticsSlotLevelWebImageOptDetailNumwebimageoptpngsuccesses OBJECT-TYPE
    SYNTAX      ConfdString
    MAX-ACCESS  read-only
    STATUS      current
    DESCRIPTION "Total number of Web Image Optimization PNG successes"
    ::= { affirmedServicesContentHttpProxyServiceStatisticsSlotLevelWebImageOptDetailEntry 27 }

affirmedServicesContentHttpProxyServiceStatisticsSlotLevelWebImageOptDetailNumwebimageoptpngbytesattempt OBJECT-TYPE
    SYNTAX      ConfdString
    MAX-ACCESS  read-only
    STATUS      current
    DESCRIPTION "Total number of Web Image Optimization PNG bytes attempt to adapt"
    ::= { affirmedServicesContentHttpProxyServiceStatisticsSlotLevelWebImageOptDetailEntry 28 }

affirmedServicesContentHttpProxyServiceStatisticsSlotLevelWebImageOptDetailNumwebimageoptpngbytesnotadapted OBJECT-TYPE
    SYNTAX      ConfdString
    MAX-ACCESS  read-only
    STATUS      current
    DESCRIPTION "Total number of Web Image Optimization PNG bytes not adapted"
    ::= { affirmedServicesContentHttpProxyServiceStatisticsSlotLevelWebImageOptDetailEntry 29 }

affirmedServicesContentHttpProxyServiceStatisticsSlotLevelWebImageOptDetailNumwebimageoptpngbytesadapted OBJECT-TYPE
    SYNTAX      ConfdString
    MAX-ACCESS  read-only
    STATUS      current
    DESCRIPTION "Total number of Web Image Optimization PNG bytes adapted"
    ::= { affirmedServicesContentHttpProxyServiceStatisticsSlotLevelWebImageOptDetailEntry 30 }

affirmedServicesContentHttpProxyServiceStatisticsSlotLevelWebImageOptDetailNumwebimageoptsrcmaxsizeexceeded OBJECT-TYPE
    SYNTAX      ConfdString
    MAX-ACCESS  read-only
    STATUS      current
    DESCRIPTION "Total number of Web Image Optimization source max size exceeded"
    ::= { affirmedServicesContentHttpProxyServiceStatisticsSlotLevelWebImageOptDetailEntry 31 }

affirmedServicesContentHttpProxyServiceStatisticsSlotLevelWebImageOptDetailNumwebimageoptcontenttypemismatches OBJECT-TYPE
    SYNTAX      ConfdString
    MAX-ACCESS  read-only
    STATUS      current
    DESCRIPTION "Total number of Web Image Optimization with Content-type mismatches"
    ::= { affirmedServicesContentHttpProxyServiceStatisticsSlotLevelWebImageOptDetailEntry 32 }

affirmedServicesContentHttpProxyServiceStatisticsSlotLevelWebImageOptDetailNumwebimageoptcpuoverload OBJECT-TYPE
    SYNTAX      ConfdString
    MAX-ACCESS  read-only
    STATUS      current
    DESCRIPTION "Total number of Web Image Optimization CPU overload"
    ::= { affirmedServicesContentHttpProxyServiceStatisticsSlotLevelWebImageOptDetailEntry 33 }

affirmedServicesContentHttpProxyServiceStatisticsSlotLevelTcpOptzTable OBJECT-TYPE
    SYNTAX      SEQUENCE OF AffirmedServicesContentHttpProxyServiceStatisticsSlotLevelTcpOptzEntry
    MAX-ACCESS  not-accessible
    STATUS      current
    DESCRIPTION ""
    ::= { affirmedServicesContentHttpProxyServiceStatisticsSlotLevel 12 }

affirmedServicesContentHttpProxyServiceStatisticsSlotLevelTcpOptzEntry OBJECT-TYPE
    SYNTAX      AffirmedServicesContentHttpProxyServiceStatisticsSlotLevelTcpOptzEntry
    MAX-ACCESS  not-accessible
    STATUS      current
    DESCRIPTION ""
    INDEX { affirmedServicesContentHttpProxyServiceStatisticsSlotLevelTcpOptzChassis, affirmedServicesContentHttpProxyServiceStatisticsSlotLevelTcpOptzSlot }
        ::= { affirmedServicesContentHttpProxyServiceStatisticsSlotLevelTcpOptzTable 1 }

AffirmedServicesContentHttpProxyServiceStatisticsSlotLevelTcpOptzEntry ::=
    SEQUENCE {
        affirmedServicesContentHttpProxyServiceStatisticsSlotLevelTcpOptzChassis Unsigned32,
        affirmedServicesContentHttpProxyServiceStatisticsSlotLevelTcpOptzSlot INTEGER,
        affirmedServicesContentHttpProxyServiceStatisticsSlotLevelTcpOptzNumtotalclientconnections ConfdString,
        affirmedServicesContentHttpProxyServiceStatisticsSlotLevelTcpOptzNumactiveclientconnections ConfdString,
        affirmedServicesContentHttpProxyServiceStatisticsSlotLevelTcpOptzNumservicedclientconnections ConfdString,
        affirmedServicesContentHttpProxyServiceStatisticsSlotLevelTcpOptzNumfailedservicedclientconnections ConfdString,
        affirmedServicesContentHttpProxyServiceStatisticsSlotLevelTcpOptzNumtotalserverconnections ConfdString,
        affirmedServicesContentHttpProxyServiceStatisticsSlotLevelTcpOptzNumactiveserverconnections ConfdString,
        affirmedServicesContentHttpProxyServiceStatisticsSlotLevelTcpOptzNumservicedserverconnections ConfdString,
        affirmedServicesContentHttpProxyServiceStatisticsSlotLevelTcpOptzNumfailedservicedserverconnections ConfdString,
        affirmedServicesContentHttpProxyServiceStatisticsSlotLevelTcpOptzNumintelligentbufferingapplied ConfdString
    }

affirmedServicesContentHttpProxyServiceStatisticsSlotLevelTcpOptzChassis OBJECT-TYPE
    SYNTAX      Unsigned32
    MAX-ACCESS  not-accessible
    STATUS      current
    DESCRIPTION "chassis ID"
    ::= { affirmedServicesContentHttpProxyServiceStatisticsSlotLevelTcpOptzEntry 1 }

affirmedServicesContentHttpProxyServiceStatisticsSlotLevelTcpOptzSlot OBJECT-TYPE
    SYNTAX      INTEGER {a1(1),a2(2),a3(3),a4(4),a5(5),a6(6),a7(7),a8(8),a9(9),a10(10),a11(11),a12(12),a13(13),a14(14),a15(15),a16(16),a17(17),a18(18),a19(19),a20(20),a21(21),a22(22),a23(23),a24(24),a25(25),a26(26),a27(27),a28(28),a29(29),a30(30),a31(31),a32(32),a33(33),a34(34),a35(35),a36(36),a37(37),a38(38),a39(39),a40(40),a41(41),a42(42),a43(43),a44(44),a45(45),a46(46),a47(47),a48(48),a49(49),a50(50),a51(51),a52(52),a53(53),a54(54),a55(55),a56(56),a57(57),a58(58),a59(59),a60(60),a61(61),a62(62),a63(63),a64(64),a65(65),a66(66),a67(67),a68(68),a69(69),a70(70),a71(71),a72(72),a73(73),a74(74),a75(75),a76(76),a77(77),a78(78),a79(79),a80(80),a81(81),a82(82),a83(83),a84(84),a85(85),a86(86),a87(87),a88(88),a89(89),a90(90),a91(91),a92(92),a93(93),a94(94),a95(95),a96(96),a97(97),a98(98),a99(99),a100(100),a101(101),a102(102),a103(103),a104(104),a105(105),a106(106),a107(107),a108(108),a109(109),a110(110),a111(111),a112(112),a113(113),a114(114),a115(115),a116(116),a117(117),a118(118),a119(119),a120(120),a121(121),a122(122),a123(123),a124(124),a125(125),a126(126),a127(127),a128(128)}
    MAX-ACCESS  not-accessible
    STATUS      current
    DESCRIPTION "slot number"
    ::= { affirmedServicesContentHttpProxyServiceStatisticsSlotLevelTcpOptzEntry 2 }

affirmedServicesContentHttpProxyServiceStatisticsSlotLevelTcpOptzNumtotalclientconnections OBJECT-TYPE
    SYNTAX      ConfdString
    MAX-ACCESS  read-only
    STATUS      current
    DESCRIPTION "Total number of TCP client connections"
    ::= { affirmedServicesContentHttpProxyServiceStatisticsSlotLevelTcpOptzEntry 3 }

affirmedServicesContentHttpProxyServiceStatisticsSlotLevelTcpOptzNumactiveclientconnections OBJECT-TYPE
    SYNTAX      ConfdString
    MAX-ACCESS  read-only
    STATUS      current
    DESCRIPTION "Number of active TCP client connections"
    ::= { affirmedServicesContentHttpProxyServiceStatisticsSlotLevelTcpOptzEntry 4 }

affirmedServicesContentHttpProxyServiceStatisticsSlotLevelTcpOptzNumservicedclientconnections OBJECT-TYPE
    SYNTAX      ConfdString
    MAX-ACCESS  read-only
    STATUS      current
    DESCRIPTION "Number of client connections that TCP Optimization Service applied"
    ::= { affirmedServicesContentHttpProxyServiceStatisticsSlotLevelTcpOptzEntry 5 }

affirmedServicesContentHttpProxyServiceStatisticsSlotLevelTcpOptzNumfailedservicedclientconnections OBJECT-TYPE
    SYNTAX      ConfdString
    MAX-ACCESS  read-only
    STATUS      current
    DESCRIPTION "Number of tcp client connections that failed applying TCP Optimization service"
    ::= { affirmedServicesContentHttpProxyServiceStatisticsSlotLevelTcpOptzEntry 6 }

affirmedServicesContentHttpProxyServiceStatisticsSlotLevelTcpOptzNumtotalserverconnections OBJECT-TYPE
    SYNTAX      ConfdString
    MAX-ACCESS  read-only
    STATUS      current
    DESCRIPTION "Total number of TCP server connections"
    ::= { affirmedServicesContentHttpProxyServiceStatisticsSlotLevelTcpOptzEntry 7 }

affirmedServicesContentHttpProxyServiceStatisticsSlotLevelTcpOptzNumactiveserverconnections OBJECT-TYPE
    SYNTAX      ConfdString
    MAX-ACCESS  read-only
    STATUS      current
    DESCRIPTION "Number of active TCP server connections"
    ::= { affirmedServicesContentHttpProxyServiceStatisticsSlotLevelTcpOptzEntry 8 }

affirmedServicesContentHttpProxyServiceStatisticsSlotLevelTcpOptzNumservicedserverconnections OBJECT-TYPE
    SYNTAX      ConfdString
    MAX-ACCESS  read-only
    STATUS      current
    DESCRIPTION "Number of server connections that TCP Optimization Service applied"
    ::= { affirmedServicesContentHttpProxyServiceStatisticsSlotLevelTcpOptzEntry 9 }

affirmedServicesContentHttpProxyServiceStatisticsSlotLevelTcpOptzNumfailedservicedserverconnections OBJECT-TYPE
    SYNTAX      ConfdString
    MAX-ACCESS  read-only
    STATUS      current
    DESCRIPTION "Number of tcp server connections that failed applying TCP Optimization service"
    ::= { affirmedServicesContentHttpProxyServiceStatisticsSlotLevelTcpOptzEntry 10 }

affirmedServicesContentHttpProxyServiceStatisticsSlotLevelTcpOptzNumintelligentbufferingapplied OBJECT-TYPE
    SYNTAX      ConfdString
    MAX-ACCESS  read-only
    STATUS      current
    DESCRIPTION "Number of tcp server connections that applied intelligent buffering service"
    ::= { affirmedServicesContentHttpProxyServiceStatisticsSlotLevelTcpOptzEntry 11 }

affirmedServicesContentHttpProxyServiceStatisticsSlotLevelDnsResolutionTable OBJECT-TYPE
    SYNTAX      SEQUENCE OF AffirmedServicesContentHttpProxyServiceStatisticsSlotLevelDnsResolutionEntry
    MAX-ACCESS  not-accessible
    STATUS      current
    DESCRIPTION ""
    ::= { affirmedServicesContentHttpProxyServiceStatisticsSlotLevel 13 }

affirmedServicesContentHttpProxyServiceStatisticsSlotLevelDnsResolutionEntry OBJECT-TYPE
    SYNTAX      AffirmedServicesContentHttpProxyServiceStatisticsSlotLevelDnsResolutionEntry
    MAX-ACCESS  not-accessible
    STATUS      current
    DESCRIPTION ""
    INDEX { affirmedServicesContentHttpProxyServiceStatisticsSlotLevelDnsResolutionChassis, affirmedServicesContentHttpProxyServiceStatisticsSlotLevelDnsResolutionSlot }
        ::= { affirmedServicesContentHttpProxyServiceStatisticsSlotLevelDnsResolutionTable 1 }

AffirmedServicesContentHttpProxyServiceStatisticsSlotLevelDnsResolutionEntry ::=
    SEQUENCE {
        affirmedServicesContentHttpProxyServiceStatisticsSlotLevelDnsResolutionChassis Unsigned32,
        affirmedServicesContentHttpProxyServiceStatisticsSlotLevelDnsResolutionSlot INTEGER,
        affirmedServicesContentHttpProxyServiceStatisticsSlotLevelDnsResolutionNumdnsresolutiontotal ConfdString,
        affirmedServicesContentHttpProxyServiceStatisticsSlotLevelDnsResolutionNumdnsresolutioncurrent ConfdString,
        affirmedServicesContentHttpProxyServiceStatisticsSlotLevelDnsResolutionNumdnsresolutionsuccess ConfdString,
        affirmedServicesContentHttpProxyServiceStatisticsSlotLevelDnsResolutionNumdnsresolutionfail ConfdString,
        affirmedServicesContentHttpProxyServiceStatisticsSlotLevelDnsResolutionNumdnsresolutionv4attempts ConfdString,
        affirmedServicesContentHttpProxyServiceStatisticsSlotLevelDnsResolutionNumdnsresolutionv6attempts ConfdString,
        affirmedServicesContentHttpProxyServiceStatisticsSlotLevelDnsResolutionNumdnsresolutionv4v6attempts ConfdString,
        affirmedServicesContentHttpProxyServiceStatisticsSlotLevelDnsResolutionNumdnsresolutioncached ConfdString,
        affirmedServicesContentHttpProxyServiceStatisticsSlotLevelDnsResolutionNumdnsresolutionv4results ConfdString,
        affirmedServicesContentHttpProxyServiceStatisticsSlotLevelDnsResolutionNumdnsresolutionv6results ConfdString,
        affirmedServicesContentHttpProxyServiceStatisticsSlotLevelDnsResolutionNumdnsresolutionv4v6results ConfdString,
        affirmedServicesContentHttpProxyServiceStatisticsSlotLevelDnsResolutionNumdnsresolutiondropped ConfdString,
        affirmedServicesContentHttpProxyServiceStatisticsSlotLevelDnsResolutionNumdnsresolutioncanceled ConfdString,
        affirmedServicesContentHttpProxyServiceStatisticsSlotLevelDnsResolutionNumdnsresolutionnoreach ConfdString,
        affirmedServicesContentHttpProxyServiceStatisticsSlotLevelDnsResolutionNumdnsresolutiontimeout ConfdString,
        affirmedServicesContentHttpProxyServiceStatisticsSlotLevelDnsResolutionNumdnsresolutionnodata ConfdString,
        affirmedServicesContentHttpProxyServiceStatisticsSlotLevelDnsResolutionNumdnsresolutionnotfound ConfdString,
        affirmedServicesContentHttpProxyServiceStatisticsSlotLevelDnsResolutionNumdnsresolutionrefused ConfdString,
        affirmedServicesContentHttpProxyServiceStatisticsSlotLevelDnsResolutionNumdnsresolutionothers ConfdString
    }

affirmedServicesContentHttpProxyServiceStatisticsSlotLevelDnsResolutionChassis OBJECT-TYPE
    SYNTAX      Unsigned32
    MAX-ACCESS  not-accessible
    STATUS      current
    DESCRIPTION "chassis ID"
    ::= { affirmedServicesContentHttpProxyServiceStatisticsSlotLevelDnsResolutionEntry 1 }

affirmedServicesContentHttpProxyServiceStatisticsSlotLevelDnsResolutionSlot OBJECT-TYPE
    SYNTAX      INTEGER {a1(1),a2(2),a3(3),a4(4),a5(5),a6(6),a7(7),a8(8),a9(9),a10(10),a11(11),a12(12),a13(13),a14(14),a15(15),a16(16),a17(17),a18(18),a19(19),a20(20),a21(21),a22(22),a23(23),a24(24),a25(25),a26(26),a27(27),a28(28),a29(29),a30(30),a31(31),a32(32),a33(33),a34(34),a35(35),a36(36),a37(37),a38(38),a39(39),a40(40),a41(41),a42(42),a43(43),a44(44),a45(45),a46(46),a47(47),a48(48),a49(49),a50(50),a51(51),a52(52),a53(53),a54(54),a55(55),a56(56),a57(57),a58(58),a59(59),a60(60),a61(61),a62(62),a63(63),a64(64),a65(65),a66(66),a67(67),a68(68),a69(69),a70(70),a71(71),a72(72),a73(73),a74(74),a75(75),a76(76),a77(77),a78(78),a79(79),a80(80),a81(81),a82(82),a83(83),a84(84),a85(85),a86(86),a87(87),a88(88),a89(89),a90(90),a91(91),a92(92),a93(93),a94(94),a95(95),a96(96),a97(97),a98(98),a99(99),a100(100),a101(101),a102(102),a103(103),a104(104),a105(105),a106(106),a107(107),a108(108),a109(109),a110(110),a111(111),a112(112),a113(113),a114(114),a115(115),a116(116),a117(117),a118(118),a119(119),a120(120),a121(121),a122(122),a123(123),a124(124),a125(125),a126(126),a127(127),a128(128)}
    MAX-ACCESS  not-accessible
    STATUS      current
    DESCRIPTION "slot number"
    ::= { affirmedServicesContentHttpProxyServiceStatisticsSlotLevelDnsResolutionEntry 2 }

affirmedServicesContentHttpProxyServiceStatisticsSlotLevelDnsResolutionNumdnsresolutiontotal OBJECT-TYPE
    SYNTAX      ConfdString
    MAX-ACCESS  read-only
    STATUS      current
    DESCRIPTION "Total number of DNS Resolution Query Attempts"
    ::= { affirmedServicesContentHttpProxyServiceStatisticsSlotLevelDnsResolutionEntry 3 }

affirmedServicesContentHttpProxyServiceStatisticsSlotLevelDnsResolutionNumdnsresolutioncurrent OBJECT-TYPE
    SYNTAX      ConfdString
    MAX-ACCESS  read-only
    STATUS      current
    DESCRIPTION "Current number of DNS Resolution Query IPv4 Attempts"
    ::= { affirmedServicesContentHttpProxyServiceStatisticsSlotLevelDnsResolutionEntry 4 }

affirmedServicesContentHttpProxyServiceStatisticsSlotLevelDnsResolutionNumdnsresolutionsuccess OBJECT-TYPE
    SYNTAX      ConfdString
    MAX-ACCESS  read-only
    STATUS      current
    DESCRIPTION "Total number of DNS Resolution Query Success"
    ::= { affirmedServicesContentHttpProxyServiceStatisticsSlotLevelDnsResolutionEntry 5 }

affirmedServicesContentHttpProxyServiceStatisticsSlotLevelDnsResolutionNumdnsresolutionfail OBJECT-TYPE
    SYNTAX      ConfdString
    MAX-ACCESS  read-only
    STATUS      current
    DESCRIPTION "Total number of DNS Resolution Query Failures"
    ::= { affirmedServicesContentHttpProxyServiceStatisticsSlotLevelDnsResolutionEntry 6 }

affirmedServicesContentHttpProxyServiceStatisticsSlotLevelDnsResolutionNumdnsresolutionv4attempts OBJECT-TYPE
    SYNTAX      ConfdString
    MAX-ACCESS  read-only
    STATUS      current
    DESCRIPTION "Total number of DNS Resolution Query IPv4 Requests"
    ::= { affirmedServicesContentHttpProxyServiceStatisticsSlotLevelDnsResolutionEntry 7 }

affirmedServicesContentHttpProxyServiceStatisticsSlotLevelDnsResolutionNumdnsresolutionv6attempts OBJECT-TYPE
    SYNTAX      ConfdString
    MAX-ACCESS  read-only
    STATUS      current
    DESCRIPTION "Total number of DNS Resolution Query IPv6 Requests"
    ::= { affirmedServicesContentHttpProxyServiceStatisticsSlotLevelDnsResolutionEntry 8 }

affirmedServicesContentHttpProxyServiceStatisticsSlotLevelDnsResolutionNumdnsresolutionv4v6attempts OBJECT-TYPE
    SYNTAX      ConfdString
    MAX-ACCESS  read-only
    STATUS      current
    DESCRIPTION "Total number of DNS Resolution Query IPv4v6 Requests"
    ::= { affirmedServicesContentHttpProxyServiceStatisticsSlotLevelDnsResolutionEntry 9 }

affirmedServicesContentHttpProxyServiceStatisticsSlotLevelDnsResolutionNumdnsresolutioncached OBJECT-TYPE
    SYNTAX      ConfdString
    MAX-ACCESS  read-only
    STATUS      current
    DESCRIPTION "Total number of DNS Resolution Query Cache Hit Results"
    ::= { affirmedServicesContentHttpProxyServiceStatisticsSlotLevelDnsResolutionEntry 10 }

affirmedServicesContentHttpProxyServiceStatisticsSlotLevelDnsResolutionNumdnsresolutionv4results OBJECT-TYPE
    SYNTAX      ConfdString
    MAX-ACCESS  read-only
    STATUS      current
    DESCRIPTION "Total number of DNS Resolution Query IPv4 Results"
    ::= { affirmedServicesContentHttpProxyServiceStatisticsSlotLevelDnsResolutionEntry 11 }

affirmedServicesContentHttpProxyServiceStatisticsSlotLevelDnsResolutionNumdnsresolutionv6results OBJECT-TYPE
    SYNTAX      ConfdString
    MAX-ACCESS  read-only
    STATUS      current
    DESCRIPTION "Total number of DNS Resolution Query IPv6 Results"
    ::= { affirmedServicesContentHttpProxyServiceStatisticsSlotLevelDnsResolutionEntry 12 }

affirmedServicesContentHttpProxyServiceStatisticsSlotLevelDnsResolutionNumdnsresolutionv4v6results OBJECT-TYPE
    SYNTAX      ConfdString
    MAX-ACCESS  read-only
    STATUS      current
    DESCRIPTION "Total number of DNS Resolution Query IPv4v6 Results"
    ::= { affirmedServicesContentHttpProxyServiceStatisticsSlotLevelDnsResolutionEntry 13 }

affirmedServicesContentHttpProxyServiceStatisticsSlotLevelDnsResolutionNumdnsresolutiondropped OBJECT-TYPE
    SYNTAX      ConfdString
    MAX-ACCESS  read-only
    STATUS      current
    DESCRIPTION "Total number of DNS Resolution Query Dropped, Not Sent"
    ::= { affirmedServicesContentHttpProxyServiceStatisticsSlotLevelDnsResolutionEntry 14 }

affirmedServicesContentHttpProxyServiceStatisticsSlotLevelDnsResolutionNumdnsresolutioncanceled OBJECT-TYPE
    SYNTAX      ConfdString
    MAX-ACCESS  read-only
    STATUS      current
    DESCRIPTION "Total number of DNS Resolution Query Canceled"
    ::= { affirmedServicesContentHttpProxyServiceStatisticsSlotLevelDnsResolutionEntry 15 }

affirmedServicesContentHttpProxyServiceStatisticsSlotLevelDnsResolutionNumdnsresolutionnoreach OBJECT-TYPE
    SYNTAX      ConfdString
    MAX-ACCESS  read-only
    STATUS      current
    DESCRIPTION "Total number of DNS Resolution Server Not-Reachable"
    ::= { affirmedServicesContentHttpProxyServiceStatisticsSlotLevelDnsResolutionEntry 16 }

affirmedServicesContentHttpProxyServiceStatisticsSlotLevelDnsResolutionNumdnsresolutiontimeout OBJECT-TYPE
    SYNTAX      ConfdString
    MAX-ACCESS  read-only
    STATUS      current
    DESCRIPTION "Total number of DNS Resolution Response Timeout"
    ::= { affirmedServicesContentHttpProxyServiceStatisticsSlotLevelDnsResolutionEntry 17 }

affirmedServicesContentHttpProxyServiceStatisticsSlotLevelDnsResolutionNumdnsresolutionnodata OBJECT-TYPE
    SYNTAX      ConfdString
    MAX-ACCESS  read-only
    STATUS      current
    DESCRIPTION "Total number of DNS Resolution Response No Data"
    ::= { affirmedServicesContentHttpProxyServiceStatisticsSlotLevelDnsResolutionEntry 18 }

affirmedServicesContentHttpProxyServiceStatisticsSlotLevelDnsResolutionNumdnsresolutionnotfound OBJECT-TYPE
    SYNTAX      ConfdString
    MAX-ACCESS  read-only
    STATUS      current
    DESCRIPTION "Total number of DNS Resolution Response Name Not Found"
    ::= { affirmedServicesContentHttpProxyServiceStatisticsSlotLevelDnsResolutionEntry 19 }

affirmedServicesContentHttpProxyServiceStatisticsSlotLevelDnsResolutionNumdnsresolutionrefused OBJECT-TYPE
    SYNTAX      ConfdString
    MAX-ACCESS  read-only
    STATUS      current
    DESCRIPTION "Total number of DNS Resolution Response Server Refused"
    ::= { affirmedServicesContentHttpProxyServiceStatisticsSlotLevelDnsResolutionEntry 20 }

affirmedServicesContentHttpProxyServiceStatisticsSlotLevelDnsResolutionNumdnsresolutionothers OBJECT-TYPE
    SYNTAX      ConfdString
    MAX-ACCESS  read-only
    STATUS      current
    DESCRIPTION "Total number of DNS Resolution Response Dailure With Other Reason"
    ::= { affirmedServicesContentHttpProxyServiceStatisticsSlotLevelDnsResolutionEntry 21 }

affirmedServicesContentHttpProxyServiceStatisticsSlotLevelTlsTable OBJECT-TYPE
    SYNTAX      SEQUENCE OF AffirmedServicesContentHttpProxyServiceStatisticsSlotLevelTlsEntry
    MAX-ACCESS  not-accessible
    STATUS      current
    DESCRIPTION ""
    ::= { affirmedServicesContentHttpProxyServiceStatisticsSlotLevel 14 }

affirmedServicesContentHttpProxyServiceStatisticsSlotLevelTlsEntry OBJECT-TYPE
    SYNTAX      AffirmedServicesContentHttpProxyServiceStatisticsSlotLevelTlsEntry
    MAX-ACCESS  not-accessible
    STATUS      current
    DESCRIPTION ""
    INDEX { affirmedServicesContentHttpProxyServiceStatisticsSlotLevelTlsChassis, affirmedServicesContentHttpProxyServiceStatisticsSlotLevelTlsSlot }
        ::= { affirmedServicesContentHttpProxyServiceStatisticsSlotLevelTlsTable 1 }

AffirmedServicesContentHttpProxyServiceStatisticsSlotLevelTlsEntry ::=
    SEQUENCE {
        affirmedServicesContentHttpProxyServiceStatisticsSlotLevelTlsChassis Unsigned32,
        affirmedServicesContentHttpProxyServiceStatisticsSlotLevelTlsSlot Unsigned32,
        affirmedServicesContentHttpProxyServiceStatisticsSlotLevelTlsNumtotalclientconnections ConfdString,
        affirmedServicesContentHttpProxyServiceStatisticsSlotLevelTlsNumcurrentclientconnections ConfdString,
        affirmedServicesContentHttpProxyServiceStatisticsSlotLevelTlsNumtermclientconnections ConfdString,
        affirmedServicesContentHttpProxyServiceStatisticsSlotLevelTlsNumipv4clientconnections ConfdString,
        affirmedServicesContentHttpProxyServiceStatisticsSlotLevelTlsNumipv6clientconnections ConfdString,
        affirmedServicesContentHttpProxyServiceStatisticsSlotLevelTlsNumclientbytesrecvd ConfdString,
        affirmedServicesContentHttpProxyServiceStatisticsSlotLevelTlsNumclientbytessent ConfdString,
        affirmedServicesContentHttpProxyServiceStatisticsSlotLevelTlsNumclientprototlsv10 ConfdString,
        affirmedServicesContentHttpProxyServiceStatisticsSlotLevelTlsNumclientprototlsv11 ConfdString,
        affirmedServicesContentHttpProxyServiceStatisticsSlotLevelTlsNumclientprototlsv12 ConfdString,
        affirmedServicesContentHttpProxyServiceStatisticsSlotLevelTlsNumclienttlserrors ConfdString,
        affirmedServicesContentHttpProxyServiceStatisticsSlotLevelTlsNumclientfderrors ConfdString,
        affirmedServicesContentHttpProxyServiceStatisticsSlotLevelTlsNumclienthandshakeerrors ConfdString,
        affirmedServicesContentHttpProxyServiceStatisticsSlotLevelTlsNumclientreaderrors ConfdString,
        affirmedServicesContentHttpProxyServiceStatisticsSlotLevelTlsNumclientwriteerrors ConfdString,
        affirmedServicesContentHttpProxyServiceStatisticsSlotLevelTlsNumtotalserverconnections ConfdString,
        affirmedServicesContentHttpProxyServiceStatisticsSlotLevelTlsNumcurrentserverconnections ConfdString,
        affirmedServicesContentHttpProxyServiceStatisticsSlotLevelTlsNumorigserverconnections ConfdString,
        affirmedServicesContentHttpProxyServiceStatisticsSlotLevelTlsNumipv4serverconnections ConfdString,
        affirmedServicesContentHttpProxyServiceStatisticsSlotLevelTlsNumipv6serverconnections ConfdString,
        affirmedServicesContentHttpProxyServiceStatisticsSlotLevelTlsNumserverbytesrecvd ConfdString,
        affirmedServicesContentHttpProxyServiceStatisticsSlotLevelTlsNumserverbytessent ConfdString,
        affirmedServicesContentHttpProxyServiceStatisticsSlotLevelTlsNumservertlsv10 ConfdString,
        affirmedServicesContentHttpProxyServiceStatisticsSlotLevelTlsNumservertlsv11 ConfdString,
        affirmedServicesContentHttpProxyServiceStatisticsSlotLevelTlsNumservertlsv12 ConfdString,
        affirmedServicesContentHttpProxyServiceStatisticsSlotLevelTlsNumservertlserror ConfdString,
        affirmedServicesContentHttpProxyServiceStatisticsSlotLevelTlsNumserverfderrors ConfdString,
        affirmedServicesContentHttpProxyServiceStatisticsSlotLevelTlsNumserverhandshakeerrors ConfdString,
        affirmedServicesContentHttpProxyServiceStatisticsSlotLevelTlsNumserverautherrors ConfdString,
        affirmedServicesContentHttpProxyServiceStatisticsSlotLevelTlsNumserverreaderrors ConfdString,
        affirmedServicesContentHttpProxyServiceStatisticsSlotLevelTlsNumserverwriteerrors ConfdString
    }

affirmedServicesContentHttpProxyServiceStatisticsSlotLevelTlsChassis OBJECT-TYPE
    SYNTAX      Unsigned32
    MAX-ACCESS  not-accessible
    STATUS      current
    DESCRIPTION "chassis ID"
    ::= { affirmedServicesContentHttpProxyServiceStatisticsSlotLevelTlsEntry 1 }

affirmedServicesContentHttpProxyServiceStatisticsSlotLevelTlsSlot OBJECT-TYPE
    SYNTAX      Unsigned32
    MAX-ACCESS  not-accessible
    STATUS      current
    DESCRIPTION "slot number"
    ::= { affirmedServicesContentHttpProxyServiceStatisticsSlotLevelTlsEntry 2 }

affirmedServicesContentHttpProxyServiceStatisticsSlotLevelTlsNumtotalclientconnections OBJECT-TYPE
    SYNTAX      ConfdString
    MAX-ACCESS  read-only
    STATUS      current
    DESCRIPTION "Total number of client connections"
    ::= { affirmedServicesContentHttpProxyServiceStatisticsSlotLevelTlsEntry 3 }

affirmedServicesContentHttpProxyServiceStatisticsSlotLevelTlsNumcurrentclientconnections OBJECT-TYPE
    SYNTAX      ConfdString
    MAX-ACCESS  read-only
    STATUS      current
    DESCRIPTION "Total number of client connections currently in use"
    ::= { affirmedServicesContentHttpProxyServiceStatisticsSlotLevelTlsEntry 4 }

affirmedServicesContentHttpProxyServiceStatisticsSlotLevelTlsNumtermclientconnections OBJECT-TYPE
    SYNTAX      ConfdString
    MAX-ACCESS  read-only
    STATUS      current
    DESCRIPTION "Total number of terminated connections"
    ::= { affirmedServicesContentHttpProxyServiceStatisticsSlotLevelTlsEntry 5 }

affirmedServicesContentHttpProxyServiceStatisticsSlotLevelTlsNumipv4clientconnections OBJECT-TYPE
    SYNTAX      ConfdString
    MAX-ACCESS  read-only
    STATUS      current
    DESCRIPTION "Total number of IPv4 client connections"
    ::= { affirmedServicesContentHttpProxyServiceStatisticsSlotLevelTlsEntry 6 }

affirmedServicesContentHttpProxyServiceStatisticsSlotLevelTlsNumipv6clientconnections OBJECT-TYPE
    SYNTAX      ConfdString
    MAX-ACCESS  read-only
    STATUS      current
    DESCRIPTION "Total number of IPv6 client connections"
    ::= { affirmedServicesContentHttpProxyServiceStatisticsSlotLevelTlsEntry 7 }

affirmedServicesContentHttpProxyServiceStatisticsSlotLevelTlsNumclientbytesrecvd OBJECT-TYPE
    SYNTAX      ConfdString
    MAX-ACCESS  read-only
    STATUS      current
    DESCRIPTION "Total number of bytes received from client"
    ::= { affirmedServicesContentHttpProxyServiceStatisticsSlotLevelTlsEntry 8 }

affirmedServicesContentHttpProxyServiceStatisticsSlotLevelTlsNumclientbytessent OBJECT-TYPE
    SYNTAX      ConfdString
    MAX-ACCESS  read-only
    STATUS      current
    DESCRIPTION "Total number of bytes sent to client"
    ::= { affirmedServicesContentHttpProxyServiceStatisticsSlotLevelTlsEntry 9 }

affirmedServicesContentHttpProxyServiceStatisticsSlotLevelTlsNumclientprototlsv10 OBJECT-TYPE
    SYNTAX      ConfdString
    MAX-ACCESS  read-only
    STATUS      current
    DESCRIPTION "Total number of TLS1.0 client requests received"
    ::= { affirmedServicesContentHttpProxyServiceStatisticsSlotLevelTlsEntry 10 }

affirmedServicesContentHttpProxyServiceStatisticsSlotLevelTlsNumclientprototlsv11 OBJECT-TYPE
    SYNTAX      ConfdString
    MAX-ACCESS  read-only
    STATUS      current
    DESCRIPTION "Total number of TLS1.1 client requests received"
    ::= { affirmedServicesContentHttpProxyServiceStatisticsSlotLevelTlsEntry 11 }

affirmedServicesContentHttpProxyServiceStatisticsSlotLevelTlsNumclientprototlsv12 OBJECT-TYPE
    SYNTAX      ConfdString
    MAX-ACCESS  read-only
    STATUS      current
    DESCRIPTION "Total number of TLS1.2 client requests received"
    ::= { affirmedServicesContentHttpProxyServiceStatisticsSlotLevelTlsEntry 12 }

affirmedServicesContentHttpProxyServiceStatisticsSlotLevelTlsNumclienttlserrors OBJECT-TYPE
    SYNTAX      ConfdString
    MAX-ACCESS  read-only
    STATUS      current
    DESCRIPTION "Total number of Client TLS Errors"
    ::= { affirmedServicesContentHttpProxyServiceStatisticsSlotLevelTlsEntry 13 }

affirmedServicesContentHttpProxyServiceStatisticsSlotLevelTlsNumclientfderrors OBJECT-TYPE
    SYNTAX      ConfdString
    MAX-ACCESS  read-only
    STATUS      current
    DESCRIPTION "Total number of Client set FD Errors"
    ::= { affirmedServicesContentHttpProxyServiceStatisticsSlotLevelTlsEntry 14 }

affirmedServicesContentHttpProxyServiceStatisticsSlotLevelTlsNumclienthandshakeerrors OBJECT-TYPE
    SYNTAX      ConfdString
    MAX-ACCESS  read-only
    STATUS      current
    DESCRIPTION "Total number of Client handshake Errors"
    ::= { affirmedServicesContentHttpProxyServiceStatisticsSlotLevelTlsEntry 15 }

affirmedServicesContentHttpProxyServiceStatisticsSlotLevelTlsNumclientreaderrors OBJECT-TYPE
    SYNTAX      ConfdString
    MAX-ACCESS  read-only
    STATUS      current
    DESCRIPTION "Total number of Client read Errors"
    ::= { affirmedServicesContentHttpProxyServiceStatisticsSlotLevelTlsEntry 16 }

affirmedServicesContentHttpProxyServiceStatisticsSlotLevelTlsNumclientwriteerrors OBJECT-TYPE
    SYNTAX      ConfdString
    MAX-ACCESS  read-only
    STATUS      current
    DESCRIPTION "Total number of Client write Errors"
    ::= { affirmedServicesContentHttpProxyServiceStatisticsSlotLevelTlsEntry 17 }

affirmedServicesContentHttpProxyServiceStatisticsSlotLevelTlsNumtotalserverconnections OBJECT-TYPE
    SYNTAX      ConfdString
    MAX-ACCESS  read-only
    STATUS      current
    DESCRIPTION "Total number of server connections"
    ::= { affirmedServicesContentHttpProxyServiceStatisticsSlotLevelTlsEntry 18 }

affirmedServicesContentHttpProxyServiceStatisticsSlotLevelTlsNumcurrentserverconnections OBJECT-TYPE
    SYNTAX      ConfdString
    MAX-ACCESS  read-only
    STATUS      current
    DESCRIPTION "Total number of server connections currently in use"
    ::= { affirmedServicesContentHttpProxyServiceStatisticsSlotLevelTlsEntry 19 }

affirmedServicesContentHttpProxyServiceStatisticsSlotLevelTlsNumorigserverconnections OBJECT-TYPE
    SYNTAX      ConfdString
    MAX-ACCESS  read-only
    STATUS      current
    DESCRIPTION "Total number of originated connections"
    ::= { affirmedServicesContentHttpProxyServiceStatisticsSlotLevelTlsEntry 20 }

affirmedServicesContentHttpProxyServiceStatisticsSlotLevelTlsNumipv4serverconnections OBJECT-TYPE
    SYNTAX      ConfdString
    MAX-ACCESS  read-only
    STATUS      current
    DESCRIPTION "Total number of IPv4 server connections"
    ::= { affirmedServicesContentHttpProxyServiceStatisticsSlotLevelTlsEntry 21 }

affirmedServicesContentHttpProxyServiceStatisticsSlotLevelTlsNumipv6serverconnections OBJECT-TYPE
    SYNTAX      ConfdString
    MAX-ACCESS  read-only
    STATUS      current
    DESCRIPTION "Total number of IPv6 server connections"
    ::= { affirmedServicesContentHttpProxyServiceStatisticsSlotLevelTlsEntry 22 }

affirmedServicesContentHttpProxyServiceStatisticsSlotLevelTlsNumserverbytesrecvd OBJECT-TYPE
    SYNTAX      ConfdString
    MAX-ACCESS  read-only
    STATUS      current
    DESCRIPTION "Total number of bytes received from server"
    ::= { affirmedServicesContentHttpProxyServiceStatisticsSlotLevelTlsEntry 23 }

affirmedServicesContentHttpProxyServiceStatisticsSlotLevelTlsNumserverbytessent OBJECT-TYPE
    SYNTAX      ConfdString
    MAX-ACCESS  read-only
    STATUS      current
    DESCRIPTION "Total number of bytes sent to server"
    ::= { affirmedServicesContentHttpProxyServiceStatisticsSlotLevelTlsEntry 24 }

affirmedServicesContentHttpProxyServiceStatisticsSlotLevelTlsNumservertlsv10 OBJECT-TYPE
    SYNTAX      ConfdString
    MAX-ACCESS  read-only
    STATUS      current
    DESCRIPTION "Total number of TLS1.0 server requests sent"
    ::= { affirmedServicesContentHttpProxyServiceStatisticsSlotLevelTlsEntry 25 }

affirmedServicesContentHttpProxyServiceStatisticsSlotLevelTlsNumservertlsv11 OBJECT-TYPE
    SYNTAX      ConfdString
    MAX-ACCESS  read-only
    STATUS      current
    DESCRIPTION "Total number of TLS1.1 server requests sent"
    ::= { affirmedServicesContentHttpProxyServiceStatisticsSlotLevelTlsEntry 26 }

affirmedServicesContentHttpProxyServiceStatisticsSlotLevelTlsNumservertlsv12 OBJECT-TYPE
    SYNTAX      ConfdString
    MAX-ACCESS  read-only
    STATUS      current
    DESCRIPTION "Total number of TLS1.2 server requests sent"
    ::= { affirmedServicesContentHttpProxyServiceStatisticsSlotLevelTlsEntry 27 }

affirmedServicesContentHttpProxyServiceStatisticsSlotLevelTlsNumservertlserror OBJECT-TYPE
    SYNTAX      ConfdString
    MAX-ACCESS  read-only
    STATUS      current
    DESCRIPTION "Total number of Server TLS Errors"
    ::= { affirmedServicesContentHttpProxyServiceStatisticsSlotLevelTlsEntry 28 }

affirmedServicesContentHttpProxyServiceStatisticsSlotLevelTlsNumserverfderrors OBJECT-TYPE
    SYNTAX      ConfdString
    MAX-ACCESS  read-only
    STATUS      current
    DESCRIPTION "Total number of Server set FD Errors"
    ::= { affirmedServicesContentHttpProxyServiceStatisticsSlotLevelTlsEntry 29 }

affirmedServicesContentHttpProxyServiceStatisticsSlotLevelTlsNumserverhandshakeerrors OBJECT-TYPE
    SYNTAX      ConfdString
    MAX-ACCESS  read-only
    STATUS      current
    DESCRIPTION "Total number of server handshake Errors"
    ::= { affirmedServicesContentHttpProxyServiceStatisticsSlotLevelTlsEntry 30 }

affirmedServicesContentHttpProxyServiceStatisticsSlotLevelTlsNumserverautherrors OBJECT-TYPE
    SYNTAX      ConfdString
    MAX-ACCESS  read-only
    STATUS      current
    DESCRIPTION "Total number of server authentication Errors"
    ::= { affirmedServicesContentHttpProxyServiceStatisticsSlotLevelTlsEntry 31 }

affirmedServicesContentHttpProxyServiceStatisticsSlotLevelTlsNumserverreaderrors OBJECT-TYPE
    SYNTAX      ConfdString
    MAX-ACCESS  read-only
    STATUS      current
    DESCRIPTION "Total number of Server read Errors"
    ::= { affirmedServicesContentHttpProxyServiceStatisticsSlotLevelTlsEntry 32 }

affirmedServicesContentHttpProxyServiceStatisticsSlotLevelTlsNumserverwriteerrors OBJECT-TYPE
    SYNTAX      ConfdString
    MAX-ACCESS  read-only
    STATUS      current
    DESCRIPTION "Total number of Server write Errors"
    ::= { affirmedServicesContentHttpProxyServiceStatisticsSlotLevelTlsEntry 33 }

affirmedServicesContentHttpProxyServiceStatisticsSlotLevelUrlRWTable OBJECT-TYPE
    SYNTAX      SEQUENCE OF AffirmedServicesContentHttpProxyServiceStatisticsSlotLevelUrlRWEntry
    MAX-ACCESS  not-accessible
    STATUS      current
    DESCRIPTION ""
    ::= { affirmedServicesContentHttpProxyServiceStatisticsSlotLevel 15 }

affirmedServicesContentHttpProxyServiceStatisticsSlotLevelUrlRWEntry OBJECT-TYPE
    SYNTAX      AffirmedServicesContentHttpProxyServiceStatisticsSlotLevelUrlRWEntry
    MAX-ACCESS  not-accessible
    STATUS      current
    DESCRIPTION ""
    INDEX { affirmedServicesContentHttpProxyServiceStatisticsSlotLevelUrlRWChassis, affirmedServicesContentHttpProxyServiceStatisticsSlotLevelUrlRWSlot }
        ::= { affirmedServicesContentHttpProxyServiceStatisticsSlotLevelUrlRWTable 1 }

AffirmedServicesContentHttpProxyServiceStatisticsSlotLevelUrlRWEntry ::=
    SEQUENCE {
        affirmedServicesContentHttpProxyServiceStatisticsSlotLevelUrlRWChassis Unsigned32,
        affirmedServicesContentHttpProxyServiceStatisticsSlotLevelUrlRWSlot Unsigned32,
        affirmedServicesContentHttpProxyServiceStatisticsSlotLevelUrlRWNumurlrwattempts ConfdString,
        affirmedServicesContentHttpProxyServiceStatisticsSlotLevelUrlRWNumurlrwsuccess ConfdString,
        affirmedServicesContentHttpProxyServiceStatisticsSlotLevelUrlRWNumurlrwdnslkupv4attempts ConfdString,
        affirmedServicesContentHttpProxyServiceStatisticsSlotLevelUrlRWNumurlrwdnslkupv6attempts ConfdString,
        affirmedServicesContentHttpProxyServiceStatisticsSlotLevelUrlRWNumurlrwdnslkupv4success ConfdString,
        affirmedServicesContentHttpProxyServiceStatisticsSlotLevelUrlRWNumurlrwdnslkupv6success ConfdString,
        affirmedServicesContentHttpProxyServiceStatisticsSlotLevelUrlRWNumurlrwdnslkupv4v6attempts ConfdString
    }

affirmedServicesContentHttpProxyServiceStatisticsSlotLevelUrlRWChassis OBJECT-TYPE
    SYNTAX      Unsigned32
    MAX-ACCESS  not-accessible
    STATUS      current
    DESCRIPTION "chassis ID"
    ::= { affirmedServicesContentHttpProxyServiceStatisticsSlotLevelUrlRWEntry 1 }

affirmedServicesContentHttpProxyServiceStatisticsSlotLevelUrlRWSlot OBJECT-TYPE
    SYNTAX      Unsigned32
    MAX-ACCESS  not-accessible
    STATUS      current
    DESCRIPTION "slot number"
    ::= { affirmedServicesContentHttpProxyServiceStatisticsSlotLevelUrlRWEntry 2 }

affirmedServicesContentHttpProxyServiceStatisticsSlotLevelUrlRWNumurlrwattempts OBJECT-TYPE
    SYNTAX      ConfdString
    MAX-ACCESS  read-only
    STATUS      current
    DESCRIPTION "Total number of url-rewrite attempts"
    ::= { affirmedServicesContentHttpProxyServiceStatisticsSlotLevelUrlRWEntry 3 }

affirmedServicesContentHttpProxyServiceStatisticsSlotLevelUrlRWNumurlrwsuccess OBJECT-TYPE
    SYNTAX      ConfdString
    MAX-ACCESS  read-only
    STATUS      current
    DESCRIPTION "Total number of url-rewrite Successes"
    ::= { affirmedServicesContentHttpProxyServiceStatisticsSlotLevelUrlRWEntry 4 }

affirmedServicesContentHttpProxyServiceStatisticsSlotLevelUrlRWNumurlrwdnslkupv4attempts OBJECT-TYPE
    SYNTAX      ConfdString
    MAX-ACCESS  read-only
    STATUS      current
    DESCRIPTION "Total number of url-rewrite DNS lookup IPv4 attempts"
    ::= { affirmedServicesContentHttpProxyServiceStatisticsSlotLevelUrlRWEntry 5 }

affirmedServicesContentHttpProxyServiceStatisticsSlotLevelUrlRWNumurlrwdnslkupv6attempts OBJECT-TYPE
    SYNTAX      ConfdString
    MAX-ACCESS  read-only
    STATUS      current
    DESCRIPTION "Total number of url-rewrite DNS lookup IPv6 attempts"
    ::= { affirmedServicesContentHttpProxyServiceStatisticsSlotLevelUrlRWEntry 6 }

affirmedServicesContentHttpProxyServiceStatisticsSlotLevelUrlRWNumurlrwdnslkupv4success OBJECT-TYPE
    SYNTAX      ConfdString
    MAX-ACCESS  read-only
    STATUS      current
    DESCRIPTION "Total number of url-rewrite DNS lookup IPv4 success"
    ::= { affirmedServicesContentHttpProxyServiceStatisticsSlotLevelUrlRWEntry 7 }

affirmedServicesContentHttpProxyServiceStatisticsSlotLevelUrlRWNumurlrwdnslkupv6success OBJECT-TYPE
    SYNTAX      ConfdString
    MAX-ACCESS  read-only
    STATUS      current
    DESCRIPTION "Total number of url-rewrite DNS lookup IPv6 success"
    ::= { affirmedServicesContentHttpProxyServiceStatisticsSlotLevelUrlRWEntry 8 }

affirmedServicesContentHttpProxyServiceStatisticsSlotLevelUrlRWNumurlrwdnslkupv4v6attempts OBJECT-TYPE
    SYNTAX      ConfdString
    MAX-ACCESS  read-only
    STATUS      current
    DESCRIPTION "Total number of url-rewrite DNS lookup IPv4v6 attempts"
    ::= { affirmedServicesContentHttpProxyServiceStatisticsSlotLevelUrlRWEntry 9 }

affirmedServicesContentHttpProxyServiceStatisticsSlotLevelBefTable OBJECT-TYPE
    SYNTAX      SEQUENCE OF AffirmedServicesContentHttpProxyServiceStatisticsSlotLevelBefEntry
    MAX-ACCESS  not-accessible
    STATUS      current
    DESCRIPTION ""
    ::= { affirmedServicesContentHttpProxyServiceStatisticsSlotLevel 16 }

affirmedServicesContentHttpProxyServiceStatisticsSlotLevelBefEntry OBJECT-TYPE
    SYNTAX      AffirmedServicesContentHttpProxyServiceStatisticsSlotLevelBefEntry
    MAX-ACCESS  not-accessible
    STATUS      current
    DESCRIPTION ""
    INDEX { affirmedServicesContentHttpProxyServiceStatisticsSlotLevelBefChassis, affirmedServicesContentHttpProxyServiceStatisticsSlotLevelBefSlot }
        ::= { affirmedServicesContentHttpProxyServiceStatisticsSlotLevelBefTable 1 }

AffirmedServicesContentHttpProxyServiceStatisticsSlotLevelBefEntry ::=
    SEQUENCE {
        affirmedServicesContentHttpProxyServiceStatisticsSlotLevelBefChassis Unsigned32,
        affirmedServicesContentHttpProxyServiceStatisticsSlotLevelBefSlot Unsigned32,
        affirmedServicesContentHttpProxyServiceStatisticsSlotLevelBefNumbefrequestprocessedlocally ConfdString,
        affirmedServicesContentHttpProxyServiceStatisticsSlotLevelBefNumbefrequestredirectsuccess ConfdString,
        affirmedServicesContentHttpProxyServiceStatisticsSlotLevelBefNumbefrequestredirectfail ConfdString,
        affirmedServicesContentHttpProxyServiceStatisticsSlotLevelBefNumbefrequestredirectreceived ConfdString,
        affirmedServicesContentHttpProxyServiceStatisticsSlotLevelBefNumbefresponseredirectsuccess ConfdString,
        affirmedServicesContentHttpProxyServiceStatisticsSlotLevelBefNumbefresponseredirectfail ConfdString,
        affirmedServicesContentHttpProxyServiceStatisticsSlotLevelBefNumbefresponseredirectreceived ConfdString,
        affirmedServicesContentHttpProxyServiceStatisticsSlotLevelBefNumbefcurrentlyidleconnections ConfdString,
        affirmedServicesContentHttpProxyServiceStatisticsSlotLevelBefNumbefreusedconnections ConfdString
    }

affirmedServicesContentHttpProxyServiceStatisticsSlotLevelBefChassis OBJECT-TYPE
    SYNTAX      Unsigned32
    MAX-ACCESS  not-accessible
    STATUS      current
    DESCRIPTION "chassis ID"
    ::= { affirmedServicesContentHttpProxyServiceStatisticsSlotLevelBefEntry 1 }

affirmedServicesContentHttpProxyServiceStatisticsSlotLevelBefSlot OBJECT-TYPE
    SYNTAX      Unsigned32
    MAX-ACCESS  not-accessible
    STATUS      current
    DESCRIPTION "slot number"
    ::= { affirmedServicesContentHttpProxyServiceStatisticsSlotLevelBefEntry 2 }

affirmedServicesContentHttpProxyServiceStatisticsSlotLevelBefNumbefrequestprocessedlocally OBJECT-TYPE
    SYNTAX      ConfdString
    MAX-ACCESS  read-only
    STATUS      current
    DESCRIPTION "Total number of requests not redirected but processed locally"
    ::= { affirmedServicesContentHttpProxyServiceStatisticsSlotLevelBefEntry 3 }

affirmedServicesContentHttpProxyServiceStatisticsSlotLevelBefNumbefrequestredirectsuccess OBJECT-TYPE
    SYNTAX      ConfdString
    MAX-ACCESS  read-only
    STATUS      current
    DESCRIPTION "Total number of back-end forwarding request redirection successes"
    ::= { affirmedServicesContentHttpProxyServiceStatisticsSlotLevelBefEntry 4 }

affirmedServicesContentHttpProxyServiceStatisticsSlotLevelBefNumbefrequestredirectfail OBJECT-TYPE
    SYNTAX      ConfdString
    MAX-ACCESS  read-only
    STATUS      current
    DESCRIPTION "Total number of back-end forwarding request redirection failures"
    ::= { affirmedServicesContentHttpProxyServiceStatisticsSlotLevelBefEntry 5 }

affirmedServicesContentHttpProxyServiceStatisticsSlotLevelBefNumbefrequestredirectreceived OBJECT-TYPE
    SYNTAX      ConfdString
    MAX-ACCESS  read-only
    STATUS      current
    DESCRIPTION "Total number of back-end forwarding request redirections received"
    ::= { affirmedServicesContentHttpProxyServiceStatisticsSlotLevelBefEntry 6 }

affirmedServicesContentHttpProxyServiceStatisticsSlotLevelBefNumbefresponseredirectsuccess OBJECT-TYPE
    SYNTAX      ConfdString
    MAX-ACCESS  read-only
    STATUS      current
    DESCRIPTION "Total number of back-end forwarding response redirection successes"
    ::= { affirmedServicesContentHttpProxyServiceStatisticsSlotLevelBefEntry 7 }

affirmedServicesContentHttpProxyServiceStatisticsSlotLevelBefNumbefresponseredirectfail OBJECT-TYPE
    SYNTAX      ConfdString
    MAX-ACCESS  read-only
    STATUS      current
    DESCRIPTION "Total number of back-end forwarding response redirection failures"
    ::= { affirmedServicesContentHttpProxyServiceStatisticsSlotLevelBefEntry 8 }

affirmedServicesContentHttpProxyServiceStatisticsSlotLevelBefNumbefresponseredirectreceived OBJECT-TYPE
    SYNTAX      ConfdString
    MAX-ACCESS  read-only
    STATUS      current
    DESCRIPTION "Total number of back-end forwarding response redirections received"
    ::= { affirmedServicesContentHttpProxyServiceStatisticsSlotLevelBefEntry 9 }

affirmedServicesContentHttpProxyServiceStatisticsSlotLevelBefNumbefcurrentlyidleconnections OBJECT-TYPE
    SYNTAX      ConfdString
    MAX-ACCESS  read-only
    STATUS      current
    DESCRIPTION "The number of BEF connections in the idle connection pool"
    ::= { affirmedServicesContentHttpProxyServiceStatisticsSlotLevelBefEntry 10 }

affirmedServicesContentHttpProxyServiceStatisticsSlotLevelBefNumbefreusedconnections OBJECT-TYPE
    SYNTAX      ConfdString
    MAX-ACCESS  read-only
    STATUS      current
    DESCRIPTION "The number of times idle BEF connections were reused"
    ::= { affirmedServicesContentHttpProxyServiceStatisticsSlotLevelBefEntry 11 }

affirmedServicesContentHttpProxyServiceStatisticsSlotLevelPremptDnsTable OBJECT-TYPE
    SYNTAX      SEQUENCE OF AffirmedServicesContentHttpProxyServiceStatisticsSlotLevelPremptDnsEntry
    MAX-ACCESS  not-accessible
    STATUS      current
    DESCRIPTION ""
    ::= { affirmedServicesContentHttpProxyServiceStatisticsSlotLevel 17 }

affirmedServicesContentHttpProxyServiceStatisticsSlotLevelPremptDnsEntry OBJECT-TYPE
    SYNTAX      AffirmedServicesContentHttpProxyServiceStatisticsSlotLevelPremptDnsEntry
    MAX-ACCESS  not-accessible
    STATUS      current
    DESCRIPTION ""
    INDEX { affirmedServicesContentHttpProxyServiceStatisticsSlotLevelPremptDnsChassis, affirmedServicesContentHttpProxyServiceStatisticsSlotLevelPremptDnsSlot }
        ::= { affirmedServicesContentHttpProxyServiceStatisticsSlotLevelPremptDnsTable 1 }

AffirmedServicesContentHttpProxyServiceStatisticsSlotLevelPremptDnsEntry ::=
    SEQUENCE {
        affirmedServicesContentHttpProxyServiceStatisticsSlotLevelPremptDnsChassis Unsigned32,
        affirmedServicesContentHttpProxyServiceStatisticsSlotLevelPremptDnsSlot Unsigned32,
        affirmedServicesContentHttpProxyServiceStatisticsSlotLevelPremptDnsNumpremptdnsrsptotal ConfdString,
        affirmedServicesContentHttpProxyServiceStatisticsSlotLevelPremptDnsNumpremptdnsrspurlrwtotal ConfdString,
        affirmedServicesContentHttpProxyServiceStatisticsSlotLevelPremptDnsNumpremptdnsrspbypass ConfdString,
        affirmedServicesContentHttpProxyServiceStatisticsSlotLevelPremptDnsNumpremptdnsrspchunked ConfdString,
        affirmedServicesContentHttpProxyServiceStatisticsSlotLevelPremptDnsNumpremptdnsreqrecvdtotal ConfdString,
        affirmedServicesContentHttpProxyServiceStatisticsSlotLevelPremptDnsNumpremptdnsreqsrvdtotal ConfdString,
        affirmedServicesContentHttpProxyServiceStatisticsSlotLevelPremptDnsNumpremptdnsreqfailtotal ConfdString
    }

affirmedServicesContentHttpProxyServiceStatisticsSlotLevelPremptDnsChassis OBJECT-TYPE
    SYNTAX      Unsigned32
    MAX-ACCESS  not-accessible
    STATUS      current
    DESCRIPTION "chassis ID"
    ::= { affirmedServicesContentHttpProxyServiceStatisticsSlotLevelPremptDnsEntry 1 }

affirmedServicesContentHttpProxyServiceStatisticsSlotLevelPremptDnsSlot OBJECT-TYPE
    SYNTAX      Unsigned32
    MAX-ACCESS  not-accessible
    STATUS      current
    DESCRIPTION "slot number"
    ::= { affirmedServicesContentHttpProxyServiceStatisticsSlotLevelPremptDnsEntry 2 }

affirmedServicesContentHttpProxyServiceStatisticsSlotLevelPremptDnsNumpremptdnsrsptotal OBJECT-TYPE
    SYNTAX      ConfdString
    MAX-ACCESS  read-only
    STATUS      current
    DESCRIPTION "Total number of HTTP Response applied preemptive-dns"
    ::= { affirmedServicesContentHttpProxyServiceStatisticsSlotLevelPremptDnsEntry 3 }

affirmedServicesContentHttpProxyServiceStatisticsSlotLevelPremptDnsNumpremptdnsrspurlrwtotal OBJECT-TYPE
    SYNTAX      ConfdString
    MAX-ACCESS  read-only
    STATUS      current
    DESCRIPTION "Total number URL rewrote in HTTP Response"
    ::= { affirmedServicesContentHttpProxyServiceStatisticsSlotLevelPremptDnsEntry 4 }

affirmedServicesContentHttpProxyServiceStatisticsSlotLevelPremptDnsNumpremptdnsrspbypass OBJECT-TYPE
    SYNTAX      ConfdString
    MAX-ACCESS  read-only
    STATUS      current
    DESCRIPTION "Total number of Responses dropping content-length header"
    ::= { affirmedServicesContentHttpProxyServiceStatisticsSlotLevelPremptDnsEntry 5 }

affirmedServicesContentHttpProxyServiceStatisticsSlotLevelPremptDnsNumpremptdnsrspchunked OBJECT-TYPE
    SYNTAX      ConfdString
    MAX-ACCESS  read-only
    STATUS      current
    DESCRIPTION "Total number of Responses got chunked"
    ::= { affirmedServicesContentHttpProxyServiceStatisticsSlotLevelPremptDnsEntry 6 }

affirmedServicesContentHttpProxyServiceStatisticsSlotLevelPremptDnsNumpremptdnsreqrecvdtotal OBJECT-TYPE
    SYNTAX      ConfdString
    MAX-ACCESS  read-only
    STATUS      current
    DESCRIPTION "Total number of Updated Requests Received"
    ::= { affirmedServicesContentHttpProxyServiceStatisticsSlotLevelPremptDnsEntry 7 }

affirmedServicesContentHttpProxyServiceStatisticsSlotLevelPremptDnsNumpremptdnsreqsrvdtotal OBJECT-TYPE
    SYNTAX      ConfdString
    MAX-ACCESS  read-only
    STATUS      current
    DESCRIPTION "Total number of Updated Requests Serviced"
    ::= { affirmedServicesContentHttpProxyServiceStatisticsSlotLevelPremptDnsEntry 8 }

affirmedServicesContentHttpProxyServiceStatisticsSlotLevelPremptDnsNumpremptdnsreqfailtotal OBJECT-TYPE
    SYNTAX      ConfdString
    MAX-ACCESS  read-only
    STATUS      current
    DESCRIPTION "Total number of Updated Requests Failed Service"
    ::= { affirmedServicesContentHttpProxyServiceStatisticsSlotLevelPremptDnsEntry 9 }

affirmedServicesContentHttpProxyServiceStatisticsSlotLevelFraudDetectionTable OBJECT-TYPE
    SYNTAX      SEQUENCE OF AffirmedServicesContentHttpProxyServiceStatisticsSlotLevelFraudDetectionEntry
    MAX-ACCESS  not-accessible
    STATUS      current
    DESCRIPTION ""
    ::= { affirmedServicesContentHttpProxyServiceStatisticsSlotLevel 18 }

affirmedServicesContentHttpProxyServiceStatisticsSlotLevelFraudDetectionEntry OBJECT-TYPE
    SYNTAX      AffirmedServicesContentHttpProxyServiceStatisticsSlotLevelFraudDetectionEntry
    MAX-ACCESS  not-accessible
    STATUS      current
    DESCRIPTION ""
    INDEX { affirmedServicesContentHttpProxyServiceStatisticsSlotLevelFraudDetectionChassis, affirmedServicesContentHttpProxyServiceStatisticsSlotLevelFraudDetectionSlot }
        ::= { affirmedServicesContentHttpProxyServiceStatisticsSlotLevelFraudDetectionTable 1 }

AffirmedServicesContentHttpProxyServiceStatisticsSlotLevelFraudDetectionEntry ::=
    SEQUENCE {
        affirmedServicesContentHttpProxyServiceStatisticsSlotLevelFraudDetectionChassis Unsigned32,
        affirmedServicesContentHttpProxyServiceStatisticsSlotLevelFraudDetectionSlot Unsigned32,
        affirmedServicesContentHttpProxyServiceStatisticsSlotLevelFraudDetectionNumfrauddetectionreq ConfdString,
        affirmedServicesContentHttpProxyServiceStatisticsSlotLevelFraudDetectionNumfrauddetectionreqnonfraud ConfdString,
        affirmedServicesContentHttpProxyServiceStatisticsSlotLevelFraudDetectionNumfrauddetectionreqfraud ConfdString,
        affirmedServicesContentHttpProxyServiceStatisticsSlotLevelFraudDetectionNumfrauddetectionreqfraudheader ConfdString,
        affirmedServicesContentHttpProxyServiceStatisticsSlotLevelFraudDetectionNumfrauddetectionreqfrauddns ConfdString,
        affirmedServicesContentHttpProxyServiceStatisticsSlotLevelFraudDetectionNumfrauddetectionreqfraudallowed ConfdString,
        affirmedServicesContentHttpProxyServiceStatisticsSlotLevelFraudDetectionNumfrauddetectionreqfraudblocked ConfdString
    }

affirmedServicesContentHttpProxyServiceStatisticsSlotLevelFraudDetectionChassis OBJECT-TYPE
    SYNTAX      Unsigned32
    MAX-ACCESS  not-accessible
    STATUS      current
    DESCRIPTION "chassis ID"
    ::= { affirmedServicesContentHttpProxyServiceStatisticsSlotLevelFraudDetectionEntry 1 }

affirmedServicesContentHttpProxyServiceStatisticsSlotLevelFraudDetectionSlot OBJECT-TYPE
    SYNTAX      Unsigned32
    MAX-ACCESS  not-accessible
    STATUS      current
    DESCRIPTION "slot number"
    ::= { affirmedServicesContentHttpProxyServiceStatisticsSlotLevelFraudDetectionEntry 2 }

affirmedServicesContentHttpProxyServiceStatisticsSlotLevelFraudDetectionNumfrauddetectionreq OBJECT-TYPE
    SYNTAX      ConfdString
    MAX-ACCESS  read-only
    STATUS      current
    DESCRIPTION "Total number of Request Validation Attempts"
    ::= { affirmedServicesContentHttpProxyServiceStatisticsSlotLevelFraudDetectionEntry 3 }

affirmedServicesContentHttpProxyServiceStatisticsSlotLevelFraudDetectionNumfrauddetectionreqnonfraud OBJECT-TYPE
    SYNTAX      ConfdString
    MAX-ACCESS  read-only
    STATUS      current
    DESCRIPTION "Total number of Non-Fraudulent Requests"
    ::= { affirmedServicesContentHttpProxyServiceStatisticsSlotLevelFraudDetectionEntry 4 }

affirmedServicesContentHttpProxyServiceStatisticsSlotLevelFraudDetectionNumfrauddetectionreqfraud OBJECT-TYPE
    SYNTAX      ConfdString
    MAX-ACCESS  read-only
    STATUS      current
    DESCRIPTION "Total number of Fraudulent Requests"
    ::= { affirmedServicesContentHttpProxyServiceStatisticsSlotLevelFraudDetectionEntry 5 }

affirmedServicesContentHttpProxyServiceStatisticsSlotLevelFraudDetectionNumfrauddetectionreqfraudheader OBJECT-TYPE
    SYNTAX      ConfdString
    MAX-ACCESS  read-only
    STATUS      current
    DESCRIPTION "Total number of Request Header Consistency Check Failures"
    ::= { affirmedServicesContentHttpProxyServiceStatisticsSlotLevelFraudDetectionEntry 6 }

affirmedServicesContentHttpProxyServiceStatisticsSlotLevelFraudDetectionNumfrauddetectionreqfrauddns OBJECT-TYPE
    SYNTAX      ConfdString
    MAX-ACCESS  read-only
    STATUS      current
    DESCRIPTION "Total number of Request DNS Check Failures"
    ::= { affirmedServicesContentHttpProxyServiceStatisticsSlotLevelFraudDetectionEntry 7 }

affirmedServicesContentHttpProxyServiceStatisticsSlotLevelFraudDetectionNumfrauddetectionreqfraudallowed OBJECT-TYPE
    SYNTAX      ConfdString
    MAX-ACCESS  read-only
    STATUS      current
    DESCRIPTION "Total number of Fraudulent Requests Allowed"
    ::= { affirmedServicesContentHttpProxyServiceStatisticsSlotLevelFraudDetectionEntry 8 }

affirmedServicesContentHttpProxyServiceStatisticsSlotLevelFraudDetectionNumfrauddetectionreqfraudblocked OBJECT-TYPE
    SYNTAX      ConfdString
    MAX-ACCESS  read-only
    STATUS      current
    DESCRIPTION "Total number of Fraudulent Requests Blocked"
    ::= { affirmedServicesContentHttpProxyServiceStatisticsSlotLevelFraudDetectionEntry 9 }

affirmedServicesContentHttpProxyServiceStatisticsSlotLevelVideoTable OBJECT-TYPE
    SYNTAX      SEQUENCE OF AffirmedServicesContentHttpProxyServiceStatisticsSlotLevelVideoEntry
    MAX-ACCESS  not-accessible
    STATUS      current
    DESCRIPTION ""
    ::= { affirmedServicesContentHttpProxyServiceStatisticsSlotLevel 19 }

affirmedServicesContentHttpProxyServiceStatisticsSlotLevelVideoEntry OBJECT-TYPE
    SYNTAX      AffirmedServicesContentHttpProxyServiceStatisticsSlotLevelVideoEntry
    MAX-ACCESS  not-accessible
    STATUS      current
    DESCRIPTION ""
    INDEX { affirmedServicesContentHttpProxyServiceStatisticsSlotLevelVideoChassis, affirmedServicesContentHttpProxyServiceStatisticsSlotLevelVideoSlot }
        ::= { affirmedServicesContentHttpProxyServiceStatisticsSlotLevelVideoTable 1 }

AffirmedServicesContentHttpProxyServiceStatisticsSlotLevelVideoEntry ::=
    SEQUENCE {
        affirmedServicesContentHttpProxyServiceStatisticsSlotLevelVideoChassis Unsigned32,
        affirmedServicesContentHttpProxyServiceStatisticsSlotLevelVideoSlot INTEGER,
        affirmedServicesContentHttpProxyServiceStatisticsSlotLevelVideoVideoattempts ConfdString,
        affirmedServicesContentHttpProxyServiceStatisticsSlotLevelVideoVideosuccesses ConfdString,
        affirmedServicesContentHttpProxyServiceStatisticsSlotLevelVideoVideosuccessescached ConfdString,
        affirmedServicesContentHttpProxyServiceStatisticsSlotLevelVideoVideoservedfromcache ConfdString,
        affirmedServicesContentHttpProxyServiceStatisticsSlotLevelVideoVideoaborts ConfdString,
        affirmedServicesContentHttpProxyServiceStatisticsSlotLevelVideoVideofailures ConfdString,
        affirmedServicesContentHttpProxyServiceStatisticsSlotLevelVideoVideoseekrequests ConfdString,
        affirmedServicesContentHttpProxyServiceStatisticsSlotLevelVideoFlvvideosuccesses ConfdString,
        affirmedServicesContentHttpProxyServiceStatisticsSlotLevelVideoFlvvideosuccessescached ConfdString,
        affirmedServicesContentHttpProxyServiceStatisticsSlotLevelVideoFlvvideoservedfromcache ConfdString,
        affirmedServicesContentHttpProxyServiceStatisticsSlotLevelVideoFlvvideoaborts ConfdString,
        affirmedServicesContentHttpProxyServiceStatisticsSlotLevelVideoMp4videosuccesses ConfdString,
        affirmedServicesContentHttpProxyServiceStatisticsSlotLevelVideoMp4videosuccessescached ConfdString,
        affirmedServicesContentHttpProxyServiceStatisticsSlotLevelVideoMp4videoservedfromcache ConfdString,
        affirmedServicesContentHttpProxyServiceStatisticsSlotLevelVideoMp4videoaborts ConfdString,
        affirmedServicesContentHttpProxyServiceStatisticsSlotLevelVideoDailymotionvideosuccesses ConfdString,
        affirmedServicesContentHttpProxyServiceStatisticsSlotLevelVideoDailymotionvideosuccessescached ConfdString,
        affirmedServicesContentHttpProxyServiceStatisticsSlotLevelVideoDailymotionvideoservedfromcache ConfdString,
        affirmedServicesContentHttpProxyServiceStatisticsSlotLevelVideoDailymotionvideoaborts ConfdString,
        affirmedServicesContentHttpProxyServiceStatisticsSlotLevelVideoMetacafevideosuccesses ConfdString,
        affirmedServicesContentHttpProxyServiceStatisticsSlotLevelVideoMetacafevideosuccessescached ConfdString,
        affirmedServicesContentHttpProxyServiceStatisticsSlotLevelVideoMetacafevideoservedfromcache ConfdString,
        affirmedServicesContentHttpProxyServiceStatisticsSlotLevelVideoMetacafevideoaborts ConfdString,
        affirmedServicesContentHttpProxyServiceStatisticsSlotLevelVideoVideosizemin ConfdString,
        affirmedServicesContentHttpProxyServiceStatisticsSlotLevelVideoVideosizemax ConfdString,
        affirmedServicesContentHttpProxyServiceStatisticsSlotLevelVideoVideosizeaverage ConfdString,
        affirmedServicesContentHttpProxyServiceStatisticsSlotLevelVideoVideosizetotal ConfdString,
        affirmedServicesContentHttpProxyServiceStatisticsSlotLevelVideoFlvvideosizemin ConfdString,
        affirmedServicesContentHttpProxyServiceStatisticsSlotLevelVideoFlvvideosizemax ConfdString,
        affirmedServicesContentHttpProxyServiceStatisticsSlotLevelVideoFlvvideosizeaverage ConfdString,
        affirmedServicesContentHttpProxyServiceStatisticsSlotLevelVideoFlvvideosizetotal ConfdString,
        affirmedServicesContentHttpProxyServiceStatisticsSlotLevelVideoMp4videosizemin ConfdString,
        affirmedServicesContentHttpProxyServiceStatisticsSlotLevelVideoMp4videosizemax ConfdString,
        affirmedServicesContentHttpProxyServiceStatisticsSlotLevelVideoMp4videosizeaverage ConfdString,
        affirmedServicesContentHttpProxyServiceStatisticsSlotLevelVideoMp4videosizetotal ConfdString,
        affirmedServicesContentHttpProxyServiceStatisticsSlotLevelVideoFlvvideodurationmin ConfdString,
        affirmedServicesContentHttpProxyServiceStatisticsSlotLevelVideoFlvvideodurationmax ConfdString,
        affirmedServicesContentHttpProxyServiceStatisticsSlotLevelVideoFlvvideodurationaverage ConfdString,
        affirmedServicesContentHttpProxyServiceStatisticsSlotLevelVideoFlvvideodurationtotal ConfdString,
        affirmedServicesContentHttpProxyServiceStatisticsSlotLevelVideoMp4videodurationmin ConfdString,
        affirmedServicesContentHttpProxyServiceStatisticsSlotLevelVideoMp4videodurationmax ConfdString,
        affirmedServicesContentHttpProxyServiceStatisticsSlotLevelVideoMp4videodurationaverage ConfdString,
        affirmedServicesContentHttpProxyServiceStatisticsSlotLevelVideoMp4videodurationtotal ConfdString,
        affirmedServicesContentHttpProxyServiceStatisticsSlotLevelVideoVideoservedbytesfromcache ConfdString,
        affirmedServicesContentHttpProxyServiceStatisticsSlotLevelVideoVideopacedrequests ConfdString,
        affirmedServicesContentHttpProxyServiceStatisticsSlotLevelVideoVideosizepacedtotal ConfdString,
        affirmedServicesContentHttpProxyServiceStatisticsSlotLevelVideoVideosizepacedsent ConfdString,
        affirmedServicesContentHttpProxyServiceStatisticsSlotLevelVideoWebmvideosuccesses ConfdString,
        affirmedServicesContentHttpProxyServiceStatisticsSlotLevelVideoWebmvideosuccessescached ConfdString,
        affirmedServicesContentHttpProxyServiceStatisticsSlotLevelVideoWebmvideoservedfromcache ConfdString,
        affirmedServicesContentHttpProxyServiceStatisticsSlotLevelVideoWebmvideoaborts ConfdString,
        affirmedServicesContentHttpProxyServiceStatisticsSlotLevelVideoWebmvideosizemin ConfdString,
        affirmedServicesContentHttpProxyServiceStatisticsSlotLevelVideoWebmvideosizemax ConfdString,
        affirmedServicesContentHttpProxyServiceStatisticsSlotLevelVideoWebmvideosizeaverage ConfdString,
        affirmedServicesContentHttpProxyServiceStatisticsSlotLevelVideoWebmvideosizetotal ConfdString,
        affirmedServicesContentHttpProxyServiceStatisticsSlotLevelVideoWebmvideodurationmin ConfdString,
        affirmedServicesContentHttpProxyServiceStatisticsSlotLevelVideoWebmvideodurationmax ConfdString,
        affirmedServicesContentHttpProxyServiceStatisticsSlotLevelVideoWebmvideodurationaverage ConfdString,
        affirmedServicesContentHttpProxyServiceStatisticsSlotLevelVideoWebmvideodurationtotal ConfdString
    }

affirmedServicesContentHttpProxyServiceStatisticsSlotLevelVideoChassis OBJECT-TYPE
    SYNTAX      Unsigned32
    MAX-ACCESS  not-accessible
    STATUS      current
    DESCRIPTION "chassis ID"
    ::= { affirmedServicesContentHttpProxyServiceStatisticsSlotLevelVideoEntry 1 }

affirmedServicesContentHttpProxyServiceStatisticsSlotLevelVideoSlot OBJECT-TYPE
    SYNTAX      INTEGER {a1(1),a2(2),a3(3),a4(4),a5(5),a6(6),a7(7),a8(8),a9(9),a10(10),a11(11),a12(12),a13(13),a14(14),a15(15),a16(16),a17(17),a18(18),a19(19),a20(20),a21(21),a22(22),a23(23),a24(24),a25(25),a26(26),a27(27),a28(28),a29(29),a30(30),a31(31),a32(32),a33(33),a34(34),a35(35),a36(36),a37(37),a38(38),a39(39),a40(40),a41(41),a42(42),a43(43),a44(44),a45(45),a46(46),a47(47),a48(48),a49(49),a50(50),a51(51),a52(52),a53(53),a54(54),a55(55),a56(56),a57(57),a58(58),a59(59),a60(60),a61(61),a62(62),a63(63),a64(64),a65(65),a66(66),a67(67),a68(68),a69(69),a70(70),a71(71),a72(72),a73(73),a74(74),a75(75),a76(76),a77(77),a78(78),a79(79),a80(80),a81(81),a82(82),a83(83),a84(84),a85(85),a86(86),a87(87),a88(88),a89(89),a90(90),a91(91),a92(92),a93(93),a94(94),a95(95),a96(96),a97(97),a98(98),a99(99),a100(100),a101(101),a102(102),a103(103),a104(104),a105(105),a106(106),a107(107),a108(108),a109(109),a110(110),a111(111),a112(112),a113(113),a114(114),a115(115),a116(116),a117(117),a118(118),a119(119),a120(120),a121(121),a122(122),a123(123),a124(124),a125(125),a126(126),a127(127),a128(128)}
    MAX-ACCESS  not-accessible
    STATUS      current
    DESCRIPTION "slot number"
    ::= { affirmedServicesContentHttpProxyServiceStatisticsSlotLevelVideoEntry 2 }

affirmedServicesContentHttpProxyServiceStatisticsSlotLevelVideoVideoattempts OBJECT-TYPE
    SYNTAX      ConfdString
    MAX-ACCESS  read-only
    STATUS      current
    DESCRIPTION "Number of video attempts"
    ::= { affirmedServicesContentHttpProxyServiceStatisticsSlotLevelVideoEntry 3 }

affirmedServicesContentHttpProxyServiceStatisticsSlotLevelVideoVideosuccesses OBJECT-TYPE
    SYNTAX      ConfdString
    MAX-ACCESS  read-only
    STATUS      current
    DESCRIPTION "Number of video successes"
    ::= { affirmedServicesContentHttpProxyServiceStatisticsSlotLevelVideoEntry 4 }

affirmedServicesContentHttpProxyServiceStatisticsSlotLevelVideoVideosuccessescached OBJECT-TYPE
    SYNTAX      ConfdString
    MAX-ACCESS  read-only
    STATUS      current
    DESCRIPTION "Number of video successes cached"
    ::= { affirmedServicesContentHttpProxyServiceStatisticsSlotLevelVideoEntry 5 }

affirmedServicesContentHttpProxyServiceStatisticsSlotLevelVideoVideoservedfromcache OBJECT-TYPE
    SYNTAX      ConfdString
    MAX-ACCESS  read-only
    STATUS      current
    DESCRIPTION "Number of video served from cache"
    ::= { affirmedServicesContentHttpProxyServiceStatisticsSlotLevelVideoEntry 6 }

affirmedServicesContentHttpProxyServiceStatisticsSlotLevelVideoVideoaborts OBJECT-TYPE
    SYNTAX      ConfdString
    MAX-ACCESS  read-only
    STATUS      current
    DESCRIPTION "Number of video aborts"
    ::= { affirmedServicesContentHttpProxyServiceStatisticsSlotLevelVideoEntry 7 }

affirmedServicesContentHttpProxyServiceStatisticsSlotLevelVideoVideofailures OBJECT-TYPE
    SYNTAX      ConfdString
    MAX-ACCESS  read-only
    STATUS      current
    DESCRIPTION "Number of video failures"
    ::= { affirmedServicesContentHttpProxyServiceStatisticsSlotLevelVideoEntry 8 }

affirmedServicesContentHttpProxyServiceStatisticsSlotLevelVideoVideoseekrequests OBJECT-TYPE
    SYNTAX      ConfdString
    MAX-ACCESS  read-only
    STATUS      current
    DESCRIPTION "Number of video seek requests"
    ::= { affirmedServicesContentHttpProxyServiceStatisticsSlotLevelVideoEntry 9 }

affirmedServicesContentHttpProxyServiceStatisticsSlotLevelVideoFlvvideosuccesses OBJECT-TYPE
    SYNTAX      ConfdString
    MAX-ACCESS  read-only
    STATUS      current
    DESCRIPTION "Number of FLV video successes"
    ::= { affirmedServicesContentHttpProxyServiceStatisticsSlotLevelVideoEntry 10 }

affirmedServicesContentHttpProxyServiceStatisticsSlotLevelVideoFlvvideosuccessescached OBJECT-TYPE
    SYNTAX      ConfdString
    MAX-ACCESS  read-only
    STATUS      current
    DESCRIPTION "Number of FLV video successes cached"
    ::= { affirmedServicesContentHttpProxyServiceStatisticsSlotLevelVideoEntry 11 }

affirmedServicesContentHttpProxyServiceStatisticsSlotLevelVideoFlvvideoservedfromcache OBJECT-TYPE
    SYNTAX      ConfdString
    MAX-ACCESS  read-only
    STATUS      current
    DESCRIPTION "Number of FLV video served from cache"
    ::= { affirmedServicesContentHttpProxyServiceStatisticsSlotLevelVideoEntry 12 }

affirmedServicesContentHttpProxyServiceStatisticsSlotLevelVideoFlvvideoaborts OBJECT-TYPE
    SYNTAX      ConfdString
    MAX-ACCESS  read-only
    STATUS      current
    DESCRIPTION "Number of FLV video aborts"
    ::= { affirmedServicesContentHttpProxyServiceStatisticsSlotLevelVideoEntry 13 }

affirmedServicesContentHttpProxyServiceStatisticsSlotLevelVideoMp4videosuccesses OBJECT-TYPE
    SYNTAX      ConfdString
    MAX-ACCESS  read-only
    STATUS      current
    DESCRIPTION "Number of MP4 video successes"
    ::= { affirmedServicesContentHttpProxyServiceStatisticsSlotLevelVideoEntry 14 }

affirmedServicesContentHttpProxyServiceStatisticsSlotLevelVideoMp4videosuccessescached OBJECT-TYPE
    SYNTAX      ConfdString
    MAX-ACCESS  read-only
    STATUS      current
    DESCRIPTION "Number of MP4 video successes cached"
    ::= { affirmedServicesContentHttpProxyServiceStatisticsSlotLevelVideoEntry 15 }

affirmedServicesContentHttpProxyServiceStatisticsSlotLevelVideoMp4videoservedfromcache OBJECT-TYPE
    SYNTAX      ConfdString
    MAX-ACCESS  read-only
    STATUS      current
    DESCRIPTION "Number of MP4 video served from cache"
    ::= { affirmedServicesContentHttpProxyServiceStatisticsSlotLevelVideoEntry 16 }

affirmedServicesContentHttpProxyServiceStatisticsSlotLevelVideoMp4videoaborts OBJECT-TYPE
    SYNTAX      ConfdString
    MAX-ACCESS  read-only
    STATUS      current
    DESCRIPTION "Number of MP4 video aborts"
    ::= { affirmedServicesContentHttpProxyServiceStatisticsSlotLevelVideoEntry 17 }

affirmedServicesContentHttpProxyServiceStatisticsSlotLevelVideoDailymotionvideosuccesses OBJECT-TYPE
    SYNTAX      ConfdString
    MAX-ACCESS  read-only
    STATUS      current
    DESCRIPTION "Number of success video served by Dailymotion"
    ::= { affirmedServicesContentHttpProxyServiceStatisticsSlotLevelVideoEntry 18 }

affirmedServicesContentHttpProxyServiceStatisticsSlotLevelVideoDailymotionvideosuccessescached OBJECT-TYPE
    SYNTAX      ConfdString
    MAX-ACCESS  read-only
    STATUS      current
    DESCRIPTION "Number of success cached video served by Dailymotion"
    ::= { affirmedServicesContentHttpProxyServiceStatisticsSlotLevelVideoEntry 19 }

affirmedServicesContentHttpProxyServiceStatisticsSlotLevelVideoDailymotionvideoservedfromcache OBJECT-TYPE
    SYNTAX      ConfdString
    MAX-ACCESS  read-only
    STATUS      current
    DESCRIPTION "Number of Dailymotion videos served from cache"
    ::= { affirmedServicesContentHttpProxyServiceStatisticsSlotLevelVideoEntry 20 }

affirmedServicesContentHttpProxyServiceStatisticsSlotLevelVideoDailymotionvideoaborts OBJECT-TYPE
    SYNTAX      ConfdString
    MAX-ACCESS  read-only
    STATUS      current
    DESCRIPTION "Number of abort video served by Dailymotion"
    ::= { affirmedServicesContentHttpProxyServiceStatisticsSlotLevelVideoEntry 21 }

affirmedServicesContentHttpProxyServiceStatisticsSlotLevelVideoMetacafevideosuccesses OBJECT-TYPE
    SYNTAX      ConfdString
    MAX-ACCESS  read-only
    STATUS      current
    DESCRIPTION "Number of success video served by Metacafe"
    ::= { affirmedServicesContentHttpProxyServiceStatisticsSlotLevelVideoEntry 22 }

affirmedServicesContentHttpProxyServiceStatisticsSlotLevelVideoMetacafevideosuccessescached OBJECT-TYPE
    SYNTAX      ConfdString
    MAX-ACCESS  read-only
    STATUS      current
    DESCRIPTION "Number of success cached video served by Metacafe"
    ::= { affirmedServicesContentHttpProxyServiceStatisticsSlotLevelVideoEntry 23 }

affirmedServicesContentHttpProxyServiceStatisticsSlotLevelVideoMetacafevideoservedfromcache OBJECT-TYPE
    SYNTAX      ConfdString
    MAX-ACCESS  read-only
    STATUS      current
    DESCRIPTION "Number of Metacafe videos served from cache"
    ::= { affirmedServicesContentHttpProxyServiceStatisticsSlotLevelVideoEntry 24 }

affirmedServicesContentHttpProxyServiceStatisticsSlotLevelVideoMetacafevideoaborts OBJECT-TYPE
    SYNTAX      ConfdString
    MAX-ACCESS  read-only
    STATUS      current
    DESCRIPTION "Number of abort video served by Metacafe"
    ::= { affirmedServicesContentHttpProxyServiceStatisticsSlotLevelVideoEntry 25 }

affirmedServicesContentHttpProxyServiceStatisticsSlotLevelVideoVideosizemin OBJECT-TYPE
    SYNTAX      ConfdString
    MAX-ACCESS  read-only
    STATUS      current
    DESCRIPTION "Minimum video size in bytes"
    ::= { affirmedServicesContentHttpProxyServiceStatisticsSlotLevelVideoEntry 26 }

affirmedServicesContentHttpProxyServiceStatisticsSlotLevelVideoVideosizemax OBJECT-TYPE
    SYNTAX      ConfdString
    MAX-ACCESS  read-only
    STATUS      current
    DESCRIPTION "Maximum video size in bytes"
    ::= { affirmedServicesContentHttpProxyServiceStatisticsSlotLevelVideoEntry 27 }

affirmedServicesContentHttpProxyServiceStatisticsSlotLevelVideoVideosizeaverage OBJECT-TYPE
    SYNTAX      ConfdString
    MAX-ACCESS  read-only
    STATUS      current
    DESCRIPTION "Average video size in bytes"
    ::= { affirmedServicesContentHttpProxyServiceStatisticsSlotLevelVideoEntry 28 }

affirmedServicesContentHttpProxyServiceStatisticsSlotLevelVideoVideosizetotal OBJECT-TYPE
    SYNTAX      ConfdString
    MAX-ACCESS  read-only
    STATUS      current
    DESCRIPTION "Total video size in bytes"
    ::= { affirmedServicesContentHttpProxyServiceStatisticsSlotLevelVideoEntry 29 }

affirmedServicesContentHttpProxyServiceStatisticsSlotLevelVideoFlvvideosizemin OBJECT-TYPE
    SYNTAX      ConfdString
    MAX-ACCESS  read-only
    STATUS      current
    DESCRIPTION "Minimum FLV video size in bytes"
    ::= { affirmedServicesContentHttpProxyServiceStatisticsSlotLevelVideoEntry 30 }

affirmedServicesContentHttpProxyServiceStatisticsSlotLevelVideoFlvvideosizemax OBJECT-TYPE
    SYNTAX      ConfdString
    MAX-ACCESS  read-only
    STATUS      current
    DESCRIPTION "Maximum FLV video size in bytes"
    ::= { affirmedServicesContentHttpProxyServiceStatisticsSlotLevelVideoEntry 31 }

affirmedServicesContentHttpProxyServiceStatisticsSlotLevelVideoFlvvideosizeaverage OBJECT-TYPE
    SYNTAX      ConfdString
    MAX-ACCESS  read-only
    STATUS      current
    DESCRIPTION "Average FLV video size in bytes"
    ::= { affirmedServicesContentHttpProxyServiceStatisticsSlotLevelVideoEntry 32 }

affirmedServicesContentHttpProxyServiceStatisticsSlotLevelVideoFlvvideosizetotal OBJECT-TYPE
    SYNTAX      ConfdString
    MAX-ACCESS  read-only
    STATUS      current
    DESCRIPTION "Total FLV video size in bytes"
    ::= { affirmedServicesContentHttpProxyServiceStatisticsSlotLevelVideoEntry 33 }

affirmedServicesContentHttpProxyServiceStatisticsSlotLevelVideoMp4videosizemin OBJECT-TYPE
    SYNTAX      ConfdString
    MAX-ACCESS  read-only
    STATUS      current
    DESCRIPTION "Minimum MP4 video size in bytes"
    ::= { affirmedServicesContentHttpProxyServiceStatisticsSlotLevelVideoEntry 34 }

affirmedServicesContentHttpProxyServiceStatisticsSlotLevelVideoMp4videosizemax OBJECT-TYPE
    SYNTAX      ConfdString
    MAX-ACCESS  read-only
    STATUS      current
    DESCRIPTION "Maximum MP4 video size in bytes"
    ::= { affirmedServicesContentHttpProxyServiceStatisticsSlotLevelVideoEntry 35 }

affirmedServicesContentHttpProxyServiceStatisticsSlotLevelVideoMp4videosizeaverage OBJECT-TYPE
    SYNTAX      ConfdString
    MAX-ACCESS  read-only
    STATUS      current
    DESCRIPTION "Average MP4 video size in bytes"
    ::= { affirmedServicesContentHttpProxyServiceStatisticsSlotLevelVideoEntry 36 }

affirmedServicesContentHttpProxyServiceStatisticsSlotLevelVideoMp4videosizetotal OBJECT-TYPE
    SYNTAX      ConfdString
    MAX-ACCESS  read-only
    STATUS      current
    DESCRIPTION "Total MP4 video size in bytes"
    ::= { affirmedServicesContentHttpProxyServiceStatisticsSlotLevelVideoEntry 37 }

affirmedServicesContentHttpProxyServiceStatisticsSlotLevelVideoFlvvideodurationmin OBJECT-TYPE
    SYNTAX      ConfdString
    MAX-ACCESS  read-only
    STATUS      current
    DESCRIPTION "Minimum FLV video duration in seconds"
    ::= { affirmedServicesContentHttpProxyServiceStatisticsSlotLevelVideoEntry 38 }

affirmedServicesContentHttpProxyServiceStatisticsSlotLevelVideoFlvvideodurationmax OBJECT-TYPE
    SYNTAX      ConfdString
    MAX-ACCESS  read-only
    STATUS      current
    DESCRIPTION "Maximum FLV video duration in seconds"
    ::= { affirmedServicesContentHttpProxyServiceStatisticsSlotLevelVideoEntry 39 }

affirmedServicesContentHttpProxyServiceStatisticsSlotLevelVideoFlvvideodurationaverage OBJECT-TYPE
    SYNTAX      ConfdString
    MAX-ACCESS  read-only
    STATUS      current
    DESCRIPTION "Average FLV video duration in seconds"
    ::= { affirmedServicesContentHttpProxyServiceStatisticsSlotLevelVideoEntry 40 }

affirmedServicesContentHttpProxyServiceStatisticsSlotLevelVideoFlvvideodurationtotal OBJECT-TYPE
    SYNTAX      ConfdString
    MAX-ACCESS  read-only
    STATUS      current
    DESCRIPTION "Total FLV video duration in seconds"
    ::= { affirmedServicesContentHttpProxyServiceStatisticsSlotLevelVideoEntry 41 }

affirmedServicesContentHttpProxyServiceStatisticsSlotLevelVideoMp4videodurationmin OBJECT-TYPE
    SYNTAX      ConfdString
    MAX-ACCESS  read-only
    STATUS      current
    DESCRIPTION "Minimum MP4 video duration in seconds"
    ::= { affirmedServicesContentHttpProxyServiceStatisticsSlotLevelVideoEntry 42 }

affirmedServicesContentHttpProxyServiceStatisticsSlotLevelVideoMp4videodurationmax OBJECT-TYPE
    SYNTAX      ConfdString
    MAX-ACCESS  read-only
    STATUS      current
    DESCRIPTION "Maximum MP4 video duration in seconds"
    ::= { affirmedServicesContentHttpProxyServiceStatisticsSlotLevelVideoEntry 43 }

affirmedServicesContentHttpProxyServiceStatisticsSlotLevelVideoMp4videodurationaverage OBJECT-TYPE
    SYNTAX      ConfdString
    MAX-ACCESS  read-only
    STATUS      current
    DESCRIPTION "Average MP4 video duration in seconds"
    ::= { affirmedServicesContentHttpProxyServiceStatisticsSlotLevelVideoEntry 44 }

affirmedServicesContentHttpProxyServiceStatisticsSlotLevelVideoMp4videodurationtotal OBJECT-TYPE
    SYNTAX      ConfdString
    MAX-ACCESS  read-only
    STATUS      current
    DESCRIPTION "Total MP4 video duration in seconds"
    ::= { affirmedServicesContentHttpProxyServiceStatisticsSlotLevelVideoEntry 45 }

affirmedServicesContentHttpProxyServiceStatisticsSlotLevelVideoVideoservedbytesfromcache OBJECT-TYPE
    SYNTAX      ConfdString
    MAX-ACCESS  read-only
    STATUS      current
    DESCRIPTION "Number of video (bytes) served from cache"
    ::= { affirmedServicesContentHttpProxyServiceStatisticsSlotLevelVideoEntry 46 }

affirmedServicesContentHttpProxyServiceStatisticsSlotLevelVideoVideopacedrequests OBJECT-TYPE
    SYNTAX      ConfdString
    MAX-ACCESS  read-only
    STATUS      current
    DESCRIPTION "Number of videos for which video-pacing was applied"
    ::= { affirmedServicesContentHttpProxyServiceStatisticsSlotLevelVideoEntry 47 }

affirmedServicesContentHttpProxyServiceStatisticsSlotLevelVideoVideosizepacedtotal OBJECT-TYPE
    SYNTAX      ConfdString
    MAX-ACCESS  read-only
    STATUS      current
    DESCRIPTION "Length in bytes of videos for which pacing is applied"
    ::= { affirmedServicesContentHttpProxyServiceStatisticsSlotLevelVideoEntry 48 }

affirmedServicesContentHttpProxyServiceStatisticsSlotLevelVideoVideosizepacedsent OBJECT-TYPE
    SYNTAX      ConfdString
    MAX-ACCESS  read-only
    STATUS      current
    DESCRIPTION "Number of bytes of paced videos delivered"
    ::= { affirmedServicesContentHttpProxyServiceStatisticsSlotLevelVideoEntry 49 }

affirmedServicesContentHttpProxyServiceStatisticsSlotLevelVideoWebmvideosuccesses OBJECT-TYPE
    SYNTAX      ConfdString
    MAX-ACCESS  read-only
    STATUS      current
    DESCRIPTION "Number of WEBM video successes"
    ::= { affirmedServicesContentHttpProxyServiceStatisticsSlotLevelVideoEntry 50 }

affirmedServicesContentHttpProxyServiceStatisticsSlotLevelVideoWebmvideosuccessescached OBJECT-TYPE
    SYNTAX      ConfdString
    MAX-ACCESS  read-only
    STATUS      current
    DESCRIPTION "Number of WEBM video successes cached"
    ::= { affirmedServicesContentHttpProxyServiceStatisticsSlotLevelVideoEntry 51 }

affirmedServicesContentHttpProxyServiceStatisticsSlotLevelVideoWebmvideoservedfromcache OBJECT-TYPE
    SYNTAX      ConfdString
    MAX-ACCESS  read-only
    STATUS      current
    DESCRIPTION "Number of WEBM video served from cache"
    ::= { affirmedServicesContentHttpProxyServiceStatisticsSlotLevelVideoEntry 52 }

affirmedServicesContentHttpProxyServiceStatisticsSlotLevelVideoWebmvideoaborts OBJECT-TYPE
    SYNTAX      ConfdString
    MAX-ACCESS  read-only
    STATUS      current
    DESCRIPTION "Number of WEBM video aborts"
    ::= { affirmedServicesContentHttpProxyServiceStatisticsSlotLevelVideoEntry 53 }

affirmedServicesContentHttpProxyServiceStatisticsSlotLevelVideoWebmvideosizemin OBJECT-TYPE
    SYNTAX      ConfdString
    MAX-ACCESS  read-only
    STATUS      current
    DESCRIPTION "Minimum WEBM video size in bytes"
    ::= { affirmedServicesContentHttpProxyServiceStatisticsSlotLevelVideoEntry 54 }

affirmedServicesContentHttpProxyServiceStatisticsSlotLevelVideoWebmvideosizemax OBJECT-TYPE
    SYNTAX      ConfdString
    MAX-ACCESS  read-only
    STATUS      current
    DESCRIPTION "Maximum WEBM video size in bytes"
    ::= { affirmedServicesContentHttpProxyServiceStatisticsSlotLevelVideoEntry 55 }

affirmedServicesContentHttpProxyServiceStatisticsSlotLevelVideoWebmvideosizeaverage OBJECT-TYPE
    SYNTAX      ConfdString
    MAX-ACCESS  read-only
    STATUS      current
    DESCRIPTION "Average WEBM video size in bytes"
    ::= { affirmedServicesContentHttpProxyServiceStatisticsSlotLevelVideoEntry 56 }

affirmedServicesContentHttpProxyServiceStatisticsSlotLevelVideoWebmvideosizetotal OBJECT-TYPE
    SYNTAX      ConfdString
    MAX-ACCESS  read-only
    STATUS      current
    DESCRIPTION "Total WEBM video size in bytes"
    ::= { affirmedServicesContentHttpProxyServiceStatisticsSlotLevelVideoEntry 57 }

affirmedServicesContentHttpProxyServiceStatisticsSlotLevelVideoWebmvideodurationmin OBJECT-TYPE
    SYNTAX      ConfdString
    MAX-ACCESS  read-only
    STATUS      current
    DESCRIPTION "Minimum WEBM video duration in seconds"
    ::= { affirmedServicesContentHttpProxyServiceStatisticsSlotLevelVideoEntry 58 }

affirmedServicesContentHttpProxyServiceStatisticsSlotLevelVideoWebmvideodurationmax OBJECT-TYPE
    SYNTAX      ConfdString
    MAX-ACCESS  read-only
    STATUS      current
    DESCRIPTION "Maximum WEBM video duration in seconds"
    ::= { affirmedServicesContentHttpProxyServiceStatisticsSlotLevelVideoEntry 59 }

affirmedServicesContentHttpProxyServiceStatisticsSlotLevelVideoWebmvideodurationaverage OBJECT-TYPE
    SYNTAX      ConfdString
    MAX-ACCESS  read-only
    STATUS      current
    DESCRIPTION "Average WEBM video duration in seconds"
    ::= { affirmedServicesContentHttpProxyServiceStatisticsSlotLevelVideoEntry 60 }

affirmedServicesContentHttpProxyServiceStatisticsSlotLevelVideoWebmvideodurationtotal OBJECT-TYPE
    SYNTAX      ConfdString
    MAX-ACCESS  read-only
    STATUS      current
    DESCRIPTION "Total WEBM video duration in seconds"
    ::= { affirmedServicesContentHttpProxyServiceStatisticsSlotLevelVideoEntry 61 }

affirmedServicesContentHttpProxyServiceStatisticsSlotLevelMediaTypeResponsesTable OBJECT-TYPE
    SYNTAX      SEQUENCE OF AffirmedServicesContentHttpProxyServiceStatisticsSlotLevelMediaTypeResponsesEntry
    MAX-ACCESS  not-accessible
    STATUS      current
    DESCRIPTION ""
    ::= { affirmedServicesContentHttpProxyServiceStatisticsSlotLevelMediaType 1 }

affirmedServicesContentHttpProxyServiceStatisticsSlotLevelMediaTypeResponsesEntry OBJECT-TYPE
    SYNTAX      AffirmedServicesContentHttpProxyServiceStatisticsSlotLevelMediaTypeResponsesEntry
    MAX-ACCESS  not-accessible
    STATUS      current
    DESCRIPTION ""
    INDEX { affirmedServicesContentHttpProxyServiceStatisticsSlotLevelMediaTypeResponsesChassis, affirmedServicesContentHttpProxyServiceStatisticsSlotLevelMediaTypeResponsesSlot }
        ::= { affirmedServicesContentHttpProxyServiceStatisticsSlotLevelMediaTypeResponsesTable 1 }

AffirmedServicesContentHttpProxyServiceStatisticsSlotLevelMediaTypeResponsesEntry ::=
    SEQUENCE {
        affirmedServicesContentHttpProxyServiceStatisticsSlotLevelMediaTypeResponsesChassis Unsigned32,
        affirmedServicesContentHttpProxyServiceStatisticsSlotLevelMediaTypeResponsesSlot INTEGER,
        affirmedServicesContentHttpProxyServiceStatisticsSlotLevelMediaTypeResponsesNumtextresphtml ConfdString,
        affirmedServicesContentHttpProxyServiceStatisticsSlotLevelMediaTypeResponsesNumtextrespxml ConfdString,
        affirmedServicesContentHttpProxyServiceStatisticsSlotLevelMediaTypeResponsesNumtextrespcss ConfdString,
        affirmedServicesContentHttpProxyServiceStatisticsSlotLevelMediaTypeResponsesNumtextrespjs ConfdString,
        affirmedServicesContentHttpProxyServiceStatisticsSlotLevelMediaTypeResponsesNumtextrespjson ConfdString,
        affirmedServicesContentHttpProxyServiceStatisticsSlotLevelMediaTypeResponsesNumtextrespplain ConfdString,
        affirmedServicesContentHttpProxyServiceStatisticsSlotLevelMediaTypeResponsesNumimagerespjpeg ConfdString,
        affirmedServicesContentHttpProxyServiceStatisticsSlotLevelMediaTypeResponsesNumimageresppng ConfdString,
        affirmedServicesContentHttpProxyServiceStatisticsSlotLevelMediaTypeResponsesNumimagerespgif ConfdString,
        affirmedServicesContentHttpProxyServiceStatisticsSlotLevelMediaTypeResponsesNumimagerespbmp ConfdString,
        affirmedServicesContentHttpProxyServiceStatisticsSlotLevelMediaTypeResponsesNumvideorespmp4 ConfdString,
        affirmedServicesContentHttpProxyServiceStatisticsSlotLevelMediaTypeResponsesNumvideorespflv ConfdString,
        affirmedServicesContentHttpProxyServiceStatisticsSlotLevelMediaTypeResponsesNumvideorespwebm ConfdString,
        affirmedServicesContentHttpProxyServiceStatisticsSlotLevelMediaTypeResponsesNumvideoresphls ConfdString,
        affirmedServicesContentHttpProxyServiceStatisticsSlotLevelMediaTypeResponsesNumvideorespdash ConfdString,
        affirmedServicesContentHttpProxyServiceStatisticsSlotLevelMediaTypeResponsesNumvideoresphds ConfdString,
        affirmedServicesContentHttpProxyServiceStatisticsSlotLevelMediaTypeResponsesNumotherrespbinary ConfdString,
        affirmedServicesContentHttpProxyServiceStatisticsSlotLevelMediaTypeResponsesNumotherrespunrecog ConfdString
    }

affirmedServicesContentHttpProxyServiceStatisticsSlotLevelMediaTypeResponsesChassis OBJECT-TYPE
    SYNTAX      Unsigned32
    MAX-ACCESS  not-accessible
    STATUS      current
    DESCRIPTION "chassis ID"
    ::= { affirmedServicesContentHttpProxyServiceStatisticsSlotLevelMediaTypeResponsesEntry 1 }

affirmedServicesContentHttpProxyServiceStatisticsSlotLevelMediaTypeResponsesSlot OBJECT-TYPE
    SYNTAX      INTEGER {a1(1),a2(2),a3(3),a4(4),a5(5),a6(6),a7(7),a8(8),a9(9),a10(10),a11(11),a12(12),a13(13),a14(14),a15(15),a16(16),a17(17),a18(18),a19(19),a20(20),a21(21),a22(22),a23(23),a24(24),a25(25),a26(26),a27(27),a28(28),a29(29),a30(30),a31(31),a32(32),a33(33),a34(34),a35(35),a36(36),a37(37),a38(38),a39(39),a40(40),a41(41),a42(42),a43(43),a44(44),a45(45),a46(46),a47(47),a48(48),a49(49),a50(50),a51(51),a52(52),a53(53),a54(54),a55(55),a56(56),a57(57),a58(58),a59(59),a60(60),a61(61),a62(62),a63(63),a64(64),a65(65),a66(66),a67(67),a68(68),a69(69),a70(70),a71(71),a72(72),a73(73),a74(74),a75(75),a76(76),a77(77),a78(78),a79(79),a80(80),a81(81),a82(82),a83(83),a84(84),a85(85),a86(86),a87(87),a88(88),a89(89),a90(90),a91(91),a92(92),a93(93),a94(94),a95(95),a96(96),a97(97),a98(98),a99(99),a100(100),a101(101),a102(102),a103(103),a104(104),a105(105),a106(106),a107(107),a108(108),a109(109),a110(110),a111(111),a112(112),a113(113),a114(114),a115(115),a116(116),a117(117),a118(118),a119(119),a120(120),a121(121),a122(122),a123(123),a124(124),a125(125),a126(126),a127(127),a128(128)}
    MAX-ACCESS  not-accessible
    STATUS      current
    DESCRIPTION "slot number"
    ::= { affirmedServicesContentHttpProxyServiceStatisticsSlotLevelMediaTypeResponsesEntry 2 }

affirmedServicesContentHttpProxyServiceStatisticsSlotLevelMediaTypeResponsesNumtextresphtml OBJECT-TYPE
    SYNTAX      ConfdString
    MAX-ACCESS  read-only
    STATUS      current
    DESCRIPTION "Number of HTML Text Responses"
    ::= { affirmedServicesContentHttpProxyServiceStatisticsSlotLevelMediaTypeResponsesEntry 3 }

affirmedServicesContentHttpProxyServiceStatisticsSlotLevelMediaTypeResponsesNumtextrespxml OBJECT-TYPE
    SYNTAX      ConfdString
    MAX-ACCESS  read-only
    STATUS      current
    DESCRIPTION "Number of XML Text Responses"
    ::= { affirmedServicesContentHttpProxyServiceStatisticsSlotLevelMediaTypeResponsesEntry 4 }

affirmedServicesContentHttpProxyServiceStatisticsSlotLevelMediaTypeResponsesNumtextrespcss OBJECT-TYPE
    SYNTAX      ConfdString
    MAX-ACCESS  read-only
    STATUS      current
    DESCRIPTION "Number of CSS Text Responses"
    ::= { affirmedServicesContentHttpProxyServiceStatisticsSlotLevelMediaTypeResponsesEntry 5 }

affirmedServicesContentHttpProxyServiceStatisticsSlotLevelMediaTypeResponsesNumtextrespjs OBJECT-TYPE
    SYNTAX      ConfdString
    MAX-ACCESS  read-only
    STATUS      current
    DESCRIPTION "Number of Javascript Text Responses"
    ::= { affirmedServicesContentHttpProxyServiceStatisticsSlotLevelMediaTypeResponsesEntry 6 }

affirmedServicesContentHttpProxyServiceStatisticsSlotLevelMediaTypeResponsesNumtextrespjson OBJECT-TYPE
    SYNTAX      ConfdString
    MAX-ACCESS  read-only
    STATUS      current
    DESCRIPTION "Number of JSON Text Responses"
    ::= { affirmedServicesContentHttpProxyServiceStatisticsSlotLevelMediaTypeResponsesEntry 7 }

affirmedServicesContentHttpProxyServiceStatisticsSlotLevelMediaTypeResponsesNumtextrespplain OBJECT-TYPE
    SYNTAX      ConfdString
    MAX-ACCESS  read-only
    STATUS      current
    DESCRIPTION "Number of Plain Text Responses"
    ::= { affirmedServicesContentHttpProxyServiceStatisticsSlotLevelMediaTypeResponsesEntry 8 }

affirmedServicesContentHttpProxyServiceStatisticsSlotLevelMediaTypeResponsesNumimagerespjpeg OBJECT-TYPE
    SYNTAX      ConfdString
    MAX-ACCESS  read-only
    STATUS      current
    DESCRIPTION "Number of JPEG Image Responses"
    ::= { affirmedServicesContentHttpProxyServiceStatisticsSlotLevelMediaTypeResponsesEntry 9 }

affirmedServicesContentHttpProxyServiceStatisticsSlotLevelMediaTypeResponsesNumimageresppng OBJECT-TYPE
    SYNTAX      ConfdString
    MAX-ACCESS  read-only
    STATUS      current
    DESCRIPTION "Number of PNG Image Responses"
    ::= { affirmedServicesContentHttpProxyServiceStatisticsSlotLevelMediaTypeResponsesEntry 10 }

affirmedServicesContentHttpProxyServiceStatisticsSlotLevelMediaTypeResponsesNumimagerespgif OBJECT-TYPE
    SYNTAX      ConfdString
    MAX-ACCESS  read-only
    STATUS      current
    DESCRIPTION "Number of GIF Image Responses"
    ::= { affirmedServicesContentHttpProxyServiceStatisticsSlotLevelMediaTypeResponsesEntry 11 }

affirmedServicesContentHttpProxyServiceStatisticsSlotLevelMediaTypeResponsesNumimagerespbmp OBJECT-TYPE
    SYNTAX      ConfdString
    MAX-ACCESS  read-only
    STATUS      current
    DESCRIPTION "Number of BMP Image Responses"
    ::= { affirmedServicesContentHttpProxyServiceStatisticsSlotLevelMediaTypeResponsesEntry 12 }

affirmedServicesContentHttpProxyServiceStatisticsSlotLevelMediaTypeResponsesNumvideorespmp4 OBJECT-TYPE
    SYNTAX      ConfdString
    MAX-ACCESS  read-only
    STATUS      current
    DESCRIPTION "Number of MP4 Video Responses"
    ::= { affirmedServicesContentHttpProxyServiceStatisticsSlotLevelMediaTypeResponsesEntry 13 }

affirmedServicesContentHttpProxyServiceStatisticsSlotLevelMediaTypeResponsesNumvideorespflv OBJECT-TYPE
    SYNTAX      ConfdString
    MAX-ACCESS  read-only
    STATUS      current
    DESCRIPTION "Number of FLV Video Responses"
    ::= { affirmedServicesContentHttpProxyServiceStatisticsSlotLevelMediaTypeResponsesEntry 14 }

affirmedServicesContentHttpProxyServiceStatisticsSlotLevelMediaTypeResponsesNumvideorespwebm OBJECT-TYPE
    SYNTAX      ConfdString
    MAX-ACCESS  read-only
    STATUS      current
    DESCRIPTION "Number of WEBM Video Responses"
    ::= { affirmedServicesContentHttpProxyServiceStatisticsSlotLevelMediaTypeResponsesEntry 15 }

affirmedServicesContentHttpProxyServiceStatisticsSlotLevelMediaTypeResponsesNumvideoresphls OBJECT-TYPE
    SYNTAX      ConfdString
    MAX-ACCESS  read-only
    STATUS      current
    DESCRIPTION "Number of HLS Video Responses"
    ::= { affirmedServicesContentHttpProxyServiceStatisticsSlotLevelMediaTypeResponsesEntry 16 }

affirmedServicesContentHttpProxyServiceStatisticsSlotLevelMediaTypeResponsesNumvideorespdash OBJECT-TYPE
    SYNTAX      ConfdString
    MAX-ACCESS  read-only
    STATUS      current
    DESCRIPTION "Number of DASH Video Responses"
    ::= { affirmedServicesContentHttpProxyServiceStatisticsSlotLevelMediaTypeResponsesEntry 17 }

affirmedServicesContentHttpProxyServiceStatisticsSlotLevelMediaTypeResponsesNumvideoresphds OBJECT-TYPE
    SYNTAX      ConfdString
    MAX-ACCESS  read-only
    STATUS      current
    DESCRIPTION "Number of HDS Video Responses"
    ::= { affirmedServicesContentHttpProxyServiceStatisticsSlotLevelMediaTypeResponsesEntry 18 }

affirmedServicesContentHttpProxyServiceStatisticsSlotLevelMediaTypeResponsesNumotherrespbinary OBJECT-TYPE
    SYNTAX      ConfdString
    MAX-ACCESS  read-only
    STATUS      current
    DESCRIPTION "Number of Binary Responses"
    ::= { affirmedServicesContentHttpProxyServiceStatisticsSlotLevelMediaTypeResponsesEntry 19 }

affirmedServicesContentHttpProxyServiceStatisticsSlotLevelMediaTypeResponsesNumotherrespunrecog OBJECT-TYPE
    SYNTAX      ConfdString
    MAX-ACCESS  read-only
    STATUS      current
    DESCRIPTION "Number of Unrecognized Responses"
    ::= { affirmedServicesContentHttpProxyServiceStatisticsSlotLevelMediaTypeResponsesEntry 20 }

affirmedServicesContentHttpProxyServiceStatisticsSlotLevelMediaTypeBytesTable OBJECT-TYPE
    SYNTAX      SEQUENCE OF AffirmedServicesContentHttpProxyServiceStatisticsSlotLevelMediaTypeBytesEntry
    MAX-ACCESS  not-accessible
    STATUS      current
    DESCRIPTION ""
    ::= { affirmedServicesContentHttpProxyServiceStatisticsSlotLevelMediaType 2 }

affirmedServicesContentHttpProxyServiceStatisticsSlotLevelMediaTypeBytesEntry OBJECT-TYPE
    SYNTAX      AffirmedServicesContentHttpProxyServiceStatisticsSlotLevelMediaTypeBytesEntry
    MAX-ACCESS  not-accessible
    STATUS      current
    DESCRIPTION ""
    INDEX { affirmedServicesContentHttpProxyServiceStatisticsSlotLevelMediaTypeBytesChassis, affirmedServicesContentHttpProxyServiceStatisticsSlotLevelMediaTypeBytesSlot }
        ::= { affirmedServicesContentHttpProxyServiceStatisticsSlotLevelMediaTypeBytesTable 1 }

AffirmedServicesContentHttpProxyServiceStatisticsSlotLevelMediaTypeBytesEntry ::=
    SEQUENCE {
        affirmedServicesContentHttpProxyServiceStatisticsSlotLevelMediaTypeBytesChassis Unsigned32,
        affirmedServicesContentHttpProxyServiceStatisticsSlotLevelMediaTypeBytesSlot INTEGER,
        affirmedServicesContentHttpProxyServiceStatisticsSlotLevelMediaTypeBytesNumtextbyteshtml ConfdString,
        affirmedServicesContentHttpProxyServiceStatisticsSlotLevelMediaTypeBytesNumtextbytesxml ConfdString,
        affirmedServicesContentHttpProxyServiceStatisticsSlotLevelMediaTypeBytesNumtextbytescss ConfdString,
        affirmedServicesContentHttpProxyServiceStatisticsSlotLevelMediaTypeBytesNumtextbytesjs ConfdString,
        affirmedServicesContentHttpProxyServiceStatisticsSlotLevelMediaTypeBytesNumtextbytesjson ConfdString,
        affirmedServicesContentHttpProxyServiceStatisticsSlotLevelMediaTypeBytesNumtextbytesplain ConfdString,
        affirmedServicesContentHttpProxyServiceStatisticsSlotLevelMediaTypeBytesNumimagebytesjpeg ConfdString,
        affirmedServicesContentHttpProxyServiceStatisticsSlotLevelMediaTypeBytesNumimagebytespng ConfdString,
        affirmedServicesContentHttpProxyServiceStatisticsSlotLevelMediaTypeBytesNumimagebytesgif ConfdString,
        affirmedServicesContentHttpProxyServiceStatisticsSlotLevelMediaTypeBytesNumimagebytesbmp ConfdString,
        affirmedServicesContentHttpProxyServiceStatisticsSlotLevelMediaTypeBytesNumvideobytesmp4 ConfdString,
        affirmedServicesContentHttpProxyServiceStatisticsSlotLevelMediaTypeBytesNumvideobytesflv ConfdString,
        affirmedServicesContentHttpProxyServiceStatisticsSlotLevelMediaTypeBytesNumvideobyteswebm ConfdString,
        affirmedServicesContentHttpProxyServiceStatisticsSlotLevelMediaTypeBytesNumvideobyteshls ConfdString,
        affirmedServicesContentHttpProxyServiceStatisticsSlotLevelMediaTypeBytesNumvideobytesdash ConfdString,
        affirmedServicesContentHttpProxyServiceStatisticsSlotLevelMediaTypeBytesNumvideobyteshds ConfdString,
        affirmedServicesContentHttpProxyServiceStatisticsSlotLevelMediaTypeBytesNumotherbytesbinary ConfdString,
        affirmedServicesContentHttpProxyServiceStatisticsSlotLevelMediaTypeBytesNumotherbytesunrecog ConfdString
    }

affirmedServicesContentHttpProxyServiceStatisticsSlotLevelMediaTypeBytesChassis OBJECT-TYPE
    SYNTAX      Unsigned32
    MAX-ACCESS  not-accessible
    STATUS      current
    DESCRIPTION "chassis ID"
    ::= { affirmedServicesContentHttpProxyServiceStatisticsSlotLevelMediaTypeBytesEntry 1 }

affirmedServicesContentHttpProxyServiceStatisticsSlotLevelMediaTypeBytesSlot OBJECT-TYPE
    SYNTAX      INTEGER {a1(1),a2(2),a3(3),a4(4),a5(5),a6(6),a7(7),a8(8),a9(9),a10(10),a11(11),a12(12),a13(13),a14(14),a15(15),a16(16),a17(17),a18(18),a19(19),a20(20),a21(21),a22(22),a23(23),a24(24),a25(25),a26(26),a27(27),a28(28),a29(29),a30(30),a31(31),a32(32),a33(33),a34(34),a35(35),a36(36),a37(37),a38(38),a39(39),a40(40),a41(41),a42(42),a43(43),a44(44),a45(45),a46(46),a47(47),a48(48),a49(49),a50(50),a51(51),a52(52),a53(53),a54(54),a55(55),a56(56),a57(57),a58(58),a59(59),a60(60),a61(61),a62(62),a63(63),a64(64),a65(65),a66(66),a67(67),a68(68),a69(69),a70(70),a71(71),a72(72),a73(73),a74(74),a75(75),a76(76),a77(77),a78(78),a79(79),a80(80),a81(81),a82(82),a83(83),a84(84),a85(85),a86(86),a87(87),a88(88),a89(89),a90(90),a91(91),a92(92),a93(93),a94(94),a95(95),a96(96),a97(97),a98(98),a99(99),a100(100),a101(101),a102(102),a103(103),a104(104),a105(105),a106(106),a107(107),a108(108),a109(109),a110(110),a111(111),a112(112),a113(113),a114(114),a115(115),a116(116),a117(117),a118(118),a119(119),a120(120),a121(121),a122(122),a123(123),a124(124),a125(125),a126(126),a127(127),a128(128)}
    MAX-ACCESS  not-accessible
    STATUS      current
    DESCRIPTION "slot number"
    ::= { affirmedServicesContentHttpProxyServiceStatisticsSlotLevelMediaTypeBytesEntry 2 }

affirmedServicesContentHttpProxyServiceStatisticsSlotLevelMediaTypeBytesNumtextbyteshtml OBJECT-TYPE
    SYNTAX      ConfdString
    MAX-ACCESS  read-only
    STATUS      current
    DESCRIPTION "Number of HTML Text Bytes"
    ::= { affirmedServicesContentHttpProxyServiceStatisticsSlotLevelMediaTypeBytesEntry 3 }

affirmedServicesContentHttpProxyServiceStatisticsSlotLevelMediaTypeBytesNumtextbytesxml OBJECT-TYPE
    SYNTAX      ConfdString
    MAX-ACCESS  read-only
    STATUS      current
    DESCRIPTION "Number of XML Text Bytes"
    ::= { affirmedServicesContentHttpProxyServiceStatisticsSlotLevelMediaTypeBytesEntry 4 }

affirmedServicesContentHttpProxyServiceStatisticsSlotLevelMediaTypeBytesNumtextbytescss OBJECT-TYPE
    SYNTAX      ConfdString
    MAX-ACCESS  read-only
    STATUS      current
    DESCRIPTION "Number of CSS Text Bytes"
    ::= { affirmedServicesContentHttpProxyServiceStatisticsSlotLevelMediaTypeBytesEntry 5 }

affirmedServicesContentHttpProxyServiceStatisticsSlotLevelMediaTypeBytesNumtextbytesjs OBJECT-TYPE
    SYNTAX      ConfdString
    MAX-ACCESS  read-only
    STATUS      current
    DESCRIPTION "Number of Javascript Text Bytes"
    ::= { affirmedServicesContentHttpProxyServiceStatisticsSlotLevelMediaTypeBytesEntry 6 }

affirmedServicesContentHttpProxyServiceStatisticsSlotLevelMediaTypeBytesNumtextbytesjson OBJECT-TYPE
    SYNTAX      ConfdString
    MAX-ACCESS  read-only
    STATUS      current
    DESCRIPTION "Number of JSON Text Bytes"
    ::= { affirmedServicesContentHttpProxyServiceStatisticsSlotLevelMediaTypeBytesEntry 7 }

affirmedServicesContentHttpProxyServiceStatisticsSlotLevelMediaTypeBytesNumtextbytesplain OBJECT-TYPE
    SYNTAX      ConfdString
    MAX-ACCESS  read-only
    STATUS      current
    DESCRIPTION "Number of Plain Text Bytes"
    ::= { affirmedServicesContentHttpProxyServiceStatisticsSlotLevelMediaTypeBytesEntry 8 }

affirmedServicesContentHttpProxyServiceStatisticsSlotLevelMediaTypeBytesNumimagebytesjpeg OBJECT-TYPE
    SYNTAX      ConfdString
    MAX-ACCESS  read-only
    STATUS      current
    DESCRIPTION "Number of JPEG Image Bytes"
    ::= { affirmedServicesContentHttpProxyServiceStatisticsSlotLevelMediaTypeBytesEntry 9 }

affirmedServicesContentHttpProxyServiceStatisticsSlotLevelMediaTypeBytesNumimagebytespng OBJECT-TYPE
    SYNTAX      ConfdString
    MAX-ACCESS  read-only
    STATUS      current
    DESCRIPTION "Number of PNG Image Bytes"
    ::= { affirmedServicesContentHttpProxyServiceStatisticsSlotLevelMediaTypeBytesEntry 10 }

affirmedServicesContentHttpProxyServiceStatisticsSlotLevelMediaTypeBytesNumimagebytesgif OBJECT-TYPE
    SYNTAX      ConfdString
    MAX-ACCESS  read-only
    STATUS      current
    DESCRIPTION "Number of GIF Image Bytes"
    ::= { affirmedServicesContentHttpProxyServiceStatisticsSlotLevelMediaTypeBytesEntry 11 }

affirmedServicesContentHttpProxyServiceStatisticsSlotLevelMediaTypeBytesNumimagebytesbmp OBJECT-TYPE
    SYNTAX      ConfdString
    MAX-ACCESS  read-only
    STATUS      current
    DESCRIPTION "Number of BMP Image Bytes"
    ::= { affirmedServicesContentHttpProxyServiceStatisticsSlotLevelMediaTypeBytesEntry 12 }

affirmedServicesContentHttpProxyServiceStatisticsSlotLevelMediaTypeBytesNumvideobytesmp4 OBJECT-TYPE
    SYNTAX      ConfdString
    MAX-ACCESS  read-only
    STATUS      current
    DESCRIPTION "Number of MP4 Video Bytes"
    ::= { affirmedServicesContentHttpProxyServiceStatisticsSlotLevelMediaTypeBytesEntry 13 }

affirmedServicesContentHttpProxyServiceStatisticsSlotLevelMediaTypeBytesNumvideobytesflv OBJECT-TYPE
    SYNTAX      ConfdString
    MAX-ACCESS  read-only
    STATUS      current
    DESCRIPTION "Number of FLV Video Bytes"
    ::= { affirmedServicesContentHttpProxyServiceStatisticsSlotLevelMediaTypeBytesEntry 14 }

affirmedServicesContentHttpProxyServiceStatisticsSlotLevelMediaTypeBytesNumvideobyteswebm OBJECT-TYPE
    SYNTAX      ConfdString
    MAX-ACCESS  read-only
    STATUS      current
    DESCRIPTION "Number of WEBM Video Bytes"
    ::= { affirmedServicesContentHttpProxyServiceStatisticsSlotLevelMediaTypeBytesEntry 15 }

affirmedServicesContentHttpProxyServiceStatisticsSlotLevelMediaTypeBytesNumvideobyteshls OBJECT-TYPE
    SYNTAX      ConfdString
    MAX-ACCESS  read-only
    STATUS      current
    DESCRIPTION "Number of HLS Video Bytes"
    ::= { affirmedServicesContentHttpProxyServiceStatisticsSlotLevelMediaTypeBytesEntry 16 }

affirmedServicesContentHttpProxyServiceStatisticsSlotLevelMediaTypeBytesNumvideobytesdash OBJECT-TYPE
    SYNTAX      ConfdString
    MAX-ACCESS  read-only
    STATUS      current
    DESCRIPTION "Number of DASH Video Bytes"
    ::= { affirmedServicesContentHttpProxyServiceStatisticsSlotLevelMediaTypeBytesEntry 17 }

affirmedServicesContentHttpProxyServiceStatisticsSlotLevelMediaTypeBytesNumvideobyteshds OBJECT-TYPE
    SYNTAX      ConfdString
    MAX-ACCESS  read-only
    STATUS      current
    DESCRIPTION "Number of HDS Video Bytes"
    ::= { affirmedServicesContentHttpProxyServiceStatisticsSlotLevelMediaTypeBytesEntry 18 }

affirmedServicesContentHttpProxyServiceStatisticsSlotLevelMediaTypeBytesNumotherbytesbinary OBJECT-TYPE
    SYNTAX      ConfdString
    MAX-ACCESS  read-only
    STATUS      current
    DESCRIPTION "Number of Binary Bytes"
    ::= { affirmedServicesContentHttpProxyServiceStatisticsSlotLevelMediaTypeBytesEntry 19 }

affirmedServicesContentHttpProxyServiceStatisticsSlotLevelMediaTypeBytesNumotherbytesunrecog OBJECT-TYPE
    SYNTAX      ConfdString
    MAX-ACCESS  read-only
    STATUS      current
    DESCRIPTION "Number of Unrecognized Bytes"
    ::= { affirmedServicesContentHttpProxyServiceStatisticsSlotLevelMediaTypeBytesEntry 20 }

affirmedServicesChargingServiceDataFlowTable OBJECT-TYPE
    SYNTAX      SEQUENCE OF AffirmedServicesChargingServiceDataFlowEntry
    MAX-ACCESS  not-accessible
    STATUS      current
    DESCRIPTION ""
    ::= { affirmedServicesCharging 1 }

affirmedServicesChargingServiceDataFlowEntry OBJECT-TYPE
    SYNTAX      AffirmedServicesChargingServiceDataFlowEntry
    MAX-ACCESS  not-accessible
    STATUS      current
    DESCRIPTION ""
    INDEX { affirmedServicesChargingServiceDataFlowChargingInstance, affirmedServicesChargingServiceDataFlowBillingPlan, affirmedServicesChargingServiceDataFlowRatingGroupPriority, affirmedServicesChargingServiceDataFlowServiceRulePriority, affirmedServicesChargingServiceDataFlowRatingGroup, affirmedServicesChargingServiceDataFlowServiceRule }
        ::= { affirmedServicesChargingServiceDataFlowTable 1 }

AffirmedServicesChargingServiceDataFlowEntry ::=
    SEQUENCE {
        affirmedServicesChargingServiceDataFlowChargingInstance String,
        affirmedServicesChargingServiceDataFlowBillingPlan String,
        affirmedServicesChargingServiceDataFlowRatingGroupPriority Unsigned32,
        affirmedServicesChargingServiceDataFlowServiceRulePriority Unsigned32,
        affirmedServicesChargingServiceDataFlowRatingGroup String,
        affirmedServicesChargingServiceDataFlowServiceRule String,
        affirmedServicesChargingServiceDataFlowRatingGroupId Unsigned32,
        affirmedServicesChargingServiceDataFlowServiceRuleId Unsigned32
    }

affirmedServicesChargingServiceDataFlowChargingInstance OBJECT-TYPE
    SYNTAX      String
    MAX-ACCESS  not-accessible
    STATUS      current
    DESCRIPTION "the name of the charging-instance"
    ::= { affirmedServicesChargingServiceDataFlowEntry 1 }

affirmedServicesChargingServiceDataFlowBillingPlan OBJECT-TYPE
    SYNTAX      String
    MAX-ACCESS  not-accessible
    STATUS      current
    DESCRIPTION "the name of the billing-plan"
    ::= { affirmedServicesChargingServiceDataFlowEntry 2 }

affirmedServicesChargingServiceDataFlowRatingGroupPriority OBJECT-TYPE
    SYNTAX      Unsigned32
    MAX-ACCESS  not-accessible
    STATUS      current
    DESCRIPTION "the priority of the rating-group, but 0 if priority-evaluation-mode is 'flat'"
    ::= { affirmedServicesChargingServiceDataFlowEntry 3 }

affirmedServicesChargingServiceDataFlowServiceRulePriority OBJECT-TYPE
    SYNTAX      Unsigned32
    MAX-ACCESS  not-accessible
    STATUS      current
    DESCRIPTION "the priority of the service-rule or the billing-plan priority override"
    ::= { affirmedServicesChargingServiceDataFlowEntry 4 }

affirmedServicesChargingServiceDataFlowRatingGroup OBJECT-TYPE
    SYNTAX      String
    MAX-ACCESS  not-accessible
    STATUS      current
    DESCRIPTION "the name of the rating-group"
    ::= { affirmedServicesChargingServiceDataFlowEntry 5 }

affirmedServicesChargingServiceDataFlowServiceRule OBJECT-TYPE
    SYNTAX      String
    MAX-ACCESS  not-accessible
    STATUS      current
    DESCRIPTION "the name of the service-rule"
    ::= { affirmedServicesChargingServiceDataFlowEntry 6 }

affirmedServicesChargingServiceDataFlowRatingGroupId OBJECT-TYPE
    SYNTAX      Unsigned32
    MAX-ACCESS  read-only
    STATUS      current
    DESCRIPTION "the internal ID of the rating-group, used to identify PDN-session service-data-flows {session-id, service-type=charging, rating-group-id, service-rule-id}"
    ::= { affirmedServicesChargingServiceDataFlowEntry 7 }

affirmedServicesChargingServiceDataFlowServiceRuleId OBJECT-TYPE
    SYNTAX      Unsigned32
    MAX-ACCESS  read-only
    STATUS      current
    DESCRIPTION "the internal ID of the service-rule, used to identify PDN-session service-data-flows {session-id, service-type=charging, rating-group-id, service-rule-id}"
    ::= { affirmedServicesChargingServiceDataFlowEntry 8 }

affirmedServicesSteeringServiceDataFlowTable OBJECT-TYPE
    SYNTAX      SEQUENCE OF AffirmedServicesSteeringServiceDataFlowEntry
    MAX-ACCESS  not-accessible
    STATUS      current
    DESCRIPTION ""
    ::= { affirmedServicesSteering 1 }

affirmedServicesSteeringServiceDataFlowEntry OBJECT-TYPE
    SYNTAX      AffirmedServicesSteeringServiceDataFlowEntry
    MAX-ACCESS  not-accessible
    STATUS      current
    DESCRIPTION ""
    INDEX { affirmedServicesSteeringServiceDataFlowSteeringPolicy, affirmedServicesSteeringServiceDataFlowSteeringFlowPriority, affirmedServicesSteeringServiceDataFlowServiceRulePriority, affirmedServicesSteeringServiceDataFlowSteeringFlow, affirmedServicesSteeringServiceDataFlowServiceRule }
        ::= { affirmedServicesSteeringServiceDataFlowTable 1 }

AffirmedServicesSteeringServiceDataFlowEntry ::=
    SEQUENCE {
        affirmedServicesSteeringServiceDataFlowSteeringPolicy String,
        affirmedServicesSteeringServiceDataFlowSteeringFlowPriority Unsigned32,
        affirmedServicesSteeringServiceDataFlowServiceRulePriority Unsigned32,
        affirmedServicesSteeringServiceDataFlowSteeringFlow String,
        affirmedServicesSteeringServiceDataFlowServiceRule String,
        affirmedServicesSteeringServiceDataFlowSteeringFlowId Unsigned32,
        affirmedServicesSteeringServiceDataFlowServiceRuleId Unsigned32
    }

affirmedServicesSteeringServiceDataFlowSteeringPolicy OBJECT-TYPE
    SYNTAX      String
    MAX-ACCESS  not-accessible
    STATUS      current
    DESCRIPTION "the name of the steering-policy"
    ::= { affirmedServicesSteeringServiceDataFlowEntry 1 }

affirmedServicesSteeringServiceDataFlowSteeringFlowPriority OBJECT-TYPE
    SYNTAX      Unsigned32
    MAX-ACCESS  not-accessible
    STATUS      current
    DESCRIPTION "the priority of the steering-flow"
    ::= { affirmedServicesSteeringServiceDataFlowEntry 2 }

affirmedServicesSteeringServiceDataFlowServiceRulePriority OBJECT-TYPE
    SYNTAX      Unsigned32
    MAX-ACCESS  not-accessible
    STATUS      current
    DESCRIPTION "the priority of the service-rule"
    ::= { affirmedServicesSteeringServiceDataFlowEntry 3 }

affirmedServicesSteeringServiceDataFlowSteeringFlow OBJECT-TYPE
    SYNTAX      String
    MAX-ACCESS  not-accessible
    STATUS      current
    DESCRIPTION "the name of the steering-flow"
    ::= { affirmedServicesSteeringServiceDataFlowEntry 4 }

affirmedServicesSteeringServiceDataFlowServiceRule OBJECT-TYPE
    SYNTAX      String
    MAX-ACCESS  not-accessible
    STATUS      current
    DESCRIPTION "the name of the service-rule"
    ::= { affirmedServicesSteeringServiceDataFlowEntry 5 }

affirmedServicesSteeringServiceDataFlowSteeringFlowId OBJECT-TYPE
    SYNTAX      Unsigned32
    MAX-ACCESS  read-only
    STATUS      current
    DESCRIPTION "the internal ID of the steering-flow, used to identify PDN-session service-data-flows {session-id, service-type=steering-policy, steering-flow-id, service-rule-id}"
    ::= { affirmedServicesSteeringServiceDataFlowEntry 6 }

affirmedServicesSteeringServiceDataFlowServiceRuleId OBJECT-TYPE
    SYNTAX      Unsigned32
    MAX-ACCESS  read-only
    STATUS      current
    DESCRIPTION "the internal ID of the service-rule, used to identify PDN-session service-data-flows {session-id, service-type=steering-policy, steering-flow-id, service-rule-id}"
    ::= { affirmedServicesSteeringServiceDataFlowEntry 7 }

affirmedServicesContentCacheProxyServiceStatisticsCluster-levelSummaryTable OBJECT-TYPE
    SYNTAX      SEQUENCE OF AffirmedServicesContentCacheProxyServiceStatisticsCluster-levelSummaryEntry
    MAX-ACCESS  not-accessible
    STATUS      current
    DESCRIPTION ""
    ::= { affirmedServicesContentCacheProxyServiceStatisticsCluster-level 1 }

affirmedServicesContentCacheProxyServiceStatisticsCluster-levelSummaryEntry OBJECT-TYPE
    SYNTAX      AffirmedServicesContentCacheProxyServiceStatisticsCluster-levelSummaryEntry
    MAX-ACCESS  not-accessible
    STATUS      current
    DESCRIPTION ""
    INDEX { affirmedServicesContentCacheProxyServiceStatisticsCluster-levelSummaryChassis }
        ::= { affirmedServicesContentCacheProxyServiceStatisticsCluster-levelSummaryTable 1 }

AffirmedServicesContentCacheProxyServiceStatisticsCluster-levelSummaryEntry ::=
    SEQUENCE {
        affirmedServicesContentCacheProxyServiceStatisticsCluster-levelSummaryChassis Unsigned32,
        affirmedServicesContentCacheProxyServiceStatisticsCluster-levelSummaryNumcacheserviceattempts ConfdString,
        affirmedServicesContentCacheProxyServiceStatisticsCluster-levelSummaryNumcacheservicesuccess ConfdString,
        affirmedServicesContentCacheProxyServiceStatisticsCluster-levelSummaryNumcacheserviceabortedbyclient ConfdString,
        affirmedServicesContentCacheProxyServiceStatisticsCluster-levelSummaryNumcacheservicefailed ConfdString,
        affirmedServicesContentCacheProxyServiceStatisticsCluster-levelSummaryNumcacheservicesuccessdisk ConfdString,
        affirmedServicesContentCacheProxyServiceStatisticsCluster-levelSummaryNumcacheservicesuccessmemory ConfdString,
        affirmedServicesContentCacheProxyServiceStatisticsCluster-levelSummaryNumcacheservicebytesdisk ConfdString,
        affirmedServicesContentCacheProxyServiceStatisticsCluster-levelSummaryNumcacheservicebytesmemory ConfdString
    }

affirmedServicesContentCacheProxyServiceStatisticsCluster-levelSummaryChassis OBJECT-TYPE
    SYNTAX      Unsigned32
    MAX-ACCESS  not-accessible
    STATUS      current
    DESCRIPTION "chassis ID"
    ::= { affirmedServicesContentCacheProxyServiceStatisticsCluster-levelSummaryEntry 1 }

affirmedServicesContentCacheProxyServiceStatisticsCluster-levelSummaryNumcacheserviceattempts OBJECT-TYPE
    SYNTAX      ConfdString
    MAX-ACCESS  read-only
    STATUS      current
    DESCRIPTION "Total number of cache service attempts"
    ::= { affirmedServicesContentCacheProxyServiceStatisticsCluster-levelSummaryEntry 2 }

affirmedServicesContentCacheProxyServiceStatisticsCluster-levelSummaryNumcacheservicesuccess OBJECT-TYPE
    SYNTAX      ConfdString
    MAX-ACCESS  read-only
    STATUS      current
    DESCRIPTION "Total number of cache service success"
    ::= { affirmedServicesContentCacheProxyServiceStatisticsCluster-levelSummaryEntry 3 }

affirmedServicesContentCacheProxyServiceStatisticsCluster-levelSummaryNumcacheserviceabortedbyclient OBJECT-TYPE
    SYNTAX      ConfdString
    MAX-ACCESS  read-only
    STATUS      current
    DESCRIPTION "Total number of proxy cache aborted by client"
    ::= { affirmedServicesContentCacheProxyServiceStatisticsCluster-levelSummaryEntry 4 }

affirmedServicesContentCacheProxyServiceStatisticsCluster-levelSummaryNumcacheservicefailed OBJECT-TYPE
    SYNTAX      ConfdString
    MAX-ACCESS  read-only
    STATUS      current
    DESCRIPTION "Total number of cache service failed"
    ::= { affirmedServicesContentCacheProxyServiceStatisticsCluster-levelSummaryEntry 5 }

affirmedServicesContentCacheProxyServiceStatisticsCluster-levelSummaryNumcacheservicesuccessdisk OBJECT-TYPE
    SYNTAX      ConfdString
    MAX-ACCESS  read-only
    STATUS      current
    DESCRIPTION "Total number of cache service success from disk"
    ::= { affirmedServicesContentCacheProxyServiceStatisticsCluster-levelSummaryEntry 6 }

affirmedServicesContentCacheProxyServiceStatisticsCluster-levelSummaryNumcacheservicesuccessmemory OBJECT-TYPE
    SYNTAX      ConfdString
    MAX-ACCESS  read-only
    STATUS      current
    DESCRIPTION "Total number of cache service success from memory"
    ::= { affirmedServicesContentCacheProxyServiceStatisticsCluster-levelSummaryEntry 7 }

affirmedServicesContentCacheProxyServiceStatisticsCluster-levelSummaryNumcacheservicebytesdisk OBJECT-TYPE
    SYNTAX      ConfdString
    MAX-ACCESS  read-only
    STATUS      current
    DESCRIPTION "Total number of cache service bytes from disk"
    ::= { affirmedServicesContentCacheProxyServiceStatisticsCluster-levelSummaryEntry 8 }

affirmedServicesContentCacheProxyServiceStatisticsCluster-levelSummaryNumcacheservicebytesmemory OBJECT-TYPE
    SYNTAX      ConfdString
    MAX-ACCESS  read-only
    STATUS      current
    DESCRIPTION "Total number of cache service bytes from memory"
    ::= { affirmedServicesContentCacheProxyServiceStatisticsCluster-levelSummaryEntry 9 }

affirmedServicesContentCacheProxyServiceStatisticsCluster-levelDetailTable OBJECT-TYPE
    SYNTAX      SEQUENCE OF AffirmedServicesContentCacheProxyServiceStatisticsCluster-levelDetailEntry
    MAX-ACCESS  not-accessible
    STATUS      current
    DESCRIPTION ""
    ::= { affirmedServicesContentCacheProxyServiceStatisticsCluster-level 2 }

affirmedServicesContentCacheProxyServiceStatisticsCluster-levelDetailEntry OBJECT-TYPE
    SYNTAX      AffirmedServicesContentCacheProxyServiceStatisticsCluster-levelDetailEntry
    MAX-ACCESS  not-accessible
    STATUS      current
    DESCRIPTION ""
    INDEX { affirmedServicesContentCacheProxyServiceStatisticsCluster-levelDetailChassis }
        ::= { affirmedServicesContentCacheProxyServiceStatisticsCluster-levelDetailTable 1 }

AffirmedServicesContentCacheProxyServiceStatisticsCluster-levelDetailEntry ::=
    SEQUENCE {
        affirmedServicesContentCacheProxyServiceStatisticsCluster-levelDetailChassis Unsigned32,
        affirmedServicesContentCacheProxyServiceStatisticsCluster-levelDetailNumcachehitobjects ConfdString,
        affirmedServicesContentCacheProxyServiceStatisticsCluster-levelDetailNumcachehitbytes ConfdString,
        affirmedServicesContentCacheProxyServiceStatisticsCluster-levelDetailNumcachemissobjects ConfdString,
        affirmedServicesContentCacheProxyServiceStatisticsCluster-levelDetailNumcachehitobjectsinmemory ConfdString,
        affirmedServicesContentCacheProxyServiceStatisticsCluster-levelDetailNumcachehitbytesinmemory ConfdString,
        affirmedServicesContentCacheProxyServiceStatisticsCluster-levelDetailNumcachehitobjectsondisk ConfdString,
        affirmedServicesContentCacheProxyServiceStatisticsCluster-levelDetailNumcachehitbytesondisk ConfdString,
        affirmedServicesContentCacheProxyServiceStatisticsCluster-levelDetailNumcurrentmetadata ConfdString,
        affirmedServicesContentCacheProxyServiceStatisticsCluster-levelDetailNumcurrentobjectsinmemory ConfdString,
        affirmedServicesContentCacheProxyServiceStatisticsCluster-levelDetailNumcurrentobjectsondisk ConfdString,
        affirmedServicesContentCacheProxyServiceStatisticsCluster-levelDetailNumcurrentbytesinmemory ConfdString,
        affirmedServicesContentCacheProxyServiceStatisticsCluster-levelDetailNumcurrentbytesondisk ConfdString,
        affirmedServicesContentCacheProxyServiceStatisticsCluster-levelDetailNumcachevideohitsobjects ConfdString,
        affirmedServicesContentCacheProxyServiceStatisticsCluster-levelDetailNumcachevideohitsbytes ConfdString,
        affirmedServicesContentCacheProxyServiceStatisticsCluster-levelDetailNumcurrentvideoobjects ConfdString,
        affirmedServicesContentCacheProxyServiceStatisticsCluster-levelDetailNumobjectspurgedtodisk ConfdString,
        affirmedServicesContentCacheProxyServiceStatisticsCluster-levelDetailNumbytespurgedtodisk ConfdString,
        affirmedServicesContentCacheProxyServiceStatisticsCluster-levelDetailNumobjectsevictedfromdisk ConfdString,
        affirmedServicesContentCacheProxyServiceStatisticsCluster-levelDetailNumbytesevictedfromdisk ConfdString,
        affirmedServicesContentCacheProxyServiceStatisticsCluster-levelDetailNumobjectsevictedfrommemory ConfdString,
        affirmedServicesContentCacheProxyServiceStatisticsCluster-levelDetailNumbytesevictedfrommemory ConfdString,
        affirmedServicesContentCacheProxyServiceStatisticsCluster-levelDetailNumcurrentcontentbuffers ConfdString,
        affirmedServicesContentCacheProxyServiceStatisticsCluster-levelDetailNumcurrentcontentblocks ConfdString,
        affirmedServicesContentCacheProxyServiceStatisticsCluster-levelDetailNumcurrentmutexblocks ConfdString,
        affirmedServicesContentCacheProxyServiceStatisticsCluster-levelDetailNumcurrentcachestate ConfdString,
        affirmedServicesContentCacheProxyServiceStatisticsCluster-levelDetailNumcurrentcontentbuffers64k ConfdString,
        affirmedServicesContentCacheProxyServiceStatisticsCluster-levelDetailNumtotalcontentbuffers4k ConfdString,
        affirmedServicesContentCacheProxyServiceStatisticsCluster-levelDetailNumtotalcontentbuffers64k ConfdString
    }

affirmedServicesContentCacheProxyServiceStatisticsCluster-levelDetailChassis OBJECT-TYPE
    SYNTAX      Unsigned32
    MAX-ACCESS  not-accessible
    STATUS      current
    DESCRIPTION "chassis ID"
    ::= { affirmedServicesContentCacheProxyServiceStatisticsCluster-levelDetailEntry 1 }

affirmedServicesContentCacheProxyServiceStatisticsCluster-levelDetailNumcachehitobjects OBJECT-TYPE
    SYNTAX      ConfdString
    MAX-ACCESS  read-only
    STATUS      current
    DESCRIPTION "Total number of objects served from cache"
    ::= { affirmedServicesContentCacheProxyServiceStatisticsCluster-levelDetailEntry 2 }

affirmedServicesContentCacheProxyServiceStatisticsCluster-levelDetailNumcachehitbytes OBJECT-TYPE
    SYNTAX      ConfdString
    MAX-ACCESS  read-only
    STATUS      current
    DESCRIPTION "Total number of bytes served from cache"
    ::= { affirmedServicesContentCacheProxyServiceStatisticsCluster-levelDetailEntry 3 }

affirmedServicesContentCacheProxyServiceStatisticsCluster-levelDetailNumcachemissobjects OBJECT-TYPE
    SYNTAX      ConfdString
    MAX-ACCESS  read-only
    STATUS      current
    DESCRIPTION "Total number of objects missed from cache"
    ::= { affirmedServicesContentCacheProxyServiceStatisticsCluster-levelDetailEntry 4 }

affirmedServicesContentCacheProxyServiceStatisticsCluster-levelDetailNumcachehitobjectsinmemory OBJECT-TYPE
    SYNTAX      ConfdString
    MAX-ACCESS  read-only
    STATUS      current
    DESCRIPTION "Total number of objects served from memory cache"
    ::= { affirmedServicesContentCacheProxyServiceStatisticsCluster-levelDetailEntry 5 }

affirmedServicesContentCacheProxyServiceStatisticsCluster-levelDetailNumcachehitbytesinmemory OBJECT-TYPE
    SYNTAX      ConfdString
    MAX-ACCESS  read-only
    STATUS      current
    DESCRIPTION "Total number of bytes served from memory cache"
    ::= { affirmedServicesContentCacheProxyServiceStatisticsCluster-levelDetailEntry 6 }

affirmedServicesContentCacheProxyServiceStatisticsCluster-levelDetailNumcachehitobjectsondisk OBJECT-TYPE
    SYNTAX      ConfdString
    MAX-ACCESS  read-only
    STATUS      current
    DESCRIPTION "Total number of objects served from disk cache"
    ::= { affirmedServicesContentCacheProxyServiceStatisticsCluster-levelDetailEntry 7 }

affirmedServicesContentCacheProxyServiceStatisticsCluster-levelDetailNumcachehitbytesondisk OBJECT-TYPE
    SYNTAX      ConfdString
    MAX-ACCESS  read-only
    STATUS      current
    DESCRIPTION "Total number of bytes served from disk cache"
    ::= { affirmedServicesContentCacheProxyServiceStatisticsCluster-levelDetailEntry 8 }

affirmedServicesContentCacheProxyServiceStatisticsCluster-levelDetailNumcurrentmetadata OBJECT-TYPE
    SYNTAX      ConfdString
    MAX-ACCESS  read-only
    STATUS      current
    DESCRIPTION "Total number of current MetaData"
    ::= { affirmedServicesContentCacheProxyServiceStatisticsCluster-levelDetailEntry 9 }

affirmedServicesContentCacheProxyServiceStatisticsCluster-levelDetailNumcurrentobjectsinmemory OBJECT-TYPE
    SYNTAX      ConfdString
    MAX-ACCESS  read-only
    STATUS      current
    DESCRIPTION "Total number of current Object in memory"
    ::= { affirmedServicesContentCacheProxyServiceStatisticsCluster-levelDetailEntry 10 }

affirmedServicesContentCacheProxyServiceStatisticsCluster-levelDetailNumcurrentobjectsondisk OBJECT-TYPE
    SYNTAX      ConfdString
    MAX-ACCESS  read-only
    STATUS      current
    DESCRIPTION "Total number of current Object on disk"
    ::= { affirmedServicesContentCacheProxyServiceStatisticsCluster-levelDetailEntry 11 }

affirmedServicesContentCacheProxyServiceStatisticsCluster-levelDetailNumcurrentbytesinmemory OBJECT-TYPE
    SYNTAX      ConfdString
    MAX-ACCESS  read-only
    STATUS      current
    DESCRIPTION "Total number of current Bytes in memory"
    ::= { affirmedServicesContentCacheProxyServiceStatisticsCluster-levelDetailEntry 12 }

affirmedServicesContentCacheProxyServiceStatisticsCluster-levelDetailNumcurrentbytesondisk OBJECT-TYPE
    SYNTAX      ConfdString
    MAX-ACCESS  read-only
    STATUS      current
    DESCRIPTION "Total number of current Bytes on disk"
    ::= { affirmedServicesContentCacheProxyServiceStatisticsCluster-levelDetailEntry 13 }

affirmedServicesContentCacheProxyServiceStatisticsCluster-levelDetailNumcachevideohitsobjects OBJECT-TYPE
    SYNTAX      ConfdString
    MAX-ACCESS  read-only
    STATUS      current
    DESCRIPTION "Total number of video objects served from cache"
    ::= { affirmedServicesContentCacheProxyServiceStatisticsCluster-levelDetailEntry 14 }

affirmedServicesContentCacheProxyServiceStatisticsCluster-levelDetailNumcachevideohitsbytes OBJECT-TYPE
    SYNTAX      ConfdString
    MAX-ACCESS  read-only
    STATUS      current
    DESCRIPTION "Total number of video bytes served from cache"
    ::= { affirmedServicesContentCacheProxyServiceStatisticsCluster-levelDetailEntry 15 }

affirmedServicesContentCacheProxyServiceStatisticsCluster-levelDetailNumcurrentvideoobjects OBJECT-TYPE
    SYNTAX      ConfdString
    MAX-ACCESS  read-only
    STATUS      current
    DESCRIPTION "Total number of current video objects in cache"
    ::= { affirmedServicesContentCacheProxyServiceStatisticsCluster-levelDetailEntry 16 }

affirmedServicesContentCacheProxyServiceStatisticsCluster-levelDetailNumobjectspurgedtodisk OBJECT-TYPE
    SYNTAX      ConfdString
    MAX-ACCESS  read-only
    STATUS      current
    DESCRIPTION "Total number of objects purged to disk"
    ::= { affirmedServicesContentCacheProxyServiceStatisticsCluster-levelDetailEntry 17 }

affirmedServicesContentCacheProxyServiceStatisticsCluster-levelDetailNumbytespurgedtodisk OBJECT-TYPE
    SYNTAX      ConfdString
    MAX-ACCESS  read-only
    STATUS      current
    DESCRIPTION "Total number of bytes purged to disk"
    ::= { affirmedServicesContentCacheProxyServiceStatisticsCluster-levelDetailEntry 18 }

affirmedServicesContentCacheProxyServiceStatisticsCluster-levelDetailNumobjectsevictedfromdisk OBJECT-TYPE
    SYNTAX      ConfdString
    MAX-ACCESS  read-only
    STATUS      current
    DESCRIPTION "Total number of objects evicted from disk"
    ::= { affirmedServicesContentCacheProxyServiceStatisticsCluster-levelDetailEntry 19 }

affirmedServicesContentCacheProxyServiceStatisticsCluster-levelDetailNumbytesevictedfromdisk OBJECT-TYPE
    SYNTAX      ConfdString
    MAX-ACCESS  read-only
    STATUS      current
    DESCRIPTION "Total number of bytes evicted from disk"
    ::= { affirmedServicesContentCacheProxyServiceStatisticsCluster-levelDetailEntry 20 }

affirmedServicesContentCacheProxyServiceStatisticsCluster-levelDetailNumobjectsevictedfrommemory OBJECT-TYPE
    SYNTAX      ConfdString
    MAX-ACCESS  read-only
    STATUS      current
    DESCRIPTION "Total number of objects evicted from memory"
    ::= { affirmedServicesContentCacheProxyServiceStatisticsCluster-levelDetailEntry 21 }

affirmedServicesContentCacheProxyServiceStatisticsCluster-levelDetailNumbytesevictedfrommemory OBJECT-TYPE
    SYNTAX      ConfdString
    MAX-ACCESS  read-only
    STATUS      current
    DESCRIPTION "Total number of bytes evicted from memory"
    ::= { affirmedServicesContentCacheProxyServiceStatisticsCluster-levelDetailEntry 22 }

affirmedServicesContentCacheProxyServiceStatisticsCluster-levelDetailNumcurrentcontentbuffers OBJECT-TYPE
    SYNTAX      ConfdString
    MAX-ACCESS  read-only
    STATUS      current
    DESCRIPTION "Total number of 4KB current content buffer"
    ::= { affirmedServicesContentCacheProxyServiceStatisticsCluster-levelDetailEntry 23 }

affirmedServicesContentCacheProxyServiceStatisticsCluster-levelDetailNumcurrentcontentblocks OBJECT-TYPE
    SYNTAX      ConfdString
    MAX-ACCESS  read-only
    STATUS      current
    DESCRIPTION "Total number of current content blocks"
    ::= { affirmedServicesContentCacheProxyServiceStatisticsCluster-levelDetailEntry 24 }

affirmedServicesContentCacheProxyServiceStatisticsCluster-levelDetailNumcurrentmutexblocks OBJECT-TYPE
    SYNTAX      ConfdString
    MAX-ACCESS  read-only
    STATUS      current
    DESCRIPTION "Total number of current mutex blocks"
    ::= { affirmedServicesContentCacheProxyServiceStatisticsCluster-levelDetailEntry 25 }

affirmedServicesContentCacheProxyServiceStatisticsCluster-levelDetailNumcurrentcachestate OBJECT-TYPE
    SYNTAX      ConfdString
    MAX-ACCESS  read-only
    STATUS      current
    DESCRIPTION "Current VM Nodes Caching"
    ::= { affirmedServicesContentCacheProxyServiceStatisticsCluster-levelDetailEntry 26 }

affirmedServicesContentCacheProxyServiceStatisticsCluster-levelDetailNumcurrentcontentbuffers64k OBJECT-TYPE
    SYNTAX      ConfdString
    MAX-ACCESS  read-only
    STATUS      current
    DESCRIPTION "Total number of 64KB current content buffer"
    ::= { affirmedServicesContentCacheProxyServiceStatisticsCluster-levelDetailEntry 27 }

affirmedServicesContentCacheProxyServiceStatisticsCluster-levelDetailNumtotalcontentbuffers4k OBJECT-TYPE
    SYNTAX      ConfdString
    MAX-ACCESS  read-only
    STATUS      current
    DESCRIPTION "Total number of available 4KB content buffers"
    ::= { affirmedServicesContentCacheProxyServiceStatisticsCluster-levelDetailEntry 28 }

affirmedServicesContentCacheProxyServiceStatisticsCluster-levelDetailNumtotalcontentbuffers64k OBJECT-TYPE
    SYNTAX      ConfdString
    MAX-ACCESS  read-only
    STATUS      current
    DESCRIPTION "Total number of available 64KB content buffers"
    ::= { affirmedServicesContentCacheProxyServiceStatisticsCluster-levelDetailEntry 29 }

affirmedServicesContentCacheProxyServiceStatisticsNode-levelSummaryTable OBJECT-TYPE
    SYNTAX      SEQUENCE OF AffirmedServicesContentCacheProxyServiceStatisticsNode-levelSummaryEntry
    MAX-ACCESS  not-accessible
    STATUS      current
    DESCRIPTION ""
    ::= { affirmedServicesContentCacheProxyServiceStatisticsNode-level 1 }

affirmedServicesContentCacheProxyServiceStatisticsNode-levelSummaryEntry OBJECT-TYPE
    SYNTAX      AffirmedServicesContentCacheProxyServiceStatisticsNode-levelSummaryEntry
    MAX-ACCESS  not-accessible
    STATUS      current
    DESCRIPTION ""
    INDEX { affirmedServicesContentCacheProxyServiceStatisticsNode-levelSummaryChassis, affirmedServicesContentCacheProxyServiceStatisticsNode-levelSummarySlot }
        ::= { affirmedServicesContentCacheProxyServiceStatisticsNode-levelSummaryTable 1 }

AffirmedServicesContentCacheProxyServiceStatisticsNode-levelSummaryEntry ::=
    SEQUENCE {
        affirmedServicesContentCacheProxyServiceStatisticsNode-levelSummaryChassis Unsigned32,
        affirmedServicesContentCacheProxyServiceStatisticsNode-levelSummarySlot INTEGER,
        affirmedServicesContentCacheProxyServiceStatisticsNode-levelSummaryNumcacheserviceattempts ConfdString,
        affirmedServicesContentCacheProxyServiceStatisticsNode-levelSummaryNumcacheservicesuccess ConfdString,
        affirmedServicesContentCacheProxyServiceStatisticsNode-levelSummaryNumcacheserviceabortedbyclient ConfdString,
        affirmedServicesContentCacheProxyServiceStatisticsNode-levelSummaryNumcacheservicefailed ConfdString,
        affirmedServicesContentCacheProxyServiceStatisticsNode-levelSummaryNumcacheservicesuccessdisk ConfdString,
        affirmedServicesContentCacheProxyServiceStatisticsNode-levelSummaryNumcacheservicesuccessmemory ConfdString,
        affirmedServicesContentCacheProxyServiceStatisticsNode-levelSummaryNumcacheservicebytesdisk ConfdString,
        affirmedServicesContentCacheProxyServiceStatisticsNode-levelSummaryNumcacheservicebytesmemory ConfdString
    }

affirmedServicesContentCacheProxyServiceStatisticsNode-levelSummaryChassis OBJECT-TYPE
    SYNTAX      Unsigned32
    MAX-ACCESS  not-accessible
    STATUS      current
    DESCRIPTION "chassis ID"
    ::= { affirmedServicesContentCacheProxyServiceStatisticsNode-levelSummaryEntry 1 }

affirmedServicesContentCacheProxyServiceStatisticsNode-levelSummarySlot OBJECT-TYPE
    SYNTAX      INTEGER {a1(1),a2(2),a3(3),a4(4),a5(5),a6(6),a7(7),a8(8),a9(9),a10(10),a11(11),a12(12),a13(13),a14(14),a15(15),a16(16),a17(17),a18(18),a19(19),a20(20),a21(21),a22(22),a23(23),a24(24),a25(25),a26(26),a27(27),a28(28),a29(29),a30(30),a31(31),a32(32),a33(33),a34(34),a35(35),a36(36),a37(37),a38(38),a39(39),a40(40),a41(41),a42(42),a43(43),a44(44),a45(45),a46(46),a47(47),a48(48),a49(49),a50(50),a51(51),a52(52),a53(53),a54(54),a55(55),a56(56),a57(57),a58(58),a59(59),a60(60),a61(61),a62(62),a63(63),a64(64),a65(65),a66(66),a67(67),a68(68),a69(69),a70(70),a71(71),a72(72),a73(73),a74(74),a75(75),a76(76),a77(77),a78(78),a79(79),a80(80),a81(81),a82(82),a83(83),a84(84),a85(85),a86(86),a87(87),a88(88),a89(89),a90(90),a91(91),a92(92),a93(93),a94(94),a95(95),a96(96),a97(97),a98(98),a99(99),a100(100),a101(101),a102(102),a103(103),a104(104),a105(105),a106(106),a107(107),a108(108),a109(109),a110(110),a111(111),a112(112),a113(113),a114(114),a115(115),a116(116),a117(117),a118(118),a119(119),a120(120),a121(121),a122(122),a123(123),a124(124),a125(125),a126(126),a127(127),a128(128)}
    MAX-ACCESS  not-accessible
    STATUS      current
    DESCRIPTION "slot number"
    ::= { affirmedServicesContentCacheProxyServiceStatisticsNode-levelSummaryEntry 2 }

affirmedServicesContentCacheProxyServiceStatisticsNode-levelSummaryNumcacheserviceattempts OBJECT-TYPE
    SYNTAX      ConfdString
    MAX-ACCESS  read-only
    STATUS      current
    DESCRIPTION "Total number of cache service attempts"
    ::= { affirmedServicesContentCacheProxyServiceStatisticsNode-levelSummaryEntry 3 }

affirmedServicesContentCacheProxyServiceStatisticsNode-levelSummaryNumcacheservicesuccess OBJECT-TYPE
    SYNTAX      ConfdString
    MAX-ACCESS  read-only
    STATUS      current
    DESCRIPTION "Total number of cache service success"
    ::= { affirmedServicesContentCacheProxyServiceStatisticsNode-levelSummaryEntry 4 }

affirmedServicesContentCacheProxyServiceStatisticsNode-levelSummaryNumcacheserviceabortedbyclient OBJECT-TYPE
    SYNTAX      ConfdString
    MAX-ACCESS  read-only
    STATUS      current
    DESCRIPTION "Total number of proxy cache aborted by client"
    ::= { affirmedServicesContentCacheProxyServiceStatisticsNode-levelSummaryEntry 5 }

affirmedServicesContentCacheProxyServiceStatisticsNode-levelSummaryNumcacheservicefailed OBJECT-TYPE
    SYNTAX      ConfdString
    MAX-ACCESS  read-only
    STATUS      current
    DESCRIPTION "Total number of cache service failed"
    ::= { affirmedServicesContentCacheProxyServiceStatisticsNode-levelSummaryEntry 6 }

affirmedServicesContentCacheProxyServiceStatisticsNode-levelSummaryNumcacheservicesuccessdisk OBJECT-TYPE
    SYNTAX      ConfdString
    MAX-ACCESS  read-only
    STATUS      current
    DESCRIPTION "Total number of cache service success from disk"
    ::= { affirmedServicesContentCacheProxyServiceStatisticsNode-levelSummaryEntry 7 }

affirmedServicesContentCacheProxyServiceStatisticsNode-levelSummaryNumcacheservicesuccessmemory OBJECT-TYPE
    SYNTAX      ConfdString
    MAX-ACCESS  read-only
    STATUS      current
    DESCRIPTION "Total number of cache service success from memory"
    ::= { affirmedServicesContentCacheProxyServiceStatisticsNode-levelSummaryEntry 8 }

affirmedServicesContentCacheProxyServiceStatisticsNode-levelSummaryNumcacheservicebytesdisk OBJECT-TYPE
    SYNTAX      ConfdString
    MAX-ACCESS  read-only
    STATUS      current
    DESCRIPTION "Total number of cache service bytes from disk"
    ::= { affirmedServicesContentCacheProxyServiceStatisticsNode-levelSummaryEntry 9 }

affirmedServicesContentCacheProxyServiceStatisticsNode-levelSummaryNumcacheservicebytesmemory OBJECT-TYPE
    SYNTAX      ConfdString
    MAX-ACCESS  read-only
    STATUS      current
    DESCRIPTION "Total number of cache service bytes from memory"
    ::= { affirmedServicesContentCacheProxyServiceStatisticsNode-levelSummaryEntry 10 }

affirmedServicesContentCacheProxyServiceStatisticsNode-levelDetailTable OBJECT-TYPE
    SYNTAX      SEQUENCE OF AffirmedServicesContentCacheProxyServiceStatisticsNode-levelDetailEntry
    MAX-ACCESS  not-accessible
    STATUS      current
    DESCRIPTION ""
    ::= { affirmedServicesContentCacheProxyServiceStatisticsNode-level 2 }

affirmedServicesContentCacheProxyServiceStatisticsNode-levelDetailEntry OBJECT-TYPE
    SYNTAX      AffirmedServicesContentCacheProxyServiceStatisticsNode-levelDetailEntry
    MAX-ACCESS  not-accessible
    STATUS      current
    DESCRIPTION ""
    INDEX { affirmedServicesContentCacheProxyServiceStatisticsNode-levelDetailChassis, affirmedServicesContentCacheProxyServiceStatisticsNode-levelDetailSlot }
        ::= { affirmedServicesContentCacheProxyServiceStatisticsNode-levelDetailTable 1 }

AffirmedServicesContentCacheProxyServiceStatisticsNode-levelDetailEntry ::=
    SEQUENCE {
        affirmedServicesContentCacheProxyServiceStatisticsNode-levelDetailChassis Unsigned32,
        affirmedServicesContentCacheProxyServiceStatisticsNode-levelDetailSlot Unsigned32,
        affirmedServicesContentCacheProxyServiceStatisticsNode-levelDetailNumcachehitobjects ConfdString,
        affirmedServicesContentCacheProxyServiceStatisticsNode-levelDetailNumcachehitbytes ConfdString,
        affirmedServicesContentCacheProxyServiceStatisticsNode-levelDetailNumcachemissobjects ConfdString,
        affirmedServicesContentCacheProxyServiceStatisticsNode-levelDetailNumcachehitobjectsinmemory ConfdString,
        affirmedServicesContentCacheProxyServiceStatisticsNode-levelDetailNumcachehitbytesinmemory ConfdString,
        affirmedServicesContentCacheProxyServiceStatisticsNode-levelDetailNumcachehitobjectsondisk ConfdString,
        affirmedServicesContentCacheProxyServiceStatisticsNode-levelDetailNumcachehitbytesondisk ConfdString,
        affirmedServicesContentCacheProxyServiceStatisticsNode-levelDetailNumcurrentmetadata ConfdString,
        affirmedServicesContentCacheProxyServiceStatisticsNode-levelDetailNumcurrentobjectsinmemory ConfdString,
        affirmedServicesContentCacheProxyServiceStatisticsNode-levelDetailNumcurrentobjectsondisk ConfdString,
        affirmedServicesContentCacheProxyServiceStatisticsNode-levelDetailNumcurrentbytesinmemory ConfdString,
        affirmedServicesContentCacheProxyServiceStatisticsNode-levelDetailNumcurrentbytesondisk ConfdString,
        affirmedServicesContentCacheProxyServiceStatisticsNode-levelDetailNumcachevideohitsobjects ConfdString,
        affirmedServicesContentCacheProxyServiceStatisticsNode-levelDetailNumcachevideohitsbytes ConfdString,
        affirmedServicesContentCacheProxyServiceStatisticsNode-levelDetailNumcurrentvideoobjects ConfdString,
        affirmedServicesContentCacheProxyServiceStatisticsNode-levelDetailNumobjectspurgedtodisk ConfdString,
        affirmedServicesContentCacheProxyServiceStatisticsNode-levelDetailNumbytespurgedtodisk ConfdString,
        affirmedServicesContentCacheProxyServiceStatisticsNode-levelDetailNumobjectsevictedfromdisk ConfdString,
        affirmedServicesContentCacheProxyServiceStatisticsNode-levelDetailNumbytesevictedfromdisk ConfdString,
        affirmedServicesContentCacheProxyServiceStatisticsNode-levelDetailNumobjectsevictedfrommemory ConfdString,
        affirmedServicesContentCacheProxyServiceStatisticsNode-levelDetailNumbytesevictedfrommemory ConfdString,
        affirmedServicesContentCacheProxyServiceStatisticsNode-levelDetailNumcurrentcontentbuffers ConfdString,
        affirmedServicesContentCacheProxyServiceStatisticsNode-levelDetailNumcurrentcontentblocks ConfdString,
        affirmedServicesContentCacheProxyServiceStatisticsNode-levelDetailNumcurrentmutexblocks ConfdString,
        affirmedServicesContentCacheProxyServiceStatisticsNode-levelDetailNumcurrentcachestate ConfdString,
        affirmedServicesContentCacheProxyServiceStatisticsNode-levelDetailNumcurrentcontentbuffers64k ConfdString,
        affirmedServicesContentCacheProxyServiceStatisticsNode-levelDetailNumtotalcontentbuffers4k ConfdString,
        affirmedServicesContentCacheProxyServiceStatisticsNode-levelDetailNumtotalcontentbuffers64k ConfdString
    }

affirmedServicesContentCacheProxyServiceStatisticsNode-levelDetailChassis OBJECT-TYPE
    SYNTAX      Unsigned32
    MAX-ACCESS  not-accessible
    STATUS      current
    DESCRIPTION "chassis ID"
    ::= { affirmedServicesContentCacheProxyServiceStatisticsNode-levelDetailEntry 1 }

affirmedServicesContentCacheProxyServiceStatisticsNode-levelDetailSlot OBJECT-TYPE
    SYNTAX      Unsigned32
    MAX-ACCESS  not-accessible
    STATUS      current
    DESCRIPTION "slot number"
    ::= { affirmedServicesContentCacheProxyServiceStatisticsNode-levelDetailEntry 2 }

affirmedServicesContentCacheProxyServiceStatisticsNode-levelDetailNumcachehitobjects OBJECT-TYPE
    SYNTAX      ConfdString
    MAX-ACCESS  read-only
    STATUS      current
    DESCRIPTION "Total number of objects served from cache"
    ::= { affirmedServicesContentCacheProxyServiceStatisticsNode-levelDetailEntry 3 }

affirmedServicesContentCacheProxyServiceStatisticsNode-levelDetailNumcachehitbytes OBJECT-TYPE
    SYNTAX      ConfdString
    MAX-ACCESS  read-only
    STATUS      current
    DESCRIPTION "Total number of bytes served from cache"
    ::= { affirmedServicesContentCacheProxyServiceStatisticsNode-levelDetailEntry 4 }

affirmedServicesContentCacheProxyServiceStatisticsNode-levelDetailNumcachemissobjects OBJECT-TYPE
    SYNTAX      ConfdString
    MAX-ACCESS  read-only
    STATUS      current
    DESCRIPTION "Total number of objects missed from cache"
    ::= { affirmedServicesContentCacheProxyServiceStatisticsNode-levelDetailEntry 5 }

affirmedServicesContentCacheProxyServiceStatisticsNode-levelDetailNumcachehitobjectsinmemory OBJECT-TYPE
    SYNTAX      ConfdString
    MAX-ACCESS  read-only
    STATUS      current
    DESCRIPTION "Total number of objects served from memory cache"
    ::= { affirmedServicesContentCacheProxyServiceStatisticsNode-levelDetailEntry 6 }

affirmedServicesContentCacheProxyServiceStatisticsNode-levelDetailNumcachehitbytesinmemory OBJECT-TYPE
    SYNTAX      ConfdString
    MAX-ACCESS  read-only
    STATUS      current
    DESCRIPTION "Total number of bytes served from memory cache"
    ::= { affirmedServicesContentCacheProxyServiceStatisticsNode-levelDetailEntry 7 }

affirmedServicesContentCacheProxyServiceStatisticsNode-levelDetailNumcachehitobjectsondisk OBJECT-TYPE
    SYNTAX      ConfdString
    MAX-ACCESS  read-only
    STATUS      current
    DESCRIPTION "Total number of objects served from disk cache"
    ::= { affirmedServicesContentCacheProxyServiceStatisticsNode-levelDetailEntry 8 }

affirmedServicesContentCacheProxyServiceStatisticsNode-levelDetailNumcachehitbytesondisk OBJECT-TYPE
    SYNTAX      ConfdString
    MAX-ACCESS  read-only
    STATUS      current
    DESCRIPTION "Total number of bytes served from disk cache"
    ::= { affirmedServicesContentCacheProxyServiceStatisticsNode-levelDetailEntry 9 }

affirmedServicesContentCacheProxyServiceStatisticsNode-levelDetailNumcurrentmetadata OBJECT-TYPE
    SYNTAX      ConfdString
    MAX-ACCESS  read-only
    STATUS      current
    DESCRIPTION "Total number of current MetaData"
    ::= { affirmedServicesContentCacheProxyServiceStatisticsNode-levelDetailEntry 10 }

affirmedServicesContentCacheProxyServiceStatisticsNode-levelDetailNumcurrentobjectsinmemory OBJECT-TYPE
    SYNTAX      ConfdString
    MAX-ACCESS  read-only
    STATUS      current
    DESCRIPTION "Total number of current Object in memory"
    ::= { affirmedServicesContentCacheProxyServiceStatisticsNode-levelDetailEntry 11 }

affirmedServicesContentCacheProxyServiceStatisticsNode-levelDetailNumcurrentobjectsondisk OBJECT-TYPE
    SYNTAX      ConfdString
    MAX-ACCESS  read-only
    STATUS      current
    DESCRIPTION "Total number of current Object on disk"
    ::= { affirmedServicesContentCacheProxyServiceStatisticsNode-levelDetailEntry 12 }

affirmedServicesContentCacheProxyServiceStatisticsNode-levelDetailNumcurrentbytesinmemory OBJECT-TYPE
    SYNTAX      ConfdString
    MAX-ACCESS  read-only
    STATUS      current
    DESCRIPTION "Total number of current Bytes in memory"
    ::= { affirmedServicesContentCacheProxyServiceStatisticsNode-levelDetailEntry 13 }

affirmedServicesContentCacheProxyServiceStatisticsNode-levelDetailNumcurrentbytesondisk OBJECT-TYPE
    SYNTAX      ConfdString
    MAX-ACCESS  read-only
    STATUS      current
    DESCRIPTION "Total number of current Bytes on disk"
    ::= { affirmedServicesContentCacheProxyServiceStatisticsNode-levelDetailEntry 14 }

affirmedServicesContentCacheProxyServiceStatisticsNode-levelDetailNumcachevideohitsobjects OBJECT-TYPE
    SYNTAX      ConfdString
    MAX-ACCESS  read-only
    STATUS      current
    DESCRIPTION "Total number of video objects served from cache"
    ::= { affirmedServicesContentCacheProxyServiceStatisticsNode-levelDetailEntry 15 }

affirmedServicesContentCacheProxyServiceStatisticsNode-levelDetailNumcachevideohitsbytes OBJECT-TYPE
    SYNTAX      ConfdString
    MAX-ACCESS  read-only
    STATUS      current
    DESCRIPTION "Total number of video bytes served from cache"
    ::= { affirmedServicesContentCacheProxyServiceStatisticsNode-levelDetailEntry 16 }

affirmedServicesContentCacheProxyServiceStatisticsNode-levelDetailNumcurrentvideoobjects OBJECT-TYPE
    SYNTAX      ConfdString
    MAX-ACCESS  read-only
    STATUS      current
    DESCRIPTION "Total number of current video objects in cache"
    ::= { affirmedServicesContentCacheProxyServiceStatisticsNode-levelDetailEntry 17 }

affirmedServicesContentCacheProxyServiceStatisticsNode-levelDetailNumobjectspurgedtodisk OBJECT-TYPE
    SYNTAX      ConfdString
    MAX-ACCESS  read-only
    STATUS      current
    DESCRIPTION "Total number of objects purged to disk"
    ::= { affirmedServicesContentCacheProxyServiceStatisticsNode-levelDetailEntry 18 }

affirmedServicesContentCacheProxyServiceStatisticsNode-levelDetailNumbytespurgedtodisk OBJECT-TYPE
    SYNTAX      ConfdString
    MAX-ACCESS  read-only
    STATUS      current
    DESCRIPTION "Total number of bytes purged to disk"
    ::= { affirmedServicesContentCacheProxyServiceStatisticsNode-levelDetailEntry 19 }

affirmedServicesContentCacheProxyServiceStatisticsNode-levelDetailNumobjectsevictedfromdisk OBJECT-TYPE
    SYNTAX      ConfdString
    MAX-ACCESS  read-only
    STATUS      current
    DESCRIPTION "Total number of objects evicted from disk"
    ::= { affirmedServicesContentCacheProxyServiceStatisticsNode-levelDetailEntry 20 }

affirmedServicesContentCacheProxyServiceStatisticsNode-levelDetailNumbytesevictedfromdisk OBJECT-TYPE
    SYNTAX      ConfdString
    MAX-ACCESS  read-only
    STATUS      current
    DESCRIPTION "Total number of bytes evicted from disk"
    ::= { affirmedServicesContentCacheProxyServiceStatisticsNode-levelDetailEntry 21 }

affirmedServicesContentCacheProxyServiceStatisticsNode-levelDetailNumobjectsevictedfrommemory OBJECT-TYPE
    SYNTAX      ConfdString
    MAX-ACCESS  read-only
    STATUS      current
    DESCRIPTION "Total number of objects evicted from memory"
    ::= { affirmedServicesContentCacheProxyServiceStatisticsNode-levelDetailEntry 22 }

affirmedServicesContentCacheProxyServiceStatisticsNode-levelDetailNumbytesevictedfrommemory OBJECT-TYPE
    SYNTAX      ConfdString
    MAX-ACCESS  read-only
    STATUS      current
    DESCRIPTION "Total number of bytes evicted from memory"
    ::= { affirmedServicesContentCacheProxyServiceStatisticsNode-levelDetailEntry 23 }

affirmedServicesContentCacheProxyServiceStatisticsNode-levelDetailNumcurrentcontentbuffers OBJECT-TYPE
    SYNTAX      ConfdString
    MAX-ACCESS  read-only
    STATUS      current
    DESCRIPTION "Total number of 4KB current content buffer"
    ::= { affirmedServicesContentCacheProxyServiceStatisticsNode-levelDetailEntry 24 }

affirmedServicesContentCacheProxyServiceStatisticsNode-levelDetailNumcurrentcontentblocks OBJECT-TYPE
    SYNTAX      ConfdString
    MAX-ACCESS  read-only
    STATUS      current
    DESCRIPTION "Total number of current content blocks"
    ::= { affirmedServicesContentCacheProxyServiceStatisticsNode-levelDetailEntry 25 }

affirmedServicesContentCacheProxyServiceStatisticsNode-levelDetailNumcurrentmutexblocks OBJECT-TYPE
    SYNTAX      ConfdString
    MAX-ACCESS  read-only
    STATUS      current
    DESCRIPTION "Total number of current mutex blocks"
    ::= { affirmedServicesContentCacheProxyServiceStatisticsNode-levelDetailEntry 26 }

affirmedServicesContentCacheProxyServiceStatisticsNode-levelDetailNumcurrentcachestate OBJECT-TYPE
    SYNTAX      ConfdString
    MAX-ACCESS  read-only
    STATUS      current
    DESCRIPTION "Current VM Nodes Caching"
    ::= { affirmedServicesContentCacheProxyServiceStatisticsNode-levelDetailEntry 27 }

affirmedServicesContentCacheProxyServiceStatisticsNode-levelDetailNumcurrentcontentbuffers64k OBJECT-TYPE
    SYNTAX      ConfdString
    MAX-ACCESS  read-only
    STATUS      current
    DESCRIPTION "Total number of 64KB current content buffer"
    ::= { affirmedServicesContentCacheProxyServiceStatisticsNode-levelDetailEntry 28 }

affirmedServicesContentCacheProxyServiceStatisticsNode-levelDetailNumtotalcontentbuffers4k OBJECT-TYPE
    SYNTAX      ConfdString
    MAX-ACCESS  read-only
    STATUS      current
    DESCRIPTION "Total number of available 4KB content buffers"
    ::= { affirmedServicesContentCacheProxyServiceStatisticsNode-levelDetailEntry 29 }

affirmedServicesContentCacheProxyServiceStatisticsNode-levelDetailNumtotalcontentbuffers64k OBJECT-TYPE
    SYNTAX      ConfdString
    MAX-ACCESS  read-only
    STATUS      current
    DESCRIPTION "Total number of available 64KB content buffers"
    ::= { affirmedServicesContentCacheProxyServiceStatisticsNode-levelDetailEntry 30 }

affirmedServicesMeteringServiceDataFlowTable OBJECT-TYPE
    SYNTAX      SEQUENCE OF AffirmedServicesMeteringServiceDataFlowEntry
    MAX-ACCESS  not-accessible
    STATUS      current
    DESCRIPTION ""
    ::= { affirmedServicesMetering 1 }

affirmedServicesMeteringServiceDataFlowEntry OBJECT-TYPE
    SYNTAX      AffirmedServicesMeteringServiceDataFlowEntry
    MAX-ACCESS  not-accessible
    STATUS      current
    DESCRIPTION ""
    INDEX { affirmedServicesMeteringServiceDataFlowMeteringService, affirmedServicesMeteringServiceDataFlowRatingGroupPriority, affirmedServicesMeteringServiceDataFlowServiceRulePriority, affirmedServicesMeteringServiceDataFlowRatingGroup, affirmedServicesMeteringServiceDataFlowServiceRule }
        ::= { affirmedServicesMeteringServiceDataFlowTable 1 }

AffirmedServicesMeteringServiceDataFlowEntry ::=
    SEQUENCE {
        affirmedServicesMeteringServiceDataFlowMeteringService String,
        affirmedServicesMeteringServiceDataFlowRatingGroupPriority Unsigned32,
        affirmedServicesMeteringServiceDataFlowServiceRulePriority Unsigned32,
        affirmedServicesMeteringServiceDataFlowRatingGroup String,
        affirmedServicesMeteringServiceDataFlowServiceRule String,
        affirmedServicesMeteringServiceDataFlowRatingGroupId Unsigned32,
        affirmedServicesMeteringServiceDataFlowServiceRuleId Unsigned32
    }

affirmedServicesMeteringServiceDataFlowMeteringService OBJECT-TYPE
    SYNTAX      String
    MAX-ACCESS  not-accessible
    STATUS      current
    DESCRIPTION "the name of the metering-service"
    ::= { affirmedServicesMeteringServiceDataFlowEntry 1 }

affirmedServicesMeteringServiceDataFlowRatingGroupPriority OBJECT-TYPE
    SYNTAX      Unsigned32
    MAX-ACCESS  not-accessible
    STATUS      current
    DESCRIPTION "the priority of the rating-group"
    ::= { affirmedServicesMeteringServiceDataFlowEntry 2 }

affirmedServicesMeteringServiceDataFlowServiceRulePriority OBJECT-TYPE
    SYNTAX      Unsigned32
    MAX-ACCESS  not-accessible
    STATUS      current
    DESCRIPTION "the priority of the service-rule"
    ::= { affirmedServicesMeteringServiceDataFlowEntry 3 }

affirmedServicesMeteringServiceDataFlowRatingGroup OBJECT-TYPE
    SYNTAX      String
    MAX-ACCESS  not-accessible
    STATUS      current
    DESCRIPTION "the name of the rating-group"
    ::= { affirmedServicesMeteringServiceDataFlowEntry 4 }

affirmedServicesMeteringServiceDataFlowServiceRule OBJECT-TYPE
    SYNTAX      String
    MAX-ACCESS  not-accessible
    STATUS      current
    DESCRIPTION "the name of the service-rule"
    ::= { affirmedServicesMeteringServiceDataFlowEntry 5 }

affirmedServicesMeteringServiceDataFlowRatingGroupId OBJECT-TYPE
    SYNTAX      Unsigned32
    MAX-ACCESS  read-only
    STATUS      current
    DESCRIPTION "the internal ID of the rating-group, used to identify PDN-session service-data-flows {session-id, service-type=metering, rating-group-id, service-rule-id}"
    ::= { affirmedServicesMeteringServiceDataFlowEntry 6 }

affirmedServicesMeteringServiceDataFlowServiceRuleId OBJECT-TYPE
    SYNTAX      Unsigned32
    MAX-ACCESS  read-only
    STATUS      current
    DESCRIPTION "the internal ID of the service-rule, used to identify PDN-session service-data-flows {session-id, service-type=metering, rating-group-id, service-rule-id}"
    ::= { affirmedServicesMeteringServiceDataFlowEntry 7 }

affirmedServicesDnsProxyServiceModuleStatsTable OBJECT-TYPE
    SYNTAX      SEQUENCE OF AffirmedServicesDnsProxyServiceModuleStatsEntry
    MAX-ACCESS  not-accessible
    STATUS      current
    DESCRIPTION ""
    ::= { affirmedServicesDnsProxyService 1 }

affirmedServicesDnsProxyServiceModuleStatsEntry OBJECT-TYPE
    SYNTAX      AffirmedServicesDnsProxyServiceModuleStatsEntry
    MAX-ACCESS  not-accessible
    STATUS      current
    DESCRIPTION ""
    INDEX { affirmedServicesDnsProxyServiceModuleStatsNode }
        ::= { affirmedServicesDnsProxyServiceModuleStatsTable 1 }

AffirmedServicesDnsProxyServiceModuleStatsEntry ::=
    SEQUENCE {
        affirmedServicesDnsProxyServiceModuleStatsNode Unsigned32,
        affirmedServicesDnsProxyServiceModuleStatsNumdnspacketsprocessed ConfdString,
        affirmedServicesDnsProxyServiceModuleStatsNumdnsupstreampacketsprocessed ConfdString,
        affirmedServicesDnsProxyServiceModuleStatsNumdnsdownstreampacketsprocessed ConfdString,
        affirmedServicesDnsProxyServiceModuleStatsNumdnspacketsignored ConfdString,
        affirmedServicesDnsProxyServiceModuleStatsNumdnsinternalerrors ConfdString,
        affirmedServicesDnsProxyServiceModuleStatsNumdnspacketsallowed ConfdString,
        affirmedServicesDnsProxyServiceModuleStatsNumdnspacketsdropped ConfdString,
        affirmedServicesDnsProxyServiceModuleStatsNumdnspacketsredirected ConfdString,
        affirmedServicesDnsProxyServiceModuleStatsNumdnspacketsexamed ConfdString,
        affirmedServicesDnsProxyServiceModuleStatsNumdnspacketsblocked ConfdString,
        affirmedServicesDnsProxyServiceModuleStatsNumdomainblockedcurrent ConfdString
    }

affirmedServicesDnsProxyServiceModuleStatsNode OBJECT-TYPE
    SYNTAX      Unsigned32
    MAX-ACCESS  not-accessible
    STATUS      current
    DESCRIPTION "Node Id from which to gather module stats"
    ::= { affirmedServicesDnsProxyServiceModuleStatsEntry 1 }

affirmedServicesDnsProxyServiceModuleStatsNumdnspacketsprocessed OBJECT-TYPE
    SYNTAX      ConfdString
    MAX-ACCESS  read-only
    STATUS      current
    DESCRIPTION "Total number of DNS packets that have been processed"
    ::= { affirmedServicesDnsProxyServiceModuleStatsEntry 2 }

affirmedServicesDnsProxyServiceModuleStatsNumdnsupstreampacketsprocessed OBJECT-TYPE
    SYNTAX      ConfdString
    MAX-ACCESS  read-only
    STATUS      current
    DESCRIPTION "Total number of upstream DNS packets that have been processed"
    ::= { affirmedServicesDnsProxyServiceModuleStatsEntry 3 }

affirmedServicesDnsProxyServiceModuleStatsNumdnsdownstreampacketsprocessed OBJECT-TYPE
    SYNTAX      ConfdString
    MAX-ACCESS  read-only
    STATUS      current
    DESCRIPTION "Total number of downstream DNS packets that have been processed"
    ::= { affirmedServicesDnsProxyServiceModuleStatsEntry 4 }

affirmedServicesDnsProxyServiceModuleStatsNumdnspacketsignored OBJECT-TYPE
    SYNTAX      ConfdString
    MAX-ACCESS  read-only
    STATUS      current
    DESCRIPTION "Total number of DNS packets that have been ignored"
    ::= { affirmedServicesDnsProxyServiceModuleStatsEntry 5 }

affirmedServicesDnsProxyServiceModuleStatsNumdnsinternalerrors OBJECT-TYPE
    SYNTAX      ConfdString
    MAX-ACCESS  read-only
    STATUS      current
    DESCRIPTION "Total number of DNS internal errors"
    ::= { affirmedServicesDnsProxyServiceModuleStatsEntry 6 }

affirmedServicesDnsProxyServiceModuleStatsNumdnspacketsallowed OBJECT-TYPE
    SYNTAX      ConfdString
    MAX-ACCESS  read-only
    STATUS      current
    DESCRIPTION "Total number of DNS requests that have been allowed"
    ::= { affirmedServicesDnsProxyServiceModuleStatsEntry 7 }

affirmedServicesDnsProxyServiceModuleStatsNumdnspacketsdropped OBJECT-TYPE
    SYNTAX      ConfdString
    MAX-ACCESS  read-only
    STATUS      current
    DESCRIPTION "Total number of DNS requests that have been blocked"
    ::= { affirmedServicesDnsProxyServiceModuleStatsEntry 8 }

affirmedServicesDnsProxyServiceModuleStatsNumdnspacketsredirected OBJECT-TYPE
    SYNTAX      ConfdString
    MAX-ACCESS  read-only
    STATUS      current
    DESCRIPTION "Total number of DNS requests that have been redirected"
    ::= { affirmedServicesDnsProxyServiceModuleStatsEntry 9 }

affirmedServicesDnsProxyServiceModuleStatsNumdnspacketsexamed OBJECT-TYPE
    SYNTAX      ConfdString
    MAX-ACCESS  read-only
    STATUS      current
    DESCRIPTION "Total number of DNS requests that have been examined by tunnel detection"
    ::= { affirmedServicesDnsProxyServiceModuleStatsEntry 10 }

affirmedServicesDnsProxyServiceModuleStatsNumdnspacketsblocked OBJECT-TYPE
    SYNTAX      ConfdString
    MAX-ACCESS  read-only
    STATUS      current
    DESCRIPTION "Total number of DNS requests that have been blocked by tunnel detection"
    ::= { affirmedServicesDnsProxyServiceModuleStatsEntry 11 }

affirmedServicesDnsProxyServiceModuleStatsNumdomainblockedcurrent OBJECT-TYPE
    SYNTAX      ConfdString
    MAX-ACCESS  read-only
    STATUS      current
    DESCRIPTION "Current number of domains blocked by tunnel detection"
    ::= { affirmedServicesDnsProxyServiceModuleStatsEntry 12 }

affirmedServicesDnsProxyServiceCacheStatsTable OBJECT-TYPE
    SYNTAX      SEQUENCE OF AffirmedServicesDnsProxyServiceCacheStatsEntry
    MAX-ACCESS  not-accessible
    STATUS      current
    DESCRIPTION ""
    ::= { affirmedServicesDnsProxyService 2 }

affirmedServicesDnsProxyServiceCacheStatsEntry OBJECT-TYPE
    SYNTAX      AffirmedServicesDnsProxyServiceCacheStatsEntry
    MAX-ACCESS  not-accessible
    STATUS      current
    DESCRIPTION ""
    INDEX { affirmedServicesDnsProxyServiceCacheStatsNode, affirmedServicesDnsProxyServiceCacheStatsNetworkContext }
        ::= { affirmedServicesDnsProxyServiceCacheStatsTable 1 }

AffirmedServicesDnsProxyServiceCacheStatsEntry ::=
    SEQUENCE {
        affirmedServicesDnsProxyServiceCacheStatsNode Unsigned32,
        affirmedServicesDnsProxyServiceCacheStatsNetworkContext String,
        affirmedServicesDnsProxyServiceCacheStatsNetworkContextId Unsigned32,
        affirmedServicesDnsProxyServiceCacheStatsNumcacheentriesadded ConfdString,
        affirmedServicesDnsProxyServiceCacheStatsNumcacheentriesdeleted ConfdString,
        affirmedServicesDnsProxyServiceCacheStatsNumcachehits ConfdString,
        affirmedServicesDnsProxyServiceCacheStatsNumcachemisses ConfdString
    }

affirmedServicesDnsProxyServiceCacheStatsNode OBJECT-TYPE
    SYNTAX      Unsigned32
    MAX-ACCESS  not-accessible
    STATUS      current
    DESCRIPTION "Node Id from which to gather module stats"
    ::= { affirmedServicesDnsProxyServiceCacheStatsEntry 1 }

affirmedServicesDnsProxyServiceCacheStatsNetworkContext OBJECT-TYPE
    SYNTAX      String
    MAX-ACCESS  not-accessible
    STATUS      current
    DESCRIPTION "Network Context name associated with this DNS cache"
    ::= { affirmedServicesDnsProxyServiceCacheStatsEntry 2 }

affirmedServicesDnsProxyServiceCacheStatsNetworkContextId OBJECT-TYPE
    SYNTAX      Unsigned32
    MAX-ACCESS  read-only
    STATUS      current
    DESCRIPTION ""
    ::= { affirmedServicesDnsProxyServiceCacheStatsEntry 3 }

affirmedServicesDnsProxyServiceCacheStatsNumcacheentriesadded OBJECT-TYPE
    SYNTAX      ConfdString
    MAX-ACCESS  read-only
    STATUS      current
    DESCRIPTION "Total number of DNS results added to the cache"
    ::= { affirmedServicesDnsProxyServiceCacheStatsEntry 4 }

affirmedServicesDnsProxyServiceCacheStatsNumcacheentriesdeleted OBJECT-TYPE
    SYNTAX      ConfdString
    MAX-ACCESS  read-only
    STATUS      current
    DESCRIPTION "Total number of DNS results deleted from the cache"
    ::= { affirmedServicesDnsProxyServiceCacheStatsEntry 5 }

affirmedServicesDnsProxyServiceCacheStatsNumcachehits OBJECT-TYPE
    SYNTAX      ConfdString
    MAX-ACCESS  read-only
    STATUS      current
    DESCRIPTION "Total number of DNS cache hits"
    ::= { affirmedServicesDnsProxyServiceCacheStatsEntry 6 }

affirmedServicesDnsProxyServiceCacheStatsNumcachemisses OBJECT-TYPE
    SYNTAX      ConfdString
    MAX-ACCESS  read-only
    STATUS      current
    DESCRIPTION "Total number of DNS cache misses"
    ::= { affirmedServicesDnsProxyServiceCacheStatsEntry 7 }

affirmedServicesDnsProxyServiceCacheStatusTable OBJECT-TYPE
    SYNTAX      SEQUENCE OF AffirmedServicesDnsProxyServiceCacheStatusEntry
    MAX-ACCESS  not-accessible
    STATUS      current
    DESCRIPTION ""
    ::= { affirmedServicesDnsProxyService 3 }

affirmedServicesDnsProxyServiceCacheStatusEntry OBJECT-TYPE
    SYNTAX      AffirmedServicesDnsProxyServiceCacheStatusEntry
    MAX-ACCESS  not-accessible
    STATUS      current
    DESCRIPTION ""
    INDEX { affirmedServicesDnsProxyServiceCacheStatusNode, affirmedServicesDnsProxyServiceCacheStatusNetworkContext }
        ::= { affirmedServicesDnsProxyServiceCacheStatusTable 1 }

AffirmedServicesDnsProxyServiceCacheStatusEntry ::=
    SEQUENCE {
        affirmedServicesDnsProxyServiceCacheStatusNode Unsigned32,
        affirmedServicesDnsProxyServiceCacheStatusNetworkContext String,
        affirmedServicesDnsProxyServiceCacheStatusNetworkContextId Unsigned32,
        affirmedServicesDnsProxyServiceCacheStatusNumCacheEntries Unsigned32
    }

affirmedServicesDnsProxyServiceCacheStatusNode OBJECT-TYPE
    SYNTAX      Unsigned32
    MAX-ACCESS  not-accessible
    STATUS      current
    DESCRIPTION "Node Id from which to display cache data"
    ::= { affirmedServicesDnsProxyServiceCacheStatusEntry 1 }

affirmedServicesDnsProxyServiceCacheStatusNetworkContext OBJECT-TYPE
    SYNTAX      String
    MAX-ACCESS  not-accessible
    STATUS      current
    DESCRIPTION "Network Context name associated with this DNS cache"
    ::= { affirmedServicesDnsProxyServiceCacheStatusEntry 2 }

affirmedServicesDnsProxyServiceCacheStatusNetworkContextId OBJECT-TYPE
    SYNTAX      Unsigned32
    MAX-ACCESS  read-only
    STATUS      current
    DESCRIPTION ""
    ::= { affirmedServicesDnsProxyServiceCacheStatusEntry 3 }

affirmedServicesDnsProxyServiceCacheStatusNumCacheEntries OBJECT-TYPE
    SYNTAX      Unsigned32
    MAX-ACCESS  read-only
    STATUS      current
    DESCRIPTION "Current number of entries in this DNS cache"
    ::= { affirmedServicesDnsProxyServiceCacheStatusEntry 4 }

affirmedServicesDnsProxyServiceCacheEntriesTable OBJECT-TYPE
    SYNTAX      SEQUENCE OF AffirmedServicesDnsProxyServiceCacheEntriesEntry
    MAX-ACCESS  not-accessible
    STATUS      current
    DESCRIPTION ""
    ::= { affirmedServicesDnsProxyService 4 }

affirmedServicesDnsProxyServiceCacheEntriesEntry OBJECT-TYPE
    SYNTAX      AffirmedServicesDnsProxyServiceCacheEntriesEntry
    MAX-ACCESS  not-accessible
    STATUS      current
    DESCRIPTION ""
    INDEX { affirmedServicesDnsProxyServiceCacheEntriesNode, affirmedServicesDnsProxyServiceCacheEntriesNetworkContext, affirmedServicesDnsProxyServiceCacheEntriesHostName, affirmedServicesDnsProxyServiceCacheEntriesIpAddr }
        ::= { affirmedServicesDnsProxyServiceCacheEntriesTable 1 }

AffirmedServicesDnsProxyServiceCacheEntriesEntry ::=
    SEQUENCE {
        affirmedServicesDnsProxyServiceCacheEntriesNode Unsigned32,
        affirmedServicesDnsProxyServiceCacheEntriesNetworkContext String,
        affirmedServicesDnsProxyServiceCacheEntriesHostName String,
        affirmedServicesDnsProxyServiceCacheEntriesIpAddr String,
        affirmedServicesDnsProxyServiceCacheEntriesNetworkContextId Unsigned32,
        affirmedServicesDnsProxyServiceCacheEntriesCacheEntryType INTEGER,
        affirmedServicesDnsProxyServiceCacheEntriesCacheEntryTtl Unsigned32,
        affirmedServicesDnsProxyServiceCacheEntriesCacheEntryLastAccessed Unsigned32,
        affirmedServicesDnsProxyServiceCacheEntriesCacheEntryExpires Unsigned32
    }

affirmedServicesDnsProxyServiceCacheEntriesNode OBJECT-TYPE
    SYNTAX      Unsigned32
    MAX-ACCESS  not-accessible
    STATUS      current
    DESCRIPTION "Node Id from which to display cache entry data"
    ::= { affirmedServicesDnsProxyServiceCacheEntriesEntry 1 }

affirmedServicesDnsProxyServiceCacheEntriesNetworkContext OBJECT-TYPE
    SYNTAX      String
    MAX-ACCESS  not-accessible
    STATUS      current
    DESCRIPTION "Network Context name associated with this DNS cache"
    ::= { affirmedServicesDnsProxyServiceCacheEntriesEntry 2 }

affirmedServicesDnsProxyServiceCacheEntriesHostName OBJECT-TYPE
    SYNTAX      String
    MAX-ACCESS  not-accessible
    STATUS      current
    DESCRIPTION "Host name of the DNS cache entry"
    ::= { affirmedServicesDnsProxyServiceCacheEntriesEntry 3 }

affirmedServicesDnsProxyServiceCacheEntriesIpAddr OBJECT-TYPE
    SYNTAX      String
    MAX-ACCESS  not-accessible
    STATUS      current
    DESCRIPTION "Ip address"
    ::= { affirmedServicesDnsProxyServiceCacheEntriesEntry 4 }

affirmedServicesDnsProxyServiceCacheEntriesNetworkContextId OBJECT-TYPE
    SYNTAX      Unsigned32
    MAX-ACCESS  read-only
    STATUS      current
    DESCRIPTION ""
    ::= { affirmedServicesDnsProxyServiceCacheEntriesEntry 5 }

affirmedServicesDnsProxyServiceCacheEntriesCacheEntryType OBJECT-TYPE
    SYNTAX      INTEGER {none(0),static(1),pending(2),negative(3),positive(4)}
    MAX-ACCESS  read-only
    STATUS      current
    DESCRIPTION "Cache entry type"
    ::= { affirmedServicesDnsProxyServiceCacheEntriesEntry 6 }

affirmedServicesDnsProxyServiceCacheEntriesCacheEntryTtl OBJECT-TYPE
    SYNTAX      Unsigned32
    MAX-ACCESS  read-only
    STATUS      current
    DESCRIPTION "Entry time to live"
    ::= { affirmedServicesDnsProxyServiceCacheEntriesEntry 7 }

affirmedServicesDnsProxyServiceCacheEntriesCacheEntryLastAccessed OBJECT-TYPE
    SYNTAX      Unsigned32
    MAX-ACCESS  read-only
    STATUS      current
    DESCRIPTION "Number of seconds since this cache entry was accessed"
    ::= { affirmedServicesDnsProxyServiceCacheEntriesEntry 8 }

affirmedServicesDnsProxyServiceCacheEntriesCacheEntryExpires OBJECT-TYPE
    SYNTAX      Unsigned32
    MAX-ACCESS  read-only
    STATUS      current
    DESCRIPTION "Number of seconds until this entry is purged from the cache"
    ::= { affirmedServicesDnsProxyServiceCacheEntriesEntry 9 }

affirmedServicesDnsProxyServiceDnsReverseCacheBackgroundResolutionSummaryTable OBJECT-TYPE
    SYNTAX      SEQUENCE OF AffirmedServicesDnsProxyServiceDnsReverseCacheBackgroundResolutionSummaryEntry
    MAX-ACCESS  not-accessible
    STATUS      current
    DESCRIPTION ""
    ::= { affirmedServicesDnsProxyServiceDnsReverseCacheBackgroundResolution 1 }

affirmedServicesDnsProxyServiceDnsReverseCacheBackgroundResolutionSummaryEntry OBJECT-TYPE
    SYNTAX      AffirmedServicesDnsProxyServiceDnsReverseCacheBackgroundResolutionSummaryEntry
    MAX-ACCESS  not-accessible
    STATUS      current
    DESCRIPTION ""
    INDEX { affirmedServicesDnsProxyServiceDnsReverseCacheBackgroundResolutionSummaryHostname, affirmedServicesDnsProxyServiceDnsReverseCacheBackgroundResolutionSummaryNetworkContext }
        ::= { affirmedServicesDnsProxyServiceDnsReverseCacheBackgroundResolutionSummaryTable 1 }

AffirmedServicesDnsProxyServiceDnsReverseCacheBackgroundResolutionSummaryEntry ::=
    SEQUENCE {
        affirmedServicesDnsProxyServiceDnsReverseCacheBackgroundResolutionSummaryHostname String,
        affirmedServicesDnsProxyServiceDnsReverseCacheBackgroundResolutionSummaryNetworkContext String,
        affirmedServicesDnsProxyServiceDnsReverseCacheBackgroundResolutionSummaryCurrentStatus String,
        affirmedServicesDnsProxyServiceDnsReverseCacheBackgroundResolutionSummaryResults String,
        affirmedServicesDnsProxyServiceDnsReverseCacheBackgroundResolutionSummaryTTL Unsigned32
    }

affirmedServicesDnsProxyServiceDnsReverseCacheBackgroundResolutionSummaryHostname OBJECT-TYPE
    SYNTAX      String
    MAX-ACCESS  not-accessible
    STATUS      current
    DESCRIPTION "Hostname"
    ::= { affirmedServicesDnsProxyServiceDnsReverseCacheBackgroundResolutionSummaryEntry 1 }

affirmedServicesDnsProxyServiceDnsReverseCacheBackgroundResolutionSummaryNetworkContext OBJECT-TYPE
    SYNTAX      String
    MAX-ACCESS  not-accessible
    STATUS      current
    DESCRIPTION "Network Context"
    ::= { affirmedServicesDnsProxyServiceDnsReverseCacheBackgroundResolutionSummaryEntry 2 }

affirmedServicesDnsProxyServiceDnsReverseCacheBackgroundResolutionSummaryCurrentStatus OBJECT-TYPE
    SYNTAX      String
    MAX-ACCESS  read-only
    STATUS      current
    DESCRIPTION "Status"
    ::= { affirmedServicesDnsProxyServiceDnsReverseCacheBackgroundResolutionSummaryEntry 3 }

affirmedServicesDnsProxyServiceDnsReverseCacheBackgroundResolutionSummaryResults OBJECT-TYPE
    SYNTAX      String
    MAX-ACCESS  read-only
    STATUS      current
    DESCRIPTION "Results"
    ::= { affirmedServicesDnsProxyServiceDnsReverseCacheBackgroundResolutionSummaryEntry 4 }

affirmedServicesDnsProxyServiceDnsReverseCacheBackgroundResolutionSummaryTTL OBJECT-TYPE
    SYNTAX      Unsigned32
    MAX-ACCESS  read-only
    STATUS      current
    DESCRIPTION "TTL"
    ::= { affirmedServicesDnsProxyServiceDnsReverseCacheBackgroundResolutionSummaryEntry 5 }

affirmedServicesDnsProxyServiceDnsReverseCacheBackgroundResolutionSummaryNewTable OBJECT-TYPE
    SYNTAX      SEQUENCE OF AffirmedServicesDnsProxyServiceDnsReverseCacheBackgroundResolutionSummaryNewEntry
    MAX-ACCESS  not-accessible
    STATUS      current
    DESCRIPTION ""
    ::= { affirmedServicesDnsProxyServiceDnsReverseCacheBackgroundResolution 2 }

affirmedServicesDnsProxyServiceDnsReverseCacheBackgroundResolutionSummaryNewEntry OBJECT-TYPE
    SYNTAX      AffirmedServicesDnsProxyServiceDnsReverseCacheBackgroundResolutionSummaryNewEntry
    MAX-ACCESS  not-accessible
    STATUS      current
    DESCRIPTION ""
    INDEX { affirmedServicesDnsProxyServiceDnsReverseCacheBackgroundResolutionSummaryNewNetworkContext, affirmedServicesDnsProxyServiceDnsReverseCacheBackgroundResolutionSummaryNewHostname }
        ::= { affirmedServicesDnsProxyServiceDnsReverseCacheBackgroundResolutionSummaryNewTable 1 }

AffirmedServicesDnsProxyServiceDnsReverseCacheBackgroundResolutionSummaryNewEntry ::=
    SEQUENCE {
        affirmedServicesDnsProxyServiceDnsReverseCacheBackgroundResolutionSummaryNewNetworkContext String,
        affirmedServicesDnsProxyServiceDnsReverseCacheBackgroundResolutionSummaryNewHostname String,
        affirmedServicesDnsProxyServiceDnsReverseCacheBackgroundResolutionSummaryNewCurrentStatus String,
        affirmedServicesDnsProxyServiceDnsReverseCacheBackgroundResolutionSummaryNewResults String,
        affirmedServicesDnsProxyServiceDnsReverseCacheBackgroundResolutionSummaryNewTTL Unsigned32
    }

affirmedServicesDnsProxyServiceDnsReverseCacheBackgroundResolutionSummaryNewNetworkContext OBJECT-TYPE
    SYNTAX      String
    MAX-ACCESS  not-accessible
    STATUS      current
    DESCRIPTION "Network Context"
    ::= { affirmedServicesDnsProxyServiceDnsReverseCacheBackgroundResolutionSummaryNewEntry 1 }

affirmedServicesDnsProxyServiceDnsReverseCacheBackgroundResolutionSummaryNewHostname OBJECT-TYPE
    SYNTAX      String
    MAX-ACCESS  not-accessible
    STATUS      current
    DESCRIPTION "Hostname"
    ::= { affirmedServicesDnsProxyServiceDnsReverseCacheBackgroundResolutionSummaryNewEntry 2 }

affirmedServicesDnsProxyServiceDnsReverseCacheBackgroundResolutionSummaryNewCurrentStatus OBJECT-TYPE
    SYNTAX      String
    MAX-ACCESS  read-only
    STATUS      current
    DESCRIPTION "Status"
    ::= { affirmedServicesDnsProxyServiceDnsReverseCacheBackgroundResolutionSummaryNewEntry 3 }

affirmedServicesDnsProxyServiceDnsReverseCacheBackgroundResolutionSummaryNewResults OBJECT-TYPE
    SYNTAX      String
    MAX-ACCESS  read-only
    STATUS      current
    DESCRIPTION "Results"
    ::= { affirmedServicesDnsProxyServiceDnsReverseCacheBackgroundResolutionSummaryNewEntry 4 }

affirmedServicesDnsProxyServiceDnsReverseCacheBackgroundResolutionSummaryNewTTL OBJECT-TYPE
    SYNTAX      Unsigned32
    MAX-ACCESS  read-only
    STATUS      current
    DESCRIPTION "TTL"
    ::= { affirmedServicesDnsProxyServiceDnsReverseCacheBackgroundResolutionSummaryNewEntry 5 }

affirmedServicesDnsProxyServiceStatisticsClusterLevelBackgroundResolutionStatisticsTable OBJECT-TYPE
    SYNTAX      SEQUENCE OF AffirmedServicesDnsProxyServiceStatisticsClusterLevelBackgroundResolutionStatisticsEntry
    MAX-ACCESS  not-accessible
    STATUS      current
    DESCRIPTION ""
    ::= { affirmedServicesDnsProxyServiceStatisticsClusterLevel 1 }

affirmedServicesDnsProxyServiceStatisticsClusterLevelBackgroundResolutionStatisticsEntry OBJECT-TYPE
    SYNTAX      AffirmedServicesDnsProxyServiceStatisticsClusterLevelBackgroundResolutionStatisticsEntry
    MAX-ACCESS  not-accessible
    STATUS      current
    DESCRIPTION ""
    INDEX { affirmedServicesDnsProxyServiceStatisticsClusterLevelBackgroundResolutionStatisticsChassis }
        ::= { affirmedServicesDnsProxyServiceStatisticsClusterLevelBackgroundResolutionStatisticsTable 1 }

AffirmedServicesDnsProxyServiceStatisticsClusterLevelBackgroundResolutionStatisticsEntry ::=
    SEQUENCE {
        affirmedServicesDnsProxyServiceStatisticsClusterLevelBackgroundResolutionStatisticsChassis Unsigned32,
        affirmedServicesDnsProxyServiceStatisticsClusterLevelBackgroundResolutionStatisticsNumrequestattempt ConfdString,
        affirmedServicesDnsProxyServiceStatisticsClusterLevelBackgroundResolutionStatisticsNumrequestsent ConfdString,
        affirmedServicesDnsProxyServiceStatisticsClusterLevelBackgroundResolutionStatisticsNumrequestfailed ConfdString,
        affirmedServicesDnsProxyServiceStatisticsClusterLevelBackgroundResolutionStatisticsNumresponsesuccess ConfdString,
        affirmedServicesDnsProxyServiceStatisticsClusterLevelBackgroundResolutionStatisticsNumresponsefailed ConfdString
    }

affirmedServicesDnsProxyServiceStatisticsClusterLevelBackgroundResolutionStatisticsChassis OBJECT-TYPE
    SYNTAX      Unsigned32
    MAX-ACCESS  not-accessible
    STATUS      current
    DESCRIPTION "Cluster ID"
    ::= { affirmedServicesDnsProxyServiceStatisticsClusterLevelBackgroundResolutionStatisticsEntry 1 }

affirmedServicesDnsProxyServiceStatisticsClusterLevelBackgroundResolutionStatisticsNumrequestattempt OBJECT-TYPE
    SYNTAX      ConfdString
    MAX-ACCESS  read-only
    STATUS      current
    DESCRIPTION "Total number of DNS requests attempted"
    ::= { affirmedServicesDnsProxyServiceStatisticsClusterLevelBackgroundResolutionStatisticsEntry 2 }

affirmedServicesDnsProxyServiceStatisticsClusterLevelBackgroundResolutionStatisticsNumrequestsent OBJECT-TYPE
    SYNTAX      ConfdString
    MAX-ACCESS  read-only
    STATUS      current
    DESCRIPTION "Total number of DNS requests sent"
    ::= { affirmedServicesDnsProxyServiceStatisticsClusterLevelBackgroundResolutionStatisticsEntry 3 }

affirmedServicesDnsProxyServiceStatisticsClusterLevelBackgroundResolutionStatisticsNumrequestfailed OBJECT-TYPE
    SYNTAX      ConfdString
    MAX-ACCESS  read-only
    STATUS      current
    DESCRIPTION "Total number of DNS requests failed to get sent"
    ::= { affirmedServicesDnsProxyServiceStatisticsClusterLevelBackgroundResolutionStatisticsEntry 4 }

affirmedServicesDnsProxyServiceStatisticsClusterLevelBackgroundResolutionStatisticsNumresponsesuccess OBJECT-TYPE
    SYNTAX      ConfdString
    MAX-ACCESS  read-only
    STATUS      current
    DESCRIPTION "Total number of DNS successful responses"
    ::= { affirmedServicesDnsProxyServiceStatisticsClusterLevelBackgroundResolutionStatisticsEntry 5 }

affirmedServicesDnsProxyServiceStatisticsClusterLevelBackgroundResolutionStatisticsNumresponsefailed OBJECT-TYPE
    SYNTAX      ConfdString
    MAX-ACCESS  read-only
    STATUS      current
    DESCRIPTION "Total number of DNS failed responses"
    ::= { affirmedServicesDnsProxyServiceStatisticsClusterLevelBackgroundResolutionStatisticsEntry 6 }

affirmedServicesDnsProxyServiceStatisticsClusterLevelBackgroundResolutionCountsTable OBJECT-TYPE
    SYNTAX      SEQUENCE OF AffirmedServicesDnsProxyServiceStatisticsClusterLevelBackgroundResolutionCountsEntry
    MAX-ACCESS  not-accessible
    STATUS      current
    DESCRIPTION ""
    ::= { affirmedServicesDnsProxyServiceStatisticsClusterLevel 2 }

affirmedServicesDnsProxyServiceStatisticsClusterLevelBackgroundResolutionCountsEntry OBJECT-TYPE
    SYNTAX      AffirmedServicesDnsProxyServiceStatisticsClusterLevelBackgroundResolutionCountsEntry
    MAX-ACCESS  not-accessible
    STATUS      current
    DESCRIPTION ""
    INDEX { affirmedServicesDnsProxyServiceStatisticsClusterLevelBackgroundResolutionCountsChassis }
        ::= { affirmedServicesDnsProxyServiceStatisticsClusterLevelBackgroundResolutionCountsTable 1 }

AffirmedServicesDnsProxyServiceStatisticsClusterLevelBackgroundResolutionCountsEntry ::=
    SEQUENCE {
        affirmedServicesDnsProxyServiceStatisticsClusterLevelBackgroundResolutionCountsChassis Unsigned32,
        affirmedServicesDnsProxyServiceStatisticsClusterLevelBackgroundResolutionCountsNumhostnameconfigured ConfdString,
        affirmedServicesDnsProxyServiceStatisticsClusterLevelBackgroundResolutionCountsNumhostnameresolved ConfdString,
        affirmedServicesDnsProxyServiceStatisticsClusterLevelBackgroundResolutionCountsNumhostnamenotresolved ConfdString
    }

affirmedServicesDnsProxyServiceStatisticsClusterLevelBackgroundResolutionCountsChassis OBJECT-TYPE
    SYNTAX      Unsigned32
    MAX-ACCESS  not-accessible
    STATUS      current
    DESCRIPTION "Clucster ID"
    ::= { affirmedServicesDnsProxyServiceStatisticsClusterLevelBackgroundResolutionCountsEntry 1 }

affirmedServicesDnsProxyServiceStatisticsClusterLevelBackgroundResolutionCountsNumhostnameconfigured OBJECT-TYPE
    SYNTAX      ConfdString
    MAX-ACCESS  read-only
    STATUS      current
    DESCRIPTION "Number of hostnames configured"
    ::= { affirmedServicesDnsProxyServiceStatisticsClusterLevelBackgroundResolutionCountsEntry 2 }

affirmedServicesDnsProxyServiceStatisticsClusterLevelBackgroundResolutionCountsNumhostnameresolved OBJECT-TYPE
    SYNTAX      ConfdString
    MAX-ACCESS  read-only
    STATUS      current
    DESCRIPTION "Number of hostnames resolved"
    ::= { affirmedServicesDnsProxyServiceStatisticsClusterLevelBackgroundResolutionCountsEntry 3 }

affirmedServicesDnsProxyServiceStatisticsClusterLevelBackgroundResolutionCountsNumhostnamenotresolved OBJECT-TYPE
    SYNTAX      ConfdString
    MAX-ACCESS  read-only
    STATUS      current
    DESCRIPTION "Number of hostnames failed to resolve"
    ::= { affirmedServicesDnsProxyServiceStatisticsClusterLevelBackgroundResolutionCountsEntry 4 }

affirmedServicesNatServiceServiceDataFlowTable OBJECT-TYPE
    SYNTAX      SEQUENCE OF AffirmedServicesNatServiceServiceDataFlowEntry
    MAX-ACCESS  not-accessible
    STATUS      current
    DESCRIPTION ""
    ::= { affirmedServicesNatService 1 }

affirmedServicesNatServiceServiceDataFlowEntry OBJECT-TYPE
    SYNTAX      AffirmedServicesNatServiceServiceDataFlowEntry
    MAX-ACCESS  not-accessible
    STATUS      current
    DESCRIPTION ""
    INDEX { affirmedServicesNatServiceServiceDataFlowNatPolicy, affirmedServicesNatServiceServiceDataFlowNatFlowPriority, affirmedServicesNatServiceServiceDataFlowServiceRulePriority, affirmedServicesNatServiceServiceDataFlowNatFlow, affirmedServicesNatServiceServiceDataFlowServiceRule }
        ::= { affirmedServicesNatServiceServiceDataFlowTable 1 }

AffirmedServicesNatServiceServiceDataFlowEntry ::=
    SEQUENCE {
        affirmedServicesNatServiceServiceDataFlowNatPolicy String,
        affirmedServicesNatServiceServiceDataFlowNatFlowPriority Unsigned32,
        affirmedServicesNatServiceServiceDataFlowServiceRulePriority Unsigned32,
        affirmedServicesNatServiceServiceDataFlowNatFlow String,
        affirmedServicesNatServiceServiceDataFlowServiceRule String,
        affirmedServicesNatServiceServiceDataFlowNatFlowId Unsigned32,
        affirmedServicesNatServiceServiceDataFlowServiceRuleId Unsigned32
    }

affirmedServicesNatServiceServiceDataFlowNatPolicy OBJECT-TYPE
    SYNTAX      String
    MAX-ACCESS  not-accessible
    STATUS      current
    DESCRIPTION "the name of the subscriber-firewall-policy"
    ::= { affirmedServicesNatServiceServiceDataFlowEntry 1 }

affirmedServicesNatServiceServiceDataFlowNatFlowPriority OBJECT-TYPE
    SYNTAX      Unsigned32
    MAX-ACCESS  not-accessible
    STATUS      current
    DESCRIPTION "the priority of the subscriber-firewall"
    ::= { affirmedServicesNatServiceServiceDataFlowEntry 2 }

affirmedServicesNatServiceServiceDataFlowServiceRulePriority OBJECT-TYPE
    SYNTAX      Unsigned32
    MAX-ACCESS  not-accessible
    STATUS      current
    DESCRIPTION "the priority of the service-rule"
    ::= { affirmedServicesNatServiceServiceDataFlowEntry 3 }

affirmedServicesNatServiceServiceDataFlowNatFlow OBJECT-TYPE
    SYNTAX      String
    MAX-ACCESS  not-accessible
    STATUS      current
    DESCRIPTION "the name of the subscriber-firewall"
    ::= { affirmedServicesNatServiceServiceDataFlowEntry 4 }

affirmedServicesNatServiceServiceDataFlowServiceRule OBJECT-TYPE
    SYNTAX      String
    MAX-ACCESS  not-accessible
    STATUS      current
    DESCRIPTION "the name of the service-rule"
    ::= { affirmedServicesNatServiceServiceDataFlowEntry 5 }

affirmedServicesNatServiceServiceDataFlowNatFlowId OBJECT-TYPE
    SYNTAX      Unsigned32
    MAX-ACCESS  read-only
    STATUS      current
    DESCRIPTION "the internal ID of the subscriber-firewall, used to identify PDN-session service-data-flows {session-id, service-type=subscriber-firewall, subscriber-firewall-flow-id, service-rule-id}"
    ::= { affirmedServicesNatServiceServiceDataFlowEntry 6 }

affirmedServicesNatServiceServiceDataFlowServiceRuleId OBJECT-TYPE
    SYNTAX      Unsigned32
    MAX-ACCESS  read-only
    STATUS      current
    DESCRIPTION "the internal ID of the service-rule, used to identify PDN-session service-data-flows {session-id, service-type=subscriber-firewall, subscriber-firewall-flow-id, service-rule-id}"
    ::= { affirmedServicesNatServiceServiceDataFlowEntry 7 }

affirmedServicesNatServiceAlgPktStatsTable OBJECT-TYPE
    SYNTAX      SEQUENCE OF AffirmedServicesNatServiceAlgPktStatsEntry
    MAX-ACCESS  not-accessible
    STATUS      current
    DESCRIPTION ""
    ::= { affirmedServicesNatService 2 }

affirmedServicesNatServiceAlgPktStatsEntry OBJECT-TYPE
    SYNTAX      AffirmedServicesNatServiceAlgPktStatsEntry
    MAX-ACCESS  not-accessible
    STATUS      current
    DESCRIPTION ""
    INDEX { affirmedServicesNatServiceAlgPktStatsType }
        ::= { affirmedServicesNatServiceAlgPktStatsTable 1 }

AffirmedServicesNatServiceAlgPktStatsEntry ::=
    SEQUENCE {
        affirmedServicesNatServiceAlgPktStatsType String,
        affirmedServicesNatServiceAlgPktStatsNumNatAlgULPkts ConfdString,
        affirmedServicesNatServiceAlgPktStatsNumNatAlgDLPkts ConfdString,
        affirmedServicesNatServiceAlgPktStatsNumPassAlgULPkts ConfdString,
        affirmedServicesNatServiceAlgPktStatsNumPassAlgDLPkts ConfdString
    }

affirmedServicesNatServiceAlgPktStatsType OBJECT-TYPE
    SYNTAX      String
    MAX-ACCESS  not-accessible
    STATUS      current
    DESCRIPTION "the name of ALG"
    ::= { affirmedServicesNatServiceAlgPktStatsEntry 1 }

affirmedServicesNatServiceAlgPktStatsNumNatAlgULPkts OBJECT-TYPE
    SYNTAX      ConfdString
    MAX-ACCESS  read-only
    STATUS      current
    DESCRIPTION "Number of Upstream NAT Packets Classified as ALG"
    ::= { affirmedServicesNatServiceAlgPktStatsEntry 2 }

affirmedServicesNatServiceAlgPktStatsNumNatAlgDLPkts OBJECT-TYPE
    SYNTAX      ConfdString
    MAX-ACCESS  read-only
    STATUS      current
    DESCRIPTION "Number of Downstream NAT Packets Classified as ALG"
    ::= { affirmedServicesNatServiceAlgPktStatsEntry 3 }

affirmedServicesNatServiceAlgPktStatsNumPassAlgULPkts OBJECT-TYPE
    SYNTAX      ConfdString
    MAX-ACCESS  read-only
    STATUS      current
    DESCRIPTION "Number of Upstream Packets Classified as ALG"
    ::= { affirmedServicesNatServiceAlgPktStatsEntry 4 }

affirmedServicesNatServiceAlgPktStatsNumPassAlgDLPkts OBJECT-TYPE
    SYNTAX      ConfdString
    MAX-ACCESS  read-only
    STATUS      current
    DESCRIPTION "Number of Downstream Packets Classified as ALG"
    ::= { affirmedServicesNatServiceAlgPktStatsEntry 5 }

affirmedServicesNatServiceNatClusterLevelModuleStatsTable OBJECT-TYPE
    SYNTAX      SEQUENCE OF AffirmedServicesNatServiceNatClusterLevelModuleStatsEntry
    MAX-ACCESS  not-accessible
    STATUS      current
    DESCRIPTION ""
    ::= { affirmedServicesNatServiceNatClusterLevel 1 }

affirmedServicesNatServiceNatClusterLevelModuleStatsEntry OBJECT-TYPE
    SYNTAX      AffirmedServicesNatServiceNatClusterLevelModuleStatsEntry
    MAX-ACCESS  not-accessible
    STATUS      current
    DESCRIPTION ""
    INDEX { affirmedServicesNatServiceNatClusterLevelModuleStatsChassis }
        ::= { affirmedServicesNatServiceNatClusterLevelModuleStatsTable 1 }

AffirmedServicesNatServiceNatClusterLevelModuleStatsEntry ::=
    SEQUENCE {
        affirmedServicesNatServiceNatClusterLevelModuleStatsChassis Unsigned32,
        affirmedServicesNatServiceNatClusterLevelModuleStatsSessionCreateFailure ConfdString,
        affirmedServicesNatServiceNatClusterLevelModuleStatsSessionCreateSuccess ConfdString,
        affirmedServicesNatServiceNatClusterLevelModuleStatsSessionDelete ConfdString,
        affirmedServicesNatServiceNatClusterLevelModuleStatsSessionIpAllocationSuccess ConfdString,
        affirmedServicesNatServiceNatClusterLevelModuleStatsSessionIpAllocationFailure ConfdString,
        affirmedServicesNatServiceNatClusterLevelModuleStatsSessionIpDeallocation ConfdString,
        affirmedServicesNatServiceNatClusterLevelModuleStatsSessionPortChunkAllocationSuccess ConfdString,
        affirmedServicesNatServiceNatClusterLevelModuleStatsSessionPortChunkAllocationFailure ConfdString,
        affirmedServicesNatServiceNatClusterLevelModuleStatsSessionPortChunkDeallocation ConfdString,
        affirmedServicesNatServiceNatClusterLevelModuleStatsAllocFailureNatPoolOutOfService ConfdString,
        affirmedServicesNatServiceNatClusterLevelModuleStatsAllocFailureOutOfNatResources ConfdString,
        affirmedServicesNatServiceNatClusterLevelModuleStatsAllocFailureActivationTimerOn ConfdString,
        affirmedServicesNatServiceNatClusterLevelModuleStatsAllocFailureSubPoolNotFound ConfdString,
        affirmedServicesNatServiceNatClusterLevelModuleStatsAllocFailureSubpoolOutOfService ConfdString,
        affirmedServicesNatServiceNatClusterLevelModuleStatsConnectionsCreated ConfdString,
        affirmedServicesNatServiceNatClusterLevelModuleStatsConnectionsDeleted ConfdString,
        affirmedServicesNatServiceNatClusterLevelModuleStatsConnectionCreateFailure ConfdString,
        affirmedServicesNatServiceNatClusterLevelModuleStatsConnectionCreateActionDrop ConfdString,
        affirmedServicesNatServiceNatClusterLevelModuleStatsConnectionCreateActionPass ConfdString,
        affirmedServicesNatServiceNatClusterLevelModuleStatsConnectionCreateIgnored ConfdString,
        affirmedServicesNatServiceNatClusterLevelModuleStatsConnectionCreateDropNetworkInitiated ConfdString,
        affirmedServicesNatServiceNatClusterLevelModuleStatsConnectionCreateFailureIpv6PrefixMismatch ConfdString,
        affirmedServicesNatServiceNatClusterLevelModuleStatsConnectionCreateFailureGeoRedMismatch ConfdString,
        affirmedServicesNatServiceNatClusterLevelModuleStatsConnectionCreateFailureNoAssociatedNatPool ConfdString,
        affirmedServicesNatServiceNatClusterLevelModuleStatsConnectionCreateFailureServiceFlowNotEnabled ConfdString,
        affirmedServicesNatServiceNatClusterLevelModuleStatsConnectionCreateFailureNatPoolNotEnabled ConfdString,
        affirmedServicesNatServiceNatClusterLevelModuleStatsConnectionCreateFailureNatAlgNotEnabled ConfdString,
        affirmedServicesNatServiceNatClusterLevelModuleStatsConnectionCreateFailureSessionNotActive ConfdString,
        affirmedServicesNatServiceNatClusterLevelModuleStatsConnectionCreateFailureNatMappingUnavailable ConfdString,
        affirmedServicesNatServiceNatClusterLevelModuleStatsConnectionCreateIgnoredNetworkInitiated ConfdString,
        affirmedServicesNatServiceNatClusterLevelModuleStatsConnectionCreateIgnoredUnsupportedIcmpType ConfdString,
        affirmedServicesNatServiceNatClusterLevelModuleStatsConnectionCreateIgnoredUnsupportedProtocol ConfdString,
        affirmedServicesNatServiceNatClusterLevelModuleStatsConnectionDeleteNatPoolConnectionPurge ConfdString,
        affirmedServicesNatServiceNatClusterLevelModuleStatsConnectionCreateTcp ConfdString,
        affirmedServicesNatServiceNatClusterLevelModuleStatsConnectionCreateUdp ConfdString,
        affirmedServicesNatServiceNatClusterLevelModuleStatsConnectionCreateIcmp ConfdString,
        affirmedServicesNatServiceNatClusterLevelModuleStatsConnectionDeleteTcp ConfdString,
        affirmedServicesNatServiceNatClusterLevelModuleStatsConnectionDeleteUdp ConfdString,
        affirmedServicesNatServiceNatClusterLevelModuleStatsConnectionDeleteIcmp ConfdString,
        affirmedServicesNatServiceNatClusterLevelModuleStatsNatFlowCreateFailure ConfdString,
        affirmedServicesNatServiceNatClusterLevelModuleStatsNatFlowCreateSuccess ConfdString,
        affirmedServicesNatServiceNatClusterLevelModuleStatsNatFlowDeleteSuccess ConfdString,
        affirmedServicesNatServiceNatClusterLevelModuleStatsNatFlowFoundConnectionCreated ConfdString,
        affirmedServicesNatServiceNatClusterLevelModuleStatsFilterAdfPacketAccepted ConfdString,
        affirmedServicesNatServiceNatClusterLevelModuleStatsFilterAdfPacketRejected ConfdString,
        affirmedServicesNatServiceNatClusterLevelModuleStatsFilterApdfPacketAccepted ConfdString,
        affirmedServicesNatServiceNatClusterLevelModuleStatsFilterApdfPacketRejected ConfdString,
        affirmedServicesNatServiceNatClusterLevelModuleStatsFilterEifPacketAccepted ConfdString,
        affirmedServicesNatServiceNatClusterLevelModuleStatsPacketTranslated ConfdString,
        affirmedServicesNatServiceNatClusterLevelModuleStatsPacketDropped ConfdString,
        affirmedServicesNatServiceNatClusterLevelModuleStatsPktDropUnknownProtocolFailure ConfdString,
        affirmedServicesNatServiceNatClusterLevelModuleStatsPktDropIcmpUnknownType ConfdString,
        affirmedServicesNatServiceNatClusterLevelModuleStatsPktDropReverseLookupFailure ConfdString,
        affirmedServicesNatServiceNatClusterLevelModuleStatsPktDropReverseSessionIdMismatch ConfdString,
        affirmedServicesNatServiceNatClusterLevelModuleStatsPktDropReverseUnknownProtocolFailure ConfdString,
        affirmedServicesNatServiceNatClusterLevelModuleStatsPktDropReversev4tov6ConversionFailure ConfdString,
        affirmedServicesNatServiceNatClusterLevelModuleStatsNatAlgUplinkPackets ConfdString,
        affirmedServicesNatServiceNatClusterLevelModuleStatsNatAlgDownlinkPackets ConfdString,
        affirmedServicesNatServiceNatClusterLevelModuleStatsPassAlgUplinkPackets ConfdString,
        affirmedServicesNatServiceNatClusterLevelModuleStatsPassAlgDownlinkPackets ConfdString,
        affirmedServicesNatServiceNatClusterLevelModuleStatsSipAlgUplinkPackets ConfdString,
        affirmedServicesNatServiceNatClusterLevelModuleStatsSipAlgDownlinkPackets ConfdString,
        affirmedServicesNatServiceNatClusterLevelModuleStatsSipPassAlgUplinkPackets ConfdString,
        affirmedServicesNatServiceNatClusterLevelModuleStatsSipPassAlgDownlinkPackets ConfdString,
        affirmedServicesNatServiceNatClusterLevelModuleStatsRtspAlgUplinkPackets ConfdString,
        affirmedServicesNatServiceNatClusterLevelModuleStatsRtspAlgDownlinkPackets ConfdString,
        affirmedServicesNatServiceNatClusterLevelModuleStatsRtspPassAlgUplinkPackets ConfdString,
        affirmedServicesNatServiceNatClusterLevelModuleStatsRtspPassAlgDownlinkPackets ConfdString,
        affirmedServicesNatServiceNatClusterLevelModuleStatsFtpAlgDownlinkPackets ConfdString,
        affirmedServicesNatServiceNatClusterLevelModuleStatsFtpAlgUplinkPackets ConfdString,
        affirmedServicesNatServiceNatClusterLevelModuleStatsFtpPassAlgDownlinkPackets ConfdString,
        affirmedServicesNatServiceNatClusterLevelModuleStatsFtpPassAlgUplinkPackets ConfdString,
        affirmedServicesNatServiceNatClusterLevelModuleStatsTftpAlgUplinkPackets ConfdString,
        affirmedServicesNatServiceNatClusterLevelModuleStatsTftpAlgDownlinkPackets ConfdString,
        affirmedServicesNatServiceNatClusterLevelModuleStatsTftpPassAlgUplinkPackets ConfdString,
        affirmedServicesNatServiceNatClusterLevelModuleStatsTftpPassAlgDownlinkPackets ConfdString,
        affirmedServicesNatServiceNatClusterLevelModuleStatsConnectionCreateIgnoredNonTcpSyn ConfdString,
        affirmedServicesNatServiceNatClusterLevelModuleStatsConnectionCreateEsp ConfdString,
        affirmedServicesNatServiceNatClusterLevelModuleStatsConnectionDeleteEsp ConfdString,
        affirmedServicesNatServiceNatClusterLevelModuleStatsAllocFailureNPTv6 ConfdString,
        affirmedServicesNatServiceNatClusterLevelModuleStatsIpsecNattAssistAlgUplinkPackets ConfdString,
        affirmedServicesNatServiceNatClusterLevelModuleStatsIpsecNattAssistAlgDownlinkPackets ConfdString,
        affirmedServicesNatServiceNatClusterLevelModuleStatsIpsecNattAssistPassAlgUplinkPackets ConfdString,
        affirmedServicesNatServiceNatClusterLevelModuleStatsIpsecNattAssistPassAlgDownlinkPackets ConfdString,
        affirmedServicesNatServiceNatClusterLevelModuleStatsConnectionCreateFailureConnTracker ConfdString,
        affirmedServicesNatServiceNatClusterLevelModuleStatsNumRejectFlowStateTrackingMisconfig ConfdString,
        affirmedServicesNatServiceNatClusterLevelModuleStatsPptpAlgDownlinkPackets ConfdString,
        affirmedServicesNatServiceNatClusterLevelModuleStatsPptpAlgUplinkPackets ConfdString,
        affirmedServicesNatServiceNatClusterLevelModuleStatsPptpPassAlgDownlinkPackets ConfdString,
        affirmedServicesNatServiceNatClusterLevelModuleStatsPptpPassAlgUplinkPackets ConfdString,
        affirmedServicesNatServiceNatClusterLevelModuleStatsPktDropConnTracker ConfdString
    }

affirmedServicesNatServiceNatClusterLevelModuleStatsChassis OBJECT-TYPE
    SYNTAX      Unsigned32
    MAX-ACCESS  not-accessible
    STATUS      current
    DESCRIPTION "Chassis id"
    ::= { affirmedServicesNatServiceNatClusterLevelModuleStatsEntry 1 }

affirmedServicesNatServiceNatClusterLevelModuleStatsSessionCreateFailure OBJECT-TYPE
    SYNTAX      ConfdString
    MAX-ACCESS  read-only
    STATUS      current
    DESCRIPTION "Number of sessions for which NAT resource(IP or port chunks) allocation failed"
    ::= { affirmedServicesNatServiceNatClusterLevelModuleStatsEntry 2 }

affirmedServicesNatServiceNatClusterLevelModuleStatsSessionCreateSuccess OBJECT-TYPE
    SYNTAX      ConfdString
    MAX-ACCESS  read-only
    STATUS      current
    DESCRIPTION "Number of sessions successfully allocated NAT resources"
    ::= { affirmedServicesNatServiceNatClusterLevelModuleStatsEntry 3 }

affirmedServicesNatServiceNatClusterLevelModuleStatsSessionDelete OBJECT-TYPE
    SYNTAX      ConfdString
    MAX-ACCESS  read-only
    STATUS      current
    DESCRIPTION "Number of session delete requests processed"
    ::= { affirmedServicesNatServiceNatClusterLevelModuleStatsEntry 4 }

affirmedServicesNatServiceNatClusterLevelModuleStatsSessionIpAllocationSuccess OBJECT-TYPE
    SYNTAX      ConfdString
    MAX-ACCESS  read-only
    STATUS      current
    DESCRIPTION "Number of NAT IP allocated successfully"
    ::= { affirmedServicesNatServiceNatClusterLevelModuleStatsEntry 5 }

affirmedServicesNatServiceNatClusterLevelModuleStatsSessionIpAllocationFailure OBJECT-TYPE
    SYNTAX      ConfdString
    MAX-ACCESS  read-only
    STATUS      current
    DESCRIPTION "Number of NAT IP allocation failure"
    ::= { affirmedServicesNatServiceNatClusterLevelModuleStatsEntry 6 }

affirmedServicesNatServiceNatClusterLevelModuleStatsSessionIpDeallocation OBJECT-TYPE
    SYNTAX      ConfdString
    MAX-ACCESS  read-only
    STATUS      current
    DESCRIPTION "Number of NAT IP deallocation"
    ::= { affirmedServicesNatServiceNatClusterLevelModuleStatsEntry 7 }

affirmedServicesNatServiceNatClusterLevelModuleStatsSessionPortChunkAllocationSuccess OBJECT-TYPE
    SYNTAX      ConfdString
    MAX-ACCESS  read-only
    STATUS      current
    DESCRIPTION "Number of Port chunks successfully allocated"
    ::= { affirmedServicesNatServiceNatClusterLevelModuleStatsEntry 8 }

affirmedServicesNatServiceNatClusterLevelModuleStatsSessionPortChunkAllocationFailure OBJECT-TYPE
    SYNTAX      ConfdString
    MAX-ACCESS  read-only
    STATUS      current
    DESCRIPTION "Number of Port chunk allocation failure"
    ::= { affirmedServicesNatServiceNatClusterLevelModuleStatsEntry 9 }

affirmedServicesNatServiceNatClusterLevelModuleStatsSessionPortChunkDeallocation OBJECT-TYPE
    SYNTAX      ConfdString
    MAX-ACCESS  read-only
    STATUS      current
    DESCRIPTION "Number of Port chunks deallocated"
    ::= { affirmedServicesNatServiceNatClusterLevelModuleStatsEntry 10 }

affirmedServicesNatServiceNatClusterLevelModuleStatsAllocFailureNatPoolOutOfService OBJECT-TYPE
    SYNTAX      ConfdString
    MAX-ACCESS  read-only
    STATUS      current
    DESCRIPTION "Number of allocation failure due to nat-pool being admin disabled"
    ::= { affirmedServicesNatServiceNatClusterLevelModuleStatsEntry 11 }

affirmedServicesNatServiceNatClusterLevelModuleStatsAllocFailureOutOfNatResources OBJECT-TYPE
    SYNTAX      ConfdString
    MAX-ACCESS  read-only
    STATUS      current
    DESCRIPTION "Number of allocation failure due to lack of IP address or Port chunks"
    ::= { affirmedServicesNatServiceNatClusterLevelModuleStatsEntry 12 }

affirmedServicesNatServiceNatClusterLevelModuleStatsAllocFailureActivationTimerOn OBJECT-TYPE
    SYNTAX      ConfdString
    MAX-ACCESS  read-only
    STATUS      current
    DESCRIPTION "Number of allocation failure due to activation timer running"
    ::= { affirmedServicesNatServiceNatClusterLevelModuleStatsEntry 13 }

affirmedServicesNatServiceNatClusterLevelModuleStatsAllocFailureSubPoolNotFound OBJECT-TYPE
    SYNTAX      ConfdString
    MAX-ACCESS  read-only
    STATUS      current
    DESCRIPTION "Number of allocation failure due to sub pool not being configured"
    ::= { affirmedServicesNatServiceNatClusterLevelModuleStatsEntry 14 }

affirmedServicesNatServiceNatClusterLevelModuleStatsAllocFailureSubpoolOutOfService OBJECT-TYPE
    SYNTAX      ConfdString
    MAX-ACCESS  read-only
    STATUS      current
    DESCRIPTION "Number of allocation failure due to sub pool being admin disabled"
    ::= { affirmedServicesNatServiceNatClusterLevelModuleStatsEntry 15 }

affirmedServicesNatServiceNatClusterLevelModuleStatsConnectionsCreated OBJECT-TYPE
    SYNTAX      ConfdString
    MAX-ACCESS  read-only
    STATUS      current
    DESCRIPTION "Number of nat connections created"
    ::= { affirmedServicesNatServiceNatClusterLevelModuleStatsEntry 16 }

affirmedServicesNatServiceNatClusterLevelModuleStatsConnectionsDeleted OBJECT-TYPE
    SYNTAX      ConfdString
    MAX-ACCESS  read-only
    STATUS      current
    DESCRIPTION "Number of nat connections deleted"
    ::= { affirmedServicesNatServiceNatClusterLevelModuleStatsEntry 17 }

affirmedServicesNatServiceNatClusterLevelModuleStatsConnectionCreateFailure OBJECT-TYPE
    SYNTAX      ConfdString
    MAX-ACCESS  read-only
    STATUS      current
    DESCRIPTION "Number of nat connection creation failures"
    ::= { affirmedServicesNatServiceNatClusterLevelModuleStatsEntry 18 }

affirmedServicesNatServiceNatClusterLevelModuleStatsConnectionCreateActionDrop OBJECT-TYPE
    SYNTAX      ConfdString
    MAX-ACCESS  read-only
    STATUS      current
    DESCRIPTION "Number of nat connections not created due to service flow action drop"
    ::= { affirmedServicesNatServiceNatClusterLevelModuleStatsEntry 19 }

affirmedServicesNatServiceNatClusterLevelModuleStatsConnectionCreateActionPass OBJECT-TYPE
    SYNTAX      ConfdString
    MAX-ACCESS  read-only
    STATUS      current
    DESCRIPTION "Number of nat connections not created due to  service flow action pass"
    ::= { affirmedServicesNatServiceNatClusterLevelModuleStatsEntry 20 }

affirmedServicesNatServiceNatClusterLevelModuleStatsConnectionCreateIgnored OBJECT-TYPE
    SYNTAX      ConfdString
    MAX-ACCESS  read-only
    STATUS      current
    DESCRIPTION "Number of nat connections create ignored due to http-proxy non transparent mode enabled"
    ::= { affirmedServicesNatServiceNatClusterLevelModuleStatsEntry 21 }

affirmedServicesNatServiceNatClusterLevelModuleStatsConnectionCreateDropNetworkInitiated OBJECT-TYPE
    SYNTAX      ConfdString
    MAX-ACCESS  read-only
    STATUS      current
    DESCRIPTION "Number of connection creations dropped as it was Network initiated and destination is ue-ip"
    ::= { affirmedServicesNatServiceNatClusterLevelModuleStatsEntry 22 }

affirmedServicesNatServiceNatClusterLevelModuleStatsConnectionCreateFailureIpv6PrefixMismatch OBJECT-TYPE
    SYNTAX      ConfdString
    MAX-ACCESS  read-only
    STATUS      current
    DESCRIPTION "Number of nat connections creation failure due to mismatch between configured NAT64 Ipv6 prefix and Network Address of the connection"
    ::= { affirmedServicesNatServiceNatClusterLevelModuleStatsEntry 23 }

affirmedServicesNatServiceNatClusterLevelModuleStatsConnectionCreateFailureGeoRedMismatch OBJECT-TYPE
    SYNTAX      ConfdString
    MAX-ACCESS  read-only
    STATUS      current
    DESCRIPTION "Number of nat connections creation failure due to mismatch between Geo-group id of the nat-pool and the session"
    ::= { affirmedServicesNatServiceNatClusterLevelModuleStatsEntry 24 }

affirmedServicesNatServiceNatClusterLevelModuleStatsConnectionCreateFailureNoAssociatedNatPool OBJECT-TYPE
    SYNTAX      ConfdString
    MAX-ACCESS  read-only
    STATUS      current
    DESCRIPTION "Number of nat connections creation failure due to subscriber-firewall-flow for nat not configured with nat-pool"
    ::= { affirmedServicesNatServiceNatClusterLevelModuleStatsEntry 25 }

affirmedServicesNatServiceNatClusterLevelModuleStatsConnectionCreateFailureServiceFlowNotEnabled OBJECT-TYPE
    SYNTAX      ConfdString
    MAX-ACCESS  read-only
    STATUS      current
    DESCRIPTION "Number of nat connection creation failure due to subscriber-firewall-flow being admin disabled"
    ::= { affirmedServicesNatServiceNatClusterLevelModuleStatsEntry 26 }

affirmedServicesNatServiceNatClusterLevelModuleStatsConnectionCreateFailureNatPoolNotEnabled OBJECT-TYPE
    SYNTAX      ConfdString
    MAX-ACCESS  read-only
    STATUS      current
    DESCRIPTION "Number of nat connections creation failure due to nat-pool being admin disabled."
    ::= { affirmedServicesNatServiceNatClusterLevelModuleStatsEntry 27 }

affirmedServicesNatServiceNatClusterLevelModuleStatsConnectionCreateFailureNatAlgNotEnabled OBJECT-TYPE
    SYNTAX      ConfdString
    MAX-ACCESS  read-only
    STATUS      current
    DESCRIPTION "Number of nat connections creation failure due to NAT ALG  being disabled"
    ::= { affirmedServicesNatServiceNatClusterLevelModuleStatsEntry 28 }

affirmedServicesNatServiceNatClusterLevelModuleStatsConnectionCreateFailureSessionNotActive OBJECT-TYPE
    SYNTAX      ConfdString
    MAX-ACCESS  read-only
    STATUS      current
    DESCRIPTION "Number of connections create failure due to inactive session. This could be a transient condition during failover allowing the UE to quickly retry."
    ::= { affirmedServicesNatServiceNatClusterLevelModuleStatsEntry 29 }

affirmedServicesNatServiceNatClusterLevelModuleStatsConnectionCreateFailureNatMappingUnavailable OBJECT-TYPE
    SYNTAX      ConfdString
    MAX-ACCESS  read-only
    STATUS      current
    DESCRIPTION "Number of nat connection creation failure due to unavailability of Nat port"
    ::= { affirmedServicesNatServiceNatClusterLevelModuleStatsEntry 30 }

affirmedServicesNatServiceNatClusterLevelModuleStatsConnectionCreateIgnoredNetworkInitiated OBJECT-TYPE
    SYNTAX      ConfdString
    MAX-ACCESS  read-only
    STATUS      current
    DESCRIPTION "Number of connection creation ignored as it was Network initiated and destination is ue-ip, port 67(dhcp)"
    ::= { affirmedServicesNatServiceNatClusterLevelModuleStatsEntry 31 }

affirmedServicesNatServiceNatClusterLevelModuleStatsConnectionCreateIgnoredUnsupportedIcmpType OBJECT-TYPE
    SYNTAX      ConfdString
    MAX-ACCESS  read-only
    STATUS      current
    DESCRIPTION "Number of connection create ignored due to unsupported ICMP type"
    ::= { affirmedServicesNatServiceNatClusterLevelModuleStatsEntry 32 }

affirmedServicesNatServiceNatClusterLevelModuleStatsConnectionCreateIgnoredUnsupportedProtocol OBJECT-TYPE
    SYNTAX      ConfdString
    MAX-ACCESS  read-only
    STATUS      current
    DESCRIPTION "Number of connection create ignored due to unsupported protocol"
    ::= { affirmedServicesNatServiceNatClusterLevelModuleStatsEntry 33 }

affirmedServicesNatServiceNatClusterLevelModuleStatsConnectionDeleteNatPoolConnectionPurge OBJECT-TYPE
    SYNTAX      ConfdString
    MAX-ACCESS  read-only
    STATUS      current
    DESCRIPTION "Number of nat connections deleted due to nat-pool/sub-pool being admin disabled"
    ::= { affirmedServicesNatServiceNatClusterLevelModuleStatsEntry 34 }

affirmedServicesNatServiceNatClusterLevelModuleStatsConnectionCreateTcp OBJECT-TYPE
    SYNTAX      ConfdString
    MAX-ACCESS  read-only
    STATUS      current
    DESCRIPTION "Number of tcp connections created"
    ::= { affirmedServicesNatServiceNatClusterLevelModuleStatsEntry 35 }

affirmedServicesNatServiceNatClusterLevelModuleStatsConnectionCreateUdp OBJECT-TYPE
    SYNTAX      ConfdString
    MAX-ACCESS  read-only
    STATUS      current
    DESCRIPTION "Number of udp connections created"
    ::= { affirmedServicesNatServiceNatClusterLevelModuleStatsEntry 36 }

affirmedServicesNatServiceNatClusterLevelModuleStatsConnectionCreateIcmp OBJECT-TYPE
    SYNTAX      ConfdString
    MAX-ACCESS  read-only
    STATUS      current
    DESCRIPTION "Number of icmp connections created"
    ::= { affirmedServicesNatServiceNatClusterLevelModuleStatsEntry 37 }

affirmedServicesNatServiceNatClusterLevelModuleStatsConnectionDeleteTcp OBJECT-TYPE
    SYNTAX      ConfdString
    MAX-ACCESS  read-only
    STATUS      current
    DESCRIPTION "Number of tcp connections deleted"
    ::= { affirmedServicesNatServiceNatClusterLevelModuleStatsEntry 38 }

affirmedServicesNatServiceNatClusterLevelModuleStatsConnectionDeleteUdp OBJECT-TYPE
    SYNTAX      ConfdString
    MAX-ACCESS  read-only
    STATUS      current
    DESCRIPTION "Number of udp connections deleted"
    ::= { affirmedServicesNatServiceNatClusterLevelModuleStatsEntry 39 }

affirmedServicesNatServiceNatClusterLevelModuleStatsConnectionDeleteIcmp OBJECT-TYPE
    SYNTAX      ConfdString
    MAX-ACCESS  read-only
    STATUS      current
    DESCRIPTION "Number of icmp connections deleted"
    ::= { affirmedServicesNatServiceNatClusterLevelModuleStatsEntry 40 }

affirmedServicesNatServiceNatClusterLevelModuleStatsNatFlowCreateFailure OBJECT-TYPE
    SYNTAX      ConfdString
    MAX-ACCESS  read-only
    STATUS      current
    DESCRIPTION "Nat flow create failure count"
    ::= { affirmedServicesNatServiceNatClusterLevelModuleStatsEntry 41 }

affirmedServicesNatServiceNatClusterLevelModuleStatsNatFlowCreateSuccess OBJECT-TYPE
    SYNTAX      ConfdString
    MAX-ACCESS  read-only
    STATUS      current
    DESCRIPTION "Nat flow create success count"
    ::= { affirmedServicesNatServiceNatClusterLevelModuleStatsEntry 42 }

affirmedServicesNatServiceNatClusterLevelModuleStatsNatFlowDeleteSuccess OBJECT-TYPE
    SYNTAX      ConfdString
    MAX-ACCESS  read-only
    STATUS      current
    DESCRIPTION "Nat flow delete success count"
    ::= { affirmedServicesNatServiceNatClusterLevelModuleStatsEntry 43 }

affirmedServicesNatServiceNatClusterLevelModuleStatsNatFlowFoundConnectionCreated OBJECT-TYPE
    SYNTAX      ConfdString
    MAX-ACCESS  read-only
    STATUS      current
    DESCRIPTION "Nat flow found connection create count"
    ::= { affirmedServicesNatServiceNatClusterLevelModuleStatsEntry 44 }

affirmedServicesNatServiceNatClusterLevelModuleStatsFilterAdfPacketAccepted OBJECT-TYPE
    SYNTAX      ConfdString
    MAX-ACCESS  read-only
    STATUS      current
    DESCRIPTION "Nat adf filter packet accepted count"
    ::= { affirmedServicesNatServiceNatClusterLevelModuleStatsEntry 45 }

affirmedServicesNatServiceNatClusterLevelModuleStatsFilterAdfPacketRejected OBJECT-TYPE
    SYNTAX      ConfdString
    MAX-ACCESS  read-only
    STATUS      current
    DESCRIPTION "Nat adf filter packet rejected count"
    ::= { affirmedServicesNatServiceNatClusterLevelModuleStatsEntry 46 }

affirmedServicesNatServiceNatClusterLevelModuleStatsFilterApdfPacketAccepted OBJECT-TYPE
    SYNTAX      ConfdString
    MAX-ACCESS  read-only
    STATUS      current
    DESCRIPTION "Nat apdf filter packet accepted count"
    ::= { affirmedServicesNatServiceNatClusterLevelModuleStatsEntry 47 }

affirmedServicesNatServiceNatClusterLevelModuleStatsFilterApdfPacketRejected OBJECT-TYPE
    SYNTAX      ConfdString
    MAX-ACCESS  read-only
    STATUS      current
    DESCRIPTION "Nat apdf filter packet rejected count"
    ::= { affirmedServicesNatServiceNatClusterLevelModuleStatsEntry 48 }

affirmedServicesNatServiceNatClusterLevelModuleStatsFilterEifPacketAccepted OBJECT-TYPE
    SYNTAX      ConfdString
    MAX-ACCESS  read-only
    STATUS      current
    DESCRIPTION "Nat eif filter packet accepted count"
    ::= { affirmedServicesNatServiceNatClusterLevelModuleStatsEntry 49 }

affirmedServicesNatServiceNatClusterLevelModuleStatsPacketTranslated OBJECT-TYPE
    SYNTAX      ConfdString
    MAX-ACCESS  read-only
    STATUS      current
    DESCRIPTION "Number of Packets successfully translated"
    ::= { affirmedServicesNatServiceNatClusterLevelModuleStatsEntry 50 }

affirmedServicesNatServiceNatClusterLevelModuleStatsPacketDropped OBJECT-TYPE
    SYNTAX      ConfdString
    MAX-ACCESS  read-only
    STATUS      current
    DESCRIPTION "Number of Packets dropped during translation"
    ::= { affirmedServicesNatServiceNatClusterLevelModuleStatsEntry 51 }

affirmedServicesNatServiceNatClusterLevelModuleStatsPktDropUnknownProtocolFailure OBJECT-TYPE
    SYNTAX      ConfdString
    MAX-ACCESS  read-only
    STATUS      current
    DESCRIPTION "Number of packets dropped due to unknown protocol in the IP header"
    ::= { affirmedServicesNatServiceNatClusterLevelModuleStatsEntry 52 }

affirmedServicesNatServiceNatClusterLevelModuleStatsPktDropIcmpUnknownType OBJECT-TYPE
    SYNTAX      ConfdString
    MAX-ACCESS  read-only
    STATUS      current
    DESCRIPTION "Number of packets dropped due to unknown ICMP type"
    ::= { affirmedServicesNatServiceNatClusterLevelModuleStatsEntry 53 }

affirmedServicesNatServiceNatClusterLevelModuleStatsPktDropReverseLookupFailure OBJECT-TYPE
    SYNTAX      ConfdString
    MAX-ACCESS  read-only
    STATUS      current
    DESCRIPTION "Number of downlink packets dropped due to reverse lookup failure"
    ::= { affirmedServicesNatServiceNatClusterLevelModuleStatsEntry 54 }

affirmedServicesNatServiceNatClusterLevelModuleStatsPktDropReverseSessionIdMismatch OBJECT-TYPE
    SYNTAX      ConfdString
    MAX-ACCESS  read-only
    STATUS      current
    DESCRIPTION "Number of downlink packets dropped due to session id mismatch for nat flow"
    ::= { affirmedServicesNatServiceNatClusterLevelModuleStatsEntry 55 }

affirmedServicesNatServiceNatClusterLevelModuleStatsPktDropReverseUnknownProtocolFailure OBJECT-TYPE
    SYNTAX      ConfdString
    MAX-ACCESS  read-only
    STATUS      current
    DESCRIPTION "Number of downlink packets dropped due to  unknown protocol"
    ::= { affirmedServicesNatServiceNatClusterLevelModuleStatsEntry 56 }

affirmedServicesNatServiceNatClusterLevelModuleStatsPktDropReversev4tov6ConversionFailure OBJECT-TYPE
    SYNTAX      ConfdString
    MAX-ACCESS  read-only
    STATUS      current
    DESCRIPTION "Number of downlink packets dropped due to v4 to v6 conversion failure for NAT64"
    ::= { affirmedServicesNatServiceNatClusterLevelModuleStatsEntry 57 }

affirmedServicesNatServiceNatClusterLevelModuleStatsNatAlgUplinkPackets OBJECT-TYPE
    SYNTAX      ConfdString
    MAX-ACCESS  read-only
    STATUS      current
    DESCRIPTION "Alg none(nat only) uplink packets count"
    ::= { affirmedServicesNatServiceNatClusterLevelModuleStatsEntry 58 }

affirmedServicesNatServiceNatClusterLevelModuleStatsNatAlgDownlinkPackets OBJECT-TYPE
    SYNTAX      ConfdString
    MAX-ACCESS  read-only
    STATUS      current
    DESCRIPTION "Alg none(nat only) downlink packets count"
    ::= { affirmedServicesNatServiceNatClusterLevelModuleStatsEntry 59 }

affirmedServicesNatServiceNatClusterLevelModuleStatsPassAlgUplinkPackets OBJECT-TYPE
    SYNTAX      ConfdString
    MAX-ACCESS  read-only
    STATUS      current
    DESCRIPTION "Alg none(nat only) pass uplink packets count"
    ::= { affirmedServicesNatServiceNatClusterLevelModuleStatsEntry 60 }

affirmedServicesNatServiceNatClusterLevelModuleStatsPassAlgDownlinkPackets OBJECT-TYPE
    SYNTAX      ConfdString
    MAX-ACCESS  read-only
    STATUS      current
    DESCRIPTION "Alg none(nat only) pass downlink packets count"
    ::= { affirmedServicesNatServiceNatClusterLevelModuleStatsEntry 61 }

affirmedServicesNatServiceNatClusterLevelModuleStatsSipAlgUplinkPackets OBJECT-TYPE
    SYNTAX      ConfdString
    MAX-ACCESS  read-only
    STATUS      current
    DESCRIPTION "Alg sip uplink packets count"
    ::= { affirmedServicesNatServiceNatClusterLevelModuleStatsEntry 62 }

affirmedServicesNatServiceNatClusterLevelModuleStatsSipAlgDownlinkPackets OBJECT-TYPE
    SYNTAX      ConfdString
    MAX-ACCESS  read-only
    STATUS      current
    DESCRIPTION "Alg sip downlink packets count"
    ::= { affirmedServicesNatServiceNatClusterLevelModuleStatsEntry 63 }

affirmedServicesNatServiceNatClusterLevelModuleStatsSipPassAlgUplinkPackets OBJECT-TYPE
    SYNTAX      ConfdString
    MAX-ACCESS  read-only
    STATUS      current
    DESCRIPTION "Alg sip pass uplink packets count"
    ::= { affirmedServicesNatServiceNatClusterLevelModuleStatsEntry 64 }

affirmedServicesNatServiceNatClusterLevelModuleStatsSipPassAlgDownlinkPackets OBJECT-TYPE
    SYNTAX      ConfdString
    MAX-ACCESS  read-only
    STATUS      current
    DESCRIPTION "Alg sip pass downlink packets count"
    ::= { affirmedServicesNatServiceNatClusterLevelModuleStatsEntry 65 }

affirmedServicesNatServiceNatClusterLevelModuleStatsRtspAlgUplinkPackets OBJECT-TYPE
    SYNTAX      ConfdString
    MAX-ACCESS  read-only
    STATUS      current
    DESCRIPTION "Alg rtsp uplink packets count"
    ::= { affirmedServicesNatServiceNatClusterLevelModuleStatsEntry 66 }

affirmedServicesNatServiceNatClusterLevelModuleStatsRtspAlgDownlinkPackets OBJECT-TYPE
    SYNTAX      ConfdString
    MAX-ACCESS  read-only
    STATUS      current
    DESCRIPTION "Alg rtsp downlink packets count"
    ::= { affirmedServicesNatServiceNatClusterLevelModuleStatsEntry 67 }

affirmedServicesNatServiceNatClusterLevelModuleStatsRtspPassAlgUplinkPackets OBJECT-TYPE
    SYNTAX      ConfdString
    MAX-ACCESS  read-only
    STATUS      current
    DESCRIPTION "Alg rtsp pass uplink packets count"
    ::= { affirmedServicesNatServiceNatClusterLevelModuleStatsEntry 68 }

affirmedServicesNatServiceNatClusterLevelModuleStatsRtspPassAlgDownlinkPackets OBJECT-TYPE
    SYNTAX      ConfdString
    MAX-ACCESS  read-only
    STATUS      current
    DESCRIPTION "Alg rtsp pass downlink packets count"
    ::= { affirmedServicesNatServiceNatClusterLevelModuleStatsEntry 69 }

affirmedServicesNatServiceNatClusterLevelModuleStatsFtpAlgDownlinkPackets OBJECT-TYPE
    SYNTAX      ConfdString
    MAX-ACCESS  read-only
    STATUS      current
    DESCRIPTION "Alg ftp downlink packets count"
    ::= { affirmedServicesNatServiceNatClusterLevelModuleStatsEntry 70 }

affirmedServicesNatServiceNatClusterLevelModuleStatsFtpAlgUplinkPackets OBJECT-TYPE
    SYNTAX      ConfdString
    MAX-ACCESS  read-only
    STATUS      current
    DESCRIPTION "Alg ftp uplink packets count"
    ::= { affirmedServicesNatServiceNatClusterLevelModuleStatsEntry 71 }

affirmedServicesNatServiceNatClusterLevelModuleStatsFtpPassAlgDownlinkPackets OBJECT-TYPE
    SYNTAX      ConfdString
    MAX-ACCESS  read-only
    STATUS      current
    DESCRIPTION "Alg ftp pass downlink packets count"
    ::= { affirmedServicesNatServiceNatClusterLevelModuleStatsEntry 72 }

affirmedServicesNatServiceNatClusterLevelModuleStatsFtpPassAlgUplinkPackets OBJECT-TYPE
    SYNTAX      ConfdString
    MAX-ACCESS  read-only
    STATUS      current
    DESCRIPTION "Alg ftp pass uplink packets count"
    ::= { affirmedServicesNatServiceNatClusterLevelModuleStatsEntry 73 }

affirmedServicesNatServiceNatClusterLevelModuleStatsTftpAlgUplinkPackets OBJECT-TYPE
    SYNTAX      ConfdString
    MAX-ACCESS  read-only
    STATUS      current
    DESCRIPTION "Alg tftp uplink packets count"
    ::= { affirmedServicesNatServiceNatClusterLevelModuleStatsEntry 74 }

affirmedServicesNatServiceNatClusterLevelModuleStatsTftpAlgDownlinkPackets OBJECT-TYPE
    SYNTAX      ConfdString
    MAX-ACCESS  read-only
    STATUS      current
    DESCRIPTION "Alg tftp downlink packets count"
    ::= { affirmedServicesNatServiceNatClusterLevelModuleStatsEntry 75 }

affirmedServicesNatServiceNatClusterLevelModuleStatsTftpPassAlgUplinkPackets OBJECT-TYPE
    SYNTAX      ConfdString
    MAX-ACCESS  read-only
    STATUS      current
    DESCRIPTION "Alg tftp pass uplink packets count"
    ::= { affirmedServicesNatServiceNatClusterLevelModuleStatsEntry 76 }

affirmedServicesNatServiceNatClusterLevelModuleStatsTftpPassAlgDownlinkPackets OBJECT-TYPE
    SYNTAX      ConfdString
    MAX-ACCESS  read-only
    STATUS      current
    DESCRIPTION "Alg tftp pass downlink packets count"
    ::= { affirmedServicesNatServiceNatClusterLevelModuleStatsEntry 77 }

affirmedServicesNatServiceNatClusterLevelModuleStatsConnectionCreateIgnoredNonTcpSyn OBJECT-TYPE
    SYNTAX      ConfdString
    MAX-ACCESS  read-only
    STATUS      current
    DESCRIPTION "Number of connection creation ignored as it was non tcp syn"
    ::= { affirmedServicesNatServiceNatClusterLevelModuleStatsEntry 78 }

affirmedServicesNatServiceNatClusterLevelModuleStatsConnectionCreateEsp OBJECT-TYPE
    SYNTAX      ConfdString
    MAX-ACCESS  read-only
    STATUS      current
    DESCRIPTION "Number of esp connections created"
    ::= { affirmedServicesNatServiceNatClusterLevelModuleStatsEntry 79 }

affirmedServicesNatServiceNatClusterLevelModuleStatsConnectionDeleteEsp OBJECT-TYPE
    SYNTAX      ConfdString
    MAX-ACCESS  read-only
    STATUS      current
    DESCRIPTION "Number of esp connections deleted"
    ::= { affirmedServicesNatServiceNatClusterLevelModuleStatsEntry 80 }

affirmedServicesNatServiceNatClusterLevelModuleStatsAllocFailureNPTv6 OBJECT-TYPE
    SYNTAX      ConfdString
    MAX-ACCESS  read-only
    STATUS      current
    DESCRIPTION "Number of sessions failed for NPTv6"
    ::= { affirmedServicesNatServiceNatClusterLevelModuleStatsEntry 81 }

affirmedServicesNatServiceNatClusterLevelModuleStatsIpsecNattAssistAlgUplinkPackets OBJECT-TYPE
    SYNTAX      ConfdString
    MAX-ACCESS  read-only
    STATUS      current
    DESCRIPTION "Alg ipsec natt assist uplink packets count"
    ::= { affirmedServicesNatServiceNatClusterLevelModuleStatsEntry 82 }

affirmedServicesNatServiceNatClusterLevelModuleStatsIpsecNattAssistAlgDownlinkPackets OBJECT-TYPE
    SYNTAX      ConfdString
    MAX-ACCESS  read-only
    STATUS      current
    DESCRIPTION "Alg ipsec natt assist downlink packets count"
    ::= { affirmedServicesNatServiceNatClusterLevelModuleStatsEntry 83 }

affirmedServicesNatServiceNatClusterLevelModuleStatsIpsecNattAssistPassAlgUplinkPackets OBJECT-TYPE
    SYNTAX      ConfdString
    MAX-ACCESS  read-only
    STATUS      current
    DESCRIPTION "Alg ipsec natt assist pass uplink packets count"
    ::= { affirmedServicesNatServiceNatClusterLevelModuleStatsEntry 84 }

affirmedServicesNatServiceNatClusterLevelModuleStatsIpsecNattAssistPassAlgDownlinkPackets OBJECT-TYPE
    SYNTAX      ConfdString
    MAX-ACCESS  read-only
    STATUS      current
    DESCRIPTION "Alg ipsec natt assist pass downlink packets count"
    ::= { affirmedServicesNatServiceNatClusterLevelModuleStatsEntry 85 }

affirmedServicesNatServiceNatClusterLevelModuleStatsConnectionCreateFailureConnTracker OBJECT-TYPE
    SYNTAX      ConfdString
    MAX-ACCESS  read-only
    STATUS      current
    DESCRIPTION "Number of connection create failures due to Connection tracker"
    ::= { affirmedServicesNatServiceNatClusterLevelModuleStatsEntry 86 }

affirmedServicesNatServiceNatClusterLevelModuleStatsNumRejectFlowStateTrackingMisconfig OBJECT-TYPE
    SYNTAX      ConfdString
    MAX-ACCESS  read-only
    STATUS      current
    DESCRIPTION "Number of connections rejected due to missing flow-idle-timeout-profile/flow-state-tracking-profile"
    ::= { affirmedServicesNatServiceNatClusterLevelModuleStatsEntry 87 }

affirmedServicesNatServiceNatClusterLevelModuleStatsPptpAlgDownlinkPackets OBJECT-TYPE
    SYNTAX      ConfdString
    MAX-ACCESS  read-only
    STATUS      current
    DESCRIPTION "Alg pptp downlink packets count"
    ::= { affirmedServicesNatServiceNatClusterLevelModuleStatsEntry 88 }

affirmedServicesNatServiceNatClusterLevelModuleStatsPptpAlgUplinkPackets OBJECT-TYPE
    SYNTAX      ConfdString
    MAX-ACCESS  read-only
    STATUS      current
    DESCRIPTION "Alg pptp uplink packets count"
    ::= { affirmedServicesNatServiceNatClusterLevelModuleStatsEntry 89 }

affirmedServicesNatServiceNatClusterLevelModuleStatsPptpPassAlgDownlinkPackets OBJECT-TYPE
    SYNTAX      ConfdString
    MAX-ACCESS  read-only
    STATUS      current
    DESCRIPTION "Alg pptp pass downlink packets count"
    ::= { affirmedServicesNatServiceNatClusterLevelModuleStatsEntry 90 }

affirmedServicesNatServiceNatClusterLevelModuleStatsPptpPassAlgUplinkPackets OBJECT-TYPE
    SYNTAX      ConfdString
    MAX-ACCESS  read-only
    STATUS      current
    DESCRIPTION "Alg pptp pass uplink packets count"
    ::= { affirmedServicesNatServiceNatClusterLevelModuleStatsEntry 91 }

affirmedServicesNatServiceNatClusterLevelModuleStatsPktDropConnTracker OBJECT-TYPE
    SYNTAX      ConfdString
    MAX-ACCESS  read-only
    STATUS      current
    DESCRIPTION "Number of packets dropped by Connection tracker(Stateful Firewall)"
    ::= { affirmedServicesNatServiceNatClusterLevelModuleStatsEntry 92 }

affirmedServicesNatServiceNatClusterLevelAlgStatsTable OBJECT-TYPE
    SYNTAX      SEQUENCE OF AffirmedServicesNatServiceNatClusterLevelAlgStatsEntry
    MAX-ACCESS  not-accessible
    STATUS      current
    DESCRIPTION ""
    ::= { affirmedServicesNatServiceNatClusterLevel 2 }

affirmedServicesNatServiceNatClusterLevelAlgStatsEntry OBJECT-TYPE
    SYNTAX      AffirmedServicesNatServiceNatClusterLevelAlgStatsEntry
    MAX-ACCESS  not-accessible
    STATUS      current
    DESCRIPTION ""
    INDEX { affirmedServicesNatServiceNatClusterLevelAlgStatsChassis, affirmedServicesNatServiceNatClusterLevelAlgStatsAlgType }
        ::= { affirmedServicesNatServiceNatClusterLevelAlgStatsTable 1 }

AffirmedServicesNatServiceNatClusterLevelAlgStatsEntry ::=
    SEQUENCE {
        affirmedServicesNatServiceNatClusterLevelAlgStatsChassis Unsigned32,
        affirmedServicesNatServiceNatClusterLevelAlgStatsAlgType String,
        affirmedServicesNatServiceNatClusterLevelAlgStatsPinholeUplinkAudio ConfdString,
        affirmedServicesNatServiceNatClusterLevelAlgStatsPinholeUplinkVideo ConfdString,
        affirmedServicesNatServiceNatClusterLevelAlgStatsPinholeDownlinkAudio ConfdString,
        affirmedServicesNatServiceNatClusterLevelAlgStatsPinholeDownlinkVideo ConfdString,
        affirmedServicesNatServiceNatClusterLevelAlgStatsPinholeDownlinkReg ConfdString,
        affirmedServicesNatServiceNatClusterLevelAlgStatsSipMangledUpstream ConfdString,
        affirmedServicesNatServiceNatClusterLevelAlgStatsSipMangledDownstream ConfdString,
        affirmedServicesNatServiceNatClusterLevelAlgStatsSipRegister ConfdString,
        affirmedServicesNatServiceNatClusterLevelAlgStatsSipInviteUpstream ConfdString,
        affirmedServicesNatServiceNatClusterLevelAlgStatsSipInviteDownstream ConfdString,
        affirmedServicesNatServiceNatClusterLevelAlgStatsSipCancelUpstream ConfdString,
        affirmedServicesNatServiceNatClusterLevelAlgStatsSipCancelDownstream ConfdString,
        affirmedServicesNatServiceNatClusterLevelAlgStatsSipByeDownstream ConfdString,
        affirmedServicesNatServiceNatClusterLevelAlgStatsSipByeUpstream ConfdString,
        affirmedServicesNatServiceNatClusterLevelAlgStatsPinholeUplinkErrorAudio ConfdString,
        affirmedServicesNatServiceNatClusterLevelAlgStatsPinholeUplinkErrorVideo ConfdString,
        affirmedServicesNatServiceNatClusterLevelAlgStatsPinholeDownlinkErrorAudio ConfdString,
        affirmedServicesNatServiceNatClusterLevelAlgStatsPinholeDownlinkErrorVideo ConfdString,
        affirmedServicesNatServiceNatClusterLevelAlgStatsPinholeDownlinkErrorReg ConfdString,
        affirmedServicesNatServiceNatClusterLevelAlgStatsSipErrorParse ConfdString,
        affirmedServicesNatServiceNatClusterLevelAlgStatsSipErrorReplaceContact ConfdString,
        affirmedServicesNatServiceNatClusterLevelAlgStatsSipErrorInviteNoBinding ConfdString,
        affirmedServicesNatServiceNatClusterLevelAlgStatsSipErrorByeNoBinding ConfdString,
        affirmedServicesNatServiceNatClusterLevelAlgStatsSipErrorAckNoBinding ConfdString,
        affirmedServicesNatServiceNatClusterLevelAlgStatsSipErrorMangle ConfdString,
        affirmedServicesNatServiceNatClusterLevelAlgStatsSipErrorContactAndUeAddrMismatch ConfdString,
        affirmedServicesNatServiceNatClusterLevelAlgStatsConnCreateSuccess ConfdString,
        affirmedServicesNatServiceNatClusterLevelAlgStatsConnCreateFailure ConfdString,
        affirmedServicesNatServiceNatClusterLevelAlgStatsPhCreateSuccess ConfdString,
        affirmedServicesNatServiceNatClusterLevelAlgStatsPhCreateFailure ConfdString,
        affirmedServicesNatServiceNatClusterLevelAlgStatsGoodBlkSizeValueInReq ConfdString,
        affirmedServicesNatServiceNatClusterLevelAlgStatsBadBlkSizeValueInReq ConfdString,
        affirmedServicesNatServiceNatClusterLevelAlgStatsBlkSizeValueMiss ConfdString,
        affirmedServicesNatServiceNatClusterLevelAlgStatsBlkSizeParamNameMiss ConfdString,
        affirmedServicesNatServiceNatClusterLevelAlgStatsBlkSizeFormatErr ConfdString,
        affirmedServicesNatServiceNatClusterLevelAlgStatsBadRelativePathName ConfdString,
        affirmedServicesNatServiceNatClusterLevelAlgStatsPass2Err ConfdString,
        affirmedServicesNatServiceNatClusterLevelAlgStatsInvalidFirstMsg ConfdString,
        affirmedServicesNatServiceNatClusterLevelAlgStatsInvalidSecondMsg ConfdString,
        affirmedServicesNatServiceNatClusterLevelAlgStatsDataMsgTooBigErr ConfdString,
        affirmedServicesNatServiceNatClusterLevelAlgStatsIgnoreTftpReqClient ConfdString,
        affirmedServicesNatServiceNatClusterLevelAlgStatsBlockedAccessServSysFile ConfdString,
        affirmedServicesNatServiceNatClusterLevelAlgStatsBadProtocol ConfdString,
        affirmedServicesNatServiceNatClusterLevelAlgStatsPortCmdCnt ConfdString,
        affirmedServicesNatServiceNatClusterLevelAlgStatsEprtCmdCnt ConfdString,
        affirmedServicesNatServiceNatClusterLevelAlgStatsPasvCmdCount ConfdString,
        affirmedServicesNatServiceNatClusterLevelAlgStatsEpsvCmdCnt ConfdString,
        affirmedServicesNatServiceNatClusterLevelAlgStatsInvalidPortCmdCnt ConfdString,
        affirmedServicesNatServiceNatClusterLevelAlgStatsInvalidPasvRspCnt ConfdString,
        affirmedServicesNatServiceNatClusterLevelAlgStatsActModeWrongAddrCnt ConfdString,
        affirmedServicesNatServiceNatClusterLevelAlgStatsPsvModeWrongAddrCnt ConfdString,
        affirmedServicesNatServiceNatClusterLevelAlgStatsUplinkPhConnCnt ConfdString,
        affirmedServicesNatServiceNatClusterLevelAlgStatsUplinkPhConnErrCnt ConfdString,
        affirmedServicesNatServiceNatClusterLevelAlgStatsDnlinkPhConnCnt ConfdString,
        affirmedServicesNatServiceNatClusterLevelAlgStatsDnlinkPhConnErrCnt ConfdString,
        affirmedServicesNatServiceNatClusterLevelAlgStatsFtpMultilineRspCnt ConfdString,
        affirmedServicesNatServiceNatClusterLevelAlgStatsFtpInvalidArgErrCnt ConfdString,
        affirmedServicesNatServiceNatClusterLevelAlgStatsFtpOpNotAllowedErrCnt ConfdString,
        affirmedServicesNatServiceNatClusterLevelAlgStatsFtpDataPortFailedErrCnt ConfdString,
        affirmedServicesNatServiceNatClusterLevelAlgStatsFtpUnsupportedNwProtocolErrCnt ConfdString,
        affirmedServicesNatServiceNatClusterLevelAlgStatsFtpCmdNotImplementedErrCnt ConfdString,
        affirmedServicesNatServiceNatClusterLevelAlgStatsFtpFailedDataConnErrCnt ConfdString,
        affirmedServicesNatServiceNatClusterLevelAlgStatsPatchPort1Cnt ConfdString,
        affirmedServicesNatServiceNatClusterLevelAlgStatsPatchPort2Cnt ConfdString,
        affirmedServicesNatServiceNatClusterLevelAlgStatsPatchPort1Err ConfdString,
        affirmedServicesNatServiceNatClusterLevelAlgStatsPatchPort2Err ConfdString,
        affirmedServicesNatServiceNatClusterLevelAlgStatsPinholePortCnt ConfdString,
        affirmedServicesNatServiceNatClusterLevelAlgStatsPinholePortErr ConfdString,
        affirmedServicesNatServiceNatClusterLevelAlgStatsInvalidClientPorts ConfdString,
        affirmedServicesNatServiceNatClusterLevelAlgStatsInvalidServerPorts ConfdString,
        affirmedServicesNatServiceNatClusterLevelAlgStatsInvalidTransaction ConfdString,
        affirmedServicesNatServiceNatClusterLevelAlgStatsRevPort1MappingFailed ConfdString,
        affirmedServicesNatServiceNatClusterLevelAlgStatsRevPort2MappingFailed ConfdString,
        affirmedServicesNatServiceNatClusterLevelAlgStatsInvalidUplinkInterleavedModeChannels ConfdString,
        affirmedServicesNatServiceNatClusterLevelAlgStatsInvalidDownlinklinkInterleavedModeChannels ConfdString,
        affirmedServicesNatServiceNatClusterLevelAlgStatsUplinkVersionNotSupported ConfdString,
        affirmedServicesNatServiceNatClusterLevelAlgStatsDownlinkVersionNotSupported ConfdString,
        affirmedServicesNatServiceNatClusterLevelAlgStatsUplinkDataPacketTransferFail ConfdString,
        affirmedServicesNatServiceNatClusterLevelAlgStatsDownlinkDataPacketTransferFail ConfdString,
        affirmedServicesNatServiceNatClusterLevelAlgStatsUplinkInterleaveModeRequest ConfdString,
        affirmedServicesNatServiceNatClusterLevelAlgStatsDownlinkInterleaveModeRequest ConfdString,
        affirmedServicesNatServiceNatClusterLevelAlgStatsUplinkOptionsRequest ConfdString,
        affirmedServicesNatServiceNatClusterLevelAlgStatsUplinkDescribeRequest ConfdString,
        affirmedServicesNatServiceNatClusterLevelAlgStatsUplinkSetupRequest ConfdString,
        affirmedServicesNatServiceNatClusterLevelAlgStatsUplinkPlayRequest ConfdString,
        affirmedServicesNatServiceNatClusterLevelAlgStatsUplinkTeardownRequest ConfdString,
        affirmedServicesNatServiceNatClusterLevelAlgStatsDownlinkOptionsResponse ConfdString,
        affirmedServicesNatServiceNatClusterLevelAlgStatsDownlinkDescribeResponse ConfdString,
        affirmedServicesNatServiceNatClusterLevelAlgStatsDownlinkSetupResponse ConfdString,
        affirmedServicesNatServiceNatClusterLevelAlgStatsDownlinkTeardownResponse ConfdString,
        affirmedServicesNatServiceNatClusterLevelAlgStatsSipUplinkUnsupportedMethod ConfdString,
        affirmedServicesNatServiceNatClusterLevelAlgStatsSipDownlinkUnsupportedMethod ConfdString
    }

affirmedServicesNatServiceNatClusterLevelAlgStatsChassis OBJECT-TYPE
    SYNTAX      Unsigned32
    MAX-ACCESS  not-accessible
    STATUS      current
    DESCRIPTION ""
    ::= { affirmedServicesNatServiceNatClusterLevelAlgStatsEntry 1 }

affirmedServicesNatServiceNatClusterLevelAlgStatsAlgType OBJECT-TYPE
    SYNTAX      String
    MAX-ACCESS  not-accessible
    STATUS      current
    DESCRIPTION ""
    ::= { affirmedServicesNatServiceNatClusterLevelAlgStatsEntry 2 }

affirmedServicesNatServiceNatClusterLevelAlgStatsPinholeUplinkAudio OBJECT-TYPE
    SYNTAX      ConfdString
    MAX-ACCESS  read-only
    STATUS      current
    DESCRIPTION "Uplink audio pinhole success"
    ::= { affirmedServicesNatServiceNatClusterLevelAlgStatsEntry 3 }

affirmedServicesNatServiceNatClusterLevelAlgStatsPinholeUplinkVideo OBJECT-TYPE
    SYNTAX      ConfdString
    MAX-ACCESS  read-only
    STATUS      current
    DESCRIPTION "Uplink video pinhole success"
    ::= { affirmedServicesNatServiceNatClusterLevelAlgStatsEntry 4 }

affirmedServicesNatServiceNatClusterLevelAlgStatsPinholeDownlinkAudio OBJECT-TYPE
    SYNTAX      ConfdString
    MAX-ACCESS  read-only
    STATUS      current
    DESCRIPTION "Downlink audio pinhole success"
    ::= { affirmedServicesNatServiceNatClusterLevelAlgStatsEntry 5 }

affirmedServicesNatServiceNatClusterLevelAlgStatsPinholeDownlinkVideo OBJECT-TYPE
    SYNTAX      ConfdString
    MAX-ACCESS  read-only
    STATUS      current
    DESCRIPTION "Downlink video pinhole success"
    ::= { affirmedServicesNatServiceNatClusterLevelAlgStatsEntry 6 }

affirmedServicesNatServiceNatClusterLevelAlgStatsPinholeDownlinkReg OBJECT-TYPE
    SYNTAX      ConfdString
    MAX-ACCESS  read-only
    STATUS      current
    DESCRIPTION "Uplink register pinhole success (TCP)"
    ::= { affirmedServicesNatServiceNatClusterLevelAlgStatsEntry 7 }

affirmedServicesNatServiceNatClusterLevelAlgStatsSipMangledUpstream OBJECT-TYPE
    SYNTAX      ConfdString
    MAX-ACCESS  read-only
    STATUS      current
    DESCRIPTION "SIP mangled Upstream"
    ::= { affirmedServicesNatServiceNatClusterLevelAlgStatsEntry 8 }

affirmedServicesNatServiceNatClusterLevelAlgStatsSipMangledDownstream OBJECT-TYPE
    SYNTAX      ConfdString
    MAX-ACCESS  read-only
    STATUS      current
    DESCRIPTION "SIP mangled Downstream"
    ::= { affirmedServicesNatServiceNatClusterLevelAlgStatsEntry 9 }

affirmedServicesNatServiceNatClusterLevelAlgStatsSipRegister OBJECT-TYPE
    SYNTAX      ConfdString
    MAX-ACCESS  read-only
    STATUS      current
    DESCRIPTION "SIP register upstream"
    ::= { affirmedServicesNatServiceNatClusterLevelAlgStatsEntry 10 }

affirmedServicesNatServiceNatClusterLevelAlgStatsSipInviteUpstream OBJECT-TYPE
    SYNTAX      ConfdString
    MAX-ACCESS  read-only
    STATUS      current
    DESCRIPTION "SIP INVITE Upstream"
    ::= { affirmedServicesNatServiceNatClusterLevelAlgStatsEntry 11 }

affirmedServicesNatServiceNatClusterLevelAlgStatsSipInviteDownstream OBJECT-TYPE
    SYNTAX      ConfdString
    MAX-ACCESS  read-only
    STATUS      current
    DESCRIPTION "SIP INVITE Downstream"
    ::= { affirmedServicesNatServiceNatClusterLevelAlgStatsEntry 12 }

affirmedServicesNatServiceNatClusterLevelAlgStatsSipCancelUpstream OBJECT-TYPE
    SYNTAX      ConfdString
    MAX-ACCESS  read-only
    STATUS      current
    DESCRIPTION "SIP CANCEL Request/Response from Upstream"
    ::= { affirmedServicesNatServiceNatClusterLevelAlgStatsEntry 13 }

affirmedServicesNatServiceNatClusterLevelAlgStatsSipCancelDownstream OBJECT-TYPE
    SYNTAX      ConfdString
    MAX-ACCESS  read-only
    STATUS      current
    DESCRIPTION "SIP CANCEL Request/Response from Downstream"
    ::= { affirmedServicesNatServiceNatClusterLevelAlgStatsEntry 14 }

affirmedServicesNatServiceNatClusterLevelAlgStatsSipByeDownstream OBJECT-TYPE
    SYNTAX      ConfdString
    MAX-ACCESS  read-only
    STATUS      current
    DESCRIPTION "SIP BYE Downstream"
    ::= { affirmedServicesNatServiceNatClusterLevelAlgStatsEntry 15 }

affirmedServicesNatServiceNatClusterLevelAlgStatsSipByeUpstream OBJECT-TYPE
    SYNTAX      ConfdString
    MAX-ACCESS  read-only
    STATUS      current
    DESCRIPTION "SIP BYE Upstream"
    ::= { affirmedServicesNatServiceNatClusterLevelAlgStatsEntry 16 }

affirmedServicesNatServiceNatClusterLevelAlgStatsPinholeUplinkErrorAudio OBJECT-TYPE
    SYNTAX      ConfdString
    MAX-ACCESS  read-only
    STATUS      current
    DESCRIPTION "Uplink audio pinhole creation fail"
    ::= { affirmedServicesNatServiceNatClusterLevelAlgStatsEntry 17 }

affirmedServicesNatServiceNatClusterLevelAlgStatsPinholeUplinkErrorVideo OBJECT-TYPE
    SYNTAX      ConfdString
    MAX-ACCESS  read-only
    STATUS      current
    DESCRIPTION "Uplink video pinhole creation fail"
    ::= { affirmedServicesNatServiceNatClusterLevelAlgStatsEntry 18 }

affirmedServicesNatServiceNatClusterLevelAlgStatsPinholeDownlinkErrorAudio OBJECT-TYPE
    SYNTAX      ConfdString
    MAX-ACCESS  read-only
    STATUS      current
    DESCRIPTION "Downlink audio pinhole creation fail"
    ::= { affirmedServicesNatServiceNatClusterLevelAlgStatsEntry 19 }

affirmedServicesNatServiceNatClusterLevelAlgStatsPinholeDownlinkErrorVideo OBJECT-TYPE
    SYNTAX      ConfdString
    MAX-ACCESS  read-only
    STATUS      current
    DESCRIPTION "Downlink video pinhole creation fail"
    ::= { affirmedServicesNatServiceNatClusterLevelAlgStatsEntry 20 }

affirmedServicesNatServiceNatClusterLevelAlgStatsPinholeDownlinkErrorReg OBJECT-TYPE
    SYNTAX      ConfdString
    MAX-ACCESS  read-only
    STATUS      current
    DESCRIPTION "Uplink register pinhole creation fail (TCP)"
    ::= { affirmedServicesNatServiceNatClusterLevelAlgStatsEntry 21 }

affirmedServicesNatServiceNatClusterLevelAlgStatsSipErrorParse OBJECT-TYPE
    SYNTAX      ConfdString
    MAX-ACCESS  read-only
    STATUS      deprecated
    DESCRIPTION "SIP error parse"
    ::= { affirmedServicesNatServiceNatClusterLevelAlgStatsEntry 22 }

affirmedServicesNatServiceNatClusterLevelAlgStatsSipErrorReplaceContact OBJECT-TYPE
    SYNTAX      ConfdString
    MAX-ACCESS  read-only
    STATUS      current
    DESCRIPTION "Header replacement error"
    ::= { affirmedServicesNatServiceNatClusterLevelAlgStatsEntry 23 }

affirmedServicesNatServiceNatClusterLevelAlgStatsSipErrorInviteNoBinding OBJECT-TYPE
    SYNTAX      ConfdString
    MAX-ACCESS  read-only
    STATUS      current
    DESCRIPTION "Binding (call id) does not exist for INVITE"
    ::= { affirmedServicesNatServiceNatClusterLevelAlgStatsEntry 24 }

affirmedServicesNatServiceNatClusterLevelAlgStatsSipErrorByeNoBinding OBJECT-TYPE
    SYNTAX      ConfdString
    MAX-ACCESS  read-only
    STATUS      current
    DESCRIPTION "Binding (call id) does not exist for BYE"
    ::= { affirmedServicesNatServiceNatClusterLevelAlgStatsEntry 25 }

affirmedServicesNatServiceNatClusterLevelAlgStatsSipErrorAckNoBinding OBJECT-TYPE
    SYNTAX      ConfdString
    MAX-ACCESS  read-only
    STATUS      current
    DESCRIPTION "Binding (call id) does not exist for ACK"
    ::= { affirmedServicesNatServiceNatClusterLevelAlgStatsEntry 26 }

affirmedServicesNatServiceNatClusterLevelAlgStatsSipErrorMangle OBJECT-TYPE
    SYNTAX      ConfdString
    MAX-ACCESS  read-only
    STATUS      current
    DESCRIPTION "SIP error mangle"
    ::= { affirmedServicesNatServiceNatClusterLevelAlgStatsEntry 27 }

affirmedServicesNatServiceNatClusterLevelAlgStatsSipErrorContactAndUeAddrMismatch OBJECT-TYPE
    SYNTAX      ConfdString
    MAX-ACCESS  read-only
    STATUS      current
    DESCRIPTION "UE IP Address mismatch in REGISTER contact header"
    ::= { affirmedServicesNatServiceNatClusterLevelAlgStatsEntry 28 }

affirmedServicesNatServiceNatClusterLevelAlgStatsConnCreateSuccess OBJECT-TYPE
    SYNTAX      ConfdString
    MAX-ACCESS  read-only
    STATUS      current
    DESCRIPTION "Connection creation success"
    ::= { affirmedServicesNatServiceNatClusterLevelAlgStatsEntry 29 }

affirmedServicesNatServiceNatClusterLevelAlgStatsConnCreateFailure OBJECT-TYPE
    SYNTAX      ConfdString
    MAX-ACCESS  read-only
    STATUS      current
    DESCRIPTION "Connection creation failure"
    ::= { affirmedServicesNatServiceNatClusterLevelAlgStatsEntry 30 }

affirmedServicesNatServiceNatClusterLevelAlgStatsPhCreateSuccess OBJECT-TYPE
    SYNTAX      ConfdString
    MAX-ACCESS  read-only
    STATUS      current
    DESCRIPTION "Pinhole creation success"
    ::= { affirmedServicesNatServiceNatClusterLevelAlgStatsEntry 31 }

affirmedServicesNatServiceNatClusterLevelAlgStatsPhCreateFailure OBJECT-TYPE
    SYNTAX      ConfdString
    MAX-ACCESS  read-only
    STATUS      current
    DESCRIPTION "Pinhole creation failure"
    ::= { affirmedServicesNatServiceNatClusterLevelAlgStatsEntry 32 }

affirmedServicesNatServiceNatClusterLevelAlgStatsGoodBlkSizeValueInReq OBJECT-TYPE
    SYNTAX      ConfdString
    MAX-ACCESS  read-only
    STATUS      current
    DESCRIPTION "Good block size in request"
    ::= { affirmedServicesNatServiceNatClusterLevelAlgStatsEntry 33 }

affirmedServicesNatServiceNatClusterLevelAlgStatsBadBlkSizeValueInReq OBJECT-TYPE
    SYNTAX      ConfdString
    MAX-ACCESS  read-only
    STATUS      current
    DESCRIPTION "Invalid block size in request"
    ::= { affirmedServicesNatServiceNatClusterLevelAlgStatsEntry 34 }

affirmedServicesNatServiceNatClusterLevelAlgStatsBlkSizeValueMiss OBJECT-TYPE
    SYNTAX      ConfdString
    MAX-ACCESS  read-only
    STATUS      current
    DESCRIPTION "Block size name present but size missing"
    ::= { affirmedServicesNatServiceNatClusterLevelAlgStatsEntry 35 }

affirmedServicesNatServiceNatClusterLevelAlgStatsBlkSizeParamNameMiss OBJECT-TYPE
    SYNTAX      ConfdString
    MAX-ACCESS  read-only
    STATUS      current
    DESCRIPTION "No room for transfer mode or optional parameters due to lack of space in buffer"
    ::= { affirmedServicesNatServiceNatClusterLevelAlgStatsEntry 36 }

affirmedServicesNatServiceNatClusterLevelAlgStatsBlkSizeFormatErr OBJECT-TYPE
    SYNTAX      ConfdString
    MAX-ACCESS  read-only
    STATUS      current
    DESCRIPTION "Format error in block size value"
    ::= { affirmedServicesNatServiceNatClusterLevelAlgStatsEntry 37 }

affirmedServicesNatServiceNatClusterLevelAlgStatsBadRelativePathName OBJECT-TYPE
    SYNTAX      ConfdString
    MAX-ACCESS  read-only
    STATUS      current
    DESCRIPTION "Access of relative path"
    ::= { affirmedServicesNatServiceNatClusterLevelAlgStatsEntry 38 }

affirmedServicesNatServiceNatClusterLevelAlgStatsPass2Err OBJECT-TYPE
    SYNTAX      ConfdString
    MAX-ACCESS  read-only
    STATUS      current
    DESCRIPTION "Pass 2 error"
    ::= { affirmedServicesNatServiceNatClusterLevelAlgStatsEntry 39 }

affirmedServicesNatServiceNatClusterLevelAlgStatsInvalidFirstMsg OBJECT-TYPE
    SYNTAX      ConfdString
    MAX-ACCESS  read-only
    STATUS      current
    DESCRIPTION "Invalid message type for the start of a transfer sequence"
    ::= { affirmedServicesNatServiceNatClusterLevelAlgStatsEntry 40 }

affirmedServicesNatServiceNatClusterLevelAlgStatsInvalidSecondMsg OBJECT-TYPE
    SYNTAX      ConfdString
    MAX-ACCESS  read-only
    STATUS      current
    DESCRIPTION "Invalid message type(invalid opcode)"
    ::= { affirmedServicesNatServiceNatClusterLevelAlgStatsEntry 41 }

affirmedServicesNatServiceNatClusterLevelAlgStatsDataMsgTooBigErr OBJECT-TYPE
    SYNTAX      ConfdString
    MAX-ACCESS  read-only
    STATUS      current
    DESCRIPTION "Block size is too big"
    ::= { affirmedServicesNatServiceNatClusterLevelAlgStatsEntry 42 }

affirmedServicesNatServiceNatClusterLevelAlgStatsIgnoreTftpReqClient OBJECT-TYPE
    SYNTAX      ConfdString
    MAX-ACCESS  read-only
    STATUS      current
    DESCRIPTION "Invalid TFTP request sent to client"
    ::= { affirmedServicesNatServiceNatClusterLevelAlgStatsEntry 43 }

affirmedServicesNatServiceNatClusterLevelAlgStatsBlockedAccessServSysFile OBJECT-TYPE
    SYNTAX      ConfdString
    MAX-ACCESS  read-only
    STATUS      current
    DESCRIPTION "Accessing of system folders such as /etc on unix/linux and \Windows folder on windows os is not allowed"
    ::= { affirmedServicesNatServiceNatClusterLevelAlgStatsEntry 44 }

affirmedServicesNatServiceNatClusterLevelAlgStatsBadProtocol OBJECT-TYPE
    SYNTAX      ConfdString
    MAX-ACCESS  read-only
    STATUS      current
    DESCRIPTION "Only UDP is allowed, TCP not supported"
    ::= { affirmedServicesNatServiceNatClusterLevelAlgStatsEntry 45 }

affirmedServicesNatServiceNatClusterLevelAlgStatsPortCmdCnt OBJECT-TYPE
    SYNTAX      ConfdString
    MAX-ACCESS  read-only
    STATUS      current
    DESCRIPTION "Total PORT commands"
    ::= { affirmedServicesNatServiceNatClusterLevelAlgStatsEntry 46 }

affirmedServicesNatServiceNatClusterLevelAlgStatsEprtCmdCnt OBJECT-TYPE
    SYNTAX      ConfdString
    MAX-ACCESS  read-only
    STATUS      current
    DESCRIPTION "Total EPRT commands"
    ::= { affirmedServicesNatServiceNatClusterLevelAlgStatsEntry 47 }

affirmedServicesNatServiceNatClusterLevelAlgStatsPasvCmdCount OBJECT-TYPE
    SYNTAX      ConfdString
    MAX-ACCESS  read-only
    STATUS      current
    DESCRIPTION "Total PASV commands"
    ::= { affirmedServicesNatServiceNatClusterLevelAlgStatsEntry 48 }

affirmedServicesNatServiceNatClusterLevelAlgStatsEpsvCmdCnt OBJECT-TYPE
    SYNTAX      ConfdString
    MAX-ACCESS  read-only
    STATUS      current
    DESCRIPTION "Total EPSV commands"
    ::= { affirmedServicesNatServiceNatClusterLevelAlgStatsEntry 49 }

affirmedServicesNatServiceNatClusterLevelAlgStatsInvalidPortCmdCnt OBJECT-TYPE
    SYNTAX      ConfdString
    MAX-ACCESS  read-only
    STATUS      current
    DESCRIPTION "Parameter(s) in PORT command is invalid (Ipv4 only)"
    ::= { affirmedServicesNatServiceNatClusterLevelAlgStatsEntry 50 }

affirmedServicesNatServiceNatClusterLevelAlgStatsInvalidPasvRspCnt OBJECT-TYPE
    SYNTAX      ConfdString
    MAX-ACCESS  read-only
    STATUS      current
    DESCRIPTION "Parameter(s) in PASV command is invalid (Ipv4 only)"
    ::= { affirmedServicesNatServiceNatClusterLevelAlgStatsEntry 51 }

affirmedServicesNatServiceNatClusterLevelAlgStatsActModeWrongAddrCnt OBJECT-TYPE
    SYNTAX      ConfdString
    MAX-ACCESS  read-only
    STATUS      current
    DESCRIPTION "UE IP Address mismatch in port command in active mode"
    ::= { affirmedServicesNatServiceNatClusterLevelAlgStatsEntry 52 }

affirmedServicesNatServiceNatClusterLevelAlgStatsPsvModeWrongAddrCnt OBJECT-TYPE
    SYNTAX      ConfdString
    MAX-ACCESS  read-only
    STATUS      current
    DESCRIPTION "Total wrong address count(Psv mode)"
    ::= { affirmedServicesNatServiceNatClusterLevelAlgStatsEntry 53 }

affirmedServicesNatServiceNatClusterLevelAlgStatsUplinkPhConnCnt OBJECT-TYPE
    SYNTAX      ConfdString
    MAX-ACCESS  read-only
    STATUS      current
    DESCRIPTION "Total uplink pinhole connection count"
    ::= { affirmedServicesNatServiceNatClusterLevelAlgStatsEntry 54 }

affirmedServicesNatServiceNatClusterLevelAlgStatsUplinkPhConnErrCnt OBJECT-TYPE
    SYNTAX      ConfdString
    MAX-ACCESS  read-only
    STATUS      current
    DESCRIPTION "Failed to create pinhole connection for FTP active mode"
    ::= { affirmedServicesNatServiceNatClusterLevelAlgStatsEntry 55 }

affirmedServicesNatServiceNatClusterLevelAlgStatsDnlinkPhConnCnt OBJECT-TYPE
    SYNTAX      ConfdString
    MAX-ACCESS  read-only
    STATUS      current
    DESCRIPTION "Total downlink pinhole connection count"
    ::= { affirmedServicesNatServiceNatClusterLevelAlgStatsEntry 56 }

affirmedServicesNatServiceNatClusterLevelAlgStatsDnlinkPhConnErrCnt OBJECT-TYPE
    SYNTAX      ConfdString
    MAX-ACCESS  read-only
    STATUS      current
    DESCRIPTION "Failed to create pinhole connection for FTP passive mode"
    ::= { affirmedServicesNatServiceNatClusterLevelAlgStatsEntry 57 }

affirmedServicesNatServiceNatClusterLevelAlgStatsFtpMultilineRspCnt OBJECT-TYPE
    SYNTAX      ConfdString
    MAX-ACCESS  read-only
    STATUS      current
    DESCRIPTION "Total multiline FTP responses"
    ::= { affirmedServicesNatServiceNatClusterLevelAlgStatsEntry 58 }

affirmedServicesNatServiceNatClusterLevelAlgStatsFtpInvalidArgErrCnt OBJECT-TYPE
    SYNTAX      ConfdString
    MAX-ACCESS  read-only
    STATUS      current
    DESCRIPTION "Total invalid-argument-error count. Syntax error in arguments passed (501)"
    ::= { affirmedServicesNatServiceNatClusterLevelAlgStatsEntry 59 }

affirmedServicesNatServiceNatClusterLevelAlgStatsFtpOpNotAllowedErrCnt OBJECT-TYPE
    SYNTAX      ConfdString
    MAX-ACCESS  read-only
    STATUS      current
    DESCRIPTION "Operator not allowed error count for PORT/EPRT. PORT/EPRT command with changed ip-address (500)"
    ::= { affirmedServicesNatServiceNatClusterLevelAlgStatsEntry 60 }

affirmedServicesNatServiceNatClusterLevelAlgStatsFtpDataPortFailedErrCnt OBJECT-TYPE
    SYNTAX      ConfdString
    MAX-ACCESS  read-only
    STATUS      current
    DESCRIPTION "Data port failed error count. Pinhole creation failure in active or passive mode or invalid PASV/EPSV response (500)"
    ::= { affirmedServicesNatServiceNatClusterLevelAlgStatsEntry 61 }

affirmedServicesNatServiceNatClusterLevelAlgStatsFtpUnsupportedNwProtocolErrCnt OBJECT-TYPE
    SYNTAX      ConfdString
    MAX-ACCESS  read-only
    STATUS      current
    DESCRIPTION "EPSV command with invalid protocol. Only supported Network protocol with EPSV is IPv6 (522)"
    ::= { affirmedServicesNatServiceNatClusterLevelAlgStatsEntry 62 }

affirmedServicesNatServiceNatClusterLevelAlgStatsFtpCmdNotImplementedErrCnt OBJECT-TYPE
    SYNTAX      ConfdString
    MAX-ACCESS  read-only
    STATUS      current
    DESCRIPTION "Invalid EPSV command (504)"
    ::= { affirmedServicesNatServiceNatClusterLevelAlgStatsEntry 63 }

affirmedServicesNatServiceNatClusterLevelAlgStatsFtpFailedDataConnErrCnt OBJECT-TYPE
    SYNTAX      ConfdString
    MAX-ACCESS  read-only
    STATUS      current
    DESCRIPTION "PASV response with changed ip-address (425)"
    ::= { affirmedServicesNatServiceNatClusterLevelAlgStatsEntry 64 }

affirmedServicesNatServiceNatClusterLevelAlgStatsPatchPort1Cnt OBJECT-TYPE
    SYNTAX      ConfdString
    MAX-ACCESS  read-only
    STATUS      current
    DESCRIPTION "Total server initiated PinHole for audio success"
    ::= { affirmedServicesNatServiceNatClusterLevelAlgStatsEntry 65 }

affirmedServicesNatServiceNatClusterLevelAlgStatsPatchPort2Cnt OBJECT-TYPE
    SYNTAX      ConfdString
    MAX-ACCESS  read-only
    STATUS      current
    DESCRIPTION "Total server initiated PinHole for video success"
    ::= { affirmedServicesNatServiceNatClusterLevelAlgStatsEntry 66 }

affirmedServicesNatServiceNatClusterLevelAlgStatsPatchPort1Err OBJECT-TYPE
    SYNTAX      ConfdString
    MAX-ACCESS  read-only
    STATUS      current
    DESCRIPTION "Total server initiated PinHole creation failure for audio"
    ::= { affirmedServicesNatServiceNatClusterLevelAlgStatsEntry 67 }

affirmedServicesNatServiceNatClusterLevelAlgStatsPatchPort2Err OBJECT-TYPE
    SYNTAX      ConfdString
    MAX-ACCESS  read-only
    STATUS      current
    DESCRIPTION "Total server initiated PinHole creation failure for video"
    ::= { affirmedServicesNatServiceNatClusterLevelAlgStatsEntry 68 }

affirmedServicesNatServiceNatClusterLevelAlgStatsPinholePortCnt OBJECT-TYPE
    SYNTAX      ConfdString
    MAX-ACCESS  read-only
    STATUS      current
    DESCRIPTION "Total client initiated PinHole success"
    ::= { affirmedServicesNatServiceNatClusterLevelAlgStatsEntry 69 }

affirmedServicesNatServiceNatClusterLevelAlgStatsPinholePortErr OBJECT-TYPE
    SYNTAX      ConfdString
    MAX-ACCESS  read-only
    STATUS      current
    DESCRIPTION "Total client initiated PinHole creation failure"
    ::= { affirmedServicesNatServiceNatClusterLevelAlgStatsEntry 70 }

affirmedServicesNatServiceNatClusterLevelAlgStatsInvalidClientPorts OBJECT-TYPE
    SYNTAX      ConfdString
    MAX-ACCESS  read-only
    STATUS      current
    DESCRIPTION "Total invalid client Ports. Either client ports are not valid"
    ::= { affirmedServicesNatServiceNatClusterLevelAlgStatsEntry 71 }

affirmedServicesNatServiceNatClusterLevelAlgStatsInvalidServerPorts OBJECT-TYPE
    SYNTAX      ConfdString
    MAX-ACCESS  read-only
    STATUS      current
    DESCRIPTION "Total invalid server Ports. Either server ports are not valid"
    ::= { affirmedServicesNatServiceNatClusterLevelAlgStatsEntry 72 }

affirmedServicesNatServiceNatClusterLevelAlgStatsInvalidTransaction OBJECT-TYPE
    SYNTAX      ConfdString
    MAX-ACCESS  read-only
    STATUS      current
    DESCRIPTION "Total invalid transaction"
    ::= { affirmedServicesNatServiceNatClusterLevelAlgStatsEntry 73 }

affirmedServicesNatServiceNatClusterLevelAlgStatsRevPort1MappingFailed OBJECT-TYPE
    SYNTAX      ConfdString
    MAX-ACCESS  read-only
    STATUS      current
    DESCRIPTION "Cannot find mapping for client audio/video port1"
    ::= { affirmedServicesNatServiceNatClusterLevelAlgStatsEntry 74 }

affirmedServicesNatServiceNatClusterLevelAlgStatsRevPort2MappingFailed OBJECT-TYPE
    SYNTAX      ConfdString
    MAX-ACCESS  read-only
    STATUS      current
    DESCRIPTION "Cannot find mapping for client audio/video port2"
    ::= { affirmedServicesNatServiceNatClusterLevelAlgStatsEntry 75 }

affirmedServicesNatServiceNatClusterLevelAlgStatsInvalidUplinkInterleavedModeChannels OBJECT-TYPE
    SYNTAX      ConfdString
    MAX-ACCESS  read-only
    STATUS      current
    DESCRIPTION "Invalid parameters in uplink interleaved mode"
    ::= { affirmedServicesNatServiceNatClusterLevelAlgStatsEntry 76 }

affirmedServicesNatServiceNatClusterLevelAlgStatsInvalidDownlinklinkInterleavedModeChannels OBJECT-TYPE
    SYNTAX      ConfdString
    MAX-ACCESS  read-only
    STATUS      current
    DESCRIPTION "Invalid parameters in downlink interleaved mode"
    ::= { affirmedServicesNatServiceNatClusterLevelAlgStatsEntry 77 }

affirmedServicesNatServiceNatClusterLevelAlgStatsUplinkVersionNotSupported OBJECT-TYPE
    SYNTAX      ConfdString
    MAX-ACCESS  read-only
    STATUS      current
    DESCRIPTION "RTSP version not supported for uplink interleave mode packet. Only RTSP/1.0 is supported"
    ::= { affirmedServicesNatServiceNatClusterLevelAlgStatsEntry 78 }

affirmedServicesNatServiceNatClusterLevelAlgStatsDownlinkVersionNotSupported OBJECT-TYPE
    SYNTAX      ConfdString
    MAX-ACCESS  read-only
    STATUS      current
    DESCRIPTION "RTSP version not supported for Downlink interleave mode  packet. Only RTSP/1.0 is supported"
    ::= { affirmedServicesNatServiceNatClusterLevelAlgStatsEntry 79 }

affirmedServicesNatServiceNatClusterLevelAlgStatsUplinkDataPacketTransferFail OBJECT-TYPE
    SYNTAX      ConfdString
    MAX-ACCESS  read-only
    STATUS      current
    DESCRIPTION "Uplink data packet transfer fail in interleave mode. Socket error/socket not connected"
    ::= { affirmedServicesNatServiceNatClusterLevelAlgStatsEntry 80 }

affirmedServicesNatServiceNatClusterLevelAlgStatsDownlinkDataPacketTransferFail OBJECT-TYPE
    SYNTAX      ConfdString
    MAX-ACCESS  read-only
    STATUS      current
    DESCRIPTION "Downlink data packet transfer fail in interleave mode. Socket inactive"
    ::= { affirmedServicesNatServiceNatClusterLevelAlgStatsEntry 81 }

affirmedServicesNatServiceNatClusterLevelAlgStatsUplinkInterleaveModeRequest OBJECT-TYPE
    SYNTAX      ConfdString
    MAX-ACCESS  read-only
    STATUS      current
    DESCRIPTION "Uplink  interleave mode request"
    ::= { affirmedServicesNatServiceNatClusterLevelAlgStatsEntry 82 }

affirmedServicesNatServiceNatClusterLevelAlgStatsDownlinkInterleaveModeRequest OBJECT-TYPE
    SYNTAX      ConfdString
    MAX-ACCESS  read-only
    STATUS      current
    DESCRIPTION "Downlink  interleave mode respone"
    ::= { affirmedServicesNatServiceNatClusterLevelAlgStatsEntry 83 }

affirmedServicesNatServiceNatClusterLevelAlgStatsUplinkOptionsRequest OBJECT-TYPE
    SYNTAX      ConfdString
    MAX-ACCESS  read-only
    STATUS      current
    DESCRIPTION "OPTIONS  request from UE"
    ::= { affirmedServicesNatServiceNatClusterLevelAlgStatsEntry 84 }

affirmedServicesNatServiceNatClusterLevelAlgStatsUplinkDescribeRequest OBJECT-TYPE
    SYNTAX      ConfdString
    MAX-ACCESS  read-only
    STATUS      current
    DESCRIPTION "DESCRIBE  request from UE"
    ::= { affirmedServicesNatServiceNatClusterLevelAlgStatsEntry 85 }

affirmedServicesNatServiceNatClusterLevelAlgStatsUplinkSetupRequest OBJECT-TYPE
    SYNTAX      ConfdString
    MAX-ACCESS  read-only
    STATUS      current
    DESCRIPTION "SETUP request from UE"
    ::= { affirmedServicesNatServiceNatClusterLevelAlgStatsEntry 86 }

affirmedServicesNatServiceNatClusterLevelAlgStatsUplinkPlayRequest OBJECT-TYPE
    SYNTAX      ConfdString
    MAX-ACCESS  read-only
    STATUS      current
    DESCRIPTION "PLAY request from UE"
    ::= { affirmedServicesNatServiceNatClusterLevelAlgStatsEntry 87 }

affirmedServicesNatServiceNatClusterLevelAlgStatsUplinkTeardownRequest OBJECT-TYPE
    SYNTAX      ConfdString
    MAX-ACCESS  read-only
    STATUS      current
    DESCRIPTION "TEARDOWN request from UE"
    ::= { affirmedServicesNatServiceNatClusterLevelAlgStatsEntry 88 }

affirmedServicesNatServiceNatClusterLevelAlgStatsDownlinkOptionsResponse OBJECT-TYPE
    SYNTAX      ConfdString
    MAX-ACCESS  read-only
    STATUS      current
    DESCRIPTION "OPTIONS  response from server"
    ::= { affirmedServicesNatServiceNatClusterLevelAlgStatsEntry 89 }

affirmedServicesNatServiceNatClusterLevelAlgStatsDownlinkDescribeResponse OBJECT-TYPE
    SYNTAX      ConfdString
    MAX-ACCESS  read-only
    STATUS      current
    DESCRIPTION "DESCRIBE  response from server"
    ::= { affirmedServicesNatServiceNatClusterLevelAlgStatsEntry 90 }

affirmedServicesNatServiceNatClusterLevelAlgStatsDownlinkSetupResponse OBJECT-TYPE
    SYNTAX      ConfdString
    MAX-ACCESS  read-only
    STATUS      current
    DESCRIPTION "SETUP  response from server"
    ::= { affirmedServicesNatServiceNatClusterLevelAlgStatsEntry 91 }

affirmedServicesNatServiceNatClusterLevelAlgStatsDownlinkTeardownResponse OBJECT-TYPE
    SYNTAX      ConfdString
    MAX-ACCESS  read-only
    STATUS      current
    DESCRIPTION "TEARDOWN  response from server"
    ::= { affirmedServicesNatServiceNatClusterLevelAlgStatsEntry 92 }

affirmedServicesNatServiceNatClusterLevelAlgStatsSipUplinkUnsupportedMethod OBJECT-TYPE
    SYNTAX      ConfdString
    MAX-ACCESS  read-only
    STATUS      current
    DESCRIPTION "OPTIONS, MESSAGE, NOTIFY, PRACK, SUBSCRIBE, UPDATE, PUBLISH, REFER and INFO methods are not supported"
    ::= { affirmedServicesNatServiceNatClusterLevelAlgStatsEntry 93 }

affirmedServicesNatServiceNatClusterLevelAlgStatsSipDownlinkUnsupportedMethod OBJECT-TYPE
    SYNTAX      ConfdString
    MAX-ACCESS  read-only
    STATUS      current
    DESCRIPTION "OPTIONS, MESSAGE, NOTIFY, PRACK, SUBSCRIBE, UPDATE, PUBLISH, REFER and INFO methods are not supported"
    ::= { affirmedServicesNatServiceNatClusterLevelAlgStatsEntry 94 }

affirmedServicesNatServiceNatNodeLevelModuleStatsTable OBJECT-TYPE
    SYNTAX      SEQUENCE OF AffirmedServicesNatServiceNatNodeLevelModuleStatsEntry
    MAX-ACCESS  not-accessible
    STATUS      current
    DESCRIPTION ""
    ::= { affirmedServicesNatServiceNatNodeLevel 1 }

affirmedServicesNatServiceNatNodeLevelModuleStatsEntry OBJECT-TYPE
    SYNTAX      AffirmedServicesNatServiceNatNodeLevelModuleStatsEntry
    MAX-ACCESS  not-accessible
    STATUS      current
    DESCRIPTION ""
    INDEX { affirmedServicesNatServiceNatNodeLevelModuleStatsChassis, affirmedServicesNatServiceNatNodeLevelModuleStatsSlot }
        ::= { affirmedServicesNatServiceNatNodeLevelModuleStatsTable 1 }

AffirmedServicesNatServiceNatNodeLevelModuleStatsEntry ::=
    SEQUENCE {
        affirmedServicesNatServiceNatNodeLevelModuleStatsChassis Unsigned32,
        affirmedServicesNatServiceNatNodeLevelModuleStatsSlot Unsigned32,
        affirmedServicesNatServiceNatNodeLevelModuleStatsSessionCreateFailure ConfdString,
        affirmedServicesNatServiceNatNodeLevelModuleStatsSessionCreateSuccess ConfdString,
        affirmedServicesNatServiceNatNodeLevelModuleStatsSessionDelete ConfdString,
        affirmedServicesNatServiceNatNodeLevelModuleStatsSessionIpAllocationSuccess ConfdString,
        affirmedServicesNatServiceNatNodeLevelModuleStatsSessionIpAllocationFailure ConfdString,
        affirmedServicesNatServiceNatNodeLevelModuleStatsSessionIpDeallocation ConfdString,
        affirmedServicesNatServiceNatNodeLevelModuleStatsSessionPortChunkAllocationSuccess ConfdString,
        affirmedServicesNatServiceNatNodeLevelModuleStatsSessionPortChunkAllocationFailure ConfdString,
        affirmedServicesNatServiceNatNodeLevelModuleStatsSessionPortChunkDeallocation ConfdString,
        affirmedServicesNatServiceNatNodeLevelModuleStatsAllocFailureNatPoolOutOfService ConfdString,
        affirmedServicesNatServiceNatNodeLevelModuleStatsAllocFailureOutOfNatResources ConfdString,
        affirmedServicesNatServiceNatNodeLevelModuleStatsAllocFailureActivationTimerOn ConfdString,
        affirmedServicesNatServiceNatNodeLevelModuleStatsAllocFailureSubPoolNotFound ConfdString,
        affirmedServicesNatServiceNatNodeLevelModuleStatsAllocFailureSubpoolOutOfService ConfdString,
        affirmedServicesNatServiceNatNodeLevelModuleStatsConnectionsCreated ConfdString,
        affirmedServicesNatServiceNatNodeLevelModuleStatsConnectionsDeleted ConfdString,
        affirmedServicesNatServiceNatNodeLevelModuleStatsConnectionCreateFailure ConfdString,
        affirmedServicesNatServiceNatNodeLevelModuleStatsConnectionCreateActionDrop ConfdString,
        affirmedServicesNatServiceNatNodeLevelModuleStatsConnectionCreateActionPass ConfdString,
        affirmedServicesNatServiceNatNodeLevelModuleStatsConnectionCreateIgnored ConfdString,
        affirmedServicesNatServiceNatNodeLevelModuleStatsConnectionCreateDropNetworkInitiated ConfdString,
        affirmedServicesNatServiceNatNodeLevelModuleStatsConnectionCreateFailureIpv6PrefixMismatch ConfdString,
        affirmedServicesNatServiceNatNodeLevelModuleStatsConnectionCreateFailureGeoRedMismatch ConfdString,
        affirmedServicesNatServiceNatNodeLevelModuleStatsConnectionCreateFailureNoAssociatedNatPool ConfdString,
        affirmedServicesNatServiceNatNodeLevelModuleStatsConnectionCreateFailureServiceFlowNotEnabled ConfdString,
        affirmedServicesNatServiceNatNodeLevelModuleStatsConnectionCreateFailureNatPoolNotEnabled ConfdString,
        affirmedServicesNatServiceNatNodeLevelModuleStatsConnectionCreateFailureNatAlgNotEnabled ConfdString,
        affirmedServicesNatServiceNatNodeLevelModuleStatsConnectionCreateFailureSessionNotActive ConfdString,
        affirmedServicesNatServiceNatNodeLevelModuleStatsConnectionCreateFailureNatMappingUnavailable ConfdString,
        affirmedServicesNatServiceNatNodeLevelModuleStatsConnectionCreateIgnoredNetworkInitiated ConfdString,
        affirmedServicesNatServiceNatNodeLevelModuleStatsConnectionCreateIgnoredUnsupportedIcmpType ConfdString,
        affirmedServicesNatServiceNatNodeLevelModuleStatsConnectionCreateIgnoredUnsupportedProtocol ConfdString,
        affirmedServicesNatServiceNatNodeLevelModuleStatsConnectionDeleteNatPoolConnectionPurge ConfdString,
        affirmedServicesNatServiceNatNodeLevelModuleStatsConnectionCreateTcp ConfdString,
        affirmedServicesNatServiceNatNodeLevelModuleStatsConnectionCreateUdp ConfdString,
        affirmedServicesNatServiceNatNodeLevelModuleStatsConnectionCreateIcmp ConfdString,
        affirmedServicesNatServiceNatNodeLevelModuleStatsConnectionDeleteTcp ConfdString,
        affirmedServicesNatServiceNatNodeLevelModuleStatsConnectionDeleteUdp ConfdString,
        affirmedServicesNatServiceNatNodeLevelModuleStatsConnectionDeleteIcmp ConfdString,
        affirmedServicesNatServiceNatNodeLevelModuleStatsNatFlowCreateFailure ConfdString,
        affirmedServicesNatServiceNatNodeLevelModuleStatsNatFlowCreateSuccess ConfdString,
        affirmedServicesNatServiceNatNodeLevelModuleStatsNatFlowDeleteSuccess ConfdString,
        affirmedServicesNatServiceNatNodeLevelModuleStatsNatFlowFoundConnectionCreated ConfdString,
        affirmedServicesNatServiceNatNodeLevelModuleStatsFilterAdfPacketAccepted ConfdString,
        affirmedServicesNatServiceNatNodeLevelModuleStatsFilterAdfPacketRejected ConfdString,
        affirmedServicesNatServiceNatNodeLevelModuleStatsFilterApdfPacketAccepted ConfdString,
        affirmedServicesNatServiceNatNodeLevelModuleStatsFilterApdfPacketRejected ConfdString,
        affirmedServicesNatServiceNatNodeLevelModuleStatsFilterEifPacketAccepted ConfdString,
        affirmedServicesNatServiceNatNodeLevelModuleStatsPacketTranslated ConfdString,
        affirmedServicesNatServiceNatNodeLevelModuleStatsPacketDropped ConfdString,
        affirmedServicesNatServiceNatNodeLevelModuleStatsPktDropUnknownProtocolFailure ConfdString,
        affirmedServicesNatServiceNatNodeLevelModuleStatsPktDropIcmpUnknownType ConfdString,
        affirmedServicesNatServiceNatNodeLevelModuleStatsPktDropReverseLookupFailure ConfdString,
        affirmedServicesNatServiceNatNodeLevelModuleStatsPktDropReverseSessionIdMismatch ConfdString,
        affirmedServicesNatServiceNatNodeLevelModuleStatsPktDropReverseUnknownProtocolFailure ConfdString,
        affirmedServicesNatServiceNatNodeLevelModuleStatsPktDropReversev4tov6ConversionFailure ConfdString,
        affirmedServicesNatServiceNatNodeLevelModuleStatsNatAlgUplinkPackets ConfdString,
        affirmedServicesNatServiceNatNodeLevelModuleStatsNatAlgDownlinkPackets ConfdString,
        affirmedServicesNatServiceNatNodeLevelModuleStatsPassAlgUplinkPackets ConfdString,
        affirmedServicesNatServiceNatNodeLevelModuleStatsPassAlgDownlinkPackets ConfdString,
        affirmedServicesNatServiceNatNodeLevelModuleStatsSipAlgUplinkPackets ConfdString,
        affirmedServicesNatServiceNatNodeLevelModuleStatsSipAlgDownlinkPackets ConfdString,
        affirmedServicesNatServiceNatNodeLevelModuleStatsSipPassAlgUplinkPackets ConfdString,
        affirmedServicesNatServiceNatNodeLevelModuleStatsSipPassAlgDownlinkPackets ConfdString,
        affirmedServicesNatServiceNatNodeLevelModuleStatsRtspAlgUplinkPackets ConfdString,
        affirmedServicesNatServiceNatNodeLevelModuleStatsRtspAlgDownlinkPackets ConfdString,
        affirmedServicesNatServiceNatNodeLevelModuleStatsRtspPassAlgUplinkPackets ConfdString,
        affirmedServicesNatServiceNatNodeLevelModuleStatsRtspPassAlgDownlinkPackets ConfdString,
        affirmedServicesNatServiceNatNodeLevelModuleStatsFtpAlgDownlinkPackets ConfdString,
        affirmedServicesNatServiceNatNodeLevelModuleStatsFtpAlgUplinkPackets ConfdString,
        affirmedServicesNatServiceNatNodeLevelModuleStatsFtpPassAlgDownlinkPackets ConfdString,
        affirmedServicesNatServiceNatNodeLevelModuleStatsFtpPassAlgUplinkPackets ConfdString,
        affirmedServicesNatServiceNatNodeLevelModuleStatsTftpAlgUplinkPackets ConfdString,
        affirmedServicesNatServiceNatNodeLevelModuleStatsTftpAlgDownlinkPackets ConfdString,
        affirmedServicesNatServiceNatNodeLevelModuleStatsTftpPassAlgUplinkPackets ConfdString,
        affirmedServicesNatServiceNatNodeLevelModuleStatsTftpPassAlgDownlinkPackets ConfdString,
        affirmedServicesNatServiceNatNodeLevelModuleStatsConnectionCreateIgnoredNonTcpSyn ConfdString,
        affirmedServicesNatServiceNatNodeLevelModuleStatsConnectionCreateEsp ConfdString,
        affirmedServicesNatServiceNatNodeLevelModuleStatsConnectionDeleteEsp ConfdString,
        affirmedServicesNatServiceNatNodeLevelModuleStatsAllocFailureNPTv6 ConfdString,
        affirmedServicesNatServiceNatNodeLevelModuleStatsIpsecNattAssistAlgUplinkPackets ConfdString,
        affirmedServicesNatServiceNatNodeLevelModuleStatsIpsecNattAssistAlgDownlinkPackets ConfdString,
        affirmedServicesNatServiceNatNodeLevelModuleStatsIpsecNattAssistPassAlgUplinkPackets ConfdString,
        affirmedServicesNatServiceNatNodeLevelModuleStatsIpsecNattAssistPassAlgDownlinkPackets ConfdString,
        affirmedServicesNatServiceNatNodeLevelModuleStatsConnectionCreateFailureConnTracker ConfdString,
        affirmedServicesNatServiceNatNodeLevelModuleStatsNumRejectFlowStateTrackingMisconfig ConfdString,
        affirmedServicesNatServiceNatNodeLevelModuleStatsPptpAlgDownlinkPackets ConfdString,
        affirmedServicesNatServiceNatNodeLevelModuleStatsPptpAlgUplinkPackets ConfdString,
        affirmedServicesNatServiceNatNodeLevelModuleStatsPptpPassAlgDownlinkPackets ConfdString,
        affirmedServicesNatServiceNatNodeLevelModuleStatsPptpPassAlgUplinkPackets ConfdString,
        affirmedServicesNatServiceNatNodeLevelModuleStatsPktDropConnTracker ConfdString
    }

affirmedServicesNatServiceNatNodeLevelModuleStatsChassis OBJECT-TYPE
    SYNTAX      Unsigned32
    MAX-ACCESS  not-accessible
    STATUS      current
    DESCRIPTION "Chassis id"
    ::= { affirmedServicesNatServiceNatNodeLevelModuleStatsEntry 1 }

affirmedServicesNatServiceNatNodeLevelModuleStatsSlot OBJECT-TYPE
    SYNTAX      Unsigned32
    MAX-ACCESS  not-accessible
    STATUS      current
    DESCRIPTION "Slot id"
    ::= { affirmedServicesNatServiceNatNodeLevelModuleStatsEntry 2 }

affirmedServicesNatServiceNatNodeLevelModuleStatsSessionCreateFailure OBJECT-TYPE
    SYNTAX      ConfdString
    MAX-ACCESS  read-only
    STATUS      current
    DESCRIPTION "Number of sessions for which NAT resource(IP or port chunks) allocation failed"
    ::= { affirmedServicesNatServiceNatNodeLevelModuleStatsEntry 3 }

affirmedServicesNatServiceNatNodeLevelModuleStatsSessionCreateSuccess OBJECT-TYPE
    SYNTAX      ConfdString
    MAX-ACCESS  read-only
    STATUS      current
    DESCRIPTION "Number of sessions successfully allocated NAT resources"
    ::= { affirmedServicesNatServiceNatNodeLevelModuleStatsEntry 4 }

affirmedServicesNatServiceNatNodeLevelModuleStatsSessionDelete OBJECT-TYPE
    SYNTAX      ConfdString
    MAX-ACCESS  read-only
    STATUS      current
    DESCRIPTION "Number of session delete requests processed"
    ::= { affirmedServicesNatServiceNatNodeLevelModuleStatsEntry 5 }

affirmedServicesNatServiceNatNodeLevelModuleStatsSessionIpAllocationSuccess OBJECT-TYPE
    SYNTAX      ConfdString
    MAX-ACCESS  read-only
    STATUS      current
    DESCRIPTION "Number of NAT IP allocated successfully"
    ::= { affirmedServicesNatServiceNatNodeLevelModuleStatsEntry 6 }

affirmedServicesNatServiceNatNodeLevelModuleStatsSessionIpAllocationFailure OBJECT-TYPE
    SYNTAX      ConfdString
    MAX-ACCESS  read-only
    STATUS      current
    DESCRIPTION "Number of NAT IP allocation failure"
    ::= { affirmedServicesNatServiceNatNodeLevelModuleStatsEntry 7 }

affirmedServicesNatServiceNatNodeLevelModuleStatsSessionIpDeallocation OBJECT-TYPE
    SYNTAX      ConfdString
    MAX-ACCESS  read-only
    STATUS      current
    DESCRIPTION "Number of NAT IP deallocation"
    ::= { affirmedServicesNatServiceNatNodeLevelModuleStatsEntry 8 }

affirmedServicesNatServiceNatNodeLevelModuleStatsSessionPortChunkAllocationSuccess OBJECT-TYPE
    SYNTAX      ConfdString
    MAX-ACCESS  read-only
    STATUS      current
    DESCRIPTION "Number of Port chunks successfully allocated"
    ::= { affirmedServicesNatServiceNatNodeLevelModuleStatsEntry 9 }

affirmedServicesNatServiceNatNodeLevelModuleStatsSessionPortChunkAllocationFailure OBJECT-TYPE
    SYNTAX      ConfdString
    MAX-ACCESS  read-only
    STATUS      current
    DESCRIPTION "Number of Port chunk allocation failure"
    ::= { affirmedServicesNatServiceNatNodeLevelModuleStatsEntry 10 }

affirmedServicesNatServiceNatNodeLevelModuleStatsSessionPortChunkDeallocation OBJECT-TYPE
    SYNTAX      ConfdString
    MAX-ACCESS  read-only
    STATUS      current
    DESCRIPTION "Number of Port chunks deallocated"
    ::= { affirmedServicesNatServiceNatNodeLevelModuleStatsEntry 11 }

affirmedServicesNatServiceNatNodeLevelModuleStatsAllocFailureNatPoolOutOfService OBJECT-TYPE
    SYNTAX      ConfdString
    MAX-ACCESS  read-only
    STATUS      current
    DESCRIPTION "Number of allocation failure due to nat-pool being admin disabled"
    ::= { affirmedServicesNatServiceNatNodeLevelModuleStatsEntry 12 }

affirmedServicesNatServiceNatNodeLevelModuleStatsAllocFailureOutOfNatResources OBJECT-TYPE
    SYNTAX      ConfdString
    MAX-ACCESS  read-only
    STATUS      current
    DESCRIPTION "Number of allocation failure due to lack of IP address or Port chunks"
    ::= { affirmedServicesNatServiceNatNodeLevelModuleStatsEntry 13 }

affirmedServicesNatServiceNatNodeLevelModuleStatsAllocFailureActivationTimerOn OBJECT-TYPE
    SYNTAX      ConfdString
    MAX-ACCESS  read-only
    STATUS      current
    DESCRIPTION "Number of allocation failure due to activation timer running"
    ::= { affirmedServicesNatServiceNatNodeLevelModuleStatsEntry 14 }

affirmedServicesNatServiceNatNodeLevelModuleStatsAllocFailureSubPoolNotFound OBJECT-TYPE
    SYNTAX      ConfdString
    MAX-ACCESS  read-only
    STATUS      current
    DESCRIPTION "Number of allocation failure due to sub pool not being configured"
    ::= { affirmedServicesNatServiceNatNodeLevelModuleStatsEntry 15 }

affirmedServicesNatServiceNatNodeLevelModuleStatsAllocFailureSubpoolOutOfService OBJECT-TYPE
    SYNTAX      ConfdString
    MAX-ACCESS  read-only
    STATUS      current
    DESCRIPTION "Number of allocation failure due to sub pool being admin disabled"
    ::= { affirmedServicesNatServiceNatNodeLevelModuleStatsEntry 16 }

affirmedServicesNatServiceNatNodeLevelModuleStatsConnectionsCreated OBJECT-TYPE
    SYNTAX      ConfdString
    MAX-ACCESS  read-only
    STATUS      current
    DESCRIPTION "Number of nat connections created"
    ::= { affirmedServicesNatServiceNatNodeLevelModuleStatsEntry 17 }

affirmedServicesNatServiceNatNodeLevelModuleStatsConnectionsDeleted OBJECT-TYPE
    SYNTAX      ConfdString
    MAX-ACCESS  read-only
    STATUS      current
    DESCRIPTION "Number of nat connections deleted"
    ::= { affirmedServicesNatServiceNatNodeLevelModuleStatsEntry 18 }

affirmedServicesNatServiceNatNodeLevelModuleStatsConnectionCreateFailure OBJECT-TYPE
    SYNTAX      ConfdString
    MAX-ACCESS  read-only
    STATUS      current
    DESCRIPTION "Number of nat connection creation failures"
    ::= { affirmedServicesNatServiceNatNodeLevelModuleStatsEntry 19 }

affirmedServicesNatServiceNatNodeLevelModuleStatsConnectionCreateActionDrop OBJECT-TYPE
    SYNTAX      ConfdString
    MAX-ACCESS  read-only
    STATUS      current
    DESCRIPTION "Number of nat connections not created due to service flow action drop"
    ::= { affirmedServicesNatServiceNatNodeLevelModuleStatsEntry 20 }

affirmedServicesNatServiceNatNodeLevelModuleStatsConnectionCreateActionPass OBJECT-TYPE
    SYNTAX      ConfdString
    MAX-ACCESS  read-only
    STATUS      current
    DESCRIPTION "Number of nat connections not created due to  service flow action pass"
    ::= { affirmedServicesNatServiceNatNodeLevelModuleStatsEntry 21 }

affirmedServicesNatServiceNatNodeLevelModuleStatsConnectionCreateIgnored OBJECT-TYPE
    SYNTAX      ConfdString
    MAX-ACCESS  read-only
    STATUS      current
    DESCRIPTION "Number of nat connections create ignored due to http-proxy non transparent mode enabled"
    ::= { affirmedServicesNatServiceNatNodeLevelModuleStatsEntry 22 }

affirmedServicesNatServiceNatNodeLevelModuleStatsConnectionCreateDropNetworkInitiated OBJECT-TYPE
    SYNTAX      ConfdString
    MAX-ACCESS  read-only
    STATUS      current
    DESCRIPTION "Number of connection creations dropped as it was Network initiated and destination is ue-ip"
    ::= { affirmedServicesNatServiceNatNodeLevelModuleStatsEntry 23 }

affirmedServicesNatServiceNatNodeLevelModuleStatsConnectionCreateFailureIpv6PrefixMismatch OBJECT-TYPE
    SYNTAX      ConfdString
    MAX-ACCESS  read-only
    STATUS      current
    DESCRIPTION "Number of nat connections creation failure due to mismatch between configured NAT64 Ipv6 prefix and Network Address of the connection"
    ::= { affirmedServicesNatServiceNatNodeLevelModuleStatsEntry 24 }

affirmedServicesNatServiceNatNodeLevelModuleStatsConnectionCreateFailureGeoRedMismatch OBJECT-TYPE
    SYNTAX      ConfdString
    MAX-ACCESS  read-only
    STATUS      current
    DESCRIPTION "Number of nat connections creation failure due to mismatch between Geo-group id of the nat-pool and the session"
    ::= { affirmedServicesNatServiceNatNodeLevelModuleStatsEntry 25 }

affirmedServicesNatServiceNatNodeLevelModuleStatsConnectionCreateFailureNoAssociatedNatPool OBJECT-TYPE
    SYNTAX      ConfdString
    MAX-ACCESS  read-only
    STATUS      current
    DESCRIPTION "Number of nat connections creation failure due to subscriber-firewall-flow for nat not configured with nat-pool"
    ::= { affirmedServicesNatServiceNatNodeLevelModuleStatsEntry 26 }

affirmedServicesNatServiceNatNodeLevelModuleStatsConnectionCreateFailureServiceFlowNotEnabled OBJECT-TYPE
    SYNTAX      ConfdString
    MAX-ACCESS  read-only
    STATUS      current
    DESCRIPTION "Number of nat connection creation failure due to subscriber-firewall-flow being admin disabled"
    ::= { affirmedServicesNatServiceNatNodeLevelModuleStatsEntry 27 }

affirmedServicesNatServiceNatNodeLevelModuleStatsConnectionCreateFailureNatPoolNotEnabled OBJECT-TYPE
    SYNTAX      ConfdString
    MAX-ACCESS  read-only
    STATUS      current
    DESCRIPTION "Number of nat connections creation failure due to nat-pool being admin disabled."
    ::= { affirmedServicesNatServiceNatNodeLevelModuleStatsEntry 28 }

affirmedServicesNatServiceNatNodeLevelModuleStatsConnectionCreateFailureNatAlgNotEnabled OBJECT-TYPE
    SYNTAX      ConfdString
    MAX-ACCESS  read-only
    STATUS      current
    DESCRIPTION "Number of nat connections creation failure due to NAT ALG  being disabled"
    ::= { affirmedServicesNatServiceNatNodeLevelModuleStatsEntry 29 }

affirmedServicesNatServiceNatNodeLevelModuleStatsConnectionCreateFailureSessionNotActive OBJECT-TYPE
    SYNTAX      ConfdString
    MAX-ACCESS  read-only
    STATUS      current
    DESCRIPTION "Number of connections create failure due to inactive session. This could be a transient condition during failover allowing the UE to quickly retry."
    ::= { affirmedServicesNatServiceNatNodeLevelModuleStatsEntry 30 }

affirmedServicesNatServiceNatNodeLevelModuleStatsConnectionCreateFailureNatMappingUnavailable OBJECT-TYPE
    SYNTAX      ConfdString
    MAX-ACCESS  read-only
    STATUS      current
    DESCRIPTION "Number of nat connection creation failure due to unavailability of Nat port"
    ::= { affirmedServicesNatServiceNatNodeLevelModuleStatsEntry 31 }

affirmedServicesNatServiceNatNodeLevelModuleStatsConnectionCreateIgnoredNetworkInitiated OBJECT-TYPE
    SYNTAX      ConfdString
    MAX-ACCESS  read-only
    STATUS      current
    DESCRIPTION "Number of connection creation ignored as it was Network initiated and destination is ue-ip, port 67(dhcp)"
    ::= { affirmedServicesNatServiceNatNodeLevelModuleStatsEntry 32 }

affirmedServicesNatServiceNatNodeLevelModuleStatsConnectionCreateIgnoredUnsupportedIcmpType OBJECT-TYPE
    SYNTAX      ConfdString
    MAX-ACCESS  read-only
    STATUS      current
    DESCRIPTION "Number of connection create ignored due to unsupported ICMP type"
    ::= { affirmedServicesNatServiceNatNodeLevelModuleStatsEntry 33 }

affirmedServicesNatServiceNatNodeLevelModuleStatsConnectionCreateIgnoredUnsupportedProtocol OBJECT-TYPE
    SYNTAX      ConfdString
    MAX-ACCESS  read-only
    STATUS      current
    DESCRIPTION "Number of connection create ignored due to unsupported protocol"
    ::= { affirmedServicesNatServiceNatNodeLevelModuleStatsEntry 34 }

affirmedServicesNatServiceNatNodeLevelModuleStatsConnectionDeleteNatPoolConnectionPurge OBJECT-TYPE
    SYNTAX      ConfdString
    MAX-ACCESS  read-only
    STATUS      current
    DESCRIPTION "Number of nat connections deleted due to nat-pool/sub-pool being admin disabled"
    ::= { affirmedServicesNatServiceNatNodeLevelModuleStatsEntry 35 }

affirmedServicesNatServiceNatNodeLevelModuleStatsConnectionCreateTcp OBJECT-TYPE
    SYNTAX      ConfdString
    MAX-ACCESS  read-only
    STATUS      current
    DESCRIPTION "Number of tcp connections created"
    ::= { affirmedServicesNatServiceNatNodeLevelModuleStatsEntry 36 }

affirmedServicesNatServiceNatNodeLevelModuleStatsConnectionCreateUdp OBJECT-TYPE
    SYNTAX      ConfdString
    MAX-ACCESS  read-only
    STATUS      current
    DESCRIPTION "Number of udp connections created"
    ::= { affirmedServicesNatServiceNatNodeLevelModuleStatsEntry 37 }

affirmedServicesNatServiceNatNodeLevelModuleStatsConnectionCreateIcmp OBJECT-TYPE
    SYNTAX      ConfdString
    MAX-ACCESS  read-only
    STATUS      current
    DESCRIPTION "Number of icmp connections created"
    ::= { affirmedServicesNatServiceNatNodeLevelModuleStatsEntry 38 }

affirmedServicesNatServiceNatNodeLevelModuleStatsConnectionDeleteTcp OBJECT-TYPE
    SYNTAX      ConfdString
    MAX-ACCESS  read-only
    STATUS      current
    DESCRIPTION "Number of tcp connections deleted"
    ::= { affirmedServicesNatServiceNatNodeLevelModuleStatsEntry 39 }

affirmedServicesNatServiceNatNodeLevelModuleStatsConnectionDeleteUdp OBJECT-TYPE
    SYNTAX      ConfdString
    MAX-ACCESS  read-only
    STATUS      current
    DESCRIPTION "Number of udp connections deleted"
    ::= { affirmedServicesNatServiceNatNodeLevelModuleStatsEntry 40 }

affirmedServicesNatServiceNatNodeLevelModuleStatsConnectionDeleteIcmp OBJECT-TYPE
    SYNTAX      ConfdString
    MAX-ACCESS  read-only
    STATUS      current
    DESCRIPTION "Number of icmp connections deleted"
    ::= { affirmedServicesNatServiceNatNodeLevelModuleStatsEntry 41 }

affirmedServicesNatServiceNatNodeLevelModuleStatsNatFlowCreateFailure OBJECT-TYPE
    SYNTAX      ConfdString
    MAX-ACCESS  read-only
    STATUS      current
    DESCRIPTION "Nat flow create failure count"
    ::= { affirmedServicesNatServiceNatNodeLevelModuleStatsEntry 42 }

affirmedServicesNatServiceNatNodeLevelModuleStatsNatFlowCreateSuccess OBJECT-TYPE
    SYNTAX      ConfdString
    MAX-ACCESS  read-only
    STATUS      current
    DESCRIPTION "Nat flow create success count"
    ::= { affirmedServicesNatServiceNatNodeLevelModuleStatsEntry 43 }

affirmedServicesNatServiceNatNodeLevelModuleStatsNatFlowDeleteSuccess OBJECT-TYPE
    SYNTAX      ConfdString
    MAX-ACCESS  read-only
    STATUS      current
    DESCRIPTION "Nat flow delete success count"
    ::= { affirmedServicesNatServiceNatNodeLevelModuleStatsEntry 44 }

affirmedServicesNatServiceNatNodeLevelModuleStatsNatFlowFoundConnectionCreated OBJECT-TYPE
    SYNTAX      ConfdString
    MAX-ACCESS  read-only
    STATUS      current
    DESCRIPTION "Nat flow found connection create count"
    ::= { affirmedServicesNatServiceNatNodeLevelModuleStatsEntry 45 }

affirmedServicesNatServiceNatNodeLevelModuleStatsFilterAdfPacketAccepted OBJECT-TYPE
    SYNTAX      ConfdString
    MAX-ACCESS  read-only
    STATUS      current
    DESCRIPTION "Nat adf filter packet accepted count"
    ::= { affirmedServicesNatServiceNatNodeLevelModuleStatsEntry 46 }

affirmedServicesNatServiceNatNodeLevelModuleStatsFilterAdfPacketRejected OBJECT-TYPE
    SYNTAX      ConfdString
    MAX-ACCESS  read-only
    STATUS      current
    DESCRIPTION "Nat adf filter packet rejected count"
    ::= { affirmedServicesNatServiceNatNodeLevelModuleStatsEntry 47 }

affirmedServicesNatServiceNatNodeLevelModuleStatsFilterApdfPacketAccepted OBJECT-TYPE
    SYNTAX      ConfdString
    MAX-ACCESS  read-only
    STATUS      current
    DESCRIPTION "Nat apdf filter packet accepted count"
    ::= { affirmedServicesNatServiceNatNodeLevelModuleStatsEntry 48 }

affirmedServicesNatServiceNatNodeLevelModuleStatsFilterApdfPacketRejected OBJECT-TYPE
    SYNTAX      ConfdString
    MAX-ACCESS  read-only
    STATUS      current
    DESCRIPTION "Nat apdf filter packet rejected count"
    ::= { affirmedServicesNatServiceNatNodeLevelModuleStatsEntry 49 }

affirmedServicesNatServiceNatNodeLevelModuleStatsFilterEifPacketAccepted OBJECT-TYPE
    SYNTAX      ConfdString
    MAX-ACCESS  read-only
    STATUS      current
    DESCRIPTION "Nat eif filter packet accepted count"
    ::= { affirmedServicesNatServiceNatNodeLevelModuleStatsEntry 50 }

affirmedServicesNatServiceNatNodeLevelModuleStatsPacketTranslated OBJECT-TYPE
    SYNTAX      ConfdString
    MAX-ACCESS  read-only
    STATUS      current
    DESCRIPTION "Number of Packets successfully translated"
    ::= { affirmedServicesNatServiceNatNodeLevelModuleStatsEntry 51 }

affirmedServicesNatServiceNatNodeLevelModuleStatsPacketDropped OBJECT-TYPE
    SYNTAX      ConfdString
    MAX-ACCESS  read-only
    STATUS      current
    DESCRIPTION "Number of Packets dropped during translation"
    ::= { affirmedServicesNatServiceNatNodeLevelModuleStatsEntry 52 }

affirmedServicesNatServiceNatNodeLevelModuleStatsPktDropUnknownProtocolFailure OBJECT-TYPE
    SYNTAX      ConfdString
    MAX-ACCESS  read-only
    STATUS      current
    DESCRIPTION "Number of packets dropped due to unknown protocol in the IP header"
    ::= { affirmedServicesNatServiceNatNodeLevelModuleStatsEntry 53 }

affirmedServicesNatServiceNatNodeLevelModuleStatsPktDropIcmpUnknownType OBJECT-TYPE
    SYNTAX      ConfdString
    MAX-ACCESS  read-only
    STATUS      current
    DESCRIPTION "Number of packets dropped due to unknown ICMP type"
    ::= { affirmedServicesNatServiceNatNodeLevelModuleStatsEntry 54 }

affirmedServicesNatServiceNatNodeLevelModuleStatsPktDropReverseLookupFailure OBJECT-TYPE
    SYNTAX      ConfdString
    MAX-ACCESS  read-only
    STATUS      current
    DESCRIPTION "Number of downlink packets dropped due to reverse lookup failure"
    ::= { affirmedServicesNatServiceNatNodeLevelModuleStatsEntry 55 }

affirmedServicesNatServiceNatNodeLevelModuleStatsPktDropReverseSessionIdMismatch OBJECT-TYPE
    SYNTAX      ConfdString
    MAX-ACCESS  read-only
    STATUS      current
    DESCRIPTION "Number of downlink packets dropped due to session id mismatch for nat flow"
    ::= { affirmedServicesNatServiceNatNodeLevelModuleStatsEntry 56 }

affirmedServicesNatServiceNatNodeLevelModuleStatsPktDropReverseUnknownProtocolFailure OBJECT-TYPE
    SYNTAX      ConfdString
    MAX-ACCESS  read-only
    STATUS      current
    DESCRIPTION "Number of downlink packets dropped due to  unknown protocol"
    ::= { affirmedServicesNatServiceNatNodeLevelModuleStatsEntry 57 }

affirmedServicesNatServiceNatNodeLevelModuleStatsPktDropReversev4tov6ConversionFailure OBJECT-TYPE
    SYNTAX      ConfdString
    MAX-ACCESS  read-only
    STATUS      current
    DESCRIPTION "Number of downlink packets dropped due to v4 to v6 conversion failure for NAT64"
    ::= { affirmedServicesNatServiceNatNodeLevelModuleStatsEntry 58 }

affirmedServicesNatServiceNatNodeLevelModuleStatsNatAlgUplinkPackets OBJECT-TYPE
    SYNTAX      ConfdString
    MAX-ACCESS  read-only
    STATUS      current
    DESCRIPTION "Alg none(nat only) uplink packets count"
    ::= { affirmedServicesNatServiceNatNodeLevelModuleStatsEntry 59 }

affirmedServicesNatServiceNatNodeLevelModuleStatsNatAlgDownlinkPackets OBJECT-TYPE
    SYNTAX      ConfdString
    MAX-ACCESS  read-only
    STATUS      current
    DESCRIPTION "Alg none(nat only) downlink packets count"
    ::= { affirmedServicesNatServiceNatNodeLevelModuleStatsEntry 60 }

affirmedServicesNatServiceNatNodeLevelModuleStatsPassAlgUplinkPackets OBJECT-TYPE
    SYNTAX      ConfdString
    MAX-ACCESS  read-only
    STATUS      current
    DESCRIPTION "Alg none(nat only) pass uplink packets count"
    ::= { affirmedServicesNatServiceNatNodeLevelModuleStatsEntry 61 }

affirmedServicesNatServiceNatNodeLevelModuleStatsPassAlgDownlinkPackets OBJECT-TYPE
    SYNTAX      ConfdString
    MAX-ACCESS  read-only
    STATUS      current
    DESCRIPTION "Alg none(nat only) pass downlink packets count"
    ::= { affirmedServicesNatServiceNatNodeLevelModuleStatsEntry 62 }

affirmedServicesNatServiceNatNodeLevelModuleStatsSipAlgUplinkPackets OBJECT-TYPE
    SYNTAX      ConfdString
    MAX-ACCESS  read-only
    STATUS      current
    DESCRIPTION "Alg sip uplink packets count"
    ::= { affirmedServicesNatServiceNatNodeLevelModuleStatsEntry 63 }

affirmedServicesNatServiceNatNodeLevelModuleStatsSipAlgDownlinkPackets OBJECT-TYPE
    SYNTAX      ConfdString
    MAX-ACCESS  read-only
    STATUS      current
    DESCRIPTION "Alg sip downlink packets count"
    ::= { affirmedServicesNatServiceNatNodeLevelModuleStatsEntry 64 }

affirmedServicesNatServiceNatNodeLevelModuleStatsSipPassAlgUplinkPackets OBJECT-TYPE
    SYNTAX      ConfdString
    MAX-ACCESS  read-only
    STATUS      current
    DESCRIPTION "Alg sip pass uplink packets count"
    ::= { affirmedServicesNatServiceNatNodeLevelModuleStatsEntry 65 }

affirmedServicesNatServiceNatNodeLevelModuleStatsSipPassAlgDownlinkPackets OBJECT-TYPE
    SYNTAX      ConfdString
    MAX-ACCESS  read-only
    STATUS      current
    DESCRIPTION "Alg sip pass downlink packets count"
    ::= { affirmedServicesNatServiceNatNodeLevelModuleStatsEntry 66 }

affirmedServicesNatServiceNatNodeLevelModuleStatsRtspAlgUplinkPackets OBJECT-TYPE
    SYNTAX      ConfdString
    MAX-ACCESS  read-only
    STATUS      current
    DESCRIPTION "Alg rtsp uplink packets count"
    ::= { affirmedServicesNatServiceNatNodeLevelModuleStatsEntry 67 }

affirmedServicesNatServiceNatNodeLevelModuleStatsRtspAlgDownlinkPackets OBJECT-TYPE
    SYNTAX      ConfdString
    MAX-ACCESS  read-only
    STATUS      current
    DESCRIPTION "Alg rtsp downlink packets count"
    ::= { affirmedServicesNatServiceNatNodeLevelModuleStatsEntry 68 }

affirmedServicesNatServiceNatNodeLevelModuleStatsRtspPassAlgUplinkPackets OBJECT-TYPE
    SYNTAX      ConfdString
    MAX-ACCESS  read-only
    STATUS      current
    DESCRIPTION "Alg rtsp pass uplink packets count"
    ::= { affirmedServicesNatServiceNatNodeLevelModuleStatsEntry 69 }

affirmedServicesNatServiceNatNodeLevelModuleStatsRtspPassAlgDownlinkPackets OBJECT-TYPE
    SYNTAX      ConfdString
    MAX-ACCESS  read-only
    STATUS      current
    DESCRIPTION "Alg rtsp pass downlink packets count"
    ::= { affirmedServicesNatServiceNatNodeLevelModuleStatsEntry 70 }

affirmedServicesNatServiceNatNodeLevelModuleStatsFtpAlgDownlinkPackets OBJECT-TYPE
    SYNTAX      ConfdString
    MAX-ACCESS  read-only
    STATUS      current
    DESCRIPTION "Alg ftp downlink packets count"
    ::= { affirmedServicesNatServiceNatNodeLevelModuleStatsEntry 71 }

affirmedServicesNatServiceNatNodeLevelModuleStatsFtpAlgUplinkPackets OBJECT-TYPE
    SYNTAX      ConfdString
    MAX-ACCESS  read-only
    STATUS      current
    DESCRIPTION "Alg ftp uplink packets count"
    ::= { affirmedServicesNatServiceNatNodeLevelModuleStatsEntry 72 }

affirmedServicesNatServiceNatNodeLevelModuleStatsFtpPassAlgDownlinkPackets OBJECT-TYPE
    SYNTAX      ConfdString
    MAX-ACCESS  read-only
    STATUS      current
    DESCRIPTION "Alg ftp pass downlink packets count"
    ::= { affirmedServicesNatServiceNatNodeLevelModuleStatsEntry 73 }

affirmedServicesNatServiceNatNodeLevelModuleStatsFtpPassAlgUplinkPackets OBJECT-TYPE
    SYNTAX      ConfdString
    MAX-ACCESS  read-only
    STATUS      current
    DESCRIPTION "Alg ftp pass uplink packets count"
    ::= { affirmedServicesNatServiceNatNodeLevelModuleStatsEntry 74 }

affirmedServicesNatServiceNatNodeLevelModuleStatsTftpAlgUplinkPackets OBJECT-TYPE
    SYNTAX      ConfdString
    MAX-ACCESS  read-only
    STATUS      current
    DESCRIPTION "Alg tftp uplink packets count"
    ::= { affirmedServicesNatServiceNatNodeLevelModuleStatsEntry 75 }

affirmedServicesNatServiceNatNodeLevelModuleStatsTftpAlgDownlinkPackets OBJECT-TYPE
    SYNTAX      ConfdString
    MAX-ACCESS  read-only
    STATUS      current
    DESCRIPTION "Alg tftp downlink packets count"
    ::= { affirmedServicesNatServiceNatNodeLevelModuleStatsEntry 76 }

affirmedServicesNatServiceNatNodeLevelModuleStatsTftpPassAlgUplinkPackets OBJECT-TYPE
    SYNTAX      ConfdString
    MAX-ACCESS  read-only
    STATUS      current
    DESCRIPTION "Alg tftp pass uplink packets count"
    ::= { affirmedServicesNatServiceNatNodeLevelModuleStatsEntry 77 }

affirmedServicesNatServiceNatNodeLevelModuleStatsTftpPassAlgDownlinkPackets OBJECT-TYPE
    SYNTAX      ConfdString
    MAX-ACCESS  read-only
    STATUS      current
    DESCRIPTION "Alg tftp pass downlink packets count"
    ::= { affirmedServicesNatServiceNatNodeLevelModuleStatsEntry 78 }

affirmedServicesNatServiceNatNodeLevelModuleStatsConnectionCreateIgnoredNonTcpSyn OBJECT-TYPE
    SYNTAX      ConfdString
    MAX-ACCESS  read-only
    STATUS      current
    DESCRIPTION "Number of connection creation ignored as it was non tcp syn"
    ::= { affirmedServicesNatServiceNatNodeLevelModuleStatsEntry 79 }

affirmedServicesNatServiceNatNodeLevelModuleStatsConnectionCreateEsp OBJECT-TYPE
    SYNTAX      ConfdString
    MAX-ACCESS  read-only
    STATUS      current
    DESCRIPTION "Number of esp connections created"
    ::= { affirmedServicesNatServiceNatNodeLevelModuleStatsEntry 80 }

affirmedServicesNatServiceNatNodeLevelModuleStatsConnectionDeleteEsp OBJECT-TYPE
    SYNTAX      ConfdString
    MAX-ACCESS  read-only
    STATUS      current
    DESCRIPTION "Number of esp connections deleted"
    ::= { affirmedServicesNatServiceNatNodeLevelModuleStatsEntry 81 }

affirmedServicesNatServiceNatNodeLevelModuleStatsAllocFailureNPTv6 OBJECT-TYPE
    SYNTAX      ConfdString
    MAX-ACCESS  read-only
    STATUS      current
    DESCRIPTION "Number of sessions failed for NPTv6"
    ::= { affirmedServicesNatServiceNatNodeLevelModuleStatsEntry 82 }

affirmedServicesNatServiceNatNodeLevelModuleStatsIpsecNattAssistAlgUplinkPackets OBJECT-TYPE
    SYNTAX      ConfdString
    MAX-ACCESS  read-only
    STATUS      current
    DESCRIPTION "Alg ipsec natt assist uplink packets count"
    ::= { affirmedServicesNatServiceNatNodeLevelModuleStatsEntry 83 }

affirmedServicesNatServiceNatNodeLevelModuleStatsIpsecNattAssistAlgDownlinkPackets OBJECT-TYPE
    SYNTAX      ConfdString
    MAX-ACCESS  read-only
    STATUS      current
    DESCRIPTION "Alg ipsec natt assist downlink packets count"
    ::= { affirmedServicesNatServiceNatNodeLevelModuleStatsEntry 84 }

affirmedServicesNatServiceNatNodeLevelModuleStatsIpsecNattAssistPassAlgUplinkPackets OBJECT-TYPE
    SYNTAX      ConfdString
    MAX-ACCESS  read-only
    STATUS      current
    DESCRIPTION "Alg ipsec natt assist pass uplink packets count"
    ::= { affirmedServicesNatServiceNatNodeLevelModuleStatsEntry 85 }

affirmedServicesNatServiceNatNodeLevelModuleStatsIpsecNattAssistPassAlgDownlinkPackets OBJECT-TYPE
    SYNTAX      ConfdString
    MAX-ACCESS  read-only
    STATUS      current
    DESCRIPTION "Alg ipsec natt assist pass downlink packets count"
    ::= { affirmedServicesNatServiceNatNodeLevelModuleStatsEntry 86 }

affirmedServicesNatServiceNatNodeLevelModuleStatsConnectionCreateFailureConnTracker OBJECT-TYPE
    SYNTAX      ConfdString
    MAX-ACCESS  read-only
    STATUS      current
    DESCRIPTION "Number of connection create failures due to Connection tracker"
    ::= { affirmedServicesNatServiceNatNodeLevelModuleStatsEntry 87 }

affirmedServicesNatServiceNatNodeLevelModuleStatsNumRejectFlowStateTrackingMisconfig OBJECT-TYPE
    SYNTAX      ConfdString
    MAX-ACCESS  read-only
    STATUS      current
    DESCRIPTION "Number of connections rejected due to missing flow-idle-timeout-profile/flow-state-tracking-profile"
    ::= { affirmedServicesNatServiceNatNodeLevelModuleStatsEntry 88 }

affirmedServicesNatServiceNatNodeLevelModuleStatsPptpAlgDownlinkPackets OBJECT-TYPE
    SYNTAX      ConfdString
    MAX-ACCESS  read-only
    STATUS      current
    DESCRIPTION "Alg pptp downlink packets count"
    ::= { affirmedServicesNatServiceNatNodeLevelModuleStatsEntry 89 }

affirmedServicesNatServiceNatNodeLevelModuleStatsPptpAlgUplinkPackets OBJECT-TYPE
    SYNTAX      ConfdString
    MAX-ACCESS  read-only
    STATUS      current
    DESCRIPTION "Alg pptp uplink packets count"
    ::= { affirmedServicesNatServiceNatNodeLevelModuleStatsEntry 90 }

affirmedServicesNatServiceNatNodeLevelModuleStatsPptpPassAlgDownlinkPackets OBJECT-TYPE
    SYNTAX      ConfdString
    MAX-ACCESS  read-only
    STATUS      current
    DESCRIPTION "Alg pptp pass downlink packets count"
    ::= { affirmedServicesNatServiceNatNodeLevelModuleStatsEntry 91 }

affirmedServicesNatServiceNatNodeLevelModuleStatsPptpPassAlgUplinkPackets OBJECT-TYPE
    SYNTAX      ConfdString
    MAX-ACCESS  read-only
    STATUS      current
    DESCRIPTION "Alg pptp pass uplink packets count"
    ::= { affirmedServicesNatServiceNatNodeLevelModuleStatsEntry 92 }

affirmedServicesNatServiceNatNodeLevelModuleStatsPktDropConnTracker OBJECT-TYPE
    SYNTAX      ConfdString
    MAX-ACCESS  read-only
    STATUS      current
    DESCRIPTION "Number of packets dropped by Connection tracker(Stateful Firewall)"
    ::= { affirmedServicesNatServiceNatNodeLevelModuleStatsEntry 93 }

affirmedServicesNatServiceNatNodeLevelAlgStatsTable OBJECT-TYPE
    SYNTAX      SEQUENCE OF AffirmedServicesNatServiceNatNodeLevelAlgStatsEntry
    MAX-ACCESS  not-accessible
    STATUS      current
    DESCRIPTION ""
    ::= { affirmedServicesNatServiceNatNodeLevel 2 }

affirmedServicesNatServiceNatNodeLevelAlgStatsEntry OBJECT-TYPE
    SYNTAX      AffirmedServicesNatServiceNatNodeLevelAlgStatsEntry
    MAX-ACCESS  not-accessible
    STATUS      current
    DESCRIPTION ""
    INDEX { affirmedServicesNatServiceNatNodeLevelAlgStatsChassis, affirmedServicesNatServiceNatNodeLevelAlgStatsSlot, affirmedServicesNatServiceNatNodeLevelAlgStatsAlgType }
        ::= { affirmedServicesNatServiceNatNodeLevelAlgStatsTable 1 }

AffirmedServicesNatServiceNatNodeLevelAlgStatsEntry ::=
    SEQUENCE {
        affirmedServicesNatServiceNatNodeLevelAlgStatsChassis Unsigned32,
        affirmedServicesNatServiceNatNodeLevelAlgStatsSlot Unsigned32,
        affirmedServicesNatServiceNatNodeLevelAlgStatsAlgType String,
        affirmedServicesNatServiceNatNodeLevelAlgStatsPinholeUplinkAudio ConfdString,
        affirmedServicesNatServiceNatNodeLevelAlgStatsPinholeUplinkVideo ConfdString,
        affirmedServicesNatServiceNatNodeLevelAlgStatsPinholeDownlinkAudio ConfdString,
        affirmedServicesNatServiceNatNodeLevelAlgStatsPinholeDownlinkVideo ConfdString,
        affirmedServicesNatServiceNatNodeLevelAlgStatsPinholeDownlinkReg ConfdString,
        affirmedServicesNatServiceNatNodeLevelAlgStatsSipMangledUpstream ConfdString,
        affirmedServicesNatServiceNatNodeLevelAlgStatsSipMangledDownstream ConfdString,
        affirmedServicesNatServiceNatNodeLevelAlgStatsSipRegister ConfdString,
        affirmedServicesNatServiceNatNodeLevelAlgStatsSipInviteUpstream ConfdString,
        affirmedServicesNatServiceNatNodeLevelAlgStatsSipInviteDownstream ConfdString,
        affirmedServicesNatServiceNatNodeLevelAlgStatsSipCancelUpstream ConfdString,
        affirmedServicesNatServiceNatNodeLevelAlgStatsSipCancelDownstream ConfdString,
        affirmedServicesNatServiceNatNodeLevelAlgStatsSipByeDownstream ConfdString,
        affirmedServicesNatServiceNatNodeLevelAlgStatsSipByeUpstream ConfdString,
        affirmedServicesNatServiceNatNodeLevelAlgStatsPinholeUplinkErrorAudio ConfdString,
        affirmedServicesNatServiceNatNodeLevelAlgStatsPinholeUplinkErrorVideo ConfdString,
        affirmedServicesNatServiceNatNodeLevelAlgStatsPinholeDownlinkErrorAudio ConfdString,
        affirmedServicesNatServiceNatNodeLevelAlgStatsPinholeDownlinkErrorVideo ConfdString,
        affirmedServicesNatServiceNatNodeLevelAlgStatsPinholeDownlinkErrorReg ConfdString,
        affirmedServicesNatServiceNatNodeLevelAlgStatsSipErrorParse ConfdString,
        affirmedServicesNatServiceNatNodeLevelAlgStatsSipErrorReplaceContact ConfdString,
        affirmedServicesNatServiceNatNodeLevelAlgStatsSipErrorInviteNoBinding ConfdString,
        affirmedServicesNatServiceNatNodeLevelAlgStatsSipErrorByeNoBinding ConfdString,
        affirmedServicesNatServiceNatNodeLevelAlgStatsSipErrorAckNoBinding ConfdString,
        affirmedServicesNatServiceNatNodeLevelAlgStatsSipErrorMangle ConfdString,
        affirmedServicesNatServiceNatNodeLevelAlgStatsSipErrorContactAndUeAddrMismatch ConfdString,
        affirmedServicesNatServiceNatNodeLevelAlgStatsConnCreateSuccess ConfdString,
        affirmedServicesNatServiceNatNodeLevelAlgStatsConnCreateFailure ConfdString,
        affirmedServicesNatServiceNatNodeLevelAlgStatsPhCreateSuccess ConfdString,
        affirmedServicesNatServiceNatNodeLevelAlgStatsPhCreateFailure ConfdString,
        affirmedServicesNatServiceNatNodeLevelAlgStatsGoodBlkSizeValueInReq ConfdString,
        affirmedServicesNatServiceNatNodeLevelAlgStatsBadBlkSizeValueInReq ConfdString,
        affirmedServicesNatServiceNatNodeLevelAlgStatsBlkSizeValueMiss ConfdString,
        affirmedServicesNatServiceNatNodeLevelAlgStatsBlkSizeParamNameMiss ConfdString,
        affirmedServicesNatServiceNatNodeLevelAlgStatsBlkSizeFormatErr ConfdString,
        affirmedServicesNatServiceNatNodeLevelAlgStatsBadRelativePathName ConfdString,
        affirmedServicesNatServiceNatNodeLevelAlgStatsPass2Err ConfdString,
        affirmedServicesNatServiceNatNodeLevelAlgStatsInvalidFirstMsg ConfdString,
        affirmedServicesNatServiceNatNodeLevelAlgStatsInvalidSecondMsg ConfdString,
        affirmedServicesNatServiceNatNodeLevelAlgStatsDataMsgTooBigErr ConfdString,
        affirmedServicesNatServiceNatNodeLevelAlgStatsIgnoreTftpReqClient ConfdString,
        affirmedServicesNatServiceNatNodeLevelAlgStatsBlockedAccessServSysFile ConfdString,
        affirmedServicesNatServiceNatNodeLevelAlgStatsBadProtocol ConfdString,
        affirmedServicesNatServiceNatNodeLevelAlgStatsPortCmdCnt ConfdString,
        affirmedServicesNatServiceNatNodeLevelAlgStatsEprtCmdCnt ConfdString,
        affirmedServicesNatServiceNatNodeLevelAlgStatsPasvCmdCount ConfdString,
        affirmedServicesNatServiceNatNodeLevelAlgStatsEpsvCmdCnt ConfdString,
        affirmedServicesNatServiceNatNodeLevelAlgStatsInvalidPortCmdCnt ConfdString,
        affirmedServicesNatServiceNatNodeLevelAlgStatsInvalidPasvRspCnt ConfdString,
        affirmedServicesNatServiceNatNodeLevelAlgStatsActModeWrongAddrCnt ConfdString,
        affirmedServicesNatServiceNatNodeLevelAlgStatsPsvModeWrongAddrCnt ConfdString,
        affirmedServicesNatServiceNatNodeLevelAlgStatsUplinkPhConnCnt ConfdString,
        affirmedServicesNatServiceNatNodeLevelAlgStatsUplinkPhConnErrCnt ConfdString,
        affirmedServicesNatServiceNatNodeLevelAlgStatsDnlinkPhConnCnt ConfdString,
        affirmedServicesNatServiceNatNodeLevelAlgStatsDnlinkPhConnErrCnt ConfdString,
        affirmedServicesNatServiceNatNodeLevelAlgStatsFtpMultilineRspCnt ConfdString,
        affirmedServicesNatServiceNatNodeLevelAlgStatsFtpInvalidArgErrCnt ConfdString,
        affirmedServicesNatServiceNatNodeLevelAlgStatsFtpOpNotAllowedErrCnt ConfdString,
        affirmedServicesNatServiceNatNodeLevelAlgStatsFtpDataPortFailedErrCnt ConfdString,
        affirmedServicesNatServiceNatNodeLevelAlgStatsFtpUnsupportedNwProtocolErrCnt ConfdString,
        affirmedServicesNatServiceNatNodeLevelAlgStatsFtpCmdNotImplementedErrCnt ConfdString,
        affirmedServicesNatServiceNatNodeLevelAlgStatsFtpFailedDataConnErrCnt ConfdString,
        affirmedServicesNatServiceNatNodeLevelAlgStatsPatchPort1Cnt ConfdString,
        affirmedServicesNatServiceNatNodeLevelAlgStatsPatchPort2Cnt ConfdString,
        affirmedServicesNatServiceNatNodeLevelAlgStatsPatchPort1Err ConfdString,
        affirmedServicesNatServiceNatNodeLevelAlgStatsPatchPort2Err ConfdString,
        affirmedServicesNatServiceNatNodeLevelAlgStatsPinholePortCnt ConfdString,
        affirmedServicesNatServiceNatNodeLevelAlgStatsPinholePortErr ConfdString,
        affirmedServicesNatServiceNatNodeLevelAlgStatsInvalidClientPorts ConfdString,
        affirmedServicesNatServiceNatNodeLevelAlgStatsInvalidServerPorts ConfdString,
        affirmedServicesNatServiceNatNodeLevelAlgStatsInvalidTransaction ConfdString,
        affirmedServicesNatServiceNatNodeLevelAlgStatsRevPort1MappingFailed ConfdString,
        affirmedServicesNatServiceNatNodeLevelAlgStatsRevPort2MappingFailed ConfdString,
        affirmedServicesNatServiceNatNodeLevelAlgStatsInvalidUplinkInterleavedModeChannels ConfdString,
        affirmedServicesNatServiceNatNodeLevelAlgStatsInvalidDownlinklinkInterleavedModeChannels ConfdString,
        affirmedServicesNatServiceNatNodeLevelAlgStatsUplinkVersionNotSupported ConfdString,
        affirmedServicesNatServiceNatNodeLevelAlgStatsDownlinkVersionNotSupported ConfdString,
        affirmedServicesNatServiceNatNodeLevelAlgStatsUplinkDataPacketTransferFail ConfdString,
        affirmedServicesNatServiceNatNodeLevelAlgStatsDownlinkDataPacketTransferFail ConfdString,
        affirmedServicesNatServiceNatNodeLevelAlgStatsUplinkInterleaveModeRequest ConfdString,
        affirmedServicesNatServiceNatNodeLevelAlgStatsDownlinkInterleaveModeRequest ConfdString,
        affirmedServicesNatServiceNatNodeLevelAlgStatsUplinkOptionsRequest ConfdString,
        affirmedServicesNatServiceNatNodeLevelAlgStatsUplinkDescribeRequest ConfdString,
        affirmedServicesNatServiceNatNodeLevelAlgStatsUplinkSetupRequest ConfdString,
        affirmedServicesNatServiceNatNodeLevelAlgStatsUplinkPlayRequest ConfdString,
        affirmedServicesNatServiceNatNodeLevelAlgStatsUplinkTeardownRequest ConfdString,
        affirmedServicesNatServiceNatNodeLevelAlgStatsDownlinkOptionsResponse ConfdString,
        affirmedServicesNatServiceNatNodeLevelAlgStatsDownlinkDescribeResponse ConfdString,
        affirmedServicesNatServiceNatNodeLevelAlgStatsDownlinkSetupResponse ConfdString,
        affirmedServicesNatServiceNatNodeLevelAlgStatsDownlinkTeardownResponse ConfdString,
        affirmedServicesNatServiceNatNodeLevelAlgStatsSipUplinkUnsupportedMethod ConfdString,
        affirmedServicesNatServiceNatNodeLevelAlgStatsSipDownlinkUnsupportedMethod ConfdString
    }

affirmedServicesNatServiceNatNodeLevelAlgStatsChassis OBJECT-TYPE
    SYNTAX      Unsigned32
    MAX-ACCESS  not-accessible
    STATUS      current
    DESCRIPTION ""
    ::= { affirmedServicesNatServiceNatNodeLevelAlgStatsEntry 1 }

affirmedServicesNatServiceNatNodeLevelAlgStatsSlot OBJECT-TYPE
    SYNTAX      Unsigned32
    MAX-ACCESS  not-accessible
    STATUS      current
    DESCRIPTION ""
    ::= { affirmedServicesNatServiceNatNodeLevelAlgStatsEntry 2 }

affirmedServicesNatServiceNatNodeLevelAlgStatsAlgType OBJECT-TYPE
    SYNTAX      String
    MAX-ACCESS  not-accessible
    STATUS      current
    DESCRIPTION ""
    ::= { affirmedServicesNatServiceNatNodeLevelAlgStatsEntry 3 }

affirmedServicesNatServiceNatNodeLevelAlgStatsPinholeUplinkAudio OBJECT-TYPE
    SYNTAX      ConfdString
    MAX-ACCESS  read-only
    STATUS      current
    DESCRIPTION "Uplink audio pinhole success"
    ::= { affirmedServicesNatServiceNatNodeLevelAlgStatsEntry 4 }

affirmedServicesNatServiceNatNodeLevelAlgStatsPinholeUplinkVideo OBJECT-TYPE
    SYNTAX      ConfdString
    MAX-ACCESS  read-only
    STATUS      current
    DESCRIPTION "Uplink video pinhole success"
    ::= { affirmedServicesNatServiceNatNodeLevelAlgStatsEntry 5 }

affirmedServicesNatServiceNatNodeLevelAlgStatsPinholeDownlinkAudio OBJECT-TYPE
    SYNTAX      ConfdString
    MAX-ACCESS  read-only
    STATUS      current
    DESCRIPTION "Downlink audio pinhole success"
    ::= { affirmedServicesNatServiceNatNodeLevelAlgStatsEntry 6 }

affirmedServicesNatServiceNatNodeLevelAlgStatsPinholeDownlinkVideo OBJECT-TYPE
    SYNTAX      ConfdString
    MAX-ACCESS  read-only
    STATUS      current
    DESCRIPTION "Downlink video pinhole success"
    ::= { affirmedServicesNatServiceNatNodeLevelAlgStatsEntry 7 }

affirmedServicesNatServiceNatNodeLevelAlgStatsPinholeDownlinkReg OBJECT-TYPE
    SYNTAX      ConfdString
    MAX-ACCESS  read-only
    STATUS      current
    DESCRIPTION "Uplink register pinhole success (TCP)"
    ::= { affirmedServicesNatServiceNatNodeLevelAlgStatsEntry 8 }

affirmedServicesNatServiceNatNodeLevelAlgStatsSipMangledUpstream OBJECT-TYPE
    SYNTAX      ConfdString
    MAX-ACCESS  read-only
    STATUS      current
    DESCRIPTION "SIP mangled Upstream"
    ::= { affirmedServicesNatServiceNatNodeLevelAlgStatsEntry 9 }

affirmedServicesNatServiceNatNodeLevelAlgStatsSipMangledDownstream OBJECT-TYPE
    SYNTAX      ConfdString
    MAX-ACCESS  read-only
    STATUS      current
    DESCRIPTION "SIP mangled Downstream"
    ::= { affirmedServicesNatServiceNatNodeLevelAlgStatsEntry 10 }

affirmedServicesNatServiceNatNodeLevelAlgStatsSipRegister OBJECT-TYPE
    SYNTAX      ConfdString
    MAX-ACCESS  read-only
    STATUS      current
    DESCRIPTION "SIP register upstream"
    ::= { affirmedServicesNatServiceNatNodeLevelAlgStatsEntry 11 }

affirmedServicesNatServiceNatNodeLevelAlgStatsSipInviteUpstream OBJECT-TYPE
    SYNTAX      ConfdString
    MAX-ACCESS  read-only
    STATUS      current
    DESCRIPTION "SIP INVITE Upstream"
    ::= { affirmedServicesNatServiceNatNodeLevelAlgStatsEntry 12 }

affirmedServicesNatServiceNatNodeLevelAlgStatsSipInviteDownstream OBJECT-TYPE
    SYNTAX      ConfdString
    MAX-ACCESS  read-only
    STATUS      current
    DESCRIPTION "SIP INVITE Downstream"
    ::= { affirmedServicesNatServiceNatNodeLevelAlgStatsEntry 13 }

affirmedServicesNatServiceNatNodeLevelAlgStatsSipCancelUpstream OBJECT-TYPE
    SYNTAX      ConfdString
    MAX-ACCESS  read-only
    STATUS      current
    DESCRIPTION "SIP CANCEL Request/Response from Upstream"
    ::= { affirmedServicesNatServiceNatNodeLevelAlgStatsEntry 14 }

affirmedServicesNatServiceNatNodeLevelAlgStatsSipCancelDownstream OBJECT-TYPE
    SYNTAX      ConfdString
    MAX-ACCESS  read-only
    STATUS      current
    DESCRIPTION "SIP CANCEL Request/Response from Downstream"
    ::= { affirmedServicesNatServiceNatNodeLevelAlgStatsEntry 15 }

affirmedServicesNatServiceNatNodeLevelAlgStatsSipByeDownstream OBJECT-TYPE
    SYNTAX      ConfdString
    MAX-ACCESS  read-only
    STATUS      current
    DESCRIPTION "SIP BYE Downstream"
    ::= { affirmedServicesNatServiceNatNodeLevelAlgStatsEntry 16 }

affirmedServicesNatServiceNatNodeLevelAlgStatsSipByeUpstream OBJECT-TYPE
    SYNTAX      ConfdString
    MAX-ACCESS  read-only
    STATUS      current
    DESCRIPTION "SIP BYE Upstream"
    ::= { affirmedServicesNatServiceNatNodeLevelAlgStatsEntry 17 }

affirmedServicesNatServiceNatNodeLevelAlgStatsPinholeUplinkErrorAudio OBJECT-TYPE
    SYNTAX      ConfdString
    MAX-ACCESS  read-only
    STATUS      current
    DESCRIPTION "Uplink audio pinhole creation fail"
    ::= { affirmedServicesNatServiceNatNodeLevelAlgStatsEntry 18 }

affirmedServicesNatServiceNatNodeLevelAlgStatsPinholeUplinkErrorVideo OBJECT-TYPE
    SYNTAX      ConfdString
    MAX-ACCESS  read-only
    STATUS      current
    DESCRIPTION "Uplink video pinhole creation fail"
    ::= { affirmedServicesNatServiceNatNodeLevelAlgStatsEntry 19 }

affirmedServicesNatServiceNatNodeLevelAlgStatsPinholeDownlinkErrorAudio OBJECT-TYPE
    SYNTAX      ConfdString
    MAX-ACCESS  read-only
    STATUS      current
    DESCRIPTION "Downlink audio pinhole creation fail"
    ::= { affirmedServicesNatServiceNatNodeLevelAlgStatsEntry 20 }

affirmedServicesNatServiceNatNodeLevelAlgStatsPinholeDownlinkErrorVideo OBJECT-TYPE
    SYNTAX      ConfdString
    MAX-ACCESS  read-only
    STATUS      current
    DESCRIPTION "Downlink video pinhole creation fail"
    ::= { affirmedServicesNatServiceNatNodeLevelAlgStatsEntry 21 }

affirmedServicesNatServiceNatNodeLevelAlgStatsPinholeDownlinkErrorReg OBJECT-TYPE
    SYNTAX      ConfdString
    MAX-ACCESS  read-only
    STATUS      current
    DESCRIPTION "Uplink register pinhole creation fail (TCP)"
    ::= { affirmedServicesNatServiceNatNodeLevelAlgStatsEntry 22 }

affirmedServicesNatServiceNatNodeLevelAlgStatsSipErrorParse OBJECT-TYPE
    SYNTAX      ConfdString
    MAX-ACCESS  read-only
    STATUS      deprecated
    DESCRIPTION "SIP error parse"
    ::= { affirmedServicesNatServiceNatNodeLevelAlgStatsEntry 23 }

affirmedServicesNatServiceNatNodeLevelAlgStatsSipErrorReplaceContact OBJECT-TYPE
    SYNTAX      ConfdString
    MAX-ACCESS  read-only
    STATUS      current
    DESCRIPTION "Header replacement error"
    ::= { affirmedServicesNatServiceNatNodeLevelAlgStatsEntry 24 }

affirmedServicesNatServiceNatNodeLevelAlgStatsSipErrorInviteNoBinding OBJECT-TYPE
    SYNTAX      ConfdString
    MAX-ACCESS  read-only
    STATUS      current
    DESCRIPTION "Binding (call id) does not exist for INVITE"
    ::= { affirmedServicesNatServiceNatNodeLevelAlgStatsEntry 25 }

affirmedServicesNatServiceNatNodeLevelAlgStatsSipErrorByeNoBinding OBJECT-TYPE
    SYNTAX      ConfdString
    MAX-ACCESS  read-only
    STATUS      current
    DESCRIPTION "Binding (call id) does not exist for BYE"
    ::= { affirmedServicesNatServiceNatNodeLevelAlgStatsEntry 26 }

affirmedServicesNatServiceNatNodeLevelAlgStatsSipErrorAckNoBinding OBJECT-TYPE
    SYNTAX      ConfdString
    MAX-ACCESS  read-only
    STATUS      current
    DESCRIPTION "Binding (call id) does not exist for ACK"
    ::= { affirmedServicesNatServiceNatNodeLevelAlgStatsEntry 27 }

affirmedServicesNatServiceNatNodeLevelAlgStatsSipErrorMangle OBJECT-TYPE
    SYNTAX      ConfdString
    MAX-ACCESS  read-only
    STATUS      current
    DESCRIPTION "SIP error mangle"
    ::= { affirmedServicesNatServiceNatNodeLevelAlgStatsEntry 28 }

affirmedServicesNatServiceNatNodeLevelAlgStatsSipErrorContactAndUeAddrMismatch OBJECT-TYPE
    SYNTAX      ConfdString
    MAX-ACCESS  read-only
    STATUS      current
    DESCRIPTION "UE IP Address mismatch in REGISTER contact header"
    ::= { affirmedServicesNatServiceNatNodeLevelAlgStatsEntry 29 }

affirmedServicesNatServiceNatNodeLevelAlgStatsConnCreateSuccess OBJECT-TYPE
    SYNTAX      ConfdString
    MAX-ACCESS  read-only
    STATUS      current
    DESCRIPTION "Connection creation success"
    ::= { affirmedServicesNatServiceNatNodeLevelAlgStatsEntry 30 }

affirmedServicesNatServiceNatNodeLevelAlgStatsConnCreateFailure OBJECT-TYPE
    SYNTAX      ConfdString
    MAX-ACCESS  read-only
    STATUS      current
    DESCRIPTION "Connection creation failure"
    ::= { affirmedServicesNatServiceNatNodeLevelAlgStatsEntry 31 }

affirmedServicesNatServiceNatNodeLevelAlgStatsPhCreateSuccess OBJECT-TYPE
    SYNTAX      ConfdString
    MAX-ACCESS  read-only
    STATUS      current
    DESCRIPTION "Pinhole creation success"
    ::= { affirmedServicesNatServiceNatNodeLevelAlgStatsEntry 32 }

affirmedServicesNatServiceNatNodeLevelAlgStatsPhCreateFailure OBJECT-TYPE
    SYNTAX      ConfdString
    MAX-ACCESS  read-only
    STATUS      current
    DESCRIPTION "Pinhole creation failure"
    ::= { affirmedServicesNatServiceNatNodeLevelAlgStatsEntry 33 }

affirmedServicesNatServiceNatNodeLevelAlgStatsGoodBlkSizeValueInReq OBJECT-TYPE
    SYNTAX      ConfdString
    MAX-ACCESS  read-only
    STATUS      current
    DESCRIPTION "Good block size in request"
    ::= { affirmedServicesNatServiceNatNodeLevelAlgStatsEntry 34 }

affirmedServicesNatServiceNatNodeLevelAlgStatsBadBlkSizeValueInReq OBJECT-TYPE
    SYNTAX      ConfdString
    MAX-ACCESS  read-only
    STATUS      current
    DESCRIPTION "Invalid block size in request"
    ::= { affirmedServicesNatServiceNatNodeLevelAlgStatsEntry 35 }

affirmedServicesNatServiceNatNodeLevelAlgStatsBlkSizeValueMiss OBJECT-TYPE
    SYNTAX      ConfdString
    MAX-ACCESS  read-only
    STATUS      current
    DESCRIPTION "Block size name present but size missing"
    ::= { affirmedServicesNatServiceNatNodeLevelAlgStatsEntry 36 }

affirmedServicesNatServiceNatNodeLevelAlgStatsBlkSizeParamNameMiss OBJECT-TYPE
    SYNTAX      ConfdString
    MAX-ACCESS  read-only
    STATUS      current
    DESCRIPTION "No room for transfer mode or optional parameters due to lack of space in buffer"
    ::= { affirmedServicesNatServiceNatNodeLevelAlgStatsEntry 37 }

affirmedServicesNatServiceNatNodeLevelAlgStatsBlkSizeFormatErr OBJECT-TYPE
    SYNTAX      ConfdString
    MAX-ACCESS  read-only
    STATUS      current
    DESCRIPTION "Format error in block size value"
    ::= { affirmedServicesNatServiceNatNodeLevelAlgStatsEntry 38 }

affirmedServicesNatServiceNatNodeLevelAlgStatsBadRelativePathName OBJECT-TYPE
    SYNTAX      ConfdString
    MAX-ACCESS  read-only
    STATUS      current
    DESCRIPTION "Access of relative path"
    ::= { affirmedServicesNatServiceNatNodeLevelAlgStatsEntry 39 }

affirmedServicesNatServiceNatNodeLevelAlgStatsPass2Err OBJECT-TYPE
    SYNTAX      ConfdString
    MAX-ACCESS  read-only
    STATUS      current
    DESCRIPTION "Pass 2 error"
    ::= { affirmedServicesNatServiceNatNodeLevelAlgStatsEntry 40 }

affirmedServicesNatServiceNatNodeLevelAlgStatsInvalidFirstMsg OBJECT-TYPE
    SYNTAX      ConfdString
    MAX-ACCESS  read-only
    STATUS      current
    DESCRIPTION "Invalid message type for the start of a transfer sequence"
    ::= { affirmedServicesNatServiceNatNodeLevelAlgStatsEntry 41 }

affirmedServicesNatServiceNatNodeLevelAlgStatsInvalidSecondMsg OBJECT-TYPE
    SYNTAX      ConfdString
    MAX-ACCESS  read-only
    STATUS      current
    DESCRIPTION "Invalid message type(invalid opcode)"
    ::= { affirmedServicesNatServiceNatNodeLevelAlgStatsEntry 42 }

affirmedServicesNatServiceNatNodeLevelAlgStatsDataMsgTooBigErr OBJECT-TYPE
    SYNTAX      ConfdString
    MAX-ACCESS  read-only
    STATUS      current
    DESCRIPTION "Block size is too big"
    ::= { affirmedServicesNatServiceNatNodeLevelAlgStatsEntry 43 }

affirmedServicesNatServiceNatNodeLevelAlgStatsIgnoreTftpReqClient OBJECT-TYPE
    SYNTAX      ConfdString
    MAX-ACCESS  read-only
    STATUS      current
    DESCRIPTION "Invalid TFTP request sent to client"
    ::= { affirmedServicesNatServiceNatNodeLevelAlgStatsEntry 44 }

affirmedServicesNatServiceNatNodeLevelAlgStatsBlockedAccessServSysFile OBJECT-TYPE
    SYNTAX      ConfdString
    MAX-ACCESS  read-only
    STATUS      current
    DESCRIPTION "Accessing of system folders such as /etc on unix/linux and \Windows folder on windows os is not allowed"
    ::= { affirmedServicesNatServiceNatNodeLevelAlgStatsEntry 45 }

affirmedServicesNatServiceNatNodeLevelAlgStatsBadProtocol OBJECT-TYPE
    SYNTAX      ConfdString
    MAX-ACCESS  read-only
    STATUS      current
    DESCRIPTION "Only UDP is allowed, TCP not supported"
    ::= { affirmedServicesNatServiceNatNodeLevelAlgStatsEntry 46 }

affirmedServicesNatServiceNatNodeLevelAlgStatsPortCmdCnt OBJECT-TYPE
    SYNTAX      ConfdString
    MAX-ACCESS  read-only
    STATUS      current
    DESCRIPTION "Total PORT commands"
    ::= { affirmedServicesNatServiceNatNodeLevelAlgStatsEntry 47 }

affirmedServicesNatServiceNatNodeLevelAlgStatsEprtCmdCnt OBJECT-TYPE
    SYNTAX      ConfdString
    MAX-ACCESS  read-only
    STATUS      current
    DESCRIPTION "Total EPRT commands"
    ::= { affirmedServicesNatServiceNatNodeLevelAlgStatsEntry 48 }

affirmedServicesNatServiceNatNodeLevelAlgStatsPasvCmdCount OBJECT-TYPE
    SYNTAX      ConfdString
    MAX-ACCESS  read-only
    STATUS      current
    DESCRIPTION "Total PASV commands"
    ::= { affirmedServicesNatServiceNatNodeLevelAlgStatsEntry 49 }

affirmedServicesNatServiceNatNodeLevelAlgStatsEpsvCmdCnt OBJECT-TYPE
    SYNTAX      ConfdString
    MAX-ACCESS  read-only
    STATUS      current
    DESCRIPTION "Total EPSV commands"
    ::= { affirmedServicesNatServiceNatNodeLevelAlgStatsEntry 50 }

affirmedServicesNatServiceNatNodeLevelAlgStatsInvalidPortCmdCnt OBJECT-TYPE
    SYNTAX      ConfdString
    MAX-ACCESS  read-only
    STATUS      current
    DESCRIPTION "Parameter(s) in PORT command is invalid (Ipv4 only)"
    ::= { affirmedServicesNatServiceNatNodeLevelAlgStatsEntry 51 }

affirmedServicesNatServiceNatNodeLevelAlgStatsInvalidPasvRspCnt OBJECT-TYPE
    SYNTAX      ConfdString
    MAX-ACCESS  read-only
    STATUS      current
    DESCRIPTION "Parameter(s) in PASV command is invalid (Ipv4 only)"
    ::= { affirmedServicesNatServiceNatNodeLevelAlgStatsEntry 52 }

affirmedServicesNatServiceNatNodeLevelAlgStatsActModeWrongAddrCnt OBJECT-TYPE
    SYNTAX      ConfdString
    MAX-ACCESS  read-only
    STATUS      current
    DESCRIPTION "UE IP Address mismatch in port command in active mode"
    ::= { affirmedServicesNatServiceNatNodeLevelAlgStatsEntry 53 }

affirmedServicesNatServiceNatNodeLevelAlgStatsPsvModeWrongAddrCnt OBJECT-TYPE
    SYNTAX      ConfdString
    MAX-ACCESS  read-only
    STATUS      current
    DESCRIPTION "Total wrong address count(Psv mode)"
    ::= { affirmedServicesNatServiceNatNodeLevelAlgStatsEntry 54 }

affirmedServicesNatServiceNatNodeLevelAlgStatsUplinkPhConnCnt OBJECT-TYPE
    SYNTAX      ConfdString
    MAX-ACCESS  read-only
    STATUS      current
    DESCRIPTION "Total uplink pinhole connection count"
    ::= { affirmedServicesNatServiceNatNodeLevelAlgStatsEntry 55 }

affirmedServicesNatServiceNatNodeLevelAlgStatsUplinkPhConnErrCnt OBJECT-TYPE
    SYNTAX      ConfdString
    MAX-ACCESS  read-only
    STATUS      current
    DESCRIPTION "Failed to create pinhole connection for FTP active mode"
    ::= { affirmedServicesNatServiceNatNodeLevelAlgStatsEntry 56 }

affirmedServicesNatServiceNatNodeLevelAlgStatsDnlinkPhConnCnt OBJECT-TYPE
    SYNTAX      ConfdString
    MAX-ACCESS  read-only
    STATUS      current
    DESCRIPTION "Total downlink pinhole connection count"
    ::= { affirmedServicesNatServiceNatNodeLevelAlgStatsEntry 57 }

affirmedServicesNatServiceNatNodeLevelAlgStatsDnlinkPhConnErrCnt OBJECT-TYPE
    SYNTAX      ConfdString
    MAX-ACCESS  read-only
    STATUS      current
    DESCRIPTION "Failed to create pinhole connection for FTP passive mode"
    ::= { affirmedServicesNatServiceNatNodeLevelAlgStatsEntry 58 }

affirmedServicesNatServiceNatNodeLevelAlgStatsFtpMultilineRspCnt OBJECT-TYPE
    SYNTAX      ConfdString
    MAX-ACCESS  read-only
    STATUS      current
    DESCRIPTION "Total multiline FTP responses"
    ::= { affirmedServicesNatServiceNatNodeLevelAlgStatsEntry 59 }

affirmedServicesNatServiceNatNodeLevelAlgStatsFtpInvalidArgErrCnt OBJECT-TYPE
    SYNTAX      ConfdString
    MAX-ACCESS  read-only
    STATUS      current
    DESCRIPTION "Total invalid-argument-error count. Syntax error in arguments passed (501)"
    ::= { affirmedServicesNatServiceNatNodeLevelAlgStatsEntry 60 }

affirmedServicesNatServiceNatNodeLevelAlgStatsFtpOpNotAllowedErrCnt OBJECT-TYPE
    SYNTAX      ConfdString
    MAX-ACCESS  read-only
    STATUS      current
    DESCRIPTION "Operator not allowed error count for PORT/EPRT. PORT/EPRT command with changed ip-address (500)"
    ::= { affirmedServicesNatServiceNatNodeLevelAlgStatsEntry 61 }

affirmedServicesNatServiceNatNodeLevelAlgStatsFtpDataPortFailedErrCnt OBJECT-TYPE
    SYNTAX      ConfdString
    MAX-ACCESS  read-only
    STATUS      current
    DESCRIPTION "Data port failed error count. Pinhole creation failure in active or passive mode or invalid PASV/EPSV response (500)"
    ::= { affirmedServicesNatServiceNatNodeLevelAlgStatsEntry 62 }

affirmedServicesNatServiceNatNodeLevelAlgStatsFtpUnsupportedNwProtocolErrCnt OBJECT-TYPE
    SYNTAX      ConfdString
    MAX-ACCESS  read-only
    STATUS      current
    DESCRIPTION "EPSV command with invalid protocol. Only supported Network protocol with EPSV is IPv6 (522)"
    ::= { affirmedServicesNatServiceNatNodeLevelAlgStatsEntry 63 }

affirmedServicesNatServiceNatNodeLevelAlgStatsFtpCmdNotImplementedErrCnt OBJECT-TYPE
    SYNTAX      ConfdString
    MAX-ACCESS  read-only
    STATUS      current
    DESCRIPTION "Invalid EPSV command (504)"
    ::= { affirmedServicesNatServiceNatNodeLevelAlgStatsEntry 64 }

affirmedServicesNatServiceNatNodeLevelAlgStatsFtpFailedDataConnErrCnt OBJECT-TYPE
    SYNTAX      ConfdString
    MAX-ACCESS  read-only
    STATUS      current
    DESCRIPTION "PASV response with changed ip-address (425)"
    ::= { affirmedServicesNatServiceNatNodeLevelAlgStatsEntry 65 }

affirmedServicesNatServiceNatNodeLevelAlgStatsPatchPort1Cnt OBJECT-TYPE
    SYNTAX      ConfdString
    MAX-ACCESS  read-only
    STATUS      current
    DESCRIPTION "Total server initiated PinHole for audio success"
    ::= { affirmedServicesNatServiceNatNodeLevelAlgStatsEntry 66 }

affirmedServicesNatServiceNatNodeLevelAlgStatsPatchPort2Cnt OBJECT-TYPE
    SYNTAX      ConfdString
    MAX-ACCESS  read-only
    STATUS      current
    DESCRIPTION "Total server initiated PinHole for video success"
    ::= { affirmedServicesNatServiceNatNodeLevelAlgStatsEntry 67 }

affirmedServicesNatServiceNatNodeLevelAlgStatsPatchPort1Err OBJECT-TYPE
    SYNTAX      ConfdString
    MAX-ACCESS  read-only
    STATUS      current
    DESCRIPTION "Total server initiated PinHole creation failure for audio"
    ::= { affirmedServicesNatServiceNatNodeLevelAlgStatsEntry 68 }

affirmedServicesNatServiceNatNodeLevelAlgStatsPatchPort2Err OBJECT-TYPE
    SYNTAX      ConfdString
    MAX-ACCESS  read-only
    STATUS      current
    DESCRIPTION "Total server initiated PinHole creation failure for video"
    ::= { affirmedServicesNatServiceNatNodeLevelAlgStatsEntry 69 }

affirmedServicesNatServiceNatNodeLevelAlgStatsPinholePortCnt OBJECT-TYPE
    SYNTAX      ConfdString
    MAX-ACCESS  read-only
    STATUS      current
    DESCRIPTION "Total client initiated PinHole success"
    ::= { affirmedServicesNatServiceNatNodeLevelAlgStatsEntry 70 }

affirmedServicesNatServiceNatNodeLevelAlgStatsPinholePortErr OBJECT-TYPE
    SYNTAX      ConfdString
    MAX-ACCESS  read-only
    STATUS      current
    DESCRIPTION "Total client initiated PinHole creation failure"
    ::= { affirmedServicesNatServiceNatNodeLevelAlgStatsEntry 71 }

affirmedServicesNatServiceNatNodeLevelAlgStatsInvalidClientPorts OBJECT-TYPE
    SYNTAX      ConfdString
    MAX-ACCESS  read-only
    STATUS      current
    DESCRIPTION "Total invalid client Ports. Either client ports are not valid"
    ::= { affirmedServicesNatServiceNatNodeLevelAlgStatsEntry 72 }

affirmedServicesNatServiceNatNodeLevelAlgStatsInvalidServerPorts OBJECT-TYPE
    SYNTAX      ConfdString
    MAX-ACCESS  read-only
    STATUS      current
    DESCRIPTION "Total invalid server Ports. Either server ports are not valid"
    ::= { affirmedServicesNatServiceNatNodeLevelAlgStatsEntry 73 }

affirmedServicesNatServiceNatNodeLevelAlgStatsInvalidTransaction OBJECT-TYPE
    SYNTAX      ConfdString
    MAX-ACCESS  read-only
    STATUS      current
    DESCRIPTION "Total invalid transaction"
    ::= { affirmedServicesNatServiceNatNodeLevelAlgStatsEntry 74 }

affirmedServicesNatServiceNatNodeLevelAlgStatsRevPort1MappingFailed OBJECT-TYPE
    SYNTAX      ConfdString
    MAX-ACCESS  read-only
    STATUS      current
    DESCRIPTION "Cannot find mapping for client audio/video port1"
    ::= { affirmedServicesNatServiceNatNodeLevelAlgStatsEntry 75 }

affirmedServicesNatServiceNatNodeLevelAlgStatsRevPort2MappingFailed OBJECT-TYPE
    SYNTAX      ConfdString
    MAX-ACCESS  read-only
    STATUS      current
    DESCRIPTION "Cannot find mapping for client audio/video port2"
    ::= { affirmedServicesNatServiceNatNodeLevelAlgStatsEntry 76 }

affirmedServicesNatServiceNatNodeLevelAlgStatsInvalidUplinkInterleavedModeChannels OBJECT-TYPE
    SYNTAX      ConfdString
    MAX-ACCESS  read-only
    STATUS      current
    DESCRIPTION "Invalid parameters in uplink interleaved mode"
    ::= { affirmedServicesNatServiceNatNodeLevelAlgStatsEntry 77 }

affirmedServicesNatServiceNatNodeLevelAlgStatsInvalidDownlinklinkInterleavedModeChannels OBJECT-TYPE
    SYNTAX      ConfdString
    MAX-ACCESS  read-only
    STATUS      current
    DESCRIPTION "Invalid parameters in downlink interleaved mode"
    ::= { affirmedServicesNatServiceNatNodeLevelAlgStatsEntry 78 }

affirmedServicesNatServiceNatNodeLevelAlgStatsUplinkVersionNotSupported OBJECT-TYPE
    SYNTAX      ConfdString
    MAX-ACCESS  read-only
    STATUS      current
    DESCRIPTION "RTSP version not supported for uplink interleave mode packet. Only RTSP/1.0 is supported"
    ::= { affirmedServicesNatServiceNatNodeLevelAlgStatsEntry 79 }

affirmedServicesNatServiceNatNodeLevelAlgStatsDownlinkVersionNotSupported OBJECT-TYPE
    SYNTAX      ConfdString
    MAX-ACCESS  read-only
    STATUS      current
    DESCRIPTION "RTSP version not supported for Downlink interleave mode  packet. Only RTSP/1.0 is supported"
    ::= { affirmedServicesNatServiceNatNodeLevelAlgStatsEntry 80 }

affirmedServicesNatServiceNatNodeLevelAlgStatsUplinkDataPacketTransferFail OBJECT-TYPE
    SYNTAX      ConfdString
    MAX-ACCESS  read-only
    STATUS      current
    DESCRIPTION "Uplink data packet transfer fail in interleave mode. Socket error/socket not connected"
    ::= { affirmedServicesNatServiceNatNodeLevelAlgStatsEntry 81 }

affirmedServicesNatServiceNatNodeLevelAlgStatsDownlinkDataPacketTransferFail OBJECT-TYPE
    SYNTAX      ConfdString
    MAX-ACCESS  read-only
    STATUS      current
    DESCRIPTION "Downlink data packet transfer fail in interleave mode. Socket inactive"
    ::= { affirmedServicesNatServiceNatNodeLevelAlgStatsEntry 82 }

affirmedServicesNatServiceNatNodeLevelAlgStatsUplinkInterleaveModeRequest OBJECT-TYPE
    SYNTAX      ConfdString
    MAX-ACCESS  read-only
    STATUS      current
    DESCRIPTION "Uplink  interleave mode request"
    ::= { affirmedServicesNatServiceNatNodeLevelAlgStatsEntry 83 }

affirmedServicesNatServiceNatNodeLevelAlgStatsDownlinkInterleaveModeRequest OBJECT-TYPE
    SYNTAX      ConfdString
    MAX-ACCESS  read-only
    STATUS      current
    DESCRIPTION "Downlink  interleave mode respone"
    ::= { affirmedServicesNatServiceNatNodeLevelAlgStatsEntry 84 }

affirmedServicesNatServiceNatNodeLevelAlgStatsUplinkOptionsRequest OBJECT-TYPE
    SYNTAX      ConfdString
    MAX-ACCESS  read-only
    STATUS      current
    DESCRIPTION "OPTIONS  request from UE"
    ::= { affirmedServicesNatServiceNatNodeLevelAlgStatsEntry 85 }

affirmedServicesNatServiceNatNodeLevelAlgStatsUplinkDescribeRequest OBJECT-TYPE
    SYNTAX      ConfdString
    MAX-ACCESS  read-only
    STATUS      current
    DESCRIPTION "DESCRIBE  request from UE"
    ::= { affirmedServicesNatServiceNatNodeLevelAlgStatsEntry 86 }

affirmedServicesNatServiceNatNodeLevelAlgStatsUplinkSetupRequest OBJECT-TYPE
    SYNTAX      ConfdString
    MAX-ACCESS  read-only
    STATUS      current
    DESCRIPTION "SETUP request from UE"
    ::= { affirmedServicesNatServiceNatNodeLevelAlgStatsEntry 87 }

affirmedServicesNatServiceNatNodeLevelAlgStatsUplinkPlayRequest OBJECT-TYPE
    SYNTAX      ConfdString
    MAX-ACCESS  read-only
    STATUS      current
    DESCRIPTION "PLAY request from UE"
    ::= { affirmedServicesNatServiceNatNodeLevelAlgStatsEntry 88 }

affirmedServicesNatServiceNatNodeLevelAlgStatsUplinkTeardownRequest OBJECT-TYPE
    SYNTAX      ConfdString
    MAX-ACCESS  read-only
    STATUS      current
    DESCRIPTION "TEARDOWN request from UE"
    ::= { affirmedServicesNatServiceNatNodeLevelAlgStatsEntry 89 }

affirmedServicesNatServiceNatNodeLevelAlgStatsDownlinkOptionsResponse OBJECT-TYPE
    SYNTAX      ConfdString
    MAX-ACCESS  read-only
    STATUS      current
    DESCRIPTION "OPTIONS  response from server"
    ::= { affirmedServicesNatServiceNatNodeLevelAlgStatsEntry 90 }

affirmedServicesNatServiceNatNodeLevelAlgStatsDownlinkDescribeResponse OBJECT-TYPE
    SYNTAX      ConfdString
    MAX-ACCESS  read-only
    STATUS      current
    DESCRIPTION "DESCRIBE  response from server"
    ::= { affirmedServicesNatServiceNatNodeLevelAlgStatsEntry 91 }

affirmedServicesNatServiceNatNodeLevelAlgStatsDownlinkSetupResponse OBJECT-TYPE
    SYNTAX      ConfdString
    MAX-ACCESS  read-only
    STATUS      current
    DESCRIPTION "SETUP  response from server"
    ::= { affirmedServicesNatServiceNatNodeLevelAlgStatsEntry 92 }

affirmedServicesNatServiceNatNodeLevelAlgStatsDownlinkTeardownResponse OBJECT-TYPE
    SYNTAX      ConfdString
    MAX-ACCESS  read-only
    STATUS      current
    DESCRIPTION "TEARDOWN  response from server"
    ::= { affirmedServicesNatServiceNatNodeLevelAlgStatsEntry 93 }

affirmedServicesNatServiceNatNodeLevelAlgStatsSipUplinkUnsupportedMethod OBJECT-TYPE
    SYNTAX      ConfdString
    MAX-ACCESS  read-only
    STATUS      current
    DESCRIPTION "OPTIONS, MESSAGE, NOTIFY, PRACK, SUBSCRIBE, UPDATE, PUBLISH, REFER and INFO methods are not supported"
    ::= { affirmedServicesNatServiceNatNodeLevelAlgStatsEntry 94 }

affirmedServicesNatServiceNatNodeLevelAlgStatsSipDownlinkUnsupportedMethod OBJECT-TYPE
    SYNTAX      ConfdString
    MAX-ACCESS  read-only
    STATUS      current
    DESCRIPTION "OPTIONS, MESSAGE, NOTIFY, PRACK, SUBSCRIBE, UPDATE, PUBLISH, REFER and INFO methods are not supported"
    ::= { affirmedServicesNatServiceNatNodeLevelAlgStatsEntry 95 }

affirmedServicesNatServiceNatSessionFlow-groupSummaryTable OBJECT-TYPE
    SYNTAX      SEQUENCE OF AffirmedServicesNatServiceNatSessionFlow-groupSummaryEntry
    MAX-ACCESS  not-accessible
    STATUS      current
    DESCRIPTION ""
    ::= { affirmedServicesNatServiceNatSessionFlow-group 1 }

affirmedServicesNatServiceNatSessionFlow-groupSummaryEntry OBJECT-TYPE
    SYNTAX      AffirmedServicesNatServiceNatSessionFlow-groupSummaryEntry
    MAX-ACCESS  not-accessible
    STATUS      current
    DESCRIPTION ""
    INDEX { affirmedServicesNatServiceNatSessionFlow-groupSummarySession-id }
        ::= { affirmedServicesNatServiceNatSessionFlow-groupSummaryTable 1 }

AffirmedServicesNatServiceNatSessionFlow-groupSummaryEntry ::=
    SEQUENCE {
        affirmedServicesNatServiceNatSessionFlow-groupSummarySession-id Unsigned32,
        affirmedServicesNatServiceNatSessionFlow-groupSummaryOutput String
    }

affirmedServicesNatServiceNatSessionFlow-groupSummarySession-id OBJECT-TYPE
    SYNTAX      Unsigned32
    MAX-ACCESS  not-accessible
    STATUS      current
    DESCRIPTION "Session Identifier"
    ::= { affirmedServicesNatServiceNatSessionFlow-groupSummaryEntry 1 }

affirmedServicesNatServiceNatSessionFlow-groupSummaryOutput OBJECT-TYPE
    SYNTAX      String
    MAX-ACCESS  read-only
    STATUS      current
    DESCRIPTION ""
    ::= { affirmedServicesNatServiceNatSessionFlow-groupSummaryEntry 2 }

affirmedServicesNatServiceNatSessionFlow-groupVerboseTable OBJECT-TYPE
    SYNTAX      SEQUENCE OF AffirmedServicesNatServiceNatSessionFlow-groupVerboseEntry
    MAX-ACCESS  not-accessible
    STATUS      current
    DESCRIPTION ""
    ::= { affirmedServicesNatServiceNatSessionFlow-group 2 }

affirmedServicesNatServiceNatSessionFlow-groupVerboseEntry OBJECT-TYPE
    SYNTAX      AffirmedServicesNatServiceNatSessionFlow-groupVerboseEntry
    MAX-ACCESS  not-accessible
    STATUS      current
    DESCRIPTION ""
    INDEX { affirmedServicesNatServiceNatSessionFlow-groupVerboseSession-id }
        ::= { affirmedServicesNatServiceNatSessionFlow-groupVerboseTable 1 }

AffirmedServicesNatServiceNatSessionFlow-groupVerboseEntry ::=
    SEQUENCE {
        affirmedServicesNatServiceNatSessionFlow-groupVerboseSession-id Unsigned32,
        affirmedServicesNatServiceNatSessionFlow-groupVerboseOutput String
    }

affirmedServicesNatServiceNatSessionFlow-groupVerboseSession-id OBJECT-TYPE
    SYNTAX      Unsigned32
    MAX-ACCESS  not-accessible
    STATUS      current
    DESCRIPTION "Session Identifier"
    ::= { affirmedServicesNatServiceNatSessionFlow-groupVerboseEntry 1 }

affirmedServicesNatServiceNatSessionFlow-groupVerboseOutput OBJECT-TYPE
    SYNTAX      String
    MAX-ACCESS  read-only
    STATUS      current
    DESCRIPTION ""
    ::= { affirmedServicesNatServiceNatSessionFlow-groupVerboseEntry 2 }

affirmedServicesNatServiceNatStatisticalNatPoolStatsTable OBJECT-TYPE
    SYNTAX      SEQUENCE OF AffirmedServicesNatServiceNatStatisticalNatPoolStatsEntry
    MAX-ACCESS  not-accessible
    STATUS      current
    DESCRIPTION ""
    ::= { affirmedServicesNatServiceNatStatistical 1 }

affirmedServicesNatServiceNatStatisticalNatPoolStatsEntry OBJECT-TYPE
    SYNTAX      AffirmedServicesNatServiceNatStatisticalNatPoolStatsEntry
    MAX-ACCESS  not-accessible
    STATUS      current
    DESCRIPTION ""
    INDEX { affirmedServicesNatServiceNatStatisticalNatPoolStatsSlot, affirmedServicesNatServiceNatStatisticalNatPoolStatsNetworkContext, affirmedServicesNatServiceNatStatisticalNatPoolStatsPoolName }
        ::= { affirmedServicesNatServiceNatStatisticalNatPoolStatsTable 1 }

AffirmedServicesNatServiceNatStatisticalNatPoolStatsEntry ::=
    SEQUENCE {
        affirmedServicesNatServiceNatStatisticalNatPoolStatsSlot Unsigned32,
        affirmedServicesNatServiceNatStatisticalNatPoolStatsNetworkContext String,
        affirmedServicesNatServiceNatStatisticalNatPoolStatsPoolName String,
        affirmedServicesNatServiceNatStatisticalNatPoolStatsSessionCreateFailure ConfdString,
        affirmedServicesNatServiceNatStatisticalNatPoolStatsSessionCreateSuccess ConfdString,
        affirmedServicesNatServiceNatStatisticalNatPoolStatsSessionDelete ConfdString,
        affirmedServicesNatServiceNatStatisticalNatPoolStatsSessionIpAllocationSuccess ConfdString,
        affirmedServicesNatServiceNatStatisticalNatPoolStatsSessionIpAllocationFailure ConfdString,
        affirmedServicesNatServiceNatStatisticalNatPoolStatsSessionIpDeallocation ConfdString,
        affirmedServicesNatServiceNatStatisticalNatPoolStatsSessionPortChunkAllocationSuccess ConfdString,
        affirmedServicesNatServiceNatStatisticalNatPoolStatsSessionPortChunkAllocationFailure ConfdString,
        affirmedServicesNatServiceNatStatisticalNatPoolStatsSessionPortChunkDeallocation ConfdString,
        affirmedServicesNatServiceNatStatisticalNatPoolStatsSessionCount ConfdString,
        affirmedServicesNatServiceNatStatisticalNatPoolStatsSessionCapacityAvailable ConfdString,
        affirmedServicesNatServiceNatStatisticalNatPoolStatsResourceUtilizationIp ConfdString,
        affirmedServicesNatServiceNatStatisticalNatPoolStatsResourceUtilizationPortChunk ConfdString,
        affirmedServicesNatServiceNatStatisticalNatPoolStatsResourceUtilizationSession ConfdString,
        affirmedServicesNatServiceNatStatisticalNatPoolStatsResourceInUseIp ConfdString,
        affirmedServicesNatServiceNatStatisticalNatPoolStatsResourceInUsePortChunk ConfdString,
        affirmedServicesNatServiceNatStatisticalNatPoolStatsAllocFailureOutOfResources ConfdString,
        affirmedServicesNatServiceNatStatisticalNatPoolStatsAllocFailureNoSubPool ConfdString,
        affirmedServicesNatServiceNatStatisticalNatPoolStatsAllocFailureSubPoolOutOfService ConfdString,
        affirmedServicesNatServiceNatStatisticalNatPoolStatsAllocFailureMaxChunksExceeded ConfdString,
        affirmedServicesNatServiceNatStatisticalNatPoolStatsConnectionsCreated ConfdString,
        affirmedServicesNatServiceNatStatisticalNatPoolStatsConnectionsDeleted ConfdString,
        affirmedServicesNatServiceNatStatisticalNatPoolStatsConnectionCreateFailure ConfdString,
        affirmedServicesNatServiceNatStatisticalNatPoolStatsConnectionCount ConfdString,
        affirmedServicesNatServiceNatStatisticalNatPoolStatsConnectionAllocateNatPortSuccess ConfdString,
        affirmedServicesNatServiceNatStatisticalNatPoolStatsConnectionAllocateNatPortFailure ConfdString,
        affirmedServicesNatServiceNatStatisticalNatPoolStatsConnectionDeallocateNatPortSuccess ConfdString,
        affirmedServicesNatServiceNatStatisticalNatPoolStatsConnectionCreateFailureNatPortUnavailable ConfdString,
        affirmedServicesNatServiceNatStatisticalNatPoolStatsAllocFailureNPTv6 ConfdString,
        affirmedServicesNatServiceNatStatisticalNatPoolStatsPerSessionPortChunksHighWatermark ConfdString
    }

affirmedServicesNatServiceNatStatisticalNatPoolStatsSlot OBJECT-TYPE
    SYNTAX      Unsigned32
    MAX-ACCESS  not-accessible
    STATUS      current
    DESCRIPTION "Slot id"
    ::= { affirmedServicesNatServiceNatStatisticalNatPoolStatsEntry 1 }

affirmedServicesNatServiceNatStatisticalNatPoolStatsNetworkContext OBJECT-TYPE
    SYNTAX      String
    MAX-ACCESS  not-accessible
    STATUS      current
    DESCRIPTION "networkcontext"
    ::= { affirmedServicesNatServiceNatStatisticalNatPoolStatsEntry 2 }

affirmedServicesNatServiceNatStatisticalNatPoolStatsPoolName OBJECT-TYPE
    SYNTAX      String
    MAX-ACCESS  not-accessible
    STATUS      current
    DESCRIPTION "NAT pool name"
    ::= { affirmedServicesNatServiceNatStatisticalNatPoolStatsEntry 3 }

affirmedServicesNatServiceNatStatisticalNatPoolStatsSessionCreateFailure OBJECT-TYPE
    SYNTAX      ConfdString
    MAX-ACCESS  read-only
    STATUS      current
    DESCRIPTION "Number of sessions for which NAT resource(IP or port chunks) allocation failed"
    ::= { affirmedServicesNatServiceNatStatisticalNatPoolStatsEntry 4 }

affirmedServicesNatServiceNatStatisticalNatPoolStatsSessionCreateSuccess OBJECT-TYPE
    SYNTAX      ConfdString
    MAX-ACCESS  read-only
    STATUS      current
    DESCRIPTION "Number of sessions successfully allocated NAT resources"
    ::= { affirmedServicesNatServiceNatStatisticalNatPoolStatsEntry 5 }

affirmedServicesNatServiceNatStatisticalNatPoolStatsSessionDelete OBJECT-TYPE
    SYNTAX      ConfdString
    MAX-ACCESS  read-only
    STATUS      current
    DESCRIPTION "Number of session delete requests processed"
    ::= { affirmedServicesNatServiceNatStatisticalNatPoolStatsEntry 6 }

affirmedServicesNatServiceNatStatisticalNatPoolStatsSessionIpAllocationSuccess OBJECT-TYPE
    SYNTAX      ConfdString
    MAX-ACCESS  read-only
    STATUS      current
    DESCRIPTION "Number of NAT IP's allocated successfully"
    ::= { affirmedServicesNatServiceNatStatisticalNatPoolStatsEntry 7 }

affirmedServicesNatServiceNatStatisticalNatPoolStatsSessionIpAllocationFailure OBJECT-TYPE
    SYNTAX      ConfdString
    MAX-ACCESS  read-only
    STATUS      current
    DESCRIPTION "Number of NAT IP allocation failure"
    ::= { affirmedServicesNatServiceNatStatisticalNatPoolStatsEntry 8 }

affirmedServicesNatServiceNatStatisticalNatPoolStatsSessionIpDeallocation OBJECT-TYPE
    SYNTAX      ConfdString
    MAX-ACCESS  read-only
    STATUS      current
    DESCRIPTION "Number of NAT IP deallocated"
    ::= { affirmedServicesNatServiceNatStatisticalNatPoolStatsEntry 9 }

affirmedServicesNatServiceNatStatisticalNatPoolStatsSessionPortChunkAllocationSuccess OBJECT-TYPE
    SYNTAX      ConfdString
    MAX-ACCESS  read-only
    STATUS      current
    DESCRIPTION "Number of Port chunks allocated successfully"
    ::= { affirmedServicesNatServiceNatStatisticalNatPoolStatsEntry 10 }

affirmedServicesNatServiceNatStatisticalNatPoolStatsSessionPortChunkAllocationFailure OBJECT-TYPE
    SYNTAX      ConfdString
    MAX-ACCESS  read-only
    STATUS      current
    DESCRIPTION "Number of Port chunk allocation failure"
    ::= { affirmedServicesNatServiceNatStatisticalNatPoolStatsEntry 11 }

affirmedServicesNatServiceNatStatisticalNatPoolStatsSessionPortChunkDeallocation OBJECT-TYPE
    SYNTAX      ConfdString
    MAX-ACCESS  read-only
    STATUS      current
    DESCRIPTION "Number of Port chunks deallocated"
    ::= { affirmedServicesNatServiceNatStatisticalNatPoolStatsEntry 12 }

affirmedServicesNatServiceNatStatisticalNatPoolStatsSessionCount OBJECT-TYPE
    SYNTAX      ConfdString
    MAX-ACCESS  read-only
    STATUS      current
    DESCRIPTION "Total number of sessions currently using NAT resources from this nat-pool"
    ::= { affirmedServicesNatServiceNatStatisticalNatPoolStatsEntry 13 }

affirmedServicesNatServiceNatStatisticalNatPoolStatsSessionCapacityAvailable OBJECT-TYPE
    SYNTAX      ConfdString
    MAX-ACCESS  read-only
    STATUS      current
    DESCRIPTION "Number of additional sessions possible"
    ::= { affirmedServicesNatServiceNatStatisticalNatPoolStatsEntry 14 }

affirmedServicesNatServiceNatStatisticalNatPoolStatsResourceUtilizationIp OBJECT-TYPE
    SYNTAX      ConfdString
    MAX-ACCESS  read-only
    STATUS      current
    DESCRIPTION "Percentage utilization of the NAT IP resources"
    ::= { affirmedServicesNatServiceNatStatisticalNatPoolStatsEntry 15 }

affirmedServicesNatServiceNatStatisticalNatPoolStatsResourceUtilizationPortChunk OBJECT-TYPE
    SYNTAX      ConfdString
    MAX-ACCESS  read-only
    STATUS      current
    DESCRIPTION "Percentage utilization of NAT Port chunk resources"
    ::= { affirmedServicesNatServiceNatStatisticalNatPoolStatsEntry 16 }

affirmedServicesNatServiceNatStatisticalNatPoolStatsResourceUtilizationSession OBJECT-TYPE
    SYNTAX      ConfdString
    MAX-ACCESS  read-only
    STATUS      current
    DESCRIPTION "Percentage utilization of the NAT resources based on current session count"
    ::= { affirmedServicesNatServiceNatStatisticalNatPoolStatsEntry 17 }

affirmedServicesNatServiceNatStatisticalNatPoolStatsResourceInUseIp OBJECT-TYPE
    SYNTAX      ConfdString
    MAX-ACCESS  read-only
    STATUS      current
    DESCRIPTION "Number of IPs currently in-use"
    ::= { affirmedServicesNatServiceNatStatisticalNatPoolStatsEntry 18 }

affirmedServicesNatServiceNatStatisticalNatPoolStatsResourceInUsePortChunk OBJECT-TYPE
    SYNTAX      ConfdString
    MAX-ACCESS  read-only
    STATUS      current
    DESCRIPTION "Number of Port chunks currently in-use"
    ::= { affirmedServicesNatServiceNatStatisticalNatPoolStatsEntry 19 }

affirmedServicesNatServiceNatStatisticalNatPoolStatsAllocFailureOutOfResources OBJECT-TYPE
    SYNTAX      ConfdString
    MAX-ACCESS  read-only
    STATUS      current
    DESCRIPTION "Number of allocation failures due to nat-pool not having enough IP or port chunks"
    ::= { affirmedServicesNatServiceNatStatisticalNatPoolStatsEntry 20 }

affirmedServicesNatServiceNatStatisticalNatPoolStatsAllocFailureNoSubPool OBJECT-TYPE
    SYNTAX      ConfdString
    MAX-ACCESS  read-only
    STATUS      current
    DESCRIPTION "Number of allocation failures due to nat-pool not having any sub-pool configured"
    ::= { affirmedServicesNatServiceNatStatisticalNatPoolStatsEntry 21 }

affirmedServicesNatServiceNatStatisticalNatPoolStatsAllocFailureSubPoolOutOfService OBJECT-TYPE
    SYNTAX      ConfdString
    MAX-ACCESS  read-only
    STATUS      current
    DESCRIPTION "Number of allocation failure due to sub-pool being admin disabled"
    ::= { affirmedServicesNatServiceNatStatisticalNatPoolStatsEntry 22 }

affirmedServicesNatServiceNatStatisticalNatPoolStatsAllocFailureMaxChunksExceeded OBJECT-TYPE
    SYNTAX      ConfdString
    MAX-ACCESS  read-only
    STATUS      current
    DESCRIPTION "Count of port chunk allocation failures due to session already using max-chunks-per-session port chunks from the nat-pool"
    ::= { affirmedServicesNatServiceNatStatisticalNatPoolStatsEntry 23 }

affirmedServicesNatServiceNatStatisticalNatPoolStatsConnectionsCreated OBJECT-TYPE
    SYNTAX      ConfdString
    MAX-ACCESS  read-only
    STATUS      current
    DESCRIPTION "Number of nat connections created"
    ::= { affirmedServicesNatServiceNatStatisticalNatPoolStatsEntry 24 }

affirmedServicesNatServiceNatStatisticalNatPoolStatsConnectionsDeleted OBJECT-TYPE
    SYNTAX      ConfdString
    MAX-ACCESS  read-only
    STATUS      current
    DESCRIPTION "Number of nat connections deleted"
    ::= { affirmedServicesNatServiceNatStatisticalNatPoolStatsEntry 25 }

affirmedServicesNatServiceNatStatisticalNatPoolStatsConnectionCreateFailure OBJECT-TYPE
    SYNTAX      ConfdString
    MAX-ACCESS  read-only
    STATUS      current
    DESCRIPTION "Number of nat connection failures"
    ::= { affirmedServicesNatServiceNatStatisticalNatPoolStatsEntry 26 }

affirmedServicesNatServiceNatStatisticalNatPoolStatsConnectionCount OBJECT-TYPE
    SYNTAX      ConfdString
    MAX-ACCESS  read-only
    STATUS      current
    DESCRIPTION "Number of connections currently using the nat-pool"
    ::= { affirmedServicesNatServiceNatStatisticalNatPoolStatsEntry 27 }

affirmedServicesNatServiceNatStatisticalNatPoolStatsConnectionAllocateNatPortSuccess OBJECT-TYPE
    SYNTAX      ConfdString
    MAX-ACCESS  read-only
    STATUS      current
    DESCRIPTION "Number of nat port allocated successfully"
    ::= { affirmedServicesNatServiceNatStatisticalNatPoolStatsEntry 28 }

affirmedServicesNatServiceNatStatisticalNatPoolStatsConnectionAllocateNatPortFailure OBJECT-TYPE
    SYNTAX      ConfdString
    MAX-ACCESS  read-only
    STATUS      current
    DESCRIPTION "Number of nat port allocation failure"
    ::= { affirmedServicesNatServiceNatStatisticalNatPoolStatsEntry 29 }

affirmedServicesNatServiceNatStatisticalNatPoolStatsConnectionDeallocateNatPortSuccess OBJECT-TYPE
    SYNTAX      ConfdString
    MAX-ACCESS  read-only
    STATUS      current
    DESCRIPTION "Number of nat port deallocate success"
    ::= { affirmedServicesNatServiceNatStatisticalNatPoolStatsEntry 30 }

affirmedServicesNatServiceNatStatisticalNatPoolStatsConnectionCreateFailureNatPortUnavailable OBJECT-TYPE
    SYNTAX      ConfdString
    MAX-ACCESS  read-only
    STATUS      current
    DESCRIPTION "Number of connection create failures due to non-availability of nat port"
    ::= { affirmedServicesNatServiceNatStatisticalNatPoolStatsEntry 31 }

affirmedServicesNatServiceNatStatisticalNatPoolStatsAllocFailureNPTv6 OBJECT-TYPE
    SYNTAX      ConfdString
    MAX-ACCESS  read-only
    STATUS      current
    DESCRIPTION "Number of sessions failed for NPTv6"
    ::= { affirmedServicesNatServiceNatStatisticalNatPoolStatsEntry 32 }

affirmedServicesNatServiceNatStatisticalNatPoolStatsPerSessionPortChunksHighWatermark OBJECT-TYPE
    SYNTAX      ConfdString
    MAX-ACCESS  read-only
    STATUS      current
    DESCRIPTION "Highest port chunk allocated to a session"
    ::= { affirmedServicesNatServiceNatStatisticalNatPoolStatsEntry 33 }

affirmedServicesNatServiceNatStatisticalSubPoolStatsTable OBJECT-TYPE
    SYNTAX      SEQUENCE OF AffirmedServicesNatServiceNatStatisticalSubPoolStatsEntry
    MAX-ACCESS  not-accessible
    STATUS      current
    DESCRIPTION ""
    ::= { affirmedServicesNatServiceNatStatistical 2 }

affirmedServicesNatServiceNatStatisticalSubPoolStatsEntry OBJECT-TYPE
    SYNTAX      AffirmedServicesNatServiceNatStatisticalSubPoolStatsEntry
    MAX-ACCESS  not-accessible
    STATUS      current
    DESCRIPTION ""
    INDEX { affirmedServicesNatServiceNatStatisticalSubPoolStatsSlot, affirmedServicesNatServiceNatStatisticalSubPoolStatsNetworkContext, affirmedServicesNatServiceNatStatisticalSubPoolStatsPoolName, affirmedServicesNatServiceNatStatisticalSubPoolStatsSubPoolName }
        ::= { affirmedServicesNatServiceNatStatisticalSubPoolStatsTable 1 }

AffirmedServicesNatServiceNatStatisticalSubPoolStatsEntry ::=
    SEQUENCE {
        affirmedServicesNatServiceNatStatisticalSubPoolStatsSlot Unsigned32,
        affirmedServicesNatServiceNatStatisticalSubPoolStatsNetworkContext String,
        affirmedServicesNatServiceNatStatisticalSubPoolStatsPoolName String,
        affirmedServicesNatServiceNatStatisticalSubPoolStatsSubPoolName String,
        affirmedServicesNatServiceNatStatisticalSubPoolStatsSessionCreateFailure ConfdString,
        affirmedServicesNatServiceNatStatisticalSubPoolStatsSessionCreateSuccess ConfdString,
        affirmedServicesNatServiceNatStatisticalSubPoolStatsSessionDelete ConfdString,
        affirmedServicesNatServiceNatStatisticalSubPoolStatsSessionIpAllocationSuccess ConfdString,
        affirmedServicesNatServiceNatStatisticalSubPoolStatsSessionIpAllocationFailure ConfdString,
        affirmedServicesNatServiceNatStatisticalSubPoolStatsSessionIpDeallocation ConfdString,
        affirmedServicesNatServiceNatStatisticalSubPoolStatsSessionPortChunkAllocationSuccess ConfdString,
        affirmedServicesNatServiceNatStatisticalSubPoolStatsSessionPortChunkAllocationFailure ConfdString,
        affirmedServicesNatServiceNatStatisticalSubPoolStatsSessionPortChunkDeallocation ConfdString,
        affirmedServicesNatServiceNatStatisticalSubPoolStatsSessionCount ConfdString,
        affirmedServicesNatServiceNatStatisticalSubPoolStatsSessionCapacityAvailable ConfdString,
        affirmedServicesNatServiceNatStatisticalSubPoolStatsResourceUtilizationIp ConfdString,
        affirmedServicesNatServiceNatStatisticalSubPoolStatsResourceUtilizationPortChunk ConfdString,
        affirmedServicesNatServiceNatStatisticalSubPoolStatsResourceUtilizationSession ConfdString,
        affirmedServicesNatServiceNatStatisticalSubPoolStatsResourceInUseIp ConfdString,
        affirmedServicesNatServiceNatStatisticalSubPoolStatsResourceInUsePortChunk ConfdString,
        affirmedServicesNatServiceNatStatisticalSubPoolStatsAllocFailureOutOfPortChunk ConfdString,
        affirmedServicesNatServiceNatStatisticalSubPoolStatsAllocFailureNatRatioExceeded ConfdString,
        affirmedServicesNatServiceNatStatisticalSubPoolStatsConnectionsCreated ConfdString,
        affirmedServicesNatServiceNatStatisticalSubPoolStatsConnectionsDeleted ConfdString,
        affirmedServicesNatServiceNatStatisticalSubPoolStatsConnectionCreateFailure ConfdString,
        affirmedServicesNatServiceNatStatisticalSubPoolStatsConnectionCount ConfdString,
        affirmedServicesNatServiceNatStatisticalSubPoolStatsConnectionAllocateNatPortSuccess ConfdString,
        affirmedServicesNatServiceNatStatisticalSubPoolStatsConnectionAllocateNatPortFailure ConfdString,
        affirmedServicesNatServiceNatStatisticalSubPoolStatsConnectionDeallocateNatPortSuccess ConfdString,
        affirmedServicesNatServiceNatStatisticalSubPoolStatsConnectionCreateFailureNatPortUnavailable ConfdString
    }

affirmedServicesNatServiceNatStatisticalSubPoolStatsSlot OBJECT-TYPE
    SYNTAX      Unsigned32
    MAX-ACCESS  not-accessible
    STATUS      current
    DESCRIPTION "Slot id"
    ::= { affirmedServicesNatServiceNatStatisticalSubPoolStatsEntry 1 }

affirmedServicesNatServiceNatStatisticalSubPoolStatsNetworkContext OBJECT-TYPE
    SYNTAX      String
    MAX-ACCESS  not-accessible
    STATUS      current
    DESCRIPTION "networkcontext"
    ::= { affirmedServicesNatServiceNatStatisticalSubPoolStatsEntry 2 }

affirmedServicesNatServiceNatStatisticalSubPoolStatsPoolName OBJECT-TYPE
    SYNTAX      String
    MAX-ACCESS  not-accessible
    STATUS      current
    DESCRIPTION "NAT pool name"
    ::= { affirmedServicesNatServiceNatStatisticalSubPoolStatsEntry 3 }

affirmedServicesNatServiceNatStatisticalSubPoolStatsSubPoolName OBJECT-TYPE
    SYNTAX      String
    MAX-ACCESS  not-accessible
    STATUS      current
    DESCRIPTION "subpool name"
    ::= { affirmedServicesNatServiceNatStatisticalSubPoolStatsEntry 4 }

affirmedServicesNatServiceNatStatisticalSubPoolStatsSessionCreateFailure OBJECT-TYPE
    SYNTAX      ConfdString
    MAX-ACCESS  read-only
    STATUS      current
    DESCRIPTION "Number of sessions for which NAT resource(IP or port chunks) allocation failed"
    ::= { affirmedServicesNatServiceNatStatisticalSubPoolStatsEntry 5 }

affirmedServicesNatServiceNatStatisticalSubPoolStatsSessionCreateSuccess OBJECT-TYPE
    SYNTAX      ConfdString
    MAX-ACCESS  read-only
    STATUS      current
    DESCRIPTION "Number of sessions successfully allocated NAT resources"
    ::= { affirmedServicesNatServiceNatStatisticalSubPoolStatsEntry 6 }

affirmedServicesNatServiceNatStatisticalSubPoolStatsSessionDelete OBJECT-TYPE
    SYNTAX      ConfdString
    MAX-ACCESS  read-only
    STATUS      current
    DESCRIPTION "Number of session delete requests processed"
    ::= { affirmedServicesNatServiceNatStatisticalSubPoolStatsEntry 7 }

affirmedServicesNatServiceNatStatisticalSubPoolStatsSessionIpAllocationSuccess OBJECT-TYPE
    SYNTAX      ConfdString
    MAX-ACCESS  read-only
    STATUS      current
    DESCRIPTION "Number of NAT IP's allocated successfully"
    ::= { affirmedServicesNatServiceNatStatisticalSubPoolStatsEntry 8 }

affirmedServicesNatServiceNatStatisticalSubPoolStatsSessionIpAllocationFailure OBJECT-TYPE
    SYNTAX      ConfdString
    MAX-ACCESS  read-only
    STATUS      current
    DESCRIPTION "Number of NAT IP allocation failure"
    ::= { affirmedServicesNatServiceNatStatisticalSubPoolStatsEntry 9 }

affirmedServicesNatServiceNatStatisticalSubPoolStatsSessionIpDeallocation OBJECT-TYPE
    SYNTAX      ConfdString
    MAX-ACCESS  read-only
    STATUS      current
    DESCRIPTION "Number of NAT IP deallocated"
    ::= { affirmedServicesNatServiceNatStatisticalSubPoolStatsEntry 10 }

affirmedServicesNatServiceNatStatisticalSubPoolStatsSessionPortChunkAllocationSuccess OBJECT-TYPE
    SYNTAX      ConfdString
    MAX-ACCESS  read-only
    STATUS      current
    DESCRIPTION "Number of Port chunks allocated successfully"
    ::= { affirmedServicesNatServiceNatStatisticalSubPoolStatsEntry 11 }

affirmedServicesNatServiceNatStatisticalSubPoolStatsSessionPortChunkAllocationFailure OBJECT-TYPE
    SYNTAX      ConfdString
    MAX-ACCESS  read-only
    STATUS      current
    DESCRIPTION "Number of Port chunk allocation failure"
    ::= { affirmedServicesNatServiceNatStatisticalSubPoolStatsEntry 12 }

affirmedServicesNatServiceNatStatisticalSubPoolStatsSessionPortChunkDeallocation OBJECT-TYPE
    SYNTAX      ConfdString
    MAX-ACCESS  read-only
    STATUS      current
    DESCRIPTION "Number of Port chunks deallocated"
    ::= { affirmedServicesNatServiceNatStatisticalSubPoolStatsEntry 13 }

affirmedServicesNatServiceNatStatisticalSubPoolStatsSessionCount OBJECT-TYPE
    SYNTAX      ConfdString
    MAX-ACCESS  read-only
    STATUS      current
    DESCRIPTION "Total number of sessions currently using NAT resources from this nat-pool"
    ::= { affirmedServicesNatServiceNatStatisticalSubPoolStatsEntry 14 }

affirmedServicesNatServiceNatStatisticalSubPoolStatsSessionCapacityAvailable OBJECT-TYPE
    SYNTAX      ConfdString
    MAX-ACCESS  read-only
    STATUS      current
    DESCRIPTION "Number of additional sessions possible"
    ::= { affirmedServicesNatServiceNatStatisticalSubPoolStatsEntry 15 }

affirmedServicesNatServiceNatStatisticalSubPoolStatsResourceUtilizationIp OBJECT-TYPE
    SYNTAX      ConfdString
    MAX-ACCESS  read-only
    STATUS      current
    DESCRIPTION "Percentage utilization of the NAT IP resources"
    ::= { affirmedServicesNatServiceNatStatisticalSubPoolStatsEntry 16 }

affirmedServicesNatServiceNatStatisticalSubPoolStatsResourceUtilizationPortChunk OBJECT-TYPE
    SYNTAX      ConfdString
    MAX-ACCESS  read-only
    STATUS      current
    DESCRIPTION "Percentage utilization of NAT Port chunk resources"
    ::= { affirmedServicesNatServiceNatStatisticalSubPoolStatsEntry 17 }

affirmedServicesNatServiceNatStatisticalSubPoolStatsResourceUtilizationSession OBJECT-TYPE
    SYNTAX      ConfdString
    MAX-ACCESS  read-only
    STATUS      current
    DESCRIPTION "Percentage utilization of the NAT resources based on current session count"
    ::= { affirmedServicesNatServiceNatStatisticalSubPoolStatsEntry 18 }

affirmedServicesNatServiceNatStatisticalSubPoolStatsResourceInUseIp OBJECT-TYPE
    SYNTAX      ConfdString
    MAX-ACCESS  read-only
    STATUS      current
    DESCRIPTION "Number of IPs currently in-use"
    ::= { affirmedServicesNatServiceNatStatisticalSubPoolStatsEntry 19 }

affirmedServicesNatServiceNatStatisticalSubPoolStatsResourceInUsePortChunk OBJECT-TYPE
    SYNTAX      ConfdString
    MAX-ACCESS  read-only
    STATUS      current
    DESCRIPTION "Number of Port chunks currently in-use"
    ::= { affirmedServicesNatServiceNatStatisticalSubPoolStatsEntry 20 }

affirmedServicesNatServiceNatStatisticalSubPoolStatsAllocFailureOutOfPortChunk OBJECT-TYPE
    SYNTAX      ConfdString
    MAX-ACCESS  read-only
    STATUS      current
    DESCRIPTION "Count of port chunk allocation failures due to IP address not having enough port chunks"
    ::= { affirmedServicesNatServiceNatStatisticalSubPoolStatsEntry 21 }

affirmedServicesNatServiceNatStatisticalSubPoolStatsAllocFailureNatRatioExceeded OBJECT-TYPE
    SYNTAX      ConfdString
    MAX-ACCESS  read-only
    STATUS      current
    DESCRIPTION "Count of port chunk allocation failures due to number of sessions being catered by IP address exceeding max-users-per-NAT-IP"
    ::= { affirmedServicesNatServiceNatStatisticalSubPoolStatsEntry 22 }

affirmedServicesNatServiceNatStatisticalSubPoolStatsConnectionsCreated OBJECT-TYPE
    SYNTAX      ConfdString
    MAX-ACCESS  read-only
    STATUS      current
    DESCRIPTION "Number of nat connections created"
    ::= { affirmedServicesNatServiceNatStatisticalSubPoolStatsEntry 23 }

affirmedServicesNatServiceNatStatisticalSubPoolStatsConnectionsDeleted OBJECT-TYPE
    SYNTAX      ConfdString
    MAX-ACCESS  read-only
    STATUS      current
    DESCRIPTION "Number of nat connections deleted"
    ::= { affirmedServicesNatServiceNatStatisticalSubPoolStatsEntry 24 }

affirmedServicesNatServiceNatStatisticalSubPoolStatsConnectionCreateFailure OBJECT-TYPE
    SYNTAX      ConfdString
    MAX-ACCESS  read-only
    STATUS      current
    DESCRIPTION "Number of nat connection failures"
    ::= { affirmedServicesNatServiceNatStatisticalSubPoolStatsEntry 25 }

affirmedServicesNatServiceNatStatisticalSubPoolStatsConnectionCount OBJECT-TYPE
    SYNTAX      ConfdString
    MAX-ACCESS  read-only
    STATUS      current
    DESCRIPTION "Number of connections currently using the nat-pool"
    ::= { affirmedServicesNatServiceNatStatisticalSubPoolStatsEntry 26 }

affirmedServicesNatServiceNatStatisticalSubPoolStatsConnectionAllocateNatPortSuccess OBJECT-TYPE
    SYNTAX      ConfdString
    MAX-ACCESS  read-only
    STATUS      current
    DESCRIPTION "Number of nat port allocated successfully"
    ::= { affirmedServicesNatServiceNatStatisticalSubPoolStatsEntry 27 }

affirmedServicesNatServiceNatStatisticalSubPoolStatsConnectionAllocateNatPortFailure OBJECT-TYPE
    SYNTAX      ConfdString
    MAX-ACCESS  read-only
    STATUS      current
    DESCRIPTION "Number of nat port allocation failure"
    ::= { affirmedServicesNatServiceNatStatisticalSubPoolStatsEntry 28 }

affirmedServicesNatServiceNatStatisticalSubPoolStatsConnectionDeallocateNatPortSuccess OBJECT-TYPE
    SYNTAX      ConfdString
    MAX-ACCESS  read-only
    STATUS      current
    DESCRIPTION "Number of nat port deallocate success"
    ::= { affirmedServicesNatServiceNatStatisticalSubPoolStatsEntry 29 }

affirmedServicesNatServiceNatStatisticalSubPoolStatsConnectionCreateFailureNatPortUnavailable OBJECT-TYPE
    SYNTAX      ConfdString
    MAX-ACCESS  read-only
    STATUS      current
    DESCRIPTION "Number of connection create failures due to non-availability of nat port"
    ::= { affirmedServicesNatServiceNatStatisticalSubPoolStatsEntry 30 }

affirmedServicesNatServiceNatGuaranteedNatPoolStatsTable OBJECT-TYPE
    SYNTAX      SEQUENCE OF AffirmedServicesNatServiceNatGuaranteedNatPoolStatsEntry
    MAX-ACCESS  not-accessible
    STATUS      current
    DESCRIPTION ""
    ::= { affirmedServicesNatServiceNatGuaranteed 1 }

affirmedServicesNatServiceNatGuaranteedNatPoolStatsEntry OBJECT-TYPE
    SYNTAX      AffirmedServicesNatServiceNatGuaranteedNatPoolStatsEntry
    MAX-ACCESS  not-accessible
    STATUS      current
    DESCRIPTION ""
    INDEX { affirmedServicesNatServiceNatGuaranteedNatPoolStatsNetworkContext, affirmedServicesNatServiceNatGuaranteedNatPoolStatsPoolName }
        ::= { affirmedServicesNatServiceNatGuaranteedNatPoolStatsTable 1 }

AffirmedServicesNatServiceNatGuaranteedNatPoolStatsEntry ::=
    SEQUENCE {
        affirmedServicesNatServiceNatGuaranteedNatPoolStatsNetworkContext String,
        affirmedServicesNatServiceNatGuaranteedNatPoolStatsPoolName String,
        affirmedServicesNatServiceNatGuaranteedNatPoolStatsSessionCreateFailure ConfdString,
        affirmedServicesNatServiceNatGuaranteedNatPoolStatsSessionCreateSuccess ConfdString,
        affirmedServicesNatServiceNatGuaranteedNatPoolStatsSessionDelete ConfdString,
        affirmedServicesNatServiceNatGuaranteedNatPoolStatsSessionIpAllocationSuccess ConfdString,
        affirmedServicesNatServiceNatGuaranteedNatPoolStatsSessionIpAllocationFailure ConfdString,
        affirmedServicesNatServiceNatGuaranteedNatPoolStatsSessionIpDeallocation ConfdString,
        affirmedServicesNatServiceNatGuaranteedNatPoolStatsSessionPortChunkAllocationSuccess ConfdString,
        affirmedServicesNatServiceNatGuaranteedNatPoolStatsSessionPortChunkAllocationFailure ConfdString,
        affirmedServicesNatServiceNatGuaranteedNatPoolStatsSessionPortChunkDeallocation ConfdString,
        affirmedServicesNatServiceNatGuaranteedNatPoolStatsSessionCount ConfdString,
        affirmedServicesNatServiceNatGuaranteedNatPoolStatsSessionCapacityAvailable ConfdString,
        affirmedServicesNatServiceNatGuaranteedNatPoolStatsResourceUtilizationIp ConfdString,
        affirmedServicesNatServiceNatGuaranteedNatPoolStatsResourceUtilizationPortChunk ConfdString,
        affirmedServicesNatServiceNatGuaranteedNatPoolStatsResourceUtilizationSession ConfdString,
        affirmedServicesNatServiceNatGuaranteedNatPoolStatsResourceInUseIp ConfdString,
        affirmedServicesNatServiceNatGuaranteedNatPoolStatsResourceInUsePortChunk ConfdString,
        affirmedServicesNatServiceNatGuaranteedNatPoolStatsAllocFailureOutOfResources ConfdString,
        affirmedServicesNatServiceNatGuaranteedNatPoolStatsAllocFailureNoSubPool ConfdString,
        affirmedServicesNatServiceNatGuaranteedNatPoolStatsAllocFailureSubPoolOutOfService ConfdString,
        affirmedServicesNatServiceNatGuaranteedNatPoolStatsAllocFailureMaxChunksExceeded ConfdString,
        affirmedServicesNatServiceNatGuaranteedNatPoolStatsConnectionsCreated ConfdString,
        affirmedServicesNatServiceNatGuaranteedNatPoolStatsConnectionsDeleted ConfdString,
        affirmedServicesNatServiceNatGuaranteedNatPoolStatsConnectionCreateFailure ConfdString,
        affirmedServicesNatServiceNatGuaranteedNatPoolStatsConnectionCount ConfdString,
        affirmedServicesNatServiceNatGuaranteedNatPoolStatsConnectionAllocateNatPortSuccess ConfdString,
        affirmedServicesNatServiceNatGuaranteedNatPoolStatsConnectionAllocateNatPortFailure ConfdString,
        affirmedServicesNatServiceNatGuaranteedNatPoolStatsConnectionDeallocateNatPortSuccess ConfdString,
        affirmedServicesNatServiceNatGuaranteedNatPoolStatsConnectionCreateFailureNatPortUnavailable ConfdString,
        affirmedServicesNatServiceNatGuaranteedNatPoolStatsAllocFailureNPTv6 ConfdString,
        affirmedServicesNatServiceNatGuaranteedNatPoolStatsPerSessionPortChunksHighWatermark ConfdString
    }

affirmedServicesNatServiceNatGuaranteedNatPoolStatsNetworkContext OBJECT-TYPE
    SYNTAX      String
    MAX-ACCESS  not-accessible
    STATUS      current
    DESCRIPTION "networkcontext"
    ::= { affirmedServicesNatServiceNatGuaranteedNatPoolStatsEntry 1 }

affirmedServicesNatServiceNatGuaranteedNatPoolStatsPoolName OBJECT-TYPE
    SYNTAX      String
    MAX-ACCESS  not-accessible
    STATUS      current
    DESCRIPTION "NAT pool"
    ::= { affirmedServicesNatServiceNatGuaranteedNatPoolStatsEntry 2 }

affirmedServicesNatServiceNatGuaranteedNatPoolStatsSessionCreateFailure OBJECT-TYPE
    SYNTAX      ConfdString
    MAX-ACCESS  read-only
    STATUS      current
    DESCRIPTION "Number of sessions for which NAT resource(IP or port chunks) allocation failed"
    ::= { affirmedServicesNatServiceNatGuaranteedNatPoolStatsEntry 3 }

affirmedServicesNatServiceNatGuaranteedNatPoolStatsSessionCreateSuccess OBJECT-TYPE
    SYNTAX      ConfdString
    MAX-ACCESS  read-only
    STATUS      current
    DESCRIPTION "Number of sessions successfully allocated NAT resources"
    ::= { affirmedServicesNatServiceNatGuaranteedNatPoolStatsEntry 4 }

affirmedServicesNatServiceNatGuaranteedNatPoolStatsSessionDelete OBJECT-TYPE
    SYNTAX      ConfdString
    MAX-ACCESS  read-only
    STATUS      current
    DESCRIPTION "Number of session delete requests processed"
    ::= { affirmedServicesNatServiceNatGuaranteedNatPoolStatsEntry 5 }

affirmedServicesNatServiceNatGuaranteedNatPoolStatsSessionIpAllocationSuccess OBJECT-TYPE
    SYNTAX      ConfdString
    MAX-ACCESS  read-only
    STATUS      current
    DESCRIPTION "Number of NAT IP's allocated successfully"
    ::= { affirmedServicesNatServiceNatGuaranteedNatPoolStatsEntry 6 }

affirmedServicesNatServiceNatGuaranteedNatPoolStatsSessionIpAllocationFailure OBJECT-TYPE
    SYNTAX      ConfdString
    MAX-ACCESS  read-only
    STATUS      current
    DESCRIPTION "Number of NAT IP allocation failure"
    ::= { affirmedServicesNatServiceNatGuaranteedNatPoolStatsEntry 7 }

affirmedServicesNatServiceNatGuaranteedNatPoolStatsSessionIpDeallocation OBJECT-TYPE
    SYNTAX      ConfdString
    MAX-ACCESS  read-only
    STATUS      current
    DESCRIPTION "Number of NAT IP deallocated"
    ::= { affirmedServicesNatServiceNatGuaranteedNatPoolStatsEntry 8 }

affirmedServicesNatServiceNatGuaranteedNatPoolStatsSessionPortChunkAllocationSuccess OBJECT-TYPE
    SYNTAX      ConfdString
    MAX-ACCESS  read-only
    STATUS      current
    DESCRIPTION "Number of Port chunks allocated successfully"
    ::= { affirmedServicesNatServiceNatGuaranteedNatPoolStatsEntry 9 }

affirmedServicesNatServiceNatGuaranteedNatPoolStatsSessionPortChunkAllocationFailure OBJECT-TYPE
    SYNTAX      ConfdString
    MAX-ACCESS  read-only
    STATUS      current
    DESCRIPTION "Number of Port chunk allocation failure"
    ::= { affirmedServicesNatServiceNatGuaranteedNatPoolStatsEntry 10 }

affirmedServicesNatServiceNatGuaranteedNatPoolStatsSessionPortChunkDeallocation OBJECT-TYPE
    SYNTAX      ConfdString
    MAX-ACCESS  read-only
    STATUS      current
    DESCRIPTION "Number of Port chunks deallocated"
    ::= { affirmedServicesNatServiceNatGuaranteedNatPoolStatsEntry 11 }

affirmedServicesNatServiceNatGuaranteedNatPoolStatsSessionCount OBJECT-TYPE
    SYNTAX      ConfdString
    MAX-ACCESS  read-only
    STATUS      current
    DESCRIPTION "Total number of sessions currently using NAT resources from this nat-pool"
    ::= { affirmedServicesNatServiceNatGuaranteedNatPoolStatsEntry 12 }

affirmedServicesNatServiceNatGuaranteedNatPoolStatsSessionCapacityAvailable OBJECT-TYPE
    SYNTAX      ConfdString
    MAX-ACCESS  read-only
    STATUS      current
    DESCRIPTION "Number of additional sessions possible"
    ::= { affirmedServicesNatServiceNatGuaranteedNatPoolStatsEntry 13 }

affirmedServicesNatServiceNatGuaranteedNatPoolStatsResourceUtilizationIp OBJECT-TYPE
    SYNTAX      ConfdString
    MAX-ACCESS  read-only
    STATUS      current
    DESCRIPTION "Percentage utilization of the NAT IP resources"
    ::= { affirmedServicesNatServiceNatGuaranteedNatPoolStatsEntry 14 }

affirmedServicesNatServiceNatGuaranteedNatPoolStatsResourceUtilizationPortChunk OBJECT-TYPE
    SYNTAX      ConfdString
    MAX-ACCESS  read-only
    STATUS      current
    DESCRIPTION "Percentage utilization of NAT Port chunk resources"
    ::= { affirmedServicesNatServiceNatGuaranteedNatPoolStatsEntry 15 }

affirmedServicesNatServiceNatGuaranteedNatPoolStatsResourceUtilizationSession OBJECT-TYPE
    SYNTAX      ConfdString
    MAX-ACCESS  read-only
    STATUS      current
    DESCRIPTION "Percentage utilization of the NAT resources based on current session count"
    ::= { affirmedServicesNatServiceNatGuaranteedNatPoolStatsEntry 16 }

affirmedServicesNatServiceNatGuaranteedNatPoolStatsResourceInUseIp OBJECT-TYPE
    SYNTAX      ConfdString
    MAX-ACCESS  read-only
    STATUS      current
    DESCRIPTION "Number of IPs currently in-use"
    ::= { affirmedServicesNatServiceNatGuaranteedNatPoolStatsEntry 17 }

affirmedServicesNatServiceNatGuaranteedNatPoolStatsResourceInUsePortChunk OBJECT-TYPE
    SYNTAX      ConfdString
    MAX-ACCESS  read-only
    STATUS      current
    DESCRIPTION "Number of Port chunks currently in-use"
    ::= { affirmedServicesNatServiceNatGuaranteedNatPoolStatsEntry 18 }

affirmedServicesNatServiceNatGuaranteedNatPoolStatsAllocFailureOutOfResources OBJECT-TYPE
    SYNTAX      ConfdString
    MAX-ACCESS  read-only
    STATUS      current
    DESCRIPTION "Number of allocation failures due to nat-pool not having enough IP or port chunks"
    ::= { affirmedServicesNatServiceNatGuaranteedNatPoolStatsEntry 19 }

affirmedServicesNatServiceNatGuaranteedNatPoolStatsAllocFailureNoSubPool OBJECT-TYPE
    SYNTAX      ConfdString
    MAX-ACCESS  read-only
    STATUS      current
    DESCRIPTION "Number of allocation failures due to nat-pool not having any sub-pool configured"
    ::= { affirmedServicesNatServiceNatGuaranteedNatPoolStatsEntry 20 }

affirmedServicesNatServiceNatGuaranteedNatPoolStatsAllocFailureSubPoolOutOfService OBJECT-TYPE
    SYNTAX      ConfdString
    MAX-ACCESS  read-only
    STATUS      current
    DESCRIPTION "Number of allocation failure due to sub-pool being admin disabled"
    ::= { affirmedServicesNatServiceNatGuaranteedNatPoolStatsEntry 21 }

affirmedServicesNatServiceNatGuaranteedNatPoolStatsAllocFailureMaxChunksExceeded OBJECT-TYPE
    SYNTAX      ConfdString
    MAX-ACCESS  read-only
    STATUS      current
    DESCRIPTION "Count of port chunk allocation failures due to session already using max-chunks-per-session port chunks from the nat-pool"
    ::= { affirmedServicesNatServiceNatGuaranteedNatPoolStatsEntry 22 }

affirmedServicesNatServiceNatGuaranteedNatPoolStatsConnectionsCreated OBJECT-TYPE
    SYNTAX      ConfdString
    MAX-ACCESS  read-only
    STATUS      current
    DESCRIPTION "Number of nat connections created"
    ::= { affirmedServicesNatServiceNatGuaranteedNatPoolStatsEntry 23 }

affirmedServicesNatServiceNatGuaranteedNatPoolStatsConnectionsDeleted OBJECT-TYPE
    SYNTAX      ConfdString
    MAX-ACCESS  read-only
    STATUS      current
    DESCRIPTION "Number of nat connections deleted"
    ::= { affirmedServicesNatServiceNatGuaranteedNatPoolStatsEntry 24 }

affirmedServicesNatServiceNatGuaranteedNatPoolStatsConnectionCreateFailure OBJECT-TYPE
    SYNTAX      ConfdString
    MAX-ACCESS  read-only
    STATUS      current
    DESCRIPTION "Number of nat connection failures"
    ::= { affirmedServicesNatServiceNatGuaranteedNatPoolStatsEntry 25 }

affirmedServicesNatServiceNatGuaranteedNatPoolStatsConnectionCount OBJECT-TYPE
    SYNTAX      ConfdString
    MAX-ACCESS  read-only
    STATUS      current
    DESCRIPTION "Number of connections currently using the nat-pool"
    ::= { affirmedServicesNatServiceNatGuaranteedNatPoolStatsEntry 26 }

affirmedServicesNatServiceNatGuaranteedNatPoolStatsConnectionAllocateNatPortSuccess OBJECT-TYPE
    SYNTAX      ConfdString
    MAX-ACCESS  read-only
    STATUS      current
    DESCRIPTION "Number of nat port allocated successfully"
    ::= { affirmedServicesNatServiceNatGuaranteedNatPoolStatsEntry 27 }

affirmedServicesNatServiceNatGuaranteedNatPoolStatsConnectionAllocateNatPortFailure OBJECT-TYPE
    SYNTAX      ConfdString
    MAX-ACCESS  read-only
    STATUS      current
    DESCRIPTION "Number of nat port allocation failure"
    ::= { affirmedServicesNatServiceNatGuaranteedNatPoolStatsEntry 28 }

affirmedServicesNatServiceNatGuaranteedNatPoolStatsConnectionDeallocateNatPortSuccess OBJECT-TYPE
    SYNTAX      ConfdString
    MAX-ACCESS  read-only
    STATUS      current
    DESCRIPTION "Number of nat port deallocate success"
    ::= { affirmedServicesNatServiceNatGuaranteedNatPoolStatsEntry 29 }

affirmedServicesNatServiceNatGuaranteedNatPoolStatsConnectionCreateFailureNatPortUnavailable OBJECT-TYPE
    SYNTAX      ConfdString
    MAX-ACCESS  read-only
    STATUS      current
    DESCRIPTION "Number of connection create failures due to non-availability of nat port"
    ::= { affirmedServicesNatServiceNatGuaranteedNatPoolStatsEntry 30 }

affirmedServicesNatServiceNatGuaranteedNatPoolStatsAllocFailureNPTv6 OBJECT-TYPE
    SYNTAX      ConfdString
    MAX-ACCESS  read-only
    STATUS      current
    DESCRIPTION "Number of sessions failed for NPTv6"
    ::= { affirmedServicesNatServiceNatGuaranteedNatPoolStatsEntry 31 }

affirmedServicesNatServiceNatGuaranteedNatPoolStatsPerSessionPortChunksHighWatermark OBJECT-TYPE
    SYNTAX      ConfdString
    MAX-ACCESS  read-only
    STATUS      current
    DESCRIPTION "Highest port chunk allocated to a session"
    ::= { affirmedServicesNatServiceNatGuaranteedNatPoolStatsEntry 32 }

affirmedServicesNatServiceNatGuaranteedSubPoolStatsTable OBJECT-TYPE
    SYNTAX      SEQUENCE OF AffirmedServicesNatServiceNatGuaranteedSubPoolStatsEntry
    MAX-ACCESS  not-accessible
    STATUS      current
    DESCRIPTION ""
    ::= { affirmedServicesNatServiceNatGuaranteed 2 }

affirmedServicesNatServiceNatGuaranteedSubPoolStatsEntry OBJECT-TYPE
    SYNTAX      AffirmedServicesNatServiceNatGuaranteedSubPoolStatsEntry
    MAX-ACCESS  not-accessible
    STATUS      current
    DESCRIPTION ""
    INDEX { affirmedServicesNatServiceNatGuaranteedSubPoolStatsNetworkContext, affirmedServicesNatServiceNatGuaranteedSubPoolStatsPoolName, affirmedServicesNatServiceNatGuaranteedSubPoolStatsSubPoolName }
        ::= { affirmedServicesNatServiceNatGuaranteedSubPoolStatsTable 1 }

AffirmedServicesNatServiceNatGuaranteedSubPoolStatsEntry ::=
    SEQUENCE {
        affirmedServicesNatServiceNatGuaranteedSubPoolStatsNetworkContext String,
        affirmedServicesNatServiceNatGuaranteedSubPoolStatsPoolName String,
        affirmedServicesNatServiceNatGuaranteedSubPoolStatsSubPoolName String,
        affirmedServicesNatServiceNatGuaranteedSubPoolStatsSessionCreateFailure ConfdString,
        affirmedServicesNatServiceNatGuaranteedSubPoolStatsSessionCreateSuccess ConfdString,
        affirmedServicesNatServiceNatGuaranteedSubPoolStatsSessionDelete ConfdString,
        affirmedServicesNatServiceNatGuaranteedSubPoolStatsSessionIpAllocationSuccess ConfdString,
        affirmedServicesNatServiceNatGuaranteedSubPoolStatsSessionIpAllocationFailure ConfdString,
        affirmedServicesNatServiceNatGuaranteedSubPoolStatsSessionIpDeallocation ConfdString,
        affirmedServicesNatServiceNatGuaranteedSubPoolStatsSessionPortChunkAllocationSuccess ConfdString,
        affirmedServicesNatServiceNatGuaranteedSubPoolStatsSessionPortChunkAllocationFailure ConfdString,
        affirmedServicesNatServiceNatGuaranteedSubPoolStatsSessionPortChunkDeallocation ConfdString,
        affirmedServicesNatServiceNatGuaranteedSubPoolStatsSessionCount ConfdString,
        affirmedServicesNatServiceNatGuaranteedSubPoolStatsSessionCapacityAvailable ConfdString,
        affirmedServicesNatServiceNatGuaranteedSubPoolStatsResourceUtilizationIp ConfdString,
        affirmedServicesNatServiceNatGuaranteedSubPoolStatsResourceUtilizationPortChunk ConfdString,
        affirmedServicesNatServiceNatGuaranteedSubPoolStatsResourceUtilizationSession ConfdString,
        affirmedServicesNatServiceNatGuaranteedSubPoolStatsResourceInUseIp ConfdString,
        affirmedServicesNatServiceNatGuaranteedSubPoolStatsResourceInUsePortChunk ConfdString,
        affirmedServicesNatServiceNatGuaranteedSubPoolStatsAllocFailureOutOfPortChunk ConfdString,
        affirmedServicesNatServiceNatGuaranteedSubPoolStatsAllocFailureNatRatioExceeded ConfdString,
        affirmedServicesNatServiceNatGuaranteedSubPoolStatsConnectionsCreated ConfdString,
        affirmedServicesNatServiceNatGuaranteedSubPoolStatsConnectionsDeleted ConfdString,
        affirmedServicesNatServiceNatGuaranteedSubPoolStatsConnectionCreateFailure ConfdString,
        affirmedServicesNatServiceNatGuaranteedSubPoolStatsConnectionCount ConfdString,
        affirmedServicesNatServiceNatGuaranteedSubPoolStatsConnectionAllocateNatPortSuccess ConfdString,
        affirmedServicesNatServiceNatGuaranteedSubPoolStatsConnectionAllocateNatPortFailure ConfdString,
        affirmedServicesNatServiceNatGuaranteedSubPoolStatsConnectionDeallocateNatPortSuccess ConfdString,
        affirmedServicesNatServiceNatGuaranteedSubPoolStatsConnectionCreateFailureNatPortUnavailable ConfdString
    }

affirmedServicesNatServiceNatGuaranteedSubPoolStatsNetworkContext OBJECT-TYPE
    SYNTAX      String
    MAX-ACCESS  not-accessible
    STATUS      current
    DESCRIPTION "networkcontext"
    ::= { affirmedServicesNatServiceNatGuaranteedSubPoolStatsEntry 1 }

affirmedServicesNatServiceNatGuaranteedSubPoolStatsPoolName OBJECT-TYPE
    SYNTAX      String
    MAX-ACCESS  not-accessible
    STATUS      current
    DESCRIPTION "NAT pool name"
    ::= { affirmedServicesNatServiceNatGuaranteedSubPoolStatsEntry 2 }

affirmedServicesNatServiceNatGuaranteedSubPoolStatsSubPoolName OBJECT-TYPE
    SYNTAX      String
    MAX-ACCESS  not-accessible
    STATUS      current
    DESCRIPTION "subpool name"
    ::= { affirmedServicesNatServiceNatGuaranteedSubPoolStatsEntry 3 }

affirmedServicesNatServiceNatGuaranteedSubPoolStatsSessionCreateFailure OBJECT-TYPE
    SYNTAX      ConfdString
    MAX-ACCESS  read-only
    STATUS      current
    DESCRIPTION "Number of sessions for which NAT resource(IP or port chunks) allocation failed"
    ::= { affirmedServicesNatServiceNatGuaranteedSubPoolStatsEntry 4 }

affirmedServicesNatServiceNatGuaranteedSubPoolStatsSessionCreateSuccess OBJECT-TYPE
    SYNTAX      ConfdString
    MAX-ACCESS  read-only
    STATUS      current
    DESCRIPTION "Number of sessions successfully allocated NAT resources"
    ::= { affirmedServicesNatServiceNatGuaranteedSubPoolStatsEntry 5 }

affirmedServicesNatServiceNatGuaranteedSubPoolStatsSessionDelete OBJECT-TYPE
    SYNTAX      ConfdString
    MAX-ACCESS  read-only
    STATUS      current
    DESCRIPTION "Number of session delete requests processed"
    ::= { affirmedServicesNatServiceNatGuaranteedSubPoolStatsEntry 6 }

affirmedServicesNatServiceNatGuaranteedSubPoolStatsSessionIpAllocationSuccess OBJECT-TYPE
    SYNTAX      ConfdString
    MAX-ACCESS  read-only
    STATUS      current
    DESCRIPTION "Number of NAT IP's allocated successfully"
    ::= { affirmedServicesNatServiceNatGuaranteedSubPoolStatsEntry 7 }

affirmedServicesNatServiceNatGuaranteedSubPoolStatsSessionIpAllocationFailure OBJECT-TYPE
    SYNTAX      ConfdString
    MAX-ACCESS  read-only
    STATUS      current
    DESCRIPTION "Number of NAT IP allocation failure"
    ::= { affirmedServicesNatServiceNatGuaranteedSubPoolStatsEntry 8 }

affirmedServicesNatServiceNatGuaranteedSubPoolStatsSessionIpDeallocation OBJECT-TYPE
    SYNTAX      ConfdString
    MAX-ACCESS  read-only
    STATUS      current
    DESCRIPTION "Number of NAT IP deallocated"
    ::= { affirmedServicesNatServiceNatGuaranteedSubPoolStatsEntry 9 }

affirmedServicesNatServiceNatGuaranteedSubPoolStatsSessionPortChunkAllocationSuccess OBJECT-TYPE
    SYNTAX      ConfdString
    MAX-ACCESS  read-only
    STATUS      current
    DESCRIPTION "Number of Port chunks allocated successfully"
    ::= { affirmedServicesNatServiceNatGuaranteedSubPoolStatsEntry 10 }

affirmedServicesNatServiceNatGuaranteedSubPoolStatsSessionPortChunkAllocationFailure OBJECT-TYPE
    SYNTAX      ConfdString
    MAX-ACCESS  read-only
    STATUS      current
    DESCRIPTION "Number of Port chunk allocation failure"
    ::= { affirmedServicesNatServiceNatGuaranteedSubPoolStatsEntry 11 }

affirmedServicesNatServiceNatGuaranteedSubPoolStatsSessionPortChunkDeallocation OBJECT-TYPE
    SYNTAX      ConfdString
    MAX-ACCESS  read-only
    STATUS      current
    DESCRIPTION "Number of Port chunks deallocated"
    ::= { affirmedServicesNatServiceNatGuaranteedSubPoolStatsEntry 12 }

affirmedServicesNatServiceNatGuaranteedSubPoolStatsSessionCount OBJECT-TYPE
    SYNTAX      ConfdString
    MAX-ACCESS  read-only
    STATUS      current
    DESCRIPTION "Total number of sessions currently using NAT resources from this nat-pool"
    ::= { affirmedServicesNatServiceNatGuaranteedSubPoolStatsEntry 13 }

affirmedServicesNatServiceNatGuaranteedSubPoolStatsSessionCapacityAvailable OBJECT-TYPE
    SYNTAX      ConfdString
    MAX-ACCESS  read-only
    STATUS      current
    DESCRIPTION "Number of additional sessions possible"
    ::= { affirmedServicesNatServiceNatGuaranteedSubPoolStatsEntry 14 }

affirmedServicesNatServiceNatGuaranteedSubPoolStatsResourceUtilizationIp OBJECT-TYPE
    SYNTAX      ConfdString
    MAX-ACCESS  read-only
    STATUS      current
    DESCRIPTION "Percentage utilization of the NAT IP resources"
    ::= { affirmedServicesNatServiceNatGuaranteedSubPoolStatsEntry 15 }

affirmedServicesNatServiceNatGuaranteedSubPoolStatsResourceUtilizationPortChunk OBJECT-TYPE
    SYNTAX      ConfdString
    MAX-ACCESS  read-only
    STATUS      current
    DESCRIPTION "Percentage utilization of NAT Port chunk resources"
    ::= { affirmedServicesNatServiceNatGuaranteedSubPoolStatsEntry 16 }

affirmedServicesNatServiceNatGuaranteedSubPoolStatsResourceUtilizationSession OBJECT-TYPE
    SYNTAX      ConfdString
    MAX-ACCESS  read-only
    STATUS      current
    DESCRIPTION "Percentage utilization of the NAT resources based on current session count"
    ::= { affirmedServicesNatServiceNatGuaranteedSubPoolStatsEntry 17 }

affirmedServicesNatServiceNatGuaranteedSubPoolStatsResourceInUseIp OBJECT-TYPE
    SYNTAX      ConfdString
    MAX-ACCESS  read-only
    STATUS      current
    DESCRIPTION "Number of IPs currently in-use"
    ::= { affirmedServicesNatServiceNatGuaranteedSubPoolStatsEntry 18 }

affirmedServicesNatServiceNatGuaranteedSubPoolStatsResourceInUsePortChunk OBJECT-TYPE
    SYNTAX      ConfdString
    MAX-ACCESS  read-only
    STATUS      current
    DESCRIPTION "Number of Port chunks currently in-use"
    ::= { affirmedServicesNatServiceNatGuaranteedSubPoolStatsEntry 19 }

affirmedServicesNatServiceNatGuaranteedSubPoolStatsAllocFailureOutOfPortChunk OBJECT-TYPE
    SYNTAX      ConfdString
    MAX-ACCESS  read-only
    STATUS      current
    DESCRIPTION "Count of port chunk allocation failures due to IP address not having enough port chunks"
    ::= { affirmedServicesNatServiceNatGuaranteedSubPoolStatsEntry 20 }

affirmedServicesNatServiceNatGuaranteedSubPoolStatsAllocFailureNatRatioExceeded OBJECT-TYPE
    SYNTAX      ConfdString
    MAX-ACCESS  read-only
    STATUS      current
    DESCRIPTION "Count of port chunk allocation failures due to number of sessions being catered by IP address exceeding max-users-per-NAT-IP"
    ::= { affirmedServicesNatServiceNatGuaranteedSubPoolStatsEntry 21 }

affirmedServicesNatServiceNatGuaranteedSubPoolStatsConnectionsCreated OBJECT-TYPE
    SYNTAX      ConfdString
    MAX-ACCESS  read-only
    STATUS      current
    DESCRIPTION "Number of nat connections created"
    ::= { affirmedServicesNatServiceNatGuaranteedSubPoolStatsEntry 22 }

affirmedServicesNatServiceNatGuaranteedSubPoolStatsConnectionsDeleted OBJECT-TYPE
    SYNTAX      ConfdString
    MAX-ACCESS  read-only
    STATUS      current
    DESCRIPTION "Number of nat connections deleted"
    ::= { affirmedServicesNatServiceNatGuaranteedSubPoolStatsEntry 23 }

affirmedServicesNatServiceNatGuaranteedSubPoolStatsConnectionCreateFailure OBJECT-TYPE
    SYNTAX      ConfdString
    MAX-ACCESS  read-only
    STATUS      current
    DESCRIPTION "Number of nat connection failures"
    ::= { affirmedServicesNatServiceNatGuaranteedSubPoolStatsEntry 24 }

affirmedServicesNatServiceNatGuaranteedSubPoolStatsConnectionCount OBJECT-TYPE
    SYNTAX      ConfdString
    MAX-ACCESS  read-only
    STATUS      current
    DESCRIPTION "Number of connections currently using the nat-pool"
    ::= { affirmedServicesNatServiceNatGuaranteedSubPoolStatsEntry 25 }

affirmedServicesNatServiceNatGuaranteedSubPoolStatsConnectionAllocateNatPortSuccess OBJECT-TYPE
    SYNTAX      ConfdString
    MAX-ACCESS  read-only
    STATUS      current
    DESCRIPTION "Number of nat port allocated successfully"
    ::= { affirmedServicesNatServiceNatGuaranteedSubPoolStatsEntry 26 }

affirmedServicesNatServiceNatGuaranteedSubPoolStatsConnectionAllocateNatPortFailure OBJECT-TYPE
    SYNTAX      ConfdString
    MAX-ACCESS  read-only
    STATUS      current
    DESCRIPTION "Number of nat port allocation failure"
    ::= { affirmedServicesNatServiceNatGuaranteedSubPoolStatsEntry 27 }

affirmedServicesNatServiceNatGuaranteedSubPoolStatsConnectionDeallocateNatPortSuccess OBJECT-TYPE
    SYNTAX      ConfdString
    MAX-ACCESS  read-only
    STATUS      current
    DESCRIPTION "Number of nat port deallocate success"
    ::= { affirmedServicesNatServiceNatGuaranteedSubPoolStatsEntry 28 }

affirmedServicesNatServiceNatGuaranteedSubPoolStatsConnectionCreateFailureNatPortUnavailable OBJECT-TYPE
    SYNTAX      ConfdString
    MAX-ACCESS  read-only
    STATUS      current
    DESCRIPTION "Number of connection create failures due to non-availability of nat port"
    ::= { affirmedServicesNatServiceNatGuaranteedSubPoolStatsEntry 29 }

affirmedServicesNatServiceNatDeterministicNatPoolStatsTable OBJECT-TYPE
    SYNTAX      SEQUENCE OF AffirmedServicesNatServiceNatDeterministicNatPoolStatsEntry
    MAX-ACCESS  not-accessible
    STATUS      current
    DESCRIPTION ""
    ::= { affirmedServicesNatServiceNatDeterministic 1 }

affirmedServicesNatServiceNatDeterministicNatPoolStatsEntry OBJECT-TYPE
    SYNTAX      AffirmedServicesNatServiceNatDeterministicNatPoolStatsEntry
    MAX-ACCESS  not-accessible
    STATUS      current
    DESCRIPTION ""
    INDEX { affirmedServicesNatServiceNatDeterministicNatPoolStatsNetworkContext, affirmedServicesNatServiceNatDeterministicNatPoolStatsPoolName }
        ::= { affirmedServicesNatServiceNatDeterministicNatPoolStatsTable 1 }

AffirmedServicesNatServiceNatDeterministicNatPoolStatsEntry ::=
    SEQUENCE {
        affirmedServicesNatServiceNatDeterministicNatPoolStatsNetworkContext String,
        affirmedServicesNatServiceNatDeterministicNatPoolStatsPoolName String,
        affirmedServicesNatServiceNatDeterministicNatPoolStatsSessionCreateFailure ConfdString,
        affirmedServicesNatServiceNatDeterministicNatPoolStatsSessionCreateSuccess ConfdString,
        affirmedServicesNatServiceNatDeterministicNatPoolStatsSessionDelete ConfdString,
        affirmedServicesNatServiceNatDeterministicNatPoolStatsSessionIpAllocationSuccess ConfdString,
        affirmedServicesNatServiceNatDeterministicNatPoolStatsSessionIpAllocationFailure ConfdString,
        affirmedServicesNatServiceNatDeterministicNatPoolStatsSessionIpDeallocation ConfdString,
        affirmedServicesNatServiceNatDeterministicNatPoolStatsSessionPortChunkAllocationSuccess ConfdString,
        affirmedServicesNatServiceNatDeterministicNatPoolStatsSessionPortChunkAllocationFailure ConfdString,
        affirmedServicesNatServiceNatDeterministicNatPoolStatsSessionPortChunkDeallocation ConfdString,
        affirmedServicesNatServiceNatDeterministicNatPoolStatsSessionCount ConfdString,
        affirmedServicesNatServiceNatDeterministicNatPoolStatsSessionCapacityAvailable ConfdString,
        affirmedServicesNatServiceNatDeterministicNatPoolStatsResourceUtilizationIp ConfdString,
        affirmedServicesNatServiceNatDeterministicNatPoolStatsResourceUtilizationPortChunk ConfdString,
        affirmedServicesNatServiceNatDeterministicNatPoolStatsResourceUtilizationSession ConfdString,
        affirmedServicesNatServiceNatDeterministicNatPoolStatsResourceInUseIp ConfdString,
        affirmedServicesNatServiceNatDeterministicNatPoolStatsResourceInUsePortChunk ConfdString,
        affirmedServicesNatServiceNatDeterministicNatPoolStatsAllocFailureOutOfResources ConfdString,
        affirmedServicesNatServiceNatDeterministicNatPoolStatsAllocFailureNoSubPool ConfdString,
        affirmedServicesNatServiceNatDeterministicNatPoolStatsAllocFailureSubPoolOutOfService ConfdString,
        affirmedServicesNatServiceNatDeterministicNatPoolStatsAllocFailureMaxChunksExceeded ConfdString,
        affirmedServicesNatServiceNatDeterministicNatPoolStatsConnectionsCreated ConfdString,
        affirmedServicesNatServiceNatDeterministicNatPoolStatsConnectionsDeleted ConfdString,
        affirmedServicesNatServiceNatDeterministicNatPoolStatsConnectionCreateFailure ConfdString,
        affirmedServicesNatServiceNatDeterministicNatPoolStatsConnectionCount ConfdString,
        affirmedServicesNatServiceNatDeterministicNatPoolStatsConnectionAllocateNatPortSuccess ConfdString,
        affirmedServicesNatServiceNatDeterministicNatPoolStatsConnectionAllocateNatPortFailure ConfdString,
        affirmedServicesNatServiceNatDeterministicNatPoolStatsConnectionDeallocateNatPortSuccess ConfdString,
        affirmedServicesNatServiceNatDeterministicNatPoolStatsConnectionCreateFailureNatPortUnavailable ConfdString,
        affirmedServicesNatServiceNatDeterministicNatPoolStatsAllocFailureNPTv6 ConfdString,
        affirmedServicesNatServiceNatDeterministicNatPoolStatsPerSessionPortChunksHighWatermark ConfdString
    }

affirmedServicesNatServiceNatDeterministicNatPoolStatsNetworkContext OBJECT-TYPE
    SYNTAX      String
    MAX-ACCESS  not-accessible
    STATUS      current
    DESCRIPTION "networkcontext"
    ::= { affirmedServicesNatServiceNatDeterministicNatPoolStatsEntry 1 }

affirmedServicesNatServiceNatDeterministicNatPoolStatsPoolName OBJECT-TYPE
    SYNTAX      String
    MAX-ACCESS  not-accessible
    STATUS      current
    DESCRIPTION "NAT pool name"
    ::= { affirmedServicesNatServiceNatDeterministicNatPoolStatsEntry 2 }

affirmedServicesNatServiceNatDeterministicNatPoolStatsSessionCreateFailure OBJECT-TYPE
    SYNTAX      ConfdString
    MAX-ACCESS  read-only
    STATUS      current
    DESCRIPTION "Number of sessions for which NAT resource(IP or port chunks) allocation failed"
    ::= { affirmedServicesNatServiceNatDeterministicNatPoolStatsEntry 3 }

affirmedServicesNatServiceNatDeterministicNatPoolStatsSessionCreateSuccess OBJECT-TYPE
    SYNTAX      ConfdString
    MAX-ACCESS  read-only
    STATUS      current
    DESCRIPTION "Number of sessions successfully allocated NAT resources"
    ::= { affirmedServicesNatServiceNatDeterministicNatPoolStatsEntry 4 }

affirmedServicesNatServiceNatDeterministicNatPoolStatsSessionDelete OBJECT-TYPE
    SYNTAX      ConfdString
    MAX-ACCESS  read-only
    STATUS      current
    DESCRIPTION "Number of session delete requests processed"
    ::= { affirmedServicesNatServiceNatDeterministicNatPoolStatsEntry 5 }

affirmedServicesNatServiceNatDeterministicNatPoolStatsSessionIpAllocationSuccess OBJECT-TYPE
    SYNTAX      ConfdString
    MAX-ACCESS  read-only
    STATUS      current
    DESCRIPTION "Number of NAT IP's allocated successfully"
    ::= { affirmedServicesNatServiceNatDeterministicNatPoolStatsEntry 6 }

affirmedServicesNatServiceNatDeterministicNatPoolStatsSessionIpAllocationFailure OBJECT-TYPE
    SYNTAX      ConfdString
    MAX-ACCESS  read-only
    STATUS      current
    DESCRIPTION "Number of NAT IP allocation failure"
    ::= { affirmedServicesNatServiceNatDeterministicNatPoolStatsEntry 7 }

affirmedServicesNatServiceNatDeterministicNatPoolStatsSessionIpDeallocation OBJECT-TYPE
    SYNTAX      ConfdString
    MAX-ACCESS  read-only
    STATUS      current
    DESCRIPTION "Number of NAT IP deallocated"
    ::= { affirmedServicesNatServiceNatDeterministicNatPoolStatsEntry 8 }

affirmedServicesNatServiceNatDeterministicNatPoolStatsSessionPortChunkAllocationSuccess OBJECT-TYPE
    SYNTAX      ConfdString
    MAX-ACCESS  read-only
    STATUS      current
    DESCRIPTION "Number of Port chunks allocated successfully"
    ::= { affirmedServicesNatServiceNatDeterministicNatPoolStatsEntry 9 }

affirmedServicesNatServiceNatDeterministicNatPoolStatsSessionPortChunkAllocationFailure OBJECT-TYPE
    SYNTAX      ConfdString
    MAX-ACCESS  read-only
    STATUS      current
    DESCRIPTION "Number of Port chunk allocation failure"
    ::= { affirmedServicesNatServiceNatDeterministicNatPoolStatsEntry 10 }

affirmedServicesNatServiceNatDeterministicNatPoolStatsSessionPortChunkDeallocation OBJECT-TYPE
    SYNTAX      ConfdString
    MAX-ACCESS  read-only
    STATUS      current
    DESCRIPTION "Number of Port chunks deallocated"
    ::= { affirmedServicesNatServiceNatDeterministicNatPoolStatsEntry 11 }

affirmedServicesNatServiceNatDeterministicNatPoolStatsSessionCount OBJECT-TYPE
    SYNTAX      ConfdString
    MAX-ACCESS  read-only
    STATUS      current
    DESCRIPTION "Total number of sessions currently using NAT resources from this nat-pool"
    ::= { affirmedServicesNatServiceNatDeterministicNatPoolStatsEntry 12 }

affirmedServicesNatServiceNatDeterministicNatPoolStatsSessionCapacityAvailable OBJECT-TYPE
    SYNTAX      ConfdString
    MAX-ACCESS  read-only
    STATUS      current
    DESCRIPTION "Number of additional sessions possible"
    ::= { affirmedServicesNatServiceNatDeterministicNatPoolStatsEntry 13 }

affirmedServicesNatServiceNatDeterministicNatPoolStatsResourceUtilizationIp OBJECT-TYPE
    SYNTAX      ConfdString
    MAX-ACCESS  read-only
    STATUS      current
    DESCRIPTION "Percentage utilization of the NAT IP resources"
    ::= { affirmedServicesNatServiceNatDeterministicNatPoolStatsEntry 14 }

affirmedServicesNatServiceNatDeterministicNatPoolStatsResourceUtilizationPortChunk OBJECT-TYPE
    SYNTAX      ConfdString
    MAX-ACCESS  read-only
    STATUS      current
    DESCRIPTION "Percentage utilization of NAT Port chunk resources"
    ::= { affirmedServicesNatServiceNatDeterministicNatPoolStatsEntry 15 }

affirmedServicesNatServiceNatDeterministicNatPoolStatsResourceUtilizationSession OBJECT-TYPE
    SYNTAX      ConfdString
    MAX-ACCESS  read-only
    STATUS      current
    DESCRIPTION "Percentage utilization of the NAT resources based on current session count"
    ::= { affirmedServicesNatServiceNatDeterministicNatPoolStatsEntry 16 }

affirmedServicesNatServiceNatDeterministicNatPoolStatsResourceInUseIp OBJECT-TYPE
    SYNTAX      ConfdString
    MAX-ACCESS  read-only
    STATUS      current
    DESCRIPTION "Number of IPs currently in-use"
    ::= { affirmedServicesNatServiceNatDeterministicNatPoolStatsEntry 17 }

affirmedServicesNatServiceNatDeterministicNatPoolStatsResourceInUsePortChunk OBJECT-TYPE
    SYNTAX      ConfdString
    MAX-ACCESS  read-only
    STATUS      current
    DESCRIPTION "Number of Port chunks currently in-use"
    ::= { affirmedServicesNatServiceNatDeterministicNatPoolStatsEntry 18 }

affirmedServicesNatServiceNatDeterministicNatPoolStatsAllocFailureOutOfResources OBJECT-TYPE
    SYNTAX      ConfdString
    MAX-ACCESS  read-only
    STATUS      current
    DESCRIPTION "Number of allocation failures due to nat-pool not having enough IP or port chunks"
    ::= { affirmedServicesNatServiceNatDeterministicNatPoolStatsEntry 19 }

affirmedServicesNatServiceNatDeterministicNatPoolStatsAllocFailureNoSubPool OBJECT-TYPE
    SYNTAX      ConfdString
    MAX-ACCESS  read-only
    STATUS      current
    DESCRIPTION "Number of allocation failures due to nat-pool not having any sub-pool configured"
    ::= { affirmedServicesNatServiceNatDeterministicNatPoolStatsEntry 20 }

affirmedServicesNatServiceNatDeterministicNatPoolStatsAllocFailureSubPoolOutOfService OBJECT-TYPE
    SYNTAX      ConfdString
    MAX-ACCESS  read-only
    STATUS      current
    DESCRIPTION "Number of allocation failure due to sub-pool being admin disabled"
    ::= { affirmedServicesNatServiceNatDeterministicNatPoolStatsEntry 21 }

affirmedServicesNatServiceNatDeterministicNatPoolStatsAllocFailureMaxChunksExceeded OBJECT-TYPE
    SYNTAX      ConfdString
    MAX-ACCESS  read-only
    STATUS      current
    DESCRIPTION "Count of port chunk allocation failures due to session already using max-chunks-per-session port chunks from the nat-pool"
    ::= { affirmedServicesNatServiceNatDeterministicNatPoolStatsEntry 22 }

affirmedServicesNatServiceNatDeterministicNatPoolStatsConnectionsCreated OBJECT-TYPE
    SYNTAX      ConfdString
    MAX-ACCESS  read-only
    STATUS      current
    DESCRIPTION "Number of nat connections created"
    ::= { affirmedServicesNatServiceNatDeterministicNatPoolStatsEntry 23 }

affirmedServicesNatServiceNatDeterministicNatPoolStatsConnectionsDeleted OBJECT-TYPE
    SYNTAX      ConfdString
    MAX-ACCESS  read-only
    STATUS      current
    DESCRIPTION "Number of nat connections deleted"
    ::= { affirmedServicesNatServiceNatDeterministicNatPoolStatsEntry 24 }

affirmedServicesNatServiceNatDeterministicNatPoolStatsConnectionCreateFailure OBJECT-TYPE
    SYNTAX      ConfdString
    MAX-ACCESS  read-only
    STATUS      current
    DESCRIPTION "Number of nat connection failures"
    ::= { affirmedServicesNatServiceNatDeterministicNatPoolStatsEntry 25 }

affirmedServicesNatServiceNatDeterministicNatPoolStatsConnectionCount OBJECT-TYPE
    SYNTAX      ConfdString
    MAX-ACCESS  read-only
    STATUS      current
    DESCRIPTION "Number of connections currently using the nat-pool"
    ::= { affirmedServicesNatServiceNatDeterministicNatPoolStatsEntry 26 }

affirmedServicesNatServiceNatDeterministicNatPoolStatsConnectionAllocateNatPortSuccess OBJECT-TYPE
    SYNTAX      ConfdString
    MAX-ACCESS  read-only
    STATUS      current
    DESCRIPTION "Number of nat port allocated successfully"
    ::= { affirmedServicesNatServiceNatDeterministicNatPoolStatsEntry 27 }

affirmedServicesNatServiceNatDeterministicNatPoolStatsConnectionAllocateNatPortFailure OBJECT-TYPE
    SYNTAX      ConfdString
    MAX-ACCESS  read-only
    STATUS      current
    DESCRIPTION "Number of nat port allocation failure"
    ::= { affirmedServicesNatServiceNatDeterministicNatPoolStatsEntry 28 }

affirmedServicesNatServiceNatDeterministicNatPoolStatsConnectionDeallocateNatPortSuccess OBJECT-TYPE
    SYNTAX      ConfdString
    MAX-ACCESS  read-only
    STATUS      current
    DESCRIPTION "Number of nat port deallocate success"
    ::= { affirmedServicesNatServiceNatDeterministicNatPoolStatsEntry 29 }

affirmedServicesNatServiceNatDeterministicNatPoolStatsConnectionCreateFailureNatPortUnavailable OBJECT-TYPE
    SYNTAX      ConfdString
    MAX-ACCESS  read-only
    STATUS      current
    DESCRIPTION "Number of connection create failures due to non-availability of nat port"
    ::= { affirmedServicesNatServiceNatDeterministicNatPoolStatsEntry 30 }

affirmedServicesNatServiceNatDeterministicNatPoolStatsAllocFailureNPTv6 OBJECT-TYPE
    SYNTAX      ConfdString
    MAX-ACCESS  read-only
    STATUS      current
    DESCRIPTION "Number of sessions failed for NPTv6"
    ::= { affirmedServicesNatServiceNatDeterministicNatPoolStatsEntry 31 }

affirmedServicesNatServiceNatDeterministicNatPoolStatsPerSessionPortChunksHighWatermark OBJECT-TYPE
    SYNTAX      ConfdString
    MAX-ACCESS  read-only
    STATUS      current
    DESCRIPTION "Highest port chunk allocated to a session"
    ::= { affirmedServicesNatServiceNatDeterministicNatPoolStatsEntry 32 }

affirmedServicesNatServiceNatDeterministicSubPoolStatsTable OBJECT-TYPE
    SYNTAX      SEQUENCE OF AffirmedServicesNatServiceNatDeterministicSubPoolStatsEntry
    MAX-ACCESS  not-accessible
    STATUS      current
    DESCRIPTION ""
    ::= { affirmedServicesNatServiceNatDeterministic 2 }

affirmedServicesNatServiceNatDeterministicSubPoolStatsEntry OBJECT-TYPE
    SYNTAX      AffirmedServicesNatServiceNatDeterministicSubPoolStatsEntry
    MAX-ACCESS  not-accessible
    STATUS      current
    DESCRIPTION ""
    INDEX { affirmedServicesNatServiceNatDeterministicSubPoolStatsNetworkContext, affirmedServicesNatServiceNatDeterministicSubPoolStatsPoolName, affirmedServicesNatServiceNatDeterministicSubPoolStatsSubPoolName }
        ::= { affirmedServicesNatServiceNatDeterministicSubPoolStatsTable 1 }

AffirmedServicesNatServiceNatDeterministicSubPoolStatsEntry ::=
    SEQUENCE {
        affirmedServicesNatServiceNatDeterministicSubPoolStatsNetworkContext String,
        affirmedServicesNatServiceNatDeterministicSubPoolStatsPoolName String,
        affirmedServicesNatServiceNatDeterministicSubPoolStatsSubPoolName String,
        affirmedServicesNatServiceNatDeterministicSubPoolStatsSessionCreateFailure ConfdString,
        affirmedServicesNatServiceNatDeterministicSubPoolStatsSessionCreateSuccess ConfdString,
        affirmedServicesNatServiceNatDeterministicSubPoolStatsSessionDelete ConfdString,
        affirmedServicesNatServiceNatDeterministicSubPoolStatsSessionIpAllocationSuccess ConfdString,
        affirmedServicesNatServiceNatDeterministicSubPoolStatsSessionIpAllocationFailure ConfdString,
        affirmedServicesNatServiceNatDeterministicSubPoolStatsSessionIpDeallocation ConfdString,
        affirmedServicesNatServiceNatDeterministicSubPoolStatsSessionPortChunkAllocationSuccess ConfdString,
        affirmedServicesNatServiceNatDeterministicSubPoolStatsSessionPortChunkAllocationFailure ConfdString,
        affirmedServicesNatServiceNatDeterministicSubPoolStatsSessionPortChunkDeallocation ConfdString,
        affirmedServicesNatServiceNatDeterministicSubPoolStatsSessionCount ConfdString,
        affirmedServicesNatServiceNatDeterministicSubPoolStatsSessionCapacityAvailable ConfdString,
        affirmedServicesNatServiceNatDeterministicSubPoolStatsResourceUtilizationIp ConfdString,
        affirmedServicesNatServiceNatDeterministicSubPoolStatsResourceUtilizationPortChunk ConfdString,
        affirmedServicesNatServiceNatDeterministicSubPoolStatsResourceUtilizationSession ConfdString,
        affirmedServicesNatServiceNatDeterministicSubPoolStatsResourceInUseIp ConfdString,
        affirmedServicesNatServiceNatDeterministicSubPoolStatsResourceInUsePortChunk ConfdString,
        affirmedServicesNatServiceNatDeterministicSubPoolStatsAllocFailureOutOfPortChunk ConfdString,
        affirmedServicesNatServiceNatDeterministicSubPoolStatsAllocFailureNatRatioExceeded ConfdString,
        affirmedServicesNatServiceNatDeterministicSubPoolStatsConnectionsCreated ConfdString,
        affirmedServicesNatServiceNatDeterministicSubPoolStatsConnectionsDeleted ConfdString,
        affirmedServicesNatServiceNatDeterministicSubPoolStatsConnectionCreateFailure ConfdString,
        affirmedServicesNatServiceNatDeterministicSubPoolStatsConnectionCount ConfdString,
        affirmedServicesNatServiceNatDeterministicSubPoolStatsConnectionAllocateNatPortSuccess ConfdString,
        affirmedServicesNatServiceNatDeterministicSubPoolStatsConnectionAllocateNatPortFailure ConfdString,
        affirmedServicesNatServiceNatDeterministicSubPoolStatsConnectionDeallocateNatPortSuccess ConfdString,
        affirmedServicesNatServiceNatDeterministicSubPoolStatsConnectionCreateFailureNatPortUnavailable ConfdString
    }

affirmedServicesNatServiceNatDeterministicSubPoolStatsNetworkContext OBJECT-TYPE
    SYNTAX      String
    MAX-ACCESS  not-accessible
    STATUS      current
    DESCRIPTION "network context"
    ::= { affirmedServicesNatServiceNatDeterministicSubPoolStatsEntry 1 }

affirmedServicesNatServiceNatDeterministicSubPoolStatsPoolName OBJECT-TYPE
    SYNTAX      String
    MAX-ACCESS  not-accessible
    STATUS      current
    DESCRIPTION "NAT pool name"
    ::= { affirmedServicesNatServiceNatDeterministicSubPoolStatsEntry 2 }

affirmedServicesNatServiceNatDeterministicSubPoolStatsSubPoolName OBJECT-TYPE
    SYNTAX      String
    MAX-ACCESS  not-accessible
    STATUS      current
    DESCRIPTION "subpool name"
    ::= { affirmedServicesNatServiceNatDeterministicSubPoolStatsEntry 3 }

affirmedServicesNatServiceNatDeterministicSubPoolStatsSessionCreateFailure OBJECT-TYPE
    SYNTAX      ConfdString
    MAX-ACCESS  read-only
    STATUS      current
    DESCRIPTION "Number of sessions for which NAT resource(IP or port chunks) allocation failed"
    ::= { affirmedServicesNatServiceNatDeterministicSubPoolStatsEntry 4 }

affirmedServicesNatServiceNatDeterministicSubPoolStatsSessionCreateSuccess OBJECT-TYPE
    SYNTAX      ConfdString
    MAX-ACCESS  read-only
    STATUS      current
    DESCRIPTION "Number of sessions successfully allocated NAT resources"
    ::= { affirmedServicesNatServiceNatDeterministicSubPoolStatsEntry 5 }

affirmedServicesNatServiceNatDeterministicSubPoolStatsSessionDelete OBJECT-TYPE
    SYNTAX      ConfdString
    MAX-ACCESS  read-only
    STATUS      current
    DESCRIPTION "Number of session delete requests processed"
    ::= { affirmedServicesNatServiceNatDeterministicSubPoolStatsEntry 6 }

affirmedServicesNatServiceNatDeterministicSubPoolStatsSessionIpAllocationSuccess OBJECT-TYPE
    SYNTAX      ConfdString
    MAX-ACCESS  read-only
    STATUS      current
    DESCRIPTION "Number of NAT IP's allocated successfully"
    ::= { affirmedServicesNatServiceNatDeterministicSubPoolStatsEntry 7 }

affirmedServicesNatServiceNatDeterministicSubPoolStatsSessionIpAllocationFailure OBJECT-TYPE
    SYNTAX      ConfdString
    MAX-ACCESS  read-only
    STATUS      current
    DESCRIPTION "Number of NAT IP allocation failure"
    ::= { affirmedServicesNatServiceNatDeterministicSubPoolStatsEntry 8 }

affirmedServicesNatServiceNatDeterministicSubPoolStatsSessionIpDeallocation OBJECT-TYPE
    SYNTAX      ConfdString
    MAX-ACCESS  read-only
    STATUS      current
    DESCRIPTION "Number of NAT IP deallocated"
    ::= { affirmedServicesNatServiceNatDeterministicSubPoolStatsEntry 9 }

affirmedServicesNatServiceNatDeterministicSubPoolStatsSessionPortChunkAllocationSuccess OBJECT-TYPE
    SYNTAX      ConfdString
    MAX-ACCESS  read-only
    STATUS      current
    DESCRIPTION "Number of Port chunks allocated successfully"
    ::= { affirmedServicesNatServiceNatDeterministicSubPoolStatsEntry 10 }

affirmedServicesNatServiceNatDeterministicSubPoolStatsSessionPortChunkAllocationFailure OBJECT-TYPE
    SYNTAX      ConfdString
    MAX-ACCESS  read-only
    STATUS      current
    DESCRIPTION "Number of Port chunk allocation failure"
    ::= { affirmedServicesNatServiceNatDeterministicSubPoolStatsEntry 11 }

affirmedServicesNatServiceNatDeterministicSubPoolStatsSessionPortChunkDeallocation OBJECT-TYPE
    SYNTAX      ConfdString
    MAX-ACCESS  read-only
    STATUS      current
    DESCRIPTION "Number of Port chunks deallocated"
    ::= { affirmedServicesNatServiceNatDeterministicSubPoolStatsEntry 12 }

affirmedServicesNatServiceNatDeterministicSubPoolStatsSessionCount OBJECT-TYPE
    SYNTAX      ConfdString
    MAX-ACCESS  read-only
    STATUS      current
    DESCRIPTION "Total number of sessions currently using NAT resources from this nat-pool"
    ::= { affirmedServicesNatServiceNatDeterministicSubPoolStatsEntry 13 }

affirmedServicesNatServiceNatDeterministicSubPoolStatsSessionCapacityAvailable OBJECT-TYPE
    SYNTAX      ConfdString
    MAX-ACCESS  read-only
    STATUS      current
    DESCRIPTION "Number of additional sessions possible"
    ::= { affirmedServicesNatServiceNatDeterministicSubPoolStatsEntry 14 }

affirmedServicesNatServiceNatDeterministicSubPoolStatsResourceUtilizationIp OBJECT-TYPE
    SYNTAX      ConfdString
    MAX-ACCESS  read-only
    STATUS      current
    DESCRIPTION "Percentage utilization of the NAT IP resources"
    ::= { affirmedServicesNatServiceNatDeterministicSubPoolStatsEntry 15 }

affirmedServicesNatServiceNatDeterministicSubPoolStatsResourceUtilizationPortChunk OBJECT-TYPE
    SYNTAX      ConfdString
    MAX-ACCESS  read-only
    STATUS      current
    DESCRIPTION "Percentage utilization of NAT Port chunk resources"
    ::= { affirmedServicesNatServiceNatDeterministicSubPoolStatsEntry 16 }

affirmedServicesNatServiceNatDeterministicSubPoolStatsResourceUtilizationSession OBJECT-TYPE
    SYNTAX      ConfdString
    MAX-ACCESS  read-only
    STATUS      current
    DESCRIPTION "Percentage utilization of the NAT resources based on current session count"
    ::= { affirmedServicesNatServiceNatDeterministicSubPoolStatsEntry 17 }

affirmedServicesNatServiceNatDeterministicSubPoolStatsResourceInUseIp OBJECT-TYPE
    SYNTAX      ConfdString
    MAX-ACCESS  read-only
    STATUS      current
    DESCRIPTION "Number of IPs currently in-use"
    ::= { affirmedServicesNatServiceNatDeterministicSubPoolStatsEntry 18 }

affirmedServicesNatServiceNatDeterministicSubPoolStatsResourceInUsePortChunk OBJECT-TYPE
    SYNTAX      ConfdString
    MAX-ACCESS  read-only
    STATUS      current
    DESCRIPTION "Number of Port chunks currently in-use"
    ::= { affirmedServicesNatServiceNatDeterministicSubPoolStatsEntry 19 }

affirmedServicesNatServiceNatDeterministicSubPoolStatsAllocFailureOutOfPortChunk OBJECT-TYPE
    SYNTAX      ConfdString
    MAX-ACCESS  read-only
    STATUS      current
    DESCRIPTION "Count of port chunk allocation failures due to IP address not having enough port chunks"
    ::= { affirmedServicesNatServiceNatDeterministicSubPoolStatsEntry 20 }

affirmedServicesNatServiceNatDeterministicSubPoolStatsAllocFailureNatRatioExceeded OBJECT-TYPE
    SYNTAX      ConfdString
    MAX-ACCESS  read-only
    STATUS      current
    DESCRIPTION "Count of port chunk allocation failures due to number of sessions being catered by IP address exceeding max-users-per-NAT-IP"
    ::= { affirmedServicesNatServiceNatDeterministicSubPoolStatsEntry 21 }

affirmedServicesNatServiceNatDeterministicSubPoolStatsConnectionsCreated OBJECT-TYPE
    SYNTAX      ConfdString
    MAX-ACCESS  read-only
    STATUS      current
    DESCRIPTION "Number of nat connections created"
    ::= { affirmedServicesNatServiceNatDeterministicSubPoolStatsEntry 22 }

affirmedServicesNatServiceNatDeterministicSubPoolStatsConnectionsDeleted OBJECT-TYPE
    SYNTAX      ConfdString
    MAX-ACCESS  read-only
    STATUS      current
    DESCRIPTION "Number of nat connections deleted"
    ::= { affirmedServicesNatServiceNatDeterministicSubPoolStatsEntry 23 }

affirmedServicesNatServiceNatDeterministicSubPoolStatsConnectionCreateFailure OBJECT-TYPE
    SYNTAX      ConfdString
    MAX-ACCESS  read-only
    STATUS      current
    DESCRIPTION "Number of nat connection failures"
    ::= { affirmedServicesNatServiceNatDeterministicSubPoolStatsEntry 24 }

affirmedServicesNatServiceNatDeterministicSubPoolStatsConnectionCount OBJECT-TYPE
    SYNTAX      ConfdString
    MAX-ACCESS  read-only
    STATUS      current
    DESCRIPTION "Number of connections currently using the nat-pool"
    ::= { affirmedServicesNatServiceNatDeterministicSubPoolStatsEntry 25 }

affirmedServicesNatServiceNatDeterministicSubPoolStatsConnectionAllocateNatPortSuccess OBJECT-TYPE
    SYNTAX      ConfdString
    MAX-ACCESS  read-only
    STATUS      current
    DESCRIPTION "Number of nat port allocated successfully"
    ::= { affirmedServicesNatServiceNatDeterministicSubPoolStatsEntry 26 }

affirmedServicesNatServiceNatDeterministicSubPoolStatsConnectionAllocateNatPortFailure OBJECT-TYPE
    SYNTAX      ConfdString
    MAX-ACCESS  read-only
    STATUS      current
    DESCRIPTION "Number of nat port allocation failure"
    ::= { affirmedServicesNatServiceNatDeterministicSubPoolStatsEntry 27 }

affirmedServicesNatServiceNatDeterministicSubPoolStatsConnectionDeallocateNatPortSuccess OBJECT-TYPE
    SYNTAX      ConfdString
    MAX-ACCESS  read-only
    STATUS      current
    DESCRIPTION "Number of nat port deallocate success"
    ::= { affirmedServicesNatServiceNatDeterministicSubPoolStatsEntry 28 }

affirmedServicesNatServiceNatDeterministicSubPoolStatsConnectionCreateFailureNatPortUnavailable OBJECT-TYPE
    SYNTAX      ConfdString
    MAX-ACCESS  read-only
    STATUS      current
    DESCRIPTION "Number of connection create failures due to non-availability of nat port"
    ::= { affirmedServicesNatServiceNatDeterministicSubPoolStatsEntry 29 }

affirmedServicesNatServiceNatDeterministicNatIpTable OBJECT-TYPE
    SYNTAX      SEQUENCE OF AffirmedServicesNatServiceNatDeterministicNatIpEntry
    MAX-ACCESS  not-accessible
    STATUS      current
    DESCRIPTION ""
    ::= { affirmedServicesNatServiceNatDeterministic 3 }

affirmedServicesNatServiceNatDeterministicNatIpEntry OBJECT-TYPE
    SYNTAX      AffirmedServicesNatServiceNatDeterministicNatIpEntry
    MAX-ACCESS  not-accessible
    STATUS      current
    DESCRIPTION ""
    INDEX { affirmedServicesNatServiceNatDeterministicNatIpNcName, affirmedServicesNatServiceNatDeterministicNatIpUeIp }
        ::= { affirmedServicesNatServiceNatDeterministicNatIpTable 1 }

AffirmedServicesNatServiceNatDeterministicNatIpEntry ::=
    SEQUENCE {
        affirmedServicesNatServiceNatDeterministicNatIpNcName String,
        affirmedServicesNatServiceNatDeterministicNatIpUeIp String,
        affirmedServicesNatServiceNatDeterministicNatIpSummary String
    }

affirmedServicesNatServiceNatDeterministicNatIpNcName OBJECT-TYPE
    SYNTAX      String
    MAX-ACCESS  not-accessible
    STATUS      current
    DESCRIPTION "Provide network context name"
    ::= { affirmedServicesNatServiceNatDeterministicNatIpEntry 1 }

affirmedServicesNatServiceNatDeterministicNatIpUeIp OBJECT-TYPE
    SYNTAX      String
    MAX-ACCESS  not-accessible
    STATUS      current
    DESCRIPTION ""
    ::= { affirmedServicesNatServiceNatDeterministicNatIpEntry 2 }

affirmedServicesNatServiceNatDeterministicNatIpSummary OBJECT-TYPE
    SYNTAX      String
    MAX-ACCESS  read-only
    STATUS      current
    DESCRIPTION ""
    ::= { affirmedServicesNatServiceNatDeterministicNatIpEntry 3 }

affirmedServicesNatServiceNatDeterministicUeIpTable OBJECT-TYPE
    SYNTAX      SEQUENCE OF AffirmedServicesNatServiceNatDeterministicUeIpEntry
    MAX-ACCESS  not-accessible
    STATUS      current
    DESCRIPTION ""
    ::= { affirmedServicesNatServiceNatDeterministic 4 }

affirmedServicesNatServiceNatDeterministicUeIpEntry OBJECT-TYPE
    SYNTAX      AffirmedServicesNatServiceNatDeterministicUeIpEntry
    MAX-ACCESS  not-accessible
    STATUS      current
    DESCRIPTION ""
    INDEX { affirmedServicesNatServiceNatDeterministicUeIpNcName, affirmedServicesNatServiceNatDeterministicUeIpNatIp, affirmedServicesNatServiceNatDeterministicUeIpNatPort }
        ::= { affirmedServicesNatServiceNatDeterministicUeIpTable 1 }

AffirmedServicesNatServiceNatDeterministicUeIpEntry ::=
    SEQUENCE {
        affirmedServicesNatServiceNatDeterministicUeIpNcName String,
        affirmedServicesNatServiceNatDeterministicUeIpNatIp String,
        affirmedServicesNatServiceNatDeterministicUeIpNatPort Unsigned32,
        affirmedServicesNatServiceNatDeterministicUeIpSummary String
    }

affirmedServicesNatServiceNatDeterministicUeIpNcName OBJECT-TYPE
    SYNTAX      String
    MAX-ACCESS  not-accessible
    STATUS      current
    DESCRIPTION ""
    ::= { affirmedServicesNatServiceNatDeterministicUeIpEntry 1 }

affirmedServicesNatServiceNatDeterministicUeIpNatIp OBJECT-TYPE
    SYNTAX      String
    MAX-ACCESS  not-accessible
    STATUS      current
    DESCRIPTION ""
    ::= { affirmedServicesNatServiceNatDeterministicUeIpEntry 2 }

affirmedServicesNatServiceNatDeterministicUeIpNatPort OBJECT-TYPE
    SYNTAX      Unsigned32
    MAX-ACCESS  not-accessible
    STATUS      current
    DESCRIPTION ""
    ::= { affirmedServicesNatServiceNatDeterministicUeIpEntry 3 }

affirmedServicesNatServiceNatDeterministicUeIpSummary OBJECT-TYPE
    SYNTAX      String
    MAX-ACCESS  read-only
    STATUS      current
    DESCRIPTION ""
    ::= { affirmedServicesNatServiceNatDeterministicUeIpEntry 4 }

affirmedServicesNatServiceNatPerfStatsNatPoolStatsTable OBJECT-TYPE
    SYNTAX      SEQUENCE OF AffirmedServicesNatServiceNatPerfStatsNatPoolStatsEntry
    MAX-ACCESS  not-accessible
    STATUS      current
    DESCRIPTION ""
    ::= { affirmedServicesNatServiceNatPerfStats 1 }

affirmedServicesNatServiceNatPerfStatsNatPoolStatsEntry OBJECT-TYPE
    SYNTAX      AffirmedServicesNatServiceNatPerfStatsNatPoolStatsEntry
    MAX-ACCESS  not-accessible
    STATUS      current
    DESCRIPTION ""
    INDEX { affirmedServicesNatServiceNatPerfStatsNatPoolStatsNetworkContext, affirmedServicesNatServiceNatPerfStatsNatPoolStatsPoolName, affirmedServicesNatServiceNatPerfStatsNatPoolStatsChassis, affirmedServicesNatServiceNatPerfStatsNatPoolStatsSlot }
        ::= { affirmedServicesNatServiceNatPerfStatsNatPoolStatsTable 1 }

AffirmedServicesNatServiceNatPerfStatsNatPoolStatsEntry ::=
    SEQUENCE {
        affirmedServicesNatServiceNatPerfStatsNatPoolStatsNetworkContext String,
        affirmedServicesNatServiceNatPerfStatsNatPoolStatsPoolName String,
        affirmedServicesNatServiceNatPerfStatsNatPoolStatsChassis Unsigned32,
        affirmedServicesNatServiceNatPerfStatsNatPoolStatsSlot Unsigned32,
        affirmedServicesNatServiceNatPerfStatsNatPoolStatsNumSessionAllocated ConfdString,
        affirmedServicesNatServiceNatPerfStatsNatPoolStatsNumSessionDeniedResource ConfdString,
        affirmedServicesNatServiceNatPerfStatsNatPoolStatsSessionCapacityPercent Unsigned32,
        affirmedServicesNatServiceNatPerfStatsNatPoolStatsSessionUtilizationPercent Unsigned32,
        affirmedServicesNatServiceNatPerfStatsNatPoolStatsIpAddressCapacityPercent Unsigned32,
        affirmedServicesNatServiceNatPerfStatsNatPoolStatsIpUtilizationPercent Unsigned32,
        affirmedServicesNatServiceNatPerfStatsNatPoolStatsPortChunkCapacityPercent Unsigned32,
        affirmedServicesNatServiceNatPerfStatsNatPoolStatsPortChunkUtilizationPercent Unsigned32,
        affirmedServicesNatServiceNatPerfStatsNatPoolStatsNatConnFailureMaxPortChunksExceeded ConfdString
    }

affirmedServicesNatServiceNatPerfStatsNatPoolStatsNetworkContext OBJECT-TYPE
    SYNTAX      String
    MAX-ACCESS  not-accessible
    STATUS      current
    DESCRIPTION "networkcontext"
    ::= { affirmedServicesNatServiceNatPerfStatsNatPoolStatsEntry 1 }

affirmedServicesNatServiceNatPerfStatsNatPoolStatsPoolName OBJECT-TYPE
    SYNTAX      String
    MAX-ACCESS  not-accessible
    STATUS      current
    DESCRIPTION "NAT pool name"
    ::= { affirmedServicesNatServiceNatPerfStatsNatPoolStatsEntry 2 }

affirmedServicesNatServiceNatPerfStatsNatPoolStatsChassis OBJECT-TYPE
    SYNTAX      Unsigned32
    MAX-ACCESS  not-accessible
    STATUS      current
    DESCRIPTION "Chassis id"
    ::= { affirmedServicesNatServiceNatPerfStatsNatPoolStatsEntry 3 }

affirmedServicesNatServiceNatPerfStatsNatPoolStatsSlot OBJECT-TYPE
    SYNTAX      Unsigned32
    MAX-ACCESS  not-accessible
    STATUS      current
    DESCRIPTION "Slot id"
    ::= { affirmedServicesNatServiceNatPerfStatsNatPoolStatsEntry 4 }

affirmedServicesNatServiceNatPerfStatsNatPoolStatsNumSessionAllocated OBJECT-TYPE
    SYNTAX      ConfdString
    MAX-ACCESS  read-only
    STATUS      current
    DESCRIPTION "Total number of sessions successfully allocated NAT resources"
    ::= { affirmedServicesNatServiceNatPerfStatsNatPoolStatsEntry 5 }

affirmedServicesNatServiceNatPerfStatsNatPoolStatsNumSessionDeniedResource OBJECT-TYPE
    SYNTAX      ConfdString
    MAX-ACCESS  read-only
    STATUS      current
    DESCRIPTION "Total number of sessions denied NAT resources"
    ::= { affirmedServicesNatServiceNatPerfStatsNatPoolStatsEntry 6 }

affirmedServicesNatServiceNatPerfStatsNatPoolStatsSessionCapacityPercent OBJECT-TYPE
    SYNTAX      Unsigned32
    MAX-ACCESS  read-only
    STATUS      current
    DESCRIPTION "Percentage of total session capacity"
    ::= { affirmedServicesNatServiceNatPerfStatsNatPoolStatsEntry 7 }

affirmedServicesNatServiceNatPerfStatsNatPoolStatsSessionUtilizationPercent OBJECT-TYPE
    SYNTAX      Unsigned32
    MAX-ACCESS  read-only
    STATUS      current
    DESCRIPTION "Percentage of session capacity being utilized"
    ::= { affirmedServicesNatServiceNatPerfStatsNatPoolStatsEntry 8 }

affirmedServicesNatServiceNatPerfStatsNatPoolStatsIpAddressCapacityPercent OBJECT-TYPE
    SYNTAX      Unsigned32
    MAX-ACCESS  read-only
    STATUS      current
    DESCRIPTION "Percentage of total IP address capacity"
    ::= { affirmedServicesNatServiceNatPerfStatsNatPoolStatsEntry 9 }

affirmedServicesNatServiceNatPerfStatsNatPoolStatsIpUtilizationPercent OBJECT-TYPE
    SYNTAX      Unsigned32
    MAX-ACCESS  read-only
    STATUS      current
    DESCRIPTION "Percentage of IP address being utilized"
    ::= { affirmedServicesNatServiceNatPerfStatsNatPoolStatsEntry 10 }

affirmedServicesNatServiceNatPerfStatsNatPoolStatsPortChunkCapacityPercent OBJECT-TYPE
    SYNTAX      Unsigned32
    MAX-ACCESS  read-only
    STATUS      current
    DESCRIPTION "Percentage of total port chunk capacity"
    ::= { affirmedServicesNatServiceNatPerfStatsNatPoolStatsEntry 11 }

affirmedServicesNatServiceNatPerfStatsNatPoolStatsPortChunkUtilizationPercent OBJECT-TYPE
    SYNTAX      Unsigned32
    MAX-ACCESS  read-only
    STATUS      current
    DESCRIPTION "Percentage of Port chunks being utilized"
    ::= { affirmedServicesNatServiceNatPerfStatsNatPoolStatsEntry 12 }

affirmedServicesNatServiceNatPerfStatsNatPoolStatsNatConnFailureMaxPortChunksExceeded OBJECT-TYPE
    SYNTAX      ConfdString
    MAX-ACCESS  read-only
    STATUS      current
    DESCRIPTION "Number of Nat Connection failures due to max port chunk exceeded"
    ::= { affirmedServicesNatServiceNatPerfStatsNatPoolStatsEntry 13 }

affirmedServicesNatServiceNatPerfStatsNodeLevelNatModuleStatsTable OBJECT-TYPE
    SYNTAX      SEQUENCE OF AffirmedServicesNatServiceNatPerfStatsNodeLevelNatModuleStatsEntry
    MAX-ACCESS  not-accessible
    STATUS      current
    DESCRIPTION ""
    ::= { affirmedServicesNatServiceNatPerfStatsNodeLevel 1 }

affirmedServicesNatServiceNatPerfStatsNodeLevelNatModuleStatsEntry OBJECT-TYPE
    SYNTAX      AffirmedServicesNatServiceNatPerfStatsNodeLevelNatModuleStatsEntry
    MAX-ACCESS  not-accessible
    STATUS      current
    DESCRIPTION ""
    INDEX { affirmedServicesNatServiceNatPerfStatsNodeLevelNatModuleStatsChassis, affirmedServicesNatServiceNatPerfStatsNodeLevelNatModuleStatsSlot }
        ::= { affirmedServicesNatServiceNatPerfStatsNodeLevelNatModuleStatsTable 1 }

AffirmedServicesNatServiceNatPerfStatsNodeLevelNatModuleStatsEntry ::=
    SEQUENCE {
        affirmedServicesNatServiceNatPerfStatsNodeLevelNatModuleStatsChassis Unsigned32,
        affirmedServicesNatServiceNatPerfStatsNodeLevelNatModuleStatsSlot Unsigned32,
        affirmedServicesNatServiceNatPerfStatsNodeLevelNatModuleStatsConnectionsCreated ConfdString,
        affirmedServicesNatServiceNatPerfStatsNodeLevelNatModuleStatsConnectionsDeleted ConfdString,
        affirmedServicesNatServiceNatPerfStatsNodeLevelNatModuleStatsConnectionCreateFailure ConfdString,
        affirmedServicesNatServiceNatPerfStatsNodeLevelNatModuleStatsConnectionCreateActionDrop ConfdString,
        affirmedServicesNatServiceNatPerfStatsNodeLevelNatModuleStatsConnectionCreateActionPass ConfdString,
        affirmedServicesNatServiceNatPerfStatsNodeLevelNatModuleStatsConnectionCreateIgnored ConfdString,
        affirmedServicesNatServiceNatPerfStatsNodeLevelNatModuleStatsConnectionCreateDropNetworkInitiated ConfdString,
        affirmedServicesNatServiceNatPerfStatsNodeLevelNatModuleStatsConnectionCreateFailureIpv6PrefixMismatch ConfdString,
        affirmedServicesNatServiceNatPerfStatsNodeLevelNatModuleStatsConnectionCreateFailureGeoRedMismatch ConfdString,
        affirmedServicesNatServiceNatPerfStatsNodeLevelNatModuleStatsConnectionCreateFailureNoAssociatedNatPool ConfdString,
        affirmedServicesNatServiceNatPerfStatsNodeLevelNatModuleStatsConnectionCreateFailureServiceFlowNotEnabled ConfdString,
        affirmedServicesNatServiceNatPerfStatsNodeLevelNatModuleStatsConnectionCreateFailureNatPoolNotEnabled ConfdString,
        affirmedServicesNatServiceNatPerfStatsNodeLevelNatModuleStatsConnectionCreateFailureNatAlgNotEnabled ConfdString,
        affirmedServicesNatServiceNatPerfStatsNodeLevelNatModuleStatsConnectionCreateFailureSessionNotActive ConfdString,
        affirmedServicesNatServiceNatPerfStatsNodeLevelNatModuleStatsConnectionCreateFailureNatMappingUnavailable ConfdString,
        affirmedServicesNatServiceNatPerfStatsNodeLevelNatModuleStatsConnectionCreateIgnoredNetworkInitiated ConfdString,
        affirmedServicesNatServiceNatPerfStatsNodeLevelNatModuleStatsConnectionCreateIgnoredUnsupportedIcmpType ConfdString,
        affirmedServicesNatServiceNatPerfStatsNodeLevelNatModuleStatsConnectionCreateIgnoredUnsupportedProtocol ConfdString,
        affirmedServicesNatServiceNatPerfStatsNodeLevelNatModuleStatsConnectionDeleteNatPoolConnectionPurge ConfdString,
        affirmedServicesNatServiceNatPerfStatsNodeLevelNatModuleStatsConnectionCreateTcp ConfdString,
        affirmedServicesNatServiceNatPerfStatsNodeLevelNatModuleStatsConnectionCreateUdp ConfdString,
        affirmedServicesNatServiceNatPerfStatsNodeLevelNatModuleStatsConnectionCreateIcmp ConfdString,
        affirmedServicesNatServiceNatPerfStatsNodeLevelNatModuleStatsConnectionDeleteTcp ConfdString,
        affirmedServicesNatServiceNatPerfStatsNodeLevelNatModuleStatsConnectionDeleteUdp ConfdString,
        affirmedServicesNatServiceNatPerfStatsNodeLevelNatModuleStatsConnectionDeleteIcmp ConfdString,
        affirmedServicesNatServiceNatPerfStatsNodeLevelNatModuleStatsConnectionCreateFailureFlowStateTracking ConfdString,
        affirmedServicesNatServiceNatPerfStatsNodeLevelNatModuleStatsConnectionCreateFailureFlowStateProfileMisconfig ConfdString
    }

affirmedServicesNatServiceNatPerfStatsNodeLevelNatModuleStatsChassis OBJECT-TYPE
    SYNTAX      Unsigned32
    MAX-ACCESS  not-accessible
    STATUS      current
    DESCRIPTION "Chassis id"
    ::= { affirmedServicesNatServiceNatPerfStatsNodeLevelNatModuleStatsEntry 1 }

affirmedServicesNatServiceNatPerfStatsNodeLevelNatModuleStatsSlot OBJECT-TYPE
    SYNTAX      Unsigned32
    MAX-ACCESS  not-accessible
    STATUS      current
    DESCRIPTION "Slot id"
    ::= { affirmedServicesNatServiceNatPerfStatsNodeLevelNatModuleStatsEntry 2 }

affirmedServicesNatServiceNatPerfStatsNodeLevelNatModuleStatsConnectionsCreated OBJECT-TYPE
    SYNTAX      ConfdString
    MAX-ACCESS  read-only
    STATUS      current
    DESCRIPTION "Number of nat connections created"
    ::= { affirmedServicesNatServiceNatPerfStatsNodeLevelNatModuleStatsEntry 3 }

affirmedServicesNatServiceNatPerfStatsNodeLevelNatModuleStatsConnectionsDeleted OBJECT-TYPE
    SYNTAX      ConfdString
    MAX-ACCESS  read-only
    STATUS      current
    DESCRIPTION "Number of nat connections deleted"
    ::= { affirmedServicesNatServiceNatPerfStatsNodeLevelNatModuleStatsEntry 4 }

affirmedServicesNatServiceNatPerfStatsNodeLevelNatModuleStatsConnectionCreateFailure OBJECT-TYPE
    SYNTAX      ConfdString
    MAX-ACCESS  read-only
    STATUS      current
    DESCRIPTION "Number of nat connection failures"
    ::= { affirmedServicesNatServiceNatPerfStatsNodeLevelNatModuleStatsEntry 5 }

affirmedServicesNatServiceNatPerfStatsNodeLevelNatModuleStatsConnectionCreateActionDrop OBJECT-TYPE
    SYNTAX      ConfdString
    MAX-ACCESS  read-only
    STATUS      current
    DESCRIPTION "Number of nat connections not created due to service flow action drop"
    ::= { affirmedServicesNatServiceNatPerfStatsNodeLevelNatModuleStatsEntry 6 }

affirmedServicesNatServiceNatPerfStatsNodeLevelNatModuleStatsConnectionCreateActionPass OBJECT-TYPE
    SYNTAX      ConfdString
    MAX-ACCESS  read-only
    STATUS      current
    DESCRIPTION "Number of nat connections not created due to  service flow action pass"
    ::= { affirmedServicesNatServiceNatPerfStatsNodeLevelNatModuleStatsEntry 7 }

affirmedServicesNatServiceNatPerfStatsNodeLevelNatModuleStatsConnectionCreateIgnored OBJECT-TYPE
    SYNTAX      ConfdString
    MAX-ACCESS  read-only
    STATUS      current
    DESCRIPTION "Number of nat connections create ignored because of http-proxy non transparent mode enabled"
    ::= { affirmedServicesNatServiceNatPerfStatsNodeLevelNatModuleStatsEntry 8 }

affirmedServicesNatServiceNatPerfStatsNodeLevelNatModuleStatsConnectionCreateDropNetworkInitiated OBJECT-TYPE
    SYNTAX      ConfdString
    MAX-ACCESS  read-only
    STATUS      current
    DESCRIPTION "Number of connection creations dropped as it was Network initiated and destination is ue-ip"
    ::= { affirmedServicesNatServiceNatPerfStatsNodeLevelNatModuleStatsEntry 9 }

affirmedServicesNatServiceNatPerfStatsNodeLevelNatModuleStatsConnectionCreateFailureIpv6PrefixMismatch OBJECT-TYPE
    SYNTAX      ConfdString
    MAX-ACCESS  read-only
    STATUS      current
    DESCRIPTION "Number of nat connections creation failure due to mismatch between configured NAT64 Ipv6 prefix and Network Address of the connection"
    ::= { affirmedServicesNatServiceNatPerfStatsNodeLevelNatModuleStatsEntry 10 }

affirmedServicesNatServiceNatPerfStatsNodeLevelNatModuleStatsConnectionCreateFailureGeoRedMismatch OBJECT-TYPE
    SYNTAX      ConfdString
    MAX-ACCESS  read-only
    STATUS      current
    DESCRIPTION "Number of nat connections creation failure due to mismatch between Geo-group id of the nat-pool and the session"
    ::= { affirmedServicesNatServiceNatPerfStatsNodeLevelNatModuleStatsEntry 11 }

affirmedServicesNatServiceNatPerfStatsNodeLevelNatModuleStatsConnectionCreateFailureNoAssociatedNatPool OBJECT-TYPE
    SYNTAX      ConfdString
    MAX-ACCESS  read-only
    STATUS      deprecated
    DESCRIPTION "Number of nat connections creation failure due to subscriber-firewall-flow for nat not configured with nat-pool"
    ::= { affirmedServicesNatServiceNatPerfStatsNodeLevelNatModuleStatsEntry 12 }

affirmedServicesNatServiceNatPerfStatsNodeLevelNatModuleStatsConnectionCreateFailureServiceFlowNotEnabled OBJECT-TYPE
    SYNTAX      ConfdString
    MAX-ACCESS  read-only
    STATUS      deprecated
    DESCRIPTION "Number of nat connection creation failure due to subscriber-firewall-flow being admin disabled"
    ::= { affirmedServicesNatServiceNatPerfStatsNodeLevelNatModuleStatsEntry 13 }

affirmedServicesNatServiceNatPerfStatsNodeLevelNatModuleStatsConnectionCreateFailureNatPoolNotEnabled OBJECT-TYPE
    SYNTAX      ConfdString
    MAX-ACCESS  read-only
    STATUS      current
    DESCRIPTION "Number of nat connections creation failure due to nat-pool being admin disabled."
    ::= { affirmedServicesNatServiceNatPerfStatsNodeLevelNatModuleStatsEntry 14 }

affirmedServicesNatServiceNatPerfStatsNodeLevelNatModuleStatsConnectionCreateFailureNatAlgNotEnabled OBJECT-TYPE
    SYNTAX      ConfdString
    MAX-ACCESS  read-only
    STATUS      deprecated
    DESCRIPTION "Number of nat connections creation failure due to NAT ALG  being disabled"
    ::= { affirmedServicesNatServiceNatPerfStatsNodeLevelNatModuleStatsEntry 15 }

affirmedServicesNatServiceNatPerfStatsNodeLevelNatModuleStatsConnectionCreateFailureSessionNotActive OBJECT-TYPE
    SYNTAX      ConfdString
    MAX-ACCESS  read-only
    STATUS      deprecated
    DESCRIPTION "Number of connections create failure due to inactive session. This could be a transient condition during failover allowing the UE to quickly retry."
    ::= { affirmedServicesNatServiceNatPerfStatsNodeLevelNatModuleStatsEntry 16 }

affirmedServicesNatServiceNatPerfStatsNodeLevelNatModuleStatsConnectionCreateFailureNatMappingUnavailable OBJECT-TYPE
    SYNTAX      ConfdString
    MAX-ACCESS  read-only
    STATUS      current
    DESCRIPTION "Number of nat connection creation failure due to unavailability of Nat port"
    ::= { affirmedServicesNatServiceNatPerfStatsNodeLevelNatModuleStatsEntry 17 }

affirmedServicesNatServiceNatPerfStatsNodeLevelNatModuleStatsConnectionCreateIgnoredNetworkInitiated OBJECT-TYPE
    SYNTAX      ConfdString
    MAX-ACCESS  read-only
    STATUS      current
    DESCRIPTION "Number of connection creation ignored as it was Network initiated and destination is ue-ip, port 67(dhcp)"
    ::= { affirmedServicesNatServiceNatPerfStatsNodeLevelNatModuleStatsEntry 18 }

affirmedServicesNatServiceNatPerfStatsNodeLevelNatModuleStatsConnectionCreateIgnoredUnsupportedIcmpType OBJECT-TYPE
    SYNTAX      ConfdString
    MAX-ACCESS  read-only
    STATUS      current
    DESCRIPTION "Number of connection create ignored due to unsupported ICMP type"
    ::= { affirmedServicesNatServiceNatPerfStatsNodeLevelNatModuleStatsEntry 19 }

affirmedServicesNatServiceNatPerfStatsNodeLevelNatModuleStatsConnectionCreateIgnoredUnsupportedProtocol OBJECT-TYPE
    SYNTAX      ConfdString
    MAX-ACCESS  read-only
    STATUS      current
    DESCRIPTION "Number of connection create ignored due to unsupported protocol"
    ::= { affirmedServicesNatServiceNatPerfStatsNodeLevelNatModuleStatsEntry 20 }

affirmedServicesNatServiceNatPerfStatsNodeLevelNatModuleStatsConnectionDeleteNatPoolConnectionPurge OBJECT-TYPE
    SYNTAX      ConfdString
    MAX-ACCESS  read-only
    STATUS      current
    DESCRIPTION "Number of nat connections deleted due to nat-pool/sub-pool being admin disabled"
    ::= { affirmedServicesNatServiceNatPerfStatsNodeLevelNatModuleStatsEntry 21 }

affirmedServicesNatServiceNatPerfStatsNodeLevelNatModuleStatsConnectionCreateTcp OBJECT-TYPE
    SYNTAX      ConfdString
    MAX-ACCESS  read-only
    STATUS      current
    DESCRIPTION "Number of tcp connections created"
    ::= { affirmedServicesNatServiceNatPerfStatsNodeLevelNatModuleStatsEntry 22 }

affirmedServicesNatServiceNatPerfStatsNodeLevelNatModuleStatsConnectionCreateUdp OBJECT-TYPE
    SYNTAX      ConfdString
    MAX-ACCESS  read-only
    STATUS      current
    DESCRIPTION "Number of udp connections created"
    ::= { affirmedServicesNatServiceNatPerfStatsNodeLevelNatModuleStatsEntry 23 }

affirmedServicesNatServiceNatPerfStatsNodeLevelNatModuleStatsConnectionCreateIcmp OBJECT-TYPE
    SYNTAX      ConfdString
    MAX-ACCESS  read-only
    STATUS      current
    DESCRIPTION "Number of icmp connections created"
    ::= { affirmedServicesNatServiceNatPerfStatsNodeLevelNatModuleStatsEntry 24 }

affirmedServicesNatServiceNatPerfStatsNodeLevelNatModuleStatsConnectionDeleteTcp OBJECT-TYPE
    SYNTAX      ConfdString
    MAX-ACCESS  read-only
    STATUS      current
    DESCRIPTION "Number of tcp connections deleted"
    ::= { affirmedServicesNatServiceNatPerfStatsNodeLevelNatModuleStatsEntry 25 }

affirmedServicesNatServiceNatPerfStatsNodeLevelNatModuleStatsConnectionDeleteUdp OBJECT-TYPE
    SYNTAX      ConfdString
    MAX-ACCESS  read-only
    STATUS      current
    DESCRIPTION "Number of udp connections deleted"
    ::= { affirmedServicesNatServiceNatPerfStatsNodeLevelNatModuleStatsEntry 26 }

affirmedServicesNatServiceNatPerfStatsNodeLevelNatModuleStatsConnectionDeleteIcmp OBJECT-TYPE
    SYNTAX      ConfdString
    MAX-ACCESS  read-only
    STATUS      current
    DESCRIPTION "Number of icmp connections deleted"
    ::= { affirmedServicesNatServiceNatPerfStatsNodeLevelNatModuleStatsEntry 27 }

affirmedServicesNatServiceNatPerfStatsNodeLevelNatModuleStatsConnectionCreateFailureFlowStateTracking OBJECT-TYPE
    SYNTAX      ConfdString
    MAX-ACCESS  read-only
    STATUS      current
    DESCRIPTION "Number of connection create failures due to flow state tracking"
    ::= { affirmedServicesNatServiceNatPerfStatsNodeLevelNatModuleStatsEntry 28 }

affirmedServicesNatServiceNatPerfStatsNodeLevelNatModuleStatsConnectionCreateFailureFlowStateProfileMisconfig OBJECT-TYPE
    SYNTAX      ConfdString
    MAX-ACCESS  read-only
    STATUS      current
    DESCRIPTION "Number of connection create failures due to flow state tracking misconfig"
    ::= { affirmedServicesNatServiceNatPerfStatsNodeLevelNatModuleStatsEntry 29 }

affirmedServicesNatServiceNatPerfStatsClusterLevelNatModuleStatsTable OBJECT-TYPE
    SYNTAX      SEQUENCE OF AffirmedServicesNatServiceNatPerfStatsClusterLevelNatModuleStatsEntry
    MAX-ACCESS  not-accessible
    STATUS      current
    DESCRIPTION ""
    ::= { affirmedServicesNatServiceNatPerfStatsClusterLevel 1 }

affirmedServicesNatServiceNatPerfStatsClusterLevelNatModuleStatsEntry OBJECT-TYPE
    SYNTAX      AffirmedServicesNatServiceNatPerfStatsClusterLevelNatModuleStatsEntry
    MAX-ACCESS  not-accessible
    STATUS      current
    DESCRIPTION ""
    INDEX { affirmedServicesNatServiceNatPerfStatsClusterLevelNatModuleStatsChassis }
        ::= { affirmedServicesNatServiceNatPerfStatsClusterLevelNatModuleStatsTable 1 }

AffirmedServicesNatServiceNatPerfStatsClusterLevelNatModuleStatsEntry ::=
    SEQUENCE {
        affirmedServicesNatServiceNatPerfStatsClusterLevelNatModuleStatsChassis Unsigned32,
        affirmedServicesNatServiceNatPerfStatsClusterLevelNatModuleStatsConnectionsCreated ConfdString,
        affirmedServicesNatServiceNatPerfStatsClusterLevelNatModuleStatsConnectionsDeleted ConfdString,
        affirmedServicesNatServiceNatPerfStatsClusterLevelNatModuleStatsConnectionCreateFailure ConfdString,
        affirmedServicesNatServiceNatPerfStatsClusterLevelNatModuleStatsConnectionCreateActionDrop ConfdString,
        affirmedServicesNatServiceNatPerfStatsClusterLevelNatModuleStatsConnectionCreateActionPass ConfdString,
        affirmedServicesNatServiceNatPerfStatsClusterLevelNatModuleStatsConnectionCreateIgnored ConfdString,
        affirmedServicesNatServiceNatPerfStatsClusterLevelNatModuleStatsConnectionCreateDropNetworkInitiated ConfdString,
        affirmedServicesNatServiceNatPerfStatsClusterLevelNatModuleStatsConnectionCreateFailureIpv6PrefixMismatch ConfdString,
        affirmedServicesNatServiceNatPerfStatsClusterLevelNatModuleStatsConnectionCreateFailureGeoRedMismatch ConfdString,
        affirmedServicesNatServiceNatPerfStatsClusterLevelNatModuleStatsConnectionCreateFailureNoAssociatedNatPool ConfdString,
        affirmedServicesNatServiceNatPerfStatsClusterLevelNatModuleStatsConnectionCreateFailureServiceFlowNotEnabled ConfdString,
        affirmedServicesNatServiceNatPerfStatsClusterLevelNatModuleStatsConnectionCreateFailureNatPoolNotEnabled ConfdString,
        affirmedServicesNatServiceNatPerfStatsClusterLevelNatModuleStatsConnectionCreateFailureNatAlgNotEnabled ConfdString,
        affirmedServicesNatServiceNatPerfStatsClusterLevelNatModuleStatsConnectionCreateFailureSessionNotActive ConfdString,
        affirmedServicesNatServiceNatPerfStatsClusterLevelNatModuleStatsConnectionCreateFailureNatMappingUnavailable ConfdString,
        affirmedServicesNatServiceNatPerfStatsClusterLevelNatModuleStatsConnectionCreateIgnoredNetworkInitiated ConfdString,
        affirmedServicesNatServiceNatPerfStatsClusterLevelNatModuleStatsConnectionCreateIgnoredUnsupportedIcmpType ConfdString,
        affirmedServicesNatServiceNatPerfStatsClusterLevelNatModuleStatsConnectionCreateIgnoredUnsupportedProtocol ConfdString,
        affirmedServicesNatServiceNatPerfStatsClusterLevelNatModuleStatsConnectionDeleteNatPoolConnectionPurge ConfdString,
        affirmedServicesNatServiceNatPerfStatsClusterLevelNatModuleStatsConnectionCreateTcp ConfdString,
        affirmedServicesNatServiceNatPerfStatsClusterLevelNatModuleStatsConnectionCreateUdp ConfdString,
        affirmedServicesNatServiceNatPerfStatsClusterLevelNatModuleStatsConnectionCreateIcmp ConfdString,
        affirmedServicesNatServiceNatPerfStatsClusterLevelNatModuleStatsConnectionDeleteTcp ConfdString,
        affirmedServicesNatServiceNatPerfStatsClusterLevelNatModuleStatsConnectionDeleteUdp ConfdString,
        affirmedServicesNatServiceNatPerfStatsClusterLevelNatModuleStatsConnectionDeleteIcmp ConfdString,
        affirmedServicesNatServiceNatPerfStatsClusterLevelNatModuleStatsConnectionCreateFailureFlowStateTracking ConfdString,
        affirmedServicesNatServiceNatPerfStatsClusterLevelNatModuleStatsConnectionCreateFailureFlowStateProfileMisconfig ConfdString
    }

affirmedServicesNatServiceNatPerfStatsClusterLevelNatModuleStatsChassis OBJECT-TYPE
    SYNTAX      Unsigned32
    MAX-ACCESS  not-accessible
    STATUS      current
    DESCRIPTION "Chassis id"
    ::= { affirmedServicesNatServiceNatPerfStatsClusterLevelNatModuleStatsEntry 1 }

affirmedServicesNatServiceNatPerfStatsClusterLevelNatModuleStatsConnectionsCreated OBJECT-TYPE
    SYNTAX      ConfdString
    MAX-ACCESS  read-only
    STATUS      current
    DESCRIPTION "Number of nat connections created"
    ::= { affirmedServicesNatServiceNatPerfStatsClusterLevelNatModuleStatsEntry 2 }

affirmedServicesNatServiceNatPerfStatsClusterLevelNatModuleStatsConnectionsDeleted OBJECT-TYPE
    SYNTAX      ConfdString
    MAX-ACCESS  read-only
    STATUS      current
    DESCRIPTION "Number of nat connections deleted"
    ::= { affirmedServicesNatServiceNatPerfStatsClusterLevelNatModuleStatsEntry 3 }

affirmedServicesNatServiceNatPerfStatsClusterLevelNatModuleStatsConnectionCreateFailure OBJECT-TYPE
    SYNTAX      ConfdString
    MAX-ACCESS  read-only
    STATUS      current
    DESCRIPTION "Number of nat connection failures"
    ::= { affirmedServicesNatServiceNatPerfStatsClusterLevelNatModuleStatsEntry 4 }

affirmedServicesNatServiceNatPerfStatsClusterLevelNatModuleStatsConnectionCreateActionDrop OBJECT-TYPE
    SYNTAX      ConfdString
    MAX-ACCESS  read-only
    STATUS      current
    DESCRIPTION "Number of nat connections not created due to service flow action drop"
    ::= { affirmedServicesNatServiceNatPerfStatsClusterLevelNatModuleStatsEntry 5 }

affirmedServicesNatServiceNatPerfStatsClusterLevelNatModuleStatsConnectionCreateActionPass OBJECT-TYPE
    SYNTAX      ConfdString
    MAX-ACCESS  read-only
    STATUS      current
    DESCRIPTION "Number of nat connections not created due to  service flow action pass"
    ::= { affirmedServicesNatServiceNatPerfStatsClusterLevelNatModuleStatsEntry 6 }

affirmedServicesNatServiceNatPerfStatsClusterLevelNatModuleStatsConnectionCreateIgnored OBJECT-TYPE
    SYNTAX      ConfdString
    MAX-ACCESS  read-only
    STATUS      current
    DESCRIPTION "Number of nat connections create ignored because of http-proxy non transparent mode enabled"
    ::= { affirmedServicesNatServiceNatPerfStatsClusterLevelNatModuleStatsEntry 7 }

affirmedServicesNatServiceNatPerfStatsClusterLevelNatModuleStatsConnectionCreateDropNetworkInitiated OBJECT-TYPE
    SYNTAX      ConfdString
    MAX-ACCESS  read-only
    STATUS      current
    DESCRIPTION "Number of connection creations dropped as it was Network initiated and destination is ue-ip"
    ::= { affirmedServicesNatServiceNatPerfStatsClusterLevelNatModuleStatsEntry 8 }

affirmedServicesNatServiceNatPerfStatsClusterLevelNatModuleStatsConnectionCreateFailureIpv6PrefixMismatch OBJECT-TYPE
    SYNTAX      ConfdString
    MAX-ACCESS  read-only
    STATUS      current
    DESCRIPTION "Number of nat connections creation failure due to mismatch between configured NAT64 Ipv6 prefix and Network Address of the connection"
    ::= { affirmedServicesNatServiceNatPerfStatsClusterLevelNatModuleStatsEntry 9 }

affirmedServicesNatServiceNatPerfStatsClusterLevelNatModuleStatsConnectionCreateFailureGeoRedMismatch OBJECT-TYPE
    SYNTAX      ConfdString
    MAX-ACCESS  read-only
    STATUS      current
    DESCRIPTION "Number of nat connections creation failure due to mismatch between Geo-group id of the nat-pool and the session"
    ::= { affirmedServicesNatServiceNatPerfStatsClusterLevelNatModuleStatsEntry 10 }

affirmedServicesNatServiceNatPerfStatsClusterLevelNatModuleStatsConnectionCreateFailureNoAssociatedNatPool OBJECT-TYPE
    SYNTAX      ConfdString
    MAX-ACCESS  read-only
    STATUS      deprecated
    DESCRIPTION "Number of nat connections creation failure due to subscriber-firewall-flow for nat not configured with nat-pool"
    ::= { affirmedServicesNatServiceNatPerfStatsClusterLevelNatModuleStatsEntry 11 }

affirmedServicesNatServiceNatPerfStatsClusterLevelNatModuleStatsConnectionCreateFailureServiceFlowNotEnabled OBJECT-TYPE
    SYNTAX      ConfdString
    MAX-ACCESS  read-only
    STATUS      deprecated
    DESCRIPTION "Number of nat connection creation failure due to subscriber-firewall-flow being admin disabled"
    ::= { affirmedServicesNatServiceNatPerfStatsClusterLevelNatModuleStatsEntry 12 }

affirmedServicesNatServiceNatPerfStatsClusterLevelNatModuleStatsConnectionCreateFailureNatPoolNotEnabled OBJECT-TYPE
    SYNTAX      ConfdString
    MAX-ACCESS  read-only
    STATUS      current
    DESCRIPTION "Number of nat connections creation failure due to nat-pool being admin disabled."
    ::= { affirmedServicesNatServiceNatPerfStatsClusterLevelNatModuleStatsEntry 13 }

affirmedServicesNatServiceNatPerfStatsClusterLevelNatModuleStatsConnectionCreateFailureNatAlgNotEnabled OBJECT-TYPE
    SYNTAX      ConfdString
    MAX-ACCESS  read-only
    STATUS      deprecated
    DESCRIPTION "Number of nat connections creation failure due to NAT ALG  being disabled"
    ::= { affirmedServicesNatServiceNatPerfStatsClusterLevelNatModuleStatsEntry 14 }

affirmedServicesNatServiceNatPerfStatsClusterLevelNatModuleStatsConnectionCreateFailureSessionNotActive OBJECT-TYPE
    SYNTAX      ConfdString
    MAX-ACCESS  read-only
    STATUS      deprecated
    DESCRIPTION "Number of connections create failure due to inactive session. This could be a transient condition during failover allowing the UE to quickly retry."
    ::= { affirmedServicesNatServiceNatPerfStatsClusterLevelNatModuleStatsEntry 15 }

affirmedServicesNatServiceNatPerfStatsClusterLevelNatModuleStatsConnectionCreateFailureNatMappingUnavailable OBJECT-TYPE
    SYNTAX      ConfdString
    MAX-ACCESS  read-only
    STATUS      current
    DESCRIPTION "Number of nat connection creation failure due to unavailability of Nat port"
    ::= { affirmedServicesNatServiceNatPerfStatsClusterLevelNatModuleStatsEntry 16 }

affirmedServicesNatServiceNatPerfStatsClusterLevelNatModuleStatsConnectionCreateIgnoredNetworkInitiated OBJECT-TYPE
    SYNTAX      ConfdString
    MAX-ACCESS  read-only
    STATUS      current
    DESCRIPTION "Number of connection creation ignored as it was Network initiated and destination is ue-ip, port 67(dhcp)"
    ::= { affirmedServicesNatServiceNatPerfStatsClusterLevelNatModuleStatsEntry 17 }

affirmedServicesNatServiceNatPerfStatsClusterLevelNatModuleStatsConnectionCreateIgnoredUnsupportedIcmpType OBJECT-TYPE
    SYNTAX      ConfdString
    MAX-ACCESS  read-only
    STATUS      current
    DESCRIPTION "Number of connection create ignored due to unsupported ICMP type"
    ::= { affirmedServicesNatServiceNatPerfStatsClusterLevelNatModuleStatsEntry 18 }

affirmedServicesNatServiceNatPerfStatsClusterLevelNatModuleStatsConnectionCreateIgnoredUnsupportedProtocol OBJECT-TYPE
    SYNTAX      ConfdString
    MAX-ACCESS  read-only
    STATUS      current
    DESCRIPTION "Number of connection create ignored due to unsupported protocol"
    ::= { affirmedServicesNatServiceNatPerfStatsClusterLevelNatModuleStatsEntry 19 }

affirmedServicesNatServiceNatPerfStatsClusterLevelNatModuleStatsConnectionDeleteNatPoolConnectionPurge OBJECT-TYPE
    SYNTAX      ConfdString
    MAX-ACCESS  read-only
    STATUS      current
    DESCRIPTION "Number of nat connections deleted due to nat-pool/sub-pool being admin disabled"
    ::= { affirmedServicesNatServiceNatPerfStatsClusterLevelNatModuleStatsEntry 20 }

affirmedServicesNatServiceNatPerfStatsClusterLevelNatModuleStatsConnectionCreateTcp OBJECT-TYPE
    SYNTAX      ConfdString
    MAX-ACCESS  read-only
    STATUS      current
    DESCRIPTION "Number of tcp connections created"
    ::= { affirmedServicesNatServiceNatPerfStatsClusterLevelNatModuleStatsEntry 21 }

affirmedServicesNatServiceNatPerfStatsClusterLevelNatModuleStatsConnectionCreateUdp OBJECT-TYPE
    SYNTAX      ConfdString
    MAX-ACCESS  read-only
    STATUS      current
    DESCRIPTION "Number of udp connections created"
    ::= { affirmedServicesNatServiceNatPerfStatsClusterLevelNatModuleStatsEntry 22 }

affirmedServicesNatServiceNatPerfStatsClusterLevelNatModuleStatsConnectionCreateIcmp OBJECT-TYPE
    SYNTAX      ConfdString
    MAX-ACCESS  read-only
    STATUS      current
    DESCRIPTION "Number of icmp connections created"
    ::= { affirmedServicesNatServiceNatPerfStatsClusterLevelNatModuleStatsEntry 23 }

affirmedServicesNatServiceNatPerfStatsClusterLevelNatModuleStatsConnectionDeleteTcp OBJECT-TYPE
    SYNTAX      ConfdString
    MAX-ACCESS  read-only
    STATUS      current
    DESCRIPTION "Number of tcp connections deleted"
    ::= { affirmedServicesNatServiceNatPerfStatsClusterLevelNatModuleStatsEntry 24 }

affirmedServicesNatServiceNatPerfStatsClusterLevelNatModuleStatsConnectionDeleteUdp OBJECT-TYPE
    SYNTAX      ConfdString
    MAX-ACCESS  read-only
    STATUS      current
    DESCRIPTION "Number of udp connections deleted"
    ::= { affirmedServicesNatServiceNatPerfStatsClusterLevelNatModuleStatsEntry 25 }

affirmedServicesNatServiceNatPerfStatsClusterLevelNatModuleStatsConnectionDeleteIcmp OBJECT-TYPE
    SYNTAX      ConfdString
    MAX-ACCESS  read-only
    STATUS      current
    DESCRIPTION "Number of icmp connections deleted"
    ::= { affirmedServicesNatServiceNatPerfStatsClusterLevelNatModuleStatsEntry 26 }

affirmedServicesNatServiceNatPerfStatsClusterLevelNatModuleStatsConnectionCreateFailureFlowStateTracking OBJECT-TYPE
    SYNTAX      ConfdString
    MAX-ACCESS  read-only
    STATUS      current
    DESCRIPTION "Number of connection create failures due to flow state tracking"
    ::= { affirmedServicesNatServiceNatPerfStatsClusterLevelNatModuleStatsEntry 27 }

affirmedServicesNatServiceNatPerfStatsClusterLevelNatModuleStatsConnectionCreateFailureFlowStateProfileMisconfig OBJECT-TYPE
    SYNTAX      ConfdString
    MAX-ACCESS  read-only
    STATUS      current
    DESCRIPTION "Number of connection create failures due to flow state tracking misconfig"
    ::= { affirmedServicesNatServiceNatPerfStatsClusterLevelNatModuleStatsEntry 28 }

affirmedServicesNatServiceConnTrackerClusterLevelConnTrackerModuleStatsTable OBJECT-TYPE
    SYNTAX      SEQUENCE OF AffirmedServicesNatServiceConnTrackerClusterLevelConnTrackerModuleStatsEntry
    MAX-ACCESS  not-accessible
    STATUS      current
    DESCRIPTION ""
    ::= { affirmedServicesNatServiceConnTrackerClusterLevel 1 }

affirmedServicesNatServiceConnTrackerClusterLevelConnTrackerModuleStatsEntry OBJECT-TYPE
    SYNTAX      AffirmedServicesNatServiceConnTrackerClusterLevelConnTrackerModuleStatsEntry
    MAX-ACCESS  not-accessible
    STATUS      current
    DESCRIPTION ""
    INDEX { affirmedServicesNatServiceConnTrackerClusterLevelConnTrackerModuleStatsChassis }
        ::= { affirmedServicesNatServiceConnTrackerClusterLevelConnTrackerModuleStatsTable 1 }

AffirmedServicesNatServiceConnTrackerClusterLevelConnTrackerModuleStatsEntry ::=
    SEQUENCE {
        affirmedServicesNatServiceConnTrackerClusterLevelConnTrackerModuleStatsChassis Unsigned32,
        affirmedServicesNatServiceConnTrackerClusterLevelConnTrackerModuleStatsOrigSynRxedTcpNoneState ConfdString,
        affirmedServicesNatServiceConnTrackerClusterLevelConnTrackerModuleStatsRespSynRxedTcpNoneState ConfdString,
        affirmedServicesNatServiceConnTrackerClusterLevelConnTrackerModuleStatsOrigSynackRxedTcpNoneState ConfdString,
        affirmedServicesNatServiceConnTrackerClusterLevelConnTrackerModuleStatsRespSynackRxedTcpNoneState ConfdString,
        affirmedServicesNatServiceConnTrackerClusterLevelConnTrackerModuleStatsOrigAckRxedTcpNoneState ConfdString,
        affirmedServicesNatServiceConnTrackerClusterLevelConnTrackerModuleStatsRespAckRxedTcpNoneState ConfdString,
        affirmedServicesNatServiceConnTrackerClusterLevelConnTrackerModuleStatsOrigFinRxedTcpNoneState ConfdString,
        affirmedServicesNatServiceConnTrackerClusterLevelConnTrackerModuleStatsRespFinRxedTcpNoneState ConfdString,
        affirmedServicesNatServiceConnTrackerClusterLevelConnTrackerModuleStatsOrigRstRxedTcpNoneState ConfdString,
        affirmedServicesNatServiceConnTrackerClusterLevelConnTrackerModuleStatsRespRstRxedTcpNoneState ConfdString,
        affirmedServicesNatServiceConnTrackerClusterLevelConnTrackerModuleStatsOrigSynRxedTcpSynSentState ConfdString,
        affirmedServicesNatServiceConnTrackerClusterLevelConnTrackerModuleStatsRespSynRxedTcpSynSentState ConfdString,
        affirmedServicesNatServiceConnTrackerClusterLevelConnTrackerModuleStatsOrigSynackRxedTcpSynSentState ConfdString,
        affirmedServicesNatServiceConnTrackerClusterLevelConnTrackerModuleStatsRespSynackRxedTcpSynSentState ConfdString,
        affirmedServicesNatServiceConnTrackerClusterLevelConnTrackerModuleStatsOrigAckRxedTcpSynSentState ConfdString,
        affirmedServicesNatServiceConnTrackerClusterLevelConnTrackerModuleStatsRespAckRxedTcpSynSentState ConfdString,
        affirmedServicesNatServiceConnTrackerClusterLevelConnTrackerModuleStatsOrigFinRxedTcpSynSentState ConfdString,
        affirmedServicesNatServiceConnTrackerClusterLevelConnTrackerModuleStatsRespFinRxedTcpSynSentState ConfdString,
        affirmedServicesNatServiceConnTrackerClusterLevelConnTrackerModuleStatsOrigRstRxedTcpSynSentState ConfdString,
        affirmedServicesNatServiceConnTrackerClusterLevelConnTrackerModuleStatsRespRstRxedTcpSynSentState ConfdString,
        affirmedServicesNatServiceConnTrackerClusterLevelConnTrackerModuleStatsOrigSynRxedTcpSynAckRcvdState ConfdString,
        affirmedServicesNatServiceConnTrackerClusterLevelConnTrackerModuleStatsRespSynRxedTcpSynAckRcvdState ConfdString,
        affirmedServicesNatServiceConnTrackerClusterLevelConnTrackerModuleStatsOrigSynackRxedTcpSynAckRcvdState ConfdString,
        affirmedServicesNatServiceConnTrackerClusterLevelConnTrackerModuleStatsRespSynackRxedTcpSynAckRcvdState ConfdString,
        affirmedServicesNatServiceConnTrackerClusterLevelConnTrackerModuleStatsOrigAckRxedTcpSynAckRcvdState ConfdString,
        affirmedServicesNatServiceConnTrackerClusterLevelConnTrackerModuleStatsRespAckRxedTcpSynAckRcvdState ConfdString,
        affirmedServicesNatServiceConnTrackerClusterLevelConnTrackerModuleStatsOrigFinRxedTcpSynAckRcvdState ConfdString,
        affirmedServicesNatServiceConnTrackerClusterLevelConnTrackerModuleStatsRespFinRxedTcpSynAckRcvdState ConfdString,
        affirmedServicesNatServiceConnTrackerClusterLevelConnTrackerModuleStatsOrigRstRxedTcpSynAckRcvdState ConfdString,
        affirmedServicesNatServiceConnTrackerClusterLevelConnTrackerModuleStatsRespRstRxedTcpSynAckRcvdState ConfdString,
        affirmedServicesNatServiceConnTrackerClusterLevelConnTrackerModuleStatsOrigSynRxedTcpEstablishedState ConfdString,
        affirmedServicesNatServiceConnTrackerClusterLevelConnTrackerModuleStatsRespSynRxedTcpEstablishedState ConfdString,
        affirmedServicesNatServiceConnTrackerClusterLevelConnTrackerModuleStatsOrigSynackRxedTcpEstablishedState ConfdString,
        affirmedServicesNatServiceConnTrackerClusterLevelConnTrackerModuleStatsRespSynackRxedTcpEstablishedState ConfdString,
        affirmedServicesNatServiceConnTrackerClusterLevelConnTrackerModuleStatsOrigAckRxedTcpEstablishedState ConfdString,
        affirmedServicesNatServiceConnTrackerClusterLevelConnTrackerModuleStatsRespAckRxedTcpEstablishedState ConfdString,
        affirmedServicesNatServiceConnTrackerClusterLevelConnTrackerModuleStatsOrigFinRxedTcpEstablishedState ConfdString,
        affirmedServicesNatServiceConnTrackerClusterLevelConnTrackerModuleStatsRespFinRxedTcpEstablishedState ConfdString,
        affirmedServicesNatServiceConnTrackerClusterLevelConnTrackerModuleStatsOrigRstRxedTcpEstablishedState ConfdString,
        affirmedServicesNatServiceConnTrackerClusterLevelConnTrackerModuleStatsRespRstRxedTcpEstablishedState ConfdString,
        affirmedServicesNatServiceConnTrackerClusterLevelConnTrackerModuleStatsOrigSynRxedTcpFinWaitState ConfdString,
        affirmedServicesNatServiceConnTrackerClusterLevelConnTrackerModuleStatsRespSynRxedTcpFinWaitState ConfdString,
        affirmedServicesNatServiceConnTrackerClusterLevelConnTrackerModuleStatsOrigSynackRxedTcpFinWaitState ConfdString,
        affirmedServicesNatServiceConnTrackerClusterLevelConnTrackerModuleStatsRespSynackRxedTcpFinWaitState ConfdString,
        affirmedServicesNatServiceConnTrackerClusterLevelConnTrackerModuleStatsOrigAckRxedTcpFinWaitState ConfdString,
        affirmedServicesNatServiceConnTrackerClusterLevelConnTrackerModuleStatsRespAckRxedTcpFinWaitState ConfdString,
        affirmedServicesNatServiceConnTrackerClusterLevelConnTrackerModuleStatsOrigFinRxedTcpFinWaitState ConfdString,
        affirmedServicesNatServiceConnTrackerClusterLevelConnTrackerModuleStatsRespFinRxedTcpFinWaitState ConfdString,
        affirmedServicesNatServiceConnTrackerClusterLevelConnTrackerModuleStatsOrigRstRxedTcpFinWaitState ConfdString,
        affirmedServicesNatServiceConnTrackerClusterLevelConnTrackerModuleStatsRespRstRxedTcpFinWaitState ConfdString,
        affirmedServicesNatServiceConnTrackerClusterLevelConnTrackerModuleStatsOrigSynRxedTcpCloseWaitState ConfdString,
        affirmedServicesNatServiceConnTrackerClusterLevelConnTrackerModuleStatsRespSynRxedTcpCloseWaitState ConfdString,
        affirmedServicesNatServiceConnTrackerClusterLevelConnTrackerModuleStatsOrigSynackRxedTcpCloseWaitState ConfdString,
        affirmedServicesNatServiceConnTrackerClusterLevelConnTrackerModuleStatsRespSynackRxedTcpCloseWaitState ConfdString,
        affirmedServicesNatServiceConnTrackerClusterLevelConnTrackerModuleStatsOrigAckRxedTcpCloseWaitState ConfdString,
        affirmedServicesNatServiceConnTrackerClusterLevelConnTrackerModuleStatsRespAckRxedTcpCloseWaitState ConfdString,
        affirmedServicesNatServiceConnTrackerClusterLevelConnTrackerModuleStatsOrigFinRxedTcpCloseWaitState ConfdString,
        affirmedServicesNatServiceConnTrackerClusterLevelConnTrackerModuleStatsRespFinRxedTcpCloseWaitState ConfdString,
        affirmedServicesNatServiceConnTrackerClusterLevelConnTrackerModuleStatsOrigRstRxedTcpCloseWaitState ConfdString,
        affirmedServicesNatServiceConnTrackerClusterLevelConnTrackerModuleStatsRespRstRxedTcpCloseWaitState ConfdString,
        affirmedServicesNatServiceConnTrackerClusterLevelConnTrackerModuleStatsOrigSynRxedTcpLastAckState ConfdString,
        affirmedServicesNatServiceConnTrackerClusterLevelConnTrackerModuleStatsRespSynRxedTcpLastAckState ConfdString,
        affirmedServicesNatServiceConnTrackerClusterLevelConnTrackerModuleStatsOrigSynackRxedTcpLastAckState ConfdString,
        affirmedServicesNatServiceConnTrackerClusterLevelConnTrackerModuleStatsRespSynackRxedTcpLastAckState ConfdString,
        affirmedServicesNatServiceConnTrackerClusterLevelConnTrackerModuleStatsOrigAckRxedTcpLastAckState ConfdString,
        affirmedServicesNatServiceConnTrackerClusterLevelConnTrackerModuleStatsRespAckRxedTcpLastAckState ConfdString,
        affirmedServicesNatServiceConnTrackerClusterLevelConnTrackerModuleStatsOrigFinRxedTcpLastAckState ConfdString,
        affirmedServicesNatServiceConnTrackerClusterLevelConnTrackerModuleStatsRespFinRxedTcpLastAckState ConfdString,
        affirmedServicesNatServiceConnTrackerClusterLevelConnTrackerModuleStatsOrigRstRxedTcpLastAckState ConfdString,
        affirmedServicesNatServiceConnTrackerClusterLevelConnTrackerModuleStatsRespRstRxedTcpLastAckState ConfdString,
        affirmedServicesNatServiceConnTrackerClusterLevelConnTrackerModuleStatsOrigSynRxedTcpTimedWaitState ConfdString,
        affirmedServicesNatServiceConnTrackerClusterLevelConnTrackerModuleStatsRespSynRxedTcpTimedWaitState ConfdString,
        affirmedServicesNatServiceConnTrackerClusterLevelConnTrackerModuleStatsOrigSynackRxedTcpTimedWaitState ConfdString,
        affirmedServicesNatServiceConnTrackerClusterLevelConnTrackerModuleStatsRespSynackRxedTcpTimedWaitState ConfdString,
        affirmedServicesNatServiceConnTrackerClusterLevelConnTrackerModuleStatsOrigAckRxedTcpTimedWaitState ConfdString,
        affirmedServicesNatServiceConnTrackerClusterLevelConnTrackerModuleStatsRespAckRxedTcpTimedWaitState ConfdString,
        affirmedServicesNatServiceConnTrackerClusterLevelConnTrackerModuleStatsOrigFinRxedTcpTimedWaitState ConfdString,
        affirmedServicesNatServiceConnTrackerClusterLevelConnTrackerModuleStatsRespFinRxedTcpTimedWaitState ConfdString,
        affirmedServicesNatServiceConnTrackerClusterLevelConnTrackerModuleStatsOrigRstRxedTcpTimedWaitState ConfdString,
        affirmedServicesNatServiceConnTrackerClusterLevelConnTrackerModuleStatsRespRstRxedTcpTimedWaitState ConfdString,
        affirmedServicesNatServiceConnTrackerClusterLevelConnTrackerModuleStatsOrigSynRxedTcpCloseState ConfdString,
        affirmedServicesNatServiceConnTrackerClusterLevelConnTrackerModuleStatsRespSynRxedTcpCloseState ConfdString,
        affirmedServicesNatServiceConnTrackerClusterLevelConnTrackerModuleStatsOrigSynackRxedTcpCloseState ConfdString,
        affirmedServicesNatServiceConnTrackerClusterLevelConnTrackerModuleStatsRespSynackRxedTcpCloseState ConfdString,
        affirmedServicesNatServiceConnTrackerClusterLevelConnTrackerModuleStatsOrigAckRxedTcpCloseState ConfdString,
        affirmedServicesNatServiceConnTrackerClusterLevelConnTrackerModuleStatsRespAckRxedTcpCloseState ConfdString,
        affirmedServicesNatServiceConnTrackerClusterLevelConnTrackerModuleStatsOrigFinRxedTcpCloseState ConfdString,
        affirmedServicesNatServiceConnTrackerClusterLevelConnTrackerModuleStatsRespFinRxedTcpCloseState ConfdString,
        affirmedServicesNatServiceConnTrackerClusterLevelConnTrackerModuleStatsOrigRstRxedTcpCloseState ConfdString,
        affirmedServicesNatServiceConnTrackerClusterLevelConnTrackerModuleStatsRespRstRxedTcpCloseState ConfdString,
        affirmedServicesNatServiceConnTrackerClusterLevelConnTrackerModuleStatsOrigSynRxedTcpBothWaySynSentState ConfdString,
        affirmedServicesNatServiceConnTrackerClusterLevelConnTrackerModuleStatsRespSynRxedTcpBothWaySynSentState ConfdString,
        affirmedServicesNatServiceConnTrackerClusterLevelConnTrackerModuleStatsOrigSynackRxedTcpBothWaySynSentState ConfdString,
        affirmedServicesNatServiceConnTrackerClusterLevelConnTrackerModuleStatsRespSynackRxedTcpBothWaySynSentState ConfdString,
        affirmedServicesNatServiceConnTrackerClusterLevelConnTrackerModuleStatsOrigAckRxedTcpBothWaySynSentState ConfdString,
        affirmedServicesNatServiceConnTrackerClusterLevelConnTrackerModuleStatsRespAckRxedTcpBothWaySynSentState ConfdString,
        affirmedServicesNatServiceConnTrackerClusterLevelConnTrackerModuleStatsOrigFinRxedTcpBothWaySynSentState ConfdString,
        affirmedServicesNatServiceConnTrackerClusterLevelConnTrackerModuleStatsRespFinRxedTcpBothWaySynSentState ConfdString,
        affirmedServicesNatServiceConnTrackerClusterLevelConnTrackerModuleStatsOrigRstRxedTcpBothWaySynSentState ConfdString,
        affirmedServicesNatServiceConnTrackerClusterLevelConnTrackerModuleStatsRespRstRxedTcpBothWaySynSentState ConfdString,
        affirmedServicesNatServiceConnTrackerClusterLevelConnTrackerModuleStatsOrigRxedUdpNoneState ConfdString,
        affirmedServicesNatServiceConnTrackerClusterLevelConnTrackerModuleStatsRespRxedUdpNoneState ConfdString,
        affirmedServicesNatServiceConnTrackerClusterLevelConnTrackerModuleStatsOrigRxedUdpOpenState ConfdString,
        affirmedServicesNatServiceConnTrackerClusterLevelConnTrackerModuleStatsRespRxedUdpOpenState ConfdString,
        affirmedServicesNatServiceConnTrackerClusterLevelConnTrackerModuleStatsOrigRxedUdpEstablishedState ConfdString,
        affirmedServicesNatServiceConnTrackerClusterLevelConnTrackerModuleStatsRespRxedUdpEstablishedState ConfdString,
        affirmedServicesNatServiceConnTrackerClusterLevelConnTrackerModuleStatsNumConnsUnSupportedProtocol ConfdString,
        affirmedServicesNatServiceConnTrackerClusterLevelConnTrackerModuleStatsNumTcpChildConnectionRequest ConfdString,
        affirmedServicesNatServiceConnTrackerClusterLevelConnTrackerModuleStatsNumUdpChildConnectionRequest ConfdString,
        affirmedServicesNatServiceConnTrackerClusterLevelConnTrackerModuleStatsNumFlowProfileNotFound ConfdString
    }

affirmedServicesNatServiceConnTrackerClusterLevelConnTrackerModuleStatsChassis OBJECT-TYPE
    SYNTAX      Unsigned32
    MAX-ACCESS  not-accessible
    STATUS      current
    DESCRIPTION "Chassis id"
    ::= { affirmedServicesNatServiceConnTrackerClusterLevelConnTrackerModuleStatsEntry 1 }

affirmedServicesNatServiceConnTrackerClusterLevelConnTrackerModuleStatsOrigSynRxedTcpNoneState OBJECT-TYPE
    SYNTAX      ConfdString
    MAX-ACCESS  read-only
    STATUS      current
    DESCRIPTION "Number of TCP SYNs received in TCP None State from Originator"
    ::= { affirmedServicesNatServiceConnTrackerClusterLevelConnTrackerModuleStatsEntry 2 }

affirmedServicesNatServiceConnTrackerClusterLevelConnTrackerModuleStatsRespSynRxedTcpNoneState OBJECT-TYPE
    SYNTAX      ConfdString
    MAX-ACCESS  read-only
    STATUS      current
    DESCRIPTION "Number of TCP SYNs received in TCP None State from Responder"
    ::= { affirmedServicesNatServiceConnTrackerClusterLevelConnTrackerModuleStatsEntry 3 }

affirmedServicesNatServiceConnTrackerClusterLevelConnTrackerModuleStatsOrigSynackRxedTcpNoneState OBJECT-TYPE
    SYNTAX      ConfdString
    MAX-ACCESS  read-only
    STATUS      current
    DESCRIPTION "Number of TCP SYNACKs received in TCP None State from Originator"
    ::= { affirmedServicesNatServiceConnTrackerClusterLevelConnTrackerModuleStatsEntry 4 }

affirmedServicesNatServiceConnTrackerClusterLevelConnTrackerModuleStatsRespSynackRxedTcpNoneState OBJECT-TYPE
    SYNTAX      ConfdString
    MAX-ACCESS  read-only
    STATUS      current
    DESCRIPTION "Number of TCP SYNACKs received in TCP None State from Responder"
    ::= { affirmedServicesNatServiceConnTrackerClusterLevelConnTrackerModuleStatsEntry 5 }

affirmedServicesNatServiceConnTrackerClusterLevelConnTrackerModuleStatsOrigAckRxedTcpNoneState OBJECT-TYPE
    SYNTAX      ConfdString
    MAX-ACCESS  read-only
    STATUS      current
    DESCRIPTION "Number of TCP ACKs received in TCP None State from Originator"
    ::= { affirmedServicesNatServiceConnTrackerClusterLevelConnTrackerModuleStatsEntry 6 }

affirmedServicesNatServiceConnTrackerClusterLevelConnTrackerModuleStatsRespAckRxedTcpNoneState OBJECT-TYPE
    SYNTAX      ConfdString
    MAX-ACCESS  read-only
    STATUS      current
    DESCRIPTION "Number of TCP ACKs received in TCP None State from Responder"
    ::= { affirmedServicesNatServiceConnTrackerClusterLevelConnTrackerModuleStatsEntry 7 }

affirmedServicesNatServiceConnTrackerClusterLevelConnTrackerModuleStatsOrigFinRxedTcpNoneState OBJECT-TYPE
    SYNTAX      ConfdString
    MAX-ACCESS  read-only
    STATUS      current
    DESCRIPTION "Number of TCP FINs received in TCP None State from Originator"
    ::= { affirmedServicesNatServiceConnTrackerClusterLevelConnTrackerModuleStatsEntry 8 }

affirmedServicesNatServiceConnTrackerClusterLevelConnTrackerModuleStatsRespFinRxedTcpNoneState OBJECT-TYPE
    SYNTAX      ConfdString
    MAX-ACCESS  read-only
    STATUS      current
    DESCRIPTION "Number of TCP FINs received in TCP None State from Responder"
    ::= { affirmedServicesNatServiceConnTrackerClusterLevelConnTrackerModuleStatsEntry 9 }

affirmedServicesNatServiceConnTrackerClusterLevelConnTrackerModuleStatsOrigRstRxedTcpNoneState OBJECT-TYPE
    SYNTAX      ConfdString
    MAX-ACCESS  read-only
    STATUS      current
    DESCRIPTION "Number of TCP RSTs received in TCP None State from Originator"
    ::= { affirmedServicesNatServiceConnTrackerClusterLevelConnTrackerModuleStatsEntry 10 }

affirmedServicesNatServiceConnTrackerClusterLevelConnTrackerModuleStatsRespRstRxedTcpNoneState OBJECT-TYPE
    SYNTAX      ConfdString
    MAX-ACCESS  read-only
    STATUS      current
    DESCRIPTION "Number of TCP RSTs received in TCP None State from Responder"
    ::= { affirmedServicesNatServiceConnTrackerClusterLevelConnTrackerModuleStatsEntry 11 }

affirmedServicesNatServiceConnTrackerClusterLevelConnTrackerModuleStatsOrigSynRxedTcpSynSentState OBJECT-TYPE
    SYNTAX      ConfdString
    MAX-ACCESS  read-only
    STATUS      current
    DESCRIPTION "Number of TCP SYNs received in TCP Syn Sent State from Originator"
    ::= { affirmedServicesNatServiceConnTrackerClusterLevelConnTrackerModuleStatsEntry 12 }

affirmedServicesNatServiceConnTrackerClusterLevelConnTrackerModuleStatsRespSynRxedTcpSynSentState OBJECT-TYPE
    SYNTAX      ConfdString
    MAX-ACCESS  read-only
    STATUS      current
    DESCRIPTION "Number of TCP SYNs received in TCP Syn Sent State from Responder"
    ::= { affirmedServicesNatServiceConnTrackerClusterLevelConnTrackerModuleStatsEntry 13 }

affirmedServicesNatServiceConnTrackerClusterLevelConnTrackerModuleStatsOrigSynackRxedTcpSynSentState OBJECT-TYPE
    SYNTAX      ConfdString
    MAX-ACCESS  read-only
    STATUS      current
    DESCRIPTION "Number of TCP SYNACKs received in TCP Syn Sent State from Originator"
    ::= { affirmedServicesNatServiceConnTrackerClusterLevelConnTrackerModuleStatsEntry 14 }

affirmedServicesNatServiceConnTrackerClusterLevelConnTrackerModuleStatsRespSynackRxedTcpSynSentState OBJECT-TYPE
    SYNTAX      ConfdString
    MAX-ACCESS  read-only
    STATUS      current
    DESCRIPTION "Number of TCP SYNACKs received in TCP Syn Sent State from Responder"
    ::= { affirmedServicesNatServiceConnTrackerClusterLevelConnTrackerModuleStatsEntry 15 }

affirmedServicesNatServiceConnTrackerClusterLevelConnTrackerModuleStatsOrigAckRxedTcpSynSentState OBJECT-TYPE
    SYNTAX      ConfdString
    MAX-ACCESS  read-only
    STATUS      current
    DESCRIPTION "Number of TCP ACKs received in TCP Syn Sent State from Originator"
    ::= { affirmedServicesNatServiceConnTrackerClusterLevelConnTrackerModuleStatsEntry 16 }

affirmedServicesNatServiceConnTrackerClusterLevelConnTrackerModuleStatsRespAckRxedTcpSynSentState OBJECT-TYPE
    SYNTAX      ConfdString
    MAX-ACCESS  read-only
    STATUS      current
    DESCRIPTION "Number of TCP ACKs received in TCP Syn Sent State from Responder"
    ::= { affirmedServicesNatServiceConnTrackerClusterLevelConnTrackerModuleStatsEntry 17 }

affirmedServicesNatServiceConnTrackerClusterLevelConnTrackerModuleStatsOrigFinRxedTcpSynSentState OBJECT-TYPE
    SYNTAX      ConfdString
    MAX-ACCESS  read-only
    STATUS      current
    DESCRIPTION "Number of TCP FINs received in TCP Syn Sent State from Originator"
    ::= { affirmedServicesNatServiceConnTrackerClusterLevelConnTrackerModuleStatsEntry 18 }

affirmedServicesNatServiceConnTrackerClusterLevelConnTrackerModuleStatsRespFinRxedTcpSynSentState OBJECT-TYPE
    SYNTAX      ConfdString
    MAX-ACCESS  read-only
    STATUS      current
    DESCRIPTION "Number of TCP FINs received in TCP Syn Sent State from Responder"
    ::= { affirmedServicesNatServiceConnTrackerClusterLevelConnTrackerModuleStatsEntry 19 }

affirmedServicesNatServiceConnTrackerClusterLevelConnTrackerModuleStatsOrigRstRxedTcpSynSentState OBJECT-TYPE
    SYNTAX      ConfdString
    MAX-ACCESS  read-only
    STATUS      current
    DESCRIPTION "Number of TCP RSTs received in TCP Syn Sent State from Originator"
    ::= { affirmedServicesNatServiceConnTrackerClusterLevelConnTrackerModuleStatsEntry 20 }

affirmedServicesNatServiceConnTrackerClusterLevelConnTrackerModuleStatsRespRstRxedTcpSynSentState OBJECT-TYPE
    SYNTAX      ConfdString
    MAX-ACCESS  read-only
    STATUS      current
    DESCRIPTION "Number of TCP RSTs received in TCP Syn Sent State from Responder"
    ::= { affirmedServicesNatServiceConnTrackerClusterLevelConnTrackerModuleStatsEntry 21 }

affirmedServicesNatServiceConnTrackerClusterLevelConnTrackerModuleStatsOrigSynRxedTcpSynAckRcvdState OBJECT-TYPE
    SYNTAX      ConfdString
    MAX-ACCESS  read-only
    STATUS      current
    DESCRIPTION "Number of TCP SYNs received in TCP SynAck Rcvd State from Originator"
    ::= { affirmedServicesNatServiceConnTrackerClusterLevelConnTrackerModuleStatsEntry 22 }

affirmedServicesNatServiceConnTrackerClusterLevelConnTrackerModuleStatsRespSynRxedTcpSynAckRcvdState OBJECT-TYPE
    SYNTAX      ConfdString
    MAX-ACCESS  read-only
    STATUS      current
    DESCRIPTION "Number of TCP SYNs received in TCP SynAck Rcvd State from Responder"
    ::= { affirmedServicesNatServiceConnTrackerClusterLevelConnTrackerModuleStatsEntry 23 }

affirmedServicesNatServiceConnTrackerClusterLevelConnTrackerModuleStatsOrigSynackRxedTcpSynAckRcvdState OBJECT-TYPE
    SYNTAX      ConfdString
    MAX-ACCESS  read-only
    STATUS      current
    DESCRIPTION "Number of TCP SYNACKs received in TCP SynAck Rcvd State from Originator"
    ::= { affirmedServicesNatServiceConnTrackerClusterLevelConnTrackerModuleStatsEntry 24 }

affirmedServicesNatServiceConnTrackerClusterLevelConnTrackerModuleStatsRespSynackRxedTcpSynAckRcvdState OBJECT-TYPE
    SYNTAX      ConfdString
    MAX-ACCESS  read-only
    STATUS      current
    DESCRIPTION "Number of TCP SYNACKs received in TCP SynAck Rcvd State from Responder"
    ::= { affirmedServicesNatServiceConnTrackerClusterLevelConnTrackerModuleStatsEntry 25 }

affirmedServicesNatServiceConnTrackerClusterLevelConnTrackerModuleStatsOrigAckRxedTcpSynAckRcvdState OBJECT-TYPE
    SYNTAX      ConfdString
    MAX-ACCESS  read-only
    STATUS      current
    DESCRIPTION "Number of TCP ACKs received in TCP SynAck Rcvd State from Originator"
    ::= { affirmedServicesNatServiceConnTrackerClusterLevelConnTrackerModuleStatsEntry 26 }

affirmedServicesNatServiceConnTrackerClusterLevelConnTrackerModuleStatsRespAckRxedTcpSynAckRcvdState OBJECT-TYPE
    SYNTAX      ConfdString
    MAX-ACCESS  read-only
    STATUS      current
    DESCRIPTION "Number of TCP ACKs received in TCP SynAck Rcvd State from Responder"
    ::= { affirmedServicesNatServiceConnTrackerClusterLevelConnTrackerModuleStatsEntry 27 }

affirmedServicesNatServiceConnTrackerClusterLevelConnTrackerModuleStatsOrigFinRxedTcpSynAckRcvdState OBJECT-TYPE
    SYNTAX      ConfdString
    MAX-ACCESS  read-only
    STATUS      current
    DESCRIPTION "Number of TCP FINs received in TCP SynAck Rcvd State from Originator"
    ::= { affirmedServicesNatServiceConnTrackerClusterLevelConnTrackerModuleStatsEntry 28 }

affirmedServicesNatServiceConnTrackerClusterLevelConnTrackerModuleStatsRespFinRxedTcpSynAckRcvdState OBJECT-TYPE
    SYNTAX      ConfdString
    MAX-ACCESS  read-only
    STATUS      current
    DESCRIPTION "Number of TCP FINs received in TCP SynAck Rcvd State from Responder"
    ::= { affirmedServicesNatServiceConnTrackerClusterLevelConnTrackerModuleStatsEntry 29 }

affirmedServicesNatServiceConnTrackerClusterLevelConnTrackerModuleStatsOrigRstRxedTcpSynAckRcvdState OBJECT-TYPE
    SYNTAX      ConfdString
    MAX-ACCESS  read-only
    STATUS      current
    DESCRIPTION "Number of TCP RSTs received in TCP SynAck Rcvd State from Originator"
    ::= { affirmedServicesNatServiceConnTrackerClusterLevelConnTrackerModuleStatsEntry 30 }

affirmedServicesNatServiceConnTrackerClusterLevelConnTrackerModuleStatsRespRstRxedTcpSynAckRcvdState OBJECT-TYPE
    SYNTAX      ConfdString
    MAX-ACCESS  read-only
    STATUS      current
    DESCRIPTION "Number of TCP RSTs received in TCP SynAck Rcvd State from Responder"
    ::= { affirmedServicesNatServiceConnTrackerClusterLevelConnTrackerModuleStatsEntry 31 }

affirmedServicesNatServiceConnTrackerClusterLevelConnTrackerModuleStatsOrigSynRxedTcpEstablishedState OBJECT-TYPE
    SYNTAX      ConfdString
    MAX-ACCESS  read-only
    STATUS      current
    DESCRIPTION "Number of TCP SYNs received in TCP Established State from Originator"
    ::= { affirmedServicesNatServiceConnTrackerClusterLevelConnTrackerModuleStatsEntry 32 }

affirmedServicesNatServiceConnTrackerClusterLevelConnTrackerModuleStatsRespSynRxedTcpEstablishedState OBJECT-TYPE
    SYNTAX      ConfdString
    MAX-ACCESS  read-only
    STATUS      current
    DESCRIPTION "Number of TCP SYNs received in TCP Established State from Responder"
    ::= { affirmedServicesNatServiceConnTrackerClusterLevelConnTrackerModuleStatsEntry 33 }

affirmedServicesNatServiceConnTrackerClusterLevelConnTrackerModuleStatsOrigSynackRxedTcpEstablishedState OBJECT-TYPE
    SYNTAX      ConfdString
    MAX-ACCESS  read-only
    STATUS      current
    DESCRIPTION "Number of TCP SYNACKs received in TCP Established State from Originator"
    ::= { affirmedServicesNatServiceConnTrackerClusterLevelConnTrackerModuleStatsEntry 34 }

affirmedServicesNatServiceConnTrackerClusterLevelConnTrackerModuleStatsRespSynackRxedTcpEstablishedState OBJECT-TYPE
    SYNTAX      ConfdString
    MAX-ACCESS  read-only
    STATUS      current
    DESCRIPTION "Number of TCP SYNACKs received in TCP Established State from Responder"
    ::= { affirmedServicesNatServiceConnTrackerClusterLevelConnTrackerModuleStatsEntry 35 }

affirmedServicesNatServiceConnTrackerClusterLevelConnTrackerModuleStatsOrigAckRxedTcpEstablishedState OBJECT-TYPE
    SYNTAX      ConfdString
    MAX-ACCESS  read-only
    STATUS      current
    DESCRIPTION "Number of TCP ACKs received in TCP Established State from Originator"
    ::= { affirmedServicesNatServiceConnTrackerClusterLevelConnTrackerModuleStatsEntry 36 }

affirmedServicesNatServiceConnTrackerClusterLevelConnTrackerModuleStatsRespAckRxedTcpEstablishedState OBJECT-TYPE
    SYNTAX      ConfdString
    MAX-ACCESS  read-only
    STATUS      current
    DESCRIPTION "Number of TCP ACKs received in TCP Established State from Responder"
    ::= { affirmedServicesNatServiceConnTrackerClusterLevelConnTrackerModuleStatsEntry 37 }

affirmedServicesNatServiceConnTrackerClusterLevelConnTrackerModuleStatsOrigFinRxedTcpEstablishedState OBJECT-TYPE
    SYNTAX      ConfdString
    MAX-ACCESS  read-only
    STATUS      current
    DESCRIPTION "Number of TCP FINs received in TCP Established State from Originator"
    ::= { affirmedServicesNatServiceConnTrackerClusterLevelConnTrackerModuleStatsEntry 38 }

affirmedServicesNatServiceConnTrackerClusterLevelConnTrackerModuleStatsRespFinRxedTcpEstablishedState OBJECT-TYPE
    SYNTAX      ConfdString
    MAX-ACCESS  read-only
    STATUS      current
    DESCRIPTION "Number of TCP FINs received in TCP Established State from Responder"
    ::= { affirmedServicesNatServiceConnTrackerClusterLevelConnTrackerModuleStatsEntry 39 }

affirmedServicesNatServiceConnTrackerClusterLevelConnTrackerModuleStatsOrigRstRxedTcpEstablishedState OBJECT-TYPE
    SYNTAX      ConfdString
    MAX-ACCESS  read-only
    STATUS      current
    DESCRIPTION "Number of TCP RSTs received in TCP Established State from Originator"
    ::= { affirmedServicesNatServiceConnTrackerClusterLevelConnTrackerModuleStatsEntry 40 }

affirmedServicesNatServiceConnTrackerClusterLevelConnTrackerModuleStatsRespRstRxedTcpEstablishedState OBJECT-TYPE
    SYNTAX      ConfdString
    MAX-ACCESS  read-only
    STATUS      current
    DESCRIPTION "Number of TCP RSTs received in TCP Established State from Responder"
    ::= { affirmedServicesNatServiceConnTrackerClusterLevelConnTrackerModuleStatsEntry 41 }

affirmedServicesNatServiceConnTrackerClusterLevelConnTrackerModuleStatsOrigSynRxedTcpFinWaitState OBJECT-TYPE
    SYNTAX      ConfdString
    MAX-ACCESS  read-only
    STATUS      current
    DESCRIPTION "Number of TCP SYNs received in TCP Fin Wait State from Originator"
    ::= { affirmedServicesNatServiceConnTrackerClusterLevelConnTrackerModuleStatsEntry 42 }

affirmedServicesNatServiceConnTrackerClusterLevelConnTrackerModuleStatsRespSynRxedTcpFinWaitState OBJECT-TYPE
    SYNTAX      ConfdString
    MAX-ACCESS  read-only
    STATUS      current
    DESCRIPTION "Number of TCP SYNs received in TCP Fin Wait State from Responder"
    ::= { affirmedServicesNatServiceConnTrackerClusterLevelConnTrackerModuleStatsEntry 43 }

affirmedServicesNatServiceConnTrackerClusterLevelConnTrackerModuleStatsOrigSynackRxedTcpFinWaitState OBJECT-TYPE
    SYNTAX      ConfdString
    MAX-ACCESS  read-only
    STATUS      current
    DESCRIPTION "Number of TCP SYNACKs received in TCP Fin Wait State from Originator"
    ::= { affirmedServicesNatServiceConnTrackerClusterLevelConnTrackerModuleStatsEntry 44 }

affirmedServicesNatServiceConnTrackerClusterLevelConnTrackerModuleStatsRespSynackRxedTcpFinWaitState OBJECT-TYPE
    SYNTAX      ConfdString
    MAX-ACCESS  read-only
    STATUS      current
    DESCRIPTION "Number of TCP SYNACKs received in TCP Fin Wait State from Responder"
    ::= { affirmedServicesNatServiceConnTrackerClusterLevelConnTrackerModuleStatsEntry 45 }

affirmedServicesNatServiceConnTrackerClusterLevelConnTrackerModuleStatsOrigAckRxedTcpFinWaitState OBJECT-TYPE
    SYNTAX      ConfdString
    MAX-ACCESS  read-only
    STATUS      current
    DESCRIPTION "Number of TCP ACKs received in TCP Fin Wait State from Originator"
    ::= { affirmedServicesNatServiceConnTrackerClusterLevelConnTrackerModuleStatsEntry 46 }

affirmedServicesNatServiceConnTrackerClusterLevelConnTrackerModuleStatsRespAckRxedTcpFinWaitState OBJECT-TYPE
    SYNTAX      ConfdString
    MAX-ACCESS  read-only
    STATUS      current
    DESCRIPTION "Number of TCP ACKs received in TCP Fin Wait State from Responder"
    ::= { affirmedServicesNatServiceConnTrackerClusterLevelConnTrackerModuleStatsEntry 47 }

affirmedServicesNatServiceConnTrackerClusterLevelConnTrackerModuleStatsOrigFinRxedTcpFinWaitState OBJECT-TYPE
    SYNTAX      ConfdString
    MAX-ACCESS  read-only
    STATUS      current
    DESCRIPTION "Number of TCP FINs received in TCP Fin Wait State from Originator"
    ::= { affirmedServicesNatServiceConnTrackerClusterLevelConnTrackerModuleStatsEntry 48 }

affirmedServicesNatServiceConnTrackerClusterLevelConnTrackerModuleStatsRespFinRxedTcpFinWaitState OBJECT-TYPE
    SYNTAX      ConfdString
    MAX-ACCESS  read-only
    STATUS      current
    DESCRIPTION "Number of TCP FINs received in TCP Fin Wait State from Responder"
    ::= { affirmedServicesNatServiceConnTrackerClusterLevelConnTrackerModuleStatsEntry 49 }

affirmedServicesNatServiceConnTrackerClusterLevelConnTrackerModuleStatsOrigRstRxedTcpFinWaitState OBJECT-TYPE
    SYNTAX      ConfdString
    MAX-ACCESS  read-only
    STATUS      current
    DESCRIPTION "Number of TCP RSTs received in TCP Fin Wait State from Originator"
    ::= { affirmedServicesNatServiceConnTrackerClusterLevelConnTrackerModuleStatsEntry 50 }

affirmedServicesNatServiceConnTrackerClusterLevelConnTrackerModuleStatsRespRstRxedTcpFinWaitState OBJECT-TYPE
    SYNTAX      ConfdString
    MAX-ACCESS  read-only
    STATUS      current
    DESCRIPTION "Number of TCP RSTs received in TCP Fin Wait State from Responder"
    ::= { affirmedServicesNatServiceConnTrackerClusterLevelConnTrackerModuleStatsEntry 51 }

affirmedServicesNatServiceConnTrackerClusterLevelConnTrackerModuleStatsOrigSynRxedTcpCloseWaitState OBJECT-TYPE
    SYNTAX      ConfdString
    MAX-ACCESS  read-only
    STATUS      current
    DESCRIPTION "Number of TCP SYNs received in TCP Close Wait State from Originator"
    ::= { affirmedServicesNatServiceConnTrackerClusterLevelConnTrackerModuleStatsEntry 52 }

affirmedServicesNatServiceConnTrackerClusterLevelConnTrackerModuleStatsRespSynRxedTcpCloseWaitState OBJECT-TYPE
    SYNTAX      ConfdString
    MAX-ACCESS  read-only
    STATUS      current
    DESCRIPTION "Number of TCP SYNs received in TCP Close Wait State from Responder"
    ::= { affirmedServicesNatServiceConnTrackerClusterLevelConnTrackerModuleStatsEntry 53 }

affirmedServicesNatServiceConnTrackerClusterLevelConnTrackerModuleStatsOrigSynackRxedTcpCloseWaitState OBJECT-TYPE
    SYNTAX      ConfdString
    MAX-ACCESS  read-only
    STATUS      current
    DESCRIPTION "Number of TCP SYNACKs received in TCP Close Wait State from Originator"
    ::= { affirmedServicesNatServiceConnTrackerClusterLevelConnTrackerModuleStatsEntry 54 }

affirmedServicesNatServiceConnTrackerClusterLevelConnTrackerModuleStatsRespSynackRxedTcpCloseWaitState OBJECT-TYPE
    SYNTAX      ConfdString
    MAX-ACCESS  read-only
    STATUS      current
    DESCRIPTION "Number of TCP SYNACKs received in TCP Close Wait State from Responder"
    ::= { affirmedServicesNatServiceConnTrackerClusterLevelConnTrackerModuleStatsEntry 55 }

affirmedServicesNatServiceConnTrackerClusterLevelConnTrackerModuleStatsOrigAckRxedTcpCloseWaitState OBJECT-TYPE
    SYNTAX      ConfdString
    MAX-ACCESS  read-only
    STATUS      current
    DESCRIPTION "Number of TCP ACKs received in TCP Close Wait State from Originator"
    ::= { affirmedServicesNatServiceConnTrackerClusterLevelConnTrackerModuleStatsEntry 56 }

affirmedServicesNatServiceConnTrackerClusterLevelConnTrackerModuleStatsRespAckRxedTcpCloseWaitState OBJECT-TYPE
    SYNTAX      ConfdString
    MAX-ACCESS  read-only
    STATUS      current
    DESCRIPTION "Number of TCP ACKs received in TCP Close Wait State from Responder"
    ::= { affirmedServicesNatServiceConnTrackerClusterLevelConnTrackerModuleStatsEntry 57 }

affirmedServicesNatServiceConnTrackerClusterLevelConnTrackerModuleStatsOrigFinRxedTcpCloseWaitState OBJECT-TYPE
    SYNTAX      ConfdString
    MAX-ACCESS  read-only
    STATUS      current
    DESCRIPTION "Number of TCP FINs received in TCP Close Wait State from Originator"
    ::= { affirmedServicesNatServiceConnTrackerClusterLevelConnTrackerModuleStatsEntry 58 }

affirmedServicesNatServiceConnTrackerClusterLevelConnTrackerModuleStatsRespFinRxedTcpCloseWaitState OBJECT-TYPE
    SYNTAX      ConfdString
    MAX-ACCESS  read-only
    STATUS      current
    DESCRIPTION "Number of TCP FINs received in TCP Close Wait State from Responder"
    ::= { affirmedServicesNatServiceConnTrackerClusterLevelConnTrackerModuleStatsEntry 59 }

affirmedServicesNatServiceConnTrackerClusterLevelConnTrackerModuleStatsOrigRstRxedTcpCloseWaitState OBJECT-TYPE
    SYNTAX      ConfdString
    MAX-ACCESS  read-only
    STATUS      current
    DESCRIPTION "Number of TCP RSTs received in TCP Close Wait State from Originator"
    ::= { affirmedServicesNatServiceConnTrackerClusterLevelConnTrackerModuleStatsEntry 60 }

affirmedServicesNatServiceConnTrackerClusterLevelConnTrackerModuleStatsRespRstRxedTcpCloseWaitState OBJECT-TYPE
    SYNTAX      ConfdString
    MAX-ACCESS  read-only
    STATUS      current
    DESCRIPTION "Number of TCP RSTs received in TCP Close Wait State from Responder"
    ::= { affirmedServicesNatServiceConnTrackerClusterLevelConnTrackerModuleStatsEntry 61 }

affirmedServicesNatServiceConnTrackerClusterLevelConnTrackerModuleStatsOrigSynRxedTcpLastAckState OBJECT-TYPE
    SYNTAX      ConfdString
    MAX-ACCESS  read-only
    STATUS      current
    DESCRIPTION "Number of TCP SYNs received in TCP Last Ack State from Originator"
    ::= { affirmedServicesNatServiceConnTrackerClusterLevelConnTrackerModuleStatsEntry 62 }

affirmedServicesNatServiceConnTrackerClusterLevelConnTrackerModuleStatsRespSynRxedTcpLastAckState OBJECT-TYPE
    SYNTAX      ConfdString
    MAX-ACCESS  read-only
    STATUS      current
    DESCRIPTION "Number of TCP SYNs received in TCP Last Ack State from Responder"
    ::= { affirmedServicesNatServiceConnTrackerClusterLevelConnTrackerModuleStatsEntry 63 }

affirmedServicesNatServiceConnTrackerClusterLevelConnTrackerModuleStatsOrigSynackRxedTcpLastAckState OBJECT-TYPE
    SYNTAX      ConfdString
    MAX-ACCESS  read-only
    STATUS      current
    DESCRIPTION "Number of TCP SYNACKs received in TCP Last Ack State from Originator"
    ::= { affirmedServicesNatServiceConnTrackerClusterLevelConnTrackerModuleStatsEntry 64 }

affirmedServicesNatServiceConnTrackerClusterLevelConnTrackerModuleStatsRespSynackRxedTcpLastAckState OBJECT-TYPE
    SYNTAX      ConfdString
    MAX-ACCESS  read-only
    STATUS      current
    DESCRIPTION "Number of TCP SYNACKs received in TCP Last Ack State from Responder"
    ::= { affirmedServicesNatServiceConnTrackerClusterLevelConnTrackerModuleStatsEntry 65 }

affirmedServicesNatServiceConnTrackerClusterLevelConnTrackerModuleStatsOrigAckRxedTcpLastAckState OBJECT-TYPE
    SYNTAX      ConfdString
    MAX-ACCESS  read-only
    STATUS      current
    DESCRIPTION "Number of TCP ACKs received in TCP Last Ack State from Originator"
    ::= { affirmedServicesNatServiceConnTrackerClusterLevelConnTrackerModuleStatsEntry 66 }

affirmedServicesNatServiceConnTrackerClusterLevelConnTrackerModuleStatsRespAckRxedTcpLastAckState OBJECT-TYPE
    SYNTAX      ConfdString
    MAX-ACCESS  read-only
    STATUS      current
    DESCRIPTION "Number of TCP ACKs received in TCP Last Ack State from Responder"
    ::= { affirmedServicesNatServiceConnTrackerClusterLevelConnTrackerModuleStatsEntry 67 }

affirmedServicesNatServiceConnTrackerClusterLevelConnTrackerModuleStatsOrigFinRxedTcpLastAckState OBJECT-TYPE
    SYNTAX      ConfdString
    MAX-ACCESS  read-only
    STATUS      current
    DESCRIPTION "Number of TCP FINs received in TCP Last Ack State from Originator"
    ::= { affirmedServicesNatServiceConnTrackerClusterLevelConnTrackerModuleStatsEntry 68 }

affirmedServicesNatServiceConnTrackerClusterLevelConnTrackerModuleStatsRespFinRxedTcpLastAckState OBJECT-TYPE
    SYNTAX      ConfdString
    MAX-ACCESS  read-only
    STATUS      current
    DESCRIPTION "Number of TCP FINs received in TCP Last Ack State from Responder"
    ::= { affirmedServicesNatServiceConnTrackerClusterLevelConnTrackerModuleStatsEntry 69 }

affirmedServicesNatServiceConnTrackerClusterLevelConnTrackerModuleStatsOrigRstRxedTcpLastAckState OBJECT-TYPE
    SYNTAX      ConfdString
    MAX-ACCESS  read-only
    STATUS      current
    DESCRIPTION "Number of TCP RSTs received in TCP Last Ack State from Originator"
    ::= { affirmedServicesNatServiceConnTrackerClusterLevelConnTrackerModuleStatsEntry 70 }

affirmedServicesNatServiceConnTrackerClusterLevelConnTrackerModuleStatsRespRstRxedTcpLastAckState OBJECT-TYPE
    SYNTAX      ConfdString
    MAX-ACCESS  read-only
    STATUS      current
    DESCRIPTION "Number of TCP RSTs received in TCP Last Ack State from Responder"
    ::= { affirmedServicesNatServiceConnTrackerClusterLevelConnTrackerModuleStatsEntry 71 }

affirmedServicesNatServiceConnTrackerClusterLevelConnTrackerModuleStatsOrigSynRxedTcpTimedWaitState OBJECT-TYPE
    SYNTAX      ConfdString
    MAX-ACCESS  read-only
    STATUS      current
    DESCRIPTION "Number of TCP SYNs received in TCP Timed Wait State from Originator"
    ::= { affirmedServicesNatServiceConnTrackerClusterLevelConnTrackerModuleStatsEntry 72 }

affirmedServicesNatServiceConnTrackerClusterLevelConnTrackerModuleStatsRespSynRxedTcpTimedWaitState OBJECT-TYPE
    SYNTAX      ConfdString
    MAX-ACCESS  read-only
    STATUS      current
    DESCRIPTION "Number of TCP SYNs received in TCP Timed Wait State from Responder"
    ::= { affirmedServicesNatServiceConnTrackerClusterLevelConnTrackerModuleStatsEntry 73 }

affirmedServicesNatServiceConnTrackerClusterLevelConnTrackerModuleStatsOrigSynackRxedTcpTimedWaitState OBJECT-TYPE
    SYNTAX      ConfdString
    MAX-ACCESS  read-only
    STATUS      current
    DESCRIPTION "Number of TCP SYNACKs received in TCP Timed Wait State from Originator"
    ::= { affirmedServicesNatServiceConnTrackerClusterLevelConnTrackerModuleStatsEntry 74 }

affirmedServicesNatServiceConnTrackerClusterLevelConnTrackerModuleStatsRespSynackRxedTcpTimedWaitState OBJECT-TYPE
    SYNTAX      ConfdString
    MAX-ACCESS  read-only
    STATUS      current
    DESCRIPTION "Number of TCP SYNACKs received in TCP Timed Wait State from Responder"
    ::= { affirmedServicesNatServiceConnTrackerClusterLevelConnTrackerModuleStatsEntry 75 }

affirmedServicesNatServiceConnTrackerClusterLevelConnTrackerModuleStatsOrigAckRxedTcpTimedWaitState OBJECT-TYPE
    SYNTAX      ConfdString
    MAX-ACCESS  read-only
    STATUS      current
    DESCRIPTION "Number of TCP ACKs received in TCP Timed Wait State from Originator"
    ::= { affirmedServicesNatServiceConnTrackerClusterLevelConnTrackerModuleStatsEntry 76 }

affirmedServicesNatServiceConnTrackerClusterLevelConnTrackerModuleStatsRespAckRxedTcpTimedWaitState OBJECT-TYPE
    SYNTAX      ConfdString
    MAX-ACCESS  read-only
    STATUS      current
    DESCRIPTION "Number of TCP ACKs received in TCP Timed Wait State from Responder"
    ::= { affirmedServicesNatServiceConnTrackerClusterLevelConnTrackerModuleStatsEntry 77 }

affirmedServicesNatServiceConnTrackerClusterLevelConnTrackerModuleStatsOrigFinRxedTcpTimedWaitState OBJECT-TYPE
    SYNTAX      ConfdString
    MAX-ACCESS  read-only
    STATUS      current
    DESCRIPTION "Number of TCP FINs received in TCP Timed Wait State from Originator"
    ::= { affirmedServicesNatServiceConnTrackerClusterLevelConnTrackerModuleStatsEntry 78 }

affirmedServicesNatServiceConnTrackerClusterLevelConnTrackerModuleStatsRespFinRxedTcpTimedWaitState OBJECT-TYPE
    SYNTAX      ConfdString
    MAX-ACCESS  read-only
    STATUS      current
    DESCRIPTION "Number of TCP FINs received in TCP Timed Wait State from Responder"
    ::= { affirmedServicesNatServiceConnTrackerClusterLevelConnTrackerModuleStatsEntry 79 }

affirmedServicesNatServiceConnTrackerClusterLevelConnTrackerModuleStatsOrigRstRxedTcpTimedWaitState OBJECT-TYPE
    SYNTAX      ConfdString
    MAX-ACCESS  read-only
    STATUS      current
    DESCRIPTION "Number of TCP RSTs received in TCP Timed Wait State from Originator"
    ::= { affirmedServicesNatServiceConnTrackerClusterLevelConnTrackerModuleStatsEntry 80 }

affirmedServicesNatServiceConnTrackerClusterLevelConnTrackerModuleStatsRespRstRxedTcpTimedWaitState OBJECT-TYPE
    SYNTAX      ConfdString
    MAX-ACCESS  read-only
    STATUS      current
    DESCRIPTION "Number of TCP RSTs received in TCP Timed Wait State from Responder"
    ::= { affirmedServicesNatServiceConnTrackerClusterLevelConnTrackerModuleStatsEntry 81 }

affirmedServicesNatServiceConnTrackerClusterLevelConnTrackerModuleStatsOrigSynRxedTcpCloseState OBJECT-TYPE
    SYNTAX      ConfdString
    MAX-ACCESS  read-only
    STATUS      current
    DESCRIPTION "Number of TCP SYNs received in TCP Close State from Originator"
    ::= { affirmedServicesNatServiceConnTrackerClusterLevelConnTrackerModuleStatsEntry 82 }

affirmedServicesNatServiceConnTrackerClusterLevelConnTrackerModuleStatsRespSynRxedTcpCloseState OBJECT-TYPE
    SYNTAX      ConfdString
    MAX-ACCESS  read-only
    STATUS      current
    DESCRIPTION "Number of TCP SYNs received in TCP Close State from Responder"
    ::= { affirmedServicesNatServiceConnTrackerClusterLevelConnTrackerModuleStatsEntry 83 }

affirmedServicesNatServiceConnTrackerClusterLevelConnTrackerModuleStatsOrigSynackRxedTcpCloseState OBJECT-TYPE
    SYNTAX      ConfdString
    MAX-ACCESS  read-only
    STATUS      current
    DESCRIPTION "Number of TCP SYNACKs received in TCP Close State from Originator"
    ::= { affirmedServicesNatServiceConnTrackerClusterLevelConnTrackerModuleStatsEntry 84 }

affirmedServicesNatServiceConnTrackerClusterLevelConnTrackerModuleStatsRespSynackRxedTcpCloseState OBJECT-TYPE
    SYNTAX      ConfdString
    MAX-ACCESS  read-only
    STATUS      current
    DESCRIPTION "Number of TCP SYNACKs received in TCP Close State from Responder"
    ::= { affirmedServicesNatServiceConnTrackerClusterLevelConnTrackerModuleStatsEntry 85 }

affirmedServicesNatServiceConnTrackerClusterLevelConnTrackerModuleStatsOrigAckRxedTcpCloseState OBJECT-TYPE
    SYNTAX      ConfdString
    MAX-ACCESS  read-only
    STATUS      current
    DESCRIPTION "Number of TCP ACKs received in TCP Close State from Originator"
    ::= { affirmedServicesNatServiceConnTrackerClusterLevelConnTrackerModuleStatsEntry 86 }

affirmedServicesNatServiceConnTrackerClusterLevelConnTrackerModuleStatsRespAckRxedTcpCloseState OBJECT-TYPE
    SYNTAX      ConfdString
    MAX-ACCESS  read-only
    STATUS      current
    DESCRIPTION "Number of TCP ACKs received in TCP Close State from Responder"
    ::= { affirmedServicesNatServiceConnTrackerClusterLevelConnTrackerModuleStatsEntry 87 }

affirmedServicesNatServiceConnTrackerClusterLevelConnTrackerModuleStatsOrigFinRxedTcpCloseState OBJECT-TYPE
    SYNTAX      ConfdString
    MAX-ACCESS  read-only
    STATUS      current
    DESCRIPTION "Number of TCP FINs received in TCP Close State from Originator"
    ::= { affirmedServicesNatServiceConnTrackerClusterLevelConnTrackerModuleStatsEntry 88 }

affirmedServicesNatServiceConnTrackerClusterLevelConnTrackerModuleStatsRespFinRxedTcpCloseState OBJECT-TYPE
    SYNTAX      ConfdString
    MAX-ACCESS  read-only
    STATUS      current
    DESCRIPTION "Number of TCP FINs received in TCP Close State from Responder"
    ::= { affirmedServicesNatServiceConnTrackerClusterLevelConnTrackerModuleStatsEntry 89 }

affirmedServicesNatServiceConnTrackerClusterLevelConnTrackerModuleStatsOrigRstRxedTcpCloseState OBJECT-TYPE
    SYNTAX      ConfdString
    MAX-ACCESS  read-only
    STATUS      current
    DESCRIPTION "Number of TCP RSTs received in TCP Close State from Originator"
    ::= { affirmedServicesNatServiceConnTrackerClusterLevelConnTrackerModuleStatsEntry 90 }

affirmedServicesNatServiceConnTrackerClusterLevelConnTrackerModuleStatsRespRstRxedTcpCloseState OBJECT-TYPE
    SYNTAX      ConfdString
    MAX-ACCESS  read-only
    STATUS      current
    DESCRIPTION "Number of TCP RSTs received in TCP Close State from Responder"
    ::= { affirmedServicesNatServiceConnTrackerClusterLevelConnTrackerModuleStatsEntry 91 }

affirmedServicesNatServiceConnTrackerClusterLevelConnTrackerModuleStatsOrigSynRxedTcpBothWaySynSentState OBJECT-TYPE
    SYNTAX      ConfdString
    MAX-ACCESS  read-only
    STATUS      current
    DESCRIPTION "Number of TCP SYNs received in TCP BothWay Syn Sent State from Originator"
    ::= { affirmedServicesNatServiceConnTrackerClusterLevelConnTrackerModuleStatsEntry 92 }

affirmedServicesNatServiceConnTrackerClusterLevelConnTrackerModuleStatsRespSynRxedTcpBothWaySynSentState OBJECT-TYPE
    SYNTAX      ConfdString
    MAX-ACCESS  read-only
    STATUS      current
    DESCRIPTION "Number of TCP SYNs received in TCP BothWay Syn Sent State from Responder"
    ::= { affirmedServicesNatServiceConnTrackerClusterLevelConnTrackerModuleStatsEntry 93 }

affirmedServicesNatServiceConnTrackerClusterLevelConnTrackerModuleStatsOrigSynackRxedTcpBothWaySynSentState OBJECT-TYPE
    SYNTAX      ConfdString
    MAX-ACCESS  read-only
    STATUS      current
    DESCRIPTION "Number of TCP SYNACKs received in TCP BothWay Syn Sent State from Originator"
    ::= { affirmedServicesNatServiceConnTrackerClusterLevelConnTrackerModuleStatsEntry 94 }

affirmedServicesNatServiceConnTrackerClusterLevelConnTrackerModuleStatsRespSynackRxedTcpBothWaySynSentState OBJECT-TYPE
    SYNTAX      ConfdString
    MAX-ACCESS  read-only
    STATUS      current
    DESCRIPTION "Number of TCP SYNACKs received in TCP BothWay Syn Sent State from Responder"
    ::= { affirmedServicesNatServiceConnTrackerClusterLevelConnTrackerModuleStatsEntry 95 }

affirmedServicesNatServiceConnTrackerClusterLevelConnTrackerModuleStatsOrigAckRxedTcpBothWaySynSentState OBJECT-TYPE
    SYNTAX      ConfdString
    MAX-ACCESS  read-only
    STATUS      current
    DESCRIPTION "Number of TCP ACKs received in TCP BothWay Syn Sent State from Originator"
    ::= { affirmedServicesNatServiceConnTrackerClusterLevelConnTrackerModuleStatsEntry 96 }

affirmedServicesNatServiceConnTrackerClusterLevelConnTrackerModuleStatsRespAckRxedTcpBothWaySynSentState OBJECT-TYPE
    SYNTAX      ConfdString
    MAX-ACCESS  read-only
    STATUS      current
    DESCRIPTION "Number of TCP ACKs received in TCP BothWay Syn Sent State from Responder"
    ::= { affirmedServicesNatServiceConnTrackerClusterLevelConnTrackerModuleStatsEntry 97 }

affirmedServicesNatServiceConnTrackerClusterLevelConnTrackerModuleStatsOrigFinRxedTcpBothWaySynSentState OBJECT-TYPE
    SYNTAX      ConfdString
    MAX-ACCESS  read-only
    STATUS      current
    DESCRIPTION "Number of TCP FINs received in TCP BothWay Syn Sent State from Originator"
    ::= { affirmedServicesNatServiceConnTrackerClusterLevelConnTrackerModuleStatsEntry 98 }

affirmedServicesNatServiceConnTrackerClusterLevelConnTrackerModuleStatsRespFinRxedTcpBothWaySynSentState OBJECT-TYPE
    SYNTAX      ConfdString
    MAX-ACCESS  read-only
    STATUS      current
    DESCRIPTION "Number of TCP FINs received in TCP BothWay Syn Sent State from Responder"
    ::= { affirmedServicesNatServiceConnTrackerClusterLevelConnTrackerModuleStatsEntry 99 }

affirmedServicesNatServiceConnTrackerClusterLevelConnTrackerModuleStatsOrigRstRxedTcpBothWaySynSentState OBJECT-TYPE
    SYNTAX      ConfdString
    MAX-ACCESS  read-only
    STATUS      current
    DESCRIPTION "Number of TCP RSTs received in TCP BothWay Syn Sent State from Originator"
    ::= { affirmedServicesNatServiceConnTrackerClusterLevelConnTrackerModuleStatsEntry 100 }

affirmedServicesNatServiceConnTrackerClusterLevelConnTrackerModuleStatsRespRstRxedTcpBothWaySynSentState OBJECT-TYPE
    SYNTAX      ConfdString
    MAX-ACCESS  read-only
    STATUS      current
    DESCRIPTION "Number of TCP RSTs received in TCP BothWay Syn Sent State from Responder"
    ::= { affirmedServicesNatServiceConnTrackerClusterLevelConnTrackerModuleStatsEntry 101 }

affirmedServicesNatServiceConnTrackerClusterLevelConnTrackerModuleStatsOrigRxedUdpNoneState OBJECT-TYPE
    SYNTAX      ConfdString
    MAX-ACCESS  read-only
    STATUS      current
    DESCRIPTION "Number of UDP messages received in UDP None State from Originator"
    ::= { affirmedServicesNatServiceConnTrackerClusterLevelConnTrackerModuleStatsEntry 102 }

affirmedServicesNatServiceConnTrackerClusterLevelConnTrackerModuleStatsRespRxedUdpNoneState OBJECT-TYPE
    SYNTAX      ConfdString
    MAX-ACCESS  read-only
    STATUS      current
    DESCRIPTION "Number of UDP messages received in UDP None State from Responder"
    ::= { affirmedServicesNatServiceConnTrackerClusterLevelConnTrackerModuleStatsEntry 103 }

affirmedServicesNatServiceConnTrackerClusterLevelConnTrackerModuleStatsOrigRxedUdpOpenState OBJECT-TYPE
    SYNTAX      ConfdString
    MAX-ACCESS  read-only
    STATUS      current
    DESCRIPTION "Number of UDP messages received in UDP Open State from Originator"
    ::= { affirmedServicesNatServiceConnTrackerClusterLevelConnTrackerModuleStatsEntry 104 }

affirmedServicesNatServiceConnTrackerClusterLevelConnTrackerModuleStatsRespRxedUdpOpenState OBJECT-TYPE
    SYNTAX      ConfdString
    MAX-ACCESS  read-only
    STATUS      current
    DESCRIPTION "Number of UDP messages received in UDP Open State from Responder"
    ::= { affirmedServicesNatServiceConnTrackerClusterLevelConnTrackerModuleStatsEntry 105 }

affirmedServicesNatServiceConnTrackerClusterLevelConnTrackerModuleStatsOrigRxedUdpEstablishedState OBJECT-TYPE
    SYNTAX      ConfdString
    MAX-ACCESS  read-only
    STATUS      current
    DESCRIPTION "Number of UDP messages received in UDP Established State from Originator"
    ::= { affirmedServicesNatServiceConnTrackerClusterLevelConnTrackerModuleStatsEntry 106 }

affirmedServicesNatServiceConnTrackerClusterLevelConnTrackerModuleStatsRespRxedUdpEstablishedState OBJECT-TYPE
    SYNTAX      ConfdString
    MAX-ACCESS  read-only
    STATUS      current
    DESCRIPTION "Number of UDP messages received in UDP Established State from Responder"
    ::= { affirmedServicesNatServiceConnTrackerClusterLevelConnTrackerModuleStatsEntry 107 }

affirmedServicesNatServiceConnTrackerClusterLevelConnTrackerModuleStatsNumConnsUnSupportedProtocol OBJECT-TYPE
    SYNTAX      ConfdString
    MAX-ACCESS  read-only
    STATUS      current
    DESCRIPTION "Number of connection state tracking requests received for unsupported protocols"
    ::= { affirmedServicesNatServiceConnTrackerClusterLevelConnTrackerModuleStatsEntry 108 }

affirmedServicesNatServiceConnTrackerClusterLevelConnTrackerModuleStatsNumTcpChildConnectionRequest OBJECT-TYPE
    SYNTAX      ConfdString
    MAX-ACCESS  read-only
    STATUS      current
    DESCRIPTION "Number of child connection state tracking requests received for TCP based ALG"
    ::= { affirmedServicesNatServiceConnTrackerClusterLevelConnTrackerModuleStatsEntry 109 }

affirmedServicesNatServiceConnTrackerClusterLevelConnTrackerModuleStatsNumUdpChildConnectionRequest OBJECT-TYPE
    SYNTAX      ConfdString
    MAX-ACCESS  read-only
    STATUS      current
    DESCRIPTION "Number of child connection state tracking requests received for UDP based ALG"
    ::= { affirmedServicesNatServiceConnTrackerClusterLevelConnTrackerModuleStatsEntry 110 }

affirmedServicesNatServiceConnTrackerClusterLevelConnTrackerModuleStatsNumFlowProfileNotFound OBJECT-TYPE
    SYNTAX      ConfdString
    MAX-ACCESS  read-only
    STATUS      current
    DESCRIPTION "Number of times flow-state-tracking-profile/flow-idle-timeout-rule not found for a connection"
    ::= { affirmedServicesNatServiceConnTrackerClusterLevelConnTrackerModuleStatsEntry 111 }

affirmedServicesNatServiceConnTrackerNodeLevelConnTrackerModuleStatsTable OBJECT-TYPE
    SYNTAX      SEQUENCE OF AffirmedServicesNatServiceConnTrackerNodeLevelConnTrackerModuleStatsEntry
    MAX-ACCESS  not-accessible
    STATUS      current
    DESCRIPTION ""
    ::= { affirmedServicesNatServiceConnTrackerNodeLevel 1 }

affirmedServicesNatServiceConnTrackerNodeLevelConnTrackerModuleStatsEntry OBJECT-TYPE
    SYNTAX      AffirmedServicesNatServiceConnTrackerNodeLevelConnTrackerModuleStatsEntry
    MAX-ACCESS  not-accessible
    STATUS      current
    DESCRIPTION ""
    INDEX { affirmedServicesNatServiceConnTrackerNodeLevelConnTrackerModuleStatsChassis, affirmedServicesNatServiceConnTrackerNodeLevelConnTrackerModuleStatsSlot }
        ::= { affirmedServicesNatServiceConnTrackerNodeLevelConnTrackerModuleStatsTable 1 }

AffirmedServicesNatServiceConnTrackerNodeLevelConnTrackerModuleStatsEntry ::=
    SEQUENCE {
        affirmedServicesNatServiceConnTrackerNodeLevelConnTrackerModuleStatsChassis Unsigned32,
        affirmedServicesNatServiceConnTrackerNodeLevelConnTrackerModuleStatsSlot Unsigned32,
        affirmedServicesNatServiceConnTrackerNodeLevelConnTrackerModuleStatsOrigSynRxedTcpNoneState ConfdString,
        affirmedServicesNatServiceConnTrackerNodeLevelConnTrackerModuleStatsRespSynRxedTcpNoneState ConfdString,
        affirmedServicesNatServiceConnTrackerNodeLevelConnTrackerModuleStatsOrigSynackRxedTcpNoneState ConfdString,
        affirmedServicesNatServiceConnTrackerNodeLevelConnTrackerModuleStatsRespSynackRxedTcpNoneState ConfdString,
        affirmedServicesNatServiceConnTrackerNodeLevelConnTrackerModuleStatsOrigAckRxedTcpNoneState ConfdString,
        affirmedServicesNatServiceConnTrackerNodeLevelConnTrackerModuleStatsRespAckRxedTcpNoneState ConfdString,
        affirmedServicesNatServiceConnTrackerNodeLevelConnTrackerModuleStatsOrigFinRxedTcpNoneState ConfdString,
        affirmedServicesNatServiceConnTrackerNodeLevelConnTrackerModuleStatsRespFinRxedTcpNoneState ConfdString,
        affirmedServicesNatServiceConnTrackerNodeLevelConnTrackerModuleStatsOrigRstRxedTcpNoneState ConfdString,
        affirmedServicesNatServiceConnTrackerNodeLevelConnTrackerModuleStatsRespRstRxedTcpNoneState ConfdString,
        affirmedServicesNatServiceConnTrackerNodeLevelConnTrackerModuleStatsOrigSynRxedTcpSynSentState ConfdString,
        affirmedServicesNatServiceConnTrackerNodeLevelConnTrackerModuleStatsRespSynRxedTcpSynSentState ConfdString,
        affirmedServicesNatServiceConnTrackerNodeLevelConnTrackerModuleStatsOrigSynackRxedTcpSynSentState ConfdString,
        affirmedServicesNatServiceConnTrackerNodeLevelConnTrackerModuleStatsRespSynackRxedTcpSynSentState ConfdString,
        affirmedServicesNatServiceConnTrackerNodeLevelConnTrackerModuleStatsOrigAckRxedTcpSynSentState ConfdString,
        affirmedServicesNatServiceConnTrackerNodeLevelConnTrackerModuleStatsRespAckRxedTcpSynSentState ConfdString,
        affirmedServicesNatServiceConnTrackerNodeLevelConnTrackerModuleStatsOrigFinRxedTcpSynSentState ConfdString,
        affirmedServicesNatServiceConnTrackerNodeLevelConnTrackerModuleStatsRespFinRxedTcpSynSentState ConfdString,
        affirmedServicesNatServiceConnTrackerNodeLevelConnTrackerModuleStatsOrigRstRxedTcpSynSentState ConfdString,
        affirmedServicesNatServiceConnTrackerNodeLevelConnTrackerModuleStatsRespRstRxedTcpSynSentState ConfdString,
        affirmedServicesNatServiceConnTrackerNodeLevelConnTrackerModuleStatsOrigSynRxedTcpSynAckRcvdState ConfdString,
        affirmedServicesNatServiceConnTrackerNodeLevelConnTrackerModuleStatsRespSynRxedTcpSynAckRcvdState ConfdString,
        affirmedServicesNatServiceConnTrackerNodeLevelConnTrackerModuleStatsOrigSynackRxedTcpSynAckRcvdState ConfdString,
        affirmedServicesNatServiceConnTrackerNodeLevelConnTrackerModuleStatsRespSynackRxedTcpSynAckRcvdState ConfdString,
        affirmedServicesNatServiceConnTrackerNodeLevelConnTrackerModuleStatsOrigAckRxedTcpSynAckRcvdState ConfdString,
        affirmedServicesNatServiceConnTrackerNodeLevelConnTrackerModuleStatsRespAckRxedTcpSynAckRcvdState ConfdString,
        affirmedServicesNatServiceConnTrackerNodeLevelConnTrackerModuleStatsOrigFinRxedTcpSynAckRcvdState ConfdString,
        affirmedServicesNatServiceConnTrackerNodeLevelConnTrackerModuleStatsRespFinRxedTcpSynAckRcvdState ConfdString,
        affirmedServicesNatServiceConnTrackerNodeLevelConnTrackerModuleStatsOrigRstRxedTcpSynAckRcvdState ConfdString,
        affirmedServicesNatServiceConnTrackerNodeLevelConnTrackerModuleStatsRespRstRxedTcpSynAckRcvdState ConfdString,
        affirmedServicesNatServiceConnTrackerNodeLevelConnTrackerModuleStatsOrigSynRxedTcpEstablishedState ConfdString,
        affirmedServicesNatServiceConnTrackerNodeLevelConnTrackerModuleStatsRespSynRxedTcpEstablishedState ConfdString,
        affirmedServicesNatServiceConnTrackerNodeLevelConnTrackerModuleStatsOrigSynackRxedTcpEstablishedState ConfdString,
        affirmedServicesNatServiceConnTrackerNodeLevelConnTrackerModuleStatsRespSynackRxedTcpEstablishedState ConfdString,
        affirmedServicesNatServiceConnTrackerNodeLevelConnTrackerModuleStatsOrigAckRxedTcpEstablishedState ConfdString,
        affirmedServicesNatServiceConnTrackerNodeLevelConnTrackerModuleStatsRespAckRxedTcpEstablishedState ConfdString,
        affirmedServicesNatServiceConnTrackerNodeLevelConnTrackerModuleStatsOrigFinRxedTcpEstablishedState ConfdString,
        affirmedServicesNatServiceConnTrackerNodeLevelConnTrackerModuleStatsRespFinRxedTcpEstablishedState ConfdString,
        affirmedServicesNatServiceConnTrackerNodeLevelConnTrackerModuleStatsOrigRstRxedTcpEstablishedState ConfdString,
        affirmedServicesNatServiceConnTrackerNodeLevelConnTrackerModuleStatsRespRstRxedTcpEstablishedState ConfdString,
        affirmedServicesNatServiceConnTrackerNodeLevelConnTrackerModuleStatsOrigSynRxedTcpFinWaitState ConfdString,
        affirmedServicesNatServiceConnTrackerNodeLevelConnTrackerModuleStatsRespSynRxedTcpFinWaitState ConfdString,
        affirmedServicesNatServiceConnTrackerNodeLevelConnTrackerModuleStatsOrigSynackRxedTcpFinWaitState ConfdString,
        affirmedServicesNatServiceConnTrackerNodeLevelConnTrackerModuleStatsRespSynackRxedTcpFinWaitState ConfdString,
        affirmedServicesNatServiceConnTrackerNodeLevelConnTrackerModuleStatsOrigAckRxedTcpFinWaitState ConfdString,
        affirmedServicesNatServiceConnTrackerNodeLevelConnTrackerModuleStatsRespAckRxedTcpFinWaitState ConfdString,
        affirmedServicesNatServiceConnTrackerNodeLevelConnTrackerModuleStatsOrigFinRxedTcpFinWaitState ConfdString,
        affirmedServicesNatServiceConnTrackerNodeLevelConnTrackerModuleStatsRespFinRxedTcpFinWaitState ConfdString,
        affirmedServicesNatServiceConnTrackerNodeLevelConnTrackerModuleStatsOrigRstRxedTcpFinWaitState ConfdString,
        affirmedServicesNatServiceConnTrackerNodeLevelConnTrackerModuleStatsRespRstRxedTcpFinWaitState ConfdString,
        affirmedServicesNatServiceConnTrackerNodeLevelConnTrackerModuleStatsOrigSynRxedTcpCloseWaitState ConfdString,
        affirmedServicesNatServiceConnTrackerNodeLevelConnTrackerModuleStatsRespSynRxedTcpCloseWaitState ConfdString,
        affirmedServicesNatServiceConnTrackerNodeLevelConnTrackerModuleStatsOrigSynackRxedTcpCloseWaitState ConfdString,
        affirmedServicesNatServiceConnTrackerNodeLevelConnTrackerModuleStatsRespSynackRxedTcpCloseWaitState ConfdString,
        affirmedServicesNatServiceConnTrackerNodeLevelConnTrackerModuleStatsOrigAckRxedTcpCloseWaitState ConfdString,
        affirmedServicesNatServiceConnTrackerNodeLevelConnTrackerModuleStatsRespAckRxedTcpCloseWaitState ConfdString,
        affirmedServicesNatServiceConnTrackerNodeLevelConnTrackerModuleStatsOrigFinRxedTcpCloseWaitState ConfdString,
        affirmedServicesNatServiceConnTrackerNodeLevelConnTrackerModuleStatsRespFinRxedTcpCloseWaitState ConfdString,
        affirmedServicesNatServiceConnTrackerNodeLevelConnTrackerModuleStatsOrigRstRxedTcpCloseWaitState ConfdString,
        affirmedServicesNatServiceConnTrackerNodeLevelConnTrackerModuleStatsRespRstRxedTcpCloseWaitState ConfdString,
        affirmedServicesNatServiceConnTrackerNodeLevelConnTrackerModuleStatsOrigSynRxedTcpLastAckState ConfdString,
        affirmedServicesNatServiceConnTrackerNodeLevelConnTrackerModuleStatsRespSynRxedTcpLastAckState ConfdString,
        affirmedServicesNatServiceConnTrackerNodeLevelConnTrackerModuleStatsOrigSynackRxedTcpLastAckState ConfdString,
        affirmedServicesNatServiceConnTrackerNodeLevelConnTrackerModuleStatsRespSynackRxedTcpLastAckState ConfdString,
        affirmedServicesNatServiceConnTrackerNodeLevelConnTrackerModuleStatsOrigAckRxedTcpLastAckState ConfdString,
        affirmedServicesNatServiceConnTrackerNodeLevelConnTrackerModuleStatsRespAckRxedTcpLastAckState ConfdString,
        affirmedServicesNatServiceConnTrackerNodeLevelConnTrackerModuleStatsOrigFinRxedTcpLastAckState ConfdString,
        affirmedServicesNatServiceConnTrackerNodeLevelConnTrackerModuleStatsRespFinRxedTcpLastAckState ConfdString,
        affirmedServicesNatServiceConnTrackerNodeLevelConnTrackerModuleStatsOrigRstRxedTcpLastAckState ConfdString,
        affirmedServicesNatServiceConnTrackerNodeLevelConnTrackerModuleStatsRespRstRxedTcpLastAckState ConfdString,
        affirmedServicesNatServiceConnTrackerNodeLevelConnTrackerModuleStatsOrigSynRxedTcpTimedWaitState ConfdString,
        affirmedServicesNatServiceConnTrackerNodeLevelConnTrackerModuleStatsRespSynRxedTcpTimedWaitState ConfdString,
        affirmedServicesNatServiceConnTrackerNodeLevelConnTrackerModuleStatsOrigSynackRxedTcpTimedWaitState ConfdString,
        affirmedServicesNatServiceConnTrackerNodeLevelConnTrackerModuleStatsRespSynackRxedTcpTimedWaitState ConfdString,
        affirmedServicesNatServiceConnTrackerNodeLevelConnTrackerModuleStatsOrigAckRxedTcpTimedWaitState ConfdString,
        affirmedServicesNatServiceConnTrackerNodeLevelConnTrackerModuleStatsRespAckRxedTcpTimedWaitState ConfdString,
        affirmedServicesNatServiceConnTrackerNodeLevelConnTrackerModuleStatsOrigFinRxedTcpTimedWaitState ConfdString,
        affirmedServicesNatServiceConnTrackerNodeLevelConnTrackerModuleStatsRespFinRxedTcpTimedWaitState ConfdString,
        affirmedServicesNatServiceConnTrackerNodeLevelConnTrackerModuleStatsOrigRstRxedTcpTimedWaitState ConfdString,
        affirmedServicesNatServiceConnTrackerNodeLevelConnTrackerModuleStatsRespRstRxedTcpTimedWaitState ConfdString,
        affirmedServicesNatServiceConnTrackerNodeLevelConnTrackerModuleStatsOrigSynRxedTcpCloseState ConfdString,
        affirmedServicesNatServiceConnTrackerNodeLevelConnTrackerModuleStatsRespSynRxedTcpCloseState ConfdString,
        affirmedServicesNatServiceConnTrackerNodeLevelConnTrackerModuleStatsOrigSynackRxedTcpCloseState ConfdString,
        affirmedServicesNatServiceConnTrackerNodeLevelConnTrackerModuleStatsRespSynackRxedTcpCloseState ConfdString,
        affirmedServicesNatServiceConnTrackerNodeLevelConnTrackerModuleStatsOrigAckRxedTcpCloseState ConfdString,
        affirmedServicesNatServiceConnTrackerNodeLevelConnTrackerModuleStatsRespAckRxedTcpCloseState ConfdString,
        affirmedServicesNatServiceConnTrackerNodeLevelConnTrackerModuleStatsOrigFinRxedTcpCloseState ConfdString,
        affirmedServicesNatServiceConnTrackerNodeLevelConnTrackerModuleStatsRespFinRxedTcpCloseState ConfdString,
        affirmedServicesNatServiceConnTrackerNodeLevelConnTrackerModuleStatsOrigRstRxedTcpCloseState ConfdString,
        affirmedServicesNatServiceConnTrackerNodeLevelConnTrackerModuleStatsRespRstRxedTcpCloseState ConfdString,
        affirmedServicesNatServiceConnTrackerNodeLevelConnTrackerModuleStatsOrigSynRxedTcpBothWaySynSentState ConfdString,
        affirmedServicesNatServiceConnTrackerNodeLevelConnTrackerModuleStatsRespSynRxedTcpBothWaySynSentState ConfdString,
        affirmedServicesNatServiceConnTrackerNodeLevelConnTrackerModuleStatsOrigSynackRxedTcpBothWaySynSentState ConfdString,
        affirmedServicesNatServiceConnTrackerNodeLevelConnTrackerModuleStatsRespSynackRxedTcpBothWaySynSentState ConfdString,
        affirmedServicesNatServiceConnTrackerNodeLevelConnTrackerModuleStatsOrigAckRxedTcpBothWaySynSentState ConfdString,
        affirmedServicesNatServiceConnTrackerNodeLevelConnTrackerModuleStatsRespAckRxedTcpBothWaySynSentState ConfdString,
        affirmedServicesNatServiceConnTrackerNodeLevelConnTrackerModuleStatsOrigFinRxedTcpBothWaySynSentState ConfdString,
        affirmedServicesNatServiceConnTrackerNodeLevelConnTrackerModuleStatsRespFinRxedTcpBothWaySynSentState ConfdString,
        affirmedServicesNatServiceConnTrackerNodeLevelConnTrackerModuleStatsOrigRstRxedTcpBothWaySynSentState ConfdString,
        affirmedServicesNatServiceConnTrackerNodeLevelConnTrackerModuleStatsRespRstRxedTcpBothWaySynSentState ConfdString,
        affirmedServicesNatServiceConnTrackerNodeLevelConnTrackerModuleStatsOrigRxedUdpNoneState ConfdString,
        affirmedServicesNatServiceConnTrackerNodeLevelConnTrackerModuleStatsRespRxedUdpNoneState ConfdString,
        affirmedServicesNatServiceConnTrackerNodeLevelConnTrackerModuleStatsOrigRxedUdpOpenState ConfdString,
        affirmedServicesNatServiceConnTrackerNodeLevelConnTrackerModuleStatsRespRxedUdpOpenState ConfdString,
        affirmedServicesNatServiceConnTrackerNodeLevelConnTrackerModuleStatsOrigRxedUdpEstablishedState ConfdString,
        affirmedServicesNatServiceConnTrackerNodeLevelConnTrackerModuleStatsRespRxedUdpEstablishedState ConfdString,
        affirmedServicesNatServiceConnTrackerNodeLevelConnTrackerModuleStatsNumConnsUnSupportedProtocol ConfdString,
        affirmedServicesNatServiceConnTrackerNodeLevelConnTrackerModuleStatsNumTcpChildConnectionRequest ConfdString,
        affirmedServicesNatServiceConnTrackerNodeLevelConnTrackerModuleStatsNumUdpChildConnectionRequest ConfdString,
        affirmedServicesNatServiceConnTrackerNodeLevelConnTrackerModuleStatsNumFlowProfileNotFound ConfdString
    }

affirmedServicesNatServiceConnTrackerNodeLevelConnTrackerModuleStatsChassis OBJECT-TYPE
    SYNTAX      Unsigned32
    MAX-ACCESS  not-accessible
    STATUS      current
    DESCRIPTION "Chassis id"
    ::= { affirmedServicesNatServiceConnTrackerNodeLevelConnTrackerModuleStatsEntry 1 }

affirmedServicesNatServiceConnTrackerNodeLevelConnTrackerModuleStatsSlot OBJECT-TYPE
    SYNTAX      Unsigned32
    MAX-ACCESS  not-accessible
    STATUS      current
    DESCRIPTION "Slot id"
    ::= { affirmedServicesNatServiceConnTrackerNodeLevelConnTrackerModuleStatsEntry 2 }

affirmedServicesNatServiceConnTrackerNodeLevelConnTrackerModuleStatsOrigSynRxedTcpNoneState OBJECT-TYPE
    SYNTAX      ConfdString
    MAX-ACCESS  read-only
    STATUS      current
    DESCRIPTION "Number of TCP SYNs received in TCP None State from Originator"
    ::= { affirmedServicesNatServiceConnTrackerNodeLevelConnTrackerModuleStatsEntry 3 }

affirmedServicesNatServiceConnTrackerNodeLevelConnTrackerModuleStatsRespSynRxedTcpNoneState OBJECT-TYPE
    SYNTAX      ConfdString
    MAX-ACCESS  read-only
    STATUS      current
    DESCRIPTION "Number of TCP SYNs received in TCP None State from Responder"
    ::= { affirmedServicesNatServiceConnTrackerNodeLevelConnTrackerModuleStatsEntry 4 }

affirmedServicesNatServiceConnTrackerNodeLevelConnTrackerModuleStatsOrigSynackRxedTcpNoneState OBJECT-TYPE
    SYNTAX      ConfdString
    MAX-ACCESS  read-only
    STATUS      current
    DESCRIPTION "Number of TCP SYNACKs received in TCP None State from Originator"
    ::= { affirmedServicesNatServiceConnTrackerNodeLevelConnTrackerModuleStatsEntry 5 }

affirmedServicesNatServiceConnTrackerNodeLevelConnTrackerModuleStatsRespSynackRxedTcpNoneState OBJECT-TYPE
    SYNTAX      ConfdString
    MAX-ACCESS  read-only
    STATUS      current
    DESCRIPTION "Number of TCP SYNACKs received in TCP None State from Responder"
    ::= { affirmedServicesNatServiceConnTrackerNodeLevelConnTrackerModuleStatsEntry 6 }

affirmedServicesNatServiceConnTrackerNodeLevelConnTrackerModuleStatsOrigAckRxedTcpNoneState OBJECT-TYPE
    SYNTAX      ConfdString
    MAX-ACCESS  read-only
    STATUS      current
    DESCRIPTION "Number of TCP ACKs received in TCP None State from Originator"
    ::= { affirmedServicesNatServiceConnTrackerNodeLevelConnTrackerModuleStatsEntry 7 }

affirmedServicesNatServiceConnTrackerNodeLevelConnTrackerModuleStatsRespAckRxedTcpNoneState OBJECT-TYPE
    SYNTAX      ConfdString
    MAX-ACCESS  read-only
    STATUS      current
    DESCRIPTION "Number of TCP ACKs received in TCP None State from Responder"
    ::= { affirmedServicesNatServiceConnTrackerNodeLevelConnTrackerModuleStatsEntry 8 }

affirmedServicesNatServiceConnTrackerNodeLevelConnTrackerModuleStatsOrigFinRxedTcpNoneState OBJECT-TYPE
    SYNTAX      ConfdString
    MAX-ACCESS  read-only
    STATUS      current
    DESCRIPTION "Number of TCP FINs received in TCP None State from Originator"
    ::= { affirmedServicesNatServiceConnTrackerNodeLevelConnTrackerModuleStatsEntry 9 }

affirmedServicesNatServiceConnTrackerNodeLevelConnTrackerModuleStatsRespFinRxedTcpNoneState OBJECT-TYPE
    SYNTAX      ConfdString
    MAX-ACCESS  read-only
    STATUS      current
    DESCRIPTION "Number of TCP FINs received in TCP None State from Responder"
    ::= { affirmedServicesNatServiceConnTrackerNodeLevelConnTrackerModuleStatsEntry 10 }

affirmedServicesNatServiceConnTrackerNodeLevelConnTrackerModuleStatsOrigRstRxedTcpNoneState OBJECT-TYPE
    SYNTAX      ConfdString
    MAX-ACCESS  read-only
    STATUS      current
    DESCRIPTION "Number of TCP RSTs received in TCP None State from Originator"
    ::= { affirmedServicesNatServiceConnTrackerNodeLevelConnTrackerModuleStatsEntry 11 }

affirmedServicesNatServiceConnTrackerNodeLevelConnTrackerModuleStatsRespRstRxedTcpNoneState OBJECT-TYPE
    SYNTAX      ConfdString
    MAX-ACCESS  read-only
    STATUS      current
    DESCRIPTION "Number of TCP RSTs received in TCP None State from Responder"
    ::= { affirmedServicesNatServiceConnTrackerNodeLevelConnTrackerModuleStatsEntry 12 }

affirmedServicesNatServiceConnTrackerNodeLevelConnTrackerModuleStatsOrigSynRxedTcpSynSentState OBJECT-TYPE
    SYNTAX      ConfdString
    MAX-ACCESS  read-only
    STATUS      current
    DESCRIPTION "Number of TCP SYNs received in TCP Syn Sent State from Originator"
    ::= { affirmedServicesNatServiceConnTrackerNodeLevelConnTrackerModuleStatsEntry 13 }

affirmedServicesNatServiceConnTrackerNodeLevelConnTrackerModuleStatsRespSynRxedTcpSynSentState OBJECT-TYPE
    SYNTAX      ConfdString
    MAX-ACCESS  read-only
    STATUS      current
    DESCRIPTION "Number of TCP SYNs received in TCP Syn Sent State from Responder"
    ::= { affirmedServicesNatServiceConnTrackerNodeLevelConnTrackerModuleStatsEntry 14 }

affirmedServicesNatServiceConnTrackerNodeLevelConnTrackerModuleStatsOrigSynackRxedTcpSynSentState OBJECT-TYPE
    SYNTAX      ConfdString
    MAX-ACCESS  read-only
    STATUS      current
    DESCRIPTION "Number of TCP SYNACKs received in TCP Syn Sent State from Originator"
    ::= { affirmedServicesNatServiceConnTrackerNodeLevelConnTrackerModuleStatsEntry 15 }

affirmedServicesNatServiceConnTrackerNodeLevelConnTrackerModuleStatsRespSynackRxedTcpSynSentState OBJECT-TYPE
    SYNTAX      ConfdString
    MAX-ACCESS  read-only
    STATUS      current
    DESCRIPTION "Number of TCP SYNACKs received in TCP Syn Sent State from Responder"
    ::= { affirmedServicesNatServiceConnTrackerNodeLevelConnTrackerModuleStatsEntry 16 }

affirmedServicesNatServiceConnTrackerNodeLevelConnTrackerModuleStatsOrigAckRxedTcpSynSentState OBJECT-TYPE
    SYNTAX      ConfdString
    MAX-ACCESS  read-only
    STATUS      current
    DESCRIPTION "Number of TCP ACKs received in TCP Syn Sent State from Originator"
    ::= { affirmedServicesNatServiceConnTrackerNodeLevelConnTrackerModuleStatsEntry 17 }

affirmedServicesNatServiceConnTrackerNodeLevelConnTrackerModuleStatsRespAckRxedTcpSynSentState OBJECT-TYPE
    SYNTAX      ConfdString
    MAX-ACCESS  read-only
    STATUS      current
    DESCRIPTION "Number of TCP ACKs received in TCP Syn Sent State from Responder"
    ::= { affirmedServicesNatServiceConnTrackerNodeLevelConnTrackerModuleStatsEntry 18 }

affirmedServicesNatServiceConnTrackerNodeLevelConnTrackerModuleStatsOrigFinRxedTcpSynSentState OBJECT-TYPE
    SYNTAX      ConfdString
    MAX-ACCESS  read-only
    STATUS      current
    DESCRIPTION "Number of TCP FINs received in TCP Syn Sent State from Originator"
    ::= { affirmedServicesNatServiceConnTrackerNodeLevelConnTrackerModuleStatsEntry 19 }

affirmedServicesNatServiceConnTrackerNodeLevelConnTrackerModuleStatsRespFinRxedTcpSynSentState OBJECT-TYPE
    SYNTAX      ConfdString
    MAX-ACCESS  read-only
    STATUS      current
    DESCRIPTION "Number of TCP FINs received in TCP Syn Sent State from Responder"
    ::= { affirmedServicesNatServiceConnTrackerNodeLevelConnTrackerModuleStatsEntry 20 }

affirmedServicesNatServiceConnTrackerNodeLevelConnTrackerModuleStatsOrigRstRxedTcpSynSentState OBJECT-TYPE
    SYNTAX      ConfdString
    MAX-ACCESS  read-only
    STATUS      current
    DESCRIPTION "Number of TCP RSTs received in TCP Syn Sent State from Originator"
    ::= { affirmedServicesNatServiceConnTrackerNodeLevelConnTrackerModuleStatsEntry 21 }

affirmedServicesNatServiceConnTrackerNodeLevelConnTrackerModuleStatsRespRstRxedTcpSynSentState OBJECT-TYPE
    SYNTAX      ConfdString
    MAX-ACCESS  read-only
    STATUS      current
    DESCRIPTION "Number of TCP RSTs received in TCP Syn Sent State from Responder"
    ::= { affirmedServicesNatServiceConnTrackerNodeLevelConnTrackerModuleStatsEntry 22 }

affirmedServicesNatServiceConnTrackerNodeLevelConnTrackerModuleStatsOrigSynRxedTcpSynAckRcvdState OBJECT-TYPE
    SYNTAX      ConfdString
    MAX-ACCESS  read-only
    STATUS      current
    DESCRIPTION "Number of TCP SYNs received in TCP SynAck Rcvd State from Originator"
    ::= { affirmedServicesNatServiceConnTrackerNodeLevelConnTrackerModuleStatsEntry 23 }

affirmedServicesNatServiceConnTrackerNodeLevelConnTrackerModuleStatsRespSynRxedTcpSynAckRcvdState OBJECT-TYPE
    SYNTAX      ConfdString
    MAX-ACCESS  read-only
    STATUS      current
    DESCRIPTION "Number of TCP SYNs received in TCP SynAck Rcvd State from Responder"
    ::= { affirmedServicesNatServiceConnTrackerNodeLevelConnTrackerModuleStatsEntry 24 }

affirmedServicesNatServiceConnTrackerNodeLevelConnTrackerModuleStatsOrigSynackRxedTcpSynAckRcvdState OBJECT-TYPE
    SYNTAX      ConfdString
    MAX-ACCESS  read-only
    STATUS      current
    DESCRIPTION "Number of TCP SYNACKs received in TCP SynAck Rcvd State from Originator"
    ::= { affirmedServicesNatServiceConnTrackerNodeLevelConnTrackerModuleStatsEntry 25 }

affirmedServicesNatServiceConnTrackerNodeLevelConnTrackerModuleStatsRespSynackRxedTcpSynAckRcvdState OBJECT-TYPE
    SYNTAX      ConfdString
    MAX-ACCESS  read-only
    STATUS      current
    DESCRIPTION "Number of TCP SYNACKs received in TCP SynAck Rcvd State from Responder"
    ::= { affirmedServicesNatServiceConnTrackerNodeLevelConnTrackerModuleStatsEntry 26 }

affirmedServicesNatServiceConnTrackerNodeLevelConnTrackerModuleStatsOrigAckRxedTcpSynAckRcvdState OBJECT-TYPE
    SYNTAX      ConfdString
    MAX-ACCESS  read-only
    STATUS      current
    DESCRIPTION "Number of TCP ACKs received in TCP SynAck Rcvd State from Originator"
    ::= { affirmedServicesNatServiceConnTrackerNodeLevelConnTrackerModuleStatsEntry 27 }

affirmedServicesNatServiceConnTrackerNodeLevelConnTrackerModuleStatsRespAckRxedTcpSynAckRcvdState OBJECT-TYPE
    SYNTAX      ConfdString
    MAX-ACCESS  read-only
    STATUS      current
    DESCRIPTION "Number of TCP ACKs received in TCP SynAck Rcvd State from Responder"
    ::= { affirmedServicesNatServiceConnTrackerNodeLevelConnTrackerModuleStatsEntry 28 }

affirmedServicesNatServiceConnTrackerNodeLevelConnTrackerModuleStatsOrigFinRxedTcpSynAckRcvdState OBJECT-TYPE
    SYNTAX      ConfdString
    MAX-ACCESS  read-only
    STATUS      current
    DESCRIPTION "Number of TCP FINs received in TCP SynAck Rcvd State from Originator"
    ::= { affirmedServicesNatServiceConnTrackerNodeLevelConnTrackerModuleStatsEntry 29 }

affirmedServicesNatServiceConnTrackerNodeLevelConnTrackerModuleStatsRespFinRxedTcpSynAckRcvdState OBJECT-TYPE
    SYNTAX      ConfdString
    MAX-ACCESS  read-only
    STATUS      current
    DESCRIPTION "Number of TCP FINs received in TCP SynAck Rcvd State from Responder"
    ::= { affirmedServicesNatServiceConnTrackerNodeLevelConnTrackerModuleStatsEntry 30 }

affirmedServicesNatServiceConnTrackerNodeLevelConnTrackerModuleStatsOrigRstRxedTcpSynAckRcvdState OBJECT-TYPE
    SYNTAX      ConfdString
    MAX-ACCESS  read-only
    STATUS      current
    DESCRIPTION "Number of TCP RSTs received in TCP SynAck Rcvd State from Originator"
    ::= { affirmedServicesNatServiceConnTrackerNodeLevelConnTrackerModuleStatsEntry 31 }

affirmedServicesNatServiceConnTrackerNodeLevelConnTrackerModuleStatsRespRstRxedTcpSynAckRcvdState OBJECT-TYPE
    SYNTAX      ConfdString
    MAX-ACCESS  read-only
    STATUS      current
    DESCRIPTION "Number of TCP RSTs received in TCP SynAck Rcvd State from Responder"
    ::= { affirmedServicesNatServiceConnTrackerNodeLevelConnTrackerModuleStatsEntry 32 }

affirmedServicesNatServiceConnTrackerNodeLevelConnTrackerModuleStatsOrigSynRxedTcpEstablishedState OBJECT-TYPE
    SYNTAX      ConfdString
    MAX-ACCESS  read-only
    STATUS      current
    DESCRIPTION "Number of TCP SYNs received in TCP Established State from Originator"
    ::= { affirmedServicesNatServiceConnTrackerNodeLevelConnTrackerModuleStatsEntry 33 }

affirmedServicesNatServiceConnTrackerNodeLevelConnTrackerModuleStatsRespSynRxedTcpEstablishedState OBJECT-TYPE
    SYNTAX      ConfdString
    MAX-ACCESS  read-only
    STATUS      current
    DESCRIPTION "Number of TCP SYNs received in TCP Established State from Responder"
    ::= { affirmedServicesNatServiceConnTrackerNodeLevelConnTrackerModuleStatsEntry 34 }

affirmedServicesNatServiceConnTrackerNodeLevelConnTrackerModuleStatsOrigSynackRxedTcpEstablishedState OBJECT-TYPE
    SYNTAX      ConfdString
    MAX-ACCESS  read-only
    STATUS      current
    DESCRIPTION "Number of TCP SYNACKs received in TCP Established State from Originator"
    ::= { affirmedServicesNatServiceConnTrackerNodeLevelConnTrackerModuleStatsEntry 35 }

affirmedServicesNatServiceConnTrackerNodeLevelConnTrackerModuleStatsRespSynackRxedTcpEstablishedState OBJECT-TYPE
    SYNTAX      ConfdString
    MAX-ACCESS  read-only
    STATUS      current
    DESCRIPTION "Number of TCP SYNACKs received in TCP Established State from Responder"
    ::= { affirmedServicesNatServiceConnTrackerNodeLevelConnTrackerModuleStatsEntry 36 }

affirmedServicesNatServiceConnTrackerNodeLevelConnTrackerModuleStatsOrigAckRxedTcpEstablishedState OBJECT-TYPE
    SYNTAX      ConfdString
    MAX-ACCESS  read-only
    STATUS      current
    DESCRIPTION "Number of TCP ACKs received in TCP Established State from Originator"
    ::= { affirmedServicesNatServiceConnTrackerNodeLevelConnTrackerModuleStatsEntry 37 }

affirmedServicesNatServiceConnTrackerNodeLevelConnTrackerModuleStatsRespAckRxedTcpEstablishedState OBJECT-TYPE
    SYNTAX      ConfdString
    MAX-ACCESS  read-only
    STATUS      current
    DESCRIPTION "Number of TCP ACKs received in TCP Established State from Responder"
    ::= { affirmedServicesNatServiceConnTrackerNodeLevelConnTrackerModuleStatsEntry 38 }

affirmedServicesNatServiceConnTrackerNodeLevelConnTrackerModuleStatsOrigFinRxedTcpEstablishedState OBJECT-TYPE
    SYNTAX      ConfdString
    MAX-ACCESS  read-only
    STATUS      current
    DESCRIPTION "Number of TCP FINs received in TCP Established State from Originator"
    ::= { affirmedServicesNatServiceConnTrackerNodeLevelConnTrackerModuleStatsEntry 39 }

affirmedServicesNatServiceConnTrackerNodeLevelConnTrackerModuleStatsRespFinRxedTcpEstablishedState OBJECT-TYPE
    SYNTAX      ConfdString
    MAX-ACCESS  read-only
    STATUS      current
    DESCRIPTION "Number of TCP FINs received in TCP Established State from Responder"
    ::= { affirmedServicesNatServiceConnTrackerNodeLevelConnTrackerModuleStatsEntry 40 }

affirmedServicesNatServiceConnTrackerNodeLevelConnTrackerModuleStatsOrigRstRxedTcpEstablishedState OBJECT-TYPE
    SYNTAX      ConfdString
    MAX-ACCESS  read-only
    STATUS      current
    DESCRIPTION "Number of TCP RSTs received in TCP Established State from Originator"
    ::= { affirmedServicesNatServiceConnTrackerNodeLevelConnTrackerModuleStatsEntry 41 }

affirmedServicesNatServiceConnTrackerNodeLevelConnTrackerModuleStatsRespRstRxedTcpEstablishedState OBJECT-TYPE
    SYNTAX      ConfdString
    MAX-ACCESS  read-only
    STATUS      current
    DESCRIPTION "Number of TCP RSTs received in TCP Established State from Responder"
    ::= { affirmedServicesNatServiceConnTrackerNodeLevelConnTrackerModuleStatsEntry 42 }

affirmedServicesNatServiceConnTrackerNodeLevelConnTrackerModuleStatsOrigSynRxedTcpFinWaitState OBJECT-TYPE
    SYNTAX      ConfdString
    MAX-ACCESS  read-only
    STATUS      current
    DESCRIPTION "Number of TCP SYNs received in TCP Fin Wait State from Originator"
    ::= { affirmedServicesNatServiceConnTrackerNodeLevelConnTrackerModuleStatsEntry 43 }

affirmedServicesNatServiceConnTrackerNodeLevelConnTrackerModuleStatsRespSynRxedTcpFinWaitState OBJECT-TYPE
    SYNTAX      ConfdString
    MAX-ACCESS  read-only
    STATUS      current
    DESCRIPTION "Number of TCP SYNs received in TCP Fin Wait State from Responder"
    ::= { affirmedServicesNatServiceConnTrackerNodeLevelConnTrackerModuleStatsEntry 44 }

affirmedServicesNatServiceConnTrackerNodeLevelConnTrackerModuleStatsOrigSynackRxedTcpFinWaitState OBJECT-TYPE
    SYNTAX      ConfdString
    MAX-ACCESS  read-only
    STATUS      current
    DESCRIPTION "Number of TCP SYNACKs received in TCP Fin Wait State from Originator"
    ::= { affirmedServicesNatServiceConnTrackerNodeLevelConnTrackerModuleStatsEntry 45 }

affirmedServicesNatServiceConnTrackerNodeLevelConnTrackerModuleStatsRespSynackRxedTcpFinWaitState OBJECT-TYPE
    SYNTAX      ConfdString
    MAX-ACCESS  read-only
    STATUS      current
    DESCRIPTION "Number of TCP SYNACKs received in TCP Fin Wait State from Responder"
    ::= { affirmedServicesNatServiceConnTrackerNodeLevelConnTrackerModuleStatsEntry 46 }

affirmedServicesNatServiceConnTrackerNodeLevelConnTrackerModuleStatsOrigAckRxedTcpFinWaitState OBJECT-TYPE
    SYNTAX      ConfdString
    MAX-ACCESS  read-only
    STATUS      current
    DESCRIPTION "Number of TCP ACKs received in TCP Fin Wait State from Originator"
    ::= { affirmedServicesNatServiceConnTrackerNodeLevelConnTrackerModuleStatsEntry 47 }

affirmedServicesNatServiceConnTrackerNodeLevelConnTrackerModuleStatsRespAckRxedTcpFinWaitState OBJECT-TYPE
    SYNTAX      ConfdString
    MAX-ACCESS  read-only
    STATUS      current
    DESCRIPTION "Number of TCP ACKs received in TCP Fin Wait State from Responder"
    ::= { affirmedServicesNatServiceConnTrackerNodeLevelConnTrackerModuleStatsEntry 48 }

affirmedServicesNatServiceConnTrackerNodeLevelConnTrackerModuleStatsOrigFinRxedTcpFinWaitState OBJECT-TYPE
    SYNTAX      ConfdString
    MAX-ACCESS  read-only
    STATUS      current
    DESCRIPTION "Number of TCP FINs received in TCP Fin Wait State from Originator"
    ::= { affirmedServicesNatServiceConnTrackerNodeLevelConnTrackerModuleStatsEntry 49 }

affirmedServicesNatServiceConnTrackerNodeLevelConnTrackerModuleStatsRespFinRxedTcpFinWaitState OBJECT-TYPE
    SYNTAX      ConfdString
    MAX-ACCESS  read-only
    STATUS      current
    DESCRIPTION "Number of TCP FINs received in TCP Fin Wait State from Responder"
    ::= { affirmedServicesNatServiceConnTrackerNodeLevelConnTrackerModuleStatsEntry 50 }

affirmedServicesNatServiceConnTrackerNodeLevelConnTrackerModuleStatsOrigRstRxedTcpFinWaitState OBJECT-TYPE
    SYNTAX      ConfdString
    MAX-ACCESS  read-only
    STATUS      current
    DESCRIPTION "Number of TCP RSTs received in TCP Fin Wait State from Originator"
    ::= { affirmedServicesNatServiceConnTrackerNodeLevelConnTrackerModuleStatsEntry 51 }

affirmedServicesNatServiceConnTrackerNodeLevelConnTrackerModuleStatsRespRstRxedTcpFinWaitState OBJECT-TYPE
    SYNTAX      ConfdString
    MAX-ACCESS  read-only
    STATUS      current
    DESCRIPTION "Number of TCP RSTs received in TCP Fin Wait State from Responder"
    ::= { affirmedServicesNatServiceConnTrackerNodeLevelConnTrackerModuleStatsEntry 52 }

affirmedServicesNatServiceConnTrackerNodeLevelConnTrackerModuleStatsOrigSynRxedTcpCloseWaitState OBJECT-TYPE
    SYNTAX      ConfdString
    MAX-ACCESS  read-only
    STATUS      current
    DESCRIPTION "Number of TCP SYNs received in TCP Close Wait State from Originator"
    ::= { affirmedServicesNatServiceConnTrackerNodeLevelConnTrackerModuleStatsEntry 53 }

affirmedServicesNatServiceConnTrackerNodeLevelConnTrackerModuleStatsRespSynRxedTcpCloseWaitState OBJECT-TYPE
    SYNTAX      ConfdString
    MAX-ACCESS  read-only
    STATUS      current
    DESCRIPTION "Number of TCP SYNs received in TCP Close Wait State from Responder"
    ::= { affirmedServicesNatServiceConnTrackerNodeLevelConnTrackerModuleStatsEntry 54 }

affirmedServicesNatServiceConnTrackerNodeLevelConnTrackerModuleStatsOrigSynackRxedTcpCloseWaitState OBJECT-TYPE
    SYNTAX      ConfdString
    MAX-ACCESS  read-only
    STATUS      current
    DESCRIPTION "Number of TCP SYNACKs received in TCP Close Wait State from Originator"
    ::= { affirmedServicesNatServiceConnTrackerNodeLevelConnTrackerModuleStatsEntry 55 }

affirmedServicesNatServiceConnTrackerNodeLevelConnTrackerModuleStatsRespSynackRxedTcpCloseWaitState OBJECT-TYPE
    SYNTAX      ConfdString
    MAX-ACCESS  read-only
    STATUS      current
    DESCRIPTION "Number of TCP SYNACKs received in TCP Close Wait State from Responder"
    ::= { affirmedServicesNatServiceConnTrackerNodeLevelConnTrackerModuleStatsEntry 56 }

affirmedServicesNatServiceConnTrackerNodeLevelConnTrackerModuleStatsOrigAckRxedTcpCloseWaitState OBJECT-TYPE
    SYNTAX      ConfdString
    MAX-ACCESS  read-only
    STATUS      current
    DESCRIPTION "Number of TCP ACKs received in TCP Close Wait State from Originator"
    ::= { affirmedServicesNatServiceConnTrackerNodeLevelConnTrackerModuleStatsEntry 57 }

affirmedServicesNatServiceConnTrackerNodeLevelConnTrackerModuleStatsRespAckRxedTcpCloseWaitState OBJECT-TYPE
    SYNTAX      ConfdString
    MAX-ACCESS  read-only
    STATUS      current
    DESCRIPTION "Number of TCP ACKs received in TCP Close Wait State from Responder"
    ::= { affirmedServicesNatServiceConnTrackerNodeLevelConnTrackerModuleStatsEntry 58 }

affirmedServicesNatServiceConnTrackerNodeLevelConnTrackerModuleStatsOrigFinRxedTcpCloseWaitState OBJECT-TYPE
    SYNTAX      ConfdString
    MAX-ACCESS  read-only
    STATUS      current
    DESCRIPTION "Number of TCP FINs received in TCP Close Wait State from Originator"
    ::= { affirmedServicesNatServiceConnTrackerNodeLevelConnTrackerModuleStatsEntry 59 }

affirmedServicesNatServiceConnTrackerNodeLevelConnTrackerModuleStatsRespFinRxedTcpCloseWaitState OBJECT-TYPE
    SYNTAX      ConfdString
    MAX-ACCESS  read-only
    STATUS      current
    DESCRIPTION "Number of TCP FINs received in TCP Close Wait State from Responder"
    ::= { affirmedServicesNatServiceConnTrackerNodeLevelConnTrackerModuleStatsEntry 60 }

affirmedServicesNatServiceConnTrackerNodeLevelConnTrackerModuleStatsOrigRstRxedTcpCloseWaitState OBJECT-TYPE
    SYNTAX      ConfdString
    MAX-ACCESS  read-only
    STATUS      current
    DESCRIPTION "Number of TCP RSTs received in TCP Close Wait State from Originator"
    ::= { affirmedServicesNatServiceConnTrackerNodeLevelConnTrackerModuleStatsEntry 61 }

affirmedServicesNatServiceConnTrackerNodeLevelConnTrackerModuleStatsRespRstRxedTcpCloseWaitState OBJECT-TYPE
    SYNTAX      ConfdString
    MAX-ACCESS  read-only
    STATUS      current
    DESCRIPTION "Number of TCP RSTs received in TCP Close Wait State from Responder"
    ::= { affirmedServicesNatServiceConnTrackerNodeLevelConnTrackerModuleStatsEntry 62 }

affirmedServicesNatServiceConnTrackerNodeLevelConnTrackerModuleStatsOrigSynRxedTcpLastAckState OBJECT-TYPE
    SYNTAX      ConfdString
    MAX-ACCESS  read-only
    STATUS      current
    DESCRIPTION "Number of TCP SYNs received in TCP Last Ack State from Originator"
    ::= { affirmedServicesNatServiceConnTrackerNodeLevelConnTrackerModuleStatsEntry 63 }

affirmedServicesNatServiceConnTrackerNodeLevelConnTrackerModuleStatsRespSynRxedTcpLastAckState OBJECT-TYPE
    SYNTAX      ConfdString
    MAX-ACCESS  read-only
    STATUS      current
    DESCRIPTION "Number of TCP SYNs received in TCP Last Ack State from Responder"
    ::= { affirmedServicesNatServiceConnTrackerNodeLevelConnTrackerModuleStatsEntry 64 }

affirmedServicesNatServiceConnTrackerNodeLevelConnTrackerModuleStatsOrigSynackRxedTcpLastAckState OBJECT-TYPE
    SYNTAX      ConfdString
    MAX-ACCESS  read-only
    STATUS      current
    DESCRIPTION "Number of TCP SYNACKs received in TCP Last Ack State from Originator"
    ::= { affirmedServicesNatServiceConnTrackerNodeLevelConnTrackerModuleStatsEntry 65 }

affirmedServicesNatServiceConnTrackerNodeLevelConnTrackerModuleStatsRespSynackRxedTcpLastAckState OBJECT-TYPE
    SYNTAX      ConfdString
    MAX-ACCESS  read-only
    STATUS      current
    DESCRIPTION "Number of TCP SYNACKs received in TCP Last Ack State from Responder"
    ::= { affirmedServicesNatServiceConnTrackerNodeLevelConnTrackerModuleStatsEntry 66 }

affirmedServicesNatServiceConnTrackerNodeLevelConnTrackerModuleStatsOrigAckRxedTcpLastAckState OBJECT-TYPE
    SYNTAX      ConfdString
    MAX-ACCESS  read-only
    STATUS      current
    DESCRIPTION "Number of TCP ACKs received in TCP Last Ack State from Originator"
    ::= { affirmedServicesNatServiceConnTrackerNodeLevelConnTrackerModuleStatsEntry 67 }

affirmedServicesNatServiceConnTrackerNodeLevelConnTrackerModuleStatsRespAckRxedTcpLastAckState OBJECT-TYPE
    SYNTAX      ConfdString
    MAX-ACCESS  read-only
    STATUS      current
    DESCRIPTION "Number of TCP ACKs received in TCP Last Ack State from Responder"
    ::= { affirmedServicesNatServiceConnTrackerNodeLevelConnTrackerModuleStatsEntry 68 }

affirmedServicesNatServiceConnTrackerNodeLevelConnTrackerModuleStatsOrigFinRxedTcpLastAckState OBJECT-TYPE
    SYNTAX      ConfdString
    MAX-ACCESS  read-only
    STATUS      current
    DESCRIPTION "Number of TCP FINs received in TCP Last Ack State from Originator"
    ::= { affirmedServicesNatServiceConnTrackerNodeLevelConnTrackerModuleStatsEntry 69 }

affirmedServicesNatServiceConnTrackerNodeLevelConnTrackerModuleStatsRespFinRxedTcpLastAckState OBJECT-TYPE
    SYNTAX      ConfdString
    MAX-ACCESS  read-only
    STATUS      current
    DESCRIPTION "Number of TCP FINs received in TCP Last Ack State from Responder"
    ::= { affirmedServicesNatServiceConnTrackerNodeLevelConnTrackerModuleStatsEntry 70 }

affirmedServicesNatServiceConnTrackerNodeLevelConnTrackerModuleStatsOrigRstRxedTcpLastAckState OBJECT-TYPE
    SYNTAX      ConfdString
    MAX-ACCESS  read-only
    STATUS      current
    DESCRIPTION "Number of TCP RSTs received in TCP Last Ack State from Originator"
    ::= { affirmedServicesNatServiceConnTrackerNodeLevelConnTrackerModuleStatsEntry 71 }

affirmedServicesNatServiceConnTrackerNodeLevelConnTrackerModuleStatsRespRstRxedTcpLastAckState OBJECT-TYPE
    SYNTAX      ConfdString
    MAX-ACCESS  read-only
    STATUS      current
    DESCRIPTION "Number of TCP RSTs received in TCP Last Ack State from Responder"
    ::= { affirmedServicesNatServiceConnTrackerNodeLevelConnTrackerModuleStatsEntry 72 }

affirmedServicesNatServiceConnTrackerNodeLevelConnTrackerModuleStatsOrigSynRxedTcpTimedWaitState OBJECT-TYPE
    SYNTAX      ConfdString
    MAX-ACCESS  read-only
    STATUS      current
    DESCRIPTION "Number of TCP SYNs received in TCP Timed Wait State from Originator"
    ::= { affirmedServicesNatServiceConnTrackerNodeLevelConnTrackerModuleStatsEntry 73 }

affirmedServicesNatServiceConnTrackerNodeLevelConnTrackerModuleStatsRespSynRxedTcpTimedWaitState OBJECT-TYPE
    SYNTAX      ConfdString
    MAX-ACCESS  read-only
    STATUS      current
    DESCRIPTION "Number of TCP SYNs received in TCP Timed Wait State from Responder"
    ::= { affirmedServicesNatServiceConnTrackerNodeLevelConnTrackerModuleStatsEntry 74 }

affirmedServicesNatServiceConnTrackerNodeLevelConnTrackerModuleStatsOrigSynackRxedTcpTimedWaitState OBJECT-TYPE
    SYNTAX      ConfdString
    MAX-ACCESS  read-only
    STATUS      current
    DESCRIPTION "Number of TCP SYNACKs received in TCP Timed Wait State from Originator"
    ::= { affirmedServicesNatServiceConnTrackerNodeLevelConnTrackerModuleStatsEntry 75 }

affirmedServicesNatServiceConnTrackerNodeLevelConnTrackerModuleStatsRespSynackRxedTcpTimedWaitState OBJECT-TYPE
    SYNTAX      ConfdString
    MAX-ACCESS  read-only
    STATUS      current
    DESCRIPTION "Number of TCP SYNACKs received in TCP Timed Wait State from Responder"
    ::= { affirmedServicesNatServiceConnTrackerNodeLevelConnTrackerModuleStatsEntry 76 }

affirmedServicesNatServiceConnTrackerNodeLevelConnTrackerModuleStatsOrigAckRxedTcpTimedWaitState OBJECT-TYPE
    SYNTAX      ConfdString
    MAX-ACCESS  read-only
    STATUS      current
    DESCRIPTION "Number of TCP ACKs received in TCP Timed Wait State from Originator"
    ::= { affirmedServicesNatServiceConnTrackerNodeLevelConnTrackerModuleStatsEntry 77 }

affirmedServicesNatServiceConnTrackerNodeLevelConnTrackerModuleStatsRespAckRxedTcpTimedWaitState OBJECT-TYPE
    SYNTAX      ConfdString
    MAX-ACCESS  read-only
    STATUS      current
    DESCRIPTION "Number of TCP ACKs received in TCP Timed Wait State from Responder"
    ::= { affirmedServicesNatServiceConnTrackerNodeLevelConnTrackerModuleStatsEntry 78 }

affirmedServicesNatServiceConnTrackerNodeLevelConnTrackerModuleStatsOrigFinRxedTcpTimedWaitState OBJECT-TYPE
    SYNTAX      ConfdString
    MAX-ACCESS  read-only
    STATUS      current
    DESCRIPTION "Number of TCP FINs received in TCP Timed Wait State from Originator"
    ::= { affirmedServicesNatServiceConnTrackerNodeLevelConnTrackerModuleStatsEntry 79 }

affirmedServicesNatServiceConnTrackerNodeLevelConnTrackerModuleStatsRespFinRxedTcpTimedWaitState OBJECT-TYPE
    SYNTAX      ConfdString
    MAX-ACCESS  read-only
    STATUS      current
    DESCRIPTION "Number of TCP FINs received in TCP Timed Wait State from Responder"
    ::= { affirmedServicesNatServiceConnTrackerNodeLevelConnTrackerModuleStatsEntry 80 }

affirmedServicesNatServiceConnTrackerNodeLevelConnTrackerModuleStatsOrigRstRxedTcpTimedWaitState OBJECT-TYPE
    SYNTAX      ConfdString
    MAX-ACCESS  read-only
    STATUS      current
    DESCRIPTION "Number of TCP RSTs received in TCP Timed Wait State from Originator"
    ::= { affirmedServicesNatServiceConnTrackerNodeLevelConnTrackerModuleStatsEntry 81 }

affirmedServicesNatServiceConnTrackerNodeLevelConnTrackerModuleStatsRespRstRxedTcpTimedWaitState OBJECT-TYPE
    SYNTAX      ConfdString
    MAX-ACCESS  read-only
    STATUS      current
    DESCRIPTION "Number of TCP RSTs received in TCP Timed Wait State from Responder"
    ::= { affirmedServicesNatServiceConnTrackerNodeLevelConnTrackerModuleStatsEntry 82 }

affirmedServicesNatServiceConnTrackerNodeLevelConnTrackerModuleStatsOrigSynRxedTcpCloseState OBJECT-TYPE
    SYNTAX      ConfdString
    MAX-ACCESS  read-only
    STATUS      current
    DESCRIPTION "Number of TCP SYNs received in TCP Close State from Originator"
    ::= { affirmedServicesNatServiceConnTrackerNodeLevelConnTrackerModuleStatsEntry 83 }

affirmedServicesNatServiceConnTrackerNodeLevelConnTrackerModuleStatsRespSynRxedTcpCloseState OBJECT-TYPE
    SYNTAX      ConfdString
    MAX-ACCESS  read-only
    STATUS      current
    DESCRIPTION "Number of TCP SYNs received in TCP Close State from Responder"
    ::= { affirmedServicesNatServiceConnTrackerNodeLevelConnTrackerModuleStatsEntry 84 }

affirmedServicesNatServiceConnTrackerNodeLevelConnTrackerModuleStatsOrigSynackRxedTcpCloseState OBJECT-TYPE
    SYNTAX      ConfdString
    MAX-ACCESS  read-only
    STATUS      current
    DESCRIPTION "Number of TCP SYNACKs received in TCP Close State from Originator"
    ::= { affirmedServicesNatServiceConnTrackerNodeLevelConnTrackerModuleStatsEntry 85 }

affirmedServicesNatServiceConnTrackerNodeLevelConnTrackerModuleStatsRespSynackRxedTcpCloseState OBJECT-TYPE
    SYNTAX      ConfdString
    MAX-ACCESS  read-only
    STATUS      current
    DESCRIPTION "Number of TCP SYNACKs received in TCP Close State from Responder"
    ::= { affirmedServicesNatServiceConnTrackerNodeLevelConnTrackerModuleStatsEntry 86 }

affirmedServicesNatServiceConnTrackerNodeLevelConnTrackerModuleStatsOrigAckRxedTcpCloseState OBJECT-TYPE
    SYNTAX      ConfdString
    MAX-ACCESS  read-only
    STATUS      current
    DESCRIPTION "Number of TCP ACKs received in TCP Close State from Originator"
    ::= { affirmedServicesNatServiceConnTrackerNodeLevelConnTrackerModuleStatsEntry 87 }

affirmedServicesNatServiceConnTrackerNodeLevelConnTrackerModuleStatsRespAckRxedTcpCloseState OBJECT-TYPE
    SYNTAX      ConfdString
    MAX-ACCESS  read-only
    STATUS      current
    DESCRIPTION "Number of TCP ACKs received in TCP Close State from Responder"
    ::= { affirmedServicesNatServiceConnTrackerNodeLevelConnTrackerModuleStatsEntry 88 }

affirmedServicesNatServiceConnTrackerNodeLevelConnTrackerModuleStatsOrigFinRxedTcpCloseState OBJECT-TYPE
    SYNTAX      ConfdString
    MAX-ACCESS  read-only
    STATUS      current
    DESCRIPTION "Number of TCP FINs received in TCP Close State from Originator"
    ::= { affirmedServicesNatServiceConnTrackerNodeLevelConnTrackerModuleStatsEntry 89 }

affirmedServicesNatServiceConnTrackerNodeLevelConnTrackerModuleStatsRespFinRxedTcpCloseState OBJECT-TYPE
    SYNTAX      ConfdString
    MAX-ACCESS  read-only
    STATUS      current
    DESCRIPTION "Number of TCP FINs received in TCP Close State from Responder"
    ::= { affirmedServicesNatServiceConnTrackerNodeLevelConnTrackerModuleStatsEntry 90 }

affirmedServicesNatServiceConnTrackerNodeLevelConnTrackerModuleStatsOrigRstRxedTcpCloseState OBJECT-TYPE
    SYNTAX      ConfdString
    MAX-ACCESS  read-only
    STATUS      current
    DESCRIPTION "Number of TCP RSTs received in TCP Close State from Originator"
    ::= { affirmedServicesNatServiceConnTrackerNodeLevelConnTrackerModuleStatsEntry 91 }

affirmedServicesNatServiceConnTrackerNodeLevelConnTrackerModuleStatsRespRstRxedTcpCloseState OBJECT-TYPE
    SYNTAX      ConfdString
    MAX-ACCESS  read-only
    STATUS      current
    DESCRIPTION "Number of TCP RSTs received in TCP Close State from Responder"
    ::= { affirmedServicesNatServiceConnTrackerNodeLevelConnTrackerModuleStatsEntry 92 }

affirmedServicesNatServiceConnTrackerNodeLevelConnTrackerModuleStatsOrigSynRxedTcpBothWaySynSentState OBJECT-TYPE
    SYNTAX      ConfdString
    MAX-ACCESS  read-only
    STATUS      current
    DESCRIPTION "Number of TCP SYNs received in TCP BothWay Syn Sent State from Originator"
    ::= { affirmedServicesNatServiceConnTrackerNodeLevelConnTrackerModuleStatsEntry 93 }

affirmedServicesNatServiceConnTrackerNodeLevelConnTrackerModuleStatsRespSynRxedTcpBothWaySynSentState OBJECT-TYPE
    SYNTAX      ConfdString
    MAX-ACCESS  read-only
    STATUS      current
    DESCRIPTION "Number of TCP SYNs received in TCP BothWay Syn Sent State from Responder"
    ::= { affirmedServicesNatServiceConnTrackerNodeLevelConnTrackerModuleStatsEntry 94 }

affirmedServicesNatServiceConnTrackerNodeLevelConnTrackerModuleStatsOrigSynackRxedTcpBothWaySynSentState OBJECT-TYPE
    SYNTAX      ConfdString
    MAX-ACCESS  read-only
    STATUS      current
    DESCRIPTION "Number of TCP SYNACKs received in TCP BothWay Syn Sent State from Originator"
    ::= { affirmedServicesNatServiceConnTrackerNodeLevelConnTrackerModuleStatsEntry 95 }

affirmedServicesNatServiceConnTrackerNodeLevelConnTrackerModuleStatsRespSynackRxedTcpBothWaySynSentState OBJECT-TYPE
    SYNTAX      ConfdString
    MAX-ACCESS  read-only
    STATUS      current
    DESCRIPTION "Number of TCP SYNACKs received in TCP BothWay Syn Sent State from Responder"
    ::= { affirmedServicesNatServiceConnTrackerNodeLevelConnTrackerModuleStatsEntry 96 }

affirmedServicesNatServiceConnTrackerNodeLevelConnTrackerModuleStatsOrigAckRxedTcpBothWaySynSentState OBJECT-TYPE
    SYNTAX      ConfdString
    MAX-ACCESS  read-only
    STATUS      current
    DESCRIPTION "Number of TCP ACKs received in TCP BothWay Syn Sent State from Originator"
    ::= { affirmedServicesNatServiceConnTrackerNodeLevelConnTrackerModuleStatsEntry 97 }

affirmedServicesNatServiceConnTrackerNodeLevelConnTrackerModuleStatsRespAckRxedTcpBothWaySynSentState OBJECT-TYPE
    SYNTAX      ConfdString
    MAX-ACCESS  read-only
    STATUS      current
    DESCRIPTION "Number of TCP ACKs received in TCP BothWay Syn Sent State from Responder"
    ::= { affirmedServicesNatServiceConnTrackerNodeLevelConnTrackerModuleStatsEntry 98 }

affirmedServicesNatServiceConnTrackerNodeLevelConnTrackerModuleStatsOrigFinRxedTcpBothWaySynSentState OBJECT-TYPE
    SYNTAX      ConfdString
    MAX-ACCESS  read-only
    STATUS      current
    DESCRIPTION "Number of TCP FINs received in TCP BothWay Syn Sent State from Originator"
    ::= { affirmedServicesNatServiceConnTrackerNodeLevelConnTrackerModuleStatsEntry 99 }

affirmedServicesNatServiceConnTrackerNodeLevelConnTrackerModuleStatsRespFinRxedTcpBothWaySynSentState OBJECT-TYPE
    SYNTAX      ConfdString
    MAX-ACCESS  read-only
    STATUS      current
    DESCRIPTION "Number of TCP FINs received in TCP BothWay Syn Sent State from Responder"
    ::= { affirmedServicesNatServiceConnTrackerNodeLevelConnTrackerModuleStatsEntry 100 }

affirmedServicesNatServiceConnTrackerNodeLevelConnTrackerModuleStatsOrigRstRxedTcpBothWaySynSentState OBJECT-TYPE
    SYNTAX      ConfdString
    MAX-ACCESS  read-only
    STATUS      current
    DESCRIPTION "Number of TCP RSTs received in TCP BothWay Syn Sent State from Originator"
    ::= { affirmedServicesNatServiceConnTrackerNodeLevelConnTrackerModuleStatsEntry 101 }

affirmedServicesNatServiceConnTrackerNodeLevelConnTrackerModuleStatsRespRstRxedTcpBothWaySynSentState OBJECT-TYPE
    SYNTAX      ConfdString
    MAX-ACCESS  read-only
    STATUS      current
    DESCRIPTION "Number of TCP RSTs received in TCP BothWay Syn Sent State from Responder"
    ::= { affirmedServicesNatServiceConnTrackerNodeLevelConnTrackerModuleStatsEntry 102 }

affirmedServicesNatServiceConnTrackerNodeLevelConnTrackerModuleStatsOrigRxedUdpNoneState OBJECT-TYPE
    SYNTAX      ConfdString
    MAX-ACCESS  read-only
    STATUS      current
    DESCRIPTION "Number of UDP messages received in UDP None State from Originator"
    ::= { affirmedServicesNatServiceConnTrackerNodeLevelConnTrackerModuleStatsEntry 103 }

affirmedServicesNatServiceConnTrackerNodeLevelConnTrackerModuleStatsRespRxedUdpNoneState OBJECT-TYPE
    SYNTAX      ConfdString
    MAX-ACCESS  read-only
    STATUS      current
    DESCRIPTION "Number of UDP messages received in UDP None State from Responder"
    ::= { affirmedServicesNatServiceConnTrackerNodeLevelConnTrackerModuleStatsEntry 104 }

affirmedServicesNatServiceConnTrackerNodeLevelConnTrackerModuleStatsOrigRxedUdpOpenState OBJECT-TYPE
    SYNTAX      ConfdString
    MAX-ACCESS  read-only
    STATUS      current
    DESCRIPTION "Number of UDP messages received in UDP Open State from Originator"
    ::= { affirmedServicesNatServiceConnTrackerNodeLevelConnTrackerModuleStatsEntry 105 }

affirmedServicesNatServiceConnTrackerNodeLevelConnTrackerModuleStatsRespRxedUdpOpenState OBJECT-TYPE
    SYNTAX      ConfdString
    MAX-ACCESS  read-only
    STATUS      current
    DESCRIPTION "Number of UDP messages received in UDP Open State from Responder"
    ::= { affirmedServicesNatServiceConnTrackerNodeLevelConnTrackerModuleStatsEntry 106 }

affirmedServicesNatServiceConnTrackerNodeLevelConnTrackerModuleStatsOrigRxedUdpEstablishedState OBJECT-TYPE
    SYNTAX      ConfdString
    MAX-ACCESS  read-only
    STATUS      current
    DESCRIPTION "Number of UDP messages received in UDP Established State from Originator"
    ::= { affirmedServicesNatServiceConnTrackerNodeLevelConnTrackerModuleStatsEntry 107 }

affirmedServicesNatServiceConnTrackerNodeLevelConnTrackerModuleStatsRespRxedUdpEstablishedState OBJECT-TYPE
    SYNTAX      ConfdString
    MAX-ACCESS  read-only
    STATUS      current
    DESCRIPTION "Number of UDP messages received in UDP Established State from Responder"
    ::= { affirmedServicesNatServiceConnTrackerNodeLevelConnTrackerModuleStatsEntry 108 }

affirmedServicesNatServiceConnTrackerNodeLevelConnTrackerModuleStatsNumConnsUnSupportedProtocol OBJECT-TYPE
    SYNTAX      ConfdString
    MAX-ACCESS  read-only
    STATUS      current
    DESCRIPTION "Number of connection state tracking requests received for unsupported protocols"
    ::= { affirmedServicesNatServiceConnTrackerNodeLevelConnTrackerModuleStatsEntry 109 }

affirmedServicesNatServiceConnTrackerNodeLevelConnTrackerModuleStatsNumTcpChildConnectionRequest OBJECT-TYPE
    SYNTAX      ConfdString
    MAX-ACCESS  read-only
    STATUS      current
    DESCRIPTION "Number of child connection state tracking requests received for TCP based ALG"
    ::= { affirmedServicesNatServiceConnTrackerNodeLevelConnTrackerModuleStatsEntry 110 }

affirmedServicesNatServiceConnTrackerNodeLevelConnTrackerModuleStatsNumUdpChildConnectionRequest OBJECT-TYPE
    SYNTAX      ConfdString
    MAX-ACCESS  read-only
    STATUS      current
    DESCRIPTION "Number of child connection state tracking requests received for UDP based ALG"
    ::= { affirmedServicesNatServiceConnTrackerNodeLevelConnTrackerModuleStatsEntry 111 }

affirmedServicesNatServiceConnTrackerNodeLevelConnTrackerModuleStatsNumFlowProfileNotFound OBJECT-TYPE
    SYNTAX      ConfdString
    MAX-ACCESS  read-only
    STATUS      current
    DESCRIPTION "Number of times flow-state-tracking-profile/flow-idle-timeout-rule not found for a connection"
    ::= { affirmedServicesNatServiceConnTrackerNodeLevelConnTrackerModuleStatsEntry 112 }

affirmedServicesContentHealthCheckServiceStatisticsCluster-levelSummaryTable OBJECT-TYPE
    SYNTAX      SEQUENCE OF AffirmedServicesContentHealthCheckServiceStatisticsCluster-levelSummaryEntry
    MAX-ACCESS  not-accessible
    STATUS      current
    DESCRIPTION ""
    ::= { affirmedServicesContentHealthCheckServiceStatisticsCluster-level 1 }

affirmedServicesContentHealthCheckServiceStatisticsCluster-levelSummaryEntry OBJECT-TYPE
    SYNTAX      AffirmedServicesContentHealthCheckServiceStatisticsCluster-levelSummaryEntry
    MAX-ACCESS  not-accessible
    STATUS      current
    DESCRIPTION ""
    INDEX { affirmedServicesContentHealthCheckServiceStatisticsCluster-levelSummaryParent, affirmedServicesContentHealthCheckServiceStatisticsCluster-levelSummaryDestination, affirmedServicesContentHealthCheckServiceStatisticsCluster-levelSummaryNetworkContext }
        ::= { affirmedServicesContentHealthCheckServiceStatisticsCluster-levelSummaryTable 1 }

AffirmedServicesContentHealthCheckServiceStatisticsCluster-levelSummaryEntry ::=
    SEQUENCE {
        affirmedServicesContentHealthCheckServiceStatisticsCluster-levelSummaryParent String,
        affirmedServicesContentHealthCheckServiceStatisticsCluster-levelSummaryDestination String,
        affirmedServicesContentHealthCheckServiceStatisticsCluster-levelSummaryNetworkContext String,
        affirmedServicesContentHealthCheckServiceStatisticsCluster-levelSummaryCurrentState String,
        affirmedServicesContentHealthCheckServiceStatisticsCluster-levelSummarySuccesses ConfdString,
        affirmedServicesContentHealthCheckServiceStatisticsCluster-levelSummaryFailures ConfdString,
        affirmedServicesContentHealthCheckServiceStatisticsCluster-levelSummaryDetails String
    }

affirmedServicesContentHealthCheckServiceStatisticsCluster-levelSummaryParent OBJECT-TYPE
    SYNTAX      String
    MAX-ACCESS  not-accessible
    STATUS      current
    DESCRIPTION "Parent Health Check Destination"
    ::= { affirmedServicesContentHealthCheckServiceStatisticsCluster-levelSummaryEntry 1 }

affirmedServicesContentHealthCheckServiceStatisticsCluster-levelSummaryDestination OBJECT-TYPE
    SYNTAX      String
    MAX-ACCESS  not-accessible
    STATUS      current
    DESCRIPTION "Health Check Destination"
    ::= { affirmedServicesContentHealthCheckServiceStatisticsCluster-levelSummaryEntry 2 }

affirmedServicesContentHealthCheckServiceStatisticsCluster-levelSummaryNetworkContext OBJECT-TYPE
    SYNTAX      String
    MAX-ACCESS  not-accessible
    STATUS      current
    DESCRIPTION "Network Context of Destination"
    ::= { affirmedServicesContentHealthCheckServiceStatisticsCluster-levelSummaryEntry 3 }

affirmedServicesContentHealthCheckServiceStatisticsCluster-levelSummaryCurrentState OBJECT-TYPE
    SYNTAX      String
    MAX-ACCESS  read-only
    STATUS      current
    DESCRIPTION "Current State of the Destination"
    ::= { affirmedServicesContentHealthCheckServiceStatisticsCluster-levelSummaryEntry 4 }

affirmedServicesContentHealthCheckServiceStatisticsCluster-levelSummarySuccesses OBJECT-TYPE
    SYNTAX      ConfdString
    MAX-ACCESS  read-only
    STATUS      current
    DESCRIPTION "Number of Successes"
    ::= { affirmedServicesContentHealthCheckServiceStatisticsCluster-levelSummaryEntry 5 }

affirmedServicesContentHealthCheckServiceStatisticsCluster-levelSummaryFailures OBJECT-TYPE
    SYNTAX      ConfdString
    MAX-ACCESS  read-only
    STATUS      current
    DESCRIPTION "Number of Failures"
    ::= { affirmedServicesContentHealthCheckServiceStatisticsCluster-levelSummaryEntry 6 }

affirmedServicesContentHealthCheckServiceStatisticsCluster-levelSummaryDetails OBJECT-TYPE
    SYNTAX      String
    MAX-ACCESS  read-only
    STATUS      current
    DESCRIPTION "State Detail if applicable"
    ::= { affirmedServicesContentHealthCheckServiceStatisticsCluster-levelSummaryEntry 7 }

affirmedServicesContentWapGwServiceServiceDataFlowTable OBJECT-TYPE
    SYNTAX      SEQUENCE OF AffirmedServicesContentWapGwServiceServiceDataFlowEntry
    MAX-ACCESS  not-accessible
    STATUS      current
    DESCRIPTION ""
    ::= { affirmedServicesContentWapGwService 1 }

affirmedServicesContentWapGwServiceServiceDataFlowEntry OBJECT-TYPE
    SYNTAX      AffirmedServicesContentWapGwServiceServiceDataFlowEntry
    MAX-ACCESS  not-accessible
    STATUS      current
    DESCRIPTION ""
    INDEX { affirmedServicesContentWapGwServiceServiceDataFlowWapGateway, affirmedServicesContentWapGwServiceServiceDataFlowWapIpFlowPriority, affirmedServicesContentWapGwServiceServiceDataFlowServiceRulePriority, affirmedServicesContentWapGwServiceServiceDataFlowWapIpFlow, affirmedServicesContentWapGwServiceServiceDataFlowServiceRule }
        ::= { affirmedServicesContentWapGwServiceServiceDataFlowTable 1 }

AffirmedServicesContentWapGwServiceServiceDataFlowEntry ::=
    SEQUENCE {
        affirmedServicesContentWapGwServiceServiceDataFlowWapGateway String,
        affirmedServicesContentWapGwServiceServiceDataFlowWapIpFlowPriority Unsigned32,
        affirmedServicesContentWapGwServiceServiceDataFlowServiceRulePriority Unsigned32,
        affirmedServicesContentWapGwServiceServiceDataFlowWapIpFlow String,
        affirmedServicesContentWapGwServiceServiceDataFlowServiceRule String,
        affirmedServicesContentWapGwServiceServiceDataFlowWapIpFlowId Unsigned32,
        affirmedServicesContentWapGwServiceServiceDataFlowServiceRuleId Unsigned32
    }

affirmedServicesContentWapGwServiceServiceDataFlowWapGateway OBJECT-TYPE
    SYNTAX      String
    MAX-ACCESS  not-accessible
    STATUS      current
    DESCRIPTION "the name of the wap-gateway"
    ::= { affirmedServicesContentWapGwServiceServiceDataFlowEntry 1 }

affirmedServicesContentWapGwServiceServiceDataFlowWapIpFlowPriority OBJECT-TYPE
    SYNTAX      Unsigned32
    MAX-ACCESS  not-accessible
    STATUS      current
    DESCRIPTION "the priority of the wap-ip-flow"
    ::= { affirmedServicesContentWapGwServiceServiceDataFlowEntry 2 }

affirmedServicesContentWapGwServiceServiceDataFlowServiceRulePriority OBJECT-TYPE
    SYNTAX      Unsigned32
    MAX-ACCESS  not-accessible
    STATUS      current
    DESCRIPTION "the priority of the service-rule"
    ::= { affirmedServicesContentWapGwServiceServiceDataFlowEntry 3 }

affirmedServicesContentWapGwServiceServiceDataFlowWapIpFlow OBJECT-TYPE
    SYNTAX      String
    MAX-ACCESS  not-accessible
    STATUS      current
    DESCRIPTION "the name of the wap-ip-flow"
    ::= { affirmedServicesContentWapGwServiceServiceDataFlowEntry 4 }

affirmedServicesContentWapGwServiceServiceDataFlowServiceRule OBJECT-TYPE
    SYNTAX      String
    MAX-ACCESS  not-accessible
    STATUS      current
    DESCRIPTION "the name of the service-rule"
    ::= { affirmedServicesContentWapGwServiceServiceDataFlowEntry 5 }

affirmedServicesContentWapGwServiceServiceDataFlowWapIpFlowId OBJECT-TYPE
    SYNTAX      Unsigned32
    MAX-ACCESS  read-only
    STATUS      current
    DESCRIPTION "the internal ID of the wap-ip-flow, used to identify PDN-session service-data-flows {session-id, service-type=wap-gateway, wap-ip-flow-id, service-rule-id}"
    ::= { affirmedServicesContentWapGwServiceServiceDataFlowEntry 6 }

affirmedServicesContentWapGwServiceServiceDataFlowServiceRuleId OBJECT-TYPE
    SYNTAX      Unsigned32
    MAX-ACCESS  read-only
    STATUS      current
    DESCRIPTION "the internal ID of the service-rule, used to identify PDN-session service-data-flows {session-id, service-type=wap-gateway, wap-ip-flow-id, service-rule-id}"
    ::= { affirmedServicesContentWapGwServiceServiceDataFlowEntry 7 }

affirmedServicesContentWapGwServiceStatisticsChassisLevelSummaryTable OBJECT-TYPE
    SYNTAX      SEQUENCE OF AffirmedServicesContentWapGwServiceStatisticsChassisLevelSummaryEntry
    MAX-ACCESS  not-accessible
    STATUS      current
    DESCRIPTION ""
    ::= { affirmedServicesContentWapGwServiceStatisticsChassisLevel 1 }

affirmedServicesContentWapGwServiceStatisticsChassisLevelSummaryEntry OBJECT-TYPE
    SYNTAX      AffirmedServicesContentWapGwServiceStatisticsChassisLevelSummaryEntry
    MAX-ACCESS  not-accessible
    STATUS      current
    DESCRIPTION ""
    INDEX { affirmedServicesContentWapGwServiceStatisticsChassisLevelSummaryChassis }
        ::= { affirmedServicesContentWapGwServiceStatisticsChassisLevelSummaryTable 1 }

AffirmedServicesContentWapGwServiceStatisticsChassisLevelSummaryEntry ::=
    SEQUENCE {
        affirmedServicesContentWapGwServiceStatisticsChassisLevelSummaryChassis Unsigned32,
        affirmedServicesContentWapGwServiceStatisticsChassisLevelSummaryNumwapgwrequestattempts ConfdString,
        affirmedServicesContentWapGwServiceStatisticsChassisLevelSummaryNumwapgwrequestsuccesses ConfdString,
        affirmedServicesContentWapGwServiceStatisticsChassisLevelSummaryNumwapgwrequestfailures ConfdString,
        affirmedServicesContentWapGwServiceStatisticsChassisLevelSummaryNumwapgwrequestaborts ConfdString,
        affirmedServicesContentWapGwServiceStatisticsChassisLevelSummaryNumwapgwresponseswithstatussuccess ConfdString,
        affirmedServicesContentWapGwServiceStatisticsChassisLevelSummaryNumwapgwresponseswithstatusredirection ConfdString,
        affirmedServicesContentWapGwServiceStatisticsChassisLevelSummaryNumwapgwresponseswithstatusclienterror ConfdString,
        affirmedServicesContentWapGwServiceStatisticsChassisLevelSummaryNumwapgwresponseswithstatusservererror ConfdString,
        affirmedServicesContentWapGwServiceStatisticsChassisLevelSummaryNumwapgwhttpgets ConfdString,
        affirmedServicesContentWapGwServiceStatisticsChassisLevelSummaryNumwapgwhttpposts ConfdString,
        affirmedServicesContentWapGwServiceStatisticsChassisLevelSummaryNumwapgwhttptransactionsinprogress ConfdString,
        affirmedServicesContentWapGwServiceStatisticsChassisLevelSummaryNumwapgwwspconnectrequestsreceived ConfdString,
        affirmedServicesContentWapGwServiceStatisticsChassisLevelSummaryNumwapgwwspconnectrepliessent ConfdString,
        affirmedServicesContentWapGwServiceStatisticsChassisLevelSummaryNumwapgwwspdisconnectsreceived ConfdString,
        affirmedServicesContentWapGwServiceStatisticsChassisLevelSummaryNumwapgwwspdisconnectssent ConfdString,
        affirmedServicesContentWapGwServiceStatisticsChassisLevelSummaryNumwapgwwspgetrequestsreceived ConfdString,
        affirmedServicesContentWapGwServiceStatisticsChassisLevelSummaryNumwapgwwsppostrequestsreceived ConfdString,
        affirmedServicesContentWapGwServiceStatisticsChassisLevelSummaryNumwapgwwsprepliessent ConfdString,
        affirmedServicesContentWapGwServiceStatisticsChassisLevelSummaryNumwapgwwspreplyconfirmationsreceived ConfdString,
        affirmedServicesContentWapGwServiceStatisticsChassisLevelSummaryNumwapgwwspsuspendrequestsreceived ConfdString,
        affirmedServicesContentWapGwServiceStatisticsChassisLevelSummaryNumwapgwwspresumerequestsreceived ConfdString,
        affirmedServicesContentWapGwServiceStatisticsChassisLevelSummaryNumwapgwwsppacketunpackingerrors ConfdString,
        affirmedServicesContentWapGwServiceStatisticsChassisLevelSummaryNumwapgwwspunhandledeventerrors ConfdString,
        affirmedServicesContentWapGwServiceStatisticsChassisLevelSummaryNumwapgwwtptransactionsresp ConfdString,
        affirmedServicesContentWapGwServiceStatisticsChassisLevelSummaryNumwapgwwtptransactionsinit ConfdString,
        affirmedServicesContentWapGwServiceStatisticsChassisLevelSummaryNumwapgwwtppacketunpackingerrors ConfdString,
        affirmedServicesContentWapGwServiceStatisticsChassisLevelSummaryNumwapgwwtpunhandledeventerrors ConfdString,
        affirmedServicesContentWapGwServiceStatisticsChassisLevelSummaryNumwapgwwtlssessionscreated ConfdString,
        affirmedServicesContentWapGwServiceStatisticsChassisLevelSummaryNumwapgwwtlssessionsopened ConfdString,
        affirmedServicesContentWapGwServiceStatisticsChassisLevelSummaryNumwapgwwtlssessionsterminated ConfdString,
        affirmedServicesContentWapGwServiceStatisticsChassisLevelSummaryNumwapgwwtlskeyexchangeerrors ConfdString,
        affirmedServicesContentWapGwServiceStatisticsChassisLevelSummaryNumwapgwwtlscipherexchangeerrors ConfdString,
        affirmedServicesContentWapGwServiceStatisticsChassisLevelSummaryNumwapgwwtlskeyidexchangeerrors ConfdString,
        affirmedServicesContentWapGwServiceStatisticsChassisLevelSummaryNumwapgwwtlspdudecrypterrors ConfdString,
        affirmedServicesContentWapGwServiceStatisticsChassisLevelSummaryNumwapgwwtlspduencrypterrors ConfdString,
        affirmedServicesContentWapGwServiceStatisticsChassisLevelSummaryNumwapgwwtlsunexpectedmessageerrors ConfdString,
        affirmedServicesContentWapGwServiceStatisticsChassisLevelSummaryNumwapgwwtlsunhandledeventerrors ConfdString,
        affirmedServicesContentWapGwServiceStatisticsChassisLevelSummaryNumwapgwwdpdatagramsreceived ConfdString,
        affirmedServicesContentWapGwServiceStatisticsChassisLevelSummaryNumwapgwwdpdatagramssent ConfdString
    }

affirmedServicesContentWapGwServiceStatisticsChassisLevelSummaryChassis OBJECT-TYPE
    SYNTAX      Unsigned32
    MAX-ACCESS  not-accessible
    STATUS      current
    DESCRIPTION "chassis ID"
    ::= { affirmedServicesContentWapGwServiceStatisticsChassisLevelSummaryEntry 1 }

affirmedServicesContentWapGwServiceStatisticsChassisLevelSummaryNumwapgwrequestattempts OBJECT-TYPE
    SYNTAX      ConfdString
    MAX-ACCESS  read-only
    STATUS      current
    DESCRIPTION "Total number of Requests Attempted"
    ::= { affirmedServicesContentWapGwServiceStatisticsChassisLevelSummaryEntry 2 }

affirmedServicesContentWapGwServiceStatisticsChassisLevelSummaryNumwapgwrequestsuccesses OBJECT-TYPE
    SYNTAX      ConfdString
    MAX-ACCESS  read-only
    STATUS      current
    DESCRIPTION "Total number of Requests Succeeded"
    ::= { affirmedServicesContentWapGwServiceStatisticsChassisLevelSummaryEntry 3 }

affirmedServicesContentWapGwServiceStatisticsChassisLevelSummaryNumwapgwrequestfailures OBJECT-TYPE
    SYNTAX      ConfdString
    MAX-ACCESS  read-only
    STATUS      current
    DESCRIPTION "Total number of Requests Failed"
    ::= { affirmedServicesContentWapGwServiceStatisticsChassisLevelSummaryEntry 4 }

affirmedServicesContentWapGwServiceStatisticsChassisLevelSummaryNumwapgwrequestaborts OBJECT-TYPE
    SYNTAX      ConfdString
    MAX-ACCESS  read-only
    STATUS      current
    DESCRIPTION "Total number of Requests Aborted"
    ::= { affirmedServicesContentWapGwServiceStatisticsChassisLevelSummaryEntry 5 }

affirmedServicesContentWapGwServiceStatisticsChassisLevelSummaryNumwapgwresponseswithstatussuccess OBJECT-TYPE
    SYNTAX      ConfdString
    MAX-ACCESS  read-only
    STATUS      current
    DESCRIPTION "Total number of responses with status success"
    ::= { affirmedServicesContentWapGwServiceStatisticsChassisLevelSummaryEntry 6 }

affirmedServicesContentWapGwServiceStatisticsChassisLevelSummaryNumwapgwresponseswithstatusredirection OBJECT-TYPE
    SYNTAX      ConfdString
    MAX-ACCESS  read-only
    STATUS      current
    DESCRIPTION "Total number of responses with status redirection"
    ::= { affirmedServicesContentWapGwServiceStatisticsChassisLevelSummaryEntry 7 }

affirmedServicesContentWapGwServiceStatisticsChassisLevelSummaryNumwapgwresponseswithstatusclienterror OBJECT-TYPE
    SYNTAX      ConfdString
    MAX-ACCESS  read-only
    STATUS      current
    DESCRIPTION "Total number of responses with status client error"
    ::= { affirmedServicesContentWapGwServiceStatisticsChassisLevelSummaryEntry 8 }

affirmedServicesContentWapGwServiceStatisticsChassisLevelSummaryNumwapgwresponseswithstatusservererror OBJECT-TYPE
    SYNTAX      ConfdString
    MAX-ACCESS  read-only
    STATUS      current
    DESCRIPTION "Total number of responses with status server error"
    ::= { affirmedServicesContentWapGwServiceStatisticsChassisLevelSummaryEntry 9 }

affirmedServicesContentWapGwServiceStatisticsChassisLevelSummaryNumwapgwhttpgets OBJECT-TYPE
    SYNTAX      ConfdString
    MAX-ACCESS  read-only
    STATUS      current
    DESCRIPTION "Total number of HTTP Gets"
    ::= { affirmedServicesContentWapGwServiceStatisticsChassisLevelSummaryEntry 10 }

affirmedServicesContentWapGwServiceStatisticsChassisLevelSummaryNumwapgwhttpposts OBJECT-TYPE
    SYNTAX      ConfdString
    MAX-ACCESS  read-only
    STATUS      current
    DESCRIPTION "Total number of HTTP Posts"
    ::= { affirmedServicesContentWapGwServiceStatisticsChassisLevelSummaryEntry 11 }

affirmedServicesContentWapGwServiceStatisticsChassisLevelSummaryNumwapgwhttptransactionsinprogress OBJECT-TYPE
    SYNTAX      ConfdString
    MAX-ACCESS  read-only
    STATUS      current
    DESCRIPTION "Total number of HTTP Transactions Currently in Progress"
    ::= { affirmedServicesContentWapGwServiceStatisticsChassisLevelSummaryEntry 12 }

affirmedServicesContentWapGwServiceStatisticsChassisLevelSummaryNumwapgwwspconnectrequestsreceived OBJECT-TYPE
    SYNTAX      ConfdString
    MAX-ACCESS  read-only
    STATUS      current
    DESCRIPTION "Total number of WSP Connect Requests Received"
    ::= { affirmedServicesContentWapGwServiceStatisticsChassisLevelSummaryEntry 13 }

affirmedServicesContentWapGwServiceStatisticsChassisLevelSummaryNumwapgwwspconnectrepliessent OBJECT-TYPE
    SYNTAX      ConfdString
    MAX-ACCESS  read-only
    STATUS      current
    DESCRIPTION "Total number of WSP Connect Replies Sent"
    ::= { affirmedServicesContentWapGwServiceStatisticsChassisLevelSummaryEntry 14 }

affirmedServicesContentWapGwServiceStatisticsChassisLevelSummaryNumwapgwwspdisconnectsreceived OBJECT-TYPE
    SYNTAX      ConfdString
    MAX-ACCESS  read-only
    STATUS      current
    DESCRIPTION "Total number of WSP Disconnects Received"
    ::= { affirmedServicesContentWapGwServiceStatisticsChassisLevelSummaryEntry 15 }

affirmedServicesContentWapGwServiceStatisticsChassisLevelSummaryNumwapgwwspdisconnectssent OBJECT-TYPE
    SYNTAX      ConfdString
    MAX-ACCESS  read-only
    STATUS      current
    DESCRIPTION "Total number of WSP Disconnects Sent"
    ::= { affirmedServicesContentWapGwServiceStatisticsChassisLevelSummaryEntry 16 }

affirmedServicesContentWapGwServiceStatisticsChassisLevelSummaryNumwapgwwspgetrequestsreceived OBJECT-TYPE
    SYNTAX      ConfdString
    MAX-ACCESS  read-only
    STATUS      current
    DESCRIPTION "Total number of WSP Get Requests Received"
    ::= { affirmedServicesContentWapGwServiceStatisticsChassisLevelSummaryEntry 17 }

affirmedServicesContentWapGwServiceStatisticsChassisLevelSummaryNumwapgwwsppostrequestsreceived OBJECT-TYPE
    SYNTAX      ConfdString
    MAX-ACCESS  read-only
    STATUS      current
    DESCRIPTION "Total number of WSP Post Requests Received"
    ::= { affirmedServicesContentWapGwServiceStatisticsChassisLevelSummaryEntry 18 }

affirmedServicesContentWapGwServiceStatisticsChassisLevelSummaryNumwapgwwsprepliessent OBJECT-TYPE
    SYNTAX      ConfdString
    MAX-ACCESS  read-only
    STATUS      current
    DESCRIPTION "Total number of WSP Replies Sent"
    ::= { affirmedServicesContentWapGwServiceStatisticsChassisLevelSummaryEntry 19 }

affirmedServicesContentWapGwServiceStatisticsChassisLevelSummaryNumwapgwwspreplyconfirmationsreceived OBJECT-TYPE
    SYNTAX      ConfdString
    MAX-ACCESS  read-only
    STATUS      current
    DESCRIPTION "Total number of WSP Reply Confirmations Received"
    ::= { affirmedServicesContentWapGwServiceStatisticsChassisLevelSummaryEntry 20 }

affirmedServicesContentWapGwServiceStatisticsChassisLevelSummaryNumwapgwwspsuspendrequestsreceived OBJECT-TYPE
    SYNTAX      ConfdString
    MAX-ACCESS  read-only
    STATUS      current
    DESCRIPTION "Total number of WSP Suspend Requests Received"
    ::= { affirmedServicesContentWapGwServiceStatisticsChassisLevelSummaryEntry 21 }

affirmedServicesContentWapGwServiceStatisticsChassisLevelSummaryNumwapgwwspresumerequestsreceived OBJECT-TYPE
    SYNTAX      ConfdString
    MAX-ACCESS  read-only
    STATUS      current
    DESCRIPTION "Total number of WSP Resume Requests Received"
    ::= { affirmedServicesContentWapGwServiceStatisticsChassisLevelSummaryEntry 22 }

affirmedServicesContentWapGwServiceStatisticsChassisLevelSummaryNumwapgwwsppacketunpackingerrors OBJECT-TYPE
    SYNTAX      ConfdString
    MAX-ACCESS  read-only
    STATUS      current
    DESCRIPTION "Total number of WSP Packet Unpacking Errors"
    ::= { affirmedServicesContentWapGwServiceStatisticsChassisLevelSummaryEntry 23 }

affirmedServicesContentWapGwServiceStatisticsChassisLevelSummaryNumwapgwwspunhandledeventerrors OBJECT-TYPE
    SYNTAX      ConfdString
    MAX-ACCESS  read-only
    STATUS      current
    DESCRIPTION "Total number of WSP Unhandled Event Errors"
    ::= { affirmedServicesContentWapGwServiceStatisticsChassisLevelSummaryEntry 24 }

affirmedServicesContentWapGwServiceStatisticsChassisLevelSummaryNumwapgwwtptransactionsresp OBJECT-TYPE
    SYNTAX      ConfdString
    MAX-ACCESS  read-only
    STATUS      current
    DESCRIPTION "Total number of WTP Transactions Responded to"
    ::= { affirmedServicesContentWapGwServiceStatisticsChassisLevelSummaryEntry 25 }

affirmedServicesContentWapGwServiceStatisticsChassisLevelSummaryNumwapgwwtptransactionsinit OBJECT-TYPE
    SYNTAX      ConfdString
    MAX-ACCESS  read-only
    STATUS      current
    DESCRIPTION "Total number of WTP Transactions Initiated"
    ::= { affirmedServicesContentWapGwServiceStatisticsChassisLevelSummaryEntry 26 }

affirmedServicesContentWapGwServiceStatisticsChassisLevelSummaryNumwapgwwtppacketunpackingerrors OBJECT-TYPE
    SYNTAX      ConfdString
    MAX-ACCESS  read-only
    STATUS      current
    DESCRIPTION "Total number of WTP Packet Unpacking Errors"
    ::= { affirmedServicesContentWapGwServiceStatisticsChassisLevelSummaryEntry 27 }

affirmedServicesContentWapGwServiceStatisticsChassisLevelSummaryNumwapgwwtpunhandledeventerrors OBJECT-TYPE
    SYNTAX      ConfdString
    MAX-ACCESS  read-only
    STATUS      current
    DESCRIPTION "Total number of WTP Unhandled Event Errors"
    ::= { affirmedServicesContentWapGwServiceStatisticsChassisLevelSummaryEntry 28 }

affirmedServicesContentWapGwServiceStatisticsChassisLevelSummaryNumwapgwwtlssessionscreated OBJECT-TYPE
    SYNTAX      ConfdString
    MAX-ACCESS  read-only
    STATUS      current
    DESCRIPTION "Total number of WTLS Sessions Created"
    ::= { affirmedServicesContentWapGwServiceStatisticsChassisLevelSummaryEntry 29 }

affirmedServicesContentWapGwServiceStatisticsChassisLevelSummaryNumwapgwwtlssessionsopened OBJECT-TYPE
    SYNTAX      ConfdString
    MAX-ACCESS  read-only
    STATUS      current
    DESCRIPTION "Total number of WTLS Sessions Opened"
    ::= { affirmedServicesContentWapGwServiceStatisticsChassisLevelSummaryEntry 30 }

affirmedServicesContentWapGwServiceStatisticsChassisLevelSummaryNumwapgwwtlssessionsterminated OBJECT-TYPE
    SYNTAX      ConfdString
    MAX-ACCESS  read-only
    STATUS      current
    DESCRIPTION "Total number of WTLS Sessions Terminated"
    ::= { affirmedServicesContentWapGwServiceStatisticsChassisLevelSummaryEntry 31 }

affirmedServicesContentWapGwServiceStatisticsChassisLevelSummaryNumwapgwwtlskeyexchangeerrors OBJECT-TYPE
    SYNTAX      ConfdString
    MAX-ACCESS  read-only
    STATUS      current
    DESCRIPTION "Total number of WTLS Key Exchange Errors"
    ::= { affirmedServicesContentWapGwServiceStatisticsChassisLevelSummaryEntry 32 }

affirmedServicesContentWapGwServiceStatisticsChassisLevelSummaryNumwapgwwtlscipherexchangeerrors OBJECT-TYPE
    SYNTAX      ConfdString
    MAX-ACCESS  read-only
    STATUS      current
    DESCRIPTION "Total number of WTLS Cipher Exchange Errors"
    ::= { affirmedServicesContentWapGwServiceStatisticsChassisLevelSummaryEntry 33 }

affirmedServicesContentWapGwServiceStatisticsChassisLevelSummaryNumwapgwwtlskeyidexchangeerrors OBJECT-TYPE
    SYNTAX      ConfdString
    MAX-ACCESS  read-only
    STATUS      current
    DESCRIPTION "Total number of WTLS Key Id Exchange Errors"
    ::= { affirmedServicesContentWapGwServiceStatisticsChassisLevelSummaryEntry 34 }

affirmedServicesContentWapGwServiceStatisticsChassisLevelSummaryNumwapgwwtlspdudecrypterrors OBJECT-TYPE
    SYNTAX      ConfdString
    MAX-ACCESS  read-only
    STATUS      current
    DESCRIPTION "Total number of WTLS Pdu Decrypt Errors"
    ::= { affirmedServicesContentWapGwServiceStatisticsChassisLevelSummaryEntry 35 }

affirmedServicesContentWapGwServiceStatisticsChassisLevelSummaryNumwapgwwtlspduencrypterrors OBJECT-TYPE
    SYNTAX      ConfdString
    MAX-ACCESS  read-only
    STATUS      current
    DESCRIPTION "Total number of WTLS Pdu Encrypt Errors"
    ::= { affirmedServicesContentWapGwServiceStatisticsChassisLevelSummaryEntry 36 }

affirmedServicesContentWapGwServiceStatisticsChassisLevelSummaryNumwapgwwtlsunexpectedmessageerrors OBJECT-TYPE
    SYNTAX      ConfdString
    MAX-ACCESS  read-only
    STATUS      current
    DESCRIPTION "Total number of WTLS Unexpected Message Errors"
    ::= { affirmedServicesContentWapGwServiceStatisticsChassisLevelSummaryEntry 37 }

affirmedServicesContentWapGwServiceStatisticsChassisLevelSummaryNumwapgwwtlsunhandledeventerrors OBJECT-TYPE
    SYNTAX      ConfdString
    MAX-ACCESS  read-only
    STATUS      current
    DESCRIPTION "Total number of WTLS Unhandled Event Errors"
    ::= { affirmedServicesContentWapGwServiceStatisticsChassisLevelSummaryEntry 38 }

affirmedServicesContentWapGwServiceStatisticsChassisLevelSummaryNumwapgwwdpdatagramsreceived OBJECT-TYPE
    SYNTAX      ConfdString
    MAX-ACCESS  read-only
    STATUS      current
    DESCRIPTION "Total number of WDP Datagrams Received"
    ::= { affirmedServicesContentWapGwServiceStatisticsChassisLevelSummaryEntry 39 }

affirmedServicesContentWapGwServiceStatisticsChassisLevelSummaryNumwapgwwdpdatagramssent OBJECT-TYPE
    SYNTAX      ConfdString
    MAX-ACCESS  read-only
    STATUS      current
    DESCRIPTION "Total number of WDP Datagrams Sent"
    ::= { affirmedServicesContentWapGwServiceStatisticsChassisLevelSummaryEntry 40 }

affirmedServicesContentWapGwServiceStatisticsNodeLevelSummaryTable OBJECT-TYPE
    SYNTAX      SEQUENCE OF AffirmedServicesContentWapGwServiceStatisticsNodeLevelSummaryEntry
    MAX-ACCESS  not-accessible
    STATUS      current
    DESCRIPTION ""
    ::= { affirmedServicesContentWapGwServiceStatisticsNodeLevel 1 }

affirmedServicesContentWapGwServiceStatisticsNodeLevelSummaryEntry OBJECT-TYPE
    SYNTAX      AffirmedServicesContentWapGwServiceStatisticsNodeLevelSummaryEntry
    MAX-ACCESS  not-accessible
    STATUS      current
    DESCRIPTION ""
    INDEX { affirmedServicesContentWapGwServiceStatisticsNodeLevelSummaryChassis, affirmedServicesContentWapGwServiceStatisticsNodeLevelSummarySlot }
        ::= { affirmedServicesContentWapGwServiceStatisticsNodeLevelSummaryTable 1 }

AffirmedServicesContentWapGwServiceStatisticsNodeLevelSummaryEntry ::=
    SEQUENCE {
        affirmedServicesContentWapGwServiceStatisticsNodeLevelSummaryChassis Unsigned32,
        affirmedServicesContentWapGwServiceStatisticsNodeLevelSummarySlot Unsigned32,
        affirmedServicesContentWapGwServiceStatisticsNodeLevelSummaryNumwapgwrequestattempts ConfdString,
        affirmedServicesContentWapGwServiceStatisticsNodeLevelSummaryNumwapgwrequestsuccesses ConfdString,
        affirmedServicesContentWapGwServiceStatisticsNodeLevelSummaryNumwapgwrequestfailures ConfdString,
        affirmedServicesContentWapGwServiceStatisticsNodeLevelSummaryNumwapgwrequestaborts ConfdString,
        affirmedServicesContentWapGwServiceStatisticsNodeLevelSummaryNumwapgwresponseswithstatussuccess ConfdString,
        affirmedServicesContentWapGwServiceStatisticsNodeLevelSummaryNumwapgwresponseswithstatusredirection ConfdString,
        affirmedServicesContentWapGwServiceStatisticsNodeLevelSummaryNumwapgwresponseswithstatusclienterror ConfdString,
        affirmedServicesContentWapGwServiceStatisticsNodeLevelSummaryNumwapgwresponseswithstatusservererror ConfdString,
        affirmedServicesContentWapGwServiceStatisticsNodeLevelSummaryNumwapgwhttpgets ConfdString,
        affirmedServicesContentWapGwServiceStatisticsNodeLevelSummaryNumwapgwhttpposts ConfdString,
        affirmedServicesContentWapGwServiceStatisticsNodeLevelSummaryNumwapgwhttptransactionsinprogress ConfdString,
        affirmedServicesContentWapGwServiceStatisticsNodeLevelSummaryNumwapgwwspconnectrequestsreceived ConfdString,
        affirmedServicesContentWapGwServiceStatisticsNodeLevelSummaryNumwapgwwspconnectrepliessent ConfdString,
        affirmedServicesContentWapGwServiceStatisticsNodeLevelSummaryNumwapgwwspdisconnectsreceived ConfdString,
        affirmedServicesContentWapGwServiceStatisticsNodeLevelSummaryNumwapgwwspdisconnectssent ConfdString,
        affirmedServicesContentWapGwServiceStatisticsNodeLevelSummaryNumwapgwwspgetrequestsreceived ConfdString,
        affirmedServicesContentWapGwServiceStatisticsNodeLevelSummaryNumwapgwwsppostrequestsreceived ConfdString,
        affirmedServicesContentWapGwServiceStatisticsNodeLevelSummaryNumwapgwwsprepliessent ConfdString,
        affirmedServicesContentWapGwServiceStatisticsNodeLevelSummaryNumwapgwwspreplyconfirmationsreceived ConfdString,
        affirmedServicesContentWapGwServiceStatisticsNodeLevelSummaryNumwapgwwspsuspendrequestsreceived ConfdString,
        affirmedServicesContentWapGwServiceStatisticsNodeLevelSummaryNumwapgwwspresumerequestsreceived ConfdString,
        affirmedServicesContentWapGwServiceStatisticsNodeLevelSummaryNumwapgwwsppacketunpackingerrors ConfdString,
        affirmedServicesContentWapGwServiceStatisticsNodeLevelSummaryNumwapgwwspunhandledeventerrors ConfdString,
        affirmedServicesContentWapGwServiceStatisticsNodeLevelSummaryNumwapgwwtptransactionsresp ConfdString,
        affirmedServicesContentWapGwServiceStatisticsNodeLevelSummaryNumwapgwwtptransactionsinit ConfdString,
        affirmedServicesContentWapGwServiceStatisticsNodeLevelSummaryNumwapgwwtppacketunpackingerrors ConfdString,
        affirmedServicesContentWapGwServiceStatisticsNodeLevelSummaryNumwapgwwtpunhandledeventerrors ConfdString,
        affirmedServicesContentWapGwServiceStatisticsNodeLevelSummaryNumwapgwwtlssessionscreated ConfdString,
        affirmedServicesContentWapGwServiceStatisticsNodeLevelSummaryNumwapgwwtlssessionsopened ConfdString,
        affirmedServicesContentWapGwServiceStatisticsNodeLevelSummaryNumwapgwwtlssessionsterminated ConfdString,
        affirmedServicesContentWapGwServiceStatisticsNodeLevelSummaryNumwapgwwtlskeyexchangeerrors ConfdString,
        affirmedServicesContentWapGwServiceStatisticsNodeLevelSummaryNumwapgwwtlscipherexchangeerrors ConfdString,
        affirmedServicesContentWapGwServiceStatisticsNodeLevelSummaryNumwapgwwtlskeyidexchangeerrors ConfdString,
        affirmedServicesContentWapGwServiceStatisticsNodeLevelSummaryNumwapgwwtlspdudecrypterrors ConfdString,
        affirmedServicesContentWapGwServiceStatisticsNodeLevelSummaryNumwapgwwtlspduencrypterrors ConfdString,
        affirmedServicesContentWapGwServiceStatisticsNodeLevelSummaryNumwapgwwtlsunexpectedmessageerrors ConfdString,
        affirmedServicesContentWapGwServiceStatisticsNodeLevelSummaryNumwapgwwtlsunhandledeventerrors ConfdString,
        affirmedServicesContentWapGwServiceStatisticsNodeLevelSummaryNumwapgwwdpdatagramsreceived ConfdString,
        affirmedServicesContentWapGwServiceStatisticsNodeLevelSummaryNumwapgwwdpdatagramssent ConfdString
    }

affirmedServicesContentWapGwServiceStatisticsNodeLevelSummaryChassis OBJECT-TYPE
    SYNTAX      Unsigned32
    MAX-ACCESS  not-accessible
    STATUS      current
    DESCRIPTION "chassis ID"
    ::= { affirmedServicesContentWapGwServiceStatisticsNodeLevelSummaryEntry 1 }

affirmedServicesContentWapGwServiceStatisticsNodeLevelSummarySlot OBJECT-TYPE
    SYNTAX      Unsigned32
    MAX-ACCESS  not-accessible
    STATUS      current
    DESCRIPTION "slot number"
    ::= { affirmedServicesContentWapGwServiceStatisticsNodeLevelSummaryEntry 2 }

affirmedServicesContentWapGwServiceStatisticsNodeLevelSummaryNumwapgwrequestattempts OBJECT-TYPE
    SYNTAX      ConfdString
    MAX-ACCESS  read-only
    STATUS      current
    DESCRIPTION "Total number of Requests Attempted"
    ::= { affirmedServicesContentWapGwServiceStatisticsNodeLevelSummaryEntry 3 }

affirmedServicesContentWapGwServiceStatisticsNodeLevelSummaryNumwapgwrequestsuccesses OBJECT-TYPE
    SYNTAX      ConfdString
    MAX-ACCESS  read-only
    STATUS      current
    DESCRIPTION "Total number of Requests Succeeded"
    ::= { affirmedServicesContentWapGwServiceStatisticsNodeLevelSummaryEntry 4 }

affirmedServicesContentWapGwServiceStatisticsNodeLevelSummaryNumwapgwrequestfailures OBJECT-TYPE
    SYNTAX      ConfdString
    MAX-ACCESS  read-only
    STATUS      current
    DESCRIPTION "Total number of Requests Failed"
    ::= { affirmedServicesContentWapGwServiceStatisticsNodeLevelSummaryEntry 5 }

affirmedServicesContentWapGwServiceStatisticsNodeLevelSummaryNumwapgwrequestaborts OBJECT-TYPE
    SYNTAX      ConfdString
    MAX-ACCESS  read-only
    STATUS      current
    DESCRIPTION "Total number of Requests Aborted"
    ::= { affirmedServicesContentWapGwServiceStatisticsNodeLevelSummaryEntry 6 }

affirmedServicesContentWapGwServiceStatisticsNodeLevelSummaryNumwapgwresponseswithstatussuccess OBJECT-TYPE
    SYNTAX      ConfdString
    MAX-ACCESS  read-only
    STATUS      current
    DESCRIPTION "Total number of responses with status success"
    ::= { affirmedServicesContentWapGwServiceStatisticsNodeLevelSummaryEntry 7 }

affirmedServicesContentWapGwServiceStatisticsNodeLevelSummaryNumwapgwresponseswithstatusredirection OBJECT-TYPE
    SYNTAX      ConfdString
    MAX-ACCESS  read-only
    STATUS      current
    DESCRIPTION "Total number of responses with status redirection"
    ::= { affirmedServicesContentWapGwServiceStatisticsNodeLevelSummaryEntry 8 }

affirmedServicesContentWapGwServiceStatisticsNodeLevelSummaryNumwapgwresponseswithstatusclienterror OBJECT-TYPE
    SYNTAX      ConfdString
    MAX-ACCESS  read-only
    STATUS      current
    DESCRIPTION "Total number of responses with status client error"
    ::= { affirmedServicesContentWapGwServiceStatisticsNodeLevelSummaryEntry 9 }

affirmedServicesContentWapGwServiceStatisticsNodeLevelSummaryNumwapgwresponseswithstatusservererror OBJECT-TYPE
    SYNTAX      ConfdString
    MAX-ACCESS  read-only
    STATUS      current
    DESCRIPTION "Total number of responses with status server error"
    ::= { affirmedServicesContentWapGwServiceStatisticsNodeLevelSummaryEntry 10 }

affirmedServicesContentWapGwServiceStatisticsNodeLevelSummaryNumwapgwhttpgets OBJECT-TYPE
    SYNTAX      ConfdString
    MAX-ACCESS  read-only
    STATUS      current
    DESCRIPTION "Total number of HTTP Gets"
    ::= { affirmedServicesContentWapGwServiceStatisticsNodeLevelSummaryEntry 11 }

affirmedServicesContentWapGwServiceStatisticsNodeLevelSummaryNumwapgwhttpposts OBJECT-TYPE
    SYNTAX      ConfdString
    MAX-ACCESS  read-only
    STATUS      current
    DESCRIPTION "Total number of HTTP Posts"
    ::= { affirmedServicesContentWapGwServiceStatisticsNodeLevelSummaryEntry 12 }

affirmedServicesContentWapGwServiceStatisticsNodeLevelSummaryNumwapgwhttptransactionsinprogress OBJECT-TYPE
    SYNTAX      ConfdString
    MAX-ACCESS  read-only
    STATUS      current
    DESCRIPTION "Total number of HTTP Transactions Currently in Progress"
    ::= { affirmedServicesContentWapGwServiceStatisticsNodeLevelSummaryEntry 13 }

affirmedServicesContentWapGwServiceStatisticsNodeLevelSummaryNumwapgwwspconnectrequestsreceived OBJECT-TYPE
    SYNTAX      ConfdString
    MAX-ACCESS  read-only
    STATUS      current
    DESCRIPTION "Total number of WSP Connect Requests Received"
    ::= { affirmedServicesContentWapGwServiceStatisticsNodeLevelSummaryEntry 14 }

affirmedServicesContentWapGwServiceStatisticsNodeLevelSummaryNumwapgwwspconnectrepliessent OBJECT-TYPE
    SYNTAX      ConfdString
    MAX-ACCESS  read-only
    STATUS      current
    DESCRIPTION "Total number of WSP Connect Replies Sent"
    ::= { affirmedServicesContentWapGwServiceStatisticsNodeLevelSummaryEntry 15 }

affirmedServicesContentWapGwServiceStatisticsNodeLevelSummaryNumwapgwwspdisconnectsreceived OBJECT-TYPE
    SYNTAX      ConfdString
    MAX-ACCESS  read-only
    STATUS      current
    DESCRIPTION "Total number of WSP Disconnects Received"
    ::= { affirmedServicesContentWapGwServiceStatisticsNodeLevelSummaryEntry 16 }

affirmedServicesContentWapGwServiceStatisticsNodeLevelSummaryNumwapgwwspdisconnectssent OBJECT-TYPE
    SYNTAX      ConfdString
    MAX-ACCESS  read-only
    STATUS      current
    DESCRIPTION "Total number of WSP Disconnects Sent"
    ::= { affirmedServicesContentWapGwServiceStatisticsNodeLevelSummaryEntry 17 }

affirmedServicesContentWapGwServiceStatisticsNodeLevelSummaryNumwapgwwspgetrequestsreceived OBJECT-TYPE
    SYNTAX      ConfdString
    MAX-ACCESS  read-only
    STATUS      current
    DESCRIPTION "Total number of WSP Get Requests Received"
    ::= { affirmedServicesContentWapGwServiceStatisticsNodeLevelSummaryEntry 18 }

affirmedServicesContentWapGwServiceStatisticsNodeLevelSummaryNumwapgwwsppostrequestsreceived OBJECT-TYPE
    SYNTAX      ConfdString
    MAX-ACCESS  read-only
    STATUS      current
    DESCRIPTION "Total number of WSP Post Requests Received"
    ::= { affirmedServicesContentWapGwServiceStatisticsNodeLevelSummaryEntry 19 }

affirmedServicesContentWapGwServiceStatisticsNodeLevelSummaryNumwapgwwsprepliessent OBJECT-TYPE
    SYNTAX      ConfdString
    MAX-ACCESS  read-only
    STATUS      current
    DESCRIPTION "Total number of WSP Replies Sent"
    ::= { affirmedServicesContentWapGwServiceStatisticsNodeLevelSummaryEntry 20 }

affirmedServicesContentWapGwServiceStatisticsNodeLevelSummaryNumwapgwwspreplyconfirmationsreceived OBJECT-TYPE
    SYNTAX      ConfdString
    MAX-ACCESS  read-only
    STATUS      current
    DESCRIPTION "Total number of WSP Reply Confirmations Received"
    ::= { affirmedServicesContentWapGwServiceStatisticsNodeLevelSummaryEntry 21 }

affirmedServicesContentWapGwServiceStatisticsNodeLevelSummaryNumwapgwwspsuspendrequestsreceived OBJECT-TYPE
    SYNTAX      ConfdString
    MAX-ACCESS  read-only
    STATUS      current
    DESCRIPTION "Total number of WSP Suspend Requests Received"
    ::= { affirmedServicesContentWapGwServiceStatisticsNodeLevelSummaryEntry 22 }

affirmedServicesContentWapGwServiceStatisticsNodeLevelSummaryNumwapgwwspresumerequestsreceived OBJECT-TYPE
    SYNTAX      ConfdString
    MAX-ACCESS  read-only
    STATUS      current
    DESCRIPTION "Total number of WSP Resume Requests Received"
    ::= { affirmedServicesContentWapGwServiceStatisticsNodeLevelSummaryEntry 23 }

affirmedServicesContentWapGwServiceStatisticsNodeLevelSummaryNumwapgwwsppacketunpackingerrors OBJECT-TYPE
    SYNTAX      ConfdString
    MAX-ACCESS  read-only
    STATUS      current
    DESCRIPTION "Total number of WSP Packet Unpacking Errors"
    ::= { affirmedServicesContentWapGwServiceStatisticsNodeLevelSummaryEntry 24 }

affirmedServicesContentWapGwServiceStatisticsNodeLevelSummaryNumwapgwwspunhandledeventerrors OBJECT-TYPE
    SYNTAX      ConfdString
    MAX-ACCESS  read-only
    STATUS      current
    DESCRIPTION "Total number of WSP Unhandled Event Errors"
    ::= { affirmedServicesContentWapGwServiceStatisticsNodeLevelSummaryEntry 25 }

affirmedServicesContentWapGwServiceStatisticsNodeLevelSummaryNumwapgwwtptransactionsresp OBJECT-TYPE
    SYNTAX      ConfdString
    MAX-ACCESS  read-only
    STATUS      current
    DESCRIPTION "Total number of WTP Transactions Responded to"
    ::= { affirmedServicesContentWapGwServiceStatisticsNodeLevelSummaryEntry 26 }

affirmedServicesContentWapGwServiceStatisticsNodeLevelSummaryNumwapgwwtptransactionsinit OBJECT-TYPE
    SYNTAX      ConfdString
    MAX-ACCESS  read-only
    STATUS      current
    DESCRIPTION "Total number of WTP Transactions Initiated"
    ::= { affirmedServicesContentWapGwServiceStatisticsNodeLevelSummaryEntry 27 }

affirmedServicesContentWapGwServiceStatisticsNodeLevelSummaryNumwapgwwtppacketunpackingerrors OBJECT-TYPE
    SYNTAX      ConfdString
    MAX-ACCESS  read-only
    STATUS      current
    DESCRIPTION "Total number of WTP Packet Unpacking Errors"
    ::= { affirmedServicesContentWapGwServiceStatisticsNodeLevelSummaryEntry 28 }

affirmedServicesContentWapGwServiceStatisticsNodeLevelSummaryNumwapgwwtpunhandledeventerrors OBJECT-TYPE
    SYNTAX      ConfdString
    MAX-ACCESS  read-only
    STATUS      current
    DESCRIPTION "Total number of WTP Unhandled Event Errors"
    ::= { affirmedServicesContentWapGwServiceStatisticsNodeLevelSummaryEntry 29 }

affirmedServicesContentWapGwServiceStatisticsNodeLevelSummaryNumwapgwwtlssessionscreated OBJECT-TYPE
    SYNTAX      ConfdString
    MAX-ACCESS  read-only
    STATUS      current
    DESCRIPTION "Total number of WTLS Sessions Created"
    ::= { affirmedServicesContentWapGwServiceStatisticsNodeLevelSummaryEntry 30 }

affirmedServicesContentWapGwServiceStatisticsNodeLevelSummaryNumwapgwwtlssessionsopened OBJECT-TYPE
    SYNTAX      ConfdString
    MAX-ACCESS  read-only
    STATUS      current
    DESCRIPTION "Total number of WTLS Sessions Opened"
    ::= { affirmedServicesContentWapGwServiceStatisticsNodeLevelSummaryEntry 31 }

affirmedServicesContentWapGwServiceStatisticsNodeLevelSummaryNumwapgwwtlssessionsterminated OBJECT-TYPE
    SYNTAX      ConfdString
    MAX-ACCESS  read-only
    STATUS      current
    DESCRIPTION "Total number of WTLS Sessions Terminated"
    ::= { affirmedServicesContentWapGwServiceStatisticsNodeLevelSummaryEntry 32 }

affirmedServicesContentWapGwServiceStatisticsNodeLevelSummaryNumwapgwwtlskeyexchangeerrors OBJECT-TYPE
    SYNTAX      ConfdString
    MAX-ACCESS  read-only
    STATUS      current
    DESCRIPTION "Total number of WTLS Key Exchange Errors"
    ::= { affirmedServicesContentWapGwServiceStatisticsNodeLevelSummaryEntry 33 }

affirmedServicesContentWapGwServiceStatisticsNodeLevelSummaryNumwapgwwtlscipherexchangeerrors OBJECT-TYPE
    SYNTAX      ConfdString
    MAX-ACCESS  read-only
    STATUS      current
    DESCRIPTION "Total number of WTLS Cipher Exchange Errors"
    ::= { affirmedServicesContentWapGwServiceStatisticsNodeLevelSummaryEntry 34 }

affirmedServicesContentWapGwServiceStatisticsNodeLevelSummaryNumwapgwwtlskeyidexchangeerrors OBJECT-TYPE
    SYNTAX      ConfdString
    MAX-ACCESS  read-only
    STATUS      current
    DESCRIPTION "Total number of WTLS Key Id Exchange Errors"
    ::= { affirmedServicesContentWapGwServiceStatisticsNodeLevelSummaryEntry 35 }

affirmedServicesContentWapGwServiceStatisticsNodeLevelSummaryNumwapgwwtlspdudecrypterrors OBJECT-TYPE
    SYNTAX      ConfdString
    MAX-ACCESS  read-only
    STATUS      current
    DESCRIPTION "Total number of WTLS Pdu Decrypt Errors"
    ::= { affirmedServicesContentWapGwServiceStatisticsNodeLevelSummaryEntry 36 }

affirmedServicesContentWapGwServiceStatisticsNodeLevelSummaryNumwapgwwtlspduencrypterrors OBJECT-TYPE
    SYNTAX      ConfdString
    MAX-ACCESS  read-only
    STATUS      current
    DESCRIPTION "Total number of WTLS Pdu Encrypt Errors"
    ::= { affirmedServicesContentWapGwServiceStatisticsNodeLevelSummaryEntry 37 }

affirmedServicesContentWapGwServiceStatisticsNodeLevelSummaryNumwapgwwtlsunexpectedmessageerrors OBJECT-TYPE
    SYNTAX      ConfdString
    MAX-ACCESS  read-only
    STATUS      current
    DESCRIPTION "Total number of WTLS Unexpected Message Errors"
    ::= { affirmedServicesContentWapGwServiceStatisticsNodeLevelSummaryEntry 38 }

affirmedServicesContentWapGwServiceStatisticsNodeLevelSummaryNumwapgwwtlsunhandledeventerrors OBJECT-TYPE
    SYNTAX      ConfdString
    MAX-ACCESS  read-only
    STATUS      current
    DESCRIPTION "Total number of WTLS Unhandled Event Errors"
    ::= { affirmedServicesContentWapGwServiceStatisticsNodeLevelSummaryEntry 39 }

affirmedServicesContentWapGwServiceStatisticsNodeLevelSummaryNumwapgwwdpdatagramsreceived OBJECT-TYPE
    SYNTAX      ConfdString
    MAX-ACCESS  read-only
    STATUS      current
    DESCRIPTION "Total number of WDP Datagrams Received"
    ::= { affirmedServicesContentWapGwServiceStatisticsNodeLevelSummaryEntry 40 }

affirmedServicesContentWapGwServiceStatisticsNodeLevelSummaryNumwapgwwdpdatagramssent OBJECT-TYPE
    SYNTAX      ConfdString
    MAX-ACCESS  read-only
    STATUS      current
    DESCRIPTION "Total number of WDP Datagrams Sent"
    ::= { affirmedServicesContentWapGwServiceStatisticsNodeLevelSummaryEntry 41 }

END

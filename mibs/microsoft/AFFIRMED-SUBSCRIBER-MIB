AFFIRMED-SUBSCRIBER-MIB DEFINITIONS ::= BEGIN
IMPORTS
    MODULE-IDENTITY, OBJECT-TYPE,
    Integer32, Unsigned32, Counter32, Counter64,
    Gauge32, IpAddress
        FROM SNMPv2-SMI
    TEXTUAL-CONVENTION, RowStatus, DateAndTime,
    TruthValue
        FROM SNMPv2-TC
;

affirmedSubscriberMIB MODULE-IDENTITY
    ORGANIZATION "Affirmed Networks, Inc."
    CONTACT-INFO "Affirmed Networks, Inc. 35 Nagog Park, Acton, MA, USA"
    DESCRIPTION ""
    ::= { 1 3 6 1 4 1 37963 10 9 }

affirmedSubscriber OBJECT IDENTIFIER ::= { affirmedSubscriberMIB 1 }

affirmedSubscriberServiceProfile OBJECT IDENTIFIER ::= { affirmedSubscriber 1 }

affirmedSubscriberProxySession OBJECT IDENTIFIER ::= { affirmedSubscriber 2 }

END

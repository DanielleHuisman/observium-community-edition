AFFIRMED-SYSTEM-MIB DEFINITIONS ::= BEGIN
IMPORTS
    MODULE-IDENTITY, OBJECT-TYPE,
    Integer32, Unsigned32, Counter32, Counter64,
    Gauge32, IpAddress
        FROM SNMPv2-SMI
    TEXTUAL-CONVENTION, RowStatus, DateAndTime,
    TruthValue
        FROM SNMPv2-TC
;

affirmedSystemMIB MODULE-IDENTITY
    ORGANIZATION "Affirmed Networks, Inc."
    CONTACT-INFO "Affirmed Networks, Inc. 35 Nagog Park, Acton, MA, USA"
    DESCRIPTION ""
    ::= { 1 3 6 1 4 1 37963 10 18 }

ConfdString ::= TEXTUAL-CONVENTION
    DISPLAY-HINT "1t"
    STATUS      current
    DESCRIPTION "xs: and confd: types mapped to strings"
    SYNTAX      OCTET STRING

affirmedSystem OBJECT IDENTIFIER ::= { affirmedSystemMIB 1 }

affirmedSystemNode OBJECT IDENTIFIER ::= { affirmedSystem 2 }

affirmedSystemUptimeTable OBJECT-TYPE
    SYNTAX      SEQUENCE OF AffirmedSystemUptimeEntry
    MAX-ACCESS  not-accessible
    STATUS      current
    DESCRIPTION ""
    ::= { affirmedSystem 1 }

affirmedSystemUptimeEntry OBJECT-TYPE
    SYNTAX      AffirmedSystemUptimeEntry
    MAX-ACCESS  not-accessible
    STATUS      current
    DESCRIPTION ""
    INDEX { affirmedSystemUptimeId }
        ::= { affirmedSystemUptimeTable 1 }

AffirmedSystemUptimeEntry ::=
    SEQUENCE {
        affirmedSystemUptimeId Integer32,
        affirmedSystemUptimeUptime ConfdString
    }

affirmedSystemUptimeId OBJECT-TYPE
    SYNTAX      Integer32
    MAX-ACCESS  not-accessible
    STATUS      current
    DESCRIPTION ""
    ::= { affirmedSystemUptimeEntry 1 }

affirmedSystemUptimeUptime OBJECT-TYPE
    SYNTAX      ConfdString
    MAX-ACCESS  read-only
    STATUS      current
    DESCRIPTION ""
    ::= { affirmedSystemUptimeEntry 2 }

affirmedSystemNodeUptimeTable OBJECT-TYPE
    SYNTAX      SEQUENCE OF AffirmedSystemNodeUptimeEntry
    MAX-ACCESS  not-accessible
    STATUS      current
    DESCRIPTION ""
    ::= { affirmedSystemNode 1 }

affirmedSystemNodeUptimeEntry OBJECT-TYPE
    SYNTAX      AffirmedSystemNodeUptimeEntry
    MAX-ACCESS  not-accessible
    STATUS      current
    DESCRIPTION ""
    INDEX { affirmedSystemNodeUptimeId, affirmedSystemNodeUptimeNodeNumber, affirmedSystemNodeUptimeCpuNumber }
        ::= { affirmedSystemNodeUptimeTable 1 }

AffirmedSystemNodeUptimeEntry ::=
    SEQUENCE {
        affirmedSystemNodeUptimeId Integer32,
        affirmedSystemNodeUptimeNodeNumber Integer32,
        affirmedSystemNodeUptimeCpuNumber Integer32,
        affirmedSystemNodeUptimeUptime ConfdString
    }

affirmedSystemNodeUptimeId OBJECT-TYPE
    SYNTAX      Integer32
    MAX-ACCESS  not-accessible
    STATUS      current
    DESCRIPTION ""
    ::= { affirmedSystemNodeUptimeEntry 1 }

affirmedSystemNodeUptimeNodeNumber OBJECT-TYPE
    SYNTAX      Integer32
    MAX-ACCESS  not-accessible
    STATUS      current
    DESCRIPTION ""
    ::= { affirmedSystemNodeUptimeEntry 2 }

affirmedSystemNodeUptimeCpuNumber OBJECT-TYPE
    SYNTAX      Integer32
    MAX-ACCESS  not-accessible
    STATUS      current
    DESCRIPTION ""
    ::= { affirmedSystemNodeUptimeEntry 3 }

affirmedSystemNodeUptimeUptime OBJECT-TYPE
    SYNTAX      ConfdString
    MAX-ACCESS  read-only
    STATUS      current
    DESCRIPTION ""
    ::= { affirmedSystemNodeUptimeEntry 4 }

END

AFFIRMED-TAM-MIB DEFINITIONS ::= BEGIN
IMPORTS
    MODULE-IDENTITY, OBJECT-TYPE,
    Integer32, Unsigned32, Counter32, Counter64,
    Gauge32, IpAddress
        FROM SNMPv2-SMI
    TEXTUAL-CONVENTION, RowStatus, DateAndTime,
    TruthValue
        FROM SNMPv2-TC
;

affirmedTamMIB MODULE-IDENTITY
    ORGANIZATION "Affirmed Networks, Inc."
    CONTACT-INFO "Affirmed Networks, Inc. 35 Nagog Park, Acton, MA, USA"
    DESCRIPTION ""
    ::= { 1 3 6 1 4 1 37963 10 28 }

ConfdString ::= TEXTUAL-CONVENTION
    DISPLAY-HINT "1t"
    STATUS      current
    DESCRIPTION "xs: and confd: types mapped to strings"
    SYNTAX      OCTET STRING

affirmedTam OBJECT IDENTIFIER ::= { affirmedTamMIB 1 }

affirmedTamTamstatisticsTable OBJECT-TYPE
    SYNTAX      SEQUENCE OF AffirmedTamTamstatisticsEntry
    MAX-ACCESS  not-accessible
    STATUS      current
    DESCRIPTION ""
    ::= { affirmedTam 1 }

affirmedTamTamstatisticsEntry OBJECT-TYPE
    SYNTAX      AffirmedTamTamstatisticsEntry
    MAX-ACCESS  not-accessible
    STATUS      current
    DESCRIPTION ""
    INDEX { affirmedTamTamstatisticsChassis, affirmedTamTamstatisticsSlot }
        ::= { affirmedTamTamstatisticsTable 1 }

AffirmedTamTamstatisticsEntry ::=
    SEQUENCE {
        affirmedTamTamstatisticsChassis Unsigned32,
        affirmedTamTamstatisticsSlot Unsigned32,
        affirmedTamTamstatisticsEastwestcorerxpkts ConfdString,
        affirmedTamTamstatisticsEastwestcorerxbytes ConfdString,
        affirmedTamTamstatisticsEastwestcoretxpkts ConfdString,
        affirmedTamTamstatisticsEastwestcoretxbytes ConfdString,
        affirmedTamTamstatisticsEastwestaccessrxpkts ConfdString,
        affirmedTamTamstatisticsEastwestaccessrxbytes ConfdString,
        affirmedTamTamstatisticsEastwestaccesstxpkts ConfdString,
        affirmedTamTamstatisticsEastwestaccesstxbytes ConfdString,
        affirmedTamTamstatisticsEastwestworkflowtoaccessrxpkts ConfdString,
        affirmedTamTamstatisticsEastwestaccesstoworkflowrxpkts ConfdString,
        affirmedTamTamstatisticsEastwestworkflowtocorerxpkts ConfdString,
        affirmedTamTamstatisticsEastwestcoretoworkflowrxpkts ConfdString,
        affirmedTamTamstatisticsEastwestsecurityrxpkts ConfdString,
        affirmedTamTamstatisticsEastwestinternalismrxpkts ConfdString
    }

affirmedTamTamstatisticsChassis OBJECT-TYPE
    SYNTAX      Unsigned32
    MAX-ACCESS  not-accessible
    STATUS      current
    DESCRIPTION "chassis id"
    ::= { affirmedTamTamstatisticsEntry 1 }

affirmedTamTamstatisticsSlot OBJECT-TYPE
    SYNTAX      Unsigned32
    MAX-ACCESS  not-accessible
    STATUS      current
    DESCRIPTION "slot id"
    ::= { affirmedTamTamstatisticsEntry 2 }

affirmedTamTamstatisticsEastwestcorerxpkts OBJECT-TYPE
    SYNTAX      ConfdString
    MAX-ACCESS  read-only
    STATUS      current
    DESCRIPTION "packets received over east-west from core for locally anchored session."
    ::= { affirmedTamTamstatisticsEntry 3 }

affirmedTamTamstatisticsEastwestcorerxbytes OBJECT-TYPE
    SYNTAX      ConfdString
    MAX-ACCESS  read-only
    STATUS      deprecated
    DESCRIPTION "bytes received over east-west from core for locally anchored session."
    ::= { affirmedTamTamstatisticsEntry 4 }

affirmedTamTamstatisticsEastwestcoretxpkts OBJECT-TYPE
    SYNTAX      ConfdString
    MAX-ACCESS  read-only
    STATUS      current
    DESCRIPTION "packets transmitted over east-west to core from locally anchored session."
    ::= { affirmedTamTamstatisticsEntry 5 }

affirmedTamTamstatisticsEastwestcoretxbytes OBJECT-TYPE
    SYNTAX      ConfdString
    MAX-ACCESS  read-only
    STATUS      deprecated
    DESCRIPTION "bytes transmitted over east-west to core from locally anchored session."
    ::= { affirmedTamTamstatisticsEntry 6 }

affirmedTamTamstatisticsEastwestaccessrxpkts OBJECT-TYPE
    SYNTAX      ConfdString
    MAX-ACCESS  read-only
    STATUS      current
    DESCRIPTION "packets received over east-west from access for locally anchored session."
    ::= { affirmedTamTamstatisticsEntry 7 }

affirmedTamTamstatisticsEastwestaccessrxbytes OBJECT-TYPE
    SYNTAX      ConfdString
    MAX-ACCESS  read-only
    STATUS      deprecated
    DESCRIPTION "bytes received over east-west from access for locally anchored session."
    ::= { affirmedTamTamstatisticsEntry 8 }

affirmedTamTamstatisticsEastwestaccesstxpkts OBJECT-TYPE
    SYNTAX      ConfdString
    MAX-ACCESS  read-only
    STATUS      current
    DESCRIPTION "packets transmitted over east-west to access from locally anchored session."
    ::= { affirmedTamTamstatisticsEntry 9 }

affirmedTamTamstatisticsEastwestaccesstxbytes OBJECT-TYPE
    SYNTAX      ConfdString
    MAX-ACCESS  read-only
    STATUS      deprecated
    DESCRIPTION "bytes transmitted over east-west to access from locally anchored session."
    ::= { affirmedTamTamstatisticsEntry 10 }

affirmedTamTamstatisticsEastwestworkflowtoaccessrxpkts OBJECT-TYPE
    SYNTAX      ConfdString
    MAX-ACCESS  read-only
    STATUS      current
    DESCRIPTION "packets to access received over east-west from remotely anchored session."
    ::= { affirmedTamTamstatisticsEntry 11 }

affirmedTamTamstatisticsEastwestaccesstoworkflowrxpkts OBJECT-TYPE
    SYNTAX      ConfdString
    MAX-ACCESS  read-only
    STATUS      current
    DESCRIPTION "packets from access received over east-west to locally anchored session."
    ::= { affirmedTamTamstatisticsEntry 12 }

affirmedTamTamstatisticsEastwestworkflowtocorerxpkts OBJECT-TYPE
    SYNTAX      ConfdString
    MAX-ACCESS  read-only
    STATUS      current
    DESCRIPTION "packets to core received over east-west from remotely anchored session."
    ::= { affirmedTamTamstatisticsEntry 13 }

affirmedTamTamstatisticsEastwestcoretoworkflowrxpkts OBJECT-TYPE
    SYNTAX      ConfdString
    MAX-ACCESS  read-only
    STATUS      current
    DESCRIPTION "packets received from core over east-west to locally anchored session."
    ::= { affirmedTamTamstatisticsEntry 14 }

affirmedTamTamstatisticsEastwestsecurityrxpkts OBJECT-TYPE
    SYNTAX      ConfdString
    MAX-ACCESS  read-only
    STATUS      current
    DESCRIPTION "packets received over the east-west for local security processing."
    ::= { affirmedTamTamstatisticsEntry 15 }

affirmedTamTamstatisticsEastwestinternalismrxpkts OBJECT-TYPE
    SYNTAX      ConfdString
    MAX-ACCESS  read-only
    STATUS      current
    DESCRIPTION "packets received from local proxy."
    ::= { affirmedTamTamstatisticsEntry 16 }

END

AFFIRMED-TEMS-NOTIFICATION-MIB DEFINITIONS ::= BEGIN

      IMPORTS

      MODULE-IDENTITY, NOTIFICATION-TYPE, IpAddress                       FROM SNMPv2-SMI
      TEXTUAL-CONVENTION,DisplayString, TruthValue,DateAndTime            FROM SNMPv2-TC
      AlarmLevel, AlarmLevelString                                        FROM AFFIRMED-TEMS-TC-MIB
      affirmedSnmpNotifications                                    		  FROM AFFIRMED-TEMS-SNMP-MIB
      temsServerPerfMetric, temsServerPerfMetricCollectedValue,
      perfMetricCriticalThreshold, perfMetricMajorThreshold,
      perfMetricMinorThreshold, perfMetricClearThreshold                  FROM AFFIRMED-TEMS-OBJECTS-MIB;

affirmedTemsNotifications MODULE-IDENTITY
        LAST-UPDATED "201504091104Z"
        ORGANIZATION "Affirmed Networks"
        CONTACT-INFO "affirmed@affirmednetworks.com"
        DESCRIPTION  "Management Information for notification/alarming the NB NMS / OSS Systems."
        REVISION      "201504091104Z"
        DESCRIPTION  "NorthBound Notification MIB for ANMS Release"
    ::= { affirmedSnmpNotifications 1 }

--
-- Notification Config
--
notificationConfig  OBJECT IDENTIFIER ::= { affirmedTemsNotifications  1 }

suppressAlarms      OBJECT-TYPE
    SYNTAX          TruthValue
    MAX-ACCESS      read-write
    STATUS          current
    DESCRIPTION     "This is used to request the EMS Server to stop sending alarms to All the Managers."
    DEFVAL          { false }
    ::= { notificationConfig 1}

--
-- Fault and Alarm object define
--
notificationObjects         OBJECT IDENTIFIER ::= { affirmedTemsNotifications 2 }

temsServerTimeStamp  OBJECT-TYPE
    SYNTAX          DateAndTime
    MAX-ACCESS      accessible-for-notify
    STATUS          current
    DESCRIPTION     "This object specifies Time at which the Alarm is triggered by the Mgmt Server"
    ::= { notificationObjects 1 }

alarmSeverity       OBJECT-TYPE
    SYNTAX          AlarmLevelString
    MAX-ACCESS      accessible-for-notify
    STATUS          current
    DESCRIPTION     "This object indicates the severity of alarm. Clear severity will be used
                     to clear the previously  raised alarm"
    ::= { notificationObjects 2 }

alarmDiagnosticData OBJECT-TYPE
    SYNTAX          DisplayString
    MAX-ACCESS      accessible-for-notify
    STATUS          current
    DESCRIPTION     "This is used as a place holder to include detailed alarm message"
    ::= { notificationObjects 3 }

networkElementIPAddress OBJECT-TYPE
    SYNTAX          IpAddress
    MAX-ACCESS      accessible-for-notify
    STATUS          current
    DESCRIPTION     "This is used to indicate the IP-Address of the Network Element serving
                     as the root cause of the problem. However, if the trap is generated by the Mgmt Server
                     itself, this may contain the IP-Address of the Mgmt Server."
    ::= { notificationObjects 4 }

networkElementSoftwareVersion OBJECT-TYPE
    SYNTAX          DisplayString
    MAX-ACCESS      accessible-for-notify
    STATUS          current
    DESCRIPTION     "Indicates the current software version of the Network Element being Managed"
    ::= { notificationObjects 5 }

cliUserName OBJECT-TYPE
    SYNTAX          DisplayString
    MAX-ACCESS      accessible-for-notify
    STATUS          current
    DESCRIPTION     "Indicates the User Name used to open the CLI Session with the Network Element"
    ::= { notificationObjects 6 }

notificationAddress OBJECT-TYPE
    SYNTAX          DisplayString
    MAX-ACCESS      accessible-for-notify
    STATUS          current
    DESCRIPTION     "Indicates the E-Mail Address used for Notification"
    ::= { notificationObjects 7 }

sourceComponent OBJECT-TYPE
    SYNTAX          DisplayString
    MAX-ACCESS      accessible-for-notify
    STATUS          current
    DESCRIPTION     "Indicates the Component within the Router / Switch responsible for the problem. It is represented in Shelf-Slot-Port format"
    ::= { notificationObjects 8 }

alarmCategory OBJECT-TYPE
    SYNTAX          DisplayString
    MAX-ACCESS      accessible-for-notify
    STATUS          current
    DESCRIPTION     "Category Assigned for the Alarm. Used as a place holder to differentiate different types of
                     Traps that can be raised from the same component of the equipment"
    ::= { notificationObjects 9 }

emsNodeIPAddress OBJECT-TYPE
    SYNTAX          IpAddress
    MAX-ACCESS      accessible-for-notify
    STATUS          current
    DESCRIPTION     "This is used to indicate the IP-Address of the EMS node for
                     EMS cluster state change notifications."
    ::= { notificationObjects 10 }

emsClusterChangeNotificationData OBJECT-TYPE
    SYNTAX          DisplayString
    MAX-ACCESS      accessible-for-notify
    STATUS          current
    DESCRIPTION     "Includes information about the current state of the EMS cluster.
                     This is included with the EMS cluster state change notifications."                     
        ::= { notificationObjects 11 }

vCenterOldStatus OBJECT-TYPE
    SYNTAX          DisplayString
    MAX-ACCESS      accessible-for-notify
    STATUS          current
    DESCRIPTION     "This is used by vcenter to indicate the old status in the notification.Sample Values: Gray/Yellow"
    ::= { notificationObjects 12 }

vCenterNewStatus OBJECT-TYPE
    SYNTAX          DisplayString
    MAX-ACCESS      accessible-for-notify
    STATUS          current
    DESCRIPTION     "This is used by vcenter to indicate the new status in the notification.Sample Values: Gray/Yellow"
    ::= { notificationObjects 13 }

vCenterTargetObjectType OBJECT-TYPE
    SYNTAX          INTEGER { unknown(1), host(2), vm(3), other(4)}
    MAX-ACCESS      accessible-for-notify
    STATUS          current
    DESCRIPTION     "This is the alarm target object type"
    ::= { notificationObjects 14 }
	
alarmRemedy OBJECT-TYPE
    SYNTAX          DisplayString
    MAX-ACCESS      accessible-for-notify
    STATUS          current
    DESCRIPTION     "It is used to indicate the potential impact of the alarm and corrective action to remedy."
    ::= { notificationObjects 15 }

alarmAdditionalInfo OBJECT-TYPE
    SYNTAX          DisplayString
    MAX-ACCESS      accessible-for-notify
    STATUS          current
    DESCRIPTION     "It contain semi-colon separated name/value pairs additional information."
    ::= { notificationObjects 16 }
    
alarmTrapOID OBJECT-TYPE
    SYNTAX          DisplayString
    MAX-ACCESS      accessible-for-notify
    STATUS          current
    DESCRIPTION     "It is used to indicate Trap OID information."
    ::= { notificationObjects 17 }

elementHostName OBJECT-TYPE
    SYNTAX          DisplayString
    MAX-ACCESS      accessible-for-notify
    STATUS          current
    DESCRIPTION     "Includes information about the host name of the element."
    ::= { notificationObjects 18 }
	
temsNorthBoundNotifications           OBJECT IDENTIFIER ::= { affirmedTemsNotifications  3 }

networkElementNotReachable NOTIFICATION-TYPE
    OBJECTS         { networkElementIPAddress,
                      alarmDiagnosticData,
                      temsServerTimeStamp,
                      alarmSeverity,
                      elementHostName
                    }
    STATUS          current
    DESCRIPTION     "Management Server will send this notification to its NB Clients (NMS / OSS) whenever
                     a managed network element turns unreachable (ICMP)."
    ::= { temsNorthBoundNotifications 1 }

networkElementNotManageable NOTIFICATION-TYPE
    OBJECTS         { networkElementIPAddress,
                      alarmDiagnosticData,
                      temsServerTimeStamp,
                      alarmSeverity,
                      elementHostName
                    }
    STATUS          current
    DESCRIPTION     "Management Server will send this notification to its NB Clients (NMS / OSS) whenever
                     a managed network element is reachable via ICMP but not reachable via the Management protocol (SNMP / TL1 )"
    ::= { temsNorthBoundNotifications 2 }

networkElementManageable NOTIFICATION-TYPE
    OBJECTS         { networkElementIPAddress,
                      alarmDiagnosticData,
                      temsServerTimeStamp,
                      alarmSeverity,
                      elementHostName
                    }
    STATUS          current
    DESCRIPTION     "Management Server will send this notification to its NB Clients (NMS / OSS) to clear the
                     not manageable events raised previously."
    ::= { temsNorthBoundNotifications 3 }

unSupportedNetworkElementVersion NOTIFICATION-TYPE
    OBJECTS         { networkElementIPAddress,
                      networkElementSoftwareVersion,
                      alarmDiagnosticData,
                      temsServerTimeStamp,
                      alarmSeverity,
                      elementHostName
                    }
    STATUS          current
    DESCRIPTION     "Management Server will send this notification to its NB Clients (NMS / OSS) whenever it
                     encounters / discovers a Network element running an Unsupported software version."
    ::= { temsNorthBoundNotifications 4 }

cliLoginFailed NOTIFICATION-TYPE
    OBJECTS         { networkElementIPAddress,
                      cliUserName,
                      alarmDiagnosticData,
                      temsServerTimeStamp,
                      alarmSeverity,
                      elementHostName
                    }
    STATUS          current
    DESCRIPTION     "Management Server will send this notification to its NB Clients (NMS / OSS) whenever it
                     could not login to the CLI (or TL1) session of the Network Element using the supplied
                     Credentials"
    ::= { temsNorthBoundNotifications 5 }

alarmEmailNotificationFailure NOTIFICATION-TYPE
    OBJECTS         { notificationAddress,
                      alarmDiagnosticData,
                      temsServerTimeStamp,
                      alarmSeverity,
                      elementHostName
                    }
    STATUS          current
    DESCRIPTION     "Management Server will send this notification to its NB Clients (NMS / OSS) upon its
                     Failure to send the E-Mail Notification to NB Clients registered for E-Mail Notification"
    ::= { temsNorthBoundNotifications 6 }

dataCollectionFailure NOTIFICATION-TYPE
    OBJECTS         { networkElementIPAddress,
                      temsServerPerfMetric,
                      alarmDiagnosticData,
                      temsServerTimeStamp,
                      alarmSeverity,
                      elementHostName
                    }
    STATUS          current
    DESCRIPTION     "Indicates a Failure during Data Collection.
                     NB managers can either ignore it (or) log-it."
    ::= { temsNorthBoundNotifications 7 }

temsServerPerfMetricCriticalTCA NOTIFICATION-TYPE
    OBJECTS         { networkElementIPAddress,
                      temsServerPerfMetric,
                      temsServerPerfMetricCollectedValue,
                      perfMetricCriticalThreshold,
					  alarmDiagnosticData,
                      temsServerTimeStamp,
                      alarmSeverity,
                      elementHostName
                    }
    STATUS          current
    DESCRIPTION     "Management Server will send this notification to its NB Clients (NMS / OSS) to report
                     a Critical Threshold Crossing Alert, whenever the Critical Threshold limit is
                     crossed for the current Performance Metric"
    ::= { temsNorthBoundNotifications 8 }

temsServerPerfMetricMajorTCA NOTIFICATION-TYPE
    OBJECTS         { networkElementIPAddress,
                      temsServerPerfMetric,
                      temsServerPerfMetricCollectedValue,
                      perfMetricMajorThreshold,
					  alarmDiagnosticData,
                      temsServerTimeStamp,
                      alarmSeverity,
                      elementHostName
                    }
    STATUS          current
    DESCRIPTION     "Management Server will send this notification to its NB Clients (NMS / OSS) to report
                     a Major Threshold Crossing Alert, whenever the Major Threshold limit is
                     crossed for the current Performance Metric"
    ::= { temsNorthBoundNotifications 9 }

temsServerPerfMetricMinorTCA NOTIFICATION-TYPE
    OBJECTS         { networkElementIPAddress,
                      temsServerPerfMetric,
                      temsServerPerfMetricCollectedValue,
                      perfMetricMinorThreshold,
					  alarmDiagnosticData,
                      temsServerTimeStamp,
                      alarmSeverity,
                      elementHostName
                    }
    STATUS          current
    DESCRIPTION     "Management Server will send this notification to its NB Clients (NMS / OSS) to report
                     a Minor Threshold Crossing Alert, whenever the Minor Threshold limit is
                     crossed for the current Performance Metric"
    ::= { temsNorthBoundNotifications 10 }

temsServerPerfMetricClearTCA NOTIFICATION-TYPE
    OBJECTS         { networkElementIPAddress,
                      temsServerPerfMetric,
                      temsServerPerfMetricCollectedValue,
                      perfMetricClearThreshold,
					  alarmDiagnosticData,
                      temsServerTimeStamp,
                      alarmSeverity,
                      elementHostName
                    }
    STATUS          current
    DESCRIPTION     "Management Server will send this notification to its NB Clients (NMS / OSS) to Clear
                     the previously raised Critical / Major / Minor TCA for this Performance Metric."
    ::= { temsNorthBoundNotifications 11 }

alarmFromNetworkElement NOTIFICATION-TYPE
    OBJECTS         { networkElementIPAddress,
                      sourceComponent,
                      alarmCategory,
                      alarmSeverity,
                      alarmDiagnosticData,
                      temsServerTimeStamp,
					  alarmRemedy,
					  alarmAdditionalInfo,
					  alarmTrapOID,
					  elementHostName
                    }
    STATUS          current
    DESCRIPTION     "Management Server will send this notification to its NB Clients (NMS / OSS) to report
                       an Alarm Raised due to the occurrence of a trap from the Network Element.
                       Severity List includes Cleared. the Clear Alarm should clear the previous raise Alarm.
                       The combination of networkElementIPAddress, sourceComponent (if any), alarmCategory (if available)
                       and alarmSeverity shall be used to uniquely identify a specific root cause"
    ::= { temsNorthBoundNotifications 12 }

hotStandbyTakesOver NOTIFICATION-TYPE
    OBJECTS         { alarmDiagnosticData,
                      temsServerTimeStamp
                    }
    STATUS          deprecated
    DESCRIPTION     "Indicates a Switchover of the Management server from primary to Standby Server.
                     Note: This alarm will be triggered only when the Management Server is deployed in a Primary - HotStandBy mode."
    ::= { temsNorthBoundNotifications 13 }

primaryServerisRestored NOTIFICATION-TYPE
    OBJECTS         { alarmDiagnosticData,
                      temsServerTimeStamp
                    }
    STATUS          deprecated
       DESCRIPTION     "Indicates that the Primary Management Server has been restored back in Service.
                     Note: This alarm will be triggered only when the Management Server is deployed in a Primary - HotStandBy mode."
    ::= { temsNorthBoundNotifications 14 }

alarmfromElementManagementSystem NOTIFICATION-TYPE
	OBJECTS			{ networkElementIPAddress,
                      sourceComponent,
                      alarmCategory,
                      alarmSeverity,
                      alarmDiagnosticData,
                      temsServerTimeStamp,
                      elementHostName
                    }
    STATUS          current
    DESCRIPTION     "Management Server will send this notification to its NB Clients (NMS / OSS) to report
                       an Alarm Raised due to the occurence of a trap from the Network Management System.
                       Severity List includes Cleared. the Clear Alarm should clear the previous raise Alarm.
                       The combination of networkElementIPAddress, sourceComponent (if any), alarmCategory (if available)
                       and alarmSeverity shall be used to uniquely identify a specific root cause"
    ::= { temsNorthBoundNotifications 15 }


geoRedundancyGroupMismatch NOTIFICATION-TYPE
    OBJECTS                 { sourceComponent,
                             networkElementIPAddress,
                             alarmDiagnosticData,
                             alarmSeverity,
			                 temsServerTimeStamp,
                      		 elementHostName
			   }
    STATUS                 current
    DESCRIPTION            "Management server will send this notification to its NB clients (NMS / OSS) when it detects
				mismatch information from EMS, active and standby network element
                The networkElementIpAddress attribute is populated with the Mgmt Server IP address"
    ::= { temsNorthBoundNotifications 16 }




vnfScaleKpiMonitorAlarm NOTIFICATION-TYPE
    OBJECTS                 { sourceComponent,
                             networkElementIPAddress,
                             alarmDiagnosticData,
                             alarmSeverity,
                             temsServerTimeStamp,
                      		 elementHostName
               }
    STATUS                 current
    DESCRIPTION            "Dynamic VM capacity management KPI monitoring alarms.
                Source is cluster[vclusterId]/<KPIName> where KPIName can be
                DCMSession, WSMSession, ASMConn, ASMThruput.
                Severity may be of one of the three values: MAJOR, CRITICAL, CLEARED
                MAJOR   The respective KPI is transitioned to one of the following states:
                    Underload threshold crossed for 80% of the duration or
                    Overload threshold crossed for 80% of the duration
                CRITICAL    The respective KPI is transitioned to one of the following states:
                    Underload condition
                    Overload condition
                CLEARED The respective KPI is transitioned to one of the following states:
                    Normal condition, i.e. in neither underload nor overload condition
                The networkElementIpAddress attribute is populated with the Mgmt Server IP address"
    ::= { temsNorthBoundNotifications 17 }


vnfScaleOutAlarm NOTIFICATION-TYPE
    OBJECTS                 { sourceComponent,
                             networkElementIPAddress,
                             alarmDiagnosticData,
                             alarmSeverity,
                             temsServerTimeStamp,
                      		 elementHostName
               }
    STATUS                 current
    DESCRIPTION            "Generated when VM scale out operation fails
                Source is cluster[vclusterId]/node[vnodeId]. Severity will be CRITICAL.
                The networkElementIpAddress attribute is populated with the Mgmt Server IP address"
    ::= { temsNorthBoundNotifications 18 }

vnfScaleInAlarm NOTIFICATION-TYPE
    OBJECTS                 { sourceComponent,
                             networkElementIPAddress,
                             alarmDiagnosticData,
                             alarmSeverity,
                             temsServerTimeStamp,
                      		 elementHostName
               }
    STATUS                 current
    DESCRIPTION            "Generated when VM scale in operation fails
                Source is cluster[vclusterId]/node[vnodeId]. Severity will be CRITICAL.
                The networkElementIpAddress attribute is populated with the Mgmt Server IP address"
    ::= { temsNorthBoundNotifications 19 }


emsClusterStatusChangeNotification NOTIFICATION-TYPE
    OBJECTS         { emsNodeIPAddress,
                      emsClusterChangeNotificationData,
                      alarmSeverity,
                      temsServerTimeStamp,
                      elementHostName
                    }
    STATUS          current
    DESCRIPTION     "Management Server will send this notification to its NB Clients (NMS / OSS) upon its
                     detection of cluster status change"
::= { temsNorthBoundNotifications 20 }


alarmFromVCenter NOTIFICATION-TYPE
    OBJECTS     { networkElementIPAddress,
			      alarmCategory,
			      vCenterTargetObjectType,
                  vCenterOldStatus,
                  vCenterNewStatus,
                  alarmDiagnosticData,
                  sourceComponent,                             
			      temsServerTimeStamp,
                  elementHostName
			    }
    STATUS                 current
    DESCRIPTION            "Management Server will send this notification to its NB Clients (NMS / OSS) to report
                      			 an Alarm Raised due to the occurence of a trap from VCenter Server"
    ::= { temsNorthBoundNotifications 21 }
    
cliLoginSuccess NOTIFICATION-TYPE
    OBJECTS         { networkElementIPAddress,
                      cliUserName,
                      alarmDiagnosticData,
                      temsServerTimeStamp,
                      alarmSeverity,
                      elementHostName
                    }
    STATUS          current
    DESCRIPTION     "Management Server will send this notification to its NB Clients (NMS / OSS) whenever it
                     could be login to the CLI (or TL1) session of the Network Element using the supplied
                     Credentials"
    ::= { temsNorthBoundNotifications 22 }  
      
cliTemplateConfigFailed NOTIFICATION-TYPE
    OBJECTS         { networkElementIPAddress,
                      alarmDiagnosticData,
                      sourceComponent,
                      temsServerTimeStamp,
                      alarmSeverity,
                      elementHostName
                    }
    STATUS          current
    DESCRIPTION     "Management Server will send this notification to its NB Clients (NMS / OSS) whenever
    				 cli template configuration failed."
    ::= { temsNorthBoundNotifications 23 }
        
cliTemplateConfigSuccess NOTIFICATION-TYPE
    OBJECTS         { networkElementIPAddress,
                      alarmDiagnosticData,
                      sourceComponent,
                      temsServerTimeStamp,
                      alarmSeverity,
                      elementHostName
                    }
    STATUS          current
    DESCRIPTION     "Management Server will send this notification to its NB Clients (NMS / OSS) whenever
    				 cli template configuration succeeds."
    ::= { temsNorthBoundNotifications 24 }
        
alarmtriggeredCliTemplateConfigFailed NOTIFICATION-TYPE
    OBJECTS         { networkElementIPAddress,
                      alarmDiagnosticData,
                      sourceComponent,
                      temsServerTimeStamp,
                      alarmSeverity,
                      elementHostName
                    }
    STATUS          current
    DESCRIPTION     "Management Server will send this notification to its NB Clients (NMS / OSS) whenever
    				 alarm triggered cli template configuration failed."
    ::= { temsNorthBoundNotifications 25 }
        
alarmtriggeredCliTemplateConfigSuccess NOTIFICATION-TYPE
    OBJECTS         { networkElementIPAddress,
                      alarmDiagnosticData,
                      sourceComponent,
                      temsServerTimeStamp,
                      alarmSeverity,
                      elementHostName
                    }
    STATUS          current
    DESCRIPTION     "Management Server will send this notification to its NB Clients (NMS / OSS) whenever
    				 alarm triggered cli template configuration succeeds."
    ::= { temsNorthBoundNotifications 26 }
        
alarmSnmpNotificationFailure NOTIFICATION-TYPE
    OBJECTS         { sourceComponent,
                      alarmDiagnosticData,
                      temsServerTimeStamp,
                      alarmSeverity,
                      elementHostName
                    }
    STATUS          current
    DESCRIPTION     "Management Server will send this notification to its NB Clients (NMS / OSS) upon its
    				Failure to forward the trap to NB Clients registered for Trap Forwarding."
    ::= { temsNorthBoundNotifications 27 }
        
masterSlaveStandbyNodeDown NOTIFICATION-TYPE
    OBJECTS         { networkElementIPAddress,
                      alarmDiagnosticData,
                      temsServerTimeStamp,
                      alarmSeverity,
                      elementHostName
                    }
    STATUS          current
    DESCRIPTION     "Management Server will send this notification to its NB Clients (NMS / OSS) to reports that
					 in cluster topology standby node moved to down state."
    ::= { temsNorthBoundNotifications 28 }
        
masterSlaveStandbyNodeUp NOTIFICATION-TYPE
    OBJECTS         { networkElementIPAddress,
                      alarmDiagnosticData,
                      temsServerTimeStamp,
                      alarmSeverity,
                      elementHostName
                    }
    STATUS          current
    DESCRIPTION     "Management Server will send this notification to its NB Clients (NMS / OSS) to reports that
					 in cluster topology standby node moved to up state."
    ::= { temsNorthBoundNotifications 29 }

NBHeartBeat NOTIFICATION-TYPE
    OBJECTS	    {}
    STATUS          current
    DESCRIPTION     "Management Server will send this notification to its INFORM supported NB Clients to verify
    				 the NB client alive status."
    ::= { temsNorthBoundNotifications 31 }


networkElementAutoUnmanage NOTIFICATION-TYPE
	 OBJECTS	    { networkElementIPAddress,
	 				  alarmCategory,
	 				  alarmSeverity,
	 				  alarmDiagnosticData,
	 				  temsServerTimeStamp,
	 				  alarmRemedy,
	 				  elementHostName
	 				  }
	 STATUS         current
	 DESCRIPTION	"Device has been automatically unmanaged due to authentication failure."
	 ::= { temsNorthBoundNotifications 32 }

networkElementManage NOTIFICATION-TYPE
	 OBJECTS	    { networkElementIPAddress,
	 				  alarmCategory,
	 				  alarmSeverity,
	 				  alarmDiagnosticData,
	 				  temsServerTimeStamp,
	 				  elementHostName
	 				  }
	 STATUS         current
	 DESCRIPTION	"Device has been managed successfully."
	 ::= { temsNorthBoundNotifications 33 }

CUPSConfigurationMismatch NOTIFICATION-TYPE
         OBJECTS            { networkElementIPAddress,
                                          alarmSource,
                                          alarmCategory,
                                          alarmSeverity,
                                          alarmMessage,
                                          alarmUpdatedTime,
                                          elementHostName
                                          }
         STATUS         current
         DESCRIPTION    "CUPS Configuration mismatch found."
         ::= { temsNorthBoundNotifications 34 }

CUPSConfigurationMatch NOTIFICATION-TYPE
         OBJECTS            { networkElementIPAddress,
                                          alarmSource,
                                          alarmCategory,
                                          alarmSeverity,
                                          alarmMessage,
                                          alarmClearedTime,
                                          elementHostName
                                          }
         STATUS         current
         DESCRIPTION    "CUPS Configuration mismatch cleared."
         ::= { temsNorthBoundNotifications 35 }

CUPSGroupCreationFailed NOTIFICATION-TYPE
         OBJECTS            { networkElementIPAddress,
                                          alarmSource,
                                          alarmCategory,
                                          alarmSeverity,
                                          alarmMessage,
                                          alarmUpdatedTime,
                                          elementHostName
                                          }
         STATUS         current
         DESCRIPTION    "CUPS Group Creation Failed. Manually remove the config from CPlane."
         ::= { temsNorthBoundNotifications 36 }

END

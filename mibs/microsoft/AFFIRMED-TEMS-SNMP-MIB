AFFIRMED-TEMS-SNMP-MIB DEFINITIONS ::= BEGIN

--
-- Top-level infrastructure of the Affirmed enterprise MIB tree
--

IMPORTS
    MODULE-IDENTITY, enterprises       FROM SNMPv2-SMI
    affirmedSnmp                       FROM AFFIRMED-SNMP-MIB;

affirmedTemsSnmp MODULE-IDENTITY
    LAST-UPDATED "201105160000Z"
    ORGANIZATION "www.affirmednetworks.com"
    CONTACT-INFO
	 "postal:   Affirmed Networks, Inc.
		    	35 Nagog Park
                Acton, MA "
    DESCRIPTION
	"Infrastructure of the Affirmed enterprise Northbound Notifications"
    REVISION     "201105160000Z"
    DESCRIPTION
	"First draft"
    ::= { affirmedSnmp 6}


--
--  AFFIRMED-TEMS-SNMP specific textual conventions
--

affirmedSnmpTc                   	   OBJECT IDENTIFIER ::= {affirmedTemsSnmp 1}

--
--  AFFIRMED-TEMS-SNMP specific notification objects
--

affirmedSnmpObjects                    OBJECT IDENTIFIER ::= {affirmedTemsSnmp 2}

--
--  AFFIRMED-TEMS-SNMP specific notifications
--

affirmedSnmpNotifications              OBJECT IDENTIFIER ::= {affirmedTemsSnmp 3}




END

AFFIRMED-TEMS-TC-MIB DEFINITIONS ::= BEGIN

    IMPORTS

    MODULE-IDENTITY, TEXTUAL-CONVENTION             FROM SNMPv2-TC
              affirmedSnmpTc                        FROM AFFIRMED-TEMS-SNMP-MIB;


affirmedTemsTc MODULE-IDENTITY
    LAST-UPDATED "200803141114Z"
    ORGANIZATION "Affirmed Networks."
    CONTACT-INFO "affirmed@affirmednetworks.com"
    DESCRIPTION  "This MIB module defines the Key Textual Conventions used in the Management Server."
    REVISION      "200803141114Z"
    DESCRIPTION  "MIB Version for ANMS  release"
    ::= { affirmedSnmpTc 1}


ResourceAdminStatus ::= TEXTUAL-CONVENTION
        STATUS current
        DESCRIPTION
            "Resource Admin Status specifies the generic Administrative states of the Resource"
        SYNTAX    INTEGER { active(1),
                            inactive(2),
                            testing(3) }

ThresholdType          ::= TEXTUAL-CONVENTION
    STATUS          current
    DESCRIPTION     "Represents The Type of the Threshold being applied to the Metric."
    SYNTAX  INTEGER {
                      increasing  (1),
                      decreasing  (2)
                    }


AlarmLevel          ::= TEXTUAL-CONVENTION
    STATUS          current
    DESCRIPTION     "Represents alarm status."
    SYNTAX  INTEGER {
                      cleared  (1),
                      warning  (2),
                      minor    (3),
                      major    (4),
                      critical (5)
                    }

AlarmLevelString ::= TEXTUAL-CONVENTION
    STATUS       current
    DESCRIPTION
            "Alarm severity level- possible values are CLEARED, WARNING, MINOR, MAJOR, CRITICAL"
    SYNTAX       OCTET STRING (SIZE (0..24))

END

AFFIRMED-USERACCESS-MIB DEFINITIONS ::= BEGIN
IMPORTS
    MODULE-IDENTITY, OBJECT-TYPE,
    Integer32, Unsigned32, Counter32, Counter64,
    Gauge32, IpAddress
        FROM SNMPv2-SMI
    TEXTUAL-CONVENTION, RowStatus, DateAndTime,
    TruthValue
        FROM SNMPv2-TC
;

affirmedUserAccessMIB MODULE-IDENTITY
    ORGANIZATION "Affirmed Networks, Inc."
    CONTACT-INFO "Affirmed Networks, Inc. 35 Nagog Park, Acton, MA, USA"
    DESCRIPTION ""
    ::= { 1 3 6 1 4 1 37963 10 19 }

String ::= TEXTUAL-CONVENTION
    DISPLAY-HINT "1t"
    STATUS      current
    DESCRIPTION "xs:string"
    SYNTAX      OCTET STRING

affirmedUserAccess OBJECT IDENTIFIER ::= { affirmedUserAccessMIB 1 }

affirmedUserAccessAaa OBJECT IDENTIFIER ::= { affirmedUserAccess 1 }

affirmedUserAccessAaaTacacsPlus OBJECT IDENTIFIER ::= { affirmedUserAccessAaa 1 }

affirmedUserAccessAaaTacacsPlusStatusTable OBJECT-TYPE
    SYNTAX      SEQUENCE OF AffirmedUserAccessAaaTacacsPlusStatusEntry
    MAX-ACCESS  not-accessible
    STATUS      current
    DESCRIPTION ""
    ::= { affirmedUserAccessAaaTacacsPlus 1 }

affirmedUserAccessAaaTacacsPlusStatusEntry OBJECT-TYPE
    SYNTAX      AffirmedUserAccessAaaTacacsPlusStatusEntry
    MAX-ACCESS  not-accessible
    STATUS      current
    DESCRIPTION ""
    INDEX { affirmedUserAccessAaaTacacsPlusStatusPriority }
        ::= { affirmedUserAccessAaaTacacsPlusStatusTable 1 }

AffirmedUserAccessAaaTacacsPlusStatusEntry ::=
    SEQUENCE {
        affirmedUserAccessAaaTacacsPlusStatusPriority Unsigned32,
        affirmedUserAccessAaaTacacsPlusStatusServer String,
        affirmedUserAccessAaaTacacsPlusStatusOperState INTEGER,
        affirmedUserAccessAaaTacacsPlusStatusConsecFailCnt Unsigned32,
        affirmedUserAccessAaaTacacsPlusStatusCredFailCnt Unsigned32,
        affirmedUserAccessAaaTacacsPlusStatusLastFail String,
        affirmedUserAccessAaaTacacsPlusStatusNextServerRetry String
    }

affirmedUserAccessAaaTacacsPlusStatusPriority OBJECT-TYPE
    SYNTAX      Unsigned32
    MAX-ACCESS  not-accessible
    STATUS      current
    DESCRIPTION "assigned priority value"
    ::= { affirmedUserAccessAaaTacacsPlusStatusEntry 1 }

affirmedUserAccessAaaTacacsPlusStatusServer OBJECT-TYPE
    SYNTAX      String
    MAX-ACCESS  read-only
    STATUS      current
    DESCRIPTION "TACACS+ server IP"
    ::= { affirmedUserAccessAaaTacacsPlusStatusEntry 2 }

affirmedUserAccessAaaTacacsPlusStatusOperState OBJECT-TYPE
    SYNTAX      INTEGER {up(101),down(102)}
    MAX-ACCESS  read-only
    STATUS      current
    DESCRIPTION "server operational state"
    ::= { affirmedUserAccessAaaTacacsPlusStatusEntry 3 }

affirmedUserAccessAaaTacacsPlusStatusConsecFailCnt OBJECT-TYPE
    SYNTAX      Unsigned32
    MAX-ACCESS  read-only
    STATUS      current
    DESCRIPTION "consecutive failure count"
    ::= { affirmedUserAccessAaaTacacsPlusStatusEntry 4 }

affirmedUserAccessAaaTacacsPlusStatusCredFailCnt OBJECT-TYPE
    SYNTAX      Unsigned32
    MAX-ACCESS  read-only
    STATUS      current
    DESCRIPTION "total credentail failures"
    ::= { affirmedUserAccessAaaTacacsPlusStatusEntry 5 }

affirmedUserAccessAaaTacacsPlusStatusLastFail OBJECT-TYPE
    SYNTAX      String
    MAX-ACCESS  read-only
    STATUS      current
    DESCRIPTION "time of latest failure"
    ::= { affirmedUserAccessAaaTacacsPlusStatusEntry 6 }

affirmedUserAccessAaaTacacsPlusStatusNextServerRetry OBJECT-TYPE
    SYNTAX      String
    MAX-ACCESS  read-only
    STATUS      current
    DESCRIPTION "earliest time to retry server"
    ::= { affirmedUserAccessAaaTacacsPlusStatusEntry 7 }

END

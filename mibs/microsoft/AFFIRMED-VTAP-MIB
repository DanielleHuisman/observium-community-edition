AFFIRMED-VTAP-MIB DEFINITIONS ::= BEGIN
IMPORTS
    MODULE-IDENTITY, OBJECT-TYPE,
    Integer32, Unsigned32, Counter32, Counter64,
    Gauge32, IpAddress
        FROM SNMPv2-SMI
    TEXTUAL-CONVENTION, RowStatus, DateAndTime,
    TruthValue
        FROM SNMPv2-TC
;

affirmedVtapMIB MODULE-IDENTITY
    ORGANIZATION "Affirmed Networks, Inc."
    CONTACT-INFO "Affirmed Networks, Inc. 35 Nagog Park, Acton, MA, USA"
    DESCRIPTION ""
    ::= { 1 3 6 1 4 1 37963 10 23 }

ConfdString ::= TEXTUAL-CONVENTION
    DISPLAY-HINT "1t"
    STATUS      current
    DESCRIPTION "xs: and confd: types mapped to strings"
    SYNTAX      OCTET STRING

String ::= TEXTUAL-CONVENTION
    DISPLAY-HINT "1t"
    STATUS      current
    DESCRIPTION "xs:string"
    SYNTAX      OCTET STRING

affirmedVtap OBJECT IDENTIFIER ::= { affirmedVtapMIB 1 }

affirmedVtapSinkTable OBJECT-TYPE
    SYNTAX      SEQUENCE OF AffirmedVtapSinkEntry
    MAX-ACCESS  not-accessible
    STATUS      current
    DESCRIPTION ""
    ::= { affirmedVtap 1 }

affirmedVtapSinkEntry OBJECT-TYPE
    SYNTAX      AffirmedVtapSinkEntry
    MAX-ACCESS  not-accessible
    STATUS      current
    DESCRIPTION ""
    INDEX { affirmedVtapSinkName }
        ::= { affirmedVtapSinkTable 1 }

AffirmedVtapSinkEntry ::=
    SEQUENCE {
        affirmedVtapSinkName String,
        affirmedVtapSinkRowstatus RowStatus
    }

affirmedVtapSinkName OBJECT-TYPE
    SYNTAX      String
    MAX-ACCESS  not-accessible
    STATUS      current
    DESCRIPTION ""
    ::= { affirmedVtapSinkEntry 1 }

affirmedVtapSinkRowstatus OBJECT-TYPE
    SYNTAX      RowStatus
    MAX-ACCESS  read-create
    STATUS      current
    DESCRIPTION ""
    ::= { affirmedVtapSinkEntry 2 }

affirmedVtapShowVtapSinkDetailTable OBJECT-TYPE
    SYNTAX      SEQUENCE OF AffirmedVtapShowVtapSinkDetailEntry
    MAX-ACCESS  not-accessible
    STATUS      current
    DESCRIPTION ""
    ::= { affirmedVtap 3 }

affirmedVtapShowVtapSinkDetailEntry OBJECT-TYPE
    SYNTAX      AffirmedVtapShowVtapSinkDetailEntry
    MAX-ACCESS  not-accessible
    STATUS      current
    DESCRIPTION ""
    INDEX { affirmedVtapShowVtapSinkDetailVtapsinkname }
        ::= { affirmedVtapShowVtapSinkDetailTable 1 }

AffirmedVtapShowVtapSinkDetailEntry ::=
    SEQUENCE {
        affirmedVtapShowVtapSinkDetailVtapsinkname String,
        affirmedVtapShowVtapSinkDetailNumIngressPackets ConfdString,
        affirmedVtapShowVtapSinkDetailNumIngressBytes ConfdString,
        affirmedVtapShowVtapSinkDetailNumEgressPackets ConfdString,
        affirmedVtapShowVtapSinkDetailNumEgressBytes ConfdString,
        affirmedVtapShowVtapSinkDetailNumIngressErrPackets ConfdString,
        affirmedVtapShowVtapSinkDetailNumIngressErrorBytes ConfdString,
        affirmedVtapShowVtapSinkDetailNumEgressErrPackets ConfdString,
        affirmedVtapShowVtapSinkDetailNumEgressErrBytes ConfdString
    }

affirmedVtapShowVtapSinkDetailVtapsinkname OBJECT-TYPE
    SYNTAX      String
    MAX-ACCESS  not-accessible
    STATUS      current
    DESCRIPTION ""
    ::= { affirmedVtapShowVtapSinkDetailEntry 1 }

affirmedVtapShowVtapSinkDetailNumIngressPackets OBJECT-TYPE
    SYNTAX      ConfdString
    MAX-ACCESS  read-only
    STATUS      current
    DESCRIPTION ""
    ::= { affirmedVtapShowVtapSinkDetailEntry 2 }

affirmedVtapShowVtapSinkDetailNumIngressBytes OBJECT-TYPE
    SYNTAX      ConfdString
    MAX-ACCESS  read-only
    STATUS      current
    DESCRIPTION ""
    ::= { affirmedVtapShowVtapSinkDetailEntry 3 }

affirmedVtapShowVtapSinkDetailNumEgressPackets OBJECT-TYPE
    SYNTAX      ConfdString
    MAX-ACCESS  read-only
    STATUS      current
    DESCRIPTION ""
    ::= { affirmedVtapShowVtapSinkDetailEntry 4 }

affirmedVtapShowVtapSinkDetailNumEgressBytes OBJECT-TYPE
    SYNTAX      ConfdString
    MAX-ACCESS  read-only
    STATUS      current
    DESCRIPTION ""
    ::= { affirmedVtapShowVtapSinkDetailEntry 5 }

affirmedVtapShowVtapSinkDetailNumIngressErrPackets OBJECT-TYPE
    SYNTAX      ConfdString
    MAX-ACCESS  read-only
    STATUS      current
    DESCRIPTION ""
    ::= { affirmedVtapShowVtapSinkDetailEntry 6 }

affirmedVtapShowVtapSinkDetailNumIngressErrorBytes OBJECT-TYPE
    SYNTAX      ConfdString
    MAX-ACCESS  read-only
    STATUS      current
    DESCRIPTION ""
    ::= { affirmedVtapShowVtapSinkDetailEntry 7 }

affirmedVtapShowVtapSinkDetailNumEgressErrPackets OBJECT-TYPE
    SYNTAX      ConfdString
    MAX-ACCESS  read-only
    STATUS      current
    DESCRIPTION ""
    ::= { affirmedVtapShowVtapSinkDetailEntry 8 }

affirmedVtapShowVtapSinkDetailNumEgressErrBytes OBJECT-TYPE
    SYNTAX      ConfdString
    MAX-ACCESS  read-only
    STATUS      current
    DESCRIPTION ""
    ::= { affirmedVtapShowVtapSinkDetailEntry 9 }

affirmedVtapShowVtapSubscriberTapDetailTable OBJECT-TYPE
    SYNTAX      SEQUENCE OF AffirmedVtapShowVtapSubscriberTapDetailEntry
    MAX-ACCESS  not-accessible
    STATUS      current
    DESCRIPTION ""
    ::= { affirmedVtap 2 }

affirmedVtapShowVtapSubscriberTapDetailEntry OBJECT-TYPE
    SYNTAX      AffirmedVtapShowVtapSubscriberTapDetailEntry
    MAX-ACCESS  not-accessible
    STATUS      current
    DESCRIPTION ""
    INDEX { affirmedVtapShowVtapSubscriberTapDetailVtapsubscribertapname }
        ::= { affirmedVtapShowVtapSubscriberTapDetailTable 1 }

AffirmedVtapShowVtapSubscriberTapDetailEntry ::=
    SEQUENCE {
        affirmedVtapShowVtapSubscriberTapDetailVtapsubscribertapname String,
        affirmedVtapShowVtapSubscriberTapDetailNumIngressPackets ConfdString,
        affirmedVtapShowVtapSubscriberTapDetailNumIngressBytes ConfdString,
        affirmedVtapShowVtapSubscriberTapDetailNumEgressPackets ConfdString,
        affirmedVtapShowVtapSubscriberTapDetailNumEgressBytes ConfdString,
        affirmedVtapShowVtapSubscriberTapDetailNumIngressErrPackets ConfdString,
        affirmedVtapShowVtapSubscriberTapDetailNumIngressErrBytes ConfdString,
        affirmedVtapShowVtapSubscriberTapDetailNumEgressErrPackets ConfdString,
        affirmedVtapShowVtapSubscriberTapDetailNumEgressErrBytes ConfdString
    }

affirmedVtapShowVtapSubscriberTapDetailVtapsubscribertapname OBJECT-TYPE
    SYNTAX      String
    MAX-ACCESS  not-accessible
    STATUS      current
    DESCRIPTION ""
    ::= { affirmedVtapShowVtapSubscriberTapDetailEntry 1 }

affirmedVtapShowVtapSubscriberTapDetailNumIngressPackets OBJECT-TYPE
    SYNTAX      ConfdString
    MAX-ACCESS  read-only
    STATUS      current
    DESCRIPTION ""
    ::= { affirmedVtapShowVtapSubscriberTapDetailEntry 2 }

affirmedVtapShowVtapSubscriberTapDetailNumIngressBytes OBJECT-TYPE
    SYNTAX      ConfdString
    MAX-ACCESS  read-only
    STATUS      current
    DESCRIPTION ""
    ::= { affirmedVtapShowVtapSubscriberTapDetailEntry 3 }

affirmedVtapShowVtapSubscriberTapDetailNumEgressPackets OBJECT-TYPE
    SYNTAX      ConfdString
    MAX-ACCESS  read-only
    STATUS      current
    DESCRIPTION ""
    ::= { affirmedVtapShowVtapSubscriberTapDetailEntry 4 }

affirmedVtapShowVtapSubscriberTapDetailNumEgressBytes OBJECT-TYPE
    SYNTAX      ConfdString
    MAX-ACCESS  read-only
    STATUS      current
    DESCRIPTION ""
    ::= { affirmedVtapShowVtapSubscriberTapDetailEntry 5 }

affirmedVtapShowVtapSubscriberTapDetailNumIngressErrPackets OBJECT-TYPE
    SYNTAX      ConfdString
    MAX-ACCESS  read-only
    STATUS      current
    DESCRIPTION ""
    ::= { affirmedVtapShowVtapSubscriberTapDetailEntry 6 }

affirmedVtapShowVtapSubscriberTapDetailNumIngressErrBytes OBJECT-TYPE
    SYNTAX      ConfdString
    MAX-ACCESS  read-only
    STATUS      current
    DESCRIPTION ""
    ::= { affirmedVtapShowVtapSubscriberTapDetailEntry 7 }

affirmedVtapShowVtapSubscriberTapDetailNumEgressErrPackets OBJECT-TYPE
    SYNTAX      ConfdString
    MAX-ACCESS  read-only
    STATUS      current
    DESCRIPTION ""
    ::= { affirmedVtapShowVtapSubscriberTapDetailEntry 8 }

affirmedVtapShowVtapSubscriberTapDetailNumEgressErrBytes OBJECT-TYPE
    SYNTAX      ConfdString
    MAX-ACCESS  read-only
    STATUS      current
    DESCRIPTION ""
    ::= { affirmedVtapShowVtapSubscriberTapDetailEntry 9 }

affirmedVtapShowVtapSubscriberTapScheduleTable OBJECT-TYPE
    SYNTAX      SEQUENCE OF AffirmedVtapShowVtapSubscriberTapScheduleEntry
    MAX-ACCESS  not-accessible
    STATUS      current
    DESCRIPTION ""
    ::= { affirmedVtap 4 }

affirmedVtapShowVtapSubscriberTapScheduleEntry OBJECT-TYPE
    SYNTAX      AffirmedVtapShowVtapSubscriberTapScheduleEntry
    MAX-ACCESS  not-accessible
    STATUS      current
    DESCRIPTION ""
    INDEX { affirmedVtapShowVtapSubscriberTapScheduleVtapsubscribertapname }
        ::= { affirmedVtapShowVtapSubscriberTapScheduleTable 1 }

AffirmedVtapShowVtapSubscriberTapScheduleEntry ::=
    SEQUENCE {
        affirmedVtapShowVtapSubscriberTapScheduleVtapsubscribertapname String,
        affirmedVtapShowVtapSubscriberTapScheduleStartTime String,
        affirmedVtapShowVtapSubscriberTapScheduleEndTime String,
        affirmedVtapShowVtapSubscriberTapScheduleDuration ConfdString,
        affirmedVtapShowVtapSubscriberTapScheduleVtapState String
    }

affirmedVtapShowVtapSubscriberTapScheduleVtapsubscribertapname OBJECT-TYPE
    SYNTAX      String
    MAX-ACCESS  not-accessible
    STATUS      current
    DESCRIPTION ""
    ::= { affirmedVtapShowVtapSubscriberTapScheduleEntry 1 }

affirmedVtapShowVtapSubscriberTapScheduleStartTime OBJECT-TYPE
    SYNTAX      String
    MAX-ACCESS  read-only
    STATUS      current
    DESCRIPTION ""
    ::= { affirmedVtapShowVtapSubscriberTapScheduleEntry 2 }

affirmedVtapShowVtapSubscriberTapScheduleEndTime OBJECT-TYPE
    SYNTAX      String
    MAX-ACCESS  read-only
    STATUS      current
    DESCRIPTION ""
    ::= { affirmedVtapShowVtapSubscriberTapScheduleEntry 3 }

affirmedVtapShowVtapSubscriberTapScheduleDuration OBJECT-TYPE
    SYNTAX      ConfdString
    MAX-ACCESS  read-only
    STATUS      current
    DESCRIPTION ""
    ::= { affirmedVtapShowVtapSubscriberTapScheduleEntry 4 }

affirmedVtapShowVtapSubscriberTapScheduleVtapState OBJECT-TYPE
    SYNTAX      String
    MAX-ACCESS  read-only
    STATUS      current
    DESCRIPTION ""
    ::= { affirmedVtapShowVtapSubscriberTapScheduleEntry 5 }

END

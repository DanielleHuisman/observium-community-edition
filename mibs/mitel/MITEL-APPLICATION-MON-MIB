-- Copyright 2002 MITEL Networks Corporation
-- All rights reserved.
-- This MITEL SNMP Management Information Base Specification
-- (Specification) embodies MITEL's confidential and
-- proprietary intellectual property. MITEL retains all
-- title and ownership in the Specification, including any
-- revisions.

-- This Specification is supplied "AS IS", and MITEL makes
-- no warranty, either express or implied, as to the use,
-- operation, condition, or performance of the Specification.


MITEL-APPLICATION-MON-MIB
	DEFINITIONS ::= BEGIN

IMPORTS
	MODULE-IDENTITY, OBJECT-TYPE, enterprises,
    Counter32, Integer32, NOTIFICATION-TYPE
        FROM SNMPv2-SMI
    NOTIFICATION-GROUP
    	FROM SNMPv2-CONF
    DisplayString
        FROM SNMPv2-TC;

mitelApplicationMon 	MODULE-IDENTITY
       LAST-UPDATED      "200204020000Z"
       ORGANIZATION      "MITEL Networks Corporation"
       CONTACT-INFO      "Standards Group,
                          Postal:    MITEL Corporation
                          350 Legget Drive, PO Box 13089
                          Kanata, Ontario
                          Canada  K2K 1X3
                          Tel: +1 613 592 2122
                          Fax: +1 613 592 4784
                          E-mail: std@mitel.com"
       DESCRIPTION       "The Mitel Application Monitor MIB."
       REVISION          "200303240136Z"
       	DESCRIPTION      "Convert to SMIv2"
       REVISION          "200204020000Z"
       	DESCRIPTION      "Mitel Application Monitor MIB version 1.0"
::= { mitelProprietary 11 }

mitel			   OBJECT IDENTIFIER ::= { enterprises 1027}
mitelProprietary 	   OBJECT IDENTIFIER ::= { mitel 4}


-- TRAPS
mitelIdentification 	  OBJECT IDENTIFIER ::= { mitel 1}
mitelIdCallServers 	  OBJECT IDENTIFIER ::= { mitelIdentification 2}
mitelIdCsIpera1000 	  OBJECT IDENTIFIER ::= { mitelIdCallServers 4}

	--************************************
	-- The mitelApplicationMon subtree...
	--************************************

DateAndTime ::= OCTET STRING(SIZE(8 | 11))

-- the Mitel Task Monitor Fault Table

    mitelApplicationMonFaultTable     OBJECT-TYPE
        SYNTAX  SEQUENCE OF MitelApplicationMonFaultEntry
	  	MAX-ACCESS  not-accessible
        STATUS  current
        DESCRIPTION
            "The Task Monitor Fault table."
        ::= { mitelApplicationMon 1 }

    mitelApplicationMonFaultEntry OBJECT-TYPE
             SYNTAX MitelApplicationMonFaultEntry
             MAX-ACCESS  not-accessible
             STATUS  current
             DESCRIPTION
                "An entry in the mitelApplicationMonFaultTable."
             INDEX   { mitelApplicationMonFaultTblIndex }
            ::= { mitelApplicationMonFaultTable 1 }

    MitelApplicationMonFaultEntry ::=
         SEQUENCE {
		 mitelApplicationMonFaultTblIndex	Integer32,
             mitelApplicationMonFaultId		INTEGER,
		 mitelApplicationMonFaultStatus	INTEGER,
 		 mitelApplicationMonFaultOccur	Counter32,
		 mitelApplicationMonFaultDateTime	DateAndTime,
		 mitelApplicationMonFaultDescr	DisplayString
	   }

    mitelApplicationMonFaultTblIndex OBJECT-TYPE
        SYNTAX           Integer32
        MAX-ACCESS           read-only
        STATUS           current
        DESCRIPTION
		"The index of the fault table."
        ::= { mitelApplicationMonFaultEntry 1 }

    mitelApplicationMonFaultId	OBJECT-TYPE
        SYNTAX INTEGER {
			appMonTaskCrashed(1)
	 	   }
        MAX-ACCESS  read-only
        STATUS  current
        DESCRIPTION
            "The mitelApplicationMonFaultId indicates the id of the fault."
        ::= { mitelApplicationMonFaultEntry 2 }

    mitelApplicationMonFaultStatus		OBJECT-TYPE
        SYNTAX INTEGER {
			set(1),
			clear(2),
			message(3)
	 	   }
        MAX-ACCESS  read-only
        STATUS  current
        DESCRIPTION
            "The mitelApplicationMonFaultStatus indicates
		 whether the fault is set or cleared or transient."
        ::= { mitelApplicationMonFaultEntry 3 }

    mitelApplicationMonFaultOccur		OBJECT-TYPE
        SYNTAX  Counter32
        MAX-ACCESS  read-only
        STATUS  current
        DESCRIPTION
            "The mitelApplicationMonFaultOccur indicates the occurence of
		 the fault since the last system restart"
            ::= { mitelApplicationMonFaultEntry 4 }

    mitelApplicationMonFaultDateTime	OBJECT-TYPE
        SYNTAX DateAndTime
        MAX-ACCESS  read-only
        STATUS  current
        DESCRIPTION
            "The mitelApplicationMonFaultOccur indicates the datetime of
		 when the fault was detected."
            ::= { mitelApplicationMonFaultEntry 5 }

   mitelApplicationMonFaultDescr		OBJECT-TYPE
        SYNTAX DisplayString
        MAX-ACCESS  read-only
        STATUS  current
        DESCRIPTION
            "The mitelApplicationMonFaultDescr contains a brief description
		of the fault."
            ::= { mitelApplicationMonFaultEntry 6 }


mitelIpera1000Notifications NOTIFICATION-GROUP
    NOTIFICATIONS	{ mitelAppMonTaskCrashedNotif }
    STATUS            current
    DESCRIPTION       "Call Server Ipera 1000 Notifications."
    ::= { mitelIdCsIpera1000 0 }

mitelAppMonTaskCrashedNotif NOTIFICATION-TYPE
	OBJECTS{
			mitelApplicationMonFaultStatus,
			mitelApplicationMonFaultDateTime,
			mitelApplicationMonFaultDescr
			}
	STATUS current
	DESCRIPTION
		"The mitelAppMonTaskCrashedNotif trap indicates
		 that a task has crashed and a system reboot is imminent."
	::= { mitelIpera1000Notifications 411 }


 END -- MITEL-APPLICATION-MON-MIB

-- Copyright 2005 MITEL Corporation
-- All rights reserved.
-- This MITEL SNMP Management Information Base Specification
-- (Specification) embodies MITEL's confidential and
-- proprietary intellectual property. MITEL retains all
-- title and ownership in the Specification, including any
-- revisions.

-- This Specification is supplied "AS IS", and MITEL makes
-- no warranty, either express or implied, as to the use,
-- operation, condition, or performance of the Specification.

MITEL-DHCP-MIB
DEFINITIONS ::= BEGIN
IMPORTS
	MODULE-IDENTITY, OBJECT-TYPE, enterprises,
    Integer32, IpAddress, TimeTicks, NOTIFICATION-TYPE
        FROM SNMPv2-SMI
    NOTIFICATION-GROUP
    	FROM SNMPv2-CONF
    DisplayString, RowStatus, TEXTUAL-CONVENTION
        FROM SNMPv2-TC;

mitelRouterDhcpGroup MODULE-IDENTITY
    LAST-UPDATED      "200511071200Z"
    ORGANIZATION      "MITEL Corporation"
    CONTACT-INFO      "Standards Group,
                       Postal:    MITEL Corporation
                       350 Legget Drive, PO Box 13089
                       Kanata, Ontario
                       Canada  K2K 1X3
                       Tel: +1 613 592 2122
                       Fax: +1 613 592 4784
                       E-mail: std@mitel.com"
    DESCRIPTION       "The MITEL DHCP MIB module."
    REVISION          "200511071200Z"
    	DESCRIPTION   "Addition of vendor-specific-information
    	              Table"
    REVISION          "200303211231Z"
    	DESCRIPTION   "Update to SMIv2"
    REVISION          "199903010000Z"
        DESCRIPTION   "DHCP MIB Version 1.0"
::= { mitelIpNetRouter 3}

MitelDhcpServerProtocol ::=       TEXTUAL-CONVENTION
        STATUS            current
        DESCRIPTION       "The MITEL-defined DHCP Protocol."
        SYNTAX            INTEGER {
                                    none(1),
                                    bootp(2),
                                    dhcp(3),
                                    bootp-or-dhcp(4)
                                }

MitelDhcpServerOptionList ::=       TEXTUAL-CONVENTION
        STATUS            current
        DESCRIPTION       "The MITEL-defined DHCP Options."
        SYNTAX            INTEGER {
                                    time-offset(2),
                                    default-router(3),
                                    time-server(4),
                                    name-server(5),  -- not DNS !!
                                    dns-server(6),
                                    log-server(7),
                                    cookie-server(8),
                                    lpr-server(9),
                                    impress-server(10),
                                    resource-location-server(11),
                                    host-name(12),
                                    boot-file-size(13),
                                    merit-dump-file-name(14),
                                    domain-name(15),
                                    swap-server(16),
                                    root-path(17),
                                    extension-path(18),
                                    ip-forwarding(19),
                                    non-local-source-routing(20),
                                    policy-filter(21),
                                    max-datagram-reassembly(22),
                                    default-ip-time-to-live(23),
                                    path-MTU-aging-timeout(24),
                                    path-MTU-plateau-table(25),
                                    interface-MTU-value(26),
                                    all-subnets-are-local(27),
                                    broadcast-address(28),
                                    perform-mask-discovery(29),
                                    mask-supplier(30),
                                    perform-router-discovery(31),
                                    router-solicitation-address(32),
                                    static-route(33),
                                    trailer-encapsulation(34),
                                    arp-cache-timeout(35),
                                    ethernet-encapsulation(36),
                                    tcp-default-ttl(37),
                                    tcp-keepalive-interval(38),
                                    tcp-keepalive-garbage(39),
                                    nis-domain-name(40),
                                    nis-server(41),
                                    ntp-server(42),
                                    vendor-specific-information(43), 
                                    netbios-ip-name-server(44),
                                    netbios-ip-dgram-distrib-server(45),
                                    netbios-ip-node-type(46),
                                    netbios-ip-scope(47),
                                    x-window-font-server(48),
                                    x-window-display-manager(49),
                                    nis-plus-domain(64),
                                    nis-plus-server(65),
                                    tftp-server-name(66),
                                    bootfile-name(67),
                                    mobile-ip-home-agent(68),
                                    smtp-server(69),
                                    pop3-server(70),
                                    nntp-server(71),
                                    www-server(72),
                                    finger-server(73),
                                    irc-server(74),
                                    streettalk-server(75),
                                    streettalk-directory-assistance-server(76),

                                    -- the following values are not
                                    -- valid for mitelDhcpServerOptionTable entries

                                    requested-ip(50),
                                    lease-time(51),
                                    option-overload(52),
                                    message-type(53),
                                    server-identifier(54),
                                    parameter-request-list(55),
                                    message(56),
                                    max-dhcp-message-size(57),
                                    renewal-time-value-t1(58),
                                    rebinding-time-value-t2(59),
                                    vendor-class-identifier(60),
                                    client-identifier(61),
                                    subnet-mask(1)
                                }

mitel			   OBJECT IDENTIFIER ::= { enterprises 1027}
mitelProprietary 	   OBJECT IDENTIFIER ::= { mitel 4}
mitelPropIpNetworking      OBJECT IDENTIFIER ::= { mitelProprietary 8 }
mitelIpNetRouter           OBJECT IDENTIFIER ::= { mitelPropIpNetworking 1 }

-- NOTIFICATIONS
mitelIdentification 	  OBJECT IDENTIFIER ::= { mitel 1}
mitelIdCallServers 	  OBJECT IDENTIFIER ::= { mitelIdentification 2}
mitelIdCsIpera1000 	  OBJECT IDENTIFIER ::= { mitelIdCallServers 4}

--
--
--        DHCP GROUP OBJECTS
--        ================
--
    mitelDhcpRelayAgentEnable OBJECT-TYPE
        SYNTAX  INTEGER {
                   enabled(1),
                   disabled(2)
                }
        MAX-ACCESS  read-write
        STATUS  current
        DESCRIPTION
                "Configures the router to enable the DHCP/BOOTP relay
        agent. The default is disabled."
        DEFVAL { 2 }
        ::= { mitelRouterDhcpGroup 1 }


    mitelDhcpRelayAgentMaxHops OBJECT-TYPE
        SYNTAX  INTEGER (1..16)
        MAX-ACCESS  read-write
        STATUS  current
        DESCRIPTION
                "This object determines the maximum allowed value the hops
                field of the received DHCP/BOOTP packet can have. Packets
        		with higher values will be rejected."
        ::= { mitelRouterDhcpGroup 2 }


    mitelDhcpRelayAgentBroadcast OBJECT-TYPE
        SYNTAX  INTEGER {
                   enabled(1),
                   disabled(2)
                }
        MAX-ACCESS  read-write
        STATUS  current
        DESCRIPTION
                "Determines wether or not the DHCP Relay Agent
        should retransmit received BOOTP requests using
        local broadcast on each IP interface.
        The default is disabled."
        ::= { mitelRouterDhcpGroup 4 }

    -- This object is the fourth object in that group.
    -- The third one is the list of configured DHCP servers
    -- known to the BOOTP relay agent. (defined further)

--
--
--
--      The DHCP/BOOTP Server Table.
--

   	 	mitelDhcpRelayAgentServerTable OBJECT-TYPE
       		SYNTAX  SEQUENCE OF MitelDhcpRelayAgentServerEntry
        	MAX-ACCESS  not-accessible
        	STATUS  current
        	DESCRIPTION
                "This table is used to display and configure the list
                of servers to which the relay agent will relay DHCP/BOOTP
                REQUEST packets."
        ::= { mitelRouterDhcpGroup 3 }


        mitelDhcpRelayAgentServerEntry OBJECT-TYPE
            SYNTAX  MitelDhcpRelayAgentServerEntry
            MAX-ACCESS  not-accessible
            STATUS  current
            DESCRIPTION
                    "Each entry in this table contains information on a
                    DHCP/BOOTP server."
            INDEX   { mitelDhcpRelayAgentServerAddr }
            ::= { mitelDhcpRelayAgentServerTable 1 }


        MitelDhcpRelayAgentServerEntry ::=
            SEQUENCE {
               mitelDhcpRelayAgentServerAddr
                  IpAddress,
               mitelDhcpRelayAgentServerName
                  DisplayString,
               mitelDhcpRelayAgentServerStatus
                  RowStatus
            }


        mitelDhcpRelayAgentServerAddr OBJECT-TYPE
            SYNTAX  IpAddress
            MAX-ACCESS  read-write
            STATUS  current
            DESCRIPTION
                    "The IP address of the DHCP/BOOTP server."
            ::= { mitelDhcpRelayAgentServerEntry 1 }


        mitelDhcpRelayAgentServerName OBJECT-TYPE
            SYNTAX  DisplayString (SIZE (1..16))
            MAX-ACCESS  read-write
            STATUS  current
            DESCRIPTION
                    "This object indicates the associated name of
                    the DHCP/BOOTP server. It's main purpose is to
            be used as a reference name."
            ::= { mitelDhcpRelayAgentServerEntry 2 }


        mitelDhcpRelayAgentServerStatus OBJECT-TYPE
            SYNTAX  RowStatus
            MAX-ACCESS  read-create
            STATUS  current
            DESCRIPTION
                    "The current status of this entry."
            REFERENCE
                    "Textual Conventions for Version 2 of the
                    Simple Network Management Protocol (RFC 1443)."
            ::= { mitelDhcpRelayAgentServerEntry 3 }


--
--
--
--      The DHCP/BOOTP Server Table.
--




    mitelDhcpServerGroup OBJECT IDENTIFIER
        ::= { mitelRouterDhcpGroup 5 }


    mitelDhcpServerGeneralGroup OBJECT IDENTIFIER
        ::= { mitelDhcpServerGroup 1 }

        mitelDhcpServerGeneralEnable OBJECT-TYPE
            SYNTAX  INTEGER {
                    enabled(1),
                    disabled(2),
		    		autoconfig(3)
                    }
            MAX-ACCESS  read-write
            STATUS  current
            DESCRIPTION
                "Configures the router to enable the DHCP/BOOTP server
                The default is disabled."
            ::= { mitelDhcpServerGeneralGroup 1 }

        mitelDhcpServerGeneralGateway OBJECT-TYPE
            SYNTAX INTEGER {
                        this-if-first(1),
                        this-if-last(2),
                        not-this-if(3)
                    }
            MAX-ACCESS read-write
            STATUS current
            DESCRIPTION
                "Determines wether or not the local IP address associated
                with the interface on which the DHCP request was received
                should be advertised as a default gateway, and if yes with
                which priority."
            ::= { mitelDhcpServerGeneralGroup 2 }

        mitelDhcpServerGeneralRefDhcpServer OBJECT-TYPE
            SYNTAX IpAddress
            MAX-ACCESS read-write
            STATUS current
            DESCRIPTION
                "Indicates if unknown requested options values should
                be obtained from another DHCP server (if possible).
                Adequate values are:
                - a specific IP address of a known DHCP server
                - a IP address specifiying the interface on which
                  the DHCP server should be found (using broadcast).
                  i.e. 0.0.0.x where x is the interface logical ID.
                - 255.255.255.255: broadcast on all interfaces.
                - 0.0.0.0: the feature is disabled."
            ::= { mitelDhcpServerGeneralGroup 3 }

        mitelDhcpServerGeneralPingStatus OBJECT-TYPE
            SYNTAX INTEGER {
                        enable(1),
                        disable(2)
                        }
            MAX-ACCESS read-write
            STATUS current
            DESCRIPTION
	           "Enable/disable PING server functionality when passing out leases."
            ::= { mitelDhcpServerGeneralGroup 4 }

--
--
--      The DHCP IP Subnet configuration table
--

    mitelDhcpServerSubnetTable OBJECT-TYPE
        SYNTAX  SEQUENCE OF MitelServerSubnetEntry
        MAX-ACCESS  not-accessible
        STATUS  current
        DESCRIPTION
                "This table is used to configure the group of IP addresses
                that can be handed out by the DHCP server."
        ::= { mitelDhcpServerGroup 2 }


        mitelDhcpServerSubnetEntry OBJECT-TYPE
            SYNTAX  MitelServerSubnetEntry
            MAX-ACCESS  not-accessible
            STATUS  current
            DESCRIPTION
                    "Each entry in this table contains information on a
                    subnet serverd by the DHCP server."
            INDEX   { mitelDhcpServerSubnetAddr, mitelDhcpServerSubnetSharedNet }
            ::= { mitelDhcpServerSubnetTable 1 }

        MitelServerSubnetEntry ::=
            SEQUENCE {
                mitelDhcpServerSubnetAddr
                    IpAddress,
                mitelDhcpServerSubnetSharedNet
                    IpAddress,
                mitelDhcpServerSubnetMask
                    IpAddress,
                mitelDhcpServerSubnetGateway
                    INTEGER,
                mitelDhcpServerSubnetName
                    DisplayString,
                mitelDhcpServerSubnetDeleteTree
                    INTEGER,
                mitelDhcpServerSubnetStatus
                    RowStatus
            }

        mitelDhcpServerSubnetAddr OBJECT-TYPE
            SYNTAX IpAddress
            MAX-ACCESS read-only
            STATUS current
            DESCRIPTION "The IP address of the subnet (key)."
            ::= { mitelDhcpServerSubnetEntry 1 }

        mitelDhcpServerSubnetSharedNet OBJECT-TYPE
            SYNTAX IpAddress
            MAX-ACCESS read-only
            STATUS current
            DESCRIPTION
                "The IP address of another subnet that is on the same shared
                media as this subnet. The address of the shared subnet MUST
                also be configured on this server. The address 0.0.0.0 should
                be used if this subnet is not shared. (key)"
            ::= { mitelDhcpServerSubnetEntry 2 }

        mitelDhcpServerSubnetMask OBJECT-TYPE
            SYNTAX IpAddress
            MAX-ACCESS read-write
            STATUS current
            DESCRIPTION "The subnet mask of the subnet."
            ::= { mitelDhcpServerSubnetEntry 3 }

        mitelDhcpServerSubnetGateway OBJECT-TYPE
            SYNTAX INTEGER {
                        this-if-first(1),
                        this-if-last(2),
                        not-this-if(3),
                        default(4)  -- as indicated in the general preference
                    }
            MAX-ACCESS read-write
            STATUS current
            DESCRIPTION
                "Indicate whether or not the IP address configured on
                the interface which received the DHCP request should be
                advertised as a default gateway. If yes, this also
                indicate the relative priority compared to additional
                gateways that might be configured (DHCP option 3)."
            ::= { mitelDhcpServerSubnetEntry 4 }

        mitelDhcpServerSubnetName OBJECT-TYPE
            SYNTAX DisplayString (SIZE (1..16))
            MAX-ACCESS read-write
            STATUS current
            DESCRIPTION
                "The name of the configured subnet (informational only)."
            ::= { mitelDhcpServerSubnetEntry 5 }

        mitelDhcpServerSubnetDeleteTree OBJECT-TYPE
            SYNTAX INTEGER {
                        enabled(1),
                        disabled(2)
                    }
            MAX-ACCESS read-write
            STATUS current
            DESCRIPTION
                    "If this flag is set to enable, when the object
                    is deleted, all the DHCP server configuration
                    objects that depend on it will be deleted at the
                    same time."
            ::= { mitelDhcpServerSubnetEntry 6 }

        mitelDhcpServerSubnetStatus OBJECT-TYPE
            SYNTAX RowStatus
            MAX-ACCESS read-create
            STATUS current
            DESCRIPTION
                    "The current status of this entry."
            REFERENCE
                    "Textual Conventions for Version 2 of the
                    Simple Network Management Protocol (RFC 1443)."
            ::= { mitelDhcpServerSubnetEntry 7 }

--
--
--
--      The DHCP IP address range configuration table
--

    mitelDhcpServerRangeTable OBJECT-TYPE
        SYNTAX SEQUENCE OF MitelDhcpServerRangeEntry
        MAX-ACCESS not-accessible
        STATUS current
        DESCRIPTION
            "A list of ranges that are configured on this server."
        ::= { mitelDhcpServerGroup 3 }


        mitelDhcpServerRangeEntry OBJECT-TYPE
            SYNTAX MitelDhcpServerRangeEntry
            MAX-ACCESS not-accessible
            STATUS current
            DESCRIPTION
                "A logical row in the mitelServerGrpRangeTblTable."
            INDEX { mitelDhcpServerRangeStart, mitelDhcpServerRangeEnd, mitelDhcpServerRangeSubnet}
            ::= { mitelDhcpServerRangeTable 1 }

        MitelDhcpServerRangeEntry ::=
            SEQUENCE {
                mitelDhcpServerRangeStart
                    IpAddress,
                mitelDhcpServerRangeEnd
                    IpAddress,
                mitelDhcpServerRangeSubnet
                    IpAddress,
                mitelDhcpServerRangeProtocol
                    MitelDhcpServerProtocol,
                mitelDhcpServerRangeGateway
                    INTEGER,
                mitelDhcpServerRangeLeaseTime
                    Integer32,
                mitelDhcpServerRangeName
                    DisplayString,
                mitelDhcpServerRangeMatchClassId
                    INTEGER,
                mitelDhcpServerRangeDeleteTree
                    INTEGER,
                mitelDhcpServerRangeStatus
                    RowStatus
            }

        mitelDhcpServerRangeStart OBJECT-TYPE
            SYNTAX IpAddress
            MAX-ACCESS read-only
            STATUS current
            DESCRIPTION
                "The IP address of the first address in the range (key)."
            ::= { mitelDhcpServerRangeEntry 1 }

        mitelDhcpServerRangeEnd OBJECT-TYPE
            SYNTAX IpAddress
            MAX-ACCESS read-only
            STATUS current
            DESCRIPTION
                "The IP address of the last address in the range."
            ::= { mitelDhcpServerRangeEntry 2 }

        mitelDhcpServerRangeSubnet OBJECT-TYPE
            SYNTAX IpAddress
            MAX-ACCESS read-only
            STATUS current
            DESCRIPTION
                "The IP address of the subnet which includes this range.
                This IP address is used to find the corresponding
                mitelDhcpServerSubnetEntry"
            ::= { mitelDhcpServerRangeEntry 3 }

        mitelDhcpServerRangeProtocol OBJECT-TYPE
            SYNTAX MitelDhcpServerProtocol
            MAX-ACCESS read-write
            STATUS current
            DESCRIPTION
                "How the addresses in that group should be assigned.
                none = the address are reserved by the administrator
                (do we need this ?)."
            ::= { mitelDhcpServerRangeEntry 4 }

        mitelDhcpServerRangeGateway OBJECT-TYPE
            SYNTAX INTEGER {
                        this-if-first(1),
                        this-if-last(2),
                        not-this-if(3),
                        default(4)  -- as indicated in the general preference
                    }
            MAX-ACCESS read-write
            STATUS current
            DESCRIPTION
                "Indicate whether or not the IP address configured on
                the interface which received the DHCP request should be
                advertised as a default gateway. If yes, this also
                indicate the relative priority compared to additional
                gateways that might be configured (DHCP option 3)."
            ::= { mitelDhcpServerRangeEntry 5 }

        mitelDhcpServerRangeLeaseTime OBJECT-TYPE
            SYNTAX Integer32
            MAX-ACCESS read-write
            STATUS current
            DESCRIPTION
                "The duration of the lease of IP addressed in this range in
                seconds.
                A value of 4294967295 (0xFFFFFFFF) means that the lease is
                permanent.
                A value of 0 (0x00000000) means that the address in that range
                can not be assigned."
            ::= { mitelDhcpServerRangeEntry 6 }

        mitelDhcpServerRangeName OBJECT-TYPE
            SYNTAX DisplayString (SIZE (1..16))
            MAX-ACCESS read-write
            STATUS current
            DESCRIPTION
                "The name of the configured range (informational only)."
            ::= { mitelDhcpServerRangeEntry 7 }

        mitelDhcpServerRangeMatchClassId OBJECT-TYPE
            SYNTAX INTEGER {
                        enabled(1),
                        disabled(2)
                    }
	    MAX-ACCESS read-write
            STATUS current
            DESCRIPTION
                    "If this flag is set to enable, IP addresses in
                    this range will only be assigned to clients
                    indicating a class ID identical to the range name."
            ::= { mitelDhcpServerRangeEntry 8 }

        mitelDhcpServerRangeDeleteTree OBJECT-TYPE
            SYNTAX INTEGER {
                        enabled(1),
                        disabled(2)
                    }
            MAX-ACCESS read-write
            STATUS current
            DESCRIPTION
                    "If this flag is set to enable, when the object
                    is deleted, all the DHCP server configuration
                    objects that depend on it will be deleted at the
                    same time."
            ::= { mitelDhcpServerRangeEntry 9 }

        mitelDhcpServerRangeStatus OBJECT-TYPE
            SYNTAX RowStatus
            MAX-ACCESS read-create
            STATUS current
            DESCRIPTION
                    "The current status of this entry."
            REFERENCE
                    "Textual Conventions for Version 2 of the
                    Simple Network Management Protocol (RFC 1443)."
            ::= { mitelDhcpServerRangeEntry 10 }


--
--
--
--      The DHCP static IP addresses table
--

    mitelDhcpServerStaticIpTable OBJECT-TYPE
        SYNTAX SEQUENCE OF MitelDhcpServerStaticIpEntry
        MAX-ACCESS not-accessible
        STATUS current
        DESCRIPTION
            "A list of the addresses that are statically configured."
        ::= { mitelDhcpServerGroup 4 }


        mitelDhcpServerStaticIpEntry OBJECT-TYPE
            SYNTAX MitelDhcpServerStaticIpEntry
            MAX-ACCESS not-accessible
            STATUS current
            DESCRIPTION
                "A logical row in the mitelDhcpServerStaticIpTable."
            INDEX { mitelDhcpServerStaticIpAddr, mitelDhcpServerStaticIpSubnet }
            ::= { mitelDhcpServerStaticIpTable 1 }

        MitelDhcpServerStaticIpEntry ::=
            SEQUENCE {
                mitelDhcpServerStaticIpAddr
                    IpAddress,
                mitelDhcpServerStaticIpSubnet
                    IpAddress,
                mitelDhcpServerStaticIpProtocol
                    MitelDhcpServerProtocol,
                mitelDhcpServerStaticIpGateway
                    INTEGER,
                mitelDhcpServerStaticIpMacAddress
                    OCTET STRING,
                mitelDhcpServerStaticIpClientId
                    OCTET STRING,
                mitelDhcpServerStaticIpName
                    DisplayString,
                mitelDhcpServerStaticIpDeleteTree
                    INTEGER,
                mitelDhcpServerStaticIpStatus
                    RowStatus
            }

        mitelDhcpServerStaticIpAddr OBJECT-TYPE
            SYNTAX IpAddress
            MAX-ACCESS read-only
            STATUS current
            DESCRIPTION
                "The IP address of the entry (key). This IP address
                has to be unique across the DHCP server configuration.
                It can not be duplicated in another mitelDhcpServerStaticIpEntry
                and it can not be part of a mitelDhcpServerRangeEntry."
            ::= { mitelDhcpServerStaticIpEntry 1 }

        mitelDhcpServerStaticIpSubnet OBJECT-TYPE
            SYNTAX IpAddress
            MAX-ACCESS read-only
            STATUS current
            DESCRIPTION
                "The IP address of the subnet which includes this IP address.
                This IP address is used to find the corresponding
                mitelDhcpServerSubnetEntry"
            ::= { mitelDhcpServerStaticIpEntry 2 }

        mitelDhcpServerStaticIpProtocol OBJECT-TYPE
            SYNTAX MitelDhcpServerProtocol
            MAX-ACCESS read-write
            STATUS current
            DESCRIPTION
                "How the addresses in that group should be assigned.
                none = the address are reserved by the administrator
                (do we need this ?)."
            ::= { mitelDhcpServerStaticIpEntry 3 }

        mitelDhcpServerStaticIpGateway OBJECT-TYPE
            SYNTAX INTEGER {
                        this-if-first(1),
                        this-if-last(2),
                        not-this-if(3),
                        default(4)  -- as indicated in the general preference
                    }
            MAX-ACCESS read-write
            STATUS current
            DESCRIPTION
                "Indicate whether or not the IP address configured on
                the interface which received the DHCP request should be
                advertised as a default gateway. If yes, this also
                indicate the relative priority compared to additional
                gateways that might be configured (DHCP option 3)."
            ::= { mitelDhcpServerStaticIpEntry 4 }

        mitelDhcpServerStaticIpMacAddress OBJECT-TYPE
            SYNTAX OCTET STRING (SIZE (1..255))
            MAX-ACCESS read-write
            STATUS current
            DESCRIPTION
                "The hardware type and hardware address of the client that has
                been assigned this IP address.  The first octet of this object
                contains the hardware type from the 'htype' field of the BOOTP
                packet and the remaining octets contain the hardware address
                from the 'chaddr' field of the BOOTP packet.

                Either the mitelDhcpServerStaticIpClientId or the
                mitelDhcpServerStaticIpMacAddress field has to have a valid
                value. If none of them are configured, then the IP address
                is just not assignable by this server."
            ::= { mitelDhcpServerStaticIpEntry 5 }

        mitelDhcpServerStaticIpClientId OBJECT-TYPE
            SYNTAX OCTET STRING (SIZE (0..255))
            MAX-ACCESS read-write
            STATUS current
            DESCRIPTION
                "The client-id of the client that has been assigned this lease.
                The client-id is the value specified in option 61 (client-id
                option) when the lease was assigned.  This object may be empty
                if the lease has not been previously assigned or if the client-
                id option was not specified when the lease was assigned.

                Either the mitelDhcpServerStaticIpClientId or the
                mitelDhcpServerStaticIpMacAddress field has to have a valid
                value. If none of them are configured, then the IP address
                is just not assignable by this server."
            ::= { mitelDhcpServerStaticIpEntry 6 }

        mitelDhcpServerStaticIpName OBJECT-TYPE
            SYNTAX DisplayString (SIZE (1..16))
            MAX-ACCESS read-write
            STATUS current
            DESCRIPTION
                "The name of the configured range (informational only)."
            ::= { mitelDhcpServerStaticIpEntry 7 }

        mitelDhcpServerStaticIpDeleteTree OBJECT-TYPE
            SYNTAX INTEGER {
                        enabled(1),
                        disabled(2)
                    }
            MAX-ACCESS read-write
            STATUS current
            DESCRIPTION
                    "If this flag is set to enable, when the object
                    is deleted, all the DHCP server configuration
                    objects that depend on it will be deleted at the
                    same time."
            ::= { mitelDhcpServerStaticIpEntry 8 }

        mitelDhcpServerStaticIpStatus OBJECT-TYPE
            SYNTAX RowStatus
            MAX-ACCESS read-create
            STATUS current
            DESCRIPTION
                    "The current status of this entry."
            REFERENCE
                    "Textual Conventions for Version 2 of the
                    Simple Network Management Protocol (RFC 1443)."
            ::= { mitelDhcpServerStaticIpEntry 9 }


--
--
--
--      The DHCP options configuration table
--

    mitelDhcpServerOptionTable OBJECT-TYPE
        SYNTAX SEQUENCE OF MitelDhcpServerOptionEntry
        MAX-ACCESS not-accessible
        STATUS current
        DESCRIPTION
            "This table contain list of options that will be sent to clients
            requesting IP addresses."
        ::= {mitelDhcpServerGroup 5}

        mitelDhcpServerOptionEntry OBJECT-TYPE
            SYNTAX MitelDhcpServerOptionEntry
            MAX-ACCESS not-accessible
            STATUS current
            DESCRIPTION
                "Each entry in this list contains information about a specific
                DHCP option."
            INDEX { mitelDhcpServerOptionAddr, mitelDhcpServerOptionNumber }
            ::= { mitelDhcpServerOptionTable 1 }

        MitelDhcpServerOptionEntry ::=
            SEQUENCE {
                mitelDhcpServerOptionAddr
                    IpAddress,
                mitelDhcpServerOptionNumber
                    MitelDhcpServerOptionList,
                mitelDhcpServerOptionDisplayFormat
                    INTEGER,
                mitelDhcpServerOptionValue
                    OCTET STRING,
                mitelDhcpServerOptionStatus
                    RowStatus
            }

        mitelDhcpServerOptionAddr OBJECT-TYPE
            SYNTAX IpAddress
            MAX-ACCESS read-only
            STATUS current
            DESCRIPTION
                "This IP address keys in either the mitelDhcpServerRangeTable
                or the mitelDhcpServerStaticIpTable or the mitelDhcpServerSubnetTable.
                It indicates the realm in which that particular option/value
                pair is to be handed out.
                If the IP address key is 0.0.0.0 this means that the option
                is valid for any of the range/static IP configured.
                In the case where the same option number is configured for
                different realms, the selection will go from the most specific
                to the most generic according to the following scheme:
                1. mitelDhcpGrpStaticIpTable or mitelDhcpServerRangeTable
                2. mitelDhcpServerSubnetTable
                3. global definition (i.e. mitelDhcpGrpOptionIp = 0.0.0.0)"
            ::= { mitelDhcpServerOptionEntry 1 }

        mitelDhcpServerOptionNumber OBJECT-TYPE
            SYNTAX MitelDhcpServerOptionList
            MAX-ACCESS read-only
            STATUS current
            DESCRIPTION
                "This is the option number as specified in RFC 2132:
                'DHCP Options and BOOTP Vendor Extensions'.
                Some of the options are not configurable that way (like
                subnet mask). The options that are not configurable are
                the ones that can be derived from the general configuration
                (from either the mitelDhcpServerSubnetTableor
                mitelDhcpServerRangeTable or mitelDhcpServerStaticIpTable) or
                that have a meaning only from the client to the server
                (such as the client ID (option 61)).
		Range: 1..254"
            ::= { mitelDhcpServerOptionEntry 2 }

        mitelDhcpServerOptionDisplayFormat OBJECT-TYPE
            SYNTAX INTEGER {
                        default(1),
                        ip-address(2),
                        ascii-string(3),
                        integer(4),
                        octet-string(5)
                    }
            MAX-ACCESS read-write
            STATUS current
            DESCRIPTION
                "This indicates how the value should be formated. This
                is informational only and may be ignored.
                If something else than default is specified, the system
                will attempt to display the value field according to
                the setting. Otherwise, it will try to establish the
                correct way to display it based on the option number."
            ::= { mitelDhcpServerOptionEntry 3 }

        mitelDhcpServerOptionValue OBJECT-TYPE
            SYNTAX OCTET STRING (SIZE (1..255))
            MAX-ACCESS read-write
            STATUS current
            DESCRIPTION
                "This contains the value of the option encoded as it will
                be sent in the DHCP packets."
            ::= { mitelDhcpServerOptionEntry 4 }

        mitelDhcpServerOptionStatus OBJECT-TYPE
            SYNTAX RowStatus
            MAX-ACCESS read-create
            STATUS current
            DESCRIPTION
                    "The current status of this entry."
            REFERENCE
                    "Textual Conventions for Version 2 of the
                    Simple Network Management Protocol (RFC 1443)."
            ::= { mitelDhcpServerOptionEntry 5 }


--
--
--
--      The DHCP assigned leases table
--

        mitelDhcpServerLeaseTable OBJECT-TYPE
            SYNTAX SEQUENCE OF MitelDhcpServerLeaseEntry
            MAX-ACCESS not-accessible
            STATUS current
            DESCRIPTION
                "This table contain a list of all the assigned leases and their
                current status."
            ::= {mitelDhcpServerGroup 6}

        mitelDhcpServerLeaseEntry OBJECT-TYPE
            SYNTAX MitelDhcpServerLeaseEntry
            MAX-ACCESS not-accessible
            STATUS current
            DESCRIPTION
                "Each entry in this list contains information about a specific
                lease."
            INDEX { mitelDhcpServerLeaseAddr }
            ::= { mitelDhcpServerLeaseTable 1 }

        MitelDhcpServerLeaseEntry ::=
            SEQUENCE {
                mitelDhcpServerLeaseAddr
                    IpAddress,
                mitelDhcpServerLeaseSubnet
                    IpAddress,
                mitelDhcpServerLeaseRange
                    IpAddress,
                mitelDhcpServerLeaseType
                    INTEGER,
                mitelDhcpServerLeaseEndTime
                    TimeTicks,
                mitelDhcpServerLeaseAllowedProtocol
                    INTEGER,
                mitelDhcpServerLeaseServedProtocol
                    INTEGER,
                mitelDhcpServerLeaseMacAddress
                    OCTET STRING,
                mitelDhcpServerLeaseClientId
                    OCTET STRING,
                mitelDhcpServerLeaseHostName
                    DisplayString,
                mitelDhcpServerLeaseDomainName
                    DisplayString,
                mitelDhcpServerLeaseServedTime
                    INTEGER,
                mitelDhcpServerLeaseStatus
                    RowStatus
            }

        mitelDhcpServerLeaseAddr OBJECT-TYPE
            SYNTAX IpAddress
            MAX-ACCESS read-only
            STATUS current
            DESCRIPTION
                "The IP address described in that lease."
            ::= { mitelDhcpServerLeaseEntry 1 }

        mitelDhcpServerLeaseSubnet OBJECT-TYPE
            SYNTAX IpAddress
            MAX-ACCESS read-only
            STATUS current
            DESCRIPTION
                "The IP address indicating the subnet to which the IP address
                belongs. That IP address can be used as a key in
                the mitelDhcpServerSubnetTable."
            ::= { mitelDhcpServerLeaseEntry 2 }

        mitelDhcpServerLeaseRange OBJECT-TYPE
            SYNTAX IpAddress
            MAX-ACCESS read-only
            STATUS current
            DESCRIPTION
                "A reference the the IP address Range from which this IP
                address has been assigned. This IP address can be used as
                a key for the mitelDhcpServerRangeTable."
            ::= { mitelDhcpServerLeaseEntry 3 }

        mitelDhcpServerLeaseType OBJECT-TYPE
            SYNTAX INTEGER {
                        static(1),
                        dynamic(2),
                        configuration-reserved(3),
                        server-reserved(4)
                    }
            MAX-ACCESS read-only
            STATUS current
            DESCRIPTION
                "The type of this address."
            ::= { mitelDhcpServerLeaseEntry 4 }

        mitelDhcpServerLeaseEndTime OBJECT-TYPE
            SYNTAX TimeTicks
            MAX-ACCESS read-only
            STATUS current
            DESCRIPTION
                "The value that sysUpTime will be when the lease expires.  A
                value of 4294967295 (i.e.: 0xFFFFFFFF) should be used for
                leases that have a lease time which is 'infinite' and for BOOTP
                leases."
            ::= { mitelDhcpServerLeaseEntry 5 }

        mitelDhcpServerLeaseAllowedProtocol OBJECT-TYPE
            SYNTAX INTEGER {
                        none(1),
                        bootp(2),
                        dhcp(3),
                        bootp-or-dhcp(4)
                    }
            MAX-ACCESS read-only
            STATUS current
            DESCRIPTION
                "The type of protocol that is allowed to be used to serve this
                address.  A type of none(1) indicates that the address is not
                available to be served (e.g.: a reserved address)."
            ::= { mitelDhcpServerLeaseEntry 6 }

        mitelDhcpServerLeaseServedProtocol OBJECT-TYPE
            SYNTAX INTEGER {
                        none(1),
                        bootp(2),
                        dhcp(3)
                    }
            MAX-ACCESS read-only
            STATUS current
            DESCRIPTION
                "The type of protocol that was used when this address was
                assigned.  This object will have the value of none(1) if the
                lease has not been served."
            ::= { mitelDhcpServerLeaseEntry 7 }

        mitelDhcpServerLeaseMacAddress OBJECT-TYPE
            SYNTAX OCTET STRING (SIZE (1..255))
            MAX-ACCESS read-only
            STATUS current
            DESCRIPTION
                "The hardware type and hardware address of the client that has
                been assigned this lease.  The first octet of this object
                contains the hardware type from the 'htype' field of the BOOTP
                packet and the remaining octets contain the hardware address
                from the 'chaddr' field of the BOOTP packet.  This object may
                be empty if the lease has not been previously served."
            ::= { mitelDhcpServerLeaseEntry 8 }

        mitelDhcpServerLeaseClientId OBJECT-TYPE
            SYNTAX OCTET STRING (SIZE (0..255))
            MAX-ACCESS read-only
            STATUS current
            DESCRIPTION
                "The client-id of the client that has been assigned this lease.
                The client-id is the value specified in option 61 (client-id
                option) when the lease was assigned.  This object may be empty
                if the lease has not been previously assigned or if the client-
                id option was not specified when the lease was assigned."
            ::= { mitelDhcpServerLeaseEntry 9 }

        mitelDhcpServerLeaseHostName OBJECT-TYPE
            SYNTAX DisplayString (SIZE (0..64))
            MAX-ACCESS read-only
            STATUS current
            DESCRIPTION
                "The host name the client is configured with or if no host name
                was configured then the host name that the client supplied when
                requesting an address."
            ::= { mitelDhcpServerLeaseEntry 10 }

        mitelDhcpServerLeaseDomainName OBJECT-TYPE
            SYNTAX DisplayString (SIZE (0..255))
                                    -- need correct maximum length
            MAX-ACCESS read-only
            STATUS current
            DESCRIPTION
                "The domain name assigned to the client."
            ::= { mitelDhcpServerLeaseEntry 11 }

        mitelDhcpServerLeaseServedTime OBJECT-TYPE
            SYNTAX INTEGER
            MAX-ACCESS read-only
            STATUS current
            DESCRIPTION
                "The system time at which this entry was created."
            ::= { mitelDhcpServerLeaseEntry 12 }

        mitelDhcpServerLeaseStatus OBJECT-TYPE
            SYNTAX RowStatus
            MAX-ACCESS read-create
            STATUS current
            DESCRIPTION
                    "The current status of this entry."
            REFERENCE
                    "Textual Conventions for Version 2 of the
                    Simple Network Management Protocol (RFC 1443)."
            ::= { mitelDhcpServerLeaseEntry 13 }

--
--  DHCP Stats Table
--

		mitelDhcpServerStatsGroup OBJECT IDENTIFIER
        	::= { mitelDhcpServerGroup 7 }

        mitelDhcpServerStatsNumServers OBJECT-TYPE
            SYNTAX INTEGER
            MAX-ACCESS read-only
            STATUS current
            DESCRIPTION
 		"This indicates the number of configured DHCP servers
		 which are used for the DHCP Relay Agent."
	    ::= { mitelDhcpServerStatsGroup 1 }

		mitelDhcpServerStatsConfSubnets OBJECT-TYPE
            SYNTAX INTEGER
            MAX-ACCESS read-only
            STATUS current
            DESCRIPTION
 		"This indicates the number of configured DHCP subnets."
	    ::= { mitelDhcpServerStatsGroup 2 }

		mitelDhcpServerStatsConfRanges OBJECT-TYPE
            SYNTAX INTEGER
            MAX-ACCESS read-only
            STATUS current
            DESCRIPTION
 		"This indicates the number of configured DHCP ranges."
	    ::= { mitelDhcpServerStatsGroup 3 }

		mitelDhcpServerStatsConfStatic OBJECT-TYPE
            SYNTAX INTEGER
            MAX-ACCESS read-only
            STATUS current
            DESCRIPTION
 		"This indicates the number of configured static IP addresses."
	    ::= { mitelDhcpServerStatsGroup 4 }

		mitelDhcpServerStatsConfOptions OBJECT-TYPE
            SYNTAX INTEGER
            MAX-ACCESS read-only
            STATUS current
            DESCRIPTION
 		"This indicates the number of configured DHCP Options."
	    ::= { mitelDhcpServerStatsGroup 5 }

		mitelDhcpServerStatsConfLeases OBJECT-TYPE
            SYNTAX INTEGER
            MAX-ACCESS read-only
            STATUS current
            DESCRIPTION
 		"This indicates the number of served leases."
	    ::= { mitelDhcpServerStatsGroup 6 }

--
--
--
--      The DHCP vendor-specific-information table
--

    mitelDhcpServerVendorInfoTable OBJECT-TYPE
        SYNTAX SEQUENCE OF MitelDhcpServerVendorInfoEntry
        MAX-ACCESS not-accessible
        STATUS current
        DESCRIPTION
            "This table contain list of vendor-specific-options 
            that will be sent to clients when requesting an IP addresses."
        ::= {mitelDhcpServerGroup 8}

        mitelDhcpServerVendorInfoEntry OBJECT-TYPE
            SYNTAX MitelDhcpServerVendorInfoEntry
            MAX-ACCESS not-accessible
            STATUS current
            DESCRIPTION
                "Each entry in this list contains information about a vendor 
                specific DHCP option."
            INDEX { mitelDhcpServerOptionAddr, mitelDhcpServerOptionNumber,
                    mitelDhcpServerVendorInfoID }
            ::= { mitelDhcpServerVendorInfoTable 1 }

        MitelDhcpServerVendorInfoEntry ::=
            SEQUENCE {
                mitelDhcpServerVendorInfoID
                    DisplayString,
                mitelDhcpServerVendorInfoName
                    DisplayString,
                mitelDhcpServerVendorInfoOptionDisplayFormat
                    INTEGER,
                mitelDhcpServerVenderInfoOptionValue
                    OCTET STRING,
                mitelDhcpServerVendorInfoStatus
                    RowStatus
            }

        mitelDhcpServerVendorInfoID OBJECT-TYPE
            SYNTAX DisplayString (SIZE (1..32))
            MAX-ACCESS read-only
            STATUS current
            DESCRIPTION
                "The unique vendor Identifier.  May or not make sense 
                to someone viewing the data."
            ::= { mitelDhcpServerVendorInfoEntry 1 }

        mitelDhcpServerVendorInfoName OBJECT-TYPE
            SYNTAX DisplayString (SIZE (1..32))
            MAX-ACCESS read-only
            STATUS current
            DESCRIPTION
                "The unique name of the vendor.  The suggestion is that
                this value be recognizable to someone viewing the data."
            ::= { mitelDhcpServerVendorInfoEntry 2 }

        mitelDhcpServerVendorInfoOptionDisplayFormat OBJECT-TYPE
            SYNTAX INTEGER {
                        default(1),
                        ip-address(2),
                        ascii-string(3),
                        integer(4),
                        octet-string(5)
                    }
            MAX-ACCESS read-write
            STATUS current
            DESCRIPTION
                "This indicates how the value should be formated. This
                is informational only and may be ignored.
                If something else than default is specified, the system
                will attempt to display the value field according to
                the setting. Otherwise, it will try to establish the
                correct way to display it based on the option number."
            ::= { mitelDhcpServerVendorInfoEntry 3 }

        mitelDhcpServerVendorInfoOptionValue OBJECT-TYPE
            SYNTAX OCTET STRING (SIZE (1..255))
            MAX-ACCESS read-write
            STATUS current
            DESCRIPTION
                "The options that the vendor, the vendor specified in
                VendorInfoID, would want to send to it's clients.  All
                content of this object would only make sense to the receiving
                client, no syntax or sematics of the content is specifed by
                this definition, that information would be specified by the vendor."
            ::= { mitelDhcpServerVendorInfoEntry 4 }

        mitelDhcpServerVendorInfoStatus OBJECT-TYPE
            SYNTAX RowStatus
            MAX-ACCESS read-create
            STATUS current
            DESCRIPTION
                    "The current status of this entry."
            REFERENCE
                    "Textual Conventions for Version 2 of the
                    Simple Network Management Protocol (RFC 1443)."
            ::= { mitelDhcpServerVendorInfoEntry 5 }

--
--   Mitel DHCP Client Table
--
		mitelDhcpClientTable OBJECT-TYPE
			SYNTAX SEQUENCE OF MitelDhcpClientEntry
			MAX-ACCESS not-accessible
			STATUS current
			DESCRIPTION
				"This table contains a list of all DHCP Clients."
			::= { mitelRouterDhcpGroup 6 }

		mitelDhcpClientEntry OBJECT-TYPE
		SYNTAX MitelDhcpClientEntry
		MAX-ACCESS not-accessible
		STATUS current
		DESCRIPTION
			"Each entry in this list contains information for a DHCP client."
		INDEX { mitelDhcpClientIndex }
		::= { mitelDhcpClientTable 1 }

		MitelDhcpClientEntry ::=
			SEQUENCE {
				mitelDhcpClientIndex INTEGER,
				mitelDhcpClientId OCTET STRING,
				mitelDhcpClientLeaseAction INTEGER,
				mitelDhcpClientIpAddress IpAddress,
				mitelDhcpClientLeaseObtained TimeTicks,
				mitelDhcpClientLeaseExpired TimeTicks,
				mitelDhcpClientDefaultGateway IpAddress,
				mitelDhcpClientServerIp IpAddress,
				mitelDhcpClientPrimaryDns IpAddress,
				mitelDhcpClientSecondaryDns IpAddress,
				mitelDhcpClientPrimaryWins IpAddress,
				mitelDhcpClientSecondaryWins IpAddress,
				mitelDhcpClientDomainName OCTET STRING,
				mitelDhcpClientName OCTET STRING,
				mitelDhcpClientAdminState INTEGER
			}

		mitelDhcpClientIndex OBJECT-TYPE
			SYNTAX INTEGER
			MAX-ACCESS read-only
			STATUS current
			DESCRIPTION
				"The Index of this Client. This object's
				value has a direct correlation to the interface
				on which DHCP client has been defined."
			::= { mitelDhcpClientEntry 1 }

		mitelDhcpClientId OBJECT-TYPE
			SYNTAX OCTET STRING
			MAX-ACCESS read-write
			STATUS current
			DESCRIPTION
				"The ID of this client"
			::= { mitelDhcpClientEntry 2 }

		mitelDhcpClientLeaseAction OBJECT-TYPE
			SYNTAX INTEGER {
				none(1),
				release(2),
				renew(3)
			     }
			MAX-ACCESS read-only
			STATUS current
			DESCRIPTION
				"The object allows the user to release the
				current IP address assigned to this DHCP
				client.  The user can also conduct a renew
				action to obtain an IP address for this client.
				By default this object will return none(1)."
			::= { mitelDhcpClientEntry 3 }

		mitelDhcpClientIpAddress OBJECT-TYPE
			SYNTAX IpAddress
			MAX-ACCESS read-only
			STATUS current
			DESCRIPTION
				"The IP of this client assigned by the DHCP
				server."
			::= { mitelDhcpClientEntry 4 }

		mitelDhcpClientLeaseObtained OBJECT-TYPE
			SYNTAX TimeTicks
			MAX-ACCESS read-only
			STATUS current
			DESCRIPTION
				"The time the lease was acquired"
			::= { mitelDhcpClientEntry 5 }

		mitelDhcpClientLeaseExpired OBJECT-TYPE
			SYNTAX TimeTicks
			MAX-ACCESS read-only
			STATUS current
			DESCRIPTION
				"The time the current lease expires."
			::= { mitelDhcpClientEntry 6 }

		mitelDhcpClientDefaultGateway OBJECT-TYPE
			SYNTAX IpAddress
			MAX-ACCESS read-only
			STATUS current
			DESCRIPTION
				"The default gateway IP for this client
				learned from the DHCP server."
			::= { mitelDhcpClientEntry 7 }

		mitelDhcpClientServerIp OBJECT-TYPE
			SYNTAX IpAddress
			MAX-ACCESS read-only
			STATUS current
			DESCRIPTION
				"The IP of this client's DHCP server."
			::= { mitelDhcpClientEntry 8 }

		mitelDhcpClientPrimaryDns OBJECT-TYPE
			SYNTAX IpAddress
			MAX-ACCESS read-only
			STATUS current
			DESCRIPTION
				"The primary DNS IP address of the client learned
				from the DHCP server."
			::= { mitelDhcpClientEntry 9 }

		mitelDhcpClientSecondaryDns OBJECT-TYPE
			SYNTAX IpAddress
			MAX-ACCESS read-only
			STATUS current
			DESCRIPTION
				"The secondary DNS IP address of the client
				learned from the DHCP server."
			::= { mitelDhcpClientEntry 10 }

		mitelDhcpClientPrimaryWins OBJECT-TYPE
			SYNTAX IpAddress
			MAX-ACCESS read-only
			STATUS current
			DESCRIPTION
				"The primary WINS IP address of the client
				learned from the DHCP server."
			::= { mitelDhcpClientEntry 11 }

		mitelDhcpClientSecondaryWins OBJECT-TYPE
			SYNTAX IpAddress
			MAX-ACCESS read-only
			STATUS current
			DESCRIPTION
				"The secondary WINS IP address of the client
				learned from the DHCP server."
			::= { mitelDhcpClientEntry 12 }

		mitelDhcpClientDomainName OBJECT-TYPE
			SYNTAX OCTET STRING
			MAX-ACCESS read-only
			STATUS current
			DESCRIPTION
				"The domain name of this client learned
				from the DHCP server."
			::= { mitelDhcpClientEntry 13 }

		mitelDhcpClientName OBJECT-TYPE
			SYNTAX OCTET STRING
			MAX-ACCESS read-only
			STATUS current
			DESCRIPTION
				"The name of this client."
			::= { mitelDhcpClientEntry 14 }

		mitelDhcpClientAdminState OBJECT-TYPE
			SYNTAX INTEGER {
				enabled(1),
				disabled(2)
			     }
			MAX-ACCESS read-only
			STATUS current
			DESCRIPTION
				"The admin status of this client."
			::= { mitelDhcpClientEntry 15 }

--
--		Notifications Definitions
--

		mitelIpera1000Notifications NOTIFICATION-GROUP
	        NOTIFICATIONS	{
	        					mitelDhcpClientObtainedIp,
	        					mitelDhcpClientLeaseExpiry
	        				}
	        STATUS            current
	        DESCRIPTION       "Call Server Ipera 1000 Notifications."
	        ::= { mitelIdCsIpera1000 0 }

		mitelDhcpClientObtainedIp    NOTIFICATION-TYPE
	        OBJECTS {
						mitelDhcpClientIndex,
						mitelDhcpClientIpAddress,
						mitelDhcpClientServerIp
	        }
	        STATUS          current
	        DESCRIPTION     "The mitelDhcpClientObtainedIP trap indicates that
							the router has obtained a lease for an IP address
							from a DHCP server."
	     ::= { mitelIpera1000Notifications 404 }

		mitelDhcpClientLeaseExpiry    NOTIFICATION-TYPE
	        OBJECTS {
						mitelDhcpClientIndex
	        }
	        STATUS          current
	        DESCRIPTION     "The mitelDhcpClientLeaseExpiry trap indicates
							that the router's DHCP client lease has expired."
	     ::= { mitelIpera1000Notifications 405 }

END

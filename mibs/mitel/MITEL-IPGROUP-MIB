-- Copyright 1999 MITEL Corporation
-- All rights reserved.
-- This MITEL SNMP Management Information Base Specification
-- (Specification) embodies MITEL's confidential and
-- proprietary intellectual property. MITEL retains all
-- title and ownership in the Specification, including any
-- revisions.

-- This Specification is supplied "AS IS", and MITEL makes
-- no warranty, either express or implied, as to the use,
-- operation, condition, or performance of the Specification.


MITEL-IPGROUP-MIB

    --FORCE-INCLUDE <mib.h>
    --FORCE-INCLUDE <snmpdefs.h>
    --FORCE-INCLUDE <snmpstat.h>
    --FORCE-INCLUDE "mibhand.h"

	DEFINITIONS ::= BEGIN

    IMPORTS
	MODULE-IDENTITY, enterprises
      FROM SNMPv2-SMI;

mitelRouterIpGroup	   MODULE-IDENTITY
       LAST-UPDATED      "200303240908Z"
       ORGANIZATION      "MITEL Corporation"
       CONTACT-INFO      "Standards Group,
                          Postal:    MITEL Corporation
                          350 Legget Drive, PO Box 13089
                          Kanata, Ontario
                          Canada  K2K 1X3
                          Tel: +1 613 592 2122
                          Fax: +1 613 592 4784
                          E-mail: std@mitel.com"
       DESCRIPTION       "The MITEL IP MIB module."
       REVISION          "200303240908Z"
           DESCRIPTION   "Convert to SMIv2"
       REVISION          "199903010000Z"
           DESCRIPTION   "IP MIB Version 1.0"
::= { mitelIpNetRouter 1}

-- To manage the creation and deletion of conceptual rows the textual
-- convention 'RowStatus' from RFC 1443 is used and is defined as
-- follows:

mitel			   OBJECT IDENTIFIER ::= { enterprises 1027}
mitelProprietary 	   OBJECT IDENTIFIER ::= { mitel 4}
mitelPropIpNetworking      OBJECT IDENTIFIER ::= { mitelProprietary 8 }
mitelIpNetRouter           OBJECT IDENTIFIER ::= { mitelPropIpNetworking 1 }


	mitelIpGrpFilterGroup OBJECT IDENTIFIER ::= { mitelRouterIpGroup 1 }
	mitelIpGrpNatGroup OBJECT IDENTIFIER ::= { mitelRouterIpGroup 2 }
	mitelIpGrpDnsGroup OBJECT IDENTIFIER ::= { mitelRouterIpGroup 3 }
	mitelIpGrpIpVirtualGroup OBJECT IDENTIFIER ::= {mitelRouterIpGroup 4 }
	mitelIpGrpLogicalGroup OBJECT IDENTIFIER ::= { mitelRouterIpGroup 5 }
	mitelIpGrpBackupWANGroup OBJECT IDENTIFIER ::= { mitelRouterIpGroup 6 }

END -- MITEL-IPGROUP-MIB

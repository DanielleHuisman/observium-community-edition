-- Copyright 1999 MITEL Corporation
-- All rights reserved.
-- This MITEL SNMP Management Information Base Specification
-- (Specification) embodies MITEL's confidential and
-- proprietary intellectual property. MITEL retains all
-- title and ownership in the Specification, including any
-- revisions.

-- This Specification is supplied "AS IS", and MITEL makes
-- no warranty, either express or implied, as to the use,
-- operation, condition, or performance of the Specification.


MITEL-IPLOGICAL-MIB
	DEFINITIONS ::= BEGIN

IMPORTS
    MODULE-IDENTITY, OBJECT-TYPE, enterprises,
    IpAddress
        FROM SNMPv2-SMI
	ifIndex
    	FROM RFC1213-MIB
    RowStatus
        FROM SNMPv2-TC;


mitelIpGrpLogicalGroup     MODULE-IDENTITY
       LAST-UPDATED      "200303240913Z"
       ORGANIZATION      "MITEL Corporation"
       CONTACT-INFO      "Standards Group,
                          Postal:    MITEL Corporation
                          350 Legget Drive, PO Box 13089
                          Kanata, Ontario
                          Canada  K2K 1X3
                          Tel: +1 613 592 2122
                          Fax: +1 613 592 4784
                          E-mail: std@mitel.com"
       DESCRIPTION       "The MITEL IP MIB module."
       REVISION          "200303240913Z"
           DESCRIPTION   "Convert to SMIv2"
       REVISION          "199903010000Z"
           DESCRIPTION   "IP MIB Version 1.0"
::= { mitelRouterIpGroup 5 }

mitel			   OBJECT IDENTIFIER ::= { enterprises 1027}
mitelProprietary 	   OBJECT IDENTIFIER ::= { mitel 4}
mitelPropIpNetworking      OBJECT IDENTIFIER ::= { mitelProprietary 8 }
mitelIpNetRouter           OBJECT IDENTIFIER ::= { mitelPropIpNetworking 1 }
mitelRouterIpGroup 	   OBJECT IDENTIFIER ::= { mitelIpNetRouter 1}



--
-- The IP Group Logical Port configuration Table
--

    mitelIpLogGrpLogicalTable OBJECT-TYPE
        SYNTAX  SEQUENCE OF MitelIpLogGrpLogicalEntry
        MAX-ACCESS  not-accessible
        STATUS  current
        DESCRIPTION
                "A table containing information about logical IP LAN
                destinations."
        ::= { mitelIpGrpLogicalGroup 1 }


        mitelIpLogGrpLogicalEntry OBJECT-TYPE
            SYNTAX  MitelIpLogGrpLogicalEntry
            MAX-ACCESS  not-accessible
            STATUS  current
            DESCRIPTION
                    "Each entry of this table contains information about
                    a specific logical interface to a local area network.
                    Each logical LAN can support routing or bridging
                    functions, these are considered virtual interfaces."
            INDEX   { ifIndex }
            ::= { mitelIpLogGrpLogicalTable 1 }

        MitelIpLogGrpLogicalEntry ::=
            SEQUENCE {
				mitelIpLogAdvertisementAddress
		                    IpAddress,
				mitelIpLogMaxAdvertisementInterval
		                    INTEGER,
				mitelIpLogMinAdvertisementInterval
		                    INTEGER,
				mitelIpLogAdvertisementLifetime
		                    INTEGER,
				mitelIpLogPerformRouterDiscovery
		                    INTEGER,
				mitelIpLogSolicitationAddress
                    IpAddress,
                mitelIpLogStatus
                    RowStatus
            }

        mitelIpLogAdvertisementAddress OBJECT-TYPE
            SYNTAX  IpAddress
            MAX-ACCESS  read-write
            STATUS  current
            DESCRIPTION
                    "The IP destination address to be used for multicast
		    Router Advertisements sent from the interface.  The
		    only permissible values are the all-systems multicast
		    address, 224.0.0.1, or the limited-broadcast address,
		    255.255.255.255.  (The all-systems address is preferred
		    wherever possible, i.e., on any link where all
		    listening hosts support IP multicast.)  Default Value is 224.0.0.1"
	    REFERENCE
		    "ICMP Router Discovery Messages (RFC 1256)."
            ::= { mitelIpLogGrpLogicalEntry 1 }


        mitelIpLogMaxAdvertisementInterval OBJECT-TYPE
	    SYNTAX  INTEGER (4..1800)
            MAX-ACCESS  read-write
            STATUS  current
            DESCRIPTION
                    "The maximum time allowed between sending multicast
		    Router Advertisements from the interface, in seconds."
	    REFERENCE
		    "ICMP Router Discovery Messages (RFC 1256)."
	    DEFVAL { 600 }
	    ::= { mitelIpLogGrpLogicalEntry 2 }


        mitelIpLogMinAdvertisementInterval OBJECT-TYPE
	    SYNTAX  INTEGER (3..1800)
            MAX-ACCESS  read-write
            STATUS  current
            DESCRIPTION
                    "The minimum time allowed between sending unsolicited
		    multicast Router Advertisements from the interface, in
		    seconds.  Must be no greater than
		    grIpLMaxAdvertisementInterval."

	    REFERENCE
		    "ICMP Router Discovery Messages (RFC 1256)."
	    DEFVAL { 450 }
	    ::= { mitelIpLogGrpLogicalEntry 3 }


        mitelIpLogAdvertisementLifetime OBJECT-TYPE
	    SYNTAX  INTEGER (4..9000)
            MAX-ACCESS  read-write
            STATUS  current
            DESCRIPTION
                    "The value to be placed in the Lifetime field of Router
		    Advertisements sent from the interface, in seconds.
		    Must be no less than grIpLMaxAdvertisementInterval."
	    REFERENCE
		    "ICMP Router Discovery Messages (RFC 1256)."
	    DEFVAL { 1800 }
        ::= { mitelIpLogGrpLogicalEntry 4 }


        mitelIpLogPerformRouterDiscovery OBJECT-TYPE
	    SYNTAX  INTEGER {
                   enabled(1),
                   disabled(2)
                }
            MAX-ACCESS  read-write
            STATUS  current
            DESCRIPTION
                    "A flag indicating whether or not the host is to perform
		    ICMP router discovery on the interface."
	    REFERENCE
		    "ICMP Router Discovery Messages (RFC 1256)."
	    DEFVAL { 1 }
	    ::= { mitelIpLogGrpLogicalEntry 5 }


        mitelIpLogSolicitationAddress OBJECT-TYPE
            SYNTAX  IpAddress
            MAX-ACCESS  read-write
            STATUS  current
            DESCRIPTION
                    "The IP destination address to be used for sending
				      Router Solicitations from the interface.  The only
				      permissible values are the all-routers multicast
				      address, 224.0.0.2, or the limited-broadcast address,
				      255.255.255.255.  (The all-routers address is preferred
				      wherever possible, i.e., on any link where all
				      advertising routers support IP multicast.)  Default 224.0.0.2"
		   REFERENCE
		      	"ICMP Router Discovery Messages (RFC 1256)."
	 		 ::= { mitelIpLogGrpLogicalEntry 6 }


        mitelIpLogStatus OBJECT-TYPE
            SYNTAX  RowStatus
            MAX-ACCESS  read-create
            STATUS  current
            DESCRIPTION
                    "The current status of this entry."
            REFERENCE
                    "Textual Conventions for Version 2 of the
                    Simple Network Management Protocol (RFC 1443)."
            ::= { mitelIpLogGrpLogicalEntry 7 }

END -- MITEL-IPLOGICAL-MIB

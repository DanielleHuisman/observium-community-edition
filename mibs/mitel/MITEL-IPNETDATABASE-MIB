-- Copyright 1999 MITEL Corporation
-- All rights reserved.
-- This MITEL SNMP Management Information Base Specification
-- (Specification) embodies MITEL's confidential and
-- proprietary intellectual property. MITEL retains all
-- title and ownership in the Specification, including any
-- revisions.

-- This Specification is supplied "AS IS", and MITEL makes
-- no warranty, either express or implied, as to the use,
-- operation, condition, or performance of the Specification.


MITEL-IPNETDATABASE-MIB
	DEFINITIONS ::= BEGIN

IMPORTS
	MODULE-IDENTITY, enterprises, Integer32, OBJECT-TYPE
      FROM SNMPv2-SMI;

mitelRouterDatabaseVersion           MODULE-IDENTITY
       LAST-UPDATED      "200303240926Z"
       ORGANIZATION      "MITEL Corporation"
       CONTACT-INFO      "Standards Group,
                          Postal:    MITEL Corporation
                          350 Legget Drive, PO Box 13089
                          Kanata, Ontario
                          Canada  K2K 1X3
                          Tel: +1 613 592 2122
                          Fax: +1 613 592 4784
                          E-mail: std@mitel.com"
       DESCRIPTION       "The MITEL IP Net Router MIB module."
       REVISION          "200303240926Z"
           DESCRIPTION   "Initial Version"
::= { mitelIpNetRouter 8 }

	mitel			   OBJECT IDENTIFIER ::= { enterprises 1027}
	mitelProprietary 	   OBJECT IDENTIFIER ::= { mitel 4}
	mitelPropIpNetworking      OBJECT IDENTIFIER ::= { mitelProprietary 8 }
	mitelIpNetRouter OBJECT IDENTIFIER ::= { mitelPropIpNetworking 1 }

	mitelRouterDatabaseMajorVersion OBJECT-TYPE
		SYNTAX Integer32
		MAX-ACCESS read-only
		STATUS current
		DESCRIPTION
			"Major version of the IP Networking database"
		::= { mitelRouterDatabaseVersion 1}

	mitelRouterDatabaseMinorVersion OBJECT-TYPE
		SYNTAX Integer32
		MAX-ACCESS read-only
		STATUS current
		DESCRIPTION
			"Minor version of the IP Networking database"
		::= { mitelRouterDatabaseVersion 2}

END -- MITEL-IPNETDATABASE-MIB

-- Copyright 1999 MITEL Corporation
-- All rights reserved.
-- This MITEL SNMP Management Information Base Specification
-- (Specification) embodies MITEL's confidential and
-- proprietary intellectual property. MITEL retains all
-- title and ownership in the Specification, including any
-- revisions.

-- This Specification is supplied "AS IS", and MITEL makes
-- no warranty, either express or implied, as to the use,
-- operation, condition, or performance of the Specification.


MITEL-IPNETROUTER-MIB
	DEFINITIONS ::= BEGIN

IMPORTS
	MODULE-IDENTITY, enterprises
      FROM SNMPv2-SMI;

mitelIpNetRouter           MODULE-IDENTITY
       LAST-UPDATED      "200303240927Z"
       ORGANIZATION      "MITEL Corporation"
       CONTACT-INFO      "Standards Group,
                          Postal:    MITEL Corporation
                          350 Legget Drive, PO Box 13089
                          Kanata, Ontario
                          Canada  K2K 1X3
                          Tel: +1 613 592 2122
                          Fax: +1 613 592 4784
                          E-mail: std@mitel.com"
       DESCRIPTION       "The MITEL IP Net Router MIB module."
       REVISION          "200303240927Z"
           DESCRIPTION   "Convert to SMIv2"
       REVISION          "199903010000Z"
           DESCRIPTION   "IP Router MIB Version 1.0"
::= { mitelPropIpNetworking 1 }

	mitel			   OBJECT IDENTIFIER ::= { enterprises 1027}
	mitelProprietary 	   OBJECT IDENTIFIER ::= { mitel 4}
	mitelPropIpNetworking      OBJECT IDENTIFIER ::= { mitelProprietary 8 }

    mitelRouterIpGroup   OBJECT IDENTIFIER ::= { mitelIpNetRouter 1 }
    mitelRouterPppGroup  OBJECT IDENTIFIER ::= { mitelIpNetRouter 2 }
    mitelRouterDhcpGroup  OBJECT IDENTIFIER ::= { mitelIpNetRouter 3 }
    mitelRouterLogicalGroup OBJECT IDENTIFIER ::= { mitelIpNetRouter 4 }
    mitelRouterIpRouterGroup OBJECT IDENTIFIER ::= { mitelIpNetRouter 5 }
    mitelRouterRipExtensionGroup OBJECT IDENTIFIER ::= { mitelIpNetRouter 6 }
    mitelRouterSnmpTrapGroup OBJECT IDENTIFIER ::= { mitelIpNetRouter 7 }

END -- MITEL-IPNETROUTER-MIB

-- Copyright 2002 MITEL Networks Corporation
-- All rights reserved.
-- This MITEL SNMP Management Information Base Specification
-- (Specification) embodies MITEL's confidential and
-- proprietary intellectual property. MITEL retains all
-- title and ownership in the Specification, including any
-- revisions.

-- This Specification is supplied "AS IS", and MITEL makes
-- no warranty, either express or implied, as to the use,
-- operation, condition, or performance of the Specification.


MITEL-MN3100-CALL-CONTROL-MIB
DEFINITIONS ::= BEGIN

IMPORTS
	MODULE-IDENTITY, OBJECT-TYPE, enterprises,
    Integer32, Counter32, NOTIFICATION-TYPE
        FROM SNMPv2-SMI
    NOTIFICATION-GROUP
    	FROM SNMPv2-CONF;

mitelCallControl 	   MODULE-IDENTITY
       LAST-UPDATED      "200204020000Z"
       ORGANIZATION      "MITEL Networks Corporation"
       CONTACT-INFO      "Standards Group,
                          Postal:    MITEL Networks Corporation
                          350 Legget Drive, PO Box 13089
                          Kanata, Ontario
                          Canada  K2K 1X3
                          Tel: +1 613 592 2122
                          Fax: +1 613 592 4784
                          E-mail: std@mitel.com"
       DESCRIPTION       "The MITEL Call CONTROL MIB module."
       REVISION          "200303241143Z"
       	DESCRIPTION     "Convert to SMIv2"
       REVISION          "200204020000Z"
       	DESCRIPTION     "Call Control Group MIB version 1.0"
::= { mitelProprietary 9 }

mitel			   OBJECT IDENTIFIER ::= { enterprises 1027}
mitelProprietary 	   OBJECT IDENTIFIER ::= { mitel 4}


-- NOTIFICATIONS
mitelIdentification 	  OBJECT IDENTIFIER ::= { mitel 1}
mitelIdCallServers 	  OBJECT IDENTIFIER ::= { mitelIdentification 2}
mitelIdCsIpera1000 	  OBJECT IDENTIFIER ::= { mitelIdCallServers 4}

    -- ************************************
    -- The mitelCallControl subtree...
    -- ************************************
-- the Mitel Call Control Fault Table

    mitelCallCtrlFaultTable     OBJECT-TYPE
        SYNTAX  SEQUENCE OF MitelCallCtrlFaultEntry
	 	MAX-ACCESS  not-accessible
        STATUS  current
        DESCRIPTION
            "The Call Control Fault table."
        ::= { mitelCallControl 1 }

    mitelCallCtrlFaultEntry OBJECT-TYPE
             SYNTAX MitelCallCtrlFaultEntry
             MAX-ACCESS  not-accessible
             STATUS  current
             DESCRIPTION
                "An entry in the mitelCallCtrlFaultTable."
             INDEX   { mitelCallCtrlFaultTblIndex }
            ::= { mitelCallCtrlFaultTable 1 }

    MitelCallCtrlFaultEntry ::=
         SEQUENCE {
		 mitelCallCtrlFaultTblIndex	Integer32,
             mitelCallCtrlFaultId		INTEGER,
		 mitelCallCtrlFaultStatus	INTEGER,
 		 mitelCallCtrlFaultOccur	Counter32
	   }

    mitelCallCtrlFaultTblIndex OBJECT-TYPE
        SYNTAX           Integer32
        MAX-ACCESS           read-only
        STATUS           current
        DESCRIPTION
		"The index of the fault table."
        ::= { mitelCallCtrlFaultEntry 1 }

    mitelCallCtrlFaultId	OBJECT-TYPE
        SYNTAX INTEGER {
			mitelCallCtrlFailedSeizeLine(1),
			mitelCallCtrlDdiMappingError (2)
	 	   }
        MAX-ACCESS  read-only
        STATUS  current
        DESCRIPTION
            "The mitelCallCtrlFaultId indicates the id of the fault."
        ::= { mitelCallCtrlFaultEntry 2 }

    mitelCallCtrlFaultStatus	OBJECT-TYPE
        SYNTAX INTEGER {
			set(1),
			clear(2),
			message(3)
	 	   }
        MAX-ACCESS  read-only
        STATUS  current
        DESCRIPTION
            "The mitelCallCtrlFaultStatus indicates whether the fault is
 		 raised or cleared."
        ::= { mitelCallCtrlFaultEntry 3 }

    mitelCallCtrlFaultOccur		OBJECT-TYPE
        SYNTAX  Counter32
        MAX-ACCESS  read-only
        STATUS  current
        DESCRIPTION
            "The mitelCallCtrlFaultOccur indicates the occurence of
		 the fault since the last system restart"
            ::= { mitelCallCtrlFaultEntry 4 }

--
--  Notification Definitions
--
mitelIpera1000Notifications NOTIFICATION-GROUP
    NOTIFICATIONS	{ mitelCallCtrlFailedSeizeLineNotif, mitelCallCtrlDdiMappingErrorNotif }
    STATUS            current
    DESCRIPTION       "Call Server Ipera 1000 Notifications."
    ::= { mitelIdCsIpera1000 0 }

mitelCallCtrlFailedSeizeLineNotif NOTIFICATION-TYPE
	OBJECTS { mitelCallCtrlFaultStatus,
			mitelCallCtrlFaultOccur }
	STATUS current
	DESCRIPTION
		"The mitelMn3100CallCtrlFaultNotif trap indicates
		 that the call control has failed to seize a line."
	::= { mitelIpera1000Notifications 406 }

mitelCallCtrlDdiMappingErrorNotif NOTIFICATION-TYPE
	OBJECTS { mitelCallCtrlFaultStatus,
			mitelCallCtrlFaultOccur }
	STATUS current
	DESCRIPTION
		"The mitelCallCtrlDdiMappingErrorNotif trap indicates
		 that a DDI mapping has failed."
	::= { mitelIpera1000Notifications 407 }

 END -- MITEL-MN3100-CALL-CONTROL-MIB

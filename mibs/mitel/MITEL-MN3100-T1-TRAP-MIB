-- Copyright 2002 MITEL Networks Corporation
-- All rights reserved.
-- This MITEL SNMP Management Information Base Specification
-- (Specification) embodies MITEL's confidential and
-- proprietary intellectual property. MITEL retains all
-- title and ownership in the Specification, including any
-- revisions.

-- This Specification is supplied "AS IS", and MITEL makes
-- no warranty, either express or implied, as to the use,
-- operation, condition, or performance of the Specification.


MITEL-MN3100-T1-TRAP-MIB
	DEFINITIONS ::= BEGIN

IMPORTS
	MODULE-IDENTITY, enterprises,
    NOTIFICATION-TYPE
        FROM SNMPv2-SMI
    NOTIFICATION-GROUP
    	FROM SNMPv2-CONF
	dsx1LineStatus
		FROM RFC1406-MIB;

mitelDS1Extension MODULE-IDENTITY
       LAST-UPDATED      "200204020000Z"
       ORGANIZATION      "MITEL Networks Corporation"
       CONTACT-INFO      "Standards Group,
                          Postal:    MITEL Networks Corporation
                          350 Legget Drive, PO Box 13089
                          Kanata, Ontario
                          Canada  K2K 1X3
                          Tel: +1 613 592 2122
                          Fax: +1 613 592 4784
                          E-mail: std@mitel.com"
       DESCRIPTION       "The MITEL Mn3100 T1 trap MIB."
       REVISION          "200303240141Z"
           DESCRIPTION   "Convert to SMIv2"
       REVISION          "200204020000Z"
           DESCRIPTION   "MN3100 T1 trap definition Version 1.0"
::= { mitelProprietary 12 }

mitel			   OBJECT IDENTIFIER ::= { enterprises 1027}
mitelProprietary 	   OBJECT IDENTIFIER ::= { mitel 4}

-- NOTIFICATIONS
mitelIdentification 	  OBJECT IDENTIFIER ::= { mitel 1}
mitelIdCallServers 	  OBJECT IDENTIFIER ::= { mitelIdentification 2}
mitelIdCsIpera1000 	  OBJECT IDENTIFIER ::= { mitelIdCallServers 4}

--
--  Notification Definitions
--
mitelIpera1000Notifications NOTIFICATION-GROUP
    NOTIFICATIONS	{ mitelMn3100dsx1LineSatusChangeNotif }
    STATUS            current
    DESCRIPTION       "Call Server Ipera 1000 Notifications."
    ::= { mitelIdCsIpera1000 0 }

mitelMn3100dsx1LineSatusChangeNotif NOTIFICATION-TYPE
	OBJECTS{ dsx1LineStatus }
	STATUS current
	DESCRIPTION
		"The mitelMn3100dsx1LineSatusChangeNotif trap indicates
		 that the line status of a T1/E1 has changed. Please refer
		 to RFC1406 for definition of dsx1LineStatus."
	::= { mitelIpera1000Notifications 410 }

END -- MITEL-3100-T1-TRAP-MIB

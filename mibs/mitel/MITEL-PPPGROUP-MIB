-- Copyright 1999 MITEL Corporation
-- All rights reserved.
-- This MITEL SNMP Management Information Base Specification
-- (Specification) embodies MITEL's confidential and
-- proprietary intellectual property. MITEL retains all
-- title and ownership in the Specification, including any
-- revisions.

-- This Specification is supplied "AS IS", and MITEL makes
-- no warranty, either express or implied, as to the use,
-- operation, condition, or performance of the Specification.


MITEL-PPPGROUP-MIB
	DEFINITIONS ::= BEGIN

IMPORTS
	MODULE-IDENTITY, OBJECT-TYPE, enterprises,
    Integer32, IpAddress
        FROM SNMPv2-SMI
    RowStatus
        FROM SNMPv2-TC;

mitelRouterPppGroup   	   MODULE-IDENTITY
       LAST-UPDATED      "200303241033Z"
       ORGANIZATION      "MITEL Corporation"
       CONTACT-INFO      "Standards Group,
                          Postal:    MITEL Corporation
                          350 Legget Drive, PO Box 13089
                          Kanata, Ontario
                          Canada  K2K 1X3
                          Tel: +1 613 592 2122
                          Fax: +1 613 592 4784
                          E-mail: std@mitel.com"
       DESCRIPTION       "The MITEL PPP MIB module."
       REVISION          "200303241033Z"
           DESCRIPTION   "Convert to SMIv2"
       REVISION          "199903010000Z"
           DESCRIPTION   "PPP MIB Version 1.0"
::= { mitelIpNetRouter 2 }

mitel			   OBJECT IDENTIFIER ::= { enterprises 1027}
mitelProprietary 	   OBJECT IDENTIFIER ::= { mitel 4}
mitelPropIpNetworking      OBJECT IDENTIFIER ::= { mitelProprietary 8 }
mitelIpNetRouter           OBJECT IDENTIFIER ::= { mitelPropIpNetworking 1 }

--

mitelPppGrpGlobalGroup     OBJECT IDENTIFIER ::= { mitelRouterPppGroup 1 }

--
-- Global PPP Definitions
--
mitelGblGrpNegotiateFirst OBJECT-TYPE
    SYNTAX  INTEGER {
                 chap(1),
                 pap(2),
		 mschap(3)
               }
    MAX-ACCESS  read-write
    STATUS  current
    DESCRIPTION
           "This attribute defines which PPP authentication protocol
	    is negotiated first on incoming call.
	    DEFAULT = chap"
    DEFVAL { chap }
    ::= { mitelPppGrpGlobalGroup 1 }


mitelGblGrpDynamicIpAddr OBJECT-TYPE
     SYNTAX  IpAddress
     MAX-ACCESS  read-write
     STATUS  current
     DESCRIPTION
	     "This attribute defines the start address
	     of the dynamic addres pool."
      ::= { mitelPppGrpGlobalGroup 2 }


mitelGblGrpNumDynamicIpAddr OBJECT-TYPE
     SYNTAX  INTEGER (0..150)
     MAX-ACCESS  read-write
     STATUS  current
     DESCRIPTION
	     "This attribute defines the number of
	     dynamic IP addresses in the pool."
     DEFVAL { 0 }
     ::= { mitelPppGrpGlobalGroup 3 }

mitelGblGrpDynamicIpAdrrHoldoff OBJECT-TYPE
     SYNTAX  INTEGER (1..300)
     MAX-ACCESS  read-write
     STATUS  current
     DESCRIPTION
	     "This attribute defines the time in seconds before
	     the same IP address can be reused after a call
	     has been disconnected."
     DEFVAL { 120 }
     ::= { mitelPppGrpGlobalGroup 4 }

mitelGblGrpRemDnsIpAddrHandling OBJECT-TYPE
    SYNTAX  INTEGER {
                 accept(1),
                 override(2),
		 overridewith(3)
            }
    MAX-ACCESS  read-write
    STATUS  current
    DESCRIPTION
           "This attribute determines wether the system can accept
	   or override the DNS IP address submitted by
	   a remote system. DEFAULT = accept.
	   Override has been superceded by overridewith."
    DEFVAL { accept }
    ::= { mitelPppGrpGlobalGroup 5 }

mitelGblGrpPrimaryWinsServerIpAddr OBJECT-TYPE
     SYNTAX  IpAddress
     MAX-ACCESS  read-write
     STATUS  current
     DESCRIPTION
             "This attribute defines the Primary WINS server IP address of
             your Network."
      ::= { mitelPppGrpGlobalGroup 6 }

mitelGblGrpSecondaryWinsServerIpAddr OBJECT-TYPE
     SYNTAX  IpAddress
     MAX-ACCESS  read-write
     STATUS  current
     DESCRIPTION
             "This attribute defines the Secondary WINS server IP address of
             your Network."
      ::= { mitelPppGrpGlobalGroup 7 }
--


--
--     Remote LAN PPP configuration table
--


mitelPppGrpRemoteConfigTable OBJECT-TYPE
     SYNTAX  SEQUENCE OF MitelPppGrpRemoteConfigEntry
     MAX-ACCESS  not-accessible
     STATUS  current
     DESCRIPTION
	     "This table contains objects that pertain to the management of
	     remote LANs that use the PPP Internet standard link protocol."
     ::= { mitelRouterPppGroup 2 }


mitelPppGrpRemoteConfigEntry OBJECT-TYPE
     SYNTAX  MitelPppGrpRemoteConfigEntry
     MAX-ACCESS  not-accessible
     STATUS  current
     DESCRIPTION
	     "A default entry at conceptual row zero does exist in this
	     table. The default entry can be used to specify the PPP
	     authentication protocol only."
     INDEX { mitelRmtCfgTableIndex}
     ::= { mitelPppGrpRemoteConfigTable 1 }


MitelPppGrpRemoteConfigEntry ::=
     SEQUENCE {
	 mitelRmtCfgTableIndex Integer32,
	 mitelRmtCfgTableIpAddrHandling    INTEGER,
	 mitelRmtCfgTableRemIpAddr   IpAddress,
	 mitelRmtCfgTableStatus	     RowStatus,
	 mitelRmtCfgTablePppMode	   INTEGER
     }

	mitelRmtCfgTableIndex OBJECT-TYPE
	SYNTAX Integer32
	MAX-ACCESS read-only
	STATUS current
	DESCRIPTION
			" This object uniquely identifies this object "
	::= { mitelPppGrpRemoteConfigEntry 1 }

mitelRmtCfgTableIpAddrHandling OBJECT-TYPE
    SYNTAX  INTEGER {
                 accept(1),
                 override(2),
		 		 assign(3)
            }
    MAX-ACCESS  read-write
    STATUS  current
    DESCRIPTION
           "This attribute determines wether the system can accept
	   or override the DNS IP address submitted by
	   a remote system. DEFAULT = accept."
    DEFVAL { accept }
    ::= { mitelPppGrpRemoteConfigEntry 2 }

mitelRmtCfgTableRemIpAddr OBJECT-TYPE
    SYNTAX  IpAddress
    MAX-ACCESS  read-write
    STATUS  current
    DESCRIPTION
           "The IP address to assign to remote if mitelRmtCfgTableIPAddrHandling
	    is set to assign(3)"
    ::= { mitelPppGrpRemoteConfigEntry 3 }

mitelRmtCfgTableStatus OBJECT-TYPE
    SYNTAX  RowStatus
    MAX-ACCESS  read-create
    STATUS  current
    DESCRIPTION
           "The current status of this entry."
    ::= { mitelPppGrpRemoteConfigEntry 4 }

mitelRmtCfgTablePppMode OBJECT-TYPE
    SYNTAX  INTEGER {
   		client(1),
		server(2)
	    }
    MAX-ACCESS  read-write
    STATUS  current
    DESCRIPTION
           "The mode PPP will be using for the given destination."
    ::= { mitelPppGrpRemoteConfigEntry 5 }


mitelPppGrpPppOverEthernetTable OBJECT-TYPE
	SYNTAX	SEQUENCE OF MitelPppGrpPppOverEthernetEntry
	MAX-ACCESS	not-accessible
	STATUS  current
	DESCRIPTION
		"Table containing the configuration items needed by the
		 PPPoE stack."
	::= {  mitelRouterPppGroup 3 }


mitelPppGrpPppOverEthernetEntry OBJECT-TYPE
	SYNTAX	MitelPppGrpPppOverEthernetEntry
	MAX-ACCESS	not-accessible
	STATUS	current
	DESCRIPTION
		"PPPoE information"
	INDEX { mitelPppOEthTableIndex }
	::= { mitelPppGrpPppOverEthernetTable 1 }


MitelPppGrpPppOverEthernetEntry ::= SEQUENCE {
	mitelPppOEthTableIndex		Integer32,
	mitelPppOEthTableEnabled	INTEGER,
	mitelPppOEthTablePacketTimeout	INTEGER,
	mitelPppOEthTablePacketRetries 	INTEGER,
	mitelPppOEthTableTotalRetries	INTEGER,
	mitelPppOEthTableServiceName	OCTET STRING,
	mitelPppOEthTableACName		OCTET STRING,
	mitelPppOEthTableStatus		RowStatus
}

mitelPppOEthTableIndex OBJECT-TYPE
	SYNTAX	Integer32
	MAX-ACCESS	read-write
	STATUS	current
	DESCRIPTION
		"Unique Identifier for an entry in PPP over Ethernet Table."
	::= { mitelPppGrpPppOverEthernetEntry 1 }


mitelPppOEthTableEnabled OBJECT-TYPE
	SYNTAX	INTEGER {
			disabled(0),
			enabled(1)
		}
	MAX-ACCESS	read-write
	STATUS	current
	DESCRIPTION
		"Is this PPPoE instance enabled or not."
	DEFVAL	{ enabled }
	::= { mitelPppGrpPppOverEthernetEntry 2 }


mitelPppOEthTablePacketTimeout OBJECT-TYPE
	SYNTAX  INTEGER (1..5)
	MAX-ACCESS	read-write
	STATUS	current
	DESCRIPTION
		"The time to wait, in seconds, for a valid response to a
		 discovery packet before resending it.
		 Warning: this value is doubled ever time a packet is
		 resent."
	DEFVAL	{ 2 }
	::= { mitelPppGrpPppOverEthernetEntry 3 }


mitelPppOEthTablePacketRetries OBJECT-TYPE
	SYNTAX	INTEGER (1..15)
	MAX-ACCESS	read-write
	STATUS	current
	DESCRIPTION
		"The number of times to resend discovery packets before
		 giving up on the negotiation."
	DEFVAL	{ 3 }
	::= { mitelPppGrpPppOverEthernetEntry 4 }


mitelPppOEthTableTotalRetries OBJECT-TYPE
	SYNTAX	INTEGER (1..15)
	MAX-ACCESS	read-write
	STATUS	current
	DESCRIPTION
		"The RFC states that failure to receive a valid PADS packet
		 should restart the negotiation. This count stops the system
		 retrying indefinitely on duff PADS packets by capping the
		 total number of retry attempts."
	DEFVAL	{ 10 }
	::= { mitelPppGrpPppOverEthernetEntry 5 }


mitelPppOEthTableServiceName OBJECT-TYPE
	SYNTAX	OCTET STRING (SIZE(0..50))
	MAX-ACCESS	read-write
	STATUS	current
	DESCRIPTION
		"The service we wish to request from the remote access
		 concentrator. Examples of the use of the service name
		 are to indicate an ISP or a class or quality of
		 service.
		 An empty string indicates any service."
	::= { mitelPppGrpPppOverEthernetEntry 6 }


mitelPppOEthTableACName OBJECT-TYPE
	SYNTAX	OCTET STRING (SIZE(0..50))
	MAX-ACCESS  read-write
	STATUS  current
	DESCRIPTION
		"Description of the remote access concentrator we wish
		 to connect to.
		 An empty string indicates no preference."
	::= { mitelPppGrpPppOverEthernetEntry 7 }

mitelPppOEthTableStatus OBJECT-TYPE
	SYNTAX	RowStatus
	MAX-ACCESS  read-create
	STATUS  current
	DESCRIPTION
		"The entry's row status."
	::= { mitelPppGrpPppOverEthernetEntry 8 }

END -- MITEL-PPPGROUP-MIB

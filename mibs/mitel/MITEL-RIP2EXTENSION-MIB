-- Copyright 1999 MITEL Corporation
-- All rights reserved.
-- This MITEL SNMP Management Information Base Specification
-- (Specification) embodies MITEL's confidential and
-- proprietary intellectual property. MITEL retains all
-- title and ownership in the Specification, including any
-- revisions.

-- This Specification is supplied "AS IS", and MITEL makes
-- no warranty, either express or implied, as to the use,
-- operation, conWCM_EVENT_STRUCT_tdition, or performance of the Specification.

MITEL-RIP2EXTENSION-MIB

DEFINITIONS ::= BEGIN

IMPORTS
	MODULE-IDENTITY, OBJECT-TYPE, enterprises
        FROM SNMPv2-SMI
    RowStatus
        FROM SNMPv2-TC
	rip2IfConfAddress
		FROM RIPv2-MIB;

mitelRouterRipExtensionGroup    MODULE-IDENTITY
       LAST-UPDATED      "200303241036Z"
       ORGANIZATION      "MITEL Corporation"
       CONTACT-INFO      "Standards Group,
                          Postal:    MITEL Corporation
                          350 Legget Drive, PO Box 13089
                          Kanata, Ontario
                          Canada  K2K 1X3
                          Tel: +1 613 592 2122
                          Fax: +1 613 592 4784
                          E-mail: std@mitel.com"
       DESCRIPTION       "The MITEL RIP2 IfConf Extension MIB module."
       REVISION          "200303241036Z"
           DESCRIPTION   "Convert to SMIv2"
       REVISION          "199903010000Z"
           DESCRIPTION   "RIP2 IfConf Extension MIB Version 1.0"
::= { mitelIpNetRouter 6 }

-- tree up
mitel			   OBJECT IDENTIFIER ::= { enterprises 1027}
mitelProprietary 	   OBJECT IDENTIFIER ::= { mitel 4}
mitelPropIpNetworking      OBJECT IDENTIFIER ::= { mitelProprietary 8 }
mitelIpNetRouter           OBJECT IDENTIFIER ::= { mitelPropIpNetworking 1 }

--
--        RIP IF Conf Extension MIB
--      =============================
--

	mitelRipExtGrpIfConfTable OBJECT-TYPE
		SYNTAX  SEQUENCE OF MitelRipExtGrpIfConfEntry
		MAX-ACCESS  not-accessible
		STATUS  current
		DESCRIPTION
			"A table containing information about logical LAN
			destinations."
		::= { mitelRouterRipExtensionGroup 1 }


			mitelRipExtGrpIfConfEntry OBJECT-TYPE
				SYNTAX  MitelRipExtGrpIfConfEntry
				MAX-ACCESS  not-accessible
				STATUS  current
				DESCRIPTION
				        "The entries in this table provide additional
					information to the Rip2IfConf table from
					RFC 1724."
				INDEX   { rip2IfConfAddress }
				::= { mitelRipExtGrpIfConfTable 1 }


			MitelRipExtGrpIfConfEntry ::=
				SEQUENCE {
			        mitelIfConfTblSendDefaultRoutes
				        INTEGER,
					mitelIfConfTblRipType
						INTEGER,
					mitelIfConfTblRowStatus
						RowStatus
				}


			mitelIfConfTblSendDefaultRoutes OBJECT-TYPE
				SYNTAX  INTEGER {
							enable(1),
							disable(2)
						}
				MAX-ACCESS  read-write
				STATUS  current
				DESCRIPTION
					"This entry determines whether default routes
					 are sent with RIP information for this IP
					 address."
				::= { mitelRipExtGrpIfConfEntry 1 }

			mitelIfConfTblRipType OBJECT-TYPE
				SYNTAX  INTEGER {
						  rip(1),
						  triggerRip(2)
				                }
				MAX-ACCESS  read-only
				STATUS  current
				DESCRIPTION
					"This entry determines which type of RIP to use on this
					 IP address."
				::= { mitelRipExtGrpIfConfEntry 2 }


			mitelIfConfTblRowStatus OBJECT-TYPE
				SYNTAX  RowStatus
				MAX-ACCESS  read-create
				STATUS  current
				DESCRIPTION
					"The current status of this entry."
				REFERENCE "Textual Conventions for Version 2 of the
					Simple Network Management Protocol (RFC 1443)."
				::= { mitelRipExtGrpIfConfEntry 3 }

END

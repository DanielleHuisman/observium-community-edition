-- Copyright 1999 MITEL Corporation
-- All rights reserved.
-- This MITEL SNMP Management Information Base Specification
-- (Specification) embodies MITEL's confidential and
-- proprietary intellectual property. MITEL retains all
-- title and ownership in the Specification, including any
-- revisions.

-- This Specification is supplied "AS IS", and MITEL makes
-- no warranty, either express or implied, as to the use,
-- operation, condition, or performance of the Specification.


MITEL-ROUTERGROUP-MIB
	DEFINITIONS ::= BEGIN

IMPORTS
	MODULE-IDENTITY, OBJECT-TYPE, enterprises,
	Integer32, IpAddress
        FROM SNMPv2-SMI
    RowStatus
        FROM SNMPv2-TC;

mitelRouterIpRouterGroup   MODULE-IDENTITY
       LAST-UPDATED      "200303241045Z"
       ORGANIZATION      "MITEL Corporation"
       CONTACT-INFO      "Standards Group,
                          Postal:    MITEL Corporation
                          350 Legget Drive, PO Box 13089
                          Kanata, Ontario
                          Canada  K2K 1X3
                          Tel: +1 613 592 2122
                          Fax: +1 613 592 4784
                          E-mail: std@mitel.com"
       DESCRIPTION       "The MITEL Router MIB module."
       REVISION          "200303241045Z"
           DESCRIPTION   "Convert to SMIv2"
       REVISION          "199903010000Z"
           DESCRIPTION   "Router Table MIB Version 1.0"
::= { mitelIpNetRouter 5 }

mitel			   OBJECT IDENTIFIER ::= { enterprises 1027}
mitelProprietary 	   OBJECT IDENTIFIER ::= { mitel 4}
mitelPropIpNetworking      OBJECT IDENTIFIER ::= { mitelProprietary 8 }
mitelIpNetRouter           OBJECT IDENTIFIER ::= { mitelPropIpNetworking 1 }


--        Routing Entry Table
--        ============================================

    mitelIpRouteTable OBJECT-TYPE
        SYNTAX  SEQUENCE OF MitelIpRouteEntry
        MAX-ACCESS  not-accessible
        STATUS  current
        DESCRIPTION
                "This table is a list of IP Routing Entries."
        ::= { mitelRouterIpRouterGroup 1 }
-- The group name may not exist, will have to check it out.

        mitelIpRouteEntry OBJECT-TYPE
            SYNTAX  MitelIpRouteEntry
            MAX-ACCESS  not-accessible
            STATUS  current
            DESCRIPTION
                    "Each entry in this table contains information of an IP Route Entry."
            INDEX   { mitelIpRouteTblDestAddress, mitelIpRouteTblGateAddress }
            ::= { mitelIpRouteTable 1 }


        MitelIpRouteEntry ::=
            SEQUENCE {
		mitelIpRouteTblDestAddress
			IpAddress,
		mitelIpRouteTblGateAddress
			IpAddress,
		mitelIpRouteTblNetmaskAddress
			IpAddress,
		mitelIpRouteTblIfIndex
			INTEGER,
		mitelIpRouteTblMetric1
			Integer32,
		mitelIpRouteTblMetric2
			Integer32,
		mitelIpRouteTblMetric3
			Integer32,
		mitelIpRouteTblMetric4
			Integer32,
		mitelIpRouteTblMetric5
			Integer32,
      	mitelIpRouteTblRouteType
      		Integer32,
       	mitelIpRouteTblRouteProto
       		Integer32,
      	mitelIpRouteTblRouteAge
      		INTEGER,
		mitelIpRouteTblBlockLearning
			INTEGER,
		mitelIpRouteTblInUse
			INTEGER,
		mitelIpRouteTblDisableLearned
			INTEGER,
		mitelIpRouteTblConvertStatic
			INTEGER,
		mitelIpRouteTblRowStatus
			RowStatus
	}

        mitelIpRouteTblDestAddress OBJECT-TYPE
            SYNTAX  IpAddress
            MAX-ACCESS  read-write
            STATUS  current
            DESCRIPTION
                    "The IP address of the destination network"
            ::= { mitelIpRouteEntry 1 }

        mitelIpRouteTblGateAddress OBJECT-TYPE
            SYNTAX  IpAddress
            MAX-ACCESS  read-write
            STATUS  current
            DESCRIPTION
                    "The Destination Gateway IP address. "
            ::= { mitelIpRouteEntry 2 }

        mitelIpRouteTblNetmaskAddress OBJECT-TYPE
            SYNTAX  IpAddress
            MAX-ACCESS  read-write
            STATUS  current
            DESCRIPTION
                    "Specifies the netmask to apply to this network. "
            ::= { mitelIpRouteEntry 3 }

        mitelIpRouteTblIfIndex OBJECT-TYPE
            SYNTAX  INTEGER (2..13)
            MAX-ACCESS  read-write
            STATUS  current
            DESCRIPTION
                    "Specifies the IfIndex to use as a key into the table. 0 & 1 are not used "
            ::= { mitelIpRouteEntry 4 }

	mitelIpRouteTblMetric1 OBJECT-TYPE
            SYNTAX  Integer32
            MAX-ACCESS  read-write
            STATUS  current
            DESCRIPTION
                    "Metric 1"
            ::= { mitelIpRouteEntry 5 }

        mitelIpRouteTblMetric2 OBJECT-TYPE
            SYNTAX  Integer32
            MAX-ACCESS  read-write
            STATUS  current
            DESCRIPTION
                    "Metric 2"
            ::= { mitelIpRouteEntry 6 }

        mitelIpRouteTblMetric3 OBJECT-TYPE
            SYNTAX  Integer32
            MAX-ACCESS  read-write
            STATUS  current
            DESCRIPTION
                    "Metric 3"
            ::= { mitelIpRouteEntry 7 }

        mitelIpRouteTblMetric4 OBJECT-TYPE
            SYNTAX  Integer32
            MAX-ACCESS  read-write
            STATUS  current
            DESCRIPTION
                    "Metric 4"
            ::= { mitelIpRouteEntry 8 }

        mitelIpRouteTblMetric5 OBJECT-TYPE
            SYNTAX  Integer32
            MAX-ACCESS  read-write
            STATUS  current
            DESCRIPTION
                    "Metric 5"
            ::= { mitelIpRouteEntry 9 }

        mitelIpRouteTblRouteType OBJECT-TYPE
            SYNTAX  Integer32
            MAX-ACCESS  read-write
            STATUS  current
            DESCRIPTION
                    "Specifies what kind of route this is."
            ::= { mitelIpRouteEntry 10 }

        mitelIpRouteTblRouteProto OBJECT-TYPE
            SYNTAX  Integer32
            MAX-ACCESS  read-write
            STATUS  current
            DESCRIPTION
                    "Specifies what protocol to use for the routing table entry."
            ::= { mitelIpRouteEntry 11 }

        mitelIpRouteTblRouteAge OBJECT-TYPE
            SYNTAX  INTEGER (0..65535)
            MAX-ACCESS  read-write
            STATUS  current
            DESCRIPTION
                    "Specifies the age of the route entry in the table."
            ::= { mitelIpRouteEntry 12 }

        mitelIpRouteTblBlockLearning OBJECT-TYPE
            SYNTAX  INTEGER {enable(1), disable(2)}
            MAX-ACCESS  read-write
            STATUS  current
            DESCRIPTION
                    "If enabled will block the learned route in question"
            ::= { mitelIpRouteEntry 13 }

        mitelIpRouteTblInUse OBJECT-TYPE
            SYNTAX  INTEGER {enable(1), disable(2)}
            MAX-ACCESS  read-write
            STATUS  current
            DESCRIPTION
                    "Specifies whether this routing entry is in use or not"
            ::= { mitelIpRouteEntry 14 }

        mitelIpRouteTblDisableLearned OBJECT-TYPE
            SYNTAX  INTEGER {enable(1), disable(2)}
            MAX-ACCESS  read-write
            STATUS  current
            DESCRIPTION
                    "Determines whether learned routes should be disabled or not"
            ::= { mitelIpRouteEntry 15 }

        mitelIpRouteTblConvertStatic OBJECT-TYPE
            SYNTAX  INTEGER {enable(1), disable(2)}
            MAX-ACCESS  read-write
            STATUS  current
            DESCRIPTION
                    "An action to convert a learned route into a static route."
            ::= { mitelIpRouteEntry 16 }

        mitelIpRouteTblRowStatus OBJECT-TYPE
            SYNTAX  RowStatus
            MAX-ACCESS  read-create
            STATUS  current
            DESCRIPTION
                    "The current status of this entry. "
            ::= { mitelIpRouteEntry 17 }

END

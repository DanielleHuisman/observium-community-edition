-- Copyright 2002 MITEL Networks Corporation
-- All rights reserved.
-- This MITEL SNMP Management Information Base Specification
-- (Specification) embodies MITEL's confidential and
-- proprietary intellectual property. MITEL retains all
-- title and ownership in the Specification, including any
-- revisions.

-- This Specification is supplied "AS IS", and MITEL makes
-- no warranty, either express or implied, as to the use,
-- operation, condition, or performance of the Specification.


MITEL-VOICE-MAIL-MIB
DEFINITIONS ::= BEGIN

IMPORTS
	MODULE-IDENTITY, OBJECT-TYPE, enterprises,
    Integer32, Counter32, NOTIFICATION-TYPE
        FROM SNMPv2-SMI
    NOTIFICATION-GROUP
    	FROM SNMPv2-CONF;

mitelVoiceMail MODULE-IDENTITY
       LAST-UPDATED      "200204020000Z"
       ORGANIZATION      "MITEL Networks Corporation"
       CONTACT-INFO      "Standards Group,
                          Postal:    MITEL Corporation
                          350 Legget Drive, PO Box 13089
                          Kanata, Ontario
                          Canada  K2K 1X3
                          Tel: +1 613 592 2122
                          Fax: +1 613 592 4784
                          E-mail: std@mitel.com"
       DESCRIPTION       "The Mitel Application Monitor MIB."
       REVISION          "200203241149Z"
       	DESCRIPTION      "Convert to SMIv2"
       REVISION          "200204020000Z"
       	DESCRIPTION      "Mitel Voice Mail MIB version 1.0"
::= { mitelProprietary 10 }

mitel			   OBJECT IDENTIFIER ::= { enterprises 1027}
mitelProprietary 	   OBJECT IDENTIFIER ::= { mitel 4}


-- TRAPS
mitelIdentification 	  OBJECT IDENTIFIER ::= { mitel 1}
mitelIdCallServers 	  OBJECT IDENTIFIER ::= { mitelIdentification 2}
mitelIdCsIpera1000 	  OBJECT IDENTIFIER ::= { mitelIdCallServers 4}

	--************************************
	-- The mitelVoiceMail subtree...
	--************************************

--the Mitel Voice Mail Configuration Table


-- the Mitel Vocice Mail Fault Table

    mitelVoiceMailFaultTable     OBJECT-TYPE
        SYNTAX  SEQUENCE OF MitelVoiceMailFaultEntry
	    MAX-ACCESS  not-accessible
        STATUS  current
        DESCRIPTION
            "The Voice Mail Fault table."
        ::= { mitelVoiceMail 1 }

    mitelVoiceMailFaultEntry OBJECT-TYPE
             SYNTAX MitelVoiceMailFaultEntry
             MAX-ACCESS  not-accessible
             STATUS  current
             DESCRIPTION
                "An entry in the mitelVoiceMailFaultTable."
             INDEX   { mitelVoiceMailFaultTblIndex }
            ::= { mitelVoiceMailFaultTable 1 }

    MitelVoiceMailFaultEntry ::=
         SEQUENCE {
		 mitelVoiceMailFaultTblIndex	Integer32,
             mitelVoiceMailFaultId		INTEGER,
		 mitelVoiceMailFaultStatus	INTEGER,
 		 mitelVoiceMailFaultOccur	Counter32
	   }

    mitelVoiceMailFaultTblIndex OBJECT-TYPE
        SYNTAX           Integer32
        MAX-ACCESS           read-only
        STATUS           current
        DESCRIPTION
		"The index of the fault table."
        ::= { mitelVoiceMailFaultEntry 1 }

    mitelVoiceMailFaultId	OBJECT-TYPE
        SYNTAX INTEGER {
			voiceMailDiskNearlyFull(1),
			voiceMailDiskFull (2)
	 	   }
        MAX-ACCESS  read-only
        STATUS  current
        DESCRIPTION
            "The mitelVoiceMailFaultId indicates the id of the fault."
        ::= { mitelVoiceMailFaultEntry 2 }

    mitelVoiceMailFaultStatus		OBJECT-TYPE
        SYNTAX INTEGER {
			set(1),
			clear(2),
			message(3)
	 	   }
        MAX-ACCESS  read-only
        STATUS  current
        DESCRIPTION
            "The mitelVoiceMailFaultStatus indicates whether the fault is
 		 set or cleared or transient"
        ::= { mitelVoiceMailFaultEntry 3 }

    mitelVoiceMailFaultOccur		OBJECT-TYPE
        SYNTAX  Counter32
        MAX-ACCESS  read-only
        STATUS  current
        DESCRIPTION
            "The mitelVoiceMailFaultOccur indicates the occurence of
		 the fault since the last system restart"
            ::= { mitelVoiceMailFaultEntry 4 }

--
--  Notification Definitions
--
mitelIpera1000Notifications NOTIFICATION-GROUP
    NOTIFICATIONS	{ mitelVoiceMailDiskNearlyFullNotif, mitelVoiceMailDiskFullNotif }
    STATUS            current
    DESCRIPTION       "Call Server Ipera 1000 Notifications."
    ::= { mitelIdCsIpera1000 0 }

mitelVoiceMailDiskNearlyFullNotif NOTIFICATION-TYPE
	OBJECTS {	mitelVoiceMailFaultStatus,
			mitelVoiceMailFaultOccur }
	STATUS current
	DESCRIPTION
		"The mitelVoiceMailDiskNearlyFullNotif trap indicates
		 that the disk for voice mail is nearly full."
	::= { mitelIpera1000Notifications 408 }

mitelVoiceMailDiskFullNotif NOTIFICATION-TYPE
	OBJECTS {	mitelVoiceMailFaultStatus,
			mitelVoiceMailFaultOccur }
	STATUS current
	DESCRIPTION
		"The mitelVoiceMailDiskFullNotif trap indicates
		 that the disk device for voice mail is full."
	::= { mitelIpera1000Notifications 409 }


 END -- MITEL-VOICE-MAIL-MIB

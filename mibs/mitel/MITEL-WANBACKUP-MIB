-- Copyright 2001 MITEL Corporation
-- All rights reserved.
-- This MITEL SNMP Management Information Base Specification
-- (Specification) embodies MITEL's confidential and
-- proprietary intellectual property. MITEL retains all
-- title and ownership in the Specification, including any
-- revisions.

-- This Specification is supplied "AS IS", and MITEL makes
-- no warranty, either express or implied, as to the use,
-- operation, condition, or performance of the Specification.

MITEL-WANBACKUP-MIB
DEFINITIONS ::= BEGIN

IMPORTS
	MODULE-IDENTITY, OBJECT-TYPE, enterprises,
    Integer32, IpAddress
    	FROM SNMPv2-SMI
    RowStatus
        FROM SNMPv2-TC;

mitelIpGrpBackupWANGroup    MODULE-IDENTITY
       LAST-UPDATED      "200303241103Z"
       ORGANIZATION      "MITEL Corporation"
       CONTACT-INFO      "Standards Group,
                          Postal:    MITEL Corporation
                          350 Legget Drive, PO Box 13089
                          Kanata, Ontario
                          Canada  K2K 1X3
                          Tel: +1 613 592 2122
                          Fax: +1 613 592 4784
                          E-mail: std@mitel.com"
       DESCRIPTION       "The MITEL IP MIB module."
       REVISION          "200303241103Z"
           DESCRIPTION   "IP MIB Version 1.0"
       REVISION          "199903010000Z"
           DESCRIPTION   "IP MIB Version 1.0"
::= { mitelRouterIpGroup 6 }

mitel			   OBJECT IDENTIFIER ::= { enterprises 1027}
mitelProprietary 	   OBJECT IDENTIFIER ::= { mitel 4}
mitelPropIpNetworking      OBJECT IDENTIFIER ::= { mitelProprietary 8 }
mitelIpNetRouter           OBJECT IDENTIFIER ::= { mitelPropIpNetworking 1 }
mitelRouterIpGroup	   OBJECT IDENTIFIER ::= { mitelIpNetRouter 1 }


--        WAN Ethernet Backup Application GROUP OBJECTS
--        =============================================

    mitelBackupWANDestIndex OBJECT-TYPE
        SYNTAX  Integer32
        MAX-ACCESS  read-only
        STATUS  current
        DESCRIPTION
                "Identifies the destination used to backup WAN Ethernet
			connection."
        ::= { mitelIpGrpBackupWANGroup 1 }


    mitelBackupWANEnable OBJECT-TYPE
        SYNTAX  INTEGER {
				enabled(1),
				disabled(2)
				}
        MAX-ACCESS  read-write
        STATUS  current
        DESCRIPTION
                "Enables or disables the backup WAN Ethernet
application."
        ::= { mitelIpGrpBackupWANGroup 2 }

    mitelBackupWANPollFreq OBJECT-TYPE
        SYNTAX  INTEGER (1..60)
        MAX-ACCESS  read-write
        STATUS  current
        DESCRIPTION
                "This object tells the WAN Ethernet application how
often it polls the destination. "
        -- DEFAULT {5}
        ::= { mitelIpGrpBackupWANGroup 3  }

    mitelBackupWANLinkStatus OBJECT-TYPE
        SYNTAX  INTEGER {
				active(1),
				down(2)
				}
        MAX-ACCESS  read-only
        STATUS  current
        DESCRIPTION
                "Shows whether the backup is up and running, or down. "
        ::= { mitelIpGrpBackupWANGroup 4  }

--        WAN Ethernet Backup Application Server Table
--        ============================================

    mitelBackupWANServerTable OBJECT-TYPE
        SYNTAX  SEQUENCE OF MitelBackupWANServerEntry
        MAX-ACCESS  not-accessible
        STATUS  current
        DESCRIPTION
                "This table is a list of servers the Backup WAN
application monitors."
        ::= { mitelIpGrpBackupWANGroup 5 }


        mitelBackupWANServerEntry OBJECT-TYPE
            SYNTAX  MitelBackupWANServerEntry
            MAX-ACCESS  not-accessible
            STATUS  current
            DESCRIPTION
                    "Each entry in this table contains information of a
server."
            INDEX   { mitelBackupWANServerIPAddr }
            ::= { mitelBackupWANServerTable 1 }


        MitelBackupWANServerEntry ::=
            SEQUENCE {
               mitelBackupWANServerIPAddr
                  IpAddress,
               mitelBackupWANServerSubnetAddr
                  IpAddress,
               mitelBackupWANServerPrimary
                  INTEGER,
               mitelBackupWANServerStatus
                  RowStatus
            }


        mitelBackupWANServerIPAddr OBJECT-TYPE
            SYNTAX  IpAddress
            MAX-ACCESS  read-write
            STATUS  current
            DESCRIPTION
                    "The IP address of the destination. It is used by
the Backup WAN Ethernet application to send monitoring
requests to. "
            ::= { mitelBackupWANServerEntry 1 }

        mitelBackupWANServerSubnetAddr OBJECT-TYPE
            SYNTAX  IpAddress
            MAX-ACCESS  read-write
            STATUS  current
            DESCRIPTION
                    "The subnet address of the destination. "
            ::= { mitelBackupWANServerEntry 2 }

        mitelBackupWANServerPrimary OBJECT-TYPE
            SYNTAX  INTEGER {
				primary(1),
				secondary(2)
				}
            MAX-ACCESS  read-write
            STATUS  current
            DESCRIPTION
                    "Specifies whether this server is primary. "
            ::= { mitelBackupWANServerEntry 3 }

        mitelBackupWANServerStatus OBJECT-TYPE
            SYNTAX  RowStatus
            MAX-ACCESS  read-create
            STATUS  current
            DESCRIPTION
                    "The current status of this entry. "
            ::= { mitelBackupWANServerEntry 4 }

END

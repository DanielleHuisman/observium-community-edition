--$Author: klewis $
--$Date: 09/01/2013 $
--Revision 1.0 
--
-- MONNIT-EGW-MIB
-- Title: MONNIT TOP LEVEL MIB FOR EGW

-- ************************************************************************
-- ************************************************************************
-- ************************************************************************
-- MONNIT-EGW-MIB { iso org(3) dod(6) internet(1) private(4)
--    enterprises(1) Monnit(41542) Product(1) EGW512(10)/TRAPARGS(110)}
-- 3.6.1.4.1.41542.1.10/110
 
MONNIT-EGW-MIB DEFINITIONS ::= BEGIN

IMPORTS
	OBJECT-TYPE		FROM RFC-1212
	TRAP-TYPE		FROM RFC-1215
	enterprises		FROM RFC1155-SMI
	DisplayString	FROM RFC1213-MIB;
	

	
Monnit				OBJECT IDENTIFIER ::= { enterprises 41542 }
EGW512				OBJECT IDENTIFIER ::= { Monnit 1 }
EGWData				OBJECT IDENTIFIER ::= { EGW512 10 }
EGWTrapArgs			OBJECT IDENTIFIER ::= { EGW512 20 }


-- ************************************************************************
-- Sections
-- ************************************************************************
GW-Section			OBJECT IDENTIFIER ::=  { EGWData 1 }
WNet-Section		OBJECT IDENTIFIER ::=  { EGWData 2 }


-- ************************************************************************
-- Gateway table
-- ************************************************************************
GWSerial	OBJECT-TYPE
	SYNTAX	GAUGE 
	ACCESS	read-only
	STATUS	mandatory
	DESCRIPTION	"Serial number of the Wireless Ethernet Gateway"
	::= { GW-Section 1 }

Version		OBJECT-TYPE
	SYNTAX	INTEGER
	ACCESS	read-only
	STATUS	mandatory
	DESCRIPTION	"Gateway firmware version"
	::= { GW-Section 2 }
	
WDCount		OBJECT-TYPE
	SYNTAX	INTEGER
	ACCESS	read-only
	STATUS	mandatory
	DESCRIPTION	"Total number of sensors registered on this gateway's data interfaces"
	::= { GW-Section 3 }


	
-- ************************************************************************
-- Sensor array table
-- ************************************************************************

WDTable		OBJECT-TYPE
	SYNTAX	SEQUENCE OF	WDEntry
	ACCESS	not-accessible
	STATUS	mandatory
	DESCRIPTION	"A List of Wireless Device Entries"
	::= { WNet-Section 1 }

WD-Entry		OBJECT-TYPE
	SYNTAX	WDEntry
	ACCESS	not-accessible
	STATUS	mandatory
	DESCRIPTION	"A Wireless Device Entry"
	INDEX { Index }
	::= { WDTable 1 }

WDEntry ::=
	SEQUENCE {
		Index		INTEGER,
		Serial		INTEGER,
		Type		INTEGER,
		Age			INTEGER,
		Active		INTEGER,
		Alarming	INTEGER,
		Voltage		INTEGER,
		RFSignal	INTEGER,
		Data1		INTEGER,
		Data2		INTEGER,
		Data3		INTEGER,
		Data4		INTEGER,
		Data5		INTEGER,
		Data6		INTEGER,
		Data7		INTEGER,
		Data8		INTEGER
	}

Index		OBJECT-TYPE
	SYNTAX	INTEGER (1..512)
	ACCESS	read-only
	STATUS	mandatory
	DEFVAL	{ 0 }
	DESCRIPTION	"The index for the specific wireless device 1..512"
	::= { WD-Entry 1 }

Serial		OBJECT-TYPE
	SYNTAX	GAUGE 
	ACCESS	read-only
	STATUS	mandatory
	DEFVAL	{ 0 }
	DESCRIPTION	"Serial number of wireless device"
	::= { WD-Entry 2 }

Type		OBJECT-TYPE
	SYNTAX	INTEGER
	ACCESS	read-only
	STATUS	mandatory
	DEFVAL	{ 0 }
	DESCRIPTION	"Numerical NodeType of the of wireless device"
	::= { WD-Entry 3 }

Age			OBJECT-TYPE
	SYNTAX	INTEGER
	ACCESS	read-only
	STATUS	mandatory
	DEFVAL	{ 0 }
	DESCRIPTION	"Number of seconds from the last wireless communication"
	::= { WD-Entry 4 }

Active		OBJECT-TYPE
	SYNTAX	INTEGER
	ACCESS	read-only
	STATUS	mandatory
	DEFVAL	{ 0 }
	DESCRIPTION	"Value depicting if the Wireless device is actively connected (1) and delivering data."
	::= { WD-Entry 5 }

Alarming	OBJECT-TYPE
	SYNTAX	INTEGER
	ACCESS	read-only
	STATUS	mandatory
	DEFVAL	{ 0 }
	DESCRIPTION	"Value depicting if the Wireless device is actively alarming(1)."
	::= { WD-Entry 6 }

Voltage		OBJECT-TYPE
	SYNTAX	INTEGER
	ACCESS	read-only
	STATUS	mandatory
	DESCRIPTION	"Battery voltage on the wireless device in mV"
	DEFVAL	{ 0 }
	::= { WD-Entry 7 }

RFSignal	OBJECT-TYPE
	SYNTAX	INTEGER
	ACCESS	read-only
	STATUS	mandatory
	DESCRIPTION	"Percentage of available wireless signal"
	DEFVAL	{ 0 }
	::= { WD-Entry 8 }

Data1		OBJECT-TYPE
	SYNTAX	INTEGER
	ACCESS	read-only
	STATUS	mandatory
	DESCRIPTION	"Data value 1 on wireless device"
	DEFVAL	{ 0 }
	::= { WD-Entry 9 }

Data2		OBJECT-TYPE
	SYNTAX	INTEGER
	ACCESS	read-only
	STATUS	mandatory
	DESCRIPTION	"Data value 2 on wireless device"
	DEFVAL	{ 0 }
	::= { WD-Entry 10 }

Data3		OBJECT-TYPE
	SYNTAX	INTEGER
	ACCESS	read-only
	STATUS	mandatory
	DESCRIPTION	"Data value 3 on wireless device"
	DEFVAL	{ 0 }
	::= { WD-Entry 11 }

Data4		OBJECT-TYPE
	SYNTAX	INTEGER
	ACCESS	read-only
	STATUS	mandatory
	DESCRIPTION	"Data value 4 on wireless device"
	DEFVAL	{ 0 }
	::= { WD-Entry 12 }

Data5		OBJECT-TYPE
	SYNTAX	INTEGER
	ACCESS	read-only
	STATUS	mandatory
	DESCRIPTION	"Data value 5 on wireless device"
	DEFVAL	{ 0 }
	::= { WD-Entry 13 }

Data6		OBJECT-TYPE
	SYNTAX	INTEGER
	ACCESS	read-only
	STATUS	mandatory
	DESCRIPTION	"Data value 6 on wireless device"
	DEFVAL	{ 0 }
	::= { WD-Entry 14 }

Data7		OBJECT-TYPE
	SYNTAX	INTEGER
	ACCESS	read-only
	STATUS	mandatory
	DESCRIPTION	"Data value 7 on wireless device"
	DEFVAL	{ 0 }
	::= { WD-Entry 15 }

Data8	OBJECT-TYPE
	SYNTAX	INTEGER
	ACCESS	read-only
	STATUS	mandatory
	DESCRIPTION	"Data value 8 on wireless device"
	DEFVAL	{ 0 }
	::= { WD-Entry 16 }


-- ************************************************************************
-- Trap Identifiers
-- ************************************************************************

egw512trap-desc	OBJECT-TYPE
	SYNTAX	DisplayString
	ACCESS	read-only
	STATUS	mandatory
	DESCRIPTION	"This OID defines a Trap String"
	::= { EGWTrapArgs 1 }

GW-online TRAP-TYPE
	ENTERPRISE Monnit
	VARIABLES { egw512trap-desc }
	DESCRIPTION "EGW SNMP Interface Active"
   --#TYPE "EGW Active"
   --#SUMMARY "Ethernet Gateway SNMP Interface Online"
   --#SEVERITY NORMAL
   --#TIMEINDEX 1
   --#HELP ""
   --#HELPTAG 0
   --#STATE OPERATIONAL 
	::= 1

WD-online TRAP-TYPE
	ENTERPRISE Monnit
	VARIABLES { egw512trap-desc }
	DESCRIPTION "Wireless Device Active"
   --#TYPE "WD Active"
   --#SUMMARY "Wireless Device Active"
   --#SEVERITY NORMAL
   --#TIMEINDEX 1
   --#HELP ""
   --#HELPTAG 0
   --#STATE OPERATIONAL 
	::= 2

WD-report-alarm TRAP-TYPE
	ENTERPRISE Monnit
	VARIABLES { egw512trap-desc }
	DESCRIPTION "Description of environmental input alarm"
   --#TYPE "WD Environmental Alarm"
   --#SUMMARY "wireless device is alarming"
   --#SEVERITY MAJOR
   --#TIMEINDEX 1
   --#HELP ""
   --#HELPTAG 0
   --#STATE OPERATIONAL 
	::= 3

WD-report-normal TRAP-TYPE
	ENTERPRISE Monnit
	VARIABLES { egw512trap-desc }
	DESCRIPTION "Description of environmental input alarm"
   --#TYPE "WD Environmental REPORT"
   --#SUMMARY "Wireless device has returned to normal"
   --#SEVERITY NORMAL
   --#TIMEINDEX 1
   --#HELP ""
   --#HELPTAG 0
   --#STATE OPERATIONAL 
	::= 4

END

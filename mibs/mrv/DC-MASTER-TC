DC-MASTER-TC DEFINITIONS ::= BEGIN
   IMPORTS
       MODULE-IDENTITY, Unsigned32,
       enterprises, Integer32                        FROM SNMPv2-SMI
       TEXTUAL-CONVENTION               FROM SNMPv2-TC;

  dcMasterTc MODULE-IDENTITY
      LAST-UPDATED "201412210000Z"  -- December 21, 2014
      ORGANIZATION "MRV Communications."
      CONTACT-INFO
                   "For technical support, please contact your service channel"
      DESCRIPTION  "The set of common Textual Conventions for use in all DCL
                    MIBs."

    -- Revision history
      REVISION     "201412210000Z"  -- December 21, 2014
      DESCRIPTION
        "Initial edition."


  ::= { opx 13 }

nbase                      OBJECT IDENTIFIER ::= { enterprises 629 }
opx                      OBJECT IDENTIFIER ::= { nbase 10 }

--Common Textual Conventions

AdminStatus ::= TEXTUAL-CONVENTION
    STATUS      current
    DESCRIPTION
       "The desired administrative state of a MIB row."
    SYNTAX      INTEGER {
                  adminStatusUp(1),
                  adminStatusDown(2)
                }

OperStatus ::= TEXTUAL-CONVENTION
    STATUS      current
    DESCRIPTION
            "The current operational state of a MIB row.  This set of values
            is used by many Data Connection products written before 2006."
    SYNTAX      INTEGER {
                  operStatusUp(1),          -- active
                  operStatusDown(2),        -- inactive
                  operStatusGoingUp(3),     -- activating
                  operStatusGoingDown(4),   -- deactivating
                  operStatusActFailed(5)    -- activation failed
                }

BaseOperStatus ::= TEXTUAL-CONVENTION
    STATUS      current
    DESCRIPTION
            "The current operational state of a MIB row.  This is a complete
            set of values used by all Data Connection products."
    SYNTAX      INTEGER {
                  operStatusUp(1),          -- active
                  operStatusDown(2),        -- inactive
                  operStatusGoingUp(3),     -- activating
                  operStatusGoingDown(4),   -- deactivating
                  operStatusActFailed(5),   -- activation failed
                  operStatusQuiescing(6),   -- quiescing, allowing row use to
                                            --   cease
                  operStatusNotReady(7),    -- not ready to activate
                  operStatusFailed(8),      -- failed, will recover when
                                            --   possible
                  operStatusPrntFailed(9),  -- a parent or grandparent has
                                            --   failed
                  operStatusFailedPerm(10), -- operator intervention required
                  operStatusFailing(11)     -- failure in progress
                }

NpgOperStatus ::= TEXTUAL-CONVENTION
    STATUS      current
    DESCRIPTION
            "The current operational state of a MIB row.  This set of values
            has been used by the Data Connection Networking Protocols Group
            since 2006."
    SYNTAX      INTEGER {
                  operStatusUp(1),          -- active
                  operStatusDown(2),        -- inactive
                  operStatusGoingUp(3),     -- activating
                  operStatusGoingDown(4),   -- deactivating
                  operStatusActFailed(5),   -- activation failed
                  operStatusFailed(8),      -- failed, will recover when
                                            --   possible
                  operStatusFailedPerm(10), -- operator intervention required
                  operStatusFailing(11)     -- failure in progress
                }

Unsigned32NonZero ::= TEXTUAL-CONVENTION
  STATUS       current
  DESCRIPTION
     "A non-zero Unsigned32."
  SYNTAX       Unsigned32 (1..'FFFFFFFF'h)

NumericIndex ::= TEXTUAL-CONVENTION
  STATUS      current
  DESCRIPTION "A numeric index value or identifier."
  SYNTAX      Integer32 (1..'7FFFFFFF'h)

NumericIndexOrZero ::= TEXTUAL-CONVENTION
  STATUS      current
  DESCRIPTION "Either a numeric index value or identifier, or the value zero
               with a special meaning defined by the object description.  Do
               not use this TC for MIB table index objects.  Zero is not valid
               for such objects."
  SYNTAX      Integer32 (0..'7FFFFFFF'h)

EntityIndex ::= TEXTUAL-CONVENTION
  STATUS      current
  DESCRIPTION "The HAF entity index value identifying a DC software entity.
              This TC is deprecated.  Use NumericIndex for all indexes."
  SYNTAX      Integer32 (1..2147483647)

EntityIndexOrZero ::= TEXTUAL-CONVENTION
  STATUS      current
  DESCRIPTION "The HAF entity index value identifying a DC software entity, or
               zero which is used to indicate that the entity is not present.
               This TC is deprecated.  Use NumericIndexOrZero for all
               references to indexes."
  SYNTAX      Integer32 (0..2147483647)

AuthUserDataString ::= TEXTUAL-CONVENTION
  STATUS      current
  DESCRIPTION "A string of user data that will be passed to the a0auth
               interface."
  SYNTAX      OCTET STRING (SIZE (0..160))

StdAccessListListIndex ::= TEXTUAL-CONVENTION
  STATUS      current
  DESCRIPTION "An arbitrary index value identifying a standard access
              list."
  SYNTAX      Integer32 (1..2147483647)

StdAccessListListIndexOrZero ::= TEXTUAL-CONVENTION
  STATUS      current
  DESCRIPTION "An arbitrary index value identifying a standard access
              list or zero for no access list."
  SYNTAX      Integer32 (0..2147483647)

StdAccessListRuleIndex ::= TEXTUAL-CONVENTION
  STATUS      current
  DESCRIPTION "An index value identifying a particular rule within a
              standard access list.  Rules are tested in order of
              increasing rule index."
  SYNTAX      Integer32 (1..2147483647)

ExtAccessListListIndex ::= TEXTUAL-CONVENTION
  STATUS      current
  DESCRIPTION "An arbitrary index value identifying an extended access
              list."
  SYNTAX      Integer32 (1..2147483647)

ExtAccessListListIndexOrZero ::= TEXTUAL-CONVENTION
  STATUS      current
  DESCRIPTION "An arbitrary index value identifying an extended access
              list or zero for no access list."
  SYNTAX      Integer32 (0..2147483647)

ExtAccessListRuleIndex ::= TEXTUAL-CONVENTION
  STATUS      current
  DESCRIPTION "An index value identifying a particular rule within an
              extended access list.  Rules are tested in order of
              increasing rule index."
  SYNTAX      Integer32 (1..2147483647)

RouteAction ::= TEXTUAL-CONVENTION
  STATUS       current
  DESCRIPTION
       "Action to perform on receipt of a packet which matches the
        destination for a static route.  This is one of:

         -  forward the packet to the address specified as the
            next-hop address

         -  handle the packet locally

         -  reject [drop and send ICMP]

         -  discard [drop but do not send ICMP]

         -  forward the packet using a tunnel."
    SYNTAX    INTEGER {
                routeActionLocal(1),
                routeActionForward(2),
                routeActionReject(3),
                routeActionDiscard(4),
                routeActionTunnel(5)
              }

AdminDistance ::= TEXTUAL-CONVENTION
  STATUS       current
  DESCRIPTION
       "The adminstrative distance used in prioritizing routes from
        different sources when selecting active routes in DC-RTM.
        The active route is chosen from those available routes which
        have the lowest associated administrative distance."
  SYNTAX       Integer32 (0..255)

PathType ::= TEXTUAL-CONVENTION
  STATUS       current
  DESCRIPTION "Protocol-specific path type."
  SYNTAX      INTEGER {
              pathTypeNone(0),                     -- None
              pathTypeOther(65536),                -- Other
              pathTypeConnected(131072),           -- Connected
              pathTypeConfiguredLocal(131073),     -- Configured Local
              pathTypeConfiguredConnected(131074), -- Configured Connected
              pathTypeStatic(196608),              -- Static
              pathTypeIcmp(262144),                -- ICMP
              pathTypeEgp(327680),                 -- Exterior Gateway Protocol
              pathTypeGgp(393216),                 -- GGP
              pathTypeHello(458752),               -- FuzzBall HelloSpeak
              pathTypeRip(524288),                 -- RIP route
              pathTypeIsisLevel1Int(589824),       -- IS-IS internal level 1
              pathTypeIsisLevel2Int(589825),       -- IS-IS internal level 2
              pathTypeIsisLevel1Ext(589826),       -- IS-IS external level 1
              pathTypeIsisLevel2Ext(589827),       -- IS-IS external level 2
              pathTypeEsis(655360),                -- ESIS route
              pathTypeIgrp(720896),                -- IGRP route
              pathTypeBbnspfigp(786432),           -- BBNSPFIGP route
              pathTypeOspfIntraArea(851968),       -- OSPF Intra-area route
              pathTypeOspfInterArea(851969),       -- OSPF Inter-area route
              pathTypeOspfType1Ext(851970),        -- OSPF exterior type 1
              pathTypeOspfType2Ext(851971),        -- OSPF exterior type 2
              pathTypeBgpInt(917504),              -- BGP Internal
              pathTypeBgpExt(917505),              -- BGP External
              pathTypeBgpVpn(917506),              -- BGP VPN route
              pathTypeIdpr(983040),                -- IDPR route
              pathTypeEigrp(1048576),              -- EIGRP summary route
              pathTypeEigrpInt(1048577),           -- EIGRP internal route
              pathTypeEigrpExt(1048578),           -- EIGRP external route
              pathTypeDvmrp(1114112)               -- DVMRP route
              }

EntityProcType ::= TEXTUAL-CONVENTION
  STATUS       current
  DESCRIPTION "Control plane entity component type."
  SYNTAX      INTEGER {
              entityRsvp(553779200),             -- 0x21020000 PCT_RRI
              entityLdpSc(587268096),            -- 0x23010000 PCT_RCS
              entityRtm(1023475712),             -- 0x3D010000 PCT_QCRT
              entityOspfPm(1040252928),          -- 0x3E010000 PCT_QOPM
              entityOspfNm(1040318464),          -- 0x3E020000 PCT_QONM
              entityIsisPm(1057030144),          -- 0x3F010000 PCT_QIPM
              entityIsisSdc(1057095680),         -- 0x3F020000 PCT_QISC
              entityBgpRm(1090584576),           -- 0x41010000 PCT_QBRM
              entityBgpNm(1090650112),           -- 0x41020000 PCT_QBNM
              entityRipPm(1174470656),           -- 0x46010000 PCT_QRPM
              entityOspfv3Pm(1241579520),        -- 0x4A010000 PCT_QOP3
              entityOspfv3Nm(1241645056)         -- 0x4A020000 PCT_QON3
              }

InetSubAddressType ::= TEXTUAL-CONVENTION
  STATUS      current
  DESCRIPTION "A value that represents a subsequent type of Internet address."
  SYNTAX      INTEGER {
              none(0),                     -- Subsequent type is unspecified
              unicast(1),                  -- Unicast
              multicast(2)                 -- Multicast
              }

BfdSessionStatus ::= TEXTUAL-CONVENTION
  STATUS      current
  DESCRIPTION "The current BFD session state of a peer."
  SYNTAX      INTEGER {
              bfdSessNotRequired(0),    -- not required
              bfdSessInitial(1),        -- initial
              bfdSessActivating(2),     -- activating
              bfdSessActive(3),         -- active
              bfdSessInactive(4),       -- inactive
              bfdSessAdminDown(5),      -- admin down
              bfdSessNoContact(6)       -- no contact
              }

IgpShortcutMetricType ::= TEXTUAL-CONVENTION
  STATUS       current
  DESCRIPTION
       "Type of metric value.  This is one of:

         -  Absolute, or fixed; the metric value defined is used as
            a path cost.

         -  Relative; the metric value defined is added to an existing
            path cost to produce the total cost of a path.
            Note that, in this case, the metric value defined may be zero,
            positive or negative."
    SYNTAX    INTEGER {
                metricTypeAbsolute(1),
                metricTypeRelative(2)
              }

IfOperStatus ::= TEXTUAL-CONVENTION
  STATUS       current
  DESCRIPTION
       "The IfOperStatus as defined in RFC 2863."
    SYNTAX  INTEGER {
                up(1),        -- ready to pass packets
                down(2),
                testing(3),   -- in some test mode
                unknown(4),   -- status can not be determined
                              -- for some reason.
                dormant(5),
                notPresent(6),    -- some component is missing
                lowerLayerDown(7) -- down due to state of
                                  -- lower-layer interface(s)
            }

MjStatus ::= TEXTUAL-CONVENTION
  STATUS      current
  DESCRIPTION "The status of a Master Join."
  SYNTAX      INTEGER {
                mjNotJoined(1),        -- initial state of join / received AHL_MJ_ACT_JOIN_GONE callback
                mjSentAddJoin(2),      -- sent ATG_FT_ADD_JOIN to System Manager
                mjSentRegister(3),     -- sent registration signal to slave
                mjJoinActive(4),       -- join is active
                mjSentUnregister(5),   -- sent unregistration signal to slave
                mjSentDelJoin(6),      -- sent ATG_FT_DELETE_JOIN to System Manager
                mjFailedToAdd(7),      -- AHL_MJ_ADD_JOIN failed
                mjFailedToRegister(8), -- slave rejected registration message
                mjFailingOver(9),      -- slave is failing over
                mjFailed(10),          -- slave has failed
                mjUnavailable(11)      -- slave is unavailable.
              }

SjStatus ::= TEXTUAL-CONVENTION
  STATUS      current
  DESCRIPTION "The status of a Slave Join."
  SYNTAX      INTEGER {
                sjNotJoined(1),        -- initial state of join / received AHL_SJ_ACT_JOIN_GONE callback
                sjJoined(2),           -- new join callback succeeded
                sjRcvdRegister(3),     -- received REGISTER signal from master
                sjJoinActive(4),       -- join is active
                sjFailingOver(5),      -- slave is failing over
                sjFailed(6),           -- slave join has failed
                sjRcvdUnregister(7),   -- received UNREGISTER signal from master
                sjUnregDone(8)         -- made AHL_MJ_UNREG_DONE request and sent UNREGISTER response
              }

InterfaceScope ::= TEXTUAL-CONVENTION
  STATUS      current
  DESCRIPTION "The scope of an interface or interface user.

               When components request information about interfaces, the
               request includes the scope of information that the component
               wishes to receive.  Only interfaces with matching scope are
               distributed to the component.

               This is an opaque structure that maps to an ATG_IF_SCOPE_ID.
               See the definition of ATG_IF_SCOPE_ID for details."
  SYNTAX      OCTET STRING (SIZE (0..3))

END

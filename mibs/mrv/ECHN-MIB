--  =======================================================================
--  File        : ethchn.mib
--  Description : Private Ethernet Channel (Port Trunking) MIB for NBase Switch Communications
--                Ethernet Switches
--  By          : Alex Ruzin
--  Version     : $Revision: 1.1.1.1 $
--  Date        : $Date: 2002/03/19 13:41:54 $
--  =======================================================================
--
--
-- Copyright (c) 1995 NBase Switch Communications.  All Rights Reserved.
--
-- Reproduction of this document is authorized on condition that this
-- copyright notice is included.  This NBase SNMP MIB Specification
-- embodies NBase's proprietary intellectual property.  NBase
-- retains all title and ownership in the specification, including any
-- revisions.
--
-- It is NBase's intent to encourage the widespread use of this
-- specification in connection with the management of NBase's
-- products. NBase grants vendor, end-users, and other interested
-- parties a non-exclusive license to use this specification in
-- connection with the management of NBase's products.
--
-- This specification is supplied "AS IS," and NBase makes no
-- warranty, either express or implied, as to the use, operation,
-- condition, or performance of the specification.
--
-- Copyright text courtesy of S. Rotenstein.
--
-- If you have any questions about this MIB, please call NBase
-- Technical Support Center at 1-800-858-7815 from inside USA or
-- 1-818-773-0900 from outside USA.
--
--
-- NBase retains the right to change this MIB without notification.
--
--
ECHN-MIB DEFINITIONS ::= BEGIN

        IMPORTS
                enterprises						FROM RFC1155-SMI
                nbSwitchG1Il          FROM OS-COMMON-TC-MIB
                OBJECT-TYPE						FROM RFC-1212;
          
-- ************************************************************
-- Object Identifiers Definition
-- ************************************************************

nbsEthChn	OBJECT IDENTIFIER ::= { nbSwitchG1Il 5 }

-- GROUPS in PTRUNK-MIB

nbsEthChnRun 	OBJECT IDENTIFIER ::= { nbsEthChn 1 }
nbsEthChnPerm	OBJECT IDENTIFIER ::= { nbsEthChn 2 }
nbsEthChnPoss	OBJECT IDENTIFIER ::= { nbsEthChn 3 }


-- ************************************************************
-- Ethernet Channel   Common  Data Base
-- ************************************************************

nbsEthChnEnable  OBJECT-TYPE
	SYNTAX  INTEGER {
		enable (1),     -- the Ethernet Channel feature is Enabled
		disable(2)      -- the Ethernet Channel feature is Disabled
        }
	ACCESS  read-only
        STATUS  mandatory
        DESCRIPTION
                "Ethernet Channel enable/disable mode of device"
        ::= { nbsEthChn 4 }

nbsEthChnPossNum  OBJECT-TYPE
        SYNTAX  INTEGER
        ACCESS  read-only
        STATUS  mandatory
        DESCRIPTION
                "Maximum Possible number of the Group for Ethernet Channels constructing."
        ::= { nbsEthChn 5 }

nbsEthChnMaxNum  OBJECT-TYPE
        SYNTAX  INTEGER
        ACCESS  read-only
        STATUS  mandatory
        DESCRIPTION
                "Maximum Real number of Ethernet Channels that may be constructed."
        ::= { nbsEthChn 6 }

nbsEthChnRunNum  OBJECT-TYPE
        SYNTAX  INTEGER
        ACCESS  read-only
        STATUS  mandatory
        DESCRIPTION
                "Real number of the Ethernet Channels in the RUN Data Base."
        ::= { nbsEthChn 7 }

nbsEthChnPermNum  OBJECT-TYPE
        SYNTAX  INTEGER
        ACCESS  read-only
        STATUS  mandatory
        DESCRIPTION
                "Real number of the Ethernet Channels in the PERM Data Base."
        ::= { nbsEthChn 8 }
        
		-- nbsEthChnRun group

-- ************************************************************
-- The Ethernet Channel  RUN Data Base
-- ************************************************************

nbsEthChnRunTable OBJECT-TYPE
        SYNTAX  SEQUENCE OF NbsEthChnRunEntry
        ACCESS  not-accessible
        STATUS  mandatory
        DESCRIPTION
                "A list of the current Ethernet Channels
                 defined. Number of entries is given by nbsEthChnMaxNum"
        ::= { nbsEthChnRun 1 }

nbsEthChnRunEntry  OBJECT-TYPE
        SYNTAX  NbsEthChnRunEntry
        ACCESS  not-accessible
        STATUS  mandatory
        DESCRIPTION
                "Contains the descriptor of a Ethernet Channel."
        INDEX { nbsEthChnRunIndex }
        ::= { nbsEthChnRunTable 1 }


NbsEthChnRunEntry ::= SEQUENCE {
        nbsEthChnRunIndex     		INTEGER,
        nbsEthChnRunStatus    		INTEGER,
	nbsEthChnRunList		OCTET STRING,
	nbsEthChnRunLinkList		OCTET STRING
        }

nbsEthChnRunIndex  OBJECT-TYPE
        SYNTAX  INTEGER
        ACCESS  read-only
        STATUS  mandatory
        DESCRIPTION
                "The serial number of this entry in the nbsEthChnRunTbl.
                 It may range from 1 to the value of nbsEthChnsRunMaxNum."
        ::= { nbsEthChnRunEntry 1 }

nbsEthChnRunStatus  OBJECT-TYPE
        SYNTAX  INTEGER {
                valid  (1),     -- the entry is valid and active
                invalid(2)      -- the entry is invalid
        }
        ACCESS  read-write
        STATUS  mandatory
        DESCRIPTION
                "The object is used to create/delete entries in the
                 nbsEthChnRunTable table.
                 Setting this value to invalid(2) for a certain
                 nbsEthChnRunIndex, deletes this entry.
                 To create a new entry a SET PDU with the
                 nbsEthChnRunList and nbsEthChnRunStatus=valid(1)
                 objects is required."
        ::= { nbsEthChnRunEntry 2 }

nbsEthChnRunList  OBJECT-TYPE
		SYNTAX  OCTET STRING
	        ACCESS  read-write
	        STATUS  mandatory
	        DESCRIPTION
		"Bitmap of ports forming the Ethernet Channel
		 in the Run Data Base.
		 Each octet within the value of this object
		 specifies a set of eight ports, with
		 the first octet specifying ports 1 through 8,
		 the second octet specifying ports 9 through 16, etc.
		 Within each octet, the most significant bit represents
		 the lowest numbered port, and the least significant bit
		 represents the highest numbered port. Thus, each port
		 of the switch is represented by a single bit within the
		 value of this object.  If that bit has a value of <1>
		 then that port is included in the set of ports.
		 The port is not included if its bit has a value of <0>."
	::= { nbsEthChnRunEntry 3 }

nbsEthChnRunLinkList  OBJECT-TYPE
		SYNTAX  OCTET STRING
	        ACCESS  read-only
	        STATUS  mandatory
	        DESCRIPTION
		"Bitmap of only Linked ports forming the Ethernet Channel
		 in the Run Data Base.
		 Each octet within the value of this object
		 specifies a set of eight ports, with
		 the first octet specifying ports 1 through 8,
		 the second octet specifying ports 9 through 16, etc.
		 Within each octet, the most significant bit represents
		 the lowest numbered port, and the least significant bit
		 represents the highest numbered port. Thus, each port
		 of the switch is represented by a single bit within the
		 value of this object.  If that bit has a value of <1>
		 then that port is included in the set of ports.
		 The port is not included if its bit has a value of <0>."
	::= { nbsEthChnRunEntry 4 }

		-- nbsEthChnPerm group

-- ************************************************************
-- The Ethernet Channel  PERM  Data Base
-- ************************************************************


nbsEthChnPermTable OBJECT-TYPE

        SYNTAX  SEQUENCE OF NbsEthChnPermEntry
        ACCESS  not-accessible
        STATUS  mandatory
        DESCRIPTION
                "A list of the current Ethernet Channels
                 defined. Number of entries is given by nbsEthChnMaxNum"
        ::= { nbsEthChnPerm 1 }

nbsEthChnPermEntry  OBJECT-TYPE
        SYNTAX  NbsEthChnPermEntry
        ACCESS  not-accessible
        STATUS  mandatory
        DESCRIPTION
                "Contains the descriptor of a Ethernet Channel."
        INDEX { nbsEthChnPermIndex }
        ::= { nbsEthChnPermTable 1 }


NbsEthChnPermEntry ::= SEQUENCE {
        nbsEthChnPermIndex     		INTEGER,
        nbsEthChnPermStatus    		INTEGER,
	nbsEthChnPermList		OCTET STRING
        }

nbsEthChnPermIndex  OBJECT-TYPE
        SYNTAX  INTEGER
        ACCESS  read-only
        STATUS  mandatory
        DESCRIPTION
                "The serial number of this entry in the nbsEthChnPermTbl.
                 It may range from 1 to the value of nbsEthChnsPermMaxNum."
        ::= { nbsEthChnPermEntry 1 }

nbsEthChnPermStatus  OBJECT-TYPE
        SYNTAX  INTEGER {
                valid  (1),     -- the entry is valid and active
                invalid(2)      -- the entry is invalid
        }
        ACCESS  read-write
        STATUS  mandatory
        DESCRIPTION
                "The object is used to create/delete entries in the
                 nbsEthChnPermTable table.
                 Setting this value to invalid(2) for a certain
                 nbsEthChnPermIndex, deletes this entry.
                 To create a new entry a SET PDU with the
                 nbsEthChnPermList and nbsEthChnPermStatus=valid(1)
                 objects is required."
        ::= { nbsEthChnPermEntry 2 }

nbsEthChnPermList  OBJECT-TYPE
		SYNTAX  OCTET STRING
	        ACCESS  read-write
	        STATUS  mandatory
	        DESCRIPTION
		"Bitmap of ports forming the Ethernet Channel
		 in the Permanent Data Base.
		 Each octet within the value of this object
		 specifies a set of eight ports, with
		 the first octet specifying ports 1 through 8,
		 the second octet specifying ports 9 through 16, etc.
		 Within each octet, the most significant bit represents
		 the lowest numbered port, and the least significant bit
		 represents the highest numbered port. Thus, each port
		 of the switch is represented by a single bit within the
		 value of this object.  If that bit has a value of <1>
		 then that port is included in the set of ports.
		 The port is not included if its bit has a value of <0>."
	::= { nbsEthChnPermEntry 3 }
-- ***************************************************************
-- The Possible  Ethernet Channel Data Base
-- ***************************************************************


nbsEthChnPossTable OBJECT-TYPE

        SYNTAX  SEQUENCE OF NbsEthChnPossEntry
        ACCESS  not-accessible
        STATUS  mandatory
        DESCRIPTION
                "A list of the possible ports for the Ethernet Channels.
                 Number of entries is given by nbsEthChnPossNum"
        ::= { nbsEthChnPoss 1 }

nbsEthChnPossEntry  OBJECT-TYPE
        SYNTAX  NbsEthChnPossEntry
        ACCESS  not-accessible
        STATUS  mandatory
        DESCRIPTION
                "Contains the descriptor of a Ethernet Channel."
        INDEX { nbsEthChnPossIndex }
        ::= { nbsEthChnPossTable 1 }


NbsEthChnPossEntry ::= SEQUENCE {
        nbsEthChnPossIndex     		INTEGER,
	nbsEthChnPossRunStatus    	INTEGER,
	nbsEthChnPossPermStatus    	INTEGER,
	nbsEthChnPossPortMaxNum		INTEGER,
	nbsEthChnPossList		OCTET STRING
	}

nbsEthChnPossIndex  OBJECT-TYPE
        SYNTAX  INTEGER
        ACCESS  read-only
        STATUS  mandatory
        DESCRIPTION
                "The serial number of this entry in the nbsEthChnPossTable.
                 It may range from 1 to the value of nbsEthChnPossNum."
        ::= { nbsEthChnPossEntry 1 }

nbsEthChnPossRunStatus  OBJECT-TYPE
        SYNTAX  INTEGER {
                true  (1),     -- ports from this the entry is used already
                false (2)      -- ports from this the entry isn't used
        }
        ACCESS  read-only
        STATUS  mandatory
        DESCRIPTION
                "The object is used to know if the current possible port list
		 is used in the RUN Ethernet Channel data base."
        ::= { nbsEthChnPossEntry 2 }

nbsEthChnPossPermStatus  OBJECT-TYPE
        SYNTAX  INTEGER {
                true  (1),     -- ports from this the entry is used already
                false (2)      -- ports from this the entry isn't used
        }
        ACCESS  read-only
        STATUS  mandatory
        DESCRIPTION
                "The object is used to know if the current possible port list
		 is used in the PERM Ethernet Channel data base."
        ::= { nbsEthChnPossEntry 3 }

nbsEthChnPossPortMaxNum  OBJECT-TYPE
        SYNTAX  INTEGER
        ACCESS  read-only
        STATUS  mandatory
        DESCRIPTION
                "The max number of ports in the this EtherChannel."
        ::= { nbsEthChnPossEntry 4 }

nbsEthChnPossList  OBJECT-TYPE
		SYNTAX  OCTET STRING
	        ACCESS  read-only
	        STATUS  mandatory
	        DESCRIPTION
		"Bitmap of ports that are possible for each Ethernet Channel.
		 Each octet within the value of this object
		 specifies a set of eight ports, with
		 the first octet specifying ports 1 through 8,
		 the second octet specifying ports 9 through 16, etc.
		 Within each octet, the most significant bit represents
		 the lowest numbered port, and the least significant bit
		 represents the highest numbered port. Thus, each port
		 of the switch is represented by a single bit within the
		 value of this object.  If that bit has a value of <1>
		 then that port is included in the set of ports.
		 The port is not included if its bit has a value of <0>."
	::= { nbsEthChnPossEntry 5 }
                
END

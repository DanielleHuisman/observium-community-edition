--  =======================================================================
--  File        : oaefrm.mib
--  Description : Private MIB for EFRM CPE
--                
--  By          : Ilan Weber, Pavel Fridland, Yakov Vaisman, Inna Levin
--  Version     : $Revision:   0.1
--  Origin Date : April 17, 2003
--  Last Change : $Date:   Jun 7, 2006
--  =======================================================================
--
--
-- Copyright (c) 2003 MRV.  All Rights Reserved.
--
-- Reproduction of this document is authorized on condition that this
-- copyright notice is included.  This MRV SNMP MIB Specification
-- embodies MRV proprietary intellectual property.
-- MRV retains all title and ownership in the specification, including any
-- revisions.
--
-- It is MRV's intent to encourage the widespread use of this
-- specification in connection with the management of MRV's
-- products. MRV grants vendor, end-users, and other interested
-- parties a non-exclusive license to use this specification in
-- connection with the management of MRV's products.
--
-- This specification is supplied "AS IS," and MRV makes no
-- warranty, either express or implied, as to the use, operation,
-- condition, or performance of the specification.
--
-- MRV retains the right to change this MIB without notification.
--

OA-EFRM-CPE-MIB DEFINITIONS ::= BEGIN

IMPORTS
    MODULE-IDENTITY, OBJECT-TYPE,
    NOTIFICATION-TYPE,
    enterprises, Counter32, Integer32    FROM SNMPv2-SMI
    TEXTUAL-CONVENTION, DisplayString    FROM SNMPv2-TC
    MODULE-COMPLIANCE, OBJECT-GROUP,
    NOTIFICATION-GROUP                   FROM SNMPv2-CONF;

oaEfrmCpe  MODULE-IDENTITY
    LAST-UPDATED "200606070000Z"  -- Jun 7, 2006
    ORGANIZATION "MRV Communications, Inc."
    CONTACT-INFO
        "For technical support,
         please contact your CSO person."
    DESCRIPTION
        "."

    -- Revision history

    REVISION "200606070000Z"  -- Jun 7, 2006
    DESCRIPTION
        "1) [oaEfrmCpePortMdi] and [oaEfrmCpePortAutoSense] Mib Objects were added
            to oaEfrmCpePortTable.
	 2) OAM Statistics Table and Phy Statistics Table were added
        "

    REVISION "200605160000Z"  -- May 16, 2006
    DESCRIPTION
        "Mib Objects for the 'Dual-Home' and 'Redundant Trunks'
         features support added:
         - [oaEfrmCoRedundantMode],
         - [oaEfrmCoRedundantActState]
        "

    REVISION "200605100000Z"  -- May 10, 2006
    DESCRIPTION
        "Mib Objects for the SFP Port parameters support added:
         - [oaEfrmSfpInfoTable],
         - [oaEfrmSfpDiagnosticTable]
        "

    REVISION "200604110000Z"  -- Apr 11, 2006
    DESCRIPTION
        "Mib Objects for the EFM 802.3ah feature support added:
         - [oaEfrmCpeModuleExtTable],
        "

    REVISION "200305190000Z"  -- May 19, 2003
    DESCRIPTION
        "Initial edition."
    ::= { oaManagement 16 }

-- ************************************************************
-- MIB place Definition
-- ************************************************************

oaccess                 OBJECT IDENTIFIER ::= { enterprises 6926 }
oaManagement            OBJECT IDENTIFIER ::= { oaccess 1 }

---------------------------------------------------------------------------
-- GROUPS in 	OA-EFRM-CPE-MIB
---------------------------------------------------------------------------

oaEfrmCpeNotifications  OBJECT IDENTIFIER ::= { oaEfrmCpe 0 }
oaEfrmCpeGenGrp         OBJECT IDENTIFIER ::= { oaEfrmCpe 2 }
oaEfrmCpeModuletGrp     OBJECT IDENTIFIER ::= { oaEfrmCpe 3 }
oaEfrmCpePortGrp        OBJECT IDENTIFIER ::= { oaEfrmCpe 4 }

oaEfrmCpeSfp            OBJECT IDENTIFIER ::= { oaEfrmCpe 10}
oaEfrmSfpMIBObjects     OBJECT IDENTIFIER ::= { oaEfrmCpeSfp 1 }

oaEfrmCpeConformance    OBJECT IDENTIFIER ::= { oaEfrmCpe 100 }

-- ************************************************************************
-- Objects for CPE General group
-- ************************************************************************

oaEfrmCpeGenSupport OBJECT-TYPE
        SYNTAX  INTEGER {
            notSupported (1),
            supported    (2)
        }       
        MAX-ACCESS  read-only
        STATUS  current
        DESCRIPTION
        "EFRM CEP feature support."

        ::= { oaEfrmCpeGenGrp 1 }

oaEfrmCoOam OBJECT-TYPE
        SYNTAX  INTEGER {
            notSupported (1),
            disable      (2),
            enable       (3)
        }
        MAX-ACCESS  read-write
        STATUS  current
        DESCRIPTION
        "OAM feature enabled or disabled on the CO."

        ::= { oaEfrmCpeGenGrp 2 }

oaEfrmCoNoDiscardLpbkdPkts OBJECT-TYPE
        SYNTAX  INTEGER {
            notSupported (1),
            disable      (2),
            enable       (3)
        }       
        MAX-ACCESS  read-write
        STATUS  current
        DESCRIPTION
        "To configure Not discard loopbacked packets (back returned 
         from CPE devices, which is configured to loopback) on the CO.
         Supported for 802.3ah protocol for all Ports."

        ::= { oaEfrmCpeGenGrp 3 }

oaEfrmCoSlowProtoPktsLoopback OBJECT-TYPE
        SYNTAX  INTEGER {
            notSupported (1),
            disable      (2),
            enable       (3)
        }       
        MAX-ACCESS  read-write
        STATUS  current
        DESCRIPTION
        "loopback slow protocol packets on the loopbacked device.
         Supported for 802.3ah protocol for all Ports."

        ::= { oaEfrmCpeGenGrp 4 }

oaEfrmCpeSlowProtoPktsLoopback OBJECT-TYPE
        SYNTAX  INTEGER {
            notSupported (1),
            disable      (2),
            enable       (3)
        }       
        MAX-ACCESS  read-write
        STATUS  current
        DESCRIPTION
        "loopback slow protocol packets on the loopbacked device.
         Supported for 802.3ah protocol for all Ports."

        ::= { oaEfrmCpeGenGrp 5 }

-- ************************************************************************
-- Objects for CPE Module group
-- ************************************************************************

oaEfrmCpeModuleTable OBJECT-TYPE
        SYNTAX  SEQUENCE OF OaEfrmCpeModuleEntry
        MAX-ACCESS  not-accessible
        STATUS  current
        DESCRIPTION
        "A table that describes the EFRM CPE Module connected"

        ::= { oaEfrmCpeModuletGrp 1 }

oaEfrmCpeModuleEntry      OBJECT-TYPE
        SYNTAX  OaEfrmCpeModuleEntry
        MAX-ACCESS  not-accessible
        STATUS  current
        DESCRIPTION
        "Contains a desription of a particular EFRM CPE Module"

        INDEX { oaEfrmCpeLocalPortIndex }

        ::= { oaEfrmCpeModuleTable 1 }

OaEfrmCpeModuleEntry ::= SEQUENCE {
    oaEfrmCpeLocalPortIndex         Integer32,
    oaEfrmCpeModuleType             INTEGER,
    oaEfrmCpeModuleRemoteLoopback   INTEGER,
    oaEfrmCpeModuleEnable           INTEGER,
    oaEfrmCpeModuleIPLessEnable     INTEGER,
    oaEfrmCpeModuleIPLessLink       INTEGER,
    oaEfrmCpeCpeCoSW                INTEGER,
    oaEfrmCpeCpeManagementSW        INTEGER,
    oaEfrmCpeCpeLINSW               INTEGER,
    oaEfrmCpeModuleMdiSW            INTEGER,
    oaEfrmCpePowerFail              INTEGER,
    oaEfrmCpeModuleName             DisplayString
}

oaEfrmCpeLocalPortIndex OBJECT-TYPE
        SYNTAX Integer32 (1..256)
        MAX-ACCESS  read-only
        STATUS  current
        DESCRIPTION
        "The index of the local port on the CO-dev
         to which this module is connected."

        ::= { oaEfrmCpeModuleEntry 1 }

oaEfrmCpeModuleType OBJECT-TYPE
        SYNTAX  INTEGER {
            notSupported       (1),
            unknownCardType    (2),
            em316efrmosCard    (3),
            em316grmahshCard  (19),
            em316efrmahshCard (21)
        }       
        MAX-ACCESS  read-only
        STATUS  current
        DESCRIPTION
        "The physical type of port. Valid port types are > 1."

        ::= { oaEfrmCpeModuleEntry 2 }

oaEfrmCpeModuleRemoteLoopback OBJECT-TYPE
        SYNTAX  INTEGER {
            notSupported (1),
            disable      (2),
            enable       (3)
        }       
        MAX-ACCESS  read-write
        STATUS  current
        DESCRIPTION
        "Remote loopback on or off if supported by board
         (e.g. T1/E1)."

        ::= { oaEfrmCpeModuleEntry 4 }

oaEfrmCpeModuleEnable OBJECT-TYPE
        SYNTAX  INTEGER {
            notSupported (1),
            disable      (2),
            enable       (3)
        }
        MAX-ACCESS  read-write
        STATUS  current
        DESCRIPTION
        "The enable/disable status of the module.
         For 'em316grmahshCard' and 'em316efrmahshCard'
         module Types returns 'notSupported'."

        ::= { oaEfrmCpeModuleEntry 5 }

oaEfrmCpeModuleIPLessEnable OBJECT-TYPE
        SYNTAX  INTEGER {
            notSupported (1),
            disable      (2),
            enable       (3)
        }       
        MAX-ACCESS  read-write
        STATUS  current
        DESCRIPTION
        "The enable/disable status/action of the IPLess.
         For 802.3ah rotocol only entries with 'enable' status
         will be accessible via SNMP GET-NEXT command.
         To use this parameter for all ports existing in the
         CO device, use [oaEfrmCoPortEnable] object."

        ::= { oaEfrmCpeModuleEntry 6 }

oaEfrmCpeModuleIPLessLink OBJECT-TYPE
        SYNTAX  INTEGER {
            notSupported (1),
            off          (2),
            on           (3)
        }       
        MAX-ACCESS  read-only
        STATUS  current
        DESCRIPTION
        "The Link status of the IPLess (Link between CO and CPE)."

        ::= { oaEfrmCpeModuleEntry 7 }

oaEfrmCpeCpeCoSW OBJECT-TYPE
        SYNTAX  INTEGER {
            notSupported (1),
            co           (2),
            cpe          (3)
        }       
        MAX-ACCESS  read-only
        STATUS  current
        DESCRIPTION
        "CO/CPE Switch position on CPE module."

        ::= { oaEfrmCpeModuleEntry 11 }

oaEfrmCpeCpeManagementSW OBJECT-TYPE
        SYNTAX  INTEGER {
            notSupported (1),
            disable      (2),
            enable       (3)
        }       
        MAX-ACCESS  read-only
        STATUS  current
        DESCRIPTION
        "Management Switch position on CPE module."

        ::= { oaEfrmCpeModuleEntry 12 }

oaEfrmCpeCpeLINSW OBJECT-TYPE
        SYNTAX  INTEGER {
            notSupported (1),
            disable      (2),
            enable       (3)
        }       
        MAX-ACCESS  read-only
        STATUS  current
        DESCRIPTION
        "Line Integrity Check 'on' or 'off'."

        ::= { oaEfrmCpeModuleEntry 13 }

oaEfrmCpeModuleMdiSW OBJECT-TYPE
        SYNTAX  INTEGER {
            notSupported (1),
            mdi          (2),
            mdix         (3),
            auto         (4)
        }       
        MAX-ACCESS  read-only
        STATUS  current
        DESCRIPTION
        "MDI/MDIX Switch position on the module."

        ::= { oaEfrmCpeModuleEntry 14 }

oaEfrmCpePowerFail OBJECT-TYPE
        SYNTAX  INTEGER {
            notSupported (1),
            fail         (2),
            good         (3),
            unknown      (4)
        }
        MAX-ACCESS  read-only
        STATUS  current
        DESCRIPTION
        "CPE Module Power Fail.
        'unknown' is no link between CO and CPE,
        and did not receive Gasp event."

        ::= { oaEfrmCpeModuleEntry 15 }

oaEfrmCpeModuleName OBJECT-TYPE
        SYNTAX  DisplayString (SIZE(0..15))
        MAX-ACCESS  read-write
        STATUS  current
        DESCRIPTION
        "The user assigned name for this CPE module."

        ::= {oaEfrmCpeModuleEntry 16 }

-- ************************************************************************
-- Objects for CPE Module Extension group
-- ************************************************************************

oaEfrmCpeModuleExtTable OBJECT-TYPE
        SYNTAX  SEQUENCE OF OaEfrmCpeModuleExtEntry
        MAX-ACCESS  not-accessible
        STATUS  current
        DESCRIPTION
        "An extension table that describes the additional EFM 802.3ah
         CPE module parameters."

        ::= { oaEfrmCpeModuletGrp 2 }

oaEfrmCpeModuleExtEntry      OBJECT-TYPE
        SYNTAX  OaEfrmCpeModuleExtEntry
        MAX-ACCESS  not-accessible
        STATUS  current
        DESCRIPTION
        "Contains a description of an extention MIB Objects
         for the particular CPE module (previuos table)."

        INDEX { oaEfrmCpeLocalPortIndex }

        ::= { oaEfrmCpeModuleExtTable 1 }

OaEfrmCpeModuleExtEntry ::= SEQUENCE {
    oaEfrmCpeModuleMacAddress       OCTET STRING,
    oaEfrmCpeModuleAppRev           DisplayString,
    oaEfrmCpeModuleFpgaRev          DisplayString,
    oaEfrmCpeModuleVendorOUI        OCTET STRING,
    oaEfrmCpeModuleVendorInfo       OCTET STRING,
    oaEfrmCpeModuleMaxPduSize       Integer32,
    oaEfrmCpeModuleDiscoveryState   INTEGER,
    oaEfrmCpeModulePduState         INTEGER,
    oaEfrmCoModuleDiscoveryState    INTEGER,
    oaEfrmCoModulePduState          INTEGER,
    oaEfrmCoRedundantMode           INTEGER,
    oaEfrmCoRedundantActState       INTEGER
}

oaEfrmCpeModuleMacAddress OBJECT-TYPE
        SYNTAX  OCTET STRING (SIZE(6))
        MAX-ACCESS  read-only
        STATUS  current
        DESCRIPTION
        "The MAC ADDRESS of the CPE module."

        ::= {oaEfrmCpeModuleExtEntry 2 }

oaEfrmCpeModuleAppRev OBJECT-TYPE
        SYNTAX  DisplayString (SIZE(0..20))
        MAX-ACCESS  read-only
        STATUS  current
        DESCRIPTION
        "The Application Revision of the CPE module."

        ::= {oaEfrmCpeModuleExtEntry 3 }

oaEfrmCpeModuleFpgaRev OBJECT-TYPE
        SYNTAX  DisplayString (SIZE(0..20))
        MAX-ACCESS  read-only
        STATUS  current
        DESCRIPTION
        "The FPGA Revision of the CPE module."

        ::= {oaEfrmCpeModuleExtEntry 4 }

oaEfrmCpeModuleVendorOUI OBJECT-TYPE
        SYNTAX  OCTET STRING (SIZE(0..3))
        MAX-ACCESS  read-only
        STATUS  current
        DESCRIPTION
        "The Vendor OUI of the CPE module."

        ::= {oaEfrmCpeModuleExtEntry 5 }

oaEfrmCpeModuleVendorInfo OBJECT-TYPE
        SYNTAX  OCTET STRING (SIZE(0..4))
        MAX-ACCESS  read-only
        STATUS  current
        DESCRIPTION
        "The Vendor Information of the CPE module."

        ::= {oaEfrmCpeModuleExtEntry 6 }

oaEfrmCpeModuleMaxPduSize OBJECT-TYPE
        SYNTAX  Integer32 (0..2147483647)
        MAX-ACCESS  read-only
        STATUS  current
        DESCRIPTION
        "The Max size of the PDU (bytes)."

        ::= {oaEfrmCpeModuleExtEntry 7 }

oaEfrmCpeModuleDiscoveryState OBJECT-TYPE
        SYNTAX  INTEGER {
            notSupported      (1),
            fault             (2),
            activeSendLocal   (3),
            passiveWait       (4),
            sendLocalRemote   (5),
            sendLocalRemoteOk (6),
            sendAny           (7)  
        }       
        MAX-ACCESS  read-only
        STATUS  current
        DESCRIPTION
        "The CPE Discovery Process State."

        ::= {oaEfrmCpeModuleExtEntry 8 }

oaEfrmCpeModulePduState OBJECT-TYPE
        SYNTAX  INTEGER {
            notSupported  (1),
            lfInfo        (2),
            rfInfo        (3), 
            info          (4),
            any           (5)
        }       
        MAX-ACCESS  read-only
        STATUS  current
        DESCRIPTION
        "The CPE PDU State."

        ::= {oaEfrmCpeModuleExtEntry 9 }

oaEfrmCoModuleDiscoveryState OBJECT-TYPE
        SYNTAX  INTEGER {
            notSupported      (1),
            fault             (2),
            activeSendLocal   (3),
            passiveWait       (4),
            sendLocalRemote   (5),
            sendLocalRemoteOk (6),
            sendAny           (7)  
        }       
        MAX-ACCESS  read-only
        STATUS  current
        DESCRIPTION
        "The CO Discovery Process State."

        ::= {oaEfrmCpeModuleExtEntry 10 }

oaEfrmCoModulePduState OBJECT-TYPE
        SYNTAX  INTEGER {
            notSupported  (1),
            lfInfo        (2),
            rfInfo        (3), 
            info          (4),
            any           (5)
        }       
        MAX-ACCESS  read-only
        STATUS  current
        DESCRIPTION
        "The CO PDU State."

        ::= {oaEfrmCpeModuleExtEntry 11 }

oaEfrmCoRedundantMode OBJECT-TYPE
        SYNTAX  INTEGER {
            notSupported    (1),
            normal          (2),
            dualHome        (3)
        }       
        MAX-ACCESS  read-write
        STATUS  current
        DESCRIPTION
        "The Redundant Mode of the CO Trunk Port.
         'dualHome'[3] and 'normal'[2] modes
         mean the CO port is working in the
         redundancy mode. It means when active CO port
         lose link, the traffic automatically shift
         to the redundant CO port."

        ::= {oaEfrmCpeModuleExtEntry 13 }

oaEfrmCoRedundantActState OBJECT-TYPE
        SYNTAX  INTEGER {
            notSupported  (1),
            inactive      (2),
            active        (3)
        }       
        MAX-ACCESS  read-only
        STATUS  current
        DESCRIPTION
        "CO Trunk Port can be 'active' or 'inactive' redundant port for CPE"

        ::= {oaEfrmCpeModuleExtEntry 15 }

-- ************************************************************************
-- Objects for CPE Module Extension group
-- ************************************************************************

oaEfrmCoModuleTable OBJECT-TYPE
        SYNTAX  SEQUENCE OF OaEfrmCoModuleEntry
        MAX-ACCESS  not-accessible
        STATUS  current
        DESCRIPTION
        "Table that describes the EFM 802.3ah
         parameters for all ports in the CO device ."

        ::= { oaEfrmCpeModuletGrp 3 }

oaEfrmCoModuleEntry      OBJECT-TYPE
        SYNTAX  OaEfrmCoModuleEntry
        MAX-ACCESS  not-accessible
        STATUS  current
        DESCRIPTION
        "Contains a descriptions of an configurable MIB Objects
         for all ports in the CO device."

        INDEX { oaEfrmCpeLocalPortIndex }

        ::= { oaEfrmCoModuleTable 1 }

OaEfrmCoModuleEntry ::= SEQUENCE {
    oaEfrmCoPortEnable            INTEGER
}

oaEfrmCoPortEnable OBJECT-TYPE
        SYNTAX  INTEGER {
            notSupported (1),
            disable      (2),
            enable       (3)
        }       
        MAX-ACCESS  read-write
        STATUS  current
        DESCRIPTION
        "The enable/disable status/action of the IPLess.
         Supported for 802.3ah protocol for all Ports in the
         CO device (the same as [oaEfrmCpeModuleIPLessEnable])."

        ::= { oaEfrmCoModuleEntry 6 }


-- ************************************************************************
-- Objects for CPE's Ports group
-- ************************************************************************

oaEfrmCpeNumberOfPorts  OBJECT-TYPE
        SYNTAX  Integer32 (1..16)
        MAX-ACCESS  read-only
        STATUS  current
        DESCRIPTION
        "Number of ports in the module."

        ::= { oaEfrmCpePortGrp 1 }

oaEfrmCpePortTable OBJECT-TYPE
        SYNTAX  SEQUENCE OF OaEfrmCpePortEntry
        MAX-ACCESS  not-accessible
        STATUS  current
        DESCRIPTION
        "A table that describes the EFRM CPE Ports"

        ::= { oaEfrmCpePortGrp 5 }

oaEfrmCpePortEntry      OBJECT-TYPE
        SYNTAX  OaEfrmCpePortEntry
        MAX-ACCESS  not-accessible
        STATUS  current
        DESCRIPTION
        "Contains a desription of a particular EFRM CPE Port"

        INDEX { oaEfrmCpeLocalPortIndex, oaEfrmCpeCPEPortIndex }

        ::= { oaEfrmCpePortTable 1 }

OaEfrmCpePortEntry ::= SEQUENCE {
    oaEfrmCpeCPEPortIndex                Integer32,
    oaEfrmCpePortType                    INTEGER,
    oaEfrmCpePortLink                    INTEGER,
    oaEfrmCpePortAutoNegotiation         INTEGER,
    oaEfrmCpePortDuplex                  INTEGER,
    oaEfrmCpePortSpeed                   INTEGER,
    oaEfrmCpePortActivity                INTEGER,
    oaEfrmCpePortLogicalType             INTEGER,
    oaEfrmCpePortConnectorType           INTEGER,
    oaEfrmCpePortConnectorSubType        INTEGER,
    oaEfrmCpePortSfpPresent              INTEGER,
    oaEfrmCpePortAutoNegCaps             BITS,
--    oaEfrmCpePortAutoNegCaps             OCTET STRING,
    oaEfrmCpePortMdi                     INTEGER,
    oaEfrmCpePortAutoSense               INTEGER

}

oaEfrmCpeCPEPortIndex OBJECT-TYPE
        SYNTAX Integer32 (1..16)
        MAX-ACCESS  read-only
        STATUS  current
        DESCRIPTION
        "The index of the port at the CPE module."

        ::= { oaEfrmCpePortEntry 2 }

oaEfrmCpePortType OBJECT-TYPE
        SYNTAX  INTEGER {
            rj45Rj45Na      (1),
            notInstalled    (2),
            unknownType     (3),
            mLcMm           (16),
            mxLcMmmx        (17),
            s1LcSms1        (18),
            s2LcSms2        (19),
            s3LcSms3        (20),
            mDscMm          (24),
            mxDscMmmx       (25),
            s1DscSms1       (26),
            s2DscSms2       (27),
            s3DscSms3       (28),
            s2ScSms2        (32),
            s3ScSms3        (33)
        }       
        MAX-ACCESS  read-only
        STATUS  current
        DESCRIPTION
        "The physical type of port.  Valid port types are > 1.
         The type name is coded as: portType & Connector & Optics :
         -------------------+-----------+-----------+-----------+
                            | Port Type | Connector |  Optics   |
         -------------------+-----------+-----------+-----------+ 
         1  = rj45Rj45Na    |  RJ45     |   RJ45    |   N/A     |
         2  = notInstalled  |  N/A      |   N/A     |   N/A     |
         3  = unknownType   |  N/A      |   N/A     |   N/A     |
         16 = mLcMm         |  M        |   LC      |   MM      |
         17 = mxLcMmmx      |  MX       |   LC      |   MM_MX   |
         18 = s1LcSms1      |  S1       |   LC      |   SM_S1   |
         19 = s2LcSms2      |  S2       |   LC      |   SM_S2   |
         20 = s3LcSms3      |  S3       |   LC      |   SM_S3   |
         24 = mDscMm        |  M        |   DSC     |   MM      |
         25 = mxDscMmmx     |  MX       |   DSC     |   MM_MX   |
         26 = s1DscSms1     |  S1       |   DSC     |   SM_S1   |
         27 = s2DscSms2     |  S2       |   DSC     |   SM_S2   |
         28 = s3DscSms3     |  S3       |   DSC     |   SM_S3   |
         32 = s2ScSms2      |  S2       |   SC      |   SM_S2   |
         33 = s3ScSms3      |  S3       |   SC      |   SM_S3   |
         -------------------+-----------+-----------+-----------+
         For 'em316grmahshCard' and 'em316efrmahshCard'
         module Types always returns 'unknownType'."

        ::= { oaEfrmCpePortEntry 5 }

oaEfrmCpePortLink OBJECT-TYPE
        SYNTAX  INTEGER {
            other        (1),
            noLink       (2),
            link         (3)
        }       
        MAX-ACCESS  read-only
        STATUS  current
        DESCRIPTION
        "The link status of the port."

        ::= { oaEfrmCpePortEntry 6 }

oaEfrmCpePortAutoNegotiation OBJECT-TYPE
        SYNTAX  INTEGER {
            notSupported (1),
            off          (2),
            on           (3)
        }       
        MAX-ACCESS  read-write
        STATUS  current
        DESCRIPTION
        "The autonegotiation status of the port."

        ::= { oaEfrmCpePortEntry 7 }

oaEfrmCpePortDuplex OBJECT-TYPE
        SYNTAX  INTEGER {
            notSupported (1),
            half         (2),
            full         (3)
        }       
        MAX-ACCESS  read-write
        STATUS  current
        DESCRIPTION
        "The duplex mode of the port."

        ::= { oaEfrmCpePortEntry 8 }

oaEfrmCpePortSpeed OBJECT-TYPE
        SYNTAX  INTEGER {
            other       (1),
            spd10mbps   (2),
            spd100mbps  (3),
            spd1000mbps (4)
        }       
        MAX-ACCESS  read-write
        STATUS  current
        DESCRIPTION
        "The actual speed of the port."

        ::= { oaEfrmCpePortEntry 9 }

oaEfrmCpePortActivity OBJECT-TYPE
        SYNTAX  INTEGER {
            notSupported (1),
            off          (2),
            on           (3)
        }
        MAX-ACCESS  read-only
        STATUS  current
        DESCRIPTION
        "The activity status of the port.
         For 'em316grmahshCard' and 'em316efrmahshCard'
         it show the Data Transferring State.
         The value 'off'[2] means that user data can not
         be transferred over corresponding trunk/user port,
         while the value 'on'[3] means that port is opened
         for the data transferring."

        ::= { oaEfrmCpePortEntry 10 }

oaEfrmCpePortLogicalType OBJECT-TYPE
        SYNTAX  INTEGER {
            notSupported (1),
            user         (2),
            trunk        (3)
        }       
        MAX-ACCESS  read-only
        STATUS  current
        DESCRIPTION
        "The logical type of the port."

        ::= { oaEfrmCpePortEntry 11 }

oaEfrmCpePortConnectorType  OBJECT-TYPE
        SYNTAX    INTEGER {
            other        (1),
            static       (2),
            gbic         (3),
            sfp          (4)
         }
	 MAX-ACCESS    read-only
         STATUS    current
         DESCRIPTION
         "Multi Connectivity Port Connector Types:
          other=(1)      - Unknown type of connector;
          static=(2)     - Not Changeable type of connector;
          gbic=(3)       - GBIC    type of connector;
          sfp=(4)        - SFP     type of connector;"

         ::= { oaEfrmCpePortEntry 12 }

oaEfrmCpePortConnectorSubType  OBJECT-TYPE
         SYNTAX    INTEGER {
             other       (1),
             rj45        (2),
             sc          (3),
             lc          (4),
             mtrj        (5),
             vf          (6)
         }
         MAX-ACCESS    read-only
         STATUS    current
         DESCRIPTION
         "Multi Connectivity Port Connector Sub Type:
          other=(1)      - Unknown or N/A Connector's connectivity Type;
          rj45=(2)       - Copper RJ45;
          sc=(3)         - Regular Fibre Optic [FO];
          lc=(4)         - LC;
          mtrj=(5)       - MTRJ;
          vf=(6)         - VF"
         ::= { oaEfrmCpePortEntry 13 }

oaEfrmCpePortSfpPresent OBJECT-TYPE
        SYNTAX  INTEGER {
            notSupported (1),
            present      (2),
            notPresent   (3)
        }       
        MAX-ACCESS  read-only
        STATUS  current
        DESCRIPTION
        "The is SubConnector present in the SFP based Port."

        ::= { oaEfrmCpePortEntry 14 }

oaEfrmCpePortAutoNegCaps OBJECT-TYPE
--        SYNTAX       OCTET STRING
        SYNTAX       BITS {
            cap10half     (0),
            cap10full     (1),
            cap100half    (2),
            cap100full    (3),
            cap1000half   (4),
            cap1000full   (5)
        }
        MAX-ACCESS  read-write
        STATUS  current
        DESCRIPTION
        "The auto-negotiation capabilites."

        ::= { oaEfrmCpePortEntry 15 }

oaEfrmCpePortMdi OBJECT-TYPE
        SYNTAX  INTEGER {
            notSupported (1),
            mdi          (2),
            mdix         (3)
        }       
        MAX-ACCESS  read-write
        STATUS  current
        DESCRIPTION
        "MDI-X or MDI mode for User port."

        ::= { oaEfrmCpePortEntry 16 }

oaEfrmCpePortAutoSense  OBJECT-TYPE
        SYNTAX  INTEGER {
            notSupported (1),
            autoSense    (2),
            force        (3)
        }       
        MAX-ACCESS  read-write
        STATUS  current
        DESCRIPTION
        "Auto-sense or Force mode for User port."

        ::= { oaEfrmCpePortEntry 17 }

-- ************************************************************
-- SFP Info Table
-- ************************************************************

oaEfrmSfpInfoTable OBJECT-TYPE
        SYNTAX SEQUENCE OF OaEfrmSfpInfoEntry
        MAX-ACCESS not-accessible
        STATUS current
        DESCRIPTION
        "The sfp information table."

        ::= { oaEfrmSfpMIBObjects 2 }

oaEfrmSfpInfoEntry OBJECT-TYPE
        SYNTAX	OaEfrmSfpInfoEntry
        MAX-ACCESS not-accessible
        STATUS current
        DESCRIPTION
        "An entry in the SFP Information Table."

        INDEX { oaEfrmCpeLocalPortIndex, oaEfrmCpeCPEPortIndex }

        ::= { oaEfrmSfpInfoTable 1 }

OaEfrmSfpInfoEntry ::= SEQUENCE {
    oaEfrmSfpInfoIdentifier                 INTEGER,
    oaEfrmSfpInfoVendorSpecId               DisplayString,
    oaEfrmSfpInfoConnector                  INTEGER,
    oaEfrmSfpInfoVendorSpecConnector        DisplayString,
    oaEfrmSfpInfoVendorName                 DisplayString,
    oaEfrmSfpInfoVendorOUI                  DisplayString,
    oaEfrmSfpInfoVendorPN                   DisplayString,
    oaEfrmSfpInfoVendorRev                  DisplayString,
    oaEfrmSfpInfoLaserWavelength            Integer32,
    oaEfrmSfpInfoVendorSN                   DisplayString,
    oaEfrmSfpInfoVendorDate                 DisplayString,
    oaEfrmSfpInfoVendorSpecLotCode          DisplayString,
    oaEfrmSfpInfoVendorSpecData             OCTET STRING,
    oaEfrmSfpInfoDiagnosticPowerType        INTEGER,
    oaEfrmSfpInfoDigitalDiagnostic          INTEGER,
    oaEfrmSfpInfoDiagCalibration            INTEGER,
    oaEfrmSfpInfoInstalledStatus            INTEGER,
    oaEfrmSfpInfofaultStatus                INTEGER,
    oaEfrmSfpInfoEnableStatus               INTEGER
}

oaEfrmSfpInfoIdentifier OBJECT-TYPE
        SYNTAX  INTEGER {
                unknown(1),
                other(2),
                gbic(3),
                fixed(4),
                sfp(5),
                xbi300pin(6),
                xenpak(7),
                xfp(8),
                xff(9),
                xfpE(10),
                xpak(11),
                x2(12),
                dsfp(13)
        }
        MAX-ACCESS read-only
        STATUS	current
        DESCRIPTION
        "The type of serial transceiver
         unknown - Unknown or unspecified
         other - Vendor specific
         gbic - GBIC
         fixed - Module/connector soldered to motherboard
         sfp - SFP transceiver
         xbi300pin - 300 pin XBI
         xenpak - XENPAK transceiver
         xfp - XFP transceiver
         xff - XFF transceiver
         xfpE - XFP-E transceiver
         xpak - XPAK transceiver
         x2 - X2 transceiver
         dsfp - DWDM SFP transceiver"

     ::= { oaEfrmSfpInfoEntry 3 }

oaEfrmSfpInfoVendorSpecId OBJECT-TYPE
        SYNTAX  DisplayString (SIZE(0..30))
        MAX-ACCESS read-only
        STATUS	current
        DESCRIPTION
        "The vendor specific identifier. This Object will be set to
        value other than null only if oaEfrmSfpInfoIdentifier returns a value
        of other"

        ::= { oaEfrmSfpInfoEntry 4 }

oaEfrmSfpInfoConnector OBJECT-TYPE
        SYNTAX  INTEGER {
                unknown(1),
                other(2),
                sc(3),
                fcs1cc(4),
                fcs2cc(5),
                bnctnc(6),
                fcch(7),
                fiberJack(8),
                lc(9),
                mtrj(10),
                mu(11),
                sg(12),
                opticalPigtail(13),
                hssdcii(34),
                copperPigtail(35)
        }
        MAX-ACCESS read-only
        STATUS	current
        DESCRIPTION
        "The type of external connector provided
             unknown - Unknown or unspecified
             other - Vendor specific
             sc - SC
             fcs1cc - Fibre Channel Style 1 copper connector
             fcs2cc - Fibre Channel Style 2 copper connector
             bnctnc - BNC/TNC
             fcch - Fibre Channel coaxial headers
             fiberJack - Fiber Jack
             lc --LC
             mtrj - MT-RJ
             mu - MU
             sg - SG
             opticalPigtail - Optical Pigtail
             hssdcii - HSSDC II
             copperPigtail - Copper Pigtail"

        ::= { oaEfrmSfpInfoEntry 8 }

oaEfrmSfpInfoVendorSpecConnector OBJECT-TYPE
        SYNTAX  DisplayString (SIZE(0..30))
        MAX-ACCESS read-only
        STATUS	current
        DESCRIPTION
        "The type of vendor specific Connector. This Object will be set to
        value other than null only if oaEfrmSfpInfoConnector returns a value of
        other."

        ::= { oaEfrmSfpInfoEntry 9 }

oaEfrmSfpInfoVendorName OBJECT-TYPE
        SYNTAX  DisplayString (SIZE(0..16))
        MAX-ACCESS read-only
        STATUS	current
        DESCRIPTION
        "The sfp vendor name which is the full name of the corporation, a
        commonly accepted abbreviation of the name of the corporation, the SCSI
        company code for the corporation, or the stock exchange code for the
        corporation."

        ::= { oaEfrmSfpInfoEntry 24 }

oaEfrmSfpInfoVendorOUI OBJECT-TYPE
        SYNTAX  DisplayString (SIZE(3))
        MAX-ACCESS read-only
        STATUS	current
        DESCRIPTION
        "The sfp vendor organizationally unique identifier field (vendor OUI)
        that contains the IEEE company identifier for the vendor. A value of
        all zero in the 3 octet field indicates that the vendor OUI is
        unspecified"

        ::= { oaEfrmSfpInfoEntry 25 }

oaEfrmSfpInfoVendorPN OBJECT-TYPE
        SYNTAX  DisplayString (SIZE(0..16))
        MAX-ACCESS read-only
        STATUS	current
        DESCRIPTION
        "The sfp vendor part number (Vendor PN) or product name if the
        Vendor PN is unspecified, the null string will be returned"

        ::= { oaEfrmSfpInfoEntry 26 }

oaEfrmSfpInfoVendorRev OBJECT-TYPE
        SYNTAX  DisplayString (SIZE(0..4))
        MAX-ACCESS read-only
        STATUS	current
        DESCRIPTION
        "The transceiver vendor's product revision number (Vendor Rev) if the
        Vendor Rev is unspecified, the null string will be returned"

        ::= { oaEfrmSfpInfoEntry 27 }

oaEfrmSfpInfoLaserWavelength OBJECT-TYPE
        SYNTAX  Integer32
        UNITS  "0.01 Nano Meter(nm)"
        MAX-ACCESS read-only
        STATUS	current
        DESCRIPTION
        "Nominal Transmitter output wavelength at room temperature.
        Units: 0.01 Nano Meter(nm)"

        ::= { oaEfrmSfpInfoEntry 28 }

-- Extended ID Fields --
oaEfrmSfpInfoVendorSN OBJECT-TYPE
        SYNTAX  DisplayString (SIZE(0..16))
        MAX-ACCESS read-only
        STATUS	current
        DESCRIPTION
        "The Sfp vendor serial number (Vendor SN) if the Vendor SN is
        unspecified, the null string will be returned"

        ::= { oaEfrmSfpInfoEntry 32 }

oaEfrmSfpInfoVendorDate OBJECT-TYPE
        SYNTAX  DisplayString (SIZE(8))
        MAX-ACCESS read-only
        STATUS	current
        DESCRIPTION
        "The Vendor's date. Formated: YY MM DD "

        ::= { oaEfrmSfpInfoEntry 33 }

oaEfrmSfpInfoVendorSpecLotCode OBJECT-TYPE
        SYNTAX  DisplayString (SIZE(2))
        MAX-ACCESS read-only
        STATUS	current
        DESCRIPTION
        "The Vendor Specific Lot code. A null value indicates that
        the lot code is unspecified."

        ::= { oaEfrmSfpInfoEntry 34 }

oaEfrmSfpInfoVendorSpecData OBJECT-TYPE
        SYNTAX  OCTET STRING (SIZE(0..32))
        MAX-ACCESS read-only
        STATUS	current
        DESCRIPTION
        "Vendor Specific Information which can be read from the SFP transceiver
        (Reference: SFF-8472, revision 9.3 -  Registers 96-127 )"

        ::= { oaEfrmSfpInfoEntry 35 }

oaEfrmSfpInfoDiagnosticPowerType OBJECT-TYPE
        SYNTAX  INTEGER {
                unknown(1),
                average(2),
                oma(3)
        }
        MAX-ACCESS read-only
        STATUS	current
        DESCRIPTION
        "The diagnostic monitoring receive power type in the SFP transceiver.
        unknown - Unknown
        avarage - Received power measurement type is avarage
        oma - Received power measurement type is OMA"

        ::= { oaEfrmSfpInfoEntry 36 }
       
oaEfrmSfpInfoDigitalDiagnostic OBJECT-TYPE
        SYNTAX  INTEGER {
                unknown(1),
                digitalDiagnostic(2),
                noDigitalDiagnostic(3)
        }
        MAX-ACCESS read-only
        STATUS	current
        DESCRIPTION
        "The diagnostic monitoring implemented in the SFP transceiver.
        unknown - Unknown
        digitalDiagMonitoring - Digital diagnostic monitoring
                                implemented.
        noDigitalDiagMonitoring - Digital diagnostic monitoring
                                not implemented."

        ::= { oaEfrmSfpInfoEntry 37 }
       
oaEfrmSfpInfoDiagCalibration OBJECT-TYPE
        SYNTAX  INTEGER {
                unknown(1),
                externalCalibration(2),
                internalCalibration(3)
        }
        MAX-ACCESS read-only
        STATUS	current
        DESCRIPTION
        "The diagnostic calibration in the SFP transceiver.
         unknown - Unknown
         ExternalCalibration - External Calibration
         InternalCalibration - Internal Calibration"

        ::= { oaEfrmSfpInfoEntry 38 }
       
oaEfrmSfpInfoInstalledStatus OBJECT-TYPE
        SYNTAX  INTEGER {
                unknown(1),
                notInstalled(2),
                installed(3)
        }
        MAX-ACCESS read-only
        STATUS	current
        DESCRIPTION
        "The current installed state of the sfp transceiver
        unknown - Unknown
        notInstalled - the SFP transceiver is not installed
        installed - the sfp transceiver is installed"

        ::= { oaEfrmSfpInfoEntry 40 }

oaEfrmSfpInfofaultStatus OBJECT-TYPE
        SYNTAX  INTEGER {
                unknown(1),
                faulty(2),
                operational(3)
        }
        MAX-ACCESS read-only
        STATUS	current
        DESCRIPTION
        "The current fault state of the sfp transceiver
        unknown - Unknown
        fault - the sfp transceiver is faulty
        operational - the sfp transceiver is working properly"

        ::= { oaEfrmSfpInfoEntry 41 }

oaEfrmSfpInfoEnableStatus OBJECT-TYPE
        SYNTAX  INTEGER {
                unknown(1),
                enabled(2),
                disabled(3)
        }
        MAX-ACCESS read-only
        STATUS	current
        DESCRIPTION
        "The current enable state of the sfp transceiver
        unknown - Unknown
        enabled - the sfp transceiver has been enabled
        disabled - the sfp transceiver has been diabled"

        ::= { oaEfrmSfpInfoEntry 42 }

-- ************************************************************
-- SFP Diagnostics Table
-- ************************************************************

oaEfrmSfpDiagnosticTable OBJECT-TYPE
        SYNTAX SEQUENCE OF OaEfrmSfpDiagnosticEntry
        MAX-ACCESS not-accessible
        STATUS current
        DESCRIPTION
        "The sfp real time diagnostic table."

       ::= { oaEfrmSfpMIBObjects 3 }

oaEfrmSfpDiagnosticEntry OBJECT-TYPE
        SYNTAX     OaEfrmSfpDiagnosticEntry
        MAX-ACCESS not-accessible
        STATUS current
        DESCRIPTION
        "An entry in the SFP Real Time Diagnostic Table"

        INDEX { oaEfrmCpeLocalPortIndex, oaEfrmCpeCPEPortIndex }

        ::= { oaEfrmSfpDiagnosticTable 1 }

OaEfrmSfpDiagnosticEntry ::= SEQUENCE {
-- Real Time Readouts
    oaEfrmSfpDiagnosticTemperature   Integer32,
    oaEfrmSfpDiagnosticVcc           Integer32,
    oaEfrmSfpDiagnosticTxBias        Integer32,
    oaEfrmSfpDiagnosticTxPower       Integer32,
    oaEfrmSfpDiagnosticRxPower       Integer32
}

oaEfrmSfpDiagnosticTemperature OBJECT-TYPE
        SYNTAX  Integer32
        UNITS  "1/10 degrees Celsius (C)"
        MAX-ACCESS read-only
        STATUS	current
        DESCRIPTION
        "Internaly measured module temperature.
        Units: 1/10 degrees Celsius (C)"

        ::= { oaEfrmSfpDiagnosticEntry 3 }

oaEfrmSfpDiagnosticVcc OBJECT-TYPE
        SYNTAX  Integer32
        UNITS  "100 micro Volts (V)"
        MAX-ACCESS read-only
        STATUS	current
        DESCRIPTION
        "Internaly measured supply voltage in transceiver.
        Units: 100 micro Volts (V)"

        ::= { oaEfrmSfpDiagnosticEntry 4 }

oaEfrmSfpDiagnosticTxBias OBJECT-TYPE
        SYNTAX  Integer32
        UNITS  "1 micro Amperes (A)"
        MAX-ACCESS read-only
        STATUS	current
        DESCRIPTION
        "Internaly measured Tx Bias current.
        Units: 1 micro Amperes (A)"

        ::= { oaEfrmSfpDiagnosticEntry 5 }

oaEfrmSfpDiagnosticTxPower OBJECT-TYPE
        SYNTAX  Integer32
        UNITS  "0.01 decibel (dBm)"
        MAX-ACCESS read-only
        STATUS	current
        DESCRIPTION
        "Internaly measured Tx output power.
        Units: 0.01 decibel (dBm)"

        ::= { oaEfrmSfpDiagnosticEntry 6 }

oaEfrmSfpDiagnosticRxPower OBJECT-TYPE
        SYNTAX  Integer32
        UNITS  "0.01 decibel (dBm)"
        MAX-ACCESS read-only
        STATUS	current
        DESCRIPTION
        "Internaly measured Rx input power.
        Units: 0.01 decibel (dBm)"

        ::= { oaEfrmSfpDiagnosticEntry 7 }

----------------------------------------------------------------
-- OAM Statistics Table.
----------------------------------------------------------------
oaEfrmCoOamPduStatisticsTable OBJECT-TYPE
        SYNTAX  SEQUENCE OF OaEfrmCoOamPduStatisticsEntry
        MAX-ACCESS  not-accessible
        STATUS  current
        DESCRIPTION
        "A table of OAM statistics for CO."

        ::= { oaEfrmCpeModuletGrp 4 }

oaEfrmCoOamPduStatisticsEntry      OBJECT-TYPE
        SYNTAX  OaEfrmCoOamPduStatisticsEntry
        MAX-ACCESS  not-accessible
        STATUS  current
        DESCRIPTION
        "Contains the OAM statistics for one CO port"

        INDEX { oaEfrmCpeLocalPortIndex }

        ::= { oaEfrmCoOamPduStatisticsTable 1 }

OaEfrmCoOamPduStatisticsEntry ::= SEQUENCE {

    oaEfrmCoInfoTxOamPduStats         Counter32,
    oaEfrmCoInfoRxOamPduStats         Counter32,
    oaEfrmCoEventTxUniqOamPduStats    Counter32,
    oaEfrmCoEventRxUniqOamPduStats    Counter32,
    oaEfrmCoEventTxDuplOamPduStats    Counter32,
    oaEfrmCoEventRxDuplOamPduStats    Counter32,
    oaEfrmCoLpbkTxOamPduStats         Counter32,
    oaEfrmCoLpbkRxOamPduStats         Counter32,
    oaEfrmCoVarReqTxOamPduStats       Counter32,
    oaEfrmCoVarReqRxOamPduStats       Counter32,
    oaEfrmCoVarRepTxOamPduStats       Counter32,
    oaEfrmCoVarRepRxOamPduStats       Counter32,
    oaEfrmCoOrgSpecTxOamPduStats      Counter32,
    oaEfrmCoOrgSpecRxOamPduStats      Counter32,
    oaEfrmCoOrgTotalTxOamPduStats     Counter32,
    oaEfrmCoOrgTotalRxOamPduStats     Counter32
}

 oaEfrmCoInfoTxOamPduStats OBJECT-TYPE
     SYNTAX       Counter32
     MAX-ACCESS   read-only
     STATUS       current
     DESCRIPTION
         "Counts OAM Information frames transmitted 
	  from the local CO port."
     ::= { oaEfrmCoOamPduStatisticsEntry 1 }
                                                                                                     
 oaEfrmCoInfoRxOamPduStats OBJECT-TYPE
     SYNTAX       Counter32
     MAX-ACCESS   read-only
     STATUS       current
     DESCRIPTION
         "Counts OAM Information frames received 
	  on the local CO port."
     ::= { oaEfrmCoOamPduStatisticsEntry 2 }

 oaEfrmCoEventTxUniqOamPduStats OBJECT-TYPE
     SYNTAX       Counter32
     MAX-ACCESS   read-only
     STATUS       current
     DESCRIPTION
         "Counts OAM unique EventNotify frames transmitted 
	  from the local CO port."
     ::= { oaEfrmCoOamPduStatisticsEntry 3 }
                                                                                                     
 oaEfrmCoEventRxUniqOamPduStats OBJECT-TYPE
     SYNTAX       Counter32
     MAX-ACCESS   read-only
     STATUS       current
     DESCRIPTION
         "Counts OAM unique EventNotify frames received 
	  on the local CO port."
     ::= { oaEfrmCoOamPduStatisticsEntry 4 }

 oaEfrmCoEventTxDuplOamPduStats OBJECT-TYPE
     SYNTAX       Counter32
     MAX-ACCESS   read-only
     STATUS       current
     DESCRIPTION
         "Counts OAM duplicate EventNotify frames transmitted 
	  from the local CO port."
     ::= { oaEfrmCoOamPduStatisticsEntry 5 }
                                                                                                     
 oaEfrmCoEventRxDuplOamPduStats OBJECT-TYPE
     SYNTAX       Counter32
     MAX-ACCESS   read-only
     STATUS       current
     DESCRIPTION
         "Counts OAM duplicate EventNotify frames received 
	  on the local CO port."
     ::= { oaEfrmCoOamPduStatisticsEntry 6 }

 oaEfrmCoLpbkTxOamPduStats OBJECT-TYPE
     SYNTAX       Counter32
     MAX-ACCESS   read-only
     STATUS       current
     DESCRIPTION
         "Counts OAM Loopback frames transmitted 
	  from the local CO port."
     ::= { oaEfrmCoOamPduStatisticsEntry 7 }
                                                                                                     
 oaEfrmCoLpbkRxOamPduStats OBJECT-TYPE
     SYNTAX       Counter32
     MAX-ACCESS   read-only
     STATUS       current
     DESCRIPTION
         "Counts OAM Loopback frames received 
	  on the local CO port."
     ::= { oaEfrmCoOamPduStatisticsEntry 8 }

 oaEfrmCoVarReqTxOamPduStats OBJECT-TYPE
     SYNTAX       Counter32
     MAX-ACCESS   read-only
     STATUS       current
     DESCRIPTION
         "Counts OAM VarRequest frames transmitted 
	  from the local CO port."
     ::= { oaEfrmCoOamPduStatisticsEntry 9 }
                                                                                                     
 oaEfrmCoVarReqRxOamPduStats OBJECT-TYPE
     SYNTAX       Counter32
     MAX-ACCESS   read-only
     STATUS       current
     DESCRIPTION
         "Counts OAM VarRequest frames received 
	  on the local CO port."
     ::= { oaEfrmCoOamPduStatisticsEntry 10 }

 oaEfrmCoVarRepTxOamPduStats OBJECT-TYPE
     SYNTAX       Counter32
     MAX-ACCESS   read-only
     STATUS       current
     DESCRIPTION
         "Counts OAM VarResponse frames transmitted 
	  from the local CO port."
     ::= { oaEfrmCoOamPduStatisticsEntry 11 }
                                                                                                     
 oaEfrmCoVarRepRxOamPduStats OBJECT-TYPE
     SYNTAX       Counter32
     MAX-ACCESS   read-only
     STATUS       current
     DESCRIPTION
         "Counts OAM VarResponse frames received 
	  on the local CO port."
     ::= { oaEfrmCoOamPduStatisticsEntry 12 }

 oaEfrmCoOrgSpecTxOamPduStats  OBJECT-TYPE
     SYNTAX       Counter32
     MAX-ACCESS   read-only
     STATUS       current
     DESCRIPTION
         "Counts OAM OrgSpecific frames transmitted 
	  from the local CO port."
     ::= { oaEfrmCoOamPduStatisticsEntry 13 }

 oaEfrmCoOrgSpecRxOamPduStats  OBJECT-TYPE
     SYNTAX       Counter32
     MAX-ACCESS   read-only
     STATUS       current
     DESCRIPTION
         "Counts OAM OrgSpecific frames received 
	  on the local CO port."
     ::= { oaEfrmCoOamPduStatisticsEntry 14 }

 oaEfrmCoOrgTotalTxOamPduStats   OBJECT-TYPE
     SYNTAX       Counter32
     MAX-ACCESS   read-only
     STATUS       current
     DESCRIPTION
         "Counts all OAM frames transmitted 
	  from the local CO port."
     ::= { oaEfrmCoOamPduStatisticsEntry 15 }

 oaEfrmCoOrgTotalRxOamPduStats   OBJECT-TYPE
     SYNTAX       Counter32
     MAX-ACCESS   read-only
     STATUS       current
     DESCRIPTION
         "Counts all OAM frames received 
	  on the local CO port."
     ::= { oaEfrmCoOamPduStatisticsEntry 16 }

----------------------------------------------------------------
-- Phy Statistics Table.
----------------------------------------------------------------
oaEfrmCpePhyStatisticsTable OBJECT-TYPE
        SYNTAX  SEQUENCE OF OaEfrmCpePhyStatisticsEntry
        MAX-ACCESS  not-accessible
        STATUS  current
        DESCRIPTION
        "A table of traffic statistics for CPE."

        ::= { oaEfrmCpeModuletGrp 5 }

oaEfrmCpePhyStatisticsEntry      OBJECT-TYPE
        SYNTAX  OaEfrmCpePhyStatisticsEntry
        MAX-ACCESS  not-accessible
        STATUS  current
        DESCRIPTION
        "Contains the PHY statistics for user/trunk CPE port"

        INDEX { oaEfrmCpeLocalPortIndex, oaEfrmCpePortLogicalType }

        ::= { oaEfrmCpePhyStatisticsTable 1 }

OaEfrmCpePhyStatisticsEntry ::= SEQUENCE {
		
    oaEfrmCpeUcastPktsTxPhyStats    	 Counter32,
    oaEfrmCpeUcastPktsRxPhyStats     	 Counter32,
    oaEfrmCpeMcastPktsTxPhyStats     	 Counter32,
    oaEfrmCpeMcastPktsRxPhyStats     	 Counter32,
    oaEfrmCpeBcastPktsTxPhyStats     	 Counter32,
    oaEfrmCpeBcastPktsRxPhyStats     	 Counter32,
    oaEfrmCpeDiscardTxPhyStats       	 Counter32,
    oaEfrmCpeDiscardRxPhyStats      	 Counter32,
    oaEfrmCpeAllignErrRxPhyStats         Counter32,
    oaEfrmCpeFCSErrRxPhyStats            Counter32,
    oaEfrmCpeUnderSizeErrRxPhyStats      Counter32,
    oaEfrmCpeOverSizeErrRxPhyStats       Counter32,
    oaEfrmCpeJabbersErrRxPhyStats        Counter32,
    oaEfrmCpeDeferredsErrPhyStats        Counter32,
    oaEfrmCpeSingleCollPhyStats          Counter32,
    oaEfrmCpeMultipleCollPhyStats        Counter32,
    oaEfrmCpeLateCollPhyStats            Counter32,
    oaEfrmCpeExcessCollPhyStats          Counter32
}

 oaEfrmCpeUcastPktsTxPhyStats OBJECT-TYPE
     SYNTAX       Counter32
     MAX-ACCESS   read-only
     STATUS       current
     DESCRIPTION
         "Counts Unicast frames transmitted from the CPE port 
	  connected to the local CO port."
     ::= { oaEfrmCpePhyStatisticsEntry 1 }

 oaEfrmCpeUcastPktsRxPhyStats OBJECT-TYPE
     SYNTAX       Counter32
     MAX-ACCESS   read-only
     STATUS       current
     DESCRIPTION
         "Counts Unicast frames received on the CPE port 
	  connected to the local CO port."
     ::= { oaEfrmCpePhyStatisticsEntry 2 }

 oaEfrmCpeMcastPktsTxPhyStats OBJECT-TYPE
     SYNTAX       Counter32
     MAX-ACCESS   read-only
     STATUS       current
     DESCRIPTION
         "Counts Multicast frames transmitted from the CPE port 
	  connected to the local CO port."
     ::= { oaEfrmCpePhyStatisticsEntry 3 }

 oaEfrmCpeMcastPktsRxPhyStats OBJECT-TYPE
     SYNTAX       Counter32
     MAX-ACCESS   read-only
     STATUS       current
     DESCRIPTION
         "Counts Multicast frames received on the CPE port 
	  connected to the local CO port."
     ::= { oaEfrmCpePhyStatisticsEntry 4 }

 oaEfrmCpeBcastPktsTxPhyStats OBJECT-TYPE
     SYNTAX       Counter32
     MAX-ACCESS   read-only
     STATUS       current
     DESCRIPTION
         "Counts Broadcast frames transmitted from the CPE port 
	  connected to the local CO port."
     ::= { oaEfrmCpePhyStatisticsEntry 5 }

 oaEfrmCpeBcastPktsRxPhyStats OBJECT-TYPE
     SYNTAX       Counter32
     MAX-ACCESS   read-only
     STATUS       current
     DESCRIPTION
         "Counts Broadcast frames received on the CPE port 
	  connected to the local CO port."
     ::= { oaEfrmCpePhyStatisticsEntry 6 }

 oaEfrmCpeDiscardTxPhyStats OBJECT-TYPE
     SYNTAX       Counter32
     MAX-ACCESS   read-only
     STATUS       current
     DESCRIPTION
         "Counts lost frames transmitted from the CPE port 
	  connected to the local CO port."
     ::= { oaEfrmCpePhyStatisticsEntry 7 }

 oaEfrmCpeDiscardRxPhyStats OBJECT-TYPE
     SYNTAX       Counter32
     MAX-ACCESS   read-only
     STATUS       current
     DESCRIPTION
         "Counts lost frames received on the CPE port 
	  connected to the local CO port."
     ::= { oaEfrmCpePhyStatisticsEntry 8 }

 oaEfrmCpeAllignErrRxPhyStats OBJECT-TYPE
     SYNTAX       Counter32
     MAX-ACCESS   read-only
     STATUS       current
     DESCRIPTION
         "Counts Allignment Error frames received on the CPE port 
	  connected to the local CO port."
     ::= { oaEfrmCpePhyStatisticsEntry 9 }

 oaEfrmCpeFCSErrRxPhyStats OBJECT-TYPE
     SYNTAX       Counter32
     MAX-ACCESS   read-only
     STATUS       current
     DESCRIPTION
         "Counts FSC Error frames received on the CPE port 
	  connected to the local CO port."
     ::= { oaEfrmCpePhyStatisticsEntry 10 }

 oaEfrmCpeUnderSizeErrRxPhyStats OBJECT-TYPE
     SYNTAX       Counter32
     MAX-ACCESS   read-only
     STATUS       current
     DESCRIPTION
         "Counts Undersize Error frames received on the CPE port 
	  connected to the local CO port."
     ::= { oaEfrmCpePhyStatisticsEntry 11 }

 oaEfrmCpeOverSizeErrRxPhyStats OBJECT-TYPE
     SYNTAX       Counter32
     MAX-ACCESS   read-only
     STATUS       current
     DESCRIPTION
         "Counts Oversize Error frames received on the CPE port 
	  connected to the local CO port."
     ::= { oaEfrmCpePhyStatisticsEntry 12 }

 oaEfrmCpeJabbersErrRxPhyStats OBJECT-TYPE
     SYNTAX       Counter32
     MAX-ACCESS   read-only
     STATUS       current
     DESCRIPTION
         "Counts Jabbers Error frames received on the CPE port 
	  connected to the local CO port."
     ::= { oaEfrmCpePhyStatisticsEntry 13 }

 oaEfrmCpeDeferredsErrPhyStats OBJECT-TYPE
     SYNTAX       Counter32
     MAX-ACCESS   read-only
     STATUS       current
     DESCRIPTION
         "Counts Deferreds Error frames transmitted from the CPE port 
	  connected to the local CO port."
     ::= { oaEfrmCpePhyStatisticsEntry 14 }

 oaEfrmCpeSingleCollPhyStats OBJECT-TYPE
     SYNTAX       Counter32
     MAX-ACCESS   read-only
     STATUS       current
     DESCRIPTION
         "Counts Single Collision frames transmitted from the CPE port 
	  connected to the local CO port."
     ::= { oaEfrmCpePhyStatisticsEntry 15 }

 oaEfrmCpeMultipleCollPhyStats OBJECT-TYPE
     SYNTAX       Counter32
     MAX-ACCESS   read-only
     STATUS       current
     DESCRIPTION
         "Counts Multiple Collision frames transmitted from the CPE port 
	  connected to the local CO port."
     ::= { oaEfrmCpePhyStatisticsEntry 16 }

 oaEfrmCpeLateCollPhyStats OBJECT-TYPE
     SYNTAX       Counter32
     MAX-ACCESS   read-only
     STATUS       current
     DESCRIPTION
         "Counts Late Collision frames transmitted from the CPE port 
	  connected to the local CO port."
     ::= { oaEfrmCpePhyStatisticsEntry 17 }

 oaEfrmCpeExcessCollPhyStats OBJECT-TYPE
     SYNTAX       Counter32
     MAX-ACCESS   read-only
     STATUS       current
     DESCRIPTION
         "Counts Excess Collision frames transmitted from the CPE port 
	  connected to the local CO port."
     ::= { oaEfrmCpePhyStatisticsEntry 18 }

-- ************************************************************
-- Objects in the Device's TRAPs Variables Group
-- ************************************************************
        
oaEfrmCpeTrapVars            OBJECT IDENTIFIER ::= { oaEfrmCpe 50 }

oaEfrmCpeTrapDescription  OBJECT-TYPE
        SYNTAX  DisplayString (SIZE(0..255))
        MAX-ACCESS  read-only
        STATUS  current
        DESCRIPTION
        "The description of the Event occures."

        ::= { oaEfrmCpeTrapVars 1 }

-- ************************************************************
-- Notification Definition section
-- ************************************************************

oaEfmCpeEventCritical NOTIFICATION-TYPE
        OBJECTS {
            oaEfrmCpeLocalPortIndex,
            oaEfrmCpeTrapDescription
        }
        STATUS  current
        DESCRIPTION
        "The SNMP trap that is generated when
         Critical event is received from CPE."

      ::= { oaEfrmCpeNotifications 14}

oaEfmCpeEventGasp NOTIFICATION-TYPE
        OBJECTS {
            oaEfrmCpeLocalPortIndex,
            oaEfrmCpeTrapDescription
        }
        STATUS  current
        DESCRIPTION
        "The SNMP trap that is generated when
         Dying Gasp event is received from CPE."

      ::= { oaEfrmCpeNotifications 15}

oaEfmCpeEventLinkFault NOTIFICATION-TYPE
        OBJECTS {
            oaEfrmCpeLocalPortIndex,
            oaEfrmCpeTrapDescription
        }
        STATUS  current
        DESCRIPTION
        "The SNMP trap that is generated when
         Link Fault event is received from CPE."

      ::= { oaEfrmCpeNotifications 16}

oaEfmCpeEventErrSymbolPeriod NOTIFICATION-TYPE
        OBJECTS {
            oaEfrmCpeLocalPortIndex,
            oaEfrmCpeTrapDescription
        }
        STATUS  current
        DESCRIPTION
        "The SNMP trap that is generated when
         Err Symbol Period event is received from CPE."

      ::= { oaEfrmCpeNotifications 17}

oaEfmCpeEventErrFrame NOTIFICATION-TYPE
        OBJECTS {
            oaEfrmCpeLocalPortIndex,
            oaEfrmCpeTrapDescription
        }
        STATUS  current
        DESCRIPTION
        "The SNMP trap that is generated when
         Err Frame event is received from CPE."

      ::= { oaEfrmCpeNotifications 18}

oaEfmCpeEventErrFramePeriod NOTIFICATION-TYPE
        OBJECTS {
            oaEfrmCpeLocalPortIndex,
            oaEfrmCpeTrapDescription
        }
        STATUS  current
        DESCRIPTION
        "The SNMP trap that is generated when
         Err Frame Period event is received from CPE."

      ::= { oaEfrmCpeNotifications 19}

oaEfmCpeEventErrFrameSecSum NOTIFICATION-TYPE
        OBJECTS {
            oaEfrmCpeLocalPortIndex,
            oaEfrmCpeTrapDescription
        }
        STATUS  current
        DESCRIPTION
        "The SNMP trap that is generated when
         Err Frame Second Summary event is received from CPE."

      ::= { oaEfrmCpeNotifications 23}


oaEfmCpeEventCpeUserPortLink NOTIFICATION-TYPE
        OBJECTS {
            oaEfrmCpeLocalPortIndex,
            oaEfrmCpePortLink,	
            oaEfrmCpeTrapDescription
        }
        STATUS  current
        DESCRIPTION
        "The SNMP trap that is generated when
         user port link change event is received from CPE."

      ::= { oaEfrmCpeNotifications 24}

oaEfmCoPortEventConnectionUp NOTIFICATION-TYPE
        OBJECTS {
            oaEfrmCpeLocalPortIndex,
            oaEfrmCpeTrapDescription
        }
        STATUS  current
        DESCRIPTION
        "The SNMP trap that is generated when
         802.3ah connection with CPE became up or down.
         The [oaEfrmCpeTrapDescription] string value
         will be 'up' or 'down'."

      ::= { oaEfrmCpeNotifications 25}

oaEfmCoPortEventRdndHomeChange NOTIFICATION-TYPE
        OBJECTS {
            oaEfrmCpeLocalPortIndex,
            oaEfrmCpeTrapDescription
        }
        STATUS  current
        DESCRIPTION
        "The SNMP trap that is generated when
         802.3ah CO port Redundancy Mode became active or inactive."

      ::= { oaEfrmCpeNotifications 26}

oaEfmCpeEventGaspClear NOTIFICATION-TYPE
        OBJECTS {
            oaEfrmCpeLocalPortIndex,
            oaEfrmCpeTrapDescription
        }
        STATUS  current
        DESCRIPTION
        "The SNMP trap that is generated when
         Dying Gasp Clear event is received from CPE."

      ::= { oaEfrmCpeNotifications 27}


-- *******************************************************************
--  Conformance Information 
-- ******************************************************************* 

oaEfrmCpeMIBCompliances     OBJECT IDENTIFIER ::= { oaEfrmCpeConformance 1 }
oaEfrmCpeMIBGroups          OBJECT IDENTIFIER ::= { oaEfrmCpeConformance 2 }

oaEfrmCpeMIBCompliance MODULE-COMPLIANCE
    STATUS current
    DESCRIPTION
        "The core compliance statement for all EFRM MIB implementations." 

    MODULE -- this module 
        MANDATORY-GROUPS { 
                          oaEfrmCpeMandatoryGroup,
                          oaEfrmCpePortMandatoryGroup,
                          oaEfrmCpeNotificationsGroup
                         }
        GROUP oaEfrmCpeOptionalGroup
        DESCRIPTION 
        "Optional objects for whole Cpe Module."

        GROUP oaEfrmCpePortOptionalGroup
        DESCRIPTION 
        "Optional objects for corresponding Cpe Port."

        GROUP oaEfrmSfpInfoOptionalGroup
        DESCRIPTION 
        "Optional objects for corresponding SFP parameters."

        GROUP oaEfrmSfpDiagnosticOptionalGroup
        DESCRIPTION 
        "Optional objects for corresponding SFP Digital Diagnostics."

    ::= { oaEfrmCpeMIBCompliances 1 }

-- ...................................................................
-- Conformance Groups 
-- ................................................................... 
 
oaEfrmCpeMandatoryGroup  OBJECT-GROUP
    OBJECTS { 
             oaEfrmCpeGenSupport,
             oaEfrmCoOam,
             oaEfrmCpeLocalPortIndex,
             oaEfrmCpeModuleType,
             oaEfrmCpeModuleIPLessEnable,
             oaEfrmCoPortEnable,
             oaEfrmCpeModuleIPLessLink,
             oaEfrmCpeNumberOfPorts,
             oaEfrmCpeTrapDescription,
             oaEfrmCpeModuleMacAddress,
             oaEfrmCpeModuleAppRev,
             oaEfrmCpeModuleVendorOUI,
             oaEfrmCpeModuleVendorInfo,
             oaEfrmCpeModuleMaxPduSize,
             oaEfrmCoModuleDiscoveryState,
             oaEfrmCoModulePduState
            }
    STATUS current 
    DESCRIPTION 
        "Mandatory CPE objects for EFRM feature
         support in the Device."

    ::= { oaEfrmCpeMIBGroups 1 }
 
oaEfrmCpePortMandatoryGroup  OBJECT-GROUP
    OBJECTS { 
             oaEfrmCpeCPEPortIndex,
             oaEfrmCpePortLink,
             oaEfrmCpePortConnectorType,
             oaEfrmCpePortConnectorSubType,
             oaEfrmCpePortSfpPresent
            }
    STATUS current 
    DESCRIPTION 
        "Mandatory CPE Port objects for EFRM feature
         support in the Device."

    ::= { oaEfrmCpeMIBGroups 2 }
 
oaEfrmCpeOptionalGroup  OBJECT-GROUP
    OBJECTS { 
             oaEfrmCpeModuleRemoteLoopback,
             oaEfrmCpeModuleEnable,
             oaEfrmCpeCpeCoSW,
             oaEfrmCpeCpeManagementSW,
             oaEfrmCpeCpeLINSW,
             oaEfrmCpeModuleMdiSW,
             oaEfrmCpePowerFail,
             oaEfrmCpeModuleName,
             oaEfrmCpeModuleFpgaRev,
             oaEfrmCpeModuleDiscoveryState,
             oaEfrmCpeModulePduState,
             oaEfrmCoRedundantMode,
             oaEfrmCoRedundantActState

            } 
    STATUS current 
    DESCRIPTION 
        "Optional CPE objects for EFM 802.3ah feature
         support in the Device."

    ::= { oaEfrmCpeMIBGroups 3 }

oaEfrmCpePortOptionalGroup  OBJECT-GROUP
    OBJECTS { 
             oaEfrmCpePortType,
             oaEfrmCpePortAutoNegotiation,
             oaEfrmCpePortDuplex,
             oaEfrmCpePortSpeed,
             oaEfrmCpePortActivity,
             oaEfrmCpePortLogicalType,
             oaEfrmCpePortAutoNegCaps,
	     oaEfrmCpePortMdi,
	     oaEfrmCpePortAutoSense,

    	     oaEfrmCoInfoTxOamPduStats,
	     oaEfrmCoInfoRxOamPduStats,
	     oaEfrmCoEventTxUniqOamPduStats,
    	     oaEfrmCoEventRxUniqOamPduStats,
	     oaEfrmCoEventTxDuplOamPduStats,
	     oaEfrmCoEventRxDuplOamPduStats,
	     oaEfrmCoLpbkTxOamPduStats,
    	     oaEfrmCoLpbkRxOamPduStats,
    	     oaEfrmCoVarReqTxOamPduStats,
    	     oaEfrmCoVarReqRxOamPduStats,
   	     oaEfrmCoVarRepTxOamPduStats,
    	     oaEfrmCoVarRepRxOamPduStats,
    	     oaEfrmCoOrgSpecTxOamPduStats,
    	     oaEfrmCoOrgSpecRxOamPduStats,
    	     oaEfrmCoOrgTotalTxOamPduStats,
    	     oaEfrmCoOrgTotalRxOamPduStats,

    	     oaEfrmCpeUcastPktsTxPhyStats,
             oaEfrmCpeUcastPktsRxPhyStats,
             oaEfrmCpeMcastPktsTxPhyStats,
             oaEfrmCpeMcastPktsRxPhyStats,
             oaEfrmCpeBcastPktsTxPhyStats,
             oaEfrmCpeBcastPktsRxPhyStats,
             oaEfrmCpeDiscardTxPhyStats,
             oaEfrmCpeDiscardRxPhyStats,
             oaEfrmCpeAllignErrRxPhyStats,
             oaEfrmCpeFCSErrRxPhyStats,
             oaEfrmCpeUnderSizeErrRxPhyStats,
             oaEfrmCpeOverSizeErrRxPhyStats,
             oaEfrmCpeJabbersErrRxPhyStats,
             oaEfrmCpeDeferredsErrPhyStats,
             oaEfrmCpeSingleCollPhyStats,
             oaEfrmCpeMultipleCollPhyStats,
             oaEfrmCpeLateCollPhyStats,
             oaEfrmCpeExcessCollPhyStats

            }
    STATUS current 
    DESCRIPTION 
        "Optional CPE Port objects for EFM 802.3ah feature
         support in the Device."

    ::= { oaEfrmCpeMIBGroups 4 }

oaEfrmCpeNotificationsGroup  NOTIFICATION-GROUP
    NOTIFICATIONS {
                   oaEfmCpeEventCritical,
                   oaEfmCpeEventGasp,
                   oaEfmCpeEventLinkFault,
                   oaEfmCpeEventErrSymbolPeriod,
                   oaEfmCpeEventErrFrame,
                   oaEfmCpeEventErrFramePeriod,
                   oaEfmCpeEventErrFrameSecSum,
                   oaEfmCpeEventCpeUserPortLink,
                   oaEfmCoPortEventConnectionUp,
                   oaEfmCoPortEventRdndHomeChange,
                   oaEfmCpeEventGaspClear
                  }
    STATUS current 
    DESCRIPTION 
        "The notification which are required to be supported by
         implementations of this MIB."

    ::= { oaEfrmCpeMIBGroups 5 }

oaEfrmSfpInfoOptionalGroup  OBJECT-GROUP
    OBJECTS { 
             oaEfrmSfpInfoIdentifier,
             oaEfrmSfpInfoVendorSpecId,
             oaEfrmSfpInfoConnector,
             oaEfrmSfpInfoVendorSpecConnector,
             oaEfrmSfpInfoVendorName,
             oaEfrmSfpInfoVendorOUI,
             oaEfrmSfpInfoVendorPN,
             oaEfrmSfpInfoVendorSN,
             oaEfrmSfpInfoVendorRev,
             oaEfrmSfpInfoLaserWavelength,
             oaEfrmSfpInfoVendorDate,
             oaEfrmSfpInfoVendorSpecLotCode,
             oaEfrmSfpInfoVendorSpecData,
             oaEfrmSfpInfoDiagnosticPowerType,
             oaEfrmSfpInfoDigitalDiagnostic,
             oaEfrmSfpInfoDiagCalibration,
             oaEfrmSfpInfoInstalledStatus,
             oaEfrmSfpInfofaultStatus,
             oaEfrmSfpInfoEnableStatus
            }
    STATUS current 
    DESCRIPTION 
        "Optional SFP Info objects for EFM 802.3ah feature
         support in the Device."

    ::= { oaEfrmCpeMIBGroups 6 }

oaEfrmSfpDiagnosticOptionalGroup  OBJECT-GROUP
    OBJECTS { 
             oaEfrmSfpDiagnosticTemperature,
             oaEfrmSfpDiagnosticVcc,
             oaEfrmSfpDiagnosticTxBias,
             oaEfrmSfpDiagnosticTxPower,
             oaEfrmSfpDiagnosticRxPower
            }
    STATUS current 
    DESCRIPTION 
        "Optional SFP Digital Diagnostics objects for EFM 802.3ah feature
         support in the Device."

    ::= { oaEfrmCpeMIBGroups 7 }

END

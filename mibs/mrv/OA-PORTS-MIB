--  =======================================================================
--  File        : oaports.mib
--  Description : Private MIB for Linux Router
--  By          : Alex & Yakov
--  Supports additional parameters for Ports configuration

-- Copyright (c) 2005 MRV.  All Rights Reserved.
--
--
-- Reproduction of this document is authorized on condition that this
-- copyright notice is included.  This MRV SNMP MIB Specification
-- embodies MRV's proprietary intellectual property.  MRV
-- retains all title and ownership in the specification, including any
-- revisions.
--
-- It is MRV's intent to encourage the widespread use of this
-- specification in connection with the management of MRV's
-- products. MRV grants vendor, end-users, and other interested
-- parties a non-exclusive license to use this specification in
-- connection with the management of MRV's products.
--
-- This specification is supplied "AS IS," and MRV makes no
-- warranty, either express or implied, as to the use, operation,
-- condition, or performance of the specification.
--
-- Copyright text courtesy of MRV
--
-- If you have any questions about this MIB, please call MRV
-- Technical Support Center at 1-800-858-7815 from inside USA or
-- 1-818-773-0900 from outside USA.
--
--
-- MRV retains the right to change this MIB without notification.

OA-PORTS-MIB DEFINITIONS ::= BEGIN

IMPORTS
    MODULE-IDENTITY, OBJECT-TYPE,
    enterprises, Integer32               FROM SNMPv2-SMI
    nbSwitchG1Il                         FROM OS-COMMON-TC-MIB
    MODULE-COMPLIANCE, OBJECT-GROUP      FROM SNMPv2-CONF;


nbPortMediaSelectMIB  MODULE-IDENTITY
    LAST-UPDATED "200603080000Z"
    ORGANIZATION "MRV Communications, Inc."
    CONTACT-INFO
        "Alex Rozin
         MRV Communication, Inc
         http://www.mrv.com
         Email:  ARozin@mrv.com"
    DESCRIPTION
        "Traffic Conditioner Counters management."

    -- Revision history

    REVISION "200603080000Z"
    DESCRIPTION
        "Initial edition."
    ::= { nbPortParams 10 }

-- ************************************************************
-- MIB place Definition
-- ************************************************************

nbPortParams                  OBJECT IDENTIFIER ::= { nbSwitchG1Il 10 }

nbPortMediaSelectConformance  OBJECT IDENTIFIER ::= { nbPortMediaSelectMIB 101 }

-- ************************************************************
-- Textual Conventions
-- ************************************************************


-- --------- nbPortMediaSelectTable ----------------

nbPortMediaSelectTable    OBJECT-TYPE
    SYNTAX       SEQUENCE OF NbPortMediaSelectEntry
    MAX-ACCESS   not-accessible
    STATUS       current
    DESCRIPTION
        "Table contains the Media Select mode and status
         for the Combo based Ports in the device.
         The number of entries is given by 'nbsSysPortsNumber'."

    ::= { nbPortMediaSelectMIB 5 }

nbPortMediaSelectEntry    OBJECT-TYPE
    SYNTAX       NbPortMediaSelectEntry
    MAX-ACCESS   not-accessible
    STATUS       current
    DESCRIPTION
        "."

    INDEX {
           nbPortMediaSelectPort
          }

    ::= { nbPortMediaSelectTable 1 }

NbPortMediaSelectEntry ::= SEQUENCE
                           {
                            nbPortMediaSelectPort     Integer32,
                            nbPortMediaSelectMode     INTEGER,
                            nbPortMediaSelectStatus   INTEGER
                           }

nbPortMediaSelectPort       OBJECT-TYPE
    SYNTAX       Integer32 (1..65535)
    MAX-ACCESS   not-accessible
    STATUS       current
    DESCRIPTION
        "A unique value for each port.
         This value ranges from 1 to the value of 'nbsSysPortsNumber'."

    ::= { nbPortMediaSelectEntry 1 }

nbPortMediaSelectMode     OBJECT-TYPE
    SYNTAX  INTEGER {
                none        (1),
                autoSelect  (2),
                forceRJ45   (3),
                forceSFP    (4),
                forceSFP100 (5)
    }
    MAX-ACCESS  read-write
    STATUS      current
    DESCRIPTION
        "The Media Select Mode of the Port for different Combo
         Ethernet Ports ['nbsPortCfgLanType'=50 [ethComboDualMode] or
         'nbsPortCfgLanType'=51 [ethComboTriMode]]:
         'none' [1]      - for all not Combo Ports(SNMP GET only).
         'autoSelect'[2] - Port Media selected automatically by Agent.
         'forceRJ45'[3]  - auto/10/100/1000MBps RJ45 Port selected by customer.
         'forceSFP'[4]   - auto/1000MBps SFP Port selected by customer
                           [relevant for 'nbsPortCfgLanType'=50 or
                           for 'nbsPortCfgLanType'=51].
         'forceSFP100'[5]- 100MBps SFP Port selected by customer
                           [relevant only for 'nbsPortCfgLanType'=51]."

    DEFVAL { autoSelect }

    ::= { nbPortMediaSelectEntry 2 }

nbPortMediaSelectStatus   OBJECT-TYPE
    SYNTAX  INTEGER {
                unknown    (1),
                rj45       (2),
                sfp        (3),
                sfp100     (4)
    }
    MAX-ACCESS  read-only
    STATUS      current
    DESCRIPTION
        "The Actual Media Select Status of the Port for different Combo
         Ethernet Ports ['nbsPortCfgLanType'=50 [ethComboDualMode] or
         'nbsPortCfgLanType'=51 [ethComboTriMode]]:
         'unknown' [1]   - When 'nbPortMediaSelectMode'=2 [autoSelect] or
                           Port Link is Down.
                           The Corresponding Port Media will be configured
                           automatically by Agent after Port Link became Up.
         'forceRJ45'[2]  - auto/10/100/1000MBps RJ45 Port successfully configured.
         'forceSFP'[3]   - auto/1000MBps SFP Port successfully configured.
         'forceSFP100'[4]- 100MBps SFP Port successfully configured."

    ::= { nbPortMediaSelectEntry 3 }

-- *******************************************************************
--  Conformance Information 
-- ******************************************************************* 

nbPortMediaSelectMIBCompliances  OBJECT IDENTIFIER ::= { nbPortMediaSelectConformance 1 }
nbPortMediaSelectMIBGroups       OBJECT IDENTIFIER ::= { nbPortMediaSelectConformance 2 }

nbPortMediaSelectMIBCompliance MODULE-COMPLIANCE
    STATUS current
    DESCRIPTION
        "The core compliance statement for all nbPortMediaSelectMIB implementations."

    MODULE -- this module 

        MANDATORY-GROUPS {
                          nbPortMediaSelectGroup
                         }

    ::= { nbPortMediaSelectMIBCompliances 1 }

-- ................................................................... 
-- Conformance Groups 
-- ................................................................... 
  
nbPortMediaSelectGroup  OBJECT-GROUP
    OBJECTS { 
             nbPortMediaSelectMode,
             nbPortMediaSelectStatus
            }
    STATUS current 
    DESCRIPTION 
        "Optional objects for grouping of Port Media Select parameters."

    ::= { nbPortMediaSelectMIBGroups 2 }
 

END

--  =======================================================================
--  File        : oaPrtcl.mib
--  Description : Private MIB for SNMP Protocol fields configuration
--  By          : Asaf & Yakov
--  Version     : 0.1
--  Date        : 
--  =======================================================================
--
--
-- Copyright (c) 2006 MRV.  All Rights Reserved.
--
--
-- Reproduction of this document is authorized on condition that this
-- copyright notice is included.  This MRV SNMP MIB Specification
-- embodies MRV's proprietary intellectual property.  MRV
-- retains all title and ownership in the specification, including any
-- revisions.
--
-- It is MRV's intent to encourage the widespread use of this
-- specification in connection with the management of MRV's
-- products. MRV grants vendor, end-users, and other interested
-- parties a non-exclusive license to use this specification in
-- connection with the management of MRV's products.
--
-- This specification is supplied "AS IS," and MRV makes no
-- warranty, either express or implied, as to the use, operation,
-- condition, or performance of the specification.
--
-- Copyright text courtesy of MRV
--
-- If you have any questions about this MIB, please call MRV
-- Technical Support Center at 1-800-858-7815 from inside USA or
-- 1-818-773-0900 from outside USA.
--
--
-- MRV retains the right to change this MIB without notification.
--

OA-PROTOCOL-PARAMETERS-MIB DEFINITIONS ::= BEGIN

  IMPORTS
    MODULE-IDENTITY, OBJECT-TYPE, enterprises    FROM SNMPv2-SMI    -- RFC2578
    MODULE-COMPLIANCE, OBJECT-GROUP              FROM SNMPv2-CONF   -- RFC2580
    DisplayString,TEXTUAL-CONVENTION             FROM SNMPv2-TC;    -- RFC2579

oaProtocolParams  MODULE-IDENTITY
    LAST-UPDATED "200811240000Z"
    ORGANIZATION "MRV Communications, Inc."
    CONTACT-INFO
        "Alex Rozin
         MRV Communication, Inc
         http://www.mrv.com
         Email:  ARozin@mrv.com

         Asaf Henig
         MRV Communication, Inc
         http://www.mrv.com
         Email:  ahenig@mrv.com

         Yakov Vaisman
         MRV Communication, Inc
         http://www.mrv.com
         Email:  yvaisman@mrv.com
	"
    DESCRIPTION
        "Supports information about different protocols parameters."

    -- Revision history

    REVISION "200811240000Z"
    DESCRIPTION
        "Initial edition."
         ::= { oaManagement 42 }

------------------------------------------------------------------------------
-- Object Identifier Definition
------------------------------------------------------------------------------

oaccess                OBJECT IDENTIFIER ::= { enterprises 6926 }
oaManagement           OBJECT IDENTIFIER ::= { oaccess 1 }

oaSnmpPrtcl            OBJECT IDENTIFIER ::= { oaProtocolParams 2 }
oaPrtclConformance     OBJECT IDENTIFIER ::= { oaProtocolParams 101 }

------------------------------------------------------------------------------
-- Textual conventions
------------------------------------------------------------------------------

EntryValidator ::= TEXTUAL-CONVENTION
    STATUS       current
    DESCRIPTION
      "Admin Status for controlling of the entry."
    SYNTAX       INTEGER { 
                   nothing    (2),
                   delete     (3),
                   create     (4),
                   enable     (5),
                   disable    (6)
                 }

------------------------------------------------------------------------------
-- Objects in the SNMP Protocol Parameters Group
------------------------------------------------------------------------------

------------------------------------------------------------------------------
-- SNMP Communities Table
------------------------------------------------------------------------------

oaSnmpSecurStrTable  OBJECT-TYPE
    SYNTAX  SEQUENCE OF OaSnmpSecurStrEntry
    MAX-ACCESS   not-accessible
    STATUS       current
    DESCRIPTION
    "This table configures Device SNMP Communities."
    ::= { oaSnmpPrtcl 2 }

oaSnmpSecurStrEntry OBJECT-TYPE
    SYNTAX       OaSnmpSecurStrEntry
    MAX-ACCESS   not-accessible
    STATUS       current
    DESCRIPTION
    "Device SNMP Community entry."
    INDEX { oaSnmpSecurStrName }
    ::= { oaSnmpSecurStrTable 1 }

OaSnmpSecurStrEntry ::= SEQUENCE {
    oaSnmpSecurStrName                 DisplayString,
    oaSnmpSecurStrAccessPermission     INTEGER,
    oaSnmpSecurStrAdminStatus          EntryValidator
    }

oaSnmpSecurStrName       OBJECT-TYPE
    SYNTAX       DisplayString (SIZE (0..33))
    MAX-ACCESS   not-accessible
    STATUS       current
    DESCRIPTION
    "SNMP packet Community Name."
    ::= { oaSnmpSecurStrEntry 1 }

oaSnmpSecurStrAccessPermission  OBJECT-TYPE
    SYNTAX       INTEGER {
       readOnly   (1),
       readWrite  (2)
    }
    MAX-ACCESS   read-write
    STATUS       current
    DESCRIPTION
    "SNMP packet Community Access Permission."
    ::= { oaSnmpSecurStrEntry 2 }

oaSnmpSecurStrAdminStatus	OBJECT-TYPE
    SYNTAX       EntryValidator
    MAX-ACCESS   read-write
    STATUS  current
    DESCRIPTION
    "Controls creation/modification/invalidation of the entry."
    ::= { oaSnmpSecurStrEntry 11 }

-- *******************************************************************
--  Conformance Information 
-- ******************************************************************* 
 
oaPrtclMIBCompliances  OBJECT IDENTIFIER ::= { oaPrtclConformance 1 }
oaPrtclMIBGroups       OBJECT IDENTIFIER ::= { oaPrtclConformance 2 }

oaPrtclMIBCompliance   MODULE-COMPLIANCE
    STATUS current 
    DESCRIPTION 
    "The core compliance statement for all
     'oaProtocolParams' MIB implementations."

    MODULE -- this module

    MANDATORY-GROUPS { 
                      oaSnmpSecurStrGroup
                     } 

    ::= { oaPrtclMIBCompliances 1 }

-- ...................................................................
-- Conformance Groups 
-- ................................................................... 
 
oaSnmpSecurStrGroup  OBJECT-GROUP
    OBJECTS { 
             oaSnmpSecurStrAccessPermission,
             oaSnmpSecurStrAdminStatus
            }
    STATUS current 
    DESCRIPTION 
    "Mandatory objects for grouping of Trap destinations parameters."
    ::= { oaPrtclMIBGroups 1 }
 

END

--  =======================================================================
--  File        : oaSlStat.mib
--  Description : Private MIB for ServiceLevel Statistics
--  By          : Yakov & Inna
--  Version     : 0.1
--  Date        : 
--  =======================================================================
--
--
-- Copyright (c) 2006 MRV.  All Rights Reserved.
--
--
-- Reproduction of this document is authorized on condition that this
-- copyright notice is included.  This MRV SNMP MIB Specification
-- embodies MRV's proprietary intellectual property.  MRV
-- retains all title and ownership in the specification, including any
-- revisions.
--
-- It is MRV's intent to encourage the widespread use of this
-- specification in connection with the management of MRV's
-- products. MRV grants vendor, end-users, and other interested
-- parties a non-exclusive license to use this specification in
-- connection with the management of MRV's products.
--
-- This specification is supplied "AS IS," and MRV makes no
-- warranty, either express or implied, as to the use, operation,
-- condition, or performance of the specification.
--
-- Copyright text courtesy of MRV
--
-- If you have any questions about this MIB, please call MRV
-- Technical Support Center at 1-800-858-7815 from inside USA or
-- 1-818-773-0900 from outside USA.
--
--
-- MRV retains the right to change this MIB without notification.
--

OA-SL-STATISTICS-MIB DEFINITIONS ::= BEGIN

  IMPORTS
    MODULE-IDENTITY, OBJECT-TYPE,
    Counter64, enterprises, Integer32    FROM SNMPv2-SMI    -- RFC2578
    MODULE-COMPLIANCE, OBJECT-GROUP      FROM SNMPv2-CONF;  -- RFC2580

oaSlStatistics  MODULE-IDENTITY
    LAST-UPDATED "200703180000Z"
    ORGANIZATION "MRV Communications, Inc."
    CONTACT-INFO

        "Inna Levin
         MRV Communication, Inc
         http://www.mrv.com
         Email:  ilevin@mrv.com

         Yakov Vaisman
         MRV Communication, Inc
         http://www.mrv.com
         Email:  yvaisman@mrv.com"

    DESCRIPTION
        "Supports information about Service Level statistics per port."

    -- Revision history

    REVISION "200703180000Z"
    DESCRIPTION
        "Initial edition."
    ::= { nbPortParams 9 }

-- ************************************************************
-- MRV Object Identifier Definition
-- ************************************************************

nbase              OBJECT IDENTIFIER ::= { enterprises 629 }
nbSwitchG1         OBJECT IDENTIFIER ::= { nbase 1 }
nbSwitchG1Il       OBJECT IDENTIFIER ::= { nbSwitchG1 50}
nbPortParams       OBJECT IDENTIFIER ::= { nbSwitchG1Il 10 }

oaSlStatConformance   OBJECT IDENTIFIER ::= { oaSlStatistics 101 }

-- ************************************************************
-- Objects in the SlStatistics Group
-- ************************************************************

oaSlStatGenSupport OBJECT-TYPE
    SYNTAX  INTEGER {
       notSupported (1),
       supported    (2)
    }       
    MAX-ACCESS  read-only
    STATUS  current
    DESCRIPTION
    "Service Level Statistics feature support."
    ::= { oaSlStatistics 1 }

-- ************************************************************

oaSlStatTable         OBJECT-TYPE
    SYNTAX  SEQUENCE OF OaSlStatEntry
    MAX-ACCESS   not-accessible
    STATUS       current
    DESCRIPTION
    "This table configures Service Level statistics."
    ::= { oaSlStatistics 2 }

oaSlStatEntry OBJECT-TYPE
    SYNTAX       OaSlStatEntry
    MAX-ACCESS   not-accessible
    STATUS       current
    DESCRIPTION
    "Service Level statistics entry."
    INDEX { oaSlStatPortIndex, oaSlStatServiceLevel }
    ::= { oaSlStatTable 1 }

OaSlStatEntry ::= SEQUENCE {
        oaSlStatPortIndex               Integer32,
        oaSlStatServiceLevel            Integer32,
        oaSlStatAggrOctets              Counter64
}

oaSlStatPortIndex OBJECT-TYPE
    SYNTAX Integer32 (1..256)
    MAX-ACCESS  read-only
    STATUS  current
    DESCRIPTION
    "The index of the local port on the CO-dev
     to which this module is connected."

    ::= { oaSlStatEntry 1 }

oaSlStatServiceLevel OBJECT-TYPE
    SYNTAX Integer32 (1..8)
    MAX-ACCESS  read-only
    STATUS  current
    DESCRIPTION
    "The Service Level value."

    ::= { oaSlStatEntry 2 }

oaSlStatAggrOctets          OBJECT-TYPE
    SYNTAX       Counter64
    MAX-ACCESS   read-only
    STATUS       current       
    DESCRIPTION
    "Admitted bytes for flow aggregate."

    ::= { oaSlStatEntry 3 }

-- *******************************************************************
--  Conformance Information 
-- ******************************************************************* 
 
oaSlStatMIBCompliances  OBJECT IDENTIFIER ::= { oaSlStatConformance 1 }
oaSlStatMIBGroups       OBJECT IDENTIFIER ::= { oaSlStatConformance 2 }

oaSlStatMIBCompliance   MODULE-COMPLIANCE
    STATUS current 
    DESCRIPTION 
    "The core compliance statement for all
     'oaSlStatistics' MIB implementations."

    MODULE -- this module

    MANDATORY-GROUPS { 
                      oaSlStatMandatoryGroup
                     } 

    ::= { oaSlStatMIBCompliances 1 }

-- ...................................................................
-- Conformance Groups 
-- ................................................................... 
 
oaSlStatMandatoryGroup  OBJECT-GROUP
    OBJECTS { 
             oaSlStatGenSupport,
             oaSlStatPortIndex,
             oaSlStatServiceLevel,
             oaSlStatAggrOctets
            }
    STATUS current 
    DESCRIPTION 
    "Mandatory objects for grouping of Service Level statistics parameters."
    ::= { oaSlStatMIBGroups 1 }
 
END

--  =======================================================================
--  File        : osSecurePush.mib
--  Description : Private MIB to manage the "secure push" feature
--  By          : Alex

-- Copyright (c) 2008 MRV.  All Rights Reserved.
--
--
-- Reproduction of this document is authorized on condition that this
-- copyright notice is included.  This MRV SNMP MIB Specification
-- embodies MRV's proprietary intellectual property.  MRV
-- retains all title and ownership in the specification, including any
-- revisions.
--
-- It is MRV's intent to encourage the widespread use of this
-- specification in connection with the management of MRV's
-- products. MRV grants vendor, end-users, and other interested
-- parties a non-exclusive license to use this specification in
-- connection with the management of MRV's products.
--
-- This specification is supplied "AS IS," and MRV makes no
-- warranty, either express or implied, as to the use, operation,
-- condition, or performance of the specification.
--
-- Copyright text courtesy of MRV
--
-- If you have any questions about this MIB, please call MRV
-- Technical Support Center at 1-800-858-7815 from inside USA or
-- 1-818-773-0900 from outside USA.
--
--
-- MRV retains the right to change this MIB without notification.

OS-SECURE-PUSH-MIB DEFINITIONS ::= BEGIN

IMPORTS
                 MODULE-IDENTITY, OBJECT-TYPE, enterprises     FROM SNMPv2-SMI
                 oaOptiSwitch                                  FROM OS-COMMON-TC-MIB
                 MODULE-COMPLIANCE, OBJECT-GROUP               FROM SNMPv2-CONF;

osSecurePush       MODULE-IDENTITY
                 LAST-UPDATED "201212190000Z" -- 19 December 2012
                 ORGANIZATION "MRV Communications, Inc."
                 CONTACT-INFO
                   "Alex Rozin
                    MRV Communication, Inc
                    http://www.mrv.com
                    Email:  ARozin@mrv.com"
                 DESCRIPTION
                    "This private MIB allow to manage the 'secure push' feature"
                 REVISION     "201212190000Z"
                 DESCRIPTION
                    "Initial edition."
                 ::= { oaOptiSwitch 24 }



-- ************************************************************
-- MIB place Definition
-- ************************************************************
osSecurePushGeneral           OBJECT IDENTIFIER ::= { osSecurePush 1 }
osSecurePushConformance       OBJECT IDENTIFIER ::= { osSecurePush 100 }
osSecurePushMIBCompliances    OBJECT IDENTIFIER ::= { osSecurePushConformance 1 }
osSecurePushMIBGroups         OBJECT IDENTIFIER ::= { osSecurePushConformance 2 }

--3456789a123456789b123456789c123456789d123456789e123456789f123456789g123456789

osSecurePushSupport OBJECT-TYPE
   SYNTAX     INTEGER { notSupported(1), supported(2) }
   MAX-ACCESS read-only
   STATUS     current
   DESCRIPTION
      "Indicates that this MIB is supported."
   ::= { osSecurePushGeneral 1 }

osSecurePushConfAdminStatus OBJECT-TYPE
   SYNTAX     INTEGER {
                unknown       (1),
                askFromServer (2)
              }
   MAX-ACCESS read-write
   STATUS     current
   DESCRIPTION
      "The value askFromServer (2) means, that the agent ask the server to download the configuration."
   ::= { osSecurePushGeneral 2 }


--- *******************************************************************
---  Compliance statements
--- ******************************************************************* 

osSecurePushMIBCompliance MODULE-COMPLIANCE
    STATUS current
    DESCRIPTION
        "The core compliance statement for all the implementations." 
    MODULE -- this module 
        MANDATORY-GROUPS {
           osSecurePushMibMandatoryGroup
           }
    ::= { osSecurePushMIBCompliances 1 }

--- ******************************************************************* 
--- Conformance Groups 
--- ******************************************************************* 
 
osSecurePushMibMandatoryGroup  OBJECT-GROUP
  OBJECTS { 
    osSecurePushSupport,
    osSecurePushConfAdminStatus
  }
  STATUS  current 
  DESCRIPTION
    "."
  ::= { osSecurePushMIBGroups 1 } 

END

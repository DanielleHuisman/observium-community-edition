-- flowManagemenet communications with AR.
--  =======================================================================
--  File        : Sec_flow.mib
--  Description : Private mib for flow entries
--  By          : Ilona
--  Version     : 0.2  
--  Date        : 
--  =======================================================================
--
--
-- Copyright (c) 1999 NBase-Xyplex.  All Rights Reserved.
--
--
-- Reproduction of this document is authorized on condition that this
-- copyright notice is included.  This NBase-Xyplex SNMP MIB Specification
-- embodies NBase-Xyplex's proprietary intellectual property.  NBase-Xyplex
-- retains all title and ownership in the specification, including any
-- revisions.
--
-- It is NBase-Xyplex's intent to encourage the widespread use of this
-- specification in connection with the management of NBase-Xyplex's
-- products. NBase-Xyplex grants vendor, end-users, and other interested
-- parties a non-exclusive license to use this specification in
-- connection with the management of NBase-Xyplex's products.
--
-- This specification is supplied "AS IS," and NBase-Xyplex makes no
-- warranty, either express or implied, as to the use, operation,
-- condition, or performance of the specification.
--
-- Copyright text courtesy of NBase-Xyplex
--
-- If you have any questions about this MIB, please call NBase-Xyplex
-- Technical Support Center at 1-800-858-7815 from inside USA or
-- 1-818-773-0900 from outside USA.
--
--
-- NBase-Xyplex retains the right to change this MIB without notification.
--

SEC-FLOW-MIB DEFINITIONS ::= BEGIN

		IMPORTS
				enterprises,
				IpAddress				FROM RFC1155-SMI
				DisplayString				FROM RFC1213-MIB
				OBJECT-TYPE				FROM RFC-1212
				TRAP-TYPE				FROM RFC-1215
				nbSwitchG1				FROM NBASE-G1-MIB;

		  MacAddress ::=  OCTET STRING(SIZE(6))

-- ************************************************************
-- NBase Object Identifier Definition
-- ************************************************************

-- nbase    OBJECT IDENTIFIER ::= { enterprises 629 }
-- nbSwitchG1         OBJECT IDENTIFIER ::= { nbase 1 }
nbSwitchG1Il       OBJECT IDENTIFIER ::= { nbSwitchG1 50}

-- GROUPS for SBC-Accelerouter Interface
nbsAccelerouter    OBJECT IDENTIFIER ::= { nbSwitchG1Il 10}


---------------------------  nbsArGen --------------------------------

nbsArSecFlow		 OBJECT IDENTIFIER ::= { nbsAccelerouter 8 }

------------------------------------------------------------------------
nbsArSecFlowTable	OBJECT-TYPE
		SYNTAX  SEQUENCE OF NbsArSecFlowEntry
		ACCESS  not-accessible
		STATUS  mandatory
		DESCRIPTION
			"."
		::= { nbsArSecFlow 1 }

nbsArSecFlowEntry  OBJECT-TYPE
		SYNTAX  NbsArSecFlowEntry
		ACCESS  not-accessible
		STATUS  mandatory
		DESCRIPTION
				"."
		INDEX { nbsArSecFlowIndex }
		::= { nbsArSecFlowTable 1 }

NbsArSecFlowEntry ::= SEQUENCE {
		nbsArSecFlowIndex			INTEGER(0..2147483647),
		nbsArSecFlowValid			INTEGER,
		nbsArSecFlowState			INTEGER,
		nbsArSecFlowLastUsedTimestamp		INTEGER(0..2147483647),
		nbsArSecFlowServTypes			INTEGER,
		nbsArSecFlowServId		        INTEGER,
		nbsArFlowID				OCTET STRING,

		nbsArFlowQoSSpec 			OCTET STRING,

		nbsArSecFlowNumOfServices		INTEGER(0..2147483647),
		nbsArSecFlowDriverData			OCTET STRING,
		nbsArSecFlowActions			OCTET STRING,
		nbsArSecFlowCounters		OCTET STRING,
		nbsArSecFlowAdminStatus			INTEGER
		}


nbsArSecFlowIndex	OBJECT-TYPE				
		SYNTAX INTEGER(0..2147483647)
		ACCESS read-write
		STATUS mandatory
		DESCRIPTION
			"."
		::= { nbsArSecFlowEntry 1 }

nbsArSecFlowValid	OBJECT-TYPE
		SYNTAX INTEGER
		ACCESS read-write
		STATUS mandatory
		DESCRIPTION
			"."
		::= { nbsArSecFlowEntry 2 }

nbsArSecFlowState	OBJECT-TYPE
		SYNTAX INTEGER
		ACCESS read-write
		STATUS mandatory
		DESCRIPTION
			"."
		::= { nbsArSecFlowEntry 3 }

nbsArSecFlowLastUsedTimestamp	OBJECT-TYPE
		SYNTAX INTEGER(0..2147483647)
		ACCESS read-write
		STATUS mandatory
		DESCRIPTION
			"."
		::= { nbsArSecFlowEntry 4 }

nbsArSecFlowServTypes	OBJECT-TYPE
		SYNTAX INTEGER
		ACCESS read-write
		STATUS mandatory
		DESCRIPTION
			"."
		::= { nbsArSecFlowEntry 5 }

nbsArSecFlowServId	OBJECT-TYPE
		SYNTAX INTEGER
		ACCESS read-write
		STATUS mandatory
		DESCRIPTION
			"."
		::= { nbsArSecFlowEntry 6 }
        
nbsArFlowID	OBJECT-TYPE
		SYNTAX OCTET STRING	 
		ACCESS read-write
		STATUS mandatory
		DESCRIPTION
			"."
		::= { nbsArSecFlowEntry 7 }


nbsArFlowQoSSpec  OBJECT-TYPE
		SYNTAX OCTET STRING
		ACCESS read-write
		STATUS mandatory
		DESCRIPTION
			"Type of quality of service supplied."
		::= { nbsArSecFlowEntry 8 }

nbsArSecFlowNumOfServices OBJECT-TYPE
		SYNTAX INTEGER(0..2147483647)
		ACCESS read-write
		STATUS mandatory
		DESCRIPTION
			"The number of service specs defined."
		::= { nbsArSecFlowEntry 9 }

nbsArSecFlowDriverData	OBJECT-TYPE
		SYNTAX OCTET STRING
		ACCESS read-write
		STATUS mandatory
		DESCRIPTION
			"."
		::= { nbsArSecFlowEntry 10 }

nbsArSecFlowActions	OBJECT-TYPE
		SYNTAX OCTET STRING
		ACCESS read-write
		STATUS mandatory
		DESCRIPTION
			"."
		::= { nbsArSecFlowEntry 11 }

nbsArSecFlowCounters	OBJECT-TYPE
		SYNTAX OCTET STRING
		ACCESS read-write
		STATUS mandatory
		DESCRIPTION
			"."
		::= { nbsArSecFlowEntry 12 }

nbsArSecFlowAdminStatus  OBJECT-TYPE
		SYNTAX INTEGER {
			none   (1),	
			add    (2),
			delete (3),
			modify (4),
			activate (5),
			deactivate (6)
		}
		ACCESS read-write
		STATUS mandatory
		DESCRIPTION
			"What action to perform."
		::= { nbsArSecFlowEntry 13 }

------------------------------------------------------------------------------------------
nbsArFlowServiceSpecTable	OBJECT-TYPE
		SYNTAX SEQUENCE OF NbsArFlowServiceSpecEntry
		ACCESS  not-accessible
		STATUS  mandatory
		DESCRIPTION
			"Specific service data entries attached to each flow entry."
		::= { nbsArSecFlow 2 }

nbsArFlowServiceSpecEntry OBJECT-TYPE
		SYNTAX  NbsArFlowServiceSpecEntry 
		ACCESS  not-accessible
		STATUS  mandatory
		DESCRIPTION
				"."
		INDEX { nbsArFlowServiceFlowIndex, nbsArFlowServiceSpecsServiceId }
		::= { nbsArFlowServiceSpecTable 1 }


NbsArFlowServiceSpecEntry ::= SEQUENCE {
		nbsArFlowServiceFlowIndex		INTEGER,
		nbsArFlowServiceSpecsServiceId		INTEGER,
		nbsArFlowServiceSpecsServiceType	INTEGER,
		nbsArFlowServiceSpecsServiceFlowIndex	INTEGER,
		nbsArFlowServiceSpecsFlowIDExtension	OCTET STRING,
		nbsArFlowServiceSpecsFlowModifier	OCTET STRING,
		nbsArFlowServiceSpecsFlowSpec		OCTET STRING,
		nbsArFlowServiceSpecsAdminStatus	INTEGER
		}

nbsArFlowServiceFlowIndex	OBJECT-TYPE
		SYNTAX INTEGER  
		ACCESS read-write
		STATUS mandatory
		DESCRIPTION
			"."
		::= { nbsArFlowServiceSpecEntry 1 }

nbsArFlowServiceSpecsServiceId	OBJECT-TYPE
		SYNTAX INTEGER  
		ACCESS read-write
		STATUS mandatory
		DESCRIPTION
			"."
		::= { nbsArFlowServiceSpecEntry 2 }

nbsArFlowServiceSpecsServiceType OBJECT-TYPE
		SYNTAX INTEGER
		ACCESS read-write
		STATUS mandatory
		DESCRIPTION
			"."
		::= { nbsArFlowServiceSpecEntry 3 }

nbsArFlowServiceSpecsServiceFlowIndex	OBJECT-TYPE
		SYNTAX INTEGER  
		ACCESS read-write
		STATUS mandatory
		DESCRIPTION
			"A reference to the service's table (installed by the service)."
		::= { nbsArFlowServiceSpecEntry 4 }

nbsArFlowServiceSpecsFlowIDExtension	OBJECT-TYPE
		SYNTAX OCTET STRING
		ACCESS read-write
		STATUS mandatory
		DESCRIPTION
			"."
		::= { nbsArFlowServiceSpecEntry 5 }

nbsArFlowServiceSpecsFlowModifier	OBJECT-TYPE
		SYNTAX OCTET STRING
		ACCESS read-write
		STATUS mandatory
		DESCRIPTION
			"."
		::= { nbsArFlowServiceSpecEntry 6 }

nbsArFlowServiceSpecsFlowSpec	OBJECT-TYPE
		SYNTAX OCTET STRING
		ACCESS read-write
		STATUS mandatory
		DESCRIPTION
			"."
		::= { nbsArFlowServiceSpecEntry 7 }

nbsArFlowServiceSpecsAdminStatus  OBJECT-TYPE
		SYNTAX INTEGER {
			none   (1),
			add    (2),
			delete (3),
			modify (4)		
		}
		ACCESS read-write
		STATUS mandatory
		DESCRIPTION
			"The action to perform."
		::= { nbsArFlowServiceSpecEntry 8 }

------------------------------------------------------------------------
nbsArFlowServicePortTable	OBJECT-TYPE
		SYNTAX SEQUENCE OF NbsArFlowServicePortEntry
		ACCESS  not-accessible
		STATUS  mandatory
		DESCRIPTION
			"."
		::= { nbsArSecFlow 3 }

nbsArFlowServicePortEntry	OBJECT-TYPE
		SYNTAX 	NbsArFlowServicePortEntry
		ACCESS  not-accessible
		STATUS  mandatory
		DESCRIPTION
			"."
		INDEX {	nbsArFlowServicePortNumber }	

		::= { nbsArFlowServicePortTable 1 }

NbsArFlowServicePortEntry ::= SEQUENCE {

		nbsArFlowServicePortNumber				INTEGER,
		nbsArFlowServicePortData				OCTET STRING, 
		nbsArFlowServicePortAdminStatus			INTEGER
		}

nbsArFlowServicePortNumber	OBJECT-TYPE
		SYNTAX INTEGER
		ACCESS read-write
		STATUS mandatory
		DESCRIPTION
			"The port number for which the configuration relates. "
		::= { nbsArFlowServicePortEntry 1 }

nbsArFlowServicePortData	OBJECT-TYPE
		SYNTAX OCTET STRING
		ACCESS read-write
		STATUS mandatory
		DESCRIPTION
			"The data describing port attributes. "
		::= { nbsArFlowServicePortEntry 2 }

nbsArFlowServicePortAdminStatus	OBJECT-TYPE
		SYNTAX INTEGER	{
            none (1),
			add  (2),
			delete (3),
			modify (4)		
		}
		ACCESS read-write
		STATUS mandatory
		DESCRIPTION
			"Port configuration status."
		::= { nbsArFlowServicePortEntry 3 }


------------------------------------------------------------------------

nbsArSecFlowFwdStatus	OBJECT-TYPE
		SYNTAX OCTET STRING
		ACCESS read-write
		STATUS mandatory
		DESCRIPTION
			"."
		::= { nbsArSecFlow 4 }

------------------------------------------------------------------------
        
END

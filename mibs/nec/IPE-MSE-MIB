--
-- ASN.1 MIB Definitions
-- Output Date: Tue Jul 12 15:00:46 2016
--

IPE-MSE-MIB DEFINITIONS ::= BEGIN

-----------------------------------------------
-- IMPORTS Definitions
-----------------------------------------------

    IMPORTS
        InterfaceIndex
            FROM IF-MIB
        enterprises, Integer32, IpAddress, NOTIFICATION-TYPE, OBJECT-TYPE,
        Opaque
            FROM SNMPv2-SMI
        TEXTUAL-CONVENTION
            FROM SNMPv2-TC;

-----------------------------------------------
-- Textual Convention Definitions
-----------------------------------------------

    IpeEnableDisableValue ::= TEXTUAL-CONVENTION
        STATUS       current
        DESCRIPTION  ""
        SYNTAX       INTEGER { invalid(0), disabled(1), enabled(2) }

    SeverityValue ::= TEXTUAL-CONVENTION
        STATUS       current
        DESCRIPTION  "Severity (CCITT Rec. X.733)"
        SYNTAX       INTEGER {
                         cleared(1),
                         indetermine(2),
                         critical(3),
                         major(4),
                         minor(5),
                         warning(6)
                     }

-----------------------------------------------
-- Begin User MIB Object Definitions
-----------------------------------------------

    nec OBJECT IDENTIFIER
        ::= { enterprises 119 }

    nec-mib OBJECT IDENTIFIER
        ::= { nec 2 }

    necProductDepend OBJECT IDENTIFIER
        ::= { nec-mib 3 }

    radioEquipment OBJECT IDENTIFIER
        ::= { necProductDepend 69 }

    pasoNeoIpe-common OBJECT IDENTIFIER
        ::= { radioEquipment 501 }

-----------------------------------------------
-- IPE COMMON Group Definitions
-----------------------------------------------

    alarmStatusGroup OBJECT IDENTIFIER
        ::= { pasoNeoIpe-common 3 }

    provisioningGroup OBJECT IDENTIFIER
        ::= { pasoNeoIpe-common 5 }

-----------------------------------------------
-- alarmStatusGroup Definitions
-----------------------------------------------

    asMseGroup OBJECT IDENTIFIER
        ::= { alarmStatusGroup 40 }

    asMseCardTable OBJECT-TYPE
        SYNTAX       SEQUENCE OF AsMseCardEntry
        MAX-ACCESS   not-accessible
        STATUS       current
        DESCRIPTION  "This table represents the alarm status for mse card."
        ::= { asMseGroup 1 }

    asMseCardEntry OBJECT-TYPE
        SYNTAX       AsMseCardEntry
        MAX-ACCESS   not-accessible
        STATUS       current
        DESCRIPTION  ""
        INDEX        { asMseCardIndex }
        ::= { asMseCardTable 1 }

    AsMseCardEntry ::= SEQUENCE {
        asMseCardIndex         Integer32,
        asMseCardNEAddress     IpAddress,
        asMseCardModuleFail    SeverityValue,
        asMseCardComFailAlarm  SeverityValue,
        asMseCardUnequipped    SeverityValue,
        asMseCardTypeMismatch  SeverityValue,
        asMseCardBusErrorTx    SeverityValue,
        asMseCardBusErrorRx    SeverityValue,
        asMseCardClkFail       SeverityValue
    }

    asMseCardIndex OBJECT-TYPE
        SYNTAX       Integer32
        MAX-ACCESS   not-accessible
        STATUS       current
        DESCRIPTION  "Index of this table."
        ::= { asMseCardEntry 1 }

    asMseCardNEAddress OBJECT-TYPE
        SYNTAX       IpAddress
        MAX-ACCESS   not-accessible
        STATUS       current
        DESCRIPTION  "reserved."
        ::= { asMseCardEntry 2 }

    asMseCardModuleFail OBJECT-TYPE
        SYNTAX       SeverityValue
        MAX-ACCESS   read-only
        STATUS       current
        DESCRIPTION  "MSE Module Alarm"
        ::= { asMseCardEntry 3 }

    asMseCardComFailAlarm OBJECT-TYPE
        SYNTAX       SeverityValue
        MAX-ACCESS   read-only
        STATUS       current
        DESCRIPTION  "MSE Communication FAIL Alarm."
        ::= { asMseCardEntry 4 }

    asMseCardUnequipped OBJECT-TYPE
        SYNTAX       SeverityValue
        MAX-ACCESS   read-only
        STATUS       current
        DESCRIPTION  
            "MSE Unequipped Alarm. The alarm shows status that the
            provisioned card is not installed."
        ::= { asMseCardEntry 5 }

    asMseCardTypeMismatch OBJECT-TYPE
        SYNTAX       SeverityValue
        MAX-ACCESS   read-only
        STATUS       current
        DESCRIPTION  
            "MSE Type Mismatch Alarm. The alarm shows status that the card
            which is different from provisioned is installed."
        ::= { asMseCardEntry 6 }

    asMseCardBusErrorTx OBJECT-TYPE
        SYNTAX       SeverityValue
        MAX-ACCESS   read-only
        STATUS       current
        DESCRIPTION  "MSE Tx Bus Error Alarm."
        ::= { asMseCardEntry 7 }

    asMseCardBusErrorRx OBJECT-TYPE
        SYNTAX       SeverityValue
        MAX-ACCESS   read-only
        STATUS       current
        DESCRIPTION  "MSE Rx Bus Error Alarm"
        ::= { asMseCardEntry 8 }

    asMseCardClkFail OBJECT-TYPE
        SYNTAX       SeverityValue
        MAX-ACCESS   read-only
        STATUS       obsolete
        DESCRIPTION  "obsoleted"
        ::= { asMseCardEntry 9 }

    asMseLineTable OBJECT-TYPE
        SYNTAX       SEQUENCE OF AsMseLineEntry
        MAX-ACCESS   not-accessible
        STATUS       current
        DESCRIPTION  "MSE E1 Channel Alarm Status table."
        ::= { asMseGroup 2 }

    asMseLineEntry OBJECT-TYPE
        SYNTAX       AsMseLineEntry
        MAX-ACCESS   not-accessible
        STATUS       current
        DESCRIPTION  ""
        INDEX        { asMseLineIfIndex }
        ::= { asMseLineTable 1 }

    AsMseLineEntry ::= SEQUENCE {
        asMseLineIfIndex            InterfaceIndex,
        asMseLineNEAddress          IpAddress,
        asMseLineBfrUnderrun        SeverityValue,
        asMseLineAdaptiveClkStatus  INTEGER
    }

    asMseLineIfIndex OBJECT-TYPE
        SYNTAX       InterfaceIndex
        MAX-ACCESS   not-accessible
        STATUS       current
        DESCRIPTION  "Index of this table."
        ::= { asMseLineEntry 1 }

    asMseLineNEAddress OBJECT-TYPE
        SYNTAX       IpAddress
        MAX-ACCESS   not-accessible
        STATUS       current
        DESCRIPTION  "reserved."
        ::= { asMseLineEntry 2 }

    asMseLineBfrUnderrun OBJECT-TYPE
        SYNTAX       SeverityValue
        MAX-ACCESS   read-only
        STATUS       current
        DESCRIPTION  "MSE E1 Channel TDM Buffer Underrun Alarm."
        ::= { asMseLineEntry 5 }

    asMseLineAdaptiveClkStatus OBJECT-TYPE
        SYNTAX       INTEGER {
                         invalid(0),
                         holdover(1),
                         acquiring(2),
                         acquired(3)
                     }
        MAX-ACCESS   read-only
        STATUS       current
        DESCRIPTION  "MSE E1 Channel Adaptive Clock Status."
        ::= { asMseLineEntry 6 }

-----------------------------------------------
-- provisioningGroup Definitions
-----------------------------------------------

    provMseGroup OBJECT IDENTIFIER
        ::= { provisioningGroup 40 }

    provMseLineModeTable OBJECT-TYPE
        SYNTAX       SEQUENCE OF ProvMseLineModeEntry
        MAX-ACCESS   not-accessible
        STATUS       current
        DESCRIPTION  ""
        ::= { provMseGroup 1 }

    provMseLineModeEntry OBJECT-TYPE
        SYNTAX       ProvMseLineModeEntry
        MAX-ACCESS   not-accessible
        STATUS       current
        DESCRIPTION  ""
        INDEX        { provMseLineModeIfIndex }
        ::= { provMseLineModeTable 1 }

    ProvMseLineModeEntry ::= SEQUENCE {
        provMseLineModeIfIndex    InterfaceIndex,
        provMseLineModeNEAddress  IpAddress,
        provMseLineModeType       INTEGER
    }

    provMseLineModeIfIndex OBJECT-TYPE
        SYNTAX       InterfaceIndex
        MAX-ACCESS   not-accessible
        STATUS       current
        DESCRIPTION  "Index of this table."
        ::= { provMseLineModeEntry 1 }

    provMseLineModeNEAddress OBJECT-TYPE
        SYNTAX       IpAddress
        MAX-ACCESS   not-accessible
        STATUS       current
        DESCRIPTION  "reserved."
        ::= { provMseLineModeEntry 2 }

    provMseLineModeType OBJECT-TYPE
        SYNTAX       INTEGER { invalid(0), none(1), satop(2) }
        MAX-ACCESS   read-write
        STATUS       current
        DESCRIPTION  "Configure MSE E1 channel PWE mode."
        DEFVAL       { none }
        ::= { provMseLineModeEntry 3 }

    provMseClockModeTable OBJECT-TYPE
        SYNTAX       SEQUENCE OF ProvMseClockModeEntry
        MAX-ACCESS   not-accessible
        STATUS       current
        DESCRIPTION  "MSE E1 channel Clock Mode Table."
        ::= { provMseGroup 2 }

    provMseClockModeEntry OBJECT-TYPE
        SYNTAX       ProvMseClockModeEntry
        MAX-ACCESS   not-accessible
        STATUS       current
        DESCRIPTION  ""
        INDEX        { provMseClockModeIfIndex }
        ::= { provMseClockModeTable 1 }

    ProvMseClockModeEntry ::= SEQUENCE {
        provMseClockModeIfIndex    InterfaceIndex,
        provMseClockModeNEAddress  IpAddress,
        provMseClockModeType       INTEGER,
        provMseClockACRLineSelect  Integer32
    }

    provMseClockModeIfIndex OBJECT-TYPE
        SYNTAX       InterfaceIndex
        MAX-ACCESS   not-accessible
        STATUS       current
        DESCRIPTION  "Index of this table."
        ::= { provMseClockModeEntry 1 }

    provMseClockModeNEAddress OBJECT-TYPE
        SYNTAX       IpAddress
        MAX-ACCESS   not-accessible
        STATUS       current
        DESCRIPTION  "reserved."
        ::= { provMseClockModeEntry 2 }

    provMseClockModeType OBJECT-TYPE
        SYNTAX       INTEGER {
                         invalid(0),
                         syncToSystem(1),
                         syncToPw(2),
                         syncToLine(3)
                     }
        MAX-ACCESS   read-write
        STATUS       current
        DESCRIPTION  
            "Configure MSE E1 channel clock mode. When 'syncToSystem' is
            configured, the line clock is synchronized to NE Clock. When
            'syncToLine' is configured, the line clock is synchronized to
            each E1 channel. When 'syncToPw' is configured, the line clock is
            synchronized to Adaptive Clock which is extracted from PWE
            packet. And if the line is referenced from other line (configured
            by 'provMseClockACRLineSelect'), the system rejects the request
            to change the 'provMseClockModeType' to the other mode."
        DEFVAL       { syncToPw }
        ::= { provMseClockModeEntry 3 }

    provMseClockACRLineSelect OBJECT-TYPE
        SYNTAX       Integer32 (1..16)
        MAX-ACCESS   read-write
        STATUS       current
        DESCRIPTION  "Assign Channel"
        ::= { provMseClockModeEntry 4 }

    provMseClockModeExtTable OBJECT-TYPE
        SYNTAX       SEQUENCE OF ProvMseClockModeExtEntry
        MAX-ACCESS   not-accessible
        STATUS       current
        DESCRIPTION  ""
        ::= { provMseGroup 3 }

    provMseClockModeExtEntry OBJECT-TYPE
        SYNTAX       ProvMseClockModeExtEntry
        MAX-ACCESS   not-accessible
        STATUS       current
        DESCRIPTION  ""
        INDEX        { provMseClockModeExtIfIndex }
        ::= { provMseClockModeExtTable 1 }

    ProvMseClockModeExtEntry ::= SEQUENCE {
        provMseClockModeExtIfIndex    InterfaceIndex,
        provMseClockModeExtNEAddress  IpAddress,
        provMseClockModeReply2Master  IpeEnableDisableValue,
        provMseClockSupplyMode        IpeEnableDisableValue
    }

    provMseClockModeExtIfIndex OBJECT-TYPE
        SYNTAX       InterfaceIndex
        MAX-ACCESS   not-accessible
        STATUS       current
        DESCRIPTION  "Index of this table."
        ::= { provMseClockModeExtEntry 1 }

    provMseClockModeExtNEAddress OBJECT-TYPE
        SYNTAX       IpAddress
        MAX-ACCESS   not-accessible
        STATUS       current
        DESCRIPTION  "reserved."
        ::= { provMseClockModeExtEntry 2 }

    provMseClockModeReply2Master OBJECT-TYPE
        SYNTAX       IpeEnableDisableValue
        MAX-ACCESS   read-write
        STATUS       current
        DESCRIPTION  "Output PW Packet to Master"
        DEFVAL       { enabled }
        ::= { provMseClockModeExtEntry 3 }

    provMseClockSupplyMode OBJECT-TYPE
        SYNTAX       IpeEnableDisableValue
        MAX-ACCESS   read-write
        STATUS       current
        DESCRIPTION  "Clock Supply Mode"
        DEFVAL       { disabled }
        ::= { provMseClockModeExtEntry 4 }

    provMseClockSelectTable OBJECT-TYPE
        SYNTAX       SEQUENCE OF ProvMseClockSelectEntry
        MAX-ACCESS   not-accessible
        STATUS       current
        DESCRIPTION  "MSE Clock Select Setting Table."
        ::= { provMseGroup 4 }

    provMseClockSelectEntry OBJECT-TYPE
        SYNTAX       ProvMseClockSelectEntry
        MAX-ACCESS   not-accessible
        STATUS       current
        DESCRIPTION  ""
        INDEX        { provMseClockSelectCardId }
        ::= { provMseClockSelectTable 1 }

    ProvMseClockSelectEntry ::= SEQUENCE {
        provMseClockSelectCardId     Integer32,
        provMseClockSelectNEAddress  IpAddress,
        provMseClockSelectLineNum    Integer32
    }

    provMseClockSelectCardId OBJECT-TYPE
        SYNTAX       Integer32
        MAX-ACCESS   not-accessible
        STATUS       current
        DESCRIPTION  "Index of this table."
        ::= { provMseClockSelectEntry 1 }

    provMseClockSelectNEAddress OBJECT-TYPE
        SYNTAX       IpAddress
        MAX-ACCESS   not-accessible
        STATUS       current
        DESCRIPTION  "reserved."
        ::= { provMseClockSelectEntry 2 }

    provMseClockSelectLineNum OBJECT-TYPE
        SYNTAX       Integer32 (1..16)
        MAX-ACCESS   read-write
        STATUS       current
        DESCRIPTION  "MSE E1 Clock Port"
        DEFVAL       { 1 }
        ::= { provMseClockSelectEntry 3 }

-----------------------------------------------
-- End User MIB Object Definitions
-----------------------------------------------

END

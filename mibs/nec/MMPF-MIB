-- ************************************************************************************************
-- FileName    :mmpfPMib.my
-- Description :MultiMedia Platform private MIB(D4000 流用,改造 MIB定義ファイル)
-- Revision History     :
--   Ver.     mark   date      
--   01.24    @024   01/16/2002
-- ************************************************************************************************

--   NECSW-MIB DEFINITIONS ::= BEGIN
MMPF-MIB DEFINITIONS ::= BEGIN


   IMPORTS
      mgmt, NetworkAddress, IpAddress, Counter, Gauge, TimeTicks
      FROM RFC1155-SMI
		Integer32, Gauge32 FROM SNMPv2-SMI
		TimeStamp, PhysAddress FROM SNMPv2-TC

      OBJECT-TYPE
      FROM RFC-1212

--      DisplayString
--      FROM RFC1155-SMI

-- @008 add from
      TruthValue
      FROM RFC1253-MIB
-- @008 add end

      TRAP-TYPE
      FROM RFC-1215;

   RowStatus   ::= INTEGER { active(1), notInService(2), notReady(3),
                       createAndGo(4), createAndWait(5), destroy(6) }

   NetPrefix ::= OCTET STRING (SIZE (13))

   DisplayString ::= OCTET STRING

   BridgeId ::= OCTET STRING (SIZE (8)) 

   Timeout ::= INTEGER -- a STP timer in units of 1/100 seconds

   DateAndTime ::= OCTET STRING (SIZE (7 | 8 | 11)) 
-- in OpenView  above must be comment 98/12/15 YI @002
   -- Added SIZE(7) for SanFran
-- The following definition was gotten from rfc1514
   --        A date-time specification for the local time of day.
   --        This data type is intended to provide a consistent
   --        method of reporting date information.
   --
   --            field  octets  contents                  range
   --            _____  ______  ________                  _____
   --              1      1-2   year                      0..65536
   --                           (in network byte order)
   --              2       3    month                     1..12
   --              3       4    day                       1..31
   --              4       5    hour                      0..23
   --              5       6    minutes                   0..59
   --              6       7    seconds                   0..60
   --                           (use 60 for leap-second)
   --              7       8    deci-seconds              0..9
   --              8       9    direction from UTC        "+" / "-"
   --                           (in ascii notation)
   --              9      10    hours from UTC            0..11
   --             10      11    minutes from UTC          0..59
   --
   --            Note that if only local time is known, then
   --            timezone information (fields 8-10) is not present.

-- The following definition was cadged from the Bridge MIB
      MacAddress ::= OCTET STRING (SIZE (6))
                                                -- a 6 octet address
                                                -- in the
                                                -- "canonical"
                                                -- order
      -- defined by IEEE 802.1a, i.e., as if it were transmitted
      -- least significant bit first, even though 802.5 (in
      -- contrast to other n802.x protocols) requires MAC
      -- addresses to be transmitted most significant bit first.
      --
      -- 16-bit addresses, if needed, are represented by setting
      -- their upper 4 octets to all 0's, i.e., AAFF would be
      -- represented as 00000000AAFF.

-- The following definition is privately defined for Sanfran Private MIB


--   nec               OBJECT IDENTIFIER ::= { enterprises 119}

--   necProduct        OBJECT IDENTIFIER ::= { nec 1 }
--   nec-mib           OBJECT IDENTIFIER ::= { nec 2 }
--   necExperimental   OBJECT IDENTIFIER ::= { nec 3 }

--   datax             OBJECT IDENTIFIER ::= { necProduct 3 }
--   ether-sw          OBJECT IDENTIFIER ::= { datax 10 }
--   sf                OBJECT IDENTIFIER ::= { ether-sw 3 }

--   necCommon         OBJECT IDENTIFIER ::= { nec-mib 1 }
--   necFunction       OBJECT IDENTIFIER ::= { nec-mib 2 }
--   necProductDepend  OBJECT IDENTIFIER ::= { nec-mib 3 }

--   datax-mib         OBJECT IDENTIFIER ::= { necProductDepend 3 }
--   ether-sw-mib      OBJECT IDENTIFIER ::= { datax-mib 10 }
--   sf-mib            OBJECT IDENTIFIER ::= { ether-sw-mib 3 }




  org         OBJECT IDENTIFIER     ::= { iso 3 }
  dod         OBJECT IDENTIFIER     ::= { org 6 }
  internet    OBJECT IDENTIFIER     ::= { dod 1 }
  private     OBJECT IDENTIFIER     ::= { internet 4 }
  enterprises OBJECT IDENTIFIER     ::= { private 1 }
  nec               OBJECT IDENTIFIER ::= { enterprises 119}


-- 98/12/15 YI mmpf => mmpf-mib CHG start @002
-- sysObjectID 
   necProduct        OBJECT IDENTIFIER ::= { nec 1 }
   datax             OBJECT IDENTIFIER ::= { necProduct 3 }
   mmpf              OBJECT IDENTIFIER ::= { datax 13 }
   mmn9110           OBJECT IDENTIFIER ::= { mmpf 1 }
   mmn9120           OBJECT IDENTIFIER ::= { mmpf 2 }
-- [sysObjectID]  MM-Node9110/MM-Node9120
--  mmn9110           OBJECT IDENTIFIER ::= { nec necProduct(1) datax(3) mmpf(13) mmn9110(1) }
--  mmn9120           OBJECT IDENTIFIER ::= { nec necProduct(1) datax(3) mmpf(13) mmn9110(2) }

-- @016 add from
-- for IX5005
   ix5005            OBJECT IDENTIFIER ::= { mmpf 3 }
-- @016 add end

-- @023 add from
-- for IX5003
   ix5003            OBJECT IDENTIFIER ::= { mmpf 4 }
-- @023 add end


   nec-mib           OBJECT IDENTIFIER ::= { nec 2 }
   necProductDepend  OBJECT IDENTIFIER ::= { nec-mib 3 }
   datax-mib         OBJECT IDENTIFIER ::= { necProductDepend 3 }
   mmpf-mib          OBJECT IDENTIFIER ::= { datax-mib 13 }


-- D4000 流用,改造 MIB定義

   mpSystem                 OBJECT IDENTIFIER ::= { mmpf-mib 1 }
   mpIfCard                 OBJECT IDENTIFIER ::= { mmpf-mib 2 }
   mpEtherPort              OBJECT IDENTIFIER ::= { mmpf-mib 3 }
   mpVlan                   OBJECT IDENTIFIER ::= { mmpf-mib 4 }
   mpBridge                 OBJECT IDENTIFIER ::= { mmpf-mib 5 }
   mpDbAccess               OBJECT IDENTIFIER ::= { mmpf-mib 6 }
   mpEventLog               OBJECT IDENTIFIER ::= { mmpf-mib 7 }
   mpUiSession              OBJECT IDENTIFIER ::= { mmpf-mib 8 }
   mpFtp                    OBJECT IDENTIFIER ::= { mmpf-mib 9 }
   mpDhcp                   OBJECT IDENTIFIER ::= { mmpf-mib 10 }
   mpIp                     OBJECT IDENTIFIER ::= { mmpf-mib 11 }
   mpRip                    OBJECT IDENTIFIER ::= { mmpf-mib 12 }
   mpSnmp                   OBJECT IDENTIFIER ::= { mmpf-mib 13 }
   mpStats                  OBJECT IDENTIFIER ::= { mmpf-mib 14 }
   mpCli                    OBJECT IDENTIFIER ::= { mmpf-mib 15 } 
   mpAtm                    OBJECT IDENTIFIER ::= { mmpf-mib 16 }
   mpLis                    OBJECT IDENTIFIER ::= { mmpf-mib 17 }
   mpDns                    OBJECT IDENTIFIER ::= { mmpf-mib 18 }
   mpLec                    OBJECT IDENTIFIER ::= { mmpf-mib 19 }
   mpMpc                    OBJECT IDENTIFIER ::= { mmpf-mib 20 }
   mpStp                    OBJECT IDENTIFIER ::= { mmpf-mib 21 }
   mpLlc                    OBJECT IDENTIFIER ::= { mmpf-mib 22 }

-- @008 add from
-- 91XX ステップ3.0 MIB定義
   mpOspf                   OBJECT IDENTIFIER ::= { mmpf-mib 23 }

-- @008 add end
-- 91XX ステップ1.0 MIB定義

   mpObsCtl                 OBJECT IDENTIFIER ::= { mmpf-mib 101 }
   mpCardInfo               OBJECT IDENTIFIER ::= { mmpf-mib 102 }
   mpInterface              OBJECT IDENTIFIER ::= { mmpf-mib 103 }

-- 91XX ステップ2.0 MIB定義

   mpPvoice                 OBJECT IDENTIFIER ::= { mmpf-mib 104 }

-- @008 add from
-- 91XX ステップ3.0 MIB定義

   mpAtmCallCtl             OBJECT IDENTIFIER ::= { mmpf-mib 110 }
   mpCes                    OBJECT IDENTIFIER ::= { mmpf-mib 111 }
   mpIpsw                   OBJECT IDENTIFIER ::= { mmpf-mib 112 }
   mpInsCtl                 OBJECT IDENTIFIER ::= { mmpf-mib 113 }
   mpFfr                    OBJECT IDENTIFIER ::= { mmpf-mib 114 }
   mpIpswAtm                OBJECT IDENTIFIER ::= { mmpf-mib 115 }
-- @008 add to
-- @017 add from
   mpPpp                    OBJECT IDENTIFIER ::= { mmpf-mib 120 }
   mpPos                    OBJECT IDENTIFIER ::= { mmpf-mib 121 }
   mpFrpp                   OBJECT IDENTIFIER ::= { mmpf-mib 123 }
   mpMpls                   OBJECT IDENTIFIER ::= { mmpf-mib 124 }
   mpMcc                    OBJECT IDENTIFIER ::= { mmpf-mib 125 }
-- @017 add to
-- @019 add from
   mpDetour                 OBJECT IDENTIFIER ::= { mmpf-mib 130 }
-- @019 add to
-- @022 add from
   mpIpv6                   OBJECT IDENTIFIER ::= { mmpf-mib 131 }
-- @022 add to
-- @024 add from
   mpNetwatch               OBJECT IDENTIFIER ::= { mmpf-mib 132 }
   mpNetping                OBJECT IDENTIFIER ::= { mmpf-mib 133 }
-- @024 add to
-- 98/12/15 YI mmpf => mmpf-mib CHG end


--  ***************************************************************************
--  the MM_Node9110/9120 System Group
--  11/30/1998 all overwrite @001
--  12/21/1998 @002
--  ***************************************************************************

   --  Implementation of this group is mandatory for all the EtherStar 
   --  systems.  

       
       mpSysSoftwareVersion OBJECT-TYPE
               SYNTAX  DisplayString (SIZE (0..255))
               ACCESS  read-only
               STATUS  mandatory
               DESCRIPTION "Indicates the software version number of 
                            this equipment"
               ::= { mpSystem 1 }
   
       mpSysTime OBJECT-TYPE
               SYNTAX  DateAndTime
               ACCESS  read-write
               STATUS  mandatory
               DESCRIPTION "It is used to set the date and time to the 
                           realtime clock of this equipment"
               ::= { mpSystem 2 }
 
       mpSysFanTable OBJECT-TYPE
               SYNTAX   SEQUENCE OF MpSysFanEntry
               ACCESS   not-accessible
               STATUS   mandatory
               DESCRIPTION "Indicates the table of the FAN information 
                            of this equipment."
               ::= { mpSystem 3 }

       mpSysFanEntry OBJECT-TYPE
               SYNTAX   MpSysFanEntry
               ACCESS   not-accessible
               STATUS   mandatory
               DESCRIPTION "Indicates the entry of the FAN information 
                            of this equipment."
               INDEX { mpSysFanIndex }
               ::= { mpSysFanTable 1 }

       MpSysFanEntry ::=
               SEQUENCE {
                        mpSysFanIndex 
                            INTEGER,
                        mpSysFanType
                            DisplayString,
                        mpSysFanStatus
                            INTEGER
                        }        

       mpSysFanIndex OBJECT-TYPE
               SYNTAX  INTEGER(1..10)
               ACCESS  read-only
               STATUS  mandatory
               DESCRIPTION "Indicates the index value to identify the 
                            FAN in the equipment uniquely.
                            If machine is 9110, the range is '1' to '6'.
                            If machine is 9120, the range is '1' to '10'."
               ::= { mpSysFanEntry 1 }

       mpSysFanType OBJECT-TYPE
               SYNTAX  DisplayString (SIZE (0..255))
               ACCESS  read-only
               STATUS  mandatory
               DESCRIPTION "Indicates the character string which
                            describes the FAN type."
               ::= { mpSysFanEntry 2 }

       mpSysFanStatus OBJECT-TYPE
               SYNTAX  INTEGER {
                               normal(1),
                               abnormal(2)
                               }
               ACCESS  read-only
               STATUS  mandatory
               DESCRIPTION "Indicates the status of the FAN operation. 
                            If it is set to '1', the FAN operation is 
                            normal. If it is set to '2', the FAN 
                            operation is abnormal."
               ::= { mpSysFanEntry 3 }

       mpSysVoltageTable OBJECT-TYPE
               SYNTAX   SEQUENCE OF MpSysVoltageEntry
               ACCESS   not-accessible
               STATUS   mandatory
               DESCRIPTION "Indicates the information of the voltages of the 
                           equipment."
               ::= { mpSystem 4 }

       mpSysVoltageEntry OBJECT-TYPE
               SYNTAX   MpSysVoltageEntry
               ACCESS   not-accessible
               STATUS   mandatory
               DESCRIPTION "Indicates the entry of the information of the 
                           voltages of the equipment."
               INDEX { mpSysVoltagePackageIndex,
                       mpSysVoltageIndex }
               ::= { mpSysVoltageTable 1 }

       MpSysVoltageEntry ::=
               SEQUENCE {
                        mpSysVoltagePackageIndex
                            INTEGER,
                        mpSysVoltageIndex 
                            INTEGER, 
                        mpSysVoltageType
                            DisplayString,
                        mpSysVoltageReading 
                            INTEGER,
                        mpSysVoltageStatus 
                            INTEGER
                        }

       mpSysVoltagePackageIndex OBJECT-TYPE
               SYNTAX  INTEGER {
                               com0(1),  -- chg to small case 12/21/98 YH
                               com1(2)
                               }
               ACCESS  read-only
               STATUS  mandatory
               DESCRIPTION "Indicates the Index value to identify the COM
                           Package in the equipment uniquely."
               ::= { mpSysVoltageEntry 1 }

       mpSysVoltageIndex OBJECT-TYPE
               SYNTAX  INTEGER {
                               volt3point3a(1),  -- chg 1st char to no-figure 12/21/98 YH
                               volt3point3b(2),
                               volt50v(3),
                               volt3point3c(4),  -- @021 add 
                               volt2point5(5),   -- @021 add 
                               volt3point3d(6)   -- @021 add 
                               }
               ACCESS  read-only
               STATUS  mandatory
               DESCRIPTION "Indicates the index value to identify uniquely the 
                           voltage provided by the power unit of the equipment."
               ::= { mpSysVoltageEntry 2 }

       mpSysVoltageType OBJECT-TYPE
               SYNTAX  DisplayString (SIZE (0..255))
               ACCESS  read-only
               STATUS  mandatory
               DESCRIPTION "Indicates the character string which describes the
                           power unit type and com type."
               ::= { mpSysVoltageEntry 3 }

       mpSysVoltageReading OBJECT-TYPE
               SYNTAX  INTEGER         
               ACCESS  read-only
               STATUS  mandatory
               DESCRIPTION "Indicates the observed voltage, in milli-volt (mV)."
               ::= { mpSysVoltageEntry 4 }

       mpSysVoltageStatus OBJECT-TYPE
               SYNTAX  INTEGER {
                               normal(1),
                               abnormal(2)
                               }
               ACCESS  read-only
               STATUS  mandatory
               DESCRIPTION "Indicates the statsus of the voltage. If it is set 
                           to '1', the voltage is within the normal range. If 
                           it is set to '2', the voltage is in the abnormal 
                           range."
               ::= { mpSysVoltageEntry 5 }

       mpSysTempTable OBJECT-TYPE
               SYNTAX  SEQUENCE OF MpSysTempEntry
               ACCESS  not-accessible
               STATUS  mandatory
               DESCRIPTION "Indicates the table of the Temperature information
                            of this equipment."
               ::={ mpSystem 5 }

       mpSysTempEntry OBJECT-TYPE
               SYNTAX   MpSysTempEntry
               ACCESS   not-accessible
               STATUS   mandatory
               DESCRIPTION "Indicates the entry of the information of the
                           temperature of the equipment."
               INDEX { mpSysTempPackageIndex }
               ::= { mpSysTempTable 1 }

       MpSysTempEntry ::=
               SEQUENCE {
                        mpSysTempPackageIndex
                            INTEGER,
                        mpSysTempType
                            DisplayString,
                        mpSysTempStatus
                            INTEGER,
                        mpSysTempReading
                            INTEGER,
                        mpSysTempMinThresh
                            INTEGER,
                        mpSysTempMaxThresh
                            INTEGER
                        }

       mpSysTempPackageIndex OBJECT-TYPE
               SYNTAX  INTEGER {
                               com0(1),  -- chg to small case 12/21/98YH
                               com1(2)
                               }
               ACCESS  read-only
               STATUS  mandatory
               DESCRIPTION "Indicates the Index value to identify the COM
                           Package in the equipment uniquely."
               ::= { mpSysTempEntry 1 }

       mpSysTempType OBJECT-TYPE
               SYNTAX  DisplayString (SIZE (0..255))
               ACCESS  read-only
               STATUS  mandatory
               DESCRIPTION "Indicates the character string which describes the
                           com unit type."
               ::= { mpSysTempEntry 2 }

       mpSysTempStatus OBJECT-TYPE
               SYNTAX  INTEGER {
                               normal(1),
                               abnormal(2)
                               }
               ACCESS  read-only
               STATUS  mandatory
               DESCRIPTION "Indicates the status of the temperature of this
                            equipment inside. If it is set to '1', the
                            temperature is within the normal temperature
                            range.  If it is set to '2', the temperrature
                            is in the abnomal range."
               ::= { mpSysTempEntry 3 }

       mpSysTempReading OBJECT-TYPE
               SYNTAX  INTEGER
               ACCESS  read-only
               STATUS  mandatory
               DESCRIPTION "Indicates the temperature of the equipment
                            inside, in degree (Celusius)."
               ::= { mpSysTempEntry 4 }

       mpSysTempMinThresh OBJECT-TYPE
               SYNTAX  INTEGER
               ACCESS  read-only
               STATUS  mandatory
               DESCRIPTION "Indicates the temperature of the equipment
                            inside, in degree (Celusius)."
               ::= { mpSysTempEntry 5 }

       mpSysTempMaxThresh OBJECT-TYPE
               SYNTAX  INTEGER
               ACCESS  read-only
               STATUS  mandatory
               DESCRIPTION "Indicates the higher threshold of the normal
                            temparature range for the equipment, in
                            degree (Celsius)."
               ::= { mpSysTempEntry 6 }

       mpSysEqpTable OBJECT-TYPE
               SYNTAX  SEQUENCE OF MpSysEqpEntry
               ACCESS  not-accessible
               STATUS  mandatory
               DESCRIPTION "Indicates the table of the outside equipment 
                            information."
               ::= { mpSystem 6 }

       mpSysEqpEntry OBJECT-TYPE
               SYNTAX  MpSysEqpEntry
               ACCESS  not-accessible
               STATUS  mandatory
               DESCRIPTION "Indicates the entry of the outside equipment
                            information."
               INDEX { mpSysEqpIndex }
               ::= { mpSysEqpTable 1 }

       MpSysEqpEntry ::=
               SEQUENCE {
                        mpSysEqpIndex
                            INTEGER,
                        mpSysEqpType
                            DisplayString,
                        mpSysEqpStatus
                            INTEGER
                        }

       mpSysEqpIndex OBJECT-TYPE
               SYNTAX  INTEGER {
                               equipment0(1),
                               equipment1(2)
                               }
               ACCESS  read-only
               STATUS  mandatory
               DESCRIPTION "Indicates the index value to identify the
                            outside equipment uniquely."
               ::= { mpSysEqpEntry 1 }

       mpSysEqpType OBJECT-TYPE
               SYNTAX  DisplayString (SIZE (0..255))
               ACCESS  read-only
               STATUS  mandatory
               DESCRIPTION "Indicates the character string which describes the
                           external equipment type."
               ::= { mpSysEqpEntry 2 }

       mpSysEqpStatus OBJECT-TYPE
               SYNTAX  INTEGER {
                               normal(1),
                               abnormal(2)
                               }
               ACCESS  read-only
               STATUS  mandatory
               DESCRIPTION "Indicates the status of the outside equipment
                            operation. If it is set to '1', the outside
                            equipment operation is normal. If it is set to
                            '2', the outside equipment operation is abnormal."
               ::= { mpSysEqpEntry 3 }

       mpSysCpuUseTable OBJECT-TYPE
               SYNTAX  SEQUENCE OF MpSysCpuUseEntry
               ACCESS  not-accessible
               STATUS  mandatory
               DESCRIPTION "Indicates the table of the percentage of cpu using 
                            information."
               ::= { mpSystem 7 }

       mpSysCpuUseEntry OBJECT-TYPE
               SYNTAX  MpSysCpuUseEntry
               ACCESS  not-accessible
               STATUS  mandatory
               DESCRIPTION "Indicates the entry of the percentage of cpu using
                            information."
               INDEX { mpSysCpuUseIndex,
                       mpSysCpuTimeIndex }
               ::= { mpSysCpuUseTable 1 }

       MpSysCpuUseEntry ::=
               SEQUENCE {
                        mpSysCpuUseIndex
                            INTEGER,
                        mpSysCpuTimeIndex
                            INTEGER,
                        mpSysCpuUseType
                            DisplayString,
                        mpSysCpuTimeType
                            DisplayString,
                        mpSysCpuUse
                            INTEGER
                        }

       mpSysCpuUseIndex OBJECT-TYPE
               SYNTAX  INTEGER {
                               slot1(1),
                               slot2(2),
                               slot3(3),
                               slot4(4),
                               slot5(5),
                               slot6(6),
                               slot7(7),
                               slot8(8),
                               slot9(9),
                               slot10(10),
                               slot11(11),
                               slot12(12),
                               com0(91),
                               com1(93)
                               }
               ACCESS  read-only
               STATUS  mandatory
               DESCRIPTION "Indicates the index value to identify the
                            package in the equipment uniquely."
               ::= { mpSysCpuUseEntry 1 }

       mpSysCpuTimeIndex OBJECT-TYPE
               SYNTAX  INTEGER {
                               seconds5(1),
                               minute1(2),
                               minutes5(3)
                               }
               ACCESS  read-only
               STATUS  mandatory
               DESCRIPTION "Indicates the index value to identify the
                            time collecting percentage of cpu using uniquely."
               ::= { mpSysCpuUseEntry 2 }

       mpSysCpuUseType OBJECT-TYPE
               SYNTAX  DisplayString (SIZE (0..255))
               ACCESS  read-only
               STATUS  mandatory
               DESCRIPTION "Indicates the character string which describes the
                           slot type."
               ::= { mpSysCpuUseEntry 3 }

       mpSysCpuTimeType OBJECT-TYPE
               SYNTAX  DisplayString (SIZE (0..255))
               ACCESS  read-only
               STATUS  mandatory
               DESCRIPTION "Indicates the character string which describes the
                           time type of collecting percentage of cpu using."
               ::= { mpSysCpuUseEntry 4 }

       mpSysCpuUse OBJECT-TYPE
               SYNTAX  INTEGER
               ACCESS  read-only
               STATUS  mandatory
               DESCRIPTION "Indicates the percentage of cpu using."
               ::= { mpSysCpuUseEntry 5 }


--  ***************************************************************************
--  the MM_Node9110/9120 Interface Card Group
--  ***************************************************************************

   --  Implementation of this group is mandatory for all the MM_Node9110/9120 systems.  

       mpIfCardTable OBJECT-TYPE
               SYNTAX   SEQUENCE OF MpIfCardEntry
               ACCESS   not-accessible
               STATUS   mandatory
               DESCRIPTION "A table that contains information about interface 
                           card." 
               ::= { mpIfCard 1 }

       mpIfCardEntry OBJECT-TYPE
               SYNTAX   MpIfCardEntry
               ACCESS   not-accessible
               STATUS   mandatory
               DESCRIPTION "A entry Indicates that contains information about interface 
                           card."  
               INDEX { mpIfCardSlotNumber }
               ::= { mpIfCardTable 1 }

       MpIfCardEntry ::=
               SEQUENCE {
                        mpIfCardSlotNumber 
                            INTEGER,
                        mpIfCardType 
                            INTEGER,
                        mpIfCardOperSide 
                            DisplayString,
                        mpIfCardOperVersion 
                            DisplayString,
                        mpIfCardSideAVersion 
                            DisplayString,       
                        mpIfCardSideBVersion 
                            DisplayString,
                        mpIfCardBootDpVersion 
                            DisplayString
                        }

       mpIfCardSlotNumber OBJECT-TYPE
               SYNTAX  INTEGER 
               ACCESS  read-only
               STATUS  mandatory
               DESCRIPTION "Indicates slot number of the interface card."
               ::= { mpIfCardEntry 1 }

       mpIfCardType OBJECT-TYPE
               SYNTAX  INTEGER
               ACCESS  read-only
               STATUS  mandatory
               DESCRIPTION "Indicates kind of the interface card."
               ::= { mpIfCardEntry 2 }

       mpIfCardOperSide OBJECT-TYPE
               SYNTAX  DisplayString (SIZE (0..255))
               ACCESS  read-only
               STATUS  mandatory
               DESCRIPTION "Indicates the side which was used for setting up"
               ::= { mpIfCardEntry 3 }

       mpIfCardOperVersion OBJECT-TYPE
               SYNTAX  DisplayString (SIZE (0..255))
               ACCESS  read-only
               STATUS  mandatory
               DESCRIPTION "Indicates the firmware version in operation."
               ::= { mpIfCardEntry 4 }

       mpIfCardSideAVersion OBJECT-TYPE
               SYNTAX  DisplayString (SIZE (0..255))
               ACCESS  read-only
               STATUS  mandatory
               DESCRIPTION "Indicates the firmware version of side A."
               ::= { mpIfCardEntry 5 }

       mpIfCardSideBVersion OBJECT-TYPE
               SYNTAX  DisplayString (SIZE (0..255))
               ACCESS  read-only
               STATUS  mandatory
               DESCRIPTION "Indicates the firmware version of side B."
               ::= { mpIfCardEntry 6 }

       mpIfCardBootDpVersion OBJECT-TYPE
               SYNTAX  DisplayString (SIZE (0..255))
               ACCESS  read-only
               STATUS  mandatory
               DESCRIPTION "Indicates the firmware version of BOOT/DP."
               ::= { mpIfCardEntry 7 }

--  ***************************************************************************
--  the MM_Node9110/9120 Ether Port Group
--  ***************************************************************************

   --  Implementation of this group is mandatory for all the MM_Node9110/9120 systems.  

       mpEtherPortTable OBJECT-TYPE
               SYNTAX   SEQUENCE OF MpEtherPortEntry
               ACCESS   not-accessible
               STATUS   mandatory
               DESCRIPTION "Indicates the table of Ether port information."
               ::= { mpEtherPort 1 }

       mpEtherPortEntry OBJECT-TYPE
               SYNTAX   MpEtherPortEntry
               ACCESS   not-accessible
               STATUS   mandatory
               DESCRIPTION "Indicates the entry of each Ether port's 
                           information."
               INDEX { mpEtherPortIfIndex }
               ::= { mpEtherPortTable 1 }

       MpEtherPortEntry ::=
               SEQUENCE {
                        mpEtherPortIfIndex 
                            INTEGER,
                        mpEtherPortLoopBackType 
                            INTEGER,
                        mpEtherPortMode 
                            INTEGER
                        }

       mpEtherPortIfIndex OBJECT-TYPE
               SYNTAX  INTEGER      
               ACCESS  read-only
               STATUS  mandatory
               DESCRIPTION "Indicates the interface number assigned to the 
                           Ether port uniquely in the equipment. Each Ethernet 
                           port identified by this object is the same Ethernet
                           port identified by the same number of the ifIndex."
               ::= { mpEtherPortEntry 1 }

       mpEtherPortLoopBackType OBJECT-TYPE
               SYNTAX  INTEGER {    
                               none(1), 
                               internal(2) 
                               }
               ACCESS  read-write
               STATUS  mandatory
               DESCRIPTION "Indicates the type of the Loop-back test. If it is 
                           set to '2', the internal Loop-back test is executed.
                           The Loop-back test is finished when one test packet 
                           has been sent. If it is set to '1', the Loop-back 
                           testing is not being executed, which means it is in 
                           the normal mode."
               ::= { mpEtherPortEntry 2 }

       mpEtherPortMode OBJECT-TYPE
               SYNTAX  INTEGER{
                               auto(1), 
                               hdx10(2),
                               fdx10(3),
                               hdx100(4), 
                               fdx100(5),
                               hdx1000(6),    -- @013
                               fdx1000(7)     -- @013
                              }
               ACCESS  read-write
               STATUS  mandatory
               DESCRIPTION "Indicates the operation mode of the port.
                           In case of Antomatical mode, the value '1' is set.
                           In case of HDX10M, the value '2' is set.
                           In case of FDX10M, the value '3' is set.
                           In case of HDX100M, the value '4' is set.
                           In case of FDX100M, the value '5' is set.
                           In case of HDX1000M, the value '6' is set.   -- @013
                           In case of FDX1000M, the value '7' is set.   -- @013
                           The default value is '1'."
               ::= { mpEtherPortEntry 3 }

       mpEtherPortStatusTable OBJECT-TYPE
               SYNTAX   SEQUENCE OF MpEtherPortStatusEntry
               ACCESS   not-accessible
               STATUS   mandatory
               DESCRIPTION "Indicates the table of Ether port status 
                           information."
               ::= { mpEtherPort 2 }

       mpEtherPortStatusEntry OBJECT-TYPE
               SYNTAX   MpEtherPortStatusEntry
               ACCESS   not-accessible
               STATUS   mandatory
               DESCRIPTION "Indicates the entry of each Ether port's status
                           information."
               INDEX { mpEtherPortStsIfIndex }
               ::= { mpEtherPortStatusTable 1 }

       MpEtherPortStatusEntry ::=
               SEQUENCE {
                        mpEtherPortStsIfIndex 
                            INTEGER,
                        mpEtherPortStsLoopBackResult 
                            INTEGER,
                        mpEtherPortStsMode 
                            INTEGER,
                        mpEtherPortStsSpeed 
                            Gauge,
                        mpEtherPortStsFullDuplex 
                            INTEGER
                        }

       mpEtherPortStsIfIndex OBJECT-TYPE
               SYNTAX  INTEGER      
               ACCESS  read-only
               STATUS  mandatory
               DESCRIPTION "Indicates the interface number assigned to the 
                           Ether port uniquely in the equipment. Each Ethernet
                           port identified by this object is the same Ethernet
                           port identified by the same number of the ifIndex."
               ::= { mpEtherPortStatusEntry 1 }

       mpEtherPortStsLoopBackResult OBJECT-TYPE
               SYNTAX  INTEGER {
                               invalid(1), 
                               notAccepted(2),
                               success(3),
                               fail(4) 
                               }            
-- @008              ACCESS  read-write
               ACCESS  read-only
               STATUS  mandatory
               DESCRIPTION "Indicates the result of the Loop-back test."
               ::= { mpEtherPortStatusEntry 2 }

       mpEtherPortStsMode OBJECT-TYPE
               SYNTAX  INTEGER {
                               auto(1), 
                               manual(2) 
                               }            
               ACCESS  read-only
               STATUS  mandatory
               DESCRIPTION "Indicates operation mode of the port.
                            If it set to '1', operation mode is automatic.
                            If it set to '2', operation mode is manual."
               ::= { mpEtherPortStatusEntry 3 }

       mpEtherPortStsSpeed OBJECT-TYPE
               SYNTAX  Gauge
               ACCESS  read-only
               STATUS  mandatory
               DESCRIPTION "Indicastes current speed of the port in bps."
               ::= { mpEtherPortStatusEntry 4 }

       mpEtherPortStsFullDuplex OBJECT-TYPE
               SYNTAX  INTEGER {
                               hdx(1), 
                               fdx(2) 
                               }            
               ACCESS  read-only
               STATUS  mandatory
               DESCRIPTION "Indicates which current port status is full-duplex
                            or half-duplex.  If it is set to '1', it is 
                            half-duplex. If it is set to '2', it is 
                            full-duplex."
               ::= { mpEtherPortStatusEntry 5 }



--  ***************************************************************************
--  the MM_Node9110/9120 Virtual LAN Group
--  ***************************************************************************

   --  Implementation of this group is mandatory for all the MM_Node9110/9120 systems.  

       mpVlanModeStatus OBJECT-TYPE
               SYNTAX  INTEGER {
                               active(1),
                               notInService(2),
                               notReady(3)
                               }
               ACCESS  read-write
               STATUS  mandatory
               DESCRIPTION "Indicates to validate the configuration of VLAN
                           group. It is set to '1' when the configuration will
                           be valid, after the value of objects had been
                           modified."
               ::= { mpVlan 1 }

       -- the VLAN table

       mpVlanTable OBJECT-TYPE
               SYNTAX  SEQUENCE OF MpVlanEntry
               ACCESS  not-accessible
               STATUS  mandatory
               DESCRIPTION "It is used for VLAN configuration."
               ::= { mpVlan 2 }

       mpVlanEntry OBJECT-TYPE
               SYNTAX  MpVlanEntry
               ACCESS  not-accessible
               STATUS  mandatory
               DESCRIPTION "Indicates the table entry of the VLAN
                           configuration."                       
               INDEX   { mpVlanIndex }
               ::= { mpVlanTable 1 }

       MpVlanEntry ::=
               SEQUENCE {
                   mpVlanIndex
                       INTEGER,
                   mpVlanRtrIndex
                       INTEGER,
                   mpVlanName
                       DisplayString,
                   mpVlanNameStatus
                       INTEGER
               }

       mpVlanIndex OBJECT-TYPE
               SYNTAX  INTEGER
               ACCESS  read-only
               STATUS  mandatory
               DESCRIPTION "Indicates the specified number to identify the 
                           VLAN. The lowest number must be assigned to the 
                           default VLAN."                                  
               ::= { mpVlanEntry 1 }

       mpVlanRtrIndex OBJECT-TYPE
               SYNTAX  INTEGER
-- @008               ACCESS  read-write
               ACCESS  read-only
               STATUS  mandatory
               DESCRIPTION "Indicates the interface number assigned to the VLAN
                           uniquely, within the equipment. The VLAN identified 
                           by this object is the same VLAN identified by the   
                           same number of ifIndex. The lowest number must be   
                           assigned to the default VLAN."                      
               ::= { mpVlanEntry 2 }

       mpVlanName OBJECT-TYPE
               SYNTAX  DisplayString (SIZE (0..40))
               ACCESS  read-write
               STATUS  mandatory
               DESCRIPTION "Indicates the name which is assigned to the VLAN  
                           for administrative purpose. I is used to assign or 
                           change the name of VLAN. In the initial state, only
                           'default' is registered as the default VLAN. The   
                           default VLAN name cannot be changed."              
               ::= { mpVlanEntry 3 }

       mpVlanNameStatus OBJECT-TYPE
               SYNTAX  INTEGER { 
                               valid(1),
                               invalid(2)
                               }
               ACCESS  read-write
               STATUS  mandatory
               DESCRIPTION "No description."
               ::= { mpVlanEntry 4 }


         -- the VLAN Group table

       mpVlanGroupTable OBJECT-TYPE
               SYNTAX  SEQUENCE OF MpVlanGroupEntry
               ACCESS  not-accessible
               STATUS  mandatory
               DESCRIPTION "This is the table entry of the VLAN group name 
                            registration."                                 
               ::= { mpVlan 3 }

       mpVlanGroupEntry OBJECT-TYPE
               SYNTAX  MpVlanGroupEntry
               ACCESS  not-accessible
               STATUS  mandatory
               DESCRIPTION "This is the table entry of the VLAN group name
                           registration."                                 
               INDEX   { mpVlanGrpIndex }
               ::= { mpVlanGroupTable 1 }

       MpVlanGroupEntry ::=
               SEQUENCE {
                   mpVlanGrpIndex
                       INTEGER,
                   mpVlanGrpName
                       DisplayString,
                   mpVlanGrpNameStatus
                       INTEGER
               }
           
       mpVlanGrpIndex OBJECT-TYPE
               SYNTAX  INTEGER
               ACCESS  read-only
               STATUS  mandatory
               DESCRIPTION "This is the index to identify VLAN group.       
                           The value of this index and the index mpVlanIndex
                           must be assigned uniquely,witrhin the range of   
                           2 - 4095."                                       
               ::= { mpVlanGroupEntry 1 }

       mpVlanGrpName OBJECT-TYPE
               SYNTAX  DisplayString (SIZE (0..40))
               ACCESS  read-write
               STATUS  mandatory
               DESCRIPTION "This object is the name defined to this VLAN
                           Group, for management purpose."              
               ::= { mpVlanGroupEntry 2 }

       mpVlanGrpNameStatus OBJECT-TYPE
               SYNTAX  INTEGER {
                               valid(1),
                               invalid(2)
                               }
               ACCESS  read-write
               STATUS  mandatory
               DESCRIPTION "This object is used to create or delete the entry
                           of mpVlanGroupTable. The value '1' is set to      
                           create the entry, and the value '2' is set to     
                           delete the entry."                                
               ::= { mpVlanGroupEntry 3 }



       -- the Bigpipe table

       mpVlanBigpipeTable OBJECT-TYPE
               SYNTAX  SEQUENCE OF MpVlanBigpipeEntry
               ACCESS  not-accessible
               STATUS  mandatory
               DESCRIPTION "This is the table type object of BigPipe name
                           registration."                                
               ::= { mpVlan 4 }

       mpVlanBigpipeEntry OBJECT-TYPE
               SYNTAX  MpVlanBigpipeEntry
               ACCESS  not-accessible
               STATUS  mandatory
               DESCRIPTION "This is the entry of the mpVlanBigPipeTable."
               INDEX   { mpVlanBigpipeIndex }
               ::= { mpVlanBigpipeTable 1 }

       MpVlanBigpipeEntry ::=
               SEQUENCE {
                   mpVlanBigpipeIndex
                       INTEGER,
                   mpVlanBigpipeName
                       DisplayString,
                   mpVlanBigpipeNameStatus
                       INTEGER,
                   mpVlanBigpipeMode          -- @013
                       INTEGER                -- @013
               }

       mpVlanBigpipeIndex OBJECT-TYPE
               SYNTAX  INTEGER
               ACCESS  read-only
               STATUS  mandatory
               DESCRIPTION "No description."

               ::= { mpVlanBigpipeEntry 1 }

       mpVlanBigpipeName OBJECT-TYPE
               SYNTAX  DisplayString (SIZE (0..40))
               ACCESS  read-write
               STATUS  mandatory
               DESCRIPTION "This is the index to identify the BigPipe. The
                           value of this index should be within 1 - 6."   
               ::= { mpVlanBigpipeEntry 2 }

       mpVlanBigpipeNameStatus OBJECT-TYPE
               SYNTAX  INTEGER { 
                               valid(1),
                               invalid(2)
                               }
               ACCESS  read-write
               STATUS  mandatory
               DESCRIPTION "This object is used to create or delete the entry
                           of mpVlanBigPipeTable. The value '1' is set to   
                           create the entry, and the value '2'  is set to   
                           delete the entry."                               
               ::= { mpVlanBigpipeEntry 3 }

-- @013 add START
       mpVlanBigpipeMode OBJECT-TYPE
               SYNTAX  INTEGER {
                               open(1),
                               clese(2)
                               }
               ACCESS  read-write
               STATUS  mandatory
               DESCRIPTION "This object is used to specify the communication 
                           status of BigPipe to VLAN. If the value is set to '1',
                           frames to/from all VLANs (except VLANs registered
                           in mpVlanBigpipeVidControlTable) are passed. If the
                           value is set to '2', frames to/from all VLANs (except
                           VLANs registered in mpVlanBigpipeVidControlTable)
                           are filtered.  The default value is '1'."
               ::= { mpVlanBigpipeEntry 4 }
-- @013 add END

       -- the Vlan Intf table

       mpVlanIntfTable OBJECT-TYPE
               SYNTAX  SEQUENCE OF MpVlanIntfEntry
               ACCESS  not-accessible
               STATUS  mandatory
               DESCRIPTION "This is the table type object of the interface
                           (Ethernet port and logical ELAN port)          
                           subsucription to VLAN."                        
               ::= { mpVlan 5 }

       mpVlanIntfEntry OBJECT-TYPE
               SYNTAX  MpVlanIntfEntry
               ACCESS  not-accessible
               STATUS  mandatory
               DESCRIPTION "This is the table entry of mpVlanIntfTable."
               INDEX   { mpVlanIntfVlanIndex,
                         mpVlanIntfNumber }
               ::= { mpVlanIntfTable 1 }

       MpVlanIntfEntry ::=
               SEQUENCE {
                   mpVlanIntfVlanIndex
                       INTEGER,
                   mpVlanIntfNumber
                       INTEGER,
                   mpVlanIntfStatus
                       INTEGER
               }

       mpVlanIntfVlanIndex OBJECT-TYPE
               SYNTAX  INTEGER
               ACCESS  read-only
               STATUS  mandatory
               DESCRIPTION "This is the index to identify the existing VLAN
                           to which the interfaces are subscribed. When the
                           equipment is just shipped from factory, all the 
                           Ethernet ports are subscribed to the default    
                           VLAN."                                          
               ::= { mpVlanIntfEntry 1 }
      
       mpVlanIntfNumber OBJECT-TYPE
               SYNTAX  INTEGER
               ACCESS  read-only
               STATUS  mandatory
               DESCRIPTION "This is the index to identify the Ethernet port 
                           number or logical ELAN port number subscribed to 
                           this VLAN. The value of this index is the same as 
                           ifIndex."                                        
               ::= { mpVlanIntfEntry 2 }

       mpVlanIntfStatus OBJECT-TYPE
               SYNTAX  INTEGER{
                              valid(1),
                              invalid(2)
                              }
               ACCESS  read-write
               STATUS  mandatory
               DESCRIPTION "This object is used to register or delete the    
                           interface to this VLAN. The value '1' is set to   
                           register the interface to this VLAN, and the value
                           '2' is set to delete the interface from this VLAN.
                           When all the interfaces are deleted from this     
                           VLAN, the table entry of this VLAN is also        
                            deleted."                                        
               ::= { mpVlanIntfEntry 3 }


       -- the Vlan Group Intf table

       mpVlanGroupIntfTable OBJECT-TYPE
               SYNTAX  SEQUENCE OF MpVlanGroupIntfEntry
               ACCESS  not-accessible
               STATUS  mandatory
               DESCRIPTION "This is the table type object of the VLAN
                           subscription to VLAN Group."              
               ::= { mpVlan 6 }

       mpVlanGroupIntfEntry OBJECT-TYPE
               SYNTAX  MpVlanGroupIntfEntry
               ACCESS  not-accessible
               STATUS  mandatory
               DESCRIPTION "This is the table entry of mpVlanGroupIntfTable."
               INDEX   { mpVlanGrpIntfIndex,
                         mpVlanGrpIntfVlanIndex }
               ::= { mpVlanGroupIntfTable 1 }

       MpVlanGroupIntfEntry ::=
               SEQUENCE {
                   mpVlanGrpIntfIndex
                       INTEGER,
                   mpVlanGrpIntfVlanIndex
                       INTEGER,
                   mpVlanGrpIntfStatus
                       INTEGER
               }

       mpVlanGrpIntfIndex OBJECT-TYPE
               SYNTAX  INTEGER
               ACCESS  read-only
               STATUS  mandatory
               DESCRIPTION "This is the index to identify the existing VLAN
                           Group to which the VLANs are subscribed."       
               ::= { mpVlanGroupIntfEntry 1 }

       mpVlanGrpIntfVlanIndex OBJECT-TYPE
               SYNTAX  INTEGER
               ACCESS  read-only
               STATUS  mandatory
               DESCRIPTION "This is the index to identify the VLAN which is
                           subscribed to this VLAN Group."                 
               ::= { mpVlanGroupIntfEntry 2 }

       mpVlanGrpIntfStatus OBJECT-TYPE
               SYNTAX  INTEGER {
                               valid(1),
                               invalid(2)
                               }
               ACCESS  read-write
               STATUS  mandatory
               DESCRIPTION "This object is used to register/delete the VLAN
                           to/from this VLAN Group. The value '1' is set to
                           register this VLAN to this VLAN Group, and the  
                           value '2' is set to delete this VLAN from this  
                           VLAN Group."                                    
               ::= { mpVlanGroupIntfEntry 3 }


       -- the Bigpipe Intf table

       mpVlanBigpipeIntfTable OBJECT-TYPE
               SYNTAX  SEQUENCE OF MpVlanBigpipeIntfEntry
               ACCESS  not-accessible
               STATUS  mandatory
               DESCRIPTION "This is the table type object of the interface 
                           (Ethernet port) subscription to BigPipe."       
               ::= { mpVlan 7 }

       mpVlanBigpipeIntfEntry OBJECT-TYPE
               SYNTAX  MpVlanBigpipeIntfEntry
               ACCESS  not-accessible
               STATUS  mandatory
               DESCRIPTION "This is the table entry of
                           mpVlanBigPipeIntfTable."   
               INDEX   { mpVlanBigpipeIntfIndex,
                         mpVlanBigpipeIntfNumber }
               ::= { mpVlanBigpipeIntfTable 1 }

       MpVlanBigpipeIntfEntry ::=
               SEQUENCE {
                   mpVlanBigpipeIntfIndex
                       INTEGER,
                   mpVlanBigpipeIntfNumber
                       INTEGER,
                   mpVlanBigpipeIntfNumberStatus
                       INTEGER
               }

       mpVlanBigpipeIntfIndex OBJECT-TYPE
               SYNTAX  INTEGER
               ACCESS  read-only
               STATUS  mandatory
               DESCRIPTION "This is the index to identify the existing
                           BigPipe."                                  
               ::= { mpVlanBigpipeIntfEntry 1 }

       mpVlanBigpipeIntfNumber OBJECT-TYPE
               SYNTAX  INTEGER
               ACCESS  read-only
               STATUS  mandatory
               DESCRIPTION "This is the index to identify the physical       
                           interface (Ethernet port) number subscribed to    
                           this BigPipe. The value of this index is the same 
                           as the value of ifIndex. The interface which is to
                           be subscribed to BigPipe must not be subscribedany
                           VLAN."                                            
               ::= { mpVlanBigpipeIntfEntry 2 }

       mpVlanBigpipeIntfNumberStatus OBJECT-TYPE
               SYNTAX  INTEGER{
                              valid(1),
                              invalid(2)
                              }
               ACCESS  read-write
               STATUS  mandatory
               DESCRIPTION "This object is used to register/delete the       
                           interface (Ethernet port) to/from this BigPipe.   
                           The value '1' is set to register this interface to
                            this BigPipe, and the value '2' is set to delete 
                           this interface from this BigPipe."                
               ::= { mpVlanBigpipeIntfEntry 3 }


       -- the Vlan Mac table

       mpVlanMacTable OBJECT-TYPE
               SYNTAX  SEQUENCE OF MpVlanMacEntry
               ACCESS  not-accessible
               STATUS  mandatory
               DESCRIPTION "This is the table type object of MAC address data
                           of the VLAN."                                    
               ::= { mpVlan 8 }

       mpVlanMacEntry OBJECT-TYPE
               SYNTAX  MpVlanMacEntry
               ACCESS  not-accessible
               STATUS  mandatory
               DESCRIPTION "This is the table entry of mpVlanMacTable."
               INDEX   { mpVlanMacVlanIndex,
                         mpVlanMacAddress }
               ::= { mpVlanMacTable 1 }

       MpVlanMacEntry ::=
               SEQUENCE {
                   mpVlanMacVlanIndex
                       INTEGER,
                   mpVlanMacAddress
                       MacAddress,
                   mpVlanMacIntfNumber
                       INTEGER,
                   mpVlanMacStatus
                       INTEGER
               }

       mpVlanMacVlanIndex OBJECT-TYPE
               SYNTAX  INTEGER
               ACCESS  read-only
               STATUS  mandatory
               DESCRIPTION "This is the index to identify the existing VLAN.
                           The value of this object is the VLAN number."    
               ::= { mpVlanMacEntry 1 }

       mpVlanMacAddress OBJECT-TYPE
               SYNTAX  MacAddress
               ACCESS  read-only
               STATUS  mandatory
               DESCRIPTION "This object is the MAC address which is included
                           in this VLAN."                                   
               ::= { mpVlanMacEntry 2 }
              
       mpVlanMacIntfNumber OBJECT-TYPE
               SYNTAX  INTEGER
               ACCESS  read-write
               STATUS  mandatory
               DESCRIPTION "This object is the Ethernet port number or     
                           logical ELAN number, from which the frame with  
                           source MAC address included in this VLAN can be 
                           received.This interface must belong to this VLAN.
                           This object is set to '0' when no port is       
                           specified."                                     
               ::= { mpVlanMacEntry 3 }

       mpVlanMacStatus OBJECT-TYPE
              SYNTAX  INTEGER {
                               valid(1),
                               invalid(2)
                               }
               ACCESS  read-write
               STATUS  mandatory
               DESCRIPTION "This object is used to create or delete the entry
                           of this table. The value '1' is set to create the 
                           entry, and the value '2' is set to deletethe      
                           entry."                                           
               ::= { mpVlanMacEntry 4 }


       --  Bigpipe Vid Control table

       mpVlanBigpipeVidControlTable OBJECT-TYPE
               SYNTAX  SEQUENCE OF MpVlanBigpipeVidControlEntry
               ACCESS  not-accessible
               STATUS  mandatory
               DESCRIPTION "This is the table type object of the filter
                           condition concerning to VID for BigPipe."  
               ::= { mpVlan 9 }

       mpVlanBigpipeVidControlEntry OBJECT-TYPE
               SYNTAX  MpVlanBigpipeVidControlEntry
               ACCESS  not-accessible
               STATUS  mandatory
               DESCRIPTION "This is the table entry of   
                           mpVlanBigpipeVidControlTable."
               INDEX   { mpVlanBigpipeVidControlIndex,
                         mpVlanBigpipeVidControlVid }
               ::= { mpVlanBigpipeVidControlTable 1 }

       MpVlanBigpipeVidControlEntry ::=
               SEQUENCE {
                   mpVlanBigpipeVidControlIndex
                       INTEGER,
                   mpVlanBigpipeVidControlVid
                       INTEGER,
                   mpVlanBigpipeVidControlStatus
                       INTEGER
               }

       mpVlanBigpipeVidControlIndex OBJECT-TYPE
               SYNTAX  INTEGER
               ACCESS  read-only
               STATUS  mandatory
               DESCRIPTION "This is the index to identify the BigPipe to
                           which this filter condition is applied."     
               ::= { mpVlanBigpipeVidControlEntry 1 }

       mpVlanBigpipeVidControlVid OBJECT-TYPE
               SYNTAX  INTEGER
               ACCESS  read-only
               STATUS  mandatory
               DESCRIPTION "This object is the VID of VLAN or VLAN Group, to
                           which this filter condition is applied."         
               ::= { mpVlanBigpipeVidControlEntry 2 }
              
       mpVlanBigpipeVidControlStatus OBJECT-TYPE
               SYNTAX  INTEGER { 
                               valid(1),
                               invalid(2)
                               }
               ACCESS  read-write
               STATUS  mandatory
               DESCRIPTION "This object is used to register/delete the VID 
                           filter condition for BigPipe. The value '1' is  
                           set to register the filter condition, and the   
                           value '2' is set to delete the filter condition."
               ::= { mpVlanBigpipeVidControlEntry 3 }


       -- Forwarding Data Base table

       mpVlanTpFdbTable  OBJECT-TYPE
               SYNTAX  SEQUENCE OF MpVlanTpFdbEntry
               ACCESS  not-accessible
               STATUS  mandatory
               DESCRIPTION "A table that contains information about 
                            forwarding database per VLAN."
               ::= { mpVlan 10 }


       mpVlanTpFdbEntry  OBJECT-TYPE
               SYNTAX  MpVlanTpFdbEntry
               ACCESS  not-accessible
               STATUS  mandatory
               DESCRIPTION "Each entry contains information about
                            forwarding database per VLAN."
               INDEX { mpVlanTpFdbVlanIndex, mpVlanTpFdbMacAddress }
               ::= { mpVlanTpFdbTable 1 }


       MpVlanTpFdbEntry ::=
               SEQUENCE {
                        mpVlanTpFdbVlanIndex 
                            INTEGER,
                        mpVlanTpFdbMacAddress 
                            MacAddress,
                        mpVlanTpFdbIntfNumber 
                            INTEGER,
                        mpVlanTpFdbStatus
                            INTEGER
                        }

       mpVlanTpFdbVlanIndex OBJECT-TYPE
              SYNTAX  INTEGER
              ACCESS  read-only
              STATUS  mandatory
              DESCRIPTION "Indicates the VLAN number to specify the
                           forwarding database per VLAN."
              ::= { mpVlanTpFdbEntry 1 }

       mpVlanTpFdbMacAddress OBJECT-TYPE
              SYNTAX  MacAddress
              ACCESS  read-only
              STATUS  mandatory
              DESCRIPTION "Indicates the destination MAC Address which 
                           belongs to the forwarding information of this
                           VLAN."
              ::= { mpVlanTpFdbEntry 2 }

       mpVlanTpFdbIntfNumber OBJECT-TYPE
              SYNTAX INTEGER
              ACCESS read-only
              STATUS mandatory
              DESCRIPTION "Either the value '0', or the port number of
                           the port from which the frame, which has a
                           source address equal to the value of the
                           'mpVlanTPFdbMacAddress', was received.
                           A value of '0' indicates that the port number
                           has not been learned but that the bridge
                           does have some forwarding information about
                           this address."
              ::= { mpVlanTpFdbEntry 3 }

       mpVlanTpFdbStatus  OBJECT-TYPE
              SYNTAX INTEGER {
                              other(1),
                              invalid(2),
                              learned(3),
                              self(4),
                              mgmt(5)
                             }
              ACCESS read-only
              STATUS mandatory
              DESCRIPTION "The state of this entry. If it is '1', this
                           entry is none of the following. If it is '2',
                           this entry is not longer valie, but has not
                           yet been flushed from the table. If it is '3',
                           this entry was learned, and is being used. If
                           it is '4', this entry is the bridge's MAC
                           addresses. If it is '5', this entry is the
                           MAC address which was registered as filtering
                           condition."
              ::= { mpVlanTpFdbEntry 4 }
   
       mpVlanTagProtocolId OBJECT-TYPE
               SYNTAX  INTEGER (1501..65535)
               ACCESS  read-write
               STATUS  mandatory
               DESCRIPTION "Indicates VLAN Tag Protocol ID used in this 
                            system. Range of VLAN Tag Protocol ID is 
                            from 1501(0x05dd) to 65535(0xffff) except 
                            2048(0x0800), 2054(0x0806)."
               ::= { mpVlan 11 }

-- @014 add START
       mpVlanTagPpTable OBJECT-TYPE
               SYNTAX  SEQUENCE OF MpVlanTagPpEntry
               ACCESS  not-accessible
               STATUS  mandatory
               DESCRIPTION "It is used for VLAN Tag PP(Point-to-Point)
                           configuration."
               ::= { mpVlan 12 }

       mpVlanTagPpEntry OBJECT-TYPE
               SYNTAX  MpVlanTagPpEntry
               ACCESS  not-accessible
               STATUS  mandatory
               DESCRIPTION "Indicates the table entry of the VLAN Tag PP
                           configuration."                       
               INDEX   { mpVlanTagPpIndex }
               ::= { mpVlanTagPpTable 1 }

       MpVlanTagPpEntry ::=
               SEQUENCE {
                   mpVlanTagPpIndex
                       INTEGER,
                   mpVlanTagPpRtrIndex
                       INTEGER,
                   mpVlanTagPpIntfNumber
                       INTEGER,
                   mpVlanTagPpName
                       DisplayString,
                   mpVlanTagPpMacType
                       INTEGER,
                   mpVlanTagPpNameStatus
                       INTEGER
               }

       mpVlanTagPpIndex OBJECT-TYPE
               SYNTAX  INTEGER
               ACCESS  read-only
               STATUS  mandatory
               DESCRIPTION "Indicates the specified number to identify the 
                           VLAN Tag PP."
               ::= { mpVlanTagPpEntry 1 }

       mpVlanTagPpRtrIndex OBJECT-TYPE
               SYNTAX  INTEGER
               ACCESS  read-only
               STATUS  mandatory
               DESCRIPTION "Indicates the interface number assigned to the VLAN
                           Tag PP uniquely, within the equipment. The VLAN Tag 
                           PP identified by this object is the same VLAN Tag PP
                           identified by the same number of ifIndex."
               ::= { mpVlanTagPpEntry 2 }

       mpVlanTagPpIntfNumber                     OBJECT-TYPE
               SYNTAX  INTEGER
               ACCESS  read-write
               STATUS  mandatory
               DESCRIPTION "This is the index to identify the Ethernet port  
                           number or PPP port number subscribed to this VLAN
                           Tag PP. The value of this index is the same as 
                           ifIndex."  
               ::= { mpVlanTagPpEntry 3 }

       mpVlanTagPpName OBJECT-TYPE
               SYNTAX  DisplayString (SIZE (0..40))
               ACCESS  read-write
               STATUS  mandatory
               DESCRIPTION "Indicates the name which is assigned to the VLAN
                           Tag PP for administrative purpose. It is used to 
                           assign or change the name of VLAN Tag PP."
               ::= { mpVlanTagPpEntry 4 }

       mpVlanTagPpMacType OBJECT-TYPE
               SYNTAX  INTEGER { 
                               global(1),
                               private(2)
                               }
               ACCESS  read-write
               STATUS  mandatory
               DESCRIPTION "Indicates the MAC address type. If the value is
                           set to '1', global MAC address of the physical port
                           is used. If the value is set to '2', private MAC 
                           address given by user (first 4 octets) is used.
                           In case of 2, the last two octets is given by the 
                           value of the mpVlanTagPpIndex."
               ::= { mpVlanTagPpEntry 5 }

       mpVlanTagPpNameStatus OBJECT-TYPE
               SYNTAX  INTEGER { 
                               valid(1),
                               invalid(2)
                               }
               ACCESS  read-write
               STATUS  mandatory
               DESCRIPTION "This object is used to register or delete the 
                           VLAN Tag PP."
               ::= { mpVlanTagPpEntry 6 }
-- @014 add END


--  ***************************************************************************
--  the MM_Node9110/9120 Bridge Group
--  ***************************************************************************

       -- Destination Mac Filter table

       mpBrgDestMacFilterTable OBJECT-TYPE
               SYNTAX  SEQUENCE OF MpBrgDestMacFilterEntry
               ACCESS  not-accessible
               STATUS  mandatory
               DESCRIPTION "This is the table type object of the filter
                           condition concerning to the destination MAC 
                           address."                                   
               ::= { mpBridge 1 }

       mpBrgDestMacFilterEntry OBJECT-TYPE
               SYNTAX  MpBrgDestMacFilterEntry
               ACCESS  not-accessible
               STATUS  mandatory
               DESCRIPTION "This is the table entry of
                           mpBrgDestMacFilterTable." 
               INDEX   { mpBrgDestMacFilterVlanIndex,
                         mpBrgDestMacFilterAddress }
               ::= { mpBrgDestMacFilterTable 1 }

       MpBrgDestMacFilterEntry ::=
               SEQUENCE {
                   mpBrgDestMacFilterVlanIndex
                       INTEGER,
                   mpBrgDestMacFilterAddress
                       MacAddress,
                   mpBrgDestMacFilterStatus
                       INTEGER
               }

       mpBrgDestMacFilterVlanIndex OBJECT-TYPE
               SYNTAX  INTEGER
               ACCESS  read-only
               STATUS  mandatory
               DESCRIPTION "This is the index to identify the VLAN to which
                           this filter condition is applied."              
               ::= { mpBrgDestMacFilterEntry 1 }

       mpBrgDestMacFilterAddress OBJECT-TYPE
               SYNTAX  MacAddress
               ACCESS  read-only
               STATUS  mandatory
               DESCRIPTION "This object is the destination MAC address which 
                           is filtered in this VLAN."                        
               ::= { mpBrgDestMacFilterEntry 2 }
              
       mpBrgDestMacFilterStatus OBJECT-TYPE
               SYNTAX  INTEGER {
                               valid(1),
                               invalid(2)
                               }
               ACCESS  read-write
               STATUS  mandatory
               DESCRIPTION "This object is used to create or delete the table
                           entry. The value '1' is set to create the entry,  
                           and the value '2' is set to delete the entry."    
               ::= { mpBrgDestMacFilterEntry 3 }


       --  Source Mac Filter table

       mpBrgSrcMacFilterTable OBJECT-TYPE
               SYNTAX  SEQUENCE OF MpBrgSrcMacFilterEntry
               ACCESS  not-accessible
               STATUS  mandatory
               DESCRIPTION "This is the table type object of the filter    
                           condition concerning to the source MAC address."
               ::= { mpBridge 2 }

       mpBrgSrcMacFilterEntry OBJECT-TYPE
               SYNTAX  MpBrgSrcMacFilterEntry
               ACCESS  not-accessible
               STATUS  mandatory
               DESCRIPTION "This is the table entry of
                           mpBrgSrcMacFilterTable."
               INDEX   { mpBrgSrcMacFilterVlanIndex,
                        mpBrgSrcMacFilterAddress }
               ::= { mpBrgSrcMacFilterTable 1 }

       MpBrgSrcMacFilterEntry ::=
               SEQUENCE {
                   mpBrgSrcMacFilterVlanIndex
                       INTEGER,
                   mpBrgSrcMacFilterAddress
                       MacAddress,
                   mpBrgSrcMacFilterStatus
                       INTEGER
               }

       mpBrgSrcMacFilterVlanIndex OBJECT-TYPE
               SYNTAX  INTEGER
               ACCESS  read-only
               STATUS  mandatory
               DESCRIPTION "This is the index to identify the VLAN to which
                           this filter condition is applied."              
               ::= { mpBrgSrcMacFilterEntry 1 }

       mpBrgSrcMacFilterAddress OBJECT-TYPE
               SYNTAX  MacAddress
               ACCESS  read-only
               STATUS  mandatory
               DESCRIPTION "This object is the source MAC address which is
                           filtered in this VLAN."                        
               ::= { mpBrgSrcMacFilterEntry 2 }
              
       mpBrgSrcMacFilterStatus OBJECT-TYPE
               SYNTAX  INTEGER {
                               valid(1),
                               invalid(2)
                               }
               ACCESS  read-write
               STATUS  mandatory
               DESCRIPTION "This object is used to create or delete the table
                           entry. The value '1' is set to create the entry,  
                           and the value '2' is set to delete the entry."    
               ::= { mpBrgSrcMacFilterEntry 3 }


       --  Destination Port Filter table

       mpBrgDestPortFilterTable OBJECT-TYPE
               SYNTAX  SEQUENCE OF MpBrgDestPortFilterEntry 
               ACCESS  not-accessible
               STATUS  mandatory
               DESCRIPTION "This is the table type ofject of the filter  
                           condition concerning to the destination port."
               ::= { mpBridge 3 }

       mpBrgDestPortFilterEntry OBJECT-TYPE
               SYNTAX  MpBrgDestPortFilterEntry
               ACCESS  not-accessible
               STATUS  mandatory
               DESCRIPTION "This is the table entry of 
                           mpBrgDestPortFilterTable."  
               INDEX   { mpBrgDestPortFilterIfIndex }
               ::= { mpBrgDestPortFilterTable 1 }

       MpBrgDestPortFilterEntry ::=
               SEQUENCE {
                   mpBrgDestPortFilterIfIndex
                       INTEGER,
                   mpBrgDestPortFilterStatus
                       INTEGER
               }

       mpBrgDestPortFilterIfIndex OBJECT-TYPE
               SYNTAX  INTEGER
               ACCESS  read-only
               STATUS  mandatory
               DESCRIPTION "This is the index to identify the destination  
                           port to which the filtering function is applied.
                           The value of this index is the same as IfIndex."
               ::= { mpBrgDestPortFilterEntry 1 }

       mpBrgDestPortFilterStatus OBJECT-TYPE
               SYNTAX  INTEGER {
                               valid(1),
                               invalid(2)
                               }
               ACCESS  read-write
               STATUS  mandatory
               DESCRIPTION "This object is used to create or delete the table
                           entry. The value '1' is set to create the entry, 
                           and the value '2' is set to delete the entry."   
               ::= { mpBrgDestPortFilterEntry 2 }


       --  Source Port Filter table

       mpBrgSrcPortFilterTable OBJECT-TYPE
               SYNTAX  SEQUENCE OF MpBrgSrcPortFilterEntry
               ACCESS  not-accessible
               STATUS  mandatory
               DESCRIPTION "This is the table type ofject of the filter
                           condition concerning to the source port."  
               ::= { mpBridge 4 }

       mpBrgSrcPortFilterEntry OBJECT-TYPE
               SYNTAX  MpBrgSrcPortFilterEntry
               ACCESS  not-accessible
               STATUS  mandatory
               DESCRIPTION "This is the table entry of 
                           mpBrgSrcPortFilterTable."
               INDEX   { mpBrgSrcPortFilterIfIndex }
               ::= { mpBrgSrcPortFilterTable 1 }

       MpBrgSrcPortFilterEntry ::=
               SEQUENCE {
                   mpBrgSrcPortFilterIfIndex
                       INTEGER,
                   mpBrgSrcPortFilterStatus
                       INTEGER
              }

       mpBrgSrcPortFilterIfIndex OBJECT-TYPE
               SYNTAX  INTEGER
               ACCESS  read-only
               STATUS  mandatory
               DESCRIPTION  "This is the index to identify the source port to 
                            which the filtering function is applied. The value
                            of this index is the same as IfIndex."            
               ::= { mpBrgSrcPortFilterEntry 1 }

       mpBrgSrcPortFilterStatus OBJECT-TYPE
               SYNTAX  INTEGER {
                               valid(1),
                               invalid(2)
                               }
               ACCESS  read-write
               STATUS  mandatory
               DESCRIPTION "This object is used to create or delete the table
                           entry. The value '1' is set to create the entry,  
                           and the value '2' is set to delete the entry."    
               ::= { mpBrgSrcPortFilterEntry 2 }


--  ***************************************************************************
--  the MM_Node9110/9120 Database Access Group
--  10/23/1998  add  mpDbAccessAllSave @001
--  12/21/1998  add  mpDbAccessAllSave @002
--  ***************************************************************************
   --  Implementation of this group is mandatory for all the SANFRAN systems.  

       mpDbAccessSave OBJECT-TYPE
               SYNTAX  INTEGER {
							   enable(1),
							   disable(2)
							   }
               ACCESS  read-write
               STATUS  mandatory
               DESCRIPTION "Signal the system applications to save their config."
--                            save処理を実行する場合は1を指定する。save処理実行中は
--                            2を返す。2を指定した場合は、何も処理を行わずにsuccessを
--                            返す。"
               ::= { mpDbAccess 1 }

       mpDbAccessAllSave OBJECT-TYPE
               SYNTAX  INTEGER {
							   enable(1),
							   disable(2)
							   }
               ACCESS  read-write
               STATUS  mandatory
               DESCRIPTION "Signal the system applications to save their all config."
--                            save all処理を実行する場合は1を指定する。save all処理実行中は
--                            2を返す。2を指定した場合は、何も処理を行わずにsuccessを
--                            返す。"
               ::= { mpDbAccess 2 }

-- ****************************************************************************
-- Event Log MIB Objects
-- 10/23/1998 all overwrite @001
-- ****************************************************************************

   --  Implementation of this group is mandatory for all the SANFRAN systems.

   --  Scalar objects

       mpEventLogAttribute OBJECT-TYPE
              SYNTAX   INTEGER {
                       wraparound (1),
                       discardnewevents (2),
                       newlog (3)
              }
              ACCESS   read-write
              STATUS   mandatory
              DESCRIPTION "Specifies the type of logging for the events."
              ::= { mpEventLog 1 }

       mpEventLogSize OBJECT-TYPE
              SYNTAX   INTEGER
              ACCESS   read-write
              STATUS   mandatory
              DESCRIPTION "Specifies the log size."
              ::= { mpEventLog 2 }

       mpEventLoggingFilter OBJECT-TYPE
              SYNTAX INTEGER  --  0x01  (bit 0)  for  CRITICAL
                              --  0x02  (bit 1)  for  MAJOR
                              --  0x04  (bit 2)  for  MINOR
                              --  0x08  (bit 3)  for  WARNING
                              --  0x10  (bit 4)  for  INFORMATIONAL
              ACCESS   read-write
              STATUS   mandatory
              DESCRIPTION "Specifies filtering to be applied to incoming
                           events. Bit mapped."
              ::= { mpEventLog 3 }

       mpEventLogEarliestEvent OBJECT-TYPE
              SYNTAX   INTEGER
              ACCESS   read-only
              STATUS   mandatory
              DESCRIPTION "Specifies the index of the earliest event in
                           the log."
              ::= { mpEventLog 4 }

       mpEventLogLatestEvent OBJECT-TYPE
              SYNTAX   INTEGER
              ACCESS   read-only
              STATUS   mandatory
              DESCRIPTION "Specifies the index of the latest event in the log."
              ::= { mpEventLog 5 }

       mpEventLogNumEntries OBJECT-TYPE
              SYNTAX   INTEGER
              ACCESS   read-only
              STATUS   mandatory
              DESCRIPTION "Specifies the number of entries in the log."
              ::= { mpEventLog 6 }

       mpEventLogCriticalEvents OBJECT-TYPE
              SYNTAX   INTEGER
              ACCESS   read-only
              STATUS   mandatory
              DESCRIPTION "Number of critical events in the log."
              ::= { mpEventLog 7 }

       mpEventLogMajorEvents OBJECT-TYPE
              SYNTAX   INTEGER
              ACCESS   read-only
              STATUS   mandatory
              DESCRIPTION "Number of major events in the log."
              ::= { mpEventLog 8 }

       mpEventLogMinorEvents OBJECT-TYPE
              SYNTAX   INTEGER
              ACCESS   read-only
              STATUS   mandatory
              DESCRIPTION "Number of minor events in the log."
              ::= { mpEventLog 9 }

       mpEventLogWarningEvents OBJECT-TYPE
              SYNTAX   INTEGER
              ACCESS   read-only
              STATUS   mandatory
              DESCRIPTION "Number of warning events in the log."
              ::= { mpEventLog 10 }

       mpEventLogInformationalEvents OBJECT-TYPE
              SYNTAX   INTEGER
              ACCESS   read-only
              STATUS   mandatory
              DESCRIPTION "Number of informational events in the log."
              ::= { mpEventLog 11 }

       mpEventLogClearAll OBJECT-TYPE
              SYNTAX   INTEGER {
                       clear (1),
                       noaction (2)
               }
              ACCESS   read-write
              STATUS   mandatory
              DESCRIPTION "Clear the log if set to clear."
              ::= { mpEventLog 12 }

       mpEventLogClearSeverity OBJECT-TYPE
              SYNTAX   INTEGER {
                       critical (1),
                       major (2),
                       minor (3),
                       warning (4),
                       informational (5),
                       noaction (6)
               }
              ACCESS   read-write
              STATUS   mandatory
              DESCRIPTION "Deletes entries in the log with specified severity."
              ::= { mpEventLog 13 }

       mpEventLogClearPeriod OBJECT-TYPE
              SYNTAX  DisplayString
              ACCESS  read-write
              STATUS  mandatory
              DESCRIPTION "Deletes entries in the log within the
                           specified period.
                           format : yyyy/[m]m/[d]d yyyy/m[m]/[d]d
                                yyyy   year
                                mm     month
                                dd     day "
              ::= { mpEventLog 14 }

   --     Tabular objects

       mpEventTable OBJECT-TYPE
              SYNTAX   SEQUENCE OF MpEventEntry
              ACCESS   not-accessible
              STATUS   mandatory
              DESCRIPTION "Event related details."
              ::= { mpEventLog 15 }

       mpEventEntry OBJECT-TYPE
              SYNTAX   MpEventEntry
              ACCESS   not-accessible
              STATUS   mandatory
              DESCRIPTION "Details for particular event."
              INDEX { mpEventIndex }
              ::= { mpEventTable 1 }

       MpEventEntry   ::=
         SEQUENCE {
                    mpEventIndex INTEGER,
                    mpEventSource INTEGER,
                    mpEventCode INTEGER,
                    mpEventTimeStamp DisplayString,
                    mpEventSeverity INTEGER,
                    mpEventDescription DisplayString
                  }

       mpEventIndex OBJECT-TYPE
              SYNTAX   INTEGER (1..4294967295)
              ACCESS   read-only
              STATUS   mandatory
              DESCRIPTION "Index to the event in the table."
              ::= { mpEventEntry 1 }

       mpEventSource OBJECT-TYPE
              SYNTAX   INTEGER
              ACCESS   read-only
              STATUS   mandatory
              DESCRIPTION "Indicates any code that may be associated with the
                          source of the event.  If no source is associated
                          defaults to 0."
              ::= { mpEventEntry 2 }

       mpEventCode OBJECT-TYPE
              SYNTAX   INTEGER
              ACCESS   read-only
              STATUS   mandatory
              DESCRIPTION "Indicates any code that may be associated with the
                          event for further details.  If no code is associated
                          defaults to 0."
              ::= { mpEventEntry 3 }

       mpEventTimeStamp OBJECT-TYPE
              SYNTAX   DisplayString
              ACCESS   read-only
              STATUS   mandatory
              DESCRIPTION "Timestamp of the event."
              ::= { mpEventEntry 4 }

       mpEventSeverity OBJECT-TYPE
              SYNTAX INTEGER
              {
                  critical(1),
                  major(2),
                  minor(3),
                  warning(4),
                  informational(5)
              }
              ACCESS   read-only
              STATUS   mandatory
              DESCRIPTION "Indicates event severity."
              ::= { mpEventEntry 5 }

       mpEventDescription OBJECT-TYPE
              SYNTAX   DisplayString (SIZE (0..255))
              ACCESS   read-only
              STATUS   mandatory
              DESCRIPTION "Brief description of the recorded event."
              ::= { mpEventEntry 6 }


       mpTrapFilterTable OBJECT-TYPE
              SYNTAX   SEQUENCE OF MpTrapFilterEntry
              ACCESS   not-accessible
              STATUS   mandatory
              DESCRIPTION "Indicates the table of Trap Filter Information."
              ::= { mpEventLog 16 }

       mpTrapFilterEntry OBJECT-TYPE
              SYNTAX   MpTrapFilterEntry
              ACCESS   not-accessible
              STATUS   mandatory
              DESCRIPTION "Indicates the entry of Trap Filter Information."
              INDEX    { mpTrapFilterEnterprise,
                         mpTrapFilterGeneric,
                         mpTrapFilterSpecific }
              ::= { mpTrapFilterTable 1 }

       MpTrapFilterEntry ::=
              SEQUENCE { mpTrapFilterGeneric INTEGER,
                         mpTrapFilterSpecific INTEGER,
                         mpTrapFilterEnterprise OBJECT IDENTIFIER,
                         mpTrapFilterStatus INTEGER,
                         mpTrapFilterName DisplayString }

       mpTrapFilterGeneric OBJECT-TYPE
              SYNTAX   INTEGER
              ACCESS   read-only
              STATUS   mandatory
              DESCRIPTION "This object is the generic-trap to identify
                           the trap to which this filter condition is
                           applied."
              ::= { mpTrapFilterEntry 1 }

       mpTrapFilterSpecific OBJECT-TYPE
              SYNTAX   INTEGER
              ACCESS   read-only
              STATUS   mandatory
              DESCRIPTION "This object is the specific-trap to identify
                           the trap to which this filter condition is
                           applied."
              ::= { mpTrapFilterEntry 2 }

       mpTrapFilterEnterprise OBJECT-TYPE
              SYNTAX   OBJECT IDENTIFIER
              ACCESS   read-only
              STATUS   mandatory
              DESCRIPTION "This object is the enterprise-trap to identify
                           the trap to which this filter condition is
                           applied."
              ::= { mpTrapFilterEntry 3 }

       mpTrapFilterStatus OBJECT-TYPE
              SYNTAX   INTEGER { enabled(1),
                                 disabled(2)
                               }
              ACCESS   read-write
              STATUS   mandatory
              DESCRIPTION "This object specifies validity of trap filter."
              ::= { mpTrapFilterEntry 4 }

       mpTrapFilterName OBJECT-TYPE
              SYNTAX    DisplayString
              ACCESS    read-only
              STATUS    mandatory
              DESCRIPTION "This object is the name of the trap to be
                           displayed."
              ::= { mpTrapFilterEntry 5 }

       mpEventTrapSeverityTable OBJECT-TYPE
              SYNTAX   SEQUENCE OF MpEventTrapSeverityEntry
              ACCESS   not-accessible
              STATUS   mandatory
              DESCRIPTION "Control Severity of Trap"
              --トラップの重要度情報を管理する
              ::= { mpEventLog 17 }

       mpEventTrapSeverityEntry OBJECT-TYPE
              SYNTAX   MpEventTrapSeverityEntry
              ACCESS   not-accessible
              STATUS   mandatory
              DESCRIPTION "severity of SpecificTrap"
              --特定トラップの重要度情報
              INDEX { mpEventTrapSeverityIndex }
              ::= { mpEventTrapSeverityTable 1 }

       MpEventTrapSeverityEntry   ::=
         SEQUENCE {
                    mpEventTrapSeverityIndex INTEGER,
                    mpEventTrapCode INTEGER,
                    mpEventTrapSeverity INTEGER,
                    mpEventTrapDescription DisplayString
                  }

       mpEventTrapSeverityIndex OBJECT-TYPE
              SYNTAX   INTEGER (1..4294967295)
              ACCESS   read-only
              STATUS   mandatory
              DESCRIPTION "Index of Trap Severity Table"
              --トラップ重要度テーブルのインデックス
              ::= { mpEventTrapSeverityEntry 1 }

       mpEventTrapCode OBJECT-TYPE
              SYNTAX   INTEGER
              ACCESS   read-only
              STATUS   mandatory
              DESCRIPTION "EventCode"
              --イベントコード
              ::= { mpEventTrapSeverityEntry 2 }

       mpEventTrapSeverity OBJECT-TYPE
              SYNTAX INTEGER
              {
                  critical(1),
                  major(2),
                  minor(3),
                  warning(4),
                  informational(5)
              }
              ACCESS   read-write
              STATUS   mandatory
              DESCRIPTION "Severity of Trap"
              --トラップの重要度
              ::= { mpEventTrapSeverityEntry 3 }

       mpEventTrapDescription OBJECT-TYPE
              SYNTAX   DisplayString (SIZE (0..255))
              ACCESS   read-only
              STATUS   mandatory
              DESCRIPTION "Information of Trap"
              --トラップの簡潔な情報
              ::= { mpEventTrapSeverityEntry 4 }

       mpEventLogAlmRenewalTimeStamp OBJECT-TYPE
              SYNTAX   TimeTicks
              ACCESS   read-only
              STATUS   mandatory
              DESCRIPTION "SysUpTime of Alm State Change"
              --ALMの状態変化が発生した時刻
              ::= { mpEventLog 18 }



-- ***************************************************************************
--  the SanFran UISM Group
-- ***************************************************************************

        mpUiSessionTable OBJECT-TYPE
                SYNTAX SEQUENCE OF MpUiSessionEntry
                ACCESS not-accessible
                STATUS mandatory
                DESCRIPTION "Table that describes active connections."
                ::= { mpUiSession 1 }

        mpUiSessionEntry OBJECT-TYPE
                SYNTAX MpUiSessionEntry
                ACCESS not-accessible
                STATUS mandatory
                DESCRIPTION "Describes each node in the session table. "
                INDEX { mpUiSessionPort }
                ::= { mpUiSessionTable 1 }

        MpUiSessionEntry ::=
                SEQUENCE {
                        mpUiSessionPort INTEGER,
                        mpUiSessionTime INTEGER,
                        mpUiSessionUserStatus INTEGER,
                        mpUiSessionStatus INTEGER
                        }

        mpUiSessionPort OBJECT-TYPE
                SYNTAX INTEGER
                ACCESS read-only
                STATUS mandatory
                DESCRIPTION "The telnet port/async port that the session is
                            using. "
                ::= { mpUiSessionEntry 1 }

        mpUiSessionTime OBJECT-TYPE
                SYNTAX DisplayString
                ACCESS read-only
                STATUS mandatory
                DESCRIPTION "The starting time of the session "
                ::= { mpUiSessionEntry 2 }

        mpUiSessionUserStatus OBJECT-TYPE
                SYNTAX INTEGER {
                       unknown (1),
                       operator (2),
                       supervisor (3)
                       }
                ACCESS read-only
                STATUS mandatory
                DESCRIPTION "Status of the session user. "
                ::= { mpUiSessionEntry 3 }

       mpUiSessionStatus OBJECT-TYPE
               SYNTAX INTEGER{
                      valid (1),
                      invalid (2)
                      }
               ACCESS read-write
               STATUS mandatory
               DESCRIPTION "Session validity "
               ::= { mpUiSessionEntry 4 }


--  ***************************************************************************
--  the MM_Node9110/9120 FTP Group
--  ***************************************************************************

   --  Implementation of this group is mandatory for all the MM_Node9110/9120 systems.  

       mpFtpServerStatus OBJECT-TYPE
               SYNTAX  INTEGER {
                              enabled(1),
                              disabled(2)
                              }
               ACCESS  read-write
               STATUS  mandatory
               DESCRIPTION "This object controls the operating status of FTP
                           server. The value '1' is set to enable the FTP   
                           server functionality, and the value '2' is set to
                           disable the FTP server functionality."           
               ::= { mpFtp 1 }


--  ***************************************************************************
--  the MM_Node9110/9120 DHCP/BOOTP Group
--  ***************************************************************************

   --  Implementation of this group is mandatory for 
   --  all the MM_Node9110/9120 systems.

       mpDhcpRelayRequests OBJECT-TYPE
              SYNTAX  Counter
              ACCESS  read-only
              STATUS  mandatory
              DESCRIPTION "This object is the counter of the total number of
                          received Dhcp Relay request."
              ::= { mpDhcp 1 }

       mpDhcpRelayReplys OBJECT-TYPE
              SYNTAX  Counter
              ACCESS  read-only
              STATUS  mandatory
              DESCRIPTION "This is the counter of the total number of
                          received Dhcp Relay reply."
              ::= { mpDhcp 2 }

       mpDhcpRelayRequestDiscards OBJECT-TYPE
              SYNTAX  Counter
              ACCESS  read-only
              STATUS  mandatory
              DESCRIPTION "This is the counter of the total number of
                          discarded Dhcp Relay request."
              ::= { mpDhcp 3 }

       mpDhcpRelayReplyDiscards OBJECT-TYPE
              SYNTAX  Counter
              ACCESS  read-only
              STATUS  mandatory
              DESCRIPTION "This is the counter of the total number of
                          discareded Dhcp Relay reply."
              ::= { mpDhcp 4 }

       mpDhcpRelayEnable OBJECT-TYPE
              SYNTAX  INTEGER {
                              enabled(1),
                              disabled(2)
                      }
              ACCESS  read-only
--            ACCESS  read-write
              STATUS  mandatory
              DESCRIPTION "The current operational state of the Dhcp Relay
                          Agent. This object is changed to '1' automatically,
                          when mpDhcpRelayIfTable is created initially.
                          Vice versa, this object is changed to '2'
                          automatically, when mpDhcpRelayIfTable is deleted
                          lastly. The default value of this object is '2'."

              ::= { mpDhcp 5 }

       mpDhcpRelayMaxHops OBJECT-TYPE
              SYNTAX  INTEGER (1..16)
              ACCESS  read-write
              STATUS  mandatory
              DESCRIPTION "This object specifies the maximum number of the
                          hop count of Dhcp Relay Agent. The value of this
                          object must be within the range of 1 - 16.
                          The default value of this object is 4."
              ::= { mpDhcp 6 }


-- @020        the BOOTP/DHCP relay destination IP address table

-- @020       mpDhcpRelayTable OBJECT-TYPE
-- @020              SYNTAX  SEQUENCE OF MpDhcpRelayEntry
-- @020              ACCESS  not-accessible
-- @020              STATUS  mandatory
-- @020              DESCRIPTION "This is the table type object of the Dhcp Relay
-- @020                          Agent data."                                     
-- @020              ::= { mpDhcp 7 }

-- @020       mpDhcpRelayEntry OBJECT-TYPE
-- @020              SYNTAX  MpDhcpRelayEntry
-- @020              ACCESS  not-accessible
-- @020              STATUS  mandatory
-- @020              DESCRIPTION "This object is the table entry of
-- @020                          mpDhcpRelayTable."               
-- @020              INDEX   { mpDhcpRelayEntIfIndex }
-- @020              ::= { mpDhcpRelayTable 1 }

-- @020       MpDhcpRelayEntry ::=
-- @020              SEQUENCE {
-- @020                  mpDhcpRelayEntIfIndex
-- @020                      INTEGER,
-- @020                  mpDhcpRelayEntAddr
-- @020                      IpAddress,
-- @020                  mpDhcpRelayEntStatus
-- @020                      INTEGER
-- @020              }

-- @020       mpDhcpRelayEntIfIndex OBJECT-TYPE
-- @020              SYNTAX  INTEGER
-- @020              ACCESS  read-only
-- @020              STATUS  mandatory
-- @020              DESCRIPTION "This is the index to identify the VLAN/LIS      
-- @020                          interface. The value of this index is the same as
-- @020                          ifIndex."                                        
-- @020              ::= { mpDhcpRelayEntry 1 }

-- @020       mpDhcpRelayEntAddr OBJECT-TYPE
-- @020              SYNTAX  IpAddress
-- @020              ACCESS  read-write
-- @020              STATUS  mandatory
-- @020              DESCRIPTION "This object specifies the relaying destination IP
-- @020                          address."                                         
-- @020              ::= { mpDhcpRelayEntry 2 }

-- @020       mpDhcpRelayEntStatus OBJECT-TYPE
-- @020              SYNTAX  INTEGER {
-- @020                              valid(1),
-- @020                              invalid(2)
-- @020                      }
-- @020              ACCESS  read-write
-- @020              STATUS  mandatory
-- @020              DESCRIPTION "This object is used to create or delete the table
-- @020                          entry. The value '1' is set to create the entry,  
-- @020                          and the value '2' is set to delete the entry."    
-- @020              ::= { mpDhcpRelayEntry 3 }


-- @020 add from

       -- the BOOTP/DHCP relay interface table

       mpDhcpRelayIfTable OBJECT-TYPE
              SYNTAX  SEQUENCE OF MpDhcpRelayIfEntry
              ACCESS  not-accessible
              STATUS  mandatory
              DESCRIPTION "This is the table type object of the Dhcp Relay
                          Agent interface data."                          
              ::= { mpDhcp 8 }

       mpDhcpRelayIfEntry OBJECT-TYPE
              SYNTAX  MpDhcpRelayIfEntry
              ACCESS  not-accessible
              STATUS  mandatory
              DESCRIPTION "This object is the table entry of
                          mpDhcpRelayIfTable."              
              INDEX   { mpDhcpRelayIfEntIfIndex }
              ::= { mpDhcpRelayIfTable 1 }

       MpDhcpRelayIfEntry ::=
              SEQUENCE {
                  mpDhcpRelayIfEntIfIndex
                      INTEGER,
                  mpDhcpRelayIfEntTransMode
                      INTEGER,
                  mpDhcpRelayIfEntRequests
                      Counter,
                  mpDhcpRelayIfEntReplies
                      Counter,
                  mpDhcpRelayIfEntRequestTransmits
                      Counter,
                  mpDhcpRelayIfEntRequestDiscards
                      Counter,
                  mpDhcpRelayIfEntReplyDiscards
                      Counter,
                  mpDhcpRelayIfEntStatus
                      INTEGER
              }

       mpDhcpRelayIfEntIfIndex OBJECT-TYPE
              SYNTAX  INTEGER
              ACCESS  read-only
              STATUS  mandatory
              DESCRIPTION "This is the index to identify the router
                          interface. The value of this index is the same as
                          ifIndex."
              ::= { mpDhcpRelayIfEntry 1 }

       mpDhcpRelayIfEntTransMode OBJECT-TYPE
              SYNTAX  INTEGER {
                          all1(1),
                          all2(2),
                          roundrobin(3)
                      }
              ACCESS  read-write
              STATUS  mandatory
              DESCRIPTION "The type of Transfer Mode.  The default value
                          of this object is '1'."
              ::= { mpDhcpRelayIfEntry 2 }

       mpDhcpRelayIfEntRequests OBJECT-TYPE
              SYNTAX  Counter
              ACCESS  read-only
              STATUS  mandatory
              DESCRIPTION "This object is the counter of the total number of
                          received BOOTP-REQUEST from this interface."
              ::= { mpDhcpRelayIfEntry 3 }

       mpDhcpRelayIfEntReplies OBJECT-TYPE
              SYNTAX  Counter
              ACCESS  read-only
              STATUS  mandatory
              DESCRIPTION "This is the counter of the total number of
                          attempt to transmit BOOTP-REPLY to this interface."
              ::= { mpDhcpRelayIfEntry 4 }

       mpDhcpRelayIfEntRequestTransmits OBJECT-TYPE
              SYNTAX  Counter
              ACCESS  read-only
              STATUS  mandatory
              DESCRIPTION "This object is the counter of the total number of
                          transmitted BOOTP-REQUEST."
              ::= { mpDhcpRelayIfEntry 5 }

       mpDhcpRelayIfEntRequestDiscards OBJECT-TYPE
              SYNTAX  Counter
              ACCESS  read-only
              STATUS  mandatory
              DESCRIPTION "This is the counter of the total number of
                          discarded BOOTP-REQUEST."
              ::= { mpDhcpRelayIfEntry 6 }

       mpDhcpRelayIfEntReplyDiscards OBJECT-TYPE
              SYNTAX  Counter
              ACCESS  read-only
              STATUS  mandatory
              DESCRIPTION "This is the counter of the total number of
                          discareded BOOTP-REPLY."
              ::= { mpDhcpRelayIfEntry 7 }

       mpDhcpRelayIfEntStatus OBJECT-TYPE
              SYNTAX  INTEGER {
                              valid(1),
                              invalid(2)
                      }
              ACCESS  read-write
              STATUS  mandatory
              DESCRIPTION "This object is used to create or delete the table
                          entry. The value '1' is set to create the entry,
                          and the value '2' is set to delete the entry."
              ::= { mpDhcpRelayIfEntry 8 }


       -- the BOOTP/DHCP relay destination IP address table

       mpDhcpRelayAddrTable OBJECT-TYPE
              SYNTAX  SEQUENCE OF MpDhcpRelayAddrEntry
              ACCESS  not-accessible
              STATUS  mandatory
              DESCRIPTION "This is the table type object of the Dhcp Relay
                          Agent Destination IP Address data."
              ::= { mpDhcp 9 }

       mpDhcpRelayAddrEntry OBJECT-TYPE
              SYNTAX  MpDhcpRelayAddrEntry
              ACCESS  not-accessible
              STATUS  mandatory
              DESCRIPTION "This object is the table entry of
                          mpDhcpRelayAddrTable."
              INDEX   { mpDhcpRelayAddrEntIfIndex, mpDhcpRelayAddrEntAddr }
              ::= { mpDhcpRelayAddrTable 1 }

       MpDhcpRelayAddrEntry ::=
              SEQUENCE {
                  mpDhcpRelayAddrEntIfIndex
                      INTEGER,
                  mpDhcpRelayAddrEntAddr
                      IpAddress,
                  mpDhcpRelayAddrEntStatus
                      INTEGER
              }

       mpDhcpRelayAddrEntIfIndex OBJECT-TYPE
              SYNTAX  INTEGER
              ACCESS  read-write
              STATUS  mandatory
              DESCRIPTION "This is the index to identify the router
                          interface. The value of this index is the same as
                          ifIndex."
              ::= { mpDhcpRelayAddrEntry 1 }

       mpDhcpRelayAddrEntAddr OBJECT-TYPE
              SYNTAX  IpAddress
              ACCESS  read-write
              STATUS  mandatory
              DESCRIPTION "This object specifies the relaying destination IP
                          address."
              ::= { mpDhcpRelayAddrEntry 2 }

       mpDhcpRelayAddrEntStatus OBJECT-TYPE
              SYNTAX  INTEGER {
                              valid(1),
                              invalid(2)
                      }
              ACCESS  read-write
              STATUS  mandatory
              DESCRIPTION "This object is used to create or delete the table
                          entry. The value '1' is set to create the entry,
                          and the value '2' is set to delete the entry."
              ::= { mpDhcpRelayAddrEntry 3 }

-- @020 add end


--  ***************************************************************************
--  the MM_Node9110/9120 IP Group
--  ***************************************************************************

   --  Implementation of this group is mandatory for all the MM_Node9110/9120 systems.  

-- @015       the IP address table

-- @015       mpIpAddrTable OBJECT-TYPE
-- @015              SYNTAX  SEQUENCE OF MpIpAddrEntry
-- @015              ACCESS  not-accessible
-- @015              STATUS  mandatory
-- @015              DESCRIPTION "The table of addressing information relevant to
-- @015                          this entity's IP addresses."
-- @015              ::= { mpIp 1 }

-- @015       mpIpAddrEntry OBJECT-TYPE
-- @015              SYNTAX  MpIpAddrEntry
-- @015              ACCESS  not-accessible
-- @015              STATUS  mandatory
-- @015              DESCRIPTION "The addressing information for one of this
-- @015                          entity's IP addresses."
-- @015              INDEX { mpIpAdEntAddr,
-- @015                      mpIpAdEntIfIndex }
-- @015              ::= { mpIpAddrTable 1 }

-- @015       MpIpAddrEntry ::=
-- @015              SEQUENCE {
-- @015                  mpIpAdEntAddr
-- @015                      IpAddress,
-- @015                  mpIpAdEntIfIndex
-- @015                      INTEGER,
-- @015                  mpIpAdEntNetMask
-- @015                      IpAddress,
-- @015                  mpIpAdEntBcastAddr
-- @015                      INTEGER,
-- @015                  mpIpAdEntStatus
-- @015                      INTEGER,
-- @015                  mpIpAdEntEncapType
-- @015                      INTEGER,
-- @015                  mpIpAdEntForwarding
-- @015                      INTEGER,
-- @008                 mpIpAdEntInOffsetIface
-- @008                     INTEGER,
-- @008                 mpIpAdEntOutOffsetIface
-- @008                     INTEGER
-- @008 add from
-- @015                  mpIpAdEntArpTimeOut
-- @015                       INTEGER,
-- @015                  mpIpAdEntIcmpRedirectStatus
-- @015                       INTEGER
-- @008 add end
-- @015              }

-- @015       mpIpAdEntAddr OBJECT-TYPE
-- @015              SYNTAX  IpAddress
-- @015              ACCESS  read-only
-- @015              STATUS  mandatory
-- @015              DESCRIPTION "The IP address to which this entry's addressing
-- @015                          information pertains. This IP address must always
-- @015                          be a unicast IP address and it should never be a
-- @015                          Class D or E IP address."
-- @015              ::= { mpIpAddrEntry 1 }

-- @015       mpIpAdEntIfIndex OBJECT-TYPE
-- @015              SYNTAX  INTEGER
-- @015              ACCESS  read-only
-- @015              STATUS  mandatory
-- @015              DESCRIPTION "The index value which uniquely identifies the
-- @015                          interface to which this entry is applicable.  The
-- @015                          interface referred by a particular value of this
-- @015                          index is the same interface as identified by the
-- @015                          same value of ifIndex."
-- @015              ::= { mpIpAddrEntry 2 }

-- @015       mpIpAdEntNetMask OBJECT-TYPE
-- @015              SYNTAX  IpAddress
-- @015              ACCESS  read-write
-- @015              STATUS  mandatory
-- @015              DESCRIPTION "The subnet mask associated with the IP address of
-- @015                          this entry.  The value of this object is an IP
-- @015                          address with the network part bits set to all 1's
-- @015                          and all the hosts part bits set to all 0's."
-- @015              ::= { mpIpAddrEntry 3 }

-- @015       mpIpAdEntBcastAddr OBJECT-TYPE
-- @015              SYNTAX  INTEGER
-- @015              ACCESS  read-write
-- @015              STATUS  mandatory
-- @015              DESCRIPTION "The value of this object is the broadcast IP
-- @015                          address for this entry. The broadcast IP address
-- @015                          is the the IP address with the host part bits
-- @015                          set to all 1's or all 0's."
-- @015              ::= { mpIpAddrEntry 4 }

-- @015       mpIpAdEntStatus OBJECT-TYPE
-- @015              SYNTAX  INTEGER {
-- @015                              valid(1),
-- @015                              invalid(2)
-- @015                              }
-- @015              ACCESS  read-write
-- @015              STATUS  mandatory
-- @015              DESCRIPTION "When an entry is created it autmatically becomes
-- @015                          valid(1). When this object is set to invalid(2)
-- @015                          then this entry will be deleted."
-- @015              ::= { mpIpAddrEntry 5 }

-- @015       mpIpAdEntEncapType OBJECT-TYPE
-- @015              SYNTAX  INTEGER {
-- @015                              none(1),
-- @015                              dix(2),
-- @015                              snap(3)
-- @015                              }
-- @015              ACCESS  read-write
-- @015              STATUS  mandatory
-- @015              DESCRIPTION "This object refers to the encapsulation type
-- @015                          for the interface of this entry. For VLAN
-- @015                          interfaces the encapsulation type can only be
-- @015                          set to dix(2) or snap(3). For LIS interfaces
-- @015                          the encapsulation type can only be set to
-- @015                          none(1)."

-- @015              ::= { mpIpAddrEntry 6 }

-- @015       mpIpAdEntForwarding OBJECT-TYPE
-- @015              SYNTAX  INTEGER {
-- @015                              forwarding(1),
-- @015                              not-forwarding(2)
-- @015                              }
-- @015              ACCESS  read-write
-- @015              STATUS  mandatory
-- @015              DESCRIPTION "This object indicates operation for data gram.
-- @015                          to forwarding(1). When this interface is IP host,
-- @015                          this object is set to not-forwarding(2)."
-- @015              ::= { mpIpAddrEntry 7 }

-- @008       mpIpAdEntInOffsetIface OBJECT-TYPE
-- @008              SYNTAX  INTEGER (0..15)
-- @008              ACCESS  read-write
-- @008              STATUS  mandatory
-- @008              DESCRIPTION "The value of this object is offset which is
-- @008                            added to RIP receiving data. The range of value
-- @008                            is from 0 to 15. The dafault value is 0"
-- @008              ::= { mpIpAddrEntry 8 }

-- @008       mpIpAdEntOutOffsetIface OBJECT-TYPE
-- @008              SYNTAX  INTEGER (0..15)
-- @008              ACCESS  read-write
-- @008              STATUS  mandatory
-- @008              DESCRIPTION "The value of this object is offset which is
-- @008                          added to RIP receiving data. The range of value
-- @008                          is from 0 to 15. The dafault value is 0"
-- @008              ::= { mpIpAddrEntry 9 }

-- @008 add from
-- @015       mpIpAdEntArpTimeOut OBJECT-TYPE
-- @015              SYNTAX  INTEGER (0..2147483647)
-- @015              ACCESS  read-write
-- @015              STATUS  mandatory
-- @015              DESCRIPTION "Effective time of the Dynamic IP ARP table
-- @015                          (ipNetToMediaTable). The value 0 means infinity."
-- @015              ::= { mpIpAddrEntry 10 }

-- @015       mpIpAdEntIcmpRedirectStatus OBJECT-TYPE
-- @015              SYNTAX  INTEGER {
-- @015                              enabled(1),
-- @015                              disabled(2)
-- @015                              }
-- @015              ACCESS  read-write
-- @015              STATUS  mandatory
-- @015              DESCRIPTION "This object indicates whether an ICMP redirect
-- @015                          message is transmitted to this Interface."
-- @015              ::= { mpIpAddrEntry 11 }
-- @008 add end

 
          -- the IP routing table

-- @008       mpIpRouteTable OBJECT-TYPE
-- @008              SYNTAX  SEQUENCE OF MpIpRouteEntry
-- @008              ACCESS  not-accessible
-- @008              STATUS  mandatory
-- @008              DESCRIPTION "This is the table type object of priprity data of
-- @008                          IP routing information."                          
-- @008              ::= { mpIp 2 }

-- @008       mpIpRouteEntry OBJECT-TYPE
-- @008              SYNTAX  MpIpRouteEntry
-- @008              ACCESS  not-accessible
-- @008              STATUS  mandatory
-- @008              DESCRIPTION "This is the table entry of mpIpRouteTable."
-- @008              INDEX  { mpIpRouteDest }
-- @008              ::= { mpIpRouteTable 1 }

-- @008       MpIpRouteEntry ::=
-- @008              SEQUENCE {
-- @008                  mpIpRouteDest
-- @008                      IpAddress,
-- @008                  mpIpRouteEntPriority
-- @008                      INTEGER
-- @008              }

-- @008       mpIpRouteDest OBJECT-TYPE
-- @008              SYNTAX  IpAddress
-- @008              ACCESS  read-only
-- @008              STATUS  mandatory
-- @008              DESCRIPTION "This object identifies the destination IP address
-- @008                          of the entry."                                    
-- @008              ::= { mpIpRouteEntry 1 }

-- @008       mpIpRouteEntPriority OBJECT-TYPE
-- @008              SYNTAX  INTEGER {
-- @008                              other(1),
-- @008                              static(2),
-- @008                              float(3)
-- @008                              }
-- @008              ACCESS  read-write
-- @008              STATUS  mandatory
-- @008              DESCRIPTION "This object specifies the priority corresponding
-- @008                          to this destination IP address. In case of static
-- @008                          registration, the value '1' is set to this object.
-- @008                          In case of floating condition, the value '2' is  
-- @008                          set to this object."                             
-- @008              ::= { mpIpRouteEntry 2 }


       -- IP Filter Exclude table

      mpIpFilterExcludeTable OBJECT-TYPE
      	      SYNTAX SEQUENCE OF MpIpFilterExcludeEntry
      	      ACCESS not-accessible
      	      STATUS mandatory
              DESCRIPTION "This is the table type object of IP address 
                          excluding filter condition. Table of Exclude 
                          IP Filter."
      	      ::= { mpIp 3 }

      mpIpFilterExcludeEntry OBJECT-TYPE
      	      SYNTAX MpIpFilterExcludeEntry
      	      ACCESS not-accessible
      	      STATUS mandatory
              DESCRIPTION "This is the table entry of 
                          mpIpFilterExcludeTable. Exclude IP Filter fields."
      	      INDEX { mpIpFilterExEntIndex }
      	      ::= { mpIpFilterExcludeTable 1 }

      MpIpFilterExcludeEntry ::=
      	      SEQUENCE {
                        mpIpFilterExEntIndex
                                     INTEGER,
                        mpIpFilterExEntInIfIndex
                                     INTEGER,
                        mpIpFilterExEntOutIfIndex
                                     INTEGER,
                        mpIpFilterExEntSrcIpAddr
                                     IpAddress,
                        mpIpFilterExEntSrcAddrMask
                                     IpAddress,
                        mpIpFilterExEntDestIpAddr
                                     IpAddress,
                        mpIpFilterExEntDestAddrMask
                                     IpAddress,
                        mpIpFilterExEntIpOptions
                                     INTEGER,
                        mpIpFilterExEntIpProcNumber
                                     INTEGER,
                        mpIpFilterExEntSrcPort
                                     INTEGER,
                        mpIpFilterExEntDestPort
                                     INTEGER,
                        mpIpFilterExEntTcpAckOffSegment
                                     INTEGER,
                        mpIpFilterExEntIcmpSend
                                     INTEGER,
                        mpIpFilterExEntEventLogging
                                     INTEGER,
                        mpIpFilterExEntStatus
                                     RowStatus
                        }

      mpIpFilterExEntIndex OBJECT-TYPE
              SYNTAX  INTEGER
              ACCESS  read-only
              STATUS  mandatory
              DESCRIPTION "This is the index to identify the IP address
                          excluding filter entry."                     
              ::= { mpIpFilterExcludeEntry 1 }

      mpIpFilterExEntInIfIndex OBJECT-TYPE
              SYNTAX  INTEGER
              ACCESS  read-write
              STATUS  mandatory
              DESCRIPTION "This object specifies the input interface number
                          to which the excluding filter is applied. The    
                          value of this object is the same as IfIndex of   
                          VLAN/LIS interface."                             
              ::= { mpIpFilterExcludeEntry 2 }

      mpIpFilterExEntOutIfIndex OBJECT-TYPE
              SYNTAX  INTEGER
              ACCESS  read-write
              STATUS  mandatory
              DESCRIPTION "This object specifies the output interface number
                          to which the excluding filter is applied. The     
                          value of this object is the same as IfIndex of    
                          VLAN/LIS interface."                              
              ::= { mpIpFilterExcludeEntry 3 }

      mpIpFilterExEntSrcIpAddr OBJECT-TYPE
              SYNTAX  IpAddress
              ACCESS  read-write
              STATUS  mandatory
              DESCRIPTION "This object specifies the source IP address to 
                          which the excluding filter is applied."        
              ::= { mpIpFilterExcludeEntry 4 }

      mpIpFilterExEntSrcAddrMask OBJECT-TYPE
              SYNTAX  IpAddress 
              ACCESS  read-write
              STATUS  mandatory
              DESCRIPTION "This object specifies the source IP address mask.
                          '1' bit is set corresponding to the IP address    
                          part which is to be ignored."                     
              ::= { mpIpFilterExcludeEntry 5 }

      mpIpFilterExEntDestIpAddr OBJECT-TYPE
              SYNTAX  IpAddress
              ACCESS  read-write
              STATUS  mandatory
              DESCRIPTION "This object specifies the destination IP address
                          to which the excluding filter is applied."       
              ::= { mpIpFilterExcludeEntry 6 }

      mpIpFilterExEntDestAddrMask OBJECT-TYPE
              SYNTAX  IpAddress 
              ACCESS  read-write
              STATUS  mandatory
              DESCRIPTION "This object specifies the destination IP address
                          mask. '1' bit is set corresponding to the IP    
                          address part which is to be ignored."           
              ::= { mpIpFilterExcludeEntry 7 }

      mpIpFilterExEntIpOptions OBJECT-TYPE
              SYNTAX  INTEGER
              ACCESS  read-write
              STATUS  mandatory
              DESCRIPTION "This object specifies the IP option to which the
                          excluding filter is applied. In case all the     
                          option is specified, the value '255' is set to   
                          this object. In case no option is specified, the 
                          value '0' is set to this object."                
              ::= { mpIpFilterExcludeEntry 8 }

      mpIpFilterExEntIpProcNumber OBJECT-TYPE
              SYNTAX  INTEGER
              ACCESS  read-write
              STATUS  mandatory
              DESCRIPTION "This obeject specifies the protocol to which the
                          excluding filter is applied. In case of ICMP, the
                          value '1' is set to this object. In case of TCP, 
                          the value '6' is set to this object. In case of  
                          UDP, the value '17' is set to this object."      
              ::= { mpIpFilterExcludeEntry 9 }


      mpIpFilterExEntSrcPort OBJECT-TYPE
              SYNTAX  INTEGER
              ACCESS  read-write
              STATUS  mandatory
              DESCRIPTION "This object specifies the receiving TCP/UDP port
                          number to which the excluding filter is applied."
              ::= { mpIpFilterExcludeEntry 10 }

      mpIpFilterExEntDestPort OBJECT-TYPE
              SYNTAX  INTEGER
              ACCESS  read-write
              STATUS  mandatory
              DESCRIPTION "This object specifies the sending TCP/UDP port  
                          number to which the excluding filter is applied."
              ::= { mpIpFilterExcludeEntry 11 }

      mpIpFilterExEntTcpAckOffSegment OBJECT-TYPE
              SYNTAX INTEGER {
                             deny(1),
                             permit(2)
                             }
              ACCESS read-write
              STATUS mandatory
              DESCRIPTION "This object specifies the pakcket handling method
                          corresponding to the ACK bit of TCP header. In    
                          case of discarding packet when ACK is off, the    
                          value '1' is set to this object. In case of not   
                          discarding packet when ACK is off, the value '2'  
                          is set to this object."                           
              ::= { mpIpFilterExcludeEntry 12 }

      mpIpFilterExEntIcmpSend OBJECT-TYPE
              SYNTAX INTEGER {
                             enabled(1),
                             disabled(2)
                             }
              ACCESS read-write
              STATUS mandatory
              DESCRIPTION "This object specifies the ICMP(error) sending   
                          method when a packet is discarded by IP filtering
                          function. In case of sending ICMP error packet,  
                          the value '1' is set to this object. In case of  
                          not sending ICMP error packet, the value '2' is  
                          set to this object."                             
              ::= { mpIpFilterExcludeEntry 13 }

      mpIpFilterExEntEventLogging OBJECT-TYPE
              SYNTAX INTEGER {
                             enabled(1),
                             disabled(2)
                             }
              ACCESS read-write
              STATUS mandatory
              DESCRIPTION "This object specifies the event handling method
                          when a packet is discarded by IP filtering      
                          function. In case of reporting it by event, the 
                          value '1' is set to this object. In case of not 
                          reporting it by event, the value '2' is set to  
                          this object."                                   
              ::= { mpIpFilterExcludeEntry 14 }

      mpIpFilterExEntStatus OBJECT-TYPE
              SYNTAX  RowStatus
              ACCESS  read-write
              STATUS  mandatory
              DESCRIPTION "This object is used to create, delete, or modify
                          this table entry."                               
              ::= { mpIpFilterExcludeEntry 15 }


      -- IP Filter Include table

      mpIpFilterIncludeTable OBJECT-TYPE
      	      SYNTAX  SEQUENCE OF MpIpFilterIncludeEntry
      	      ACCESS  not-accessible
      	      STATUS  mandatory
              DESCRIPTION "This is the table type object of IP pass-filter
                          condition data."                                
      	      ::= { mpIp 4 }

      mpIpFilterIncludeEntry OBJECT-TYPE
      	      SYNTAX  MpIpFilterIncludeEntry
      	      ACCESS  not-accessible
      	      STATUS  mandatory
              DESCRIPTION "This is the table entry of
                          mpIpFilterIncludeTable."   
      	      INDEX { mpIpFilterInEntIndex }
      	      ::= { mpIpFilterIncludeTable 1 }

      MpIpFilterIncludeEntry ::=
      	      SEQUENCE {
      		        mpIpFilterInEntIndex
                                     INTEGER,
      		        mpIpFilterInEntInIfIndex
                                     INTEGER,
      		        mpIpFilterInEntOutIfIndex
                                     INTEGER,
                        mpIpFilterInEntSrcIpAddr
                                     IpAddress,
                        mpIpFilterInEntSrcAddrMask
                                     IpAddress,
                        mpIpFilterInEntDestIpAddr
                                     IpAddress,
                        mpIpFilterInEntDestAddrMask
                                     IpAddress,
                        mpIpFilterInEntIpOptions
                                     INTEGER,
                        mpIpFilterInEntIpProcNumber
                                     INTEGER,
                        mpIpFilterInEntSrcPort
                                     INTEGER,
                        mpIpFilterInEntDestPort
                                     INTEGER,
                        mpIpFilterInEntTcpAckOffSegment
                                     INTEGER,
                        mpIpFilterInEntLifeTime
                                     INTEGER,
                        mpIpFilterInEntStatus
                                     RowStatus
      			}

      mpIpFilterInEntIndex OBJECT-TYPE
              SYNTAX  INTEGER
              ACCESS  read-only
              STATUS  mandatory
              DESCRIPTION "This is the index to identify the IP pass-filter
                          condition table entry."                          
              ::= { mpIpFilterIncludeEntry 1 }

      mpIpFilterInEntInIfIndex OBJECT-TYPE
              SYNTAX  INTEGER
              ACCESS  read-write
              STATUS  mandatory
              DESCRIPTION "This object specifies the input interface to   
                          which the IP pass-filter is applied. The value  
                          of this index is the same as IfIndex of VLAN/LIS
                          interface."                                     
              ::= { mpIpFilterIncludeEntry 2 }

      mpIpFilterInEntOutIfIndex OBJECT-TYPE
              SYNTAX  INTEGER
              ACCESS  read-write
              STATUS  mandatory
              DESCRIPTION "This object specifies the output interface to   
                          which the IP pass-filter is applied. The value of
                          this index is the same as IfIndex of VLAN/LIS    
                          interface."                                      
              ::= { mpIpFilterIncludeEntry 3 }

      mpIpFilterInEntSrcIpAddr OBJECT-TYPE
              SYNTAX  IpAddress
              ACCESS  read-write
              STATUS  mandatory
              DESCRIPTION "This object specifies the source IP address to
                          which the IP pass-filter is applied."          

              ::= { mpIpFilterIncludeEntry 4 }

      mpIpFilterInEntSrcAddrMask OBJECT-TYPE
              SYNTAX  IpAddress 
              ACCESS  read-write
              STATUS  mandatory
              DESCRIPTION "This object specified the source IP address mask. 
                          '1' bit is set corresponding to the IP address    
                          part which is to be ignored."                     
              ::= { mpIpFilterIncludeEntry 5 }

      mpIpFilterInEntDestIpAddr OBJECT-TYPE
              SYNTAX  IpAddress
              ACCESS  read-write
              STATUS  mandatory
              DESCRIPTION "This object specifies the destination IP address
                          to which the IP pass-filter is applied."         
              ::= { mpIpFilterIncludeEntry 6 }

      mpIpFilterInEntDestAddrMask OBJECT-TYPE
              SYNTAX  IpAddress 
              ACCESS  read-write
              STATUS  mandatory
              DESCRIPTION "This object specified the destination IP address
                          mask. '1' bit is set corresponding to the IP     
                          address part which is to be ignored."            
              ::= { mpIpFilterIncludeEntry 7 }

      mpIpFilterInEntIpOptions OBJECT-TYPE
              SYNTAX  INTEGER
              ACCESS  read-write
              STATUS  mandatory
              DESCRIPTION "This object specifies the IP option to which the
                          IP pass-filter is applied. In case all the option
                          is specified, the value '255' is set to this     
                          object. In case no option is specified, the value
                          '0' is set to this object."                      
              ::= { mpIpFilterIncludeEntry 8 }

      mpIpFilterInEntIpProcNumber OBJECT-TYPE
              SYNTAX  INTEGER
              ACCESS  read-write
              STATUS  mandatory
              DESCRIPTION "This obeject specifies the protocol to which the 
                          IP pass-filter is applied.                        
                          In case of ICMP, the value '1' is set to this     
                          object. In case of TCP, the value '6' is set to   
                          this object. In case of UDP, the value '17' is set
                          to this object."                                  
              ::= { mpIpFilterIncludeEntry 9 }


      mpIpFilterInEntSrcPort OBJECT-TYPE
              SYNTAX  INTEGER
              ACCESS  read-write
              STATUS  mandatory
              DESCRIPTION "This object specifies the receiving TCP/UDP port
                          number to which the IP pass-filter is applied."  
              ::= { mpIpFilterIncludeEntry 10 }

      mpIpFilterInEntDestPort OBJECT-TYPE
              SYNTAX  INTEGER
              ACCESS  read-write
              STATUS  mandatory
              DESCRIPTION "This object specifies the sending TCP/UDP port
                          number to which the IP pass-filter is applied."
              ::= { mpIpFilterIncludeEntry 11 }

      mpIpFilterInEntTcpAckOffSegment OBJECT-TYPE
              SYNTAX INTEGER {
                             deny(1),
                             permit(2)
                             }
              ACCESS read-write
              STATUS mandatory
              DESCRIPTION "This object specifies the pakcket handling method
                          corresponding to the ACK bit of TCP header. In    
                          case of discarding packet when ACK is off, the    
                          value '1' is set to this object. In case of not   
                          discarding packet when ACK is off, the value '2'  
                          is set to this object."                           
              ::= { mpIpFilterIncludeEntry 12 }

      mpIpFilterInEntLifeTime OBJECT-TYPE
              SYNTAX  INTEGER
              ACCESS  read-write
              STATUS  mandatory
              DESCRIPTION "This object specifies the valid time period of   
                          this IP pass-filter condition. When the valid time
                          period expired, this entry is deleted             
                          automatically. In case of setting the value '0' to
                          this object, this IP pass-filter condition lasts  
                          until it is deleted by operator command."         
              ::= { mpIpFilterIncludeEntry 13 }

      mpIpFilterInEntStatus OBJECT-TYPE
              SYNTAX  RowStatus
              ACCESS  read-write
              STATUS  mandatory
              DESCRIPTION "This object is used to create, delete, or modify
                          this table entry."                               
              ::= { mpIpFilterIncludeEntry 14 }


      -- IP Filter Statistics

      mpIpInFilterDiscards OBJECT-TYPE
              SYNTAX  Counter
              ACCESS  read-only
              STATUS  mandatory
              DESCRIPTION "This object is the counter of total number of the
                          receiving packets discarded by this IP filter." 
              ::= { mpIp 5 }

      mpIpOutFilterDiscards OBJECT-TYPE
              SYNTAX  Counter
              ACCESS  read-only
              STATUS  mandatory
              DESCRIPTION "This object is the counter of total number of the
                          receiving packets discarded by this IP filter."    
              ::= { mpIp 6 }

-- @008 add from
      -- IP Static Route table

      mpIpStaticRouteTable OBJECT-TYPE
              SYNTAX  SEQUENCE OF MpIpStaticRouteEntry
              ACCESS  not-accessible
              STATUS  mandatory
              DESCRIPTION "The table of static route."
              ::= { mpIp 7 }

      mpIpStaticRouteEntry OBJECT-TYPE
              SYNTAX  MpIpStaticRouteEntry
              ACCESS  not-accessible
              STATUS  mandatory
              DESCRIPTION "A entry of static route."
              INDEX { mpIpStaticRouteDest, mpIpStaticRouteMask,
                      mpIpStaticRouteNextHop }
              ::= { mpIpStaticRouteTable 1 }

       MpIpStaticRouteEntry ::=
              SEQUENCE {
                  mpIpStaticRouteDest
                      IpAddress, 
                  mpIpStaticRouteMask
                      IpAddress,
                  mpIpStaticRouteNextHop
                      IpAddress,
                  mpIpStaticRouteIfIndex
                      INTEGER,
                  mpIpStaticRouteType
                      INTEGER,
                  mpIpStaticRoutePriority
                      INTEGER,
                  mpIpStaticRouteTag
                      INTEGER,
                  mpIpStaticRouteStatus 
                      INTEGER
              }

      mpIpStaticRouteDest OBJECT-TYPE
              SYNTAX  IpAddress 
              ACCESS  read-only
              STATUS  mandatory
              DESCRIPTION "This object specifies destination IP Address of 
                          static route."
              ::= { mpIpStaticRouteEntry 1 }

      mpIpStaticRouteMask OBJECT-TYPE
              SYNTAX  IpAddress
              ACCESS  read-only
              STATUS  mandatory
              DESCRIPTION "This object specifies network mask of static route."
              ::= { mpIpStaticRouteEntry 2 }

      mpIpStaticRouteNextHop OBJECT-TYPE
              SYNTAX  IpAddress
              ACCESS  read-only
              STATUS  mandatory
              DESCRIPTION "This object specifies next-hop IP Address of 
                          static route. The value 0 is specified when route
                          type is 'other','reject' or' local'."
              ::= { mpIpStaticRouteEntry 3 }

      mpIpStaticRouteIfIndex OBJECT-TYPE
              SYNTAX  INTEGER
              ACCESS  read-write
              STATUS  mandatory
              DESCRIPTION "This object specifies the outgoing ifIndex."
              ::= { mpIpStaticRouteEntry 4 }

      mpIpStaticRouteType OBJECT-TYPE
              SYNTAX  INTEGER {
                              other(1),
                              reject(2),
                              local(3),
                              remote(4)
                              }
              ACCESS  read-write
              STATUS  mandatory
              DESCRIPTION "This object specifies the route type. The route 
                          type other(1) is not reflected to IP routing table.
                          The route type reject(2) is used to discard 
                          corresponding IP packet."
              ::= { mpIpStaticRouteEntry 5 }

      mpIpStaticRoutePriority OBJECT-TYPE 
              SYNTAX  INTEGER (1..255)
              ACCESS  read-write
              STATUS  mandatory
              DESCRIPTION "This object specifies route priority. The
                          entry which route priority is the smallest in
                          usable next-hop is reflected to IP routing table 
                          when route priority is different in every next-hop 
                          at the case of multi-path."     
              ::= { mpIpStaticRouteEntry 6 }

      mpIpStaticRouteTag OBJECT-TYPE
              SYNTAX  INTEGER 
              ACCESS  read-write
              STATUS  mandatory
              DESCRIPTION "This object specifies route tag. In case route type
                           is 'reject', setting to this object is prohibited."
              ::= { mpIpStaticRouteEntry 7 }

      mpIpStaticRouteStatus OBJECT-TYPE
              SYNTAX  INTEGER {
                              valid(1),
                              invalid(2)
                              }
              ACCESS  read-write
              STATUS  mandatory
              DESCRIPTION "This object specifies status of this entry.
                          When entry is deleted, invalid(2) is set."
              ::= { mpIpStaticRouteEntry 8 }

      -- IP Route Priority table

      mpIpRoutePriorityTable OBJECT-TYPE
              SYNTAX  SEQUENCE OF MpIpRoutePriorityEntry
              ACCESS  not-accessible
              STATUS  mandatory
              DESCRIPTION "The route priority table of the routing protocol
                          unit. The value of this table is the default value 
                          of each routing protocol of this system. It is used
                          for tie-break when the requirement of the addition
                          of routing table for the same network from plural
                          routing protocols occur and route priority is the 
                          same."
              ::= { mpIp 8 }

      mpIpRoutePriorityEntry OBJECT-TYPE
              SYNTAX  MpIpRoutePriorityEntry
              ACCESS  not-accessible
              STATUS  mandatory
              DESCRIPTION "A route priority entry of the routing protocol."
              INDEX { mpIpRoutePriorityProtocol }
              ::= { mpIpRoutePriorityTable 1 }

      MpIpRoutePriorityEntry ::=
              SEQUENCE {
                  mpIpRoutePriorityProtocol
                       INTEGER,
                  mpIpRoutePriorityValue
                       INTEGER
              }

      mpIpRoutePriorityProtocol OBJECT-TYPE
              SYNTAX  INTEGER {
                              other(1),
                              local(2),
                              static(3),
                              ospfIntraArea(4),
                              ospfInterArea(5),
                              ospfExternal(6),
                              rip(7)
                              }
              ACCESS  read-only
              STATUS  mandatory
              DESCRIPTION "This object specifies the protocol of IP routing
                           table."
              ::= { mpIpRoutePriorityEntry 1 }

      mpIpRoutePriorityValue OBJECT-TYPE
              SYNTAX   INTEGER (0..255)
              ACCESS  read-only
              STATUS  mandatory
              DESCRIPTION "This object specifies route priority value."
              ::= { mpIpRoutePriorityEntry 2 }

      -- IP Import List table

      mpIpImportListTable OBJECT-TYPE
              SYNTAX  SEQUENCE OF MpIpImportListEntry
              ACCESS  not-accessible
              STATUS  mandatory
              DESCRIPTION "The table which is used to distribute route 
                          information to different routing protocol.
                          It defines condition of routing table to be 
                          distributed and value to be used at 
                          distributing."
              ::= { mpIp 9 }

      mpIpImportListEntry OBJECT-TYPE
              SYNTAX  MpIpImportListEntry
              ACCESS  not-accessible
              STATUS  mandatory
              DESCRIPTION "The entry which is used to distribute route 
                          information to different routing protocol."
              INDEX { mpIpImportListNumber }
              ::= { mpIpImportListTable 1 }

      MpIpImportListEntry ::=
              SEQUENCE {
                  mpIpImportListNumber
                       INTEGER,
                  mpIpImportListAction
                       INTEGER,
                  mpIpImportListConIfIndex
                       INTEGER,
                  mpIpImportListConNetAddr
                       IpAddress,
                  mpIpImportListConNetMask
                       IpAddress,
                  mpIpImportListConNetStatus
                       INTEGER,
                  mpIpImportListConRangeStatus
                       INTEGER,
                  mpIpImportListConNextHop
                       IpAddress,
                  mpIpImportListConSource
                       IpAddress,
                  mpIpImportListConSourceStatus
                       INTEGER,
                  mpIpImportListConMetric
                       INTEGER,
                  mpIpImportListConRouteType
                       INTEGER,
                  mpIpImportListConTag
                       INTEGER,
                  mpIpImportListConTagStatus
                       INTEGER,
                  mpIpImportListConPId
                       INTEGER,
                  mpIpImportListSetNetAddr
                       IpAddress,
                  mpIpImportListSetNetMask
                       IpAddress,
                  mpIpImportListSetNetStatus
                       INTEGER,
                  mpIpImportListSetMetric
                       INTEGER,
                  mpIpImportListSetNextHop
                       IpAddress,
                  mpIpImportListSetTag
                       INTEGER,
                  mpIpImportListSetRouteType
                       INTEGER,
                  mpIpImportListTableStatus
                       INTEGER
              }

      mpIpImportListNumber OBJECT-TYPE
              SYNTAX  INTEGER
              ACCESS  read-only
              STATUS  mandatory
              DESCRIPTION "This object specifies import-list number."
              ::= { mpIpImportListEntry 1 }

      mpIpImportListAction OBJECT-TYPE
              SYNTAX  INTEGER {
                              import(1),
                              deny(2)
                              }
              ACCESS  read-write
              STATUS  mandatory
              DESCRIPTION "This object specifies whether routing table
                          corresponding to the condition is distributed 
                          or ignored."
              ::= { mpIpImportListEntry 2 }

      mpIpImportListConIfIndex OBJECT-TYPE
              SYNTAX  INTEGER
              ACCESS  read-write
              STATUS  mandatory
              DESCRIPTION "This object specifies a condition by the outgoing
                          interface. The value 0 means it is outside of the
                          condition decision."
              ::= { mpIpImportListEntry 3 }

      mpIpImportListConNetAddr OBJECT-TYPE
              SYNTAX  IpAddress
              ACCESS  read-write
              STATUS  mandatory
              DESCRIPTION "This object specifies the network address. It is 
                          shared with the network condition and the range 
                          condition. "
              ::= { mpIpImportListEntry 4 }

      mpIpImportListConNetMask OBJECT-TYPE
              SYNTAX  IpAddress
              ACCESS  read-write
              STATUS  mandatory
              DESCRIPTION "This object specifies the network mask. It is shared
                          with the network condition and the range condition."
              ::= { mpIpImportListEntry 5 }

      mpIpImportListConNetStatus OBJECT-TYPE
              SYNTAX  INTEGER {
                              valid(1),
                              invalid(2)
                              }
              ACCESS  read-write
              STATUS  mandatory
              DESCRIPTION "This object specifies the status of condition about 
                          network address."
              ::= { mpIpImportListEntry 6 }

      mpIpImportListConRangeStatus OBJECT-TYPE
              SYNTAX  INTEGER {
                              valid(1),
                              invalid(2)
                              }
              ACCESS  read-write
              STATUS  mandatory
              DESCRIPTION "This object specifies the status of condition about 
                          network address range."
              ::= { mpIpImportListEntry 7 }

      mpIpImportListConNextHop OBJECT-TYPE
              SYNTAX  IpAddress
              ACCESS  read-write
              STATUS  mandatory
              DESCRIPTION "This object specifies the condition about next-hop. 
                          The value 0 means it is outside of the condition 
                          decision."
              ::= { mpIpImportListEntry 8 }

      mpIpImportListConSource OBJECT-TYPE
              SYNTAX  IpAddress
              ACCESS  read-write
              STATUS  mandatory
              DESCRIPTION "This object specifies IP address or router ID of 
                          advertising router."
              ::= { mpIpImportListEntry 9 }

      mpIpImportListConSourceStatus OBJECT-TYPE
              SYNTAX  INTEGER {
                              valid(1),
                              invalid(2)
                              }
              ACCESS  read-write
              STATUS  mandatory
              DESCRIPTION "This object specifies the status of condition 
                          about advertising router."
              ::= { mpIpImportListEntry 10 }

      mpIpImportListConMetric OBJECT-TYPE
              SYNTAX  INTEGER
              ACCESS  read-write
              STATUS  mandatory
              DESCRIPTION "This object specifies the condition about metric. 
                          The value 0 means it is outside of the condition 
                          decision."
              ::= { mpIpImportListEntry 11 }

      mpIpImportListConRouteType OBJECT-TYPE
              SYNTAX  INTEGER {
                              other(1),
                              internal(2),
                              intraArea(3),
                              interArea(4),
                              external(5),
                              type1External(6),
                              type2External(7)
                              }
              ACCESS  read-write
              STATUS  mandatory
              DESCRIPTION "This object specifies the condition about route
                          type. The value 0 means it is outside of the 
                          condition decision."
              ::= { mpIpImportListEntry 12 }

      mpIpImportListConTag OBJECT-TYPE
              SYNTAX  INTEGER
              ACCESS  read-write
              STATUS  mandatory
              DESCRIPTION "This object specifies route tag."
              ::= { mpIpImportListEntry 13 }

      mpIpImportListConTagStatus OBJECT-TYPE
              SYNTAX  INTEGER {
                              valid(1),
                              invalid(2)
                              }
              ACCESS  read-write
              STATUS  mandatory
              DESCRIPTION "This object specifies the status of condition 
                          about route tag."
              ::= { mpIpImportListEntry 14 }

      mpIpImportListConPId OBJECT-TYPE
              SYNTAX  INTEGER(0..255)
              ACCESS  read-write
              STATUS  mandatory
              DESCRIPTION "This object specifies the condition about protocol
                          ID. The value 0 means it is outside of the condition
                          decision."
              ::= { mpIpImportListEntry 15 }

        mpIpImportListSetNetAddr OBJECT-TYPE
              SYNTAX  IpAddress
              ACCESS  read-write
              STATUS  mandatory
              DESCRIPTION "This object specifies the network address which is
                          applied when routing table corresponding to the 
                          condition is distributed."
              ::= { mpIpImportListEntry 16 }

        mpIpImportListSetNetMask OBJECT-TYPE
              SYNTAX  IpAddress
              ACCESS  read-write
              STATUS  mandatory
              DESCRIPTION "This object specifies the mask address which is
                          applied when routing table corresponding to the 
                          condition is distributed."
              ::= { mpIpImportListEntry 17 }

        mpIpImportListSetNetStatus OBJECT-TYPE
              SYNTAX  INTEGER {
                              valid(1),
                              invalid(2)
                              }
              ACCESS  read-write
              STATUS  mandatory
              DESCRIPTION "This object specifies the status of network 
                          address which is applied when routing table 
                          corresponding to the condition is distributed."
              ::= { mpIpImportListEntry 18 }

        mpIpImportListSetMetric OBJECT-TYPE
              SYNTAX   INTEGER
              ACCESS  read-write
              STATUS  mandatory
              DESCRIPTION "This object specifies the metric value which is 
                          applied when routing table corresponding to the 
                          condition is distributed."
              ::= { mpIpImportListEntry 19 }

        mpIpImportListSetNextHop OBJECT-TYPE
              SYNTAX  IpAddress
              ACCESS  read-write
              STATUS  mandatory
              DESCRIPTION "This object specifies the next-hop IP address
                          which is applied when routing table corresponding
                          to the condition is distributed."
              ::= { mpIpImportListEntry 20 }

        mpIpImportListSetTag OBJECT-TYPE
              SYNTAX  INTEGER 
              ACCESS  read-write
              STATUS  mandatory
              DESCRIPTION "This object specifies the route tag which is applied
                          when routing table corresponding to the condition is 
                          distributed."
              ::= { mpIpImportListEntry 21 }

        mpIpImportListSetRouteType OBJECT-TYPE
              SYNTAX  INTEGER {
                              type1External(1),
                              type2External(2)
                              }
              ACCESS  read-write
              STATUS  mandatory
              DESCRIPTION "This object specifies the external route type which 
                          is applied when routing table corresponding to the 
                          condition is distributed to OSPF."
              ::= { mpIpImportListEntry 22 }

        mpIpImportListTableStatus OBJECT-TYPE
              SYNTAX  INTEGER {
                              valid(1),
                              invalid(2)
                              }
              ACCESS  read-write
              STATUS  mandatory
              DESCRIPTION "This object specifies status of this entry.
                          When entry is deleted, invalid(2) is set."
              ::= { mpIpImportListEntry 23 }
-- @008 add end


-- @015 add from

       -- the VPN table

       mpIpVpnTable OBJECT-TYPE
              SYNTAX  SEQUENCE OF MpIpVpnEntry
              ACCESS  not-accessible
              STATUS  mandatory
              DESCRIPTION "The table of addressing information relevant to
                          this entity's ifIndex."
              ::= { mpIp 10 }

       mpIpVpnEntry OBJECT-TYPE
              SYNTAX  MpIpVpnEntry
              ACCESS  not-accessible
              STATUS  mandatory
              DESCRIPTION "The addressing information for one of this
                          entity's ifIndex."
              INDEX { mpIpVpnIfIndex }
              ::= { mpIpVpnTable 1 }

       MpIpVpnEntry ::=
              SEQUENCE {
                  mpIpVpnIfIndex
                      INTEGER,
                  mpIpVpnId
                      INTEGER
              }

       mpIpVpnIfIndex OBJECT-TYPE
              SYNTAX  INTEGER
              ACCESS  read-only
              STATUS  mandatory
              DESCRIPTION "The index value which uniquely identifies the
                          interface to which this entry is applicable.  The
                          interface referred by a particular value of this
                          index is the same interface as identified by the
                          same value of ifIndex."
              ::= { mpIpVpnEntry 1 }

       mpIpVpnId OBJECT-TYPE
              SYNTAX  INTEGER
              ACCESS  read-write
              STATUS  mandatory
              DESCRIPTION "This is the index to identify VPN the entry.
                          The value of this index must be assigned uniquely,
                          witrhin the range of 1 - 65535."
              ::= { mpIpVpnEntry 2 }


       -- the VPN IP group table

       mpIpVpnIpGroupTable OBJECT-TYPE
              SYNTAX  SEQUENCE OF MpIpVpnIpGroupEntry
              ACCESS  not-accessible
              STATUS  mandatory
              DESCRIPTION "The table of IP group information relevant to
                          this entity's VPNID."
              ::= { mpIp 11 }

       mpIpVpnIpGroupEntry OBJECT-TYPE
              SYNTAX  MpIpVpnIpGroupEntry
              ACCESS  not-accessible
              STATUS  mandatory
              DESCRIPTION "The IP group information for one of this
                          entity's VPNID."
              INDEX { mpIpVpnIpGroupVpnId }
              ::= { mpIpVpnIpGroupTable 1 }

       MpIpVpnIpGroupEntry ::=
              SEQUENCE {
                  mpIpVpnIpGroupVpnId
                      INTEGER,
                  mpIpVpnIpForwarding
                      INTEGER,
                  mpIpVpnIpDefaultTTL
                      INTEGER,
                  mpIpVpnIpInReceives
                      Counter,
                  mpIpVpnIpInHdrErrors
                      Counter,
                  mpIpVpnIpInAddrErrors
                      Counter,
                  mpIpVpnIpForwDatagrams
                      Counter,
                  mpIpVpnIpInUnknownProtos
                      Counter,
                  mpIpVpnIpInDiscards
                      Counter,
                  mpIpVpnIpInDelivers
                      Counter,
                  mpIpVpnIpOutRequests
                      Counter,
                  mpIpVpnIpOutDiscards
                      Counter,
                  mpIpVpnIpOutNoRoutes
                      Counter,
                  mpIpVpnIpReasmTimeout
                      Counter,
                  mpIpVpnIpReasmReqds
                      Counter,
                  mpIpVpnIpReasmOKs
                      Counter,
                  mpIpVpnIpReasmFails
                      Counter,
                  mpIpVpnIpFragOKs
                      Counter,
                  mpIpVpnIpFragFails
                      Counter,
                  mpIpVpnIpFragCreates
                      Counter,
                  mpIpVpnIpRoutingDiscards
                      Counter,
                  mpIpVpnIpInFilterDiscards
                      Counter,
                  mpIpVpnIpOutFilterDiscards
                      Counter,
                  mpIpVpnIpGroupStatus
                      INTEGER
              }

       mpIpVpnIpGroupVpnId OBJECT-TYPE
              SYNTAX  INTEGER
              ACCESS  read-only
              STATUS  mandatory
              DESCRIPTION "This is the index to identify the VPN entry.
                          The value of this index must be assigned uniquely,
                          witrhin the range of 1 - 65535."
              ::= { mpIpVpnIpGroupEntry 1 }

       mpIpVpnIpForwarding OBJECT-TYPE
              SYNTAX  INTEGER {
                          forwarding(1),    -- acting as a gateway
                          not-forwarding(2) -- NOT acting as a gateway
                      }
              ACCESS  read-write
              STATUS  mandatory
              DESCRIPTION
                      "The indication of whether this entity is acting
                      as an IP gateway in respect to the forwarding of
                      datagrams received by, but not addressed to, this
                      entity.  IP gateways forward datagrams.  IP hosts
                      do not (except those source-routed via the host).

                      Note that for some managed nodes, this object may
                      take on only a subset of the values possible.
                      Accordingly, it is appropriate for an agent to
                      return a `badValue' response if a management
                      station attempts to change this object to an
                      inappropriate value."
              ::= { mpIpVpnIpGroupEntry 2 }

       mpIpVpnIpDefaultTTL OBJECT-TYPE
              SYNTAX  INTEGER
              ACCESS  read-write
              STATUS  mandatory
              DESCRIPTION
                      "The default value inserted into the Time-To-Live
                      field of the IP header of datagrams originated at
                      this entity, whenever a TTL value is not supplied
                      by the transport layer protocol."
              ::= { mpIpVpnIpGroupEntry 3 }

       mpIpVpnIpInReceives OBJECT-TYPE
              SYNTAX  Counter
              ACCESS  read-only
              STATUS  mandatory
              DESCRIPTION
                      "The total number of input datagrams received from
                      interfaces, including those received in error."
              ::= { mpIpVpnIpGroupEntry 4 }

       mpIpVpnIpInHdrErrors OBJECT-TYPE
              SYNTAX  Counter
              ACCESS  read-only
              STATUS  mandatory
              DESCRIPTION
                      "The number of input datagrams discarded due to
                      errors in their IP headers, including bad
                      checksums, version number mismatch, other format
                      errors, time-to-live exceeded, errors discovered
                      in processing their IP options, etc."
              ::= { mpIpVpnIpGroupEntry 5 }

       mpIpVpnIpInAddrErrors OBJECT-TYPE
              SYNTAX  Counter
              ACCESS  read-only
              STATUS  mandatory
              DESCRIPTION
                      "The number of input datagrams discarded because
                      the IP address in their IP header's destination
                      field was not a valid address to be received at
                      this entity.  This count includes invalid
                      addresses (e.g., 0.0.0.0) and addresses of
                      unsupported Classes (e.g., Class E).  For entities
                      which are not IP Gateways and therefore do not
                      forward datagrams, this counter includes datagrams
                      discarded because the destination address was not
                      a local address."
              ::= { mpIpVpnIpGroupEntry 6 }

       mpIpVpnIpForwDatagrams OBJECT-TYPE
              SYNTAX  Counter
              ACCESS  read-only
              STATUS  mandatory
              DESCRIPTION
                      "The number of input datagrams for which this
                      entity was not their final IP destination, as a
                      result of which an attempt was made to find a
                      route to forward them to that final destination.
                      In entities which do not act as IP Gateways, this
                      counter will include only those packets which were
                      Source-Routed via this entity, and the Source-
                      Route option processing was successful."
              ::= { mpIpVpnIpGroupEntry 7 }

       mpIpVpnIpInUnknownProtos OBJECT-TYPE
              SYNTAX  Counter
              ACCESS  read-only
              STATUS  mandatory
              DESCRIPTION
                      "The number of locally-addressed datagrams
                      received successfully but discarded because of an
                      unknown or unsupported protocol."
              ::= { mpIpVpnIpGroupEntry 8 }

       mpIpVpnIpInDiscards OBJECT-TYPE
              SYNTAX  Counter
              ACCESS  read-only
              STATUS  mandatory
              DESCRIPTION
                      "The number of input IP datagrams for which no
                      problems were encountered to prevent their
                      continued processing, but which were discarded
                      (e.g., for lack of buffer space).  Note that this
                      counter does not include any datagrams discarded
                      while awaiting re-assembly."
              ::= { mpIpVpnIpGroupEntry 9 }

       mpIpVpnIpInDelivers OBJECT-TYPE
              SYNTAX  Counter
              ACCESS  read-only
              STATUS  mandatory
              DESCRIPTION
                      "The total number of input datagrams successfully
                      delivered to IP user-protocols (including ICMP)."
              ::= { mpIpVpnIpGroupEntry 10 }

       mpIpVpnIpOutRequests OBJECT-TYPE
              SYNTAX  Counter
              ACCESS  read-only
              STATUS  mandatory
              DESCRIPTION
                      "The total number of IP datagrams which local IP
                      user-protocols (including ICMP) supplied to IP in
                      requests for transmission.  Note that this counter
                      does not include any datagrams counted in
                      ipForwDatagrams."
              ::= { mpIpVpnIpGroupEntry 11 }

       mpIpVpnIpOutDiscards OBJECT-TYPE
              SYNTAX  Counter
              ACCESS  read-only
              STATUS  mandatory
              DESCRIPTION
                      "The number of output IP datagrams for which no
                      problem was encountered to prevent their
                      transmission to their destination, but which were
                      discarded (e.g., for lack of buffer space).  Note
                      that this counter would include datagrams counted
                      in ipForwDatagrams if any such packets met this
                      (discretionary) discard criterion."
              ::= { mpIpVpnIpGroupEntry 12 }

       mpIpVpnIpOutNoRoutes OBJECT-TYPE
              SYNTAX  Counter
              ACCESS  read-only
              STATUS  mandatory
              DESCRIPTION
                      "The number of IP datagrams discarded because no
                      route could be found to transmit them to their
                      destination.  Note that this counter includes any
                      packets counted in ipForwDatagrams which meet this
                      `no-route' criterion.  Note that this includes any
                      datagarms which a host cannot route because all of
                      its default gateways are down."
              ::= { mpIpVpnIpGroupEntry 13 }

       mpIpVpnIpReasmTimeout OBJECT-TYPE
              SYNTAX  INTEGER
              ACCESS  read-only
              STATUS  mandatory
              DESCRIPTION
                      "The maximum number of seconds which received
                      fragments are held while they are awaiting
                      reassembly at this entity."
              ::= { mpIpVpnIpGroupEntry 14 }

       mpIpVpnIpReasmReqds OBJECT-TYPE
              SYNTAX  Counter
              ACCESS  read-only
              STATUS  mandatory
              DESCRIPTION
                      "The number of IP fragments received which needed
                      to be reassembled at this entity."
              ::= { mpIpVpnIpGroupEntry 15 }

       mpIpVpnIpReasmOKs OBJECT-TYPE
              SYNTAX  Counter
              ACCESS  read-only
              STATUS  mandatory
              DESCRIPTION
                      "The number of IP datagrams successfully re-
                      assembled."
              ::= { mpIpVpnIpGroupEntry 16 }

       mpIpVpnIpReasmFails OBJECT-TYPE
              SYNTAX  Counter
              ACCESS  read-only
              STATUS  mandatory
              DESCRIPTION
                      "The number of failures detected by the IP re-
                      assembly algorithm (for whatever reason: timed
                      out, errors, etc).  Note that this is not
                      necessarily a count of discarded IP fragments
                      since some algorithms (notably the algorithm in
                      RFC 815) can lose track of the number of fragments
                      by combining them as they are received."
              ::= { mpIpVpnIpGroupEntry 17 }

       mpIpVpnIpFragOKs OBJECT-TYPE
              SYNTAX  Counter
              ACCESS  read-only
              STATUS  mandatory
              DESCRIPTION
                      "The number of IP datagrams that have been
                      successfully fragmented at this entity."
              ::= { mpIpVpnIpGroupEntry 18 }

       mpIpVpnIpFragFails OBJECT-TYPE
              SYNTAX  Counter
              ACCESS  read-only
              STATUS  mandatory
              DESCRIPTION
                      "The number of IP datagrams that have been
                      discarded because they needed to be fragmented at
                      this entity but could not be, e.g., because their
                      Don't Fragment flag was set."
              ::= { mpIpVpnIpGroupEntry 19 }

       mpIpVpnIpFragCreates OBJECT-TYPE
              SYNTAX  Counter
              ACCESS  read-only
              STATUS  mandatory
              DESCRIPTION
                      "The number of IP datagram fragments that have
                      been generated as a result of fragmentation at
                      this entity."
              ::= { mpIpVpnIpGroupEntry 20 }

       mpIpVpnIpRoutingDiscards OBJECT-TYPE
              SYNTAX  Counter
              ACCESS  read-only
              STATUS  mandatory
              DESCRIPTION
                      "The number of routing entries which were chosen
                      to be discarded even though they are valid.  One
                      possible reason for discarding such an entry could
                      be to free-up buffer space for other routing."
              ::= { mpIpVpnIpGroupEntry 21 }

       mpIpVpnIpInFilterDiscards OBJECT-TYPE
              SYNTAX  Counter
              ACCESS  read-only
              STATUS  mandatory
              DESCRIPTION "This object is the counter of total number of the
                          receiving packets discarded by this IP filter."
              ::= { mpIpVpnIpGroupEntry 22 }

       mpIpVpnIpOutFilterDiscards OBJECT-TYPE
              SYNTAX  Counter
              ACCESS  read-only
              STATUS  mandatory
              DESCRIPTION "This object is the counter of total number of the
                          receiving packets discarded by this IP filter."
              ::= { mpIpVpnIpGroupEntry 23 }

       mpIpVpnIpGroupStatus OBJECT-TYPE
              SYNTAX  INTEGER {
                              valid(1),
                              invalid(2)
                              }
              ACCESS  read-write
              STATUS  mandatory
              DESCRIPTION "When an entry is created it autmatically becomes
                          valid(1). When this object is set to invalid(2)
                          then this entry will be deleted."
              ::= { mpIpVpnIpGroupEntry 24 }


       -- the VPN IP address table

       mpIpVpnIpAddrTable OBJECT-TYPE
              SYNTAX  SEQUENCE OF MpIpVpnIpAddrEntry
              ACCESS  not-accessible
              STATUS  mandatory
              DESCRIPTION "The table of addressing information relevant to
                          this entity's VPNID & IP addresses."
              ::= { mpIp 12 }

       mpIpVpnIpAddrEntry OBJECT-TYPE
              SYNTAX  MpIpVpnIpAddrEntry
              ACCESS  not-accessible
              STATUS  mandatory
              DESCRIPTION "The addressing information for one of this
                          entity's VPNID & IP addresses."
              INDEX { mpIpVpnIpAdEntVpnId,
                      mpIpVpnIpAdEntIfIndex,
                      mpIpVpnIpAdEntAddr,
                      mpIpVpnIpAdEntNetMask }
              ::= { mpIpVpnIpAddrTable 1 }

       MpIpVpnIpAddrEntry ::=
              SEQUENCE {
                  mpIpVpnIpAdEntVpnId
                      INTEGER,
                  mpIpVpnIpAdEntIfIndex
                      INTEGER,
                  mpIpVpnIpAdEntAddr
                      IpAddress,
                  mpIpVpnIpAdEntNetMask
                      IpAddress,
                  mpIpVpnIpAdEntBcastAddr
                      INTEGER,
                  mpIpVpnIpAdEntReasmMaxSize
                      INTEGER,
                  mpIpVpnIpAdEntStatus
                      INTEGER,
                  mpIpVpnIpAdEntEncapType
                      INTEGER,
                  mpIpVpnIpAdEntForwarding
                      INTEGER,
                  mpIpVpnIpAdEntArpTimeOut
                      INTEGER,
                  mpIpVpnIpAdEntIcmpRedirectStatus
                      INTEGER,
                  mpIpVpnIpAdEntIcmpUnreachNetInStatus
                      INTEGER,
                  mpIpVpnIpAdEntIcmpUnreachNetOutStatus
                      INTEGER,
                  mpIpVpnIpAdEntIcmpUnreachHostInStatus
                      INTEGER,
                  mpIpVpnIpAdEntIcmpUnreachHostOutStatus
                      INTEGER,
                  mpIpVpnIpAdEntIcmpUnreachProtInStatus
                      INTEGER,
                  mpIpVpnIpAdEntIcmpUnreachProtOutStatus
                      INTEGER,
                  mpIpVpnIpAdEntIcmpUnreachPortInStatus
                      INTEGER,
                  mpIpVpnIpAdEntIcmpUnreachPortOutStatus
                      INTEGER,
                  mpIpVpnIpAdEntIcmpUnreachFragNeededInStatus
                      INTEGER,
                  mpIpVpnIpAdEntIcmpUnreachFragNeededOutStatus
                      INTEGER,
                  mpIpVpnIpAdEntIcmpUnreachRouteFailInStatus
                      INTEGER,
                  mpIpVpnIpAdEntIcmpUnreachRouteFailOutStatus
                      INTEGER,
                  mpIpVpnIpAdEntIcmpTtlExceedInStatus
                      INTEGER,
                  mpIpVpnIpAdEntIcmpTtlExceedOutStatus
                      INTEGER,
                  mpIpVpnIpAdEntIcmpReassemblyExceedInStatus
                      INTEGER,
                  mpIpVpnIpAdEntIcmpReassemblyExceedOutStatus
                      INTEGER,
                  mpIpVpnIpAdEntIcmpParamProbInStatus
                      INTEGER,
                  mpIpVpnIpAdEntIcmpParamProbOutStatus
                      INTEGER,
                  mpIpVpnIpAdEntProxyArpStatus
                      INTEGER,
                  mpIpVpnIpAdEntDirectedBroadcastStatus
                      INTEGER,
                  mpIpVpnIpAdEntPathThroughListNumber
                      INTEGER,
                  mpIpVpnIpAdEntExtendedStaticRouteListNumber
                      INTEGER
              }

       mpIpVpnIpAdEntVpnId OBJECT-TYPE
              SYNTAX  INTEGER
              ACCESS  read-only
              STATUS  mandatory
              DESCRIPTION "This is the index to identify the VPN entry.
                          The value of this index must be assigned uniquely,
                          witrhin the range of 1 - 65535."
              ::= { mpIpVpnIpAddrEntry 1 }

       mpIpVpnIpAdEntIfIndex OBJECT-TYPE
              SYNTAX  INTEGER
              ACCESS  read-only
              STATUS  mandatory
              DESCRIPTION "The index value which uniquely identifies the
                          interface to which this entry is applicable.  The
                          interface referred by a particular value of this
                          index is the same interface as identified by the
                          same value of ifIndex."
              ::= { mpIpVpnIpAddrEntry 2 }

       mpIpVpnIpAdEntAddr OBJECT-TYPE
              SYNTAX  IpAddress
              ACCESS  read-only
              STATUS  mandatory
              DESCRIPTION "The IP address to which this entry's addressing
                          information pertains. This IP address must always
                          be a unicast IP address and it should never be a
                          Class D or E IP address."
              ::= { mpIpVpnIpAddrEntry 3 }

       mpIpVpnIpAdEntNetMask OBJECT-TYPE
              SYNTAX  IpAddress
              ACCESS  read-write
              STATUS  mandatory
              DESCRIPTION "The subnet mask associated with the IP address of
                          this entry.  The value of this object is an IP
                          address with the network part bits set to all 1's
                          and all the hosts part bits set to all 0's."
              ::= { mpIpVpnIpAddrEntry 4 }

       mpIpVpnIpAdEntBcastAddr OBJECT-TYPE
              SYNTAX  INTEGER
              ACCESS  read-write
              STATUS  mandatory
              DESCRIPTION "The value of this object is the broadcast IP
                          address for this entry. The broadcast IP address
                          is the the IP address with the host part bits
                          set to all 1's or all 0's."
              ::= { mpIpVpnIpAddrEntry 5 }

       mpIpVpnIpAdEntReasmMaxSize OBJECT-TYPE
              SYNTAX  INTEGER (0..65535)
              ACCESS  read-only
              STATUS  mandatory
              DESCRIPTION "The size of the largest IP datagram which this
                          entity can re-assemble from incoming IP fragmented
                          datagrams received on this interface."
              ::= { mpIpVpnIpAddrEntry 6 }

       mpIpVpnIpAdEntStatus OBJECT-TYPE
              SYNTAX  INTEGER {
                              valid(1),
                              invalid(2)
                              }
              ACCESS  read-write
              STATUS  mandatory
              DESCRIPTION "When an entry is created it autmatically becomes
                          valid(1). When this object is set to invalid(2)
                          then this entry will be deleted."
              ::= { mpIpVpnIpAddrEntry 7 }

       mpIpVpnIpAdEntEncapType OBJECT-TYPE
              SYNTAX  INTEGER {
                              none(1),
                              dix(2),
                              snap(3)
                              }
              ACCESS  read-write
              STATUS  mandatory
              DESCRIPTION "This object refers to the encapsulation type
                          for the interface of this entry. For VLAN
                          interfaces the encapsulation type can only be
                          set to dix(2) or snap(3). For LIS interfaces
                          the encapsulation type can only be set to
                          none(1)."
              ::= { mpIpVpnIpAddrEntry 8 }

       mpIpVpnIpAdEntForwarding OBJECT-TYPE
              SYNTAX  INTEGER {
                              forwarding(1),
                              not-forwarding(2)
                              }
              ACCESS  read-write
              STATUS  mandatory
              DESCRIPTION "This object indicates operation for data gram.
                          to forwarding(1). When this interface is IP host,
                          this object is set to not-forwarding(2)."
              ::= { mpIpVpnIpAddrEntry 9 }

       mpIpVpnIpAdEntArpTimeOut OBJECT-TYPE
              SYNTAX  INTEGER (0..2147483647)
              ACCESS  read-write
              STATUS  mandatory
              DESCRIPTION "Effective time of the Dynamic VPN IP ARP table
                          (mpIpVpnIpNetToMediaTable). The value 0 means
                          infinity."
              ::= { mpIpVpnIpAddrEntry 10 }

       mpIpVpnIpAdEntIcmpRedirectStatus OBJECT-TYPE
              SYNTAX  INTEGER {
                              enabled(1),
                              disabled(2)
                              }
              ACCESS  read-write
              STATUS  mandatory
              DESCRIPTION "This object indicates whether an ICMP redirect
                          message is transmitted to this Interface."
              ::= { mpIpVpnIpAddrEntry 11 }

       mpIpVpnIpAdEntIcmpUnreachNetInStatus OBJECT-TYPE
              SYNTAX  INTEGER {
                              enabled(1),
                              disabled(2)
                              }
              ACCESS  read-write
              STATUS  mandatory
              DESCRIPTION "This object indicates whether an ICMP destination
                          unreachable(network unreachable in) message is
                          transmitted to this Interface."
              ::= { mpIpVpnIpAddrEntry 12 }

       mpIpVpnIpAdEntIcmpUnreachNetOutStatus OBJECT-TYPE
              SYNTAX  INTEGER {
                              enabled(1),
                              disabled(2)
                              }
              ACCESS  read-write
              STATUS  mandatory
              DESCRIPTION "This object indicates whether an ICMP destination
                          unreachable(network unreachable out) message is
                          transmitted to this Interface."
              ::= { mpIpVpnIpAddrEntry 13 }

       mpIpVpnIpAdEntIcmpUnreachHostInStatus OBJECT-TYPE
              SYNTAX  INTEGER {
                              enabled(1),
                              disabled(2)
                              }
              ACCESS  read-write
              STATUS  mandatory
              DESCRIPTION "This object indicates whether an ICMP destination
                          unreachable(host unreachable in) message is
                          transmitted to this Interface."
              ::= { mpIpVpnIpAddrEntry 14 }

       mpIpVpnIpAdEntIcmpUnreachHostOutStatus OBJECT-TYPE
              SYNTAX  INTEGER {
                              enabled(1),
                              disabled(2)
                              }
              ACCESS  read-write
              STATUS  mandatory
              DESCRIPTION "This object indicates whether an ICMP destination
                          unreachable(host unreachable out) message is
                          transmitted to this Interface."
              ::= { mpIpVpnIpAddrEntry 15 }

       mpIpVpnIpAdEntIcmpUnreachProtInStatus OBJECT-TYPE
              SYNTAX  INTEGER {
                              enabled(1),
                              disabled(2)
                              }
              ACCESS  read-write
              STATUS  mandatory
              DESCRIPTION "This object indicates whether an ICMP destination
                          unreachable(protocol unreachable in) message is
                          transmitted to this Interface."
              ::= { mpIpVpnIpAddrEntry 16 }

       mpIpVpnIpAdEntIcmpUnreachProtOutStatus OBJECT-TYPE
              SYNTAX  INTEGER {
                              enabled(1),
                              disabled(2)
                              }
              ACCESS  read-write
              STATUS  mandatory
              DESCRIPTION "This object indicates whether an ICMP destination
                          unreachable(protocol unreachable out) message is
                          transmitted to this Interface."
              ::= { mpIpVpnIpAddrEntry 17 }

       mpIpVpnIpAdEntIcmpUnreachPortInStatus OBJECT-TYPE
              SYNTAX  INTEGER {
                              enabled(1),
                              disabled(2)
                              }
              ACCESS  read-write
              STATUS  mandatory
              DESCRIPTION "This object indicates whether an ICMP destination
                          unreachable(port unreachable in) message is
                          transmitted to this Interface."
              ::= { mpIpVpnIpAddrEntry 18 }

       mpIpVpnIpAdEntIcmpUnreachPortOutStatus OBJECT-TYPE
              SYNTAX  INTEGER {
                              enabled(1),
                              disabled(2)
                              }
              ACCESS  read-write
              STATUS  mandatory
              DESCRIPTION "This object indicates whether an ICMP destination
                          unreachable(port unreachable out) message is
                          transmitted to this Interface."
              ::= { mpIpVpnIpAddrEntry 19 }

       mpIpVpnIpAdEntIcmpUnreachFragNeededInStatus OBJECT-TYPE
              SYNTAX  INTEGER {
                              enabled(1),
                              disabled(2)
                              }
              ACCESS  read-write
              STATUS  mandatory
              DESCRIPTION "This object indicates whether an ICMP destination
                          unreachable(fragmentation needed and DF set in)
                          message is transmitted to this Interface."
              ::= { mpIpVpnIpAddrEntry 20 }

       mpIpVpnIpAdEntIcmpUnreachFragNeededOutStatus OBJECT-TYPE
              SYNTAX  INTEGER {
                              enabled(1),
                              disabled(2)
                              }
              ACCESS  read-write
              STATUS  mandatory
              DESCRIPTION "This object indicates whether an ICMP destination
                          unreachable(fragmentation needed and DF set out)
                          message is transmitted to this Interface."
              ::= { mpIpVpnIpAddrEntry 21 }

       mpIpVpnIpAdEntIcmpUnreachRouteFailInStatus OBJECT-TYPE
              SYNTAX  INTEGER {
                              enabled(1),
                              disabled(2)
                              }
              ACCESS  read-write
              STATUS  mandatory
              DESCRIPTION "This object indicates whether an ICMP destination
                          unreachable(source route failed in)message is
                          transmitted to this Interface."
              ::= { mpIpVpnIpAddrEntry 22 }

       mpIpVpnIpAdEntIcmpUnreachRouteFailOutStatus OBJECT-TYPE
              SYNTAX  INTEGER {
                              enabled(1),
                              disabled(2)
                              }
              ACCESS  read-write
              STATUS  mandatory
              DESCRIPTION "This object indicates whether an ICMP destination
                          unreachable(source route failed out)message is
                          transmitted to this Interface."
              ::= { mpIpVpnIpAddrEntry 23 }

       mpIpVpnIpAdEntIcmpTtlExceedInStatus OBJECT-TYPE
              SYNTAX  INTEGER {
                              enabled(1),
                              disabled(2)
                              }
              ACCESS  read-write
              STATUS  mandatory
              DESCRIPTION "This object indicates whether an ICMP time
                          exceeded(time to live exceeded in transit in)
                          message is transmitted to this Interface."
              ::= { mpIpVpnIpAddrEntry 24 }

       mpIpVpnIpAdEntIcmpTtlExceedOutStatus OBJECT-TYPE
              SYNTAX  INTEGER {
                              enabled(1),
                              disabled(2)
                              }
              ACCESS  read-write
              STATUS  mandatory
              DESCRIPTION "This object indicates whether an ICMP time
                          exceeded(time to live exceeded in transit out)
                          message is transmitted to this Interface."
              ::= { mpIpVpnIpAddrEntry 25 }

       mpIpVpnIpAdEntIcmpReassemblyExceedInStatus OBJECT-TYPE
              SYNTAX  INTEGER {
                              enabled(1),
                              disabled(2)
                              }
              ACCESS  read-write
              STATUS  mandatory
              DESCRIPTION "This object indicates whether an ICMP time
                          exceeded(fragment reassembly time exceeded in)
                          message is transmitted to this Interface."
              ::= { mpIpVpnIpAddrEntry 26 }

       mpIpVpnIpAdEntIcmpReassemblyExceedOutStatus OBJECT-TYPE
              SYNTAX  INTEGER {
                              enabled(1),
                              disabled(2)
                              }
              ACCESS  read-write
              STATUS  mandatory
              DESCRIPTION "This object indicates whether an ICMP time
                          exceeded(fragment reassembly time exceeded out)
                          message is transmitted to this Interface."
              ::= { mpIpVpnIpAddrEntry 27 }

       mpIpVpnIpAdEntIcmpParamProbInStatus OBJECT-TYPE
              SYNTAX  INTEGER {
                              enabled(1),
                              disabled(2)
                              }
              ACCESS  read-write
              STATUS  mandatory
              DESCRIPTION "This object indicates whether an ICMP parameter
                          problem(in) message is transmitted to this
                          Interface."
              ::= { mpIpVpnIpAddrEntry 28 }

       mpIpVpnIpAdEntIcmpParamProbOutStatus OBJECT-TYPE
              SYNTAX  INTEGER {
                              enabled(1),
                              disabled(2)
                              }
              ACCESS  read-write
              STATUS  mandatory
              DESCRIPTION "This object indicates whether an ICMP parameter
                          problem(out) message is transmitted to this
                          Interface."
              ::= { mpIpVpnIpAddrEntry 29 }

       mpIpVpnIpAdEntProxyArpStatus OBJECT-TYPE
              SYNTAX  INTEGER {
                              enabled(1),
                              disabled(2)
                              }
              ACCESS  read-write
              STATUS  mandatory
              DESCRIPTION "This object controls the operating status of the
                          Proxy ARP in this Interface.This object is set
                          to '1' to enable the Proxy ARP functionality, and
                          is set to '2' to disable the Proxy ARP
                          functionality."
              ::= { mpIpVpnIpAddrEntry 30 }

       mpIpVpnIpAdEntDirectedBroadcastStatus OBJECT-TYPE
              SYNTAX  INTEGER {
                              enabled(1),
                              disabled(2)
                              }
              ACCESS  read-write
              STATUS  mandatory
              DESCRIPTION "This object controls the operating status of the
                          Directed Broadcast Forwarding in this Interface.
                          This object is set to '1' to enable the Directed
                          Broadcast Forwarding functionality, and is set to
                          '2' to disable the Directed Broadcast Forwarding
                          functionality."
              ::= { mpIpVpnIpAddrEntry 31 }

       mpIpVpnIpAdEntPathThroughListNumber OBJECT-TYPE
              SYNTAX  INTEGER (0..2147483647)
              ACCESS  read-write
              STATUS  mandatory
              DESCRIPTION "This object controls the operating status of the
                          Path Through Forwarding in this Interface.
                          This object is set to 'except 0' to enable the 
                          Path Through Forwarding functionality, and is set 
                          to '0' to disable the Path Through Forwarding
                          functionality.But, this number must be in relation
                          to the direction-list."
              ::= { mpIpVpnIpAddrEntry 32 }

       mpIpVpnIpAdEntExtendedStaticRouteListNumber OBJECT-TYPE
              SYNTAX  INTEGER (0..2147483647)
              ACCESS  read-write
              STATUS  mandatory
              DESCRIPTION "This object controls the operating status of the
                          Extended Static Routing in this Interface.
                          This object is set to 'except 0' to enable the 
                          Extended Static Routing functionality, and is set
                          to '0' to disable the Extended Static Routing
                          functionality.But, this number must be in relation
                          to the direction-list."
              ::= { mpIpVpnIpAddrEntry 33 }


       -- the VPN IP cidr table

       mpIpVpnIpCidrTable OBJECT-TYPE
              SYNTAX  SEQUENCE OF MpIpVpnIpCidrEntry
              ACCESS  not-accessible
              STATUS  mandatory
              DESCRIPTION "The table of IP cidr information relevant to
                          this entity's VPNID."
              ::= { mpIp 13 }

       mpIpVpnIpCidrEntry OBJECT-TYPE
              SYNTAX  MpIpVpnIpCidrEntry
              ACCESS  not-accessible
              STATUS  mandatory
              DESCRIPTION "The IP cidr information for one of this
                          entity's VPNID."
              INDEX { mpIpVpnIpCidrVpnId }
              ::= { mpIpVpnIpCidrTable 1 }

       MpIpVpnIpCidrEntry ::=
              SEQUENCE {
                  mpIpVpnIpCidrVpnId
                      INTEGER,
                  mpIpVpnIpCidrRouteNumber
                      Gauge32
              }

       mpIpVpnIpCidrVpnId OBJECT-TYPE
              SYNTAX  INTEGER
              ACCESS  read-only
              STATUS  mandatory
              DESCRIPTION "This is the index to identify the VPN entry.
                          The value of this index must be assigned uniquely,
                          witrhin the range of 1 - 65535."
              ::= { mpIpVpnIpCidrEntry 1 }

       mpIpVpnIpCidrRouteNumber OBJECT-TYPE
              SYNTAX   Gauge32
              MAX-ACCESS read-only
-- @015              STATUS   current
              STATUS  mandatory
              DESCRIPTION "The number of current mpIpVpnIpCidrRouteTable 
                          entries that are not invalid."
              ::= { mpIpVpnIpCidrEntry 2 }


       -- the VPN IP cidr route table

       -- The IP CIDR Route Table obsoletes and replaces the ipRoute
       -- Table current in MIB-I and MIB-II and the IP Forwarding Table.
       -- It adds knowledge of the autonomous system of the next hop,
       -- multiple next hops, and policy routing, and Classless

       -- Inter-Domain Routing.

       mpIpVpnIpCidrRouteTable OBJECT-TYPE
              SYNTAX   SEQUENCE OF MpIpVpnIpCidrRouteEntry
              MAX-ACCESS not-accessible
-- @015              STATUS   current
              STATUS  mandatory
              DESCRIPTION "This entity's IP Routing table."
              REFERENCE "RFC 1213 Section 6.6, The IP Group"
              ::= { mpIp 14 }

       mpIpVpnIpCidrRouteEntry OBJECT-TYPE
              SYNTAX   MpIpVpnIpCidrRouteEntry
              MAX-ACCESS not-accessible
-- @015              STATUS   current
              STATUS  mandatory
              DESCRIPTION "A particular route to  a  particular  destina-
                          tion, under a particular policy."
              INDEX { mpIpVpnIpCidrRouteVpnId,
                      mpIpVpnIpCidrRouteDest,
                      mpIpVpnIpCidrRouteMask,
                      mpIpVpnIpCidrRouteTos,
                      mpIpVpnIpCidrRouteNextHop }
              ::= { mpIpVpnIpCidrRouteTable 1 }

       MpIpVpnIpCidrRouteEntry ::=
              SEQUENCE {
                  mpIpVpnIpCidrRouteVpnId
                      INTEGER,
                  mpIpVpnIpCidrRouteDest
                      IpAddress,
                  mpIpVpnIpCidrRouteMask
                      IpAddress,
                  mpIpVpnIpCidrRouteTos
                      Integer32,
                  mpIpVpnIpCidrRouteNextHop
                      IpAddress,
                  mpIpVpnIpCidrRouteIfIndex
                      Integer32,
                  mpIpVpnIpCidrRouteType
                      INTEGER,
                  mpIpVpnIpCidrRouteProto
                      INTEGER,
                  mpIpVpnIpCidrRouteAge
                      Integer32,
                  mpIpVpnIpCidrRouteInfo
                      OBJECT IDENTIFIER,
                  mpIpVpnIpCidrRouteNextHopAS
                      Integer32,
                  mpIpVpnIpCidrRouteMetric1
                      Integer32,
                  mpIpVpnIpCidrRouteMetric2
                      Integer32,
                  mpIpVpnIpCidrRouteMetric3
                      Integer32,
                  mpIpVpnIpCidrRouteMetric4
                      Integer32,
                  mpIpVpnIpCidrRouteMetric5
                      Integer32,
                  mpIpVpnIpCidrRouteStatus
                      RowStatus
              }

       mpIpVpnIpCidrRouteVpnId OBJECT-TYPE
              SYNTAX  INTEGER
              ACCESS  read-only
              STATUS  mandatory
              DESCRIPTION "This is the index to identify the VPN entry.
                          The value of this index must be assigned uniquely,
                          witrhin the range of 1 - 65535."
              ::= { mpIpVpnIpCidrRouteEntry 1 }

       mpIpVpnIpCidrRouteDest OBJECT-TYPE
              SYNTAX   IpAddress
              MAX-ACCESS read-only
-- @015              STATUS   current
              STATUS  mandatory
              DESCRIPTION
                 "The destination IP address of this route.
                 This object may not take a Multicast (Class  D)
                 address value.
                 Any assignment (implicit or  otherwise)  of  an
                 instance  of  this  object to a value x must be
                 rejected if the bitwise logical-AND of  x  with
                 the  value of the corresponding instance of the
                 mpIpVpnIpCidrRouteMask object is not equal to x."
              ::= { mpIpVpnIpCidrRouteEntry 2 }

       mpIpVpnIpCidrRouteMask OBJECT-TYPE
              SYNTAX   IpAddress
              MAX-ACCESS read-only
-- @015              STATUS   current
              STATUS  mandatory
              DESCRIPTION
                 "Indicate the mask to be logical-ANDed with the
                 destination  address  before  being compared to
                 the value in the  mpIpVpnIpCidrRouteDest  field. 
                 For those systems that do not support arbitrary
                 subnet masks, an agent constructs the value  of
                 the  mpIpVpnIpCidrRouteMask  by reference to the 
                 IP Address Class.
                 Any assignment (implicit or  otherwise)  of  an
                 instance  of  this  object to a value x must be
                 rejected if the bitwise logical-AND of  x  with
                 the  value of the corresponding instance of the
                 mpIpVpnIpCidrRouteDest  object  is  not  equal 
                 to mpIpVpnIpCidrRouteDest."
              ::= { mpIpVpnIpCidrRouteEntry 3 }
       
       -- The following convention is included for specification
       -- of TOS Field contents.  At this time, the Host Requirements
       -- and the Router Requirements documents disagree on the width
       -- of the TOS field.  This mapping describes the Router
       -- Requirements mapping, and leaves room to widen the TOS field
       -- without impact to fielded systems.

       mpIpVpnIpCidrRouteTos OBJECT-TYPE
              SYNTAX   Integer32
              MAX-ACCESS read-only
-- @015              STATUS   current
              STATUS  mandatory
              DESCRIPTION
                 "The policy specifier is the IP TOS Field.  The encoding
                 of IP TOS is as specified  by  the  following convention.
                 Zero indicates the default path if no more  specific
                 policy applies.

              +-----+-----+-----+-----+-----+-----+-----+-----+
              |                 |                       |     |
              |   PRECEDENCE    |    TYPE OF SERVICE    |  0  |
              |                 |                       |     |
              +-----+-----+-----+-----+-----+-----+-----+-----+

                   IP TOS                IP TOS
              Field     Policy      Field     Policy
              Contents    Code      Contents    Code
              0 0 0 0  ==>   0      0 0 0 1  ==>   2
              0 0 1 0  ==>   4      0 0 1 1  ==>   6
              0 1 0 0  ==>   8      0 1 0 1  ==>  10
              0 1 1 0  ==>  12      0 1 1 1  ==>  14
              1 0 0 0  ==>  16      1 0 0 1  ==>  18
              1 0 1 0  ==>  20      1 0 1 1  ==>  22
              1 1 0 0  ==>  24      1 1 0 1  ==>  26
              1 1 1 0  ==>  28      1 1 1 1  ==>  30"
              ::= { mpIpVpnIpCidrRouteEntry 4 }

       mpIpVpnIpCidrRouteNextHop OBJECT-TYPE
              SYNTAX   IpAddress
              MAX-ACCESS read-only
-- @015              STATUS   current
              STATUS  mandatory
              DESCRIPTION
                 "On remote routes, the address of the next sys-
                 tem en route; Otherwise, 0.0.0.0."
              ::= { mpIpVpnIpCidrRouteEntry 5 }

       mpIpVpnIpCidrRouteIfIndex OBJECT-TYPE
              SYNTAX   Integer32
-- @015             MAX-ACCESS read-create
              MAX-ACCESS read-only
-- @015              STATUS   current
              STATUS  mandatory
              DESCRIPTION
                 "The ifIndex value which identifies  the  local
                 interface  through  which  the next hop of this
                 route should be reached."
                 DEFVAL { 0 }
              ::= { mpIpVpnIpCidrRouteEntry 6 }

       mpIpVpnIpCidrRouteType OBJECT-TYPE
              SYNTAX   INTEGER {
                       other    (1), -- not specified by this MIB
                       reject   (2), -- route which discards traffic
                       local    (3), -- local interface
                       remote   (4)  -- remote destination
                    }
-- @015             MAX-ACCESS read-create
              MAX-ACCESS read-only
-- @015              STATUS   current
              STATUS  mandatory
              DESCRIPTION
                 "The type of route.  Note that local(3)  refers
                 to  a route for which the next hop is the final
                 destination; remote(4) refers to  a  route  for
                 which  the  next  hop is not the final destina-
                 tion.

                 Routes which do not result in traffic forwarding or
                 rejection should not be displayed even if the
                 implementation keeps them stored internally.
                 reject (2) refers to a route which, if matched, discards
                 the message as unreachable. This is used in some
                 protocols as a means of correctly aggregating routes."
              ::= { mpIpVpnIpCidrRouteEntry 7 }

       mpIpVpnIpCidrRouteProto OBJECT-TYPE
              SYNTAX   INTEGER {
                       other     (1),  -- not specified
                       local     (2),  -- local interface
                       netmgmt   (3),  -- static route
                       icmp      (4),  -- result of ICMP Redirect
                               -- the following are all dynamic
                               -- routing protocols
                       egp        (5),  -- Exterior Gateway Protocol
                       ggp        (6),  -- Gateway-Gateway Protocol
                       hello      (7),  -- FuzzBall HelloSpeak
                       rip        (8),  -- Berkeley RIP or RIP-II
                       isIs       (9),  -- Dual IS-IS
                       esIs       (10), -- ISO 9542
                       ciscoIgrp  (11), -- Cisco IGRP
                       bbnSpfIgp  (12), -- BBN SPF IGP
                       ospf       (13), -- Open Shortest Path First
                       bgp        (14), -- Border Gateway Protocol
                       idpr       (15), -- InterDomain Policy Routing
                       ciscoEigrp (16)  -- Cisco EIGRP
                    }
              MAX-ACCESS read-only
-- @015              STATUS   current
              STATUS  mandatory
              DESCRIPTION
                 "The routing mechanism via which this route was
                 learned.  Inclusion of values for gateway rout-
                 ing protocols is not  intended  to  imply  that
                 hosts should support those protocols."
              ::= { mpIpVpnIpCidrRouteEntry 8 }

       mpIpVpnIpCidrRouteAge OBJECT-TYPE
              SYNTAX   Integer32
              MAX-ACCESS read-only
-- @015              STATUS   current
              STATUS  mandatory
              DESCRIPTION
                 "The number of seconds  since  this  route  was
                 last  updated  or  otherwise  determined  to be
                 correct.  Note that no semantics of  `too  old'
                 can  be implied except through knowledge of the
                 routing  protocol  by  which  the   route   was
                 learned."
              DEFVAL  { 0 }
              ::= { mpIpVpnIpCidrRouteEntry 9 }

       mpIpVpnIpCidrRouteInfo OBJECT-TYPE
              SYNTAX   OBJECT IDENTIFIER
-- @015             MAX-ACCESS read-create
              MAX-ACCESS read-only
-- @015              STATUS   current
              STATUS  mandatory
              DESCRIPTION
                 "A reference to MIB definitions specific to the
                 particular  routing protocol which is responsi-
                 ble for this route, as determined by the  value
                 specified in the route's mpIpVpnIpCidrRouteProto 
                 value.
                 If this information is not present,  its  value
                 should be set to the OBJECT IDENTIFIER { 0 0 },
                 which is a syntactically valid object  identif-
                 ier, and any implementation conforming to ASN.1
                 and the Basic Encoding Rules must  be  able  to
                 generate and recognize this value."
              ::= { mpIpVpnIpCidrRouteEntry 10 }

       mpIpVpnIpCidrRouteNextHopAS OBJECT-TYPE
              SYNTAX   Integer32
-- @015             MAX-ACCESS read-create
              MAX-ACCESS read-only
-- @015              STATUS   current
              STATUS  mandatory
              DESCRIPTION
                 "The Autonomous System Number of the Next  Hop.
                 The  semantics of this object are determined by
                 the routing-protocol specified in  the  route's
                 mpIpVpnIpCidrRouteProto  value.  When  this 
                 object is unknown or  not  relevant  its  value
                 should be set to zero."
              DEFVAL { 0 }
              ::= { mpIpVpnIpCidrRouteEntry 11 }

       mpIpVpnIpCidrRouteMetric1 OBJECT-TYPE
              SYNTAX   Integer32
-- @015             MAX-ACCESS read-create
              MAX-ACCESS read-only
-- @015              STATUS   current
              STATUS  mandatory
              DESCRIPTION
                 "The primary routing  metric  for  this  route.
                 The  semantics of this metric are determined by
                 the routing-protocol specified in  the  route's
                 mpIpVpnIpCidrRouteProto  value.  If this metric
                 is not used, its value should be set to -1."
              DEFVAL { -1 }
              ::= { mpIpVpnIpCidrRouteEntry 12 }

       mpIpVpnIpCidrRouteMetric2 OBJECT-TYPE
              SYNTAX   Integer32
-- @015             MAX-ACCESS read-create
              MAX-ACCESS read-only
-- @015              STATUS   current
              STATUS  mandatory
              DESCRIPTION
                 "An alternate routing metric  for  this  route.
                 The  semantics of this metric are determined by
                 the routing-protocol specified in  the  route's
                 mpIpVpnIpCidrRouteProto  value.  If this metric
                 is not used, its value should be set to -1."
              DEFVAL { -1 }
              ::= { mpIpVpnIpCidrRouteEntry 13 }

       mpIpVpnIpCidrRouteMetric3 OBJECT-TYPE
              SYNTAX   Integer32
-- @015             MAX-ACCESS read-create
              MAX-ACCESS read-only
-- @015              STATUS   current
              STATUS  mandatory
              DESCRIPTION
                 "An alternate routing metric  for  this  route.
                 The  semantics of this metric are determined by
                 the routing-protocol specified in  the  route's
                 mpIpVpnIpCidrRouteProto  value.  If this metric
                 is not used, its value should be set to -1."
              DEFVAL { -1 }
              ::= { mpIpVpnIpCidrRouteEntry 14 }

       mpIpVpnIpCidrRouteMetric4 OBJECT-TYPE
              SYNTAX   Integer32
-- @015             MAX-ACCESS read-create
              MAX-ACCESS read-only
-- @015              STATUS   current
              STATUS  mandatory
              DESCRIPTION
                 "An alternate routing metric  for  this  route.
                 The  semantics of this metric are determined by
                 the routing-protocol specified in  the  route's
                 mpIpVpnIpCidrRouteProto  value.  If this metric
                 is not used, its value should be set to -1."
              DEFVAL { -1 }
              ::= { mpIpVpnIpCidrRouteEntry 15 }

       mpIpVpnIpCidrRouteMetric5 OBJECT-TYPE
              SYNTAX   Integer32
-- @015             MAX-ACCESS read-create
              MAX-ACCESS read-only
-- @015              STATUS   current
              STATUS  mandatory
              DESCRIPTION
                 "An alternate routing metric  for  this  route.
                 The  semantics of this metric are determined by
                 the routing-protocol specified in  the  route's
                 mpIpVpnIpCidrRouteProto  value.  If this metric
                 is not used, its value should be set to -1."
              DEFVAL { -1 }
              ::= { mpIpVpnIpCidrRouteEntry 16 }

       mpIpVpnIpCidrRouteStatus OBJECT-TYPE
              SYNTAX   RowStatus
-- @015             MAX-ACCESS read-create
              MAX-ACCESS read-only
-- @015              STATUS   current
              STATUS  mandatory
              DESCRIPTION
                 "The row status variable, used according to
                 row installation and removal conventions."
              ::= { mpIpVpnIpCidrRouteEntry 17 }

       -- conformance information


       -- the VPN IP routing table

       -- The IP routing table contains an entry for each route
       -- presently known to this entity.

       mpIpVpnIpRouteTable OBJECT-TYPE
              SYNTAX  SEQUENCE OF MpIpVpnIpRouteEntry
              ACCESS  not-accessible
              STATUS  mandatory
              DESCRIPTION
                      "This entity's IP Routing table."
              ::= { mpIp 15 }

       mpIpVpnIpRouteEntry OBJECT-TYPE
              SYNTAX  MpIpVpnIpRouteEntry
              ACCESS  not-accessible
              STATUS  mandatory
              DESCRIPTION
                      "A route to a particular destination."
              INDEX   { mpIpVpnIpRouteVpnId,
                        mpIpVpnIpRouteDest }
              ::= { mpIpVpnIpRouteTable 1 }

       MpIpVpnIpRouteEntry ::=
              SEQUENCE {
                  mpIpVpnIpRouteVpnId
                      INTEGER,
                  mpIpVpnIpRouteDest
                      IpAddress,
                  mpIpVpnIpRouteIfIndex
                      INTEGER,
                  mpIpVpnIpRouteMetric1
                      INTEGER,
                  mpIpVpnIpRouteMetric2
                      INTEGER,
                  mpIpVpnIpRouteMetric3
                      INTEGER,
                  mpIpVpnIpRouteMetric4
                      INTEGER,
                  mpIpVpnIpRouteNextHop
                      IpAddress,
                  mpIpVpnIpRouteType
                      INTEGER,
                  mpIpVpnIpRouteProto
                      INTEGER,
                  mpIpVpnIpRouteAge
                      INTEGER,
                  mpIpVpnIpRouteMask
                      IpAddress,
                  mpIpVpnIpRouteMetric5
                      INTEGER,
                  mpIpVpnIpRouteInfo
                      OBJECT IDENTIFIER
              }

       mpIpVpnIpRouteVpnId OBJECT-TYPE
              SYNTAX  INTEGER
              ACCESS  read-only
              STATUS  mandatory
              DESCRIPTION "This is the index to identify the VPN entry.
                          The value of this index must be assigned uniquely,
                          witrhin the range of 1 - 65535."
              ::= { mpIpVpnIpRouteEntry 1 }

       mpIpVpnIpRouteDest OBJECT-TYPE
              SYNTAX  IpAddress
              ACCESS  read-write
              STATUS  mandatory
              DESCRIPTION
                   "The destination IP address of this route.  An
                   entry with a value of 0.0.0.0 is considered a
                   default route.  Multiple routes to a single
                   destination can appear in the table, but access to
                   such multiple entries is dependent on the table-
                   access mechanisms defined by the network
                   management protocol in use."
              ::= { mpIpVpnIpRouteEntry 2 }

       mpIpVpnIpRouteIfIndex OBJECT-TYPE
              SYNTAX  INTEGER
              ACCESS  read-write
              STATUS  mandatory
              DESCRIPTION
                   "The index value which uniquely identifies the
                   local interface through which the next hop of this
                   route should be reached.  The interface identified
                   by a particular value of this index is the same
                   interface as identified by the same value of
                   ifIndex."
              ::= { mpIpVpnIpRouteEntry 3 }

       mpIpVpnIpRouteMetric1 OBJECT-TYPE
              SYNTAX  INTEGER
              ACCESS  read-write
              STATUS  mandatory
              DESCRIPTION
                   "The primary routing metric for this route.  The
                   semantics of this metric are determined by the
                   routing-protocol specified in the route's
                   mpIpVpnIpRouteProto value.  If this metric is
                   not used, its value should be set to -1."
              ::= { mpIpVpnIpRouteEntry 4 }

       mpIpVpnIpRouteMetric2 OBJECT-TYPE
              SYNTAX  INTEGER
              ACCESS  read-write
              STATUS  mandatory
              DESCRIPTION
                   "An alternate routing metric for this route.  The
                   semantics of this metric are determined by the
                   routing-protocol specified in the route's
                   mpIpVpnIpRouteProto value.  If this metric is
                   not used, its value should be set to -1."
              ::= { mpIpVpnIpRouteEntry 5 }

       mpIpVpnIpRouteMetric3 OBJECT-TYPE
              SYNTAX  INTEGER
              ACCESS  read-write
              STATUS  mandatory
              DESCRIPTION
                   "An alternate routing metric for this route.  The
                   semantics of this metric are determined by the
                   routing-protocol specified in the route's
                   mpIpVpnIpRouteProto value.  If this metric is
                   not used, its value should be set to -1."
              ::= { mpIpVpnIpRouteEntry 6 }

       mpIpVpnIpRouteMetric4 OBJECT-TYPE
              SYNTAX  INTEGER
              ACCESS  read-write
              STATUS  mandatory
              DESCRIPTION
                   "An alternate routing metric for this route.  The
                   semantics of this metric are determined by the
                   routing-protocol specified in the route's
                   ipRouteProto value.  If this metric is not used,
                   its value should be set to -1."
              ::= { mpIpVpnIpRouteEntry 7 }

       mpIpVpnIpRouteNextHop OBJECT-TYPE
              SYNTAX  IpAddress
              ACCESS  read-write
              STATUS  mandatory
              DESCRIPTION
                   "The IP address of the next hop of this route.
                   (In the case of a route bound to an interface
                   which is realized via a broadcast media, the value
                   of this field is the agent's IP address on that
                   interface.)"
              ::= { mpIpVpnIpRouteEntry 8 }

       mpIpVpnIpRouteType OBJECT-TYPE
              SYNTAX  INTEGER {
                       other(1),        -- none of the following
                       invalid(2),      -- an invalidated route
                                        -- route to directly
                       direct(3),       -- connected (sub-)network
                                        -- route to a non-local
                       indirect(4)      -- host/network/sub-network
                   }
              ACCESS  read-write
              STATUS  mandatory
              DESCRIPTION
                   "The type of route.  Note that the values
                   direct(3) and indirect(4) refer to the notion of
                   direct and indirect routing in the IP
                   architecture.

                   Setting this object to the value invalid(2) has
                   the effect of invalidating the corresponding entry
                   in the  mpIpVpnIpRouteTable  object.  That is, it
                   effectively dissasociates the destination
                   identified with said entry from the route
                   identified with said entry.  It is an
                   implementation-specific matter as to whether the
                   agent removes an invalidated entry from the table.
                   Accordingly, management stations must be prepared
                   to receive tabular information from agents that
                   corresponds to entries not currently in use.
                   Proper interpretation of such entries requires
                   examination of the relevant mpIpVpnIpRouteType
                   object."
              ::= { mpIpVpnIpRouteEntry 9 }

       mpIpVpnIpRouteProto OBJECT-TYPE
              SYNTAX  INTEGER {
                       other(1),       -- none of the following
                                       -- non-protocol information,
                                       -- e.g., manually configured
                       local(2),       -- entries
                                       -- set via a network
                       netmgmt(3),     -- management protocol
                                       -- obtained via ICMP,
                       icmp(4),        -- e.g., Redirect
                                       -- the remaining values are
                                       -- all gateway routing
                                       -- protocols
                       egp(5),
                       ggp(6),
                       hello(7),
                       rip(8),
                       is-is(9),
                       es-is(10),
                       ciscoIgrp(11),
                       bbnSpfIgp(12),
                       ospf(13),
                       bgp(14)
                   }
              ACCESS  read-only
              STATUS  mandatory
              DESCRIPTION
                   "The routing mechanism via which this route was
                   learned.  Inclusion of values for gateway routing
                   protocols is not intended to imply that hosts
                   should support those protocols."
              ::= { mpIpVpnIpRouteEntry 10 }

       mpIpVpnIpRouteAge OBJECT-TYPE
              SYNTAX  INTEGER
              ACCESS  read-write
              STATUS  mandatory
              DESCRIPTION
                   "The number of seconds since this route was last
                   updated or otherwise determined to be correct.
                   Note that no semantics of `too old' can be implied
                   except through knowledge of the routing protocol
                   by which the route was learned."
              ::= { mpIpVpnIpRouteEntry 11 }

       mpIpVpnIpRouteMask OBJECT-TYPE
              SYNTAX  IpAddress
              ACCESS  read-write
              STATUS  mandatory
              DESCRIPTION
                   "Indicate the mask to be logical-ANDed with the
                   destination address before being compared to the
                   value in the  mpIpVpnIpRouteDest  field.  For
                   those systems that do not support arbitrary subnet
                   masks,  an  agent  constructs  the  value  of  the 
                   mpIpVpnIpRouteMask  by  determining  whether  the
                   value  of  the  correspondent  mpIpVpnIpRouteDest
                   field  belong  to  a  class-A, B, or C  network,
                   and then using one of:

                        mask           network
                        255.0.0.0      class-A
                        255.255.0.0    class-B
                        255.255.255.0  class-C

                   If the value of the mpIpVpnIpRouteDest is 0.0.0.0
                   (a default route),  then the mask value is also
                   0.0.0.0.  It should be noted that all IP routing
                   subsystems implicitly use this mechanism."
              ::= { mpIpVpnIpRouteEntry 12 }

       mpIpVpnIpRouteMetric5 OBJECT-TYPE
              SYNTAX  INTEGER
              ACCESS  read-write
              STATUS  mandatory
              DESCRIPTION
                   "An alternate routing metric for this route.  The
                   semantics of this metric are determined by the
                   routing-protocol specified in the route's
                   mpIpVpnIpRouteProto value.  If this metric is not
                   used,  its value should be set to -1."
              ::= { mpIpVpnIpRouteEntry 13 }

       mpIpVpnIpRouteInfo OBJECT-TYPE
              SYNTAX  OBJECT IDENTIFIER
              ACCESS  read-only
              STATUS  mandatory
              DESCRIPTION
                   "A reference to MIB definitions specific to the
                   particular routing protocol which is responsible
                   for this route, as determined by the value
                   specified in the route's  mpIpVpnIpRouteProto
                   value.  If this information is not present,  its
                   value should be set to the OBJECT IDENTIFIER
                   { 0 0 },  which is a syntatically valid object
                   identifier, and any conformant implementation of
                   ASN.1  and  BER  must  be able to generate and
                   recognize this value."
              ::= { mpIpVpnIpRouteEntry 14 }


       -- the VPN IP address translation table

       -- The IP address translation table contain the IpAddress to
       -- `physical' address equivalences.  Some interfaces do not
       -- use translation tables for determining address
       -- equivalences (e.g., DDN-X.25 has an algorithmic method);
       -- if all interfaces are of this type, then the Address
       -- Translation table is empty, i.e., has zero entries.

       mpIpVpnIpNetToMediaTable OBJECT-TYPE
              SYNTAX  SEQUENCE OF MpIpVpnIpNetToMediaEntry
              ACCESS  not-accessible
              STATUS  mandatory
              DESCRIPTION
                   "The IP Address Translation table used for mapping
                   from IP addresses to physical addresses."
              ::= { mpIp 16 }

       mpIpVpnIpNetToMediaEntry OBJECT-TYPE
              SYNTAX  MpIpVpnIpNetToMediaEntry
              ACCESS  not-accessible
              STATUS  mandatory
              DESCRIPTION
                   "Each entry contains one IpAddress to `physical'
                   address equivalence."
              INDEX   { mpIpVpnIpNetToMediaVpnId,
                        mpIpVpnIpNetToMediaIfIndex,
                        mpIpVpnIpNetToMediaNetAddress }
              ::= { mpIpVpnIpNetToMediaTable 1 }

       MpIpVpnIpNetToMediaEntry ::=
              SEQUENCE {
                  mpIpVpnIpNetToMediaVpnId
                      INTEGER,
                  mpIpVpnIpNetToMediaIfIndex
                      INTEGER,
                  mpIpVpnIpNetToMediaPhysAddress
                      PhysAddress,
                  mpIpVpnIpNetToMediaNetAddress
                      IpAddress,
                  mpIpVpnIpNetToMediaType
                      INTEGER
              }

       mpIpVpnIpNetToMediaVpnId OBJECT-TYPE
              SYNTAX  INTEGER
              ACCESS  read-only
              STATUS  mandatory
              DESCRIPTION "This is the index to identify the VPN entry.
                          The value of this index must be assigned uniquely,
                          witrhin the range of 1 - 65535."
              ::= { mpIpVpnIpNetToMediaEntry 1 }

       mpIpVpnIpNetToMediaIfIndex OBJECT-TYPE
              SYNTAX  INTEGER
              ACCESS  read-write
              STATUS  mandatory
              DESCRIPTION
                   "The interface on which this entry's equivalence
                   is effective.  The interface identified by a
                   particular value of this index is the same
                   interface as identified by the same value of
                   ifIndex."
              ::= { mpIpVpnIpNetToMediaEntry 2 }

       mpIpVpnIpNetToMediaPhysAddress OBJECT-TYPE
              SYNTAX  PhysAddress
              ACCESS  read-write
              STATUS  mandatory
              DESCRIPTION
                   "The media-dependent `physical' address."
              ::= { mpIpVpnIpNetToMediaEntry 3 }

       mpIpVpnIpNetToMediaNetAddress OBJECT-TYPE
              SYNTAX  IpAddress
              ACCESS  read-write
              STATUS  mandatory
              DESCRIPTION
                   "The IpAddress corresponding to the media-
                   dependent `physical' address."
              ::= { mpIpVpnIpNetToMediaEntry 4 }

       mpIpVpnIpNetToMediaType OBJECT-TYPE
              SYNTAX  INTEGER {
                       other(1),        -- none of the following
                       invalid(2),      -- an invalidated mapping
                       dynamic(3),
                       static(4)
                   }
              ACCESS  read-write
              STATUS  mandatory
              DESCRIPTION
                   "The type of mapping.

                   Setting this object to the value invalid(2) has
                   the effect of invalidating the corresponding entry
                   in the  mpIpVpnIpNetToMediaTable.  That is,  it
                   effectively dissasociates the interface identified
                   with said entry from the mapping identified with
                   said entry.
                   It is an implementation-specific matter as to
                   whether the agent removes an invalidated entry
                   from the table.  Accordingly, management stations
                   must be prepared to receive tabular information
                   from agents that corresponds to entries not
                   currently in use.  Proper interpretation of such
                   entries requires examination of the relevant
                   mpIpVpnIpNetToMediaType  object."
              ::= { mpIpVpnIpNetToMediaEntry 5 }


       -- the VPN static proxy ARP table

       mpIpVpnStaticProxyArpTable OBJECT-TYPE
              SYNTAX  SEQUENCE OF MpIpVpnStaticProxyArpEntry
              ACCESS  not-accessible
              STATUS  mandatory
              DESCRIPTION
                   "This entity's Static Proxy ARP table."
              ::= { mpIp 17 }

       mpIpVpnStaticProxyArpEntry OBJECT-TYPE
              SYNTAX  MpIpVpnStaticProxyArpEntry
              ACCESS  not-accessible
              STATUS  mandatory
              DESCRIPTION
                   "This entity's Static Proxy ARP table."
              INDEX   { mpIpVpnStaticProxyArpVpnId,
                        mpIpVpnStaticProxyArpIfIndex,
                        mpIpVpnStaticProxyArpNetAddress,
                        mpIpVpnStaticProxyArpNetMask }
              ::= { mpIpVpnStaticProxyArpTable 1 }

       MpIpVpnStaticProxyArpEntry ::=
              SEQUENCE {
                  mpIpVpnStaticProxyArpVpnId
                      INTEGER,
                  mpIpVpnStaticProxyArpIfIndex
                      INTEGER,
                  mpIpVpnStaticProxyArpNetAddress
                      IpAddress,
                  mpIpVpnStaticProxyArpNetMask
                      IpAddress,
                  mpIpVpnStaticProxyArpStatus
                      INTEGER
              }

       mpIpVpnStaticProxyArpVpnId OBJECT-TYPE
              SYNTAX  INTEGER
              ACCESS  read-only
              STATUS  mandatory
              DESCRIPTION "This is the index to identify the VPN entry.
                          The value of this index must be assigned uniquely,
                          witrhin the range of 1 - 65535."
              ::= { mpIpVpnStaticProxyArpEntry 1 }

       mpIpVpnStaticProxyArpIfIndex OBJECT-TYPE
              SYNTAX  INTEGER
              ACCESS  read-write
              STATUS  mandatory
              DESCRIPTION
                   "The interface on which this entry's equivalence
                   is effective.  The interface identified by a
                   particular value of this index is the same
                   interface as identified by the same value of
                   ifIndex."
              ::= { mpIpVpnStaticProxyArpEntry 2 }

       mpIpVpnStaticProxyArpNetAddress OBJECT-TYPE
              SYNTAX  IpAddress
              ACCESS  read-write
              STATUS  mandatory
              DESCRIPTION
                   "The IpAddress corresponding to the media-
                   dependent `physical' address."
              ::= { mpIpVpnStaticProxyArpEntry 3 }

       mpIpVpnStaticProxyArpNetMask OBJECT-TYPE
              SYNTAX  IpAddress
              ACCESS  read-write
              STATUS  mandatory
              DESCRIPTION
                   "The IpAddress corresponding to the media-
                   dependent `physical' address."
              ::= { mpIpVpnStaticProxyArpEntry 4 }

       mpIpVpnStaticProxyArpStatus OBJECT-TYPE
              SYNTAX  INTEGER {
                              valid(1),
                              invalid(2)
                              }
              ACCESS  read-write
              STATUS  mandatory
              DESCRIPTION "When an entry is created it autmatically becomes
                          valid(1). When this object is set to invalid(2)
                          then this entry will be deleted."
              ::= { mpIpVpnStaticProxyArpEntry 5 }


       -- the VPN ICMP table

       -- Implementation of the ICMP group is mandatory for all
       -- systems.

       mpIpVpnIcmpTable OBJECT-TYPE
              SYNTAX  SEQUENCE OF MpIpVpnIcmpEntry
              ACCESS  not-accessible
              STATUS  mandatory
              DESCRIPTION "The table of ICMP group information relevant to
                          this entity's VPNID."
              ::= { mpIp 18 }

       mpIpVpnIcmpEntry OBJECT-TYPE
              SYNTAX  MpIpVpnIcmpEntry
              ACCESS  not-accessible
              STATUS  mandatory
              DESCRIPTION "The ICMP group information for one of this
                          entity's VPNID."
              INDEX   { mpIpVpnIcmpVpnId }
              ::= { mpIpVpnIcmpTable 1 }

       MpIpVpnIcmpEntry ::=
              SEQUENCE {
                  mpIpVpnIcmpVpnId
                      INTEGER,
                  mpIpVpnIcmpInMsgs
                      Counter,
                  mpIpVpnIcmpInErrors
                      Counter,
                  mpIpVpnIcmpInDestUnreachs
                      Counter,
                  mpIpVpnIcmpInTimeExcds
                      Counter,
                  mpIpVpnIcmpInParmProbs
                      Counter,
                  mpIpVpnIcmpInSrcQuenchs
                      Counter,
                  mpIpVpnIcmpInRedirects
                      Counter,
                  mpIpVpnIcmpInEchos
                      Counter,
                  mpIpVpnIcmpInEchoReps
                      Counter,
                  mpIpVpnIcmpInTimestamps
                      Counter,
                  mpIpVpnIcmpInTimestampReps
                      Counter,
                  mpIpVpnIcmpInAddrMasks
                      Counter,
                  mpIpVpnIcmpInAddrMaskReps
                      Counter,
                  mpIpVpnIcmpOutMsgs
                      Counter,
                  mpIpVpnIcmpOutErrors
                      Counter,
                  mpIpVpnIcmpOutDestUnreachs
                      Counter,
                  mpIpVpnIcmpOutTimeExcds
                      Counter,
                  mpIpVpnIcmpOutParmProbs
                      Counter,
                  mpIpVpnIcmpOutSrcQuenchs
                      Counter,
                  mpIpVpnIcmpOutRedirects
                      Counter,
                  mpIpVpnIcmpOutEchos
                      Counter,
                  mpIpVpnIcmpOutEchoReps
                      Counter,
                  mpIpVpnIcmpOutTimestamps
                      Counter,
                  mpIpVpnIcmpOutTimestampReps
                      Counter,
                  mpIpVpnIcmpOutAddrMasks
                      Counter,
                  mpIpVpnIcmpOutAddrMaskReps
                      Counter
              }

       mpIpVpnIcmpVpnId OBJECT-TYPE
              SYNTAX  INTEGER
              ACCESS  read-only
              STATUS  mandatory
              DESCRIPTION "This is the index to identify the VPN entry.
                          The value of this index must be assigned uniquely,
                          witrhin the range of 1 - 65535."
              ::= { mpIpVpnIcmpEntry 1 }

       mpIpVpnIcmpInMsgs OBJECT-TYPE
              SYNTAX  Counter
              ACCESS  read-only
              STATUS  mandatory
              DESCRIPTION
                      "The total number of ICMP messages which the
                      entity received.  Note that this counter includes
                      all those counted by mpIpVpnIcmpInErrors."
              ::= { mpIpVpnIcmpEntry 2 }

       mpIpVpnIcmpInErrors OBJECT-TYPE
              SYNTAX  Counter
              ACCESS  read-only
              STATUS  mandatory
              DESCRIPTION
                      "The number of ICMP messages which the entity
                      received but determined as having ICMP-specific
                      errors (bad ICMP checksums, bad length, etc.)."
              ::= { mpIpVpnIcmpEntry 3 }

       mpIpVpnIcmpInDestUnreachs OBJECT-TYPE
              SYNTAX  Counter
              ACCESS  read-only
              STATUS  mandatory
              DESCRIPTION
                      "The number of ICMP Destination Unreachable
                      messages received."
              ::= { mpIpVpnIcmpEntry 4 }

       mpIpVpnIcmpInTimeExcds OBJECT-TYPE
              SYNTAX  Counter
              ACCESS  read-only
              STATUS  mandatory
              DESCRIPTION
                      "The number of ICMP Time Exceeded messages
                      received."
              ::= { mpIpVpnIcmpEntry 5 }

       mpIpVpnIcmpInParmProbs OBJECT-TYPE
              SYNTAX  Counter
              ACCESS  read-only
              STATUS  mandatory
              DESCRIPTION
                      "The number of ICMP Parameter Problem messages
                      received."
              ::= { mpIpVpnIcmpEntry 6 }

       mpIpVpnIcmpInSrcQuenchs OBJECT-TYPE
              SYNTAX  Counter
              ACCESS  read-only
              STATUS  mandatory
              DESCRIPTION
                      "The number of ICMP Source Quench messages
                      received."
              ::= { mpIpVpnIcmpEntry 7 }

       mpIpVpnIcmpInRedirects OBJECT-TYPE
              SYNTAX  Counter
              ACCESS  read-only
              STATUS  mandatory
              DESCRIPTION
                      "The number of ICMP Redirect messages received."
              ::= { mpIpVpnIcmpEntry 8 }

       mpIpVpnIcmpInEchos OBJECT-TYPE
              SYNTAX  Counter
              ACCESS  read-only
              STATUS  mandatory
              DESCRIPTION
                      "The number of ICMP Echo (request) messages
                      received."
              ::= { mpIpVpnIcmpEntry 9 }

       mpIpVpnIcmpInEchoReps OBJECT-TYPE
              SYNTAX  Counter
              ACCESS  read-only
              STATUS  mandatory
              DESCRIPTION
                      "The number of ICMP Echo Reply messages received."
              ::= { mpIpVpnIcmpEntry 10 }

       mpIpVpnIcmpInTimestamps OBJECT-TYPE
              SYNTAX  Counter
              ACCESS  read-only
              STATUS  mandatory
              DESCRIPTION
                      "The number of ICMP Timestamp (request) messages
                      received."
              ::= { mpIpVpnIcmpEntry 11 }

       mpIpVpnIcmpInTimestampReps OBJECT-TYPE
              SYNTAX  Counter
              ACCESS  read-only
              STATUS  mandatory
              DESCRIPTION
                      "The number of ICMP Timestamp Reply messages
                      received."
              ::= { mpIpVpnIcmpEntry 12 }

       mpIpVpnIcmpInAddrMasks OBJECT-TYPE
              SYNTAX  Counter
              ACCESS  read-only
              STATUS  mandatory
              DESCRIPTION
                      "The number of ICMP Address Mask Request messages
                      received."
              ::= { mpIpVpnIcmpEntry 13 }

       mpIpVpnIcmpInAddrMaskReps OBJECT-TYPE
              SYNTAX  Counter
              ACCESS  read-only
              STATUS  mandatory
              DESCRIPTION
                      "The number of ICMP Address Mask Reply messages
                      received."
              ::= { mpIpVpnIcmpEntry 14 }

       mpIpVpnIcmpOutMsgs OBJECT-TYPE
              SYNTAX  Counter
              ACCESS  read-only
              STATUS  mandatory
              DESCRIPTION
                      "The total number of ICMP messages which this
                      entity attempted to send.  Note that this counter
                      includes all those counted by mpIpVpnIcmpOutErrors."
              ::= { mpIpVpnIcmpEntry 15 }

       mpIpVpnIcmpOutErrors OBJECT-TYPE
              SYNTAX  Counter
              ACCESS  read-only
              STATUS  mandatory
              DESCRIPTION
                      "The number of ICMP messages which this entity did
                      not send due to problems discovered within ICMP
                      such as a lack of buffers.  This value should not
                      include errors discovered outside the ICMP layer
                      such as the inability of IP to route the resultant
                      datagram.  In some implementations there may be no
                      types of error which contribute to this counter's
                      value."
              ::= { mpIpVpnIcmpEntry 16 }

       mpIpVpnIcmpOutDestUnreachs OBJECT-TYPE
              SYNTAX  Counter
              ACCESS  read-only
              STATUS  mandatory
              DESCRIPTION
                      "The number of ICMP Destination Unreachable
                      messages sent."
              ::= { mpIpVpnIcmpEntry 17 }

       mpIpVpnIcmpOutTimeExcds OBJECT-TYPE
              SYNTAX  Counter
              ACCESS  read-only
              STATUS  mandatory
              DESCRIPTION
                      "The number of ICMP Time Exceeded messages sent."
              ::= { mpIpVpnIcmpEntry 18 }

       mpIpVpnIcmpOutParmProbs OBJECT-TYPE
              SYNTAX  Counter
              ACCESS  read-only
              STATUS  mandatory
              DESCRIPTION
                      "The number of ICMP Parameter Problem messages
                      sent."
              ::= { mpIpVpnIcmpEntry 19 }

       mpIpVpnIcmpOutSrcQuenchs OBJECT-TYPE
              SYNTAX  Counter
              ACCESS  read-only
              STATUS  mandatory
              DESCRIPTION
                      "The number of ICMP Source Quench messages sent."
              ::= { mpIpVpnIcmpEntry 20 }

       mpIpVpnIcmpOutRedirects OBJECT-TYPE
              SYNTAX  Counter
              ACCESS  read-only
              STATUS  mandatory
              DESCRIPTION
                      "The number of ICMP Redirect messages sent.  For a
                      host, this object will always be zero, since hosts
                      do not send redirects."
              ::= { mpIpVpnIcmpEntry 21 }

       mpIpVpnIcmpOutEchos OBJECT-TYPE
              SYNTAX  Counter
              ACCESS  read-only
              STATUS  mandatory
              DESCRIPTION
                      "The number of ICMP Echo (request) messages sent."
              ::= { mpIpVpnIcmpEntry 22 }

       mpIpVpnIcmpOutEchoReps OBJECT-TYPE
              SYNTAX  Counter
              ACCESS  read-only
              STATUS  mandatory
              DESCRIPTION
                      "The number of ICMP Echo Reply messages sent."
              ::= { mpIpVpnIcmpEntry 23 }

       mpIpVpnIcmpOutTimestamps OBJECT-TYPE
              SYNTAX  Counter
              ACCESS  read-only
              STATUS  mandatory
              DESCRIPTION
                      "The number of ICMP Timestamp (request) messages
                      sent."
              ::= { mpIpVpnIcmpEntry 24 }

       mpIpVpnIcmpOutTimestampReps OBJECT-TYPE
              SYNTAX  Counter
              ACCESS  read-only
              STATUS  mandatory
              DESCRIPTION
                      "The number of ICMP Timestamp Reply messages
                      sent."
              ::= { mpIpVpnIcmpEntry 25 }

       mpIpVpnIcmpOutAddrMasks OBJECT-TYPE
              SYNTAX  Counter
              ACCESS  read-only
              STATUS  mandatory
              DESCRIPTION
                      "The number of ICMP Address Mask Request messages
                      sent."
              ::= { mpIpVpnIcmpEntry 26 }

       mpIpVpnIcmpOutAddrMaskReps OBJECT-TYPE
              SYNTAX  Counter
              ACCESS  read-only
              STATUS  mandatory
              DESCRIPTION
                      "The number of ICMP Address Mask Reply messages
                      sent."
              ::= { mpIpVpnIcmpEntry 27 }

-- @015 add end

-- @018 add from

       -- the VPN Ping table

       mpIpVpnPingTable OBJECT-TYPE
              SYNTAX  SEQUENCE OF MpIpVpnPingEntry
              ACCESS  not-accessible
              STATUS  mandatory
              DESCRIPTION "The table of ping management information relevant to
                          this entity's ICMP echo identifier."
              ::= { mpIp 19 }

       mpIpVpnPingEntry OBJECT-TYPE
              SYNTAX  MpIpVpnPingEntry
              ACCESS  not-accessible
              STATUS  mandatory
              DESCRIPTION "The ping management information for one of this
                          entity's ICMP echo identifier."
              INDEX { mpIpVpnPingId }
              ::= { mpIpVpnPingTable 1 }

       MpIpVpnPingEntry ::=
              SEQUENCE {
                  mpIpVpnPingId
                      INTEGER,
                  mpIpVpnPingVpnId
                      INTEGER,
                  mpIpVpnPingTarget
                      IpAddress,
                  mpIpVpnPingRequestSend
                      INTEGER,
                  mpIpVpnPingDataLength
                      INTEGER,
                  mpIpVpnPingSendTos
                      INTEGER,
                  mpIpVpnPingSendTtl
                      INTEGER,
                  mpIpVpnPingSendTimeOut
                      INTEGER,
                  mpIpVpnPingSendInterface
                      INTEGER,
                  mpIpVpnPingStatus
                      INTEGER,
                  mpIpVpnPingResult
                      INTEGER,
                  mpIpVpnPingErrorSourceAddress
                      IpAddress
              }

       mpIpVpnPingId OBJECT-TYPE
              SYNTAX  INTEGER
              ACCESS  read-only
              STATUS  mandatory
              DESCRIPTION "This is the index to identify the ping entry.
                          The value of this index must be assigned uniquely,
                          within the range of 1 - 65535."
              ::= { mpIpVpnPingEntry 1 }

       mpIpVpnPingVpnId OBJECT-TYPE
              SYNTAX  INTEGER
              ACCESS  read-write
              STATUS  mandatory
              DESCRIPTION "The value of this object is the VPNID for this
                          entry, within the range of 1 - 65535."
              ::= { mpIpVpnPingEntry 2 }

       mpIpVpnPingTarget OBJECT-TYPE
              SYNTAX  IpAddress
              ACCESS  read-write
              STATUS  mandatory
              DESCRIPTION "The value of this object is the destination IP
                          address for this entry. This IP address must
                          always be a unicast IP address and it should
                          never be a Class D or E IP address."
              ::= { mpIpVpnPingEntry 3 }

       mpIpVpnPingRequestSend OBJECT-TYPE
              SYNTAX  INTEGER
              ACCESS  read-only
              STATUS  mandatory
              DESCRIPTION "The value of this object is the ping request
                          number of the times."
              ::= { mpIpVpnPingEntry 4 }

       mpIpVpnPingDataLength OBJECT-TYPE
              SYNTAX  INTEGER
              ACCESS  read-write
              STATUS  mandatory
              DESCRIPTION "The value of this object is the ping data
                          length, within the range of 0 - 65507."
              ::= { mpIpVpnPingEntry 5 }

       mpIpVpnPingSendTos OBJECT-TYPE
              SYNTAX  INTEGER
              ACCESS  read-write
              STATUS  mandatory
              DESCRIPTION "The value of this object is the TOS value in
                          ping packet, within the range of 0 - 0xfe."
              ::= { mpIpVpnPingEntry 6 }

       mpIpVpnPingSendTtl OBJECT-TYPE
              SYNTAX  INTEGER
              ACCESS  read-write
              STATUS  mandatory
              DESCRIPTION "The value of this object is the TTL value in
                          ping packet, within the range of 1 - 255."
              ::= { mpIpVpnPingEntry 7 }

       mpIpVpnPingSendTimeOut OBJECT-TYPE
              SYNTAX  INTEGER
              ACCESS  read-write
              STATUS  mandatory
              DESCRIPTION "The value of this object is the ping time out
                          value, within the range of 1 - 60 seconds."
              ::= { mpIpVpnPingEntry 8 }

       mpIpVpnPingSendInterface OBJECT-TYPE
              SYNTAX  INTEGER
              ACCESS  read-write
              STATUS  mandatory
              DESCRIPTION "The value of this object is ifIndex. IP address
                          assigned ifIndex is set as source IP address in
                          ping packets."
              ::= { mpIpVpnPingEntry 9 }

       mpIpVpnPingStatus OBJECT-TYPE
              SYNTAX  INTEGER {
                              create(1),
                              inProgress(2),
                              complete(3),
                              destroy(4)
                              }
              ACCESS  read-write
              STATUS  mandatory
              DESCRIPTION "This object refers to the ping entry status.
                          When this object is set to create(1), ping
                          entry is created. Set to inProgress(2), ping
                          is Started. When a reply or icmp error
                          receiveed and time out occured, the status
                          become complete(3). This object can not set to
                          complete(3). Set to destroy(4), entry is
                          deleted."
              ::= { mpIpVpnPingEntry 10 }

       mpIpVpnPingResult OBJECT-TYPE
              SYNTAX  INTEGER
              ACCESS  read-only
              STATUS  mandatory
              DESCRIPTION "This object refers to the ping result status."
              ::= { mpIpVpnPingEntry 11 }

       mpIpVpnPingErrorSourceAddress OBJECT-TYPE
              SYNTAX  IpAddress
              ACCESS  read-only
              STATUS  mandatory
              DESCRIPTION "This value of this object is the error source
                          IP address in icmp error reply message."
              ::= { mpIpVpnPingEntry 12 }

-- @018 add end


--  ***************************************************************************
--  the MM_Node9110/9120 RIP Group
--  ***************************************************************************

       mpRip2IfConfTable OBJECT-TYPE
               SYNTAX   SEQUENCE OF MpRip2IfConfEntry
               ACCESS   not-accessible
               STATUS   mandatory
               DESCRIPTION "This is the table type object of the RIP sending
               operation mode."
               ::= { mpRip 1 }

       mpRip2IfConfEntry OBJECT-TYPE
               SYNTAX   MpRip2IfConfEntry
               ACCESS   not-accessible
               STATUS   mandatory
               DESCRIPTION "This is the table entry of mpRip2IfconfTable."
               INDEX { mpRip2IfConfAddress }
               ::= { mpRip2IfConfTable 1 }

       MpRip2IfConfEntry ::=
               SEQUENCE {
                        mpRip2IfConfAddress 
                                     IpAddress,
                        mpRip2IfConfPoisoned
                                     INTEGER,
-- @008 add from
                        mpRip2IfConfAddress
                                     IpAddress,
                        mpRip2IfConfPoisoned
                                     INTEGER,
                        mpRip2IfConfSplitHorizon
                                     INTEGER,
                        mpRip2IfConfHostAdvertise
                                     INTEGER,
                        mpRip2IfConfInOffset
                                     INTEGER,
                        mpRip2IfConfOutOffset
                                     INTEGER,
                        mpRip2IfConfDefType
                                     INTEGER,
                        mpRip2IfConfDefMetric
                                     INTEGER,
                        mpRip2IfConfDefAddress
                                     IpAddress,
                        mpRip2IfConfDefTag
                                     INTEGER,
                        mpRip2IfConfDefProtocol
                                     INTEGER,
                        mpRip2IfConfDefImportList
                                     INTEGER,
                        mpRip2IfConfRoutePriority
                                     INTEGER
-- @008 add end
                        }

       mpRip2IfConfAddress OBJECT-TYPE
               SYNTAX  IpAddress
               ACCESS  read-only
               STATUS  mandatory
               DESCRIPTION "This object specifies the IP address of the 
                           interface to which the RIP packet is sent."
               ::= { mpRip2IfConfEntry 1 }

       mpRip2IfConfPoisoned OBJECT-TYPE
               SYNTAX  INTEGER {
                               enabled(1),
                               disabled(2)
                               }
               ACCESS  read-write
               STATUS  mandatory
               DESCRIPTION "This object specifies the RIP sending mode of
                           this interface. In case of Sprit Horizon with
                           Poisoned Reverse, the value '1' is set to this
                           object. In case of Sprit Horizon, the value '2'
                           is set to this object."
               ::= { mpRip2IfConfEntry 2 }

-- @008 add from
       mpRip2IfConfSplitHorizon OBJECT-TYPE
               SYNTAX  INTEGER { 
                               enabled(1), 
                               disabled(2) 
                               }
               ACCESS  read-write
               STATUS  mandatory
               DESCRIPTION "The flag about Split-Horizon of this interface."
               ::= { mpRip2IfConfEntry 3 }

       mpRip2IfConfHostAdvertise OBJECT-TYPE
               SYNTAX  INTEGER {
                               enabled(1),
                               disabled(2)
                               }
               ACCESS  read-write
               STATUS  mandatory
               DESCRIPTION "The flag which shows whether IP address of    
                           interface that condition is Down is transmitted 
                           as Host Route to this Interface."               
               ::= { mpRip2IfConfEntry 4 }

       mpRip2IfConfInOffset OBJECT-TYPE
               SYNTAX  INTEGER (0..15)
               ACCESS  read-write
               STATUS  mandatory
               DESCRIPTION "This object specifies the metric value to be added
                           to the route information of RIP-response which is 
                           received from this interface."
               ::= { mpRip2IfConfEntry 5 }

       mpRip2IfConfOutOffset OBJECT-TYPE
               SYNTAX  INTEGER (0..15)
               ACCESS  read-write
               STATUS  mandatory
               DESCRIPTION "This object specifies the metric value to be added
                           to the route information of RIP-response which is
                           sent to this interface."
               ::= { mpRip2IfConfEntry 6 }

       mpRip2IfConfDefType OBJECT-TYPE
               SYNTAX  INTEGER { 
                               no(1),
                               distribute(2),
                               always(3),
                               importList(4) 
                               }
               ACCESS  read-write
               STATUS  mandatory
               DESCRIPTION "The timing when default route is advertised 
                           to this interface."
               ::= { mpRip2IfConfEntry 7 }

       mpRip2IfConfDefMetric OBJECT-TYPE
               SYNTAX  INTEGER (1..15)
               ACCESS  read-write
               STATUS  mandatory
               DESCRIPTION "The metric value of default route to be used
                           when the advertised timing(mpRip2IfConfDefType)
                           is set to 'always'."
               ::= { mpRip2IfConfEntry 8 }

       mpRip2IfConfDefAddress OBJECT-TYPE
               SYNTAX  IpAddress
               ACCESS  read-write
               STATUS  mandatory
               DESCRIPTION "The  next-hop  IP addess  of default  route 
                           to  be used  when  the  advertised  timing
                           (mpRip2IfConfDefType) is  set  to 'always'."
               ::= { mpRip2IfConfEntry 9 }

       mpRip2IfConfDefTag OBJECT-TYPE
               SYNTAX  INTEGER(1..65535)
               ACCESS  read-write
               STATUS  mandatory
               DESCRIPTION "The route tag of default route to be used
                           when the advertised timing(mpRip2IfConfDefType)
                           is set to 'always'."
               ::= { mpRip2IfConfEntry 10 }

       mpRip2IfConfDefProtocol OBJECT-TYPE
               SYNTAX  INTEGER { 
                               local(2), 
                               static(3),
                               ospf(13) 
                               }
               ACCESS  read-write
               STATUS  mandatory
               DESCRIPTION "The protocol of routing table to be used for 
                           condition decision when the advertised timing
                           (mpRip2IfConfDefType) is set to 'importList'."
               ::= { mpRip2IfConfEntry 11 }

       mpRip2IfConfDefImportList OBJECT-TYPE
               SYNTAX  INTEGER
               ACCESS  read-write
               STATUS  mandatory
               DESCRIPTION "The route tag of default route to be used
                           when the advertised timing(mpRip2IfConfDefType)
                           is set to 'always'."
               ::= { mpRip2IfConfEntry 12 }

       mpRip2IfConfRoutePriority OBJECT-TYPE
               SYNTAX  INTEGER (0..255)
               ACCESS  read-write
               STATUS  mandatory
               DESCRIPTION "The route priority value which is used when 
                           the route information of RIP-response received 
                           from this interface is reflected. The value 0
                           means route priority is not used for each 
                           interface."
               ::= { mpRip2IfConfEntry 13 }

       mpRip2PeerTable OBJECT-TYPE
               SYNTAX  SEQUENCE OF MpRip2PeerEntry 
               ACCESS  not-accessible
               STATUS  mandatory
               DESCRIPTION "The Neighbor information table to transmit
                           RIP-response with unicast."
               ::= { mpRip 2 }

       mpRip2PeerEntry OBJECT-TYPE
               SYNTAX  MpRip2PeerEntry 
               ACCESS  not-accessible
               STATUS  mandatory
               DESCRIPTION "The Neighbor information Entry to transmit 
                           RIP-response with unicast."
               INDEX { mpRip2PeerAddress }
               ::= { mpRip2PeerTable 1 }

       MpRip2PeerEntry ::=
               SEQUENCE {
                        mpRip2PeerAddress
                                     IpAddress,
                        mpRip2PeerVersion
                                     INTEGER,
                        mpRip2PeerStatus
                                     RowStatus
                        }

       mpRip2PeerAddress OBJECT-TYPE
               SYNTAX  IpAddress
               ACCESS  read-only
               STATUS  mandatory
               DESCRIPTION "This object specifies IP Address of Neighbor 
                           which transmits RIP-response with unicast."
               ::= { mpRip2PeerEntry 1 }

       mpRip2PeerVersion OBJECT-TYPE
            SYNTAX   INTEGER {
                             doNotSend(1),
                             ripVersion1(2),
                             rip1Compatible(3),
                             ripVersion2(4)
                             }
               ACCESS  read-write
               STATUS  mandatory
               DESCRIPTION "This object specifies version of RIP-response."
               ::= { mpRip2PeerEntry 2 }

        mpRip2PeerStatus OBJECT-TYPE
               SYNTAX  RowStatus
               ACCESS  read-write
               STATUS  mandatory
               DESCRIPTION "This object is used to create, delete, or modify
                           this table entry."                               
               ::= { mpRip2PeerEntry 3 }

       mpRip2ImportListTable OBJECT-TYPE
               SYNTAX  SEQUENCE OF MpRip2ImportListEntry
               ACCESS  not-accessible
               STATUS  mandatory
               DESCRIPTION "The table for importing route information 
                           to other routing protocols or RIP."
               ::= { mpRip 3 }

       mpRip2ImportListEntry OBJECT-TYPE
               SYNTAX  MpRip2ImportListEntry
               ACCESS  not-accessible
               STATUS  mandatory
               DESCRIPTION "The table for importing route information 
                           to other routing protocols or RIP."       
               INDEX { mpRip2ImportListProtocol, 
                       mpRip2ImportListNumber }
               ::= { mpRip2ImportListTable 1 }

       MpRip2ImportListEntry ::=
               SEQUENCE {
                        mpRip2ImportListProtocol
                                     INTEGER,
                        mpRip2ImportListNumber
                                     INTEGER,
                        mpRip2ImportListStatus
                                     INTEGER
                        }

       mpRip2ImportListProtocol OBJECT-TYPE
               SYNTAX  INTEGER {
                                local(2),
                                static(3),
                                ospf(13)
                                }
               ACCESS  read-only
               STATUS  mandatory
               DESCRIPTION "This object specifies protocol of IP routing 
                           table."
               ::= { mpRip2ImportListEntry 1 }

       mpRip2ImportListNumber OBJECT-TYPE
               SYNTAX  INTEGER
               ACCESS  read-only
               STATUS  mandatory
               DESCRIPTION "This object specifies import list number."
               ::= { mpRip2ImportListEntry 2 }

       mpRip2ImportListStatus OBJECT-TYPE
               SYNTAX  RowStatus
               ACCESS  read-write
               STATUS  mandatory
               DESCRIPTION "This object is used to create, delete, or modify
                           this table entry."                               
               ::= { mpRip2ImportListEntry 3 }

       mpRip2NetworkPriorityTable OBJECT-TYPE
               SYNTAX  SEQUENCE OF MpRip2NetworkPriorityEntry 
               ACCESS  not-accessible
               STATUS  mandatory
               DESCRIPTION "The table to specify route priority to each
                            network at creating IP routing table."
               ::= { mpRip 4 }

       mpRip2NetworkPriorityEntry OBJECT-TYPE
               SYNTAX  MpRip2NetworkPriorityEntry
               ACCESS  not-accessible
               STATUS  mandatory
               DESCRIPTION "The entry to specify route priority to each
                            network at creating IP routing table."    
               INDEX { mpRip2NetworkPriorityAddr, 
                       mpRip2NetworkPriorityMask }
               ::= { mpRip2NetworkPriorityTable 1 }

       MpRip2NetworkPriorityEntry ::= 
               SEQUENCE {
                        mpRip2NetworkPriorityAddr
                                     IpAddress,
                        mpRip2NetworkPriorityMask
                                     IpAddress,
                        mpRip2NetworkPriorityValue
                                     INTEGER,
                        mpRip2NetworkPriorityStatus
                                     RowStatus
                        }

        mpRip2NetworkPriorityAddr OBJECT-TYPE
               SYNTAX  IpAddress
               ACCESS  read-only
               STATUS  mandatory
               DESCRIPTION "This object specifies network IP address."
               ::= { mpRip2NetworkPriorityEntry 1 }

        mpRip2NetworkPriorityMask OBJECT-TYPE
               SYNTAX  IpAddress
               ACCESS  read-only
               STATUS  mandatory
               DESCRIPTION "This object specifies network mask."
               ::= { mpRip2NetworkPriorityEntry 2 }

        mpRip2NetworkPriorityValue OBJECT-TYPE
               SYNTAX  INTEGER (1..255)
               ACCESS  read-write
               STATUS  mandatory
               DESCRIPTION "This object specifies the value of route 
                           priority."
               ::= { mpRip2NetworkPriorityEntry 3 }

        mpRip2NetworkPriorityStatus OBJECT-TYPE
               SYNTAX  RowStatus
               ACCESS  read-write
               STATUS  mandatory
               DESCRIPTION "This object is used to create, delete, or modify
                           this table entry."                               
               ::= { mpRip2NetworkPriorityEntry 4 }

        mpRip2RoutePriority OBJECT-TYPE
            SYNTAX   INTEGER(1..255)
               ACCESS  read-write
               STATUS  mandatory
               DESCRIPTION "The route priority value to be used when the 
                           route information of RIP-response received is 
                           reflected. It is used  when the route priority
                            of interface has not been registered 
                           (mpRip2IfConfRoutePriority is 0) and route 
                           information doesn't correspond to any network 
                           route priority table(mpRip2NetworkPriorityTable)."
               ::= { mpRip 5 }
-- @008 add end

-- ***************************************************************************
-- Snmp Community and Trap Community name table.
-- ***************************************************************************

   --  Implementation of this group is mandatory for all the SanFran systems.

   mpSnmpCommunityTable OBJECT-TYPE
           SYNTAX  SEQUENCE OF MpSnmpCommunityEntry
           ACCESS  not-accessible
           STATUS  mandatory
           DESCRIPTION "The community table (1-5 entries).  This table
                        lists community strings and their access levels.
                        When a Snmp message is received by this entity, the
                        community string in the message is compared with
                        this table to determine access rights of sender."
           ::= { mpSnmp 1 }

   mpSnmpCommunityEntry  OBJECT-TYPE
           SYNTAX  MpSnmpCommunityEntry
           ACCESS  not-accessible
           STATUS  mandatory
           DESCRIPTION   "A community table entry."
           INDEX         { mpSnmpCommunityIndex, mpSnmpCommunityAddr }
           ::= { mpSnmpCommunityTable 1 }

   MpSnmpCommunityEntry ::=
           SEQUENCE  {
                     mpSnmpCommunityIndex  INTEGER,
                     mpSnmpCommunityStatus INTEGER,
                     mpSnmpCommunityAccess INTEGER,
                     mpSnmpCommunityAddr IpAddress,
                     mpSnmpCommunityName DisplayString
                     }

   mpSnmpCommunityIndex OBJECT-TYPE
           SYNTAX  INTEGER
           ACCESS  not-accessible
           STATUS  mandatory
           DESCRIPTION "This object specifies the addition/deletion of a
                        particular trap community."
           ::= { mpSnmpCommunityEntry 1 }

   mpSnmpCommunityStatus OBJECT-TYPE
           SYNTAX  INTEGER {
                            valid(1),      -- add this entry
                            notinuseyet(2),-- after setting it to valid and
                                           -- before
                                           -- setting the community name
                            invalid(3)     -- delete this entry
                            }
           ACCESS  not-accessible 
           STATUS  mandatory
           DESCRIPTION   "This object specifies the addition/deletion of a
                          particular community. Entries 1 and 2 are reserved
                          for public access( read-only ) and NEC's NMS read
                          -write."
           ::= { mpSnmpCommunityEntry 2 }

   mpSnmpCommunityAccess OBJECT-TYPE
           SYNTAX  INTEGER {
                           readOnly(1),
                           readWrite(2)
                           }
           ACCESS  not-accessible 
           STATUS  mandatory
           DESCRIPTION  "A value of readWrite(2) allows the community to
                         read and write all objects in the MIB.  A value of
                         readOnly(1) allows the community to read all objs."
           ::= { mpSnmpCommunityEntry 3 }

   mpSnmpCommunityAddr     OBJECT-TYPE
           SYNTAX  IpAddress
           ACCESS  not-accessible 
           STATUS  mandatory
           DESCRIPTION  "IP address of the registered NMS. This is actually
                         a lists of IP addresses, maximum of 5. A special
                         indexing must be implemented to get all the list
                         of IP addresses for each entry."
           ::= { mpSnmpCommunityEntry 4 }

   mpSnmpCommunityName OBJECT-TYPE
           SYNTAX  DisplayString (SIZE (1..64))
           ACCESS  not-accessible 
           STATUS  mandatory
           DESCRIPTION "Configurable community string with access rights
                        defined by the value of sysCommunityAccess."
           ::= { mpSnmpCommunityEntry 5 }


   mpSnmpTrapCommunityTable OBJECT-TYPE
           SYNTAX  SEQUENCE OF MpSnmpTrapCommunityEntry
           ACCESS  not-accessible
           STATUS  mandatory
           DESCRIPTION  "The trap receiver table (0 to 5 entries).  This
                        table lists the addresses of stations that should
                        receive trap messages from this
                        entity when an exception condition occurs."
           ::= { mpSnmp 2 }

   mpSnmpTrapCommunityEntry OBJECT-TYPE
           SYNTAX  MpSnmpTrapCommunityEntry
           ACCESS  not-accessible
           STATUS  mandatory
           DESCRIPTION  "A trap receiver table entry."
           INDEX  { mpSnmpTrapCommunityIndex }
           ::= { mpSnmpTrapCommunityTable 1 }

   MpSnmpTrapCommunityEntry ::=
           SEQUENCE  {
                     mpSnmpTrapCommunityIndex  INTEGER,
                     mpSnmpTrapCommunityStatus INTEGER,
                     mpSnmpTrapCommunityType   INTEGER,
                     mpSnmpTrapCommunityAddr   IpAddress,
                     mpSnmpTrapCommunityName   DisplayString
                      }

   mpSnmpTrapCommunityIndex OBJECT-TYPE
           SYNTAX  INTEGER
           ACCESS  not-accessible 
           STATUS  mandatory
           DESCRIPTION  "This object specifies the row for a particular
                        trap community."
           ::= { mpSnmpTrapCommunityEntry 1 }

   mpSnmpTrapCommunityStatus OBJECT-TYPE
           SYNTAX  INTEGER {
                           valid(1),      -- add this entry
                           notinuseyet(2),-- after setting it to valid and
                                          -- before
                                          -- setting the community name
                           invalid(3)     -- delete this entry
                           }
           ACCESS  not-accessible 
           STATUS  mandatory
           DESCRIPTION "This object specifies the addition/deletion of a
                       particular trap community."
           ::= { mpSnmpTrapCommunityEntry 2 }

   mpSnmpTrapCommunityType OBJECT-TYPE
           SYNTAX  INTEGER {
                           networkmanager(1), -- only one supported
                           telephone(2),      -- not yet supported
                           faxmachine(3),     -- not yet supported
                           pager(4),          -- not yet supported
                           emailaddress(5)    -- not yet supported
                           }
           ACCESS  not-accessible 
           STATUS  mandatory
           DESCRIPTION  "This object specifies the recipient of a
                        generated trap.  AS of the moment only a
                        NMS station is supported."
           ::= { mpSnmpTrapCommunityEntry 3 }

   mpSnmpTrapCommunityAddr OBJECT-TYPE
           SYNTAX  IpAddress
           ACCESS  not-accessible 
           STATUS  mandatory
           DESCRIPTION  "For type NMS,IP address for trap receiver.
                        (For now type NMS is yet supported).
                        For telephone,fax, and pager, phone number.
                        For email, this is an Internet email address."
           ::= { mpSnmpTrapCommunityEntry 4 }

   mpSnmpTrapCommunityName OBJECT-TYPE
           SYNTAX  DisplayString (SIZE (1..64))
           ACCESS  not-accessible 
           STATUS  mandatory
           DESCRIPTION  "Community string used for trap messages to this
                        trap receiver."
           ::= { mpSnmpTrapCommunityEntry 5 }


-- ロックMIBグループ  @008
   mpSnmpLockMib        OBJECT IDENTIFIER ::= { mpSnmp 3 }

-- ロックMIB IPアドレス  @008
   mpSnmpLockMibIPaddress       OBJECT-TYPE
        SYNTAX       IpAddress
        ACCESS       read-write
        STATUS       mandatory
        DESCRIPTION   "if IPaddress is 0.0.0.0,  NMS doesn't SET LockMIB.
                       if not, only 1 NMS is successing to SET LockMIB.
                       note : NMS must SET own IPaddress to LockMIB before 
                       NMS tries to SET some specific MIB"
-- このMIBの値が 0.0.0.0 であれば、どのNMSも ロックMIBにSETしていないことを示す。
-- 0.0.0.0 以外であれば、既に、ロックMIBをSETしているNMSが存在することを示す。
-- 注．NMS は、特定の排他制御が必要なMIBに対するSET処理を行う前に ロックMIBへの自IPアドレスの
--     設定が成功していることを確認しなければならない。
        ::= { mpSnmpLockMib 1 }


--  ***************************************************************************
--  the SanFran Statistics Group
--  ***************************************************************************

   --  Implementation of this group is mandatory for all the SanFran systems.


       mpMonitorGroupTable   OBJECT-TYPE
              SYNTAX   SEQUENCE OF MpMonitorGroupEntry
              ACCESS   not-accessible
              STATUS   mandatory
              DESCRIPTION "Monitoring Group related details."
              ::= { mpStats 1 }


       mpMonitorGroupEntry OBJECT-TYPE
              SYNTAX   MpMonitorGroupEntry
              ACCESS   not-accessible
              STATUS   mandatory
              DESCRIPTION "Details for a group of monitored statistics."
              INDEX { mpMonGrpObjectInstance, mpMonGrpObjectId }
              ::= { mpMonitorGroupTable 1 }


       MpMonitorGroupEntry   ::=
         SEQUENCE {
                  mpMonGrpIndex INTEGER,
                  mpMonGrpObjectId OBJECT IDENTIFIER,
                  mpMonGrpObjectInstance INTEGER,
                  mpMonGrpPollInt INTEGER,
                  mpMonGrpStatus INTEGER,
                  mpMonGrpName DisplayString
                  }


       mpMonGrpIndex OBJECT-TYPE
              SYNTAX   INTEGER
              ACCESS   not-accessible
              STATUS   mandatory
              DESCRIPTION "Specifies the table entry."
              ::= { mpMonitorGroupEntry 1 }


       mpMonGrpObjectId   OBJECT-TYPE
              SYNTAX   OBJECT IDENTIFIER
              ACCESS   not-accessible
              STATUS   mandatory
              DESCRIPTION "Name of the port/module to which the info in the
                          table entry applies to."
              ::= { mpMonitorGroupEntry 2 }


       mpMonGrpObjectInstance OBJECT-TYPE
              SYNTAX   INTEGER
              ACCESS   not-accessible
              STATUS   mandatory
              DESCRIPTION "Instance to which the info in the table entry 
                          applies to."
              ::= { mpMonitorGroupEntry 3 }


       mpMonGrpPollInt OBJECT-TYPE
              SYNTAX   INTEGER
              ACCESS   not-accessible
              STATUS   mandatory
              DESCRIPTION "Interval at which the polling for values is done."
              ::= { mpMonitorGroupEntry 4 }


       mpMonGrpStatus OBJECT-TYPE
              SYNTAX   INTEGER{
                       enabled(1),
                       disabled(2)
                       }
              ACCESS   not-accessible
              STATUS   mandatory
              DESCRIPTION "Setting this field to disable deletes the entry from
                           the list of monitored groups."
              ::= { mpMonitorGroupEntry 5 }

       mpMonGrpName OBJECT-TYPE
              SYNTAX   DisplayString (SIZE (0..80))
              ACCESS   not-accessible
              STATUS   mandatory
              DESCRIPTION "The text value of the monitor group.  For release 1,
                          read-only but release 2 will allow the user to set
                          the monitor group name to any textual description."
              ::= { mpMonitorGroupEntry 6 }


        mpStatObjectTable OBJECT-TYPE
             SYNTAX  SEQUENCE OF MpStatObjectEntry
             ACCESS  not-accessible
             STATUS  mandatory
             DESCRIPTION "Object related statistics details."
             ::= { mpStats 2 }


        mpStatObjectEntry OBJECT-TYPE
             SYNTAX  MpStatObjectEntry
             ACCESS  not-accessible
             STATUS  mandatory
             DESCRIPTION "Details of statistics."
             INDEX { mpStatObjectGroupId, mpStatObjectId }
             ::= { mpStatObjectTable 1 } 


        MpStatObjectEntry ::=
             SEQUENCE {
                      mpStatObjectIndex  INTEGER,
                      mpStatObjectGroupId  INTEGER,
                      mpStatObjectId  OBJECT IDENTIFIER,
                      mpStatObjectName DisplayString,
                      mpStatObjectCurValue  INTEGER,
                      mpStatObjectCumRate  INTEGER,
                      mpStatObjectIntRate  INTEGER
                      }


        mpStatObjectIndex  OBJECT-TYPE
             SYNTAX  INTEGER
             ACCESS  not-accessible
             STATUS  mandatory
             DESCRIPTION "Specifies the table entry."
             ::= { mpStatObjectEntry 1 }


        mpStatObjectGroupId  OBJECT-TYPE
             SYNTAX  INTEGER
             ACCESS  not-accessible
             STATUS  mandatory
             DESCRIPTION "Monitoring Group that this obj belongs to."
             ::= { mpStatObjectEntry 2 }


        mpStatObjectId  OBJECT-TYPE
             SYNTAX  OBJECT IDENTIFIER
             ACCESS  not-accessible
             STATUS  mandatory
             DESCRIPTION "OID of the object."
             ::= { mpStatObjectEntry 3 }


        mpStatObjectName  OBJECT-TYPE
             SYNTAX  DisplayString(SIZE (0..80))
             ACCESS  not-accessible
             STATUS  mandatory
             DESCRIPTION "Textual equivalent of the object."
             ::= { mpStatObjectEntry 4 }


        mpStatObjectCurValue  OBJECT-TYPE
             SYNTAX  INTEGER
             ACCESS  not-accessible
             STATUS  mandatory
             DESCRIPTION "Current value of the object."
             ::= { mpStatObjectEntry 5 }

        mpStatObjectCumRate  OBJECT-TYPE
             SYNTAX  INTEGER
             ACCESS  not-accessible
             STATUS  mandatory
             DESCRIPTION "Cumulative rate of the object."
             ::= { mpStatObjectEntry 6 }


        mpStatObjectIntRate  OBJECT-TYPE
             SYNTAX  INTEGER
             ACCESS  not-accessible
             STATUS  mandatory
             DESCRIPTION "Rate of change of the objetc's statistics."
             ::= { mpStatObjectEntry 7 }

--  ***************************************************************************
--  the MM_Node9110/9120 CLI Group
--  ***************************************************************************

   --  Implementation of this group is mandatory for all the MM_Node9110/9120 systems.

       mpCliOperatorTable OBJECT-TYPE
               SYNTAX   SEQUENCE OF MpCliOperatorEntry
               ACCESS   not-accessible
               STATUS   mandatory
               DESCRIPTION "Indicates the table of operator mode user for CLI"
               ::= { mpCli 1 }

       mpCliOperatorEntry OBJECT-TYPE
               SYNTAX   MpCliOperatorEntry
               ACCESS   not-accessible
               STATUS   mandatory
               DESCRIPTION "Indicates the entry of operator mode user
                           information."
               INDEX { mpCliOperatorIndex }
               ::= { mpCliOperatorTable 1 }

       MpCliOperatorEntry  ::=
               SEQUENCE {
                         mpCliOperatorIndex
                            INTEGER,
                         mpCliOperatorName
                            DisplayString,
                         mpCliOperatorPasswd
                            DisplayString,
                         mpCliOperatorLoginPasswd
                            DisplayString,
                         mpCliOperatorStatus
                            INTEGER
                        }

       mpCliOperatorIndex OBJECT-TYPE
               SYNTAX  INTEGER
               ACCESS  read-only
               STATUS  mandatory
               DESCRIPTION "This is the index to identify the existing 
                            operator mode user."
               ::= { mpCliOperatorEntry 1 }

       mpCliOperatorName OBJECT-TYPE
               SYNTAX  DisplayString(SIZE (0..40)) 
               ACCESS  read-write
               STATUS  mandatory
               DESCRIPTION "This object is the operator user name."
               ::= { mpCliOperatorEntry 2 }

       mpCliOperatorPasswd OBJECT-TYPE
               SYNTAX  DisplayString(SIZE (0..40)) 
               ACCESS  read-write
               STATUS  mandatory
               DESCRIPTION "This object is the operator user password 
                           which is used for user login."
               ::= { mpCliOperatorEntry 3 }

       mpCliOperatorLoginPasswd OBJECT-TYPE
               SYNTAX  DisplayString(SIZE (0..40)) 
               ACCESS  read-write
               STATUS  mandatory
               DESCRIPTION "This objects is the operator user password 
                           entered by user at login." 
               ::= { mpCliOperatorEntry 4 }

       mpCliOperatorStatus OBJECT-TYPE
               SYNTAX  INTEGER {
                               valid(1),
                               notinuseyet(2),
                               invalid(3)
                               }
               ACCESS  read-write 
               STATUS  mandatory
               DESCRIPTION "This object specifies the addition/deletion of a
                           operator."
               ::= { mpCliOperatorEntry 5 }


       mpCliSupervisorTable OBJECT-TYPE
               SYNTAX   SEQUENCE OF MpCliSupervisorEntry
               ACCESS   not-accessible
               STATUS   mandatory
               DESCRIPTION "Indicates the table of supervisor mode user for CLI"
               ::= { mpCli 2 }

       mpCliSupervisorEntry OBJECT-TYPE
               SYNTAX   MpCliSupervisorEntry
               ACCESS   not-accessible
               STATUS   mandatory
               DESCRIPTION "Indicates the entry of supervisor mode user
                           information."
               INDEX { mpCliSupervisorIndex }
               ::= { mpCliSupervisorTable 1 }

       MpCliSupervisorEntry  ::=
               SEQUENCE {
                         mpCliSupervisorIndex
                            INTEGER,
                         mpCliSupervisorName
                            DisplayString,
                         mpCliSupervisorPasswd
                            DisplayString,
                         mpCliSupervisorLoginPasswd
                            DisplayString,
                         mpCliSupervisorStatus
                            INTEGER
                        }

       mpCliSupervisorIndex OBJECT-TYPE
               SYNTAX  INTEGER
               ACCESS  read-only
               STATUS  mandatory
               DESCRIPTION "This is the index to identify the existing 
                            supervisor mode user"
               ::= { mpCliSupervisorEntry 1 }

       mpCliSupervisorName OBJECT-TYPE
               SYNTAX  DisplayString(SIZE (0..40)) 
               ACCESS  read-write
               STATUS  mandatory
               DESCRIPTION "This object is the supervisor user name."
               ::= { mpCliSupervisorEntry 2 }

       mpCliSupervisorPasswd OBJECT-TYPE
               SYNTAX  DisplayString(SIZE (0..40)) 
               ACCESS  read-write
               STATUS  mandatory
               DESCRIPTION "This object is the supervisor user 
                           password which is used for user login."
               ::= { mpCliSupervisorEntry 3 }

       mpCliSupervisorLoginPasswd OBJECT-TYPE
               SYNTAX  DisplayString(SIZE (0..40)) 
               ACCESS  read-write
               STATUS  mandatory
               DESCRIPTION "This objects is the supervisor user password 
                           entered by user at login."
               ::= { mpCliSupervisorEntry 4 }

       mpCliSupervisorStatus OBJECT-TYPE
               SYNTAX  INTEGER {
                               valid(1),
                               notinuseyet(2),
                               invalid(3)
                               }
               ACCESS  read-write
               STATUS  mandatory
               DESCRIPTION "This object specifies the addition/deletion of a
                           supervisor."
               ::= { mpCliSupervisorEntry 5 }

--  ***************************************************************************
--  the SanFran ATM Group
--  ***************************************************************************

   --  Implementation of this group is mandatory for all the SanFran systems.


       mpAtmInterfaceConfTable OBJECT-TYPE
               SYNTAX   SEQUENCE OF MpAtmInterfaceConfEntry
               ACCESS   not-accessible
               STATUS   mandatory
               DESCRIPTION "This table contains ATM local interface
                            configuration parameters, one entry per ATM
                            interface port."
               ::= { mpAtm 1 }

       mpAtmInterfaceConfEntry OBJECT-TYPE
               SYNTAX   MpAtmInterfaceConfEntry
               ACCESS   not-accessible
               STATUS   mandatory
               DESCRIPTION "This list contains ATM interface configuration
                            parameters and state variables."
               INDEX { mpAtmInterfaceIfIndex }
               ::= { mpAtmInterfaceConfTable  1 }

       MpAtmInterfaceConfEntry ::=
               SEQUENCE {
                        mpAtmInterfaceIfIndex  INTEGER,
                        mpAtmInterfaceAdminPrefix  OCTET STRING,
                        mpAtmInterfaceAdminEsi  OCTET STRING,
                        mpAtmInterfaceMaxVpiVciBits  INTEGER   
                        }  

       mpAtmInterfaceIfIndex OBJECT-TYPE
               SYNTAX  INTEGER
               ACCESS  read-only
               STATUS  mandatory
               DESCRIPTION "Indicates the index value to identify the
                            ATM interface in this equipment. Each ATM
                            interface identified by this object is the 
                            same interface identified by the same number
                            of ifIndex."
               ::= { mpAtmInterfaceConfEntry 1 }

       mpAtmInterfaceAdminPrefix OBJECT-TYPE
               SYNTAX  OCTET STRING (SIZE(0 | 13))
               ACCESS  read-write
               STATUS  mandatory
               DESCRIPTION "An prefix assigned for administrative 
                            purpose. This value is displayed as the
                            instance of atmInterfaceAdminAddress
                            object of ATM MIB."
               ::= { mpAtmInterfaceConfEntry 2 } 

       mpAtmInterfaceAdminEsi OBJECT-TYPE
               SYNTAX  OCTET STRING (SIZE(0 | 6))
               ACCESS  read-write
               STATUS  mandatory
               DESCRIPTION "An ESI assigned for administrative 
                            purpose. This value is displayed as the
                            instance of atmInterfaceAdminAddress
                            object of ATM MIB."
               ::= { mpAtmInterfaceConfEntry 3 }

       mpAtmInterfaceMaxVpiVciBits OBJECT-TYPE
               SYNTAX  INTEGER
               ACCESS  read-only
               STATUS  mandatory
               DESCRIPTION "This object sets the maximum number of
                            the sum of VPI/VCI bit number that are
                            able to use at this interface."
               ::= { mpAtmInterfaceConfEntry 4 } 

       mpAtmVccConfigTable OBJECT-TYPE
               SYNTAX   SEQUENCE OF MpAtmVccConfigEntry
               ACCESS   not-accessible
               STATUS   mandatory
               DESCRIPTION "This table contains VCC configuration 
                            parameters, one entry per ATM interface
                            port."
               ::= { mpAtm 2 }

       mpAtmVccConfigEntry OBJECT-TYPE
               SYNTAX   MpAtmVccConfigEntry
               ACCESS   not-accessible
               STATUS   mandatory
               DESCRIPTION "This list contains VCC configuration
                            parameters and state variables."
               INDEX    { mpAtmVccIfIndex }
               ::= { mpAtmVccConfigTable 1 }

       MpAtmVccConfigEntry ::=
               SEQUENCE {
                        mpAtmVccIfIndex  INTEGER,
                        mpAtmVccFrameFormat  INTEGER,
                        mpAtmVccF4OamSupport  INTEGER,
                        mpAtmVccF5OamSupport  INTEGER,
                        mpAtmVccFailTimerLof  INTEGER,
                        mpAtmVccFailTimerLos  INTEGER,
                        mpAtmVccRecoverTimerLof  INTEGER,
                        mpAtmVccRecoverTimerLos  INTEGER,
                        mpAtmVccFailTimerLop  INTEGER,    -- add @003
                        mpAtmVccRecoverTimerLop  INTEGER, -- add @003
                        mpAtmVccCdv  INTEGER,             -- add @003
                        mpAtmVccClockMode  INTEGER        -- add @003
                        }  

       mpAtmVccIfIndex OBJECT-TYPE
               SYNTAX  INTEGER
               ACCESS  read-only
               STATUS  mandatory
               DESCRIPTION "Indicates the index value to identify the
                            ATM interface in this equipment. Each ATM
                            interface identified by this object is the 
                            same interface identified by the same number
                            of ifIndex."
               ::= { mpAtmVccConfigEntry 1 }

       mpAtmVccFrameFormat OBJECT-TYPE
               SYNTAX  INTEGER {
                               sonet(1),
                               sdh(2)
                               }
               ACCESS  read-write
               STATUS  mandatory
               DESCRIPTION "The type of frame format for use 
                            at this ATM interface."
               ::= { mpAtmVccConfigEntry 2 }

       mpAtmVccF4OamSupport OBJECT-TYPE
               SYNTAX   INTEGER { 
                                support(1), 
                                nonSupport(2) 
                                }              
               ACCESS   read-write
               STATUS   mandatory
               DESCRIPTION "Indicates whether the F4 OAM functionality is 
                           supported or not, for the ATM interface of this 
                           equipment. This object can be modified only when all 
                           the ATM interfaces are blocked. If it is set to '1', 
                           the F5 OAM functionality is supported. If it is set 
                           to '2', it is not supported."
               ::= { mpAtmVccConfigEntry 3 }

       mpAtmVccF5OamSupport OBJECT-TYPE
               SYNTAX   INTEGER { 
                                support(1), 
                                nonSupport(2) 
                                }              
               ACCESS   read-write
               STATUS   mandatory
               DESCRIPTION "Indicates whether the F5 OAM functionality is 
                           supported or not, for the ATM interface of this 
                           equipment. This object can be modified only when all 
                           the ATM interfaces are blocked. If it is set to '1', 
                           the F5 OAM functionality is supported. If it is set 
                           to '2', it is not supported."
               ::= { mpAtmVccConfigEntry 4 }

       mpAtmVccFailTimerLof OBJECT-TYPE
               SYNTAX   INTEGER          
                                        -- value = 100*n (n=1,2,3,..,600)
               ACCESS   read-write
               STATUS   mandatory
               DESCRIPTION "It is used to set the timer value of the LOF (Loss 
                           of Frames) failure detection timer (msec). It is 
                           possible to set the integer of a multiple of 100."
               ::= { mpAtmVccConfigEntry 5 }

       mpAtmVccFailTimerLos OBJECT-TYPE
               SYNTAX   INTEGER          
                                        -- value = 100*n (n=1,2,3,..,600)
               ACCESS   read-write
               STATUS   mandatory
               DESCRIPTION "It is used to set the timer value of the LOS (Loss 
                           of Signal) failure detection timer (msec). It is 
                           possible to set the integer of a multiple of 100."
               ::= { mpAtmVccConfigEntry 6 }

       mpAtmVccRecoverTimerLof OBJECT-TYPE
               SYNTAX   INTEGER          
                                        -- value = 100*n (n=1,2,3,..,600)
               ACCESS   read-write
               STATUS   mandatory
               DESCRIPTION "It is used to set the timer value of the LOF (Loss 
                           of Frames) recovery detection timer (msec). It is 
                           possible to set the integer of a multiple of 100."
               ::= { mpAtmVccConfigEntry 7 }

       mpAtmVccRecoverTimerLos OBJECT-TYPE
               SYNTAX   INTEGER          
                                        -- value = 100*n (n=1,2,3,..,600)
               ACCESS   read-write
               STATUS   mandatory
               DESCRIPTION "It is used to set the timer value of the LOS (Loss 
                           of Signal) recovery detection timer (msec). It is 
                           possible to set the integer of a multiple of 100."
               ::= { mpAtmVccConfigEntry 8 }

       -- add  this Object @003 
       mpAtmVccFailTimerLop OBJECT-TYPE
               SYNTAX   INTEGER          
                                        -- value = 100*n (n=1,2,3,..,600)
               ACCESS   read-write
               STATUS   mandatory
               DESCRIPTION "It is used to set the timer value of the LOP (Loss 
                           of Pointer) failure detection timer (msec). It is 
                           possible to set the integer of a multiple of 100."
               ::= { mpAtmVccConfigEntry 9 }

       -- add  this Object @003 
       mpAtmVccRecoverTimerLop OBJECT-TYPE
               SYNTAX   INTEGER          
                                        -- value = 100*n (n=1,2,3,..,600)
               ACCESS   read-write
               STATUS   mandatory
               DESCRIPTION "It is used to set the timer value of the LOP (Loss 
                           of Pointer) recovery detection timer (msec). It is 
                           possible to set the integer of a multiple of 100."
               ::= { mpAtmVccConfigEntry 10 }

       -- add  this Object @003 
       mpAtmVccCdv OBJECT-TYPE
               SYNTAX   INTEGER          
               ACCESS   read-write
               STATUS   mandatory
               DESCRIPTION "It is used to set the value of CDV(Cell Delay 
                           Variation) which is used for ATM Mega-Link."
               ::= { mpAtmVccConfigEntry 11 }

       -- add  this Object @003 
       mpAtmVccClockMode OBJECT-TYPE
               SYNTAX   INTEGER { 
                                line(1), 
                                internal(2) 
                                }              
               ACCESS   read-write
               STATUS   mandatory
               DESCRIPTION "It is used to set clock mode of ATM. If it is 
                           set to '1', the clock received from the line is 
                           used. If it is  set to '2', the internal clock is 
                           used."
               ::= { mpAtmVccConfigEntry 12 }

       mpAtmSscopConfigTable OBJECT-TYPE
               SYNTAX   SEQUENCE OF MpAtmSscopConfigEntry 
               ACCESS   not-accessible
               STATUS   mandatory
               DESCRIPTION "Indicates the table of SSCOP layer parameter 
                           configuration."
               ::= { mpAtm 3 }

       mpAtmSscopConfigEntry OBJECT-TYPE
               SYNTAX   MpAtmSscopConfigEntry
               ACCESS   not-accessible
               STATUS   mandatory
               DESCRIPTION "Indicates the entry of SSCOP layer configuration."
               INDEX { mpAtmSscopIfIndex }
               ::= { mpAtmSscopConfigTable 1 }

       MpAtmSscopConfigEntry ::=
               SEQUENCE {
                        mpAtmSscopIfIndex INTEGER,
                        mpAtmSscopTimerConnectControl INTEGER,
                        mpAtmSscopTimerKeepalive INTEGER,
                        mpAtmSscopTimerNoResponse INTEGER,
                        mpAtmSscopTimerPoll INTEGER,
                        mpAtmSscopTimerIdle INTEGER,
                        mpAtmSscopMaxConnectControl INTEGER,
                        mpAtmSscopMaxPd INTEGER
                        }

       mpAtmSscopIfIndex OBJECT-TYPE
               SYNTAX   INTEGER          
               ACCESS   read-only
               STATUS   mandatory
               DESCRIPTION "Indicates the index value to identify the ATM 
                           interface in this equipment. Each ATM interface 
                           identified by this object is the same interface 
                           identified by the same number of ifIndex."
               ::= { mpAtmSscopConfigEntry 1 }

       mpAtmSscopTimerConnectControl OBJECT-TYPE
               SYNTAX   INTEGER           
                                         -- unit = msec
                                         -- value = 250*n (n=1,2,3,..,240)
                                         -- The default value is recommended by 
                                         -- ITU-T.
               ACCESS   read-write
               STATUS   mandatory
               DESCRIPTION "It is used to set the timer value of the SSCOP 
                           connection control PDU re-sending interval timer 
                           (msec).  The timer value must be the same as the 
                           that of the equipment connected to itself. It is 
                           possible to set the integer of a multiple of 250."
               ::= { mpAtmSscopConfigEntry 2 }

       mpAtmSscopTimerKeepalive OBJECT-TYPE
               SYNTAX   INTEGER           
                                         -- unit = msec
                                         -- value = 250*n (n=1,2,3,..,240)
                                         -- The default value is recommended by 
                                         -- ITU-T.
               ACCESS   read-write
               STATUS   mandatory
               DESCRIPTION "It is used to set the timer value of the POLL PDU 
                           re-sending interval timer, which is used when there 
                           is no SD PDU to be sent, in the data transmission 
                           phase (msec). The timer value must be the same as 
                           that of the equipment connected to itself. It is 
                           possible to set the integer of a multiple of 250."
               ::= { mpAtmSscopConfigEntry 3 }

       mpAtmSscopTimerNoResponse OBJECT-TYPE
               SYNTAX   INTEGER          
                                         -- unit = msec
                                         -- value = 250*n (n=1,2,3,..,240)
                                         -- The default value is recommended by 
                                         -- ITU-T.
               ACCESS   read-write
               STATUS   mandatory
               DESCRIPTION "It is used to set the timer value of the STAT PDU 
                           waiting timer (msec). This is the connection 
                           observation timer in the data transmission phase. 
                           When it expires, the connection is disconnected. 
                           The timer value must be the same as that of the 
                           equipment connected to itself. It is possible to 
                           set the integer of a multiple of 250."
               ::= { mpAtmSscopConfigEntry 4 }

       mpAtmSscopTimerPoll OBJECT-TYPE
               SYNTAX   INTEGER          
                                         -- unit = msec
                                         -- value = 250*n (n=1,2,3,..,240)
                                         -- The default value is recommended by 
                                         -- ITU-T.
               ACCESS   read-write
               STATUS   mandatory
               DESCRIPTION "It is used to set the timer value of the POLL PDU 
                           sending interval timer in the data transmission 
                           phase (msec). The timer value must be the same as 
                           that of the equipment connected to itself. It is 
                           possible to set the integer of a multiple of 250."
               ::= { mpAtmSscopConfigEntry 5 }

       mpAtmSscopTimerIdle OBJECT-TYPE
               SYNTAX   INTEGER          
                                         -- unit = msec
                                         -- value = 250*n (n=1,2,3,..,240)
                                         -- The default value is recommended by 
                                         -- ITU-T.
               ACCESS   read-write
               STATUS   mandatory
               DESCRIPTION "It is used to set the timer value of the POLL PDU 
                           sending interval timer, which is used when there is 
                           no SD PDU to be sent, in the data transmission phase 
                           (msec). The timer value must be the same as that of 
                           the equipment connected to itself. It is possible 
                           to set the integer of a multiple of 250."
               ::= { mpAtmSscopConfigEntry 6 }

       mpAtmSscopMaxConnectControl OBJECT-TYPE
               SYNTAX   INTEGER          
                                         -- The default value is recommended by 
                                         -- ITU-T.
               ACCESS   read-write
               STATUS   mandatory
               DESCRIPTION "Indicates the MAX retry count value of the SSCOP 
                           connection control PDU sending."
               ::= { mpAtmSscopConfigEntry 7 }

       mpAtmSscopMaxPd OBJECT-TYPE
               SYNTAX   INTEGER          
                                         -- The default value is recommended by 
                                         -- ITU-T.
               ACCESS   read-write
               STATUS   mandatory
               DESCRIPTION "Indicates the sending timing of the POLL PDU. After 
                           the PDUs as many as the number specified by this 
                           object are sent, one POLL PDU is sent."
               ::= { mpAtmSscopConfigEntry 8 }

       mpAtmSignalingConfigTable OBJECT-TYPE
               SYNTAX   SEQUENCE OF MpAtmSignalingConfigEntry
               ACCESS   not-accessible
               STATUS   mandatory
               DESCRIPTION "This table contains ATM Signaling configuration
                            parameters, one entry per ATM interface port."
               ::= { mpAtm 4 }

       mpAtmSignalingConfigEntry OBJECT-TYPE
               SYNTAX   MpAtmSignalingConfigEntry
               ACCESS   not-accessible
               STATUS   mandatory
               DESCRIPTION "This list contains ATM signaling configuration
                            parameters and state variables."
               INDEX    { mpAtmSigIfIndex }
               ::= { mpAtmSignalingConfigTable 1 }

       MpAtmSignalingConfigEntry ::=
               SEQUENCE {
                        mpAtmSigIfIndex INTEGER,
                        mpAtmSigSvcSupportFlag INTEGER,
                        mpAtmSigUniVersion INTEGER
                        }  

       mpAtmSigIfIndex OBJECT-TYPE
               SYNTAX  INTEGER
               ACCESS  read-only
               STATUS  mandatory
               DESCRIPTION "Indicates the index value to identify the
                            ATM interface in this equipment. Each ATM
                            interface identified by this object is the 
                            same interface identified by the same number
                            of ifIndex."
               ::= { mpAtmSignalingConfigEntry 1 }

       mpAtmSigSvcSupportFlag OBJECT-TYPE
               SYNTAX  INTEGER {
                               support(1),
                               nonSupport(2) 
                               }
               ACCESS  read-write
               STATUS  mandatory
               DESCRIPTION "Indicates whether the SVC functionality is 
                            supported or not, for the ATM interface of
                            this equipment. If it is set to '1', SVC
                            functionality is supported. If it is set to
                            '2', it is not supported."
               ::= { mpAtmSignalingConfigEntry  2 }

       mpAtmSigUniVersion OBJECT-TYPE
               SYNTAX INTEGER {
                              uni3-0(1), 
                              uni3-1(2)
                              }
               ACCESS  read-write
               STATUS  mandatory
               DESCRIPTION "This specifies the ATM Forum UNI version which
                            is used by the ATM ports of this equipment as
                            the ATM Signaling functionality. This object
                            can be set only when all the ATM ports are
                            closed. It is set to '1' in the case of UNI3.0,
                            and is set to '2' in the case of UNI3.1."
               ::= { mpAtmSignalingConfigEntry   3 }

       mpAtmIlmiConfigTable OBJECT-TYPE
               SYNTAX   SEQUENCE OF MpAtmIlmiConfigEntry
               ACCESS   not-accessible
               STATUS   mandatory
               DESCRIPTION "This table contains ILMI configuration parameters,
                            one entry per ATM interface port."
               ::= { mpAtm 5 }

       mpAtmIlmiConfigEntry OBJECT-TYPE
               SYNTAX   MpAtmIlmiConfigEntry
               ACCESS   not-accessible
               STATUS   mandatory
               DESCRIPTION "This list contains ILMI configuration parameters
                            and state variables."
               INDEX    { mpAtmIlmiIfIndex }
               ::= { mpAtmIlmiConfigTable 1 }

       MpAtmIlmiConfigEntry ::=
               SEQUENCE {
                        mpAtmIlmiIfIndex INTEGER,
                        mpAtmIlmiFlag INTEGER
                        }  

       mpAtmIlmiIfIndex OBJECT-TYPE
               SYNTAX  INTEGER
               ACCESS  read-only
               STATUS  mandatory
               DESCRIPTION "Indicates the index value to identify the
                            ATM interface in this equipment. Each ATM
                            interface identified by this object is the 
                            same interface identified by the same number
                            of ifIndex."
               ::= { mpAtmIlmiConfigEntry 1 }

       mpAtmIlmiFlag OBJECT-TYPE
               SYNTAX INTEGER {
                                 support(1),
                                 nonSupport(2)
                              }
               ACCESS  read-write
               STATUS  mandatory
               DESCRIPTION "This object indicates ILMI Function support
                            status."
               ::= { mpAtmIlmiConfigEntry 2 }

       mpAtmStatisticsTable OBJECT-TYPE
               SYNTAX   SEQUENCE OF MpAtmStatisticsEntry
               ACCESS   not-accessible
               STATUS   mandatory
               DESCRIPTION "Indicates the table of the statistics data of the 
                           SONET or SDH base ATM interface."
               ::= { mpAtm 6 }

       mpAtmStatisticsEntry OBJECT-TYPE
               SYNTAX   MpAtmStatisticsEntry
               ACCESS   not-accessible
               STATUS   mandatory
               DESCRIPTION "Indicates the entry of the statistics data of each 
                           ATM interface."
               INDEX { mpAtmStatIfIndex }
               ::= { mpAtmStatisticsTable 1 }

       MpAtmStatisticsEntry ::=
               SEQUENCE {
                        mpAtmStatIfIndex INTEGER,
                        mpAtmStatVpiVciErrs Counter,
                        mpAtmStatRcvOverRunErrs Counter,
                        mpAtmStatInvalidCellErrs Counter,
                        mpAtmStatRcvBufEmptys Counter,
                        mpAtmStatRcvStsAlmostFulls Counter,
                        mpAtmStatSndStsAlmostFulls Counter,
                        mpAtmStatOolErrs Counter,
                        mpAtmStatLocErrs Counter,
                        mpAtmStatHecErrs Counter,
                        mpAtmStatOcdErrs Counter,
                        mpAtmStatTcOverFlowErrs Counter,
                        mpAtmStatParityErrs Counter,
                        mpAtmStatC2Errs Counter,
                        mpAtmStatLopErrs Counter,
                        mpAtmStatPaisErrs Counter,
                        mpAtmStatPrdiErrs Counter,
                        mpAtmStatB3Errs Counter,
                        mpAtmStatPathFebeErrs Counter,
                        mpAtmStatB2Errs Counter,
                        mpAtmStatLineFebeErrs Counter,
                        mpAtmStatLaisErrs Counter,
                        mpAtmStatLrdiErrs Counter,
                        mpAtmStatOofErrs Counter,
                        mpAtmStatB1Errs Counter,
                        mpAtmStatLosErrs Counter,
                        mpAtmStatLofErrs Counter,
                        mpAtmStatInPackets Counter,
                        mpAtmStatInOctets Counter,
                        mpAtmStatOutPackets Counter,
                        mpAtmStatOutOctets Counter
                        }
  
       mpAtmStatIfIndex OBJECT-TYPE
               SYNTAX   INTEGER        
               ACCESS   read-only
               STATUS   mandatory
               DESCRIPTION "Indicates the index value to identify the ATM 
                           interface uniquely within the equipment. Each ATM 
                           interface identified by this object is the same
                           ATM interface identified by the ifIndex."
               ::= { mpAtmStatisticsEntry 1 }

       mpAtmStatVpiVciErrs OBJECT-TYPE
               SYNTAX   Counter        
               ACCESS   read-only
               STATUS   mandatory
               DESCRIPTION "Indicates the counter value of the VPI/VCI error."
               ::= { mpAtmStatisticsEntry 2 }

       mpAtmStatRcvOverRunErrs OBJECT-TYPE
               SYNTAX   Counter        
               ACCESS   read-only
               STATUS   mandatory
               DESCRIPTION "Indicates the counter value of the receiving FIFO 
                           over-run error."
               ::= { mpAtmStatisticsEntry 3 }

       mpAtmStatInvalidCellErrs OBJECT-TYPE
               SYNTAX   Counter        
               ACCESS   read-only
               STATUS   mandatory
               DESCRIPTION "Indicates the counter value of the received 
                           invalid cell."
               ::= { mpAtmStatisticsEntry 4 }

       mpAtmStatRcvBufEmptys OBJECT-TYPE
               SYNTAX   Counter        
               ACCESS   read-only
               STATUS   mandatory
               DESCRIPTION "Indicates the counter value of the received free 
                           buffer empty."
               ::= { mpAtmStatisticsEntry 5 }

       mpAtmStatRcvStsAlmostFulls OBJECT-TYPE
               SYNTAX   Counter        
               ACCESS   read-only
               STATUS   mandatory
               DESCRIPTION "Indicates the counter value of the Rx Status Queue 
                           Almost Full."
               ::= { mpAtmStatisticsEntry 6 }

       mpAtmStatSndStsAlmostFulls OBJECT-TYPE
               SYNTAX   Counter        
               ACCESS   read-only
               STATUS   mandatory
               DESCRIPTION "Indicates the counter value of the Tx Status Queue 
                           Almost Full."
               ::= { mpAtmStatisticsEntry 7 }

       mpAtmStatOolErrs OBJECT-TYPE
               SYNTAX   Counter        
               ACCESS   read-only
               STATUS   mandatory
               DESCRIPTION "Indicates OOL(Out of Lock) error counter value."
               ::= { mpAtmStatisticsEntry 8 }

       mpAtmStatLocErrs OBJECT-TYPE
               SYNTAX   Counter        
               ACCESS   read-only
               STATUS   mandatory
               DESCRIPTION "Indicates LOC(Loss Of Cell Delineation) error 
                           counter value." 
               ::= { mpAtmStatisticsEntry 9 }

       mpAtmStatHecErrs OBJECT-TYPE
               SYNTAX   Counter        
               ACCESS   read-only
               STATUS   mandatory
               DESCRIPTION "Indicates the ATM cell HEC error counter value."
               ::= { mpAtmStatisticsEntry 10 }

       mpAtmStatOcdErrs OBJECT-TYPE
               SYNTAX   Counter        
               ACCESS   read-only
               STATUS   mandatory
               DESCRIPTION "Indicates OCD(Out Of Cell Delineation) error 
                           counter value."
               ::= { mpAtmStatisticsEntry 11 }

       mpAtmStatTcOverFlowErrs OBJECT-TYPE
               SYNTAX   Counter        
               ACCESS   read-only
               STATUS   mandatory
               DESCRIPTION "Indicates the counter value of the FIFO overflow."
               ::= { mpAtmStatisticsEntry 12 }

       mpAtmStatParityErrs OBJECT-TYPE
               SYNTAX   Counter        
               ACCESS   read-only
               STATUS   mandatory
               DESCRIPTION "Indicates the counter value of the parity error."
               ::= { mpAtmStatisticsEntry 13 }

       mpAtmStatC2Errs OBJECT-TYPE
               SYNTAX   Counter        
               ACCESS   read-only
               STATUS   mandatory
               DESCRIPTION "Indicates the C2 error counter value."
               ::= { mpAtmStatisticsEntry 14 }

       mpAtmStatLopErrs OBJECT-TYPE
               SYNTAX   Counter        
               ACCESS   read-only
               STATUS   mandatory
               DESCRIPTION "Indicates the LOP(Loss of Pointer) error counter
                           value."
               ::= { mpAtmStatisticsEntry 15 }

       mpAtmStatPaisErrs OBJECT-TYPE
               SYNTAX   Counter        
               ACCESS   read-only
               STATUS   mandatory
               DESCRIPTION "Indicates the Path Alarm Indication error counter 
                           value."
               ::= { mpAtmStatisticsEntry 16 }

       mpAtmStatPrdiErrs OBJECT-TYPE
               SYNTAX   Counter        
               ACCESS   read-only
               STATUS   mandatory
               DESCRIPTION "Indicates the Path Remote Path Indication error 
                           counter value."
               ::= { mpAtmStatisticsEntry 17 }

       mpAtmStatB3Errs OBJECT-TYPE
               SYNTAX   Counter        
               ACCESS   read-only
               STATUS   mandatory
               DESCRIPTION "Indicates the B3 error counter value."
               ::= { mpAtmStatisticsEntry 18 }

       mpAtmStatPathFebeErrs OBJECT-TYPE
               SYNTAX   Counter        
               ACCESS   read-only
               STATUS   mandatory
               DESCRIPTION "Indicates the Path FEBE error counter value."
               ::= { mpAtmStatisticsEntry 19 }

       mpAtmStatB2Errs OBJECT-TYPE
               SYNTAX   Counter        
               ACCESS   read-only
               STATUS   mandatory
               DESCRIPTION "Indicates the B2 error counter value."
               ::= { mpAtmStatisticsEntry 20 }

       mpAtmStatLineFebeErrs OBJECT-TYPE
               SYNTAX   Counter        
               ACCESS   read-only
               STATUS   mandatory
               DESCRIPTION "Indicates the Line FEBE error counter value." 
               ::= { mpAtmStatisticsEntry 21 }

       mpAtmStatLaisErrs OBJECT-TYPE
               SYNTAX   Counter        
               ACCESS   read-only
               STATUS   mandatory
               DESCRIPTION "Indicates the Line Alarm Indication error counter 
                           value."
               ::= { mpAtmStatisticsEntry 22 }

       mpAtmStatLrdiErrs OBJECT-TYPE
               SYNTAX   Counter        
               ACCESS   read-only
               STATUS   mandatory
               DESCRIPTION "Indicates the Line Remote Path indication error 
                           counter value."
               ::= { mpAtmStatisticsEntry 23 }

       mpAtmStatOofErrs OBJECT-TYPE
               SYNTAX   Counter        
               ACCESS   read-only
               STATUS   mandatory
               DESCRIPTION "Indicates the OOF(Out of Frame) error counter
                           value."
               ::= { mpAtmStatisticsEntry 24 }

       mpAtmStatB1Errs OBJECT-TYPE
               SYNTAX   Counter
               ACCESS   read-only
               STATUS   mandatory
               DESCRIPTION "Indicates the B1 error counter value."
               ::= { mpAtmStatisticsEntry 25 }

       mpAtmStatLosErrs OBJECT-TYPE
               SYNTAX   Counter        
               ACCESS   read-only
               STATUS   mandatory
               DESCRIPTION "Indicates the LOS(Loss of Signal) error counter 
                           value."
               ::= { mpAtmStatisticsEntry 26 }

       mpAtmStatLofErrs OBJECT-TYPE
               SYNTAX   Counter
               ACCESS   read-only
               STATUS   mandatory
               DESCRIPTION "Inicates the LOF(Loss of Frame) error counter 
                           value."
               ::= { mpAtmStatisticsEntry 27 }

       mpAtmStatInPackets OBJECT-TYPE
               SYNTAX   Counter        
               ACCESS   read-only
               STATUS   mandatory
               DESCRIPTION "Indicates the counter value of the incoming 
                           packets."
               ::= { mpAtmStatisticsEntry 28 }

       mpAtmStatInOctets OBJECT-TYPE
               SYNTAX   Counter        
               ACCESS   read-only
               STATUS   mandatory
               DESCRIPTION "Indicates the counter value of the incoming 
                           octets."
               ::= { mpAtmStatisticsEntry 29 }

       mpAtmStatOutPackets OBJECT-TYPE
               SYNTAX   Counter        
               ACCESS   read-only
               STATUS   mandatory
               DESCRIPTION "Indicates the counter value of the outgoing 
                           packets."
               ::= { mpAtmStatisticsEntry 30 }

       mpAtmStatOutOctets OBJECT-TYPE
               SYNTAX   Counter        
               ACCESS   read-only
               STATUS   mandatory
               DESCRIPTION "Indicates the counter value of the outgoing
                           octets."
               ::= { mpAtmStatisticsEntry 31 }

       mpAtmNetPrefixTable OBJECT-TYPE
               SYNTAX   SEQUENCE OF MpAtmNetPrefixEntry
               ACCESS   not-accessible
               STATUS   mandatory
               DESCRIPTION "This table contains network prefix of
                            ATM address got by ILMI."
               ::= { mpAtm 7}

       mpAtmNetPrefixEntry OBJECT-TYPE
               SYNTAX   MpAtmNetPrefixEntry
               ACCESS   not-accessible
               STATUS   mandatory
               DESCRIPTION "This list contains network prefix of
                            ATM address got by ILMI."
               INDEX    { mpAtmNetPrefixPort, mpAtmNetPrefixPrefix }
               ::= { mpAtmNetPrefixTable 1 }

       MpAtmNetPrefixEntry ::=
               SEQUENCE {
                        mpAtmNetPrefixPort  INTEGER,
                        mpAtmNetPrefixPrefix  NetPrefix,
                        mpAtmNetPrefixStatus  INTEGER
                        }

       mpAtmNetPrefixPort OBJECT-TYPE
               SYNTAX  INTEGER
               ACCESS  read-only
               STATUS  mandatory
               DESCRIPTION "A unique value which identifies the ATM Port."
               ::= { mpAtmNetPrefixEntry 1 }

       mpAtmNetPrefixPrefix OBJECT-TYPE
               SYNTAX  NetPrefix
               ACCESS  read-only
               STATUS  mandatory
               DESCRIPTION "The network Prefix for ATM address."
               ::= { mpAtmNetPrefixEntry 2 }

       mpAtmNetPrefixStatus OBJECT-TYPE
               SYNTAX  INTEGER{
                    valid(1),
                    invalid(2)
                    }
               ACCESS  read-only
               STATUS  mandatory
               DESCRIPTION "Indicates the validity of the network prefix."
               ::= { mpAtmNetPrefixEntry 3 }

       -- add  this Object @003 
       mpAtmVpcTable OBJECT-TYPE
               SYNTAX   SEQUENCE OF MpAtmVpcEntry
               ACCESS   not-accessible
               STATUS   mandatory
               DESCRIPTION "This table contains VPL configuration 
                           parameters, one entry per ATM interface port."
               ::= { mpAtm 8 }

       -- add  this Object @003 
       mpAtmVpcEntry OBJECT-TYPE
               SYNTAX   MpAtmVpcEntry
               ACCESS   not-accessible
               STATUS   mandatory
               DESCRIPTION "This list contains VPL configuration 
                           parameters and state variables."
               INDEX    { mpAtmVpcIfIndex,
                          mpAtmVpcVpi }
               ::= { mpAtmVpcTable 1 }

       -- add  this Object @003 
       MpAtmVpcEntry ::=
               SEQUENCE {
                        mpAtmVpcIfIndex INTEGER,
                        mpAtmVpcVpi INTEGER,
                        mpAtmVpcAdminStatus INTEGER,
                        mpAtmVpcOperStatus INTEGER,
                        mpAtmVpcLastChange TimeStamp,
                        mpAtmVpcShapingType INTEGER ,
                        mpAtmVpcTransmitTrafficDescrIndex INTEGER ,
                        mpAtmVpcRowStatus RowStatus
                        }  

       -- add  this Object @003 
       mpAtmVpcIfIndex OBJECT-TYPE
               SYNTAX  INTEGER
               ACCESS  read-only
               STATUS  mandatory
               DESCRIPTION "Indicates the index value to identify the
                           ATM interface in this equipment. Each ATM
                           interface identified by this object is the 
                           same interface identified by the same number
                           of ifIndex."
               ::= { mpAtmVpcEntry 1 }

       -- add  this Object @003 
       mpAtmVpcVpi OBJECT-TYPE
               SYNTAX INTEGER 
               ACCESS  read-only
               STATUS  mandatory
               DESCRIPTION "The VPI value of the VPL.
                           Note that the VPI=0 is not used
                           for a VPL not associated with a VCL.
                           The maximum VPI value cannot
                           exceed the value allowable by the
                           atmInterfaceMaxVpiBits."
               ::= { mpAtmVpcEntry 2 }

       -- add  this Object @003 
       mpAtmVpcAdminStatus OBJECT-TYPE
               SYNTAX  INTEGER {
                    up(1),
                    down(2)
                    }
               ACCESS  read-write
               STATUS  mandatory
               DESCRIPTION "This object is implemented only for a VPL which
                           terminates a VPC (i.e.,
                           one which is NOT cross-connected to other VPLs).
                           Its value specifies the desired administrative
                           state of the VPL.  The up and down states indicate
                           that the traffic flow is enabled and disabled
                           respectively for this VPL."
               ::= { mpAtmVpcEntry  3 }

       -- add  this Object @003 
       mpAtmVpcOperStatus OBJECT-TYPE
               SYNTAX  INTEGER {
                    up(1),
                    down(2),
                    unknown(3)
                    }
               ACCESS  read-only       
               STATUS  mandatory
               DESCRIPTION "This object indicates the current operational
                           status of the VPL.  The up and down states
                           indicate that the VPL is currently
                           operational, or not operational, respectively.
                           The unknown state indicates that the status of
                           this VPL cannot be determined."
               ::= { mpAtmVpcEntry  4 }

       -- add  this Object @003 
       mpAtmVpcLastChange OBJECT-TYPE
               SYNTAX  TimeStamp
               ACCESS  read-only
               STATUS  mandatory
               DESCRIPTION "The value of MIB II's sysUpTime object
                           at the time this VPL entered its current
                           operational state.  If the current state was
                           entered prior to the last re-initialization of the
                           agent, then this object contains a zero value."
               ::= { mpAtmVpcEntry  5 }

       -- add  this Object @003 
       mpAtmVpcShapingType OBJECT-TYPE
               SYNTAX INTEGER {
                                 vpShaping(1),
                                 vcShaping(2)
                              }
               ACCESS  read-write
               STATUS  mandatory
               DESCRIPTION "This object indicates shaping type used 
                           for VPC status."
               ::= { mpAtmVpcEntry 6 }

       -- add  this Object @003 
       mpAtmVpcTransmitTrafficDescrIndex OBJECT-TYPE
               SYNTAX  INTEGER
               ACCESS  read-write
               STATUS  mandatory
               DESCRIPTION "The value of this object identifies the row
                           of the ATM Traffic Descriptor Table which applies
                           to the transmit direction of this VCL."
               ::= { mpAtmVpcEntry  7 }

       -- add  this Object @003 
       mpAtmVpcRowStatus OBJECT-TYPE
               SYNTAX  RowStatus
               ACCESS  read-write
               STATUS  mandatory
               DESCRIPTION "This object is used to create, delete or
                           modify a row in this table.  To create
                           a new VCL, this object is initially set
                           to 'createAndWait' or 'createAndGo'.
                           This object must not be set to 'active'
                           unless the following columnar objects exist
                           in this row:
                           atmVclReceiveTrafficDescrIndex,
                           atmVclTransmitTrafficDescrIndex.
                           In addition, if the local VCL end-point
                           is also the VCC end-point:
                           atmVccAalType.
                           In addition, for AAL5 connections only:
                           atmVccAal5CpcsTransmitSduSize,
                           atmVccAal5CpcsReceiveSduSize, and
                           atmVccAal5EncapsType."
               ::= { mpAtmVpcEntry  8 }

       -- add  this Object @003 
       mpAtmTrafficTable OBJECT-TYPE
               SYNTAX   SEQUENCE OF MpAtmTrafficEntry
               ACCESS   not-accessible
               STATUS   mandatory
               DESCRIPTION "This table contains information on ATM 
                           traffic parameters."
               ::= { mpAtm 9 }

       -- add  this Object @003 
       mpAtmTrafficEntry OBJECT-TYPE
               SYNTAX   MpAtmTrafficEntry
               ACCESS   not-accessible
               STATUS   mandatory
               DESCRIPTION "This list contains ATM traffic parameters."
               INDEX { mpAtmTrafficDescrParamIndex }
               ::= { mpAtmTrafficTable 1 }

       -- add  this Object @003 
       MpAtmTrafficEntry ::=
               SEQUENCE {
                        mpAtmTrafficDescrParamIndex INTEGER,
                        mpAtmTrafficCdv INTEGER
                        }  

       -- add  this Object @003 
       mpAtmTrafficDescrParamIndex OBJECT-TYPE
               SYNTAX  INTEGER
               ACCESS  read-only
               STATUS  mandatory
               DESCRIPTION "Indicates the index of ATM traffic entry."
               ::= { mpAtmTrafficEntry 1 }

       -- add  this Object @003 
       mpAtmTrafficCdv OBJECT-TYPE
               SYNTAX INTEGER (0..750) 
               ACCESS  read-write
               STATUS  mandatory
               DESCRIPTION "Indicate the CDV(Cell Delay Variation) value"
               ::= { mpAtmTrafficEntry 2 }


--  ***************************************************************************
--  the SanFran LIS Group
--  ***************************************************************************

   --  Implementation of this group is mandatory for all the SanFran systems.  


       mpLisNameTable OBJECT-TYPE
               SYNTAX   SEQUENCE OF MpLisNameEntry
               ACCESS   not-accessible
               STATUS   mandatory
               DESCRIPTION "A table that is used for registoring LIS name."
               ::= { mpLis 1 }

       mpLisNameEntry OBJECT-TYPE
               SYNTAX   MpLisNameEntry
               ACCESS   not-accessible
               STATUS   mandatory
               DESCRIPTION "An entry of LIS name."
               INDEX { mpLisIndex }
               ::= { mpLisNameTable 1 }

       MpLisNameEntry ::=
               SEQUENCE {
                        mpLisIndex INTEGER,
                        mpLisRtrIndex INTEGER,
                        mpLisName DisplayString,
                        mpLisNameStatus INTEGER
                        }

       mpLisIndex OBJECT-TYPE
               SYNTAX   INTEGER           
               ACCESS   read-only
               STATUS   mandatory
               DESCRIPTION " A number that uniquely assigned to the LIS."
               ::= { mpLisNameEntry 1 }

       mpLisRtrIndex OBJECT-TYPE
               SYNTAX   INTEGER           
                                          -- These values are defined by a 
                                          -- configuration file.
               ACCESS   read-only
               STATUS   mandatory
               DESCRIPTION "An interface number that uniquely assigned to the 
                           LIS of the Unit. The LIS recognized by this number 
                           is the same as what is recognized by same number of 
                           ifIndex."
               ::= { mpLisNameEntry 2 }

       mpLisName OBJECT-TYPE
               SYNTAX   DisplayString (SIZE (0..40))
               ACCESS   read-write
               STATUS   mandatory
               DESCRIPTION "A name assigned to the LIS for management purpose.
                           This object is used for setting or changing a name 
                           of the LIS."
               ::= { mpLisNameEntry 3 }

       mpLisNameStatus OBJECT-TYPE
               SYNTAX   INTEGER { 
                                valid(1), 
                                invalid(2) 
                                }
               ACCESS   read-write
               STATUS   mandatory
               DESCRIPTION "This object is used for registoring or deleting an 
                           entry of the table. 1 is set when registroing and 2 
                           is set when deletion."
               ::= { mpLisNameEntry 4 }

       mpLisAdminTable OBJECT-TYPE
               SYNTAX   SEQUENCE OF MpLisAdminEntry
               ACCESS   not-accessible
               STATUS   mandatory
               DESCRIPTION "A table including LIS information."
               ::= { mpLis 2 }

       mpLisAdminEntry OBJECT-TYPE
               SYNTAX   MpLisAdminEntry
               ACCESS   not-accessible
               STATUS   mandatory
               DESCRIPTION "An entry in LIS management table.
 
                           Registoring LIS
                           (1) Manager satation generates a LIS entry in 
                               mpLisAdminTable by setting mpLisAdmRowStatus as 
                               createAndWait(5).
                           (2) Manager station, if necessary, sets value of 
                               management object of mpLisAdminTable.
                           (3) Manager station enables a LIS entry by setting 
                               mpLisAdmRowStatus as active(1).
 
                           Deletion of LIS
                           (1) Manager station disables a LIS entry bu setting 
                               mpLisAdmRowStatus as notInService(2).
                           (2) A LIS is deleted by setting mpLisAdmRowStatus as 
                               destroy(6).  An agent may release all related 
                               resources at the moment."
               INDEX { mpLisAdmIndex }
               ::= { mpLisAdminTable 1 }

       MpLisAdminEntry ::=
               SEQUENCE {
                        mpLisAdmIndex INTEGER,
                        mpLisAdmAtmArpSvExistence INTEGER,
                        mpLisAdmAtmArpSvCallType INTEGER,
                        mpLisAdmAtmArpSvAtmAddress OCTET STRING,
                        mpLisAdmAtmArpSvAtmPortNumber INTEGER,
                        mpLisAdmAtmArpSvVpi INTEGER,
                        mpLisAdmAtmArpSvVci INTEGER,
                        mpLisAdmSvTrafficId INTEGER,
                        mpLisAdmAtmArpSvVcStatus INTEGER,
                        mpLisAdmAtmArpSvRetryCount INTEGER,
                        mpLisAdmLisStatus INTEGER,
                        mpLisAdmMyAtmAddressSel  OCTET STRING,
                        mpLisAdmMyIpAddress IpAddress,
                        mpLisAdmMyNetMask IpAddress,
                        mpLisAdmAtmPortNumber INTEGER,
                        mpLisAdmAtmArpTables INTEGER,
                        mpLisAdmSndMtuSize INTEGER,
                        mpLisAdmRcvMtuSize INTEGER,
                        mpLisAdmTrafficId INTEGER,
                        mpLisAdmRowStatus RowStatus
                        }

       mpLisAdmIndex OBJECT-TYPE
               SYNTAX   INTEGER           
               ACCESS   read-only
               STATUS   mandatory
               DESCRIPTION "This object shows a unique number assigned to this 
                           LIS."
               ::= { mpLisAdminEntry 1 }

       mpLisAdmAtmArpSvExistence OBJECT-TYPE
               SYNTAX   INTEGER { 
                                existence(1), 
                                notExisting(2) 
                                }
               ACCESS   read-write
               STATUS   mandatory
               DESCRIPTION "This object identifies extistence or non-existence 
                           of ATM ARP server. If it exists, 1 is set. If it 
                           does not exist, 2 is set."
               ::= { mpLisAdminEntry 2 }

       mpLisAdmAtmArpSvCallType OBJECT-TYPE
               SYNTAX   INTEGER { 
                                svc(1), 
                                pcv(2) 
                                }
               ACCESS   read-write
               STATUS   mandatory
               DESCRIPTION "This object shows a type of connection between the 
                           LIS and an ATM ARP server. If it is SVC, 1 is shown.
                           If it is PVC, 2 is shown."
               ::= { mpLisAdminEntry 3 }

       mpLisAdmAtmArpSvAtmAddress OBJECT-TYPE
               SYNTAX   OCTET STRING (SIZE(0 | 20))
               ACCESS   read-write
               STATUS   mandatory
               DESCRIPTION "This object assigns ATM address of an ATM ARP 
                           server in the LIS."
               ::= { mpLisAdminEntry 4 }

       mpLisAdmAtmArpSvAtmPortNumber OBJECT-TYPE
               SYNTAX   INTEGER           
               ACCESS   read-write
               STATUS   mandatory
               DESCRIPTION "This object assigns a number of ATM port which is 
                            used when the LIS is connected to the ATM server 
                            by PVC. If these are conencted by SVC, this object 
                            shows currently assigned number of ATM port."
               ::= { mpLisAdminEntry 5 }

       mpLisAdmAtmArpSvVpi OBJECT-TYPE
               SYNTAX   INTEGER           
               ACCESS   read-write
               STATUS   mandatory
               DESCRIPTION "This object assigns a number of VPI which is used 
                           when the LIS is connected to the ATM server by PVC.
                           If these are conencted by SVC, this object shows 
                           currently assigned number of VPI."
               ::= { mpLisAdminEntry 6 }

       mpLisAdmAtmArpSvVci OBJECT-TYPE
               SYNTAX   INTEGER           
               ACCESS   read-write
               STATUS   mandatory
               DESCRIPTION "This object assigns a number of VCI which is used 
                           when the LIS is connected to the ATM server by PVC.
                           If these are conencted by SVC, this object shows 
                           currently assigned number of VCI."
               ::= { mpLisAdminEntry 7 }

        mpLisAdmSvTrafficId OBJECT-TYPE
               SYNTAX   INTEGER           
               ACCESS   read-write
               STATUS   mandatory
               DESCRIPTION "This object assigns a number of traffic ID  which
                           is used when the LIS is connected to the ATM server."
               ::= { mpLisAdminEntry 8 }

       mpLisAdmAtmArpSvVcStatus OBJECT-TYPE
               SYNTAX   INTEGER { 
                                 open(1),
                                 setting(2),
                                 usable(3),
                                 sendToAtm(4),
                                 sendAndRcvAtm(5),
                                 rcvFromAtm(6),
                                 disconnect(7),
                                 disconnectWaiting(8)
                                }
               ACCESS   read-only
               STATUS   mandatory
               DESCRIPTION "This object shows status of connection between 
                           the LIS and an ATM ARP server in follwing number:
                           Open = 1
                           Being configurated = 2
                           Available to use = 3
                           Available to transmit to ATM = 4
                           Available to transmit and receiving to/from ATM = 5
                           Available to receive from ATM = 6
                           Being disconnected = 7
                           Waiting for disconnection = 8"
               ::= { mpLisAdminEntry 9 }

       mpLisAdmAtmArpSvRetryCount OBJECT-TYPE
               SYNTAX   INTEGER          
               ACCESS   read-only
               STATUS   mandatory
               DESCRIPTION "This object shows the number of retrying of 
                           connection request caused by connection failure 
                           between ATM ARP server and the LIS."
               ::= { mpLisAdminEntry 10 }

      mpLisAdmLisStatus OBJECT-TYPE
               SYNTAX  INTEGER {
                                usable(1),
                                in-ATM-ARP-request-waiting(2),
                                down(3),
                                notInService(4)
                                } 
               ACCESS  read-only
               STATUS  mandatory
               DESCRIPTION "This object shows status of connection between
                             the LIS and an ATM ARP server in following
                             number:
                             the LIS is available  = 1
                             waiting for In-ATM-ARP-request = 2
                             not available due to failure = 3
                             not available by configuration = 4"
               ::= { mpLisAdminEntry 11 }

       mpLisAdmMyAtmAddressSel OBJECT-TYPE
               SYNTAX   OCTET STRING (SIZE( 0 | 1 )) 
               ACCESS   read-write
               STATUS   mandatory
               DESCRIPTION "This object assignes ATM address that is used by 
                            the LIS interface."
               ::= { mpLisAdminEntry 12 }

       mpLisAdmMyIpAddress OBJECT-TYPE
               SYNTAX   IpAddress
               ACCESS   read-only
               STATUS   mandatory
               DESCRIPTION "This object assignes IP address that is used by 
                           the LIS interface."
               ::= { mpLisAdminEntry 13 }

       mpLisAdmMyNetMask OBJECT-TYPE
               SYNTAX   IpAddress
               ACCESS   read-only
               STATUS   mandatory
               DESCRIPTION "This object assignes subnet mask of IP addresss 
                           that is used by the LIS interface."
               ::= { mpLisAdminEntry 14 }

       mpLisAdmAtmPortNumber OBJECT-TYPE
-- @008               SYNTAX   IpAddress
               SYNTAX   INTEGER          
-- @008               ACCESS   read-only
               ACCESS   read-write
               STATUS   mandatory
               DESCRIPTION "This object assignes number of ATM port
                           that is used by the LIS interface."
               ::= { mpLisAdminEntry 15 }

       mpLisAdmAtmArpTables OBJECT-TYPE
               SYNTAX   INTEGER          
               ACCESS   read-only
               STATUS   mandatory
               DESCRIPTION "This object shows the number of ARP tables that are 
                           registored in the LIS."
               ::= { mpLisAdminEntry 16 }

       mpLisAdmSndMtuSize OBJECT-TYPE
               SYNTAX   INTEGER          
                                     -- The default value is recommended by 
                                     -- RFC1755.
               ACCESS   read-write
               STATUS   mandatory
               DESCRIPTION "This object assigns the maximum size of transmitted 
                           AAL5 CPCS PDU payload in octet."
               ::= { mpLisAdminEntry 17 }

       mpLisAdmRcvMtuSize OBJECT-TYPE
               SYNTAX   INTEGER          
                                      -- The default value is recommended by 
                                      -- RFC1755.
               ACCESS   read-write
               STATUS   mandatory
               DESCRIPTION "This object assigns the maximum size of received 
                           AAL5 CPCS PDU payload in octet."
               ::= { mpLisAdminEntry 18 }

       mpLisAdmTrafficId OBJECT-TYPE
               SYNTAX   INTEGER          
               ACCESS   read-write
               STATUS   mandatory
               DESCRIPTION "This object shows the number of default traffic ID 
                           that is used by the LIS interface."
               ::= { mpLisAdminEntry 19 }

       mpLisAdmRowStatus OBJECT-TYPE
               SYNTAX   RowStatus
               ACCESS   read-write 
               STATUS   mandatory
               DESCRIPTION "The object is used for generating, deleting 
                           or modifying a row of the table. In case of
                           of modifying this entry, this object must be
                           changed from active(1) to notInService(2)."        
               ::= { mpLisAdminEntry 20 }

       mpLisAtmArpAdminTable OBJECT-TYPE
               SYNTAX   SEQUENCE OF MpLisAtmArpAdminEntry
               ACCESS   not-accessible
               STATUS   mandatory
               DESCRIPTION "The table includes information of ATM ARP table."
               ::= { mpLis 3 }

       mpLisAtmArpAdminEntry OBJECT-TYPE
               SYNTAX   MpLisAtmArpAdminEntry
               ACCESS   not-accessible
               STATUS   mandatory
               DESCRIPTION " The entry includes information of each ATM ARP 
                           table.
 
                           Registration of PVC or static SVC
                           (1) Manager generates an ATM ARP management entry in 
                               mpLisAtmArpAdminTable by setting 
                               mpLisAtmArpAdmRowStatus as createAndWait(5).
                           (2) Manager sets the number of management object of 
                               mpLisAtmArpAdminTable if necessary.
                           (3) Manager enables the ATM ARP entry by setting 
                               mpLisAtmArpAdmRowStatus as active(1).
 
                           Deletion of PVC or static SVC
                           (1) Manager disables the ATM ARP entry by setting 
                               mpLisAtmArpAdmRowStatus as notInService(2).
                           (2) ATM ARP is deleted by setting 
                               mpLisAtmArpAdmRowStatus as destroy(6). An agent 
                               may release all related resources at the moment."
               INDEX { mpLisAtmArpAdmLisIndex, mpLisAtmArpAdmIpAddress }
               ::= { mpLisAtmArpAdminTable 1 }

       MpLisAtmArpAdminEntry ::=
               SEQUENCE {
                         mpLisAtmArpAdmLisIndex INTEGER,
                         mpLisAtmArpAdmCallType INTEGER,
                         mpLisAtmArpAdmIpAddress IpAddress,
                         mpLisAtmArpAdmAtmAddress OCTET STRING,
                         mpLisAtmArpAdmMyAtmAddress OCTET STRING,
                         mpLisAtmArpAdmAtmPortNumber INTEGER,
                         mpLisAtmArpAdmVpi INTEGER,
                         mpLisAtmArpAdmVci INTEGER,
                         mpLisAtmArpAdmTrafficId INTEGER,
                         mpLisAtmArpAdmTableStatus INTEGER,
                         mpLisAtmArpAdmAgingTime Gauge,
                         mpLisAtmArpAdmRetryCount INTEGER,
                         mpLisAtmArpAdmRowStatus RowStatus
                        }

       mpLisAtmArpAdmLisIndex OBJECT-TYPE
               SYNTAX   INTEGER          
               ACCESS   read-only
               STATUS   mandatory
               DESCRIPTION "This object shows the unique number assigned to the 
                           LIS."
               ::= { mpLisAtmArpAdminEntry 1 }

       mpLisAtmArpAdmCallType OBJECT-TYPE
               SYNTAX   INTEGER { 
                                dynamicSvc(1), 
                                staticSvc(2), 
                                agingPvc(3), 
                                noAgingPvc(4) 
                                }        
               ACCESS   read-write
               STATUS   mandatory
               DESCRIPTION "This object shows the type of connection between 
                           ATM ARP client and the LIS.
                             If it is dynamic SVC, 1 is shown.
                             If it is static SVC, 2 is shown.
                             If it is PVC with aging, 3 is shown.
                             If it is PVC without aging, 3 is shown."
               ::= { mpLisAtmArpAdminEntry 2 }

       mpLisAtmArpAdmIpAddress OBJECT-TYPE
               SYNTAX   IpAddress
               ACCESS   read-only
               STATUS   mandatory
               DESCRIPTION "This object is used for configuring or 
                            acknowledging of destination IP address. if the 
                            connection between ATM ARP client and the LIS is 
                            PVC. If the connection is dynamic SVC or static 
                            SVC, the object cannot be set.  However it shows 
                            the currently used destination IP address."
               ::= { mpLisAtmArpAdminEntry 3 }

       mpLisAtmArpAdmAtmAddress OBJECT-TYPE
               SYNTAX   OCTET STRING (SIZE(0 | 20))
               ACCESS   read-write
               STATUS   mandatory
               DESCRIPTION "This object is used for configuring or 
                           acknowledging of destination ATM address. if the 
                           connection between ATM ARP client and the LIS is 
                           PVC. If the connection is dynamic SVC or static 
                           SVC, the object cannot be set.  However it shows 
                           the currently used destination ATM address."
               ::= { mpLisAtmArpAdminEntry 4 }

       mpLisAtmArpAdmMyAtmAddress OBJECT-TYPE
               SYNTAX   OCTET STRING (SIZE(0 | 20))
               ACCESS   read-only
               STATUS   mandatory
               DESCRIPTION "This object assigns an ATM address that is used at 
                           the interface of the LIS."
               ::= { mpLisAtmArpAdminEntry 5 }

       mpLisAtmArpAdmAtmPortNumber OBJECT-TYPE
               SYNTAX   INTEGER          
               ACCESS   read-write    
               STATUS   mandatory
               DESCRIPTION "This object assigns a number of ATM port which is 
                           used when the LIS is connected to the ATM client 
                           by PVC. If these are conencted by dynamic SVC or 
                           static SVC, this object shows currently assigned 
                           number of ATM port."
               ::= { mpLisAtmArpAdminEntry 6 }

       mpLisAtmArpAdmVpi OBJECT-TYPE
               SYNTAX   INTEGER          
               ACCESS   read-write    
               STATUS   mandatory
               DESCRIPTION "This object assigns a number of VPI which is used 
                           when the LIS is connected to the ATM client by PVC. 
                           If these are conencted by dynamic SVC or static SVC,
                           this object shows currently assigned number of VPI."
               ::= { mpLisAtmArpAdminEntry 7 }

       mpLisAtmArpAdmVci OBJECT-TYPE
               SYNTAX   INTEGER          
               ACCESS   read-write
               STATUS   mandatory
               DESCRIPTION "This object assigns a number of VCI which is used 
                           when the LIS is connected to the ATM client by PVC. 
                           If these are conencted by dynamic SVC or static SVC,
                           this object shows currently assigned number of VCI."
               ::= { mpLisAtmArpAdminEntry 8 }

        mpLisAtmArpAdmTrafficId OBJECT-TYPE
               SYNTAX   INTEGER          
               ACCESS   read-write
               STATUS   mandatory
               DESCRIPTION "This object shows the number of traffic ID that is 
                           used for PVC connection between ATM ARP cliennt and 
                           the LIS." 
               ::= { mpLisAtmArpAdminEntry 9 }

       mpLisAtmArpAdmTableStatus OBJECT-TYPE
               SYNTAX   INTEGER { 
                                usable(1), 
                                confirming(2), 
                                atmArpReplyWaiting(3),
                                inAtmArpRequestWaiting(4), 
                                aging(5), 
                                noService(6), 
                                unused(7) 
                                }        
               ACCESS   read-only
               STATUS   mandatory
               DESCRIPTION "This object shows status of ATM ARP table in 
                           follwing number:
                             the table is available                      = 1
                             waiting for acknowledge of being available  = 2
                             waiting for ATM-ARP-reply                   = 3
                             waiting for InATM-ARP-reply                 = 4
                             aging                                       = 5
                             not available to service                    = 6
                             not available to use                        = 7"
               ::= { mpLisAtmArpAdminEntry 10 }

       mpLisAtmArpAdmAgingTime OBJECT-TYPE
               SYNTAX   Gauge            
               ACCESS   read-only
               STATUS   mandatory
               DESCRIPTION "Indicates the passing time value (sec) of the
                            ATMARP table aging timer. The timer is incre-
                            mented by 1 sec."
               ::= { mpLisAtmArpAdminEntry 11 }

       mpLisAtmArpAdmRetryCount OBJECT-TYPE
               SYNTAX   INTEGER          
               ACCESS   read-only
               STATUS   mandatory
               DESCRIPTION "This object shows the number of retrying of 
                           connection request caused by connection failure 
                           between ATM ARP client and the LIS."
               ::= { mpLisAtmArpAdminEntry 12 }

       mpLisAtmArpAdmRowStatus OBJECT-TYPE
               SYNTAX   RowStatus        --  INTEGER { active(1),
                                         -- notInService(2), notReady(3), 
                                         -- createAndWait(5), destroy(6) }
                                         -- The value 'createAndGo(4)' is not 
                                         -- supported.
               ACCESS   read-write
               STATUS   mandatory
               DESCRIPTION "The object is used for generating, deleting
                            or modifying a row of the table. In case
                            of modifying this entry. This object must
                            be changed from active(1) to notInService(2)."
               ::= { mpLisAtmArpAdminEntry 13 }

       mpLisVcAdminTable OBJECT-TYPE
               SYNTAX   SEQUENCE OF MpLisVcAdminEntry
               ACCESS   not-accessible
               STATUS   mandatory
               DESCRIPTION "The table includes information of VC table."
               ::= { mpLis 4 }

       mpLisVcAdminEntry OBJECT-TYPE
               SYNTAX   MpLisVcAdminEntry
               ACCESS   not-accessible
               STATUS   mandatory
               DESCRIPTION " The entry includes information of each VC."
               INDEX { mpLisVcAdmLisIndex, mpLisVcAdmIpAddress }
               ::= { mpLisVcAdminTable 1 }

       MpLisVcAdminEntry ::=
               SEQUENCE {
                        mpLisVcAdmLisIndex INTEGER,
                        mpLisVcAdmIpAddress IpAddress,
                        mpLisVcAdmType INTEGER,
                        mpLisVcAdmVcStatus INTEGER,
                        mpLisVcAdmInactivityTime Gauge,
                        mpLisVcAdmHoldingTime Gauge
                        }

       mpLisVcAdmLisIndex OBJECT-TYPE
               SYNTAX   INTEGER          
               ACCESS   read-only
               STATUS   mandatory
               DESCRIPTION "This object shows the unique number assigned to the 
                           LIS."
               ::= { mpLisVcAdminEntry 1 }

       mpLisVcAdmIpAddress OBJECT-TYPE
               SYNTAX   IpAddress
               ACCESS   read-only
               STATUS   mandatory
               DESCRIPTION "This object assign the destination IP address."
               ::= { mpLisVcAdminEntry 2 }

       mpLisVcAdmType OBJECT-TYPE
               SYNTAX    INTEGER { 
                                 send-out(1), 
                                 receive-in(2) 
                                 }
               ACCESS   read-only
               STATUS   mandatory
               DESCRIPTION "This object shows the type of VC management table.
                           If the table is generated by originating connection, 
                           the type is 1. If the table is generated by receiving
                           connection, the type is 2."
               ::= { mpLisVcAdminEntry 3 }

       mpLisVcAdmVcStatus OBJECT-TYPE
               SYNTAX   INTEGER { 
                                open(1), 
                                setting(2), 
                                usable(3), 
                                sendToAtm(4), 
                                sendAndRcvAtm(5),
                                rcvFromAtm(6), 
                                disconnect(7), 
                                disconnectWaiting(8) 
                                }        
               ACCESS   read-only
               STATUS   mandatory
               DESCRIPTION "This object shows the status of VC connection as 
                           following numbers:
                             Open = 1
                             Being configurated = 2
                             Available to use  = 3
                             Available to transmit to ATM = 4
                             Available to transmit and receiving to/from ATM = 5
                             Available to receive from ATM = 6
                             Being disconected  = 7
                             Waiting for disconection =8"
               ::= { mpLisVcAdminEntry 4 }

       mpLisVcAdmInactivityTime OBJECT-TYPE
               SYNTAX   Gauge            
               ACCESS   read-only
               STATUS   mandatory
               DESCRIPTION "Indicates the passing time value (sec) of the
                            inactivity timer. The timer is incremented by
                            1 sec."
               ::= { mpLisVcAdminEntry 5 }

       mpLisVcAdmHoldingTime OBJECT-TYPE
               SYNTAX   Gauge            
               ACCESS   read-only
               STATUS   mandatory
               DESCRIPTION "Indicates the remaining time value (sec) of 
                            the holding timer. The timer is incremented
                            by 1 sec."
               ::= { mpLisVcAdminEntry 6 }

       mpLisStatisticsTable OBJECT-TYPE
               SYNTAX   SEQUENCE OF MpLisStatisticsEntry
               ACCESS   not-accessible
               STATUS   mandatory
               DESCRIPTION "This object includes statistics information of the 
                           LIS."
               ::= { mpLis 5 }

       mpLisStatisticsEntry OBJECT-TYPE
               SYNTAX   MpLisStatisticsEntry
               ACCESS   not-accessible
               STATUS   mandatory
               DESCRIPTION "This entry includes counters of each statistics 
                           information."
               INDEX { mpLisStatIndex }
               ::= { mpLisStatisticsTable 1 }

       MpLisStatisticsEntry ::=
               SEQUENCE {
                        mpLisStatIndex INTEGER, 
                        mpLisStatAtmArpRequestSends Counter,
                        mpLisStatAtmArpReplyReceives Counter,
                        mpLisStatAtmArpNakReceives Counter, 
                        mpLisStatAtmArpReplyTimeouts Counter,
                        mpLisStatInAtmArpRequestSends Counter,
                        mpLisStatInAtmArpReplyReceives Counter,
                        mpLisStatInAtmArpRequestReceives Counter,
                        mpLisStatInAtmArpReplyTimeouts Counter,
                        mpLisStatVcInactDisconnects Counter,
                        mpLisStatVcResourceDisconnects Counter,
                        mpLisStatAtmArpTableAgingouts Counter,
                        mpLisStatAtmArpTableDeletions Counter,
                        mpLisStatInPkts Counter,
                        mpLisStatInReceivePkts Counter,
                        mpLisStatInDiscards Counter,
                        mpLisStatInMtuSizeOvers Counter,
                        mpLisStatInSnapErrs Counter,
                        mpLisStatOutPkts Counter,
                        mpLisStatOutTransmitPkts Counter,
                        mpLisStatOutNoRoutes Counter,
                        mpLisStatOutSvFaults Counter,
                        mpLisStatOutCircuitFaults Counter,
                        mpLisStatOutMaxQueues Counter,
                        mpLisStatOutDestUnusuals Counter,
                        mpLisStatOutMtuSizeOvers Counter,
                        mpLisStatOutVcFailures Counter,
                        mpLisStatOutDiscards Counter,
                        mpLisStatOutMaxVcExceeds Counter,
                        mpLisStatVcSetupCounts Counter,
                        mpLisStatVcMaxExceedFailCounts Counter,
                        mpLisStatVcResourceFailCounts Counter,
                        mpLisStatVcAcceptCounts Counter,
                        mpLisStatVcMaxExceedDenyCounts Counter,
                        mpLisStatVcResourceDenyCounts Counter
                        }

       mpLisStatIndex OBJECT-TYPE
               SYNTAX   INTEGER          
               ACCESS   read-only
               STATUS   mandatory
               DESCRIPTION "This object shows the unique number assigned to 
                           the LIS."
               ::= { mpLisStatisticsEntry 1 }

       mpLisStatAtmArpRequestSends OBJECT-TYPE
               SYNTAX   Counter            
               ACCESS   read-only
               STATUS   mandatory
               DESCRIPTION "This object shows the number of transmission of 
                           ATM ARP request."
               ::= { mpLisStatisticsEntry 2 }

       mpLisStatAtmArpReplyReceives OBJECT-TYPE
               SYNTAX   Counter            
               ACCESS   read-only
               STATUS   mandatory
               DESCRIPTION "This object shows the number of receiving of ATM 
                           ARP reply."
               ::= { mpLisStatisticsEntry 3 }

       mpLisStatAtmArpNakReceives OBJECT-TYPE
               SYNTAX   Counter            
               ACCESS   read-only
               STATUS   mandatory
               DESCRIPTION "This object shows the number of receiving of ATM 
                           ARP NAK."
               ::= { mpLisStatisticsEntry 4 }

       mpLisStatAtmArpReplyTimeouts OBJECT-TYPE
               SYNTAX   Counter            
               ACCESS   read-only
               STATUS   mandatory
               DESCRIPTION "This object shows the number of timed-out in 
                           waiting for ATM ARP reply."
               ::= { mpLisStatisticsEntry 5 }

       mpLisStatInAtmArpRequestSends OBJECT-TYPE
               SYNTAX   Counter            
               ACCESS   read-only
               STATUS   mandatory
               DESCRIPTION "This object shows the number of transmission of 
                           InATM ARP request."
               ::= { mpLisStatisticsEntry 6 }

       mpLisStatInAtmArpReplyReceives OBJECT-TYPE
               SYNTAX   Counter            
               ACCESS   read-only
               STATUS   mandatory
               DESCRIPTION "This object shows the number of receiving of InATM 
                           ARP reply."
               ::= { mpLisStatisticsEntry 7 }

       mpLisStatInAtmArpRequestReceives OBJECT-TYPE
               SYNTAX   Counter            
               ACCESS   read-only
               STATUS   mandatory
               DESCRIPTION "This object shows the number of receiving of InATM 
                           ARP request."
               ::= { mpLisStatisticsEntry 8 }

       mpLisStatInAtmArpReplyTimeouts OBJECT-TYPE
               SYNTAX   Counter            
               ACCESS   read-only
               STATUS   mandatory
               DESCRIPTION "This object shows the number of timed-out in 
                           waiting for InATM ARP reply."
               ::= { mpLisStatisticsEntry 9 }

       mpLisStatVcInactDisconnects OBJECT-TYPE
               SYNTAX   Counter            
               ACCESS   read-only
               STATUS   mandatory
               DESCRIPTION "This object shows the number of disconenction by 
                           inactivity timer."
               ::= { mpLisStatisticsEntry 10 }

       mpLisStatVcResourceDisconnects OBJECT-TYPE
               SYNTAX   Counter            
               ACCESS   read-only
               STATUS   mandatory
               DESCRIPTION "This object shows the number of disconenction by 
                           resource limitation."
               ::= { mpLisStatisticsEntry 11 }

       mpLisStatAtmArpTableAgingouts OBJECT-TYPE
               SYNTAX   Counter            
               ACCESS   read-only
               STATUS   mandatory
               DESCRIPTION "This object show the number of ATM ARP table that 
                           is deleted due to aged out."
               ::= { mpLisStatisticsEntry 12 }

       mpLisStatAtmArpTableDeletions OBJECT-TYPE
               SYNTAX   Counter            
               ACCESS   read-only
               STATUS   mandatory
               DESCRIPTION "This object show the number of ATM ARP table that 
                           is deleted due to resource limitation."
               ::= { mpLisStatisticsEntry 13 }

       mpLisStatInPkts OBJECT-TYPE
               SYNTAX   Counter            
               ACCESS   read-only
               STATUS   mandatory
               DESCRIPTION "This object show the number of packets transmitted 
                           to IP router part."
               ::= { mpLisStatisticsEntry 14 }

       mpLisStatInReceivePkts OBJECT-TYPE
               SYNTAX   Counter            
               ACCESS   read-only
               STATUS   mandatory
               DESCRIPTION "This object show the number of packets received 
                           from ATM interface."
               ::= { mpLisStatisticsEntry 15 }

       mpLisStatInDiscards OBJECT-TYPE
               SYNTAX   Counter            
               ACCESS   read-only
               STATUS   mandatory
               DESCRIPTION "This object show the number of packets that are 
                           discarded due to resource limitation."
               ::= { mpLisStatisticsEntry 16 }

       mpLisStatInMtuSizeOvers OBJECT-TYPE
               SYNTAX   Counter            
               ACCESS   read-only
               STATUS   mandatory
               DESCRIPTION "This object show the number of discarded packets 
                           due to exceeding MTU."
               ::= { mpLisStatisticsEntry 17 }

       mpLisStatInSnapErrs OBJECT-TYPE
               SYNTAX   Counter            
               ACCESS   read-only
               STATUS   mandatory
               DESCRIPTION "This object show the number of discarded packets 
                           due to format error of SNAP in IP over ATM."
               ::= { mpLisStatisticsEntry 18 }

       mpLisStatOutPkts OBJECT-TYPE
               SYNTAX   Counter            
               ACCESS   read-only
               STATUS   mandatory
               DESCRIPTION "This object show the number of packets received 
                           from  IP router part."
               ::= { mpLisStatisticsEntry 19 }

       mpLisStatOutTransmitPkts OBJECT-TYPE
               SYNTAX   Counter            
               ACCESS   read-only
               STATUS   mandatory
               DESCRIPTION "This object show the number of packets transmitted 
                           to ATM interface."
               ::= { mpLisStatisticsEntry 20 }

       mpLisStatOutNoRoutes OBJECT-TYPE
               SYNTAX   Counter            
               ACCESS   read-only
               STATUS   mandatory
               DESCRIPTION " This object show the number of discarded packets 
                           due to route unknown."
               ::= { mpLisStatisticsEntry 21 }

       mpLisStatOutSvFaults OBJECT-TYPE
               SYNTAX   Counter            
               ACCESS   read-only
               STATUS   mandatory
               DESCRIPTION "This object show the number of discarded packets 
                           due to failure of ATM ARP server."
               ::= { mpLisStatisticsEntry 22 }

       mpLisStatOutCircuitFaults OBJECT-TYPE
               SYNTAX   Counter            
               ACCESS   read-only
               STATUS   mandatory
               DESCRIPTION "This object show the number of discarded packets 
                           due to failure of link."
               ::= { mpLisStatisticsEntry 23 }

       mpLisStatOutMaxQueues OBJECT-TYPE
               SYNTAX   Counter            
               ACCESS   read-only
               STATUS   mandatory
               DESCRIPTION "This object show the number of discarded packets 
                           due to overflowing queue."
               ::= { mpLisStatisticsEntry 24 }

       mpLisStatOutDestUnusuals OBJECT-TYPE
               SYNTAX   Counter            
               ACCESS   read-only
               STATUS   mandatory
               DESCRIPTION "This object show the number of discarded packets 
                           due to illegal destination."
               ::= { mpLisStatisticsEntry 25 }

       mpLisStatOutMtuSizeOvers OBJECT-TYPE
               SYNTAX   Counter            
               ACCESS   read-only
               STATUS   mandatory
               DESCRIPTION "This object show the number of discarded packets 
                            that are received from IP router part due to 
                            exceeding MTU."
               ::= { mpLisStatisticsEntry 26 }

       mpLisStatOutVcFailures OBJECT-TYPE
               SYNTAX   Counter            
               ACCESS   read-only
               STATUS   mandatory
               DESCRIPTION "This object show the number of discarded packets 
                           due to configuration failure of connection."
               ::= { mpLisStatisticsEntry 27 }

       mpLisStatOutDiscards OBJECT-TYPE
               SYNTAX   Counter            
               ACCESS   read-only
               STATUS   mandatory
               DESCRIPTION "This object show the number of discarded packets 
                           due to resource limitation in transmitting."
               ::= { mpLisStatisticsEntry 28 }

       mpLisStatOutMaxVcExceeds OBJECT-TYPE
               SYNTAX   Counter            
               ACCESS   read-only
               STATUS   mandatory
               DESCRIPTION "This object show the number of discarded packets 
                           due to exceeding the maximum number of VC 
                           connection."
               ::= { mpLisStatisticsEntry 29 }

       mpLisStatVcSetupCounts OBJECT-TYPE
               SYNTAX   Counter            
               ACCESS   read-only
               STATUS   mandatory
               DESCRIPTION "This object shows the number of configuring of 
                           call."
               ::= { mpLisStatisticsEntry 30 }

       mpLisStatVcMaxExceedFailCounts OBJECT-TYPE
               SYNTAX   Counter            
               ACCESS   read-only
               STATUS   mandatory
               DESCRIPTION "This object shows the number of failure of call 
                           configuration due to exceeding the maximum 
                           simultaneous connections of VC."
               ::= { mpLisStatisticsEntry 31 }

       mpLisStatVcResourceFailCounts OBJECT-TYPE
               SYNTAX   Counter            
               ACCESS   read-only
               STATUS   mandatory
               DESCRIPTION "This object shows the number of failure of call 
                           configuration due to resource limitation."
               ::= { mpLisStatisticsEntry 32 }

       mpLisStatVcAcceptCounts OBJECT-TYPE
               SYNTAX   Counter            
               ACCESS   read-only
               STATUS   mandatory
               DESCRIPTION "This object shows the number of called by ATM ARP 
                           client."
               ::= { mpLisStatisticsEntry 33 }

       mpLisStatVcMaxExceedDenyCounts OBJECT-TYPE
               SYNTAX   Counter            
               ACCESS   read-only
               STATUS   mandatory
               DESCRIPTION "This object shows the number of refusing incoming 
                           call due to exceeding the maximum simultaneous 
                           connections of VC."
               ::= { mpLisStatisticsEntry 34 }
 
       mpLisStatVcResourceDenyCounts OBJECT-TYPE
               SYNTAX   Counter            
               ACCESS   read-only
               STATUS   mandatory
               DESCRIPTION "This object shows the number of refusing incoming 
                           call due to resource limitation."
               ::= { mpLisStatisticsEntry 35 }

       mpLisPvcRegistNumber OBJECT-TYPE
               SYNTAX   INTEGER           
               ACCESS   read-only
               STATUS   mandatory
               DESCRIPTION "This object shows the total number of currently 
                           registored PVC."
               ::= { mpLis 6 }

       mpLisStSvcRegistNumber OBJECT-TYPE
               SYNTAX   INTEGER           
               ACCESS   read-only
               STATUS   mandatory
               DESCRIPTION "This object shows the total number of currently 
                           registored static SVC."
               ::= { mpLis 7 }

       mpLisVcConnectNumber OBJECT-TYPE
               SYNTAX   INTEGER           
               ACCESS   read-only
               STATUS   mandatory
               DESCRIPTION "This object shows the total number of currently 
                           connected VC in IP over ATM functional block."
               ::= { mpLis 8 }

       mpLisSysInactivityTimer OBJECT-TYPE
               SYNTAX   INTEGER           
                                    -- The default value is recommended by 
                                    -- RFC1755.
               ACCESS   read-write
               STATUS   mandatory
               DESCRIPTION "This object shows the value of inactivity timer in 
                           second."
               ::= { mpLis 9 }

       mpLisSysHoldingTimer OBJECT-TYPE
               SYNTAX   INTEGER           
                                  -- The default value is recommended by 
                                  -- RFC1755.
               ACCESS   read-write
               STATUS   mandatory
               DESCRIPTION "This object shows the value of holding timer in 
                           second."
               ::= { mpLis 10 }

       mpLisSysAtmArpReplyTimer OBJECT-TYPE
               SYNTAX   INTEGER           
               ACCESS   read-write
               STATUS   mandatory
               DESCRIPTION "This object shows the value of ATM ARP reply 
                           waiting timer in second."
               ::= { mpLis 11 }

       mpLisSysInAtmArpRequestTimer OBJECT-TYPE
               SYNTAX   INTEGER           
               ACCESS   read-write
               STATUS   mandatory
               DESCRIPTION "This object shows the value of In ATM ARP request 
                           waiting timer in second."
               ::= { mpLis 12 }

       mpLisSysInAtmArpReplyTimer OBJECT-TYPE
               SYNTAX   INTEGER           
               ACCESS   read-write
               STATUS   mandatory
               DESCRIPTION "This object shows the value of In ATM ARP reply 
                           waiting timer in second."
               ::= { mpLis 13 }

       mpLisSysAtmArpAgingTime OBJECT-TYPE
               SYNTAX   INTEGER           
                                    -- The default value is recommended by 
                                    -- RFC1577.
               ACCESS   read-write
               STATUS   mandatory
               DESCRIPTION "This object sets the aging time of ATM ARP in 
                            second."
               ::= { mpLis 14 }

       mpLisSysAtmArpSvPollTime OBJECT-TYPE
               SYNTAX   INTEGER           
               ACCESS   read-write
               STATUS   mandatory
               DESCRIPTION "This obhject sets cycle time to check status of VC 
                           connection of ATM ARP server in second."
               ::= { mpLis 15 }

       mpLisSysAtmArpSvRetry OBJECT-TYPE
               SYNTAX   INTEGER           
               ACCESS   read-write
               STATUS   mandatory
               DESCRIPTION "This object sets the number of retrying in case of 
                           failure of call configuration to ATM ARP server."
               ::= { mpLis 16 }

       mpLisSysAtmArpClRetry OBJECT-TYPE
               SYNTAX   INTEGER           
               ACCESS   read-write
               STATUS   mandatory
               DESCRIPTION "This object sets the number of retrying in case of 
                           failure of call configuration to ATM ARP client."
               ::= { mpLis 17 }

       mpLisSysAtmArpReqRetry OBJECT-TYPE
               SYNTAX   INTEGER           
               ACCESS   read-write
               STATUS   mandatory
               DESCRIPTION "This object sets tne number of retrying of ATM ARP
                           request in case of no response from ATM ARP server 
                           to which ATM ARP request is sent before timer 
                           expiration."
               ::= { mpLis 18 }

       mpLisSysInAtmArpReqRetry OBJECT-TYPE
               SYNTAX   INTEGER           
               ACCESS   read-write
               STATUS   mandatory
               DESCRIPTION "This object sets tne number of retrying of InATM ARP
                           request in case of no response from ATM ARP client 
                           to which InATM ARP request is sent before timer 
                           expiration."
               ::= { mpLis 19 }

       mpLisSysMaxVcConnect OBJECT-TYPE
               SYNTAX   INTEGER           
               ACCESS   read-write
               STATUS   mandatory
               DESCRIPTION "This object sets the maximum number of simultaneous 
                           connections that is used in IP over ATM functional 
                           block. This number is the sum of PVC, dynamic SVC 
                           and static SVC that are able to connect 
                           simultaneously."
               ::= { mpLis 20 }

       mpLisSysMaxQueueNumber OBJECT-TYPE
               SYNTAX  INTEGER
               ACCESS  read-write
               STATUS  mandatory
               DESCRIPTION "The object sets the maximum number of queues
                            include packets that are received from IP
                            router."
               ::= { mpLis 21 }

--  ***************************************************************************
--  the SanFran DNS Group
--  ***************************************************************************

   --  Implementation of this group is mandatory for all the SanFran systems.

        mpDnsClientNameServerTable OBJECT-TYPE
                SYNTAX SEQUENCE OF MpDnsClientNameServerEntry
                ACCESS not-accessible
                STATUS mandatory
                DESCRIPTION "Table of DNS name server IP addresses."
                ::= { mpDns 1 }

        mpDnsClientNameServerEntry OBJECT-TYPE
                SYNTAX MpDnsClientNameServerEntry
                ACCESS not-accessible
                STATUS mandatory
                DESCRIPTION "Entry of DNS name server IP address."
                INDEX { mpDnsClientServerEntIpAddress }
                ::= { mpDnsClientNameServerTable 1 }

        MpDnsClientNameServerEntry ::=
                SEQUENCE {
                         mpDnsClientServerEntIpAddress
                              IpAddress,
                         mpDnsClientServerEntStatus
                              INTEGER
                         }
                
        mpDnsClientServerEntIpAddress OBJECT-TYPE
                SYNTAX IpAddress
                ACCESS read-only
                STATUS mandatory
                DESCRIPTION "DNS name server IP address."
                ::= { mpDnsClientNameServerEntry 1 }

        mpDnsClientServerEntStatus OBJECT-TYPE
                SYNTAX INTEGER {
                               valid(1),
                               invalid(2)
                               }
                ACCESS read-write
                STATUS mandatory
                DESCRIPTION "DNS name server table entry status."
                ::= { mpDnsClientNameServerEntry 2 }

        mpDnsClientStaticRRTable OBJECT-TYPE
                SYNTAX SEQUENCE OF MpDnsClientStaticRREntry
                ACCESS not-accessible
                STATUS mandatory
                DESCRIPTION "Table of DNS Resource Records(RR)."
                ::= { mpDns 2 }

        mpDnsClientStaticRREntry OBJECT-TYPE
                SYNTAX MpDnsClientStaticRREntry
                ACCESS not-accessible
                STATUS mandatory
                DESCRIPTION "Entry of DNS Resource Record."
                INDEX { mpDnsClientStaticRREntIndex }
                ::= { mpDnsClientStaticRRTable 1 }

        MpDnsClientStaticRREntry ::=
                SEQUENCE {
                         mpDnsClientStaticRREntIndex
                                INTEGER,
                         mpDnsClientStaticRREntHostName
                                DisplayString,
                         mpDnsClientStaticRREntTimeToLive
                                INTEGER,
                         mpDnsClientStaticRREntType
                                INTEGER,
                         mpDnsClientStaticRREntIpAddress
                                IpAddress,
                         mpDnsClientStaticRREntStatus
                                INTEGER
                         }

        mpDnsClientStaticRREntIndex OBJECT-TYPE
                SYNTAX INTEGER
                ACCESS read-only
                STATUS mandatory
                DESCRIPTION "Index of a particular entry."
                ::= { mpDnsClientStaticRREntry 1 }

        mpDnsClientStaticRREntHostName OBJECT-TYPE
                SYNTAX DisplayString (SIZE (0..60))
                ACCESS read-write
                STATUS mandatory
                DESCRIPTION "The RR's host name field."
                ::= { mpDnsClientStaticRREntry 2 }

        mpDnsClientStaticRREntTimeToLive OBJECT-TYPE
                SYNTAX INTEGER
                ACCESS read-write
                STATUS mandatory
                DESCRIPTION "The RR's Time to Live field. Currently,
                            this value can be set to -1 (infinity) only."
                ::= { mpDnsClientStaticRREntry 3 }

        mpDnsClientStaticRREntType OBJECT-TYPE
              SYNTAX  INTEGER {
                          type-a(1)         -- Host Address
                      }
                ACCESS read-write
                STATUS mandatory
                DESCRIPTION "The RR's type field."
                ::= { mpDnsClientStaticRREntry 4 }

        mpDnsClientStaticRREntIpAddress OBJECT-TYPE
                SYNTAX IpAddress
                ACCESS read-write
                STATUS mandatory
                DESCRIPTION "The RR's IP address field."
                ::= { mpDnsClientStaticRREntry 5 }

        mpDnsClientStaticRREntStatus OBJECT-TYPE
                SYNTAX INTEGER {
                               valid(1),
                               invalid(2)
                               }
                ACCESS read-write
                STATUS mandatory
                DESCRIPTION "The RR's entry status."
                ::= { mpDnsClientStaticRREntry 6 }

        mpDnsClientLocalDomainTable OBJECT-TYPE
                SYNTAX SEQUENCE OF MpDnsClientLocalDomainEntry
                ACCESS not-accessible
                STATUS mandatory
                DESCRIPTION "Table of DNS local domain names."
                ::= { mpDns 3 }

        mpDnsClientLocalDomainEntry OBJECT-TYPE
                SYNTAX MpDnsClientLocalDomainEntry
                ACCESS not-accessible
                STATUS mandatory
                DESCRIPTION "Entry of DNS local domain name."
                INDEX { mpDnsClientLocalDomainEntIndex }
                ::= { mpDnsClientLocalDomainTable 1 }

        MpDnsClientLocalDomainEntry ::=
                SEQUENCE {
                         mpDnsClientLocalDomainEntIndex
                                INTEGER,
                         mpDnsClientLocalDomainEntName
                                DisplayString,
                         mpDnsClientLocalDomainEntStatus
                                INTEGER
                         }

        mpDnsClientLocalDomainEntIndex OBJECT-TYPE
                SYNTAX INTEGER
                ACCESS read-only
                STATUS mandatory
                DESCRIPTION "Index of a particular entry."
                ::= { mpDnsClientLocalDomainEntry 1 }

        mpDnsClientLocalDomainEntName OBJECT-TYPE
                SYNTAX DisplayString (SIZE (0..255))
                ACCESS read-write
                STATUS mandatory
                DESCRIPTION "Local domain name field."
                ::= { mpDnsClientLocalDomainEntry 2 }

        mpDnsClientLocalDomainEntStatus OBJECT-TYPE
                SYNTAX INTEGER {
                               valid(1),
                               invalid(2)
                               }
                ACCESS read-write
                STATUS mandatory
                DESCRIPTION "Local domain table entry status."
                ::= { mpDnsClientLocalDomainEntry 3 }

        mpDnsClientMaxTimeToLive OBJECT-TYPE
                SYNTAX INTEGER
                ACCESS read-write
                STATUS mandatory
                DESCRIPTION "DNS cache maximum Time to Live(TTL)."
                ::= { mpDns 4 }

        mpDnsClientNumberOfQueries OBJECT-TYPE
                SYNTAX Counter
                ACCESS read-only
                STATUS mandatory
                DESCRIPTION "A counter on how many RR queries have been
                            sent to name server(s)."
                ::= { mpDns 5 }

        mpDnsClientNumberOfResponses OBJECT-TYPE
                SYNTAX Counter
                ACCESS read-only
                STATUS mandatory
                DESCRIPTION "A counter on how many RR responses have been
                            received from name server(s)."
                ::= { mpDns 6 }


--  ***************************************************************************
--  the SanFran LEC Group
--  ***************************************************************************

   --  Implementation of this group is mandatory for all the SanFran systems.  


       mpLecConfigTable OBJECT-TYPE
               SYNTAX   SEQUENCE OF MpLecConfigEntry
               ACCESS   not-accessible
               STATUS   mandatory
               DESCRIPTION "Indicates the table of the LEC information."
               ::= { mpLec 1 }

       mpLecConfigEntry OBJECT-TYPE
               SYNTAX   MpLecConfigEntry
               ACCESS   not-accessible
               STATUS   mandatory
               DESCRIPTION "Indicates the entry of the LEC information."
               INDEX { mpLecIndex }
               ::= { mpLecConfigTable 1 }

       MpLecConfigEntry ::=
               SEQUENCE {
                        mpLecIndex INTEGER,
                        mpLecArpCacheDeleteTime INTEGER,
                        mpLecUnsolicArpResAccept INTEGER,
                        mpLecVccAgingAction INTEGER,
                        mpLecUnknownFrameSendTiming INTEGER,
                        mpLecType  INTEGER,
                        mpLecPrimaryAtmInterface INTEGER,
                        mpLecDefaultSendTrafficId INTEGER,
                        mpLecAtmAddressSel OCTET STRING,
                        mpLecDefaultRcvTrafficId INTEGER,
                        mpLecLecsId INTEGER                 -- @012
                        }

       mpLecIndex OBJECT-TYPE
               SYNTAX   INTEGER             --  (1..2147483647)
               ACCESS   read-only
               STATUS   mandatory
               DESCRIPTION "Indicates the index value to identify this entry."
               ::= { mpLecConfigEntry 1 }

       mpLecArpCacheDeleteTime OBJECT-TYPE
               SYNTAX   INTEGER           
               ACCESS   read-write
               STATUS   mandatory
               DESCRIPTION "The aging time for the unused ARP cache entry 
                           (sec)."
               ::= { mpLecConfigEntry 2 }

       mpLecUnsolicArpResAccept OBJECT-TYPE
               SYNTAX   INTEGER { 
                                enabled(1), 
                                disabled(2) 
                                }         
               ACCESS   read-write
               STATUS   mandatory
               DESCRIPTION "Indicate whether the LEC does the address learning 
                           by the LE_ARP_RESPONSE which is broadcasted to 
                           another LEC, or not. If the value 'enabled(1)' is 
                           set, the LEC does the address learning. If the 
                           value 'disabled(2)' is set, the LEC does not do the 
                           address learning."
               ::= { mpLecConfigEntry 3 }

       mpLecVccAgingAction OBJECT-TYPE
               SYNTAX   INTEGER { 
                                noCut(1), 
                                myConnectCut(2), 
                                otherConnectCut(3), 
                                allCut(4) 
                                }        
               ACCESS   read-write
               STATUS   mandatory
               DESCRIPTION "Indicate whether the LEC disconnects the unused VCC
                           for a time defined as C12. The time value is given 
                           by the lecVCCTimeoutPeriod (LEC MIB).
                           If the value 'noCut(1)' is set, the LEC does not 
                           disconnect the VCC. If the value 'myConnectCut(2)' 
                           is set, the LEC disconnects only the VCC which the 
                           LEC sets up. If the value 'otherConnectCut(3)' is 
                           set, the LEC disconnects only the VCC which the 
                           destination LEC sets up. If the value 'allCut(4)' is
                           set, the LEC disconnects all the VCCs."
               ::= { mpLecConfigEntry 4 }

       mpLecUnknownFrameSendTiming OBJECT-TYPE
               SYNTAX   INTEGER { 
                                soon(1), 
                                later(2), 
                                noSend(3) 
                                }        
               ACCESS   read-write
               STATUS   mandatory
               DESCRIPTION "Indicate the timing to send an unknown frame to 
                           the BUS. If the value 'soon(1)' is set, the LEC 
                           sends the packet immediately. If the value 'later(2)'
                           is set, the LEC sends the packet after a time 
                           defined by mpLeUnknownFrameWaitTime. If the value 
                           'noSend(3)' is set, the LEC does not send the 
                           packet."
               ::= { mpLecConfigEntry 5 }

       mpLecType OBJECT-TYPE
               SYNTAX  INTEGER {atmForum(1), serverLess(2)}
               ACCESS  read-write
               STATUS  mandatory
               DESCRIPTION "Indicates one of the LEC types described as
                            follows:
                            a) The LEC defined by ATM Forum
                            b) The proprietary LEC (serverless method)
                               defined by NEC.
                            If it is set to '1', this entry uses the
                            method defined by ATM Forum. If it is set to
                            '2', this entry uses the proprietary LEC 
                            defined by NEC."
               ::= { mpLecConfigEntry 6 }

       mpLecPrimaryAtmInterface OBJECT-TYPE
               SYNTAX  INTEGER
               ACCESS  read-write
               STATUS  mandatory
               DESCRIPTION "Indicates number of ATM port which is used for 
                            decision of primary ATM address."
               ::= { mpLecConfigEntry 7 }

        mpLecDefaultSendTrafficId OBJECT-TYPE
               SYNTAX  INTEGER
               ACCESS  read-write
               STATUS  mandatory
               DESCRIPTION "Indicates the number of default send traffic ID 
                            that is used by LEC."
               ::= { mpLecConfigEntry 8 }

       mpLecAtmAddressSel OBJECT-TYPE
               SYNTAX  OCTET STRING (1)
               ACCESS  read-write
               STATUS  mandatory
               DESCRIPTION "Indicates SEL of primary ATM address for LEC"
               ::= { mpLecConfigEntry 9 }

        mpLecDefaultRcvTrafficId OBJECT-TYPE
               SYNTAX  INTEGER
               ACCESS  read-write
               STATUS  mandatory
               DESCRIPTION "Indicates the number of default receive traffic ID
                            that is used by LEC."
               ::= { mpLecConfigEntry 10 }

-- @012 add START
       mpLecLecsId OBJECT-TYPE
              SYNTAX  INTEGER
              ACCESS  read-write
              STATUS  mandatory
              DESCRIPTION "Indicates the number of Lecs ID that is used by LEC."
              ::= { mpLecConfigEntry 11 }
-- @012 add END

       mpLecsConfigTable OBJECT-TYPE
               SYNTAX   SEQUENCE OF MpLecsConfigEntry
               ACCESS   not-accessible
               STATUS   mandatory
               DESCRIPTION "Indicates the table of LECS information."
               ::= { mpLec 2 }

       mpLecsConfigEntry OBJECT-TYPE
               SYNTAX   MpLecsConfigEntry
               ACCESS   not-accessible
               STATUS   mandatory
               DESCRIPTION "Indicates the table entry of LECS information.

                            LECS Registration:
                            1) The object 'mpLecsRowStatus' is set to
                               'createAndWait(5)', to create LECS entry
                               into the table 'mpLecsConfigTable'.
                            2) The appropriate values are set to the object
                               'mpLecsConfigTable'.
                            3) 'active(1)' is set to the object 
                               'mpLecRowStatus', to activate the LECS entry.

                            LECS deletion:
                            1) 'notInService(2)' is set to the object
                               'mpLecsRowStatus', to deactivate the LECS
                               entry.
                            2) 'destroy(6)' is set to the object
                               'mpLecRowStatus', to delete the LECS entry."   
 
               INDEX { mpLecsIndex }
               ::= { mpLecsConfigTable 1 }

       MpLecsConfigEntry ::=
               SEQUENCE {
                        mpLecsIndex INTEGER,
                        mpLecsCallType INTEGER,
                        mpLecsAtmAddress OCTET STRING,
                        mpLecsInterface INTEGER,
                        mpLecsConfigDirectVpi INTEGER,
                        mpLecsConfigDirectVci INTEGER,
                        mpLecsConfigDirectSendTrafficId INTEGER,
                        mpLecsRowStatus RowStatus,
                        mpLecsConfigDirectRcvTrafficId INTEGER
                        }

       mpLecsIndex OBJECT-TYPE
               SYNTAX   INTEGER 
               ACCESS   read-only
               STATUS   mandatory
               DESCRIPTION "Indicates the index value to identify this 
                            table entry."
               ::= { mpLecsConfigEntry 1 }

       mpLecsCallType OBJECT-TYPE
               SYNTAX   INTEGER {
                                staticSvc(1),
                                pvc(2)
                                }
               ACCESS   read-write
               STATUS   mandatory
               DESCRIPTION "Indicates the type of the connection between
                            this LEC and the LECS. If it is set to '1',
                            the type is SVC for ATM address registration.
                            If it is set to '2', the type is PVC for
                            VPI/VCI registration."
               ::= { mpLecsConfigEntry 2 }

       mpLecsAtmAddress OBJECT-TYPE
               SYNTAX   OCTET STRING (SIZE(0..255))
               ACCESS   read-write
               STATUS   mandatory
               DESCRIPTION "Indicates the ATM address of the LECS."
               ::= { mpLecsConfigEntry 3 }

       mpLecsInterface OBJECT-TYPE
               SYNTAX   INTEGER 
               ACCESS   read-write
               STATUS   mandatory
               DESCRIPTION "Indicates the ATM interface number to which
                            the LECS is connected."
               ::= { mpLecsConfigEntry 4 }

       mpLecsConfigDirectVpi OBJECT-TYPE
               SYNTAX   INTEGER (0..255)
               ACCESS   read-write
               STATUS   mandatory
               DESCRIPTION "Indicates the VPI of the Configuration
                            Direct VCC."
               ::= { mpLecsConfigEntry 5 }

       mpLecsConfigDirectVci OBJECT-TYPE
               SYNTAX   INTEGER (0..65535)
               ACCESS   read-write
               STATUS   mandatory
               DESCRIPTION "Indicates the VCI of the Configuration 
                            Direct VCC."
               ::= { mpLecsConfigEntry 6 }

       mpLecsConfigDirectSendTrafficId OBJECT-TYPE
               SYNTAX   INTEGER 
               ACCESS   read-write
               STATUS   mandatory
               DESCRIPTION "Indicates the send traffic ID of the Configuration 
                            Direct VCC."
               ::= { mpLecsConfigEntry 7 }

       mpLecsRowStatus OBJECT-TYPE
               SYNTAX   RowStatus
               ACCESS   read-write
               STATUS   mandatory
               DESCRIPTION "This object is used to create, delete, 
                            or modify the row within this table.
                            Within each conceptual mpLecsConfigTable
                            row, objects which are writable may be
                            modified regardless of the value of 
                            mpLecsRowStatus. It is not necessary
                            to set a row's status to 'notInService'
                            first."
               ::= { mpLecsConfigEntry 8 }

       mpLecsConfigDirectRcvTrafficId OBJECT-TYPE
               SYNTAX   INTEGER 
               ACCESS   read-write
               STATUS   mandatory
               DESCRIPTION "Indicates receive the traffic ID of the 
                            Configuration Direct VCC."
               ::= { mpLecsConfigEntry 9 }

       mpLecServerConfigTable OBJECT-TYPE
               SYNTAX   SEQUENCE OF MpLecServerConfigEntry
               ACCESS   not-accessible
               STATUS   mandatory
               DESCRIPTION "Indicates the table of the Server 
                            Information."
               ::= { mpLec 3 }

       mpLecServerConfigEntry OBJECT-TYPE
               SYNTAX   MpLecServerConfigEntry
               ACCESS   not-accessible
               STATUS   mandatory
               DESCRIPTION "Indicates the entry of the Server
                            Information."
               INDEX { mpLecSvIndex }
               ::= { mpLecServerConfigTable 1 }

       MpLecServerConfigEntry ::=
               SEQUENCE {
                        mpLecSvIndex INTEGER,
                        mpLecSvConfigLecsType INTEGER,
                        mpLecSvConfigLecsIndex INTEGER,
                        mpLecSvLesCallType INTEGER,
                        mpLecSvCtrlDirectVccInterface INTEGER,
                        mpLecSvCtrlDirectVpi INTEGER,
                        mpLecSvCtrlDirectVci INTEGER,
                        mpLecSvCtrlDirectSendTrafficId INTEGER,
                        mpLecSvCtrlDistributeVccInterface INTEGER,
                        mpLecSvCtrlDistributeVpi INTEGER,
                        mpLecSvCtrlDistributeVci INTEGER,
                        mpLecSvCtrlDistributeSendTrafficId INTEGER,
                        mpLecSvBusCallType INTEGER,
                        mpLecSvMcastSendVccInterface INTEGER,
                        mpLecSvMcastSendVpi INTEGER,
                        mpLecSvMcastSendVci INTEGER,
                        mpLecSvMcastSendSendTrafficId INTEGER,
                        mpLecSvMcastForwardVccInterface INTEGER,
                        mpLecSvMcastForwardVpi INTEGER,
                        mpLecSvMcastForwardVci INTEGER,
                        mpLecSvMcastForwardSendTrafficId INTEGER,
                        mpLecSvCtrlDirectRcvTrafficId INTEGER,
                        mpLecSvCtrlDistributeRcvTrafficId INTEGER,
                        mpLecSvMcastSendRcvTrafficId INTEGER,
                        mpLecSvMcastForwardRcvTrafficId INTEGER
                        }

       mpLecSvIndex OBJECT-TYPE
               SYNTAX   INTEGER 
               ACCESS   read-only
               STATUS   mandatory
               DESCRIPTION "Indicates the lecIndex of the LEC
                            which corresponds to this entry."
               ::= { mpLecServerConfigEntry 1 }

       mpLecSvConfigLecsType OBJECT-TYPE
               SYNTAX   INTEGER {
                                enabled(1),
                                disabled(2)
                                }
               ACCESS   read-write
               STATUS   mandatory
               DESCRIPTION "Indicates whether the LECS registered in 
                            the table 'mpLecsConfigTable' is used or 
                            not, when 'automatic(1)' is set to the
                            object 'lecConfigMode'(LEC MIB).
                            If it is set to '2', the LECS is not used.
                            In case when the LECS registered is not used,
                            the LECS should be specified by the method
                            defined by ATM Forum."
               ::= { mpLecServerConfigEntry 2 }

       mpLecSvConfigLecsIndex OBJECT-TYPE
               SYNTAX   INTEGER 
               ACCESS   read-write
               STATUS   mandatory
               DESCRIPTION "Indicates the 'mpLecsIndex' of the table
                            'mpLecsConfigTable', to identify the LECS.
                            This object is valid only when 'enable(1)'
                            is set to the object 'mpLecsSvConfigLecsType'."
               ::= { mpLecServerConfigEntry 3 }

       mpLecSvLesCallType OBJECT-TYPE
               SYNTAX   INTEGER {
                                staticSvc(1),
                                pvc(2)
                                }
               ACCESS   read-write
               STATUS   mandatory
               DESCRIPTION "Indicates the type of the connection between
                            this LEC and the LES."
               ::= { mpLecServerConfigEntry 4 }

       mpLecSvCtrlDirectVccInterface OBJECT-TYPE
               SYNTAX   INTEGER
               ACCESS   read-write
               STATUS   mandatory
               DESCRIPTION "Indicates the ATM interface number
                            on which the Control Direct VCC is set."
               ::= { mpLecServerConfigEntry 5 }

       mpLecSvCtrlDirectVpi OBJECT-TYPE
               SYNTAX   INTEGER
               ACCESS   read-write
               STATUS   mandatory
               DESCRIPTION "Indicates the VPI of this Control Direct VCC."
               ::= { mpLecServerConfigEntry 6 }

       mpLecSvCtrlDirectVci OBJECT-TYPE
               SYNTAX   INTEGER
               ACCESS   read-write
               STATUS   mandatory
               DESCRIPTION "Indicates the VCI of this Control Direct VCC."
               ::= { mpLecServerConfigEntry 7 }

       mpLecSvCtrlDirectSendTrafficId OBJECT-TYPE
               SYNTAX   INTEGER
               ACCESS   read-write
               STATUS   mandatory
               DESCRIPTION "Indicates the shaper send traffic ID of the Control
                            Direct VCC."
               ::= { mpLecServerConfigEntry 8 }

       mpLecSvCtrlDistributeVccInterface OBJECT-TYPE
               SYNTAX   INTEGER
               ACCESS   read-write
               STATUS   mandatory
               DESCRIPTION "Indicates the ATM interface number on 
                            which the Control Distribute VCC is set."
               ::= { mpLecServerConfigEntry 9 }

       mpLecSvCtrlDistributeVpi OBJECT-TYPE
               SYNTAX   INTEGER
               ACCESS   read-write
               STATUS   mandatory
               DESCRIPTION "Indicates the VPI of the Control Distribute
                            VCC."
               ::= { mpLecServerConfigEntry 10 }

       mpLecSvCtrlDistributeVci OBJECT-TYPE
               SYNTAX   INTEGER
               ACCESS   read-write
               STATUS   mandatory
               DESCRIPTION "Indicates the VCI of the Control 
                            Distribute VCC."
               ::= { mpLecServerConfigEntry 11 }

       mpLecSvCtrlDistributeSendTrafficId OBJECT-TYPE
               SYNTAX   INTEGER
               ACCESS   read-write
               STATUS   mandatory
               DESCRIPTION "Indicates the send traffic ID of the Control
                            Distribute VCC."
               ::= { mpLecServerConfigEntry 12 }

       mpLecSvBusCallType OBJECT-TYPE
               SYNTAX   INTEGER {
                                dynamicSvc(1),
                                pvc(2)
                                }
               ACCESS   read-write
               STATUS   mandatory
               DESCRIPTION "Indicates the type of the connection
                            between this LEC and the BUS. If it is
                            set to '1', the type is SVC specified by the
                            address resolution function. If it is set to '2'
                            the type is PVC for VPI/VCI registration."
               ::= { mpLecServerConfigEntry 13 }

       mpLecSvMcastSendVccInterface OBJECT-TYPE
               SYNTAX   INTEGER
               ACCESS   read-write
               STATUS   mandatory
               DESCRIPTION "Indicates the ATM interface number on which
                            the Multicast Send VCC is set."
               ::= { mpLecServerConfigEntry 14 }

       mpLecSvMcastSendVpi OBJECT-TYPE
               SYNTAX   INTEGER
               ACCESS   read-write
               STATUS   mandatory
               DESCRIPTION "Indicates the VPI of the Multicast
                            Send VCC."
               ::= { mpLecServerConfigEntry 15 }

       mpLecSvMcastSendVci OBJECT-TYPE
               SYNTAX   INTEGER
               ACCESS   read-write
               STATUS   mandatory
               DESCRIPTION "Indicates the VCI of the Multicast
                            Send VCC."
               ::= { mpLecServerConfigEntry 16 }

       mpLecSvMcastSendSendTrafficId OBJECT-TYPE
               SYNTAX   INTEGER
               ACCESS   read-write
               STATUS   mandatory
               DESCRIPTION "Indicates the send traffic ID of the 
                            Multicast Send VCC."
               ::= { mpLecServerConfigEntry 17 }

       mpLecSvMcastForwardVccInterface OBJECT-TYPE
               SYNTAX   INTEGER
               ACCESS   read-write
               STATUS   mandatory
               DESCRIPTION "Indicates the ATM interface number on
                            which the Multicast Forward VCC is set."
               ::= { mpLecServerConfigEntry 18 }

       mpLecSvMcastForwardVpi OBJECT-TYPE
               SYNTAX   INTEGER
               ACCESS   read-write
               STATUS   mandatory
               DESCRIPTION "Indicates the VPI of the Multicast
                            Forward VCC."
               ::= { mpLecServerConfigEntry 19 }

       mpLecSvMcastForwardVci OBJECT-TYPE
               SYNTAX   INTEGER
               ACCESS   read-write
               STATUS   mandatory
               DESCRIPTION "Indicates the VCI of the Multicast
                            Forward VCC."
               ::= { mpLecServerConfigEntry 20 }

       mpLecSvMcastForwardSendTrafficId OBJECT-TYPE
               SYNTAX   INTEGER
               ACCESS   read-write
               STATUS   mandatory
               DESCRIPTION "Indicates the send traffic ID of the Multicast
                            Forward VCC."
               ::= { mpLecServerConfigEntry 21 }

       mpLecSvCtrlDirectRcvTrafficId OBJECT-TYPE
               SYNTAX   INTEGER
               ACCESS   read-write
               STATUS   mandatory
               DESCRIPTION "Indicates the shaper receive traffic ID of the
                            Control Direct VCC."
               ::= { mpLecServerConfigEntry 22 }

       mpLecSvCtrlDistributeRcvTrafficId OBJECT-TYPE
               SYNTAX   INTEGER
               ACCESS   read-write
               STATUS   mandatory
               DESCRIPTION "Indicates the receive traffic ID of the Control
                            Distribute VCC."
               ::= { mpLecServerConfigEntry 23 }

       mpLecSvMcastSendRcvTrafficId OBJECT-TYPE
               SYNTAX   INTEGER
               ACCESS   read-write
               STATUS   mandatory
               DESCRIPTION "Indicates the receive traffic ID of the 
                            Multicast Send VCC."
               ::= { mpLecServerConfigEntry 24 }

       mpLecSvMcastForwardRcvTrafficId OBJECT-TYPE
               SYNTAX   INTEGER
               ACCESS   read-write
               STATUS   mandatory
               DESCRIPTION "Indicates the receive traffic ID of the Multicast
                            Forward VCC."
               ::= { mpLecServerConfigEntry 25 }

       mpLeArpTable OBJECT-TYPE
               SYNTAX   SEQUENCE OF MpLeArpEntry
               ACCESS   not-accessible
               STATUS   mandatory
               DESCRIPTION "Indicates the table of the LE-ARP information."
               ::= { mpLec 4 }

       mpLeArpEntry OBJECT-TYPE
               SYNTAX   MpLeArpEntry
               ACCESS   not-accessible
               STATUS   mandatory
               DESCRIPTION "Indicates the entry of the LE-ARP information.
                           The LE-ARP address information is registered by the 
                           following procedure ;
 
                           1)  The NW manager creates LE-ARP table entry in 
                               mpLeArpTable, by setting 'createAndWait(5)' to 
                               LeArpRowStatus.
 
                           2)  The NW manager sets the appropriate values to 
			       the objects contained in mpLeArpTable.
 
                           3)  The NW manager activates the LE-ARP table entry,
                               by setting 'active(1)' to LeArpRowStatus.
 
                           The LE-ARP address information is deleted by the 
                           following procedure ;
 
                           1)  The NW manager inactivates the LE-ARP table 
                               entry, by setting 'notInService(2)' to 
                               LeArpRowStatus.
 
                           2)  The LE-ARP table entry is deleted, by setting 
                               'destroy(6)' to LeArpRowStatus."
               INDEX { mpLeArpLecIndex, mpLeArpMacAddress }
               ::= { mpLeArpTable 1 }

       MpLeArpEntry ::=
               SEQUENCE {
                        mpLeArpLecIndex INTEGER,
                        mpLeArpMacAddress MacAddress,
                        mpLeArpCallType INTEGER,
                        mpLeArpInterface INTEGER,
                        mpLeArpVpi INTEGER,
                        mpLeArpVci INTEGER,
                        mpLeArpSendTrafficId INTEGER,
                        mpLeArpRcvTrafficId INTEGER
                        }

       mpLeArpLecIndex OBJECT-TYPE
               SYNTAX   INTEGER 
               ACCESS   read-only
               STATUS   mandatory
               DESCRIPTION "Indicates the 'lecIndex' of this client."
               ::= { mpLeArpEntry 1 }

       mpLeArpMacAddress OBJECT-TYPE
               SYNTAX   MacAddress 
               ACCESS   read-only
               STATUS   mandatory
               DESCRIPTION "The MAC address for which this cache entry 
                           provides a translation."
               ::= { mpLeArpEntry 2 }

       mpLeArpCallType OBJECT-TYPE
               SYNTAX   INTEGER { 
                                svc(1), 
                                pvc(2) 
                                }         
               ACCESS   read-write
               STATUS   mandatory
               DESCRIPTION "Indicates the virtual circuit connection type
                            of the LE-ARP entry. If it is set to '1', it is
                            SVC connection. If it is set to '2', it is PVC
                            connection. It is used to set the connection
                            type when an entry is added to the object
                            'mpLeArpTable'."
               ::= { mpLeArpEntry 3 }

       mpLeArpInterface OBJECT-TYPE
               SYNTAX   INTEGER   
               ACCESS   read-write
               STATUS   mandatory
               DESCRIPTION "Indicates the ATM interface number of this LE-ARP 
                            entry. In case of PVC connection, this object is 
                            used to set and confirm the ATM interface number 
                            which is used. In case of SVC connection, it is 
                            used to display the ATM interface number which is 
                            currently used, but it cannot be used to set."
               ::= { mpLeArpEntry 4 }

       mpLeArpVpi OBJECT-TYPE
               SYNTAX   INTEGER   
               ACCESS   read-write
               STATUS   mandatory
               DESCRIPTION "Indicates the VPI value of this LE-ARP entry.
                            In case of PVC connection, this object is used to
                            set and confirm the VPI value which is used. In 
                            case of SVC connection, it is used to display the
                            VPI value which is currently used, but it cannot
                            be used to set."
               ::= { mpLeArpEntry 5 }

       mpLeArpVci OBJECT-TYPE
               SYNTAX   INTEGER           
               ACCESS   read-write
               STATUS   mandatory
               DESCRIPTION "Indicates the VCI value of this LE-ARP entry.
                            In case of PVC connection, this object is used
                            to set and confirm the VCI value which is used.
                            In case of SVC connection, it is used to display
                            the VCI value which is currently used, but it
                            cannot be used to set."
               ::= { mpLeArpEntry 6 }

       mpLeArpSendTrafficId OBJECT-TYPE
               SYNTAX   INTEGER           
               ACCESS   read-write
               STATUS   mandatory
               DESCRIPTION "Indicates the send traffic ID which is used by
                            the LE-ARP entry. In case of PVC connection,
                            this object is used to set and confirm the
                            used traffic ID. In case of SVC connection,
                            it is used to display the used traffic ID, 
                            but it cannot be used to set."
               ::= { mpLeArpEntry 7 }

       mpLeArpRcvTrafficId OBJECT-TYPE
               SYNTAX   INTEGER           
               ACCESS   read-write
               STATUS   mandatory
               DESCRIPTION "Indicates the receive traffic ID which is used by
                            the LE-ARP entry. In case of PVC connection,
                            this object is used to set and confirm the
                            used traffic ID. In case of SVC connection,
                            it is used to display the used traffic ID, 
                            but it cannot be used to set."
               ::= { mpLeArpEntry 8 }

       mpLecStatisticsTable OBJECT-TYPE
               SYNTAX   SEQUENCE OF MpLecStatisticsEntry
               ACCESS   not-accessible
               STATUS   mandatory
               DESCRIPTION "Indicates the table of the LEC statistics
                            information."
               ::= { mpLec 5 }

        mpLecStatisticsEntry OBJECT-TYPE
               SYNTAX   MpLecStatisticsEntry
               ACCESS   not-accessible
               STATUS   mandatory
               DESCRIPTION "Indicates the entry of statistics information
                            counters."
               INDEX { mpLecStatIndex }
               ::= { mpLecStatisticsTable 1 }

       MpLecStatisticsEntry ::=
               SEQUENCE {
                        mpLecStatIndex INTEGER,
                        mpLecStatVcSetupSndCounts Counter,
                        mpLecStatVcSetupRcvCounts Counter,
                        mpLecStatVcReleaseSndCounts Counter,
                        mpLecStatVcReleaseRcvCounts Counter,
                        mpLecStatInContFrameFailures Counter,
                        mpLecStatInDataFrameFailures Counter,
                        mpLecStatInNarpRequests Counter,
                        mpLecStatInTopologyRequests Counter,
                        mpLecStatInBusUcastFrames Counter,
                        mpLecStatInBusMcastFrames Counter,
                        mpLecStatInBusBcastFrames Counter,
                        mpLecStatOutContFrameFailures Counter,
                        mpLecStatOutDataFrameFailures Counter,
                        mpLecStatOutNarpRequests Counter,
                        mpLecStatOutTopologyRequests Counter,
                        mpLecStatOutBusUcastFrames Counter,
                        mpLecStatOutBusMcastFrames Counter,
                        mpLecStatOutBusBcastFrames Counter,
                        mpLecStatEchoControlFrames Counter,
                        mpLecStatInNoIDEntryDataFrames Counter,
                        mpLecStatOutNoIDEntryDataFrames Counter,
                        mpLecStatEchoControlFrames Counter,
                        mpLecStatInNoIDEntryDataFrames Counter,
                        mpLecStatOutNoIDEntryDataFrames Counter
                        }

       mpLecStatIndex OBJECT-TYPE
-- remove @003               SYNTAX   INTEGER (1..2147483647)
               SYNTAX   INTEGER  -- add @003
               ACCESS   read-only
               STATUS   mandatory
               DESCRIPTION "Indicates the lecindex to identify the 
                            LEC which corresponds to this entry."
               ::= { mpLecStatisticsEntry 1 }

       mpLecStatVcSetupSndCounts OBJECT-TYPE
               SYNTAX   Counter
               ACCESS   read-only
               STATUS   mandatory
               DESCRIPTION "Indicates the number of the call set-up
                            done by the LAN Emulation function."
               ::= { mpLecStatisticsEntry 2 }

       mpLecStatVcSetupRcvCounts OBJECT-TYPE
               SYNTAX   Counter
               ACCESS   read-only
               STATUS   mandatory
               DESCRIPTION "Indicates the number of the incoming call
                            received by the LAN Emulation function."
               ::= { mpLecStatisticsEntry 3 }

       mpLecStatVcReleaseSndCounts OBJECT-TYPE
               SYNTAX   Counter
               ACCESS   read-only
               STATUS   mandatory
               DESCRIPTION "Indicates the number of the call cleared by
                            itself, by LAN Emulation function."
               ::= { mpLecStatisticsEntry 4 }

       mpLecStatVcReleaseRcvCounts OBJECT-TYPE
               SYNTAX   Counter
               ACCESS   read-only
               STATUS   mandatory
               DESCRIPTION "Indicates the number of the call cleared by
                            the destination entity, by LAN Emulation
                            function."
               ::= { mpLecStatisticsEntry 5 }

       mpLecStatInContFrameFailures OBJECT-TYPE
               SYNTAX   Counter
               ACCESS   read-only
               STATUS   mandatory
               DESCRIPTION "Indicates the number of the discarded control
                            frames received."
               ::= { mpLecStatisticsEntry 6 }

       mpLecStatInDataFrameFailures OBJECT-TYPE
               SYNTAX   Counter
               ACCESS   read-only
               STATUS   mandatory
               DESCRIPTION "Indicates the number of discarded data frames
                            received."
               ::= { mpLecStatisticsEntry 7 }

       mpLecStatInNarpRequests OBJECT-TYPE
               SYNTAX   Counter
               ACCESS   read-only
               STATUS   mandatory
               DESCRIPTION "Indicates the number of the received LENARP
                            REQUEST frames."
               ::= { mpLecStatisticsEntry 8 }

       mpLecStatInTopologyRequests OBJECT-TYPE
               SYNTAX   Counter
               ACCESS   read-only
               STATUS   mandatory
               DESCRIPTION "Indicates the number of the received 
                            LE-TOPOLOGY-REQUEST frames."
               ::= { mpLecStatisticsEntry 9 }

       mpLecStatInBusUcastFrames OBJECT-TYPE
               SYNTAX   Counter
               ACCESS   read-only
               STATUS   mandatory
               DESCRIPTION "Indicates the number of the unknown unicast
                            frames received from the BUS."
               ::= { mpLecStatisticsEntry 10 }

       mpLecStatInBusMcastFrames OBJECT-TYPE
               SYNTAX   Counter
               ACCESS   read-only
               STATUS   mandatory
               DESCRIPTION "Indicates the number of the multicast
                            frames received from the BUS."
               ::= { mpLecStatisticsEntry 11 }

       mpLecStatInBusBcastFrames OBJECT-TYPE
               SYNTAX   Counter
               ACCESS   read-only
               STATUS   mandatory
               DESCRIPTION "Indicates the number of the broadcast 
                            frames received from the BUS."
               ::= { mpLecStatisticsEntry 12 }

       mpLecStatOutContFrameFailures OBJECT-TYPE
               SYNTAX   Counter
               ACCESS   read-only
               STATUS   mandatory
               DESCRIPTION "Indicates the number of the discarded
                            control frames to be sent."
               ::= { mpLecStatisticsEntry 13 }

       mpLecStatOutDataFrameFailures OBJECT-TYPE
               SYNTAX   Counter
               ACCESS   read-only
               STATUS   mandatory
               DESCRIPTION "Indicates the number of the discarded
                            data frames to be sent."
               ::= { mpLecStatisticsEntry 14 }

       mpLecStatOutNarpRequests OBJECT-TYPE
               SYNTAX   Counter
               ACCESS   read-only
               STATUS   mandatory
               DESCRIPTION "Indicates the number of the LE-N&RP-
                            REQUEST frames sent."
               ::= { mpLecStatisticsEntry 15 }

       mpLecStatOutTopologyRequests OBJECT-TYPE
               SYNTAX   Counter
               ACCESS   read-only
               STATUS   mandatory
               DESCRIPTION "Indicates the number of the LE TOPOLOGY@
                            REQUEST frames sent."
               ::= { mpLecStatisticsEntry 16 }

       mpLecStatOutBusUcastFrames OBJECT-TYPE
               SYNTAX   Counter
               ACCESS   read-only
               STATUS   mandatory
               DESCRIPTION "Indicates the number of the unknown unicast
                            frames sent to the BUS."
               ::= { mpLecStatisticsEntry 17 }

       mpLecStatOutBusMcastFrames OBJECT-TYPE
               SYNTAX   Counter
               ACCESS   read-only
               STATUS   mandatory
               DESCRIPTION "Indicates the number of the multicast frames
                            sent to the BUS."
               ::= { mpLecStatisticsEntry 18 }

       mpLecStatOutBusBcastFrames OBJECT-TYPE
               SYNTAX   Counter
               ACCESS   read-only
               STATUS   mandatory
               DESCRIPTION "Indicates the number of the broadcast frames
                            sent to the BUS."
               ::= { mpLecStatisticsEntry 19 }

       mpLecStatEchoControlFrames OBJECT-TYPE
               SYNTAX   Counter
               ACCESS   read-only
               STATUS   mandatory
               DESCRIPTION "Indicates the number of the echo frames of control 
                            frame. The echo frame is that Lec ID of received 
                            control frame is self Lec ID"
               ::= { mpLecStatisticsEntry 20 }

       mpLecStatInNoIDEntryDataFrames OBJECT-TYPE
               SYNTAX   Counter
               ACCESS   read-only
               STATUS   mandatory
               DESCRIPTION "Indicates the number of received data frames without
                            being switched by IPFE."
               ::= { mpLecStatisticsEntry 21 }

       mpLecStatOutNoIDEntryDataFrames OBJECT-TYPE
               SYNTAX   Counter
               ACCESS   read-only
               STATUS   mandatory
               DESCRIPTION "Indicates the number of sent data frames without
                            being switched by IPFE."
               ::= { mpLecStatisticsEntry 22 }

       mpLecElanTotalCount OBJECT-TYPE
               SYNTAX   INTEGER
               ACCESS   read-only
               STATUS   mandatory
               DESCRIPTION "Indicates the number of Emulated LAN
                            (ELAN) currently configured."
               ::= { mpLec 6 }

       mpLecSysMaxVcConnect OBJECT-TYPE
               SYNTAX   INTEGER
               ACCESS   read-write
               STATUS   mandatory
               DESCRIPTION "Indicates the number of the virtual circuits
                            which are possible to be set simultaneously,
                            used by LEC function. It is the total number
                            of PVCs and SVCs which is possible to be
                            set simultaneously."
               ::= { mpLec 7 }


--  ***************************************************************************
--  the SanFran MPC Group
--  ***************************************************************************

   --  Implementation of this group is mandatory for all the SanFran systems.  


       mpMpcCfgTable OBJECT-TYPE
               SYNTAX   SEQUENCE OF MpMpcCfgEntry
               ACCESS   not-accessible
               STATUS   mandatory
               DESCRIPTION "Indicates the configuration table of the MPC 
                            information."
               ::= { mpMpc 1 }

       mpMpcCfgEntry OBJECT-TYPE
               SYNTAX   MpMpcCfgEntry
               ACCESS   not-accessible
               STATUS   mandatory
               DESCRIPTION "Indicates the configuration entry of the MPC 
                            information."
               INDEX { mpMpcCfgIndex }
               ::= { mpMpcCfgTable 1 }

       MpMpcCfgEntry  ::=
               SEQUENCE {
                        mpMpcCfgIndex INTEGER,
                        mpMpcOperatStatus INTEGER,
-- @011                 mpMpcTrafficId INTEGER,
                        mpMpcSndTrafficId INTEGER,    -- @011 add
                        mpMpcRcvTrafficId INTEGER,    -- @011 add
                        mpMpcPrtNum INTEGER,
                        mpMpcMaxMps INTEGER,
                        mpMpcMaxCache INTEGER
                        }

       mpMpcCfgIndex  OBJECT-TYPE
               SYNTAX   INTEGER   
               ACCESS   read-only
               STATUS   mandatory
               DESCRIPTION "Indicates the index of the MPC which corresponds 
                            to this entry."
               ::= { mpMpcCfgEntry 1 }

       mpMpcOperatStatus OBJECT-TYPE
               SYNTAX   INTEGER           
-- @008               ACCESS   read-write
               ACCESS   read-only
               STATUS   mandatory
               DESCRIPTION "Indicates the operation status of MPC. It indicates
                            whether MPC is actually active or not."
               ::= { mpMpcCfgEntry 2 }

-- @001       mpMpcTrafficId OBJECT-TYPE
--               SYNTAX   INTEGER
--               ACCESS   read-write
--               STATUS   mandatory
--               DESCRIPTION "Indicate the traffic ID which is specified when 
--                            MPC connects VC."
--               ::= { mpMpcCfgEntry 3 }

-- @011 add from
       mpMpcSndTrafficId OBJECT-TYPE
               SYNTAX   INTEGER
               ACCESS   read-write
               STATUS   mandatory
               DESCRIPTION "Indicate the traffic ID which is specified when 
                            MPC connects VC."
               ::= { mpMpcCfgEntry 3 }

       mpMpcRcvTrafficId OBJECT-TYPE
               SYNTAX   INTEGER
               ACCESS   read-write
               STATUS   mandatory
               DESCRIPTION "Indicate the traffic ID which is specified when 
                            MPC connects VC."
               ::= { mpMpcCfgEntry 4 }
-- @011 add end

       mpMpcPrtNum OBJECT-TYPE
               SYNTAX   INTEGER
               ACCESS   read-write
               STATUS   mandatory
               DESCRIPTION "This object assigns a number of ATM port which is
                            used when the MPC is connected."
               ::= { mpMpcCfgEntry 5 }    -- @011

       mpMpcMaxMps OBJECT-TYPE
               SYNTAX   INTEGER 
               ACCESS   read-write
               STATUS   mandatory
               DESCRIPTION "Indicate the maximum number of MPSs which can be 
                            recognized by MPC. MPC is created so as to recognize
                            MPS up to the value set by this object."
               ::= { mpMpcCfgEntry 6 }    -- @011

       mpMpcMaxCache OBJECT-TYPE
               SYNTAX  INTEGER
               ACCESS  read-write
               STATUS  mandatory
               DESCRIPTION "Indicate the maximum number of cache entry which can be 
                            recognized by MPC. MPC is created so as to have cache
                            up to the value set by this object. Both Ingress cache
                            and Egress cache are set."
               ::= { mpMpcCfgEntry 7 }    -- @011


       mpMpcCacheCntTable OBJECT-TYPE
               SYNTAX   SEQUENCE OF MpMpcCacheCntEntry
               ACCESS   not-accessible
               STATUS   mandatory
               DESCRIPTION "Indicates the MPoA Client cache table which includes
                            used number of MPC cache managed by agent."
               ::= { mpMpc 2 }

       mpMpcCacheCntEntry OBJECT-TYPE
               SYNTAX   MpMpcCacheCntEntry
               ACCESS   not-accessible
               STATUS   mandatory
               DESCRIPTION "Indicates the MPoA Client cache entry which includes
                            used number of MPC cache managed by agent."
               INDEX { mpMpcCacheCntIndex }
               ::= { mpMpcCacheCntTable 1 }

       MpMpcCacheCntEntry ::=
               SEQUENCE {
                        mpMpcCacheCntIndex INTEGER,
                        mpMpcIngressCacheCnt INTEGER,
                        mpMpcEgressCacheCnt INTEGER
                        }

       mpMpcCacheCntIndex OBJECT-TYPE
               SYNTAX   INTEGER 
               ACCESS   read-only
               STATUS   mandatory
               DESCRIPTION "Indicates the index of the MPC which corresponds 
                            to this entry."
               ::= { mpMpcCacheCntEntry 1 }

       mpMpcIngressCacheCnt OBJECT-TYPE
               SYNTAX   INTEGER           
               ACCESS   read-only
               STATUS   mandatory
               DESCRIPTION "Indicates the number of Ingress cache which is being
                            used by MPC. This object is used to know the use for
                            the value set by mpMpcMaxCache."
               ::= { mpMpcCacheCntEntry 2 }

       mpMpcEgressCacheCnt OBJECT-TYPE
               SYNTAX   INTEGER 
               ACCESS   read-only
               STATUS   mandatory
               DESCRIPTION "Indicates the number of Egress cache which is being
                            used by MPC. This object is used to know the use for
                            the value set by mpMpcMaxCache."
               ::= { mpMpcCacheCntEntry 3 }

       mpMpcMaxReqSelNum OBJECT-TYPE
               SYNTAX   INTEGER 
               ACCESS   read-write
               STATUS   mandatory
               DESCRIPTION "Indicates the number of SELs which can be used by 
                            all MPC managed by this agent and which are used 
                            for capsuling IP."
               ::= { mpMpc 3 }

       mpMpcUseSelNum OBJECT-TYPE
               SYNTAX  INTEGER 
               ACCESS  read-only
               STATUS  mandatory
               DESCRIPTION "Indicates the number of SELs which is being used 
                            by all MPC managed by this agent and which are used
                            for capsuling IP."
               ::= { mpMpc 4 }


--  ***************************************************************************
--  the SanFran STP Group
--  ***************************************************************************

   --  Implementation of this group is mandatory for all the SanFran systems.


          mpStpVlanTable OBJECT-TYPE
              SYNTAX  SEQUENCE OF MpStpVlanEntry
              ACCESS  not-accessible
              STATUS  mandatory
              DESCRIPTION "A table that contains information for the  
                          Spanning Tree Protocol."                   
              ::= { mpStp 1 }

          mpStpVlanEntry OBJECT-TYPE
              SYNTAX  MpStpVlanEntry
              ACCESS  not-accessible
              STATUS  mandatory
              DESCRIPTION "A list of information about the Spanning
                          Tree Protocol."                         
              INDEX   { mpStpVlanIndex }
              ::= { mpStpVlanTable 1 }

          MpStpVlanEntry ::=
              SEQUENCE {
                  mpStpVlanIndex
                      INTEGER,
                  mpStpVlanProtocolSpecification
                      INTEGER,
                  mpStpVlanPriority
                      INTEGER,
                  mpStpVlanTimeSinceTopologyChange
                      TimeTicks,
                  mpStpVlanTopChanges
                      Counter,
                  mpStpVlanDesignatedRoot
                      BridgeId,
                  mpStpVlanRootCost
                      INTEGER,
                  mpStpVlanRootPort
                      INTEGER,
                  mpStpVlanMaxAge
                      Timeout,
                  mpStpVlanHelloTime
                      Timeout,
                  mpStpVlanHoldTime
                      INTEGER,
                  mpStpVlanForwardDelay
                      Timeout,
                  mpStpVlanBridgeMaxAge
                      Timeout,
                  mpStpVlanBridgeHelloTime
                      Timeout,
                  mpStpVlanBridgeForwardDelay
                      Timeout,
                  mpStpVlanSupportStatus
                      INTEGER
              }

          mpStpVlanIndex OBJECT-TYPE
              SYNTAX  INTEGER 
              ACCESS  read-only
              STATUS  mandatory
              DESCRIPTION "Indicates the index value to identify this
                          table entry."
              ::= { mpStpVlanEntry 1 }

          mpStpVlanProtocolSpecification OBJECT-TYPE
              SYNTAX  INTEGER {
                          unknown(1),
                          decLb100(2),
                          ieee8021d(3)
                      }
              ACCESS  read-only
              STATUS  mandatory
              DESCRIPTION "An indication of what version of the Spanning      
                          Tree Protocol is being run.  The value              
                          'decLb100(2)' indicates the DEC LANbridge 100       
                          Spanning Tree protocol.  IEEE 802.1d                
                          implementations will return 'ieee8021d(3)'.  If     
                          future versions of the IEEE Spanning Tree Protocol  
                          are released that are incompatible with the         
                          current version a new value will be defined."       
              ::= { mpStpVlanEntry 2 }

          mpStpVlanPriority OBJECT-TYPE
              SYNTAX  INTEGER (0..65535)
              ACCESS  read-write
              STATUS  mandatory
              DESCRIPTION "The value of the write-able portion of the Bridge 
                          ID, i.e., the first two octets of the (8 octet     
                          long) Bridge ID.  The other (last) 6 octets of the 
                          Bridge ID are given by the value of                
                          dot1dBaseBridgeAddress."                           
              REFERENCE "IEEE 802.1D-1990: Section 4.5.3.7"
              ::= { mpStpVlanEntry 3 }

          mpStpVlanTimeSinceTopologyChange OBJECT-TYPE
              SYNTAX  TimeTicks
              ACCESS  read-only
              STATUS  mandatory
              DESCRIPTION "The time (in hundredths of a second) since the 
                          last time a topology change was detected by the 
                          bridge entity."                                 
              REFERENCE "IEEE 802.1D-1990: Section 6.8.1.1.3"
              ::= { mpStpVlanEntry 4 }

          mpStpVlanTopChanges OBJECT-TYPE
              SYNTAX  Counter
              ACCESS  read-only
              STATUS  mandatory
              DESCRIPTION "The total number of topology changes detected by 
                          this bridge since the management entity was last  
                          reset or initialized."                            
              REFERENCE "IEEE 802.1D-1990: Section 6.8.1.1.3"
              ::= { mpStpVlanEntry 5 }

          mpStpVlanDesignatedRoot OBJECT-TYPE
              SYNTAX  BridgeId
              ACCESS  read-only
              STATUS  mandatory
              DESCRIPTION "The bridge identifier of the root of the spanning
                          tree as determined by the Spanning Tree Protocol  
                          as executed by this node.  This value is used as  
                          the Root Identifier parameter in all Configuration
                          Bridge PDUs originated by this node."             
              REFERENCE "IEEE 802.1D-1990: Section 4.5.3.1"
              ::= { mpStpVlanEntry 6 }

          mpStpVlanRootCost OBJECT-TYPE
              SYNTAX  INTEGER
              ACCESS  read-only
              STATUS  mandatory
              DESCRIPTION "The cost of the path to the root as seen from 
                          this bridge."                                  
              REFERENCE "IEEE 802.1D-1990: Section 4.5.3.2"
              ::= { mpStpVlanEntry 7 }

          mpStpVlanRootPort OBJECT-TYPE
              SYNTAX  INTEGER
              ACCESS  read-only
              STATUS  mandatory
              DESCRIPTION "The port number of the port which offers the
                          lowest cost path from this bridge to the root
                          bridge."                                     
              REFERENCE "IEEE 802.1D-1990: Section 4.5.3.3"
              ::= { mpStpVlanEntry 8 }

          mpStpVlanMaxAge OBJECT-TYPE
              SYNTAX  Timeout
              ACCESS  read-only
              STATUS  mandatory
              DESCRIPTION "The maximum age of Spanning Tree Protocol        
                          information learned from the network on any port  
                          before it is discarded, in units of hundredths of 
                          a second.  This is the actual value that this     
                          bridge is currently using."                       
              REFERENCE "IEEE 802.1D-1990: Section 4.5.3.4"
              ::= { mpStpVlanEntry 9 }

          mpStpVlanHelloTime OBJECT-TYPE
              SYNTAX  Timeout
              ACCESS  read-only
              STATUS  mandatory
              DESCRIPTION "The amount of time between the transmission of
                          Configuration bridge PDUs by this node on any port
                          when it is the root of the spanning tree or trying
                          to become so, in units of hundredths of a second.
                          This is the actual value that this bridge is
                          currently using."
              REFERENCE "IEEE 802.1D-1990: Section 4.5.3.5"
              ::= { mpStpVlanEntry 10 }

          mpStpVlanHoldTime OBJECT-TYPE
              SYNTAX  INTEGER
              ACCESS  read-only
              STATUS  mandatory
              DESCRIPTION "This time value determines the interval length
                          during which no more than two Configuration bridge
                          PDUs shall be transmitted by this node, in units
                          of hundredths of a second."
              REFERENCE "IEEE 802.1D-1990: Section 4.5.3.14"
              ::= { mpStpVlanEntry 11 }

          mpStpVlanForwardDelay OBJECT-TYPE
              SYNTAX  Timeout
              ACCESS  read-only
              STATUS  mandatory
              DESCRIPTION "This time value, measured in units of hundredths  
                          of a second, controls how fast a port changes its  
                          spanning state when moving towards the Forwarding  
                          state.  The value determines how long the port     
                          stays in each of the Listening and Learning        
                          states, which precede the Forwarding state.  This  
                          value is also used, when a topology change has     
                          been detected and is underway, to age all dynamic  
                          entries in the Forwarding Database.  [Note that    
                          this value is the one that this bridge is          
                          currently using, in contrast to                    
                          mpStpVlanBridgeForwardDelay which is the value that
                          this bridge and all others would start using       
                          if/when this bridge were to become the root."     
              REFERENCE "IEEE 802.1D-1990: Section 4.5.3.6"
              ::= { mpStpVlanEntry 12 }

          mpStpVlanBridgeMaxAge OBJECT-TYPE
              SYNTAX  Timeout (600..4000)
              ACCESS  read-write
              STATUS  mandatory
              DESCRIPTION "The value that all bridges use for MaxAge when  
                          this bridge is acting as the root.  Note that    
                          802.1D-1990 specifies that the range for this    
                          parameter is related to the value of             
                          mpStpVlanBridgeHelloTime. The granularity of this
                          timer is specified by 802.1D-1990 to be 1 second.
                          An agent may return a badValue error if a set is 
                          attempted to a value which is not a whole number 
                          of seconds."                                     
              REFERENCE "IEEE 802.1D-1990: Section 4.5.3.8"
              ::= { mpStpVlanEntry 13 }

          mpStpVlanBridgeHelloTime OBJECT-TYPE
              SYNTAX  Timeout (100..1000)
              ACCESS  read-write
              STATUS  mandatory
              DESCRIPTION "The value that all bridges use for HelloTime when
                          this bridge is acting as the root.  The          
                          granularity of this timer is specified by 802.1D-
                          1990 to be 1 second.  An agent may return a      
                          badValue error if a set is attempted to a value  
                          which is not a whole number of seconds."         
                                                              
              REFERENCE "IEEE 802.1D-1990: Section 4.5.3.9"
              ::= { mpStpVlanEntry 14 }

          mpStpVlanBridgeForwardDelay OBJECT-TYPE
              SYNTAX  Timeout (400..3000)
              ACCESS  read-write
              STATUS  mandatory
              DESCRIPTION "The value that all bridges use for ForwardDelay   
                          when this bridge is acting as the root.  Note that 
                          802.1D-1990 specifies that the range for this      
                          parameter is related to the value of               
                          mpStpVlanBridgeMaxAge.  The granularity of this    
                          timer is specified by 802.1D-1990 to be 1 second.  
                          An agent may return a badValue error if a set is   
                          attempted to a value which is not a whole number." 
              REFERENCE "IEEE 802.1D-1990: Section 4.5.3.10"
              ::= { mpStpVlanEntry 15 }


          mpStpVlanSupportStatus OBJECT-TYPE
              SYNTAX  INTEGER {
                          support(1), 
                          nonSupport(2)
                      }
              ACCESS  read-write
              STATUS  mandatory
              DESCRIPTION "Indicate whether the VLAN supports Spanning Tree      
                          Protocol or not. If the value 'support(1)' is set,     
                          the VLAN supports Spanning Tree Protocol. If the       
                          value 'nonSupport(2)' is set, the VLAN does not support
                          Spanning Tree Protocol."                               
              ::= { mpStpVlanEntry 16 }


          -- The Spanning Tree Port Table

          mpStpPortTable OBJECT-TYPE
              SYNTAX  SEQUENCE OF MpStpPortEntry
              ACCESS  not-accessible
              STATUS  mandatory
              DESCRIPTION "A table that contains port-specific information 
                          for the Spanning Tree Protocol."                 
              ::= { mpStp 2 }

          mpStpPortEntry OBJECT-TYPE
              SYNTAX  MpStpPortEntry
              ACCESS  not-accessible
              STATUS  mandatory
              DESCRIPTION "A list of information maintained by every port
                          about the Spanning Tree Protocol state for that
                          port."                                         
              INDEX   { mpStpPortVlanIndex,
                        mpStpPort }
              ::= { mpStpPortTable 1 }

          MpStpPortEntry ::=
              SEQUENCE {
                  mpStpPortVlanIndex
                      INTEGER,
                  mpStpPort
                      INTEGER,
                  mpStpPortPriority
                      INTEGER,
                  mpStpPortState
                      INTEGER,
                  mpStpPortEnable
                      INTEGER,
                  mpStpPortPathCost
                      INTEGER,
                  mpStpPortDesignatedRoot
                      BridgeId,
                  mpStpPortDesignatedCost
                      INTEGER,
                  mpStpPortDesignatedBridge
                      BridgeId,
                  mpStpPortDesignatedPort
                      OCTET STRING,
                  mpStpPortForwardTransitions
                      Counter
              }

          mpStpPortVlanIndex OBJECT-TYPE
              SYNTAX  INTEGER 
              ACCESS  read-only
              STATUS  mandatory
              DESCRIPTION "The VLAN ID for which this entry contains     
                          Spanning Tree Protocol management information."
              ::= { mpStpPortEntry 1 }

          mpStpPort OBJECT-TYPE
              SYNTAX  INTEGER 
              ACCESS  read-only
              STATUS  mandatory
              DESCRIPTION "The port number of the port for which this entry
                          contains Spanning Tree Protocol management       
                          information."                                    
              REFERENCE "IEEE 802.1D-1990: Section 6.8.2.1.2"
              ::= { mpStpPortEntry 2 }

          mpStpPortPriority OBJECT-TYPE
              SYNTAX  INTEGER (0..255)
              ACCESS  read-write
              STATUS  mandatory
              DESCRIPTION "The value of the priority field which is       
                          contained in the first (in network byte order)  
                          octet of the (2 octet long) Port ID.  The other 
                          octet of the Port ID is given by the value of   
                          mpStpPort."                                     
              REFERENCE "IEEE 802.1D-1990: Section 4.5.5.1"
              ::= { mpStpPortEntry 3 }

          mpStpPortState OBJECT-TYPE
              SYNTAX  INTEGER {
                          disabled(1),
                          blocking(2),
                          listening(3),
                          learning(4),
                          forwarding(5),
                          broken(6)
                      }
              ACCESS  read-only
              STATUS  mandatory
              DESCRIPTION "The port's current state as defined by           
                          application of the Spanning Tree Protocol.  This  
                          state controls what action a port takes on        
                          reception of a frame.  If the bridge has detected 
                          a port that is malfunctioning it will place that  
                          port into the broken(6) state.  For ports which   
                          are disabled (see mpStpPortEnable), this object   
                          will have a value of disabled(1)."                
              REFERENCE "IEEE 802.1D-1990: Section 4.5.5.2"
              ::= { mpStpPortEntry 4 }

          mpStpPortEnable OBJECT-TYPE
              SYNTAX  INTEGER {
                          enabled(1),
                          disabled(2)
                      }
              ACCESS  read-write
              STATUS  mandatory
              DESCRIPTION "The enabled/disabled status of the port."
              REFERENCE "IEEE 802.1D-1990: Section 4.5.5.2"
              ::= { mpStpPortEntry 5 }

          mpStpPortPathCost OBJECT-TYPE
              SYNTAX  INTEGER (1..65535)
              ACCESS  read-write
              STATUS  mandatory
              DESCRIPTION "The contribution of this port to the path cost of
                          paths towards the spanning tree root which include
                          this port.  802.1D-1990 recommends that the       
                          default value of this parameter be in inverse     
                          proportion to the speed of the attached LAN."     
              REFERENCE "IEEE 802.1D-1990: Section 4.5.5.3"
              ::= { mpStpPortEntry 6 }

          mpStpPortDesignatedRoot OBJECT-TYPE
              SYNTAX  BridgeId
              ACCESS  read-only
              STATUS  mandatory
              DESCRIPTION "The unique Bridge Identifier of the Bridge    
                          recorded as the Root in the Configuration BPDUs
                          transmitted by the Designated Bridge for the   
                          segment to which the port is attached."        
              REFERENCE "IEEE 802.1D-1990: Section 4.5.5.4"
              ::= { mpStpPortEntry 7 }

          mpStpPortDesignatedCost OBJECT-TYPE
              SYNTAX  INTEGER
              ACCESS  read-only
              STATUS  mandatory
              DESCRIPTION "The path cost of the Designated Port of the    
                          segment connected to this port.  This value is  
                          compared to the Root Path Cost field in received
                          bridge PDUs."                                   
              REFERENCE "IEEE 802.1D-1990: Section 4.5.5.5"
              ::= { mpStpPortEntry 8 }

          mpStpPortDesignatedBridge OBJECT-TYPE
              SYNTAX  BridgeId
              ACCESS  read-only
              STATUS  mandatory
              DESCRIPTION "The Bridge Identifier of the bridge which this
                          port considers to be the Designated Bridge for 
                          this port's segment."                          
              REFERENCE "IEEE 802.1D-1990: Section 4.5.5.6"
              ::= { mpStpPortEntry 9 }

          mpStpPortDesignatedPort OBJECT-TYPE
              SYNTAX  OCTET STRING (SIZE (2))
              ACCESS  read-only
              STATUS  mandatory
              DESCRIPTION "The Port Identifier of the port on the Designated
                          Bridge for this port's segment."                  
              REFERENCE "IEEE 802.1D-1990: Section 4.5.5.7"
              ::= { mpStpPortEntry 10 }

          mpStpPortForwardTransitions OBJECT-TYPE
              SYNTAX  Counter
              ACCESS  read-only
              STATUS  mandatory
              DESCRIPTION "The number of times this port has transitioned  
                          from the Learning state to the Forwarding state."
              ::= { mpStpPortEntry 11 }


--  ***************************************************************************
--  the SanFran LLC Group
--  ***************************************************************************

   --  Implementation of this group is mandatory for all the SanFran systems.  

-- @011 add from
       mpLlcSharedVccMaxSduSize OBJECT-TYPE
               SYNTAX   INTEGER (1..65535)
               ACCESS   read-write
               STATUS   mandatory
               DESCRIPTION "Indicates Maximum SDU size for common VCC which 
                           is managed by LLC. LLC make a common VCC according 
                           to Maximum SDU size set by this MIB object."
               ::= { mpLlc 1 }

       mpLlcAgeOutTime OBJECT-TYPE
               SYNTAX   INTEGER (1..4294967295)
               ACCESS   read-write
               STATUS   mandatory
               DESCRIPTION "Indicates no communication time which is used to 
                           judge age out on LLC/SNAP capsulation VCC aging.
                           The VCC is released when no communication time 
                           of sending/receiving data reach this value."
               ::= { mpLlc 2 }
-- @011 delete end

-- @009 add from
       mpLlcPvcTable OBJECT-TYPE
               SYNTAX   SEQUENCE OF MpLlcPvcEntry
               ACCESS   not-accessible
               STATUS   mandatory
               DESCRIPTION
                        "A table contains information of a PVC."
               ::= { mpLlc 3 }    -- @011

       mpLlcPvcEntry OBJECT-TYPE
               SYNTAX   MpLlcPvcEntry
               ACCESS   not-accessible
               STATUS   mandatory
               DESCRIPTION
                        "A entry indicates a member of PVC information on a ATM interface."
               INDEX { mpLlcPvcIdIndex }
               ::= { mpLlcPvcTable 1 }

       MpLlcPvcEntry ::=
               SEQUENCE {
                        mpLlcPvcIdIndex                 INTEGER,
                        mpLlcPvcPort                    INTEGER,
                        mpLlcPvcVpi                     INTEGER,
                        mpLlcPvcVci                     INTEGER,
                        mpLlcPvcSdu                     INTEGER,
                        mpLlcPvcVcPriority              INTEGER,    -- add @010
                        mpLlcPvcForwardTrafficId        INTEGER,
                        mpLlcPvcBackwardTrafficId       INTEGER,
                        mpLlcPvcAdminStatus             INTEGER,
                        mpLlcPvcOperStatus              INTEGER,
                        mpLlcPvcRowStatus               RowStatus
               }

       mpLlcPvcIdIndex OBJECT-TYPE
             SYNTAX   INTEGER (1..2147483647)
             ACCESS   read-only
             STATUS   mandatory
             DESCRIPTION
                      "The value of this object is an index of PVC entry table.
                       The index indicates the Virtual Circuit Identifier (VC ID)."
             ::= { mpLlcPvcEntry 1 }

       mpLlcPvcPort OBJECT-TYPE
             SYNTAX   INTEGER
             ACCESS   read-write
             STATUS   mandatory
             DESCRIPTION
                      "The value of this object identifies an ATM port number."
             ::= { mpLlcPvcEntry 2 }

       mpLlcPvcVpi OBJECT-TYPE
             SYNTAX   INTEGER
             ACCESS   read-write
             STATUS   mandatory
             DESCRIPTION
                      "The value of this object identifies a VPI."
             ::= { mpLlcPvcEntry 3 }

       mpLlcPvcVci OBJECT-TYPE
             SYNTAX   INTEGER
             ACCESS   read-write
             STATUS   mandatory
             DESCRIPTION
                      "The vaule of this object identifies a VCI."
             ::= { mpLlcPvcEntry 4 }

       mpLlcPvcSdu OBJECT-TYPE
             SYNTAX   INTEGER (1..65535)
             ACCESS   read-write
             STATUS   mandatory
             DESCRIPTION
                      "The value of this object identifies a Service Data Unit."
             DEFVAL   { 9188 }
             ::= { mpLlcPvcEntry 5 }

-- @010 add from
       mpLlcPvcVcPriority OBJECT-TYPE
             SYNTAX   INTEGER
             ACCESS   read-write
             STATUS   mandatory
             DESCRIPTION   "The object indicates a priority on a specified VC
                            when VC is not one in a PVC."
             ::= { mpLlcPvcEntry 6 }
-- @010 add end

       mpLlcPvcForwardTrafficId OBJECT-TYPE
             SYNTAX   INTEGER
             ACCESS   read-write
             STATUS   mandatory
             DESCRIPTION
                      "The value of this object identifies a traffic-id for
                       outgoing at a specified ATM port."
             DEFVAL   { 1 }
             ::= { mpLlcPvcEntry 7 }    -- @010

       mpLlcPvcBackwardTrafficId OBJECT-TYPE
             SYNTAX   INTEGER
             ACCESS   read-write
             STATUS   mandatory
             DESCRIPTION
                      "The vaule of this object identifies a traffic-id for
                       incoming at a specified ATM port."
             DEFVAL   { 1 }
             ::= { mpLlcPvcEntry 8 }    -- @010

       mpLlcPvcAdminStatus OBJECT-TYPE
             SYNTAX   INTEGER {
                                up(1),
                                down(2)
                              }
             ACCESS   read-write
             STATUS   mandatory
             DESCRIPTION
                      "The value of this object indicates status of a VC."
             ::= { mpLlcPvcEntry 9 }    -- @010

       mpLlcPvcOperStatus OBJECT-TYPE
             SYNTAX   INTEGER {
                                up(1),
                                down(2)
                              }
             ACCESS   read-write
             STATUS   mandatory
             DESCRIPTION   "The object indicates the current operational status
                            of a VC."
             ::= { mpLlcPvcEntry 10 }    -- @010

       mpLlcPvcRowStatus OBJECT-TYPE
             SYNTAX   RowStatus
             ACCESS   read-write
             STATUS   mandatory
             DESCRIPTION
                      "This object is used to create, delete or modify a row in
                       this table."
             ::= { mpLlcPvcEntry 11 }    -- @010
-- @009 add to


-- @008 add from
--  ***************************************************************************
--  the SanFran OSPF Group
--  ***************************************************************************

   --  Implementation of this group is mandatory for all the SanFran systems.  

        mpOspfGeneral OBJECT IDENTIFIER ::= { mpOspf 1 }

        mpOspfVersionNumber OBJECT-TYPE
               SYNTAX   INTEGER
               ACCESS   read-only   
               STATUS   mandatory
               DESCRIPTION 
                        "The current version number of the OSPF  proto-
                        col is 2."
               ::= { mpOspfGeneral 1 }

        mpOspfTOSSupport OBJECT-TYPE
               SYNTAX   TruthValue 
               ACCESS   read-only   
               STATUS   mandatory
               DESCRIPTION 
                        "The router's support for type-of-service rout-
                        ing."                                          
               ::= { mpOspfGeneral 2 }

        mpOspfExtLsdbLimit OBJECT-TYPE
               SYNTAX   INTEGER
               ACCESS   read-only   
               STATUS   mandatory
               DESCRIPTION 
                        "The  maximum   number   of   non-default   AS-
                        external-LSAs entries that can be stored in the
                        link-state database.  If the value is -1,  then
                        there is no limit.                             
                                                                       
                        When the number of non-default AS-external-LSAs
                        in   a  router's  link-state  database  reaches
                        ospfExtLsdbLimit, the router  enters  Overflow-
                        State.   The   router  never  holds  more  than
                        ospfExtLsdbLimit  non-default  AS-external-LSAs
                        in  its  database. OspfExtLsdbLimit MUST be set
                        identically in all routers attached to the OSPF
                        backbone  and/or  any regular OSPF area. (i.e.,
                        OSPF stub areas and NSSAs are excluded)."      
               ::= { mpOspfGeneral 3 }

        mpOspfExitOverflowInterval OBJECT-TYPE
               SYNTAX   INTEGER
               ACCESS   read-only   
               STATUS   mandatory
               DESCRIPTION 
                        "The number of  seconds  that,  after  entering
                        OverflowState,  a  router will attempt to leave
                        OverflowState. This allows the router to  again
                        originate  non-default  AS-external-LSAs.  When
                        set to 0, the router will not  leave  Overflow-
                        State until restarted."                        
               ::= { mpOspfGeneral 4 }

        mpOspfInReceives OBJECT-TYPE
               SYNTAX   Counter
               ACCESS   read-only   
               STATUS   mandatory
               DESCRIPTION 
                        "The total number of received error packets."
               ::= { mpOspfGeneral 5 }

        mpOspfInErrors OBJECT-TYPE
               SYNTAX   Counter
               ACCESS   read-only
               STATUS   mandatory
               DESCRIPTION
                        "The number of received error packets."
               ::= { mpOspfGeneral 6 }

        mpOspfGlobalTable OBJECT-TYPE
               SYNTAX   SEQUENCE OF MpOspfGlobalEntry
               ACCESS   not-accessible
               STATUS   mandatory
               DESCRIPTION
                        "Information describing the configured  parame-
                        ters and cumulative statistics of the router's
                        OSPF process."
               ::= { mpOspf 2 }

        mpOspfGlobalEntry OBJECT-TYPE
               SYNTAX   MpOspfGlobalEntry
               ACCESS   not-accessible
               STATUS   mandatory
               DESCRIPTION
                        "Information describing the configured  parame-
                        ters and cumulative statistics of the router's
                        OSPF process."
               INDEX { mpOspfGlobalProcessId }
               ::= { mpOspfGlobalTable 1 }

        MpOspfGlobalEntry ::=
               SEQUENCE {
                        mpOspfGlobalProcessId
                            INTEGER,
                        mpOspfGlobalMode
                            INTEGER,
                        mpOspfGlobalRouterId
                            IpAddress,
                        mpOspfGlobalAreaBdrRtrStatus
                            TruthValue,
                        mpOspfGlobalASBdrRtrStatus
                            TruthValue,
                        mpOspfGlobalRFC1583Compatibility
                            INTEGER,
                        mpOspfGlobalDefaultRouteType
                            INTEGER,
                        mpOspfGlobalDefMetric
                            INTEGER,
                        mpOspfGlobalDefExternalType
                            INTEGER,
                        mpOspfGlobalDefAddress
                            IpAddress,
                        mpOspfGlobalDefTag
                            INTEGER,
                        mpOspfGlobalDefProtocol
                            INTEGER,
                        mpOspfGlobalDefImportList
                            INTEGER,
                        mpOspfGlobalIntraAreaRoutePriority
                            INTEGER,
                        mpOspfGlobalInterAreaRoutePriority
                            INTEGER,
                        mpOspfGlobalExternalRoutePriority
                            INTEGER,
                        mpOspfGlobalMulticastExtensions
                            INTEGER,
                        mpOspfGlobalDemandExtensions
                           TruthValue,
                        mpOspfGlobalRouterLsaCount
                            Gauge,
                        mpOspfGlobalNetworkLsaCount
                            Gauge,
                        mpOspfGlobalSummaryNetworkLsaCount
                            Gauge,
                        mpOspfGlobalSummaryRouterLsaCount
                            Gauge,
                        mpOspfGlobalExternalLsaCount
                            Gauge,
                        mpOspfGlobalExternalLsaCksumSum
                            Gauge,
                        mpOspfGlobalReceives
                            Counter,
                        mpOspfGlobalReceiveBadAuths
                            Counter,
                        mpOspfGlobalReceiveBadPackets
                            Counter,
                        mpOspfGlobalMulticastSends
                            Counter,
                        mpOspfGlobalUnicastSends
                            Counter,
                        mpOspfGlobalSpfRuns
                            Counter,
                        mpOspfGlobalIncSummaryUpdates
                            Counter,
                        mpOspfGlobalIncExternalUpdates
                            Counter,
                        mpOspfGlobalLsAgeOutCounts
                            Counter,
                        mpOspfGlobalLsFlushCounts
                            Counter,
                        mpOspfGlobalLsdbAllocs
                            Counter,
                        mpOspfGlobalLsdbFrees
                            Counter,
                        mpOspfGlobalBufferAllocFailures
                            Counter
                        }
              
        mpOspfGlobalProcessId OBJECT-TYPE
               SYNTAX   INTEGER
               ACCESS   read-only   
               STATUS   mandatory
               DESCRIPTION
                        "The process ID of OSPF."
               ::= { mpOspfGlobalEntry 1 }

        mpOspfGlobalMode OBJECT-TYPE
               SYNTAX   INTEGER    {
                    disable(1),
                    enable(2),
                    change(3),
                    cancel(4),
                    active(5)
                  }
               ACCESS   read-write   
               STATUS   mandatory
               DESCRIPTION 
                        "Status of OSPF process."
               ::= { mpOspfGlobalEntry 2 }

        mpOspfGlobalRouterId OBJECT-TYPE
               SYNTAX   IpAddress
               ACCESS   read-write  
               STATUS   mandatory                        
               DESCRIPTION
                        "A  32-bit  integer  uniquely  identifying  the
                        router in the Autonomous System.

                        By  convention,  to  ensure  uniqueness,   this
                        should  default  to  the  value  of  one of the
                        router's IP interface addresses."
               ::= { mpOspfGlobalEntry 3 }

        mpOspfGlobalAreaBdrRtrStatus OBJECT-TYPE
               SYNTAX   TruthValue
               ACCESS   read-only   
               STATUS   mandatory
               DESCRIPTION
                        "A flag to note whether this router is an  area
                        border router."
               ::= { mpOspfGlobalEntry 4 }

        mpOspfGlobalASBdrRtrStatus OBJECT-TYPE
               SYNTAX   TruthValue
               ACCESS   read-write   
               STATUS   mandatory
               DESCRIPTION
                        "A flag to note whether this router is  config-
                        ured as an Autonomous System border router."
               ::= { mpOspfGlobalEntry 5 }

        mpOspfGlobalRFC1583Compatibility OBJECT-TYPE
               SYNTAX   INTEGER { 
                                enabled(1),
                                disabled(2)
                                }
               ACCESS   read-write   
               STATUS   mandatory
               DESCRIPTION
                        "Indicates the whether calculation of AS external 
                        route is done with RFC1583 mode or RFC2328 mode."
               ::= { mpOspfGlobalEntry 6 }

        mpOspfGlobalDefaultRouteType OBJECT-TYPE
               SYNTAX   INTEGER { 
                                no(1),
                                always(2),
                                import-list(3)
                                }
               ACCESS   read-write   
               STATUS   mandatory
               DESCRIPTION
                        "Indeicates the timing to advertise default route."
               ::= { mpOspfGlobalEntry 7 }

        mpOspfGlobalDefMetric OBJECT-TYPE
               SYNTAX   INTEGER(1..16777215)
               ACCESS   read-write   
               STATUS   mandatory
               DESCRIPTION
                        "The external cost of default route to be used when 
                        the advertising timing of default route is 'always'."
               ::= { mpOspfGlobalEntry 8 }

        mpOspfGlobalDefExternalType OBJECT-TYPE
               SYNTAX   INTEGER {
                                type1(1),
                                type2(2)
                                }
               ACCESS   read-write   
               STATUS   mandatory
               DESCRIPTION
                        "The external type of default route to be used when
                        the advertising timing of default route is 'always'."
               ::= { mpOspfGlobalEntry 9 }

        mpOspfGlobalDefAddress OBJECT-TYPE
               SYNTAX   IpAddress
               ACCESS   read-write   
               STATUS   mandatory
               DESCRIPTION
                        "The forwarding address of default route to be used 
                        when the advertising timing of default route is 
                        'always'."
               ::= { mpOspfGlobalEntry 10 }

        mpOspfGlobalDefTag OBJECT-TYPE
               SYNTAX   INTEGER(0..4294967295)
               ACCESS   read-write   
               STATUS   mandatory
               DESCRIPTION
                        "The route tag of default route to be used when the 
                        advertising timing of default route is 'always'."
               ::= { mpOspfGlobalEntry 11 }

        mpOspfGlobalDefProtocol OBJECT-TYPE
               SYNTAX   INTEGER { 
                                local(2),
                                static(3),
                                rip(8)
                                }
               ACCESS   read-write   
               STATUS   mandatory
               DESCRIPTION
                        "The routing protocol of routing table which judges 
                        the condition of import-list When the advertising 
                        timing of default route is 'import-list'."
               ::= { mpOspfGlobalEntry 12 }

        mpOspfGlobalDefImportList OBJECT-TYPE
               SYNTAX   INTEGER(1..4294967295)
               ACCESS   read-write   
               STATUS   mandatory
               DESCRIPTION
                        "The import-list number which judges the condition 
                        of import-list When the advertising timing of default
                        route is 'import-list'."
               ::= { mpOspfGlobalEntry 13 }

        mpOspfGlobalIntraAreaRoutePriority OBJECT-TYPE
               SYNTAX   INTEGER(1..255)
               ACCESS   read-write   
               STATUS   mandatory
               DESCRIPTION
                        "The route priority which is used when intra-area 
                        route is made in IP routing table."
               ::= { mpOspfGlobalEntry 14 }

        mpOspfGlobalInterAreaRoutePriority OBJECT-TYPE
               SYNTAX   INTEGER(1..255)
               ACCESS   read-write   
               STATUS   mandatory
               DESCRIPTION
                        "The route priority which is used when inter-area 
                        route is made in IP routing table."
               ::= { mpOspfGlobalEntry 15 }

        mpOspfGlobalExternalRoutePriority OBJECT-TYPE
               SYNTAX   INTEGER(1..255)
               ACCESS   read-write   
               STATUS   mandatory
               DESCRIPTION
                        "The route priority which is used when AS external 
                        route is made in IP routing table."
               ::= { mpOspfGlobalEntry 16 }

        mpOspfGlobalMulticastExtensions OBJECT-TYPE
               SYNTAX   INTEGER(0..7)
               ACCESS   read-write   
               STATUS   mandatory
               DESCRIPTION
                        "A Bit Mask indicating whether  the  router  is
                        forwarding  IP  multicast  (Class  D) datagrams
                        based on the algorithms defined in  the  Multi-
                        cast Extensions to OSPF.                       
                                                                       
                        Bit 0, if set, indicates that  the  router  can
                        forward  IP multicast datagrams in the router's
                        directly attached areas (called intra-area mul-
                        ticast routing).                               
                                                                       
                        Bit 1, if set, indicates that  the  router  can
                        forward  IP  multicast  datagrams  between OSPF
                        areas (called inter-area multicast routing).   
                                                                       
                        Bit 2, if set, indicates that  the  router  can
                        forward  IP  multicast  datagrams between Auto-
                        nomous Systems (called inter-AS multicast rout-
                        ing).                                          
                                                                       
                        Only certain combinations of bit  settings  are
                        allowed,  namely: 0 (no multicast forwarding is
                        enabled), 1 (intra-area multicasting  only),  3
                        (intra-area  and  inter-area  multicasting),  5
                        (intra-area and inter-AS  multicasting)  and  7
                        (multicasting  everywhere). By default, no mul-
                        ticast forwarding is enabled."
                        -- fixed to 0
               ::= { mpOspfGlobalEntry 17 }

        mpOspfGlobalDemandExtensions OBJECT-TYPE
               SYNTAX  TruthValue
               ACCESS   read-write   
               STATUS   mandatory
               DESCRIPTION
                        "The router's support for demand routing."
                        -- fixed to false
               ::= { mpOspfGlobalEntry 18 }

        mpOspfGlobalRouterLsaCount OBJECT-TYPE
               SYNTAX   Gauge
               ACCESS   read-only   
               STATUS   mandatory
               DESCRIPTION
                        "The number of Router (LS type 1)  link-state
                        advertisements in the link-state database."
               ::= { mpOspfGlobalEntry 19 }

        mpOspfGlobalNetworkLsaCount OBJECT-TYPE
               SYNTAX   Gauge
               ACCESS   read-only   
               STATUS   mandatory
               DESCRIPTION
                        "The number of Network (LS type 2)  link-state
                        advertisements in the link-state database."
               ::= { mpOspfGlobalEntry 20 }

        mpOspfGlobalSummaryNetworkLsaCount OBJECT-TYPE
               SYNTAX   Gauge
               ACCESS   read-only   
               STATUS   mandatory
               DESCRIPTION
                        "The number of Summary Network (LS type 3)  link-state
                        advertisements in the link-state database."
               ::= { mpOspfGlobalEntry 21 }

        mpOspfGlobalSummaryRouterLsaCount OBJECT-TYPE
               SYNTAX   Gauge
               ACCESS   read-only   
               STATUS   mandatory
               DESCRIPTION
                        "The number of Summary Router (LS type 4)  link-state
                        advertisements in the link-state database."
               ::= { mpOspfGlobalEntry 22 }

        mpOspfGlobalExternalLsaCount OBJECT-TYPE
               SYNTAX   Gauge
               ACCESS   read-only   
               STATUS   mandatory
               DESCRIPTION
                        "The number of external (LS type 5)  link-state
                        advertisements in the link-state database."
               ::= { mpOspfGlobalEntry 23 }

        mpOspfGlobalExternalLsaCksumSum OBJECT-TYPE
               SYNTAX   Gauge
               ACCESS   read-only   
               STATUS   mandatory
               DESCRIPTION
                        "The 32-bit unsigned sum of the LS checksums of
                        the  external  link-state  advertisements  con-
                        tained in the link-state  database.   This  sum
                        can  be  used  to determine if there has been a
                        change in a router's link state  database,  and
                        to  compare  the  link-state  database  of  two
                        routers."
               ::= { mpOspfGlobalEntry 24 }

        mpOspfGlobalReceives OBJECT-TYPE
               SYNTAX   Counter
               ACCESS   read-only   
               STATUS   mandatory
               DESCRIPTION
                        "The number of received packets."
               ::= { mpOspfGlobalEntry 25 }

        mpOspfGlobalReceiveBadAuths OBJECT-TYPE
               SYNTAX   Counter
               ACCESS   read-only   
               STATUS   mandatory
               DESCRIPTION
                        "The number of received packets which were discarded
                         for authentication error."
               ::= { mpOspfGlobalEntry 26 }

        mpOspfGlobalReceiveBadPackets OBJECT-TYPE
               SYNTAX   Counter
               ACCESS   read-only   
               STATUS   mandatory
               DESCRIPTION
                        "The number of received packets which were discarded
                         except authentication error."
               ::= { mpOspfGlobalEntry 27 }

        mpOspfGlobalMulticastSends OBJECT-TYPE
               SYNTAX   Counter
               ACCESS   read-only   
               STATUS   mandatory
               DESCRIPTION
                        "The number of multicast sent packets."
               ::= { mpOspfGlobalEntry 28 }

        mpOspfGlobalUnicastSends OBJECT-TYPE
               SYNTAX   Counter
               ACCESS   read-only   
               STATUS   mandatory
               DESCRIPTION
                        "The number of unicast sent packets."
               ::= { mpOspfGlobalEntry 29 }

        mpOspfGlobalSpfRuns OBJECT-TYPE
               SYNTAX   Counter
               ACCESS   read-only   
               STATUS   mandatory
               DESCRIPTION
                        "The number of times of the calculation for shortest
                        path tree."
               ::= { mpOspfGlobalEntry 30 }

        mpOspfGlobalIncSummaryUpdates OBJECT-TYPE
               SYNTAX   Counter
               ACCESS   read-only   
               STATUS   mandatory
               DESCRIPTION
                        "The number of summary incremental updates."
               ::= { mpOspfGlobalEntry 31 }

        mpOspfGlobalIncExternalUpdates OBJECT-TYPE
               SYNTAX   Counter
               ACCESS   read-only   
               STATUS   mandatory
               DESCRIPTION
                        "The number of external incremental updates."
               ::= { mpOspfGlobalEntry 32 }

        mpOspfGlobalLsAgeOutCounts OBJECT-TYPE
               SYNTAX   Counter
               ACCESS   read-only   
               STATUS   mandatory
               DESCRIPTION
                        "The number of LSAs which were reached max age."
               ::= { mpOspfGlobalEntry 33 }

        mpOspfGlobalLsFlushCounts OBJECT-TYPE
               SYNTAX   Counter
               ACCESS   read-only   
               STATUS   mandatory
               DESCRIPTION
                        "The number of LSAs which max age were set up and 
                        which was removed forcibly."
               ::= { mpOspfGlobalEntry 34 }

        mpOspfGlobalLsdbAllocs OBJECT-TYPE
               SYNTAX   Counter
               ACCESS   read-only   
               STATUS   mandatory
               DESCRIPTION
                        "The number of LSAs which were allocated."
               ::= { mpOspfGlobalEntry 35 }

        mpOspfGlobalLsdbFrees OBJECT-TYPE
               SYNTAX   Counter
               ACCESS   read-only   
               STATUS   mandatory
               DESCRIPTION
                        "The number of LSAs which were released."
               ::= { mpOspfGlobalEntry 36 }

        mpOspfGlobalBufferAllocFailures OBJECT-TYPE
               SYNTAX   Counter
               ACCESS   read-only   
               STATUS   mandatory
               DESCRIPTION
                        "The number of times that it failed to hunt the 
                        buffer for the packet transmission."
               ::= { mpOspfGlobalEntry 37 }

        mpOspfImportListTable OBJECT-TYPE
               SYNTAX   SEQUENCE OF MpOspfImportListEntry
               ACCESS   not-accessible
               STATUS   mandatory
               DESCRIPTION
                        "The table to import routing information from other 
                        routing protocol to the OSPF process."
               ::= { mpOspf 3 }

        mpOspfImportListEntry OBJECT-TYPE
               SYNTAX   MpOspfImportListEntry
               ACCESS   not-accessible
               STATUS   mandatory
               DESCRIPTION
                        "The entry to import routing information from other 
                        routing protocol to the OSPF process."
               INDEX { mpOspfImportListProcessId, mpOspfImportListProtocol,
                       mpOspfImportListNumber }
               ::= { mpOspfImportListTable 1 }

         MpOspfImportListEntry ::=
               SEQUENCE {
                        mpOspfImportListProcessId
                            INTEGER,
                        mpOspfImportListProtocol
                            INTEGER,
                        mpOspfImportListNumber
                            INTEGER,
                        mpOspfImportListStatus
                            RowStatus
                        }

        mpOspfImportListProcessId OBJECT-TYPE
               SYNTAX   INTEGER
               ACCESS   read-only   
               STATUS   mandatory
               DESCRIPTION
                        "The process ID of OSPF."
               ::= { mpOspfImportListEntry 1 }

        mpOspfImportListProtocol OBJECT-TYPE
               SYNTAX   INTEGER    {
                    local(2),
                    static(3),
                    rip(8)
                  }
               ACCESS   read-only   
               STATUS   mandatory
               DESCRIPTION
                        "The protocol of IP routing table."
               ::= { mpOspfImportListEntry 2 }

        mpOspfImportListNumber OBJECT-TYPE
               SYNTAX   INTEGER
               ACCESS   read-only   
               STATUS   mandatory
               DESCRIPTION
                        "The import list number."
               ::= { mpOspfImportListEntry 3 }

        mpOspfImportListStatus OBJECT-TYPE
               SYNTAX   RowStatus
               ACCESS   read-write   
               STATUS   mandatory
               DESCRIPTION
                        "This variable displays the status of  the  en-
                        try.  Setting it to 'invalid' has the effect of
                        rendering it inoperative.  The internal  effect
                        (row removal) is implementation dependent."
               ::= { mpOspfImportListEntry 4 }

        mpOspfNetworkPriorityTable OBJECT-TYPE
               SYNTAX   SEQUENCE OF MpOspfNetworkPriorityEntry
               ACCESS   not-accessible
               STATUS   mandatory
               DESCRIPTION
                        "The table to specify route priority for each network 
                        at making IP routing table."
               ::= { mpOspf 4 }

        mpOspfNetworkPriorityEntry OBJECT-TYPE
               SYNTAX   MpOspfNetworkPriorityEntry
               ACCESS   not-accessible
               STATUS   mandatory
               DESCRIPTION
                        "The entry to specify route priority for each network 
                        at making IP routing table."
               INDEX { mpOspfNetworkPriorityProcessID, mpOspfNetworkPriorityAddress,
                       mpOspfNetworkPriorityMask }
               ::= { mpOspfNetworkPriorityTable 1 }

        MpOspfNetworkPriorityEntry ::=
               SEQUENCE {
                        mpOspfNetworkPriorityProcessID
                            INTEGER,
                        mpOspfNetworkPriorityAddress
                            IpAddress,
                        mpOspfNetworkPriorityMask
                            IpAddress,
                        mpOspfNetworkPriorityValue
                            INTEGER,
                        mpOspfNetworkPriorityStatus
                            RowStatus
                        }

        mpOspfNetworkPriorityProcessID OBJECT-TYPE
               SYNTAX   INTEGER
               ACCESS   read-only   
               STATUS   mandatory
               DESCRIPTION
                        "The process ID of OSPF."
               ::= { mpOspfNetworkPriorityEntry 1 }

        mpOspfNetworkPriorityAddress OBJECT-TYPE
               SYNTAX   IpAddress
               ACCESS   read-only   
               STATUS   mandatory
               DESCRIPTION
                        "The network address."
               ::= { mpOspfNetworkPriorityEntry 2 }

        mpOspfNetworkPriorityMask OBJECT-TYPE
               SYNTAX   IpAddress
               ACCESS   read-only   
               STATUS   mandatory
               DESCRIPTION
                        "The network mask."
               ::= { mpOspfNetworkPriorityEntry 3 }

        mpOspfNetworkPriorityValue OBJECT-TYPE
               SYNTAX   INTEGER(1..255)
               ACCESS   read-write   
               STATUS   mandatory
               DESCRIPTION
                        "The route priority."
               ::= { mpOspfNetworkPriorityEntry 4 }

        mpOspfNetworkPriorityStatus OBJECT-TYPE
               SYNTAX   RowStatus
               ACCESS   read-write   
               STATUS   mandatory
               DESCRIPTION
                        "This variable displays the status of  the  en-
                        try.  Setting it to 'invalid' has the effect of
                        rendering it inoperative.  The internal  effect
                        (row removal) is implementation dependent."    
               ::= { mpOspfNetworkPriorityEntry 5 }

        mpOspfAreaTable OBJECT-TYPE
               SYNTAX   SEQUENCE OF MpOspfAreaEntry
               ACCESS   not-accessible
               STATUS   mandatory
               DESCRIPTION 
                        "Information describing the configured  parame-
                        ters  and cumulative statistics of the router's
                        attached areas."                               
               ::= { mpOspf 5 }

        mpOspfAreaEntry OBJECT-TYPE
               SYNTAX   MpOspfAreaEntry
               ACCESS   not-accessible
               STATUS   mandatory
               DESCRIPTION 
                        "Information describing the configured  parame-
                        ters  and  cumulative  statistics of one of the
                        router's attached areas."                      
               INDEX { mpOspfAreaProcessId, mpOspfAreaId }
               ::= { mpOspfAreaTable 1 }

        MpOspfAreaEntry ::=
               SEQUENCE {
                        mpOspfAreaProcessId
                            INTEGER,
                        mpOspfAreaId
                            IpAddress,
                        mpOspfAreaImportAsExternal
                            INTEGER,
                        mpOspfAreaStubMetric
                            INTEGER,
                        mpOspfAreaSummary
                            INTEGER,
                        mpOspfAreaConfigIfCount
                            Gauge,
                        mpOspfAreaActiveIfCount
                           Gauge,
                        mpOspfAreaTransitCapability
                           TruthValue,
                        mpOspfAreaTransitNetCount
                           Gauge,
                        mpOspfAreaRtrCount
                           Gauge,
                        mpOspfAreaBdrRtrCount
                           Gauge,
                        mpOspfAreaAsBdrRtrCount
                           Gauge,
                        mpOspfAreaLsaCount
                           Gauge,
                        mpOspfAreaLsaCksumSum
                           Gauge,
                        mpOspfAreaStatus
                           RowStatus
                        }

        mpOspfAreaProcessId OBJECT-TYPE
               SYNTAX   INTEGER
               ACCESS   read-only
               STATUS   mandatory
               DESCRIPTION
                        "The process ID of OSPF."
               ::= { mpOspfAreaEntry 1 }

        mpOspfAreaId OBJECT-TYPE
               SYNTAX   IpAddress
               ACCESS   read-only
               STATUS   mandatory
               DESCRIPTION 
                        "A 32-bit integer uniquely identifying an area.
                        Area ID 0.0.0.0 is used for the OSPF backbone."
               ::= { mpOspfAreaEntry 2 }

        mpOspfAreaImportAsExternal OBJECT-TYPE
               SYNTAX   INTEGER    {
                    importExternal (1),
                    importNoExternal (2),
                    importNssa (3)
                  }
               ACCESS   read-write
               STATUS   mandatory
               DESCRIPTION 
                        "The area's support for importing  AS  external
                        link- state advertisements."                   
               ::= { mpOspfAreaEntry 3 }

        mpOspfAreaStubMetric OBJECT-TYPE
               SYNTAX   INTEGER(1..65535)
               ACCESS   read-write
               STATUS   mandatory
               DESCRIPTION
                        "The metric to be set up to default route which 
                        advertises to stub area."
               ::= { mpOspfAreaEntry 4 }

        mpOspfAreaSummary OBJECT-TYPE
               SYNTAX   INTEGER    {
                    noAreaSummary (1),
                    sendAreaSummary (2)
                  }
               ACCESS   read-write   
               STATUS   mandatory
               DESCRIPTION 
                        "The variable ospfAreaSummary controls the  im-
                        port  of  summary LSAs into stub areas.  It has
                        no effect on other areas.                      
                                                                        
                        If it is noAreaSummary, the router will neither
                        originate  nor  propagate summary LSAs into the
                        stub area.  It will rely entirely  on  its  de-
                        fault route.                                   
                                                                        
                        If it is sendAreaSummary, the router will  both
                        summarize and propagate summary LSAs."         
               ::= { mpOspfAreaEntry 5 }

        mpOspfAreaConfigIfCount OBJECT-TYPE
               SYNTAX   Gauge
               ACCESS   read-only   
               STATUS   mandatory
               DESCRIPTION
                        "The number of the registered interfaces."
               ::= { mpOspfAreaEntry 6 }

        mpOspfAreaActiveIfCount OBJECT-TYPE
               SYNTAX   Gauge
               ACCESS   read-only   
               STATUS   mandatory
               DESCRIPTION
                        "The number of the interface during operation."
               ::= { mpOspfAreaEntry 7 }

        mpOspfAreaTransitCapability OBJECT-TYPE
               SYNTAX   TruthValue
               ACCESS   read-only   
               STATUS   mandatory
               DESCRIPTION
                        "Indicates whether it is the area which active 
                        virtual link exists in."
               ::= { mpOspfAreaEntry 8 }

        mpOspfAreaTransitNetCount OBJECT-TYPE
               SYNTAX   Gauge
               ACCESS   read-only   
               STATUS   mandatory
               DESCRIPTION
                        "The number of reachable transit networks. "
               ::= { mpOspfAreaEntry 9 }

        mpOspfAreaRtrCount OBJECT-TYPE
               SYNTAX   Gauge
               ACCESS   read-only   
               STATUS   mandatory
               DESCRIPTION
                        "The number of reachable routers."
               ::= { mpOspfAreaEntry 10 }

        mpOspfAreaBdrRtrCount OBJECT-TYPE
               SYNTAX   Gauge
               ACCESS   read-only   
               STATUS   mandatory
               DESCRIPTION 
                        "The total number of area border routers reach-
                        able within this area.  This is initially zero,
                        and is calculated in each SPF Pass."           
               ::= { mpOspfAreaEntry 11 }

        mpOspfAreaAsBdrRtrCount OBJECT-TYPE
               SYNTAX   Gauge
               ACCESS   read-only   
               STATUS   mandatory
               DESCRIPTION 
                        "The total number of Autonomous  System  border
                        routers  reachable  within  this area.  This is
                        initially zero, and is calculated in  each  SPF
                        Pass."                                         
               ::= { mpOspfAreaEntry 12 }

        mpOspfAreaLsaCount OBJECT-TYPE
               SYNTAX   Gauge
               ACCESS   read-only   
               STATUS   mandatory
               DESCRIPTION 
                        "The total number of link-state  advertisements
                        in  this  area's link-state database, excluding
                        AS External LSA's."                            
               ::= { mpOspfAreaEntry 13 }

        mpOspfAreaLsaCksumSum OBJECT-TYPE
               SYNTAX   Gauge
               ACCESS   read-only   
               STATUS   mandatory
               DESCRIPTION 
                        "The 32-bit unsigned sum of the link-state  ad-
                        vertisements'  LS  checksums  contained in this
                        area's link-state database.  This sum  excludes
                        external (LS type 5) link-state advertisements.
                        The sum can be used to determine if  there  has
                        been  a  change  in a router's link state data-
                        base, and to compare the link-state database of
                        two routers."                                 
               ::= { mpOspfAreaEntry 14 }

        mpOspfAreaStatus OBJECT-TYPE
               SYNTAX   RowStatus
               ACCESS   read-write   
               STATUS   mandatory
               DESCRIPTION 
                        "This variable displays the status of  the  en-
                        try.  Setting it to 'invalid' has the effect of
                        rendering it inoperative.  The internal  effect
                        (row removal) is implementation dependent."    
               ::= { mpOspfAreaEntry 15 }

        mpOspfLsdbTable OBJECT-TYPE
               SYNTAX   SEQUENCE OF MpOspfLsdbEntry
               ACCESS   not-accessible
               STATUS   mandatory
               DESCRIPTION 
                        "The OSPF Process's Link State Database."
               ::= { mpOspf 6 }

        mpOspfLsdbEntry OBJECT-TYPE
               SYNTAX   MpOspfLsdbEntry
               ACCESS   not-accessible
               STATUS   mandatory
               DESCRIPTION 
                        "A single Link State Advertisement."
               INDEX { mpOspfLsdbProcessId, mpOspfLsdbAreaId, mpOspfLsdbType,
                    mpOspfLsdbLsid, mpOspfLsdbRouterId }
               ::= { mpOspfLsdbTable 1 }

        MpOspfLsdbEntry ::=
               SEQUENCE {
                        mpOspfLsdbProcessId
                            INTEGER,
                        mpOspfLsdbAreaId
                            IpAddress,
                        mpOspfLsdbType
                            INTEGER,
                        mpOspfLsdbLsid 
                            IpAddress,
                        mpOspfLsdbRouterId 
                            IpAddress,
                        mpOspfLsdbSequence
                            INTEGER,
                        mpOspfLsdbAge
                            INTEGER,
                        mpOspfLsdbChecksum
                            INTEGER,
                        mpOspfLsdbAdvertisement
                            OCTET STRING 
                        }

        mpOspfLsdbProcessId OBJECT-TYPE
               SYNTAX   INTEGER
               ACCESS   read-only   
               STATUS   mandatory
               DESCRIPTION
                        "The process ID of OSPF."
               ::= { mpOspfLsdbEntry 1 }

        mpOspfLsdbAreaId OBJECT-TYPE
               SYNTAX   IpAddress
               ACCESS   read-only   
               STATUS   mandatory
               DESCRIPTION 
                        "The 32 bit identifier of the Area  from  which
                        the LSA was received."                         
               ::= { mpOspfLsdbEntry 2 }

        mpOspfLsdbType OBJECT-TYPE
               SYNTAX   INTEGER    {
                    routerLink (1),
                    networkLink (2),
                    summaryLink (3),
                    asSummaryLink (4),
                    asExternalLink (5), -- but see ospfExtLsdbTable
                    multicastLink (6),
                    nssaExternalLink (7)
                  }
               ACCESS   read-only   
               STATUS   mandatory
               DESCRIPTION 
                        "The type  of  the  link  state  advertisement.
                        Each  link state type has a separate advertise-
                        ment format."                                  
               ::= { mpOspfLsdbEntry 3 }

        mpOspfLsdbLsid OBJECT-TYPE
               SYNTAX   IpAddress
               ACCESS   read-only   
               STATUS   mandatory
               DESCRIPTION 
                        "The Link State ID is an LS Type Specific field
                        containing either a Router ID or an IP Address;
                        it identifies the piece of the  routing  domain
                        that is being described by the advertisement." 
               ::= { mpOspfLsdbEntry 4 }

        mpOspfLsdbRouterId OBJECT-TYPE
               SYNTAX   IpAddress
               ACCESS   read-only   
               STATUS   mandatory
               DESCRIPTION 
                        "The 32 bit number that uniquely identifies the
                        originating router in the Autonomous System."  
               ::= { mpOspfLsdbEntry 5 }

        mpOspfLsdbSequence OBJECT-TYPE
               SYNTAX   INTEGER
               ACCESS   read-only   
               STATUS   mandatory
               DESCRIPTION 
                        "The sequence number field is a  signed  32-bit
                        integer.   It  is used to detect old and dupli-
                        cate link state advertisements.  The  space  of
                        sequence  numbers  is  linearly  ordered.   The
                        larger the sequence number the more recent  the
                        advertisement."                                
               ::= { mpOspfLsdbEntry 6 }

        mpOspfLsdbAge OBJECT-TYPE
               SYNTAX   INTEGER
               ACCESS   read-only   
               STATUS   mandatory
               DESCRIPTION 
                        "This field is the age of the link state adver-
                        tisement in seconds."
               ::= { mpOspfLsdbEntry 7 }

        mpOspfLsdbChecksum OBJECT-TYPE
               SYNTAX   INTEGER
               ACCESS   read-only   
               STATUS   mandatory
               DESCRIPTION 
                        "This field is the  checksum  of  the  complete
                        contents  of  the  advertisement, excepting the
                        age field.  The age field is excepted  so  that
                        an   advertisement's  age  can  be  incremented
                        without updating the  checksum.   The  checksum
                        used  is  the same that is used for ISO connec-
                        tionless datagrams; it is commonly referred  to
                        as the Fletcher checksum."                     
               ::= { mpOspfLsdbEntry 8 }

        mpOspfLsdbAdvertisement OBJECT-TYPE
               SYNTAX   OCTET STRING (SIZE (1..65535))
               ACCESS   read-only   
               STATUS   mandatory
               DESCRIPTION
                        "The entire Link State Advertisement, including
                        its header."                                   
               ::= { mpOspfLsdbEntry 9 }

        mpOspfAreaRangeTable OBJECT-TYPE
               SYNTAX   SEQUENCE OF MpOspfAreaRangeEntry
               ACCESS   not-accessible
               STATUS   mandatory
               DESCRIPTION 
                        "A range if IP addresses  specified  by  an  IP
                        address/IP  network  mask  pair.   For example,
                        class B address range of X.X.X.X with a network
                        mask  of  255.255.0.0 includes all IP addresses
                        from X.X.0.0 to X.X.255.255"                   
               ::= { mpOspf 7 }

        mpOspfAreaRangeEntry OBJECT-TYPE
               SYNTAX   MpOspfAreaRangeEntry
               ACCESS   not-accessible
               STATUS   mandatory
               DESCRIPTION 
                        "A range if IP addresses  specified  by  an  IP
                        address/IP  network  mask  pair.   For example,
                        class B address range of X.X.X.X with a network
                        mask  of  255.255.0.0 includes all IP addresses
                        from X.X.0.0 to X.X.255.255"                   
               INDEX { mpOspfAreaRangeProcessId, mpOspfAreaRangeAreaId,
                       mpOspfAreaRangeNet, mpOspfAreaRangeMask }
               ::= { mpOspfAreaRangeTable 1 }

        MpOspfAreaRangeEntry ::=
               SEQUENCE {
                        mpOspfAreaRangeProcessId
                            INTEGER,
                        mpOspfAreaRangeAreaId
                            IpAddress,
                        mpOspfAreaRangeNet
                            IpAddress,
                        mpOspfAreaRangeMask
                            IpAddress,
                        mpOspfAreaRangeEffect
                            INTEGER,
                        mpOspfAreaRangeStatus
                            RowStatus
                        }

        mpOspfAreaRangeProcessId OBJECT-TYPE
               SYNTAX   INTEGER
               ACCESS   read-only   
               STATUS   mandatory
               DESCRIPTION
                        "The process ID of OSPF."
               ::= { mpOspfAreaRangeEntry 1 }

        mpOspfAreaRangeAreaId OBJECT-TYPE
               SYNTAX   IpAddress
               ACCESS   read-only   
               STATUS   mandatory
               DESCRIPTION 
                        "The Area the Address  Range  is  to  be  found
                        within."
               ::= { mpOspfAreaRangeEntry 2 }

        mpOspfAreaRangeNet OBJECT-TYPE
               SYNTAX   IpAddress
               ACCESS   read-only   
               STATUS   mandatory
               DESCRIPTION 
                        "The IP Address of the Net or Subnet  indicated
                        by the range."
               ::= { mpOspfAreaRangeEntry 3 }

        mpOspfAreaRangeMask OBJECT-TYPE
               SYNTAX   IpAddress
               ACCESS   read-only   
               STATUS   mandatory
               DESCRIPTION 
                        "The Subnet Mask that pertains to  the  Net  or
                         Subnet."
               ::= { mpOspfAreaRangeEntry 4 }

        mpOspfAreaRangeEffect OBJECT-TYPE
               SYNTAX   INTEGER    {
                    advertiseMatching (1),
                    doNotAdvertiseMatching (2)
                  }
               ACCESS   read-write   
               STATUS   mandatory
               DESCRIPTION 
                        "Subnets subsumed by ranges either trigger  the
                        advertisement  of the indicated summary (adver-
                        tiseMatching), or result in  the  subnet's  not
                        being advertised at all outside the area."     
               ::= { mpOspfAreaRangeEntry 5 }

        mpOspfAreaRangeStatus OBJECT-TYPE
               SYNTAX   RowStatus
               ACCESS   read-write   
               STATUS   mandatory
               DESCRIPTION 
                        "This variable displays the status of  the  en-
                        try.  Setting it to 'invalid' has the effect of
                        rendering it inoperative.  The internal  effect
                        (row removal) is implementation dependent."    
               ::= { mpOspfAreaRangeEntry 6 }

        mpOspfHostTable OBJECT-TYPE
               SYNTAX   SEQUENCE OF MpOspfHostEntry
               ACCESS   not-accessible
               STATUS   mandatory
               DESCRIPTION 
                        "The list of Hosts, and their metrics, that the
                        router will advertise as host routes."         
               ::= { mpOspf 8 }

        mpOspfHostEntry OBJECT-TYPE
               SYNTAX   MpOspfHostEntry
               ACCESS   not-accessible
               STATUS   mandatory
               DESCRIPTION 
                        "A metric to be advertised, for a given type of
                        service, when a given host is reachable."      
               INDEX { mpOspfHostProcessId, mpOspfHostIpAddress }
               ::= { mpOspfHostTable 1 }

        MpOspfHostEntry  ::=
               SEQUENCE {
                        mpOspfHostProcessId
                            INTEGER,
                        mpOspfHostIpAddress
                            IpAddress,
                        mpOspfHostMetric
                            INTEGER,
                        mpOspfHostStatus
                            RowStatus
                        }

        mpOspfHostProcessId OBJECT-TYPE
               SYNTAX   INTEGER
               ACCESS   read-only   
               STATUS   mandatory
               DESCRIPTION
                        "The process ID of OSPF."
               ::= { mpOspfHostEntry 1 }

        mpOspfHostIpAddress OBJECT-TYPE
               SYNTAX   IpAddress
               ACCESS   read-only   
               STATUS   mandatory
               DESCRIPTION 
                        "The IP Address of the Host."
               ::= { mpOspfHostEntry 2 }

        mpOspfHostMetric OBJECT-TYPE
               SYNTAX   INTEGER (1..65535)
               ACCESS   read-write   
               STATUS   mandatory
               DESCRIPTION 
                        "The Metric to be advertised."
               ::= { mpOspfHostEntry 3 }

        mpOspfHostStatus OBJECT-TYPE
               SYNTAX   RowStatus
               ACCESS   read-write   
               STATUS   mandatory
               DESCRIPTION 
                        "This variable displays the status of  the  en-
                        try.  Setting it to 'invalid' has the effect of
                        rendering it inoperative.  The internal  effect
                        (row removal) is implementation dependent."    
               ::= { mpOspfHostEntry 4 }

        mpOspfIfTable OBJECT-TYPE
               SYNTAX   SEQUENCE OF MpOspfIfEntry
               ACCESS   not-accessible
               STATUS   mandatory
               DESCRIPTION 
                        "The OSPF Interface Table describes the  inter-
                        faces from the viewpoint of OSPF."
               ::= { mpOspf 9 }

        mpOspfIfEntry OBJECT-TYPE
               SYNTAX   MpOspfIfEntry
               ACCESS   not-accessible
               STATUS   mandatory
               DESCRIPTION 
                        "The OSPF Interface Entry describes one  inter-
                        face from the viewpoint of OSPF."
               INDEX { mpOspfIfProcessId, mpOspfIfIndex }
               ::= { mpOspfIfTable 1 }

        MpOspfIfEntry  ::=
               SEQUENCE {
                        mpOspfIfProcessId
                            INTEGER,
                        mpOspfIfIndex
                            INTEGER,
                        mpOspfIfIpAddress
                            IpAddress,
                        mpOspfIfIpMask
                            IpAddress,
                        mpOspfIfAreaId
                            IpAddress,
                        mpOspfIfType
                            INTEGER,
                        mpOspfIfMetric
                            INTEGER,
                        mpOspfIfRtrPriority
                            INTEGER,
                        mpOspfIfTransitDelay
                            INTEGER,
                        mpOspfIfRetransInterval
                            INTEGER,
                        mpOspfIfHelloInterval
                            INTEGER,
                        mpOspfIfRtrDeadInterval
                            INTEGER,
                        mpOspfIfPollInterval
                            INTEGER,
                        mpOspfIfState
                            INTEGER,
                        mpOspfIfDesignatedRouter
                            IpAddress,
                        mpOspfIfBackupDesignatedRouter
                            IpAddress,
                        mpOspfIfAuthType
                            INTEGER,
                        mpOspfIfAuthKeyId
                            INTEGER,
                        mpOspfIfAuthKey
                            OCTET STRING,
                        mpOspfIfMulticastForwarding
                            INTEGER,
                        mpOspfIfDemand
                            TruthValue,
                        mpOspfIfEvents
                            Counter,
                        mpOspfIfNeighbors
                            Gauge,
                        mpOspfIfAdjacencies
                            Gauge,
                        mpOspfIfFullyAdjacencies
                            Gauge,
                        mpOspfIfLsUpdateFloods
                            Counter,
                        mpOspfIfDelayedAckSends
                            Counter,
                        mpOspfIfStatus
                            RowStatus
                        }

        mpOspfIfProcessId OBJECT-TYPE
               SYNTAX   INTEGER
               ACCESS   read-only   
               STATUS   mandatory
               DESCRIPTION
                        "The process ID of OSPF."
               ::= { mpOspfIfEntry 1 }

        mpOspfIfIndex OBJECT-TYPE
               SYNTAX   INTEGER
               ACCESS   read-only   
               STATUS   mandatory
               DESCRIPTION
                        "This object specifies ifIndex of interface."
               ::= { mpOspfIfEntry 2 }

        mpOspfIfIpAddress OBJECT-TYPE
               SYNTAX   IpAddress
               ACCESS   read-only   
               STATUS   mandatory
               DESCRIPTION 
                        "The IP address of this OSPF interface."
               ::= { mpOspfIfEntry 3 }

        mpOspfIfIpMask OBJECT-TYPE
               SYNTAX   IpAddress
               ACCESS   read-only   
               STATUS   mandatory
               DESCRIPTION
                        "The network mask registered in interface."
               ::= { mpOspfIfEntry 4 }

        mpOspfIfAreaId OBJECT-TYPE
               SYNTAX   IpAddress
               ACCESS   read-write   
               STATUS   mandatory
               DESCRIPTION 
                        "A 32-bit integer uniquely identifying the area
                        to  which  the  interface  connects.   Area  ID
                        0.0.0.0 is used for the OSPF backbone."        
               ::= { mpOspfIfEntry 5 }

        mpOspfIfType OBJECT-TYPE
               SYNTAX   INTEGER    {
                    broadcast (1),
                    nbma (2),
                    pointToPoint (3),
                    pointToMultipoint (5)
                  }
               ACCESS   read-write   
               STATUS   mandatory
               DESCRIPTION 
                        "The OSPF interface type.                      
                        By way of a default, this field may be intuited
                        from the corresponding value of ifType.  Broad-
                        cast LANs, such as  Ethernet  and  IEEE  802.5,
                        take  the  value  'broadcast', X.25 and similar
                        technologies take the value 'nbma',  and  links
                        that  are  definitively point to point take the
                        value 'pointToPoint'."                         
               ::= { mpOspfIfEntry 6 }

        mpOspfIfMetric OBJECT-TYPE
               SYNTAX   INTEGER (1..65535)
               ACCESS   read-write   
               STATUS   mandatory
               DESCRIPTION
                        "The metric of this interface."
               ::= { mpOspfIfEntry 7 }

        mpOspfIfRtrPriority OBJECT-TYPE
               SYNTAX   INTEGER (0..255)
               ACCESS   read-write   
               STATUS   mandatory
               DESCRIPTION 
                        "The  priority  of  this  interface.   Used  in
                        multi-access  networks,  this  field is used in
                        the designated router election algorithm.   The
                        value 0 signifies that the router is not eligi-
                        ble to become the  designated  router  on  this
                        particular  network.   In the event of a tie in
                        this value, routers will use their Router ID as
                        a tie breaker."                                
               ::= { mpOspfIfEntry 8 }

        mpOspfIfTransitDelay OBJECT-TYPE
               SYNTAX   INTEGER (1..3600)
               ACCESS   read-write   
               STATUS   mandatory
               DESCRIPTION 
                        "The estimated number of seconds  it  takes  to
                        transmit  a  link state update packet over this
                        interface."                                    
               ::= { mpOspfIfEntry 9 }

        mpOspfIfRetransInterval OBJECT-TYPE
               SYNTAX   INTEGER (1..3600)
               ACCESS   read-write   
               STATUS   mandatory
               DESCRIPTION 
                        "The number of seconds between  link-state  ad-
                        vertisement  retransmissions,  for  adjacencies
                        belonging to this  interface.   This  value  is
                        also used when retransmitting database descrip-
                        tion and link-state request packets."          
               ::= { mpOspfIfEntry 10 }

        mpOspfIfHelloInterval OBJECT-TYPE
               SYNTAX   INTEGER (1..65535)
               ACCESS   read-write   
               STATUS   mandatory
               DESCRIPTION 
                        "The length of time, in  seconds,  between  the
                        Hello  packets that the router sends on the in-
                        terface.  This value must be the same  for  all
                        routers attached to a common network."         
               ::= { mpOspfIfEntry 11 }

        mpOspfIfRtrDeadInterval OBJECT-TYPE
               SYNTAX   INTEGER (1..2147483647)
               ACCESS   read-write   
               STATUS   mandatory
               DESCRIPTION 
                        "The number of seconds that  a  router's  Hello
                        packets  have  not been seen before it's neigh-
                        bors declare the router down.  This  should  be
                        some  multiple  of  the  Hello  interval.  This
                        value must be the same for all routers attached
                        to a common network."                          
               ::= { mpOspfIfEntry 12 }

        mpOspfIfPollInterval OBJECT-TYPE
               SYNTAX   INTEGER (0..2147483647)
               ACCESS   read-write   
               STATUS   mandatory
               DESCRIPTION 
                        "The larger time interval, in seconds,  between
                        the  Hello  packets  sent  to  an inactive non-
                        broadcast multi- access neighbor."
               ::= { mpOspfIfEntry 13 }

        mpOspfIfState OBJECT-TYPE
               SYNTAX   INTEGER    {
                    down (1),
                    loopback (2),
                    waiting (3),
                    pointToPoint (4),
                    designatedRouter (5),
                    backupDesignatedRouter (6),
                    otherDesignatedRouter (7)
                  }
               ACCESS   read-only   
               STATUS   mandatory
               DESCRIPTION 
                        "The OSPF Interface State."
               ::= { mpOspfIfEntry 14 }

        mpOspfIfDesignatedRouter OBJECT-TYPE
               SYNTAX   IpAddress
               ACCESS   read-only   
               STATUS   mandatory
               DESCRIPTION 
                        "The IP Address of the Designated Router."
               ::= { mpOspfIfEntry 15 }

        mpOspfIfBackupDesignatedRouter OBJECT-TYPE
               SYNTAX   IpAddress
               ACCESS   read-only   
               STATUS   mandatory
               DESCRIPTION 
                        "The  IP  Address  of  the  Backup   Designated
                        Router."
               ::= { mpOspfIfEntry 16 }

        mpOspfIfAuthType OBJECT-TYPE
               SYNTAX   INTEGER
                    -- none (0),
                    -- simplePassword (1)
                    -- md5 (2)
                    -- reserved for specification by IANA (> 2)
               ACCESS   read-write   
               STATUS   mandatory
               DESCRIPTION
                        "The authentication type specified for  an  in-
                        terface.   Additional  authentication types may
                        be assigned locally."                          
               ::= { mpOspfIfEntry 17 }

        mpOspfIfAuthKeyId OBJECT-TYPE
               SYNTAX   INTEGER (0..255)
               ACCESS   read-write   
               STATUS   mandatory
               DESCRIPTION
                        "The Key ID to be used when an authentication 
                        type is MD5. The value from 1 to 255 are used 
                        for  key  ID.  'Get' is not allowed  for this 
                        object.  The  value  0  will  be  returned as 
                        meaningless value when Get-Request is received 
                        for this object."
               ::= { mpOspfIfEntry 18 }

        mpOspfIfAuthKey OBJECT-TYPE
               SYNTAX   OCTET STRING (SIZE(16))
               ACCESS   read-write   
               STATUS   mandatory
               DESCRIPTION 
                        "The Authentication Key.  If the Area's Author-
                        ization  Type  is  simplePassword,  and the key
                        length is shorter than 8 octets, the agent will
                        left adjust and zero fill to 8 octets.         
                                                                       
                        Note that unauthenticated  interfaces  need  no
                        authentication key, and simple password authen-
                        tication cannot use a key of more  than  8  oc-
                        tets.  Larger keys are useful only with authen-
                        tication mechanisms not specified in this docu-
                        ment.                                          
                                                                       
                        When read, ospfIfAuthKey always returns an  Oc-
                        tet String of length zero."                    
               ::= { mpOspfIfEntry 19 }

        mpOspfIfMulticastForwarding OBJECT-TYPE
               SYNTAX   INTEGER    {
                            blocked (1),     -- no multicast forwarding
                            multicast (2),   -- using multicast address
                            unicast (3)      -- to each OSPF neighbor
                  }
               ACCESS   read-write   
               STATUS   mandatory
               DESCRIPTION 
                        "The way multicasts should  forwarded  on  this
                        interface;  not  forwarded,  forwarded  as data
                        link multicasts, or forwarded as data link uni-
                        casts.   Data link multicasting is not meaning-
                        ful on point to point and NBMA interfaces,  and
                        setting ospfMulticastForwarding to 0 effective-
                        ly disables all multicast forwarding."         
               ::= { mpOspfIfEntry 20 }

        mpOspfIfDemand OBJECT-TYPE
               SYNTAX   TruthValue
               ACCESS   read-write   
               STATUS   mandatory
               DESCRIPTION 
                        "Indicates whether Demand OSPF procedures (hel-
                        lo supression to FULL neighbors and setting the
                        DoNotAge flag on proogated LSAs) should be per-
                        formed on this interface."                     
               ::= { mpOspfIfEntry 21 }

        mpOspfIfEvents OBJECT-TYPE
               SYNTAX   Counter
               ACCESS   read-only   
               STATUS   mandatory
               DESCRIPTION 
                        "The number of times this  OSPF  interface  has
                        changed its state, or an error has occurred."  
               ::= { mpOspfIfEntry 22 }

        mpOspfIfNeighbors OBJECT-TYPE
               SYNTAX   Gauge
               ACCESS   read-only   
               STATUS   mandatory
               DESCRIPTION
                        "The number of Neighbors."
               ::= { mpOspfIfEntry 23 }

        mpOspfIfAdjacencies OBJECT-TYPE
               SYNTAX   Gauge
               ACCESS   read-only   
               STATUS   mandatory
               DESCRIPTION
                        "The number of adjacent Neighbors."
               ::= { mpOspfIfEntry 24 }

        mpOspfIfFullyAdjacencies OBJECT-TYPE
               SYNTAX   Gauge
               ACCESS   read-only   
               STATUS   mandatory
               DESCRIPTION
                        "The number of fully adjacent Neighbors."
               ::= { mpOspfIfEntry 25 }

        mpOspfIfLsUpdateFloods OBJECT-TYPE
               SYNTAX   Counter
               ACCESS   read-only   
               STATUS   mandatory
               DESCRIPTION
                        "The number of LS-update floods."
               ::= { mpOspfIfEntry 26 }

        mpOspfIfDelayedAckSends OBJECT-TYPE
               SYNTAX   Counter
               ACCESS   read-only   
               STATUS   mandatory
               DESCRIPTION
                        "The number of LS-Ack floods."
               ::= { mpOspfIfEntry 27 }

        mpOspfIfStatus OBJECT-TYPE
               SYNTAX   RowStatus
               ACCESS   read-write   
               STATUS   mandatory
               DESCRIPTION 
                        "This variable displays the status of  the  en-
                        try.  Setting it to 'invalid' has the effect of
                        rendering it inoperative.  The internal  effect
                        (row removal) is implementation dependent."    
               ::= { mpOspfIfEntry 28 }

        mpOspfVirtIfTable OBJECT-TYPE
               SYNTAX   SEQUENCE OF MpOspfVirtIfEntry
               ACCESS   not-accessible
               STATUS   mandatory
               DESCRIPTION 
                        "Information about this router's virtual inter-
                        faces."
               ::= { mpOspf 10 }

        mpOspfVirtIfEntry OBJECT-TYPE
               SYNTAX   MpOspfVirtIfEntry
               ACCESS   not-accessible
               STATUS   mandatory
               DESCRIPTION 
                        "Information about a single Virtual Interface."
               INDEX { mpOspfVirtIfProcessId, mpOspfVirtIfId }
               ::= { mpOspfVirtIfTable 1 }

        MpOspfVirtIfEntry ::=
               SEQUENCE {
                        mpOspfVirtIfProcessId
                            INTEGER,
                        mpOspfVirtIfId
                            INTEGER,
                        mpOspfVirtIfNeighbor
                            IpAddress,
                        mpOspfVirtIfAreaId
                            IpAddress,
                        mpOspfVirtIfMetric
                            INTEGER,
                        mpOspfVirtIfTransitDelay
                            INTEGER,
                        mpOspfVirtIfRetransInterval
                            INTEGER,
                        mpOspfVirtIfHelloInterval
                            INTEGER,
                        mpOspfVirtIfRtrDeadInterval
                            INTEGER,
                        mpOspfVirtIfState
                            INTEGER,
                        mpOspfVirtIfAuthType
                            INTEGER,
                        mpOspfVirtIfAuthKeyId
                            INTEGER,
                        mpOspfVirtIfAuthKey
                            OCTET STRING,
                        mpOspfVirtIfEvents
                            Counter,
                        mpOspfVirtIfNeighbors
                            Gauge,
                        mpOspfVirtIfAdjacencies
                            Gauge,
                        mpOspfVirtIfFullyAdjacencies
                            Gauge,
                        mpOspfVirtIfLsUpdateFloods
                            Counter,
                        mpOspfVirtIfDelayedAckSends
                            Counter,
                        mpOspfVirtIfStatus
                            RowStatus
                        }

        mpOspfVirtIfProcessId OBJECT-TYPE
               SYNTAX   INTEGER
               ACCESS   read-only   
               STATUS   mandatory
               DESCRIPTION
                        "The process ID of OSPF."
               ::= { mpOspfVirtIfEntry 1 }

        mpOspfVirtIfId OBJECT-TYPE
               SYNTAX   INTEGER
               ACCESS   read-only   
               STATUS   mandatory
               DESCRIPTION
                        "Identification which is used to distinguish
                         virtual link."
               ::= { mpOspfVirtIfEntry 2 }

        mpOspfVirtIfNeighbor OBJECT-TYPE
               SYNTAX   IpAddress
               ACCESS   read-write   
               STATUS   mandatory
               DESCRIPTION 
                        "The Router ID of the Virtual Neighbor."
               ::= { mpOspfVirtIfEntry 3 }

        mpOspfVirtIfAreaId OBJECT-TYPE
               SYNTAX   IpAddress
               ACCESS   read-write   
               STATUS   mandatory
               DESCRIPTION 
                        "The  Transit  Area  that  the   Virtual   Link
                        traverses.  By definition, this is not 0.0.0.0"
               ::= { mpOspfVirtIfEntry 4 }

        mpOspfVirtIfMetric OBJECT-TYPE
               SYNTAX   INTEGER
               ACCESS   read-only   
               STATUS   mandatory
               DESCRIPTION
                        "The metric until end point router."
               ::= { mpOspfVirtIfEntry 5 }

        mpOspfVirtIfTransitDelay OBJECT-TYPE
               SYNTAX   INTEGER (1..3600)
               ACCESS   read-write   
               STATUS   mandatory
               DESCRIPTION 
                        "The estimated number of seconds  it  takes  to
                        transmit  a link- state update packet over this
                        interface."                                    
               ::= { mpOspfVirtIfEntry 6 }

        mpOspfVirtIfRetransInterval OBJECT-TYPE
               SYNTAX   INTEGER (1..3600)
               ACCESS   read-write   
               STATUS   mandatory
               DESCRIPTION 
                        "The number of seconds between  link-state  ad-
                        vertisement  retransmissions,  for  adjacencies
                        belonging to this  interface.   This  value  is
                        also used when retransmitting database descrip-
                        tion  and  link-state  request  packets.   This
                        value  should  be well over the expected round-
                        trip time."                                    
               ::= { mpOspfVirtIfEntry 7 }

        mpOspfVirtIfHelloInterval OBJECT-TYPE
               SYNTAX   INTEGER (1..65535)
               ACCESS   read-write   
               STATUS   mandatory
               DESCRIPTION 
                        "The length of time, in  seconds,  between  the
                        Hello  packets that the router sends on the in-
                        terface.  This value must be the same  for  the
                        virtual neighbor."                             
               ::= { mpOspfVirtIfEntry 8 }

        mpOspfVirtIfRtrDeadInterval OBJECT-TYPE
               SYNTAX   INTEGER (1..2147483647)
               ACCESS   read-write   
               STATUS   mandatory
               DESCRIPTION 
                        "The number of seconds that  a  router's  Hello
                        packets  have  not been seen before it's neigh-
                        bors declare the router down.  This  should  be
                        some  multiple  of  the  Hello  interval.  This
                        value must be the same for the  virtual  neigh-
                        bor."                                          
               ::= { mpOspfVirtIfEntry 9 }

        mpOspfVirtIfState OBJECT-TYPE
               SYNTAX   INTEGER    {
                    down (1),            -- these use the same encoding
                    pointToPoint (4)     -- as the ospfIfTable
                  }
               ACCESS   read-only   
               STATUS   mandatory
               DESCRIPTION 
                        "OSPF virtual interface states."
               ::= { mpOspfVirtIfEntry 10 }

        mpOspfVirtIfAuthType OBJECT-TYPE
               SYNTAX   INTEGER (0..255)
                    -- none (0),
                    -- simplePassword (1)
                    -- md5 (2)
                    -- reserved for specification by IANA (> 2)
               ACCESS   read-write   
               STATUS   mandatory
               DESCRIPTION 
                        "The authentication type specified for a virtu-
                        al  interface.  Additional authentication types
                        may be assigned locally."
               ::= { mpOspfVirtIfEntry 11 }

        mpOspfVirtIfAuthKeyId OBJECT-TYPE
               SYNTAX   INTEGER (0..255)
               ACCESS   read-write   
               STATUS   mandatory
               DESCRIPTION
                        "The Key ID to be used when an authentication 
                        type is MD5. The value from 1 to 255 are used 
                        for  key  ID.  'Get' is not allowed  for this 
                        object.  The  value  0  will  be  returned as 
                        meaningless value when Get-Request is received 
                        for this object."
               ::= { mpOspfVirtIfEntry 12 }

        mpOspfVirtIfAuthKey OBJECT-TYPE
               SYNTAX   OCTET STRING (SIZE(16))
               ACCESS   read-write   
               STATUS   mandatory
               DESCRIPTION
                        "If Authentication Type is simplePassword,  the
                        device  will left adjust and zero fill to 8 oc-
                        tets.                                          
                                                                       
                        If Authentication Type is md5,  the device will
                        left adjust and zero fill to 16 octets.        
                                                                       
                        Note that unauthenticated  interfaces  need  no
                        authentication key, and simple password authen-
                        tication cannot use a key of more  than  8  oc-
                        tets.                                          
                                                                       
                        When read, mpOspfVirtIfAuthKey always returns a
                        string of length zero."                        
               ::= { mpOspfVirtIfEntry 13 }

        mpOspfVirtIfEvents OBJECT-TYPE
               SYNTAX   Counter
               ACCESS   read-only   
               STATUS   mandatory
               DESCRIPTION 
                        "The number of state changes or error events on
                        this Virtual Link."
               ::= { mpOspfVirtIfEntry 14 }

        mpOspfVirtIfNeighbors OBJECT-TYPE
               SYNTAX   Gauge
               ACCESS   read-only   
               STATUS   mandatory
               DESCRIPTION
                        "The number of neighbors."
               ::= { mpOspfVirtIfEntry 15 }

        mpOspfVirtIfAdjacencies OBJECT-TYPE
               SYNTAX   Gauge
               ACCESS   read-only   
               STATUS   mandatory
               DESCRIPTION
                        "The number of adjacent neighbors."
               ::= { mpOspfVirtIfEntry 16 }

        mpOspfVirtIfFullyAdjacencies OBJECT-TYPE
               SYNTAX   Gauge
               ACCESS   read-only   
               STATUS   mandatory
               DESCRIPTION
                        "The number of fully adjacent neighbors."
               ::= { mpOspfVirtIfEntry 17 }

        mpOspfVirtIfLsUpdateFloods OBJECT-TYPE
               SYNTAX   Counter
               ACCESS   read-only   
               STATUS   mandatory
               DESCRIPTION
                        "The number of LS-update floods."
               ::= { mpOspfVirtIfEntry 18 }

        mpOspfVirtIfDelayedAckSends OBJECT-TYPE
               SYNTAX   Counter
               ACCESS   read-only   
               STATUS   mandatory
               DESCRIPTION
                        "The number of LS-Ack floods."
               ::= { mpOspfVirtIfEntry 19 }

        mpOspfVirtIfStatus OBJECT-TYPE
               SYNTAX   RowStatus
               ACCESS   read-write   
               STATUS   mandatory
               DESCRIPTION
                        "This variable displays the status of  the  en-
                        try.  Setting it to 'invalid' has the effect of
                        rendering it inoperative.  The internal  effect
                        (row removal) is implementation dependent."
               ::= { mpOspfVirtIfEntry 20 }

        mpOspfNbrTable OBJECT-TYPE
               SYNTAX   SEQUENCE OF MpOspfNbrEntry
               ACCESS   not-accessible
               STATUS   mandatory
               DESCRIPTION 
                        "A table of non-virtual neighbor information."
               ::= { mpOspf 11 }

        mpOspfNbrEntry OBJECT-TYPE
               SYNTAX   MpOspfNbrEntry
               ACCESS   not-accessible
               STATUS   mandatory
               DESCRIPTION 
                        "The information regarding a single neighbor."
               INDEX { mpOspfNbrProcessId, mpOspfNbrIfIndex, mpOspfNbrIpAddress }
               ::= { mpOspfNbrTable 1 }

        MpOspfNbrEntry ::=
               SEQUENCE {
                        mpOspfNbrProcessId
                            INTEGER,
                        mpOspfNbrIfIndex
                            INTEGER,
                        mpOspfNbrIpAddress
                            IpAddress,
                        mpOspfNbrRtrId
                            IpAddress,
                        mpOspfNbrOptions
                            INTEGER,
                        mpOspfNbrPriority
                            INTEGER,
                        mpOspfNbrCost
                            INTEGER,
                        mpOspfNbrState
                            INTEGER,
                        mpOspfNbrPermanence
                            INTEGER,
                        mpOspfNbrHelloSuppressed
                            TruthValue,
                        mpOspfNbrSelectedDr
                            IpAddress,
                        mpOspfNbrSelectedBdr
                            IpAddress,
                        mpOspfNbrLsSummaryListLen
                            Gauge,
                        mpOspfNbrLsRetransQLen
                            Gauge,
                        mpOspfNbrLsReqListLen
                            Gauge,
                        mpOspfNbrLsUpdateRetrans
                            Counter,
                        mpOspfNbrDirectAckSends
                            Counter,
                        mpOspfNbrDupUpdateReceives
                            Counter,
                        mpOspfNbrOldUpdateReceives
                            Counter,
                        mpOspfNbrDupAckReceives
                            Counter,
                        mpOspfNbrLosses
                            Counter,
                        mpOspfNbrAdjacencyResets
                            Counter,
                        mpOspfNbrStatus
                            RowStatus
                        }

        mpOspfNbrProcessId OBJECT-TYPE
               SYNTAX   INTEGER
               ACCESS   read-only   
               STATUS   mandatory
               DESCRIPTION
                        "The process ID of OSPF."
               ::= { mpOspfNbrEntry 1 }

        mpOspfNbrIfIndex OBJECT-TYPE
               SYNTAX   INTEGER
               ACCESS   read-only   
               STATUS   mandatory
               DESCRIPTION
                        "The ifIndex of interface related to the 
                        neighbior."
               ::= { mpOspfNbrEntry 2 }

        mpOspfNbrIpAddress OBJECT-TYPE
               SYNTAX   IpAddress
               ACCESS   read-only   
               STATUS   mandatory
               DESCRIPTION 
                        "The IP address this neighbor is using  in  its
                        IP  Source  Address.  Note that, on addressless
                        links, this will not be 0.0.0.0,  but  the  ad-
                        dress of another of the neighbor's interfaces."
               ::= { mpOspfNbrEntry 3 }

        mpOspfNbrRtrId OBJECT-TYPE
               SYNTAX   IpAddress
               ACCESS   read-only   
               STATUS   mandatory
               DESCRIPTION 
                        "A 32-bit integer (represented as a type  IpAd-
                        dress)  uniquely  identifying  the  neighboring
                        router in the Autonomous System."              
               ::= { mpOspfNbrEntry 4 }

        mpOspfNbrOptions OBJECT-TYPE
               SYNTAX   INTEGER
               ACCESS   read-only   
               STATUS   mandatory
               DESCRIPTION 
                        "A Bit Mask corresponding to the neighbor's op-
                        tions field.                                   
                                                                        
                        Bit 0, if set, indicates that the  system  will
                        operate  on  Type of Service metrics other than
                        TOS 0.  If zero, the neighbor will  ignore  all
                        metrics except the TOS 0 metric.               
                                                                        
                        Bit 1, if set, indicates  that  the  associated
                        area  accepts and operates on external informa-
                        tion; if zero, it is a stub area.              
                                                                        
                        Bit 2, if set, indicates that the system is ca-
                        pable  of routing IP Multicast datagrams; i.e.,
                        that it implements the Multicast Extensions  to
                        OSPF.                                          
                                                                        
                        Bit 3, if set, indicates  that  the  associated
                        area  is  an  NSSA.  These areas are capable of
                        carrying type 7 external advertisements,  which
                        are  translated into type 5 external advertise-
                        ments at NSSA borders."                        
               ::= { mpOspfNbrEntry 5 }

        mpOspfNbrPriority OBJECT-TYPE
               SYNTAX   INTEGER (0..255)
               ACCESS   read-write   
               STATUS   mandatory
               DESCRIPTION
                        "The priority of this neighbor in the designat-
                        ed router election algorithm.  The value 0 sig-
                        nifies that the neighbor is not eligible to be-
                        come  the  designated router on this particular
                        network."                                      
               ::= { mpOspfNbrEntry 6 }

        mpOspfNbrCost OBJECT-TYPE
               SYNTAX   INTEGER (1..65535)
               ACCESS   read-write   
               STATUS   mandatory
               DESCRIPTION
                        "The metric to the neighbor which is used for 
                        Point-to-MultiPoint network."
               ::= { mpOspfNbrEntry 7 }

        mpOspfNbrState OBJECT-TYPE
               SYNTAX   INTEGER    {
                    down (1),
                    attempt (2),
                    init (3),
                    twoWay (4),
                    exchangeStart (5),
                    exchange (6),
                    loading (7),
                    full (8)
                  }
               ACCESS   read-only   
               STATUS   mandatory
               DESCRIPTION 
                        "The State of the relationship with this Neighbor."
               ::= { mpOspfNbrEntry 8 }

        mpOspfNbrPermanence OBJECT-TYPE
               SYNTAX   INTEGER    {
                    dynamic (1),        -- learned through protocol
                    permanent (2)       -- configured address
                  }
               ACCESS   read-only   
               STATUS   mandatory
               DESCRIPTION 
                        "This variable displays the status of  the  en-
                        try.   'dynamic'  and  'permanent' refer to how
                        the neighbor became known."                    
               ::= { mpOspfNbrEntry 9 }

        mpOspfNbrHelloSuppressed OBJECT-TYPE
               SYNTAX   TruthValue
               ACCESS   read-only   
               STATUS   mandatory
               DESCRIPTION 
                        "Indicates whether Hellos are being  suppressed
                        to the neighbor."
               ::= { mpOspfNbrEntry 10 }

        mpOspfNbrSelectedDr OBJECT-TYPE
               SYNTAX   IpAddress
               ACCESS   read-only   
               STATUS   mandatory
               DESCRIPTION
                        "The designated router which neighbor selects."
               ::= { mpOspfNbrEntry 11 }

        mpOspfNbrSelectedBdr OBJECT-TYPE
               SYNTAX   IpAddress
               ACCESS   read-only   
               STATUS   mandatory
               DESCRIPTION
                        "The backup designated router which neighbor selects."
               ::= { mpOspfNbrEntry 12 }

        mpOspfNbrLsSummaryListLen OBJECT-TYPE
               SYNTAX   Gauge
               ACCESS   read-only   
               STATUS   mandatory
               DESCRIPTION
                        "The current length of the LS-summary queue."
               ::= { mpOspfNbrEntry 13 }

        mpOspfNbrLsRetransQLen OBJECT-TYPE
               SYNTAX   Gauge
               ACCESS   read-only   
               STATUS   mandatory
               DESCRIPTION 
                        "The  current  length  of  the   retransmission
                        queue."
               ::= { mpOspfNbrEntry 14 }

        mpOspfNbrLsReqListLen OBJECT-TYPE
               SYNTAX   Gauge
               ACCESS   read-only   
               STATUS   mandatory
               DESCRIPTION
                        "The current length of the LS-request queue."
               ::= { mpOspfNbrEntry 15 }

        mpOspfNbrLsUpdateRetrans OBJECT-TYPE
               SYNTAX   Counter
               ACCESS   read-only   
               STATUS   mandatory
               DESCRIPTION
                        "The number of times of LS-update re-transmission."
               ::= { mpOspfNbrEntry 16 }

        mpOspfNbrDirectAckSends OBJECT-TYPE
               SYNTAX   Counter
               ACCESS   read-only   
               STATUS   mandatory
               DESCRIPTION
                        "The number of times of LS-Ack Unicast transmission."
               ::= { mpOspfNbrEntry 17 }

        mpOspfNbrDupUpdateReceives OBJECT-TYPE
               SYNTAX   Counter
               ACCESS   read-only   
               STATUS   mandatory
               DESCRIPTION
                        "The number of times that overlapped LSA was 
                        received."
               ::= { mpOspfNbrEntry 18 }

        mpOspfNbrOldUpdateReceives OBJECT-TYPE
               SYNTAX   Counter
               ACCESS   read-only   
               STATUS   mandatory
               DESCRIPTION
                        "The number of times that old LSA was received."
               ::= { mpOspfNbrEntry 19 }

        mpOspfNbrDupAckReceives OBJECT-TYPE
               SYNTAX   Counter
               ACCESS   read-only   
               STATUS   mandatory
               DESCRIPTION
                        "The number of times that overlapped LS-Ack was 
                        received."
               ::= { mpOspfNbrEntry 20 }

        mpOspfNbrLosses OBJECT-TYPE
               SYNTAX   Counter
               ACCESS   read-only   
               STATUS   mandatory
               DESCRIPTION
                        "The number of times that Neighbor down was 
                        recognized."
               ::= { mpOspfNbrEntry 21 }

        mpOspfNbrAdjacencyResets OBJECT-TYPE
               SYNTAX   Counter
               ACCESS   read-only   
               STATUS   mandatory
               DESCRIPTION
                        "The number of times that Adjacency was reset."
               ::= { mpOspfNbrEntry 22 }

        mpOspfNbrStatus OBJECT-TYPE
               SYNTAX   RowStatus
               ACCESS   read-write   
               STATUS   mandatory
               DESCRIPTION 
                        "This variable displays the status of  the  en-
                        try.  Setting it to 'invalid' has the effect of
                        rendering it inoperative.  The internal  effect
                        (row removal) is implementation dependent."    
               ::= { mpOspfNbrEntry 23 }

        mpOspfVirtNbrTable OBJECT-TYPE
               SYNTAX   SEQUENCE OF MpOspfVirtNbrEntry
               ACCESS   not-accessible
               STATUS   mandatory
               DESCRIPTION 
                        "A table of virtual neighbor information."
               ::= { mpOspf 12 }

        mpOspfVirtNbrEntry OBJECT-TYPE
               SYNTAX   MpOspfVirtNbrEntry
               ACCESS   not-accessible
               STATUS   mandatory
               DESCRIPTION 
                        "Virtual neighbor information."
               INDEX { mpOspfVirtNbrProcessId, mpOspfVirtNbrIfId }
               ::= { mpOspfVirtNbrTable 1 }
                             
        MpOspfVirtNbrEntry ::=
               SEQUENCE {
                        mpOspfVirtNbrProcessId
                            INTEGER,
                        mpOspfVirtNbrIfId
                            INTEGER,
                        mpOspfVirtNbrAreaId
                            IpAddress,
                        mpOspfVirtNbrRtrId
                            IpAddress,
                        mpOspfVirtNbrIpAddress
                            IpAddress,
                        mpOspfVirtNbrOptions
                            INTEGER,
                        mpOspfVirtNbrState
                            INTEGER,
                        mpOspfVirtNbrHelloSuppressed
                            TruthValue,
                        mpOspfVirtNbrLsSummaryListLen
                            Gauge,
                        mpOspfVirtNbrLsRetransQLen
                            Gauge,
                        mpOspfVirtNbrLsReqListLen
                            Gauge,
                        mpOspfVirtNbrLsUpdateRetrans
                            Counter,
                        mpOspfVirtNbrDirectAckSends
                            Counter,
                        mpOspfVirtNbrDupUpdateReceives
                            Counter,
                        mpOspfVirtNbrOldUpdateReceives
                            Counter,
                        mpOspfVirtNbrDupAckReceives
                            Counter,
                        mpOspfVirtNbrLosses
                            Counter,
                        mpOspfVirtNbrAdjacencyResets
                            Counter
                        }

        mpOspfVirtNbrProcessId OBJECT-TYPE
               SYNTAX   INTEGER
               ACCESS   read-only   
               STATUS   mandatory
               DESCRIPTION
                        "The process ID of OSPF."
               ::= { mpOspfVirtNbrEntry 1 }

        mpOspfVirtNbrIfId OBJECT-TYPE
               SYNTAX   INTEGER
               ACCESS   read-only   
               STATUS   mandatory
               DESCRIPTION
                        "The ifIndex of Interface which transmits packet
                        to Neighbor."
               ::= { mpOspfVirtNbrEntry 2 }

        mpOspfVirtNbrAreaId OBJECT-TYPE
               SYNTAX   IpAddress
               ACCESS   read-only   
               STATUS   mandatory
               DESCRIPTION 
                        "The Transit Area Identifier."
               ::= { mpOspfVirtNbrEntry 3 }

        mpOspfVirtNbrRtrId OBJECT-TYPE
               SYNTAX   IpAddress
               ACCESS   read-only   
               STATUS   mandatory
               DESCRIPTION 
                        "A  32-bit  integer  uniquely  identifying  the
                        neighboring router in the Autonomous System."
               ::= { mpOspfVirtNbrEntry 4 }

        mpOspfVirtNbrIpAddress OBJECT-TYPE
               SYNTAX   IpAddress
               ACCESS   read-only   
               STATUS   mandatory
               DESCRIPTION 
                        "The IP address this Virtual  Neighbor  is  us-
                        ing."
               ::= { mpOspfVirtNbrEntry 5 }

        mpOspfVirtNbrOptions OBJECT-TYPE
               SYNTAX   INTEGER
               ACCESS   read-only   
               STATUS   mandatory
               DESCRIPTION 
                        "A Bit Mask corresponding to the neighbor's op-
                        tions field.                                   
                                                                       
                        Bit 1, if set, indicates that the  system  will
                        operate  on  Type of Service metrics other than
                        TOS 0.  If zero, the neighbor will  ignore  all
                        metrics except the TOS 0 metric.               
                                                                       
                        Bit 2, if set, indicates  that  the  system  is
                        Network  Multicast  capable; ie, that it imple-
                        ments OSPF Multicast Routing."                 
               ::= { mpOspfVirtNbrEntry 6 }

        mpOspfVirtNbrState OBJECT-TYPE
               SYNTAX   INTEGER    {
                    down (1),
                    attempt (2),
                    init (3),
                    twoWay (4),
                    exchangeStart (5),
                    exchange (6),
                    loading (7),
                    full (8)
                  }
               ACCESS   read-only   
               STATUS   mandatory
               DESCRIPTION 
                        "The state of the  Virtual  Neighbor  Relation-
                        ship."
               ::= { mpOspfVirtNbrEntry 7 }

        mpOspfVirtNbrHelloSuppressed OBJECT-TYPE
               SYNTAX   TruthValue
               ACCESS   read-only   
               STATUS   mandatory
               DESCRIPTION 
                        "Indicates whether Hellos are being  suppressed
                        to the neighbor"
               ::= { mpOspfVirtNbrEntry 8 }

        mpOspfVirtNbrLsSummaryListLen OBJECT-TYPE
               SYNTAX   Gauge
               ACCESS   read-only   
               STATUS   mandatory
               DESCRIPTION
                        "The current length of the LS-summary queue."
               ::= { mpOspfVirtNbrEntry 9 }

        mpOspfVirtNbrLsRetransQLen OBJECT-TYPE
               SYNTAX   Gauge
               ACCESS   read-only   
               STATUS   mandatory
               DESCRIPTION 
                        "The  current  length  of  the   retransmission
                        queue."
               ::= { mpOspfVirtNbrEntry 10 }

        mpOspfVirtNbrLsReqListLen OBJECT-TYPE
               SYNTAX   Gauge
               ACCESS   read-only   
               STATUS   mandatory
               DESCRIPTION
                        "The current length of the LS-request queue."
               ::= { mpOspfVirtNbrEntry 11 }

        mpOspfVirtNbrLsUpdateRetrans OBJECT-TYPE
               SYNTAX   Counter
               ACCESS   read-only   
               STATUS   mandatory
               DESCRIPTION
                        "The number of times of LS-update re-transmission."
               ::= { mpOspfVirtNbrEntry 12 }

        mpOspfVirtNbrDirectAckSends OBJECT-TYPE
               SYNTAX   Counter
               ACCESS   read-only   
               STATUS   mandatory
               DESCRIPTION
                        "The number of times of LS-Ack unicast transmission."
               ::= { mpOspfVirtNbrEntry 13 }

        mpOspfVirtNbrDupUpdateReceives OBJECT-TYPE
               SYNTAX   Counter
               ACCESS   read-only   
               STATUS   mandatory
               DESCRIPTION
                        "The number of times that overlapped LSA was 
                        received."
               ::= { mpOspfVirtNbrEntry 14 }

        mpOspfVirtNbrOldUpdateReceives OBJECT-TYPE
               SYNTAX   Counter
               ACCESS   read-only   
               STATUS   mandatory
               DESCRIPTION
                        "The number of times that old LSA was received."
               ::= { mpOspfVirtNbrEntry 15 }

        mpOspfVirtNbrDupAckReceives OBJECT-TYPE
               SYNTAX   Counter
               ACCESS   read-only   
               STATUS   mandatory
               DESCRIPTION
                        "The number of times that overlapped LS-Ack was 
                        received."
               ::= { mpOspfVirtNbrEntry 16 }

        mpOspfVirtNbrLosses OBJECT-TYPE
               SYNTAX   Counter
               ACCESS   read-only   
               STATUS   mandatory
               DESCRIPTION
                        "The number of times that Neighbor down was 
                        recognized."
               ::= { mpOspfVirtNbrEntry 17 }

        mpOspfVirtNbrAdjacencyResets OBJECT-TYPE
               SYNTAX   Counter
               ACCESS   read-only   
               STATUS   mandatory
               DESCRIPTION
                        "The number of times that Adjacency was reset."
               ::= { mpOspfVirtNbrEntry 18 }

        mpOspfExtLsdbTable OBJECT-TYPE
               SYNTAX   SEQUENCE OF MpOspfExtLsdbEntry
               ACCESS   not-accessible
               STATUS   mandatory
               DESCRIPTION 
                        "The OSPF Process's Links State Database."
               ::= { mpOspf 13 }

        mpOspfExtLsdbEntry OBJECT-TYPE
               SYNTAX   MpOspfExtLsdbEntry
               ACCESS   not-accessible
               STATUS   mandatory
               DESCRIPTION 
                        "A single Link State Advertisement."
               INDEX { mpOspfExtLsdbProcessId, mpOspfExtLsdbLsid,
                      mpOspfExtLsdbRouterId }
               ::= { mpOspfExtLsdbTable 1 }

        MpOspfExtLsdbEntry ::=
               SEQUENCE {
                        mpOspfExtLsdbProcessId
                            INTEGER,
                        mpOspfExtLsdbLsid
                            IpAddress,
                        mpOspfExtLsdbRouterId
                            IpAddress,
                        mpOspfExtLsdbType
                            INTEGER,
                        mpOspfExtLsdbSequence
                            INTEGER,
                        mpOspfExtLsdbAge
                            INTEGER,
                        mpOspfExtLsdbChecksum
                            INTEGER,
                        mpOspfExtLsdbAdvertisement
                            OCTET STRING
                        }

        mpOspfExtLsdbProcessId OBJECT-TYPE
               SYNTAX   INTEGER
               ACCESS   read-only
               STATUS   mandatory
               DESCRIPTION
                        "The process ID of OSPF."
               ::= { mpOspfExtLsdbEntry 1 }

        mpOspfExtLsdbLsid OBJECT-TYPE
               SYNTAX   IpAddress
               ACCESS   read-only
               STATUS   mandatory
               DESCRIPTION 
                        "The Link State ID is an LS Type Specific field
                        containing either a Router ID or an IP Address;
                        it identifies the piece of the  routing  domain
                        that is being described by the advertisement." 
               ::= { mpOspfExtLsdbEntry 2 }

        mpOspfExtLsdbRouterId OBJECT-TYPE
               SYNTAX   IpAddress
               ACCESS   read-only
               STATUS   mandatory
               DESCRIPTION 
                        "The 32 bit number that uniquely identifies the
                        originating router in the Autonomous System."  
               ::= { mpOspfExtLsdbEntry 3 }

        mpOspfExtLsdbType OBJECT-TYPE
               SYNTAX   INTEGER    {
                    asExternalLink (5)
                  }
               ACCESS   read-only
               STATUS   mandatory
               DESCRIPTION 
                       "The type  of  the  link  state  advertisement.
                       Each  link state type has a separate advertise-
                       ment format."                                  
               ::= { mpOspfExtLsdbEntry 4 }

        mpOspfExtLsdbSequence OBJECT-TYPE
               SYNTAX   INTEGER
               ACCESS   read-only
               STATUS   mandatory
               DESCRIPTION 
                        "The sequence number field is a  signed  32-bit
                        integer.   It  is used to detect old and dupli-
                        cate link state advertisements.  The  space  of
                        sequence  numbers  is  linearly  ordered.   The
                        larger the sequence number the more recent  the
                        advertisement."                                
               ::= { mpOspfExtLsdbEntry 5 }

        mpOspfExtLsdbAge OBJECT-TYPE
               SYNTAX   INTEGER
               ACCESS   read-only
               STATUS   mandatory
               DESCRIPTION 
                        "This field is the age of the link state adver-
                        tisement in seconds."                          
               ::= { mpOspfExtLsdbEntry 6 }

        mpOspfExtLsdbChecksum OBJECT-TYPE
               SYNTAX   INTEGER
               ACCESS   read-only
               STATUS   mandatory
               DESCRIPTION 
                        "This field is the  checksum  of  the  complete
                        contents  of  the  advertisement, excepting the
                        age field.  The age field is excepted  so  that
                        an   advertisement's  age  can  be  incremented
                        without updating the  checksum.   The  checksum
                        used  is  the same that is used for ISO connec-
                        tionless datagrams; it is commonly referred  to
                        as the Fletcher checksum."                     
                ::= { mpOspfExtLsdbEntry 7 }

        mpOspfExtLsdbAdvertisement OBJECT-TYPE
               SYNTAX   OCTET STRING (SIZE(36))
               ACCESS   read-only
               STATUS   mandatory
               DESCRIPTION 
                        "The entire Link State Advertisement, including
                        its header."                                   
                ::= { mpOspfExtLsdbEntry 8 }
-- @008 add end


-- *******************************************************************
-- Traps used by SanFran. This will be added as soon as new trap MIB 
-- objects comes out.
-- *******************************************************************
-- @001
-- specific-trapの値は、上位3桁（機能ブロック単位の値）に変更する。  11/19 YI
-- 下位4桁（TRAPコード値）をシステム仕様書通り修正する。
-- 4桁目を発生・復旧に振り分ける。0=発生  1=復旧
-- 11/30/98 Trap：temperatureFault ～ returnedToOldFiles まで、上書き

-- *******************************************************************
-- System Manager Traps used by ATM-SW. 
-- *******************************************************************
-- @002
-- VARIABLES変更

-- FAN障害発生
fanUnitFault  TRAP-TYPE
     ENTERPRISE           { mmn9110 }
     VARIABLES            { mpEventTimeStamp,
                            mpEventSeverity,
                            mpEventDescription,
                            mpSysFanType }
     DESCRIPTION
        "This trap is issued when a fan is failured."
    --  ファン障害発生を通知する。

     ::= 170001


-- FAN障害復旧
fanUnitFaultRecover  TRAP-TYPE
     ENTERPRISE           { mmn9110 }
     VARIABLES            { mpEventTimeStamp,
                            mpEventSeverity,
                            mpEventDescription,
                            mpSysFanType }
     DESCRIPTION
        "This trap is issured when a fan is recovered."
    --  ファン障害復旧を通知する。

     ::= 171001


-- 温度障害発生
temperatureFault  TRAP-TYPE
     ENTERPRISE           { mmn9110 }
     VARIABLES            { mpEventTimeStamp,
                            mpEventSeverity,
                            mpEventDescription,
                            mpSysTempType }
     DESCRIPTION
        "This trap is issured when a temperature become abnormal."
    -- 温度障害発生を通知する。

     ::= 170002


-- 温度障害復旧
temperatureFaultRecover  TRAP-TYPE
     ENTERPRISE           { mmn9110 }
     VARIABLES            { mpEventTimeStamp,
                            mpEventSeverity,
                            mpEventDescription,
                            mpSysTempType }
     DESCRIPTION
        "This trap is issured when a temperature is recovered."
    --  温度障害復旧を通知する。

     ::= 171002


-- 電圧障害発生
voltageFault  TRAP-TYPE
     ENTERPRISE           { mmn9110 }
     VARIABLES            { mpEventTimeStamp,
                            mpEventSeverity,
                            mpEventDescription,
                            mpSysVoltageType }
     DESCRIPTION
        "This trap is issued when a voltage is failured."
    -- 電圧障害発生を通知する。

     ::= 170003


-- 電圧障害復旧
voltageFaultRecover  TRAP-TYPE
     ENTERPRISE           { mmn9110 }
     VARIABLES            { mpEventTimeStamp,
                            mpEventSeverity,
                            mpEventDescription,
                            mpSysVoltageType }
     DESCRIPTION
        "This trap is issued when a voltage is recovered."
    -- 電圧障害復旧を通知する。

     ::= 171003


-- 外部装置障害
exEquipmentFault  TRAP-TYPE
     ENTERPRISE           { mmn9110 }
     VARIABLES            { mpEventTimeStamp,
                            mpEventSeverity,
                            mpEventDescription,
                            mpSysEqpType }
     DESCRIPTION
        "This trap is issued when a equipment is failured."
    -- 外部装置障害発生を通知する。

     ::= 170004


exEquipmentFaultRecover  TRAP-TYPE
     ENTERPRISE           { mmn9110 }
     VARIABLES            { mpEventTimeStamp,
                            mpEventSeverity,
                            mpEventDescription,
                            mpSysEqpType }
     DESCRIPTION
        "This trap is issued when a equipment is recovered."
    -- 外部装置障害復旧を通知する。

     ::= 171004


-- COM-COM間BUSパリティエラー発生
combusParityError  TRAP-TYPE
     ENTERPRISE           { mmn9110 }
     VARIABLES            { mpEventTimeStamp,
                            mpEventSeverity,
                            mpEventDescription }
     DESCRIPTION
        "This trap is issued when a COM-COM bus parity error is occurred."
    -- COM-COM間のバスパリティエラー発生を通知する。

     ::= 170005


-- COM-COM間BUSパリティエラー復旧
combusParityErrorRecover  TRAP-TYPE
     ENTERPRISE           { mmn9110 }
     VARIABLES            { mpEventTimeStamp,
                            mpEventSeverity,
                            mpEventDescription }
     DESCRIPTION
        "This trap is issued when a COM-COM bus parity error is recovered."
    -- COM-COM間のバスパリティエラー復旧を通知する。

     ::= 171005


-- COM-COM間BUSレディアラームエラー発生
combusReadyAlmError  TRAP-TYPE
     ENTERPRISE           { mmn9110 }
     VARIABLES            { mpEventTimeStamp,
                            mpEventSeverity,
                            mpEventDescription }
     DESCRIPTION
        "This trap is issued when a COM-COM bus ready alarm error is occurred."
    -- COM-COM間のバスレディアラームエラー発生を通知する。

     ::= 170006


-- COM-COM間BUSレディアラームエラー復旧
combusReadyAlmErrorRecover  TRAP-TYPE
     ENTERPRISE           { mmn9110 }
     VARIABLES            { mpEventTimeStamp,
                            mpEventSeverity,
                            mpEventDescription }
     DESCRIPTION
        "This trap is issued when a COM-COM bus ready alarm error is recovered."
    -- COM-COM間のバスレディアラームエラー復旧を通知する。

     ::= 171006


-- Stby COM-Bridge間PCI SERR発生
combrgPciSerrFault  TRAP-TYPE
     ENTERPRISE           { mmn9110 }
     VARIABLES            { mpEventTimeStamp,
                            mpEventSeverity,
                            mpEventDescription }
     DESCRIPTION
        "This trap is issued when a Stby COM-Bridge pci serr is occurred."
    -- スタンバイCOM-Bridge間のPCI Serr発生を通知する。

     ::= 170007


-- Stby COM-Bridge間PCI SERR復旧
combrgPciSerrFaultRecover  TRAP-TYPE
     ENTERPRISE           { mmn9110 }
     VARIABLES            { mpEventTimeStamp,
                            mpEventSeverity,
                            mpEventDescription }
     DESCRIPTION
        "This trap is issued when a Stby COM-Bridge pci serr is recoverd."
    -- スタンバイCOM-Bridge間のPCI Serr復旧を通知する。

     ::= 171007


-- Version値書込みNG @007
versionWriteNg  TRAP-TYPE
     ENTERPRISE           { mmn9110 }
     VARIABLES            { mpEventTimeStamp,
                            mpEventSeverity,
                            mpEventDescription }
     DESCRIPTION
        "This trap is issued when failured to write version at file."
    -- バージョンのファイルへの書込み失敗を通知する。

     ::= 170008


-- Version値書込み復旧 @007
versionWriteNgRecover  TRAP-TYPE
     ENTERPRISE           { mmn9110 }
     VARIABLES            { mpEventTimeStamp,
                            mpEventSeverity,
                            mpEventDescription }
     DESCRIPTION
        "This trap is issued when recover from failure status to write version at file."
    -- バージョンのファイルへの書込み失敗状態からの復旧を通知する。

     ::= 171008


-- *******************************************************************
-- CLI Traps used by ATM-SW. 
-- *******************************************************************
    supervisorLogin    TRAP-TYPE
    ENTERPRISE         mmn9110 
    VARIABLES            { mpEventTimeStamp,
                            mpEventSeverity,
                            mpEventDescription }
    DESCRIPTION        "Supervisor logs in the system."
    ::= 1280001

    supervisorExit     TRAP-TYPE
    ENTERPRISE         mmn9110
    VARIABLES            { mpEventTimeStamp,
                            mpEventSeverity,
                            mpEventDescription }
    DESCRIPTION        "Supervisor exits from the system."
    ::= 1281001

    supervisorLoginFailure TRAP-TYPE
    ENTERPRISE             mmn9110
    VARIABLES            { mpEventTimeStamp,
                            mpEventSeverity,
                            mpEventDescription }
    DESCRIPTION            "Supervisor login failure from the system."
    ::= 1280002

-- *******************************************************************
-- File Manager Traps used by ATM-SW. 
-- *******************************************************************
    returnedToOldFiles TRAP-TYPE
    ENTERPRISE         mmn9110 
    VARIABLES            { mpEventTimeStamp,
                            mpEventSeverity,
                            mpEventDescription }
    DESCRIPTION        "Returned to the previous system files."
    ::= 200001


END

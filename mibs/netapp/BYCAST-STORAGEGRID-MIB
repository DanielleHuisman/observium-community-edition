BYCAST-STORAGEGRID-MIB DEFINITIONS ::= BEGIN

IMPORTS
    enterprises, MODULE-IDENTITY
        FROM SNMPv2-SMI
    DisplayString
        FROM SNMPv2-TC
    OBJECT-TYPE
        FROM RFC-1212;

bycast MODULE-IDENTITY
    LAST-UPDATED    "200706071725Z"
    ORGANIZATION    "NetApp Inc."
    CONTACT-INFO    "Website: www.netapp.com"
    DESCRIPTION     "The MIB Module for the legacy Bycast entities."
    REVISION        "200706071725Z"
    DESCRIPTION     "Initial revision."
::= {enterprises 28669}

version1    OBJECT IDENTIFIER ::= {bycast 1}
common      OBJECT IDENTIFIER ::= {version1 0}
nmsmi       OBJECT IDENTIFIER ::= {common 1}
system      OBJECT IDENTIFIER ::= {nmsmi 1}

status  OBJECT-TYPE
    SYNTAX      INTEGER { unknown(1), adminDown(11), normal(21), notice(31), minor(41), major(51), critical(61) }
    MAX-ACCESS  read-only
    STATUS      current
    DESCRIPTION
            "The system status of a StorageGRID:
              unknown(1) - At least one service is in the Unknown state and requires immediate investigation.
              adminDown(11) - All the services have been deliberately shutdown for maintenance by a grid administrator.
              normal(21) - All services are working normally.
              notice(31) - An unusual condition that does not affect normal operation.
              minor(41) - An abnormal condition that could affect operation in the future; should be investigated to prevent escalation.
              major(51) - An abnormal condition that currently affects operation; requires prompt attention to prevent escalation.
              critical(61) - An abnormal condition that has stopped normal operation; should be addressed immediately."
    ::= {system 1}

label  OBJECT-TYPE
    SYNTAX      DisplayString
    MAX-ACCESS  read-only
    STATUS      current
    DESCRIPTION
            "The system label of the grid as reported by the NMS MI."
    ::= {system 2}

END

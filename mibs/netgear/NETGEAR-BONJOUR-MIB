NETGEAR-BONJOUR-MIB DEFINITIONS ::= BEGIN

-- Broadcom NETGEAR BONJOUR MIB
-- Copyright 2017 Broadcom.
-- This SNMP Management Information Specification
-- embodies Broadcom's confidential and proprietary
-- intellectual property.  Broadcom retains all title
-- and ownership in the Specification including any revisions.

-- This Specification is supplied "AS IS", Broadcom
-- makes no warranty, either expressed or implied,
-- as to the use, operation, condition, or performance of the
-- Specification.

IMPORTS
    MODULE-IDENTITY, OBJECT-TYPE        FROM SNMPv2-SMI
    ng7000managedswitch                            FROM NETGEAR-REF-MIB;

    fastPathBonjour MODULE-IDENTITY
       LAST-UPDATED "201706060000Z" -- 06 June 2017 12:00:00 GMT
       ORGANIZATION "Netgear Inc"
       CONTACT-INFO ""

        DESCRIPTION
          "The Netgear Private MIB for Bonjour"

        -- Revision history.
        REVISION
          "201706060000Z" -- 06 June 2017 12:00:00 GMT
        DESCRIPTION
          "Initial version."

    ::= { ng7000managedswitch 71 }

-- ***************************************************************************
--
-- The Bonjour Objects Group
-- Manage Bonjour settings.
--
-- ***************************************************************************
agentBonjourObjects  OBJECT IDENTIFIER ::= { fastPathBonjour 1 }

-- ***************************************************************************
--
-- The Bonjour Global Group
-- Manage Global Bonjour settings.
--
-- ***************************************************************************
agentBonjourGlobal  OBJECT IDENTIFIER ::= { agentBonjourObjects 1 }

-- ****************************************************************************
--
-- The Bonjour Admin Mode
--
-- ****************************************************************************
agentBonjourAdminMode OBJECT-TYPE
  SYNTAX     INTEGER {
                disable(0),
                enable(1)
                }
  MAX-ACCESS read-write
  STATUS     current
  DESCRIPTION
        "An indication of whether the Bonjour Protocol
        is currently running."
  DEFVAL     { enable }
  ::= { agentBonjourGlobal 1 }

END

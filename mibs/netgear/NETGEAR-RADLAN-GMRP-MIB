NETGEAR-RADLAN-GMRP-MIB DEFINITIONS ::= BEGIN

-- Title:                RADLAN ROS
--                       Private GMRP MIB
-- Version:              7.46
-- Date:                 15-Jan-2007

IMPORTS
    rnd                                                     FROM NETGEAR-RADLAN-MIB
    OBJECT-TYPE, MODULE-IDENTITY                            FROM SNMPv2-SMI
    TruthValue, TimeInterval                                FROM SNMPv2-TC
    EnabledStatus                                           FROM P-BRIDGE-MIB
    dot1dBasePort                                           FROM BRIDGE-MIB;


rlGmrp MODULE-IDENTITY
                LAST-UPDATED "200701020000Z"
                ORGANIZATION "Radlan - a MARVELL company.
                              Marvell Semiconductor, Inc."
                CONTACT-INFO
                      "www.marvell.com"
                DESCRIPTION
                      "This private MIB module defines GMRP private MIBs."
                REVISION "200701020000Z"
                DESCRIPTION
                      "Initial revision."
        ::= { rnd 75 }

rlGmrpSupported OBJECT-TYPE
    SYNTAX  TruthValue
    MAX-ACCESS  read-only
    STATUS  current
    DESCRIPTION
        "Is Gmrp supported in the device or not."
    ::= { rlGmrp 1 }

rlGmrpMibVersion OBJECT-TYPE
    SYNTAX  INTEGER
    MAX-ACCESS  read-only
    STATUS  current
    DESCRIPTION
        "MIB's version, the current version is 1."
    ::= { rlGmrp 2 }

rlPortGmrpTimersTable OBJECT-TYPE
    SYNTAX  SEQUENCE OF RlPortGmrpTimersEntry
    MAX-ACCESS  not-accessible
    STATUS  current
    DESCRIPTION
        "A table of Gmrp timer values for every bridge
         port.  This is indexed by dot1dBasePort."
    ::= { rlGmrp 3 }

rlPortGmrpTimersEntry OBJECT-TYPE
    SYNTAX  RlPortGmrpTimersEntry
    MAX-ACCESS  not-accessible
    STATUS  current
    DESCRIPTION
        "Gmrp timer values for a bridge port."
    INDEX   { dot1dBasePort }
    ::= { rlPortGmrpTimersTable 1 }

RlPortGmrpTimersEntry ::=
    SEQUENCE {
        rlPortGmrpJoinTime          TimeInterval,
        rlPortGmrpLeaveTime         TimeInterval,
        rlPortGmrpLeaveAllTime      TimeInterval,
        rlPortGmrpOverrideGarp      EnabledStatus
    }

rlPortGmrpJoinTime OBJECT-TYPE
    SYNTAX  TimeInterval
    MAX-ACCESS  read-write
    STATUS  current
    DESCRIPTION
        "The Gmrp Join time, in centiseconds."
    DEFVAL { 20 }
    ::= { rlPortGmrpTimersEntry 1 }

rlPortGmrpLeaveTime OBJECT-TYPE
    SYNTAX  TimeInterval
    MAX-ACCESS  read-write
    STATUS  current
    DESCRIPTION
        "The Gmrp Leave time, in centiseconds."
    DEFVAL { 60 }
    ::= { rlPortGmrpTimersEntry 2 }

rlPortGmrpLeaveAllTime OBJECT-TYPE
    SYNTAX  TimeInterval
    MAX-ACCESS  read-write
    STATUS  current
    DESCRIPTION
        "The Gmrp LeaveAll time, in centiseconds."
    DEFVAL { 1000 }
    ::= { rlPortGmrpTimersEntry 3 }

rlPortGmrpOverrideGarp OBJECT-TYPE
    SYNTAX  EnabledStatus
    MAX-ACCESS  read-write
    STATUS  current
    DESCRIPTION
        "If enabled{1}, Gmrp timer values for this port are
         determined by the values in this entry. Otherwise, they
         are determined by the values in dot1dPortGarpTable."
    DEFVAL { disabled }
    ::= { rlPortGmrpTimersEntry 4 }

rlGmrpVlanTable OBJECT-TYPE
    SYNTAX  SEQUENCE OF RlGmrpVlanEntry
    MAX-ACCESS  not-accessible
    STATUS  current
    DESCRIPTION
        "This table is to Enable/Disable Gmrp in the vlan."
    ::= { rlGmrp 4 }

rlGmrpVlanEntry OBJECT-TYPE
    SYNTAX  RlGmrpVlanEntry
    MAX-ACCESS  not-accessible
    STATUS  current
    DESCRIPTION
        "An entry in the rlGmrpVlanTable."
    INDEX  { rlGmrpVlanTag }
    ::= { rlGmrpVlanTable 1 }

RlGmrpVlanEntry ::= SEQUENCE {
    rlGmrpVlanTag                  INTEGER,
    rlGmrpVlanEnable               TruthValue
}

rlGmrpVlanTag OBJECT-TYPE
    SYNTAX  INTEGER
    MAX-ACCESS  read-only
    STATUS  current
    DESCRIPTION
        "The tag of the VLAN for which this entry contains information."
    ::= { rlGmrpVlanEntry 1 }

rlGmrpVlanEnable OBJECT-TYPE
    SYNTAX  TruthValue
    MAX-ACCESS  read-write
    STATUS  current
    DESCRIPTION
        "Enable/Disable Gmrp in the vlan."
    DEFVAL { false }
    ::= { rlGmrpVlanEntry 2 }

END

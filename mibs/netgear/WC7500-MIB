WC7500-MIB DEFINITIONS ::= BEGIN

--
-- Example MIB objects for agent module example implementations
--

IMPORTS
    MODULE-IDENTITY, OBJECT-TYPE, Integer32,
    NOTIFICATION-TYPE,IpAddress             FROM SNMPv2-SMI
    RowStatus, StorageType                  FROM SNMPv2-TC
    OBJECT-GROUP                            FROM SNMPv2-CONF                    
    DisplayString, MacAddress               FROM SNMPv2-TC;



-- ********************************************************************
-- *  MODULE IDENTITY
-- ********************************************************************

wc7500 MODULE-IDENTITY 
    LAST-UPDATED "2012251000Z"          -- 25 10, 2012 at 2:50 GMT
    ORGANIZATION 
        "NETGEAR Inc."
    CONTACT-INFO 
        "4500 Great America Parkway
        Santa Clara, California 95054
        Phone: (408) 907-8000
        Fax: (408) 907-8097
        Web Site: http://www.netgear.com"
    DESCRIPTION 
       "The MIB module for 802.11a/b/g/n Prosafe
        500AP Wireless Management System iso(1).
        org(3).dod(6).internet(1).private(4).
          enterprises(1).netgear(4526).productID(100).
          Wlancontroller(8).wc7500(6)"
    ::= { wlancontroller 6 }


-- The Enterprises Number
                -- 1.3.6.1.4.1.4526     
                netgear OBJECT IDENTIFIER ::= { enterprises 4526 }
        
                -- 1.3.6.1.4.1.4526.100
                productID  OBJECT IDENTIFIER ::= { netgear 100 }

                -- 1.3.6.1.4.1.4526.100.8
                wlancontroller OBJECT IDENTIFIER ::= { productID 8 }
      
wcNotifications               OBJECT IDENTIFIER ::= { wc7500 20 }
wcNotificationPrefix          OBJECT IDENTIFIER
                                  ::= { wcNotifications 0 }
wcNotificationObjects         OBJECT IDENTIFIER
                                  ::= { wcNotifications 3 }


wcSystemGeneralSettings       OBJECT IDENTIFIER ::= { wc7500 1 }
wcName OBJECT-TYPE
    SYNTAX      DisplayString
    MAX-ACCESS  read-write
    STATUS      current
    DESCRIPTION
        "WC7500 controller name."
    ::= { wcSystemGeneralSettings 1 }

wcCountry OBJECT-TYPE
	SYNTAX  INTEGER {
		albania(8),
		algeria(12),
		azerbaijan(31),
		argentina(32),
		asia(33),
		australia(36),
		austria(40),
		bahrain(48),
		armenia(51),
		belgium(56),
		bolivia(68),
		brazil(76),
		belize(84),
		brunei(96),
		bulgaria(100),
		belarus(112),
		canada(124),
		chile(152),
		china(156),
		taiwan(158),
		colombia(170),
		costaRica(188),
		croatia(191),
		cyprus(196),
		czechRepublic(203),
		denmark(208),
		dominicanRepublic(214),
		ecuador(218),
		elSalvador(222),
		estonia(233),
		europe(234),
		finland(246),
		france(250),
		georgia(268),
		germany(276),
		greece(300),
		guatemala(320),
		honduras(340),
		hongkong(344),
		hungary(348),
		iceland(352),
		india(356),
		indonesia(360),
		iran(364),
		ireland(372),
		israel(376),
		italy(380),
		japan(392),
		kazakhstan(398),
		jordan(400),
		northKorea(408),
		koreaRepublic(410),
		kuwait(414),
		lebanon(422),
		latvia(428),
		liechtenstein(438),
		lithuania(440),
		luxembourg(442),
		macau(446),
		malaysia(458),
		malta(470),
		mexico(484),
		monaco(492),
		marocco(504),
		oman(512),
		netherlands(528),
		newZealand(554),
		norway(578),
		pakistan(586),
		panama(591),
		peru(604),
		philippines(608),
		poland(616),
		portugal(620),
		puertoRico(630),
		qatar(634),
		romania(642),
		russia(643),
		saudiArabia(682),
		singapore(702),
		slovakRepublic(703),
		vietnam(704),
		slovenia(705),
		southAfrica(710),
		zimbabwe(716),
		spain(724),
		sweden(752),
		switzerland(756),
		syria(760),
		thailand(764),
		trinidadAndTobago(780),
		unitedArabEmirates(784),
		tunisia(788),
		turkey(792),
		ukraine(804),
		macedonia(807),
		egypt(818),
		unitedKingdom(826),
		unitedStates(840),
		uruguay(858),
		uzbekistan(860),
		venezuela(862),
		yemen(887)
		}
	MAX-ACCESS  read-write
	STATUS      current
	DESCRIPTION
		"WC7500 controllers country."
    DEFVAL { 840 }
    ::= { wcSystemGeneralSettings 2 }

wcLocation OBJECT-TYPE
    SYNTAX      DisplayString
    MAX-ACCESS  read-write
    STATUS      current
    DESCRIPTION
        "WC7500 controllers location."
    ::= { wcSystemGeneralSettings 3 }
wcState OBJECT-TYPE
    SYNTAX      INTEGER {
                     applied(1),
                     modified(2),
                     apply(3)
                 }
    MAX-ACCESS  read-write
    STATUS      current
    DESCRIPTION
        "State flag is used to apply the configuration.
         applied(1)  : configuration is fresh or applied already.
         modified(2) : some of the configuration field is modified but not yet applied.
         apply(3) : Use this value to apply modified configuration"
   ::= { wcSystemGeneralSettings 4 }

wcIpVlan       OBJECT IDENTIFIER ::= { wc7500 2 }
wcIpVlanIp OBJECT-TYPE
    SYNTAX      IpAddress
    MAX-ACCESS  read-write
    STATUS      current
    DESCRIPTION
        "IP address of controller"
    ::= { wcIpVlan 1 }

wcIpVlanSubnetMask OBJECT-TYPE
    SYNTAX      IpAddress
    MAX-ACCESS  read-write
    STATUS      current
    DESCRIPTION
        "Subnet mask for controller IP"
    ::= { wcIpVlan 2 }

wcIpVlanDefaultGateway OBJECT-TYPE
    SYNTAX      IpAddress
    MAX-ACCESS  read-write
    STATUS      current
    DESCRIPTION
        "Default Gateway servers IP address."
    ::= { wcIpVlan 3 }

wcIpVlanPrimaryDnsServer OBJECT-TYPE
    SYNTAX      IpAddress
    MAX-ACCESS  read-write
    STATUS      current
    DESCRIPTION
        "Primary DNS Server IP address"
    ::= { wcIpVlan 4 }
wcIpVlanSecondaryDnsServer OBJECT-TYPE
    SYNTAX      IpAddress
    MAX-ACCESS  read-write
    STATUS      current
    DESCRIPTION
        "Secondary DNS Server IP address"
    ::= { wcIpVlan 5 }

wcIpVlanWinsServer OBJECT-TYPE
    SYNTAX      DisplayString
    MAX-ACCESS  read-write
    STATUS      current
    DESCRIPTION
        "Wins Server IP address."
    ::= { wcIpVlan 6 }

wcIpVlanVlanEnable OBJECT-TYPE
    SYNTAX      INTEGER { 
                    disable(0),
                    enable(1) 
                }
    MAX-ACCESS  read-write
    STATUS      current
    DESCRIPTION
        "Enable-Disable Vlan.
         disable(0) : To disable Vlan
         enable(1) : To enable Vlan"
    ::= { wcIpVlan 7 }

wcIpVlanUntaggedVlan OBJECT-TYPE
    SYNTAX      Integer32
    MAX-ACCESS  read-write
    STATUS      current
    DESCRIPTION
        "WC7500 controller untagged vlan"
    ::= { wcIpVlan 8 }
wcIpVlanManagementVlan OBJECT-TYPE
    SYNTAX      Integer32
    MAX-ACCESS  read-write
    STATUS      current
    DESCRIPTION
        "WC7500 controller management vlan"
    ::= { wcIpVlan 9 }

wcIpVlanState OBJECT-TYPE
    SYNTAX      INTEGER {
                     applied(1),
                     modified(2),
                     apply(3)
                 }
    MAX-ACCESS  read-write
    STATUS      current
    DESCRIPTION
        "State flag is used to apply the configuration.
         applied(1)  : configuration is fresh or applied already.
         modified(2) : some of the configurations field are modified
                       but not yet applied.
         apply(3)    : Use this value to apply modified configuration"
    ::= { wcIpVlan 10 }

wcAccessPoint                 OBJECT IDENTIFIER ::= { wc7500 3 }
wcAccessPointTable OBJECT-TYPE
    SYNTAX      SEQUENCE OF WcAccessPointEntry
    MAX-ACCESS  not-accessible
    STATUS      current
    DESCRIPTION
        "List of access points managed by WC7500.
         MAC address is the key index for this table "
    ::= {  wcAccessPoint 1 }

WcAccessPointEntry ::= SEQUENCE {
        wcAccessPointMac             MacAddress,
        wcAccessPointIp              IpAddress,
        wcAccessPointSubnetMask      IpAddress,  
        wcAccessPointDefaultGateway  IpAddress,
        wcAccessPointVlanEnable      INTEGER,
        wcAccessPointUntaggedVlan    Integer32,
        wcAccessPointManagementVlan  Integer32,
        wcAccessPointName            DisplayString,
        wcAccessPointModel           DisplayString,
        wcAccessPointGroup           Integer32,
        wcAccessPointAntenna         Integer32,
        wcAccessPointBuilding        Integer32,
        wcAccessPointFloor           Integer32,
        wcAccessPointLocation        DisplayString,
        wcAccessPointLocX            Integer32,
        wcAccessPointLocY            Integer32,
        wcAccessPointState           DisplayString,
        wcAccessPointRowStatus       RowStatus
}

wcAccessPointEntry OBJECT-TYPE
    SYNTAX      WcAccessPointEntry
    MAX-ACCESS  not-accessible
    STATUS      current
    DESCRIPTION
        "A row describing configuration of one managed access point."
    INDEX   { wcAccessPointMac }
    ::= {wcAccessPointTable 1 }

wcAccessPointMac OBJECT-TYPE
    SYNTAX      MacAddress
    MAX-ACCESS  read-only
    STATUS      current
    DESCRIPTION
        "MAC address of Access Point" 
    ::= { wcAccessPointEntry 1 }

wcAccessPointIp  OBJECT-TYPE
    SYNTAX      IpAddress
    MAX-ACCESS  read-only
    STATUS      current
    DESCRIPTION
        "IP address of Access Point" 
    ::= { wcAccessPointEntry 2 }
wcAccessPointSubnetMask  OBJECT-TYPE
    SYNTAX      IpAddress
    MAX-ACCESS  read-only
    STATUS      current
    DESCRIPTION
        "IP subnet mask of Access Point" 
    ::= { wcAccessPointEntry 3 }
wcAccessPointDefaultGateway  OBJECT-TYPE
    SYNTAX      IpAddress
    MAX-ACCESS  read-only
    STATUS      current
    DESCRIPTION
        "Default gateway for Access Point." 
    ::= { wcAccessPointEntry 4 }
wcAccessPointVlanEnable  OBJECT-TYPE
    SYNTAX      INTEGER { 
                    disable(0),
                    enable(1) 
                }
    MAX-ACCESS  read-write
    STATUS      current
    DESCRIPTION
        "Enable-Disable Vlan.
         disable(0) : To disable Vlan
         enable(1) : To enable Vlan"
    ::= { wcAccessPointEntry 5 }
wcAccessPointUntaggedVlan  OBJECT-TYPE
    SYNTAX      Integer32
    MAX-ACCESS  read-write
    STATUS      current
    DESCRIPTION
        "Access Point Untagged Vlan." 
    ::= { wcAccessPointEntry 6 }
wcAccessPointManagementVlan  OBJECT-TYPE
    SYNTAX      Integer32
    MAX-ACCESS  read-write
    STATUS      current
    DESCRIPTION
        "Access Point Management Vlan" 
    ::= { wcAccessPointEntry 7 }

wcAccessPointName  OBJECT-TYPE
    SYNTAX    DisplayString 
    MAX-ACCESS  read-write
    STATUS      current
    DESCRIPTION
        "Access Point Name" 
    ::= { wcAccessPointEntry 8 }


wcAccessPointModel  OBJECT-TYPE
    SYNTAX      DisplayString
    MAX-ACCESS  read-only
    STATUS      current
    DESCRIPTION
        "Access Point Model" 
    ::= { wcAccessPointEntry 9 }
wcAccessPointGroup  OBJECT-TYPE
    SYNTAX      Integer32
    MAX-ACCESS  read-only
    STATUS      current
    DESCRIPTION
        "Access Point Group id" 
    ::= { wcAccessPointEntry 10 }
wcAccessPointAntenna  OBJECT-TYPE
    SYNTAX      Integer32
    MAX-ACCESS  read-only
    STATUS      current
    DESCRIPTION
        "Access Point Antenna" 
    ::= { wcAccessPointEntry 11 }
wcAccessPointBuilding  OBJECT-TYPE
    SYNTAX      Integer32
    MAX-ACCESS  read-write
    STATUS      current
    DESCRIPTION
        "Access Point building index." 
    ::= { wcAccessPointEntry 12 }
wcAccessPointFloor  OBJECT-TYPE
    SYNTAX      Integer32
    MAX-ACCESS  read-write
    STATUS      current
    DESCRIPTION
        "Access Point floor index" 
    ::= { wcAccessPointEntry 13 }
wcAccessPointLocation  OBJECT-TYPE
    SYNTAX      DisplayString
    MAX-ACCESS  read-write
    STATUS      current
    DESCRIPTION
        "Access Point location string" 
    ::= { wcAccessPointEntry 14 }
wcAccessPointLocX  OBJECT-TYPE
    SYNTAX      Integer32
    MAX-ACCESS  read-only
    STATUS      current
    DESCRIPTION
        "Access Point location x-axis (in meters)" 
    ::= { wcAccessPointEntry 15 }
wcAccessPointLocY  OBJECT-TYPE
    SYNTAX      Integer32
    MAX-ACCESS  read-only
    STATUS      current
    DESCRIPTION
        "Access Point location y-axis (in meters)" 
    ::= { wcAccessPointEntry 16 }
wcAccessPointState  OBJECT-TYPE
    SYNTAX      DisplayString
    MAX-ACCESS  read-only
    STATUS      current
    DESCRIPTION
        "Access Point Status" 
    ::= { wcAccessPointEntry 17 }

wcAccessPointRowStatus  OBJECT-TYPE
    SYNTAX      RowStatus
    MAX-ACCESS  read-write
    STATUS      current
    DESCRIPTION
        "Row Status is used to apply the access point configuration.
            active(1) - send rowstatus as active(1) to apply the configuration.
            notReady(3) - Indicates that some columns in the row are modified and not yet applied.
            notInService(2), createAndWait(5), createAndGo(4), destroy(6) - not valid for this table."
    ::= { wcAccessPointEntry 18 }


wcClients                     OBJECT IDENTIFIER ::= { wc7500 4 }

wcClientListTable OBJECT-TYPE
    SYNTAX      SEQUENCE OF WcClientListEntry
    MAX-ACCESS  not-accessible
    STATUS      current
    DESCRIPTION
        "List of all the clients connected to Access points managed by WC7500"
    ::= {  wcClients 1 }

WcClientListEntry ::= SEQUENCE {
    wcClientMac         MacAddress,
    wcClientIp          IpAddress,
    wcClientLocation    DisplayString,
    wcClientApName      DisplayString,
    wcClientApIp        IpAddress,
    wcClientApMac       MacAddress,
    wcClientBssid       DisplayString,
    wcClientSsid        DisplayString
}

wcClientListEntry OBJECT-TYPE
    SYNTAX      WcClientListEntry
    MAX-ACCESS  not-accessible
    STATUS      current
    DESCRIPTION
        "Each row give info about a client and access point to which it is connected."
    ::= { wcClientListTable 1 }

wcClientMac OBJECT-TYPE
    SYNTAX      MacAddress
    MAX-ACCESS  read-only
    STATUS      current
    DESCRIPTION
        "Mac address of the client." 
    ::= { wcClientListEntry 1 }

wcClientIp  OBJECT-TYPE
    SYNTAX      IpAddress
    MAX-ACCESS  read-only
    STATUS      current
    DESCRIPTION
        "IP address of the client." 
    ::= { wcClientListEntry 2 }


wcClientLocation  OBJECT-TYPE
    SYNTAX      DisplayString
    MAX-ACCESS  read-only
    STATUS      current
    DESCRIPTION
        "client location." 
    ::= { wcClientListEntry 3 }

wcClientApName     OBJECT-TYPE
    SYNTAX      DisplayString
    MAX-ACCESS  read-only
    STATUS      current
    DESCRIPTION
        "Name of Access Point to which cleint is connected." 
    ::= { wcClientListEntry 4 }

wcClientApIp     OBJECT-TYPE
    SYNTAX      IpAddress
    MAX-ACCESS  read-only
    STATUS      current
    DESCRIPTION
        "IP Address of Access Point to which cleint is connected."
    ::= { wcClientListEntry 5 }

wcClientApMac     OBJECT-TYPE
    SYNTAX      MacAddress
    MAX-ACCESS  read-only
    STATUS      current
    DESCRIPTION
        "MAC address of Access Point to which cleint is connected." 
    ::= { wcClientListEntry 6 }

wcClientBssid     OBJECT-TYPE
    SYNTAX      DisplayString
    MAX-ACCESS  read-only
    STATUS      current
    DESCRIPTION
        "Brodcast SSID of Access Point." 
    ::= { wcClientListEntry 7 }

wcClientSsid     OBJECT-TYPE
    SYNTAX      DisplayString
    MAX-ACCESS  read-only
    STATUS      current
    DESCRIPTION
        "SSID of Access Point." 
    ::= { wcClientListEntry 8 }

WcAccessPointDetailsEntry ::= SEQUENCE {
    wcAccessPointDetailsMac                                 MacAddress,
    wcAccessPointDetailsIp                                  IpAddress,
    wcAccessPointDetailsName                                DisplayString,
    wcAccessPointDetailsModel                               DisplayString,
    wcAccessPointDetailsGroup                               Integer32,
    wcAccessPointDetails24GHzChannel                        DisplayString,
    wcAccessPointDetails5GHzChannel                         DisplayString,
    wcAccessPointDetails24GHzOperatingChannel               DisplayString,
    wcAccessPointDetails5GHzOperatingChannel                DisplayString,
    wcAccessPointDetailsChannelMgmt                         Integer32,
    wcAccessPointDetails24GHzLoadBalanceMaxClients          Integer32,
    wcAccessPointDetails5GHzLoadBalanceMaxClients           Integer32,
    wcAccessPointDetails24GHzLoadBalanceSignalQuality       Integer32,
    wcAccessPointDetails5GHzLoadBalanceSignalQuality        Integer32
}


wcAccessPointDetailsTable OBJECT-TYPE
    SYNTAX      SEQUENCE OF WcAccessPointDetailsEntry
    MAX-ACCESS  not-accessible
    STATUS      current
    DESCRIPTION
        "This table provides detailed configuration of access point."
    ::= {  wcAccessPoint 2 }

wcAccessPointDetailsEntry OBJECT-TYPE
    SYNTAX      WcAccessPointDetailsEntry
    MAX-ACCESS  not-accessible
    STATUS      current
    DESCRIPTION
        "A row describing detailed configuration of one managed access point."
    INDEX   { wcAccessPointDetailsMac }
    ::= {wcAccessPointDetailsTable 1 }

wcAccessPointDetailsMac OBJECT-TYPE
    SYNTAX      MacAddress
    MAX-ACCESS  read-only
    STATUS      current
    DESCRIPTION
        "Access Point MAC address." 
    ::= { wcAccessPointDetailsEntry 1 }

wcAccessPointDetailsIp  OBJECT-TYPE
    SYNTAX      IpAddress
    MAX-ACCESS  read-only
    STATUS      current
    DESCRIPTION
        "Access Point IP address." 
    ::= { wcAccessPointDetailsEntry 2 }

wcAccessPointDetailsName  OBJECT-TYPE
    SYNTAX      DisplayString
    MAX-ACCESS  read-only
    STATUS      current
    DESCRIPTION
        "Access Point Name." 
    ::= { wcAccessPointDetailsEntry 3 }
    
wcAccessPointDetailsModel  OBJECT-TYPE
    SYNTAX      DisplayString
    MAX-ACCESS  read-only
    STATUS      current
    DESCRIPTION
        "Access Point model." 
    ::= { wcAccessPointDetailsEntry 4 }

wcAccessPointDetailsGroup  OBJECT-TYPE
    SYNTAX      Integer32
    MAX-ACCESS  read-only
    STATUS      current
    DESCRIPTION
        "Access Point group index." 
    ::= { wcAccessPointDetailsEntry 5 }

wcAccessPointDetails24GHzChannel  OBJECT-TYPE
    SYNTAX      DisplayString
    MAX-ACCESS  read-only
    STATUS      current
    DESCRIPTION
        "Access Point 2.4 GHz channel." 
    ::= { wcAccessPointDetailsEntry 6 }

wcAccessPointDetails5GHzChannel  OBJECT-TYPE
    SYNTAX      DisplayString
    MAX-ACCESS  read-only
    STATUS      current
    DESCRIPTION
        "Access Point 5 GHz channel." 
    ::= { wcAccessPointDetailsEntry 7 }

wcAccessPointDetails24GHzOperatingChannel  OBJECT-TYPE
    SYNTAX      DisplayString
    MAX-ACCESS  read-only
    STATUS      current
    DESCRIPTION
        "Access Point 2.4 GHz operating channel." 
    ::= { wcAccessPointDetailsEntry 8 }

wcAccessPointDetails5GHzOperatingChannel  OBJECT-TYPE
    SYNTAX      DisplayString
    MAX-ACCESS  read-only
    STATUS      current
    DESCRIPTION
        "Access Point 5 GHz channel." 
    ::= { wcAccessPointDetailsEntry 9 }

wcAccessPointDetailsChannelMgmt  OBJECT-TYPE
    SYNTAX      Integer32
    MAX-ACCESS  read-only
    STATUS      current
    DESCRIPTION
        "This field tells if auto channel allocation is on or not."
    ::= { wcAccessPointDetailsEntry 10 }

wcAccessPointDetails24GHzLoadBalanceMaxClients  OBJECT-TYPE
    SYNTAX      Integer32
    MAX-ACCESS  read-only
    STATUS      current
    DESCRIPTION
        "Max number of clients for 2.4 GHz load balancing." 
    ::= { wcAccessPointDetailsEntry 11 }

wcAccessPointDetails5GHzLoadBalanceMaxClients  OBJECT-TYPE
    SYNTAX      Integer32
    MAX-ACCESS  read-only
    STATUS      current
    DESCRIPTION
        "Max number of clients for 5 GHz load balancing." 
    ::= { wcAccessPointDetailsEntry 12 }

wcAccessPointDetails24GHzLoadBalanceSignalQuality  OBJECT-TYPE
    SYNTAX      Integer32
    MAX-ACCESS  read-only
    STATUS      current
    DESCRIPTION
        "Signal quality for 2.4 GHz load balancing." 
    ::= { wcAccessPointDetailsEntry 13 }

wcAccessPointDetails5GHzLoadBalanceSignalQuality  OBJECT-TYPE
    SYNTAX      Integer32
    MAX-ACCESS  read-only
    STATUS      current
    DESCRIPTION
        "Signal quality for 5 GHz load balancing." 
    ::= { wcAccessPointDetailsEntry 14 }

WcClientDetailsEntry ::= SEQUENCE {
    wcClientDetailsMac          MacAddress,
    wcClientDetailsAp           DisplayString,
    wcClientDetailsBssid        DisplayString,
    wcClientDetailsSsid         DisplayString,
    wcClientDetailsFrequency    DisplayString,
    wcClientDetailsAuth         DisplayString,
    wcClientDetailsCipher       DisplayString,
    wcClientDetailsAid          Integer32,
    wcClientDetailsRssi         Integer32,
    wcClientDetailsTxPower      Integer32,
    wcClientDetailsTxRate       DisplayString,
    wcClientDetailsTxBytes      Integer32,
    wcClientDetailsRxRate       DisplayString,
    wcClientDetailsRxBytes      Integer32,
    wcClientDetailsTxPackets    Integer32,
    wcClientDetailsRxPackets    Integer32,
    wcClientDetailsUptime       DisplayString
}

wcClientDetailsTable OBJECT-TYPE
    SYNTAX      SEQUENCE OF WcClientDetailsEntry
    MAX-ACCESS  not-accessible
    STATUS      current
    DESCRIPTION
        "Detailed information about the clients connected to Access Points managed by WC7500."
    ::= {  wcClients 2 }

wcClientDetailsEntry OBJECT-TYPE
    SYNTAX      WcClientDetailsEntry
    MAX-ACCESS  not-accessible
    STATUS      current
    DESCRIPTION
        "A row describing detailed information about each client."
--    INDEX   { wcClientListMac }
    ::= {wcClientDetailsTable 1 }

wcClientDetailsMac   OBJECT-TYPE
    SYNTAX      MacAddress
    MAX-ACCESS  read-only
    STATUS      current
    DESCRIPTION
        "MAC address of the client." 
    ::= { wcClientDetailsEntry 1 }

wcClientDetailsAp   OBJECT-TYPE
    SYNTAX      DisplayString
    MAX-ACCESS  read-only
    STATUS      current
    DESCRIPTION
        "Name of Access Point to which client is connected." 
    ::= { wcClientDetailsEntry 2 }

wcClientDetailsBssid   OBJECT-TYPE
    SYNTAX      DisplayString
    MAX-ACCESS  read-only
    STATUS      current
    DESCRIPTION
        "Bssid of the client." 
    ::= { wcClientDetailsEntry 3 }

wcClientDetailsSsid   OBJECT-TYPE
    SYNTAX      DisplayString
    MAX-ACCESS  read-only
    STATUS      current
    DESCRIPTION
        "SSID to which client is connected." 
    ::= { wcClientDetailsEntry 4 }

wcClientDetailsFrequency   OBJECT-TYPE
    SYNTAX      DisplayString
    MAX-ACCESS  read-only
    STATUS      current
    DESCRIPTION
        "Frequent band of client." 
    ::= { wcClientDetailsEntry 5 }

wcClientDetailsAuth   OBJECT-TYPE
    SYNTAX      DisplayString
    MAX-ACCESS  read-only
    STATUS      current
    DESCRIPTION
        "Authentication method." 
    ::= { wcClientDetailsEntry 6 }

wcClientDetailsCipher   OBJECT-TYPE
    SYNTAX      DisplayString
    MAX-ACCESS  read-only
    STATUS      current
    DESCRIPTION
        "Cleint cipher" 
    ::= { wcClientDetailsEntry 7 }

wcClientDetailsAid   OBJECT-TYPE
    SYNTAX      Integer32
    MAX-ACCESS  read-only
    STATUS      current
    DESCRIPTION
        "Client Aid" 
    ::= { wcClientDetailsEntry 8 }

wcClientDetailsRssi   OBJECT-TYPE
    SYNTAX      Integer32
    MAX-ACCESS  read-only
    STATUS      current
    DESCRIPTION
        "Clients RSSI"
    ::= { wcClientDetailsEntry 9 }

wcClientDetailsTxPower   OBJECT-TYPE
    SYNTAX      Integer32
    MAX-ACCESS  read-only
    STATUS      current
    DESCRIPTION
        "Client transmit power" 
    ::= { wcClientDetailsEntry 10 }

wcClientDetailsTxRate   OBJECT-TYPE
    SYNTAX      DisplayString
    MAX-ACCESS  read-only
    STATUS      current
    DESCRIPTION
        "Client transmited data rate." 
    ::= { wcClientDetailsEntry 11 }

wcClientDetailsTxBytes   OBJECT-TYPE
    SYNTAX      Integer32
    MAX-ACCESS  read-only
    STATUS      current
    DESCRIPTION
        "Client transmited number of bytes." 
    ::= { wcClientDetailsEntry 12 }

wcClientDetailsRxRate   OBJECT-TYPE
    SYNTAX      DisplayString
    MAX-ACCESS  read-only
    STATUS      current
    DESCRIPTION
        "Client received data rate." 
    ::= { wcClientDetailsEntry 13 }

wcClientDetailsRxBytes   OBJECT-TYPE
    SYNTAX      Integer32
    MAX-ACCESS  read-only
    STATUS      current
    DESCRIPTION
        "Client received number of bytes." 
    ::= { wcClientDetailsEntry 14 }

wcClientDetailsTxPackets   OBJECT-TYPE
    SYNTAX      Integer32
    MAX-ACCESS  read-only
    STATUS      current
    DESCRIPTION
        "Client transmitted number of bytes"
    ::= { wcClientDetailsEntry 15 }

wcClientDetailsRxPackets   OBJECT-TYPE
    SYNTAX      Integer32
    MAX-ACCESS  read-only
    STATUS      current
    DESCRIPTION
        "Client received number of packets" 
    ::= { wcClientDetailsEntry 16 }
    
wcClientDetailsUptime   OBJECT-TYPE
    SYNTAX      DisplayString
    MAX-ACCESS  read-only
    STATUS      current
    DESCRIPTION
        "Client Uptime."
    ::= { wcClientDetailsEntry 17 }


wcProfiles                 OBJECT IDENTIFIER ::= { wc7500 5 }

wcProfileGroupsTable OBJECT-TYPE
    SYNTAX      SEQUENCE OF WcProfileGroupsEntry
    MAX-ACCESS  not-accessible
    STATUS      current
    DESCRIPTION
        "List of profile groups."
    ::= {  wcProfiles 1 }

WcProfileGroupsEntry ::= SEQUENCE {
        wcProfileGroupGroupIdx      Integer32,
        wcProfileGroupName          DisplayString,
        wcProfileGroupBgProfiles    Integer32,
        wcProfileGroupAProfiles     Integer32,
        wcProfileGroupsRowStatus    RowStatus
}

wcProfileGroupsEntry OBJECT-TYPE
    SYNTAX      WcProfileGroupsEntry
    MAX-ACCESS  read-create
    STATUS      current
    DESCRIPTION
        "A row describing a profile-group."
    INDEX   { wcProfileGroupGroupIdx }
    ::= { wcProfileGroupsTable 1 }

wcProfileGroupGroupIdx   OBJECT-TYPE
    SYNTAX      Integer32
    MAX-ACCESS  not-accessible
    STATUS      current
    DESCRIPTION
        "Profile group index." 
    ::= { wcProfileGroupsEntry 1 }

wcProfileGroupName   OBJECT-TYPE
    SYNTAX      DisplayString
    MAX-ACCESS  read-only
    STATUS      current
    DESCRIPTION
        "Name of profile-group" 
    ::= { wcProfileGroupsEntry 2 }
wcProfileGroupBgProfiles   OBJECT-TYPE
    SYNTAX      Integer32
    MAX-ACCESS  read-only
    STATUS      current
    DESCRIPTION
        "Number of 802.11b/bg/ng profiles." 
    ::= { wcProfileGroupsEntry 3 }
wcProfileGroupAProfiles   OBJECT-TYPE
    SYNTAX      Integer32
    MAX-ACCESS  read-only
    STATUS      current
    DESCRIPTION
        "Number of 802.11a/na profiles." 
    ::= { wcProfileGroupsEntry 4 }
wcProfileGroupsRowStatus   OBJECT-TYPE
    SYNTAX      RowStatus
    MAX-ACCESS  read-create
    STATUS      current
    DESCRIPTION
           "active(1) - Default value of row status.
            createAndGo(4) - To create a new profile group.
                             group-index must be provided to add a new profile group.
                             Note: After creation of profile-group, group-index can be different from
                             what is provided.
            destroy(6) - To delete a profile group."
    ::= { wcProfileGroupsEntry 5 }
    

wcProfilesTable OBJECT-TYPE
    SYNTAX      SEQUENCE OF WcProfilesEntry
    MAX-ACCESS  not-accessible
    STATUS      current
    DESCRIPTION
        "List of all the profiles."
    ::= {  wcProfiles 2 }

WcProfilesEntry ::= SEQUENCE {
        wcProfilesGroupIdx                   Integer32,
        wcProfilesRadio                      DisplayString,
        wcProfilesName                       DisplayString,
        wcProfilesSsid                       DisplayString,
        wcProfilesBssid                      INTEGER,
        wcProfilesAuthentication             INTEGER,
        wcProfilesEncryption                 INTEGER,
        wcProfilesKeyIndex                   Integer32,
        wcProfilesKey1                       DisplayString,
        wcProfilesKey2                       DisplayString,
        wcProfilesKey3                       DisplayString,
        wcProfilesKey4                       DisplayString,
        wcProfilesClientSepration            INTEGER,
        wcProfilesVlan                       Integer32,
        wcProfilesAuthServerGroup            Integer32,
        wcProfilesAclGroup                   Integer32,
        wcProfilesCaptivePortal              INTEGER,
        wcProfilesWiFiMultimedia             INTEGER,
        wcProfilesWiFiMultimediaPowerSave    INTEGER,
        wcProfilesRowStatus                  RowStatus
}

wcProfilesEntry OBJECT-TYPE
    SYNTAX      WcProfilesEntry
    MAX-ACCESS  read-create
    STATUS      current
    DESCRIPTION
        "A row describing a profile. A profile is identified by
        its group-index, radio-mode, and profile-index."
    INDEX   { wcProfilesGroupIdx, wcProfilesRadioMode, wcProfilesIdx }
    ::= {wcProfilesTable 1 }

wcProfilesGroupIdx   OBJECT-TYPE
    SYNTAX      Integer32
    MAX-ACCESS  not-accessible
    STATUS      current
    DESCRIPTION
        "Profile group index to which this profile belongs. for basic group index=0." 
    ::= { wcProfilesEntry 1 }

wcProfilesRadioMode   OBJECT-TYPE
    SYNTAX      DisplayString
    MAX-ACCESS  not-accessible
    STATUS      current
    DESCRIPTION
        "Profile radio mode, one of 802.11b/bg/ng or 802.11a/na." 
    ::= { wcProfilesEntry 2 }

wcProfilesIdx   OBJECT-TYPE
    SYNTAX      Integer32
    MAX-ACCESS  not-accessible
    STATUS      current
    DESCRIPTION
        "Profile index which identifies a profile in a group." 
    ::= { wcProfilesEntry 3 }

wcProfilesName   OBJECT-TYPE
    SYNTAX      DisplayString
    MAX-ACCESS  read-write
    STATUS      current
    DESCRIPTION
        "Profile name."
    ::= { wcProfilesEntry 4 }
wcProfilesSsid   OBJECT-TYPE
    SYNTAX      DisplayString
    MAX-ACCESS  read-write
    STATUS      current
    DESCRIPTION
        "SSID of profile." 
    ::= { wcProfilesEntry 5 }
wcProfilesBssid   OBJECT-TYPE
    SYNTAX      INTEGER {
                     enable(1),
                     disable(0)
                 }
    MAX-ACCESS  read-write
    STATUS      current
    DESCRIPTION
        "Enable/Disable broadcast of SSID." 
    ::= { wcProfilesEntry 6 }
wcProfilesAuthentication   OBJECT-TYPE
    SYNTAX      INTEGER {
                     openSystem(1),
                     sharedKey(2),
                     legacy8021x(3),
                     wpaWithRadius(5),
                     wpa2WithRadius(7),
                     wpawpa2WithRadius(9),
                     wpapsk(6),
                     wpa2psk(8),
                     wpapskwpa2psk(10)
                }
    MAX-ACCESS  read-write
    STATUS      current
    DESCRIPTION
        "Authentication type." 
    ::= { wcProfilesEntry 7 }
wcProfilesEncryption   OBJECT-TYPE
    SYNTAX      INTEGER {
                    none(0),
                    i64BitWEP(1),
                    i128BitWEP(2),
                    i152BitWEP(3),
                    tkip(4),
                    tkipAES(5),
                    aes(7)
    }
    MAX-ACCESS  read-write
    STATUS      current
    DESCRIPTION
        "Encryption type." 
    ::= { wcProfilesEntry 8 }
wcProfilesKeyIndex   OBJECT-TYPE
    SYNTAX      Integer32
    MAX-ACCESS  read-write
    STATUS      current
    DESCRIPTION
        "Index of key used out of following four keys." 
    ::= { wcProfilesEntry 9 }
wcProfilesKey1   OBJECT-TYPE
    SYNTAX      DisplayString
    MAX-ACCESS  read-write
    STATUS      current
    DESCRIPTION
        "key 1" 
    ::= { wcProfilesEntry 10 }
wcProfilesKey2   OBJECT-TYPE
    SYNTAX      DisplayString
    MAX-ACCESS  read-write
    STATUS      current
    DESCRIPTION
        "key 2" 
    ::= { wcProfilesEntry 11 }
wcProfilesKey3   OBJECT-TYPE
    SYNTAX      DisplayString
    MAX-ACCESS  read-write
    STATUS      current
    DESCRIPTION
        "key 3" 
    ::= { wcProfilesEntry 12 }
wcProfilesKey4   OBJECT-TYPE
    SYNTAX      DisplayString
    MAX-ACCESS  read-write
    STATUS      current
    DESCRIPTION
        "key 4" 
    ::= { wcProfilesEntry 13 }
wcProfilesClientSepration   OBJECT-TYPE
    SYNTAX      INTEGER {
                     enable(1),
                     disable(0)
                 }
    MAX-ACCESS  read-write
    STATUS      current
    DESCRIPTION
        "Enable/Disable client seperation." 
    ::= { wcProfilesEntry 14 }
wcProfilesVlan   OBJECT-TYPE
    SYNTAX      Integer32
    MAX-ACCESS  read-write
    STATUS      current
    DESCRIPTION
        "Vlan"
    ::= { wcProfilesEntry 15 }
wcProfilesAuthServerGroup   OBJECT-TYPE
    SYNTAX      Integer32
    MAX-ACCESS  read-write
    STATUS      current
    DESCRIPTION
        "Index of Authetication server group used for this profile." 
    ::= { wcProfilesEntry 16 }
wcProfilesAclGroup   OBJECT-TYPE
    SYNTAX      Integer32
    MAX-ACCESS  read-write
    STATUS      current
    DESCRIPTION
        "Index of ACL group used for this profile." 
    ::= { wcProfilesEntry 17 }
wcProfilesCaptivePortal   OBJECT-TYPE
    SYNTAX      INTEGER {
                     enable(1),
                     disable(0)
                 }
    MAX-ACCESS  read-write
    STATUS      current
    DESCRIPTION
        "Enable/Disable captive portal." 
    ::= { wcProfilesEntry 18 }
wcProfilesWiFiMultimedia   OBJECT-TYPE
    SYNTAX      INTEGER {
                     enable(1),
                     disable(0)
                 }
    MAX-ACCESS  read-write
    STATUS      current
    DESCRIPTION
        "Enable/Disable WiFi Multimedia." 
    ::= { wcProfilesEntry 19 }
wcProfilesWiFiMultimediaPowerSave   OBJECT-TYPE
    SYNTAX      INTEGER {
                     enable(1),
                     disable(0)
                 }
    MAX-ACCESS  read-write
    STATUS      current
    DESCRIPTION
        "Enable/Disable WiFi Multimedia Powersave."
    ::= { wcProfilesEntry 20 }

wcProfilesRowStatus   OBJECT-TYPE
    SYNTAX      RowStatus
    MAX-ACCESS  read-create
    STATUS      current
    DESCRIPTION
        "Row Status is used to apply modified profile configuration, create and destroy a new profile.
            active(1) - Indicates there is no modifications pending for commit for this profile.
            notReady(3) - Indicates that some columns in the row are modified and not yet applied.
                          send active(1) to apply modified configurations.
            createAndGo(4) - To create a new profile. group-index, radio-mode and profile-index must be 
                             provided to add a new profile.
                             Note: After creation of a profile, profile-index can be different from
                             what is provided.
            destroy(6) - To delete a profile.
            notInService(2), createAndWait(5) - not valid for this table."
    ::= { wcProfilesEntry 21 }
END

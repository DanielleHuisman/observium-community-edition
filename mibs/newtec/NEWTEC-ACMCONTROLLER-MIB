NEWTEC-ACMCONTROLLER-MIB DEFINITIONS ::= BEGIN

IMPORTS
    Integer32,
    Unsigned32,
    MODULE-IDENTITY,
    OBJECT-IDENTITY,
    OBJECT-TYPE
        FROM SNMPv2-SMI

    MODULE-COMPLIANCE,
    OBJECT-GROUP
        FROM SNMPv2-CONF
    
    ntcFunction
        FROM NEWTEC-MAIN-MIB;


--
--  Module Identification
--

ntcAcmController   MODULE-IDENTITY
    LAST-UPDATED "201407150800Z"
    ORGANIZATION "Newtec Cy"
    CONTACT-INFO
        "Newtec Cy
         Postal: Newtec Cy
                 Laarstraat 5
                 B-9100 Sint-Niklaas
                 Belgium

                Tel: +32 3 780 65 00
                Fax: +32 3 780 65 49
                Web: www.newtec.be
                E-mail: techsupport@newtec.be"
    DESCRIPTION
        "Newtec modular ACMCONTROLLER MIB containing definitions for the ACM
        controller."

    REVISION  "201407150800Z"
    DESCRIPTION
        "DVB-S2X support"
    REVISION  "201402031200Z"
    DESCRIPTION
        "Added automatic-mode for MODCOD selection algorithm, added monitoring"
    REVISION  "201307050600Z"
    DESCRIPTION
        "Some monitoring parameters added"
    REVISION  "201301081200Z"
    DESCRIPTION
        "Initial release for NOP1760 R1.0"
    ::= { ntcFunction  2800 }
    

--
-- Top-Level Structure
--

-- ntcAcmController content

ntcAcmCtrlObjects                OBJECT-IDENTITY
    STATUS        current
    DESCRIPTION   "Container holding ntcAcmCtrlObjects definitions."
    ::= { ntcAcmController 1 }
    
ntcAcmCtrlConformance            OBJECT-IDENTITY
    STATUS        current
    DESCRIPTION   "Conformance requirements."
    ::= { ntcAcmController 2 }
    
-- ntcAcmCtrlObjects content

ntcAcmCtrlDvbS2                  OBJECT-IDENTITY
    STATUS        current
    DESCRIPTION   "Container holding ntcAcmCtrlDvbS2 definitions."
    ::= { ntcAcmCtrlObjects 4 }
    
ntcAcmCtrlS2Ext                  OBJECT-IDENTITY
    STATUS        current
    DESCRIPTION   "Container holding ntcAcmCtrlS2Ext definitions."
    ::= { ntcAcmCtrlObjects 5 }
    
ntcAcmCtrlMon                    OBJECT-IDENTITY
    STATUS        current
    DESCRIPTION   "Container holding ntcAcmCtrlMon definitions."
    ::= { ntcAcmCtrlObjects 6 }
    
-- ntcAcmCtrlConformance content

ntcAcmCtrlConfCompliance         OBJECT-IDENTITY
    STATUS        current
    DESCRIPTION   "Device compliance statements."
    ::= { ntcAcmCtrlConformance 1 }
    
ntcAcmCtrlConfGroup              OBJECT-IDENTITY
    STATUS        current
    DESCRIPTION   "Groups used by device compliance statements."
    ::= { ntcAcmCtrlConformance 2 }
    

--
-- Managed Objects
--

ntcAcmCtrlEnable                 OBJECT-TYPE
    SYNTAX      INTEGER { off(0), on(1), monitoringOnly(2) }
    MAX-ACCESS  read-write
    STATUS      current
    DESCRIPTION
        "Enable or disable the ACM controller"
    DEFVAL { off }
    ::= { ntcAcmCtrlObjects 1 }
    
ntcAcmCtrlMode                   OBJECT-TYPE
    SYNTAX      INTEGER { dvbs2(1), s2ext(3), dvbs2x(7) }
    MAX-ACCESS  read-write
    STATUS      current
    DESCRIPTION
        "The modulation standard defines the operating mode of the ACM controller
        - DVB-S2 : compatible with EN302307
        - S2 Extensions : Newtec proprietary modulation to improve DVB-S2"
    DEFVAL { dvbs2 }
    ::= { ntcAcmCtrlObjects 2 }
    
ntcAcmCtrlModCodAlgor            OBJECT-TYPE
    SYNTAX      INTEGER { headerEsno(1), linkMargin(2), linearCarrier(3), nonLinearCarrier(4), auto(5) }
    MAX-ACCESS  read-write
    STATUS      current
    DESCRIPTION
        "MODCOD selection algorithm. Different algorithms exist, optimized for
        different conditions (e.g. saturated transponder)."
    DEFVAL { auto }
    ::= { ntcAcmCtrlObjects 3 }
    
ntcAcmCtrlS2MinModCod            OBJECT-TYPE
    SYNTAX      INTEGER { unused(0), qpsk14(1), qpsk13(2), qpsk25(3), qpsk12(4), qpsk35(5), qpsk23(6), qpsk34(7), qpsk45(8), qpsk56(9), qpsk89(10), qpsk910(11), e8psk35(12), e8psk23(13), e8psk34(14), e8psk56(15), e8psk89(16), e8psk910(17), e16apsk23(18), e16apsk34(19), e16apsk45(20), e16apsk56(21), e16apsk89(22), e16apsk910(23), e32apsk34(24), e32apsk45(25), e32apsk56(26), e32apsk89(27), e32apsk910(28), qpsk1345(29), qpsk920(30), qpsk1120(31), e8apsk59l(32), e8apsk2645l(33), e8psk2336(34), e8psk2536(35), e8psk1318(36), e16apsk12l(37), e16apsk815l(38), e16apsk59l(39), e16apsk2645(40), e16apsk35(41), e16apsk35l(42), e16apsk2845(43), e16apsk2336(44), e16apsk23l(45), e16apsk2536(46), e16apsk1318(47), e16apsk79(48), e16apsk7790(49), e32apsk23l(50), e32apsk3245(51), e32apsk1115(52), e32apsk79(53), e64apsk3245l(54), e64apsk1115(55), e64apsk79(56), e64apsk45(57), e64apsk56(58), e128apsk34(59), e128apsk79(60), e256apsk2945l(61), e256apsk23l(62), e256apsk3145l(63), e256apsk3245(64), e256apsk1115l(65), e256apsk34(66), qpsk1145(67), qpsk415(68), qpsk1445(69), qpsk715(70), qpsk815(71), qpsk3245(72), e8psk715(73), e8psk815(74), e8psk2645(75), e8psk3245(76), e16apsk715(77), e16apsk815(78), e16apsk3245(79), e32apsk23(80) }
    MAX-ACCESS  read-write
    STATUS      current
    DESCRIPTION
        "The minimum MODCOD that is allowed to be selected in the ACM system"
    DEFVAL { unused }
    ::= { ntcAcmCtrlDvbS2 1 }
    
ntcAcmCtrlS2MaxModCod            OBJECT-TYPE
    SYNTAX      INTEGER { unused(0), qpsk14(1), qpsk13(2), qpsk25(3), qpsk12(4), qpsk35(5), qpsk23(6), qpsk34(7), qpsk45(8), qpsk56(9), qpsk89(10), qpsk910(11), e8psk35(12), e8psk23(13), e8psk34(14), e8psk56(15), e8psk89(16), e8psk910(17), e16apsk23(18), e16apsk34(19), e16apsk45(20), e16apsk56(21), e16apsk89(22), e16apsk910(23), e32apsk34(24), e32apsk45(25), e32apsk56(26), e32apsk89(27), e32apsk910(28), qpsk1345(29), qpsk920(30), qpsk1120(31), e8apsk59l(32), e8apsk2645l(33), e8psk2336(34), e8psk2536(35), e8psk1318(36), e16apsk12l(37), e16apsk815l(38), e16apsk59l(39), e16apsk2645(40), e16apsk35(41), e16apsk35l(42), e16apsk2845(43), e16apsk2336(44), e16apsk23l(45), e16apsk2536(46), e16apsk1318(47), e16apsk79(48), e16apsk7790(49), e32apsk23l(50), e32apsk3245(51), e32apsk1115(52), e32apsk79(53), e64apsk3245l(54), e64apsk1115(55), e64apsk79(56), e64apsk45(57), e64apsk56(58), e128apsk34(59), e128apsk79(60), e256apsk2945l(61), e256apsk23l(62), e256apsk3145l(63), e256apsk3245(64), e256apsk1115l(65), e256apsk34(66), qpsk1145(67), qpsk415(68), qpsk1445(69), qpsk715(70), qpsk815(71), qpsk3245(72), e8psk715(73), e8psk815(74), e8psk2645(75), e8psk3245(76), e16apsk715(77), e16apsk815(78), e16apsk3245(79), e32apsk23(80) }
    MAX-ACCESS  read-write
    STATUS      current
    DESCRIPTION
        "The maximum MODCOD that is allowed to be selected in the ACM system"
    DEFVAL { unused }
    ::= { ntcAcmCtrlDvbS2 2 }
    
ntcAcmCtrlS2ModCodsTable         OBJECT-TYPE
    SYNTAX      SEQUENCE OF NtcAcmCtrlS2ModCodsEntry
    MAX-ACCESS  not-accessible
    STATUS      current
    DESCRIPTION
        "A table containing the ntcAcmCtrlS2ModCods"
    ::= { ntcAcmCtrlDvbS2 3 }

ntcAcmCtrlS2ModCodsEntry         OBJECT-TYPE
    SYNTAX      NtcAcmCtrlS2ModCodsEntry
    MAX-ACCESS  not-accessible
    STATUS      current
    DESCRIPTION
        "A conceptual row of the ntcAcmCtrlS2ModCodsTable."
    INDEX   { ntcAcmCtrlS2ModCod  }
    ::= { ntcAcmCtrlS2ModCodsTable 1 }

NtcAcmCtrlS2ModCodsEntry         ::= SEQUENCE {
    ntcAcmCtrlS2ModCod          INTEGER,
    ntcAcmCtrlS2McEnable        INTEGER,
    ntcAcmCtrlS2McMinMargin     Integer32,
    ntcAcmCtrlS2McTargMargin    Integer32,
    ntcAcmCtrlS2McDistMargin    Integer32
    }
    
ntcAcmCtrlS2ModCod               OBJECT-TYPE
    SYNTAX      INTEGER { unused(0), qpsk14(1), qpsk13(2), qpsk25(3), qpsk12(4), qpsk35(5), qpsk23(6), qpsk34(7), qpsk45(8), qpsk56(9), qpsk89(10), qpsk910(11), e8psk35(12), e8psk23(13), e8psk34(14), e8psk56(15), e8psk89(16), e8psk910(17), e16apsk23(18), e16apsk34(19), e16apsk45(20), e16apsk56(21), e16apsk89(22), e16apsk910(23), e32apsk34(24), e32apsk45(25), e32apsk56(26), e32apsk89(27), e32apsk910(28), qpsk1345(29), qpsk920(30), qpsk1120(31), e8apsk59l(32), e8apsk2645l(33), e8psk2336(34), e8psk2536(35), e8psk1318(36), e16apsk12l(37), e16apsk815l(38), e16apsk59l(39), e16apsk2645(40), e16apsk35(41), e16apsk35l(42), e16apsk2845(43), e16apsk2336(44), e16apsk23l(45), e16apsk2536(46), e16apsk1318(47), e16apsk79(48), e16apsk7790(49), e32apsk23l(50), e32apsk3245(51), e32apsk1115(52), e32apsk79(53), e64apsk3245l(54), e64apsk1115(55), e64apsk79(56), e64apsk45(57), e64apsk56(58), e128apsk34(59), e128apsk79(60), e256apsk2945l(61), e256apsk23l(62), e256apsk3145l(63), e256apsk3245(64), e256apsk1115l(65), e256apsk34(66), qpsk1145(67), qpsk415(68), qpsk1445(69), qpsk715(70), qpsk815(71), qpsk3245(72), e8psk715(73), e8psk815(74), e8psk2645(75), e8psk3245(76), e16apsk715(77), e16apsk815(78), e16apsk3245(79), e32apsk23(80) }
    MAX-ACCESS  not-accessible
    STATUS      current
    DESCRIPTION
        "S2 Modulation & coding scheme (MODCOD)."
    ::= { ntcAcmCtrlS2ModCodsEntry 1 }
    
ntcAcmCtrlS2McEnable             OBJECT-TYPE
    SYNTAX      INTEGER { off(0), on(1) }
    MAX-ACCESS  read-write
    STATUS      current
    DESCRIPTION
        "Enable or disable a MODCOD for ACM purposes"
    DEFVAL { on }
    ::= { ntcAcmCtrlS2ModCodsEntry 2 }
    
ntcAcmCtrlS2McMinMargin          OBJECT-TYPE
    SYNTAX      Integer32 (-1000..3000)
    UNITS       "dB"
    MAX-ACCESS  read-write
    STATUS      current
    DESCRIPTION
        "The minimum margin required to stay on a given MODCOD"
    DEFVAL { 0 }
    ::= { ntcAcmCtrlS2ModCodsEntry 3 }
    
ntcAcmCtrlS2McTargMargin         OBJECT-TYPE
    SYNTAX      Integer32 (-1000..3000)
    UNITS       "dB"
    MAX-ACCESS  read-write
    STATUS      current
    DESCRIPTION
        "The minimum margin required to step up to this MODCOD"
    DEFVAL { 30 }
    ::= { ntcAcmCtrlS2ModCodsEntry 4 }
    
ntcAcmCtrlS2McDistMargin         OBJECT-TYPE
    SYNTAX      Integer32 (0..3000)
    UNITS       "dB"
    MAX-ACCESS  read-write
    STATUS      current
    DESCRIPTION
        "The required margin to cope with the distortion on this MODCOD"
    DEFVAL { 0 }
    ::= { ntcAcmCtrlS2ModCodsEntry 5 }
    
ntcAcmCtrlS2ExtMinModCod         OBJECT-TYPE
    SYNTAX      INTEGER { unused(0), qpsk45180(1), qpsk60180(2), qpsk72180(3), qpsk80180(4), qpsk90180(5), qpsk100180(6), qpsk108180(7), qpsk114180(8), qpsk120180(9), qpsk126180(10), qpsk135180(11), qpsk144180(12), qpsk150180(13), qpsk160180(14), qpsk162180(15), e8psk80180(16), e8psk90180(17), e8psk100180(18), e8psk108180(19), e8psk114180(20), e8psk120180(21), e8psk126180(22), e8psk135180(23), e8psk144180(24), e8psk150180(25), e16apsk80180(26), e16apsk90180(27), e16apsk100180(28), e16apsk108180(29), e16apsk114180(30), e16apsk120180(31), e16apsk126180(32), e16apsk135180(33), e16apsk144180(34), e16apsk150180(35), e16apsk160180(36), e16apsk162180(37), e32apsk100180(38), e32apsk108180(39), e32apsk114180(40), e32apsk120180(41), e32apsk126180(42), e32apsk135180(43), e32apsk144180(44), e32apsk150180(45), e32apsk160180(46), e32apsk162180(47), e64apsk90180(48), e64apsk100180(49), e64apsk108180(50), e64apsk114180(51), e64apsk120180(52), e64apsk126180(53), e64apsk135180(54), e64apsk144180(55), e64apsk150180(56), e64apsk160180(57), e64apsk162180(58), e8pskl80180(59), e8pskl90180(60), e8pskl100180(61), e8pskl108180(62), e8pskl114180(63), e8pskl120180(64), e16apskl80180(65), e16apskl90180(66), e16apskl100180(67), e16apskl108180(68), e16apskl114180(69), e16apskl120180(70), e16apskl126180(71), e16apskl135180(72), e16apskl144180(73), e16apskl150180(74), e16apskl160180(75), e16apskl162180(76), e64apskl90180(77), e64apskl100180(78), e64apskl108180(79), e64apskl114180(80), e64apskl120180(81), e64apskl126180(82), e64apskl135180(83), e64apskl144180(84), e64apskl150180(85), e64apskl160180(86), e64apskl162180(87) }
    MAX-ACCESS  read-write
    STATUS      current
    DESCRIPTION
        "The minimum MODCOD that is allowed to be selected in the ACM system"
    DEFVAL { unused }
    ::= { ntcAcmCtrlS2Ext 1 }
    
ntcAcmCtrlS2ExtMaxModCod         OBJECT-TYPE
    SYNTAX      INTEGER { unused(0), qpsk45180(1), qpsk60180(2), qpsk72180(3), qpsk80180(4), qpsk90180(5), qpsk100180(6), qpsk108180(7), qpsk114180(8), qpsk120180(9), qpsk126180(10), qpsk135180(11), qpsk144180(12), qpsk150180(13), qpsk160180(14), qpsk162180(15), e8psk80180(16), e8psk90180(17), e8psk100180(18), e8psk108180(19), e8psk114180(20), e8psk120180(21), e8psk126180(22), e8psk135180(23), e8psk144180(24), e8psk150180(25), e16apsk80180(26), e16apsk90180(27), e16apsk100180(28), e16apsk108180(29), e16apsk114180(30), e16apsk120180(31), e16apsk126180(32), e16apsk135180(33), e16apsk144180(34), e16apsk150180(35), e16apsk160180(36), e16apsk162180(37), e32apsk100180(38), e32apsk108180(39), e32apsk114180(40), e32apsk120180(41), e32apsk126180(42), e32apsk135180(43), e32apsk144180(44), e32apsk150180(45), e32apsk160180(46), e32apsk162180(47), e64apsk90180(48), e64apsk100180(49), e64apsk108180(50), e64apsk114180(51), e64apsk120180(52), e64apsk126180(53), e64apsk135180(54), e64apsk144180(55), e64apsk150180(56), e64apsk160180(57), e64apsk162180(58), e8pskl80180(59), e8pskl90180(60), e8pskl100180(61), e8pskl108180(62), e8pskl114180(63), e8pskl120180(64), e16apskl80180(65), e16apskl90180(66), e16apskl100180(67), e16apskl108180(68), e16apskl114180(69), e16apskl120180(70), e16apskl126180(71), e16apskl135180(72), e16apskl144180(73), e16apskl150180(74), e16apskl160180(75), e16apskl162180(76), e64apskl90180(77), e64apskl100180(78), e64apskl108180(79), e64apskl114180(80), e64apskl120180(81), e64apskl126180(82), e64apskl135180(83), e64apskl144180(84), e64apskl150180(85), e64apskl160180(86), e64apskl162180(87) }
    MAX-ACCESS  read-write
    STATUS      current
    DESCRIPTION
        "The maximum MODCOD that is allowed to be selected in the ACM system"
    DEFVAL { unused }
    ::= { ntcAcmCtrlS2Ext 2 }
    
ntcAcmCtrlS2ExtModCodsTable      OBJECT-TYPE
    SYNTAX      SEQUENCE OF NtcAcmCtrlS2ExtModCodsEntry
    MAX-ACCESS  not-accessible
    STATUS      current
    DESCRIPTION
        "A table containing the ntcAcmCtrlS2ExtModCods"
    ::= { ntcAcmCtrlS2Ext 3 }

ntcAcmCtrlS2ExtModCodsEntry      OBJECT-TYPE
    SYNTAX      NtcAcmCtrlS2ExtModCodsEntry
    MAX-ACCESS  not-accessible
    STATUS      current
    DESCRIPTION
        "A conceptual row of the ntcAcmCtrlS2ExtModCodsTable."
    INDEX   { ntcAcmCtrlS2ExtModCod  }
    ::= { ntcAcmCtrlS2ExtModCodsTable 1 }

NtcAcmCtrlS2ExtModCodsEntry      ::= SEQUENCE {
    ntcAcmCtrlS2ExtModCod          INTEGER,
    ntcAcmCtrlS2ExtMcEnable        INTEGER,
    ntcAcmCtrlS2ExtMcMinMargin     Integer32,
    ntcAcmCtrlS2ExtMcTargMargin    Integer32,
    ntcAcmCtrlS2ExtMcDistMargin    Integer32
    }
    
ntcAcmCtrlS2ExtModCod            OBJECT-TYPE
    SYNTAX      INTEGER { unused(0), qpsk45180(1), qpsk60180(2), qpsk72180(3), qpsk80180(4), qpsk90180(5), qpsk100180(6), qpsk108180(7), qpsk114180(8), qpsk120180(9), qpsk126180(10), qpsk135180(11), qpsk144180(12), qpsk150180(13), qpsk160180(14), qpsk162180(15), e8psk80180(16), e8psk90180(17), e8psk100180(18), e8psk108180(19), e8psk114180(20), e8psk120180(21), e8psk126180(22), e8psk135180(23), e8psk144180(24), e8psk150180(25), e16apsk80180(26), e16apsk90180(27), e16apsk100180(28), e16apsk108180(29), e16apsk114180(30), e16apsk120180(31), e16apsk126180(32), e16apsk135180(33), e16apsk144180(34), e16apsk150180(35), e16apsk160180(36), e16apsk162180(37), e32apsk100180(38), e32apsk108180(39), e32apsk114180(40), e32apsk120180(41), e32apsk126180(42), e32apsk135180(43), e32apsk144180(44), e32apsk150180(45), e32apsk160180(46), e32apsk162180(47), e64apsk90180(48), e64apsk100180(49), e64apsk108180(50), e64apsk114180(51), e64apsk120180(52), e64apsk126180(53), e64apsk135180(54), e64apsk144180(55), e64apsk150180(56), e64apsk160180(57), e64apsk162180(58), e8pskl80180(59), e8pskl90180(60), e8pskl100180(61), e8pskl108180(62), e8pskl114180(63), e8pskl120180(64), e16apskl80180(65), e16apskl90180(66), e16apskl100180(67), e16apskl108180(68), e16apskl114180(69), e16apskl120180(70), e16apskl126180(71), e16apskl135180(72), e16apskl144180(73), e16apskl150180(74), e16apskl160180(75), e16apskl162180(76), e64apskl90180(77), e64apskl100180(78), e64apskl108180(79), e64apskl114180(80), e64apskl120180(81), e64apskl126180(82), e64apskl135180(83), e64apskl144180(84), e64apskl150180(85), e64apskl160180(86), e64apskl162180(87) }
    MAX-ACCESS  not-accessible
    STATUS      current
    DESCRIPTION
        "S2 Extensions Modulation & coding scheme (MODCOD)"
    ::= { ntcAcmCtrlS2ExtModCodsEntry 1 }
    
ntcAcmCtrlS2ExtMcEnable          OBJECT-TYPE
    SYNTAX      INTEGER { off(0), on(1) }
    MAX-ACCESS  read-write
    STATUS      current
    DESCRIPTION
        "Enable or disable a MODCOD for ACM purposes"
    DEFVAL { on }
    ::= { ntcAcmCtrlS2ExtModCodsEntry 2 }
    
ntcAcmCtrlS2ExtMcMinMargin       OBJECT-TYPE
    SYNTAX      Integer32 (-1000..3000)
    UNITS       "dB"
    MAX-ACCESS  read-write
    STATUS      current
    DESCRIPTION
        "The minimum margin required to stay on a given MODCOD"
    DEFVAL { 0 }
    ::= { ntcAcmCtrlS2ExtModCodsEntry 3 }
    
ntcAcmCtrlS2ExtMcTargMargin      OBJECT-TYPE
    SYNTAX      Integer32 (-1000..3000)
    UNITS       "dB"
    MAX-ACCESS  read-write
    STATUS      current
    DESCRIPTION
        "The minimum margin required to step up to this MODCOD"
    DEFVAL { 30 }
    ::= { ntcAcmCtrlS2ExtModCodsEntry 4 }
    
ntcAcmCtrlS2ExtMcDistMargin      OBJECT-TYPE
    SYNTAX      Integer32 (0..3000)
    UNITS       "dB"
    MAX-ACCESS  read-write
    STATUS      current
    DESCRIPTION
        "The required margin to cope with the distortion on this MODCOD"
    DEFVAL { 0 }
    ::= { ntcAcmCtrlS2ExtModCodsEntry 5 }
    
ntcAcmCtrlMonConfMsgCounter      OBJECT-TYPE
    SYNTAX      Unsigned32
    MAX-ACCESS  read-only
    STATUS      current
    DESCRIPTION
        "The number of forward configuration messages transmitted"
    ::= { ntcAcmCtrlMon 1 }
    
ntcAcmCtrlFbAcceptedCounter      OBJECT-TYPE
    SYNTAX      Unsigned32
    MAX-ACCESS  read-only
    STATUS      current
    DESCRIPTION
        "The number of accepted feedback messages"
    ::= { ntcAcmCtrlMon 2 }
    
ntcAcmCtrlFbDiscardedCounter     OBJECT-TYPE
    SYNTAX      Unsigned32
    MAX-ACCESS  read-only
    STATUS      current
    DESCRIPTION
        "The number of discarded feedback messages"
    ::= { ntcAcmCtrlMon 3 }
    
ntcAcmCtrlMonCounterReset        OBJECT-TYPE
    SYNTAX      INTEGER { counting(0), reset(1) }
    MAX-ACCESS  read-write
    STATUS      current
    DESCRIPTION
        "Reset the monitoring counters and event log."
    DEFVAL { counting }
    ::= { ntcAcmCtrlMon 4 }
    
ntcAcmCtrlModcodTuning           OBJECT-TYPE
    SYNTAX      INTEGER { auto(1), manual(2) }
    MAX-ACCESS  read-write
    STATUS      current
    DESCRIPTION
        "Select modcod tuning table configuration."
    DEFVAL { auto }
    ::= { ntcAcmCtrlObjects 7 }
    
ntcAcmCtrlMinMargin              OBJECT-TYPE
    SYNTAX      Integer32 (-1000..3000)
    UNITS       "dB"
    MAX-ACCESS  read-write
    STATUS      current
    DESCRIPTION
        "The minimum margin required to stay on a given MODCOD"
    DEFVAL { 0 }
    ::= { ntcAcmCtrlObjects 8 }
    
ntcAcmCtrlTargetMargin           OBJECT-TYPE
    SYNTAX      Integer32 (-1000..3000)
    UNITS       "dB"
    MAX-ACCESS  read-write
    STATUS      current
    DESCRIPTION
        "The minimum margin required to step up to this MODCOD"
    DEFVAL { 30 }
    ::= { ntcAcmCtrlObjects 9 }
    

--
--  Module Conformance
--

ntcAcmCtrlConfGrpV1Standard      OBJECT-GROUP
    OBJECTS    {
                   ntcAcmCtrlEnable,
                   ntcAcmCtrlMode,
                   ntcAcmCtrlModCodAlgor,
                   ntcAcmCtrlS2MinModCod,
                   ntcAcmCtrlS2MaxModCod,
                   ntcAcmCtrlS2McEnable,
                   ntcAcmCtrlS2McMinMargin,
                   ntcAcmCtrlS2McTargMargin,
                   ntcAcmCtrlS2McDistMargin,
                   ntcAcmCtrlS2ExtMinModCod,
                   ntcAcmCtrlS2ExtMaxModCod,
                   ntcAcmCtrlS2ExtMcEnable,
                   ntcAcmCtrlS2ExtMcMinMargin,
                   ntcAcmCtrlS2ExtMcTargMargin,
                   ntcAcmCtrlS2ExtMcDistMargin,
                   ntcAcmCtrlMonConfMsgCounter,
                   ntcAcmCtrlFbAcceptedCounter,
                   ntcAcmCtrlFbDiscardedCounter,
                   ntcAcmCtrlMonCounterReset,
                   ntcAcmCtrlModcodTuning,
                   ntcAcmCtrlMinMargin,
                   ntcAcmCtrlTargetMargin
               }
    STATUS      current
    DESCRIPTION
        "Managed objects that constitute version 1 of a system device with standard capabilities."
    ::= { ntcAcmCtrlConfGroup 1}
    
ntcAcmCtrlConfCompV1Standard     MODULE-COMPLIANCE
    STATUS      current
    DESCRIPTION
        "Compliance statement for Newtec device MIB implementations."
    MODULE  -- this module
    MANDATORY-GROUPS
                  {
                      ntcAcmCtrlConfGrpV1Standard
                  }
    ::= { ntcAcmCtrlConfCompliance  1 }
    

END

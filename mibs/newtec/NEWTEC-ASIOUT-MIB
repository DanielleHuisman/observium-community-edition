NEWTEC-ASIOUT-MIB DEFINITIONS ::= BEGIN

IMPORTS
    Unsigned32,
    MODULE-IDENTITY,
    OBJECT-IDENTITY,
    OBJECT-TYPE
        FROM SNMPv2-SMI

    MODULE-COMPLIANCE,
    OBJECT-GROUP
        FROM SNMPv2-CONF
    
    NtcAlarmState,
    NtcEnable,
    NtcPid
        FROM NEWTEC-TC-MIB

    ntcFunction
        FROM NEWTEC-MAIN-MIB;


--
--  Module Identification
--

ntcAsiOut   MODULE-IDENTITY
    LAST-UPDATED "201409090900Z"
    ORGANIZATION "Newtec Cy"
    CONTACT-INFO
        "Newtec Cy
         Postal: Newtec Cy
                 Laarstraat 5
                 B-9100 Sint-Niklaas
                 Belgium

                Tel: +32 3 780 65 00
                Fax: +32 3 780 65 49
                Web: www.newtec.be
                E-mail: techsupport@newtec.be"
    DESCRIPTION
        "Newtec modular ASI output MIB containing definitions for ASI output
        functionality."

    REVISION  "201409090900Z"
    DESCRIPTION
        "ntcAsiOutInputSelection enumeration extended"
    REVISION  "201303271000Z"
    DESCRIPTION
        "Release for M6100 R1.3"
    REVISION  "201206281200Z"
    DESCRIPTION
        "Release for M6100 R1.2"
    ::= { ntcFunction  900 }
    

--
-- Top-Level Structure
--

-- ntcAsiOut content

ntcAsiOutObjects                 OBJECT-IDENTITY
    STATUS        current
    DESCRIPTION   "Container holding ntcAsiOutObjects definitions."
    ::= { ntcAsiOut 1 }
    
ntcAsiOutConformance             OBJECT-IDENTITY
    STATUS        current
    DESCRIPTION   "Conformance requirements."
    ::= { ntcAsiOut 2 }
    
-- ntcAsiOutObjects content

ntcAsiOutPrbsGenerator           OBJECT-IDENTITY
    STATUS        current
    DESCRIPTION   "Container holding ntcAsiOutPrbsGenerator definitions."
    ::= { ntcAsiOutObjects 4 }
    
ntcAsiOutNcrGenerator            OBJECT-IDENTITY
    STATUS        current
    DESCRIPTION   "Container holding ntcAsiOutNcrGenerator definitions."
    ::= { ntcAsiOutObjects 5 }
    
ntcAsiOutAlarm                   OBJECT-IDENTITY
    STATUS        current
    DESCRIPTION   "Container holding ntcAsiOutAlarm definitions."
    ::= { ntcAsiOutObjects 6 }
    
-- ntcAsiOutConformance content

ntcAsiOutConfCompliance          OBJECT-IDENTITY
    STATUS        current
    DESCRIPTION   "Device compliance statements."
    ::= { ntcAsiOutConformance 1 }
    
ntcAsiOutConfGroup               OBJECT-IDENTITY
    STATUS        current
    DESCRIPTION   "Groups used by device compliance statements."
    ::= { ntcAsiOutConformance 2 }
    

--
-- Managed Objects
--

ntcAsiOutInputSelection          OBJECT-TYPE
    SYNTAX      INTEGER { none(0), modulatorinput(2), activeinput(3), nonactiveinput(4), demod(5), prbsgenerator(100), ncrstream(101) }
    MAX-ACCESS  read-write
    STATUS      current
    DESCRIPTION
        "Input selection for the ASI block. It selects which signal has to be sent over
        the output ASI interface."
    DEFVAL { none }
    ::= { ntcAsiOutObjects 1 }
    
ntcAsiOutOutputSelection         OBJECT-TYPE
    SYNTAX      INTEGER { none(0), asi1(1), asi2(2), asi1and2(40) }
    MAX-ACCESS  read-write
    STATUS      current
    DESCRIPTION
        "Configuration of the ASI output connector(s). It is also possible to select
        several connectors. In this case the same signal is sent to different ASI
        output connectors."
    DEFVAL { none }
    ::= { ntcAsiOutObjects 2 }
    
ntcAsiOutMeasuredTsBitRate       OBJECT-TYPE
    SYNTAX      Unsigned32
    UNITS       "bps"
    MAX-ACCESS  read-only
    STATUS      current
    DESCRIPTION
        "Displays the measured ASI output TS bit rate in bps."
    ::= { ntcAsiOutObjects 3 }
    
ntcAsiOutPrbsGenOutputTsBitRate  OBJECT-TYPE
    SYNTAX      Unsigned32
    UNITS       "bps"
    MAX-ACCESS  read-write
    STATUS      current
    DESCRIPTION
        "Configure the PRBS generator ASI output TS bit rate value in bps."
    DEFVAL { 1000000 }
    ::= { ntcAsiOutPrbsGenerator 1 }
    
ntcAsiOutPrbsGenType             OBJECT-TYPE
    SYNTAX      INTEGER { prbs(0), counter(1) }
    MAX-ACCESS  read-write
    STATUS      current
    DESCRIPTION
        "
        - PRBS : Configures the test generator to generate transport stream packets
        containing PRBS data. The generated PRBS complies with HP3764 Compatible
        2^23-1 PRBS sequence as specified in CCITT Rec. 0.151.
        - Counter : Configures the test generator to generate transport stream packets
        containing 8-bit counter values as data. This counter data can not be analyzed
        by the test detector. It can only be used for manual verification by an
        external analyzer."
    DEFVAL { prbs }
    ::= { ntcAsiOutPrbsGenerator 2 }
    
ntcAsiOutPrbsGenPidHandling      OBJECT-TYPE
    SYNTAX      NtcEnable
    MAX-ACCESS  read-write
    STATUS      current
    DESCRIPTION
        "Configuration of the PID (Packet Identifier) handling in the PRBS Generator.
        Configuration of the test generator to generate transport stream packets with
        a valid transport stream header. The configured PID is inserted in the
        transport stream header and the continuity counter is incrementing. Possible
        settings;
        - Off: Transport stream packets are generated without a valid transport stream
        header. In this case, a 0x47 sync marker is generated followed by 187 test
        bytes.
        - On: When enabled, transport stream packets are generated with a configurable
        PID. (A burst of TS packets will be generated with a configurable of number
        data packets and a configurable number of null packets.)"
    DEFVAL { off }
    ::= { ntcAsiOutPrbsGenerator 3 }
    
ntcAsiOutPrbsGenPidValue         OBJECT-TYPE
    SYNTAX      NtcPid
    MAX-ACCESS  read-write
    STATUS      current
    DESCRIPTION
        "Configuration of the PRBS generator data packet PID value."
    DEFVAL { 1 }
    ::= { ntcAsiOutPrbsGenerator 4 }
    
ntcAsiOutPrbsGenNumberDataPkt    OBJECT-TYPE
    SYNTAX      Unsigned32 (1..4294967295)
    MAX-ACCESS  read-write
    STATUS      current
    DESCRIPTION
        "Configuration of the number of datapackets per burst. Current devices have an
        upper limit of 255. The number of null packets per burst is also configurable."
    DEFVAL { 1 }
    ::= { ntcAsiOutPrbsGenerator 5 }
    
ntcAsiOutPrbsGenNumberNullPkt    OBJECT-TYPE
    SYNTAX      Unsigned32
    MAX-ACCESS  read-write
    STATUS      current
    DESCRIPTION
        "Configuration of the number of null packets per burst. Current devices have an
        upper limit of 255. The number of datapackets is also configurable."
    DEFVAL { 0 }
    ::= { ntcAsiOutPrbsGenerator 6 }
    
ntcAsiOutNcrGenOutputTsBitRate   OBJECT-TYPE
    SYNTAX      Unsigned32
    UNITS       "bps"
    MAX-ACCESS  read-write
    STATUS      current
    DESCRIPTION
        "Configure the NCR generator ASI output TS bit rate value in bps."
    DEFVAL { 1000000 }
    ::= { ntcAsiOutNcrGenerator 1 }
    
ntcAsiOutAlmGeneralAsiOutput     OBJECT-TYPE
    SYNTAX      NtcAlarmState
    MAX-ACCESS  read-only
    STATUS      current
    DESCRIPTION
        "This alarm is raised when there is a general ASI output alarm. This variable
        indicates the current status of the alarm."
    ::= { ntcAsiOutAlarm 1 }
    
ntcAsiOutAlmNoOutputSignal       OBJECT-TYPE
    SYNTAX      NtcAlarmState
    MAX-ACCESS  read-only
    STATUS      current
    DESCRIPTION
        "This alarm is raised when no output signal is detected at the selected ASI
        output. This variable indicates the current status of the alarm."
    ::= { ntcAsiOutAlarm 2 }
    
ntcAsiOutAlmNoOutputSignalAsi1   OBJECT-TYPE
    SYNTAX      NtcAlarmState
    MAX-ACCESS  read-only
    STATUS      current
    DESCRIPTION
        "This alarm is raised when no output signal is detected at the ASI1 output.
        This variable indicates the current status of the alarm."
    ::= { ntcAsiOutAlarm 3 }
    
ntcAsiOutAlmNoOutputSignalAsi2   OBJECT-TYPE
    SYNTAX      NtcAlarmState
    MAX-ACCESS  read-only
    STATUS      current
    DESCRIPTION
        "This alarm is raised when no output signal is detected at the ASI2 output.
        This variable indicates the current status of the alarm."
    ::= { ntcAsiOutAlarm 4 }
    

--
--  Module Conformance
--

ntcAsiOutConfGrpV1Standard       OBJECT-GROUP
    OBJECTS    {
                   ntcAsiOutInputSelection,
                   ntcAsiOutOutputSelection,
                   ntcAsiOutMeasuredTsBitRate,
                   ntcAsiOutPrbsGenOutputTsBitRate,
                   ntcAsiOutPrbsGenType,
                   ntcAsiOutPrbsGenPidHandling,
                   ntcAsiOutPrbsGenPidValue,
                   ntcAsiOutPrbsGenNumberDataPkt,
                   ntcAsiOutPrbsGenNumberNullPkt,
                   ntcAsiOutNcrGenOutputTsBitRate,
                   ntcAsiOutAlmGeneralAsiOutput,
                   ntcAsiOutAlmNoOutputSignal,
                   ntcAsiOutAlmNoOutputSignalAsi1,
                   ntcAsiOutAlmNoOutputSignalAsi2
               }
    STATUS      current
    DESCRIPTION
        "Managed objects that constitute version 1 of a system device with standard capabilities."
    ::= { ntcAsiOutConfGroup 1}
    
ntcAsiOutConfCompV1Standard      MODULE-COMPLIANCE
    STATUS      current
    DESCRIPTION
        "Compliance statement for Newtec device MIB implementations."
    MODULE  -- this module
    MANDATORY-GROUPS
                  {
                      ntcAsiOutConfGrpV1Standard
                  }
    ::= { ntcAsiOutConfCompliance  1 }
    

END

NEWTEC-AUPCCLIENT-MIB DEFINITIONS ::= BEGIN

IMPORTS
    Unsigned32,
    Integer32,
    MODULE-IDENTITY,
    OBJECT-IDENTITY,
    OBJECT-TYPE
        FROM SNMPv2-SMI

    MODULE-COMPLIANCE,
    OBJECT-GROUP
        FROM SNMPv2-CONF
    
    NtcAlarmState,
    NtcEnable
        FROM NEWTEC-TC-MIB

    ntcFunction
        FROM NEWTEC-MAIN-MIB;


--
--  Module Identification
--

ntcAupcClient   MODULE-IDENTITY
    LAST-UPDATED "201410310800Z"
    ORGANIZATION "Newtec Cy"
    CONTACT-INFO
        "Newtec Cy
         Postal: Newtec Cy
                 Laarstraat 5
                 B-9100 Sint-Niklaas
                 Belgium

                Tel: +32 3 780 65 00
                Fax: +32 3 780 65 49
                Web: www.newtec.be
                E-mail: techsupport@newtec.be"
    DESCRIPTION
        "Newtec modular AUPC client MIB containing definitions for the AUPC client."

    REVISION  "201410310800Z"
    DESCRIPTION
        "ntcAupcClientCfgRemoteTermId column added"
    REVISION  "201309180800Z"
    DESCRIPTION
        "Alarms Status as Textual Conventions"
    REVISION  "201305220600Z"
    DESCRIPTION
        "Initial release for MDM6000 R1.1"
    ::= { ntcFunction  4100 }
    

--
-- Top-Level Structure
--

-- ntcAupcClient content

ntcAupcClientObjects             OBJECT-IDENTITY
    STATUS        current
    DESCRIPTION   "Container holding ntcAupcClientObjects definitions."
    ::= { ntcAupcClient 1 }
    
ntcAupcClntConformance           OBJECT-IDENTITY
    STATUS        current
    DESCRIPTION   "Conformance requirements."
    ::= { ntcAupcClient 2 }
    
-- ntcAupcClientObjects content

ntcAupcClientAlarm               OBJECT-IDENTITY
    STATUS        current
    DESCRIPTION   "Container holding ntcAupcClientAlarm definitions."
    ::= { ntcAupcClientObjects 1 }
    
-- ntcAupcClntConformance content

ntcAupcClntConfCompliance        OBJECT-IDENTITY
    STATUS        current
    DESCRIPTION   "Device compliance statements."
    ::= { ntcAupcClntConformance 1 }
    
ntcAupcClntConfGroup             OBJECT-IDENTITY
    STATUS        current
    DESCRIPTION   "Groups used by device compliance statements."
    ::= { ntcAupcClntConformance 2 }
    

--
-- Managed Objects
--

ntcAupcClientAlmCalibAbsent      OBJECT-TYPE
    SYNTAX      NtcAlarmState
    MAX-ACCESS  read-only
    STATUS      current
    DESCRIPTION
        "This alarm indicates that the AUPC client subsystem has not been calibrated
        This variable indicates the current status of the alarm."
    ::= { ntcAupcClientAlarm 1 }
    
ntcAupcClientAlmCalibViolation   OBJECT-TYPE
    SYNTAX      NtcAlarmState
    MAX-ACCESS  read-only
    STATUS      current
    DESCRIPTION
        "This alarm indicates that the AUPC client wants to operate outside the
        calibrated range This variable indicates the current status of the alarm."
    ::= { ntcAupcClientAlarm 2 }
    
ntcAupcClientAlarmStateTable     OBJECT-TYPE
    SYNTAX      SEQUENCE OF NtcAupcClientAlarmStateEntry
    MAX-ACCESS  not-accessible
    STATUS      current
    DESCRIPTION
        "A table containing the ntcAupcClientAlarmState"
    ::= { ntcAupcClientObjects 2 }

ntcAupcClientAlarmStateEntry     OBJECT-TYPE
    SYNTAX      NtcAupcClientAlarmStateEntry
    MAX-ACCESS  not-accessible
    STATUS      current
    DESCRIPTION
        "A conceptual row of the ntcAupcClientAlarmStateTable."
    INDEX   { ntcAupcClientASDemodId  }
    ::= { ntcAupcClientAlarmStateTable 1 }

NtcAupcClientAlarmStateEntry     ::= SEQUENCE {
    ntcAupcClientASDemodId           INTEGER,
    ntcAupcClientASCalibAbsent       NtcAlarmState,
    ntcAupcClientASCalibViolation    NtcAlarmState
    }
    
ntcAupcClientASDemodId           OBJECT-TYPE
    SYNTAX      INTEGER { demod1(1), demod2(2), demod3(3) }
    MAX-ACCESS  not-accessible
    STATUS      current
    DESCRIPTION
        "The id of the demodulator"
    ::= { ntcAupcClientAlarmStateEntry 1 }
    
ntcAupcClientASCalibAbsent       OBJECT-TYPE
    SYNTAX      NtcAlarmState
    MAX-ACCESS  read-only
    STATUS      current
    DESCRIPTION
        "This alarm indicates that the AUPC client subsystem has not been calibrated
        This variable indicates the current status of the alarm."
    ::= { ntcAupcClientAlarmStateEntry 2 }
    
ntcAupcClientASCalibViolation    OBJECT-TYPE
    SYNTAX      NtcAlarmState
    MAX-ACCESS  read-only
    STATUS      current
    DESCRIPTION
        "This alarm indicates that the AUPC client wants to operate outside the
        calibrated range This variable indicates the current status of the alarm."
    ::= { ntcAupcClientAlarmStateEntry 3 }
    
ntcAupcClientCfgTable            OBJECT-TYPE
    SYNTAX      SEQUENCE OF NtcAupcClientCfgEntry
    MAX-ACCESS  not-accessible
    STATUS      current
    DESCRIPTION
        "A table containing the ntcAupcClientCfg"
    ::= { ntcAupcClientObjects 3 }

ntcAupcClientCfgEntry            OBJECT-TYPE
    SYNTAX      NtcAupcClientCfgEntry
    MAX-ACCESS  not-accessible
    STATUS      current
    DESCRIPTION
        "A conceptual row of the ntcAupcClientCfgTable."
    INDEX   { ntcAupcClientCfgDemodId  }
    ::= { ntcAupcClientCfgTable 1 }

NtcAupcClientCfgEntry            ::= SEQUENCE {
    ntcAupcClientCfgDemodId         INTEGER,
    ntcAupcClientCfgEnable          NtcEnable,
    ntcAupcClientCfgRemoteTermId    Unsigned32
    }
    
ntcAupcClientCfgDemodId          OBJECT-TYPE
    SYNTAX      INTEGER { demod1(1), demod2(2), demod3(3) }
    MAX-ACCESS  not-accessible
    STATUS      current
    DESCRIPTION
        "The id of the demodulator"
    ::= { ntcAupcClientCfgEntry 1 }
    
ntcAupcClientCfgEnable           OBJECT-TYPE
    SYNTAX      NtcEnable
    MAX-ACCESS  read-write
    STATUS      current
    DESCRIPTION
        "Enable or disable the AUPC client function"
    DEFVAL { off }
    ::= { ntcAupcClientCfgEntry 2 }
    
ntcAupcClientCfgRemoteTermId     OBJECT-TYPE
    SYNTAX      Unsigned32 (0..65277)
    MAX-ACCESS  read-write
    STATUS      current
    DESCRIPTION
        "Identification of the controller terminal, for use by the ACM and AUPC control
        messages."
    DEFVAL { 0 }
    ::= { ntcAupcClientCfgEntry 3 }
    
ntcAupcClientCalibTable          OBJECT-TYPE
    SYNTAX      SEQUENCE OF NtcAupcClientCalibEntry
    MAX-ACCESS  not-accessible
    STATUS      current
    DESCRIPTION
        "A table containing the ntcAupcClientCalib"
    ::= { ntcAupcClientObjects 4 }

ntcAupcClientCalibEntry          OBJECT-TYPE
    SYNTAX      NtcAupcClientCalibEntry
    MAX-ACCESS  not-accessible
    STATUS      current
    DESCRIPTION
        "A conceptual row of the ntcAupcClientCalibTable."
    INDEX   { ntcAupcClientCalibDemodId  }
    ::= { ntcAupcClientCalibTable 1 }

NtcAupcClientCalibEntry          ::= SEQUENCE {
    ntcAupcClientCalibDemodId        INTEGER,
    ntcAupcClientCalibNomInputLvl    Integer32,
    ntcAupcClientCalibNomEsNo        Integer32
    }
    
ntcAupcClientCalibDemodId        OBJECT-TYPE
    SYNTAX      INTEGER { demod1(1), demod2(2), demod3(3) }
    MAX-ACCESS  not-accessible
    STATUS      current
    DESCRIPTION
        "The id of the demodulator"
    ::= { ntcAupcClientCalibEntry 1 }
    
ntcAupcClientCalibNomInputLvl    OBJECT-TYPE
    SYNTAX      Integer32 (-1000..500)
    UNITS       "dBm"
    MAX-ACCESS  read-write
    STATUS      current
    DESCRIPTION
        "Nominal input level, recorded at calibration time"
    DEFVAL { -150 }
    ::= { ntcAupcClientCalibEntry 2 }
    
ntcAupcClientCalibNomEsNo        OBJECT-TYPE
    SYNTAX      Integer32 (-1000..4000)
    UNITS       "dB"
    MAX-ACCESS  read-write
    STATUS      current
    DESCRIPTION
        "Nominal Es/N0"
    DEFVAL { 0 }
    ::= { ntcAupcClientCalibEntry 3 }
    
ntcAupcClientMonTable            OBJECT-TYPE
    SYNTAX      SEQUENCE OF NtcAupcClientMonEntry
    MAX-ACCESS  not-accessible
    STATUS      current
    DESCRIPTION
        "A table containing the ntcAupcClientMon"
    ::= { ntcAupcClientObjects 5 }

ntcAupcClientMonEntry            OBJECT-TYPE
    SYNTAX      NtcAupcClientMonEntry
    MAX-ACCESS  not-accessible
    STATUS      current
    DESCRIPTION
        "A conceptual row of the ntcAupcClientMonTable."
    INDEX   { ntcAupcClientMonDemodId  }
    ::= { ntcAupcClientMonTable 1 }

NtcAupcClientMonEntry            ::= SEQUENCE {
    ntcAupcClientMonDemodId           INTEGER,
    ntcAupcClientMonState             INTEGER,
    ntcAupcClientMonInputLvl          Integer32,
    ntcAupcClientMonEsNo              Integer32,
    ntcAupcClientMonCurPwrCompen      Integer32,
    ntcAupcClientMonEstRmtUpFading    Integer32
    }
    
ntcAupcClientMonDemodId          OBJECT-TYPE
    SYNTAX      INTEGER { demod1(1), demod2(2), demod3(3) }
    MAX-ACCESS  not-accessible
    STATUS      current
    DESCRIPTION
        "The id of the demodulator"
    ::= { ntcAupcClientMonEntry 1 }
    
ntcAupcClientMonState            OBJECT-TYPE
    SYNTAX      INTEGER { off(0), notCalibrated(1), calibrated(2), waitingForController(3), reporting(4), nolock(5), alarm(6) }
    MAX-ACCESS  read-only
    STATUS      current
    DESCRIPTION
        "The AUPC client state"
    ::= { ntcAupcClientMonEntry 2 }
    
ntcAupcClientMonInputLvl         OBJECT-TYPE
    SYNTAX      Integer32 (-1000..500)
    UNITS       "dBm"
    MAX-ACCESS  read-only
    STATUS      current
    DESCRIPTION
        "Input level"
    ::= { ntcAupcClientMonEntry 3 }
    
ntcAupcClientMonEsNo             OBJECT-TYPE
    SYNTAX      Integer32 (-1000..4000)
    UNITS       "dB"
    MAX-ACCESS  read-only
    STATUS      current
    DESCRIPTION
        "Received Es/N0"
    ::= { ntcAupcClientMonEntry 4 }
    
ntcAupcClientMonCurPwrCompen     OBJECT-TYPE
    SYNTAX      Integer32 (-1000..5000)
    UNITS       "dB"
    MAX-ACCESS  read-only
    STATUS      current
    DESCRIPTION
        "Current power compensation on the uplink"
    ::= { ntcAupcClientMonEntry 5 }
    
ntcAupcClientMonEstRmtUpFading   OBJECT-TYPE
    SYNTAX      Integer32 (-1000..5000)
    UNITS       "dB"
    MAX-ACCESS  read-only
    STATUS      current
    DESCRIPTION
        "Estimated remote uplink fading"
    ::= { ntcAupcClientMonEntry 6 }
    

--
--  Module Conformance
--

ntcAupcClntConfGrpV1Standard     OBJECT-GROUP
    OBJECTS    {
                   ntcAupcClientAlmCalibAbsent,
                   ntcAupcClientAlmCalibViolation,
                   ntcAupcClientASCalibAbsent,
                   ntcAupcClientASCalibViolation,
                   ntcAupcClientCfgEnable,
                   ntcAupcClientCfgRemoteTermId,
                   ntcAupcClientCalibNomInputLvl,
                   ntcAupcClientCalibNomEsNo,
                   ntcAupcClientMonState,
                   ntcAupcClientMonInputLvl,
                   ntcAupcClientMonEsNo,
                   ntcAupcClientMonCurPwrCompen,
                   ntcAupcClientMonEstRmtUpFading
               }
    STATUS      current
    DESCRIPTION
        "Managed objects that constitute version 1 of a system device with standard capabilities."
    ::= { ntcAupcClntConfGroup 1}
    
ntcAupcClntConfCompV1Standard    MODULE-COMPLIANCE
    STATUS      current
    DESCRIPTION
        "Compliance statement for Newtec device MIB implementations."
    MODULE  -- this module
    MANDATORY-GROUPS
                  {
                      ntcAupcClntConfGrpV1Standard
                  }
    ::= { ntcAupcClntConfCompliance  1 }
    

END

NEWTEC-AUPCCONTROLLER-MIB DEFINITIONS ::= BEGIN

IMPORTS
    Integer32,
    Unsigned32,
    Counter64,
    MODULE-IDENTITY,
    OBJECT-IDENTITY,
    OBJECT-TYPE
        FROM SNMPv2-SMI

    MODULE-COMPLIANCE,
    OBJECT-GROUP
        FROM SNMPv2-CONF
    
    NtcEnable
        FROM NEWTEC-TC-MIB

    ntcFunction
        FROM NEWTEC-MAIN-MIB;


--
--  Module Identification
--

ntcAupcController   MODULE-IDENTITY
    LAST-UPDATED "201710161200Z"
    ORGANIZATION "Newtec Cy"
    CONTACT-INFO
        "Newtec Cy
         Postal: Newtec Cy
                 Laarstraat 5
                 B-9100 Sint-Niklaas
                 Belgium

                Tel: +32 3 780 65 00
                Fax: +32 3 780 65 49
                Web: www.newtec.be
                E-mail: techsupport@newtec.be"
    DESCRIPTION
        "Newtec modular AUPC controller MIB containing definitions for the AUPC
        controller."

    REVISION  "201710161200Z"
    DESCRIPTION
        "range extended for ntcAupcCtrlReqModulatorPower, ntcAupcCtrlCurModulatorPower,
        ntcAupcCtrlMaximumModPower and ntcAupcCtrlNominalModPower"
    REVISION  "201402031200Z"
    DESCRIPTION
        "Unit of MaximumPowerStep corrected"
    REVISION  "201305220600Z"
    DESCRIPTION
        "Initial release for MDM6000 R1.1"
    ::= { ntcFunction  4200 }
    

--
-- Top-Level Structure
--

-- ntcAupcController content

ntcAupcCtrlObjects               OBJECT-IDENTITY
    STATUS        current
    DESCRIPTION   "Container holding ntcAupcCtrlObjects definitions."
    ::= { ntcAupcController 1 }
    
ntcAupcCtrlConformance           OBJECT-IDENTITY
    STATUS        current
    DESCRIPTION   "Conformance requirements."
    ::= { ntcAupcController 2 }
    
-- ntcAupcCtrlObjects content

ntcAupcCtrlMonitoring            OBJECT-IDENTITY
    STATUS        current
    DESCRIPTION   "Container holding ntcAupcCtrlMonitoring definitions."
    ::= { ntcAupcCtrlObjects 7 }
    
-- ntcAupcCtrlConformance content

ntcAupcCtrlConfCompliance        OBJECT-IDENTITY
    STATUS        current
    DESCRIPTION   "Device compliance statements."
    ::= { ntcAupcCtrlConformance 1 }
    
ntcAupcCtrlConfGroup             OBJECT-IDENTITY
    STATUS        current
    DESCRIPTION   "Groups used by device compliance statements."
    ::= { ntcAupcCtrlConformance 2 }
    

--
-- Managed Objects
--

ntcAupcCtrlEnable                OBJECT-TYPE
    SYNTAX      NtcEnable
    MAX-ACCESS  read-write
    STATUS      current
    DESCRIPTION
        "Enable or disable the AUPC controller"
    DEFVAL { off }
    ::= { ntcAupcCtrlObjects 1 }
    
ntcAupcCtrlNominalModPower       OBJECT-TYPE
    SYNTAX      Integer32 (-400..100)
    UNITS       "dBm"
    MAX-ACCESS  read-write
    STATUS      current
    DESCRIPTION
        "Nominal modulator output power setting in dBm. Adjustable in steps of 0.1 dBm.
        Float represented as integer is scaled by a factor of 10. i.e. a value of
        '-103' means '-10.3' dBm Note that the range normally starts from
        -35.0, there is one exceptional product that allows it to start from
        -40.0 in a very special use case."
    DEFVAL { -150 }
    ::= { ntcAupcCtrlObjects 2 }
    
ntcAupcCtrlMaximumModPower       OBJECT-TYPE
    SYNTAX      Integer32 (-400..100)
    UNITS       "dBm"
    MAX-ACCESS  read-write
    STATUS      current
    DESCRIPTION
        "Maximum modulator output power setting in dBm. Adjustable in steps of 0.1 dBm.
        Float represented as integer is scaled by a factor of 10. i.e. a value of
        '-103' means '-10.3' dBm Note that the range normally starts from
        -35.0, there is one exceptional product that allows it to start from
        -40.0 in a very special use case."
    DEFVAL { -150 }
    ::= { ntcAupcCtrlObjects 3 }
    
ntcAupcCtrlMaximumPowerStepUp    OBJECT-TYPE
    SYNTAX      Integer32 (0..100)
    UNITS       "dBm/s"
    MAX-ACCESS  read-write
    STATUS      current
    DESCRIPTION
        "Maximum step size by which the modulator power level is raised per second
        Float represented as integer is scaled by a factor of 10. i.e. a value of '10'
        means '1' dBm/s"
    DEFVAL { 1 }
    ::= { ntcAupcCtrlObjects 4 }
    
ntcAupcCtrlMaximumPowerStepDown  OBJECT-TYPE
    SYNTAX      Integer32 (0..100)
    UNITS       "dBm/s"
    MAX-ACCESS  read-write
    STATUS      current
    DESCRIPTION
        "Maximum step size by which the modulator power level is decreased per second
        Float represented as integer is scaled by a factor of 10. i.e. a value of '10'
        means '1' dBm/s"
    DEFVAL { 5 }
    ::= { ntcAupcCtrlObjects 5 }
    
ntcAupcCtrlRefTerm               OBJECT-TYPE
    SYNTAX      Unsigned32 (0..65277)
    MAX-ACCESS  read-write
    STATUS      current
    DESCRIPTION
        "The reference terminal that feeds the AUPC algorithm. Terminal '0' indicates
        that the input of every terminal can be used."
    DEFVAL { 0 }
    ::= { ntcAupcCtrlObjects 6 }
    
ntcAupcCtrlForwardConfigCounter  OBJECT-TYPE
    SYNTAX      Counter64
    MAX-ACCESS  read-only
    STATUS      current
    DESCRIPTION
        "The number of forward configuration messages"
    ::= { ntcAupcCtrlMonitoring 1 }
    
ntcAupcCtrlClientFeedbackCounter OBJECT-TYPE
    SYNTAX      Counter64
    MAX-ACCESS  read-only
    STATUS      current
    DESCRIPTION
        "The number of client feedback messages received"
    ::= { ntcAupcCtrlMonitoring 2 }
    
ntcAupcCtrlPowerRequestCounter   OBJECT-TYPE
    SYNTAX      Counter64
    MAX-ACCESS  read-only
    STATUS      current
    DESCRIPTION
        "The number of power updates"
    ::= { ntcAupcCtrlMonitoring 3 }
    
ntcAupcCtrlReqModulatorPower     OBJECT-TYPE
    SYNTAX      Integer32 (-400..100)
    UNITS       "dBm"
    MAX-ACCESS  read-only
    STATUS      current
    DESCRIPTION
        "The requested modulator power in dBm. Float represented as integer is scaled
        by a factor of 10. i.e. a value of '-103' means '-10.3' dBm Note that the
        range normally starts from
        -35.0, there is one exceptional product that allows it to start from
        -40.0 in a very special use case."
    ::= { ntcAupcCtrlMonitoring 4 }
    
ntcAupcCtrlCurModulatorPower     OBJECT-TYPE
    SYNTAX      Integer32 (-400..100)
    UNITS       "dBm"
    MAX-ACCESS  read-only
    STATUS      current
    DESCRIPTION
        "The current modulator power in dBm. Float represented as integer is scaled by
        a factor of 10. i.e. a value of '-103' means '-10.3' dBm Note that the range
        normally starts from
        -35.0, there is one exceptional product that allows it to start from
        -40.0 in a very special use case."
    ::= { ntcAupcCtrlMonitoring 5 }
    

--
--  Module Conformance
--

ntcAupcCtrlConfGrpV1Standard     OBJECT-GROUP
    OBJECTS    {
                   ntcAupcCtrlEnable,
                   ntcAupcCtrlNominalModPower,
                   ntcAupcCtrlMaximumModPower,
                   ntcAupcCtrlMaximumPowerStepUp,
                   ntcAupcCtrlMaximumPowerStepDown,
                   ntcAupcCtrlRefTerm,
                   ntcAupcCtrlForwardConfigCounter,
                   ntcAupcCtrlClientFeedbackCounter,
                   ntcAupcCtrlPowerRequestCounter,
                   ntcAupcCtrlReqModulatorPower,
                   ntcAupcCtrlCurModulatorPower
               }
    STATUS      current
    DESCRIPTION
        "Managed objects that constitute version 1 of a system device with standard capabilities."
    ::= { ntcAupcCtrlConfGroup 1}
    
ntcAupcCtrlConfCompV1Standard    MODULE-COMPLIANCE
    STATUS      current
    DESCRIPTION
        "Compliance statement for Newtec device MIB implementations."
    MODULE  -- this module
    MANDATORY-GROUPS
                  {
                      ntcAupcCtrlConfGrpV1Standard
                  }
    ::= { ntcAupcCtrlConfCompliance  1 }
    

END

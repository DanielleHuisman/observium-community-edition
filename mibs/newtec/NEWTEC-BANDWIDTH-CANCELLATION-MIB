NEWTEC-BANDWIDTH-CANCELLATION-MIB DEFINITIONS ::= BEGIN

IMPORTS
    Unsigned32,
    Integer32,
    MODULE-IDENTITY,
    OBJECT-IDENTITY,
    OBJECT-TYPE
        FROM SNMPv2-SMI

    MODULE-COMPLIANCE,
    OBJECT-GROUP
        FROM SNMPv2-CONF
    
    Float32TC
        FROM FLOAT-TC-MIB

    NtcAlarmState,
    NtcEnable
        FROM NEWTEC-TC-MIB

    DisplayString
        FROM SNMPv2-TC

    ntcFunction
        FROM NEWTEC-MAIN-MIB;


--
--  Module Identification
--

ntcBandwidthCancellation   MODULE-IDENTITY
    LAST-UPDATED "201602011100Z"
    ORGANIZATION "Newtec Cy"
    CONTACT-INFO
        "Newtec Cy
         Postal: Newtec Cy
                 Laarstraat 5
                 B-9100 Sint-Niklaas
                 Belgium

                Tel: +32 3 780 65 00
                Fax: +32 3 780 65 49
                Web: www.newtec.be
                E-mail: techsupport@newtec.be"
    DESCRIPTION
        "Newtec modular BANDWIDTH-CANCELLATION MIB"

    REVISION  "201602011100Z"
    DESCRIPTION
        "Initial release for MDM6000 R3.1.1"
    ::= { ntcFunction  9100 }
    

--
-- Top-Level Structure
--

-- ntcBandwidthCancellation content

ntcBwCObjects                    OBJECT-IDENTITY
    STATUS        current
    DESCRIPTION   "Container holding ntcBwCObjects definitions."
    ::= { ntcBandwidthCancellation 1 }
    
ntcBwCConformance                OBJECT-IDENTITY
    STATUS        current
    DESCRIPTION   "Conformance requirements."
    ::= { ntcBandwidthCancellation 2 }
    
-- ntcBwCObjects content

ntcBwCAlarm                      OBJECT-IDENTITY
    STATUS        current
    DESCRIPTION   "Container holding ntcBwCAlarm definitions."
    ::= { ntcBwCObjects 1 }
    
-- ntcBwCConformance content

ntcBwCConfCompliance             OBJECT-IDENTITY
    STATUS        current
    DESCRIPTION   "Device compliance statements."
    ::= { ntcBwCConformance 1 }
    
ntcBwCConfGroup                  OBJECT-IDENTITY
    STATUS        current
    DESCRIPTION   "Groups used by device compliance statements."
    ::= { ntcBwCConformance 2 }
    

--
-- Managed Objects
--

ntcBwCAlarmNoLock                OBJECT-TYPE
    SYNTAX      NtcAlarmState
    MAX-ACCESS  read-only
    STATUS      current
    DESCRIPTION
        "This alarm is raised when the bandwidth canceller is enabled but not locked
        This variable indicates the current status of the alarm."
    ::= { ntcBwCAlarm 1 }
    
ntcBwCCfgTable                   OBJECT-TYPE
    SYNTAX      SEQUENCE OF NtcBwCCfgEntry
    MAX-ACCESS  not-accessible
    STATUS      current
    DESCRIPTION
        "Configuration table"
    ::= { ntcBwCObjects 2 }

ntcBwCCfgEntry                   OBJECT-TYPE
    SYNTAX      NtcBwCCfgEntry
    MAX-ACCESS  not-accessible
    STATUS      current
    DESCRIPTION
        "A conceptual row of the ntcBwCCfgTable."
    INDEX   { ntcBwCCfgName  }
    ::= { ntcBwCCfgTable 1 }

NtcBwCCfgEntry                   ::= SEQUENCE {
    ntcBwCCfgName                      DisplayString,
    ntcBwCCfgEnable                    NtcEnable,
    ntcBwCCfgExpRoundTripDelay         Unsigned32,
    ntcBwCCfgRoundTripDelayUncert      Unsigned32,
    ntcBwCCfgLocalCenterFreqOffset     Integer32,
    ntcBwCCfgLocalCenterFreqUncert     Unsigned32,
    ntcBwCCfgLocalSpectralInversion    INTEGER,
    ntcBwCCfgBandwidthMode             INTEGER
    }
    
ntcBwCCfgName                    OBJECT-TYPE
    SYNTAX      DisplayString (SIZE(1..32))
    MAX-ACCESS  not-accessible
    STATUS      current
    DESCRIPTION
        "Name of the input configuration"
    ::= { ntcBwCCfgEntry 1 }
    
ntcBwCCfgEnable                  OBJECT-TYPE
    SYNTAX      NtcEnable
    MAX-ACCESS  read-write
    STATUS      current
    DESCRIPTION
        "Enable or disable bandwidth cancellation"
    DEFVAL { off }
    ::= { ntcBwCCfgEntry 2 }
    
ntcBwCCfgExpRoundTripDelay       OBJECT-TYPE
    SYNTAX      Unsigned32 (0..500)
    UNITS       "ms"
    MAX-ACCESS  read-write
    STATUS      current
    DESCRIPTION
        "Set this to the round trip delay the carrier (that is uplinked, received and
        cancelled out) will experience. The closer this value is to the actual delay,
        the faster the cancelling will start. Set this value to 0 when doing a
        back-to-back test."
    DEFVAL { 250 }
    ::= { ntcBwCCfgEntry 3 }
    
ntcBwCCfgRoundTripDelayUncert    OBJECT-TYPE
    SYNTAX      Unsigned32 (1..100)
    UNITS       "ms"
    MAX-ACCESS  read-write
    STATUS      current
    DESCRIPTION
        "The delay search window that the cancellation function will use to try to
        acquire full lock. Advised starting value is set to 20 ms but once the actual
        round trip delay is known, the search range can be decreased to reduce search
        time and speed up full lock. However, some range should still be allowed to
        accommodate change in delay due to Doppler effects."
    DEFVAL { 20 }
    ::= { ntcBwCCfgEntry 4 }
    
ntcBwCCfgLocalCenterFreqOffset   OBJECT-TYPE
    SYNTAX      Integer32 (-100000000..100000000)
    UNITS       "Hz"
    MAX-ACCESS  read-write
    STATUS      current
    DESCRIPTION
        "The center frequency offset of the received local carrier (that is uplinked,
        received and cancelled out)"
    DEFVAL { 0 }
    ::= { ntcBwCCfgEntry 5 }
    
ntcBwCCfgLocalCenterFreqUncert   OBJECT-TYPE
    SYNTAX      Unsigned32 (50000..7500000)
    UNITS       "Hz"
    MAX-ACCESS  read-write
    STATUS      current
    DESCRIPTION
        "The frequency search window in which the demodulator will search for the
        received local carrier. By observing the local carrier center frequency
        offset, this value can be decreased to reduce search time and speed up full
        lock."
    DEFVAL { 50000 }
    ::= { ntcBwCCfgEntry 6 }
    
ntcBwCCfgLocalSpectralInversion  OBJECT-TYPE
    SYNTAX      INTEGER { direct(0), inverted(1), automatic(2) }
    MAX-ACCESS  read-write
    STATUS      current
    DESCRIPTION
        "In case an upconverter or the satellite transponder inverses the spectrum of
        the carrier, the cancellation function needs to re-inverse the spectrum prior
        to actual cancellation. In case automatic is used, the canceller will toggle
        continuously between inverted and direct spectrum. In order to speed up lock
        time, observe the detected inversion in the monitoring parameter 'local
        spectral inversion' and set the detected inversion here."
    DEFVAL { automatic }
    ::= { ntcBwCCfgEntry 7 }
    
ntcBwCCfgBandwidthMode           OBJECT-TYPE
    SYNTAX      INTEGER { normal(0), robust(1), fine(2) }
    MAX-ACCESS  read-write
    STATUS      current
    DESCRIPTION
        "The Bandwidth Mode sets the range of parameters of the acquisition loops. Use
        the bandwidth mode to balance search range versus acquisition time. Normal:
        standard settings for the acquisition loops. Robust: extended ranges of the
        parameters in the acquisition loops. This can cope with bigger uncertainties
        but potentially increases lock time. Fine: when all parameters are accurately
        known and set and there is no change over time, the fine mode can be used to
        achieve the fastest lock time."
    DEFVAL { normal }
    ::= { ntcBwCCfgEntry 8 }
    
ntcBwCMonTable                   OBJECT-TYPE
    SYNTAX      SEQUENCE OF NtcBwCMonEntry
    MAX-ACCESS  not-accessible
    STATUS      current
    DESCRIPTION
        "Monitoring table"
    ::= { ntcBwCObjects 3 }

ntcBwCMonEntry                   OBJECT-TYPE
    SYNTAX      NtcBwCMonEntry
    MAX-ACCESS  not-accessible
    STATUS      current
    DESCRIPTION
        "A conceptual row of the ntcBwCMonTable."
    AUGMENTS   { ntcBwCCfgEntry }
    ::= { ntcBwCMonTable 1 }

NtcBwCMonEntry                   ::= SEQUENCE {
    ntcBwCMonState                      INTEGER,
    ntcBwCMonRoundTripDelay             Float32TC,
    ntcBwCMonLocalToTotalPowerRatio     Float32TC,
    ntcBwCMonLocalToRemotePowerRatio    Float32TC,
    ntcBwCMonLocalLevel                 Float32TC,
    ntcBwCMonLocalSymbolRate            Unsigned32,
    ntcBwCMonLocalFreqOffset            Float32TC,
    ntcBwCMonLocalSpectralInversion     INTEGER
    }
    
ntcBwCMonState                   OBJECT-TYPE
    SYNTAX      INTEGER { off(0), searching(1), locked(2) }
    MAX-ACCESS  read-only
    STATUS      current
    DESCRIPTION
        "The state of the bandwidth cancellation function can be off (in case bandwidth
        cancellation is disabled), searching (when in the process of acquiring lock)
        or locked when the cancellation function is fully operational."
    ::= { ntcBwCMonEntry 1 }
    
ntcBwCMonRoundTripDelay          OBJECT-TYPE
    SYNTAX      Float32TC
    UNITS       "ms"
    MAX-ACCESS  read-only
    STATUS      current
    DESCRIPTION
        "The measured round trip delay the carrier (that is uplinked and again
        received) experiences. Use this value to fine tune the control parameter
        'Expected round trip delay'. The round trip delay can slightly change due to
        Doppler and the satellite moving in its 'box'."
    ::= { ntcBwCMonEntry 2 }
    
ntcBwCMonLocalToTotalPowerRatio  OBJECT-TYPE
    SYNTAX      Float32TC
    UNITS       "dB"
    MAX-ACCESS  read-only
    STATUS      current
    DESCRIPTION
        "The measured ratio between the total received power at the input of the modem
        and the received local carrier power."
    ::= { ntcBwCMonEntry 3 }
    
ntcBwCMonLocalToRemotePowerRatio OBJECT-TYPE
    SYNTAX      Float32TC
    UNITS       "dB"
    MAX-ACCESS  read-only
    STATUS      current
    DESCRIPTION
        "The measured ratio between the remote carrier power and the received local
        carrier power."
    ::= { ntcBwCMonEntry 4 }
    
ntcBwCMonLocalLevel              OBJECT-TYPE
    SYNTAX      Float32TC
    UNITS       "dBm"
    MAX-ACCESS  read-only
    STATUS      current
    DESCRIPTION
        "The power of the received local carrier (that is uplinked then received) prior
        to actual cancellation."
    ::= { ntcBwCMonEntry 5 }
    
ntcBwCMonLocalSymbolRate         OBJECT-TYPE
    SYNTAX      Unsigned32 (0..133000000)
    UNITS       "baud"
    MAX-ACCESS  read-only
    STATUS      current
    DESCRIPTION
        "The measured symbolrate of the local carrier (that is uplink, received and
        cancelled out)."
    ::= { ntcBwCMonEntry 6 }
    
ntcBwCMonLocalFreqOffset         OBJECT-TYPE
    SYNTAX      Float32TC
    UNITS       "Hz"
    MAX-ACCESS  read-only
    STATUS      current
    DESCRIPTION
        "The difference between the set local carrier frequency and the actual detected
        local carrier frequency."
    ::= { ntcBwCMonEntry 7 }
    
ntcBwCMonLocalSpectralInversion  OBJECT-TYPE
    SYNTAX      INTEGER { direct(0), inverted(1), unknown(2) }
    MAX-ACCESS  read-only
    STATUS      current
    DESCRIPTION
        "The spectral inversion of the local carrier (that is uplinked and again
        received) that is applied. This can be either have been set manually or
        detected automatically (by using the 'automatic' setting in the 'Local carrier
        spectral inversion' control parameter. Once the spectral inversion is know it
        is advised to set it manual to the correct value in order to reduced
        cancellation lock time."
    ::= { ntcBwCMonEntry 8 }
    
ntcBwCAlarmStateTable            OBJECT-TYPE
    SYNTAX      SEQUENCE OF NtcBwCAlarmStateEntry
    MAX-ACCESS  not-accessible
    STATUS      current
    DESCRIPTION
        "Alarm Status table"
    ::= { ntcBwCObjects 4 }

ntcBwCAlarmStateEntry            OBJECT-TYPE
    SYNTAX      NtcBwCAlarmStateEntry
    MAX-ACCESS  not-accessible
    STATUS      current
    DESCRIPTION
        "A conceptual row of the ntcBwCAlarmStateTable."
    AUGMENTS   { ntcBwCCfgEntry }
    ::= { ntcBwCAlarmStateTable 1 }

NtcBwCAlarmStateEntry            ::= SEQUENCE {
    ntcBwCASNoLock    NtcAlarmState
    }
    
ntcBwCASNoLock                   OBJECT-TYPE
    SYNTAX      NtcAlarmState
    MAX-ACCESS  read-only
    STATUS      current
    DESCRIPTION
        "This alarm is raised when the bandwidth canceller is enabled but not locked
        This variable indicates the current status of the alarm."
    ::= { ntcBwCAlarmStateEntry 1 }
    

--
--  Module Conformance
--

ntcBwCConfGrpV1Standard          OBJECT-GROUP
    OBJECTS    {
                   ntcBwCAlarmNoLock,
                   ntcBwCCfgEnable,
                   ntcBwCCfgExpRoundTripDelay,
                   ntcBwCCfgRoundTripDelayUncert,
                   ntcBwCCfgLocalCenterFreqOffset,
                   ntcBwCCfgLocalCenterFreqUncert,
                   ntcBwCCfgLocalSpectralInversion,
                   ntcBwCCfgBandwidthMode,
                   ntcBwCMonState,
                   ntcBwCMonRoundTripDelay,
                   ntcBwCMonLocalToTotalPowerRatio,
                   ntcBwCMonLocalToRemotePowerRatio,
                   ntcBwCMonLocalLevel,
                   ntcBwCMonLocalSymbolRate,
                   ntcBwCMonLocalFreqOffset,
                   ntcBwCMonLocalSpectralInversion,
                   ntcBwCASNoLock
               }
    STATUS      current
    DESCRIPTION
        "Managed objects that constitute version 1 of a system device with standard capabilities."
    ::= { ntcBwCConfGroup 1}
    
ntcBwCConfCompV1Standard         MODULE-COMPLIANCE
    STATUS      current
    DESCRIPTION
        "Compliance statement for Newtec device MIB implementations."
    MODULE  -- this module
    MANDATORY-GROUPS
                  {
                      ntcBwCConfGrpV1Standard
                  }
    ::= { ntcBwCConfCompliance  1 }
    

END

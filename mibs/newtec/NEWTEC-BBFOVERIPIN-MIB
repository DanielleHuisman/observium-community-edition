NEWTEC-BBFOVERIPIN-MIB DEFINITIONS ::= BEGIN

IMPORTS
    IpAddress,
    Unsigned32,
    Counter32,
    MODULE-IDENTITY,
    OBJECT-IDENTITY,
    OBJECT-TYPE
        FROM SNMPv2-SMI

    MODULE-COMPLIANCE,
    OBJECT-GROUP
        FROM SNMPv2-CONF
    
    NtcAlarmState,
    NtcEnable
        FROM NEWTEC-TC-MIB

    DisplayString,
    RowStatus
        FROM SNMPv2-TC

    ntcFunction
        FROM NEWTEC-MAIN-MIB;


--
--  Module Identification
--

ntcBbfOverIpIn   MODULE-IDENTITY
    LAST-UPDATED "201707101200Z"
    ORGANIZATION "Newtec Cy"
    CONTACT-INFO
        "Newtec Cy
         Postal: Newtec Cy
                 Laarstraat 5
                 B-9100 Sint-Niklaas
                 Belgium

                Tel: +32 3 780 65 00
                Fax: +32 3 780 65 49
                Web: www.newtec.be
                E-mail: techsupport@newtec.be"
    DESCRIPTION
        "Newtec modular BBFoverIP input MIB containing definitions for DVB-S2 BaseBand
        Frames over IP input functionality."

    REVISION  "201707101200Z"
    DESCRIPTION
        "Descriptions updated with regex"
    REVISION  "201409090900Z"
    DESCRIPTION
        "Minimum value of string keys adjusted"
    REVISION  "201407150800Z"
    DESCRIPTION
        "Change default multicast reception IP address"
    REVISION  "201309180800Z"
    DESCRIPTION
        "Alarms Status as Textual Conventions"
    REVISION  "201305220600Z"
    DESCRIPTION
        "Release for MDM6000 R1.1"
    REVISION  "201303271000Z"
    DESCRIPTION
        "Release for M6100 R1.3"
    REVISION  "201301081200Z"
    DESCRIPTION
        "Initial release for MDM6000 R1.0"
    ::= { ntcFunction  1200 }
    

--
-- Top-Level Structure
--

-- ntcBbfOverIpIn content

ntcBbfOIpInObjects               OBJECT-IDENTITY
    STATUS        current
    DESCRIPTION   "Container holding ntcBbfOIpInObjects definitions."
    ::= { ntcBbfOverIpIn 1 }
    
ntcBbfOIpInConformance           OBJECT-IDENTITY
    STATUS        current
    DESCRIPTION   "Conformance requirements."
    ::= { ntcBbfOverIpIn 2 }
    
-- ntcBbfOIpInObjects content

ntcBbfOIpInMonitor               OBJECT-IDENTITY
    STATUS        current
    DESCRIPTION   "Container holding ntcBbfOIpInMonitor definitions."
    ::= { ntcBbfOIpInObjects 4 }
    
ntcBbfOIpInAlarm                 OBJECT-IDENTITY
    STATUS        current
    DESCRIPTION   "Container holding ntcBbfOIpInAlarm definitions."
    ::= { ntcBbfOIpInObjects 5 }
    
-- ntcBbfOIpInConformance content

ntcBbfOIpInConfCompliance        OBJECT-IDENTITY
    STATUS        current
    DESCRIPTION   "Device compliance statements."
    ::= { ntcBbfOIpInConformance 1 }
    
ntcBbfOIpInConfGroup             OBJECT-IDENTITY
    STATUS        current
    DESCRIPTION   "Groups used by device compliance statements."
    ::= { ntcBbfOIpInConformance 2 }
    

--
-- Managed Objects
--

ntcBbfOIpInEnable                OBJECT-TYPE
    SYNTAX      NtcEnable
    MAX-ACCESS  read-write
    STATUS      current
    DESCRIPTION
        "Enable or disable BBF over IP reception."
    DEFVAL { off }
    ::= { ntcBbfOIpInObjects 1 }
    
ntcBbfOIpInInputSelection        OBJECT-TYPE
    SYNTAX      INTEGER { none(1), data1(2), data2(3), data(4), any(5) }
    MAX-ACCESS  read-write
    STATUS      current
    DESCRIPTION
        "Configures the input interface for the BBF over IP functionality."
    DEFVAL { none }
    ::= { ntcBbfOIpInObjects 2 }
    
ntcConfigurationTableTable       OBJECT-TYPE
    SYNTAX      SEQUENCE OF NtcConfigurationTableEntry
    MAX-ACCESS  not-accessible
    STATUS      current
    DESCRIPTION
        "Configuration table"
    ::= { ntcBbfOIpInObjects 3 }

ntcConfigurationTableEntry       OBJECT-TYPE
    SYNTAX      NtcConfigurationTableEntry
    MAX-ACCESS  not-accessible
    STATUS      current
    DESCRIPTION
        "A conceptual row of the ntcConfigurationTableTable."
    INDEX   { ntcConfigurationTableName  }
    ::= { ntcConfigurationTableTable 1 }

NtcConfigurationTableEntry       ::= SEQUENCE {
    ntcConfigurationTableName         DisplayString,
    ntcConfigurationTableRowStatus    RowStatus,
    ntcBbfOIpInEpEnable               NtcEnable,
    ntcBbfOIpInIpEpAddressType        INTEGER,
    ntcBbfOIpInEpMulticastAddress     IpAddress,
    ntcBbfOIpInEpIpUdpPort            Unsigned32,
    ntcBbfOIpInEpBbfType              INTEGER,
    ntcBbfOIpInEpSourceRedundancy     NtcEnable
    }
    
ntcConfigurationTableName        OBJECT-TYPE
    SYNTAX      DisplayString (SIZE(1..32))
    MAX-ACCESS  not-accessible
    STATUS      current
    DESCRIPTION
        "Name of the configuration"
    ::= { ntcConfigurationTableEntry 1 }
    
ntcConfigurationTableRowStatus   OBJECT-TYPE
    SYNTAX      RowStatus
    MAX-ACCESS  read-create
    STATUS      current
    DESCRIPTION
        "The status of this conceptual row. An existing conceptual row can be in any
        one of the three states, 'notReady', 'notInService', or 'active'. If the
        manager wishes to add a row in a single shot with values for all the columns,
        the status column should be given as 'createAndGo(4)'. After the creation of a
        row, its value is set to active(1). If a row has to be created with values for
        only some columns, the status column should be 'createAndWait(5)'. Also, this
        row with partially filled columns has the status 'notReady(3)'. The entry
        remains in this state until the values for all the columns is set. After all
        the values are set, the agent changes this value to active(1).'"
    ::= { ntcConfigurationTableEntry 2 }
    
ntcBbfOIpInEpEnable              OBJECT-TYPE
    SYNTAX      NtcEnable
    MAX-ACCESS  read-create
    STATUS      current
    DESCRIPTION
        "Enable or disable a BBF endpoint."
    ::= { ntcConfigurationTableEntry 3 }
    
ntcBbfOIpInIpEpAddressType       OBJECT-TYPE
    SYNTAX      INTEGER { unicast(0), multicast(1) }
    MAX-ACCESS  read-create
    STATUS      current
    DESCRIPTION
        "Configuration of the IP address type for BBF over IP reception. (unicast or
        multicast)"
    ::= { ntcConfigurationTableEntry 4 }
    
ntcBbfOIpInEpMulticastAddress    OBJECT-TYPE
    SYNTAX      IpAddress 
    MAX-ACCESS  read-create
    STATUS      current
    DESCRIPTION
        "Multicast IP address used to receive the BBF over IP data. Regular expression
        : (?-mix:^\d{1,3}\.\d{1,3}\.\d{1,3}\.\d{1,3}$)"
    ::= { ntcConfigurationTableEntry 5 }
    
ntcBbfOIpInEpIpUdpPort           OBJECT-TYPE
    SYNTAX      Unsigned32 (1..65535)
    MAX-ACCESS  read-create
    STATUS      current
    DESCRIPTION
        "Configuration of the UDP port on which the BBF over IP is received"
    ::= { ntcConfigurationTableEntry 6 }
    
ntcBbfOIpInEpBbfType             OBJECT-TYPE
    SYNTAX      INTEGER { dvbbbf(0), ntcbbf(1) }
    MAX-ACCESS  read-create
    STATUS      current
    DESCRIPTION
        "Type of baseband frames which are received in the BBF over IP functionality."
    ::= { ntcConfigurationTableEntry 7 }
    
ntcBbfOIpInEpSourceRedundancy    OBJECT-TYPE
    SYNTAX      NtcEnable
    MAX-ACCESS  read-create
    STATUS      current
    DESCRIPTION
        "Enable or disable source redundancy."
    ::= { ntcConfigurationTableEntry 8 }
    
ntcBbfOIpInMonCounterReset       OBJECT-TYPE
    SYNTAX      INTEGER { counting(0), reset(1) }
    MAX-ACCESS  read-write
    STATUS      current
    DESCRIPTION
        "Reset the BBF over IP traffic and monitor counters."
    DEFVAL { counting }
    ::= { ntcBbfOIpInMonitor 1 }
    
ntcBbfOIpInMonBbfInputBitRateT   OBJECT-TYPE
    SYNTAX      Unsigned32
    UNITS       "bps"
    MAX-ACCESS  read-only
    STATUS      current
    DESCRIPTION
        "Total BBF over IP input bit rate in bps."
    ::= { ntcBbfOIpInMonitor 2 }
    
ntcBbfOIpInMonBbfInCountT        OBJECT-TYPE
    SYNTAX      Counter32
    UNITS       "frames"
    MAX-ACCESS  read-only
    STATUS      current
    DESCRIPTION
        "Number of received BBFs."
    ::= { ntcBbfOIpInMonitor 3 }
    
ntcBbfOIpInMonBbfOutCountT       OBJECT-TYPE
    SYNTAX      Counter32
    UNITS       "frames"
    MAX-ACCESS  read-only
    STATUS      current
    DESCRIPTION
        "Total number of transmitted BBFs."
    ::= { ntcBbfOIpInMonitor 4 }
    
ntcBbfOIpInMonBbfDropCountT      OBJECT-TYPE
    SYNTAX      Counter32
    UNITS       "frames"
    MAX-ACCESS  read-only
    STATUS      current
    DESCRIPTION
        "Total number of dropped BBFs."
    ::= { ntcBbfOIpInMonitor 5 }
    
ntcBbfOIpInMonBbfOverflowCountT  OBJECT-TYPE
    SYNTAX      Counter32
    UNITS       "frames"
    MAX-ACCESS  read-only
    STATUS      current
    DESCRIPTION
        "Total number of BBFs that are dropped because the input data buffer is full."
    ::= { ntcBbfOIpInMonitor 6 }
    
ntcBbfOIpInMonBbfByteOutCountT   OBJECT-TYPE
    SYNTAX      Counter32
    UNITS       "bytes"
    MAX-ACCESS  read-only
    STATUS      current
    DESCRIPTION
        "This parameter counts the total number of Baseband Frame bytes properly
        transmitted"
    ::= { ntcBbfOIpInMonitor 7 }
    
ntcBbfOIpInMonBbfInvFrameCountT  OBJECT-TYPE
    SYNTAX      Counter32
    UNITS       "frames"
    MAX-ACCESS  read-only
    STATUS      current
    DESCRIPTION
        "Total number of BBFs that are dropped because the received modulation type is
        not active on the device."
    ::= { ntcBbfOIpInMonitor 8 }
    
ntcBbfOIpInMonBbfDiscontCountT   OBJECT-TYPE
    SYNTAX      Counter32
    UNITS       "frames"
    MAX-ACCESS  read-only
    STATUS      current
    DESCRIPTION
        "Total number of discontinuity counts over all BBF streams."
    ::= { ntcBbfOIpInMonitor 9 }
    
ntcBbfOIpInMonBbfModcodNSCountT  OBJECT-TYPE
    SYNTAX      Counter32
    UNITS       "frames"
    MAX-ACCESS  read-only
    STATUS      current
    DESCRIPTION
        "Total number of BBFs which are dropped because the received modcod is not
        licensed."
    ::= { ntcBbfOIpInMonitor 10 }
    
ntcMonitoringTableTable          OBJECT-TYPE
    SYNTAX      SEQUENCE OF NtcMonitoringTableEntry
    MAX-ACCESS  not-accessible
    STATUS      current
    DESCRIPTION
        "Monitoring table"
    ::= { ntcBbfOIpInMonitor 11 }

ntcMonitoringTableEntry          OBJECT-TYPE
    SYNTAX      NtcMonitoringTableEntry
    MAX-ACCESS  not-accessible
    STATUS      current
    DESCRIPTION
        "A conceptual row of the ntcMonitoringTableTable."
    INDEX   { ntcMonitoringTableName  }
    ::= { ntcMonitoringTableTable 1 }

NtcMonitoringTableEntry          ::= SEQUENCE {
    ntcMonitoringTableName            DisplayString,
    ntcBbfOIpInMonBbfInputBitRate     Unsigned32,
    ntcBbfOIpInMonSourceAddress       DisplayString,
    ntcBbfOIpInMonBbfInCount          Counter32,
    ntcBbfOIpInMonBbfOutCount         Counter32,
    ntcBbfOIpInMonBbfByteOutCount     Counter32,
    ntcBbfOIpInMonBbfDropCount        Counter32,
    ntcBbfOIpInMonBbfOverflowCount    Counter32,
    ntcBbfOIpInMonBbfInvFrameCount    Counter32,
    ntcBbfOIpInMonBbfDiscontCount     Counter32,
    ntcBbfOIpInMonBbfModNS            Counter32,
    ntcBbfOIpInMonBbfByteCorCount     Counter32,
    ntcBbfOIpInMonBbfInvSignCount     Counter32
    }
    
ntcMonitoringTableName           OBJECT-TYPE
    SYNTAX      DisplayString (SIZE(0..32))
    MAX-ACCESS  not-accessible
    STATUS      current
    DESCRIPTION
        "Name of the output monitor"
    ::= { ntcMonitoringTableEntry 1 }
    
ntcBbfOIpInMonBbfInputBitRate    OBJECT-TYPE
    SYNTAX      Unsigned32
    UNITS       "bps"
    MAX-ACCESS  read-only
    STATUS      current
    DESCRIPTION
        "BBF over IP input bit rate in bps."
    ::= { ntcMonitoringTableEntry 2 }
    
ntcBbfOIpInMonSourceAddress      OBJECT-TYPE
    SYNTAX      DisplayString (SIZE(0..32))
    MAX-ACCESS  read-only
    STATUS      current
    DESCRIPTION
        "Source sending the traffic"
    ::= { ntcMonitoringTableEntry 3 }
    
ntcBbfOIpInMonBbfInCount         OBJECT-TYPE
    SYNTAX      Counter32
    UNITS       "frames"
    MAX-ACCESS  read-only
    STATUS      current
    DESCRIPTION
        "Number of received BBFs."
    ::= { ntcMonitoringTableEntry 4 }
    
ntcBbfOIpInMonBbfOutCount        OBJECT-TYPE
    SYNTAX      Counter32
    UNITS       "frames"
    MAX-ACCESS  read-only
    STATUS      current
    DESCRIPTION
        "Number of transmitted BBFs."
    ::= { ntcMonitoringTableEntry 5 }
    
ntcBbfOIpInMonBbfByteOutCount    OBJECT-TYPE
    SYNTAX      Counter32
    UNITS       "bytes"
    MAX-ACCESS  read-only
    STATUS      current
    DESCRIPTION
        "This parameter counts the number of Baseband Frame bytes properly transmitted
        in a stream."
    ::= { ntcMonitoringTableEntry 6 }
    
ntcBbfOIpInMonBbfDropCount       OBJECT-TYPE
    SYNTAX      Counter32
    UNITS       "frames"
    MAX-ACCESS  read-only
    STATUS      current
    DESCRIPTION
        "Number of dropped BBFs."
    ::= { ntcMonitoringTableEntry 7 }
    
ntcBbfOIpInMonBbfOverflowCount   OBJECT-TYPE
    SYNTAX      Counter32
    UNITS       "frames"
    MAX-ACCESS  read-only
    STATUS      current
    DESCRIPTION
        "Number of BBFs that are dropped for a specific BBF stream because the input
        data buffer is full."
    ::= { ntcMonitoringTableEntry 8 }
    
ntcBbfOIpInMonBbfInvFrameCount   OBJECT-TYPE
    SYNTAX      Counter32
    UNITS       "frames"
    MAX-ACCESS  read-only
    STATUS      current
    DESCRIPTION
        "Number of BBFs that are dropped because the received modulation type is not
        active on the device."
    ::= { ntcMonitoringTableEntry 9 }
    
ntcBbfOIpInMonBbfDiscontCount    OBJECT-TYPE
    SYNTAX      Counter32
    UNITS       "frames"
    MAX-ACCESS  read-only
    STATUS      current
    DESCRIPTION
        "When the sequence numbers are not continuous for a certain BBF stream this
        counter will be incremented."
    ::= { ntcMonitoringTableEntry 10 }
    
ntcBbfOIpInMonBbfModNS           OBJECT-TYPE
    SYNTAX      Counter32
    UNITS       "frames"
    MAX-ACCESS  read-only
    STATUS      current
    DESCRIPTION
        "Number of BBFs which are dropped because the received modcod is not licensed
        for a specified BBF stream."
    ::= { ntcMonitoringTableEntry 11 }
    
ntcBbfOIpInMonBbfByteCorCount    OBJECT-TYPE
    SYNTAX      Counter32
    UNITS       "bytes"
    MAX-ACCESS  read-only
    STATUS      current
    DESCRIPTION
        "This parameter counts the number of corrupted Baseband Frame bytes that are
        dropped for a certain BBF stream."
    ::= { ntcMonitoringTableEntry 12 }
    
ntcBbfOIpInMonBbfInvSignCount    OBJECT-TYPE
    SYNTAX      Counter32
    UNITS       "frames"
    MAX-ACCESS  read-only
    STATUS      current
    DESCRIPTION
        "This parameter counts the number of invalid Tellitec Signalling Frames that
        are dropped for a certain BBF stream."
    ::= { ntcMonitoringTableEntry 13 }
    
ntcAlarmStatusTableTable         OBJECT-TYPE
    SYNTAX      SEQUENCE OF NtcAlarmStatusTableEntry
    MAX-ACCESS  not-accessible
    STATUS      current
    DESCRIPTION
        "Alarm status table"
    ::= { ntcBbfOIpInMonitor 12 }

ntcAlarmStatusTableEntry         OBJECT-TYPE
    SYNTAX      NtcAlarmStatusTableEntry
    MAX-ACCESS  not-accessible
    STATUS      current
    DESCRIPTION
        "A conceptual row of the ntcAlarmStatusTableTable."
    INDEX   { ntcStreamInx  }
    ::= { ntcAlarmStatusTableTable 1 }

NtcAlarmStatusTableEntry         ::= SEQUENCE {
    ntcStreamInx                       DisplayString,
    ntcBbfOIpInMonBbfNoInpDataError    NtcAlarmState,
    ntcBbfOverflowError                NtcAlarmState,
    ntcBbfDiscontinuityError           NtcAlarmState,
    ntcBbfModcodNotSupportedError      NtcAlarmState
    }
    
ntcStreamInx                     OBJECT-TYPE
    SYNTAX      DisplayString (SIZE(0..32))
    MAX-ACCESS  not-accessible
    STATUS      current
    DESCRIPTION
        "Name of the alarm monitor"
    ::= { ntcAlarmStatusTableEntry 1 }
    
ntcBbfOIpInMonBbfNoInpDataError  OBJECT-TYPE
    SYNTAX      NtcAlarmState
    MAX-ACCESS  read-only
    STATUS      current
    DESCRIPTION
        "This alarm is raised when no input data is received between a 1 second time
        interval for 1 or more BBF streams. This variable indicates the current status
        of the alarm."
    ::= { ntcAlarmStatusTableEntry 2 }
    
ntcBbfOverflowError              OBJECT-TYPE
    SYNTAX      NtcAlarmState
    MAX-ACCESS  read-only
    STATUS      current
    DESCRIPTION
        "This alarm is raised when the input data buffer for 1 or more BBF streams is
        full. This variable indicates the current status of the alarm."
    ::= { ntcAlarmStatusTableEntry 3 }
    
ntcBbfDiscontinuityError         OBJECT-TYPE
    SYNTAX      NtcAlarmState
    MAX-ACCESS  read-only
    STATUS      current
    DESCRIPTION
        "The alarm is raised when the sequence numbers are not continuous for a
        specific ntS2BBF input stream for 5 sec. This variable indicates the current
        status of the alarm."
    ::= { ntcAlarmStatusTableEntry 4 }
    
ntcBbfModcodNotSupportedError    OBJECT-TYPE
    SYNTAX      NtcAlarmState
    MAX-ACCESS  read-only
    STATUS      current
    DESCRIPTION
        "This alarm is raised when Baseband frames are dropped due to receiving a non
        licensed modcod. This variable indicates the current status of the alarm."
    ::= { ntcAlarmStatusTableEntry 5 }
    
ntcBbfOIpInMonBbfByteCorCountT   OBJECT-TYPE
    SYNTAX      Counter32
    UNITS       "bytes"
    MAX-ACCESS  read-only
    STATUS      current
    DESCRIPTION
        "Total number of corrupted Baseband Frame bytes that are dropped for all BBF
        streams."
    ::= { ntcBbfOIpInMonitor 13 }
    
ntcBbfOIpInMonBbfInvSignCountT   OBJECT-TYPE
    SYNTAX      Counter32
    UNITS       "frames"
    MAX-ACCESS  read-only
    STATUS      current
    DESCRIPTION
        "Total number of invalid Tellitec Signalling Frames that are dropped for all
        BBF streams."
    ::= { ntcBbfOIpInMonitor 14 }
    
ntcBbfOIpInAlmGeneralBbfOverIpIn OBJECT-TYPE
    SYNTAX      NtcAlarmState
    MAX-ACCESS  read-only
    STATUS      current
    DESCRIPTION
        "This alarm is raised when there is a general BBF over IP Input alarm. This
        variable indicates the current status of the alarm."
    ::= { ntcBbfOIpInAlarm 1 }
    
ntcBbfOIpInAlmNoInputData        OBJECT-TYPE
    SYNTAX      NtcAlarmState
    MAX-ACCESS  read-only
    STATUS      current
    DESCRIPTION
        "This alarm is raised when no input data is received between a 1 second time
        interval for 1 or more BBF streams. This variable indicates the current status
        of the alarm."
    ::= { ntcBbfOIpInAlarm 2 }
    
ntcBbfOIpInAlmBufferOverflow     OBJECT-TYPE
    SYNTAX      NtcAlarmState
    MAX-ACCESS  read-only
    STATUS      current
    DESCRIPTION
        "This alarm is raised when the input data buffer for 1 or more BBF streams is
        full. This variable indicates the current status of the alarm."
    ::= { ntcBbfOIpInAlarm 3 }
    
ntcBbfOIpInAlBbfOverIPDiscont    OBJECT-TYPE
    SYNTAX      NtcAlarmState
    MAX-ACCESS  read-only
    STATUS      current
    DESCRIPTION
        "The alarm is raised when the sequence numbers are not continuous for a
        specific ntS2BBF input stream for 5 sec. This variable indicates the current
        status of the alarm."
    ::= { ntcBbfOIpInAlarm 4 }
    
ntcBbfOIpInAlBbfOverIPModNS      OBJECT-TYPE
    SYNTAX      NtcAlarmState
    MAX-ACCESS  read-only
    STATUS      current
    DESCRIPTION
        "This alarm is raised when Baseband frames are dropped due to receiving a non
        licensed modcod. This variable indicates the current status of the alarm."
    ::= { ntcBbfOIpInAlarm 5 }
    

--
--  Module Conformance
--

ntcBbfOIpInConfGrpV1Standard     OBJECT-GROUP
    OBJECTS    {
                   ntcBbfOIpInEnable,
                   ntcBbfOIpInInputSelection,
                   ntcConfigurationTableRowStatus,
                   ntcBbfOIpInEpEnable,
                   ntcBbfOIpInIpEpAddressType,
                   ntcBbfOIpInEpMulticastAddress,
                   ntcBbfOIpInEpIpUdpPort,
                   ntcBbfOIpInEpBbfType,
                   ntcBbfOIpInEpSourceRedundancy,
                   ntcBbfOIpInMonCounterReset,
                   ntcBbfOIpInMonBbfInputBitRateT,
                   ntcBbfOIpInMonBbfInCountT,
                   ntcBbfOIpInMonBbfOutCountT,
                   ntcBbfOIpInMonBbfDropCountT,
                   ntcBbfOIpInMonBbfOverflowCountT,
                   ntcBbfOIpInMonBbfByteOutCountT,
                   ntcBbfOIpInMonBbfInvFrameCountT,
                   ntcBbfOIpInMonBbfDiscontCountT,
                   ntcBbfOIpInMonBbfModcodNSCountT,
                   ntcBbfOIpInMonBbfInputBitRate,
                   ntcBbfOIpInMonSourceAddress,
                   ntcBbfOIpInMonBbfInCount,
                   ntcBbfOIpInMonBbfOutCount,
                   ntcBbfOIpInMonBbfByteOutCount,
                   ntcBbfOIpInMonBbfDropCount,
                   ntcBbfOIpInMonBbfOverflowCount,
                   ntcBbfOIpInMonBbfInvFrameCount,
                   ntcBbfOIpInMonBbfDiscontCount,
                   ntcBbfOIpInMonBbfModNS,
                   ntcBbfOIpInMonBbfByteCorCount,
                   ntcBbfOIpInMonBbfInvSignCount,
                   ntcBbfOIpInMonBbfNoInpDataError,
                   ntcBbfOverflowError,
                   ntcBbfDiscontinuityError,
                   ntcBbfModcodNotSupportedError,
                   ntcBbfOIpInMonBbfByteCorCountT,
                   ntcBbfOIpInMonBbfInvSignCountT,
                   ntcBbfOIpInAlmGeneralBbfOverIpIn,
                   ntcBbfOIpInAlmNoInputData,
                   ntcBbfOIpInAlmBufferOverflow,
                   ntcBbfOIpInAlBbfOverIPDiscont,
                   ntcBbfOIpInAlBbfOverIPModNS
               }
    STATUS      current
    DESCRIPTION
        "Managed objects that constitute version 1 of a system device with standard capabilities."
    ::= { ntcBbfOIpInConfGroup 1}
    
ntcBbfOIpInConfCompV1Standard    MODULE-COMPLIANCE
    STATUS      current
    DESCRIPTION
        "Compliance statement for Newtec device MIB implementations."
    MODULE  -- this module
    MANDATORY-GROUPS
                  {
                      ntcBbfOIpInConfGrpV1Standard
                  }
    ::= { ntcBbfOIpInConfCompliance  1 }
    

END

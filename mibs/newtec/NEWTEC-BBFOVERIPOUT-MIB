NEWTEC-BBFOVERIPOUT-MIB DEFINITIONS ::= BEGIN

IMPORTS
    IpAddress,
    Unsigned32,
    Counter32,
    MODULE-IDENTITY,
    OBJECT-IDENTITY,
    OBJECT-TYPE
        FROM SNMPv2-SMI

    MODULE-COMPLIANCE,
    OBJECT-GROUP
        FROM SNMPv2-CONF
    
    NtcEnable
        FROM NEWTEC-TC-MIB

    ntcFunction
        FROM NEWTEC-MAIN-MIB;


--
--  Module Identification
--

ntcBbfOverIpOut   MODULE-IDENTITY
    LAST-UPDATED "201802020900Z"
    ORGANIZATION "Newtec Cy"
    CONTACT-INFO
        "Newtec Cy
         Postal: Newtec Cy
                 Laarstraat 5
                 B-9100 Sint-Niklaas
                 Belgium

                Tel: +32 3 780 65 00
                Fax: +32 3 780 65 49
                Web: www.newtec.be
                E-mail: techsupport@newtec.be"
    DESCRIPTION
        "Newtec modular BBFoverIP output MIB containing definitions for DVB-S2 BaseBand
        Frames over IP output functionality."

    REVISION  "201802020900Z"
    DESCRIPTION
        "Description of ntcBbfOIpOutDestinationIpAddress extended with regex."
    REVISION  "201710161200Z"
    DESCRIPTION
        "ntcBbfOIpOutEncapProt column added to ntcBbfOIpOutDestinations table"
    REVISION  "201504130700Z"
    DESCRIPTION
        "ntcBbfOIpOutDestinations and ntcBbfOIpOutMonInvalFram added"
    REVISION  "201305220600Z"
    DESCRIPTION
        "Release for MDM6000 R1.1"
    REVISION  "201301081200Z"
    DESCRIPTION
        "Initial release for MDM6000 R1.0"
    ::= { ntcFunction  1300 }
    

--
-- Top-Level Structure
--

-- ntcBbfOverIpOut content

ntcBbfOIpOutObjects              OBJECT-IDENTITY
    STATUS        current
    DESCRIPTION   "Container holding ntcBbfOIpOutObjects definitions."
    ::= { ntcBbfOverIpOut 1 }
    
ntcBbfOIpOutConformance          OBJECT-IDENTITY
    STATUS        current
    DESCRIPTION   "Conformance requirements."
    ::= { ntcBbfOverIpOut 2 }
    
-- ntcBbfOIpOutObjects content

ntcBbfOIpOutMonitor              OBJECT-IDENTITY
    STATUS        current
    DESCRIPTION   "Container holding ntcBbfOIpOutMonitor definitions."
    ::= { ntcBbfOIpOutObjects 4 }
    
-- ntcBbfOIpOutConformance content

ntcBbfOIpOutConfCompliance       OBJECT-IDENTITY
    STATUS        current
    DESCRIPTION   "Device compliance statements."
    ::= { ntcBbfOIpOutConformance 1 }
    
ntcBbfOIpOutConfGroup            OBJECT-IDENTITY
    STATUS        current
    DESCRIPTION   "Groups used by device compliance statements."
    ::= { ntcBbfOIpOutConformance 2 }
    

--
-- Managed Objects
--

ntcBbfOIpOutEnable               OBJECT-TYPE
    SYNTAX      NtcEnable
    MAX-ACCESS  read-write
    STATUS      current
    DESCRIPTION
        "Enable or disable BBF over IP transmission."
    DEFVAL { off }
    ::= { ntcBbfOIpOutObjects 1 }
    
ntcBbfOIpOutOutputSelection      OBJECT-TYPE
    SYNTAX      INTEGER { data1(1), data2(2), data(3), sat1(4), sat2(5), sat(6) }
    MAX-ACCESS  read-write
    STATUS      current
    DESCRIPTION
        "Configures the output interface for the BBF over IP functionality."
    DEFVAL { data1 }
    ::= { ntcBbfOIpOutObjects 2 }
    
ntcBbfOIpOutDestinationsTable    OBJECT-TYPE
    SYNTAX      SEQUENCE OF NtcBbfOIpOutDestinationsEntry
    MAX-ACCESS  not-accessible
    STATUS      current
    DESCRIPTION
        "A table containing the ntcBbfOIpOutDestinations"
    ::= { ntcBbfOIpOutObjects 3 }

ntcBbfOIpOutDestinationsEntry    OBJECT-TYPE
    SYNTAX      NtcBbfOIpOutDestinationsEntry
    MAX-ACCESS  not-accessible
    STATUS      current
    DESCRIPTION
        "A conceptual row of the ntcBbfOIpOutDestinationsTable."
    INDEX   { ntcBbfOIpOutDestinationsDemodId  }
    ::= { ntcBbfOIpOutDestinationsTable 1 }

NtcBbfOIpOutDestinationsEntry    ::= SEQUENCE {
    ntcBbfOIpOutDestinationsDemodId     INTEGER,
    ntcBbfOIpOutBbfOutEnable            NtcEnable,
    ntcBbfOIpOutDestinationIpAddress    IpAddress,
    ntcBbfOIpOutDestinationUdpPort      Unsigned32,
    ntcBbfOIpOutPassInvalidFrames       NtcEnable,
    ntcBbfOIpOutEncapProt               INTEGER
    }
    
ntcBbfOIpOutDestinationsDemodId  OBJECT-TYPE
    SYNTAX      INTEGER { demod1(1), demod2(2), demod3(3) }
    MAX-ACCESS  not-accessible
    STATUS      current
    DESCRIPTION
        "The id of the demodulator"
    ::= { ntcBbfOIpOutDestinationsEntry 1 }
    
ntcBbfOIpOutBbfOutEnable         OBJECT-TYPE
    SYNTAX      NtcEnable
    MAX-ACCESS  read-write
    STATUS      current
    DESCRIPTION
        "Enable or disable BBF over IP output stream."
    DEFVAL { off }
    ::= { ntcBbfOIpOutDestinationsEntry 2 }
    
ntcBbfOIpOutDestinationIpAddress OBJECT-TYPE
    SYNTAX      IpAddress 
    MAX-ACCESS  read-write
    STATUS      current
    DESCRIPTION
        "IP address used to send the BBF over IP data to. Regular expression :
        (?-mix:^\d{1,3}\.\d{1,3}\.\d{1,3}\.\d{1,3}$)"
    ::= { ntcBbfOIpOutDestinationsEntry 3 }
    
ntcBbfOIpOutDestinationUdpPort   OBJECT-TYPE
    SYNTAX      Unsigned32 (1..65535)
    MAX-ACCESS  read-write
    STATUS      current
    DESCRIPTION
        "Configuration of the UDP port to which the BBF over IP is sent"
    ::= { ntcBbfOIpOutDestinationsEntry 4 }
    
ntcBbfOIpOutPassInvalidFrames    OBJECT-TYPE
    SYNTAX      NtcEnable
    MAX-ACCESS  read-write
    STATUS      current
    DESCRIPTION
        "Enable the transmission of invalid basebandframes."
    DEFVAL { off }
    ::= { ntcBbfOIpOutDestinationsEntry 5 }
    
ntcBbfOIpOutEncapProt            OBJECT-TYPE
    SYNTAX      INTEGER { udp(0), rtp(1) }
    MAX-ACCESS  read-write
    STATUS      current
    DESCRIPTION
        "Encapsulation protocol used for the output BBF over IP functionality (UDP or
        RTP)."
    DEFVAL { udp }
    ::= { ntcBbfOIpOutDestinationsEntry 6 }
    
ntcBbfOIpOutMonReset             OBJECT-TYPE
    SYNTAX      INTEGER { counting(0), reset(1) }
    MAX-ACCESS  read-write
    STATUS      current
    DESCRIPTION
        "Reset the BBF over IP traffic and monitor counters."
    DEFVAL { counting }
    ::= { ntcBbfOIpOutMonitor 1 }
    
ntcBbfOIpOutMonOutputBbfBitRate  OBJECT-TYPE
    SYNTAX      Unsigned32
    UNITS       "bps"
    MAX-ACCESS  read-only
    STATUS      current
    DESCRIPTION
        "BBF over IP output bit rate in bps."
    ::= { ntcBbfOIpOutMonitor 2 }
    
ntcBbfOIpOutMonBbfInCount        OBJECT-TYPE
    SYNTAX      Counter32
    UNITS       "frames"
    MAX-ACCESS  read-only
    STATUS      current
    DESCRIPTION
        "Number of received BBFs."
    ::= { ntcBbfOIpOutMonitor 3 }
    
ntcBbfOIpOutMonBbfOutCount       OBJECT-TYPE
    SYNTAX      Counter32
    UNITS       "frames"
    MAX-ACCESS  read-only
    STATUS      current
    DESCRIPTION
        "Number of transmitted BBFs."
    ::= { ntcBbfOIpOutMonitor 4 }
    
ntcBbfOIpOutMonBbfDropCount      OBJECT-TYPE
    SYNTAX      Counter32
    UNITS       "frames"
    MAX-ACCESS  read-only
    STATUS      current
    DESCRIPTION
        "Number of dropped BBFs."
    ::= { ntcBbfOIpOutMonitor 5 }
    
ntcBbfOIpOutMonDestTable         OBJECT-TYPE
    SYNTAX      SEQUENCE OF NtcBbfOIpOutMonDestEntry
    MAX-ACCESS  not-accessible
    STATUS      current
    DESCRIPTION
        "A table containing the ntcBbfOIpOutMonDest"
    ::= { ntcBbfOIpOutMonitor 6 }

ntcBbfOIpOutMonDestEntry         OBJECT-TYPE
    SYNTAX      NtcBbfOIpOutMonDestEntry
    MAX-ACCESS  not-accessible
    STATUS      current
    DESCRIPTION
        "A conceptual row of the ntcBbfOIpOutMonDestTable."
    INDEX   { ntcBbfOIpOutMonDestDemodId  }
    ::= { ntcBbfOIpOutMonDestTable 1 }

NtcBbfOIpOutMonDestEntry         ::= SEQUENCE {
    ntcBbfOIpOutMonDestDemodId         INTEGER,
    ntcBbfOIpOutMonDestBitRate         Unsigned32,
    ntcBbfOIpOutMonDestBbfInCount      Counter32,
    ntcBbfOIpOutMonDestBbfOutCount     Counter32,
    ntcBbfOIpOutMonDestBbfDropCount    Counter32
    }
    
ntcBbfOIpOutMonDestDemodId       OBJECT-TYPE
    SYNTAX      INTEGER { demod1(1), demod2(2), demod3(3) }
    MAX-ACCESS  not-accessible
    STATUS      current
    DESCRIPTION
        "The id of the demodulator"
    ::= { ntcBbfOIpOutMonDestEntry 1 }
    
ntcBbfOIpOutMonDestBitRate       OBJECT-TYPE
    SYNTAX      Unsigned32
    UNITS       "bps"
    MAX-ACCESS  read-only
    STATUS      current
    DESCRIPTION
        "BBF over IP output bit rate in bps."
    ::= { ntcBbfOIpOutMonDestEntry 2 }
    
ntcBbfOIpOutMonDestBbfInCount    OBJECT-TYPE
    SYNTAX      Counter32
    UNITS       "frames"
    MAX-ACCESS  read-only
    STATUS      current
    DESCRIPTION
        "Number of received BBFs."
    ::= { ntcBbfOIpOutMonDestEntry 3 }
    
ntcBbfOIpOutMonDestBbfOutCount   OBJECT-TYPE
    SYNTAX      Counter32
    UNITS       "frames"
    MAX-ACCESS  read-only
    STATUS      current
    DESCRIPTION
        "Number of transmitted BBFs."
    ::= { ntcBbfOIpOutMonDestEntry 4 }
    
ntcBbfOIpOutMonDestBbfDropCount  OBJECT-TYPE
    SYNTAX      Counter32
    UNITS       "frames"
    MAX-ACCESS  read-only
    STATUS      current
    DESCRIPTION
        "Number of dropped BBFs."
    ::= { ntcBbfOIpOutMonDestEntry 5 }
    
ntcBbfOIpOutMonInvalFramTable    OBJECT-TYPE
    SYNTAX      SEQUENCE OF NtcBbfOIpOutMonInvalFramEntry
    MAX-ACCESS  not-accessible
    STATUS      current
    DESCRIPTION
        "A table containing the ntcBbfOIpOutMonInvalFram"
    ::= { ntcBbfOIpOutMonitor 7 }

ntcBbfOIpOutMonInvalFramEntry    OBJECT-TYPE
    SYNTAX      NtcBbfOIpOutMonInvalFramEntry
    MAX-ACCESS  not-accessible
    STATUS      current
    DESCRIPTION
        "A conceptual row of the ntcBbfOIpOutMonInvalFramTable."
    INDEX   { ntcBbfOIpOutMonInvalFramDemodId  }
    ::= { ntcBbfOIpOutMonInvalFramTable 1 }

NtcBbfOIpOutMonInvalFramEntry    ::= SEQUENCE {
    ntcBbfOIpOutMonInvalFramDemodId    INTEGER,
    ntcBbfOIpOutMonInvalCrc8           Counter32,
    ntcBbfOIpOutMonInvalPadd           Counter32
    }
    
ntcBbfOIpOutMonInvalFramDemodId  OBJECT-TYPE
    SYNTAX      INTEGER { demod1(1), demod2(2), demod3(3) }
    MAX-ACCESS  not-accessible
    STATUS      current
    DESCRIPTION
        "The id of the demodulator"
    ::= { ntcBbfOIpOutMonInvalFramEntry 1 }
    
ntcBbfOIpOutMonInvalCrc8         OBJECT-TYPE
    SYNTAX      Counter32
    UNITS       "frames"
    MAX-ACCESS  read-only
    STATUS      current
    DESCRIPTION
        "Number of transmitted BBFs with CRC 8 errors in the BBF header"
    ::= { ntcBbfOIpOutMonInvalFramEntry 2 }
    
ntcBbfOIpOutMonInvalPadd         OBJECT-TYPE
    SYNTAX      Counter32
    UNITS       "frames"
    MAX-ACCESS  read-only
    STATUS      current
    DESCRIPTION
        "Number of transmitted BBFs with non-zero padding"
    ::= { ntcBbfOIpOutMonInvalFramEntry 3 }
    

--
--  Module Conformance
--

ntcBbfOIpOutConfGrpV1Standard    OBJECT-GROUP
    OBJECTS    {
                   ntcBbfOIpOutEnable,
                   ntcBbfOIpOutOutputSelection,
                   ntcBbfOIpOutBbfOutEnable,
                   ntcBbfOIpOutDestinationIpAddress,
                   ntcBbfOIpOutDestinationUdpPort,
                   ntcBbfOIpOutPassInvalidFrames,
                   ntcBbfOIpOutEncapProt,
                   ntcBbfOIpOutMonReset,
                   ntcBbfOIpOutMonOutputBbfBitRate,
                   ntcBbfOIpOutMonBbfInCount,
                   ntcBbfOIpOutMonBbfOutCount,
                   ntcBbfOIpOutMonBbfDropCount,
                   ntcBbfOIpOutMonDestBitRate,
                   ntcBbfOIpOutMonDestBbfInCount,
                   ntcBbfOIpOutMonDestBbfOutCount,
                   ntcBbfOIpOutMonDestBbfDropCount,
                   ntcBbfOIpOutMonInvalCrc8,
                   ntcBbfOIpOutMonInvalPadd
               }
    STATUS      current
    DESCRIPTION
        "Managed objects that constitute version 1 of a system device with standard capabilities."
    ::= { ntcBbfOIpOutConfGroup 1}
    
ntcBbfOIpOutConfCompV1Standard   MODULE-COMPLIANCE
    STATUS      current
    DESCRIPTION
        "Compliance statement for Newtec device MIB implementations."
    MODULE  -- this module
    MANDATORY-GROUPS
                  {
                      ntcBbfOIpOutConfGrpV1Standard
                  }
    ::= { ntcBbfOIpOutConfCompliance  1 }
    

END

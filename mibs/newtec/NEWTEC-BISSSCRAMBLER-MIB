NEWTEC-BISSSCRAMBLER-MIB DEFINITIONS ::= BEGIN

IMPORTS
    Unsigned32,
    MODULE-IDENTITY,
    OBJECT-IDENTITY,
    OBJECT-TYPE
        FROM SNMPv2-SMI

    MODULE-COMPLIANCE,
    OBJECT-GROUP
        FROM SNMPv2-CONF
    
    NtcAlarmState,
    NtcEnable
        FROM NEWTEC-TC-MIB

    DisplayString
        FROM SNMPv2-TC

    ntcFunction
        FROM NEWTEC-MAIN-MIB;


--
--  Module Identification
--

ntcBissScrambler   MODULE-IDENTITY
    LAST-UPDATED "201707101200Z"
    ORGANIZATION "Newtec Cy"
    CONTACT-INFO
        "Newtec Cy
         Postal: Newtec Cy
                 Laarstraat 5
                 B-9100 Sint-Niklaas
                 Belgium

                Tel: +32 3 780 65 00
                Fax: +32 3 780 65 49
                Web: www.newtec.be
                E-mail: techsupport@newtec.be"
    DESCRIPTION
        "Newtec Biss Scrambler MIB"

    REVISION  "201707101200Z"
    DESCRIPTION
        "Descriptions updated with regex"
    REVISION  "201409090900Z"
    DESCRIPTION
        "Minimum value of string keys adjusted"
    REVISION  "201307021000Z"
    DESCRIPTION
        "BissKey default changed"
    REVISION  "201303271000Z"
    DESCRIPTION
        "Initial release for M6100 R1.3"
    ::= { ntcFunction  3100 }
    

--
-- Top-Level Structure
--

-- ntcBissScrambler content

ntcBissScrObjects                OBJECT-IDENTITY
    STATUS        current
    DESCRIPTION   "Container holding ntcBissScrObjects definitions."
    ::= { ntcBissScrambler 1 }
    
ntcBissScrConformance            OBJECT-IDENTITY
    STATUS        current
    DESCRIPTION   "Conformance requirements."
    ::= { ntcBissScrambler 2 }
    
-- ntcBissScrObjects content

ntcBissScrKeys                   OBJECT-IDENTITY
    STATUS        current
    DESCRIPTION   "Container holding ntcBissScrKeys definitions."
    ::= { ntcBissScrObjects 7 }
    
ntcBissMonitor                   OBJECT-IDENTITY
    STATUS        current
    DESCRIPTION   "Container holding ntcBissMonitor definitions."
    ::= { ntcBissScrObjects 8 }
    
ntcBissAlarms                    OBJECT-IDENTITY
    STATUS        current
    DESCRIPTION   "Container holding ntcBissAlarms definitions."
    ::= { ntcBissScrObjects 9 }
    
-- ntcBissScrConformance content

ntcBissScrConfCompliance         OBJECT-IDENTITY
    STATUS        current
    DESCRIPTION   "Device compliance statements."
    ::= { ntcBissScrConformance 1 }
    
ntcBissScrConfGroup              OBJECT-IDENTITY
    STATUS        current
    DESCRIPTION   "Groups used by device compliance statements."
    ::= { ntcBissScrConformance 2 }
    

--
-- Managed Objects
--

ntcBissScrambling                OBJECT-TYPE
    SYNTAX      NtcEnable
    MAX-ACCESS  read-write
    STATUS      current
    DESCRIPTION
        "Enable or disable the scrambling."
    DEFVAL { off }
    ::= { ntcBissScrObjects 1 }
    
ntcBissScramblingMode            OBJECT-TYPE
    SYNTAX      INTEGER { standard(0), raw(1) }
    MAX-ACCESS  read-write
    STATUS      current
    DESCRIPTION
        "The scrambling mode which can be standard or raw."
    DEFVAL { standard }
    ::= { ntcBissScrObjects 2 }
    
ntcBissKeyParity                 OBJECT-TYPE
    SYNTAX      INTEGER { odd(0), even(1) }
    MAX-ACCESS  read-write
    STATUS      current
    DESCRIPTION
        "Specify whether the odd or even session word will be used"
    DEFVAL { even }
    ::= { ntcBissScrObjects 3 }
    
ntcBissScramblingSuppression     OBJECT-TYPE
    SYNTAX      INTEGER { disabled(0), enabled(1) }
    MAX-ACCESS  read-write
    STATUS      current
    DESCRIPTION
        "Suppress scrambling when a PAT or PMT error occurs"
    DEFVAL { enabled }
    ::= { ntcBissScrObjects 4 }
    
ntcBissMinRawUnscrambledPid      OBJECT-TYPE
    SYNTAX      Unsigned32 (0..8190)
    MAX-ACCESS  read-write
    STATUS      current
    DESCRIPTION
        "The low range PID not to scramble in Raw mode"
    DEFVAL { 0 }
    ::= { ntcBissScrObjects 5 }
    
ntcBissMaxRawUnscrambledPid      OBJECT-TYPE
    SYNTAX      Unsigned32 (0..8190)
    MAX-ACCESS  read-write
    STATUS      current
    DESCRIPTION
        "The high range PID not to scramble in Raw mode"
    DEFVAL { 31 }
    ::= { ntcBissScrObjects 6 }
    
ntcBissClearKeys                 OBJECT-TYPE
    SYNTAX      INTEGER { donothing(0), clearkeys(1) }
    MAX-ACCESS  read-write
    STATUS      current
    DESCRIPTION
        "Erase all the keys"
    DEFVAL { donothing }
    ::= { ntcBissScrKeys 1 }
    
ntcBissEvenSessionWord           OBJECT-TYPE
    SYNTAX      DisplayString (SIZE(12..12))
    MAX-ACCESS  read-write
    STATUS      current
    DESCRIPTION
        "The clear even session word. Regular expression :
        (?-mix:[A-Fa-f0-9]{12}|[\*]{12})"
    DEFVAL { "************" }
    ::= { ntcBissScrKeys 2 }
    
ntcBissOddSessionWord            OBJECT-TYPE
    SYNTAX      DisplayString (SIZE(12..12))
    MAX-ACCESS  read-write
    STATUS      current
    DESCRIPTION
        "The clear odd session word. Regular expression :
        (?-mix:[A-Fa-f0-9]{12}|[\*]{12})"
    DEFVAL { "************" }
    ::= { ntcBissScrKeys 3 }
    
ntcBissEncryptedEvenSessionWord  OBJECT-TYPE
    SYNTAX      DisplayString (SIZE(16..16))
    MAX-ACCESS  read-write
    STATUS      current
    DESCRIPTION
        "The encrypted even session word. Regular expression :
        (?-mix:[A-Fa-f0-9]{16}|[\*]{16})"
    DEFVAL { "****************" }
    ::= { ntcBissScrKeys 4 }
    
ntcBissEncryptedOddSessionWord   OBJECT-TYPE
    SYNTAX      DisplayString (SIZE(16..16))
    MAX-ACCESS  read-write
    STATUS      current
    DESCRIPTION
        "The encrypted odd session word. Regular expression :
        (?-mix:[A-Fa-f0-9]{16}|[\*]{16})"
    DEFVAL { "****************" }
    ::= { ntcBissScrKeys 5 }
    
ntcBissInKeyEncryptionMode       OBJECT-TYPE
    SYNTAX      INTEGER { buried(0), injected(1) }
    MAX-ACCESS  read-write
    STATUS      current
    DESCRIPTION
        "The encryption mode used for encrypted session words. This can be the buried
        Id or the injected Id."
    DEFVAL { buried }
    ::= { ntcBissScrKeys 6 }
    
ntcBissInjectedId                OBJECT-TYPE
    SYNTAX      DisplayString (SIZE(14..14))
    MAX-ACCESS  read-write
    STATUS      current
    DESCRIPTION
        "The injected identifier for decrypting the encrypted session word Regular
        expression : (?-mix:[A-Fa-f0-9]{14}|[\*]{14})"
    DEFVAL { "00000000000000" }
    ::= { ntcBissScrKeys 7 }
    
ntcBissBuriedId                  OBJECT-TYPE
    SYNTAX      DisplayString (SIZE(14..14))
    MAX-ACCESS  read-only
    STATUS      current
    DESCRIPTION
        "The Buried identifier for decrypting the encrypted session word"
    ::= { ntcBissScrKeys 8 }
    
ntcBissSetupId                   OBJECT-TYPE
    SYNTAX      DisplayString (SIZE(12..12))
    MAX-ACCESS  read-write
    STATUS      current
    DESCRIPTION
        "User specified Setup ID Regular expression : (?-mix:[A-Fa-f0-9]{12}|[\*]{12})"
    DEFVAL { "BD28121969BD" }
    ::= { ntcBissScrKeys 9 }
    
ntcBissScramblingState           OBJECT-TYPE
    SYNTAX      INTEGER { scrambling(0), suppressed(1), unscrambled(2) }
    MAX-ACCESS  read-only
    STATUS      current
    DESCRIPTION
        "The real state of the scrambler"
    ::= { ntcBissMonitor 1 }
    
ntcBissSessionWordChanged        OBJECT-TYPE
    SYNTAX      DisplayString (SIZE(0..30))
    MAX-ACCESS  read-only
    STATUS      current
    DESCRIPTION
        "The date and time when the session word was changed for the last time"
    ::= { ntcBissMonitor 2 }
    
ntcGeneralBissError              OBJECT-TYPE
    SYNTAX      NtcAlarmState
    MAX-ACCESS  read-only
    STATUS      current
    DESCRIPTION
        "This alarm is raised when there is a general Biss error This variable
        indicates the current status of the alarm."
    ::= { ntcBissAlarms 1 }
    
ntcPatError                      OBJECT-TYPE
    SYNTAX      NtcAlarmState
    MAX-ACCESS  read-only
    STATUS      current
    DESCRIPTION
        "This alarm is raised when the CRC of the PAT is not valid. This variable
        indicates the current status of the alarm."
    ::= { ntcBissAlarms 2 }
    
ntcPmtError                      OBJECT-TYPE
    SYNTAX      NtcAlarmState
    MAX-ACCESS  read-only
    STATUS      current
    DESCRIPTION
        "This alarm is raised when the CRC of the PMT is not valid. This variable
        indicates the current status of the alarm."
    ::= { ntcBissAlarms 3 }
    
ntcCatError                      OBJECT-TYPE
    SYNTAX      NtcAlarmState
    MAX-ACCESS  read-only
    STATUS      current
    DESCRIPTION
        "This alarm is raised when the CRC of the CAT is not valid. This variable
        indicates the current status of the alarm."
    ::= { ntcBissAlarms 4 }
    
ntcAlreadyScrambled              OBJECT-TYPE
    SYNTAX      NtcAlarmState
    MAX-ACCESS  read-only
    STATUS      current
    DESCRIPTION
        "This alarm is raised when a packet of a program is already scrambled This
        variable indicates the current status of the alarm."
    ::= { ntcBissAlarms 5 }
    
ntcCaDescriptorFoundOnInput      OBJECT-TYPE
    SYNTAX      NtcAlarmState
    MAX-ACCESS  read-only
    STATUS      current
    DESCRIPTION
        "This alarm is raised when a CA descriptor is found on input This variable
        indicates the current status of the alarm."
    ::= { ntcBissAlarms 6 }
    
ntcScramblingError               OBJECT-TYPE
    SYNTAX      NtcAlarmState
    MAX-ACCESS  read-only
    STATUS      current
    DESCRIPTION
        "This alarm is raised when errors are happening in the scrambling core. This
        variable indicates the current status of the alarm."
    ::= { ntcBissAlarms 7 }
    
ntcSwRefusedError                OBJECT-TYPE
    SYNTAX      NtcAlarmState
    MAX-ACCESS  read-only
    STATUS      current
    DESCRIPTION
        "This alarm is raised when the session words are changing too rapidly while
        scrambling is active. This variable indicates the current status of the alarm."
    ::= { ntcBissAlarms 8 }
    

--
--  Module Conformance
--

ntcBissScrConfGrpV1Standard      OBJECT-GROUP
    OBJECTS    {
                   ntcBissScrambling,
                   ntcBissScramblingMode,
                   ntcBissKeyParity,
                   ntcBissScramblingSuppression,
                   ntcBissMinRawUnscrambledPid,
                   ntcBissMaxRawUnscrambledPid,
                   ntcBissClearKeys,
                   ntcBissEvenSessionWord,
                   ntcBissOddSessionWord,
                   ntcBissEncryptedEvenSessionWord,
                   ntcBissEncryptedOddSessionWord,
                   ntcBissInKeyEncryptionMode,
                   ntcBissInjectedId,
                   ntcBissBuriedId,
                   ntcBissSetupId,
                   ntcBissScramblingState,
                   ntcBissSessionWordChanged,
                   ntcGeneralBissError,
                   ntcPatError,
                   ntcPmtError,
                   ntcCatError,
                   ntcAlreadyScrambled,
                   ntcCaDescriptorFoundOnInput,
                   ntcScramblingError,
                   ntcSwRefusedError
               }
    STATUS      current
    DESCRIPTION
        "Managed objects that constitute version 1 of a system device with standard capabilities."
    ::= { ntcBissScrConfGroup 1}
    
ntcBissScrConfCompV1Standard     MODULE-COMPLIANCE
    STATUS      current
    DESCRIPTION
        "Compliance statement for Newtec device MIB implementations."
    MODULE  -- this module
    MANDATORY-GROUPS
                  {
                      ntcBissScrConfGrpV1Standard
                  }
    ::= { ntcBissScrConfCompliance  1 }
    

END

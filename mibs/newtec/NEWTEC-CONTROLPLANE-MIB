NEWTEC-CONTROLPLANE-MIB DEFINITIONS ::= BEGIN

IMPORTS
    Unsigned32,
    MODULE-IDENTITY,
    OBJECT-IDENTITY,
    OBJECT-TYPE
        FROM SNMPv2-SMI

    MODULE-COMPLIANCE,
    OBJECT-GROUP
        FROM SNMPv2-CONF
    
    NtcAlarmState,
    NtcEnable,
    NtcNetworkAddress
        FROM NEWTEC-TC-MIB

    DisplayString
        FROM SNMPv2-TC

    ntcFunction
        FROM NEWTEC-MAIN-MIB;


--
--  Module Identification
--

ntcControlPlane   MODULE-IDENTITY
    LAST-UPDATED "201802020900Z"
    ORGANIZATION "Newtec Cy"
    CONTACT-INFO
        "Newtec Cy
         Postal: Newtec Cy
                 Laarstraat 5
                 B-9100 Sint-Niklaas
                 Belgium

                Tel: +32 3 780 65 00
                Fax: +32 3 780 65 49
                Web: www.newtec.be
                E-mail: techsupport@newtec.be"
    DESCRIPTION
        "Newtec modular Control Plane MIB containing definitions for Control Plane
        functionality."

    REVISION  "201802020900Z"
    DESCRIPTION
        "Description of ntcCtrlPlaneMasterIp extended with regexp"
    REVISION  "201410310800Z"
    DESCRIPTION
        "ntcCtrlPlaneCfg parameters made configurable"
    REVISION  "201409041200Z"
    DESCRIPTION
        "ntcCtrlPlaneCfgMaxQTime units corrected"
    REVISION  "201407150800Z"
    DESCRIPTION
        "DVB-S2X support"
    REVISION  "201305220600Z"
    DESCRIPTION
        "Initial release for MDM6000 R1.1"
    ::= { ntcFunction  4300 }
    

--
-- Top-Level Structure
--

-- ntcControlPlane content

ntcCtrlPlaneObjects              OBJECT-IDENTITY
    STATUS        current
    DESCRIPTION   "Container holding ntcCtrlPlaneObjects definitions."
    ::= { ntcControlPlane 1 }
    
ntcCtrlPlaneConformance          OBJECT-IDENTITY
    STATUS        current
    DESCRIPTION   "Conformance requirements."
    ::= { ntcControlPlane 2 }
    
-- ntcCtrlPlaneObjects content

ntcCtrlPlaneCfg                  OBJECT-IDENTITY
    STATUS        current
    DESCRIPTION   "Container holding ntcCtrlPlaneCfg definitions."
    ::= { ntcCtrlPlaneObjects 2 }
    
ntcCtrlPlaneAlarm                OBJECT-IDENTITY
    STATUS        current
    DESCRIPTION   "Container holding ntcCtrlPlaneAlarm definitions."
    ::= { ntcCtrlPlaneObjects 4 }
    
-- ntcCtrlPlaneConformance content

ntcCtrlPlaneConfCompliance       OBJECT-IDENTITY
    STATUS        current
    DESCRIPTION   "Device compliance statements."
    ::= { ntcCtrlPlaneConformance 1 }
    
ntcCtrlPlaneConfGroup            OBJECT-IDENTITY
    STATUS        current
    DESCRIPTION   "Groups used by device compliance statements."
    ::= { ntcCtrlPlaneConformance 2 }
    

--
-- Managed Objects
--

ntcCtrlPlaneEnable               OBJECT-TYPE
    SYNTAX      NtcEnable
    MAX-ACCESS  read-write
    STATUS      current
    DESCRIPTION
        "Enable or disable the Control Plane functionality."
    DEFVAL { off }
    ::= { ntcCtrlPlaneObjects 1 }
    
ntcCtrlPlaneCfgNomS2ModCod       OBJECT-TYPE
    SYNTAX      INTEGER { unspecified(0), qpsk14(1), qpsk13(2), qpsk25(3), qpsk12(4), qpsk35(5), qpsk23(6), qpsk34(7), qpsk45(8), qpsk56(9), qpsk89(10), qpsk910(11), e8psk35(12), e8psk23(13), e8psk34(14), e8psk56(15), e8psk89(16), e8psk910(17), e16apsk23(18), e16apsk34(19), e16apsk45(20), e16apsk56(21), e16apsk89(22), e16apsk910(23), e32apsk34(24), e32apsk45(25), e32apsk56(26), e32apsk89(27), e32apsk910(28), qpsk1345(29), qpsk920(30), qpsk1120(31), e8apsk59l(32), e8apsk2645l(33), e8psk2336(34), e8psk2536(35), e8psk1318(36), e16apsk12l(37), e16apsk815l(38), e16apsk59l(39), e16apsk2645(40), e16apsk35(41), e16apsk35l(42), e16apsk2845(43), e16apsk2336(44), e16apsk23l(45), e16apsk2536(46), e16apsk1318(47), e16apsk79(48), e16apsk7790(49), e32apsk23l(50), e32apsk3245(51), e32apsk1115(52), e32apsk79(53), e64apsk3245l(54), e64apsk1115(55), e64apsk79(56), e64apsk45(57), e64apsk56(58), e128apsk34(59), e128apsk79(60), e256apsk2945l(61), e256apsk23l(62), e256apsk3145l(63), e256apsk3245(64), e256apsk1115l(65), e256apsk34(66), qpsk1145(67), qpsk415(68), qpsk1445(69), qpsk715(70), qpsk815(71), qpsk3245(72), e8psk715(73), e8psk815(74), e8psk2645(75), e8psk3245(76), e16apsk715(77), e16apsk815(78), e16apsk3245(79), e32apsk23(80) }
    MAX-ACCESS  read-write
    STATUS      current
    DESCRIPTION
        "The MODCOD that the Control Plane uses in S2 mode."
    DEFVAL { qpsk34 }
    ::= { ntcCtrlPlaneCfg 1 }
    
ntcCtrlPlaneCfgNomS2EModCod      OBJECT-TYPE
    SYNTAX      INTEGER { unspecified(0), qpsk45180(129), qpsk60180(130), qpsk72180(131), qpsk80180(132), qpsk90180(133), qpsk100180(134), qpsk108180(135), qpsk114180(136), qpsk120180(137), qpsk126180(138), qpsk135180(139), qpsk144180(140), qpsk150180(141), qpsk160180(142), qpsk162180(143), e8psk80180(144), e8psk90180(145), e8psk100180(146), e8psk108180(147), e8psk114180(148), e8psk120180(149), e8psk126180(150), e8psk135180(151), e8psk144180(152), e8psk150180(153), e16apsk80180(154), e16apsk90180(155), e16apsk100180(156), e16apsk108180(157), e16apsk114180(158), e16apsk120180(159), e16apsk126180(160), e16apsk135180(161), e16apsk144180(162), e16apsk150180(163), e16apsk160180(164), e16apsk162180(165), e32apsk100180(166), e32apsk108180(167), e32apsk114180(168), e32apsk120180(169), e32apsk126180(170), e32apsk135180(171), e32apsk144180(172), e32apsk150180(173), e32apsk160180(174), e32apsk162180(175), e64apsk90180(176), e64apsk100180(177), e64apsk108180(178), e64apsk114180(179), e64apsk120180(180), e64apsk126180(181), e64apsk135180(182), e64apsk144180(183), e64apsk150180(184), e64apsk160180(185), e64apsk162180(186), e8pskl80180(187), e8pskl90180(188), e8pskl100180(189), e8pskl108180(190), e8pskl114180(191), e8pskl120180(192), e16apskl80180(193), e16apskl90180(194), e16apskl100180(195), e16apskl108180(196), e16apskl114180(197), e16apskl120180(198), e16apskl126180(199), e16apskl135180(200), e16apskl144180(201), e16apskl150180(202), e16apskl160180(203), e16apskl162180(204), e64apskl90180(205), e64apskl100180(206), e64apskl108180(207), e64apskl114180(208), e64apskl120180(209), e64apskl126180(210), e64apskl135180(211), e64apskl144180(212), e64apskl150180(213), e64apskl160180(214), e64apskl162180(215) }
    MAX-ACCESS  read-write
    STATUS      current
    DESCRIPTION
        "The MODCOD that the Control Plane uses in S2 Extensions mode."
    DEFVAL { qpsk45180 }
    ::= { ntcCtrlPlaneCfg 2 }
    
ntcCtrlPlaneCfgFrmTyp            OBJECT-TYPE
    SYNTAX      INTEGER { short(0), normal(1) }
    MAX-ACCESS  read-write
    STATUS      current
    DESCRIPTION
        "The type of frames for this encapsulator. If the control plane traffic is
        merged into a user ISI, the frametype is inherited from the user traffic
        configuration."
    DEFVAL { normal }
    ::= { ntcCtrlPlaneCfg 3 }
    
ntcCtrlPlaneCfgIsi               OBJECT-TYPE
    SYNTAX      Unsigned32
    MAX-ACCESS  read-write
    STATUS      current
    DESCRIPTION
        "The ISI of the channel"
    DEFVAL { 63 }
    ::= { ntcCtrlPlaneCfg 4 }
    
ntcCtrlPlaneCfgLabel             OBJECT-TYPE
    SYNTAX      DisplayString (SIZE(0..30))
    MAX-ACCESS  read-write
    STATUS      current
    DESCRIPTION
        "Label of the destination channel."
    DEFVAL { "3F:FF:FF" }
    ::= { ntcCtrlPlaneCfg 5 }
    
ntcCtrlPlaneCfgCir               OBJECT-TYPE
    SYNTAX      Unsigned32
    UNITS       "bits"
    MAX-ACCESS  read-write
    STATUS      current
    DESCRIPTION
        "Define the guaranteed bit rate (CIR) for Control Plane data shaping."
    DEFVAL { 256000 }
    ::= { ntcCtrlPlaneCfg 6 }
    
ntcCtrlPlaneCfgPir               OBJECT-TYPE
    SYNTAX      Unsigned32
    UNITS       "bits"
    MAX-ACCESS  read-write
    STATUS      current
    DESCRIPTION
        "Define the peak bit rate (PIR) for Control Plane data shaping."
    DEFVAL { 1000000 }
    ::= { ntcCtrlPlaneCfg 7 }
    
ntcCtrlPlaneCfgPrio              OBJECT-TYPE
    SYNTAX      Unsigned32
    MAX-ACCESS  read-write
    STATUS      current
    DESCRIPTION
        "Define the priority for Control Plane data shaping node when dividing rate
        between nodes."
    DEFVAL { 0 }
    ::= { ntcCtrlPlaneCfg 8 }
    
ntcCtrlPlaneCfgMaxQTime          OBJECT-TYPE
    SYNTAX      Unsigned32
    UNITS       "ms"
    MAX-ACCESS  read-write
    STATUS      current
    DESCRIPTION
        "The maximum time packets are allowed to remain in a shaping queue before being
        dropped."
    DEFVAL { 100 }
    ::= { ntcCtrlPlaneCfg 9 }
    
ntcCtrlPlaneMasterIp             OBJECT-TYPE
    SYNTAX      NtcNetworkAddress
    MAX-ACCESS  read-write
    STATUS      current
    DESCRIPTION
        "IP address of Control Plane Master used to obtain Control Plane setup Regular
        expression : (?-mix:^\d{1,3}\.\d{1,3}\.\d{1,3}\.\d{1,3}$)"
    DEFVAL { "0.0.0.0" }
    ::= { ntcCtrlPlaneObjects 3 }
    
ntcCtrlPlaneAlmNoMaster          OBJECT-TYPE
    SYNTAX      NtcAlarmState
    MAX-ACCESS  read-only
    STATUS      current
    DESCRIPTION
        "This alarm is raised when the control plane master doesn't respond to the
        control plane slave's requests. This variable indicates the current status of
        the alarm."
    ::= { ntcCtrlPlaneAlarm 1 }
    

--
--  Module Conformance
--

ntcCtrlPlaneConfGrpV1Standard    OBJECT-GROUP
    OBJECTS    {
                   ntcCtrlPlaneEnable,
                   ntcCtrlPlaneCfgNomS2ModCod,
                   ntcCtrlPlaneCfgNomS2EModCod,
                   ntcCtrlPlaneCfgFrmTyp,
                   ntcCtrlPlaneCfgIsi,
                   ntcCtrlPlaneCfgLabel,
                   ntcCtrlPlaneCfgCir,
                   ntcCtrlPlaneCfgPir,
                   ntcCtrlPlaneCfgPrio,
                   ntcCtrlPlaneCfgMaxQTime,
                   ntcCtrlPlaneMasterIp,
                   ntcCtrlPlaneAlmNoMaster
               }
    STATUS      current
    DESCRIPTION
        "Managed objects that constitute version 1 of a system device with standard capabilities."
    ::= { ntcCtrlPlaneConfGroup 1}
    
ntcCtrlPlaneConfCompV1Standard   MODULE-COMPLIANCE
    STATUS      current
    DESCRIPTION
        "Compliance statement for Newtec device MIB implementations."
    MODULE  -- this module
    MANDATORY-GROUPS
                  {
                      ntcCtrlPlaneConfGrpV1Standard
                  }
    ::= { ntcCtrlPlaneConfCompliance  1 }
    

END

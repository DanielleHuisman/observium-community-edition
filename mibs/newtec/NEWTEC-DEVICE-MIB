NEWTEC-DEVICE-MIB DEFINITIONS ::= BEGIN

IMPORTS
    Unsigned32,
    IpAddress,
    Integer32,
    MODULE-IDENTITY,
    OBJECT-IDENTITY,
    OBJECT-TYPE
        FROM SNMPv2-SMI

    MODULE-COMPLIANCE,
    OBJECT-GROUP
        FROM SNMPv2-CONF
    
    Float32TC
        FROM FLOAT-TC-MIB

    NtcAlarmState,
    NtcEnable
        FROM NEWTEC-TC-MIB

    DisplayString
        FROM SNMPv2-TC

    ntcFunction
        FROM NEWTEC-MAIN-MIB;


--
--  Module Identification
--

ntcDevice   MODULE-IDENTITY
    LAST-UPDATED "201710231200Z"
    ORGANIZATION "Newtec Cy"
    CONTACT-INFO
        "Newtec Cy
         Postal: Newtec Cy
                 Laarstraat 5
                 B-9100 Sint-Niklaas
                 Belgium

                Tel: +32 3 780 65 00
                Fax: +32 3 780 65 49
                Web: www.newtec.be
                E-mail: techsupport@newtec.be"
    DESCRIPTION
        "Newtec modular device MIB containing definitions for device level
        functionality."

    REVISION  "201710231200Z"
    DESCRIPTION
        "ntcDevCliInactivityTimeout units changed"
    REVISION  "201707101200Z"
    DESCRIPTION
        "Descriptions updated with regex + added ntcDevMonGlobalCpuLoad,
        ntcDevActCfgState, ntcDevRest and ntcDevRestEnable"
    REVISION  "201608050800Z"
    DESCRIPTION
        "ntcDevAlmLicenseUpgradeFailure added"
    REVISION  "201605170900Z"
    DESCRIPTION
        "ntcDevSnmpNotifDestDestination disallow empty key"
    REVISION  "201510191100Z"
    DESCRIPTION
        "ntcDevSnmpNotifDestDestination range extended"
    REVISION  "201509251100Z"
    DESCRIPTION
        "ntcDevIdLicenseType enum extended and HW failure- and Internalerror-alarms/mon
        added"
    REVISION  "201504130700Z"
    DESCRIPTION
        "License parameters added"
    REVISION  "201409090900Z"
    DESCRIPTION
        "Cosmetic changes"
    REVISION  "201407080900Z"
    DESCRIPTION
        "autosave and carrierid added"
    REVISION  "201403181200Z"
    DESCRIPTION
        "Location and Operator id parameters added."
    REVISION  "201305220600Z"
    DESCRIPTION
        "Release for MDM6000 and NOP1760 R1.1"
    REVISION  "201301081200Z"
    DESCRIPTION
        "Release for MDM6000 and NOP1760 R1.0"
    REVISION  "201206281200Z"
    DESCRIPTION
        "Release for M6100 R1.2"
    ::= { ntcFunction  100 }
    

--
-- Top-Level Structure
--

-- ntcDevice content

ntcDevObjects                    OBJECT-IDENTITY
    STATUS        current
    DESCRIPTION   "Container holding ntcDevObjects definitions."
    ::= { ntcDevice 1 }
    
ntcDevConformance                OBJECT-IDENTITY
    STATUS        current
    DESCRIPTION   "Conformance requirements."
    ::= { ntcDevice 2 }
    
-- ntcDevObjects content

ntcDevIdentification             OBJECT-IDENTITY
    STATUS        current
    DESCRIPTION   "Container holding ntcDevIdentification definitions."
    ::= { ntcDevObjects 1 }
    
ntcDevFrontPanel                 OBJECT-IDENTITY
    STATUS        current
    DESCRIPTION   "Container holding ntcDevFrontPanel definitions."
    ::= { ntcDevObjects 2 }
    
ntcDevSnmp                       OBJECT-IDENTITY
    STATUS        current
    DESCRIPTION   "Container holding ntcDevSnmp definitions."
    ::= { ntcDevObjects 3 }
    
ntcDevCli                        OBJECT-IDENTITY
    STATUS        current
    DESCRIPTION   "Container holding ntcDevCli definitions."
    ::= { ntcDevObjects 4 }
    
ntcDevGui                        OBJECT-IDENTITY
    STATUS        current
    DESCRIPTION   "Container holding ntcDevGui definitions."
    ::= { ntcDevObjects 5 }
    
ntcDevFtp                        OBJECT-IDENTITY
    STATUS        current
    DESCRIPTION   "Container holding ntcDevFtp definitions."
    ::= { ntcDevObjects 6 }
    
ntcDevLog                        OBJECT-IDENTITY
    STATUS        current
    DESCRIPTION   "Container holding ntcDevLog definitions."
    ::= { ntcDevObjects 7 }
    
ntcDevDateTime                   OBJECT-IDENTITY
    STATUS        current
    DESCRIPTION   "Container holding ntcDevDateTime definitions."
    ::= { ntcDevObjects 8 }
    
ntcDevMonitor                    OBJECT-IDENTITY
    STATUS        current
    DESCRIPTION   "Container holding ntcDevMonitor definitions."
    ::= { ntcDevObjects 9 }
    
ntcDevAlarm                      OBJECT-IDENTITY
    STATUS        current
    DESCRIPTION   "Container holding ntcDevAlarm definitions."
    ::= { ntcDevObjects 10 }
    
ntcDevOperatorIdentification     OBJECT-IDENTITY
    STATUS        current
    DESCRIPTION   "Container holding ntcDevOperatorIdentification definitions."
    ::= { ntcDevObjects 12 }
    
ntcDevLocation                   OBJECT-IDENTITY
    STATUS        current
    DESCRIPTION   "Container holding ntcDevLocation definitions."
    ::= { ntcDevObjects 13 }
    
ntcDevConfiguration              OBJECT-IDENTITY
    STATUS        current
    DESCRIPTION   "Container holding ntcDevConfiguration definitions."
    ::= { ntcDevObjects 14 }
    
ntcDevRest                       OBJECT-IDENTITY
    STATUS        current
    DESCRIPTION   "Container holding ntcDevRest definitions."
    ::= { ntcDevObjects 15 }
    
-- ntcDevSnmp content

ntcDevSnmpNotification           OBJECT-IDENTITY
    STATUS        current
    DESCRIPTION   "Container holding ntcDevSnmpNotification definitions."
    ::= { ntcDevSnmp 1 }
    
-- ntcDevLog content

ntcDevLogLocal                   OBJECT-IDENTITY
    STATUS        current
    DESCRIPTION   "Container holding ntcDevLogLocal definitions."
    ::= { ntcDevLog 1 }
    
ntcDevLogRemote                  OBJECT-IDENTITY
    STATUS        current
    DESCRIPTION   "Container holding ntcDevLogRemote definitions."
    ::= { ntcDevLog 2 }
    
-- ntcDevDateTime content

ntcDevDtNtp                      OBJECT-IDENTITY
    STATUS        current
    DESCRIPTION   "Container holding ntcDevDtNtp definitions."
    ::= { ntcDevDateTime 3 }
    
-- ntcDevConformance content

ntcDevConfCompliance             OBJECT-IDENTITY
    STATUS        current
    DESCRIPTION   "Device compliance statements."
    ::= { ntcDevConformance 1 }
    
ntcDevConfGroup                  OBJECT-IDENTITY
    STATUS        current
    DESCRIPTION   "Groups used by device compliance statements."
    ::= { ntcDevConformance 2 }
    

--
-- Managed Objects
--

ntcDevIdLabel                    OBJECT-TYPE
    SYNTAX      DisplayString (SIZE(0..50))
    MAX-ACCESS  read-write
    STATUS      current
    DESCRIPTION
        "The device label can be used to distinguish a set of identical devices in a
        group. e.g. Identical modulator devices can be labeled 'modulator 1',
        'modulator 2'"
    ::= { ntcDevIdentification 1 }
    
ntcDevIdSerialNumber             OBJECT-TYPE
    SYNTAX      DisplayString (SIZE(0..100))
    MAX-ACCESS  read-only
    STATUS      current
    DESCRIPTION
        "The device serial number."
    ::= { ntcDevIdentification 2 }
    
ntcDevIdUniqueId                 OBJECT-TYPE
    SYNTAX      DisplayString (SIZE(0..100))
    MAX-ACCESS  read-only
    STATUS      current
    DESCRIPTION
        "An identifier which is unique and specific for a device."
    ::= { ntcDevIdentification 3 }
    
ntcDevIdProduct                  OBJECT-TYPE
    SYNTAX      DisplayString (SIZE(0..30))
    MAX-ACCESS  read-only
    STATUS      current
    DESCRIPTION
        "The official Newtec product name of the device."
    ::= { ntcDevIdentification 4 }
    
ntcDevIdDeviceDescription        OBJECT-TYPE
    SYNTAX      DisplayString (SIZE(0..100))
    MAX-ACCESS  read-only
    STATUS      current
    DESCRIPTION
        "The device description explains the main usage of the device."
    ::= { ntcDevIdentification 5 }
    
ntcDevIdTypeId                   OBJECT-TYPE
    SYNTAX      DisplayString (SIZE(0..100))
    MAX-ACCESS  read-only
    STATUS      current
    DESCRIPTION
        "The device type identifier."
    ::= { ntcDevIdentification 6 }
    
ntcDevIdHardwareRevision         OBJECT-TYPE
    SYNTAX      DisplayString (SIZE(0..100))
    MAX-ACCESS  read-only
    STATUS      current
    DESCRIPTION
        "Device hardware revision."
    ::= { ntcDevIdentification 7 }
    
ntcDevIdSoftwareId               OBJECT-TYPE
    SYNTAX      DisplayString (SIZE(0..50))
    MAX-ACCESS  read-only
    STATUS      current
    DESCRIPTION
        "Device software identification."
    ::= { ntcDevIdentification 8 }
    
ntcDevIdSoftwareVersion          OBJECT-TYPE
    SYNTAX      DisplayString (SIZE(0..100))
    MAX-ACCESS  read-only
    STATUS      current
    DESCRIPTION
        "Device software version."
    ::= { ntcDevIdentification 9 }
    
ntcDevIdDeviceOptionsTable       OBJECT-TYPE
    SYNTAX      SEQUENCE OF NtcDevIdDeviceOptionsEntry
    MAX-ACCESS  not-accessible
    STATUS      current
    DESCRIPTION
        "Overview of the enabled device options. These options are specified in the
        license file."
    ::= { ntcDevIdentification 10 }

ntcDevIdDeviceOptionsEntry       OBJECT-TYPE
    SYNTAX      NtcDevIdDeviceOptionsEntry
    MAX-ACCESS  not-accessible
    STATUS      current
    DESCRIPTION
        "A conceptual row of the ntcDevIdDeviceOptionsTable."
    INDEX   { ntcDevIdDeviceOptionsSalesCode  }
    ::= { ntcDevIdDeviceOptionsTable 1 }

NtcDevIdDeviceOptionsEntry       ::= SEQUENCE {
    ntcDevIdDeviceOptionsSalesCode      DisplayString,
    ntcDevIdDeviceOptionsDescription    DisplayString
    }
    
ntcDevIdDeviceOptionsSalesCode   OBJECT-TYPE
    SYNTAX      DisplayString (SIZE(0..66))
    MAX-ACCESS  not-accessible
    STATUS      current
    DESCRIPTION
        "Sales Code used to specify a specific device option."
    ::= { ntcDevIdDeviceOptionsEntry 1 }
    
ntcDevIdDeviceOptionsDescription OBJECT-TYPE
    SYNTAX      DisplayString (SIZE(0..255))
    MAX-ACCESS  read-only
    STATUS      current
    DESCRIPTION
        "Detailled description of a specific sales code."
    ::= { ntcDevIdDeviceOptionsEntry 2 }
    
ntcDevIdLicenseType              OBJECT-TYPE
    SYNTAX      INTEGER { permanent(0), temporaryEndDate(1), temporaryCredits(2), temporaryCreditsUnderRedundancy(3) }
    MAX-ACCESS  read-only
    STATUS      current
    DESCRIPTION
        "The type of the License"
    ::= { ntcDevIdentification 11 }
    
ntcDevIdLicenseTimeRemain        OBJECT-TYPE
    SYNTAX      DisplayString (SIZE(0..50))
    MAX-ACCESS  read-only
    STATUS      current
    DESCRIPTION
        "The remaining time for a temporary license."
    ::= { ntcDevIdentification 12 }
    
ntcDevFpEnable                   OBJECT-TYPE
    SYNTAX      NtcEnable
    MAX-ACCESS  read-write
    STATUS      current
    DESCRIPTION
        "Enable or disable the front panel."
    DEFVAL { on }
    ::= { ntcDevFrontPanel 1 }
    
ntcDevFpiAccessLevel             OBJECT-TYPE
    SYNTAX      INTEGER { readonly(0), operator(1), expert(2) }
    MAX-ACCESS  read-write
    STATUS      current
    DESCRIPTION
        "Access level for the front panel."
    DEFVAL { operator }
    ::= { ntcDevFrontPanel 2 }
    
ntcDevSnmpNotifDestTable         OBJECT-TYPE
    SYNTAX      SEQUENCE OF NtcDevSnmpNotifDestEntry
    MAX-ACCESS  not-accessible
    STATUS      current
    DESCRIPTION
        "A table containing the ntcDevSnmpNotifDest"
    ::= { ntcDevSnmpNotification 1 }

ntcDevSnmpNotifDestEntry         OBJECT-TYPE
    SYNTAX      NtcDevSnmpNotifDestEntry
    MAX-ACCESS  not-accessible
    STATUS      current
    DESCRIPTION
        "A conceptual row of the ntcDevSnmpNotifDestTable."
    INDEX   { ntcDevSnmpNotifDestDestination  }
    ::= { ntcDevSnmpNotifDestTable 1 }

NtcDevSnmpNotifDestEntry         ::= SEQUENCE {
    ntcDevSnmpNotifDestDestination    Unsigned32,
    ntcDevSnmpNotifDestIpAddress      IpAddress,
    ntcDevSnmpNotifDestType           INTEGER,
    ntcDevSnmpNotifDestCommunity      DisplayString
    }
    
ntcDevSnmpNotifDestDestination   OBJECT-TYPE
    SYNTAX      Unsigned32 (1..4)
    MAX-ACCESS  not-accessible
    STATUS      current
    DESCRIPTION
        "The index of the destination"
    ::= { ntcDevSnmpNotifDestEntry 1 }
    
ntcDevSnmpNotifDestIpAddress     OBJECT-TYPE
    SYNTAX      IpAddress 
    MAX-ACCESS  read-write
    STATUS      current
    DESCRIPTION
        "IP address used as destinations of the SNMP notifications to send. Regular
        expression : (?-mix:^\d{1,3}\.\d{1,3}\.\d{1,3}\.\d{1,3}$)"
    DEFVAL { '00000000'h }
    ::= { ntcDevSnmpNotifDestEntry 2 }
    
ntcDevSnmpNotifDestType          OBJECT-TYPE
    SYNTAX      INTEGER { trapV1(0), trapV2(1), inform(2) }
    MAX-ACCESS  read-write
    STATUS      current
    DESCRIPTION
        "Specify the type of SNMP notification to be sent to the management station.
        Notice that clients with SNMPv1 require TrapV1."
    DEFVAL { trapV2 }
    ::= { ntcDevSnmpNotifDestEntry 3 }
    
ntcDevSnmpNotifDestCommunity     OBJECT-TYPE
    SYNTAX      DisplayString (SIZE(1..30))
    MAX-ACCESS  read-write
    STATUS      current
    DESCRIPTION
        "Specifies the notification community, which is an alphanumeric non-empty
        string of less than 30 characters. Regular expression : (?-mix:[A-Za-z0-9]+)"
    DEFVAL { "trapcom" }
    ::= { ntcDevSnmpNotifDestEntry 4 }
    
ntcDevCliRemoteEnable            OBJECT-TYPE
    SYNTAX      NtcEnable
    MAX-ACCESS  read-write
    STATUS      current
    DESCRIPTION
        "Enable or disable the remote CLI (Command Line Interface) interface."
    DEFVAL { on }
    ::= { ntcDevCli 1 }
    
ntcDevCliInactivityTimeout       OBJECT-TYPE
    SYNTAX      Unsigned32
    UNITS       "s"
    MAX-ACCESS  read-write
    STATUS      current
    DESCRIPTION
        "The CLI (Command Line Interface) inactivity timeout specifies the time a CLI
        session is kept open without user interaction. The timeout is specified in
        seconds. If 0 is specified the connection will never be closed."
    DEFVAL { 600 }
    ::= { ntcDevCli 2 }
    
ntcDevGuiEnable                  OBJECT-TYPE
    SYNTAX      NtcEnable
    MAX-ACCESS  read-write
    STATUS      current
    DESCRIPTION
        "Specify if the GUI is enabled or disabled"
    DEFVAL { on }
    ::= { ntcDevGui 1 }
    
ntcDevFtpEnable                  OBJECT-TYPE
    SYNTAX      NtcEnable
    MAX-ACCESS  read-write
    STATUS      current
    DESCRIPTION
        "Enable or disable FTP (File Transfer Protocol)."
    DEFVAL { on }
    ::= { ntcDevFtp 1 }
    
ntcDevFtpAnonymousEnable         OBJECT-TYPE
    SYNTAX      NtcEnable
    MAX-ACCESS  read-write
    STATUS      current
    DESCRIPTION
        "Enable or disable the FTP anonymous account."
    DEFVAL { on }
    ::= { ntcDevFtp 2 }
    
ntcDevLogLocEnable               OBJECT-TYPE
    SYNTAX      NtcEnable
    MAX-ACCESS  read-write
    STATUS      current
    DESCRIPTION
        "Enable or disable the local logging."
    DEFVAL { on }
    ::= { ntcDevLogLocal 1 }
    
ntcDevLogRemEnable               OBJECT-TYPE
    SYNTAX      NtcEnable
    MAX-ACCESS  read-write
    STATUS      current
    DESCRIPTION
        "Enable or disable remote logging via syslog."
    DEFVAL { off }
    ::= { ntcDevLogRemote 1 }
    
ntcDevLogRemIpAddress            OBJECT-TYPE
    SYNTAX      IpAddress 
    MAX-ACCESS  read-write
    STATUS      current
    DESCRIPTION
        "Remote syslog IP address Regular expression :
        (?-mix:^\d{1,3}\.\d{1,3}\.\d{1,3}\.\d{1,3}$)"
    DEFVAL { '00000000'h }
    ::= { ntcDevLogRemote 2 }
    
ntcDevLogRemUdpPort              OBJECT-TYPE
    SYNTAX      Unsigned32 (1..65535)
    MAX-ACCESS  read-write
    STATUS      current
    DESCRIPTION
        "Remote syslog UDP port."
    DEFVAL { 514 }
    ::= { ntcDevLogRemote 3 }
    
ntcDevLogFilterTable             OBJECT-TYPE
    SYNTAX      SEQUENCE OF NtcDevLogFilterEntry
    MAX-ACCESS  not-accessible
    STATUS      current
    DESCRIPTION
        "A table containing the ntcDevLogFilter"
    ::= { ntcDevLog 3 }

ntcDevLogFilterEntry             OBJECT-TYPE
    SYNTAX      NtcDevLogFilterEntry
    MAX-ACCESS  not-accessible
    STATUS      current
    DESCRIPTION
        "A conceptual row of the ntcDevLogFilterTable."
    INDEX   { ntcDevLogFilterFacility  }
    ::= { ntcDevLogFilterTable 1 }

NtcDevLogFilterEntry             ::= SEQUENCE {
    ntcDevLogFilterFacility    DisplayString,
    ntcDevLogFilterLevel       INTEGER
    }
    
ntcDevLogFilterFacility          OBJECT-TYPE
    SYNTAX      DisplayString (SIZE(0..32))
    MAX-ACCESS  not-accessible
    STATUS      current
    DESCRIPTION
        "The logging facility identifies the source of information that needs to be
        logged."
    ::= { ntcDevLogFilterEntry 1 }
    
ntcDevLogFilterLevel             OBJECT-TYPE
    SYNTAX      INTEGER { off(0), trace(1), debug(2), info(3), notice(4), warn(5), error(6), alert(7), emerg(8) }
    MAX-ACCESS  read-write
    STATUS      current
    DESCRIPTION
        "Filter level for this facility"
    DEFVAL { info }
    ::= { ntcDevLogFilterEntry 2 }
    
ntcDevDtDate                     OBJECT-TYPE
    SYNTAX      DisplayString (SIZE(0..18))
    MAX-ACCESS  read-write
    STATUS      current
    DESCRIPTION
        "Date (format is fixed as: dd/mm/yyyy) of the device"
    DEFVAL { "01/01/2001" }
    ::= { ntcDevDateTime 1 }
    
ntcDevDtTime                     OBJECT-TYPE
    SYNTAX      DisplayString (SIZE(0..18))
    MAX-ACCESS  read-write
    STATUS      current
    DESCRIPTION
        "Device time (format is fixed as: hh:mm:ss)"
    DEFVAL { "00:00:00" }
    ::= { ntcDevDateTime 2 }
    
ntcDevDtNtpEnable                OBJECT-TYPE
    SYNTAX      NtcEnable
    MAX-ACCESS  read-write
    STATUS      current
    DESCRIPTION
        "Enable or disable NTP client functionality."
    DEFVAL { off }
    ::= { ntcDevDtNtp 1 }
    
ntcDevDtNtpPeerTable             OBJECT-TYPE
    SYNTAX      SEQUENCE OF NtcDevDtNtpPeerEntry
    MAX-ACCESS  not-accessible
    STATUS      current
    DESCRIPTION
        "A table containing the ntcDevDtNtpPeer"
    ::= { ntcDevDtNtp 2 }

ntcDevDtNtpPeerEntry             OBJECT-TYPE
    SYNTAX      NtcDevDtNtpPeerEntry
    MAX-ACCESS  not-accessible
    STATUS      current
    DESCRIPTION
        "A conceptual row of the ntcDevDtNtpPeerTable."
    INDEX   { ntcDevDtNtpPeerPeer  }
    ::= { ntcDevDtNtpPeerTable 1 }

NtcDevDtNtpPeerEntry             ::= SEQUENCE {
    ntcDevDtNtpPeerPeer         Unsigned32,
    ntcDevDtNtpPeerIpAddress    IpAddress
    }
    
ntcDevDtNtpPeerPeer              OBJECT-TYPE
    SYNTAX      Unsigned32
    MAX-ACCESS  not-accessible
    STATUS      current
    DESCRIPTION
        "The index of the NTP peer servers."
    ::= { ntcDevDtNtpPeerEntry 1 }
    
ntcDevDtNtpPeerIpAddress         OBJECT-TYPE
    SYNTAX      IpAddress 
    MAX-ACCESS  read-write
    STATUS      current
    DESCRIPTION
        "NTP peer IP address Regular expression :
        (?-mix:^\d{1,3}\.\d{1,3}\.\d{1,3}\.\d{1,3}$)"
    DEFVAL { '00000000'h }
    ::= { ntcDevDtNtpPeerEntry 2 }
    
ntcDevMonTemperature             OBJECT-TYPE
    SYNTAX      Integer32
    UNITS       "Celsius"
    MAX-ACCESS  read-only
    STATUS      current
    DESCRIPTION
        "Displays the board temperature expressed in degrees Celsius."
    ::= { ntcDevMonitor 1 }
    
ntcDevMonPowerSupply             OBJECT-TYPE
    SYNTAX      Integer32
    UNITS       "V"
    MAX-ACCESS  read-only
    STATUS      current
    DESCRIPTION
        "Indicates the input voltage of the board power supply expressed in Volt. Float
        represented as integer is scaled by a factor of 100. e.g. a value of 1194
        means a voltage level of 11.94V"
    ::= { ntcDevMonitor 2 }
    
ntcDevMonCpuLoad                 OBJECT-TYPE
    SYNTAX      DisplayString (SIZE(0..1000))
    MAX-ACCESS  read-only
    STATUS      current
    DESCRIPTION
        "Indicates the current CPU utilization in percentage (%)."
    ::= { ntcDevMonitor 3 }
    
ntcDevMonMemoryUse               OBJECT-TYPE
    SYNTAX      Unsigned32 (0..100)
    UNITS       "%"
    MAX-ACCESS  read-only
    STATUS      current
    DESCRIPTION
        "Indicates the memory usage in % of the total available memory."
    ::= { ntcDevMonitor 4 }
    
ntcDevMonUptime                  OBJECT-TYPE
    SYNTAX      DisplayString (SIZE(0..30))
    MAX-ACCESS  read-only
    STATUS      current
    DESCRIPTION
        "Device uptime expressed in day(s) hour(s) minute(s) second(s)."
    ::= { ntcDevMonitor 5 }
    
ntcDevMonSensorsTable            OBJECT-TYPE
    SYNTAX      SEQUENCE OF NtcDevMonSensorsEntry
    MAX-ACCESS  not-accessible
    STATUS      current
    DESCRIPTION
        "Sensors"
    ::= { ntcDevMonitor 6 }

ntcDevMonSensorsEntry            OBJECT-TYPE
    SYNTAX      NtcDevMonSensorsEntry
    MAX-ACCESS  not-accessible
    STATUS      current
    DESCRIPTION
        "A conceptual row of the ntcDevMonSensorsTable."
    INDEX   { ntcDevMonSensorsSensor  }
    ::= { ntcDevMonSensorsTable 1 }

NtcDevMonSensorsEntry            ::= SEQUENCE {
    ntcDevMonSensorsSensor    DisplayString,
    ntcDevMonSensorsValue     DisplayString
    }
    
ntcDevMonSensorsSensor           OBJECT-TYPE
    SYNTAX      DisplayString (SIZE(0..32))
    MAX-ACCESS  not-accessible
    STATUS      current
    DESCRIPTION
        "Name of the sensor"
    ::= { ntcDevMonSensorsEntry 1 }
    
ntcDevMonSensorsValue            OBJECT-TYPE
    SYNTAX      DisplayString (SIZE(0..32))
    MAX-ACCESS  read-only
    STATUS      current
    DESCRIPTION
        "Value displayed by the sensor"
    ::= { ntcDevMonSensorsEntry 2 }
    
ntcDevMonHwFailureCause          OBJECT-TYPE
    SYNTAX      DisplayString (SIZE(0..100))
    MAX-ACCESS  read-only
    STATUS      current
    DESCRIPTION
        "The Hardware Failure Cause."
    ::= { ntcDevMonitor 7 }
    
ntcDevMonInternalErrorCause      OBJECT-TYPE
    SYNTAX      DisplayString (SIZE(0..100))
    MAX-ACCESS  read-only
    STATUS      current
    DESCRIPTION
        "The Internal Error Cause."
    ::= { ntcDevMonitor 8 }
    
ntcDevMonGlobalCpuLoad           OBJECT-TYPE
    SYNTAX      OCTET STRING (SIZE(0..1000))
    MAX-ACCESS  read-only
    STATUS      current
    DESCRIPTION
        "Indicates the current global CPU utilization in percentage (%)."
    ::= { ntcDevMonitor 9 }
    
ntcDevAlmGenDeviceAlarm          OBJECT-TYPE
    SYNTAX      NtcAlarmState
    MAX-ACCESS  read-only
    STATUS      current
    DESCRIPTION
        "This alarm is raised when there is a general device failure. This variable
        indicates the current status of the alarm."
    ::= { ntcDevAlarm 1 }
    
ntcDevAlmGenBootConfigFailure    OBJECT-TYPE
    SYNTAX      NtcAlarmState
    MAX-ACCESS  read-only
    STATUS      current
    DESCRIPTION
        "Alarm raised when an erroneous boot configuration was attempted and failed.
        This variable indicates the current status of the alarm."
    ::= { ntcDevAlarm 2 }
    
ntcDevAlmGenInterfaceAlarm       OBJECT-TYPE
    SYNTAX      NtcAlarmState
    MAX-ACCESS  read-only
    STATUS      current
    DESCRIPTION
        "This alarm is raised when an error is reported on an interface which is used
        in the datapath. This variable indicates the current status of the alarm."
    ::= { ntcDevAlarm 3 }
    
ntcDevAlmTemperature             OBJECT-TYPE
    SYNTAX      NtcAlarmState
    MAX-ACCESS  read-only
    STATUS      current
    DESCRIPTION
        "This alarm is raised when the monitored temperature exceeds 85 degrees
        Celsius. This variable indicates the current status of the alarm."
    ::= { ntcDevAlarm 4 }
    
ntcDevAlmInvalidLicenseFile      OBJECT-TYPE
    SYNTAX      NtcAlarmState
    MAX-ACCESS  read-only
    STATUS      current
    DESCRIPTION
        "This alarm is raised when the license file is non-existent or wrongly signed.
        This variable indicates the current status of the alarm."
    ::= { ntcDevAlarm 5 }
    
ntcDevAlmFrontPanelFailure       OBJECT-TYPE
    SYNTAX      NtcAlarmState
    MAX-ACCESS  read-only
    STATUS      current
    DESCRIPTION
        "This alarm is raised when Frontpanel communication failed. This variable
        indicates the current status of the alarm."
    ::= { ntcDevAlarm 6 }
    
ntcDevAlmUpgradeFailure          OBJECT-TYPE
    SYNTAX      NtcAlarmState
    MAX-ACCESS  read-only
    STATUS      current
    DESCRIPTION
        "This alarm is raised when a software upgrade has failed This variable
        indicates the current status of the alarm."
    ::= { ntcDevAlarm 7 }
    
ntcDevAlmNtpNoPeerFailure        OBJECT-TYPE
    SYNTAX      NtcAlarmState
    MAX-ACCESS  read-only
    STATUS      current
    DESCRIPTION
        "This alarm is raised when none of the configured NTP servers can be reached
        This variable indicates the current status of the alarm."
    ::= { ntcDevAlarm 8 }
    
ntcDevAlmLicenseExpireFile       OBJECT-TYPE
    SYNTAX      NtcAlarmState
    MAX-ACCESS  read-only
    STATUS      current
    DESCRIPTION
        "This alarm is raised when the (temporary) license file is about to expire This
        variable indicates the current status of the alarm."
    ::= { ntcDevAlarm 9 }
    
ntcDevAlmHardwareInventory       OBJECT-TYPE
    SYNTAX      NtcAlarmState
    MAX-ACCESS  read-only
    STATUS      current
    DESCRIPTION
        "This alarm is raised when the hardware inventory is no longer matching with
        the production inventory. This variable indicates the current status of the
        alarm."
    ::= { ntcDevAlarm 10 }
    
ntcDevAlmHardwareFailure         OBJECT-TYPE
    SYNTAX      NtcAlarmState
    MAX-ACCESS  read-only
    STATUS      current
    DESCRIPTION
        "This alarm is raised when the hardware is malfunctioning. This variable
        indicates the current status of the alarm."
    ::= { ntcDevAlarm 11 }
    
ntcDevAlmInternalError           OBJECT-TYPE
    SYNTAX      NtcAlarmState
    MAX-ACCESS  read-only
    STATUS      current
    DESCRIPTION
        "This alarm is raised when a certain internal error occurs. This could be
        solved by a reboot, or upgrading to the latest firmware. This variable
        indicates the current status of the alarm."
    ::= { ntcDevAlarm 12 }
    
ntcDevAlmLicenseUpgradeFailure   OBJECT-TYPE
    SYNTAX      NtcAlarmState
    MAX-ACCESS  read-only
    STATUS      current
    DESCRIPTION
        "This alarm is raised when a license upgrade has failed This variable indicates
        the current status of the alarm."
    ::= { ntcDevAlarm 13 }
    
ntcDevReset                      OBJECT-TYPE
    SYNTAX      INTEGER { running(0), hardware(1), software(2), configs(3) }
    MAX-ACCESS  read-write
    STATUS      current
    DESCRIPTION
        "Reset the device."
    DEFVAL { running }
    ::= { ntcDevObjects 11 }
    
ntcDevTelephonenbr               OBJECT-TYPE
    SYNTAX      DisplayString (SIZE(0..20))
    MAX-ACCESS  read-write
    STATUS      current
    DESCRIPTION
        "Operators telephone number (for example +323 780 65 00 ) Regular expression :
        (?-mix:(\+?[ \d)(]*)?)"
    DEFVAL { "" }
    ::= { ntcDevOperatorIdentification 1 }
    
ntcDevTelephoneext               OBJECT-TYPE
    SYNTAX      DisplayString (SIZE(0..10))
    MAX-ACCESS  read-write
    STATUS      current
    DESCRIPTION
        "Operators telephone extension number (for example 0154) Regular expression :
        (?-mix:\d*)"
    DEFVAL { "" }
    ::= { ntcDevOperatorIdentification 2 }
    
ntcDevCarrId                     OBJECT-TYPE
    SYNTAX      DisplayString (SIZE(0..5))
    MAX-ACCESS  read-write
    STATUS      current
    DESCRIPTION
        "Name of carrier company Regular expression : (?-mix:[
        -~]*)"
    ::= { ntcDevOperatorIdentification 3 }
    
ntcDevIdLongitude                OBJECT-TYPE
    SYNTAX      Float32TC
    UNITS       "deg."
    MAX-ACCESS  read-write
    STATUS      current
    DESCRIPTION
        "Geo coordinates of modulator in degrees (longitude from +000.0000 to
        +/-180.0000)"
    DEFVAL { '00000000'H }
    ::= { ntcDevLocation 1 }
    
ntcDevIdLatitude                 OBJECT-TYPE
    SYNTAX      Float32TC
    UNITS       "deg."
    MAX-ACCESS  read-write
    STATUS      current
    DESCRIPTION
        "Geo coordinates of modulator in degrees (latitude from +00.0000 to +/-90.0000)"
    DEFVAL { '00000000'H }
    ::= { ntcDevLocation 2 }
    
ntcDevAutoSave                   OBJECT-TYPE
    SYNTAX      NtcEnable
    MAX-ACCESS  read-write
    STATUS      current
    DESCRIPTION
        "Enable or disable automatic save of configuration"
    DEFVAL { off }
    ::= { ntcDevConfiguration 1 }
    
ntcDevActCfgState                OBJECT-TYPE
    SYNTAX      INTEGER { saved(0), updatedNotSaved(1) }
    MAX-ACCESS  read-only
    STATUS      current
    DESCRIPTION
        "Indicates whether the active configuration was persistently saved or not after
        the last data update."
    ::= { ntcDevConfiguration 2 }
    
ntcDevRestEnable                 OBJECT-TYPE
    SYNTAX      NtcEnable
    MAX-ACCESS  read-write
    STATUS      current
    DESCRIPTION
        "Enable or disable ReST interface."
    DEFVAL { on }
    ::= { ntcDevRest 1 }
    

--
--  Module Conformance
--

ntcDevConfGrpV1Standard          OBJECT-GROUP
    OBJECTS    {
                   ntcDevIdLabel,
                   ntcDevIdSerialNumber,
                   ntcDevIdUniqueId,
                   ntcDevIdProduct,
                   ntcDevIdDeviceDescription,
                   ntcDevIdTypeId,
                   ntcDevIdHardwareRevision,
                   ntcDevIdSoftwareId,
                   ntcDevIdSoftwareVersion,
                   ntcDevIdDeviceOptionsDescription,
                   ntcDevIdLicenseType,
                   ntcDevIdLicenseTimeRemain,
                   ntcDevFpEnable,
                   ntcDevFpiAccessLevel,
                   ntcDevSnmpNotifDestIpAddress,
                   ntcDevSnmpNotifDestType,
                   ntcDevSnmpNotifDestCommunity,
                   ntcDevCliRemoteEnable,
                   ntcDevCliInactivityTimeout,
                   ntcDevGuiEnable,
                   ntcDevFtpEnable,
                   ntcDevFtpAnonymousEnable,
                   ntcDevLogLocEnable,
                   ntcDevLogRemEnable,
                   ntcDevLogRemIpAddress,
                   ntcDevLogRemUdpPort,
                   ntcDevLogFilterLevel,
                   ntcDevDtDate,
                   ntcDevDtTime,
                   ntcDevDtNtpEnable,
                   ntcDevDtNtpPeerIpAddress,
                   ntcDevMonTemperature,
                   ntcDevMonPowerSupply,
                   ntcDevMonCpuLoad,
                   ntcDevMonMemoryUse,
                   ntcDevMonUptime,
                   ntcDevMonSensorsValue,
                   ntcDevMonHwFailureCause,
                   ntcDevMonInternalErrorCause,
                   ntcDevMonGlobalCpuLoad,
                   ntcDevAlmGenDeviceAlarm,
                   ntcDevAlmGenBootConfigFailure,
                   ntcDevAlmGenInterfaceAlarm,
                   ntcDevAlmTemperature,
                   ntcDevAlmInvalidLicenseFile,
                   ntcDevAlmFrontPanelFailure,
                   ntcDevAlmUpgradeFailure,
                   ntcDevAlmNtpNoPeerFailure,
                   ntcDevAlmLicenseExpireFile,
                   ntcDevAlmHardwareInventory,
                   ntcDevAlmHardwareFailure,
                   ntcDevAlmInternalError,
                   ntcDevAlmLicenseUpgradeFailure,
                   ntcDevReset,
                   ntcDevTelephonenbr,
                   ntcDevTelephoneext,
                   ntcDevCarrId,
                   ntcDevIdLongitude,
                   ntcDevIdLatitude,
                   ntcDevAutoSave,
                   ntcDevActCfgState,
                   ntcDevRestEnable
               }
    STATUS      current
    DESCRIPTION
        "Managed objects that constitute version 1 of a system device with standard capabilities."
    ::= { ntcDevConfGroup 1}
    
ntcDevConfCompV1Standard         MODULE-COMPLIANCE
    STATUS      current
    DESCRIPTION
        "Compliance statement for Newtec device MIB implementations."
    MODULE  -- this module
    MANDATORY-GROUPS
                  {
                      ntcDevConfGrpV1Standard
                  }
    ::= { ntcDevConfCompliance  1 }
    

END

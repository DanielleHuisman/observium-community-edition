NEWTEC-DSSOVERIPOUT-MIB DEFINITIONS ::= BEGIN

IMPORTS
    Unsigned32,
    MODULE-IDENTITY,
    OBJECT-IDENTITY,
    OBJECT-TYPE
        FROM SNMPv2-SMI

    MODULE-COMPLIANCE,
    OBJECT-GROUP
        FROM SNMPv2-CONF
    
    NtcAlarmState,
    NtcEnable,
    NtcNetworkAddress
        FROM NEWTEC-TC-MIB

    ntcFunction
        FROM NEWTEC-MAIN-MIB;


--
--  Module Identification
--

ntcDssOverIpOut   MODULE-IDENTITY
    LAST-UPDATED "201707101200Z"
    ORGANIZATION "Newtec Cy"
    CONTACT-INFO
        "Newtec Cy
         Postal: Newtec Cy
                 Laarstraat 5
                 B-9100 Sint-Niklaas
                 Belgium

                Tel: +32 3 780 65 00
                Fax: +32 3 780 65 49
                Web: www.newtec.be
                E-mail: techsupport@newtec.be"
    DESCRIPTION
        "Newtec modular DSSoIP output MIB containing definitions for DSS over IP output
        functionality."

    REVISION  "201707101200Z"
    DESCRIPTION
        "Descriptions updated with regex"
    REVISION  "201602020700Z"
    DESCRIPTION
        "initial release"
    ::= { ntcFunction  9300 }
    

--
-- Top-Level Structure
--

-- ntcDssOverIpOut content

ntcDssOIpOutObjects              OBJECT-IDENTITY
    STATUS        current
    DESCRIPTION   "Container holding ntcDssOIpOutObjects definitions."
    ::= { ntcDssOverIpOut 1 }
    
ntcDssOIpOutConformance          OBJECT-IDENTITY
    STATUS        current
    DESCRIPTION   "Conformance requirements."
    ::= { ntcDssOverIpOut 2 }
    
-- ntcDssOIpOutObjects content

ntcDssOIpOutConfiguration        OBJECT-IDENTITY
    STATUS        current
    DESCRIPTION   "Container holding ntcDssOIpOutConfiguration definitions."
    ::= { ntcDssOIpOutObjects 1 }
    
ntcDssOIpOutMonitoring           OBJECT-IDENTITY
    STATUS        current
    DESCRIPTION   "Container holding ntcDssOIpOutMonitoring definitions."
    ::= { ntcDssOIpOutObjects 2 }
    
ntcDssOIpOutAlarms               OBJECT-IDENTITY
    STATUS        current
    DESCRIPTION   "Container holding ntcDssOIpOutAlarms definitions."
    ::= { ntcDssOIpOutObjects 3 }
    
-- ntcDssOIpOutConformance content

ntcDssOIpOutConfCompliance       OBJECT-IDENTITY
    STATUS        current
    DESCRIPTION   "Device compliance statements."
    ::= { ntcDssOIpOutConformance 1 }
    
ntcDssOIpOutConfGroup            OBJECT-IDENTITY
    STATUS        current
    DESCRIPTION   "Groups used by device compliance statements."
    ::= { ntcDssOIpOutConformance 2 }
    

--
-- Managed Objects
--

ntcDssOIpOutEnable               OBJECT-TYPE
    SYNTAX      NtcEnable
    MAX-ACCESS  read-write
    STATUS      current
    DESCRIPTION
        "Enable or disable endpoint DSS over IP output."
    DEFVAL { off }
    ::= { ntcDssOIpOutConfiguration 1 }
    
ntcDssOIpOutDssEncapProtocol     OBJECT-TYPE
    SYNTAX      INTEGER { udp(0), rtp(1), rtpfeccolsonly(2), rtpfeccolsandrows(3) }
    MAX-ACCESS  read-write
    STATUS      current
    DESCRIPTION
        "Encapsulation protocol used for the output DSS over IP functionality (UDP or
        RTP)."
    DEFVAL { udp }
    ::= { ntcDssOIpOutConfiguration 2 }
    
ntcDssOIpOutDestUdpPort          OBJECT-TYPE
    SYNTAX      Unsigned32 (1..65535)
    MAX-ACCESS  read-write
    STATUS      current
    DESCRIPTION
        "Configuration of the UDP port on which the DSS over IP is sent"
    ::= { ntcDssOIpOutConfiguration 3 }
    
ntcDssOIpOutDestIpAddress        OBJECT-TYPE
    SYNTAX      NtcNetworkAddress
    MAX-ACCESS  read-write
    STATUS      current
    DESCRIPTION
        "The destination IP Address Regular expression :
        (?-mix:^\d{1,3}\.\d{1,3}\.\d{1,3}\.\d{1,3}$)"
    DEFVAL { "10.0.0.1" }
    ::= { ntcDssOIpOutConfiguration 4 }
    
ntcDssOIpOutTtl                  OBJECT-TYPE
    SYNTAX      Unsigned32 (1..255)
    MAX-ACCESS  read-write
    STATUS      current
    DESCRIPTION
        "Multicast TTL to be set in the transmitted IP multicast packets"
    DEFVAL { 8 }
    ::= { ntcDssOIpOutConfiguration 5 }
    
ntcDssOIpOutDssPacketsInFrame    OBJECT-TYPE
    SYNTAX      Unsigned32 (1..10)
    UNITS       "packets"
    MAX-ACCESS  read-write
    STATUS      current
    DESCRIPTION
        "Number of DSS packets in an UDP frame"
    DEFVAL { 10 }
    ::= { ntcDssOIpOutConfiguration 6 }
    
ntcDssOIpOutRtpFecColumns        OBJECT-TYPE
    SYNTAX      Unsigned32 (1..20)
    MAX-ACCESS  read-write
    STATUS      current
    DESCRIPTION
        "Select the RTP FEC Columns (L) to use. This value will also put a limitation
        on the value of RTP FEC Rows (D), L*D < 100 ."
    DEFVAL { 10 }
    ::= { ntcDssOIpOutConfiguration 7 }
    
ntcDssOIpOutRtpFecRows           OBJECT-TYPE
    SYNTAX      Unsigned32 (4..20)
    MAX-ACCESS  read-write
    STATUS      current
    DESCRIPTION
        "Select the RTP FEC Rows (D) to use. This value is limitated by the value of
        RTP FEC Columns (L), L*D <= 100 ."
    DEFVAL { 10 }
    ::= { ntcDssOIpOutConfiguration 8 }
    
ntcDssOIpOutCounterReset         OBJECT-TYPE
    SYNTAX      INTEGER { counting(0), reset(1) }
    MAX-ACCESS  read-write
    STATUS      current
    DESCRIPTION
        "Reset the TS over IP out traffic and monitor counters."
    DEFVAL { counting }
    ::= { ntcDssOIpOutMonitoring 1 }
    
ntcDssOIpOutBitrate              OBJECT-TYPE
    SYNTAX      Unsigned32
    UNITS       "bps"
    MAX-ACCESS  read-only
    STATUS      current
    DESCRIPTION
        "DSS over IP output bit rate in bps."
    ::= { ntcDssOIpOutMonitoring 2 }
    
ntcDssOIpOutAlNoOutput           OBJECT-TYPE
    SYNTAX      NtcAlarmState
    MAX-ACCESS  read-only
    STATUS      current
    DESCRIPTION
        "This alarm is raised when there is no output. This variable indicates the
        current status of the alarm."
    ::= { ntcDssOIpOutAlarms 1 }
    
ntcDssOIpOutAlOutputOverflow     OBJECT-TYPE
    SYNTAX      NtcAlarmState
    MAX-ACCESS  read-only
    STATUS      current
    DESCRIPTION
        "This alarm is raised when the bitrate send out is higher than the max possible
        for the given interface. This variable indicates the current status of the
        alarm."
    ::= { ntcDssOIpOutAlarms 2 }
    

--
--  Module Conformance
--

ntcDssOIpOutConfGrpV1Standard    OBJECT-GROUP
    OBJECTS    {
                   ntcDssOIpOutEnable,
                   ntcDssOIpOutDssEncapProtocol,
                   ntcDssOIpOutDestUdpPort,
                   ntcDssOIpOutDestIpAddress,
                   ntcDssOIpOutTtl,
                   ntcDssOIpOutDssPacketsInFrame,
                   ntcDssOIpOutRtpFecColumns,
                   ntcDssOIpOutRtpFecRows,
                   ntcDssOIpOutCounterReset,
                   ntcDssOIpOutBitrate,
                   ntcDssOIpOutAlNoOutput,
                   ntcDssOIpOutAlOutputOverflow
               }
    STATUS      current
    DESCRIPTION
        "Managed objects that constitute version 1 of a system device with standard capabilities."
    ::= { ntcDssOIpOutConfGroup 1}
    
ntcDssOIpOutConfCompV1Standard   MODULE-COMPLIANCE
    STATUS      current
    DESCRIPTION
        "Compliance statement for Newtec device MIB implementations."
    MODULE  -- this module
    MANDATORY-GROUPS
                  {
                      ntcDssOIpOutConfGrpV1Standard
                  }
    ::= { ntcDssOIpOutConfCompliance  1 }
    

END

NEWTEC-DUALPOWERSUPPLY-MIB DEFINITIONS ::= BEGIN

IMPORTS
    MODULE-IDENTITY,
    OBJECT-IDENTITY,
    OBJECT-TYPE
        FROM SNMPv2-SMI

    MODULE-COMPLIANCE,
    OBJECT-GROUP
        FROM SNMPv2-CONF
    
    NtcAlarmState
        FROM NEWTEC-TC-MIB

    ntcFunction
        FROM NEWTEC-MAIN-MIB;


--
--  Module Identification
--

ntcDualPowerSupply   MODULE-IDENTITY
    LAST-UPDATED "201211131200Z"
    ORGANIZATION "Newtec Cy"
    CONTACT-INFO
        "Newtec Cy
         Postal: Newtec Cy
                 Laarstraat 5
                 B-9100 Sint-Niklaas
                 Belgium

                Tel: +32 3 780 65 00
                Fax: +32 3 780 65 49
                Web: www.newtec.be
                E-mail: techsupport@newtec.be"
    DESCRIPTION
        "Newtec modular DUALPOWERSUPPLY input MIB containing definitions for Dual power
        supply functionality."

    REVISION  "201211131200Z"
    DESCRIPTION
        "Initial Release for MDM6000"
    ::= { ntcFunction  3000 }
    

--
-- Top-Level Structure
--

-- ntcDualPowerSupply content

ntcDualPSObjects                 OBJECT-IDENTITY
    STATUS        current
    DESCRIPTION   "Container holding ntcDualPSObjects definitions."
    ::= { ntcDualPowerSupply 1 }
    
ntcDualPSConformance             OBJECT-IDENTITY
    STATUS        current
    DESCRIPTION   "Conformance requirements."
    ::= { ntcDualPowerSupply 2 }
    
-- ntcDualPSObjects content

ntcDualPSAlarm                   OBJECT-IDENTITY
    STATUS        current
    DESCRIPTION   "Container holding ntcDualPSAlarm definitions."
    ::= { ntcDualPSObjects 1 }
    
-- ntcDualPSConformance content

ntcDualPSConfCompliance          OBJECT-IDENTITY
    STATUS        current
    DESCRIPTION   "Device compliance statements."
    ::= { ntcDualPSConformance 1 }
    
ntcDualPSConfGroup               OBJECT-IDENTITY
    STATUS        current
    DESCRIPTION   "Groups used by device compliance statements."
    ::= { ntcDualPSConformance 2 }
    

--
-- Managed Objects
--

ntcDualPSAlmPowerSupplyAFailure  OBJECT-TYPE
    SYNTAX      NtcAlarmState
    MAX-ACCESS  read-only
    STATUS      current
    DESCRIPTION
        "This alarm is raised when power supply A has failed. This variable indicates
        the current status of the alarm."
    ::= { ntcDualPSAlarm 1 }
    
ntcDualPSAlmPowerSupplyBFailure  OBJECT-TYPE
    SYNTAX      NtcAlarmState
    MAX-ACCESS  read-only
    STATUS      current
    DESCRIPTION
        "This alarm is raised when power supply B has failed. This variable indicates
        the current status of the alarm."
    ::= { ntcDualPSAlarm 2 }
    

--
--  Module Conformance
--

ntcDualPSConfGrpV1Standard       OBJECT-GROUP
    OBJECTS    {
                   ntcDualPSAlmPowerSupplyAFailure,
                   ntcDualPSAlmPowerSupplyBFailure
               }
    STATUS      current
    DESCRIPTION
        "Managed objects that constitute version 1 of a system device with standard capabilities."
    ::= { ntcDualPSConfGroup 1}
    
ntcDualPSConfCompV1Standard      MODULE-COMPLIANCE
    STATUS      current
    DESCRIPTION
        "Compliance statement for Newtec device MIB implementations."
    MODULE  -- this module
    MANDATORY-GROUPS
                  {
                      ntcDualPSConfGrpV1Standard
                  }
    ::= { ntcDualPSConfCompliance  1 }
    

END

NEWTEC-ENCAPDECAP-MIB DEFINITIONS ::= BEGIN

IMPORTS
    MODULE-IDENTITY,
    OBJECT-IDENTITY,
    OBJECT-TYPE
        FROM SNMPv2-SMI

    MODULE-COMPLIANCE,
    OBJECT-GROUP
        FROM SNMPv2-CONF
    
    ntcFunction
        FROM NEWTEC-MAIN-MIB;


--
--  Module Identification
--

ntcEncapDecap   MODULE-IDENTITY
    LAST-UPDATED "201402031200Z"
    ORGANIZATION "Newtec Cy"
    CONTACT-INFO
        "Newtec Cy
         Postal: Newtec Cy
                 Laarstraat 5
                 B-9100 Sint-Niklaas
                 Belgium

                Tel: +32 3 780 65 00
                Fax: +32 3 780 65 49
                Web: www.newtec.be
                E-mail: techsupport@newtec.be"
    DESCRIPTION
        "Newtec modular MIB containing definitions that apply to both encapsulation and
        decapsulation."

    REVISION  "201402031200Z"
    DESCRIPTION
        "Common encapsulation + decapsulation parameters"
    ::= { ntcFunction  2220 }
    

--
-- Top-Level Structure
--

-- ntcEncapDecap content

ntcEncapDecapObjects             OBJECT-IDENTITY
    STATUS        current
    DESCRIPTION   "Container holding ntcEncapDecapObjects definitions."
    ::= { ntcEncapDecap 1 }
    
ntcEncapDecapConformance         OBJECT-IDENTITY
    STATUS        current
    DESCRIPTION   "Conformance requirements."
    ::= { ntcEncapDecap 2 }
    
-- ntcEncapDecapConformance content

ntcEncapDecapConfCompliance      OBJECT-IDENTITY
    STATUS        current
    DESCRIPTION   "Device compliance statements."
    ::= { ntcEncapDecapConformance 1 }
    
ntcEncapDecapConfGroup           OBJECT-IDENTITY
    STATUS        current
    DESCRIPTION   "Groups used by device compliance statements."
    ::= { ntcEncapDecapConformance 2 }
    

--
-- Managed Objects
--

ntcEncapDecapForwardingMode      OBJECT-TYPE
    SYNTAX      INTEGER { l2(0), l3(1) }
    MAX-ACCESS  read-write
    STATUS      current
    DESCRIPTION
        "The default forwarding mode."
    DEFVAL { l3 }
    ::= { ntcEncapDecapObjects 1 }
    

--
--  Module Conformance
--

ntcEncapDecapConfGrpV1Standard   OBJECT-GROUP
    OBJECTS    {
                   ntcEncapDecapForwardingMode
               }
    STATUS      current
    DESCRIPTION
        "Managed objects that constitute version 1 of a system device with standard capabilities."
    ::= { ntcEncapDecapConfGroup 1}
    
ntcEncapDecapConfCompV1Standard  MODULE-COMPLIANCE
    STATUS      current
    DESCRIPTION
        "Compliance statement for Newtec device MIB implementations."
    MODULE  -- this module
    MANDATORY-GROUPS
                  {
                      ntcEncapDecapConfGrpV1Standard
                  }
    ::= { ntcEncapDecapConfCompliance  1 }
    

END

NEWTEC-ETHERNET-MIB DEFINITIONS ::= BEGIN

IMPORTS
    Unsigned32,
    Counter32,
    Counter64,
    MODULE-IDENTITY,
    OBJECT-IDENTITY,
    OBJECT-TYPE
        FROM SNMPv2-SMI

    MODULE-COMPLIANCE,
    OBJECT-GROUP
        FROM SNMPv2-CONF
    
    NtcAlarmState,
    NtcEnable
        FROM NEWTEC-TC-MIB

    MacAddress
        FROM SNMPv2-TC

    ntcFunction
        FROM NEWTEC-MAIN-MIB;


--
--  Module Identification
--

ntcEthernet   MODULE-IDENTITY
    LAST-UPDATED "201802020900Z"
    ORGANIZATION "Newtec Cy"
    CONTACT-INFO
        "Newtec Cy
         Postal: Newtec Cy
                 Laarstraat 5
                 B-9100 Sint-Niklaas
                 Belgium

                Tel: +32 3 780 65 00
                Fax: +32 3 780 65 49
                Web: www.newtec.be
                E-mail: techsupport@newtec.be"
    DESCRIPTION
        "Newtec modular ethernet interface MIB containing definitions for management
        and ethernet interface functionality."

    REVISION  "201802020900Z"
    DESCRIPTION
        "Only Cosmetic change of units"
    REVISION  "201707101200Z"
    DESCRIPTION
        "Input and Output error counters for Data and Mgmt interfaces"
    REVISION  "201411241200Z"
    DESCRIPTION
        "ntcEtherIfRedDataGwUnreachImpact added"
    REVISION  "201305220600Z"
    DESCRIPTION
        "Release for MDM6000 and NOP1760 R1.1"
    REVISION  "201303271000Z"
    DESCRIPTION
        "Release for M6100 R1.3"
    REVISION  "201301081200Z"
    DESCRIPTION
        "Release for MDM6000 and NOP1760 R1.0"
    REVISION  "201206281200Z"
    DESCRIPTION
        "Release for M6100 R1.2"
    ::= { ntcFunction  500 }
    

--
-- Top-Level Structure
--

-- ntcEthernet content

ntcEtherObjects                  OBJECT-IDENTITY
    STATUS        current
    DESCRIPTION   "Container holding ntcEtherObjects definitions."
    ::= { ntcEthernet 1 }
    
ntcEtherConformance              OBJECT-IDENTITY
    STATUS        current
    DESCRIPTION   "Conformance requirements."
    ::= { ntcEthernet 2 }
    
-- ntcEtherObjects content

ntcEtherInterfaceRedundancy      OBJECT-IDENTITY
    STATUS        current
    DESCRIPTION   "Container holding ntcEtherInterfaceRedundancy definitions."
    ::= { ntcEtherObjects 5 }
    
ntcEtherAlarm                    OBJECT-IDENTITY
    STATUS        current
    DESCRIPTION   "Container holding ntcEtherAlarm definitions."
    ::= { ntcEtherObjects 6 }
    
-- ntcEtherInterfaceRedundancy content

ntcEtherIfRedMgmt                OBJECT-IDENTITY
    STATUS        current
    DESCRIPTION   "Container holding ntcEtherIfRedMgmt definitions."
    ::= { ntcEtherInterfaceRedundancy 1 }
    
ntcEtherIfRedData                OBJECT-IDENTITY
    STATUS        current
    DESCRIPTION   "Container holding ntcEtherIfRedData definitions."
    ::= { ntcEtherInterfaceRedundancy 2 }
    
ntcEtherIfRedSat                 OBJECT-IDENTITY
    STATUS        current
    DESCRIPTION   "Container holding ntcEtherIfRedSat definitions."
    ::= { ntcEtherInterfaceRedundancy 3 }
    
-- ntcEtherConformance content

ntcEtherConfCompliance           OBJECT-IDENTITY
    STATUS        current
    DESCRIPTION   "Device compliance statements."
    ::= { ntcEtherConformance 1 }
    
ntcEtherConfGroup                OBJECT-IDENTITY
    STATUS        current
    DESCRIPTION   "Groups used by device compliance statements."
    ::= { ntcEtherConformance 2 }
    

--
-- Managed Objects
--

ntcEtherLinkMgmtTable            OBJECT-TYPE
    SYNTAX      SEQUENCE OF NtcEtherLinkMgmtEntry
    MAX-ACCESS  not-accessible
    STATUS      current
    DESCRIPTION
        "A table containing the ntcEtherLinkMgmt"
    ::= { ntcEtherObjects 1 }

ntcEtherLinkMgmtEntry            OBJECT-TYPE
    SYNTAX      NtcEtherLinkMgmtEntry
    MAX-ACCESS  not-accessible
    STATUS      current
    DESCRIPTION
        "A conceptual row of the ntcEtherLinkMgmtTable."
    INDEX   { ntcEtherLinkMgmtInterface  }
    ::= { ntcEtherLinkMgmtTable 1 }

NtcEtherLinkMgmtEntry            ::= SEQUENCE {
    ntcEtherLinkMgmtInterface           INTEGER,
    ntcEtherLinkMgmtEnable              NtcEnable,
    ntcEtherLinkMgmtMacAddress          MacAddress,
    ntcEtherLinkMgmtAutoNegotiation     NtcEnable,
    ntcEtherLinkMgmtAdvertisedSpeeds    INTEGER,
    ntcEtherLinkMgmtForcedSpeed         INTEGER,
    ntcEtherLinkMgmtLinkState           INTEGER,
    ntcEtherLinkMgmtMtu                 Unsigned32
    }
    
ntcEtherLinkMgmtInterface        OBJECT-TYPE
    SYNTAX      INTEGER { mgmt1(0), mgmt2(1), mgmtfp(2) }
    MAX-ACCESS  not-accessible
    STATUS      current
    DESCRIPTION
        "The name of Management Ethernet interface"
    ::= { ntcEtherLinkMgmtEntry 1 }
    
ntcEtherLinkMgmtEnable           OBJECT-TYPE
    SYNTAX      NtcEnable
    MAX-ACCESS  read-write
    STATUS      current
    DESCRIPTION
        "Enable or disable the corresponding Ethernet interface."
    DEFVAL { off }
    ::= { ntcEtherLinkMgmtEntry 2 }
    
ntcEtherLinkMgmtMacAddress       OBJECT-TYPE
    SYNTAX      MacAddress
    MAX-ACCESS  read-only
    STATUS      current
    DESCRIPTION
        "MAC address of an Ethernet interface."
    ::= { ntcEtherLinkMgmtEntry 3 }
    
ntcEtherLinkMgmtAutoNegotiation  OBJECT-TYPE
    SYNTAX      NtcEnable
    MAX-ACCESS  read-write
    STATUS      current
    DESCRIPTION
        "Enable or disable autonegotiation. AutoNegotiation is a procedure where two
        connected devices choose the same Ethernet transmission parameters (Speed,
        duplex/simplex mode and flow control)."
    DEFVAL { on }
    ::= { ntcEtherLinkMgmtEntry 4 }
    
ntcEtherLinkMgmtAdvertisedSpeeds OBJECT-TYPE
    SYNTAX      INTEGER { all(0), e10BTHalfDuplex(1), e10BTFullDuplex(2), e100BTHalfDuplex(3), e100BTFullDuplex(4), e1000BTFullDuplex(5) }
    MAX-ACCESS  read-write
    STATUS      current
    DESCRIPTION
        "Configure the advertised speeds during autonegotiation."
    DEFVAL { all }
    ::= { ntcEtherLinkMgmtEntry 5 }
    
ntcEtherLinkMgmtForcedSpeed      OBJECT-TYPE
    SYNTAX      INTEGER { e10BTHalfDuplex(1), e10BTFullDuplex(2), e100BTHalfDuplex(3), e100BTFullDuplex(4) }
    MAX-ACCESS  read-write
    STATUS      current
    DESCRIPTION
        "Configure forced speed with disabled autonegotation."
    DEFVAL { e100BTFullDuplex }
    ::= { ntcEtherLinkMgmtEntry 6 }
    
ntcEtherLinkMgmtLinkState        OBJECT-TYPE
    SYNTAX      INTEGER { linkDown(0), e10BTHalfDuplex(1), e10BTFullDuplex(2), e100BTHalfDuplex(3), e100BTFullDuplex(4), e1000BTFullDuplex(5), e10GSFPplus(6) }
    MAX-ACCESS  read-only
    STATUS      current
    DESCRIPTION
        "Indicates the link state of the Ethernet interface."
    ::= { ntcEtherLinkMgmtEntry 7 }
    
ntcEtherLinkMgmtMtu              OBJECT-TYPE
    SYNTAX      Unsigned32 (68..9216)
    MAX-ACCESS  read-write
    STATUS      current
    DESCRIPTION
        "Configuration of the MTU of the interface."
    DEFVAL { 1500 }
    ::= { ntcEtherLinkMgmtEntry 8 }
    
ntcEtherLinkDataTable            OBJECT-TYPE
    SYNTAX      SEQUENCE OF NtcEtherLinkDataEntry
    MAX-ACCESS  not-accessible
    STATUS      current
    DESCRIPTION
        "A table containing the ntcEtherLinkData"
    ::= { ntcEtherObjects 2 }

ntcEtherLinkDataEntry            OBJECT-TYPE
    SYNTAX      NtcEtherLinkDataEntry
    MAX-ACCESS  not-accessible
    STATUS      current
    DESCRIPTION
        "A conceptual row of the ntcEtherLinkDataTable."
    INDEX   { ntcEtherLinkDataInterface  }
    ::= { ntcEtherLinkDataTable 1 }

NtcEtherLinkDataEntry            ::= SEQUENCE {
    ntcEtherLinkDataInterface           INTEGER,
    ntcEtherLinkDataEnable              NtcEnable,
    ntcEtherLinkDataMacAddress          MacAddress,
    ntcEtherLinkDataAutoNegotiation     NtcEnable,
    ntcEtherLinkDataAdvertisedSpeeds    INTEGER,
    ntcEtherLinkDataForcedSpeed         INTEGER,
    ntcEtherLinkDataLinkState           INTEGER,
    ntcEtherLinkDataMtu                 Unsigned32
    }
    
ntcEtherLinkDataInterface        OBJECT-TYPE
    SYNTAX      INTEGER { data1(0), data2(1), sat1(2), sat2(3) }
    MAX-ACCESS  not-accessible
    STATUS      current
    DESCRIPTION
        "The name of a Data Ethernet Interface"
    ::= { ntcEtherLinkDataEntry 1 }
    
ntcEtherLinkDataEnable           OBJECT-TYPE
    SYNTAX      NtcEnable
    MAX-ACCESS  read-write
    STATUS      current
    DESCRIPTION
        "Enable or disable the corresponding Ethernet interface."
    DEFVAL { off }
    ::= { ntcEtherLinkDataEntry 2 }
    
ntcEtherLinkDataMacAddress       OBJECT-TYPE
    SYNTAX      MacAddress
    MAX-ACCESS  read-only
    STATUS      current
    DESCRIPTION
        "MAC address of an Ethernet interface."
    ::= { ntcEtherLinkDataEntry 3 }
    
ntcEtherLinkDataAutoNegotiation  OBJECT-TYPE
    SYNTAX      NtcEnable
    MAX-ACCESS  read-write
    STATUS      current
    DESCRIPTION
        "Enable or disable autonegotiation. AutoNegotiation is a procedure where two
        connected devices choose the same Ethernet transmission parameters (Speed,
        duplex/simplex mode and flow control)."
    DEFVAL { on }
    ::= { ntcEtherLinkDataEntry 4 }
    
ntcEtherLinkDataAdvertisedSpeeds OBJECT-TYPE
    SYNTAX      INTEGER { all(0), e10BTHalfDuplex(1), e10BTFullDuplex(2), e100BTHalfDuplex(3), e100BTFullDuplex(4), e1000BTFullDuplex(5) }
    MAX-ACCESS  read-write
    STATUS      current
    DESCRIPTION
        "Configure the advertised speeds during autonegotiation."
    DEFVAL { all }
    ::= { ntcEtherLinkDataEntry 5 }
    
ntcEtherLinkDataForcedSpeed      OBJECT-TYPE
    SYNTAX      INTEGER { e10BTHalfDuplex(1), e10BTFullDuplex(2), e100BTHalfDuplex(3), e100BTFullDuplex(4) }
    MAX-ACCESS  read-write
    STATUS      current
    DESCRIPTION
        "Configure forced speed with disabled autonegotation."
    DEFVAL { e100BTFullDuplex }
    ::= { ntcEtherLinkDataEntry 6 }
    
ntcEtherLinkDataLinkState        OBJECT-TYPE
    SYNTAX      INTEGER { linkDown(0), e10BTHalfDuplex(1), e10BTFullDuplex(2), e100BTHalfDuplex(3), e100BTFullDuplex(4), e1000BTFullDuplex(5), e10GSFPplus(6) }
    MAX-ACCESS  read-only
    STATUS      current
    DESCRIPTION
        "Indicates the link state of the Ethernet interface."
    ::= { ntcEtherLinkDataEntry 7 }
    
ntcEtherLinkDataMtu              OBJECT-TYPE
    SYNTAX      Unsigned32 (68..9216)
    MAX-ACCESS  read-write
    STATUS      current
    DESCRIPTION
        "Configuration of the MTU of the interface."
    DEFVAL { 1500 }
    ::= { ntcEtherLinkDataEntry 8 }
    
ntcEtherStatMgmtTable            OBJECT-TYPE
    SYNTAX      SEQUENCE OF NtcEtherStatMgmtEntry
    MAX-ACCESS  not-accessible
    STATUS      current
    DESCRIPTION
        "A table containing the ntcEtherStatMgmt"
    ::= { ntcEtherObjects 3 }

ntcEtherStatMgmtEntry            OBJECT-TYPE
    SYNTAX      NtcEtherStatMgmtEntry
    MAX-ACCESS  not-accessible
    STATUS      current
    DESCRIPTION
        "A conceptual row of the ntcEtherStatMgmtTable."
    INDEX   { ntcEtherStatMgmtInterface  }
    ::= { ntcEtherStatMgmtTable 1 }

NtcEtherStatMgmtEntry            ::= SEQUENCE {
    ntcEtherStatMgmtInterface        INTEGER,
    ntcEtherStatMgmtInputBytes       Counter32,
    ntcEtherStatMgmtInputPackets     Counter32,
    ntcEtherStatMgmtInputDropped     Counter32,
    ntcEtherStatMgmtOutputBytes      Counter32,
    ntcEtherStatMgmtOutputPackets    Counter32,
    ntcEtherStatMgmtOutputDropped    Counter32,
    ntcEtherStatMgmtInputErrors      Counter64,
    ntcEtherStatMgmtOutputerrors     Counter64
    }
    
ntcEtherStatMgmtInterface        OBJECT-TYPE
    SYNTAX      INTEGER { mgmt1(0), mgmt2(1), mgmtfp(2), mgmtbond(3) }
    MAX-ACCESS  not-accessible
    STATUS      current
    DESCRIPTION
        "The name of a Management Ethernet Interface"
    ::= { ntcEtherStatMgmtEntry 1 }
    
ntcEtherStatMgmtInputBytes       OBJECT-TYPE
    SYNTAX      Counter32
    UNITS       "bytes"
    MAX-ACCESS  read-only
    STATUS      current
    DESCRIPTION
        "Ethernet input byte counter."
    ::= { ntcEtherStatMgmtEntry 2 }
    
ntcEtherStatMgmtInputPackets     OBJECT-TYPE
    SYNTAX      Counter32
    UNITS       "packets"
    MAX-ACCESS  read-only
    STATUS      current
    DESCRIPTION
        "Ethernet input packet counter."
    ::= { ntcEtherStatMgmtEntry 3 }
    
ntcEtherStatMgmtInputDropped     OBJECT-TYPE
    SYNTAX      Counter32
    UNITS       "packets"
    MAX-ACCESS  read-only
    STATUS      current
    DESCRIPTION
        "Indicates the number of dropped packets at input."
    ::= { ntcEtherStatMgmtEntry 4 }
    
ntcEtherStatMgmtOutputBytes      OBJECT-TYPE
    SYNTAX      Counter32
    UNITS       "bytes"
    MAX-ACCESS  read-only
    STATUS      current
    DESCRIPTION
        "Indicates the number of available bytes on the output."
    ::= { ntcEtherStatMgmtEntry 5 }
    
ntcEtherStatMgmtOutputPackets    OBJECT-TYPE
    SYNTAX      Counter32
    UNITS       "packets"
    MAX-ACCESS  read-only
    STATUS      current
    DESCRIPTION
        "Ethernet output packet counter"
    ::= { ntcEtherStatMgmtEntry 6 }
    
ntcEtherStatMgmtOutputDropped    OBJECT-TYPE
    SYNTAX      Counter32
    UNITS       "packets"
    MAX-ACCESS  read-only
    STATUS      current
    DESCRIPTION
        "Ethernet output packets dropped counter"
    ::= { ntcEtherStatMgmtEntry 7 }
    
ntcEtherStatMgmtInputErrors      OBJECT-TYPE
    SYNTAX      Counter64
    UNITS       "packets"
    MAX-ACCESS  read-only
    STATUS      current
    DESCRIPTION
        "Indicates the number of error packets at input."
    ::= { ntcEtherStatMgmtEntry 8 }
    
ntcEtherStatMgmtOutputerrors     OBJECT-TYPE
    SYNTAX      Counter64
    UNITS       "packets"
    MAX-ACCESS  read-only
    STATUS      current
    DESCRIPTION
        "Indicates the number of error packets at output."
    ::= { ntcEtherStatMgmtEntry 9 }
    
ntcEtherStatDataTable            OBJECT-TYPE
    SYNTAX      SEQUENCE OF NtcEtherStatDataEntry
    MAX-ACCESS  not-accessible
    STATUS      current
    DESCRIPTION
        "A table containing the ntcEtherStatData"
    ::= { ntcEtherObjects 4 }

ntcEtherStatDataEntry            OBJECT-TYPE
    SYNTAX      NtcEtherStatDataEntry
    MAX-ACCESS  not-accessible
    STATUS      current
    DESCRIPTION
        "A conceptual row of the ntcEtherStatDataTable."
    INDEX   { ntcEtherStatDataInterface  }
    ::= { ntcEtherStatDataTable 1 }

NtcEtherStatDataEntry            ::= SEQUENCE {
    ntcEtherStatDataInterface        INTEGER,
    ntcEtherStatDataInputBytes       Counter32,
    ntcEtherStatDataInputPackets     Counter32,
    ntcEtherStatDataInputDropped     Counter32,
    ntcEtherStatDataOutputBytes      Counter32,
    ntcEtherStatDataOutputPackets    Counter32,
    ntcEtherStatDataOutputDropped    Counter32,
    ntcEtherStatDataInputErrors      Counter64,
    ntcEtherStatDataOutputerrors     Counter64
    }
    
ntcEtherStatDataInterface        OBJECT-TYPE
    SYNTAX      INTEGER { data1(0), data2(1), databond(2), sat1(3), sat2(4), satbond(5) }
    MAX-ACCESS  not-accessible
    STATUS      current
    DESCRIPTION
        "The name of a Data Ethernet interface"
    ::= { ntcEtherStatDataEntry 1 }
    
ntcEtherStatDataInputBytes       OBJECT-TYPE
    SYNTAX      Counter32
    UNITS       "bytes"
    MAX-ACCESS  read-only
    STATUS      current
    DESCRIPTION
        "Ethernet input byte counter."
    ::= { ntcEtherStatDataEntry 2 }
    
ntcEtherStatDataInputPackets     OBJECT-TYPE
    SYNTAX      Counter32
    UNITS       "packets"
    MAX-ACCESS  read-only
    STATUS      current
    DESCRIPTION
        "Ethernet input packet counter."
    ::= { ntcEtherStatDataEntry 3 }
    
ntcEtherStatDataInputDropped     OBJECT-TYPE
    SYNTAX      Counter32
    UNITS       "packets"
    MAX-ACCESS  read-only
    STATUS      current
    DESCRIPTION
        "Indicates the number of dropped packets at input."
    ::= { ntcEtherStatDataEntry 4 }
    
ntcEtherStatDataOutputBytes      OBJECT-TYPE
    SYNTAX      Counter32
    UNITS       "bytes"
    MAX-ACCESS  read-only
    STATUS      current
    DESCRIPTION
        "Indicates the number of available bytes on the output."
    ::= { ntcEtherStatDataEntry 5 }
    
ntcEtherStatDataOutputPackets    OBJECT-TYPE
    SYNTAX      Counter32
    UNITS       "packets"
    MAX-ACCESS  read-only
    STATUS      current
    DESCRIPTION
        "Ethernet output packet counter"
    ::= { ntcEtherStatDataEntry 6 }
    
ntcEtherStatDataOutputDropped    OBJECT-TYPE
    SYNTAX      Counter32
    UNITS       "packets"
    MAX-ACCESS  read-only
    STATUS      current
    DESCRIPTION
        "Ethernet output packets dropped counter"
    ::= { ntcEtherStatDataEntry 7 }
    
ntcEtherStatDataInputErrors      OBJECT-TYPE
    SYNTAX      Counter64
    UNITS       "packets"
    MAX-ACCESS  read-only
    STATUS      current
    DESCRIPTION
        "Indicates the number of error packets at input."
    ::= { ntcEtherStatDataEntry 8 }
    
ntcEtherStatDataOutputerrors     OBJECT-TYPE
    SYNTAX      Counter64
    UNITS       "packets"
    MAX-ACCESS  read-only
    STATUS      current
    DESCRIPTION
        "Indicates the number of error packets at output."
    ::= { ntcEtherStatDataEntry 9 }
    
ntcEtherIfRedMgmtSwitchOrder     OBJECT-TYPE
    SYNTAX      INTEGER { none(0), mgmt1or2(1), mgmt1before2(2), mgmt2before1(3) }
    MAX-ACCESS  read-write
    STATUS      current
    DESCRIPTION
        "Configuration of the management interface link redundancy."
    DEFVAL { none }
    ::= { ntcEtherIfRedMgmt 1 }
    
ntcEtherIfRedMgmtSwitchCount     OBJECT-TYPE
    SYNTAX      Counter32
    MAX-ACCESS  read-only
    STATUS      current
    DESCRIPTION
        "Counts the number of times the device switched to another Ethernet data
        interface."
    ::= { ntcEtherIfRedMgmt 2 }
    
ntcEtherIfRedMgmtActiveInterface OBJECT-TYPE
    SYNTAX      INTEGER { none(0), mgmt1(1), mgmt2(2), na(3) }
    MAX-ACCESS  read-only
    STATUS      current
    DESCRIPTION
        "Displays the active interface of the MGMT redundancy group."
    ::= { ntcEtherIfRedMgmt 3 }
    
ntcEtherIfRedDataSwitchOrder     OBJECT-TYPE
    SYNTAX      INTEGER { none(0), data1or2(1), data1before2(2), data2before1(3), data1(4), data2(5) }
    MAX-ACCESS  read-write
    STATUS      current
    DESCRIPTION
        "Configure the data interface link redundancy."
    DEFVAL { none }
    ::= { ntcEtherIfRedData 1 }
    
ntcEtherIfRedDataSwitchCount     OBJECT-TYPE
    SYNTAX      Counter32
    MAX-ACCESS  read-only
    STATUS      current
    DESCRIPTION
        "Counts the number of times the device switched to another Ethernet data
        interface."
    ::= { ntcEtherIfRedData 2 }
    
ntcEtherIfRedDataActiveInterface OBJECT-TYPE
    SYNTAX      INTEGER { none(0), data1(1), data2(2), na(3) }
    MAX-ACCESS  read-only
    STATUS      current
    DESCRIPTION
        "Displays the active interface of the Data redundancy group"
    ::= { ntcEtherIfRedData 3 }
    
ntcEtherIfRedDataGwUnreachImpact OBJECT-TYPE
    SYNTAX      INTEGER { noImpact(0), linkRedundancyTrigger(1) }
    MAX-ACCESS  read-write
    STATUS      current
    DESCRIPTION
        "Configure the impact of a Gateway Unreachable alarm on link redundancy. We
        recommend that the gateway is reachable via both links, so you can keep the
        default setting of noImpact. A real link alarm, has priority above the gateway
        unreachable alarm. If a switchover happened due to an unreachable gateway, we
        operate non-revertive (we don't switch back because the gateway is again
        reachable via the original interface, however we do switch back because of a
        new alarm that might occur)."
    DEFVAL { noImpact }
    ::= { ntcEtherIfRedData 4 }
    
ntcEtherIfRedSatSwitchOrder      OBJECT-TYPE
    SYNTAX      INTEGER { none(0), sat1or2(1), sat1before2(2), sat2before1(3), sat1(4), sat2(5) }
    MAX-ACCESS  read-write
    STATUS      current
    DESCRIPTION
        "Configure the sat interface link redundancy."
    DEFVAL { none }
    ::= { ntcEtherIfRedSat 1 }
    
ntcEtherIfRedSatSwitchCount      OBJECT-TYPE
    SYNTAX      Counter32
    MAX-ACCESS  read-only
    STATUS      current
    DESCRIPTION
        "Counts the number of times the device switched to another Ethernet sat
        interface."
    ::= { ntcEtherIfRedSat 2 }
    
ntcEtherIfRedSatActiveInterface  OBJECT-TYPE
    SYNTAX      INTEGER { none(0), sat1(1), sat2(2), na(3) }
    MAX-ACCESS  read-only
    STATUS      current
    DESCRIPTION
        "Displays the active interface of the Sat redundancy group"
    ::= { ntcEtherIfRedSat 3 }
    
ntcEtherAlmMgmt1EthLinkFail      OBJECT-TYPE
    SYNTAX      NtcAlarmState
    MAX-ACCESS  read-only
    STATUS      current
    DESCRIPTION
        "This alarm is raised when there is no signal on the corresponding Ethernet
        interface. This variable indicates the current status of the alarm."
    ::= { ntcEtherAlarm 1 }
    
ntcEtherAlmMgmt1EthHalfDuplex    OBJECT-TYPE
    SYNTAX      NtcAlarmState
    MAX-ACCESS  read-only
    STATUS      current
    DESCRIPTION
        "This alarm is raised when an Ethernet interface is in half duplex mode as a
        result of a link negotiation. The alarm is not raised when the Ethernet
        interface was forced in half duplex mode by configuration on the device. This
        variable indicates the current status of the alarm."
    ::= { ntcEtherAlarm 2 }
    
ntcEtherAlmMgmt2EthLinkFail      OBJECT-TYPE
    SYNTAX      NtcAlarmState
    MAX-ACCESS  read-only
    STATUS      current
    DESCRIPTION
        "This alarm is raised when there is no signal on the corresponding Ethernet
        interface. This variable indicates the current status of the alarm."
    ::= { ntcEtherAlarm 3 }
    
ntcEtherAlmMgmt2EthHalfDuplex    OBJECT-TYPE
    SYNTAX      NtcAlarmState
    MAX-ACCESS  read-only
    STATUS      current
    DESCRIPTION
        "This alarm is raised when an Ethernet interface is in half duplex mode as a
        result of a link negotiation. The alarm is not raised when the Ethernet
        interface was forced in half duplex mode by configuration on the device. This
        variable indicates the current status of the alarm."
    ::= { ntcEtherAlarm 4 }
    
ntcEtherAlmData1EthLinkFail      OBJECT-TYPE
    SYNTAX      NtcAlarmState
    MAX-ACCESS  read-only
    STATUS      current
    DESCRIPTION
        "This alarm is raised when there is no signal on the corresponding Ethernet
        interface. This variable indicates the current status of the alarm."
    ::= { ntcEtherAlarm 5 }
    
ntcEtherAlmData1EthHalfDuplex    OBJECT-TYPE
    SYNTAX      NtcAlarmState
    MAX-ACCESS  read-only
    STATUS      current
    DESCRIPTION
        "This alarm is raised when an Ethernet interface is in half duplex mode as a
        result of a link negotiation. The alarm is not raised when the Ethernet
        interface was forced in half duplex mode by configuration on the device. This
        variable indicates the current status of the alarm."
    ::= { ntcEtherAlarm 6 }
    
ntcEtherAlmData2EthLinkFail      OBJECT-TYPE
    SYNTAX      NtcAlarmState
    MAX-ACCESS  read-only
    STATUS      current
    DESCRIPTION
        "This alarm is raised when there is no signal on the corresponding Ethernet
        interface. This variable indicates the current status of the alarm."
    ::= { ntcEtherAlarm 7 }
    
ntcEtherAlmData2EthHalfDuplex    OBJECT-TYPE
    SYNTAX      NtcAlarmState
    MAX-ACCESS  read-only
    STATUS      current
    DESCRIPTION
        "This alarm is raised when an Ethernet interface is in half duplex mode as a
        result of a link negotiation. The alarm is not raised when the Ethernet
        interface was forced in half duplex mode by configuration on the device. This
        variable indicates the current status of the alarm."
    ::= { ntcEtherAlarm 8 }
    
ntcEtherAlmMgmtFpEthLinkFail     OBJECT-TYPE
    SYNTAX      NtcAlarmState
    MAX-ACCESS  read-only
    STATUS      current
    DESCRIPTION
        "This alarm is raised when there is no signal on the corresponding Ethernet
        interface. This variable indicates the current status of the alarm."
    ::= { ntcEtherAlarm 9 }
    
ntcEtherAlmMgmtFpEthHalfDuplex   OBJECT-TYPE
    SYNTAX      NtcAlarmState
    MAX-ACCESS  read-only
    STATUS      current
    DESCRIPTION
        "This alarm is raised when an Ethernet interface is in half duplex mode as a
        result of a link negotiation. The alarm is not raised when the Ethernet
        interface was forced in half duplex mode by configuration on the device. This
        variable indicates the current status of the alarm."
    ::= { ntcEtherAlarm 10 }
    
ntcEtherAlmMgmtEthInterfaceFail  OBJECT-TYPE
    SYNTAX      NtcAlarmState
    MAX-ACCESS  read-only
    STATUS      current
    DESCRIPTION
        "This alarm is raised when a failure is detected on the Ethernet interface.
        This variable indicates the current status of the alarm."
    ::= { ntcEtherAlarm 11 }
    
ntcEtherAlmDataEthInterfaceFail  OBJECT-TYPE
    SYNTAX      NtcAlarmState
    MAX-ACCESS  read-only
    STATUS      current
    DESCRIPTION
        "This alarm is raised when a failure is detected on the Ethernet interface.
        This variable indicates the current status of the alarm."
    ::= { ntcEtherAlarm 12 }
    
ntcEtherAlmSat1EthLinkFail       OBJECT-TYPE
    SYNTAX      NtcAlarmState
    MAX-ACCESS  read-only
    STATUS      current
    DESCRIPTION
        "This alarm is raised when there is no signal on the corresponding Ethernet
        interface. This variable indicates the current status of the alarm."
    ::= { ntcEtherAlarm 13 }
    
ntcEtherAlmSat1EthHalfDuplex     OBJECT-TYPE
    SYNTAX      NtcAlarmState
    MAX-ACCESS  read-only
    STATUS      current
    DESCRIPTION
        "This alarm is raised when an Ethernet interface is in half duplex mode as a
        result of a link negotiation. The alarm is not raised when the Ethernet
        interface was forced in half duplex mode by configuration on the device. This
        variable indicates the current status of the alarm."
    ::= { ntcEtherAlarm 14 }
    
ntcEtherAlmSat2EthLinkFail       OBJECT-TYPE
    SYNTAX      NtcAlarmState
    MAX-ACCESS  read-only
    STATUS      current
    DESCRIPTION
        "This alarm is raised when there is no signal on the corresponding Ethernet
        interface. This variable indicates the current status of the alarm."
    ::= { ntcEtherAlarm 15 }
    
ntcEtherAlmSat2EthHalfDuplex     OBJECT-TYPE
    SYNTAX      NtcAlarmState
    MAX-ACCESS  read-only
    STATUS      current
    DESCRIPTION
        "This alarm is raised when an Ethernet interface is in half duplex mode as a
        result of a link negotiation. The alarm is not raised when the Ethernet
        interface was forced in half duplex mode by configuration on the device. This
        variable indicates the current status of the alarm."
    ::= { ntcEtherAlarm 16 }
    
ntcEtherAlmSatEthInterfaceFail   OBJECT-TYPE
    SYNTAX      NtcAlarmState
    MAX-ACCESS  read-only
    STATUS      current
    DESCRIPTION
        "This alarm is raised when a failure is detected on the Ethernet interface.
        This variable indicates the current status of the alarm."
    ::= { ntcEtherAlarm 17 }
    
ntcEtherAlmMgmtEthGenIfFail      OBJECT-TYPE
    SYNTAX      NtcAlarmState
    MAX-ACCESS  read-only
    STATUS      current
    DESCRIPTION
        "This alarm is raised when a failure is detected on the Ethernet interface.
        This variable indicates the current status of the alarm."
    ::= { ntcEtherAlarm 18 }
    
ntcEtherAlmDataEthGenIfFail      OBJECT-TYPE
    SYNTAX      NtcAlarmState
    MAX-ACCESS  read-only
    STATUS      current
    DESCRIPTION
        "This alarm is raised when a failure is detected on the Ethernet interface.
        This variable indicates the current status of the alarm."
    ::= { ntcEtherAlarm 19 }
    
ntcEtherAlmSatEthGenIfFail       OBJECT-TYPE
    SYNTAX      NtcAlarmState
    MAX-ACCESS  read-only
    STATUS      current
    DESCRIPTION
        "This alarm is raised when a failure is detected on the Ethernet interface.
        This variable indicates the current status of the alarm."
    ::= { ntcEtherAlarm 20 }
    
ntcEtherDataIgmpVersion          OBJECT-TYPE
    SYNTAX      INTEGER { v2(0), v3(1) }
    MAX-ACCESS  read-write
    STATUS      current
    DESCRIPTION
        "IGMP Version for the Data interfaces."
    DEFVAL { v2 }
    ::= { ntcEtherObjects 7 }
    

--
--  Module Conformance
--

ntcEtherConfGrpV1Standard        OBJECT-GROUP
    OBJECTS    {
                   ntcEtherLinkMgmtEnable,
                   ntcEtherLinkMgmtMacAddress,
                   ntcEtherLinkMgmtAutoNegotiation,
                   ntcEtherLinkMgmtAdvertisedSpeeds,
                   ntcEtherLinkMgmtForcedSpeed,
                   ntcEtherLinkMgmtLinkState,
                   ntcEtherLinkMgmtMtu,
                   ntcEtherLinkDataEnable,
                   ntcEtherLinkDataMacAddress,
                   ntcEtherLinkDataAutoNegotiation,
                   ntcEtherLinkDataAdvertisedSpeeds,
                   ntcEtherLinkDataForcedSpeed,
                   ntcEtherLinkDataLinkState,
                   ntcEtherLinkDataMtu,
                   ntcEtherStatMgmtInputBytes,
                   ntcEtherStatMgmtInputPackets,
                   ntcEtherStatMgmtInputDropped,
                   ntcEtherStatMgmtOutputBytes,
                   ntcEtherStatMgmtOutputPackets,
                   ntcEtherStatMgmtOutputDropped,
                   ntcEtherStatMgmtInputErrors,
                   ntcEtherStatMgmtOutputerrors,
                   ntcEtherStatDataInputBytes,
                   ntcEtherStatDataInputPackets,
                   ntcEtherStatDataInputDropped,
                   ntcEtherStatDataOutputBytes,
                   ntcEtherStatDataOutputPackets,
                   ntcEtherStatDataOutputDropped,
                   ntcEtherStatDataInputErrors,
                   ntcEtherStatDataOutputerrors,
                   ntcEtherIfRedMgmtSwitchOrder,
                   ntcEtherIfRedMgmtSwitchCount,
                   ntcEtherIfRedMgmtActiveInterface,
                   ntcEtherIfRedDataSwitchOrder,
                   ntcEtherIfRedDataSwitchCount,
                   ntcEtherIfRedDataActiveInterface,
                   ntcEtherIfRedDataGwUnreachImpact,
                   ntcEtherIfRedSatSwitchOrder,
                   ntcEtherIfRedSatSwitchCount,
                   ntcEtherIfRedSatActiveInterface,
                   ntcEtherAlmMgmt1EthLinkFail,
                   ntcEtherAlmMgmt1EthHalfDuplex,
                   ntcEtherAlmMgmt2EthLinkFail,
                   ntcEtherAlmMgmt2EthHalfDuplex,
                   ntcEtherAlmData1EthLinkFail,
                   ntcEtherAlmData1EthHalfDuplex,
                   ntcEtherAlmData2EthLinkFail,
                   ntcEtherAlmData2EthHalfDuplex,
                   ntcEtherAlmMgmtFpEthLinkFail,
                   ntcEtherAlmMgmtFpEthHalfDuplex,
                   ntcEtherAlmMgmtEthInterfaceFail,
                   ntcEtherAlmDataEthInterfaceFail,
                   ntcEtherAlmSat1EthLinkFail,
                   ntcEtherAlmSat1EthHalfDuplex,
                   ntcEtherAlmSat2EthLinkFail,
                   ntcEtherAlmSat2EthHalfDuplex,
                   ntcEtherAlmSatEthInterfaceFail,
                   ntcEtherAlmMgmtEthGenIfFail,
                   ntcEtherAlmDataEthGenIfFail,
                   ntcEtherAlmSatEthGenIfFail,
                   ntcEtherDataIgmpVersion
               }
    STATUS      current
    DESCRIPTION
        "Managed objects that constitute version 1 of a system device with standard capabilities."
    ::= { ntcEtherConfGroup 1}
    
ntcEtherConfCompV1Standard       MODULE-COMPLIANCE
    STATUS      current
    DESCRIPTION
        "Compliance statement for Newtec device MIB implementations."
    MODULE  -- this module
    MANDATORY-GROUPS
                  {
                      ntcEtherConfGrpV1Standard
                  }
    ::= { ntcEtherConfCompliance  1 }
    

END

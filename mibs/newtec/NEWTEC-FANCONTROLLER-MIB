NEWTEC-FANCONTROLLER-MIB DEFINITIONS ::= BEGIN

IMPORTS
    MODULE-IDENTITY,
    OBJECT-IDENTITY,
    OBJECT-TYPE
        FROM SNMPv2-SMI

    MODULE-COMPLIANCE,
    OBJECT-GROUP
        FROM SNMPv2-CONF
    
    NtcAlarmState
        FROM NEWTEC-TC-MIB

    ntcFunction
        FROM NEWTEC-MAIN-MIB;


--
--  Module Identification
--

ntcFanController   MODULE-IDENTITY
    LAST-UPDATED "201307050600Z"
    ORGANIZATION "Newtec Cy"
    CONTACT-INFO
        "Newtec Cy
         Postal: Newtec Cy
                 Laarstraat 5
                 B-9100 Sint-Niklaas
                 Belgium

                Tel: +32 3 780 65 00
                Fax: +32 3 780 65 49
                Web: www.newtec.be
                E-mail: techsupport@newtec.be"
    DESCRIPTION
        "Newtec modular FANCONTROLLER input MIB containing definitions for fan
        functionality."

    REVISION  "201307050600Z"
    DESCRIPTION
        "Initial release for MDM6000 and NOP1760 R1.1"
    ::= { ntcFunction  3500 }
    

--
-- Top-Level Structure
--

-- ntcFanController content

ntcFanCObjects                   OBJECT-IDENTITY
    STATUS        current
    DESCRIPTION   "Container holding ntcFanCObjects definitions."
    ::= { ntcFanController 1 }
    
ntcFanCConformance               OBJECT-IDENTITY
    STATUS        current
    DESCRIPTION   "Conformance requirements."
    ::= { ntcFanController 2 }
    
-- ntcFanCObjects content

ntcFanAlarm                      OBJECT-IDENTITY
    STATUS        current
    DESCRIPTION   "Container holding ntcFanAlarm definitions."
    ::= { ntcFanCObjects 1 }
    
-- ntcFanCConformance content

ntcFanCConfCompliance            OBJECT-IDENTITY
    STATUS        current
    DESCRIPTION   "Device compliance statements."
    ::= { ntcFanCConformance 1 }
    
ntcFanCConfGroup                 OBJECT-IDENTITY
    STATUS        current
    DESCRIPTION   "Groups used by device compliance statements."
    ::= { ntcFanCConformance 2 }
    

--
-- Managed Objects
--

ntcFanCAlmFanFailure             OBJECT-TYPE
    SYNTAX      NtcAlarmState
    MAX-ACCESS  read-only
    STATUS      current
    DESCRIPTION
        "This alarm is raised when a fan failure occurs. This variable indicates the
        current status of the alarm."
    ::= { ntcFanAlarm 1 }
    

--
--  Module Conformance
--

ntcFanCConfGrpV1Standard         OBJECT-GROUP
    OBJECTS    {
                   ntcFanCAlmFanFailure
               }
    STATUS      current
    DESCRIPTION
        "Managed objects that constitute version 1 of a system device with standard capabilities."
    ::= { ntcFanCConfGroup 1}
    
ntcFanCConfCompV1Standard        MODULE-COMPLIANCE
    STATUS      current
    DESCRIPTION
        "Compliance statement for Newtec device MIB implementations."
    MODULE  -- this module
    MANDATORY-GROUPS
                  {
                      ntcFanCConfGrpV1Standard
                  }
    ::= { ntcFanCConfCompliance  1 }
    

END

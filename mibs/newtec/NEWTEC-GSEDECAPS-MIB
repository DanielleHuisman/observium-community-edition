NEWTEC-GSEDECAPS-MIB DEFINITIONS ::= BEGIN

IMPORTS
    Counter64,
    Unsigned32,
    MODULE-IDENTITY,
    OBJECT-IDENTITY,
    OBJECT-TYPE
        FROM SNMPv2-SMI

    MODULE-COMPLIANCE,
    OBJECT-GROUP
        FROM SNMPv2-CONF
    
    NtcEnable
        FROM NEWTEC-TC-MIB

    DisplayString,
    RowStatus
        FROM SNMPv2-TC

    ntcFunction
        FROM NEWTEC-MAIN-MIB;


--
--  Module Identification
--

ntcGseDecaps   MODULE-IDENTITY
    LAST-UPDATED "201802020900Z"
    ORGANIZATION "Newtec Cy"
    CONTACT-INFO
        "Newtec Cy
         Postal: Newtec Cy
                 Laarstraat 5
                 B-9100 Sint-Niklaas
                 Belgium

                Tel: +32 3 780 65 00
                Fax: +32 3 780 65 49
                Web: www.newtec.be
                E-mail: techsupport@newtec.be"
    DESCRIPTION
        "Newtec modular GSEDECAPS output MIB containing definitions for GSE
        Decapsulation functionality."

    REVISION  "201802020900Z"
    DESCRIPTION
        "ntcGseDecDestMac and ntcGseDecDestMacEnable added"
    REVISION  "201509251100Z"
    DESCRIPTION
        "ntcGseDecBbfChannels column added to ntcGseDecBbfChanAccessVlan table"
    REVISION  "201504130700Z"
    DESCRIPTION
        "Addition of channel monitoring parameters + some ranges extended"
    REVISION  "201501300800Z"
    DESCRIPTION
        "only cosmetic changes"
    REVISION  "201410070800Z"
    DESCRIPTION
        "ntcGseDecXpeChecksum added"
    REVISION  "201407150800Z"
    DESCRIPTION
        "Support filtering of packets without a label"
    REVISION  "201402031200Z"
    DESCRIPTION
        "Extended the decapsulation model to support XPE, MPE and ULE next to GSE"
    REVISION  "201307050600Z"
    DESCRIPTION
        "Some defaults changed"
    REVISION  "201305220600Z"
    DESCRIPTION
        "Release for MDM6000 and NOP1760 R1.1"
    REVISION  "201301081200Z"
    DESCRIPTION
        "Initial release for NOP1760 R1.0"
    ::= { ntcFunction  2200 }
    

--
-- Top-Level Structure
--

-- ntcGseDecaps content

ntcGseDecObjects                 OBJECT-IDENTITY
    STATUS        current
    DESCRIPTION   "Container holding ntcGseDecObjects definitions."
    ::= { ntcGseDecaps 1 }
    
ntcGseDecConformance             OBJECT-IDENTITY
    STATUS        current
    DESCRIPTION   "Conformance requirements."
    ::= { ntcGseDecaps 2 }
    
-- ntcGseDecObjects content

ntcGseDecMonitor                 OBJECT-IDENTITY
    STATUS        current
    DESCRIPTION   "Container holding ntcGseDecMonitor definitions."
    ::= { ntcGseDecObjects 4 }
    
-- ntcGseDecConformance content

ntcGseDecConfCompliance          OBJECT-IDENTITY
    STATUS        current
    DESCRIPTION   "Device compliance statements."
    ::= { ntcGseDecConformance 1 }
    
ntcGseDecConfGroup               OBJECT-IDENTITY
    STATUS        current
    DESCRIPTION   "Groups used by device compliance statements."
    ::= { ntcGseDecConformance 2 }
    

--
-- Managed Objects
--

ntcGseDecEnable                  OBJECT-TYPE
    SYNTAX      NtcEnable
    MAX-ACCESS  read-write
    STATUS      current
    DESCRIPTION
        "Enable or disable GSE decapsulation."
    DEFVAL { off }
    ::= { ntcGseDecObjects 1 }
    
ntcGseDecOutputSelection         OBJECT-TYPE
    SYNTAX      INTEGER { none(0), data1(1), data2(2), data(3) }
    MAX-ACCESS  read-write
    STATUS      current
    DESCRIPTION
        "Configures the output interface for the GSE decapsulation functionality."
    DEFVAL { data1 }
    ::= { ntcGseDecObjects 2 }
    
ntcGseDecIsiFilter               OBJECT-TYPE
    SYNTAX      NtcEnable
    MAX-ACCESS  read-write
    STATUS      current
    DESCRIPTION
        "Enable or disable ISI filtering for all GSE channels, should only be disabled
        when working in single stream mode."
    DEFVAL { on }
    ::= { ntcGseDecObjects 3 }
    
ntcGseDecMonReset                OBJECT-TYPE
    SYNTAX      INTEGER { counting(0), reset(1) }
    MAX-ACCESS  read-write
    STATUS      current
    DESCRIPTION
        "Reset the GSE traffic and monitor counters."
    DEFVAL { counting }
    ::= { ntcGseDecMonitor 1 }
    
ntcGseDecMonOutBitRate           OBJECT-TYPE
    SYNTAX      Counter64
    UNITS       "bps"
    MAX-ACCESS  read-only
    STATUS      current
    DESCRIPTION
        "GSE decapsulated data bit rate in bps."
    ::= { ntcGseDecMonitor 2 }
    
ntcGseDecMonOutByteCnt           OBJECT-TYPE
    SYNTAX      Counter64
    UNITS       "bytes"
    MAX-ACCESS  read-only
    STATUS      current
    DESCRIPTION
        "Number of decapsulated bytes."
    ::= { ntcGseDecMonitor 3 }
    
ntcGseDecMonOutPktCnt            OBJECT-TYPE
    SYNTAX      Counter64
    UNITS       "packets"
    MAX-ACCESS  read-only
    STATUS      current
    DESCRIPTION
        "Number of transmitted decapsulated packets."
    ::= { ntcGseDecMonitor 4 }
    
ntcGseDecMonDropByteCnt          OBJECT-TYPE
    SYNTAX      Counter64
    UNITS       "bytes"
    MAX-ACCESS  read-only
    STATUS      current
    DESCRIPTION
        "Number of dropped payload bytes."
    ::= { ntcGseDecMonitor 5 }
    
ntcGseDecMonDropPktCnt           OBJECT-TYPE
    SYNTAX      Counter64
    UNITS       "packets"
    MAX-ACCESS  read-only
    STATUS      current
    DESCRIPTION
        "Number of dropped decapsulated packets."
    ::= { ntcGseDecMonitor 6 }
    
ntcGseDecMonChanTable            OBJECT-TYPE
    SYNTAX      SEQUENCE OF NtcGseDecMonChanEntry
    MAX-ACCESS  not-accessible
    STATUS      current
    DESCRIPTION
        "Gse Decapsulation Monitoring"
    ::= { ntcGseDecMonitor 7 }

ntcGseDecMonChanEntry            OBJECT-TYPE
    SYNTAX      NtcGseDecMonChanEntry
    MAX-ACCESS  not-accessible
    STATUS      current
    DESCRIPTION
        "A conceptual row of the ntcGseDecMonChanTable."
    INDEX   { ntcGseDecMonChanCounterInx  }
    ::= { ntcGseDecMonChanTable 1 }

NtcGseDecMonChanEntry            ::= SEQUENCE {
    ntcGseDecMonChanCounterInx       Unsigned32,
    ntcGseDecMonChanName             DisplayString,
    ntcGseDecMonChanByteCnt          Counter64,
    ntcGseDecMonChanPktCnt           Counter64,
    ntcGseDecMonChanByteDropCount    Counter64,
    ntcGseDecMonChanDropPktCnt       Counter64,
    ntcGseDecMonChanModCod           INTEGER,
    ntcGseDecMonChanLinkMargin       DisplayString
    }
    
ntcGseDecMonChanCounterInx       OBJECT-TYPE
    SYNTAX      Unsigned32
    MAX-ACCESS  not-accessible
    STATUS      current
    DESCRIPTION
        "The index of the row"
    ::= { ntcGseDecMonChanEntry 1 }
    
ntcGseDecMonChanName             OBJECT-TYPE
    SYNTAX      DisplayString (SIZE(0..100))
    MAX-ACCESS  read-only
    STATUS      current
    DESCRIPTION
        "The name of the channel"
    ::= { ntcGseDecMonChanEntry 2 }
    
ntcGseDecMonChanByteCnt          OBJECT-TYPE
    SYNTAX      Counter64
    UNITS       "bytes"
    MAX-ACCESS  read-only
    STATUS      current
    DESCRIPTION
        "Number of decapsulated bytes."
    ::= { ntcGseDecMonChanEntry 3 }
    
ntcGseDecMonChanPktCnt           OBJECT-TYPE
    SYNTAX      Counter64
    UNITS       "packets"
    MAX-ACCESS  read-only
    STATUS      current
    DESCRIPTION
        "Number of transmitted decapsulated packets."
    ::= { ntcGseDecMonChanEntry 4 }
    
ntcGseDecMonChanByteDropCount    OBJECT-TYPE
    SYNTAX      Counter64
    UNITS       "bytes"
    MAX-ACCESS  read-only
    STATUS      current
    DESCRIPTION
        "Number of dropped payload bytes."
    ::= { ntcGseDecMonChanEntry 5 }
    
ntcGseDecMonChanDropPktCnt       OBJECT-TYPE
    SYNTAX      Counter64
    UNITS       "packets"
    MAX-ACCESS  read-only
    STATUS      current
    DESCRIPTION
        "Number of dropped decapsulated packets."
    ::= { ntcGseDecMonChanEntry 6 }
    
ntcGseDecMonChanModCod           OBJECT-TYPE
    SYNTAX      INTEGER { unspecified(0), qpsk14(1), qpsk13(2), qpsk25(3), qpsk12(4), qpsk35(5), qpsk23(6), qpsk34(7), qpsk45(8), qpsk56(9), qpsk89(10), qpsk910(11), e8psk35(12), e8psk23(13), e8psk34(14), e8psk56(15), e8psk89(16), e8psk910(17), e16apsk23(18), e16apsk34(19), e16apsk45(20), e16apsk56(21), e16apsk89(22), e16apsk910(23), e32apsk34(24), e32apsk45(25), e32apsk56(26), e32apsk89(27), e32apsk910(28), qpsk45180(129), qpsk60180(130), qpsk72180(131), qpsk80180(132), qpsk90180(133), qpsk100180(134), qpsk108180(135), qpsk114180(136), qpsk120180(137), qpsk126180(138), qpsk135180(139), qpsk144180(140), qpsk150180(141), qpsk160180(142), qpsk162180(143), e8psk80180(144), e8psk90180(145), e8psk100180(146), e8psk108180(147), e8psk114180(148), e8psk120180(149), e8psk126180(150), e8psk135180(151), e8psk144180(152), e8psk150180(153), e16apsk80180(154), e16apsk90180(155), e16apsk100180(156), e16apsk108180(157), e16apsk114180(158), e16apsk120180(159), e16apsk126180(160), e16apsk135180(161), e16apsk144180(162), e16apsk150180(163), e16apsk160180(164), e16apsk162180(165), e32apsk100180(166), e32apsk108180(167), e32apsk114180(168), e32apsk120180(169), e32apsk126180(170), e32apsk135180(171), e32apsk144180(172), e32apsk150180(173), e32apsk160180(174), e32apsk162180(175), e64apsk90180(176), e64apsk100180(177), e64apsk108180(178), e64apsk114180(179), e64apsk120180(180), e64apsk126180(181), e64apsk135180(182), e64apsk144180(183), e64apsk150180(184), e64apsk160180(185), e64apsk162180(186), e8pskl80180(187), e8pskl90180(188), e8pskl100180(189), e8pskl108180(190), e8pskl114180(191), e8pskl120180(192), e16apskl80180(193), e16apskl90180(194), e16apskl100180(195), e16apskl108180(196), e16apskl114180(197), e16apskl120180(198), e16apskl126180(199), e16apskl135180(200), e16apskl144180(201), e16apskl150180(202), e16apskl160180(203), e16apskl162180(204), e64apskl90180(205), e64apskl100180(206), e64apskl108180(207), e64apskl114180(208), e64apskl120180(209), e64apskl126180(210), e64apskl135180(211), e64apskl144180(212), e64apskl150180(213), e64apskl160180(214), e64apskl162180(215), qpsk1345(256), qpsk920(257), qpsk1120(258), e8apsk59l(259), e8apsk2645l(260), e8psk2336(261), e8psk2536(262), e8psk1318(263), e16apsk12l(264), e16apsk815l(265), e16apsk59l(266), e16apsk2645(267), e16apsk35(268), e16apsk35l(269), e16apsk2845(270), e16apsk2336(271), e16apsk23l(272), e16apsk2536(273), e16apsk1318(274), e16apsk79(275), e16apsk7790(276), e32apsk23l(277), e32apsk3245(278), e32apsk1115(279), e32apsk79(280), e64apsk3245l(281), e64apsk1115(282), e64apsk79(283), e64apsk45(284), e64apsk56(285), e128apsk34(286), e128apsk79(287), e256apsk2945l(288), e256apsk23l(289), e256apsk3145l(290), e256apsk3245(291), e256apsk1115l(292), e256apsk34(293), qpsk1145(294), qpsk415(295), qpsk1445(296), qpsk715(297), qpsk815(298), qpsk3245(299), e8psk715(300), e8psk815(301), e8psk2645(302), e8psk3245(303), e16apsk715(304), e16apsk815(305), e16apsk3245(306), e32apsk23(307) }
    MAX-ACCESS  read-only
    STATUS      current
    DESCRIPTION
        "The highest decapsulated modcod during that last monitoring period"
    ::= { ntcGseDecMonChanEntry 7 }
    
ntcGseDecMonChanLinkMargin       OBJECT-TYPE
    SYNTAX      DisplayString (SIZE(0..16))
    MAX-ACCESS  read-only
    STATUS      current
    DESCRIPTION
        "Link margin of the decapsulated traffic"
    ::= { ntcGseDecMonChanEntry 8 }
    
ntcGseDecMonMonCod               OBJECT-TYPE
    SYNTAX      INTEGER { unspecified(0), qpsk14(1), qpsk13(2), qpsk25(3), qpsk12(4), qpsk35(5), qpsk23(6), qpsk34(7), qpsk45(8), qpsk56(9), qpsk89(10), qpsk910(11), e8psk35(12), e8psk23(13), e8psk34(14), e8psk56(15), e8psk89(16), e8psk910(17), e16apsk23(18), e16apsk34(19), e16apsk45(20), e16apsk56(21), e16apsk89(22), e16apsk910(23), e32apsk34(24), e32apsk45(25), e32apsk56(26), e32apsk89(27), e32apsk910(28), qpsk45180(129), qpsk60180(130), qpsk72180(131), qpsk80180(132), qpsk90180(133), qpsk100180(134), qpsk108180(135), qpsk114180(136), qpsk120180(137), qpsk126180(138), qpsk135180(139), qpsk144180(140), qpsk150180(141), qpsk160180(142), qpsk162180(143), e8psk80180(144), e8psk90180(145), e8psk100180(146), e8psk108180(147), e8psk114180(148), e8psk120180(149), e8psk126180(150), e8psk135180(151), e8psk144180(152), e8psk150180(153), e16apsk80180(154), e16apsk90180(155), e16apsk100180(156), e16apsk108180(157), e16apsk114180(158), e16apsk120180(159), e16apsk126180(160), e16apsk135180(161), e16apsk144180(162), e16apsk150180(163), e16apsk160180(164), e16apsk162180(165), e32apsk100180(166), e32apsk108180(167), e32apsk114180(168), e32apsk120180(169), e32apsk126180(170), e32apsk135180(171), e32apsk144180(172), e32apsk150180(173), e32apsk160180(174), e32apsk162180(175), e64apsk90180(176), e64apsk100180(177), e64apsk108180(178), e64apsk114180(179), e64apsk120180(180), e64apsk126180(181), e64apsk135180(182), e64apsk144180(183), e64apsk150180(184), e64apsk160180(185), e64apsk162180(186), e8pskl80180(187), e8pskl90180(188), e8pskl100180(189), e8pskl108180(190), e8pskl114180(191), e8pskl120180(192), e16apskl80180(193), e16apskl90180(194), e16apskl100180(195), e16apskl108180(196), e16apskl114180(197), e16apskl120180(198), e16apskl126180(199), e16apskl135180(200), e16apskl144180(201), e16apskl150180(202), e16apskl160180(203), e16apskl162180(204), e64apskl90180(205), e64apskl100180(206), e64apskl108180(207), e64apskl114180(208), e64apskl120180(209), e64apskl126180(210), e64apskl135180(211), e64apskl144180(212), e64apskl150180(213), e64apskl160180(214), e64apskl162180(215), qpsk1345(256), qpsk920(257), qpsk1120(258), e8apsk59l(259), e8apsk2645l(260), e8psk2336(261), e8psk2536(262), e8psk1318(263), e16apsk12l(264), e16apsk815l(265), e16apsk59l(266), e16apsk2645(267), e16apsk35(268), e16apsk35l(269), e16apsk2845(270), e16apsk2336(271), e16apsk23l(272), e16apsk2536(273), e16apsk1318(274), e16apsk79(275), e16apsk7790(276), e32apsk23l(277), e32apsk3245(278), e32apsk1115(279), e32apsk79(280), e64apsk3245l(281), e64apsk1115(282), e64apsk79(283), e64apsk45(284), e64apsk56(285), e128apsk34(286), e128apsk79(287), e256apsk2945l(288), e256apsk23l(289), e256apsk3145l(290), e256apsk3245(291), e256apsk1115l(292), e256apsk34(293), qpsk1145(294), qpsk415(295), qpsk1445(296), qpsk715(297), qpsk815(298), qpsk3245(299), e8psk715(300), e8psk815(301), e8psk2645(302), e8psk3245(303), e16apsk715(304), e16apsk815(305), e16apsk3245(306), e32apsk23(307) }
    MAX-ACCESS  read-only
    STATUS      current
    DESCRIPTION
        "The highest decapsulated modcod during that last monitoring period"
    ::= { ntcGseDecMonitor 8 }
    
ntcGseDecMonLinkMargin           OBJECT-TYPE
    SYNTAX      DisplayString (SIZE(0..16))
    MAX-ACCESS  read-only
    STATUS      current
    DESCRIPTION
        "Link margin of the decapsulated traffic"
    ::= { ntcGseDecMonitor 9 }
    
ntcGseDecChannelsTable           OBJECT-TYPE
    SYNTAX      SEQUENCE OF NtcGseDecChannelsEntry
    MAX-ACCESS  not-accessible
    STATUS      current
    DESCRIPTION
        "A table containing the ntcGseDecChannels"
    ::= { ntcGseDecObjects 5 }

ntcGseDecChannelsEntry           OBJECT-TYPE
    SYNTAX      NtcGseDecChannelsEntry
    MAX-ACCESS  not-accessible
    STATUS      current
    DESCRIPTION
        "A conceptual row of the ntcGseDecChannelsTable."
    INDEX   { ntcGseDecChannelsName  }
    ::= { ntcGseDecChannelsTable 1 }

NtcGseDecChannelsEntry           ::= SEQUENCE {
    ntcGseDecChannelsName         DisplayString,
    ntcGseDecChannelsRowStatus    RowStatus,
    ntcGseDecChanEnable           NtcEnable,
    ntcGseDecChanDemodId          Unsigned32,
    ntcGseDecChanIsi              Unsigned32,
    ntcGseDecChanLabel            DisplayString,
    ntcGseDecChanLabelFilter      INTEGER
    }
    
ntcGseDecChannelsName            OBJECT-TYPE
    SYNTAX      DisplayString (SIZE(1..100))
    MAX-ACCESS  not-accessible
    STATUS      current
    DESCRIPTION
        "The name of the channel"
    ::= { ntcGseDecChannelsEntry 1 }
    
ntcGseDecChannelsRowStatus       OBJECT-TYPE
    SYNTAX      RowStatus
    MAX-ACCESS  read-create
    STATUS      current
    DESCRIPTION
        "The status of this conceptual row. An existing conceptual row can be in any
        one of the three states, 'notReady', 'notInService', or 'active'. If the
        manager wishes to add a row in a single shot with values for all the columns,
        the status column should be given as 'createAndGo(4)'. After the creation of a
        row, its value is set to active(1). If a row has to be created with values for
        only some columns, the status column should be 'createAndWait(5)'. Also, this
        row with partially filled columns has the status 'notReady(3)'. The entry
        remains in this state until the values for all the columns is set. After all
        the values are set, the agent changes this value to active(1).'"
    ::= { ntcGseDecChannelsEntry 2 }
    
ntcGseDecChanEnable              OBJECT-TYPE
    SYNTAX      NtcEnable
    MAX-ACCESS  read-create
    STATUS      current
    DESCRIPTION
        "Enable or disable the corresponding channel."
    ::= { ntcGseDecChannelsEntry 3 }
    
ntcGseDecChanDemodId             OBJECT-TYPE
    SYNTAX      Unsigned32
    MAX-ACCESS  read-create
    STATUS      current
    DESCRIPTION
        "The ID of demodulator of the channel"
    ::= { ntcGseDecChannelsEntry 4 }
    
ntcGseDecChanIsi                 OBJECT-TYPE
    SYNTAX      Unsigned32
    MAX-ACCESS  read-create
    STATUS      current
    DESCRIPTION
        "The ISI of the channel"
    ::= { ntcGseDecChannelsEntry 5 }
    
ntcGseDecChanLabel               OBJECT-TYPE
    SYNTAX      DisplayString (SIZE(0..30))
    MAX-ACCESS  read-create
    STATUS      current
    DESCRIPTION
        "Label filter to be applied."
    ::= { ntcGseDecChannelsEntry 6 }
    
ntcGseDecChanLabelFilter         OBJECT-TYPE
    SYNTAX      INTEGER { nofilter(0), use36bytes(1) }
    MAX-ACCESS  read-create
    STATUS      current
    DESCRIPTION
        "Deprecated. label filtering is expressed through the label itself"
    ::= { ntcGseDecChannelsEntry 7 }
    
ntcGseDecBbfChannelsTable        OBJECT-TYPE
    SYNTAX      SEQUENCE OF NtcGseDecBbfChannelsEntry
    MAX-ACCESS  not-accessible
    STATUS      current
    DESCRIPTION
        "A table containing the ntcGseDecBbfChannels"
    ::= { ntcGseDecObjects 6 }

ntcGseDecBbfChannelsEntry        OBJECT-TYPE
    SYNTAX      NtcGseDecBbfChannelsEntry
    MAX-ACCESS  not-accessible
    STATUS      current
    DESCRIPTION
        "A conceptual row of the ntcGseDecBbfChannelsTable."
    INDEX   { ntcGseDecBbfChannelsName  }
    ::= { ntcGseDecBbfChannelsTable 1 }

NtcGseDecBbfChannelsEntry        ::= SEQUENCE {
    ntcGseDecBbfChannelsName          DisplayString,
    ntcGseDecBbfChannelsRowStatus     RowStatus,
    ntcGseDecBbfChanEnable            NtcEnable,
    ntcGseDecBbfChanInputTypeName     OCTET STRING,
    ntcGseDecBbfChanInputInstName     OCTET STRING,
    ntcGseDecBbfChanLabel             DisplayString,
    ntcGseDecBbfChanLabelFilter       INTEGER,
    ntcGseDecBbfChanVirtualNetwork    OCTET STRING,
    ntcGseDecBbfChanAccessVlan        Unsigned32
    }
    
ntcGseDecBbfChannelsName         OBJECT-TYPE
    SYNTAX      DisplayString (SIZE(1..100))
    MAX-ACCESS  not-accessible
    STATUS      current
    DESCRIPTION
        "The name of the channel"
    ::= { ntcGseDecBbfChannelsEntry 1 }
    
ntcGseDecBbfChannelsRowStatus    OBJECT-TYPE
    SYNTAX      RowStatus
    MAX-ACCESS  read-create
    STATUS      current
    DESCRIPTION
        "The status of this conceptual row. An existing conceptual row can be in any
        one of the three states, 'notReady', 'notInService', or 'active'. If the
        manager wishes to add a row in a single shot with values for all the columns,
        the status column should be given as 'createAndGo(4)'. After the creation of a
        row, its value is set to active(1). If a row has to be created with values for
        only some columns, the status column should be 'createAndWait(5)'. Also, this
        row with partially filled columns has the status 'notReady(3)'. The entry
        remains in this state until the values for all the columns is set. After all
        the values are set, the agent changes this value to active(1).'"
    ::= { ntcGseDecBbfChannelsEntry 2 }
    
ntcGseDecBbfChanEnable           OBJECT-TYPE
    SYNTAX      NtcEnable
    MAX-ACCESS  read-create
    STATUS      current
    DESCRIPTION
        "Enable or disable the corresponding channel."
    ::= { ntcGseDecBbfChannelsEntry 3 }
    
ntcGseDecBbfChanInputTypeName    OBJECT-TYPE
    SYNTAX      OCTET STRING (SIZE(0..255))
    MAX-ACCESS  read-create
    STATUS      current
    DESCRIPTION
        "The input type of the decapsulation channel."
    ::= { ntcGseDecBbfChannelsEntry 4 }
    
ntcGseDecBbfChanInputInstName    OBJECT-TYPE
    SYNTAX      OCTET STRING (SIZE(0..255))
    MAX-ACCESS  read-create
    STATUS      current
    DESCRIPTION
        "The input instance name."
    ::= { ntcGseDecBbfChannelsEntry 5 }
    
ntcGseDecBbfChanLabel            OBJECT-TYPE
    SYNTAX      DisplayString (SIZE(0..30))
    MAX-ACCESS  read-create
    STATUS      current
    DESCRIPTION
        "Label filter to be applied."
    ::= { ntcGseDecBbfChannelsEntry 6 }
    
ntcGseDecBbfChanLabelFilter      OBJECT-TYPE
    SYNTAX      INTEGER { nofilter(0), use36bytes(1) }
    MAX-ACCESS  read-create
    STATUS      current
    DESCRIPTION
        "Deprecated. label filtering is expressed through the label itself"
    ::= { ntcGseDecBbfChannelsEntry 7 }
    
ntcGseDecBbfChanVirtualNetwork   OBJECT-TYPE
    SYNTAX      OCTET STRING (SIZE(0..255))
    MAX-ACCESS  read-create
    STATUS      current
    DESCRIPTION
        "The virtual network (addressing scope)"
    ::= { ntcGseDecBbfChannelsEntry 8 }
    
ntcGseDecBbfChanAccessVlan       OBJECT-TYPE
    SYNTAX      Unsigned32 (0..4095)
    MAX-ACCESS  read-create
    STATUS      current
    DESCRIPTION
        "If a non-zero Access VLAN is associated to an decapsulation channel, traffic
        from this channel is tagged with this VLAN"
    ::= { ntcGseDecBbfChannelsEntry 9 }
    
ntcGseDecIsisTable               OBJECT-TYPE
    SYNTAX      SEQUENCE OF NtcGseDecIsisEntry
    MAX-ACCESS  not-accessible
    STATUS      current
    DESCRIPTION
        "A table containing the ntcGseDecIsis"
    ::= { ntcGseDecObjects 7 }

ntcGseDecIsisEntry               OBJECT-TYPE
    SYNTAX      NtcGseDecIsisEntry
    MAX-ACCESS  not-accessible
    STATUS      current
    DESCRIPTION
        "A conceptual row of the ntcGseDecIsisTable."
    INDEX   { ntcGseDecIsisName  }
    ::= { ntcGseDecIsisTable 1 }

NtcGseDecIsisEntry               ::= SEQUENCE {
    ntcGseDecIsisName                DisplayString,
    ntcGseDecIsisRowStatus           RowStatus,
    ntcGseDecIsiEnable               NtcEnable,
    ntcGseDecIsiIsi                  Unsigned32,
    ntcGseDecIsiProtocol             INTEGER,
    ntcGseDecIsiInputTypeName        OCTET STRING,
    ntcGseDecIsiInputInstanceName    OCTET STRING
    }
    
ntcGseDecIsisName                OBJECT-TYPE
    SYNTAX      DisplayString (SIZE(1..100))
    MAX-ACCESS  not-accessible
    STATUS      current
    DESCRIPTION
        "The name of the Isi"
    ::= { ntcGseDecIsisEntry 1 }
    
ntcGseDecIsisRowStatus           OBJECT-TYPE
    SYNTAX      RowStatus
    MAX-ACCESS  read-create
    STATUS      current
    DESCRIPTION
        "The status of this conceptual row. An existing conceptual row can be in any
        one of the three states, 'notReady', 'notInService', or 'active'. If the
        manager wishes to add a row in a single shot with values for all the columns,
        the status column should be given as 'createAndGo(4)'. After the creation of a
        row, its value is set to active(1). If a row has to be created with values for
        only some columns, the status column should be 'createAndWait(5)'. Also, this
        row with partially filled columns has the status 'notReady(3)'. The entry
        remains in this state until the values for all the columns is set. After all
        the values are set, the agent changes this value to active(1).'"
    ::= { ntcGseDecIsisEntry 2 }
    
ntcGseDecIsiEnable               OBJECT-TYPE
    SYNTAX      NtcEnable
    MAX-ACCESS  read-create
    STATUS      current
    DESCRIPTION
        "Enable or disable the corresponding decapsulator."
    ::= { ntcGseDecIsisEntry 3 }
    
ntcGseDecIsiIsi                  OBJECT-TYPE
    SYNTAX      Unsigned32
    MAX-ACCESS  read-create
    STATUS      current
    DESCRIPTION
        "The ISI of the channel"
    ::= { ntcGseDecIsisEntry 4 }
    
ntcGseDecIsiProtocol             OBJECT-TYPE
    SYNTAX      INTEGER { default(0), gse(1), xpe(2) }
    MAX-ACCESS  read-create
    STATUS      current
    DESCRIPTION
        "The baseband frame decapsulation protocol."
    ::= { ntcGseDecIsisEntry 5 }
    
ntcGseDecIsiInputTypeName        OBJECT-TYPE
    SYNTAX      OCTET STRING (SIZE(0..255))
    MAX-ACCESS  read-create
    STATUS      current
    DESCRIPTION
        "The input type of the decapsulation channel."
    ::= { ntcGseDecIsisEntry 6 }
    
ntcGseDecIsiInputInstanceName    OBJECT-TYPE
    SYNTAX      OCTET STRING (SIZE(0..255))
    MAX-ACCESS  read-create
    STATUS      current
    DESCRIPTION
        "The input instance name."
    ::= { ntcGseDecIsisEntry 7 }
    
ntcGseDecDefDecProt              OBJECT-TYPE
    SYNTAX      INTEGER { gse(0), xpe(1) }
    MAX-ACCESS  read-write
    STATUS      current
    DESCRIPTION
        "The default baseband frame decapsulation protocol."
    DEFVAL { gse }
    ::= { ntcGseDecObjects 8 }
    
ntcGseDecXpeChecksum             OBJECT-TYPE
    SYNTAX      INTEGER { crc32(0), off(1) }
    MAX-ACCESS  read-write
    STATUS      current
    DESCRIPTION
        "The checksum type of the XPE packets to be decapsulated"
    DEFVAL { crc32 }
    ::= { ntcGseDecObjects 9 }
    
ntcGseDecDestMacEnable           OBJECT-TYPE
    SYNTAX      NtcEnable
    MAX-ACCESS  read-write
    STATUS      current
    DESCRIPTION
        "Enable or disable routing to a predefined destination MAC address."
    DEFVAL { off }
    ::= { ntcGseDecObjects 10 }
    
ntcGseDecDestMac                 OBJECT-TYPE
    SYNTAX      DisplayString
    MAX-ACCESS  read-write
    STATUS      current
    DESCRIPTION
        "Destination MAC Address Regular expression :
        (?-mix:^([\da-fA-F]{2}:){5}[\da-fA-F]{2}$)"
    DEFVAL { "00:00:00:00:00:00" }
    ::= { ntcGseDecObjects 11 }
    
ntcGseDecPidFilter               OBJECT-TYPE
    SYNTAX      NtcEnable
    MAX-ACCESS  read-write
    STATUS      current
    DESCRIPTION
        "Enable or disable PID filtering for all MPE/ULE decapsulation channels."
    DEFVAL { on }
    ::= { ntcGseDecObjects 12 }
    

--
--  Module Conformance
--

ntcGseDecConfGrpV1Standard       OBJECT-GROUP
    OBJECTS    {
                   ntcGseDecEnable,
                   ntcGseDecOutputSelection,
                   ntcGseDecIsiFilter,
                   ntcGseDecMonReset,
                   ntcGseDecMonOutBitRate,
                   ntcGseDecMonOutByteCnt,
                   ntcGseDecMonOutPktCnt,
                   ntcGseDecMonDropByteCnt,
                   ntcGseDecMonDropPktCnt,
                   ntcGseDecMonChanName,
                   ntcGseDecMonChanByteCnt,
                   ntcGseDecMonChanPktCnt,
                   ntcGseDecMonChanByteDropCount,
                   ntcGseDecMonChanDropPktCnt,
                   ntcGseDecMonChanModCod,
                   ntcGseDecMonChanLinkMargin,
                   ntcGseDecMonMonCod,
                   ntcGseDecMonLinkMargin,
                   ntcGseDecChannelsRowStatus,
                   ntcGseDecChanEnable,
                   ntcGseDecChanDemodId,
                   ntcGseDecChanIsi,
                   ntcGseDecChanLabel,
                   ntcGseDecChanLabelFilter,
                   ntcGseDecBbfChannelsRowStatus,
                   ntcGseDecBbfChanEnable,
                   ntcGseDecBbfChanInputTypeName,
                   ntcGseDecBbfChanInputInstName,
                   ntcGseDecBbfChanLabel,
                   ntcGseDecBbfChanLabelFilter,
                   ntcGseDecBbfChanVirtualNetwork,
                   ntcGseDecBbfChanAccessVlan,
                   ntcGseDecIsisRowStatus,
                   ntcGseDecIsiEnable,
                   ntcGseDecIsiIsi,
                   ntcGseDecIsiProtocol,
                   ntcGseDecIsiInputTypeName,
                   ntcGseDecIsiInputInstanceName,
                   ntcGseDecDefDecProt,
                   ntcGseDecXpeChecksum,
                   ntcGseDecDestMacEnable,
                   ntcGseDecDestMac,
                   ntcGseDecPidFilter
               }
    STATUS      current
    DESCRIPTION
        "Managed objects that constitute version 1 of a system device with standard capabilities."
    ::= { ntcGseDecConfGroup 1}
    
ntcGseDecConfCompV1Standard      MODULE-COMPLIANCE
    STATUS      current
    DESCRIPTION
        "Compliance statement for Newtec device MIB implementations."
    MODULE  -- this module
    MANDATORY-GROUPS
                  {
                      ntcGseDecConfGrpV1Standard
                  }
    ::= { ntcGseDecConfCompliance  1 }
    

END

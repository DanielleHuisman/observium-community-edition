NEWTEC-GSEENCAPS-MIB DEFINITIONS ::= BEGIN

IMPORTS
    Unsigned32,
    Counter64,
    MODULE-IDENTITY,
    OBJECT-IDENTITY,
    OBJECT-TYPE
        FROM SNMPv2-SMI

    MODULE-COMPLIANCE,
    OBJECT-GROUP
        FROM SNMPv2-CONF
    
    NtcEnable
        FROM NEWTEC-TC-MIB

    DisplayString,
    RowStatus
        FROM SNMPv2-TC

    ntcFunction
        FROM NEWTEC-MAIN-MIB;


--
--  Module Identification
--

ntcGseEncaps   MODULE-IDENTITY
    LAST-UPDATED "201509251100Z"
    ORGANIZATION "Newtec Cy"
    CONTACT-INFO
        "Newtec Cy
         Postal: Newtec Cy
                 Laarstraat 5
                 B-9100 Sint-Niklaas
                 Belgium

                Tel: +32 3 780 65 00
                Fax: +32 3 780 65 49
                Web: www.newtec.be
                E-mail: techsupport@newtec.be"
    DESCRIPTION
        "Newtec modular GSEENCAPS input MIB containing definitions for GSE
        Encapsulation functionality."

    REVISION  "201509251100Z"
    DESCRIPTION
        "ntcGseEncBbfChannels column added to ntcGseEncBbfChanAccessVlan table"
    REVISION  "201504130700Z"
    DESCRIPTION
        "Some ranges extended + ntcGseEncStreamMode description adapted"
    REVISION  "201501300800Z"
    DESCRIPTION
        "ntcGseEncS2Modcod and ntcGseEncFrameType added"
    REVISION  "201412030700Z"
    DESCRIPTION
        "ntcGseEncStreamMode added."
    REVISION  "201407150800Z"
    DESCRIPTION
        "DVB-S2X support"
    REVISION  "201402031200Z"
    DESCRIPTION
        "Extended the encapsulation model to support XPE, MPE and ULE next to GSE"
    REVISION  "201307050600Z"
    DESCRIPTION
        "Some defaults changed"
    REVISION  "201305220600Z"
    DESCRIPTION
        "Release for MDM6000 and NOP1760 R1.1"
    REVISION  "201301081200Z"
    DESCRIPTION
        "Initial release for NOP1760 R1.0"
    ::= { ntcFunction  2100 }
    

--
-- Top-Level Structure
--

-- ntcGseEncaps content

ntcGseEncObjects                 OBJECT-IDENTITY
    STATUS        current
    DESCRIPTION   "Container holding ntcGseEncObjects definitions."
    ::= { ntcGseEncaps 1 }
    
ntcGseEncConformance             OBJECT-IDENTITY
    STATUS        current
    DESCRIPTION   "Conformance requirements."
    ::= { ntcGseEncaps 2 }
    
-- ntcGseEncObjects content

ntcGseEncCarrier                 OBJECT-IDENTITY
    STATUS        current
    DESCRIPTION   "Container holding ntcGseEncCarrier definitions."
    ::= { ntcGseEncObjects 1 }
    
ntcGseEncMonitor                 OBJECT-IDENTITY
    STATUS        current
    DESCRIPTION   "Container holding ntcGseEncMonitor definitions."
    ::= { ntcGseEncObjects 2 }
    
-- ntcGseEncCarrier content

ntcGseEncCarLinkOpt              OBJECT-IDENTITY
    STATUS        current
    DESCRIPTION   "Container holding ntcGseEncCarLinkOpt definitions."
    ::= { ntcGseEncCarrier 4 }
    
-- ntcGseEncConformance content

ntcGseEncConfCompliance          OBJECT-IDENTITY
    STATUS        current
    DESCRIPTION   "Device compliance statements."
    ::= { ntcGseEncConformance 1 }
    
ntcGseEncConfGroup               OBJECT-IDENTITY
    STATUS        current
    DESCRIPTION   "Groups used by device compliance statements."
    ::= { ntcGseEncConformance 2 }
    

--
-- Managed Objects
--

ntcGseEncModStandard             OBJECT-TYPE
    SYNTAX      INTEGER { dvbs2(1), s2ext(3), dvbs2x(7) }
    MAX-ACCESS  read-write
    STATUS      current
    DESCRIPTION
        "The modulation standard defines the major operating mode of the modulator.
        - DVB-S : compatible with EN300421 for QPSK and EN301210 for 8 PSK and 16QAM.
        - DVB-S2 : compatible with EN302307-1.
        - S2 Extensions : Newtec proprietary modulation to improve DVB-S2.
        - DVB-S2X: compatible with EN302307-2."
    DEFVAL { dvbs2 }
    ::= { ntcGseEncCarrier 1 }
    
ntcGseEncPilots                  OBJECT-TYPE
    SYNTAX      NtcEnable
    MAX-ACCESS  read-write
    STATUS      current
    DESCRIPTION
        "Dvb Physical Layer Pilot insertion."
    DEFVAL { on }
    ::= { ntcGseEncCarrier 2 }
    
ntcGseEncSymbolRate              OBJECT-TYPE
    SYNTAX      Unsigned32
    UNITS       "baud"
    MAX-ACCESS  read-write
    STATUS      current
    DESCRIPTION
        "Symbol rate of the outgoing carrier"
    DEFVAL { 5000000 }
    ::= { ntcGseEncCarrier 3 }
    
ntcGseEncTransMode               OBJECT-TYPE
    SYNTAX      INTEGER { single(1), multiple(2), singlelin(3) }
    MAX-ACCESS  read-write
    STATUS      current
    DESCRIPTION
        "Transponder Operation Mode selection."
    DEFVAL { multiple }
    ::= { ntcGseEncCarLinkOpt 1 }
    
ntcGseEncEquaEnable              OBJECT-TYPE
    SYNTAX      NtcEnable
    MAX-ACCESS  read-write
    STATUS      current
    DESCRIPTION
        "Specify whether modulator (NonLinear) Equalink is enabled."
    DEFVAL { off }
    ::= { ntcGseEncCarLinkOpt 2 }
    
ntcGseEncStreamMode              OBJECT-TYPE
    SYNTAX      INTEGER { multistream(1), singlestream(2) }
    MAX-ACCESS  read-write
    STATUS      current
    DESCRIPTION
        "Specify if more than one baseband frame stream is multiplexed into the
        modulator or not. This sometimes impacts receiver compatibility."
    DEFVAL { multistream }
    ::= { ntcGseEncCarrier 5 }
    
ntcGseEncS2Modcod                OBJECT-TYPE
    SYNTAX      INTEGER { unspecified(0), qpsk14(1), qpsk13(2), qpsk25(3), qpsk12(4), qpsk35(5), qpsk23(6), qpsk34(7), qpsk45(8), qpsk56(9), qpsk89(10), qpsk910(11), e8psk35(12), e8psk23(13), e8psk34(14), e8psk56(15), e8psk89(16), e8psk910(17), e16apsk23(18), e16apsk34(19), e16apsk45(20), e16apsk56(21), e16apsk89(22), e16apsk910(23), e32apsk34(24), e32apsk45(25), e32apsk56(26), e32apsk89(27), e32apsk910(28), qpsk1345(29), qpsk920(30), qpsk1120(31), e8apsk59l(32), e8apsk2645l(33), e8psk2336(34), e8psk2536(35), e8psk1318(36), e16apsk12l(37), e16apsk815l(38), e16apsk59l(39), e16apsk2645(40), e16apsk35(41), e16apsk35l(42), e16apsk2845(43), e16apsk2336(44), e16apsk23l(45), e16apsk2536(46), e16apsk1318(47), e16apsk79(48), e16apsk7790(49), e32apsk23l(50), e32apsk3245(51), e32apsk1115(52), e32apsk79(53), e64apsk3245l(54), e64apsk1115(55), e64apsk79(56), e64apsk45(57), e64apsk56(58), e128apsk34(59), e128apsk79(60), e256apsk2945l(61), e256apsk23l(62), e256apsk3145l(63), e256apsk3245(64), e256apsk1115l(65), e256apsk34(66), qpsk1145(67), qpsk415(68), qpsk1445(69), qpsk715(70), qpsk815(71), qpsk3245(72), e8psk715(73), e8psk815(74), e8psk2645(75), e8psk3245(76), e16apsk715(77), e16apsk815(78), e16apsk3245(79), e32apsk23(80) }
    MAX-ACCESS  read-write
    STATUS      current
    DESCRIPTION
        "The single-stream modcod for all channels, in S2 mode"
    DEFVAL { qpsk34 }
    ::= { ntcGseEncCarrier 6 }
    
ntcGseEncFrameType               OBJECT-TYPE
    SYNTAX      INTEGER { short(0), normal(1) }
    MAX-ACCESS  read-write
    STATUS      current
    DESCRIPTION
        "The type of frames for this encapsulator."
    DEFVAL { normal }
    ::= { ntcGseEncCarrier 7 }
    
ntcGseEncMonChannelTable         OBJECT-TYPE
    SYNTAX      SEQUENCE OF NtcGseEncMonChannelEntry
    MAX-ACCESS  not-accessible
    STATUS      current
    DESCRIPTION
        "GSE Channels Monitoring"
    ::= { ntcGseEncMonitor 1 }

ntcGseEncMonChannelEntry         OBJECT-TYPE
    SYNTAX      NtcGseEncMonChannelEntry
    MAX-ACCESS  not-accessible
    STATUS      current
    DESCRIPTION
        "A conceptual row of the ntcGseEncMonChannelTable."
    INDEX   { ntcGseEncMonChannelInx  }
    ::= { ntcGseEncMonChannelTable 1 }

NtcGseEncMonChannelEntry         ::= SEQUENCE {
    ntcGseEncMonChannelInx              Unsigned32,
    ntcGseEncMonChannelName             DisplayString,
    ntcGseEncMonChannelNominalModcod    INTEGER,
    ntcGseEncMonChannelModcod           INTEGER,
    ntcGseEncMonChannelModcodChanges    Counter64,
    ntcGseEncProtocol                   INTEGER
    }
    
ntcGseEncMonChannelInx           OBJECT-TYPE
    SYNTAX      Unsigned32
    MAX-ACCESS  not-accessible
    STATUS      current
    DESCRIPTION
        "The index of the row (temporary until we have dynamic tables)"
    ::= { ntcGseEncMonChannelEntry 1 }
    
ntcGseEncMonChannelName          OBJECT-TYPE
    SYNTAX      DisplayString (SIZE(0..100))
    MAX-ACCESS  read-only
    STATUS      current
    DESCRIPTION
        "The name of the channel"
    ::= { ntcGseEncMonChannelEntry 2 }
    
ntcGseEncMonChannelNominalModcod OBJECT-TYPE
    SYNTAX      INTEGER { unspecified(0), qpsk14(1), qpsk13(2), qpsk25(3), qpsk12(4), qpsk35(5), qpsk23(6), qpsk34(7), qpsk45(8), qpsk56(9), qpsk89(10), qpsk910(11), e8psk35(12), e8psk23(13), e8psk34(14), e8psk56(15), e8psk89(16), e8psk910(17), e16apsk23(18), e16apsk34(19), e16apsk45(20), e16apsk56(21), e16apsk89(22), e16apsk910(23), e32apsk34(24), e32apsk45(25), e32apsk56(26), e32apsk89(27), e32apsk910(28), qpsk45180(129), qpsk60180(130), qpsk72180(131), qpsk80180(132), qpsk90180(133), qpsk100180(134), qpsk108180(135), qpsk114180(136), qpsk120180(137), qpsk126180(138), qpsk135180(139), qpsk144180(140), qpsk150180(141), qpsk160180(142), qpsk162180(143), e8psk80180(144), e8psk90180(145), e8psk100180(146), e8psk108180(147), e8psk114180(148), e8psk120180(149), e8psk126180(150), e8psk135180(151), e8psk144180(152), e8psk150180(153), e16apsk80180(154), e16apsk90180(155), e16apsk100180(156), e16apsk108180(157), e16apsk114180(158), e16apsk120180(159), e16apsk126180(160), e16apsk135180(161), e16apsk144180(162), e16apsk150180(163), e16apsk160180(164), e16apsk162180(165), e32apsk100180(166), e32apsk108180(167), e32apsk114180(168), e32apsk120180(169), e32apsk126180(170), e32apsk135180(171), e32apsk144180(172), e32apsk150180(173), e32apsk160180(174), e32apsk162180(175), e64apsk90180(176), e64apsk100180(177), e64apsk108180(178), e64apsk114180(179), e64apsk120180(180), e64apsk126180(181), e64apsk135180(182), e64apsk144180(183), e64apsk150180(184), e64apsk160180(185), e64apsk162180(186), e8pskl80180(187), e8pskl90180(188), e8pskl100180(189), e8pskl108180(190), e8pskl114180(191), e8pskl120180(192), e16apskl80180(193), e16apskl90180(194), e16apskl100180(195), e16apskl108180(196), e16apskl114180(197), e16apskl120180(198), e16apskl126180(199), e16apskl135180(200), e16apskl144180(201), e16apskl150180(202), e16apskl160180(203), e16apskl162180(204), e64apskl90180(205), e64apskl100180(206), e64apskl108180(207), e64apskl114180(208), e64apskl120180(209), e64apskl126180(210), e64apskl135180(211), e64apskl144180(212), e64apskl150180(213), e64apskl160180(214), e64apskl162180(215), qpsk1345(256), qpsk920(257), qpsk1120(258), e8apsk59l(259), e8apsk2645l(260), e8psk2336(261), e8psk2536(262), e8psk1318(263), e16apsk12l(264), e16apsk815l(265), e16apsk59l(266), e16apsk2645(267), e16apsk35(268), e16apsk35l(269), e16apsk2845(270), e16apsk2336(271), e16apsk23l(272), e16apsk2536(273), e16apsk1318(274), e16apsk79(275), e16apsk7790(276), e32apsk23l(277), e32apsk3245(278), e32apsk1115(279), e32apsk79(280), e64apsk3245l(281), e64apsk1115(282), e64apsk79(283), e64apsk45(284), e64apsk56(285), e128apsk34(286), e128apsk79(287), e256apsk2945l(288), e256apsk23l(289), e256apsk3145l(290), e256apsk3245(291), e256apsk1115l(292), e256apsk34(293), qpsk1145(294), qpsk415(295), qpsk1445(296), qpsk715(297), qpsk815(298), qpsk3245(299), e8psk715(300), e8psk815(301), e8psk2645(302), e8psk3245(303), e16apsk715(304), e16apsk815(305), e16apsk3245(306), e32apsk23(307) }
    MAX-ACCESS  read-only
    STATUS      current
    DESCRIPTION
        "The initial MODCOD configured for this channel."
    ::= { ntcGseEncMonChannelEntry 3 }
    
ntcGseEncMonChannelModcod        OBJECT-TYPE
    SYNTAX      INTEGER { unspecified(0), qpsk14(1), qpsk13(2), qpsk25(3), qpsk12(4), qpsk35(5), qpsk23(6), qpsk34(7), qpsk45(8), qpsk56(9), qpsk89(10), qpsk910(11), e8psk35(12), e8psk23(13), e8psk34(14), e8psk56(15), e8psk89(16), e8psk910(17), e16apsk23(18), e16apsk34(19), e16apsk45(20), e16apsk56(21), e16apsk89(22), e16apsk910(23), e32apsk34(24), e32apsk45(25), e32apsk56(26), e32apsk89(27), e32apsk910(28), qpsk45180(129), qpsk60180(130), qpsk72180(131), qpsk80180(132), qpsk90180(133), qpsk100180(134), qpsk108180(135), qpsk114180(136), qpsk120180(137), qpsk126180(138), qpsk135180(139), qpsk144180(140), qpsk150180(141), qpsk160180(142), qpsk162180(143), e8psk80180(144), e8psk90180(145), e8psk100180(146), e8psk108180(147), e8psk114180(148), e8psk120180(149), e8psk126180(150), e8psk135180(151), e8psk144180(152), e8psk150180(153), e16apsk80180(154), e16apsk90180(155), e16apsk100180(156), e16apsk108180(157), e16apsk114180(158), e16apsk120180(159), e16apsk126180(160), e16apsk135180(161), e16apsk144180(162), e16apsk150180(163), e16apsk160180(164), e16apsk162180(165), e32apsk100180(166), e32apsk108180(167), e32apsk114180(168), e32apsk120180(169), e32apsk126180(170), e32apsk135180(171), e32apsk144180(172), e32apsk150180(173), e32apsk160180(174), e32apsk162180(175), e64apsk90180(176), e64apsk100180(177), e64apsk108180(178), e64apsk114180(179), e64apsk120180(180), e64apsk126180(181), e64apsk135180(182), e64apsk144180(183), e64apsk150180(184), e64apsk160180(185), e64apsk162180(186), e8pskl80180(187), e8pskl90180(188), e8pskl100180(189), e8pskl108180(190), e8pskl114180(191), e8pskl120180(192), e16apskl80180(193), e16apskl90180(194), e16apskl100180(195), e16apskl108180(196), e16apskl114180(197), e16apskl120180(198), e16apskl126180(199), e16apskl135180(200), e16apskl144180(201), e16apskl150180(202), e16apskl160180(203), e16apskl162180(204), e64apskl90180(205), e64apskl100180(206), e64apskl108180(207), e64apskl114180(208), e64apskl120180(209), e64apskl126180(210), e64apskl135180(211), e64apskl144180(212), e64apskl150180(213), e64apskl160180(214), e64apskl162180(215), qpsk1345(256), qpsk920(257), qpsk1120(258), e8apsk59l(259), e8apsk2645l(260), e8psk2336(261), e8psk2536(262), e8psk1318(263), e16apsk12l(264), e16apsk815l(265), e16apsk59l(266), e16apsk2645(267), e16apsk35(268), e16apsk35l(269), e16apsk2845(270), e16apsk2336(271), e16apsk23l(272), e16apsk2536(273), e16apsk1318(274), e16apsk79(275), e16apsk7790(276), e32apsk23l(277), e32apsk3245(278), e32apsk1115(279), e32apsk79(280), e64apsk3245l(281), e64apsk1115(282), e64apsk79(283), e64apsk45(284), e64apsk56(285), e128apsk34(286), e128apsk79(287), e256apsk2945l(288), e256apsk23l(289), e256apsk3145l(290), e256apsk3245(291), e256apsk1115l(292), e256apsk34(293), qpsk1145(294), qpsk415(295), qpsk1445(296), qpsk715(297), qpsk815(298), qpsk3245(299), e8psk715(300), e8psk815(301), e8psk2645(302), e8psk3245(303), e16apsk715(304), e16apsk815(305), e16apsk3245(306), e32apsk23(307) }
    MAX-ACCESS  read-only
    STATUS      current
    DESCRIPTION
        "The actual MODCOD used by this channel."
    ::= { ntcGseEncMonChannelEntry 4 }
    
ntcGseEncMonChannelModcodChanges OBJECT-TYPE
    SYNTAX      Counter64
    MAX-ACCESS  read-only
    STATUS      current
    DESCRIPTION
        "Number of times the MODCOD has changed."
    ::= { ntcGseEncMonChannelEntry 5 }
    
ntcGseEncProtocol                OBJECT-TYPE
    SYNTAX      INTEGER { gse(0), xpe(1), mpe(2), ule(3) }
    MAX-ACCESS  read-only
    STATUS      current
    DESCRIPTION
        "The encapsulation protocol."
    ::= { ntcGseEncMonChannelEntry 6 }
    
ntcGseEncapsTable                OBJECT-TYPE
    SYNTAX      SEQUENCE OF NtcGseEncapsEntry
    MAX-ACCESS  not-accessible
    STATUS      current
    DESCRIPTION
        "A table containing the ntcGseEncaps"
    ::= { ntcGseEncObjects 3 }

ntcGseEncapsEntry                OBJECT-TYPE
    SYNTAX      NtcGseEncapsEntry
    MAX-ACCESS  not-accessible
    STATUS      current
    DESCRIPTION
        "A conceptual row of the ntcGseEncapsTable."
    INDEX   { ntcGseEncapsIsi  }
    ::= { ntcGseEncapsTable 1 }

NtcGseEncapsEntry                ::= SEQUENCE {
    ntcGseEncapsIsi          Unsigned32,
    ntcGseEncapsRowStatus    RowStatus,
    ntcGseEncapsEnable       NtcEnable,
    ntcGseEncapsFrmTp        INTEGER
    }
    
ntcGseEncapsIsi                  OBJECT-TYPE
    SYNTAX      Unsigned32
    MAX-ACCESS  not-accessible
    STATUS      current
    DESCRIPTION
        "The ISI that identifies this encapsulator (table key)."
    ::= { ntcGseEncapsEntry 1 }
    
ntcGseEncapsRowStatus            OBJECT-TYPE
    SYNTAX      RowStatus
    MAX-ACCESS  read-create
    STATUS      current
    DESCRIPTION
        "The status of this conceptual row. An existing conceptual row can be in any
        one of the three states, 'notReady', 'notInService', or 'active'. If the
        manager wishes to add a row in a single shot with values for all the columns,
        the status column should be given as 'createAndGo(4)'. After the creation of a
        row, its value is set to active(1). If a row has to be created with values for
        only some columns, the status column should be 'createAndWait(5)'. Also, this
        row with partially filled columns has the status 'notReady(3)'. The entry
        remains in this state until the values for all the columns is set. After all
        the values are set, the agent changes this value to active(1).'"
    ::= { ntcGseEncapsEntry 2 }
    
ntcGseEncapsEnable               OBJECT-TYPE
    SYNTAX      NtcEnable
    MAX-ACCESS  read-create
    STATUS      current
    DESCRIPTION
        "Enable or disable the corresponding encapsulator."
    ::= { ntcGseEncapsEntry 3 }
    
ntcGseEncapsFrmTp                OBJECT-TYPE
    SYNTAX      INTEGER { short(0), normal(1) }
    MAX-ACCESS  read-create
    STATUS      current
    DESCRIPTION
        "The type of frames for this encapsulator."
    ::= { ntcGseEncapsEntry 4 }
    
ntcGseEncChannelsTable           OBJECT-TYPE
    SYNTAX      SEQUENCE OF NtcGseEncChannelsEntry
    MAX-ACCESS  not-accessible
    STATUS      current
    DESCRIPTION
        "A table containing the ntcGseEncChannels"
    ::= { ntcGseEncObjects 4 }

ntcGseEncChannelsEntry           OBJECT-TYPE
    SYNTAX      NtcGseEncChannelsEntry
    MAX-ACCESS  not-accessible
    STATUS      current
    DESCRIPTION
        "A conceptual row of the ntcGseEncChannelsTable."
    INDEX   { ntcGseEncChannelsName  }
    ::= { ntcGseEncChannelsTable 1 }

NtcGseEncChannelsEntry           ::= SEQUENCE {
    ntcGseEncChannelsName          DisplayString,
    ntcGseEncChannelsRowStatus     RowStatus,
    ntcGseEncChanEnable            NtcEnable,
    ntcGseEncChanIsi               Unsigned32,
    ntcGseEncChanLabel             DisplayString,
    ntcGseEncChanNomS2Modcod       INTEGER,
    ntcGseEncChanNomS2ExtModcod    INTEGER,
    ntcGseEncChanAcmEnable         NtcEnable,
    ntcGseEncChanTermName          DisplayString
    }
    
ntcGseEncChannelsName            OBJECT-TYPE
    SYNTAX      DisplayString (SIZE(1..100))
    MAX-ACCESS  not-accessible
    STATUS      current
    DESCRIPTION
        "The name of the channel"
    ::= { ntcGseEncChannelsEntry 1 }
    
ntcGseEncChannelsRowStatus       OBJECT-TYPE
    SYNTAX      RowStatus
    MAX-ACCESS  read-create
    STATUS      current
    DESCRIPTION
        "The status of this conceptual row. An existing conceptual row can be in any
        one of the three states, 'notReady', 'notInService', or 'active'. If the
        manager wishes to add a row in a single shot with values for all the columns,
        the status column should be given as 'createAndGo(4)'. After the creation of a
        row, its value is set to active(1). If a row has to be created with values for
        only some columns, the status column should be 'createAndWait(5)'. Also, this
        row with partially filled columns has the status 'notReady(3)'. The entry
        remains in this state until the values for all the columns is set. After all
        the values are set, the agent changes this value to active(1).'"
    ::= { ntcGseEncChannelsEntry 2 }
    
ntcGseEncChanEnable              OBJECT-TYPE
    SYNTAX      NtcEnable
    MAX-ACCESS  read-create
    STATUS      current
    DESCRIPTION
        "Enable or disable the corresponding destination channel."
    ::= { ntcGseEncChannelsEntry 3 }
    
ntcGseEncChanIsi                 OBJECT-TYPE
    SYNTAX      Unsigned32
    MAX-ACCESS  read-create
    STATUS      current
    DESCRIPTION
        "The ISI of the channel"
    ::= { ntcGseEncChannelsEntry 4 }
    
ntcGseEncChanLabel               OBJECT-TYPE
    SYNTAX      DisplayString (SIZE(0..30))
    MAX-ACCESS  read-create
    STATUS      current
    DESCRIPTION
        "Label of the destination channel or the special identifier 'multicast'."
    ::= { ntcGseEncChannelsEntry 5 }
    
ntcGseEncChanNomS2Modcod         OBJECT-TYPE
    SYNTAX      INTEGER { unspecified(0), qpsk14(1), qpsk13(2), qpsk25(3), qpsk12(4), qpsk35(5), qpsk23(6), qpsk34(7), qpsk45(8), qpsk56(9), qpsk89(10), qpsk910(11), e8psk35(12), e8psk23(13), e8psk34(14), e8psk56(15), e8psk89(16), e8psk910(17), e16apsk23(18), e16apsk34(19), e16apsk45(20), e16apsk56(21), e16apsk89(22), e16apsk910(23), e32apsk34(24), e32apsk45(25), e32apsk56(26), e32apsk89(27), e32apsk910(28), qpsk1345(29), qpsk920(30), qpsk1120(31), e8apsk59l(32), e8apsk2645l(33), e8psk2336(34), e8psk2536(35), e8psk1318(36), e16apsk12l(37), e16apsk815l(38), e16apsk59l(39), e16apsk2645(40), e16apsk35(41), e16apsk35l(42), e16apsk2845(43), e16apsk2336(44), e16apsk23l(45), e16apsk2536(46), e16apsk1318(47), e16apsk79(48), e16apsk7790(49), e32apsk23l(50), e32apsk3245(51), e32apsk1115(52), e32apsk79(53), e64apsk3245l(54), e64apsk1115(55), e64apsk79(56), e64apsk45(57), e64apsk56(58), e128apsk34(59), e128apsk79(60), e256apsk2945l(61), e256apsk23l(62), e256apsk3145l(63), e256apsk3245(64), e256apsk1115l(65), e256apsk34(66), qpsk1145(67), qpsk415(68), qpsk1445(69), qpsk715(70), qpsk815(71), qpsk3245(72), e8psk715(73), e8psk815(74), e8psk2645(75), e8psk3245(76), e16apsk715(77), e16apsk815(78), e16apsk3245(79), e32apsk23(80) }
    MAX-ACCESS  read-create
    STATUS      current
    DESCRIPTION
        "The initial MODCOD that this channel uses in S2 mode."
    ::= { ntcGseEncChannelsEntry 6 }
    
ntcGseEncChanNomS2ExtModcod      OBJECT-TYPE
    SYNTAX      INTEGER { unspecified(0), qpsk45180(129), qpsk60180(130), qpsk72180(131), qpsk80180(132), qpsk90180(133), qpsk100180(134), qpsk108180(135), qpsk114180(136), qpsk120180(137), qpsk126180(138), qpsk135180(139), qpsk144180(140), qpsk150180(141), qpsk160180(142), qpsk162180(143), e8psk80180(144), e8psk90180(145), e8psk100180(146), e8psk108180(147), e8psk114180(148), e8psk120180(149), e8psk126180(150), e8psk135180(151), e8psk144180(152), e8psk150180(153), e16apsk80180(154), e16apsk90180(155), e16apsk100180(156), e16apsk108180(157), e16apsk114180(158), e16apsk120180(159), e16apsk126180(160), e16apsk135180(161), e16apsk144180(162), e16apsk150180(163), e16apsk160180(164), e16apsk162180(165), e32apsk100180(166), e32apsk108180(167), e32apsk114180(168), e32apsk120180(169), e32apsk126180(170), e32apsk135180(171), e32apsk144180(172), e32apsk150180(173), e32apsk160180(174), e32apsk162180(175), e64apsk90180(176), e64apsk100180(177), e64apsk108180(178), e64apsk114180(179), e64apsk120180(180), e64apsk126180(181), e64apsk135180(182), e64apsk144180(183), e64apsk150180(184), e64apsk160180(185), e64apsk162180(186), e8pskl80180(187), e8pskl90180(188), e8pskl100180(189), e8pskl108180(190), e8pskl114180(191), e8pskl120180(192), e16apskl80180(193), e16apskl90180(194), e16apskl100180(195), e16apskl108180(196), e16apskl114180(197), e16apskl120180(198), e16apskl126180(199), e16apskl135180(200), e16apskl144180(201), e16apskl150180(202), e16apskl160180(203), e16apskl162180(204), e64apskl90180(205), e64apskl100180(206), e64apskl108180(207), e64apskl114180(208), e64apskl120180(209), e64apskl126180(210), e64apskl135180(211), e64apskl144180(212), e64apskl150180(213), e64apskl160180(214), e64apskl162180(215) }
    MAX-ACCESS  read-create
    STATUS      current
    DESCRIPTION
        "The initial MODCOD that this channel uses in S2 Extensions mode."
    ::= { ntcGseEncChannelsEntry 7 }
    
ntcGseEncChanAcmEnable           OBJECT-TYPE
    SYNTAX      NtcEnable
    MAX-ACCESS  read-create
    STATUS      current
    DESCRIPTION
        "Enable or disable the ACM for this channel. This only takes effect when the
        encapsulator ACM is on."
    ::= { ntcGseEncChannelsEntry 8 }
    
ntcGseEncChanTermName            OBJECT-TYPE
    SYNTAX      DisplayString (SIZE(0..100))
    MAX-ACCESS  read-create
    STATUS      current
    DESCRIPTION
        "The name of the terminal to which this channel is configured"
    ::= { ntcGseEncChannelsEntry 9 }
    
ntcGseEncIsisTable               OBJECT-TYPE
    SYNTAX      SEQUENCE OF NtcGseEncIsisEntry
    MAX-ACCESS  not-accessible
    STATUS      current
    DESCRIPTION
        "A table containing the ntcGseEncIsis"
    ::= { ntcGseEncObjects 5 }

ntcGseEncIsisEntry               OBJECT-TYPE
    SYNTAX      NtcGseEncIsisEntry
    MAX-ACCESS  not-accessible
    STATUS      current
    DESCRIPTION
        "A conceptual row of the ntcGseEncIsisTable."
    INDEX   { ntcGseEncIsisName  }
    ::= { ntcGseEncIsisTable 1 }

NtcGseEncIsisEntry               ::= SEQUENCE {
    ntcGseEncIsisName         DisplayString,
    ntcGseEncIsisRowStatus    RowStatus,
    ntcGseEncIsiEnable        NtcEnable,
    ntcGseEncIsiIsi           Unsigned32,
    ntcGseEncIsiFrmTp         INTEGER,
    ntcGseEncIsiProtocol      INTEGER
    }
    
ntcGseEncIsisName                OBJECT-TYPE
    SYNTAX      DisplayString (SIZE(1..100))
    MAX-ACCESS  not-accessible
    STATUS      current
    DESCRIPTION
        "The name of the Isi"
    ::= { ntcGseEncIsisEntry 1 }
    
ntcGseEncIsisRowStatus           OBJECT-TYPE
    SYNTAX      RowStatus
    MAX-ACCESS  read-create
    STATUS      current
    DESCRIPTION
        "The status of this conceptual row. An existing conceptual row can be in any
        one of the three states, 'notReady', 'notInService', or 'active'. If the
        manager wishes to add a row in a single shot with values for all the columns,
        the status column should be given as 'createAndGo(4)'. After the creation of a
        row, its value is set to active(1). If a row has to be created with values for
        only some columns, the status column should be 'createAndWait(5)'. Also, this
        row with partially filled columns has the status 'notReady(3)'. The entry
        remains in this state until the values for all the columns is set. After all
        the values are set, the agent changes this value to active(1).'"
    ::= { ntcGseEncIsisEntry 2 }
    
ntcGseEncIsiEnable               OBJECT-TYPE
    SYNTAX      NtcEnable
    MAX-ACCESS  read-create
    STATUS      current
    DESCRIPTION
        "Enable or disable the corresponding encapsulator."
    ::= { ntcGseEncIsisEntry 3 }
    
ntcGseEncIsiIsi                  OBJECT-TYPE
    SYNTAX      Unsigned32
    MAX-ACCESS  read-create
    STATUS      current
    DESCRIPTION
        "The ISI that identifies this encapsulator (table key)."
    ::= { ntcGseEncIsisEntry 4 }
    
ntcGseEncIsiFrmTp                OBJECT-TYPE
    SYNTAX      INTEGER { short(0), normal(1) }
    MAX-ACCESS  read-create
    STATUS      current
    DESCRIPTION
        "The type of frames for this encapsulator."
    ::= { ntcGseEncIsisEntry 5 }
    
ntcGseEncIsiProtocol             OBJECT-TYPE
    SYNTAX      INTEGER { default(0), gse(1), xpe(2) }
    MAX-ACCESS  read-create
    STATUS      current
    DESCRIPTION
        "The baseband frame encapsulation protocol."
    ::= { ntcGseEncIsisEntry 6 }
    
ntcGseEncBbfChannelsTable        OBJECT-TYPE
    SYNTAX      SEQUENCE OF NtcGseEncBbfChannelsEntry
    MAX-ACCESS  not-accessible
    STATUS      current
    DESCRIPTION
        "A table containing the ntcGseEncBbfChannels"
    ::= { ntcGseEncObjects 6 }

ntcGseEncBbfChannelsEntry        OBJECT-TYPE
    SYNTAX      NtcGseEncBbfChannelsEntry
    MAX-ACCESS  not-accessible
    STATUS      current
    DESCRIPTION
        "A conceptual row of the ntcGseEncBbfChannelsTable."
    INDEX   { ntcGseEncBbfChannelsName  }
    ::= { ntcGseEncBbfChannelsTable 1 }

NtcGseEncBbfChannelsEntry        ::= SEQUENCE {
    ntcGseEncBbfChannelsName           DisplayString,
    ntcGseEncBbfChannelsRowStatus      RowStatus,
    ntcGseEncBbfChanEnable             NtcEnable,
    ntcGseEncBbfChanOutTypeName        OCTET STRING,
    ntcGseEncBbfChanOutInstanceName    OCTET STRING,
    ntcGseEncBbfChanLabel              DisplayString,
    ntcGseEncBbfChanNomS2Modcod        INTEGER,
    ntcGseEncBbfChanNomS2ExtModcod     INTEGER,
    ntcGseEncBbfChanAcmEnable          NtcEnable,
    ntcGseEncBbfChanTermName           DisplayString,
    ntcGseEncBbfChanAccessVlan         Unsigned32
    }
    
ntcGseEncBbfChannelsName         OBJECT-TYPE
    SYNTAX      DisplayString (SIZE(1..100))
    MAX-ACCESS  not-accessible
    STATUS      current
    DESCRIPTION
        "The name of the channel"
    ::= { ntcGseEncBbfChannelsEntry 1 }
    
ntcGseEncBbfChannelsRowStatus    OBJECT-TYPE
    SYNTAX      RowStatus
    MAX-ACCESS  read-create
    STATUS      current
    DESCRIPTION
        "The status of this conceptual row. An existing conceptual row can be in any
        one of the three states, 'notReady', 'notInService', or 'active'. If the
        manager wishes to add a row in a single shot with values for all the columns,
        the status column should be given as 'createAndGo(4)'. After the creation of a
        row, its value is set to active(1). If a row has to be created with values for
        only some columns, the status column should be 'createAndWait(5)'. Also, this
        row with partially filled columns has the status 'notReady(3)'. The entry
        remains in this state until the values for all the columns is set. After all
        the values are set, the agent changes this value to active(1).'"
    ::= { ntcGseEncBbfChannelsEntry 2 }
    
ntcGseEncBbfChanEnable           OBJECT-TYPE
    SYNTAX      NtcEnable
    MAX-ACCESS  read-create
    STATUS      current
    DESCRIPTION
        "Enable or disable the corresponding destination channel."
    ::= { ntcGseEncBbfChannelsEntry 3 }
    
ntcGseEncBbfChanOutTypeName      OBJECT-TYPE
    SYNTAX      OCTET STRING (SIZE(0..255))
    MAX-ACCESS  read-create
    STATUS      current
    DESCRIPTION
        "The output type of the encapsulation channel."
    ::= { ntcGseEncBbfChannelsEntry 4 }
    
ntcGseEncBbfChanOutInstanceName  OBJECT-TYPE
    SYNTAX      OCTET STRING (SIZE(0..255))
    MAX-ACCESS  read-create
    STATUS      current
    DESCRIPTION
        "The output instance name."
    ::= { ntcGseEncBbfChannelsEntry 5 }
    
ntcGseEncBbfChanLabel            OBJECT-TYPE
    SYNTAX      DisplayString (SIZE(0..30))
    MAX-ACCESS  read-create
    STATUS      current
    DESCRIPTION
        "Label of the destination channel or the special identifier 'multicast'."
    ::= { ntcGseEncBbfChannelsEntry 6 }
    
ntcGseEncBbfChanNomS2Modcod      OBJECT-TYPE
    SYNTAX      INTEGER { unspecified(0), qpsk14(1), qpsk13(2), qpsk25(3), qpsk12(4), qpsk35(5), qpsk23(6), qpsk34(7), qpsk45(8), qpsk56(9), qpsk89(10), qpsk910(11), e8psk35(12), e8psk23(13), e8psk34(14), e8psk56(15), e8psk89(16), e8psk910(17), e16apsk23(18), e16apsk34(19), e16apsk45(20), e16apsk56(21), e16apsk89(22), e16apsk910(23), e32apsk34(24), e32apsk45(25), e32apsk56(26), e32apsk89(27), e32apsk910(28), qpsk1345(29), qpsk920(30), qpsk1120(31), e8apsk59l(32), e8apsk2645l(33), e8psk2336(34), e8psk2536(35), e8psk1318(36), e16apsk12l(37), e16apsk815l(38), e16apsk59l(39), e16apsk2645(40), e16apsk35(41), e16apsk35l(42), e16apsk2845(43), e16apsk2336(44), e16apsk23l(45), e16apsk2536(46), e16apsk1318(47), e16apsk79(48), e16apsk7790(49), e32apsk23l(50), e32apsk3245(51), e32apsk1115(52), e32apsk79(53), e64apsk3245l(54), e64apsk1115(55), e64apsk79(56), e64apsk45(57), e64apsk56(58), e128apsk34(59), e128apsk79(60), e256apsk2945l(61), e256apsk23l(62), e256apsk3145l(63), e256apsk3245(64), e256apsk1115l(65), e256apsk34(66), qpsk1145(67), qpsk415(68), qpsk1445(69), qpsk715(70), qpsk815(71), qpsk3245(72), e8psk715(73), e8psk815(74), e8psk2645(75), e8psk3245(76), e16apsk715(77), e16apsk815(78), e16apsk3245(79), e32apsk23(80) }
    MAX-ACCESS  read-create
    STATUS      current
    DESCRIPTION
        "The initial MODCOD that this channel uses in S2 mode."
    ::= { ntcGseEncBbfChannelsEntry 7 }
    
ntcGseEncBbfChanNomS2ExtModcod   OBJECT-TYPE
    SYNTAX      INTEGER { unspecified(0), qpsk45180(129), qpsk60180(130), qpsk72180(131), qpsk80180(132), qpsk90180(133), qpsk100180(134), qpsk108180(135), qpsk114180(136), qpsk120180(137), qpsk126180(138), qpsk135180(139), qpsk144180(140), qpsk150180(141), qpsk160180(142), qpsk162180(143), e8psk80180(144), e8psk90180(145), e8psk100180(146), e8psk108180(147), e8psk114180(148), e8psk120180(149), e8psk126180(150), e8psk135180(151), e8psk144180(152), e8psk150180(153), e16apsk80180(154), e16apsk90180(155), e16apsk100180(156), e16apsk108180(157), e16apsk114180(158), e16apsk120180(159), e16apsk126180(160), e16apsk135180(161), e16apsk144180(162), e16apsk150180(163), e16apsk160180(164), e16apsk162180(165), e32apsk100180(166), e32apsk108180(167), e32apsk114180(168), e32apsk120180(169), e32apsk126180(170), e32apsk135180(171), e32apsk144180(172), e32apsk150180(173), e32apsk160180(174), e32apsk162180(175), e64apsk90180(176), e64apsk100180(177), e64apsk108180(178), e64apsk114180(179), e64apsk120180(180), e64apsk126180(181), e64apsk135180(182), e64apsk144180(183), e64apsk150180(184), e64apsk160180(185), e64apsk162180(186), e8pskl80180(187), e8pskl90180(188), e8pskl100180(189), e8pskl108180(190), e8pskl114180(191), e8pskl120180(192), e16apskl80180(193), e16apskl90180(194), e16apskl100180(195), e16apskl108180(196), e16apskl114180(197), e16apskl120180(198), e16apskl126180(199), e16apskl135180(200), e16apskl144180(201), e16apskl150180(202), e16apskl160180(203), e16apskl162180(204), e64apskl90180(205), e64apskl100180(206), e64apskl108180(207), e64apskl114180(208), e64apskl120180(209), e64apskl126180(210), e64apskl135180(211), e64apskl144180(212), e64apskl150180(213), e64apskl160180(214), e64apskl162180(215) }
    MAX-ACCESS  read-create
    STATUS      current
    DESCRIPTION
        "The initial MODCOD that this channel uses in S2 Extensions mode."
    ::= { ntcGseEncBbfChannelsEntry 8 }
    
ntcGseEncBbfChanAcmEnable        OBJECT-TYPE
    SYNTAX      NtcEnable
    MAX-ACCESS  read-create
    STATUS      current
    DESCRIPTION
        "Enable or disable the ACM for this channel. This only takes effect when the
        encapsulator ACM is on."
    ::= { ntcGseEncBbfChannelsEntry 9 }
    
ntcGseEncBbfChanTermName         OBJECT-TYPE
    SYNTAX      DisplayString (SIZE(0..100))
    MAX-ACCESS  read-create
    STATUS      current
    DESCRIPTION
        "The name of the terminal to which this channel is configured"
    ::= { ntcGseEncBbfChannelsEntry 10 }
    
ntcGseEncBbfChanAccessVlan       OBJECT-TYPE
    SYNTAX      Unsigned32 (0..4095)
    MAX-ACCESS  read-create
    STATUS      current
    DESCRIPTION
        "If a non-zero Access VLAN is associated to an encapsulation channel, traffic
        from this VLAN is transmitted untagged to the channel."
    ::= { ntcGseEncBbfChannelsEntry 11 }
    
ntcGseEncDefEncProt              OBJECT-TYPE
    SYNTAX      INTEGER { gse(0), xpe(1) }
    MAX-ACCESS  read-write
    STATUS      current
    DESCRIPTION
        "The default baseband frame encapsulation protocol."
    DEFVAL { gse }
    ::= { ntcGseEncObjects 7 }
    

--
--  Module Conformance
--

ntcGseEncConfGrpV1Standard       OBJECT-GROUP
    OBJECTS    {
                   ntcGseEncModStandard,
                   ntcGseEncPilots,
                   ntcGseEncSymbolRate,
                   ntcGseEncTransMode,
                   ntcGseEncEquaEnable,
                   ntcGseEncStreamMode,
                   ntcGseEncS2Modcod,
                   ntcGseEncFrameType,
                   ntcGseEncMonChannelName,
                   ntcGseEncMonChannelNominalModcod,
                   ntcGseEncMonChannelModcod,
                   ntcGseEncMonChannelModcodChanges,
                   ntcGseEncProtocol,
                   ntcGseEncapsRowStatus,
                   ntcGseEncapsEnable,
                   ntcGseEncapsFrmTp,
                   ntcGseEncChannelsRowStatus,
                   ntcGseEncChanEnable,
                   ntcGseEncChanIsi,
                   ntcGseEncChanLabel,
                   ntcGseEncChanNomS2Modcod,
                   ntcGseEncChanNomS2ExtModcod,
                   ntcGseEncChanAcmEnable,
                   ntcGseEncChanTermName,
                   ntcGseEncIsisRowStatus,
                   ntcGseEncIsiEnable,
                   ntcGseEncIsiIsi,
                   ntcGseEncIsiFrmTp,
                   ntcGseEncIsiProtocol,
                   ntcGseEncBbfChannelsRowStatus,
                   ntcGseEncBbfChanEnable,
                   ntcGseEncBbfChanOutTypeName,
                   ntcGseEncBbfChanOutInstanceName,
                   ntcGseEncBbfChanLabel,
                   ntcGseEncBbfChanNomS2Modcod,
                   ntcGseEncBbfChanNomS2ExtModcod,
                   ntcGseEncBbfChanAcmEnable,
                   ntcGseEncBbfChanTermName,
                   ntcGseEncBbfChanAccessVlan,
                   ntcGseEncDefEncProt
               }
    STATUS      current
    DESCRIPTION
        "Managed objects that constitute version 1 of a system device with standard capabilities."
    ::= { ntcGseEncConfGroup 1}
    
ntcGseEncConfCompV1Standard      MODULE-COMPLIANCE
    STATUS      current
    DESCRIPTION
        "Compliance statement for Newtec device MIB implementations."
    MODULE  -- this module
    MANDATORY-GROUPS
                  {
                      ntcGseEncConfGrpV1Standard
                  }
    ::= { ntcGseEncConfCompliance  1 }
    

END

NEWTEC-MAIN-MIB DEFINITIONS ::= BEGIN

IMPORTS

    enterprises,
    MODULE-IDENTITY,
    OBJECT-IDENTITY
        FROM SNMPv2-SMI;


--
-- Module Identification
--

ntcMIB                           MODULE-IDENTITY

    LAST-UPDATED  "201511201200Z"
    ORGANIZATION  "Newtec Cy"
    CONTACT-INFO
        "Newtec Cy
         Postal: Newtec Cy
                 Laarstraat 5
                 B-9100 Sint-Niklaas
                 Belgium

                 Tel: +32 3 780 65 00
                 Fax: +32 3 780 65 49
         Web:    www.newtec.be
         E-mail: techsupport@newtec.be"
    DESCRIPTION
        "Newtec corporate main MIB serving as framework for all MIBs
         supported by Newtec equipment."

    REVISION      "201511201200Z"
    DESCRIPTION
        "Systems range added"

    REVISION      "201309021200Z"
    DESCRIPTION
        "Experimental and LDAP range added"

    REVISION      "201206281200Z"
    DESCRIPTION
        "Release for M6100 R1.2"

    REVISION      "200405041100Z"
    DESCRIPTION
        "Add the ntcSecurity branch"

    REVISION      "200003271400Z"
    DESCRIPTION
         "Initial version of the Newtec top level MIB"

    ::= { enterprises 5835 }


--
-- Top-Level Structure
--

-- ntcMIB content

ntcSems                          OBJECT-IDENTITY
    STATUS        current
    DESCRIPTION   "Subtree for definitions for SEMS, Newtec's Satellite
                   Earth-station Management System"
    ::= { ntcMIB 1 }

ntcPlex                          OBJECT-IDENTITY
    STATUS        obsolete
    DESCRIPTION   "Extensions of ntcSems specific for the SkyPlex
                   system."
    ::= { ntcMIB 2 }

ntcDevices                       OBJECT-IDENTITY
    STATUS        current
    DESCRIPTION   "Subtree to manage newtec devices"
    ::= { ntcMIB 3 }

ntcSecurity                      OBJECT-IDENTITY
    STATUS        obsolete
    DESCRIPTION   "Subtree to manage/monitor all kinds of security
                   related parameters such as intrusion detection."
    ::= { ntcMIB 4 }

ntcPublic                        OBJECT-IDENTITY
    STATUS        current
    DESCRIPTION   "This is where modular MIB definitions relating to
                   released functionality are published since 2012."
    ::= { ntcMIB 5 }

ntcExperimental                  OBJECT-IDENTITY
    STATUS        current
    DESCRIPTION   "Experimental subtree"
    ::= { ntcMIB 6 }

ntcLDAP                          OBJECT-IDENTITY
    STATUS        current
    DESCRIPTION   "OID range used by Newtec LDAP schema"
    ::= { ntcMIB 7 }

ntcSystems                       OBJECT-IDENTITY
    STATUS        current
    DESCRIPTION   "OID range used by Newtec Systems"
    ::= { ntcMIB 8 }


-- ntcPublic content

ntcGeneric                       OBJECT-IDENTITY
    STATUS        current
    DESCRIPTION   "This is where MIB definitions that are applicable
                   across all MIbs, are found. In particular, this is
                   where the Newtec textual conventions MIB is located."
    ::= { ntcPublic 1 }

ntcFunction                      OBJECT-IDENTITY
    STATUS        current
    DESCRIPTION   "This is where MIB definitions for all modular
                   functional blocks that are used in some product
                   configuration, are located. Functional blocks are
                   re-usable units of cohesive functionality that are
                   always deployed together. They are further organised
                   into subtrees according to their functional
                   categories."
    ::= { ntcPublic 2 }

ntcEvent                         OBJECT-IDENTITY
    STATUS        current
    DESCRIPTION   "This is where definitions related to event management
                   and reporting, are located. Modular MIBs use a single
                   general format notification (trap) to report events
                   from any functional block. The data definitions here
                   are used to describe what event occurred, which
                   functional block it occurred in, and in what device
                   that functional block is located. The definitions are
                   independent of the functional blocks that populate
                   them."
    ::= { ntcPublic 3 }


END

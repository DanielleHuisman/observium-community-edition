NEWTEC-MODULATORPOWERPROXY-MIB DEFINITIONS ::= BEGIN

IMPORTS
    Integer32,
    Counter64,
    MODULE-IDENTITY,
    OBJECT-IDENTITY,
    OBJECT-TYPE
        FROM SNMPv2-SMI

    MODULE-COMPLIANCE,
    OBJECT-GROUP
        FROM SNMPv2-CONF
    
    NtcEnable
        FROM NEWTEC-TC-MIB

    ntcFunction
        FROM NEWTEC-MAIN-MIB;


--
--  Module Identification
--

ntcModulatorPowerProxy   MODULE-IDENTITY
    LAST-UPDATED "201305220600Z"
    ORGANIZATION "Newtec Cy"
    CONTACT-INFO
        "Newtec Cy
         Postal: Newtec Cy
                 Laarstraat 5
                 B-9100 Sint-Niklaas
                 Belgium

                Tel: +32 3 780 65 00
                Fax: +32 3 780 65 49
                Web: www.newtec.be
                E-mail: techsupport@newtec.be"
    DESCRIPTION
        "Newtec modular Modulator power proxy MIB containing definitions for the
        Modulator power proxy."

    REVISION  "201305220600Z"
    DESCRIPTION
        "Initial release for MDM6000 R1.1"
    ::= { ntcFunction  3400 }
    

--
-- Top-Level Structure
--

-- ntcModulatorPowerProxy content

ntcModulatorPowerProxyObjects    OBJECT-IDENTITY
    STATUS        current
    DESCRIPTION   "Container holding ntcModulatorPowerProxyObjects definitions."
    ::= { ntcModulatorPowerProxy 1 }
    
ntcModPwrProxyConformance        OBJECT-IDENTITY
    STATUS        current
    DESCRIPTION   "Conformance requirements."
    ::= { ntcModulatorPowerProxy 2 }
    
-- ntcModulatorPowerProxyObjects content

ntcModPowerProxyMonitoring       OBJECT-IDENTITY
    STATUS        current
    DESCRIPTION   "Container holding ntcModPowerProxyMonitoring definitions."
    ::= { ntcModulatorPowerProxyObjects 2 }
    
-- ntcModPwrProxyConformance content

ntcModPwrProxyConfCompliance     OBJECT-IDENTITY
    STATUS        current
    DESCRIPTION   "Device compliance statements."
    ::= { ntcModPwrProxyConformance 1 }
    
ntcModPwrProxyConfGroup          OBJECT-IDENTITY
    STATUS        current
    DESCRIPTION   "Groups used by device compliance statements."
    ::= { ntcModPwrProxyConformance 2 }
    

--
-- Managed Objects
--

ntcModPowerProxyEnable           OBJECT-TYPE
    SYNTAX      NtcEnable
    MAX-ACCESS  read-write
    STATUS      current
    DESCRIPTION
        "Enable or disable the Modulator power proxy"
    DEFVAL { off }
    ::= { ntcModulatorPowerProxyObjects 1 }
    
ntcModPowerProxyRmtUpcState      OBJECT-TYPE
    SYNTAX      INTEGER { off(0), on(1) }
    MAX-ACCESS  read-only
    STATUS      current
    DESCRIPTION
        "The state of the remote uplink power controller"
    ::= { ntcModPowerProxyMonitoring 1 }
    
ntcModPowerProxyCurModPower      OBJECT-TYPE
    SYNTAX      Integer32 (-350..100)
    UNITS       "dBm"
    MAX-ACCESS  read-only
    STATUS      current
    DESCRIPTION
        "The current modulator power in dBm. Float represented as integer is scaled by
        a factor of 10. i.e. a value of '-103' means '-10.3' dBm"
    ::= { ntcModPowerProxyMonitoring 2 }
    
ntcModPowerProxyPowerReqCounter  OBJECT-TYPE
    SYNTAX      Counter64
    MAX-ACCESS  read-only
    STATUS      current
    DESCRIPTION
        "The number of power updates"
    ::= { ntcModPowerProxyMonitoring 3 }
    

--
--  Module Conformance
--

ntcModPwrProxyConfGrpV1Standard  OBJECT-GROUP
    OBJECTS    {
                   ntcModPowerProxyEnable,
                   ntcModPowerProxyRmtUpcState,
                   ntcModPowerProxyCurModPower,
                   ntcModPowerProxyPowerReqCounter
               }
    STATUS      current
    DESCRIPTION
        "Managed objects that constitute version 1 of a system device with standard capabilities."
    ::= { ntcModPwrProxyConfGroup 1}
    
ntcModPwrProxyConfCompV1Standard MODULE-COMPLIANCE
    STATUS      current
    DESCRIPTION
        "Compliance statement for Newtec device MIB implementations."
    MODULE  -- this module
    MANDATORY-GROUPS
                  {
                      ntcModPwrProxyConfGrpV1Standard
                  }
    ::= { ntcModPwrProxyConfCompliance  1 }
    

END

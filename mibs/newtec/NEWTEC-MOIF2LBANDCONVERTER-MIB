NEWTEC-MOIF2LBANDCONVERTER-MIB DEFINITIONS ::= BEGIN

IMPORTS
    MODULE-IDENTITY,
    OBJECT-IDENTITY,
    OBJECT-TYPE
        FROM SNMPv2-SMI

    MODULE-COMPLIANCE,
    OBJECT-GROUP
        FROM SNMPv2-CONF
    
    NtcAlarmState
        FROM NEWTEC-TC-MIB

    ntcFunction
        FROM NEWTEC-MAIN-MIB;


--
--  Module Identification
--

ntcMoIF2LbandConverter   MODULE-IDENTITY
    LAST-UPDATED "201502190900Z"
    ORGANIZATION "Newtec Cy"
    CONTACT-INFO
        "Newtec Cy
         Postal: Newtec Cy
                 Laarstraat 5
                 B-9100 Sint-Niklaas
                 Belgium

                Tel: +32 3 780 65 00
                Fax: +32 3 780 65 49
                Web: www.newtec.be
                E-mail: techsupport@newtec.be"
    DESCRIPTION
        "Newtec modular IF2Lband convertor MIB containing definitions for IF2Lband
        convertor functionality."

    REVISION  "201502190900Z"
    DESCRIPTION
        "initial version."
    ::= { ntcFunction  8600 }
    

--
-- Top-Level Structure
--

-- ntcMoIF2LbandConverter content

ntcMoIF2LConvObjects             OBJECT-IDENTITY
    STATUS        current
    DESCRIPTION   "Container holding ntcMoIF2LConvObjects definitions."
    ::= { ntcMoIF2LbandConverter 1 }
    
ntcMoIF2LConvConformance         OBJECT-IDENTITY
    STATUS        current
    DESCRIPTION   "Conformance requirements."
    ::= { ntcMoIF2LbandConverter 2 }
    
-- ntcMoIF2LConvObjects content

ntcMoIF2LConvAlarm               OBJECT-IDENTITY
    STATUS        current
    DESCRIPTION   "Container holding ntcMoIF2LConvAlarm definitions."
    ::= { ntcMoIF2LConvObjects 1 }
    
-- ntcMoIF2LConvConformance content

ntcMoIF2LConvConfCompliance      OBJECT-IDENTITY
    STATUS        current
    DESCRIPTION   "Device compliance statements."
    ::= { ntcMoIF2LConvConformance 1 }
    
ntcMoIF2LConvConfGroup           OBJECT-IDENTITY
    STATUS        current
    DESCRIPTION   "Groups used by device compliance statements."
    ::= { ntcMoIF2LConvConformance 2 }
    

--
-- Managed Objects
--

ntcMoIF2LConvHardware            OBJECT-TYPE
    SYNTAX      NtcAlarmState
    MAX-ACCESS  read-only
    STATUS      current
    DESCRIPTION
        "This alarm is raised when the converter is not working correctly due to
        hardware failures on the converter module This variable indicates the current
        status of the alarm."
    ::= { ntcMoIF2LConvAlarm 1 }
    
ntcMoIF2LConvCommunication       OBJECT-TYPE
    SYNTAX      NtcAlarmState
    MAX-ACCESS  read-only
    STATUS      current
    DESCRIPTION
        "This alarm is raised when the converter is not working correctly due to
        communication failures on the converter module This variable indicates the
        current status of the alarm."
    ::= { ntcMoIF2LConvAlarm 2 }
    

--
--  Module Conformance
--

ntcMoIF2LConvConfGrpV1Standard   OBJECT-GROUP
    OBJECTS    {
                   ntcMoIF2LConvHardware,
                   ntcMoIF2LConvCommunication
               }
    STATUS      current
    DESCRIPTION
        "Managed objects that constitute version 1 of a system device with standard capabilities."
    ::= { ntcMoIF2LConvConfGroup 1}
    
ntcMoIF2LConvConfCompV1Standard  MODULE-COMPLIANCE
    STATUS      current
    DESCRIPTION
        "Compliance statement for Newtec device MIB implementations."
    MODULE  -- this module
    MANDATORY-GROUPS
                  {
                      ntcMoIF2LConvConfGrpV1Standard
                  }
    ::= { ntcMoIF2LConvConfCompliance  1 }
    

END

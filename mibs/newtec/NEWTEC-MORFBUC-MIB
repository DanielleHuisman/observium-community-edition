NEWTEC-MORFBUC-MIB DEFINITIONS ::= BEGIN

IMPORTS
    MODULE-IDENTITY,
    OBJECT-IDENTITY,
    OBJECT-TYPE
        FROM SNMPv2-SMI

    MODULE-COMPLIANCE,
    OBJECT-GROUP
        FROM SNMPv2-CONF
    
    NtcAlarmState
        FROM NEWTEC-TC-MIB

    ntcFunction
        FROM NEWTEC-MAIN-MIB;


--
--  Module Identification
--

ntcMoRfBlockUpConv   MODULE-IDENTITY
    LAST-UPDATED "201605170900Z"
    ORGANIZATION "Newtec Cy"
    CONTACT-INFO
        "Newtec Cy
         Postal: Newtec Cy
                 Laarstraat 5
                 B-9100 Sint-Niklaas
                 Belgium

                Tel: +32 3 780 65 00
                Fax: +32 3 780 65 49
                Web: www.newtec.be
                E-mail: techsupport@newtec.be"
    DESCRIPTION
        "Newtec modular RF block upconvertor MIB containing definitions for the
        convertor functionality."

    REVISION  "201605170900Z"
    DESCRIPTION
        "Initial release for M6100 R2.8"
    ::= { ntcFunction  10000 }
    

--
-- Top-Level Structure
--

-- ntcMoRfBlockUpConv content

ntcMoRfBucObjects                OBJECT-IDENTITY
    STATUS        current
    DESCRIPTION   "Container holding ntcMoRfBucObjects definitions."
    ::= { ntcMoRfBlockUpConv 1 }
    
ntcMoRfBucConformance            OBJECT-IDENTITY
    STATUS        current
    DESCRIPTION   "Conformance requirements."
    ::= { ntcMoRfBlockUpConv 2 }
    
-- ntcMoRfBucObjects content

ntcMoRfBucAlarm                  OBJECT-IDENTITY
    STATUS        current
    DESCRIPTION   "Container holding ntcMoRfBucAlarm definitions."
    ::= { ntcMoRfBucObjects 1 }
    
-- ntcMoRfBucConformance content

ntcMoRfBucConfCompliance         OBJECT-IDENTITY
    STATUS        current
    DESCRIPTION   "Device compliance statements."
    ::= { ntcMoRfBucConformance 1 }
    
ntcMoRfBucConfGroup              OBJECT-IDENTITY
    STATUS        current
    DESCRIPTION   "Groups used by device compliance statements."
    ::= { ntcMoRfBucConformance 2 }
    

--
-- Managed Objects
--

ntcMoRfBucHardware               OBJECT-TYPE
    SYNTAX      NtcAlarmState
    MAX-ACCESS  read-only
    STATUS      current
    DESCRIPTION
        "This alarm is raised when the converter is not working correctly due to
        hardware failures on the converter module This variable indicates the current
        status of the alarm."
    ::= { ntcMoRfBucAlarm 1 }
    
ntcMoRfBucCommunication          OBJECT-TYPE
    SYNTAX      NtcAlarmState
    MAX-ACCESS  read-only
    STATUS      current
    DESCRIPTION
        "This alarm is raised when the converter is not working correctly due to
        communication failures on the converter module This variable indicates the
        current status of the alarm."
    ::= { ntcMoRfBucAlarm 2 }
    

--
--  Module Conformance
--

ntcMoRfBucConfGrpV1Standard      OBJECT-GROUP
    OBJECTS    {
                   ntcMoRfBucHardware,
                   ntcMoRfBucCommunication
               }
    STATUS      current
    DESCRIPTION
        "Managed objects that constitute version 1 of a system device with standard capabilities."
    ::= { ntcMoRfBucConfGroup 1}
    
ntcMoRfBucConfCompV1Standard     MODULE-COMPLIANCE
    STATUS      current
    DESCRIPTION
        "Compliance statement for Newtec device MIB implementations."
    MODULE  -- this module
    MANDATORY-GROUPS
                  {
                      ntcMoRfBucConfGrpV1Standard
                  }
    ::= { ntcMoRfBucConfCompliance  1 }
    

END

NEWTEC-NOTIFICATION-MIB DEFINITIONS ::= BEGIN

IMPORTS

    MODULE-IDENTITY,
    NOTIFICATION-TYPE,
    OBJECT-IDENTITY,
    OBJECT-TYPE,
	Counter32
        FROM SNMPv2-SMI

    MODULE-COMPLIANCE,
    NOTIFICATION-GROUP,
    OBJECT-GROUP
        FROM SNMPv2-CONF

    DisplayString
        FROM SNMPv2-TC

    NtcAlarmState
        FROM NEWTEC-TC-MIB		
		
    ntcEvent
        FROM NEWTEC-MAIN-MIB;


--
--  Module Identification
--

ntcNotification                  MODULE-IDENTITY

    LAST-UPDATED  "201206281200Z"
    ORGANIZATION  "Newtec Cy"
    CONTACT-INFO
        "Newtec Cy
         Postal: Newtec Cy
                 Laarstraat 5
                 B-9100 Sint-Niklaas
                 Belgium

                 Tel: +32 3 780 65 00
                 Fax: +32 3 780 65 49
         Web:    www.newtec.be
         E-mail: techsupport@newtec.be"
    DESCRIPTION
        "Newtec modular event notification MIB containing definitions
         for the reporting of all events of interest. It applies only to
         events that occur in modular functional blocks."


    REVISION      "201206281200Z"
    DESCRIPTION
        "Release for M6100 R1.2"
        
    REVISION      "201205161235Z"
    DESCRIPTION
        "Initial version."

    ::= { ntcEvent 2 }


--
-- Top-Level Structure
--

-- ntcNotification content

ntcNotifObjects                  OBJECT-IDENTITY
    STATUS        current
    DESCRIPTION   "Notification data objects."
    ::= { ntcNotification 1 }

ntcNotifConformance              OBJECT-IDENTITY
    STATUS        current
    DESCRIPTION   "Conformance requirements."
    ::= { ntcNotification 2 }

-- ntcNotifObjects content

ntcNotifReportList               OBJECT-IDENTITY
    STATUS        current
    DESCRIPTION   "Reports issued with the notification - always one,
                   but included to ensure reverse-mappability with
                   trap objects in SMIv1."
    ::= { ntcNotifObjects 0 }

ntcNotifField                    OBJECT-IDENTITY
    STATUS        current
    DESCRIPTION   "Fields comprising the notification report."
    ::= { ntcNotifObjects 1 }

-- ntcNotifConformance content

ntcNotifConfGroup                OBJECT-IDENTITY
    STATUS        current
    DESCRIPTION   "Groups used by notification compliance statements."
    ::= { ntcNotifConformance 1 }

ntcNotifConfCompliance           OBJECT-IDENTITY
    STATUS        current
    DESCRIPTION   "Notification compliance statements."
    ::= { ntcNotifConformance 2 }


--
-- Notification Data Objects
--

-- ntcNotifField content

ntcNotifFldSeqNbr              OBJECT-TYPE
    SYNTAX        Counter32
    MAX-ACCESS    accessible-for-notify
    STATUS        current
    DESCRIPTION   "The sequence number of this alarm report.
	               This counter will increment sequentially for 
				   each ntcNotifAlReport that is sent out and can 
				   be used by trapsinks to determine if any trap 
				   got lost in transit.
				   This same sequence number if also logged in the 
				   ntcAlmLogTable to allow NMS systems to synchronize
				   the trap history"
    ::= { ntcNotifField 1 }

ntcNotifFldSeverity              OBJECT-TYPE
    SYNTAX        DisplayString
    MAX-ACCESS    accessible-for-notify
    STATUS        current
    DESCRIPTION   "The seriousness of the event being reported."
    ::= { ntcNotifField 2 }

ntcNotifFldDevice                OBJECT-TYPE
    SYNTAX        DisplayString
    MAX-ACCESS    accessible-for-notify
    STATUS        current
    DESCRIPTION   "User-assigned name for the device that originated
                   the notification. This is ntcDevIdLabel which can
                   be configured via the NEWTEC-DEVICE-MIB."
    ::= { ntcNotifField 3 }

ntcNotifFldFunctionName          OBJECT-TYPE
    SYNTAX        DisplayString
    MAX-ACCESS    accessible-for-notify
    STATUS        current
    DESCRIPTION   "Name of the functional block that originated the
                   notification."
    ::= { ntcNotifField 4 }

ntcNotifFldFunctionId            OBJECT-TYPE
    SYNTAX        OBJECT IDENTIFIER
    MAX-ACCESS    accessible-for-notify
    STATUS        current
    DESCRIPTION   "The MIB root node OID of the functional block that
                   originated the notification."
    ::= { ntcNotifField 5 }

ntcNotifFldObjectName            OBJECT-TYPE
    SYNTAX        DisplayString
    MAX-ACCESS    accessible-for-notify
    STATUS        current
    DESCRIPTION   "Name of the managed data object that the notification
                   most relates to."
    ::= { ntcNotifField 6 }

ntcNotifFldObjectId              OBJECT-TYPE
    SYNTAX        OBJECT IDENTIFIER
    MAX-ACCESS    accessible-for-notify
    STATUS        current
    DESCRIPTION   "The managed data object OID that the notification
                   most relates to."
    ::= { ntcNotifField 7 }

ntcNotifFldDescription           OBJECT-TYPE
    SYNTAX        DisplayString
    MAX-ACCESS    accessible-for-notify
    STATUS        current
    DESCRIPTION   "Explanation of the event that the notification was
                   generated for."
    ::= { ntcNotifField 8 }

ntcNotifFldAlarmStatus           OBJECT-TYPE
    SYNTAX        NtcAlarmState
    MAX-ACCESS    accessible-for-notify
    STATUS        current
    DESCRIPTION   "Contains the new value of the alarmstate at the 
	               time the trap is send."
    ::= { ntcNotifField 9 }	
	
-- ntcNotifReportList content

ntcNotifAlReport                 NOTIFICATION-TYPE
    OBJECTS       {
                      ntcNotifFldSeqNbr,
                      ntcNotifFldSeverity,
                      ntcNotifFldDevice,
                      ntcNotifFldFunctionName,
                      ntcNotifFldFunctionId,
                      ntcNotifFldObjectName,
                      ntcNotifFldObjectId,
                      ntcNotifFldDescription,
                      ntcNotifFldAlarmStatus
                  }
    STATUS        current
    DESCRIPTION   "This trap/notification is send each time an alarm in 
	               the device changes state."
    ::= { ntcNotifReportList 1 }


--
--  Module Conformance
--

ntcNotifConfGrpFldV1Standard     OBJECT-GROUP
    OBJECTS       {
                      ntcNotifFldSeqNbr,
                      ntcNotifFldSeverity,
                      ntcNotifFldDevice,
                      ntcNotifFldFunctionName,
                      ntcNotifFldFunctionId,
                      ntcNotifFldObjectName,
                      ntcNotifFldObjectId,
                      ntcNotifFldDescription,
                      ntcNotifFldAlarmStatus
                  }
    STATUS        current
    DESCRIPTION   "Managed objects that constitute version 1 of an event
                   notification with standard capabilities."
    ::= { ntcNotifConfGroup 1 }

ntcNotifConfGrpRepV1Standard     NOTIFICATION-GROUP
    NOTIFICATIONS {
                      ntcNotifAlReport
                  }
    STATUS        current
    DESCRIPTION   "Managed objects that constitute version 1 of an event
                   notification with standard capabilities."
    ::= { ntcNotifConfGroup 2 }

ntcNotifConfCompV1Standard       MODULE-COMPLIANCE
    STATUS        current
    DESCRIPTION   "Compliance statement for Newtec event notification
                   MIB implementations."
    MODULE        -- this module
    MANDATORY-GROUPS
                  {
                      ntcNotifConfGrpFldV1Standard,
                      ntcNotifConfGrpRepV1Standard
                  }
    ::= { ntcNotifConfCompliance 1 }

END

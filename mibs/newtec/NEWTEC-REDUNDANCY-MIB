NEWTEC-REDUNDANCY-MIB DEFINITIONS ::= BEGIN

IMPORTS
    Unsigned32,
    MODULE-IDENTITY,
    OBJECT-IDENTITY,
    OBJECT-TYPE
        FROM SNMPv2-SMI

    MODULE-COMPLIANCE,
    OBJECT-GROUP
        FROM SNMPv2-CONF
    
    NtcEnable
        FROM NEWTEC-TC-MIB

    DisplayString
        FROM SNMPv2-TC

    ntcFunction
        FROM NEWTEC-MAIN-MIB;


--
--  Module Identification
--

ntcRedundancy   MODULE-IDENTITY
    LAST-UPDATED "201801161000Z"
    ORGANIZATION "Newtec Cy"
    CONTACT-INFO
        "Newtec Cy
         Postal: Newtec Cy
                 Laarstraat 5
                 B-9100 Sint-Niklaas
                 Belgium

                Tel: +32 3 780 65 00
                Fax: +32 3 780 65 49
                Web: www.newtec.be
                E-mail: techsupport@newtec.be"
    DESCRIPTION
        "Newtec modular MIB containing definitions for redundancy functionality."

    REVISION  "201801161000Z"
    DESCRIPTION
        "ntcRedunMonitoring and ntcRedunType added"
    REVISION  "201301081200Z"
    DESCRIPTION
        "Release for MDM6000 and NOP1760 R1.0"
    REVISION  "201206281200Z"
    DESCRIPTION
        "Release for M6100 R1.2"
    ::= { ntcFunction  1800 }
    

--
-- Top-Level Structure
--

-- ntcRedundancy content

ntcRedunObjects                  OBJECT-IDENTITY
    STATUS        current
    DESCRIPTION   "Container holding ntcRedunObjects definitions."
    ::= { ntcRedundancy 1 }
    
ntcRedunConformance              OBJECT-IDENTITY
    STATUS        current
    DESCRIPTION   "Conformance requirements."
    ::= { ntcRedundancy 2 }
    
-- ntcRedunConformance content

ntcRedunConfCompliance           OBJECT-IDENTITY
    STATUS        current
    DESCRIPTION   "Device compliance statements."
    ::= { ntcRedunConformance 1 }
    
ntcRedunConfGroup                OBJECT-IDENTITY
    STATUS        current
    DESCRIPTION   "Groups used by device compliance statements."
    ::= { ntcRedunConformance 2 }
    

--
-- Managed Objects
--

ntcRedunEnable                   OBJECT-TYPE
    SYNTAX      NtcEnable
    MAX-ACCESS  read-write
    STATUS      current
    DESCRIPTION
        "Enable or disable Device Redundancy."
    DEFVAL { off }
    ::= { ntcRedunObjects 1 }
    
ntcRedunInitialState             OBJECT-TYPE
    SYNTAX      INTEGER { standby(0), active(1) }
    MAX-ACCESS  read-write
    STATUS      current
    DESCRIPTION
        "Initial Device Redundancy State when Device Redundancy is enabled. In Standby
        state the modulator output will be disabled."
    DEFVAL { standby }
    ::= { ntcRedunObjects 2 }
    
ntcRedunOperationalState         OBJECT-TYPE
    SYNTAX      INTEGER { active(0), standby(1), na(2) }
    MAX-ACCESS  read-only
    STATUS      current
    DESCRIPTION
        "Displays the operational device redundancy state. It is only relevant when
        device redundancy is enabled."
    ::= { ntcRedunObjects 3 }
    
ntcRedunType                     OBJECT-TYPE
    SYNTAX      INTEGER { unit(0), carrier(1) }
    MAX-ACCESS  read-write
    STATUS      current
    DESCRIPTION
        "Defines the type of redundancy to support which can be either for the full
        device (unit) or a partial part of the device (carrier)."
    DEFVAL { unit }
    ::= { ntcRedunObjects 4 }
    
ntcRedunMonitoringTable          OBJECT-TYPE
    SYNTAX      SEQUENCE OF NtcRedunMonitoringEntry
    MAX-ACCESS  not-accessible
    STATUS      current
    DESCRIPTION
        "Monitoring table"
    ::= { ntcRedunObjects 5 }

ntcRedunMonitoringEntry          OBJECT-TYPE
    SYNTAX      NtcRedunMonitoringEntry
    MAX-ACCESS  not-accessible
    STATUS      current
    DESCRIPTION
        "A conceptual row of the ntcRedunMonitoringTable."
    INDEX   { ntcRedunMonitoringName  }
    ::= { ntcRedunMonitoringTable 1 }

NtcRedunMonitoringEntry          ::= SEQUENCE {
    ntcRedunMonitoringName    Unsigned32,
    ntcRedunCarrType          DisplayString,
    ntcRedunCarrName          DisplayString,
    ntcRedunOpState           INTEGER
    }
    
ntcRedunMonitoringName           OBJECT-TYPE
    SYNTAX      Unsigned32
    MAX-ACCESS  not-accessible
    STATUS      current
    DESCRIPTION
        "The index of the row"
    ::= { ntcRedunMonitoringEntry 1 }
    
ntcRedunCarrType                 OBJECT-TYPE
    SYNTAX      DisplayString (SIZE(0..32))
    MAX-ACCESS  read-only
    STATUS      current
    DESCRIPTION
        "This defines the type where the Carrier Id is derived from."
    ::= { ntcRedunMonitoringEntry 2 }
    
ntcRedunCarrName                 OBJECT-TYPE
    SYNTAX      DisplayString (SIZE(0..32))
    MAX-ACCESS  read-only
    STATUS      current
    DESCRIPTION
        "This defines the name where the Carrier Id is derived from."
    ::= { ntcRedunMonitoringEntry 3 }
    
ntcRedunOpState                  OBJECT-TYPE
    SYNTAX      INTEGER { active(0), standby(1), na(2) }
    MAX-ACCESS  read-only
    STATUS      current
    DESCRIPTION
        "Displays the operational device redundancy state. It is only relevant when
        device redundancy is enabled."
    ::= { ntcRedunMonitoringEntry 4 }
    

--
--  Module Conformance
--

ntcRedunConfGrpV1Standard        OBJECT-GROUP
    OBJECTS    {
                   ntcRedunEnable,
                   ntcRedunInitialState,
                   ntcRedunOperationalState,
                   ntcRedunType,
                   ntcRedunCarrType,
                   ntcRedunCarrName,
                   ntcRedunOpState
               }
    STATUS      current
    DESCRIPTION
        "Managed objects that constitute version 1 of a system device with standard capabilities."
    ::= { ntcRedunConfGroup 1}
    
ntcRedunConfCompV1Standard       MODULE-COMPLIANCE
    STATUS      current
    DESCRIPTION
        "Compliance statement for Newtec device MIB implementations."
    MODULE  -- this module
    MANDATORY-GROUPS
                  {
                      ntcRedunConfGrpV1Standard
                  }
    ::= { ntcRedunConfCompliance  1 }
    

END

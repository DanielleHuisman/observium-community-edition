NEWTEC-REFERENCECLOCK-MIB DEFINITIONS ::= BEGIN

IMPORTS
    MODULE-IDENTITY,
    OBJECT-IDENTITY,
    OBJECT-TYPE
        FROM SNMPv2-SMI

    MODULE-COMPLIANCE,
    OBJECT-GROUP
        FROM SNMPv2-CONF
    
    NtcAlarmState
        FROM NEWTEC-TC-MIB

    ntcFunction
        FROM NEWTEC-MAIN-MIB;


--
--  Module Identification
--

ntcReferenceClock   MODULE-IDENTITY
    LAST-UPDATED "201309200800Z"
    ORGANIZATION "Newtec Cy"
    CONTACT-INFO
        "Newtec Cy
         Postal: Newtec Cy
                 Laarstraat 5
                 B-9100 Sint-Niklaas
                 Belgium

                Tel: +32 3 780 65 00
                Fax: +32 3 780 65 49
                Web: www.newtec.be
                E-mail: techsupport@newtec.be"
    DESCRIPTION
        "Newtec modular reference clock MIB containing definitions for reference clock
        functionality."

    REVISION  "201309200800Z"
    DESCRIPTION
        "Lock alarm added"
    REVISION  "201206281200Z"
    DESCRIPTION
        "Release for M6100 R1.2"
    ::= { ntcFunction  300 }
    

--
-- Top-Level Structure
--

-- ntcReferenceClock content

ntcRefClkObjects                 OBJECT-IDENTITY
    STATUS        current
    DESCRIPTION   "Container holding ntcRefClkObjects definitions."
    ::= { ntcReferenceClock 1 }
    
ntcRefClkConformance             OBJECT-IDENTITY
    STATUS        current
    DESCRIPTION   "Conformance requirements."
    ::= { ntcReferenceClock 2 }
    
-- ntcRefClkObjects content

ntcRefClkAlarm                   OBJECT-IDENTITY
    STATUS        current
    DESCRIPTION   "Container holding ntcRefClkAlarm definitions."
    ::= { ntcRefClkObjects 3 }
    
-- ntcRefClkConformance content

ntcRefClkConfCompliance          OBJECT-IDENTITY
    STATUS        current
    DESCRIPTION   "Device compliance statements."
    ::= { ntcRefClkConformance 1 }
    
ntcRefClkConfGroup               OBJECT-IDENTITY
    STATUS        current
    DESCRIPTION   "Groups used by device compliance statements."
    ::= { ntcRefClkConformance 2 }
    

--
-- Managed Objects
--

ntcRefClkRefSelection            OBJECT-TYPE
    SYNTAX      INTEGER { internal(0), external(1) }
    MAX-ACCESS  read-write
    STATUS      current
    DESCRIPTION
        "The network clock for the devices can be derived from an external reference
        clock, or from the internal oscillator."
    DEFVAL { internal }
    ::= { ntcRefClkObjects 1 }
    
ntcRefClkExtRefFrequency         OBJECT-TYPE
    SYNTAX      INTEGER { e1Mhz(0), e2Mhz(1), e5Mhz(3), e10Mhz(4), e20Mhz(5) }
    MAX-ACCESS  read-write
    STATUS      current
    DESCRIPTION
        "Select the frequency of the external reference clock."
    DEFVAL { e10Mhz }
    ::= { ntcRefClkObjects 2 }
    
ntcRefClkAlmRefClockNoSignal     OBJECT-TYPE
    SYNTAX      NtcAlarmState
    MAX-ACCESS  read-only
    STATUS      current
    DESCRIPTION
        "This alarm is raised when no signal is detected on the ReferenceClock input
        connector. This variable indicates the current status of the alarm."
    ::= { ntcRefClkAlarm 1 }
    
ntcRefClkAlmRefClockNoLock       OBJECT-TYPE
    SYNTAX      NtcAlarmState
    MAX-ACCESS  read-only
    STATUS      current
    DESCRIPTION
        "This alarm is raised when the device cannot lock on the reference clock. This
        variable indicates the current status of the alarm."
    ::= { ntcRefClkAlarm 2 }
    
ntcRefClkActiveRef               OBJECT-TYPE
    SYNTAX      INTEGER { internal(0), external(1) }
    MAX-ACCESS  read-only
    STATUS      current
    DESCRIPTION
        "The network clock for the devices can be derived from an external reference
        clock, or from the internal oscillator."
    ::= { ntcRefClkObjects 4 }
    

--
--  Module Conformance
--

ntcRefClkConfGrpV1Standard       OBJECT-GROUP
    OBJECTS    {
                   ntcRefClkRefSelection,
                   ntcRefClkExtRefFrequency,
                   ntcRefClkAlmRefClockNoSignal,
                   ntcRefClkAlmRefClockNoLock,
                   ntcRefClkActiveRef
               }
    STATUS      current
    DESCRIPTION
        "Managed objects that constitute version 1 of a system device with standard capabilities."
    ::= { ntcRefClkConfGroup 1}
    
ntcRefClkConfCompV1Standard      MODULE-COMPLIANCE
    STATUS      current
    DESCRIPTION
        "Compliance statement for Newtec device MIB implementations."
    MODULE  -- this module
    MANDATORY-GROUPS
                  {
                      ntcRefClkConfGrpV1Standard
                  }
    ::= { ntcRefClkConfCompliance  1 }
    

END

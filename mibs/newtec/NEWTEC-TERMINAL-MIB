NEWTEC-TERMINAL-MIB DEFINITIONS ::= BEGIN

IMPORTS
    Unsigned32,
    MODULE-IDENTITY,
    OBJECT-IDENTITY,
    OBJECT-TYPE
        FROM SNMPv2-SMI

    MODULE-COMPLIANCE,
    OBJECT-GROUP
        FROM SNMPv2-CONF
    
    ntcFunction
        FROM NEWTEC-MAIN-MIB;


--
--  Module Identification
--

ntcTerminal   MODULE-IDENTITY
    LAST-UPDATED "201301081200Z"
    ORGANIZATION "Newtec Cy"
    CONTACT-INFO
        "Newtec Cy
         Postal: Newtec Cy
                 Laarstraat 5
                 B-9100 Sint-Niklaas
                 Belgium

                Tel: +32 3 780 65 00
                Fax: +32 3 780 65 49
                Web: www.newtec.be
                E-mail: techsupport@newtec.be"
    DESCRIPTION
        "Newtec modular Traffic Shaper MIB containing definitions for ACM terminal
        information."

    REVISION  "201301081200Z"
    DESCRIPTION
        "Initial release for MDM6000 R1.0"
    ::= { ntcFunction  2900 }
    

--
-- Top-Level Structure
--

-- ntcTerminal content

ntcTermObjects                   OBJECT-IDENTITY
    STATUS        current
    DESCRIPTION   "Container holding ntcTermObjects definitions."
    ::= { ntcTerminal 1 }
    
ntcTermConformance               OBJECT-IDENTITY
    STATUS        current
    DESCRIPTION   "Conformance requirements."
    ::= { ntcTerminal 2 }
    
-- ntcTermConformance content

ntcTermConfCompliance            OBJECT-IDENTITY
    STATUS        current
    DESCRIPTION   "Device compliance statements."
    ::= { ntcTermConformance 1 }
    
ntcTermConfGroup                 OBJECT-IDENTITY
    STATUS        current
    DESCRIPTION   "Groups used by device compliance statements."
    ::= { ntcTermConformance 2 }
    

--
-- Managed Objects
--

ntcTermId                        OBJECT-TYPE
    SYNTAX      Unsigned32 (0..65277)
    MAX-ACCESS  read-write
    STATUS      current
    DESCRIPTION
        "Identification of the terminal"
    DEFVAL { 0 }
    ::= { ntcTermObjects 1 }
    

--
--  Module Conformance
--

ntcTermConfGrpV1Standard         OBJECT-GROUP
    OBJECTS    {
                   ntcTermId
               }
    STATUS      current
    DESCRIPTION
        "Managed objects that constitute version 1 of a system device with standard capabilities."
    ::= { ntcTermConfGroup 1}
    
ntcTermConfCompV1Standard        MODULE-COMPLIANCE
    STATUS      current
    DESCRIPTION
        "Compliance statement for Newtec device MIB implementations."
    MODULE  -- this module
    MANDATORY-GROUPS
                  {
                      ntcTermConfGrpV1Standard
                  }
    ::= { ntcTermConfCompliance  1 }
    

END

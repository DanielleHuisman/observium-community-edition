NEWTEC-TSOVERIPIN-MIB DEFINITIONS ::= BEGIN

IMPORTS
    IpAddress,
    Unsigned32,
    Counter32,
    MODULE-IDENTITY,
    OBJECT-IDENTITY,
    OBJECT-TYPE
        FROM SNMPv2-SMI

    MODULE-COMPLIANCE,
    OBJECT-GROUP
        FROM SNMPv2-CONF
    
    NtcAlarmState,
    NtcEnable,
    NtcNetworkAddress
        FROM NEWTEC-TC-MIB

    DisplayString
        FROM SNMPv2-TC

    ntcFunction
        FROM NEWTEC-MAIN-MIB;


--
--  Module Identification
--

ntcTsOverIpIn   MODULE-IDENTITY
    LAST-UPDATED "201707101200Z"
    ORGANIZATION "Newtec Cy"
    CONTACT-INFO
        "Newtec Cy
         Postal: Newtec Cy
                 Laarstraat 5
                 B-9100 Sint-Niklaas
                 Belgium

                Tel: +32 3 780 65 00
                Fax: +32 3 780 65 49
                Web: www.newtec.be
                E-mail: techsupport@newtec.be"
    DESCRIPTION
        "Newtec modular TSoIP input MIB containing definitions for TS over IP input
        functionality."

    REVISION  "201707101200Z"
    DESCRIPTION
        "Descriptions updated with regex"
    REVISION  "201602020700Z"
    DESCRIPTION
        "AutoPcrDetection, InputRateType, InMonActivePCRPID and PcrPid added"
    REVISION  "201502190900Z"
    DESCRIPTION
        "ntcTsOIpInMonRtpFecDropCount added and descriptions updated"
    REVISION  "201409090900Z"
    DESCRIPTION
        "Descriptions adapted"
    REVISION  "201303271000Z"
    DESCRIPTION
        "Release for M6100 R1.3"
    REVISION  "201206281200Z"
    DESCRIPTION
        "Release for M6100 R1.2"
    ::= { ntcFunction  600 }
    

--
-- Top-Level Structure
--

-- ntcTsOverIpIn content

ntcTsOIpInObjects                OBJECT-IDENTITY
    STATUS        current
    DESCRIPTION   "Container holding ntcTsOIpInObjects definitions."
    ::= { ntcTsOverIpIn 1 }
    
ntcTsOIpInConformance            OBJECT-IDENTITY
    STATUS        current
    DESCRIPTION   "Conformance requirements."
    ::= { ntcTsOverIpIn 2 }
    
-- ntcTsOIpInObjects content

ntcTsOIpInMonitor                OBJECT-IDENTITY
    STATUS        current
    DESCRIPTION   "Container holding ntcTsOIpInMonitor definitions."
    ::= { ntcTsOIpInObjects 11 }
    
ntcTsOIpInAlarm                  OBJECT-IDENTITY
    STATUS        current
    DESCRIPTION   "Container holding ntcTsOIpInAlarm definitions."
    ::= { ntcTsOIpInObjects 12 }
    
-- ntcTsOIpInConformance content

ntcTsOIpInConfCompliance         OBJECT-IDENTITY
    STATUS        current
    DESCRIPTION   "Device compliance statements."
    ::= { ntcTsOIpInConformance 1 }
    
ntcTsOIpInConfGroup              OBJECT-IDENTITY
    STATUS        current
    DESCRIPTION   "Groups used by device compliance statements."
    ::= { ntcTsOIpInConformance 2 }
    

--
-- Managed Objects
--

ntcTsOIpInEnable                 OBJECT-TYPE
    SYNTAX      NtcEnable
    MAX-ACCESS  read-write
    STATUS      current
    DESCRIPTION
        "Enable or disable TS (Transport Stream) over IP reception."
    DEFVAL { off }
    ::= { ntcTsOIpInObjects 1 }
    
ntcTsOIpInInputSelection         OBJECT-TYPE
    SYNTAX      INTEGER { none(1), data1(2), data2(3), data(4), any(5) }
    MAX-ACCESS  read-write
    STATUS      current
    DESCRIPTION
        "Select the input interface for the TS over IP functionality."
    DEFVAL { none }
    ::= { ntcTsOIpInObjects 2 }
    
ntcTsOIpInTsEncapProtocol        OBJECT-TYPE
    SYNTAX      INTEGER { udp(0), rtp(1), rtpfec(2) }
    MAX-ACCESS  read-write
    STATUS      current
    DESCRIPTION
        "Encapsulation protocol used for the received TS over IP functionality (UDP,
        RTP and RTP with FEC)."
    DEFVAL { udp }
    ::= { ntcTsOIpInObjects 3 }
    
ntcTsOIpInIpAddressType          OBJECT-TYPE
    SYNTAX      INTEGER { unicast(0), multicast(1) }
    MAX-ACCESS  read-write
    STATUS      current
    DESCRIPTION
        "Configuration of the IP address type for TS over IP reception. (unicast or
        multicast)"
    DEFVAL { unicast }
    ::= { ntcTsOIpInObjects 4 }
    
ntcTsOIpInMulticastAddress       OBJECT-TYPE
    SYNTAX      IpAddress 
    MAX-ACCESS  read-write
    STATUS      current
    DESCRIPTION
        "Define the multicast IP address used to receive the TS over IP data
        functionality. Regular expression :
        (?-mix:^\d{1,3}\.\d{1,3}\.\d{1,3}\.\d{1,3}$)"
    DEFVAL { 'e0010001'h }
    ::= { ntcTsOIpInObjects 5 }
    
ntcTsOIpInUdpPort                OBJECT-TYPE
    SYNTAX      Unsigned32 (1..65535)
    MAX-ACCESS  read-write
    STATUS      current
    DESCRIPTION
        "Configure the UDP port on which the TS over IP stream is received."
    DEFVAL { 56789 }
    ::= { ntcTsOIpInObjects 6 }
    
ntcTsOIpInTrafficProfile         OBJECT-TYPE
    SYNTAX      INTEGER { vbr(0), cbr(1) }
    MAX-ACCESS  read-write
    STATUS      current
    DESCRIPTION
        "Configure the TS input traffic profile for the TS stream (CBR=constant or
        VBR=variable bitrate)."
    DEFVAL { cbr }
    ::= { ntcTsOIpInObjects 7 }
    
ntcTsOIpInMaxTrafficJitter       OBJECT-TYPE
    SYNTAX      Unsigned32
    UNITS       "ms"
    MAX-ACCESS  read-write
    STATUS      deprecated
    DESCRIPTION
        "The maximum traffic jitter that can be introduced by the IP network, for the
        TS Over IP input traffic. Current devices support a range of 0 to 150 ms."
    DEFVAL { 50 }
    ::= { ntcTsOIpInObjects 8 }
    
ntcTsOIpInMaxBufferDelay         OBJECT-TYPE
    SYNTAX      Unsigned32
    UNITS       "ms"
    MAX-ACCESS  read-write
    STATUS      current
    DESCRIPTION
        "The maximum delay introduced by the device to compensate jitter introduced by
        the IP network. This is only relevant for CBR traffic."
    DEFVAL { 250 }
    ::= { ntcTsOIpInObjects 9 }
    
ntcTsOIpInInputTsBitRate         OBJECT-TYPE
    SYNTAX      Unsigned32
    UNITS       "bps"
    MAX-ACCESS  read-write
    STATUS      current
    DESCRIPTION
        "TS input rate in bps used with a constant bitrate input traffic profile.
        Current devices support a range of 10 to 250000000 bps."
    DEFVAL { 1000000 }
    ::= { ntcTsOIpInObjects 10 }
    
ntcTsOIpInMonResetCounters       OBJECT-TYPE
    SYNTAX      INTEGER { counting(0), reset(1) }
    MAX-ACCESS  read-write
    STATUS      current
    DESCRIPTION
        "Reset the TS over IP traffic and monitor counters."
    DEFVAL { counting }
    ::= { ntcTsOIpInMonitor 1 }
    
ntcTsOIpInMonInputTsBitRate      OBJECT-TYPE
    SYNTAX      Unsigned32
    UNITS       "bps"
    MAX-ACCESS  read-only
    STATUS      current
    DESCRIPTION
        "Displays the measured TS over IP input TS bit rate in bps."
    ::= { ntcTsOIpInMonitor 2 }
    
ntcTsOIpInMonBufferDelay         OBJECT-TYPE
    SYNTAX      Unsigned32
    UNITS       "ms"
    MAX-ACCESS  read-only
    STATUS      current
    DESCRIPTION
        "The delay introduced by the device to compensate the jitter introduced by the
        IP network. This is only relevant for CBR traffic."
    ::= { ntcTsOIpInMonitor 3 }
    
ntcTsOIpInMonMinBufferFilling    OBJECT-TYPE
    SYNTAX      Unsigned32
    UNITS       "ms"
    MAX-ACCESS  read-only
    STATUS      current
    DESCRIPTION
        "The measured minimum buffer delay in the buffer which compensate the jitter of
        the IP network. This is only relevant for CBR traffic."
    ::= { ntcTsOIpInMonitor 4 }
    
ntcTsOIpInMonMaxBufferFilling    OBJECT-TYPE
    SYNTAX      Unsigned32
    UNITS       "ms"
    MAX-ACCESS  read-only
    STATUS      current
    DESCRIPTION
        "The measured maximum buffer delay in the buffer which compensate the jitter of
        the IP network. This is only relevant for CBR traffic."
    ::= { ntcTsOIpInMonitor 5 }
    
ntcTsOIpInMonSourceInfo          OBJECT-TYPE
    SYNTAX      DisplayString (SIZE(0..32))
    MAX-ACCESS  read-only
    STATUS      current
    DESCRIPTION
        "Displays the IP address (and UDP port) of the source that is generating the TS
        over IP traffic."
    ::= { ntcTsOIpInMonitor 6 }
    
ntcTsOIpInMonRtpFecScheme        OBJECT-TYPE
    SYNTAX      DisplayString (SIZE(0..32))
    MAX-ACCESS  read-only
    STATUS      current
    DESCRIPTION
        "Displays the type of Rtp FEC Scheme currently used (if any)."
    ::= { ntcTsOIpInMonitor 7 }
    
ntcTsOIpInMonTsInCount           OBJECT-TYPE
    SYNTAX      Counter32
    UNITS       "packets"
    MAX-ACCESS  read-only
    STATUS      current
    DESCRIPTION
        "Displays the Number of received TS packets in UDP mode."
    ::= { ntcTsOIpInMonitor 8 }
    
ntcTsOIpInMonRtpInCount          OBJECT-TYPE
    SYNTAX      Counter32
    UNITS       "packets"
    MAX-ACCESS  read-only
    STATUS      current
    DESCRIPTION
        "Displays the number of received RTP packets. (only applicable when RTP is
        used)"
    ::= { ntcTsOIpInMonitor 9 }
    
ntcTsOIpInMonRtpColumnFecInCount OBJECT-TYPE
    SYNTAX      Counter32
    UNITS       "packets"
    MAX-ACCESS  read-only
    STATUS      current
    DESCRIPTION
        "Displays the number of received (input) RTP column FEC packets."
    ::= { ntcTsOIpInMonitor 10 }
    
ntcTsOIpInMonRtpRowFecInCount    OBJECT-TYPE
    SYNTAX      Counter32
    UNITS       "packets"
    MAX-ACCESS  read-only
    STATUS      current
    DESCRIPTION
        "Displays the number of received RTP row FEC packets. (Only applicable when RTP
        with FEC is used.)"
    ::= { ntcTsOIpInMonitor 11 }
    
ntcTsOIpInMonTsOutCount          OBJECT-TYPE
    SYNTAX      Counter32
    UNITS       "packets"
    MAX-ACCESS  read-only
    STATUS      current
    DESCRIPTION
        "Displays the number of valid TS packets leaving the TS over IP input
        processing."
    ::= { ntcTsOIpInMonitor 12 }
    
ntcTsOIpInMonTsDropCount         OBJECT-TYPE
    SYNTAX      Counter32
    UNITS       "packets"
    MAX-ACCESS  read-only
    STATUS      current
    DESCRIPTION
        "Number of dropped TS packets. (When RTP is used the number of dropped TS
        packets in the RTP frame is counted.)"
    ::= { ntcTsOIpInMonitor 13 }
    
ntcTsOIpInMonTsOverflowCount     OBJECT-TYPE
    SYNTAX      Counter32
    UNITS       "packets"
    MAX-ACCESS  read-only
    STATUS      current
    DESCRIPTION
        "Displays the number of TS packets that are dropped because of an overflow
        situation."
    ::= { ntcTsOIpInMonitor 14 }
    
ntcTsOIpInMonRtpDropCount        OBJECT-TYPE
    SYNTAX      Counter32
    UNITS       "packets"
    MAX-ACCESS  read-only
    STATUS      current
    DESCRIPTION
        "Displays the number of dropped RTP packets. (This is only applicable when RTP
        is used.)"
    ::= { ntcTsOIpInMonitor 15 }
    
ntcTsOIpInMonRtpRepairCount      OBJECT-TYPE
    SYNTAX      Counter32
    UNITS       "packets"
    MAX-ACCESS  read-only
    STATUS      current
    DESCRIPTION
        "Displays the number of repaired RTP packets by using the received FEC
        information. (This is only applicable for RTP with FEC)"
    ::= { ntcTsOIpInMonitor 16 }
    
ntcTsOIpInMonRtpFecDropCount     OBJECT-TYPE
    SYNTAX      Counter32
    UNITS       "packets"
    MAX-ACCESS  read-only
    STATUS      current
    DESCRIPTION
        "Displays the number of dropped uncorrectable packets. (This is only applicable
        when RTP-FEC is used.)"
    ::= { ntcTsOIpInMonitor 17 }
    
ntcTsOIpInMonActivePCRPID        OBJECT-TYPE
    SYNTAX      Unsigned32 (0..8190)
    MAX-ACCESS  read-only
    STATUS      current
    DESCRIPTION
        "Active PCR PID."
    ::= { ntcTsOIpInMonitor 18 }
    
ntcTsOIpInAlmGeneralTsOverIpIn   OBJECT-TYPE
    SYNTAX      NtcAlarmState
    MAX-ACCESS  read-only
    STATUS      current
    DESCRIPTION
        "This alarm is raised when there is a general TS over IP Input alarm. This
        variable indicates the current status of the alarm."
    ::= { ntcTsOIpInAlarm 1 }
    
ntcTsOIpInAlmNoInputData         OBJECT-TYPE
    SYNTAX      NtcAlarmState
    MAX-ACCESS  read-only
    STATUS      current
    DESCRIPTION
        "This alarm is raised when no input data is received for the TS over IP
        functionality. This variable indicates the current status of the alarm."
    ::= { ntcTsOIpInAlarm 2 }
    
ntcTsOIpInAlmBufferOverflow      OBJECT-TYPE
    SYNTAX      NtcAlarmState
    MAX-ACCESS  read-only
    STATUS      current
    DESCRIPTION
        "This alarm is raised when the input data buffer of TS over IP is full. This
        variable indicates the current status of the alarm."
    ::= { ntcTsOIpInAlarm 3 }
    
ntcTsOIpInAlmBufferUnflow        OBJECT-TYPE
    SYNTAX      NtcAlarmState
    MAX-ACCESS  read-only
    STATUS      current
    DESCRIPTION
        "This alarm is raised when the input data buffer is below the minimum value.
        This variable indicates the current status of the alarm."
    ::= { ntcTsOIpInAlarm 4 }
    
ntcTsOIpInAlmRtpNoSync           OBJECT-TYPE
    SYNTAX      NtcAlarmState
    MAX-ACCESS  read-only
    STATUS      current
    DESCRIPTION
        "This alarm is raised when no valid RTP input data is received. This variable
        indicates the current status of the alarm."
    ::= { ntcTsOIpInAlarm 5 }
    
ntcTsOIpInAlmInvalidTsBitRate    OBJECT-TYPE
    SYNTAX      NtcAlarmState
    MAX-ACCESS  read-only
    STATUS      current
    DESCRIPTION
        "This alarm is raised when the measured input Ts Bitrate is higher/lower then
        the configured value. (only relevant for a CBR Traffic profile) This variable
        indicates the current status of the alarm."
    ::= { ntcTsOIpInAlarm 6 }
    
ntcTsOIpInMulticastSourceA       OBJECT-TYPE
    SYNTAX      NtcNetworkAddress
    MAX-ACCESS  read-write
    STATUS      current
    DESCRIPTION
        "Multicast source Address. Regular expression :
        (?-mix:^\d{1,3}\.\d{1,3}\.\d{1,3}\.\d{1,3}$)"
    DEFVAL { "0.0.0.0" }
    ::= { ntcTsOIpInObjects 13 }
    
ntcTsOIpInMulticastSourceB       OBJECT-TYPE
    SYNTAX      NtcNetworkAddress
    MAX-ACCESS  read-write
    STATUS      current
    DESCRIPTION
        "Multicast source Address. Regular expression :
        (?-mix:^\d{1,3}\.\d{1,3}\.\d{1,3}\.\d{1,3}$)"
    DEFVAL { "0.0.0.0" }
    ::= { ntcTsOIpInObjects 14 }
    
ntcTsOIpInInputRateType          OBJECT-TYPE
    SYNTAX      INTEGER { userdefined(0), pcr(1) }
    MAX-ACCESS  read-write
    STATUS      current
    DESCRIPTION
        "When the operator selects 'User Defined', the actual input rate and the
        control loop type needs to be specified further. In the other case, PCR PID
        and control loop type is used."
    DEFVAL { pcr }
    ::= { ntcTsOIpInObjects 15 }
    
ntcTsOIpInAutoPcrDetection       OBJECT-TYPE
    SYNTAX      NtcEnable
    MAX-ACCESS  read-write
    STATUS      current
    DESCRIPTION
        "Enable or disable Auto PCR Detection."
    DEFVAL { on }
    ::= { ntcTsOIpInObjects 16 }
    
ntcTsOIpInPcrPid                 OBJECT-TYPE
    SYNTAX      Unsigned32 (0..8191)
    MAX-ACCESS  read-write
    STATUS      current
    DESCRIPTION
        "PCR PID."
    DEFVAL { 8191 }
    ::= { ntcTsOIpInObjects 17 }
    

--
--  Module Conformance
--

ntcTsOIpInConfGrpV1Standard      OBJECT-GROUP
    OBJECTS    {
                   ntcTsOIpInEnable,
                   ntcTsOIpInInputSelection,
                   ntcTsOIpInTsEncapProtocol,
                   ntcTsOIpInIpAddressType,
                   ntcTsOIpInMulticastAddress,
                   ntcTsOIpInUdpPort,
                   ntcTsOIpInTrafficProfile,
                   ntcTsOIpInMaxBufferDelay,
                   ntcTsOIpInInputTsBitRate,
                   ntcTsOIpInMonResetCounters,
                   ntcTsOIpInMonInputTsBitRate,
                   ntcTsOIpInMonBufferDelay,
                   ntcTsOIpInMonMinBufferFilling,
                   ntcTsOIpInMonMaxBufferFilling,
                   ntcTsOIpInMonSourceInfo,
                   ntcTsOIpInMonRtpFecScheme,
                   ntcTsOIpInMonTsInCount,
                   ntcTsOIpInMonRtpInCount,
                   ntcTsOIpInMonRtpColumnFecInCount,
                   ntcTsOIpInMonRtpRowFecInCount,
                   ntcTsOIpInMonTsOutCount,
                   ntcTsOIpInMonTsDropCount,
                   ntcTsOIpInMonTsOverflowCount,
                   ntcTsOIpInMonRtpDropCount,
                   ntcTsOIpInMonRtpRepairCount,
                   ntcTsOIpInMonRtpFecDropCount,
                   ntcTsOIpInMonActivePCRPID,
                   ntcTsOIpInAlmGeneralTsOverIpIn,
                   ntcTsOIpInAlmNoInputData,
                   ntcTsOIpInAlmBufferOverflow,
                   ntcTsOIpInAlmBufferUnflow,
                   ntcTsOIpInAlmRtpNoSync,
                   ntcTsOIpInAlmInvalidTsBitRate,
                   ntcTsOIpInMulticastSourceA,
                   ntcTsOIpInMulticastSourceB,
                   ntcTsOIpInInputRateType,
                   ntcTsOIpInAutoPcrDetection,
                   ntcTsOIpInPcrPid
               }
    STATUS      current
    DESCRIPTION
        "Managed objects that constitute version 1 of a system device with standard capabilities."
    ::= { ntcTsOIpInConfGroup 1}
    
ntcTsOIpInConfGrpObsolete        OBJECT-GROUP
    OBJECTS    {
                   ntcTsOIpInMaxTrafficJitter
               }
    STATUS      obsolete
    DESCRIPTION
        "Managed objects which are deprecated or obsolete"
    ::= { ntcTsOIpInConfGroup 2}
    
ntcTsOIpInConfCompV1Standard     MODULE-COMPLIANCE
    STATUS      current
    DESCRIPTION
        "Compliance statement for Newtec device MIB implementations."
    MODULE  -- this module
    MANDATORY-GROUPS
                  {
                      ntcTsOIpInConfGrpV1Standard
                  }
    ::= { ntcTsOIpInConfCompliance  1 }
    

END

NEWTEC-TSOVERIPOUT-MIB DEFINITIONS ::= BEGIN

IMPORTS
    Unsigned32,
    Counter32,
    MODULE-IDENTITY,
    OBJECT-IDENTITY,
    OBJECT-TYPE
        FROM SNMPv2-SMI

    MODULE-COMPLIANCE,
    OBJECT-GROUP
        FROM SNMPv2-CONF
    
    NtcAlarmState,
    NtcEnable,
    NtcNetworkAddress
        FROM NEWTEC-TC-MIB

    ntcFunction
        FROM NEWTEC-MAIN-MIB;


--
--  Module Identification
--

ntcTsOverIpOut   MODULE-IDENTITY
    LAST-UPDATED "201707101200Z"
    ORGANIZATION "Newtec Cy"
    CONTACT-INFO
        "Newtec Cy
         Postal: Newtec Cy
                 Laarstraat 5
                 B-9100 Sint-Niklaas
                 Belgium

                Tel: +32 3 780 65 00
                Fax: +32 3 780 65 49
                Web: www.newtec.be
                E-mail: techsupport@newtec.be"
    DESCRIPTION
        "Newtec modular TSoverIP output MIB containing definitions for singlestream TS
        over IP output functionality."

    REVISION  "201707101200Z"
    DESCRIPTION
        "Descriptions updated with regex"
    REVISION  "201612051200Z"
    DESCRIPTION
        "ntcTsOIpOutFlushScheduleTime added"
    REVISION  "201602020700Z"
    DESCRIPTION
        "ntcTsOIpOutRtpFecColumns and ntcTsOIpOutRtpFecRows added"
    REVISION  "201409090900Z"
    DESCRIPTION
        "Initial release for M6100-2.5"
    ::= { ntcFunction  8400 }
    

--
-- Top-Level Structure
--

-- ntcTsOverIpOut content

ntcTsOIpOutObjects               OBJECT-IDENTITY
    STATUS        current
    DESCRIPTION   "Container holding ntcTsOIpOutObjects definitions."
    ::= { ntcTsOverIpOut 1 }
    
ntcTsOIpOutConformance           OBJECT-IDENTITY
    STATUS        current
    DESCRIPTION   "Conformance requirements."
    ::= { ntcTsOverIpOut 2 }
    
-- ntcTsOIpOutObjects content

ntcTsOIpOutConfiguration         OBJECT-IDENTITY
    STATUS        current
    DESCRIPTION   "Container holding ntcTsOIpOutConfiguration definitions."
    ::= { ntcTsOIpOutObjects 1 }
    
ntcTsOIpOutMonitoring            OBJECT-IDENTITY
    STATUS        current
    DESCRIPTION   "Container holding ntcTsOIpOutMonitoring definitions."
    ::= { ntcTsOIpOutObjects 2 }
    
ntcTsOIpOutAlarms                OBJECT-IDENTITY
    STATUS        current
    DESCRIPTION   "Container holding ntcTsOIpOutAlarms definitions."
    ::= { ntcTsOIpOutObjects 3 }
    
-- ntcTsOIpOutConformance content

ntcTsOIpOutConfCompliance        OBJECT-IDENTITY
    STATUS        current
    DESCRIPTION   "Device compliance statements."
    ::= { ntcTsOIpOutConformance 1 }
    
ntcTsOIpOutConfGroup             OBJECT-IDENTITY
    STATUS        current
    DESCRIPTION   "Groups used by device compliance statements."
    ::= { ntcTsOIpOutConformance 2 }
    

--
-- Managed Objects
--

ntcTsOIpOutEnable                OBJECT-TYPE
    SYNTAX      NtcEnable
    MAX-ACCESS  read-write
    STATUS      current
    DESCRIPTION
        "Enable or disable endpoint Ts over Ip output."
    DEFVAL { off }
    ::= { ntcTsOIpOutConfiguration 1 }
    
ntcTsOIpOutTsEncapProtocol       OBJECT-TYPE
    SYNTAX      INTEGER { udp(0), rtp(1), rtpfeccolsonly(2), rtpfeccolsandrows(3) }
    MAX-ACCESS  read-write
    STATUS      current
    DESCRIPTION
        "Encapsulation protocol used for the output TS over IP functionality (UDP or
        RTP)."
    DEFVAL { udp }
    ::= { ntcTsOIpOutConfiguration 2 }
    
ntcTsOIpOutDestUdpPort           OBJECT-TYPE
    SYNTAX      Unsigned32 (1..65535)
    MAX-ACCESS  read-write
    STATUS      current
    DESCRIPTION
        "Configuration of the UDP port on which the TS over IP is sent"
    ::= { ntcTsOIpOutConfiguration 3 }
    
ntcTsOIpOutDestIpAddress         OBJECT-TYPE
    SYNTAX      NtcNetworkAddress
    MAX-ACCESS  read-write
    STATUS      current
    DESCRIPTION
        "The destination IP Address Regular expression :
        (?-mix:^\d{1,3}\.\d{1,3}\.\d{1,3}\.\d{1,3}$)"
    DEFVAL { "10.0.0.1" }
    ::= { ntcTsOIpOutConfiguration 4 }
    
ntcTsOIpOutTtl                   OBJECT-TYPE
    SYNTAX      Unsigned32 (1..255)
    MAX-ACCESS  read-write
    STATUS      current
    DESCRIPTION
        "Multicast TTL to be set in the transmitted IP multicast packets"
    DEFVAL { 8 }
    ::= { ntcTsOIpOutConfiguration 5 }
    
ntcTsOIpOutTsPacketsInFrame      OBJECT-TYPE
    SYNTAX      Unsigned32 (1..7)
    UNITS       "packets"
    MAX-ACCESS  read-write
    STATUS      current
    DESCRIPTION
        "Number of TS packets in an UDP frame"
    DEFVAL { 7 }
    ::= { ntcTsOIpOutConfiguration 6 }
    
ntcTsOIpOutRtpFecColumns         OBJECT-TYPE
    SYNTAX      Unsigned32 (1..20)
    MAX-ACCESS  read-write
    STATUS      current
    DESCRIPTION
        "Select the RTP FEC Columns (L) to use. This value will also put a limitation
        on the value of RTP FEC Rows (D), L*D < 100 ."
    DEFVAL { 10 }
    ::= { ntcTsOIpOutConfiguration 7 }
    
ntcTsOIpOutRtpFecRows            OBJECT-TYPE
    SYNTAX      Unsigned32 (4..20)
    MAX-ACCESS  read-write
    STATUS      current
    DESCRIPTION
        "Select the RTP FEC Rows (D) to use. This value is limitated by the value of
        RTP FEC Columns (L), L*D <= 100 ."
    DEFVAL { 10 }
    ::= { ntcTsOIpOutConfiguration 8 }
    
ntcTsOIpOutFlushScheduleTime     OBJECT-TYPE
    SYNTAX      Unsigned32 (500..5000)
    UNITS       "us"
    MAX-ACCESS  read-write
    STATUS      current
    DESCRIPTION
        "Timeframe in which packet buffers are being flushed."
    DEFVAL { 4000 }
    ::= { ntcTsOIpOutConfiguration 9 }
    
ntcTsOIpOutCounterReset          OBJECT-TYPE
    SYNTAX      INTEGER { counting(0), reset(1) }
    MAX-ACCESS  read-write
    STATUS      current
    DESCRIPTION
        "Reset the TS over IP out traffic and monitor counters."
    DEFVAL { counting }
    ::= { ntcTsOIpOutMonitoring 1 }
    
ntcTsOIpOutBitrate               OBJECT-TYPE
    SYNTAX      Unsigned32
    UNITS       "bps"
    MAX-ACCESS  read-only
    STATUS      current
    DESCRIPTION
        "TS over IP output bit rate in bps."
    ::= { ntcTsOIpOutMonitoring 2 }
    
ntcTsOIpOutDropCount             OBJECT-TYPE
    SYNTAX      Counter32
    UNITS       "packets"
    MAX-ACCESS  read-only
    STATUS      current
    DESCRIPTION
        "Number of dropped TS packets."
    ::= { ntcTsOIpOutMonitoring 3 }
    
ntcTsOIpOutOverflowCount         OBJECT-TYPE
    SYNTAX      Counter32
    UNITS       "packets"
    MAX-ACCESS  read-only
    STATUS      current
    DESCRIPTION
        "Displays the number of TS packets that are dropped because of an overflow
        situation."
    ::= { ntcTsOIpOutMonitoring 4 }
    
ntcTsOIpOutAlNoOutput            OBJECT-TYPE
    SYNTAX      NtcAlarmState
    MAX-ACCESS  read-only
    STATUS      current
    DESCRIPTION
        "This alarm is raised when there is no output. This variable indicates the
        current status of the alarm."
    ::= { ntcTsOIpOutAlarms 1 }
    
ntcTsOIpOutAlOutputOverflow      OBJECT-TYPE
    SYNTAX      NtcAlarmState
    MAX-ACCESS  read-only
    STATUS      current
    DESCRIPTION
        "This alarm is raised when the bitrate send out is higher than the max possible
        for the given interface. This variable indicates the current status of the
        alarm."
    ::= { ntcTsOIpOutAlarms 2 }
    

--
--  Module Conformance
--

ntcTsOIpOutConfGrpV1Standard     OBJECT-GROUP
    OBJECTS    {
                   ntcTsOIpOutEnable,
                   ntcTsOIpOutTsEncapProtocol,
                   ntcTsOIpOutDestUdpPort,
                   ntcTsOIpOutDestIpAddress,
                   ntcTsOIpOutTtl,
                   ntcTsOIpOutTsPacketsInFrame,
                   ntcTsOIpOutRtpFecColumns,
                   ntcTsOIpOutRtpFecRows,
                   ntcTsOIpOutFlushScheduleTime,
                   ntcTsOIpOutCounterReset,
                   ntcTsOIpOutBitrate,
                   ntcTsOIpOutDropCount,
                   ntcTsOIpOutOverflowCount,
                   ntcTsOIpOutAlNoOutput,
                   ntcTsOIpOutAlOutputOverflow
               }
    STATUS      current
    DESCRIPTION
        "Managed objects that constitute version 1 of a system device with standard capabilities."
    ::= { ntcTsOIpOutConfGroup 1}
    
ntcTsOIpOutConfCompV1Standard    MODULE-COMPLIANCE
    STATUS      current
    DESCRIPTION
        "Compliance statement for Newtec device MIB implementations."
    MODULE  -- this module
    MANDATORY-GROUPS
                  {
                      ntcTsOIpOutConfGrpV1Standard
                  }
    ::= { ntcTsOIpOutConfCompliance  1 }
    

END

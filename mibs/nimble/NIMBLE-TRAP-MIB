NIMBLE-TRAP-MIB DEFINITIONS ::= BEGIN

IMPORTS
    MODULE-IDENTITY, OBJECT-TYPE, NOTIFICATION-TYPE
        FROM SNMPv2-SMI
    DisplayString
        FROM SNMPv2-TC
    nimble
        FROM NIMBLE-MIB;

nimble-traps MODULE-IDENTITY
    LAST-UPDATED    "201406130000Z"
    ORGANIZATION    "Nimble Storage, Inc."
    CONTACT-INFO
            "Nimble Storage

            support@nimblestorage.com"
    DESCRIPTION
        "Alert SMI Information for Nimble"

    REVISION    "201406130000Z"
    DESCRIPTION "Nimble Storage 2.2.0.0 Trap MIB"
    REVISION    "201405090000Z"
    DESCRIPTION "Nimble Storage 2.0.8.0 Trap MIB"
    REVISION    "201207120000Z"
    DESCRIPTION "Nimble Storage 1.4.0.0 Trap MIB"
    REVISION    "201206120000Z"
    DESCRIPTION "Initial revision"
    ::= { nimble 2 }

--
-- Nimble traps (which are actually SNMP Notifications)
--

trapObjects OBJECT IDENTIFIER ::= { nimble-traps 1 }

trapvariables OBJECT IDENTIFIER ::= { trapObjects 1 }

trapMsg OBJECT-TYPE
    SYNTAX  DisplayString (SIZE(0..255))
    MAX-ACCESS  read-only
    STATUS      current
    DESCRIPTION
    "Message string. This is the full text of the alert message."
::= { trapvariables 1 }

trapSeverity OBJECT-TYPE
    SYNTAX  DisplayString
    MAX-ACCESS  read-only
    STATUS      current
    DESCRIPTION
    "The severity level of the trap (informational, notice, warning, error, critical)."
::= { trapvariables 2 }

trapOriginatorName OBJECT-TYPE
    SYNTAX  DisplayString
    MAX-ACCESS  read-only
    STATUS      current
    DESCRIPTION
    "The array name that originated the trap."
::= { trapvariables 3 }

trapOriginatorSerialNumber OBJECT-TYPE
    SYNTAX  DisplayString
    MAX-ACCESS  read-only
    STATUS      current
    DESCRIPTION
    "The serial number of the array that originated the trap."
::= { trapvariables 4 }

trapOriginatorGroupName OBJECT-TYPE
    SYNTAX  DisplayString
    MAX-ACCESS  read-only
    STATUS      current
    DESCRIPTION
    "The name of the group that originated the trap."
::= { trapvariables 5 }

trapOriginatorGroupID OBJECT-TYPE
    SYNTAX  DisplayString
    MAX-ACCESS  read-only
    STATUS      current
    DESCRIPTION
    "The ID of the group that originated the trap."
::= { trapvariables 6 }

trapTarget OBJECT-TYPE
    SYNTAX  DisplayString
    MAX-ACCESS  read-only
    STATUS      current
    DESCRIPTION
    "The object for which this trap was generated."
::= { trapvariables 7 }

trapTargetType OBJECT-TYPE
    SYNTAX  DisplayString
    MAX-ACCESS  read-only
    STATUS      current
    DESCRIPTION
    "The type of object for which this trap was generated."
::= { trapvariables 8 }


traps OBJECT IDENTIFIER ::= { trapObjects 2 }


nimbleDsdRedEntry0101Deprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Low writable space"
::= { traps 101 }

nimbleDsdSpaceRedExit NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Writable space reclaimed"
::= { traps 102 }

nimbleDsdSpaceCrit0103Deprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Critically low writable space"
::= { traps 103 }

nimbleDsdSpaceUtilizationHigh NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "High system utilization"
::= { traps 104 }

nimbleDsdSpaceUtilizationOk NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "System utilization OK"
::= { traps 105 }

nimbleDsdSpaceUtilizationCrit NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Critically high system utilization"
::= { traps 106 }

nimbleDsdSpaceRedEntry0107Deprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Critically low writable space"
::= { traps 107 }

nimbleDsdSpaceCrit0110Deprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Critically low writable space"
::= { traps 110 }

nimbleDsdSpaceRedEntry NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Critically low writable space"
::= { traps 111 }

nimbleDsdSpaceCrit NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Critically low writable space"
::= { traps 112 }

nimbleCtrlrException NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Unhandled controller exception"
::= { traps 2001 }

nimbleCtrlrTakeover NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Controller takeover occurred"
::= { traps 2002 }

nimbleCtrlrStandbyAvail NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Standby controller available"
::= { traps 2003 }

nimbleCtrlrStandbyUnavail NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Standby controller not available"
::= { traps 2004 }

nimbleCtrlrExcessiveRestarts NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Excessive controller restarts detected"
::= { traps 2005 }

nimbleServiceReboot NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Restarting controller to recover service"
::= { traps 2006 }

nimbleUserReboot NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Rebooting controller on user request"
::= { traps 2007 }

nimbleUserRebootFailed NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to reboot controller per user request"
::= { traps 2008 }

nimbleUserHalt NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Halting controller on user request"
::= { traps 2009 }

nimbleUserHaltFailed NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to halt controller per user request"
::= { traps 2010 }

nimbleCtrlrStandbyUnavailInfo NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Standby controller not available"
::= { traps 2011 }

nimbleCtrlrStandbyUnavailWarn NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Standby controller not available for an extended period"
::= { traps 2012 }

nimbleCtrlrExceptionWarn NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Unhandled controller exception"
::= { traps 2013 }

nimbleCtrlrExceptionCrit NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Unhandled controller exception"
::= { traps 2014 }

nimbleCtrlrStandbyUnavailWarnTimeDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Standby controller not available for an extended period"
::= { traps 2015 }

nimbleCtrlrStandbyUnavailWarnTime NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Standby controller not available for an extended period"
::= { traps 2016 }

nimbleCtrlrTakeoverWarn NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Controller takeover occurred"
::= { traps 2017 }

nimbleCtrlrFailoverDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Controller failover occurred"
::= { traps 2018 }

nimbleCtrlrFailover NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Controller failover occurred"
::= { traps 2019 }

nimbleServiceStarted NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Service started"
::= { traps 2101 }

nimbleServiceDeadRestart NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Service stopped unexpectedly"
::= { traps 2102 }

nimbleServiceDeadNoRestart NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Service stopped unexpectedly"
::= { traps 2103 }

nimbleServiceCreateTunnel NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Created secure tunnel to Nimble Storage Support"
::= { traps 2104 }

nimbleServiceTerminateTunnel NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Tunnel to Nimble Storage Support has been terminated"
::= { traps 2105 }

nimbleServiceEssentialStoppedDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Service stopped unexpectedly"
::= { traps 2106 }

nimbleServiceEssentialStopped NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Service stopped unexpectedly"
::= { traps 2107 }

nimbleServiceEmailAlertFailedDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Failed to send alert e-mail"
::= { traps 2108 }

nimbleServiceEmailAlertFailed NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to send alert e-mail"
::= { traps 2109 }

nimbleTestDbg NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Test alert"
::= { traps 5000 }

nimbleTestInfo NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Test alert"
::= { traps 5001 }

nimbleTestErr NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Test alert"
::= { traps 5002 }

nimbleTestNot NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Test alert"
::= { traps 5003 }

nimbleTestNoteDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Test alert"
::= { traps 5004 }

nimbleTestWarn NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Test alert"
::= { traps 5005 }

nimbleTestCrit NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Test alert"
::= { traps 5006 }

nimbleTestNote NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Test alert"
::= { traps 5007 }

nimbleUpdateUnpackFail NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Unpacking update package failed"
::= { traps 6000 }

nimbleUpdateStartedDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Software update started"
::= { traps 6001 }

nimbleUpdateRevert NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Reverting software to previous version"
::= { traps 6002 }

nimbleUpdateSuccessDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Successfully updated software"
::= { traps 6003 }

nimbleUpdateRollback NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Rolling back software"
::= { traps 6004 }

nimbleUpdatePrecheckFail NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Update package pre-check failed"
::= { traps 6005 }

nimbleUpdateFailMsg NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Software update failed"
::= { traps 6007 }

nimbleUpdateUnpackStarted NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Unpacking update package"
::= { traps 6008 }

nimbleUpdateUnpackDone NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Unpacked update package"
::= { traps 6009 }

nimbleUpdateSwitchRoot NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Software update reboot"
::= { traps 6010 }

nimbleUpdateDownloadFailed NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to download software update package"
::= { traps 6011 }

nimbleUpdateFailTmpFsFull NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Software update failed. /tmp is full"
::= { traps 6012 }

nimbleUpdateFailScratchFsFull NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Software update failed. scratch space is full"
::= { traps 6013 }

nimbleUpdateFailVarFsFull NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Software update failed. /var is full"
::= { traps 6014 }

nimbleUpdateFailConfigFsFull NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Software update failed. Configuration space is full"
::= { traps 6015 }

nimbleUpdateFailUsbFsFull NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Software update failed. Recovery OS space is full"
::= { traps 6016 }

nimbleUpdatePkgNotFound NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Software update package was not found"
::= { traps 6017 }

nimbleUpdatePkgWrongSig NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Software update package has wrong signature"
::= { traps 6018 }

nimbleUpdatePkgWrongCksum NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Software update package has wrong checksum"
::= { traps 6019 }

nimbleUpdateNetDegradeDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Software update precheck failed. Network connectivity will degrade after software update"
::= { traps 6020 }

nimbleUpdateDisallowSoloDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Software update failed. Update cannot be applied while services cannot be failed over to other controller"
::= { traps 6021 }

nimbleUpdateDisallowSolo NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Software update cannot be applied."
::= { traps 6022 }

nimbleUpdateNetDegrade NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Software update precheck failed. Network connectivity will degrade after software update"
::= { traps 6023 }

nimbleUpdateRaidDegrade NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Software update precheck failed. RAID assembly failed on standby controller and prevents software update to proceed"
::= { traps 6024 }

nimbleUpdateStarted NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Software update started"
::= { traps 6025 }

nimbleUpdateSuccess NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Successfully updated software"
::= { traps 6026 }

nimbleUpdateArrayUnreachable NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to contact a member array during software update"
::= { traps 6501 }

nimbleUpdateArrayFailed NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to update software on a member array"
::= { traps 6502 }

nimbleUpdateArrayTimedOut NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Software update on a member array timed out"
::= { traps 6503 }

nimbleArrayUnreachableDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "A member array became unreachable"
::= { traps 10010 }

nimbleArrayReachableDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "A member array became reachable"
::= { traps 10011 }

nimbleArrayUnreachable NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "A member array is unreachable"
::= { traps 10012 }

nimbleArrayReachable NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "A member array is reachable"
::= { traps 10013 }

nimbleUserClearedSysCache NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Cache cleared by user"
::= { traps 10101 }

nimbleVolSpcCurWarningUp NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume space usage over warning limit"
::= { traps 10200 }

nimbleVolSpcCurWarningDown NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume space usage below warning limit"
::= { traps 10201 }

nimbleVolSpcCurQuotaUp NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume space usage over quota"
::= { traps 10202 }

nimbleVolSpcCurQuotaDown NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume space usage below quota"
::= { traps 10203 }

nimbleVolSpcSnapWarningUp NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume snapshot space usage over warning limit"
::= { traps 10204 }

nimbleVolSpcSnapWarningDown NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume snapshot space usage below warning limit"
::= { traps 10205 }

nimbleVolSpcSnapQuotaUp NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume snapshot space usage over quota"
::= { traps 10206 }

nimbleVolSpcSnapQuotaDown NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume snapshot space usage below quota"
::= { traps 10207 }

nimbleGmVolSpcCurCritUp NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume space usage approaching quota"
::= { traps 10208 }

nimbleGmVolSpcCurCritDown NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume space usage below critical limit"
::= { traps 10209 }

nimbleGmSnapSpcCurCritUp NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume snapshot space usage approaching quota"
::= { traps 10210 }

nimbleGmSnapSpcCurCritDown NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume snapshot space usage below critical limit"
::= { traps 10211 }

nimbleGmVolSpcCurQuotaOffline NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume being taken offline because it is above its quota"
::= { traps 10212 }

nimbleGmVolSpcCurQuotaSet NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "The quota for volume is being set to 100%% because it is above its current quota"
::= { traps 10213 }

nimbleGmVolSpcSnapQuotaOffline NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume being taken offline because it is above its snapshot quota"
::= { traps 10214 }

nimbleGmVolSpcSnapQuotaSet NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "The snapshot quota for volume is being set to unlimited because it is above its snapshot quota"
::= { traps 10215 }

nimbleGmVolSpcCurReserveOffline NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume being taken offline because it is above its reserve and system is out of free space"
::= { traps 10216 }

nimbleGmVolSpcCurReserveSet NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume reserve is being set to zero because it is above its reserve and system is out of free space"
::= { traps 10217 }

nimbleGmVolSpcSnapReserveOffline NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume being taken offline because it is above its snapshot reserve and system is out of free space"
::= { traps 10218 }

nimbleGmVolSpcSnapReserveSet NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume snapshot reserve is being set to zero because it is above its reserve and system is out of free space"
::= { traps 10219 }

nimbleGmVolSpcCurWarningUp NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume space usage over warning limit"
::= { traps 10220 }

nimbleGmVolSpcCurWarningDown NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume space usage below warning limit"
::= { traps 10221 }

nimbleGmVolSpcCurQuotaUp NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume space usage is over the configured quota"
::= { traps 10222 }

nimbleGmVolSpcCurQuotaDown NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume space usage is now below the configured quota"
::= { traps 10223 }

nimbleGmVolSpcSnapWarningUp NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume snapshot space usage over warning limit"
::= { traps 10224 }

nimbleGmVolSpcSnapWarningDown NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume snapshot space usage below warning limit"
::= { traps 10225 }

nimbleGmVolSpcSnapQuotaUp NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume snapshot space usage over quota"
::= { traps 10226 }

nimbleGmVolSpcSnapQuotaDown NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume snapshot space usage below quota"
::= { traps 10227 }

nimbleVolAttrSyncDelay NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume attributes synchronization to arrays in the pool delayed"
::= { traps 10228 }

nimbleGmPoolArrAssgnDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Failed to assign array to pool"
::= { traps 10229 }

nimbleGmPoolArrUnassgnDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Failed to unassign array from pool"
::= { traps 10230 }

nimbleGmVolSpcCurCritUpUnlim NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume space usage approaching quota"
::= { traps 10231 }

nimbleGmSnapSpcCurCritUpUnlim NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume snapshot space usage approaching quota"
::= { traps 10232 }

nimbleGmVolSpcReserveUp NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume space usage is above its reserve"
::= { traps 10233 }

nimbleGmVolSpcReserveDown NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume space usage is below its reserve"
::= { traps 10234 }

nimbleGmSnapSpcReserveUp NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume snapshot space usage is above its reserve"
::= { traps 10235 }

nimbleGmSnapSpcReserveDown NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume snapshot space usage is below its reserve"
::= { traps 10236 }

nimbleGmPoolMrgDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Failed to merge pools."
::= { traps 10240 }

nimbleVolAttrSyncSuccess NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume attributes synchronization to arrays in the pool succeeded"
::= { traps 10241 }

nimbleSnapAttrSyncDelay NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Snapshot attributes synchronization to arrays in the pool delayed"
::= { traps 10242 }

nimbleSnapAttrSyncSuccess NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Snapshot attributes synchronization to arrays in the pool succeeded"
::= { traps 10243 }

nimbleGroupAttrSyncDelay NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Configuration synchronization to array delayed"
::= { traps 10244 }

nimbleGroupAttrSyncComplete NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Configuration synchronization completed for array"
::= { traps 10245 }

nimbleGlCtrlrAttrSyncDelayDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Group Leader Platform Configuration synchronization is delayed"
::= { traps 10246 }

nimbleGlCtrlrAttrSyncCompleteDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Group Leader Configuration synchronization completed"
::= { traps 10247 }

nimbleGlCtrlrAttrSyncDelay NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Configuration synchronization to array delayed"
::= { traps 10248 }

nimbleGlCtrlrAttrSyncComplete NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Configuration synchronization completed for array"
::= { traps 10249 }

nimbleVolMoveComplete NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume completed move to destination pool"
::= { traps 10250 }

nimbleVolMoveAbortComplete NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume completed aborting move to destination pool"
::= { traps 10251 }

nimbleGmPoolArrUnassgnCompleteDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Completed unassign of array from pool"
::= { traps 10252 }

nimbleGmPoolArrUnassgnComplete NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Completed unassign of array from pool"
::= { traps 10253 }

nimbleGmPoolArrAssgn NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to assign array to pool"
::= { traps 10256 }

nimbleGmPoolArrUnassgn NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to unassign array from pool"
::= { traps 10257 }

nimbleGmPoolMrg NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to merge pools."
::= { traps 10260 }

nimbleGmVolSpcCurCritUpNonWritable NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume space usage approaching volume quota"
::= { traps 10261 }

nimbleGmVolSpcCurQuotaNonWritable NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume being set to non-writable because it is above its volume quota"
::= { traps 10262 }

nimbleGmSnapSpcCurCritUpNonWritable NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume snapshot space usage approaching snapshot quota"
::= { traps 10263 }

nimbleGmVolSpcSnapQuotaNonWritable NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume being set to non-writable because it is above its snapshot quota"
::= { traps 10264 }

nimbleGmVolSpcCurReserveNonWritable NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume being set to non-writable because it is above its reserve and system is out of free space"
::= { traps 10265 }

nimbleGmVolSpcSnapReserveNonWritable NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume being set to non-writable because it is above its snapshot reserve and system is out of free space"
::= { traps 10266 }

nimbleSchedSnapSucceededDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Scheduled snapshot succeeded"
::= { traps 10300 }

nimbleSchedSnapFailed NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Scheduled snapshot failed"
::= { traps 10301 }

nimbleSchedSnapSkippedExists NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Scheduled snapshot skipped"
::= { traps 10302 }

nimbleSchedSnapSkippedHandover NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Scheduled snapshot skipped"
::= { traps 10303 }

nimbleSchedSnapSucceededLagInfoDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Scheduled snapshot succeeded"
::= { traps 10304 }

nimbleSchedSnapFailedVmwareCredentialDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Scheduled snapshot failed"
::= { traps 10305 }

nimbleSchedSnapFailedVmwareConnectionTimeoutDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Scheduled snapshot failed"
::= { traps 10306 }

nimbleSchedSnapFailedVmwareConnectionRefusedDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Scheduled snapshot failed"
::= { traps 10307 }

nimbleSchedSnapFailedVmwareConnectionResetDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Scheduled snapshot failed"
::= { traps 10308 }

nimbleSchedSnapFailedVmwareConnectionNorouteDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Scheduled snapshot failed"
::= { traps 10309 }

nimbleSchedSnapFailedVmwareConnectionSocketDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Scheduled snapshot failed"
::= { traps 10310 }

nimbleSchedSnapFailedVmwareConnectionUnreachableDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Scheduled snapshot failed"
::= { traps 10311 }

nimbleSchedSnapFailedVmwareDisabledDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Scheduled snapshot failed"
::= { traps 10312 }

nimbleSchedSnapFailedVmwareObjectnfDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Scheduled snapshot failed"
::= { traps 10313 }

nimbleSchedSnapFailedVmwarePermissionDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Scheduled snapshot failed"
::= { traps 10314 }

nimbleSchedSnapFailedVmwareUkhostDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Scheduled snapshot failed"
::= { traps 10315 }

nimbleSchedSnapFailedVmwareEncodingPlainDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Scheduled snapshot failed"
::= { traps 10316 }

nimbleSchedSnapFailedVmwareNullDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Scheduled snapshot failed"
::= { traps 10317 }

nimbleSchedSnapFailedVmwareDcnotfoundDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Scheduled snapshot failed"
::= { traps 10318 }

nimbleSchedSnapFailedVmwareVolsnemptyDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Scheduled snapshot failed"
::= { traps 10319 }

nimbleSchedSnapFailedVmwareUnknownDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Scheduled snapshot failed"
::= { traps 10320 }

nimbleSchedSnapFailedVmwareBsizeDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Scheduled snapshot succeeded with warning"
::= { traps 10321 }

nimbleSchedSnapSucceeded NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Scheduled snapshot succeeded"
::= { traps 10322 }

nimbleSchedSnapSucceededLagInfo NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Scheduled snapshot succeeded"
::= { traps 10323 }

nimbleSchedSnapFailedVmwareDisabledDeprecatedTwo NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Scheduled snapshot failed"
::= { traps 10324 }

nimbleSchedSnapFailedVmwareTimeoutDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Scheduled snapshot failed"
::= { traps 10325 }

nimbleSchedSnapFailedVmwareSnapNameMaxLengthExceededDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Scheduled snapshot failed"
::= { traps 10326 }

nimbleSchedSnapFallback NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Application synchronization failed"
::= { traps 10327 }

nimbleSchedSnapFailedVmwarePermissionPerVm NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with VMware vCenter"
::= { traps 10340 }

nimbleSchedSnapFailedVmwareObjectnfPerVm NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with VMware vCenter"
::= { traps 10341 }

nimbleSchedSnapFailedVmwareEncodingPlainPerVm NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with VMware vCenter"
::= { traps 10342 }

nimbleSchedSnapFailedVmwareNullPerVm NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with VMware vCenter"
::= { traps 10343 }

nimbleSchedSnapFailedVmwareDcnotfoundPerVm NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with VMware vCenter"
::= { traps 10344 }

nimbleSchedSnapFailedVmwareVolsnemptyPerVm NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with VMware vCenter"
::= { traps 10345 }

nimbleSchedSnapFailedVmwareUnknownPerVmDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Failed to synchronize with VMware vCenter"
::= { traps 10346 }

nimbleSchedSnapFailedVmwareBsizePerVm NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with VMware vCenter"
::= { traps 10347 }

nimbleSchedSnapFailedVmwareDisabledPerVm NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with VMware vCenter"
::= { traps 10348 }

nimbleSchedSnapFailedVmwareTimeoutPerVm NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with VMware vCenter"
::= { traps 10349 }

nimbleSchedSnapFailedVmwareSnapNameMaxLengthExceededPerVm NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with VMware vCenter"
::= { traps 10350 }

nimbleSchedSnapFailedVmwareGuestToolsNotRunningPerVm NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with VMware vCenter"
::= { traps 10351 }

nimbleSchedSnapFailedVmwareInvalidVcenter NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with VMware vCenter"
::= { traps 10352 }

nimbleSchedSnapFailedVmwareBusy NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with VMware vCenter"
::= { traps 10353 }

nimbleSchedSnapFailedVssIncompatible NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Scheduled snapshot failed"
::= { traps 10354 }

nimbleSchedSnapFailedVmwareCredentialNw NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with VMware vCenter"
::= { traps 10355 }

nimbleSchedSnapFailedVmwareConnectionTimeoutNw NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with VMware vCenter"
::= { traps 10356 }

nimbleSchedSnapFailedVmwareConnectionRefusedNw NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with VMware vCenter"
::= { traps 10357 }

nimbleSchedSnapFailedVmwareConnectionResetNw NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with VMware vCenter"
::= { traps 10358 }

nimbleSchedSnapFailedVmwareConnectionNorouteNw NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with VMware vCenter"
::= { traps 10359 }

nimbleSchedSnapFailedVmwareConnectionSocketNw NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with VMware vCenter"
::= { traps 10360 }

nimbleSchedSnapFailedVmwareConnectionUnreachableNw NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with VMware vCenter"
::= { traps 10361 }

nimbleSchedSnapFailedVmwareUkhostNw NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with VMware vCenter"
::= { traps 10362 }

nimbleSchedSnapFailedVmwareConnectionUnknownNw NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with VMware vCenter"
::= { traps 10363 }

nimbleSchedSnapFailedVmwareTimeoutNw NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with VMware vCenter"
::= { traps 10364 }

nimbleSchedSnapFailedVmwareUnknownNw NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with VMware vCenter"
::= { traps 10365 }

nimbleSchedSnapFailedVmwareUnknownPerVm NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with VMware vCenter"
::= { traps 10366 }

nimbleSchedSnapFailedVmwareQuiescingVmFailed NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with VMware vCenter"
::= { traps 10367 }

nimbleGmSpaceReserveWarnUp NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Used space above warning limit"
::= { traps 10401 }

nimbleGmSpaceReserveWarnDown NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Used space below warning limits"
::= { traps 10402 }

nimbleGmSpaceReserveCritUp NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Used space above critical level"
::= { traps 10403 }

nimbleGmSpaceReserveCritDown NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Used space below critical limits"
::= { traps 10404 }

nimbleGmSpaceUtilizationOk NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Array space utilization OK"
::= { traps 10405 }

nimbleGmSpaceUtilizationInfo NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "High array space utilization"
::= { traps 10406 }

nimbleGmSpaceUtilizationHigh NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "High array space utilization"
::= { traps 10407 }

nimbleGmSpaceUtilizationCrit NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Critically high array space utilization"
::= { traps 10408 }

nimbleGmPoolSpaceReserveWarnUpDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Used space in the pool above warning limit"
::= { traps 10409 }

nimbleGmPoolSpaceReserveWarnDownDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Used space in the pool below warning limits"
::= { traps 10410 }

nimbleGmPoolSpaceReserveCritUpDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Used space in the pool above critical level"
::= { traps 10411 }

nimbleGmPoolSpaceReserveCritDownDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Used space in the pool below critical limits"
::= { traps 10412 }

nimbleGmPoolSpaceUtilizationOkDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Pool space utilization OK"
::= { traps 10413 }

nimbleGmPoolSpaceUtilizationInfoDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "High pool space utilization"
::= { traps 10414 }

nimbleGmPoolSpaceUtilizationHighDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "High pool space utilization"
::= { traps 10415 }

nimbleGmPoolSpaceUtilizationCritDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Critically high pool space utilization"
::= { traps 10416 }

nimbleGmPoolSpaceReserveWarnUp NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Used space in the pool above warning limit"
::= { traps 10417 }

nimbleGmPoolSpaceReserveWarnDown NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Used space in the pool below warning limits"
::= { traps 10418 }

nimbleGmPoolSpaceReserveCritUp NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Used space in the pool above critical level"
::= { traps 10419 }

nimbleGmPoolSpaceReserveCritDown NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Used space in the pool below critical limits"
::= { traps 10420 }

nimbleGmPoolSpaceUtilizationOk NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Pool space utilization OK"
::= { traps 10421 }

nimbleGmPoolSpaceUtilizationInfo NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "High pool space utilization"
::= { traps 10422 }

nimbleGmPoolSpaceUtilizationHigh NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "High pool space utilization"
::= { traps 10423 }

nimbleGmPoolSpaceUtilizationCrit NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Critically high pool space utilization"
::= { traps 10424 }

nimbleLimitMaxOver NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Object count reached maximum limit"
::= { traps 10500 }

nimbleLimitMaxUnder NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Object count under maximum limit"
::= { traps 10501 }

nimbleLimitWarnOver NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Object count over warning limit"
::= { traps 10502 }

nimbleLimitWarnUnder NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Object count under warning limit"
::= { traps 10503 }

nimbleReplSnapcollSucceeded NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Replication succeeded"
::= { traps 11000 }

nimbleReplSnapcollDelayedInfo NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Excessive replication delay"
::= { traps 11001 }

nimbleReplSnapcollDelayedWarn NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Excessive replication delay"
::= { traps 11002 }

nimbleReplPartnerSyncFail NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Partner synchronization failed"
::= { traps 11003 }

nimbleReplBranchPinned NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume replication stalled"
::= { traps 11004 }

nimbleReplHandoverCompleted NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume collection handover completed"
::= { traps 11005 }

nimbleReplMultiArrayGroup NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Replication between multi-array scaleout group and pre-scaleout array is not supported"
::= { traps 11006 }

nimbleReplPartnerMisconfiguration NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Replication between a scaleout group and pre-scaleout array must be configured over the management network"
::= { traps 11007 }

nimbleReplSnapshotCorrectedDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Replication resynchronized"
::= { traps 11008 }

nimbleReplCbrRequestedDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Resynchronization not supported"
::= { traps 11009 }

nimbleReplCbrNeeded NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Resynchronization not supported"
::= { traps 11010 }

nimbleReplSnapshotCorrectedDeprecated2 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Replication resynchronized"
::= { traps 11011 }

nimbleReplCbrRequestedDeprecated2 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Resynchronization not supported"
::= { traps 11012 }

nimbleReplPartnerAuthFailDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Partner authentication failed"
::= { traps 11013 }

nimbleReplSnapshotCorrected NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Replicated snapshot resynchronized"
::= { traps 11014 }

nimbleReplCbrRequested NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Replicated snapshot resynchronization not supported"
::= { traps 11015 }

nimbleReplPartnerAuthFail NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Replication partner authentication failed"
::= { traps 11016 }

nimbleOvertempShutdownDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Overtemperature shutdown"
::= { traps 12000 }

nimbleCtrlrOvertempDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Controller overtemperature"
::= { traps 12001 }

nimbleBackplaneOvertempDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Backplane over-temperature"
::= { traps 12002 }

nimbleDiskFailedCritDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Disk failed"
::= { traps 12100 }

nimbleDiskFailedDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Disk failed"
::= { traps 12101 }

nimbleDiskAbsentDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Disk missing"
::= { traps 12102 }

nimbleDiskAddedDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Disk added"
::= { traps 12103 }

nimbleDiskRemovedDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Disk removed"
::= { traps 12104 }

nimbleSsdFailedDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "SSD failed"
::= { traps 12105 }

nimbleSsdAbsentDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "SSD missing"
::= { traps 12106 }

nimbleSsdAddedDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "SSD added"
::= { traps 12107 }

nimbleSsdRemovedDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "SSD removed"
::= { traps 12108 }

nimbleDiskInvalidLabel NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Foreign disk detected"
::= { traps 12109 }

nimbleSsdInvalidLabel NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Foreign SSD detected"
::= { traps 12110 }

nimbleDiskSizeMismatchDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Invalid disk size for this model"
::= { traps 12111 }

nimbleHddFailedV2 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Disk failed"
::= { traps 12112 }

nimbleHddAbsentV2 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Disk missing"
::= { traps 12113 }

nimbleHddAddedV2 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Disk added"
::= { traps 12114 }

nimbleHddRemovedV2 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Disk removed"
::= { traps 12115 }

nimbleSsdFailedV2 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "SSD failed"
::= { traps 12116 }

nimbleSsdAbsentV2 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "SSD missing"
::= { traps 12117 }

nimbleSsdAddedV2 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "SSD added"
::= { traps 12118 }

nimbleSsdRemovedV2 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "SSD removed"
::= { traps 12119 }

nimbleSsdLastOne NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Only one SSD drive left"
::= { traps 12120 }

nimbleHddFailedV3 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Disk failed"
::= { traps 12121 }

nimbleHddAddedV3 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Disk added"
::= { traps 12122 }

nimbleHddRemovedV3 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Disk removed"
::= { traps 12123 }

nimbleSsdFailedV3 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "SSD failed"
::= { traps 12124 }

nimbleSsdAddedV3 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "SSD added"
::= { traps 12125 }

nimbleSsdRemovedV3 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "SSD removed"
::= { traps 12126 }

nimbleDiskSizeMismatchV2 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Invalid disk size for this shelf"
::= { traps 12127 }

nimbleSsdSizeMismatchV2 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Invalid SSD size for this shelf"
::= { traps 12128 }

nimbleHddFailedAfsDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Disk not supported on All Flash Shelf"
::= { traps 12129 }

nimbleHddFailedAfs NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Disk not supported on All-Flash Shelf"
::= { traps 12130 }

nimbleIpIfDown NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "IP interface down"
::= { traps 12200 }

nimbleIpIfUp NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "IP interface up"
::= { traps 12201 }

nimbleIpIfGroupUnavailDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Group IP interface unavailable"
::= { traps 12202 }

nimbleIpIfDataUnavailDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "All Data IP interfaces unavailable"
::= { traps 12203 }

nimbleIpIfCantFailoverDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "IP connectivity lost"
::= { traps 12204 }

nimbleSubnetNicMigrationDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Migrating subnet NIC configuration"
::= { traps 12205 }

nimbleSubnetNicMissingDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "NIC for subnet missing"
::= { traps 12206 }

nimbleIpNicMigrationDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Migrating IP NIC configuration"
::= { traps 12207 }

nimbleIpNicMissingDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "NIC for IP missing"
::= { traps 12208 }

nimbleRouteNicMigrationDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Migrating route NIC configuration"
::= { traps 12209 }

nimbleRouteNicMissingDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "NIC for route missing"
::= { traps 12210 }

nimbleIpIfFailover NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Standby controller has better network connectivity. Failing services over to standby controller"
::= { traps 12211 }

nimbleIpDupFound NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Duplicate IP Address Detected"
::= { traps 12212 }

nimbleIpIfDiscoveryUnavailDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Discovery IP interface unavailable"
::= { traps 12213 }

nimbleIpIfTargetUnavailDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Target IP interfaces unavailable"
::= { traps 12214 }

nimbleIpIfGroupUnavail NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Link down for Group IP interface(s)"
::= { traps 12215 }

nimbleIpIfDiscoveryUnavail NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Link down for Discovery IP interface(s)"
::= { traps 12216 }

nimbleIpIfTargetUnavail NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Link down for Target IP interface(s)"
::= { traps 12217 }

nimbleIpIfDataUnavail NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Link down for Data IP interface(s)"
::= { traps 12218 }

nimbleIpIfIscsiDataUnavail NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Link down for iSCSI Data IP interface(s)"
::= { traps 12219 }

nimbleIpIfClusterDataUnavail NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Link down for cluster Data IP interface(s)"
::= { traps 12220 }

nimbleUnresponsiveNicDetected NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Unresponsive NIC Port Detected"
::= { traps 12221 }

nimbleIpIfCantFailoverDeprecated2 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "IP connectivity lost"
::= { traps 12222 }

nimbleIpIfCantFailover NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Network connectivity lost"
::= { traps 12223 }

nimbleSensorLinearWarn NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Sensor: Alert raised"
::= { traps 12301 }

nimbleSensorLinearClear NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Sensor: Alert cleared"
::= { traps 12302 }

nimbleSensorBoolWarn NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Sensor: Alert raised"
::= { traps 12303 }

nimbleSensorBoolClear NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Sensor: Alert cleared"
::= { traps 12304 }

nimbleSensorDoesNotExist NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Sensor: is missing?:"
::= { traps 12305 }

nimbleNvramBattDisabled NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "NVRAM battery is disabled"
::= { traps 12306 }

nimbleNvramBattDisabledCrit NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "NVRAM batteries are disabled"
::= { traps 12307 }

nimbleNvramBattOk NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "NVRAM battery is OK"
::= { traps 12308 }

nimbleTempSensorHighDep NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "System temperature is warm"
::= { traps 12310 }

nimbleTempSensorLowDep NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "System temperature is cold"
::= { traps 12311 }

nimbleTempSensorOkDep NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "System temperature is ok"
::= { traps 12312 }

nimbleTempSensorMissingDep NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Temperature sensor failed"
::= { traps 12313 }

nimbleTempSensorOperationalDep NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Temperature sensor is ok"
::= { traps 12314 }

nimbleFanSensorHighDep NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Fan in high speed"
::= { traps 12315 }

nimbleFanSensorLowDep NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Fan in low speed"
::= { traps 12316 }

nimbleFanSensorOkDep NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Fan is ok"
::= { traps 12317 }

nimbleFanSensorStoppedDep NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Fan  stopped"
::= { traps 12318 }

nimbleFanSensorMissingDep NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Fan missing"
::= { traps 12319 }

nimblePwrSupplySensorFailDep NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Power supply fail"
::= { traps 12320 }

nimblePwrSupplySensorMissingDep NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Power supply missing"
::= { traps 12321 }

nimblePwrSupplySensorOkDep NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Power supply is ok"
::= { traps 12322 }

nimbleTempSensorHighDep2 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "System temperature is warm"
::= { traps 12323 }

nimbleTempSensorLowDep2 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "System temperature is cold"
::= { traps 12324 }

nimbleTempSensorOkDep2 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "System temperature is ok"
::= { traps 12325 }

nimbleTempSensorMissingDep2 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Temperature sensor failed"
::= { traps 12326 }

nimbleTempSensorOperationalDep2 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Temperature sensor is ok"
::= { traps 12327 }

nimbleFanSensorHighDep2 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Fan in high speed"
::= { traps 12328 }

nimbleFanSensorLowDep2 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Fan in low speed"
::= { traps 12329 }

nimbleFanSensorOkDep2 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Fan is ok"
::= { traps 12330 }

nimbleFanSensorStoppedDep2 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Fan  stopped"
::= { traps 12331 }

nimbleFanSensorMissingDep2 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Fan missing"
::= { traps 12332 }

nimblePwrSupplySensorFailDep2 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Power supply fail"
::= { traps 12333 }

nimblePwrSupplySensorMissingDep2 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Power supply missing"
::= { traps 12334 }

nimblePwrSupplySensorOkDep2 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Power supply is ok"
::= { traps 12335 }

nimbleTempSensorHighDeprecatedDep2 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "System temperature is warm"
::= { traps 12336 }

nimbleTempSensorLow NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "System temperature is cold"
::= { traps 12337 }

nimbleTempSensorOk NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "System temperature is OK"
::= { traps 12338 }

nimbleTempSensorMissing NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Temperature sensor failed"
::= { traps 12339 }

nimbleTempSensorOperational NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Temperature sensor is OK"
::= { traps 12340 }

nimbleFanSensorHigh NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Fan is at high speed"
::= { traps 12341 }

nimbleFanSensorLow NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Fan is at low speed"
::= { traps 12342 }

nimbleFanSensorOk NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Fan is OK"
::= { traps 12343 }

nimbleFanSensorStopped NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Fan  stopped"
::= { traps 12344 }

nimbleFanSensorMissing NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Fan missing"
::= { traps 12345 }

nimblePwrSupplySensorFail NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Power supply fail"
::= { traps 12346 }

nimblePwrSupplySensorMissing NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Power supply missing"
::= { traps 12347 }

nimblePwrSupplySensorOk NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Power supply is OK"
::= { traps 12348 }

nimbleRaidDegraded NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "RAID array degraded"
::= { traps 12400 }

nimbleRaidRebuildStart NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "RAID array rebuild started"
::= { traps 12401 }

nimbleRaidRebuildDone NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "RAID array rebuild is done"
::= { traps 12402 }

nimbleRaidRebuildFailRead NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "RAID array rebuild failed"
::= { traps 12403 }

nimbleRaidRebuildFail NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "RAID array rebuild failed"
::= { traps 12404 }

nimbleRaidDisksMissing NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Disks missing from RAID array"
::= { traps 12405 }

nimbleRaidSpare NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Disk marked as spare"
::= { traps 12406 }

nimbleRaidAssemblyFailed NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Could not assemble RAID array"
::= { traps 12407 }

nimbleRaidDegradedV2 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "RAID array degraded"
::= { traps 12408 }

nimbleRaidRebuildStartV2 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "RAID array rebuild started"
::= { traps 12409 }

nimbleRaidRebuildDoneV2 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "RAID array rebuild is done"
::= { traps 12410 }

nimbleRaidRebuildFailReadV2 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "RAID array rebuild failed"
::= { traps 12411 }

nimbleRaidRebuildFailV2 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "RAID array rebuild failed"
::= { traps 12412 }

nimbleRaidDisksMissingV2 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Disks missing from RAID array"
::= { traps 12413 }

nimbleRaidSpareV2 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Disk marked as spare"
::= { traps 12414 }

nimbleRaidAssemblyFailedV2 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Could not assemble RAID array"
::= { traps 12415 }

nimbleRaidRebuildScheduledV2 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "RAID array rebuild scheduled"
::= { traps 12416 }

nimbleRaidRebuildStopV2 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "RAID array rebuild stopped"
::= { traps 12417 }

nimbleIscsiMultiInitiatorDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Multi initiator login"
::= { traps 12500 }

nimbleIscsiConnHardLimitDeprecated1 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Too many iscsi connections"
::= { traps 12501 }

nimbleIscsiUnalignedOpsDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Too many unaligned iscsi reads/writes"
::= { traps 12502 }

nimbleIscsiMultiInitiator NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Multi initiator login"
::= { traps 12503 }

nimbleIscsiConnHardLimitDeprecated2 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Too many iSCSI connections"
::= { traps 12504 }

nimbleIscsiUnalignedOps NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Too many unaligned iSCSI reads/writes"
::= { traps 12505 }

nimbleIscsiConnHardLimit NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Too many iSCSI connections"
::= { traps 12506 }

nimbleIscsiErroneousItorConns NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "iSCSI connections from initiator repeatedly closed by array due to improper target IP configuration"
::= { traps 12057 }

nimbleNvramBattCharging NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "NVRAM battery is charging"
::= { traps 12601 }

nimbleNvramBattCharged NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "NVRAM battery has finished charging"
::= { traps 12602 }

nimbleNvramFpgaVersion NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "NVRAM version is incompatible"
::= { traps 12603 }

nimbleNvramMbeDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "NVRAM card multi-bit error (MBE) detected"
::= { traps 12604 }

nimbleNvramSbeDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "NVRAM card single-bit error (SBE) detected"
::= { traps 12605 }

nimbleNvramMbe NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "NVRAM card non-correctable multi-bit error (MBE) detected"
::= { traps 12606 }

nimbleNvramSbe NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "NVRAM card correctable single-bit error (SBE) detected"
::= { traps 12607 }

nimbleNvdimmReservedBlocksWarn NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "NVDIMM reserved flash blocks reached the upper threshold"
::= { traps 12608 }

nimbleNvdimmReservedBlocksCrit NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "NVDIMM reserved flash blocks reached the lower threshold"
::= { traps 12609 }

nimbleNvdimmUltracapDischargedDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "NVDIMM ultracap cacapcitance discharged"
::= { traps 12610 }

nimbleNtbBadLink NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "NTB_BAD_LINK"
::= { traps 12611 }

nimbleNvdimmUltracapDischarged NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "NVDIMM ultracap capacitance discharged"
::= { traps 12612 }

nimbleNvramMissing NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "NVRAM module missing"
::= { traps 12613 }

nimbleShelfCtrlrSide NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Shelf controller connected to wrong side of host controller"
::= { traps 12701 }

nimbleShelfSesErr NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Shelf SES device not ready"
::= { traps 12702 }

nimbleShelfDiskSasLink NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "SAS link of a shelf slot is degraded"
::= { traps 12703 }

nimbleShelfDiskCount NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Not enough disk in shelf"
::= { traps 12704 }

nimbleShelfInvalidEeprom NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "System cannot read shelf serial number"
::= { traps 12705 }

nimbleShelfWrongSasPortDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "SAS cable connected to wrong port"
::= { traps 12706 }

nimbleShelfSasLink NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "SAS link(s) between the shelves is(are) degraded"
::= { traps 12707 }

nimbleShelfSasExpErr NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "SAS expander error"
::= { traps 12708 }

nimbleShelfCtrlrLoop NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Shelf SAS loop detected"
::= { traps 12709 }

nimbleShelfMissing NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Shelf appear only on one side of host controllers"
::= { traps 12710 }

nimbleShelfOrder NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Shelf controller connection order mismatched"
::= { traps 12711 }

nimbleShelfSesMshipErrDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Cannot access shelf SES device"
::= { traps 12712 }

nimbleShelfFailover NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Controller failover due to shelf problem"
::= { traps 12713 }

nimbleShelfNewShelf NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "New Shelf detected"
::= { traps 12714 }

nimbleShelfDisconnect NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Shelf is disconnected"
::= { traps 12715 }

nimbleShelfChassisSwap NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Shelf chassis swap detected"
::= { traps 12716 }

nimbleShelfLocIdOverLimit NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Shelf daisy chain too long"
::= { traps 12717 }

nimbleShelfActivatedDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "New shelf is activated"
::= { traps 12718 }

nimbleShelfReconnect NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Connection to shelf is restored"
::= { traps 12719 }

nimbleShelfSasLinkDisabledDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "SAS link disabled"
::= { traps 12720 }

nimbleShelfDiskSasLinkErrDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Excessive link error on disk"
::= { traps 12721 }

nimbleShelfWrongSasPortDeprecated2 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "SAS cable connected to wrong port"
::= { traps 12730 }

nimbleShelfSesMshipErrDeprecated2 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Cannot access shelf SES device"
::= { traps 12731 }

nimbleShelfSasLinkDisabled NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "SAS link disabled"
::= { traps 12732 }

nimbleShelfDiskSasLinkErr NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Excessive link error on disk"
::= { traps 12733 }

nimbleShelfWrongSasPort NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "SAS cable connected to wrong port"
::= { traps 12734 }

nimbleShelfSesMshipErrDeprecated3 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Cannot access shelf SES device"
::= { traps 12735 }

nimbleShelfSesMshipErrDeprecated4 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Cannot access shelf SES device"
::= { traps 12736 }

nimbleShelfActivatedV2Deprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "New shelf is activated"
::= { traps 12737 }

nimbleShelfSesMshipErr NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Cannot access shelf SES device"
::= { traps 12738 }

nimbleShelfActivatedV2 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "New shelf activated"
::= { traps 12739 }

nimblePhysMemMismatch NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Physical memory detected is less than installed"
::= { traps 12901 }

nimbleVolSysLimitWarnEnter NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Total number of volumes approaching system limit"
::= { traps 13101 }

nimbleVolSysLimitWarnExit NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Total number of volumes below warning threshold"
::= { traps 13102 }

nimbleGmTakeoverSuccessDeprecatedDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Group Leader role takeover succeeded"
::= { traps 13501 }

nimbleGmTakeoverSuccessDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Group Leader role takeover succeeded"
::= { traps 13504 }

nimbleGmTakeoverSuccess NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Group Leader role take over succeeded"
::= { traps 13505 }

nimbleGmMigrateFailure NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Group Leader role migrate failed"
::= { traps 13506 }

nimbleGmTakeoverRejectByArrayDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Group Leader role takeover has been rejected by a member array"
::= { traps 13502 }

nimbleGmTakeoverRejectByArray NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Group Leader role takeover has been rejected by a member array"
::= { traps 13503 }

nimbleGmGrpMrgDone NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Group merge completed successfully"
::= { traps 13601 }

nimbleGmGrpQscFail NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to stop services on source group for group merge"
::= { traps 13602 }

nimbleGmGrpMrgRollbackDone NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Completed rollback of group merge operation"
::= { traps 13603 }

nimbleGmGrpMrgReassFail NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Group merge operation is not complete on some arrays"
::= { traps 13604 }

nimbleGmGrpMrgDbFail NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to merge configuration from source group"
::= { traps 13605 }

nimbleGmBinMigContAbortDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Data Migration is getting delayed because of continuous restarts"
::= { traps 13701 }

nimbleGmBinMigContAbort NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Data migration is delayed because of repeated restarts"
::= { traps 13702 }

nimbleCsmodelChanged NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "CS-Model changed"
::= { traps 14000 }

nimbleCsmodelUnknown NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "CS-Model unknown"
::= { traps 14001 }

nimbleTempSensorHighDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "The system temperature is beginning to exceed the allowable operating temperature. If it continues to exceed allowed operating temperature"
::= { traps 14002 }

nimbleOvertempShutdownDeprecated2 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Controller shutdown occurred due to excessive temperature"
::= { traps 14003 }

nimbleCtrlrOvertemp NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Controller exceeds allowable operating temperature"
::= { traps 14004 }

nimbleBackplaneOvertemp NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Backplane exceeds allowable operating temperature"
::= { traps 14005 }

nimbleTempSensorHighDeprecated2 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "System temperature is too high."
::= { traps 14006 }

nimbleTempSensorCrithighDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "System temperature continues to be high."
::= { traps 14007 }

nimblePwrSupplySensorCallsupportDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Power supply down revisioned"
::= { traps 14008 }

nimbleOvertempShutdown NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Controller shutdown occurred due to excessive temperature"
::= { traps 14009 }

nimblePwrSupplySensorCallsupport NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Power supply down revisioned"
::= { traps 14010 }

nimbleTempSensorHigh NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Array temperature is too high"
::= { traps 14011 }

nimbleTempSensorCrithigh NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Array temperature continues to be high"
::= { traps 14012 }

nimbleUpdateUnknownFirmware NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "An unknown firmware version was detected"
::= { traps 14200 }

nimbleFcLinkUp NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Fibre Channel link up"
::= { traps 14400 }

nimbleFcLinkDown NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Fibre Channel link down"
::= { traps 14401 }

nimbleFcLinkNotConnected NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Fibre Channel link not connected"
::= { traps 14402 }

nimbleEventPurging NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Oldest events removed from the system"
::= { traps 14700 }

nimbleEventWarnOver NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Events count reached warning threshold"
::= { traps 14701 }

END

ALCATEL-IGMP-SNOOPING-MIB DEFINITIONS ::= BEGIN

IMPORTS
    InetAddress, InetAddressType
                                                         FROM INET-ADDRESS-MIB
    MODULE-COMPLIANCE, NOTIFICATION-GROUP,
    OBJECT-GROUP
                                                         FROM SNMPv2-CONF
    Counter32, Integer32, IpAddress,
    MODULE-IDENTITY, NOTIFICATION-TYPE,
    OBJECT-TYPE, TimeTicks, Unsigned32
                                                         FROM SNMPv2-SMI
    DisplayString, RowStatus,
    TEXTUAL-CONVENTION, TimeStamp,
    TruthValue
                                                         FROM SNMPv2-TC
    alcatelCommonMIBModules,
    alcatelConformance, alcatelNotifyPrefix,
    alcatelObjects
                                                         FROM TIMETRA-GLOBAL-MIB
    tmnxMcacLagPortsDown, tmnxMcacLevelId
                                                         FROM TIMETRA-MCAST-CAC-MIB
    sapEncapValue, sapPortId
                                                         FROM TIMETRA-SAP-MIB
    sdpBindId
                                                         FROM TIMETRA-SDP-MIB
    SdpId, svcId
                                                         FROM TIMETRA-SERV-MIB
    TItemDescription,
    TPolicyStatementNameOrEmpty,
    TmnxAdminState, TmnxEncapVal,
    TmnxIgmpGroupFilterMode,
    TmnxIgmpGroupType,
    TmnxIgmpSnpgGroupType, TmnxIgmpVersion,
    TmnxOperState, TmnxPortID, TmnxServId,
    TmnxVcIdOrNone
                                                         FROM TIMETRA-TC-MIB
    ;

alcatelIgmpSnoopingMIBModule     MODULE-IDENTITY
    LAST-UPDATED "201601010000Z"
    ORGANIZATION "Nokia"
    CONTACT-INFO
        "Nokia SROS Support
         Web: http://www.nokia.com"
    DESCRIPTION
        "This document is the SNMP MIB module to manage and provision the IGMP
         snooping feature protocol for the Nokia 7x50 device.

         Copyright 2004-2018 Nokia. All rights reserved. Reproduction of this
         document is authorized on the condition that the foregoing copyright
         notice is included.

         This SNMP MIB module (Specification) embodies Nokia's
         proprietary intellectual property.  Nokia retains
         all title and ownership in the Specification, including any
         revisions.

         Nokia grants all interested parties a non-exclusive license to use and
         distribute an unmodified copy of this Specification in connection with
         management of Nokia products, and without fee, provided this copyright
         notice and license appear on all copies.

         This Specification is supplied 'as is', and Nokia makes no warranty,
         either express or implied, as to the use, operation, condition, or
         performance of the Specification."

    REVISION    "201601010000Z"
    DESCRIPTION
        "Rev 14.0               01 Jan 2016 00:00
         14.0 release of the ALCATEL-IGMP-SNOOPING-MIB."

    REVISION    "201501010000Z"
    DESCRIPTION
        "Rev 13.0               01 Jan 2015 00:00
         13.0 release of the ALCATEL-IGMP-SNOOPING-MIB."

    REVISION    "201401010000Z"
    DESCRIPTION
        "Rev 12.0               01 Jan 2014 00:00
         12.0 release of the ALCATEL-IGMP-SNOOPING-MIB."

    REVISION    "200801010000Z"
    DESCRIPTION
        "Rev 6.0                01 Jan 2008 00:00
         6.0 release of the ALCATEL-IGMP-SNOOPING-MIB."

    REVISION    "200701010000Z"
    DESCRIPTION
        "Rev 5.0                01 Jan 2007 00:00
         5.0 release of the ALCATEL-IGMP-SNOOPING-MIB."

    REVISION    "200508310000Z"
    DESCRIPTION
        "Rev 3.0                31 Aug 2005 00:00
         3.0 release of the ALCATEL-IGMP-SNOOPING-MIB."

    REVISION    "200503290000Z"
    DESCRIPTION
        "Rev 2.0                29 Mar 2005 00:00
         2.0 release of the ALCATEL-IGMP-SNOOPING-MIB."

    REVISION    "200405170000Z"
    DESCRIPTION
        "Rev 1.0                17 May 2004 00:00
         1.0 release of the ALCATEL-IGMP-SNOOPING-MIB."

    ::= { alcatelCommonMIBModules 2 }

AlxIgmpSnpgAdminState            ::= TEXTUAL-CONVENTION
    STATUS      current
    DESCRIPTION
        "The AlxIgmpSnpgAdminState data type is an enumerated integer that
         describes the values used to identify the administrative state."
    SYNTAX      INTEGER {
        enabled  (1),
        disabled (2)
    }

AlxIgmpSnpgLocation              ::= TEXTUAL-CONVENTION
    STATUS      current
    DESCRIPTION
        "The data type AlxIgmpSnpgLocation represents the
         type of the local 'interface':
         - 'sap(1)'  : sap interface
         - 'sdp(2)'  : mesh-sdp or spoke-sdp interface.
         - 'rvpls(3)': routed vpls Layer 3 interface.
         - 'vxlan(4)': vxlan endpoint for ethernet vpn"
    SYNTAX      INTEGER {
        sap      (1),
        sdp      (2),
        rvpls    (3),
        vxlan    (4),
        evpnMpls (5)
    }

alxIgmpSnoopingObjs              OBJECT IDENTIFIER ::= { alcatelObjects 2 }

alxIgmpSnoopingTlsObjs           OBJECT IDENTIFIER ::= { alxIgmpSnoopingObjs 1 }

tlsIgmpSnpgConfigTable           OBJECT-TYPE
    SYNTAX      SEQUENCE OF TlsIgmpSnpgConfigEntry
    MAX-ACCESS  not-accessible
    STATUS      current
    DESCRIPTION
        "The table tlsIgmpSnpgConfigTable contains objects to configure the
         IGMP snooping feature within a Tls service."
    ::= { alxIgmpSnoopingTlsObjs 1 }

tlsIgmpSnpgConfigEntry           OBJECT-TYPE
    SYNTAX      TlsIgmpSnpgConfigEntry
    MAX-ACCESS  not-accessible
    STATUS      current
    DESCRIPTION
        "Each row represents an instance of IGMP snooping running within a Tls
         service. Entries in this table cannot be created or deleted via SNMP
         operations. An entry in this table will be created by the agent upon
         creation of a new Tls service (svcTlsInfoTable). The entry is
         destroyed when the Tls service is removed."
    INDEX       { svcId }
    ::= { tlsIgmpSnpgConfigTable 1 }

TlsIgmpSnpgConfigEntry           ::= SEQUENCE
{
    tlsIgmpSnpgCfgAdminState         AlxIgmpSnpgAdminState,
    tlsIgmpSnpgCfgGenQueryIntvl      Unsigned32,
    tlsIgmpSnpgCfgRobustCount        Unsigned32,
    tlsIgmpSnpgCfgReportSrcAddress   IpAddress,
    tlsIgmpSnpgCfgMvrAdminState      AlxIgmpSnpgAdminState,
    tlsIgmpSnpgCfgMvrDescription     TItemDescription,
    tlsIgmpSnpgCfgMvrPolicy          TPolicyStatementNameOrEmpty,
    tlsIgmpSnpgCfgQuerySrcAddress    IpAddress,
    tlsIgmpSnpgCfgQuerySrcAddrType   INTEGER,
    tlsIgmpSnpgCfgLastChangeTime     TimeStamp,
    tlsIgmpSnpgCfgFwdIpv4McastToInt  TruthValue,
    tlsIgmpSnpgCfgRvplsMrouter       TruthValue,
    tlsIgmpSnpgCfgIpMcastEcmp        TruthValue,
    tlsIgmpSnpgCfgTxSmetRoutes       Unsigned32
}

tlsIgmpSnpgCfgAdminState         OBJECT-TYPE
    SYNTAX      AlxIgmpSnpgAdminState
    MAX-ACCESS  read-write
    STATUS      current
    DESCRIPTION
        "The value of the object tlsIgmpSnpgCfgAdminState specifies the
         administrative state of the IGMP snooping feature associated with this
         Tls."
    DEFVAL      { disabled }
    ::= { tlsIgmpSnpgConfigEntry 1 }

tlsIgmpSnpgCfgGenQueryIntvl      OBJECT-TYPE
    SYNTAX      Unsigned32 (1..65535)
    UNITS       "seconds"
    MAX-ACCESS  read-write
    STATUS      current
    DESCRIPTION
        "The value of the object tlsIgmpSnpgCfgGenQueryIntvl specifies the
         Queriers Query Interval, on networks where the active Querier is not
         running IGMPv3 (meaning that the Query Interval is not sent in the
         Query PDU).

         For these networks, this object needs to be set to the same value as
         what is configured on the Querier."
    DEFVAL      { 125 }
    ::= { tlsIgmpSnpgConfigEntry 2 }

tlsIgmpSnpgCfgRobustCount        OBJECT-TYPE
    SYNTAX      Unsigned32 (1..255)
    MAX-ACCESS  read-write
    STATUS      current
    DESCRIPTION
        "The value of the object tlsIgmpSnpgCfgRobustCount specifies the
         Querier's Robustness Variable, on networks where the active Querier is
         not running IGMPv3 (meaning that the Robustness Variable is not sent
         in the Query PDU).

         For these networks, this object needs to be set to the same value as
         what is configured on the Querier."
    DEFVAL      { 2 }
    ::= { tlsIgmpSnpgConfigEntry 3 }

tlsIgmpSnpgCfgReportSrcAddress   OBJECT-TYPE
    SYNTAX      IpAddress
    MAX-ACCESS  read-write
    STATUS      current
    DESCRIPTION
        "The value of the object tlsIgmpSnpgCfgReportSrcAddress specifies the
         source IP address used when generating IGMP reports. Although a zero
         source address is allowed according to the IGMPv3 spec, some routers
         seem to drop these zero-source reports."
    DEFVAL      { '00000000'H }
    ::= { tlsIgmpSnpgConfigEntry 4 }

tlsIgmpSnpgCfgMvrAdminState      OBJECT-TYPE
    SYNTAX      AlxIgmpSnpgAdminState
    MAX-ACCESS  read-write
    STATUS      current
    DESCRIPTION
        "The value of the object tlsIgmpSnpgCfgMvrAdminState specifies the
         administrative state of the IGMP snooping Multicast VPLS Registration
         feature associated with this Tls."
    DEFVAL      { disabled }
    ::= { tlsIgmpSnpgConfigEntry 5 }

tlsIgmpSnpgCfgMvrDescription     OBJECT-TYPE
    SYNTAX      TItemDescription
    MAX-ACCESS  read-write
    STATUS      current
    DESCRIPTION
        "The value of the object tlsIgmpSnpgCfgMvrDescription specifies a user
         provided description for the IGMP snooping Multicast VPLS Registration
         configuration associated with this Tls."
    DEFVAL      { "" }
    ::= { tlsIgmpSnpgConfigEntry 6 }

tlsIgmpSnpgCfgMvrPolicy          OBJECT-TYPE
    SYNTAX      TPolicyStatementNameOrEmpty
    MAX-ACCESS  read-write
    STATUS      current
    DESCRIPTION
        "The value of the object tlsIgmpSnpgCfgMvrPolicy specifies the policy
         statement that is applied to decide whether or not a multicast group
         learned on a SAP with the object sapIgmpSnpgCfgMvrFromVplsId set to
         this Tls can be joined to this Tls.

         If an empty string is provided, all groups learned on these SAPs are
         joined without applying a policy."
    DEFVAL      { "" }
    ::= { tlsIgmpSnpgConfigEntry 7 }

tlsIgmpSnpgCfgQuerySrcAddress    OBJECT-TYPE
    SYNTAX      IpAddress
    MAX-ACCESS  read-write
    STATUS      current
    DESCRIPTION
        "The value of the object tlsIgmpSnpgCfgQuerySrcAddress specifies,
         together with the value of object tlsIgmpSnpgCfgQuerySrcAddrType, the
         source IP address used when generating IGMP queries.

         The value of this object is only used when the value of
         tlsIgmpSnpgCfgQuerySrcAddrType is 'querySrcAddr (1)'."
    DEFVAL      { '00000000'H }
    ::= { tlsIgmpSnpgConfigEntry 8 }

tlsIgmpSnpgCfgQuerySrcAddrType   OBJECT-TYPE
    SYNTAX      INTEGER {
        querySrcAddr (1),
        systemIpAddr (2)
    }
    MAX-ACCESS  read-write
    STATUS      current
    DESCRIPTION
        "The value of the object tlsIgmpSnpgCfgQuerySrcAddrType specifies,
         together with the value of object tlsIgmpSnpgCfgQuerySrcAddress, the
         source IP address used when generating IGMP queries.

         When the value of this object is 'querySrcAddr (1)', the value
         configured in tlsIgmpSnpgCfgQuerySrcAddress is used as the query
         source address. When the value of this object is 'systemIpAddr (2)',
         the IP address of the system interface is used."
    DEFVAL      { systemIpAddr }
    ::= { tlsIgmpSnpgConfigEntry 9 }

tlsIgmpSnpgCfgLastChangeTime     OBJECT-TYPE
    SYNTAX      TimeStamp
    MAX-ACCESS  read-only
    STATUS      current
    DESCRIPTION
        "The value of the object tlsIgmpSnpgCfgLastChangeTime indicates the
         sysUpTime at the time of the last modification of this entry."
    ::= { tlsIgmpSnpgConfigEntry 10 }

tlsIgmpSnpgCfgFwdIpv4McastToInt  OBJECT-TYPE
    SYNTAX      TruthValue
    MAX-ACCESS  read-write
    STATUS      current
    DESCRIPTION
        "The value of the object tlsIgmpSnpgCfgFwdIpv4McastToInt specifies
         whether or not to forward IPv4 multicast traffic from the VPLS to the
         Routed-VPLS L3 interface."
    DEFVAL      { false }
    ::= { tlsIgmpSnpgConfigEntry 11 }

tlsIgmpSnpgCfgRvplsMrouter       OBJECT-TYPE
    SYNTAX      TruthValue
    MAX-ACCESS  read-write
    STATUS      current
    DESCRIPTION
        "The value of the object tlsIgmpSnpgCfgRvplsMrouter specifies whether a
         multicast router is attached behind the Routed-VPLS L3 interface."
    DEFVAL      { false }
    ::= { tlsIgmpSnpgConfigEntry 12 }

tlsIgmpSnpgCfgIpMcastEcmp        OBJECT-TYPE
    SYNTAX      TruthValue
    MAX-ACCESS  read-write
    STATUS      current
    DESCRIPTION
        "The value of tlsIgmpSnpgCfgIpMcastEcmp specifies whether ECMP behavior
         is enabled on R-VPLS services on multicast traffic."
    DEFVAL      { false }
    ::= { tlsIgmpSnpgConfigEntry 13 }

tlsIgmpSnpgCfgTxSmetRoutes       OBJECT-TYPE
    SYNTAX      Unsigned32
    MAX-ACCESS  read-only
    STATUS      current
    DESCRIPTION
        "tlsIgmpSnpgCfgTxSmetRoutes is the number of advertised BGP Smet routes
         on this service."
    ::= { tlsIgmpSnpgConfigEntry 14 }

tlsIgmpSnpgQuerierTable          OBJECT-TYPE
    SYNTAX      SEQUENCE OF TlsIgmpSnpgQuerierEntry
    MAX-ACCESS  not-accessible
    STATUS      current
    DESCRIPTION
        "The table tlsIgmpSnpgQuerierTable contains information related to the
         active IGMP Querier found in each Tls Service."
    ::= { alxIgmpSnoopingTlsObjs 2 }

tlsIgmpSnpgQuerierEntry          OBJECT-TYPE
    SYNTAX      TlsIgmpSnpgQuerierEntry
    MAX-ACCESS  not-accessible
    STATUS      current
    DESCRIPTION
        "Each row represents information on the active IGMP Querier within a
         Tls service. Entries in this table cannot be created or deleted via
         SNMP operations. An entry in this table will be created by the agent
         upon detection of an IGMP Querier in a Tls service for which IGMP
         snooping is enabled (via tlsIgmpSnpgCfgAdminState)."
    INDEX       { svcId }
    ::= { tlsIgmpSnpgQuerierTable 1 }

TlsIgmpSnpgQuerierEntry          ::= SEQUENCE
{
    tlsIgmpSnpgQuerierVersion        TmnxIgmpVersion,
    tlsIgmpSnpgQuerierAddress        IpAddress,
    tlsIgmpSnpgQuerierLocale         AlxIgmpSnpgLocation,
    tlsIgmpSnpgQuerierPortId         TmnxPortID,
    tlsIgmpSnpgQuerierEncapValue     TmnxEncapVal,
    tlsIgmpSnpgQuerierSdpId          SdpId,
    tlsIgmpSnpgQuerierVcId           TmnxVcIdOrNone,
    tlsIgmpSnpgQuerierUpTime         TimeTicks,
    tlsIgmpSnpgQuerierExpiryTime     Unsigned32,
    tlsIgmpSnpgQuerierGenQueryIntvl  Unsigned32,
    tlsIgmpSnpgQuerierGenRespIntvl   Unsigned32,
    tlsIgmpSnpgQuerierRobustCount    Unsigned32,
    tlsIgmpSnpgQuerierVRtrId         Unsigned32,
    tlsIgmpSnpgQuerierIfIndex        Unsigned32,
    tlsIgmpSnpgQuerierVTEPAddr       IpAddress,
    tlsIgmpSnpgQuerierVNI            Unsigned32
}

tlsIgmpSnpgQuerierVersion        OBJECT-TYPE
    SYNTAX      TmnxIgmpVersion
    MAX-ACCESS  read-only
    STATUS      current
    DESCRIPTION
        "The value of the object tlsIgmpSnpgQuerierVersion indicates the
         version of the IGMP protocol that is sent by the active IGMP Querier
         detected in this Tls."
    ::= { tlsIgmpSnpgQuerierEntry 1 }

tlsIgmpSnpgQuerierAddress        OBJECT-TYPE
    SYNTAX      IpAddress
    MAX-ACCESS  read-only
    STATUS      current
    DESCRIPTION
        "The value of the object tlsIgmpSnpgQuerierAddress indicates the source
         IP address used by IGMP queries sent out by the active Querier."
    ::= { tlsIgmpSnpgQuerierEntry 2 }

tlsIgmpSnpgQuerierLocale         OBJECT-TYPE
    SYNTAX      AlxIgmpSnpgLocation
    MAX-ACCESS  read-only
    STATUS      current
    DESCRIPTION
        "The value of the object tlsIgmpSnpgQuerierLocale indicates where the
         Querier was detected.

         An IGMP Querier found on a local SAP has the value 'sap(1)'. An IGMP
         Querier detected on an SDP has the value 'sdp(2)'."
    ::= { tlsIgmpSnpgQuerierEntry 3 }

tlsIgmpSnpgQuerierPortId         OBJECT-TYPE
    SYNTAX      TmnxPortID
    MAX-ACCESS  read-only
    STATUS      current
    DESCRIPTION
        "The value of the object tlsIgmpSnpgQuerierPortId indicates, together
         with the object tlsIgmpSnpgQuerierEncapValue, the SAP on which the
         active Querier is detected.

         The value of this object is only meaningful when the value of
         tlsIgmpSnpgQuerierLocale is 'sap(1)'."
    ::= { tlsIgmpSnpgQuerierEntry 4 }

tlsIgmpSnpgQuerierEncapValue     OBJECT-TYPE
    SYNTAX      TmnxEncapVal
    MAX-ACCESS  read-only
    STATUS      current
    DESCRIPTION
        "The value of the object tlsIgmpSnpgQuerierEncapValue indicates,
         together with the object tlsIgmpSnpgQuerierPortId, the SAP on which
         the active Querier is detected.

         The value of this object is only meaningful when the value of
         tlsIgmpSnpgQuerierLocale is 'sap(1)'."
    ::= { tlsIgmpSnpgQuerierEntry 5 }

tlsIgmpSnpgQuerierSdpId          OBJECT-TYPE
    SYNTAX      SdpId
    MAX-ACCESS  read-only
    STATUS      current
    DESCRIPTION
        "The value of the object tlsIgmpSnpgQuerierSdpId indicates, together
         with the object tlsIgmpSnpgQuerierVcId, the SDP Binding on which the
         active Querier is detected.

         The value of this object is only meaningful when the value of
         tlsIgmpSnpgQuerierLocale is 'sdp(2)'."
    ::= { tlsIgmpSnpgQuerierEntry 6 }

tlsIgmpSnpgQuerierVcId           OBJECT-TYPE
    SYNTAX      TmnxVcIdOrNone
    MAX-ACCESS  read-only
    STATUS      current
    DESCRIPTION
        "The value of the object tlsIgmpSnpgQuerierVcId indicates, together
         with the object tlsIgmpSnpgQuerierSdpId, the SDP Binding on which the
         active Querier is detected.

         The value of this object is only meaningful when the value of
         tlsIgmpSnpgQuerierLocale is 'sdp(2)'."
    ::= { tlsIgmpSnpgQuerierEntry 7 }

tlsIgmpSnpgQuerierUpTime         OBJECT-TYPE
    SYNTAX      TimeTicks
    MAX-ACCESS  read-only
    STATUS      current
    DESCRIPTION
        "The value of the object tlsIgmpSnpgQuerierUpTime indicates how long
         (in centiseconds) that this Querier has been known as the current
         active IGMP Querier."
    ::= { tlsIgmpSnpgQuerierEntry 8 }

tlsIgmpSnpgQuerierExpiryTime     OBJECT-TYPE
    SYNTAX      Unsigned32
    UNITS       "seconds"
    MAX-ACCESS  read-only
    STATUS      current
    DESCRIPTION
        "The value of the object tlsIgmpSnpgQuerierExpiryTime indicates the
         time in seconds after which this Querier is no longer known as the
         current active IGMP Querier."
    ::= { tlsIgmpSnpgQuerierEntry 9 }

tlsIgmpSnpgQuerierGenQueryIntvl  OBJECT-TYPE
    SYNTAX      Unsigned32
    UNITS       "seconds"
    MAX-ACCESS  read-only
    STATUS      current
    DESCRIPTION
        "The value of the object tlsIgmpSnpgQuerierGenQueryIntvl indicates the
         General Query Interval used by the active IGMPv3 Querier. For an
         IGMPv1 or IGMPv2 Querier this value is a copy of
         tlsIgmpSnpgCfgGenQueryIntvl."
    ::= { tlsIgmpSnpgQuerierEntry 10 }

tlsIgmpSnpgQuerierGenRespIntvl   OBJECT-TYPE
    SYNTAX      Unsigned32
    UNITS       "deciseconds"
    MAX-ACCESS  read-only
    STATUS      current
    DESCRIPTION
        "The value of the object tlsIgmpSnpgQuerierGenRespIntvl indicates the
         General Query Response interval (in 1/10 seconds) used by the active
         IGMPv3 Querier."
    ::= { tlsIgmpSnpgQuerierEntry 11 }

tlsIgmpSnpgQuerierRobustCount    OBJECT-TYPE
    SYNTAX      Unsigned32
    MAX-ACCESS  read-only
    STATUS      current
    DESCRIPTION
        "The value of the object tlsIgmpSnpgQuerierRobustCount indicates the
         Robust Count value used by the active IGMPv3 Querier. For an IGMPv1 or
         IGMPv2 Querier this value is a copy of tlsIgmpSnpgCfgRobustCount."
    ::= { tlsIgmpSnpgQuerierEntry 12 }

tlsIgmpSnpgQuerierVRtrId         OBJECT-TYPE
    SYNTAX      Unsigned32
    MAX-ACCESS  read-only
    STATUS      current
    DESCRIPTION
        "The value of the object tlsIgmpSnpgQuerierVRtrId indicates together
         with the object tlsIgmpSnpgQuerierIfIndex, the rvpls interface on
         which the active Querier is detected.

         The value of this object is only meaningful when the value of
         tlsIgmpSnpgQuerierLocale is 'rvpls(3)'."
    ::= { tlsIgmpSnpgQuerierEntry 13 }

tlsIgmpSnpgQuerierIfIndex        OBJECT-TYPE
    SYNTAX      Unsigned32
    MAX-ACCESS  read-only
    STATUS      current
    DESCRIPTION
        "The value of the object tlsIgmpSnpgQuerierIfIndex indicates together
         with the object tlsIgmpSnpgQuerierVRtrId, the rvpls interface on which
         the active Querier is detected.

         The value of this object is only meaningful when the value of
         tlsIgmpSnpgQuerierLocale is 'rvpls(3)'."
    ::= { tlsIgmpSnpgQuerierEntry 14 }

tlsIgmpSnpgQuerierVTEPAddr       OBJECT-TYPE
    SYNTAX      IpAddress
    MAX-ACCESS  read-only
    STATUS      current
    DESCRIPTION
        "The value of the object tlsIgmpSnpgQuerierVTEPAddr indicates VXLAN
         (virtual extensible LAN) Tunnel Endpoint address of ethernet VPN
         (EVPN) destination on which the active Querier is detected.

         The value of this object is only meaningful when the value of
         tlsIgmpSnpgQuerierLocale is 'vxlan(4)'."
    ::= { tlsIgmpSnpgQuerierEntry 15 }

tlsIgmpSnpgQuerierVNI            OBJECT-TYPE
    SYNTAX      Unsigned32
    MAX-ACCESS  read-only
    STATUS      current
    DESCRIPTION
        "The value of the object tlsIgmpSnpgQuerierVNI indicates VXLAN (virtual
         extensible LAN) Network Identifier (VNI) of the endpoint of ethernet
         VPN (EVPN) destination interface on which the active Querier is
         detected.

         The value of this object is only meaningful when the value of
         tlsIgmpSnpgQuerierLocale is 'vxlan(4)'."
    ::= { tlsIgmpSnpgQuerierEntry 16 }

tlsIgmpSnpgProxyGroupTable       OBJECT-TYPE
    SYNTAX      SEQUENCE OF TlsIgmpSnpgProxyGroupEntry
    MAX-ACCESS  not-accessible
    STATUS      current
    DESCRIPTION
        "The table tlsIgmpSnpgProxyGroupTable together with the table
         tlsIgmpSnpgProxyGrpSrcTable contains multicast group address
         information collected by IGMP snooping for this Tls. The content of
         this table is used by the system to 'proxy-report' towards the IGMP
         Querier."
    ::= { alxIgmpSnoopingTlsObjs 3 }

tlsIgmpSnpgProxyGroupEntry       OBJECT-TYPE
    SYNTAX      TlsIgmpSnpgProxyGroupEntry
    MAX-ACCESS  not-accessible
    STATUS      current
    DESCRIPTION
        "Each entry in this table contains information about a multicast group
         address known in this Tls. If a group source list is present it is
         described in the corresponding entries of the
         tlsIgmpSnpgProxyGrpSrcTable table."
    INDEX       {
        svcId,
        tlsIgmpSnpgProxyGroupAddress
    }
    ::= { tlsIgmpSnpgProxyGroupTable 1 }

TlsIgmpSnpgProxyGroupEntry       ::= SEQUENCE
{
    tlsIgmpSnpgProxyGroupAddress     IpAddress,
    tlsIgmpSnpgProxyGroupFilterMode  TmnxIgmpGroupFilterMode,
    tlsIgmpSnpgProxyGroupUpTime      TimeTicks
}

tlsIgmpSnpgProxyGroupAddress     OBJECT-TYPE
    SYNTAX      IpAddress
    MAX-ACCESS  not-accessible
    STATUS      current
    DESCRIPTION
        "The value of the object tlsIgmpSnpgProxyGroupAddress indicates the IP
         multicast group address for which this entry contains information."
    ::= { tlsIgmpSnpgProxyGroupEntry 1 }

tlsIgmpSnpgProxyGroupFilterMode  OBJECT-TYPE
    SYNTAX      TmnxIgmpGroupFilterMode
    MAX-ACCESS  read-only
    STATUS      current
    DESCRIPTION
        "The value of the object tlsIgmpSnpgProxyGroupFilterMode indicates the
         filter-mode for this group."
    ::= { tlsIgmpSnpgProxyGroupEntry 2 }

tlsIgmpSnpgProxyGroupUpTime      OBJECT-TYPE
    SYNTAX      TimeTicks
    MAX-ACCESS  read-only
    STATUS      current
    DESCRIPTION
        "The value of the object tlsIgmpSnpgProxyGroupUpTime indicates how long
         (in centiseconds) that the group address already exists in the
         database."
    ::= { tlsIgmpSnpgProxyGroupEntry 3 }

tlsIgmpSnpgProxyGrpSrcTable      OBJECT-TYPE
    SYNTAX      SEQUENCE OF TlsIgmpSnpgProxyGrpSrcEntry
    MAX-ACCESS  not-accessible
    STATUS      current
    DESCRIPTION
        "The table tlsIgmpSnpgProxyGrpSrcTable lists the IPv4 multicast Sources
         corresponding to the IPv4 multicast groups listed in the
         tlsIgmpSnpgProxyGroupTable."
    ::= { alxIgmpSnoopingTlsObjs 4 }

tlsIgmpSnpgProxyGrpSrcEntry      OBJECT-TYPE
    SYNTAX      TlsIgmpSnpgProxyGrpSrcEntry
    MAX-ACCESS  not-accessible
    STATUS      current
    DESCRIPTION
        "tlsIgmpSnpgProxyGrpSrcEntry describes an entry in the
         tlsIgmpSnpgProxyGrpSrcTable. Each entry represents an IPv4 multicast
         Source for which the system is interested/not interested in receiving
         multicast traffic from."
    INDEX       {
        svcId,
        tlsIgmpSnpgProxyGroupAddress,
        tlsIgmpSnpgProxyGrpSrcAddr
    }
    ::= { tlsIgmpSnpgProxyGrpSrcTable 1 }

TlsIgmpSnpgProxyGrpSrcEntry      ::= SEQUENCE
{
    tlsIgmpSnpgProxyGrpSrcAddr       IpAddress,
    tlsIgmpSnpgProxyGrpSrcUpTime     TimeTicks
}

tlsIgmpSnpgProxyGrpSrcAddr       OBJECT-TYPE
    SYNTAX      IpAddress
    MAX-ACCESS  not-accessible
    STATUS      current
    DESCRIPTION
        "The value of the object tlsIgmpSnpgProxyGrpSrcAddr indicates the IPv4
         multicast Source address."
    ::= { tlsIgmpSnpgProxyGrpSrcEntry 1 }

tlsIgmpSnpgProxyGrpSrcUpTime     OBJECT-TYPE
    SYNTAX      TimeTicks
    MAX-ACCESS  read-only
    STATUS      current
    DESCRIPTION
        "The value of the object tlsIgmpSnpgProxyGrpSrcUpTime indicates how
         long (in centiseconds) that the Source address already exists in the
         database."
    ::= { tlsIgmpSnpgProxyGrpSrcEntry 2 }

tlsIgmpSnpgMRouterTable          OBJECT-TYPE
    SYNTAX      SEQUENCE OF TlsIgmpSnpgMRouterEntry
    MAX-ACCESS  not-accessible
    STATUS      current
    DESCRIPTION
        "The table tlsIgmpSnpgMRouterTable contains information related to the
         multicast routers found in each Tls Service."
    ::= { alxIgmpSnoopingTlsObjs 5 }

tlsIgmpSnpgMRouterEntry          OBJECT-TYPE
    SYNTAX      TlsIgmpSnpgMRouterEntry
    MAX-ACCESS  not-accessible
    STATUS      current
    DESCRIPTION
        "Each row contains information about one specific multicast router
         known within a Tls service. Entries in this table cannot be created or
         deleted via SNMP operations. An entry in this table will be created by
         the agent upon detection of a multicast router in a Tls service for
         which IGMP snooping is enabled (via tlsIgmpSnpgCfgAdminState)."
    INDEX       {
        svcId,
        tlsIgmpSnpgMRouterAddress
    }
    ::= { tlsIgmpSnpgMRouterTable 1 }

TlsIgmpSnpgMRouterEntry          ::= SEQUENCE
{
    tlsIgmpSnpgMRouterAddress        IpAddress,
    tlsIgmpSnpgMRouterLocale         AlxIgmpSnpgLocation,
    tlsIgmpSnpgMRouterPortId         TmnxPortID,
    tlsIgmpSnpgMRouterEncapValue     TmnxEncapVal,
    tlsIgmpSnpgMRouterSdpId          SdpId,
    tlsIgmpSnpgMRouterVcId           TmnxVcIdOrNone,
    tlsIgmpSnpgMRouterVersion        TmnxIgmpVersion,
    tlsIgmpSnpgMRouterExpiryTime     Unsigned32,
    tlsIgmpSnpgMRouterUpTime         TimeTicks,
    tlsIgmpSnpgMRouterGenQueryIntvl  Unsigned32,
    tlsIgmpSnpgMRouterGenRespIntvl   Unsigned32,
    tlsIgmpSnpgMRouterRobustCount    Unsigned32,
    tlsIgmpSnpgMRouterVRtrId         Unsigned32,
    tlsIgmpSnpgMRouterIfIndex        Unsigned32,
    tlsIgmpSnpgMRouterVTEPAddr       IpAddress,
    tlsIgmpSnpgMRouterVNI            Unsigned32
}

tlsIgmpSnpgMRouterAddress        OBJECT-TYPE
    SYNTAX      IpAddress
    MAX-ACCESS  read-only
    STATUS      current
    DESCRIPTION
        "The value of the object tlsIgmpSnpgMRouterAddress indicates the source
         IP address used by IGMP queries sent out by this multicast router."
    ::= { tlsIgmpSnpgMRouterEntry 1 }

tlsIgmpSnpgMRouterLocale         OBJECT-TYPE
    SYNTAX      AlxIgmpSnpgLocation
    MAX-ACCESS  read-only
    STATUS      current
    DESCRIPTION
        "The value of the object tlsIgmpSnpgMRouterLocale indicates where this
         multicast router was detected.

         A multicast router found on a local SAP has the value 'sap(1)'. A
         multicast router detected on an SDP has the value 'sdp(2)'."
    ::= { tlsIgmpSnpgMRouterEntry 2 }

tlsIgmpSnpgMRouterPortId         OBJECT-TYPE
    SYNTAX      TmnxPortID
    MAX-ACCESS  read-only
    STATUS      current
    DESCRIPTION
        "The value of the object tlsIgmpSnpgMRouterPortId indicates, together
         with the object tlsIgmpSnpgMRouterEncapValue, the SAP on which this
         multicast router is detected.

         The value of this object is only meaningful when the value of
         tlsIgmpSnpgMRouterLocale is 'sap(1)'."
    ::= { tlsIgmpSnpgMRouterEntry 3 }

tlsIgmpSnpgMRouterEncapValue     OBJECT-TYPE
    SYNTAX      TmnxEncapVal
    MAX-ACCESS  read-only
    STATUS      current
    DESCRIPTION
        "The value of the object tlsIgmpSnpgMRouterEncapValue indicates,
         together with the object tlsIgmpSnpgMRouterPortId, the SAP on which
         this multicast router is detected.

         The value of this object is only meaningful when the value of
         tlsIgmpSnpgMRouterLocale is 'sap(1)'."
    ::= { tlsIgmpSnpgMRouterEntry 4 }

tlsIgmpSnpgMRouterSdpId          OBJECT-TYPE
    SYNTAX      SdpId
    MAX-ACCESS  read-only
    STATUS      current
    DESCRIPTION
        "The value of the object tlsIgmpSnpgMRouterSdpId indicates, together
         with the object tlsIgmpSnpgMRouterVcId, the SDP Bind on which this
         multicast router is detected.

         The value of this object is only meaningful when the value of
         tlsIgmpSnpgMRouterLocale is 'sdp(2)'."
    ::= { tlsIgmpSnpgMRouterEntry 5 }

tlsIgmpSnpgMRouterVcId           OBJECT-TYPE
    SYNTAX      TmnxVcIdOrNone
    MAX-ACCESS  read-only
    STATUS      current
    DESCRIPTION
        "The value of the object tlsIgmpSnpgMRouterVcId indicates, together
         with the object tlsIgmpSnpgMRouterSdpId, the SDP Bind on which this
         multicast router is detected.

         The value of this object is only meaningful when the value of
         tlsIgmpSnpgMRouterLocale is 'sdp(2)'."
    ::= { tlsIgmpSnpgMRouterEntry 6 }

tlsIgmpSnpgMRouterVersion        OBJECT-TYPE
    SYNTAX      TmnxIgmpVersion
    MAX-ACCESS  read-only
    STATUS      current
    DESCRIPTION
        "The value of the object tlsIgmpSnpgMRouterVersion indicates the
         version of the IGMP protocol used by this multicast router."
    ::= { tlsIgmpSnpgMRouterEntry 7 }

tlsIgmpSnpgMRouterExpiryTime     OBJECT-TYPE
    SYNTAX      Unsigned32
    UNITS       "seconds"
    MAX-ACCESS  read-only
    STATUS      current
    DESCRIPTION
        "The value of the object tlsIgmpSnpgMRouterExpiryTime indicates the
         time in seconds after which this multicast router is no longer known
         in this Tls."
    ::= { tlsIgmpSnpgMRouterEntry 8 }

tlsIgmpSnpgMRouterUpTime         OBJECT-TYPE
    SYNTAX      TimeTicks
    MAX-ACCESS  read-only
    STATUS      current
    DESCRIPTION
        "The value of the object tlsIgmpSnpgMRouterUpTime indicates how long
         (in centiseconds) that this multicast router has been known in this
         Tls."
    ::= { tlsIgmpSnpgMRouterEntry 9 }

tlsIgmpSnpgMRouterGenQueryIntvl  OBJECT-TYPE
    SYNTAX      Unsigned32
    UNITS       "seconds"
    MAX-ACCESS  read-only
    STATUS      current
    DESCRIPTION
        "The value of the object tlsIgmpSnpgMRouterGenQueryIntvl indicates the
         General Query Interval used by this multicast router in case of
         IGMPv3. For an IGMPv1 or IGMPv2 multicast router this value is a copy
         of tlsIgmpSnpgCfgGenQueryIntvl."
    ::= { tlsIgmpSnpgMRouterEntry 10 }

tlsIgmpSnpgMRouterGenRespIntvl   OBJECT-TYPE
    SYNTAX      Unsigned32
    UNITS       "deciseconds"
    MAX-ACCESS  read-only
    STATUS      current
    DESCRIPTION
        "The value of the object tlsIgmpSnpgMRouterGenRespIntvl indicates the
         General Query Response interval (in 1/10 seconds) used by this
         multicast router in case of IGMPv3."
    ::= { tlsIgmpSnpgMRouterEntry 11 }

tlsIgmpSnpgMRouterRobustCount    OBJECT-TYPE
    SYNTAX      Unsigned32
    MAX-ACCESS  read-only
    STATUS      current
    DESCRIPTION
        "The value of the object tlsIgmpSnpgMRouterRobustCount indicates the
         Robust Count value used by this multicast router in case of IGMPv3.
         For an IGMPv1 or IGMPv2 multicast router this value is a copy of
         tlsIgmpSnpgCfgRobustCount."
    ::= { tlsIgmpSnpgMRouterEntry 12 }

tlsIgmpSnpgMRouterVRtrId         OBJECT-TYPE
    SYNTAX      Unsigned32
    MAX-ACCESS  read-only
    STATUS      current
    DESCRIPTION
        "The value of the object tlsIgmpSnpgMRouterVRtrId indicates, together
         with the object tlsIgmpSnpgMRouterIfIndex, the rvpls interface on
         which this multicast router is detected.

         The value of this object is only meaningful when the value of
         tlsIgmpSnpgMRouterLocale is 'rvpls(3)'."
    ::= { tlsIgmpSnpgMRouterEntry 13 }

tlsIgmpSnpgMRouterIfIndex        OBJECT-TYPE
    SYNTAX      Unsigned32
    MAX-ACCESS  read-only
    STATUS      current
    DESCRIPTION
        "The value of the object tlsIgmpSnpgMRouterIfIndex indicates, together
         with the object tlsIgmpSnpgMRouterVRtrId, the rvpls interface on which
         this multicast router is detected.

         The value of this object is only meaningful when the value of
         tlsIgmpSnpgMRouterLocale is 'rvpls(3)'."
    ::= { tlsIgmpSnpgMRouterEntry 14 }

tlsIgmpSnpgMRouterVTEPAddr       OBJECT-TYPE
    SYNTAX      IpAddress
    MAX-ACCESS  read-only
    STATUS      current
    DESCRIPTION
        "The value of the object tlsIgmpSnpgMRouterVTEPAddr indicates VXLAN
         (virtual extensible LAN) Tunnel Endpoint address of ethernet VPN
         (EVPN) destination on which this multicast router is detected.

         The value of this object is only meaningful when the value of
         tlsIgmpSnpgMRouterLocale is 'vxlan(4)'."
    ::= { tlsIgmpSnpgMRouterEntry 15 }

tlsIgmpSnpgMRouterVNI            OBJECT-TYPE
    SYNTAX      Unsigned32
    MAX-ACCESS  read-only
    STATUS      current
    DESCRIPTION
        "The value of the object tlsIgmpSnpgMRouterVNI indicates VXLAN (virtual
         extensible LAN) Network Identifier (VNI) of the endpoint of ethernet
         VPN (EVPN) destination interface on which this multicast router is
         detected.

         The value of this object is only meaningful when the value of
         tlsIgmpSnpgMRouterLocale is 'vxlan(4)'."
    ::= { tlsIgmpSnpgMRouterEntry 16 }

alxIgmpSnoopingSapObjs           OBJECT IDENTIFIER ::= { alxIgmpSnoopingObjs 2 }

sapIgmpSnpgConfigTable           OBJECT-TYPE
    SYNTAX      SEQUENCE OF SapIgmpSnpgConfigEntry
    MAX-ACCESS  not-accessible
    STATUS      current
    DESCRIPTION
        "The  sapIgmpSnpgConfigTable contains objects to
         configure the IGMP snooping feature on a SAP within a
         Tls."
    ::= { alxIgmpSnoopingSapObjs 1 }

sapIgmpSnpgConfigEntry           OBJECT-TYPE
    SYNTAX      SapIgmpSnpgConfigEntry
    MAX-ACCESS  not-accessible
    STATUS      current
    DESCRIPTION
        "Each row contains IGMP snooping configuration parameters for a SAP
         within a Tls. Entries in this table cannot be created or deleted via
         SNMP operations. An entry in this table will be created by the agent
         upon creation of a new SAP (sapTlsInfoTable). The entry is destroyed
         when the SAP or Tls service is removed."
    INDEX       {
        svcId,
        sapPortId,
        sapEncapValue
    }
    ::= { sapIgmpSnpgConfigTable 1 }

SapIgmpSnpgConfigEntry           ::= SEQUENCE
{
    sapIgmpSnpgCfgImportPlcy         TPolicyStatementNameOrEmpty,
    sapIgmpSnpgCfgFastLeave          AlxIgmpSnpgAdminState,
    sapIgmpSnpgCfgMRouter            TruthValue,
    sapIgmpSnpgCfgSendQueries        AlxIgmpSnpgAdminState,
    sapIgmpSnpgCfgGenQueryIntvl      Unsigned32,
    sapIgmpSnpgCfgQueryRespIntvl     Unsigned32,
    sapIgmpSnpgCfgRobustCount        Unsigned32,
    sapIgmpSnpgCfgLastMembIntvl      Unsigned32,
    sapIgmpSnpgCfgMaxNbrGrps         Integer32,
    sapIgmpSnpgCfgMvrFromVplsId      TmnxServId,
    sapIgmpSnpgCfgMvrToSapPortId     TmnxPortID,
    sapIgmpSnpgCfgMvrToSapEncapVal   TmnxEncapVal,
    sapIgmpSnpgCfgVersion            TmnxIgmpVersion,
    sapIgmpSnpgCfgMcacPolicyName     TPolicyStatementNameOrEmpty,
    sapIgmpSnpgCfgMcacUnconstBW      Integer32,
    sapIgmpSnpgCfgMcacConstAdmSt     TmnxAdminState,
    sapIgmpSnpgCfgMcacPrRsvMndBW     Integer32,
    sapIgmpSnpgCfgMcacinUseMandBw    Unsigned32,
    sapIgmpSnpgCfgMcacinUseOpnlBw    Unsigned32,
    sapIgmpSnpgCfgMcacAvailMandBw    Unsigned32,
    sapIgmpSnpgCfgMcacAvailOpnlBw    Unsigned32,
    sapIgmpSnpgCfgMcacValInTrans     TruthValue,
    sapIgmpSnpgCfgLastChangeTime     TimeStamp,
    sapIgmpSnpgCfgMaxNbrSrcs         Unsigned32,
    sapIgmpSnpgCfgDisRtrAlertChk     TruthValue,
    sapIgmpSnpgCfgMaxNbrGrpSrcs      Unsigned32,
    sapIgmpSnpgCfgMcacUseLagPortWt   TruthValue,
    sapIgmpSnpgCfgMcacIfPolicyName   TPolicyStatementNameOrEmpty
}

sapIgmpSnpgCfgImportPlcy         OBJECT-TYPE
    SYNTAX      TPolicyStatementNameOrEmpty
    MAX-ACCESS  read-write
    STATUS      current
    DESCRIPTION
        "The value of the object sapIgmpSnpgCfgImportPlcy specifies the policy
         statement that must be applied to all incoming IGMP messages on this
         SAP."
    DEFVAL      { "" }
    ::= { sapIgmpSnpgConfigEntry 1 }

sapIgmpSnpgCfgFastLeave          OBJECT-TYPE
    SYNTAX      AlxIgmpSnpgAdminState
    MAX-ACCESS  read-write
    STATUS      current
    DESCRIPTION
        "The value of the object sapIgmpSnpgCfgFastLeave specifies whether fast
         leave is allowed on this SAP.

         If set to 'enabled(1)', the system prunes the port on which an IGMP
         'leave' message has been received without waiting for the Group
         Specific Query to timeout."
    DEFVAL      { disabled }
    ::= { sapIgmpSnpgConfigEntry 2 }

sapIgmpSnpgCfgMRouter            OBJECT-TYPE
    SYNTAX      TruthValue
    MAX-ACCESS  read-write
    STATUS      current
    DESCRIPTION
        "The value of the object sapIgmpSnpgCfgMRouter specifies whether a
         multicast router is attached behind this SAP.

         If sapIgmpSnpgCfgSendQueries is set to 'enabled(1)', the system acts
         as if this object was set to 'false(2)'."
    DEFVAL      { false }
    ::= { sapIgmpSnpgConfigEntry 3 }

sapIgmpSnpgCfgSendQueries        OBJECT-TYPE
    SYNTAX      AlxIgmpSnpgAdminState
    MAX-ACCESS  read-write
    STATUS      current
    DESCRIPTION
        "The value of the object sapIgmpSnpgCfgSendQueries specifies whether
         the system generates General Queries by itself on this SAP."
    DEFVAL      { disabled }
    ::= { sapIgmpSnpgConfigEntry 4 }

sapIgmpSnpgCfgGenQueryIntvl      OBJECT-TYPE
    SYNTAX      Unsigned32 (2..1024)
    UNITS       "seconds"
    MAX-ACCESS  read-write
    STATUS      current
    DESCRIPTION
        "The value of the object sapIgmpSnpgCfgGenQueryIntvl specifies the
         interval (in seconds) between two consecutive general queries sent by
         the system on this SAP.

         The value of this object is only meaningful when the value of
         sapIgmpSnpgCfgSendQueries is 'enabled(1)'."
    DEFVAL      { 125 }
    ::= { sapIgmpSnpgConfigEntry 5 }

sapIgmpSnpgCfgQueryRespIntvl     OBJECT-TYPE
    SYNTAX      Unsigned32 (1..1023)
    UNITS       "seconds"
    MAX-ACCESS  read-write
    STATUS      current
    DESCRIPTION
        "The value of the object sapIgmpSnpgCfgQueryRespIntvl specifies the
         maximum response time (in seconds) advertised in IGMPv2/v3 queries.

         The value of this object is only meaningful when the value of
         sapIgmpSnpgCfgSendQueries is 'enabled(1)'."
    DEFVAL      { 10 }
    ::= { sapIgmpSnpgConfigEntry 6 }

sapIgmpSnpgCfgRobustCount        OBJECT-TYPE
    SYNTAX      Unsigned32 (2..7)
    MAX-ACCESS  read-write
    STATUS      current
    DESCRIPTION
        "The value of the object sapIgmpSnpgCfgRobustCount specifies the
         robustness variable on this SAP.

         This object allows tuning for the expected packet loss on this SAP. If
         a SAP is expected to be lossy, the Robustness Variable may be
         increased. IGMP snooping is robust to (Robustness Variable-1) packet
         losses.

         The value of this object is only meaningful when the value of
         sapIgmpSnpgCfgSendQueries is 'enabled(1)'."
    DEFVAL      { 2 }
    ::= { sapIgmpSnpgConfigEntry 7 }

sapIgmpSnpgCfgLastMembIntvl      OBJECT-TYPE
    SYNTAX      Unsigned32 (1..50)
    UNITS       "deciseconds"
    MAX-ACCESS  read-write
    STATUS      current
    DESCRIPTION
        "The value of the object sapIgmpSnpgCfgLastMembIntvl specifies the Max
         Response Time (in deciseconds) used in Group-Specific and
         Group-Source-Specific Queries sent in response to 'leave' messages.
         This is also the amount of time between Group-Specific Query messages.

         This value may be tuned to modify the leave latency of the network. A
         reduced value results in reduced time to detect the loss of the last
         member of a group."
    DEFVAL      { 10 }
    ::= { sapIgmpSnpgConfigEntry 8 }

sapIgmpSnpgCfgMaxNbrGrps         OBJECT-TYPE
    SYNTAX      Integer32 (0..16000)
    MAX-ACCESS  read-write
    STATUS      current
    DESCRIPTION
        "The value of the object sapIgmpSnpgCfgMaxNbrGrps specifies how many
         group addresses are allowed for this SAP.

         The value 0 means that no limit is imposed."
    DEFVAL      { 0 }
    ::= { sapIgmpSnpgConfigEntry 9 }

sapIgmpSnpgCfgMvrFromVplsId      OBJECT-TYPE
    SYNTAX      TmnxServId
    MAX-ACCESS  read-write
    STATUS      current
    DESCRIPTION
        "The value of the object sapIgmpSnpgCfgMvrFromVplsId specifies from
         which Tls the multicast streams corresponding to the groups learned
         via this SAP are copied.

         Groups which cannot be joined to the corresponding MVR Tls (because
         MVR is not up or the configured MVR policy rejects the group) copy the
         multicast streams from the local Tls if IGMP snooping is up (i.e.
         tlsIgmpSnpgCfgAdminState is 'enabled(1)')."
    DEFVAL      { 0 }
    ::= { sapIgmpSnpgConfigEntry 10 }

sapIgmpSnpgCfgMvrToSapPortId     OBJECT-TYPE
    SYNTAX      TmnxPortID
    MAX-ACCESS  read-write
    STATUS      current
    DESCRIPTION
        "The value of the object sapIgmpSnpgCfgMvrToSapPortId specifies,
         together with sapIgmpSnpgCfgMvrToSapEncapVal, the SAP to which the
         multicast streams corresponding to the groups learned via this SAP are
         copied. As a consequence, the streams will not exit this SAP anymore."
    DEFVAL      { 0 }
    ::= { sapIgmpSnpgConfigEntry 11 }

sapIgmpSnpgCfgMvrToSapEncapVal   OBJECT-TYPE
    SYNTAX      TmnxEncapVal
    MAX-ACCESS  read-write
    STATUS      current
    DESCRIPTION
        "The value of the object sapIgmpSnpgCfgMvrToSapEncapVal specifies,
         together with sapIgmpSnpgCfgMvrToSapPortId, the SAP to which the
         multicast streams corresponding to the groups learned via this SAP are
         copied. As a consequence, the streams will not exit this SAP anymore."
    DEFVAL      { 0 }
    ::= { sapIgmpSnpgConfigEntry 12 }

sapIgmpSnpgCfgVersion            OBJECT-TYPE
    SYNTAX      TmnxIgmpVersion
    MAX-ACCESS  read-write
    STATUS      current
    DESCRIPTION
        "The value of the object sapIgmpSnpgCfgVersion specifies the version of
         IGMP running on this SAP."
    DEFVAL      { version3 }
    ::= { sapIgmpSnpgConfigEntry 13 }

sapIgmpSnpgCfgMcacPolicyName     OBJECT-TYPE
    SYNTAX      TPolicyStatementNameOrEmpty
    MAX-ACCESS  read-write
    STATUS      current
    DESCRIPTION
        "The value of sapIgmpSnpgCfgMcacPolicyName specifies the name of the
         multicast CAC (Connection Admission Control) policy."
    DEFVAL      { "" }
    ::= { sapIgmpSnpgConfigEntry 14 }

sapIgmpSnpgCfgMcacUnconstBW      OBJECT-TYPE
    SYNTAX      Integer32 (-1..2147483647)
    UNITS       "kilobps"
    MAX-ACCESS  read-write
    STATUS      current
    DESCRIPTION
        "The value of sapIgmpSnpgCfgMcacUnconstBW specifies the bandwidth
         assigned for interface's multicast CAC policy traffic in kilobits per
         second(kbps).

         If the default value of '-1' is set, there is no constraint on
         bandwidth allocated at the interface.

         If the value of sapIgmpSnpgCfgMcacUnconstBW is set to '0' and if a
         multicast CAC policy is assigned on the interface, then no group
         (channel) from that policy is allowed on that interface."
    DEFVAL      { -1 }
    ::= { sapIgmpSnpgConfigEntry 15 }

sapIgmpSnpgCfgMcacConstAdmSt     OBJECT-TYPE
    SYNTAX      TmnxAdminState
    MAX-ACCESS  read-write
    STATUS      current
    DESCRIPTION
        "The value of sapIgmpSnpgCfgMcacConstAdmSt specifies the administrative
         state of the multicast CAC policy's constraints."
    DEFVAL      { inService }
    ::= { sapIgmpSnpgConfigEntry 16 }

sapIgmpSnpgCfgMcacPrRsvMndBW     OBJECT-TYPE
    SYNTAX      Integer32 (-1..2147483647)
    UNITS       "kilobps"
    MAX-ACCESS  read-write
    STATUS      current
    DESCRIPTION
        "The value of sapIgmpSnpgCfgMcacPrRsvMndBW specifies the bandwidth
         pre-reserved for all the mandatory channels on a given interface in
         kilobits per second(kbps).

         If the value of sapIgmpSnpgCfgMcacUnconstBW is '0', no mandatory
         channels are allowed. If the value of sapIgmpSnpgCfgMcacPrRsvMndBW is
         '-1', then all mandatory and optional channels are allowed.

         If the value of sapIgmpSnpgCfgMcacPrRsvMndBW is equal to the value of
         sapIgmpSnpgCfgMcacUnconstBW, then all the unconstrained bandwidth on a
         given interface is allocated to mandatory channels configured through
         multicast CAC policy on that interface and no optional groups
         (channels) are allowed.

         The value of sapIgmpSnpgCfgMcacPrRsvMndBW should always be less than
         or equal to that of sapIgmpSnpgCfgMcacUnconstBW. An attempt to set the
         value of sapIgmpSnpgCfgMcacPrRsvMndBW greater than that of
         sapIgmpSnpgCfgMcacUnconstBW will result in inconsistent value error."
    DEFVAL      { -1 }
    ::= { sapIgmpSnpgConfigEntry 17 }

sapIgmpSnpgCfgMcacinUseMandBw    OBJECT-TYPE
    SYNTAX      Unsigned32
    UNITS       "kilobps"
    MAX-ACCESS  read-only
    STATUS      current
    DESCRIPTION
        "The value of sapIgmpSnpgCfgMcacinUseMandBw indicates the in-use
         bandwidth in kilobits per second(kbps) for the mandatory channels for
         this protocol interface instance."
    ::= { sapIgmpSnpgConfigEntry 18 }

sapIgmpSnpgCfgMcacinUseOpnlBw    OBJECT-TYPE
    SYNTAX      Unsigned32
    UNITS       "kilobps"
    MAX-ACCESS  read-only
    STATUS      current
    DESCRIPTION
        "The value of sapIgmpSnpgCfgMcacinUseOpnlBw indicates the in-use
         bandwidth in kilobits per second(kbps) for the optional channels for
         this protocol interface instance."
    ::= { sapIgmpSnpgConfigEntry 19 }

sapIgmpSnpgCfgMcacAvailMandBw    OBJECT-TYPE
    SYNTAX      Unsigned32
    UNITS       "kilobps"
    MAX-ACCESS  read-only
    STATUS      current
    DESCRIPTION
        "The value of sapIgmpSnpgCfgMcacAvailMandBw indicates the pre-reserved
         bandwidth in kilobits per second(kbps) for the mandatory channels for
         this interface instance."
    ::= { sapIgmpSnpgConfigEntry 20 }

sapIgmpSnpgCfgMcacAvailOpnlBw    OBJECT-TYPE
    SYNTAX      Unsigned32
    UNITS       "kilobps"
    MAX-ACCESS  read-only
    STATUS      current
    DESCRIPTION
        "The value of sapIgmpSnpgCfgMcacAvailOpnlBw indicates the available
         bandwidth in kilobits per second(kbps) for this interface instance."
    ::= { sapIgmpSnpgConfigEntry 21 }

sapIgmpSnpgCfgMcacValInTrans     OBJECT-TYPE
    SYNTAX      TruthValue
    MAX-ACCESS  read-only
    STATUS      current
    DESCRIPTION
        "The value of sapIgmpSnpgCfgMcacValInTrans indicates that the
         operational (available and in-use mandatory/optional) value for the
         following objects are in transition due to configuration change:

         sapIgmpSnpgCfgMcacinUseMandBw sapIgmpSnpgCfgMcacinUseOpnlBw
         sapIgmpSnpgCfgMcacAvailMandBw sapIgmpSnpgCfgMcacAvailOpnlBw

         When multicast CAC Policy is applied on the interface for the join of
         the next channel, the operational values will be recalculated and
         applied to the above objects and the value for
         sapIgmpSnpgCfgMcacValInTrans will be set to 'false(2)'.

         If the value of sapIgmpSnpgCfgMcacValInTrans is 'true(1)' then the
         values are in transition."
    ::= { sapIgmpSnpgConfigEntry 22 }

sapIgmpSnpgCfgLastChangeTime     OBJECT-TYPE
    SYNTAX      TimeStamp
    MAX-ACCESS  read-only
    STATUS      current
    DESCRIPTION
        "The value of the object sapIgmpSnpgCfgLastChangeTime indicates the
         sysUpTime at the time of the last modification of this entry."
    ::= { sapIgmpSnpgConfigEntry 23 }

sapIgmpSnpgCfgMaxNbrSrcs         OBJECT-TYPE
    SYNTAX      Unsigned32 (0..1000)
    MAX-ACCESS  read-write
    STATUS      current
    DESCRIPTION
        "The value of the object sapIgmpSnpgCfgMaxNbrSrcs specifies how many
         source addresses are allowed per group address for this SAP.

         The value 0 means that no limit is imposed."
    DEFVAL      { 0 }
    ::= { sapIgmpSnpgConfigEntry 24 }

sapIgmpSnpgCfgDisRtrAlertChk     OBJECT-TYPE
    SYNTAX      TruthValue
    MAX-ACCESS  read-write
    STATUS      current
    DESCRIPTION
        "sapIgmpSnpgCfgDisRtrAlertChk is used to enable/disable router alert
         checking for IGMP messages received on this sap.

         If this flag is set to 'true', checking is disabled."
    DEFVAL      { false }
    ::= { sapIgmpSnpgConfigEntry 25 }

sapIgmpSnpgCfgMaxNbrGrpSrcs      OBJECT-TYPE
    SYNTAX      Unsigned32 (0..32000)
    MAX-ACCESS  read-write
    STATUS      current
    DESCRIPTION
        "The value of the object sapIgmpSnpgCfgMaxNbrGrpSrcs specifies how many
         group source addresses are allowed per group address for this SAP.

         The value 0 means that no limit is imposed."
    DEFVAL      { 0 }
    ::= { sapIgmpSnpgConfigEntry 26 }

sapIgmpSnpgCfgMcacUseLagPortWt   OBJECT-TYPE
    SYNTAX      TruthValue
    MAX-ACCESS  read-write
    STATUS      current
    DESCRIPTION
        "The value of sapIgmpSnpgCfgMcacUseLagPortWt specifies if this system
         must use the LAG port weight while calculating Multicast CAC
         constraints.

         The LAG port weight is configured with the object
         TIMETRA-LAG-MIB::tLagPortWeightSpeed."
    DEFVAL      { false }
    ::= { sapIgmpSnpgConfigEntry 27 }

sapIgmpSnpgCfgMcacIfPolicyName   OBJECT-TYPE
    SYNTAX      TPolicyStatementNameOrEmpty
    MAX-ACCESS  read-write
    STATUS      current
    DESCRIPTION
        "The value of sapIgmpSnpgCfgMcacIfPolicyName specifies the name of the
         multicast CAC (Connection Admission Control) interface policy."
    DEFVAL      { "" }
    ::= { sapIgmpSnpgConfigEntry 28 }

sapIgmpSnpgGroupTable            OBJECT-TYPE
    SYNTAX      SEQUENCE OF SapIgmpSnpgGroupEntry
    MAX-ACCESS  not-accessible
    STATUS      current
    DESCRIPTION
        "sapIgmpSnpgGroupTable together with the table sapIgmpSnpgGrpSrcTable
         contains multicast group address information collected by IGMP
         snooping for each SAP."
    ::= { alxIgmpSnoopingSapObjs 2 }

sapIgmpSnpgGroupEntry            OBJECT-TYPE
    SYNTAX      SapIgmpSnpgGroupEntry
    MAX-ACCESS  not-accessible
    STATUS      current
    DESCRIPTION
        "Each entry in this table indicates a multicast group address learned
         by IGMP snooping on this SAP. If a Source list is present it is
         described in the corresponding entries of the sapIgmpSnpgGrpSrcTable
         table."
    INDEX       {
        svcId,
        sapPortId,
        sapEncapValue,
        sapIgmpSnpgGrpAddress
    }
    ::= { sapIgmpSnpgGroupTable 1 }

SapIgmpSnpgGroupEntry            ::= SEQUENCE
{
    sapIgmpSnpgGrpAddress            IpAddress,
    sapIgmpSnpgGrpType               TmnxIgmpGroupType,
    sapIgmpSnpgGrpFilterMode         TmnxIgmpGroupFilterMode,
    sapIgmpSnpgGrpUpTime             TimeTicks,
    sapIgmpSnpgGrpExpiryTime         Unsigned32,
    sapIgmpSnpgGrpCompatMode         Unsigned32,
    sapIgmpSnpgGrpV1HostExpTime      Unsigned32,
    sapIgmpSnpgGrpV2HostExpTime      Unsigned32,
    sapIgmpSnpgGrpMvrFromVplsId      TmnxServId,
    sapIgmpSnpgGrpMvrToSapPortId     TmnxPortID,
    sapIgmpSnpgGrpMvrToSapEncapVal   TmnxEncapVal
}

sapIgmpSnpgGrpAddress            OBJECT-TYPE
    SYNTAX      IpAddress
    MAX-ACCESS  not-accessible
    STATUS      current
    DESCRIPTION
        "The value of the object sapIgmpSnpgGrpAddress indicates the IPv4
         multicast group address for which this entry contains information."
    ::= { sapIgmpSnpgGroupEntry 1 }

sapIgmpSnpgGrpType               OBJECT-TYPE
    SYNTAX      TmnxIgmpGroupType
    MAX-ACCESS  read-only
    STATUS      current
    DESCRIPTION
        "The value of the object sapIgmpSnpgGrpType indicates whether this
         entry was learned dynamically or was statically configured."
    ::= { sapIgmpSnpgGroupEntry 2 }

sapIgmpSnpgGrpFilterMode         OBJECT-TYPE
    SYNTAX      TmnxIgmpGroupFilterMode
    MAX-ACCESS  read-only
    STATUS      current
    DESCRIPTION
        "The value of the object sapIgmpSnpgGrpFilterMode indicates the
         filter-mode for this group."
    ::= { sapIgmpSnpgGroupEntry 3 }

sapIgmpSnpgGrpUpTime             OBJECT-TYPE
    SYNTAX      TimeTicks
    MAX-ACCESS  read-only
    STATUS      current
    DESCRIPTION
        "The value of the object sapIgmpSnpgGrpUpTime indicates how long (in
         centiseconds) that the group address already exists in the database
         for this SAP."
    ::= { sapIgmpSnpgGroupEntry 4 }

sapIgmpSnpgGrpExpiryTime         OBJECT-TYPE
    SYNTAX      Unsigned32
    UNITS       "seconds"
    MAX-ACCESS  read-only
    STATUS      current
    DESCRIPTION
        "The value of the object sapIgmpSnpgGrpExpiryTime indicates the amount
         of time remaining before this entry will be aged out."
    ::= { sapIgmpSnpgGroupEntry 5 }

sapIgmpSnpgGrpCompatMode         OBJECT-TYPE
    SYNTAX      Unsigned32
    MAX-ACCESS  read-only
    STATUS      current
    DESCRIPTION
        "The value of the object sapIgmpSnpgGrpCompatMode indicates
         the IGMP version applicable  on this SAP for this
         multicast group address. This corresponds to the lowest version
         seen for this group address on this SAP."
    ::= { sapIgmpSnpgGroupEntry 6 }

sapIgmpSnpgGrpV1HostExpTime      OBJECT-TYPE
    SYNTAX      Unsigned32
    UNITS       "seconds"
    MAX-ACCESS  read-only
    STATUS      current
    DESCRIPTION
        "The value of the object sapIgmpSnpgGrpV1HostExpTime indicates the time
         remaining until the system will assume that there are no longer any
         IGMPv1 members on this SAP.

         Upon hearing any IGMPv1 Membership Report, this value is reset to the
         group membership interval. While this time remaining is non-zero, the
         system ignores any IGMPv2 and IGMPv3 'leave' messages for this group
         that it receives on this SAP."
    ::= { sapIgmpSnpgGroupEntry 7 }

sapIgmpSnpgGrpV2HostExpTime      OBJECT-TYPE
    SYNTAX      Unsigned32
    UNITS       "seconds"
    MAX-ACCESS  read-only
    STATUS      current
    DESCRIPTION
        "The value of the object sapIgmpSnpgGrpV2HostExpTime indicates the time
         remaining until the system will assume that there are no longer any
         IGMPv2 members on the SAP.

         Upon hearing any IGMPv2 Membership Report, this value is reset to the
         group membership interval. While this time remaining is non-zero, the
         system ignores any IGMPv3 'leave' messages for this group that it
         receives on this SAP."
    ::= { sapIgmpSnpgGroupEntry 8 }

sapIgmpSnpgGrpMvrFromVplsId      OBJECT-TYPE
    SYNTAX      TmnxServId
    MAX-ACCESS  read-only
    STATUS      current
    DESCRIPTION
        "The value of the object sapIgmpSnpgGrpMvrFromVplsId indicates from
         which Tls the multicast streams corresponding to this group are
         copied.

         A value of 0 means that MVR is not applicable for this group and the
         corresponding streams are copied from the local Tls."
    ::= { sapIgmpSnpgGroupEntry 9 }

sapIgmpSnpgGrpMvrToSapPortId     OBJECT-TYPE
    SYNTAX      TmnxPortID
    MAX-ACCESS  read-only
    STATUS      current
    DESCRIPTION
        "The value of the object sapIgmpSnpgGrpMvrToSapPortId indicates
         together with sapIgmpSnpgGrpMvrToSapEncapVal, to which SAP the
         multicast streams corresponding to this group are copied.

         If both values are 0, the corresponding streams are copied to this
         local SAP."
    ::= { sapIgmpSnpgGroupEntry 10 }

sapIgmpSnpgGrpMvrToSapEncapVal   OBJECT-TYPE
    SYNTAX      TmnxEncapVal
    MAX-ACCESS  read-only
    STATUS      current
    DESCRIPTION
        "The value of the object sapIgmpSnpgGrpMvrToSapEncapVal indicates,
         together with sapIgmpSnpgGrpMvrToSapPortId, to which SAP the multicast
         streams corresponding to this group are copied.

         If both values are 0, the corresponding streams are copied to this
         local SAP."
    ::= { sapIgmpSnpgGroupEntry 11 }

sapIgmpSnpgGrpSrcTable           OBJECT-TYPE
    SYNTAX      SEQUENCE OF SapIgmpSnpgGrpSrcEntry
    MAX-ACCESS  not-accessible
    STATUS      current
    DESCRIPTION
        "sapIgmpSnpgGrpSrcTable lists the IPv4 multicast Sources corresponding
         to the IPv4 multicast groups listed in the sapIgmpSnpgGroupTable."
    ::= { alxIgmpSnoopingSapObjs 3 }

sapIgmpSnpgGrpSrcEntry           OBJECT-TYPE
    SYNTAX      SapIgmpSnpgGrpSrcEntry
    MAX-ACCESS  not-accessible
    STATUS      current
    DESCRIPTION
        "An entry in the sapIgmpSnpgGrpSrcTable. Each entry represents a Source
         address from which receivers are interested/not interested in
         receiving multicast traffic from."
    INDEX       {
        svcId,
        sapPortId,
        sapEncapValue,
        sapIgmpSnpgGrpAddress,
        sapIgmpSnpgGrpSrcAddr
    }
    ::= { sapIgmpSnpgGrpSrcTable 1 }

SapIgmpSnpgGrpSrcEntry           ::= SEQUENCE
{
    sapIgmpSnpgGrpSrcAddr            IpAddress,
    sapIgmpSnpgGrpSrcType            TmnxIgmpGroupType,
    sapIgmpSnpgGrpSrcUpTime          TimeTicks,
    sapIgmpSnpgGrpSrcExpiryTime      Unsigned32
}

sapIgmpSnpgGrpSrcAddr            OBJECT-TYPE
    SYNTAX      IpAddress
    MAX-ACCESS  not-accessible
    STATUS      current
    DESCRIPTION
        "The value of the object sapIgmpSnpgGrpSrcAddr indicates the address of
         the Source sending multicast traffic to the group identified by
         sapIgmpSnpgGrpAddress.

         If the value of sapIgmpSnpgGrpFilterMode corresponding to this entry
         is 'include(1)', the receivers are interested in receiving traffic
         from this Source.

         If the value of sapIgmpSnpgGrpFilterMode corresponding to this entry
         is 'exclude(2)', the receivers are not interested in receiving traffic
         from this Source."
    ::= { sapIgmpSnpgGrpSrcEntry 1 }

sapIgmpSnpgGrpSrcType            OBJECT-TYPE
    SYNTAX      TmnxIgmpGroupType
    MAX-ACCESS  read-only
    STATUS      current
    DESCRIPTION
        "The value of the object sapIgmpSnpgGrpSrcType indicates how this
         source entry was learned.

         If this source entry was learned, it is set to 'dynamic(2)'. For
         statically configured sources, the value is set to 'static(1)'."
    ::= { sapIgmpSnpgGrpSrcEntry 2 }

sapIgmpSnpgGrpSrcUpTime          OBJECT-TYPE
    SYNTAX      TimeTicks
    MAX-ACCESS  read-only
    STATUS      current
    DESCRIPTION
        "The value of the object sapIgmpSnpgGrpSrcUpTime indicates how long (in
         centiseconds) that the Source address already exists in the database
         for this SAP."
    ::= { sapIgmpSnpgGrpSrcEntry 3 }

sapIgmpSnpgGrpSrcExpiryTime      OBJECT-TYPE
    SYNTAX      Unsigned32
    UNITS       "seconds"
    MAX-ACCESS  read-only
    STATUS      current
    DESCRIPTION
        "The value of the object sapIgmpSnpgGrpSrcExpiryTime indicates the
         minimum amount of time remaining before this entry will be aged out.

         If the value of sapIgmpSnpgGrpSrcExpiryTime is non-zero and the value
         of sapIgmpSnpgGrpFilterMode corresponding to this entry is
         'include(1)', it means that there are currently one or more systems
         which desire to receive multicast traffic for this Source.

         If this timer expires and the value of sapIgmpSnpgGrpFilterMode is
         'include(1)', the system concludes that traffic from this particular
         Source is no longer desired on the attached network, and deletes this
         entry.

         If the value of sapIgmpSnpgGrpSrcExpiryTime is non-zero and the
         filter-mode for the group is 'exclude(2)', it means that at least one
         system desires to receive multicast traffic from this source.

         If the value of sapIgmpSnpgGrpSrcExpiryTime is zero and the
         filter-mode for the group is 'exclude(2)', it means that no system
         desires to receive multicast traffic from this Source."
    ::= { sapIgmpSnpgGrpSrcEntry 4 }

sapIgmpSnpgStaticGrpSrcTable     OBJECT-TYPE
    SYNTAX      SEQUENCE OF SapIgmpSnpgStaticGrpSrcEntry
    MAX-ACCESS  not-accessible
    STATUS      current
    DESCRIPTION
        "The table sapIgmpSnpgStaticGrpSrcTable contains statically configured
         (S,G) entries for each SAP."
    ::= { alxIgmpSnoopingSapObjs 4 }

sapIgmpSnpgStaticGrpSrcEntry     OBJECT-TYPE
    SYNTAX      SapIgmpSnpgStaticGrpSrcEntry
    MAX-ACCESS  not-accessible
    STATUS      current
    DESCRIPTION
        "An entry in the sapIgmpSnpgStaticGrpSrcTable. Entries can be created
         or deleted by an SNMP SET request to sapIgmpSnpgStaticRowstatus."
    INDEX       {
        svcId,
        sapPortId,
        sapEncapValue,
        sapIgmpSnpgStaticGroupAddr,
        sapIgmpSnpgStaticSourceAddr
    }
    ::= { sapIgmpSnpgStaticGrpSrcTable 1 }

SapIgmpSnpgStaticGrpSrcEntry     ::= SEQUENCE
{
    sapIgmpSnpgStaticGroupAddr       IpAddress,
    sapIgmpSnpgStaticSourceAddr      IpAddress,
    sapIgmpSnpgStaticRowstatus       RowStatus,
    sapIgmpSnpgStaticLastChangeTime  TimeStamp
}

sapIgmpSnpgStaticGroupAddr       OBJECT-TYPE
    SYNTAX      IpAddress
    MAX-ACCESS  not-accessible
    STATUS      current
    DESCRIPTION
        "The value of the object sapIgmpSnpgStaticGroupAddr specifies the group
         multicast address for this statically configured (S,G) entry for this
         SAP."
    ::= { sapIgmpSnpgStaticGrpSrcEntry 1 }

sapIgmpSnpgStaticSourceAddr      OBJECT-TYPE
    SYNTAX      IpAddress
    MAX-ACCESS  not-accessible
    STATUS      current
    DESCRIPTION
        "The value of the object sapIgmpSnpgStaticSourceAddr specifies the
         Source IP address for this statically configured (S,G) entry for this
         SAP.

         For a (*,G) entry this object must be set to 0.0.0.0."
    ::= { sapIgmpSnpgStaticGrpSrcEntry 2 }

sapIgmpSnpgStaticRowstatus       OBJECT-TYPE
    SYNTAX      RowStatus
    MAX-ACCESS  read-create
    STATUS      current
    DESCRIPTION
        "The value of the object sapIgmpSnpgStaticRowstatus specifies the row
         status used for creation or deletion of sapIgmpSnpgStaticGrpSrcTable
         entries."
    ::= { sapIgmpSnpgStaticGrpSrcEntry 3 }

sapIgmpSnpgStaticLastChangeTime  OBJECT-TYPE
    SYNTAX      TimeStamp
    MAX-ACCESS  read-only
    STATUS      current
    DESCRIPTION
        "The value of the object sapIgmpSnpgStaticLastChangeTime indicates the
         sysUpTime at the time of the last modification of this entry."
    ::= { sapIgmpSnpgStaticGrpSrcEntry 4 }

sapIgmpSnpgStatsTable            OBJECT-TYPE
    SYNTAX      SEQUENCE OF SapIgmpSnpgStatsEntry
    MAX-ACCESS  not-accessible
    STATUS      current
    DESCRIPTION
        "sapIgmpSnpgStatsTable contains statistics on IGMP snooping per SAP."
    ::= { alxIgmpSnoopingSapObjs 5 }

sapIgmpSnpgStatsEntry            OBJECT-TYPE
    SYNTAX      SapIgmpSnpgStatsEntry
    MAX-ACCESS  not-accessible
    STATUS      current
    DESCRIPTION
        "sapIgmpSnpgStatsEntry is an entry in the sapIgmpSnpgStatsTable. Each
         entry contains IGMP snooping statics for a SAP in a Tls."
    INDEX       {
        svcId,
        sapPortId,
        sapEncapValue
    }
    ::= { sapIgmpSnpgStatsTable 1 }

SapIgmpSnpgStatsEntry            ::= SEQUENCE
{
    sapIgmpSnpgTxGenQueries          Counter32,
    sapIgmpSnpgTxGrpSpecQueries      Counter32,
    sapIgmpSnpgTxSrcSpecQueries      Counter32,
    sapIgmpSnpgTxV1Reports           Counter32,
    sapIgmpSnpgTxV2Reports           Counter32,
    sapIgmpSnpgTxV3Reports           Counter32,
    sapIgmpSnpgTxV2Leaves            Counter32,
    sapIgmpSnpgRxGenQueries          Counter32,
    sapIgmpSnpgRxGrpSpecQueries      Counter32,
    sapIgmpSnpgRxSrcSpecQueries      Counter32,
    sapIgmpSnpgRxV1Reports           Counter32,
    sapIgmpSnpgRxV2Reports           Counter32,
    sapIgmpSnpgRxV3Reports           Counter32,
    sapIgmpSnpgRxV2Leaves            Counter32,
    sapIgmpSnpgRxUnknownType         Counter32,
    sapIgmpSnpgFwdGenQueries         Counter32,
    sapIgmpSnpgFwdGrpSpecQueries     Counter32,
    sapIgmpSnpgFwdSrcSpecQueries     Counter32,
    sapIgmpSnpgFwdV1Reports          Counter32,
    sapIgmpSnpgFwdV2Reports          Counter32,
    sapIgmpSnpgFwdV3Reports          Counter32,
    sapIgmpSnpgFwdV2Leaves           Counter32,
    sapIgmpSnpgFwdUnknownType        Counter32,
    sapIgmpSnpgRxBadLenPkts          Counter32,
    sapIgmpSnpgRxBadIpChksmPkts      Counter32,
    sapIgmpSnpgRxBadIgmpChksmPkts    Counter32,
    sapIgmpSnpgRxBadEncodedPkts      Counter32,
    sapIgmpSnpgRxNoRtrAlertPkts      Counter32,
    sapIgmpSnpgRxZeroSrcAdrPkts      Counter32,
    sapIgmpSnpgSendQueryCfgDrops     Counter32,
    sapIgmpSnpgImportPolicyDrops     Counter32,
    sapIgmpSnpgMaxNumGroupsDrops     Counter32,
    sapIgmpSnpgMvrFromVplsCfgDrops   Counter32,
    sapIgmpSnpgMvrToSapCfgDrops      Counter32,
    sapIgmpSnpgRxWrongVersionPkts    Counter32,
    sapIgmpSnpgMcacPolicyDrops       Counter32,
    sapIgmpSnpgMcsFailures           Counter32,
    sapIgmpSnpgRxLocalScopePkts      Counter32,
    sapIgmpSnpgRxRsvdScopePkts       Counter32,
    sapIgmpSnpgMaxNumSourcesDrops    Counter32,
    sapIgmpSnpgMaxNumGrpSrcsDrops    Counter32
}

sapIgmpSnpgTxGenQueries          OBJECT-TYPE
    SYNTAX      Counter32
    MAX-ACCESS  read-only
    STATUS      current
    DESCRIPTION
        "The value of the object sapIgmpSnpgTxGenQueries indicates the number
         of IGMP General Queries transmitted on this SAP."
    ::= { sapIgmpSnpgStatsEntry 1 }

sapIgmpSnpgTxGrpSpecQueries      OBJECT-TYPE
    SYNTAX      Counter32
    MAX-ACCESS  read-only
    STATUS      current
    DESCRIPTION
        "The value of the object sapIgmpSnpgTxGrpSpecQueries indicates the
         number of IGMP Group-Specific Queries transmitted on this SAP."
    ::= { sapIgmpSnpgStatsEntry 2 }

sapIgmpSnpgTxSrcSpecQueries      OBJECT-TYPE
    SYNTAX      Counter32
    MAX-ACCESS  read-only
    STATUS      current
    DESCRIPTION
        "The value of the object sapIgmpSnpgTxSrcSpecQueries indicates the
         number of IGMP Group-And-Source-Specific Queries transmitted on this
         SAP."
    ::= { sapIgmpSnpgStatsEntry 3 }

sapIgmpSnpgTxV1Reports           OBJECT-TYPE
    SYNTAX      Counter32
    MAX-ACCESS  read-only
    STATUS      current
    DESCRIPTION
        "The value of the object sapIgmpSnpgTxV1Reports indicates the number of
         IGMPv1 Reports transmitted on this SAP."
    ::= { sapIgmpSnpgStatsEntry 4 }

sapIgmpSnpgTxV2Reports           OBJECT-TYPE
    SYNTAX      Counter32
    MAX-ACCESS  read-only
    STATUS      current
    DESCRIPTION
        "The value of the object sapIgmpSnpgTxV2Reports indicates the number of
         IGMPv2 Reports transmitted on this SAP."
    ::= { sapIgmpSnpgStatsEntry 5 }

sapIgmpSnpgTxV3Reports           OBJECT-TYPE
    SYNTAX      Counter32
    MAX-ACCESS  read-only
    STATUS      current
    DESCRIPTION
        "The value of the object sapIgmpSnpgTxV3Reports indicates the number of
         IGMPv3 Reports transmitted on this SAP."
    ::= { sapIgmpSnpgStatsEntry 6 }

sapIgmpSnpgTxV2Leaves            OBJECT-TYPE
    SYNTAX      Counter32
    MAX-ACCESS  read-only
    STATUS      current
    DESCRIPTION
        "The value of the object sapIgmpSnpgTxV2Leaves indicates the number of
         IGMPv2 Leaves transmitted on this SAP."
    ::= { sapIgmpSnpgStatsEntry 7 }

sapIgmpSnpgRxGenQueries          OBJECT-TYPE
    SYNTAX      Counter32
    MAX-ACCESS  read-only
    STATUS      current
    DESCRIPTION
        "The value of the object sapIgmpSnpgRxGenQueries indicates the number
         of IGMP General Queries received on this SAP."
    ::= { sapIgmpSnpgStatsEntry 8 }

sapIgmpSnpgRxGrpSpecQueries      OBJECT-TYPE
    SYNTAX      Counter32
    MAX-ACCESS  read-only
    STATUS      current
    DESCRIPTION
        "The value of the object sapIgmpSnpgRxGrpSpecQueries indicates the
         number of IGMP Group-Specific Queries received on this SAP."
    ::= { sapIgmpSnpgStatsEntry 9 }

sapIgmpSnpgRxSrcSpecQueries      OBJECT-TYPE
    SYNTAX      Counter32
    MAX-ACCESS  read-only
    STATUS      current
    DESCRIPTION
        "The value of the object sapIgmpSnpgRxSrcSpecQueries indicates the
         number of IGMP Group-And-Source-Specific Queries received on this SAP."
    ::= { sapIgmpSnpgStatsEntry 10 }

sapIgmpSnpgRxV1Reports           OBJECT-TYPE
    SYNTAX      Counter32
    MAX-ACCESS  read-only
    STATUS      current
    DESCRIPTION
        "The value of the object sapIgmpSnpgRxV1Reports indicates the number of
         IGMPv1 Reports received on this SAP."
    ::= { sapIgmpSnpgStatsEntry 11 }

sapIgmpSnpgRxV2Reports           OBJECT-TYPE
    SYNTAX      Counter32
    MAX-ACCESS  read-only
    STATUS      current
    DESCRIPTION
        "The value of the object sapIgmpSnpgRxV2Reports indicates the number of
         IGMPv2 Reports received on this SAP."
    ::= { sapIgmpSnpgStatsEntry 12 }

sapIgmpSnpgRxV3Reports           OBJECT-TYPE
    SYNTAX      Counter32
    MAX-ACCESS  read-only
    STATUS      current
    DESCRIPTION
        "The value of the object sapIgmpSnpgRxV3Reports indicates the number of
         IGMPv3 Reports received on this SAP."
    ::= { sapIgmpSnpgStatsEntry 13 }

sapIgmpSnpgRxV2Leaves            OBJECT-TYPE
    SYNTAX      Counter32
    MAX-ACCESS  read-only
    STATUS      current
    DESCRIPTION
        "The value of the object sapIgmpSnpgRxV2Leaves indicates the number of
         IGMPv2 Leaves received on this SAP."
    ::= { sapIgmpSnpgStatsEntry 14 }

sapIgmpSnpgRxUnknownType         OBJECT-TYPE
    SYNTAX      Counter32
    MAX-ACCESS  read-only
    STATUS      current
    DESCRIPTION
        "The value of the object sapIgmpSnpgRxUnknownType indicates the number
         of IGMP unknown type packets received on this SAP."
    ::= { sapIgmpSnpgStatsEntry 15 }

sapIgmpSnpgFwdGenQueries         OBJECT-TYPE
    SYNTAX      Counter32
    MAX-ACCESS  read-only
    STATUS      current
    DESCRIPTION
        "The value of the object sapIgmpSnpgFwdGenQueries indicates the number
         of IGMP General Queries forwarded on this SAP."
    ::= { sapIgmpSnpgStatsEntry 16 }

sapIgmpSnpgFwdGrpSpecQueries     OBJECT-TYPE
    SYNTAX      Counter32
    MAX-ACCESS  read-only
    STATUS      current
    DESCRIPTION
        "The value of the object sapIgmpSnpgFwdGrpSpecQueries indicates the
         number of IGMP Group-Specific Queries forwarded on this SAP."
    ::= { sapIgmpSnpgStatsEntry 17 }

sapIgmpSnpgFwdSrcSpecQueries     OBJECT-TYPE
    SYNTAX      Counter32
    MAX-ACCESS  read-only
    STATUS      current
    DESCRIPTION
        "The value of the object sapIgmpSnpgFwdSrcSpecQueries indicates the
         number of IGMP Group-And-Source-Specific Queries forwarded on this
         SAP."
    ::= { sapIgmpSnpgStatsEntry 18 }

sapIgmpSnpgFwdV1Reports          OBJECT-TYPE
    SYNTAX      Counter32
    MAX-ACCESS  read-only
    STATUS      current
    DESCRIPTION
        "The value of the object sapIgmpSnpgFwdV1Reports indicates the number
         of IGMPv1 Reports forwarded on this SAP."
    ::= { sapIgmpSnpgStatsEntry 19 }

sapIgmpSnpgFwdV2Reports          OBJECT-TYPE
    SYNTAX      Counter32
    MAX-ACCESS  read-only
    STATUS      current
    DESCRIPTION
        "The value of the object sapIgmpSnpgFwdV2Reports indicates the number
         of IGMPv2 Reports forwarded on this SAP."
    ::= { sapIgmpSnpgStatsEntry 20 }

sapIgmpSnpgFwdV3Reports          OBJECT-TYPE
    SYNTAX      Counter32
    MAX-ACCESS  read-only
    STATUS      current
    DESCRIPTION
        "The value of the object sapIgmpSnpgFwdV3Reports indicates the number
         of IGMPv3 Reports forwarded on this SAP."
    ::= { sapIgmpSnpgStatsEntry 21 }

sapIgmpSnpgFwdV2Leaves           OBJECT-TYPE
    SYNTAX      Counter32
    MAX-ACCESS  read-only
    STATUS      current
    DESCRIPTION
        "The value of the object sapIgmpSnpgFwdV2Leaves indicates the number of
         IGMPv2 Leaves forwarded on this SAP."
    ::= { sapIgmpSnpgStatsEntry 22 }

sapIgmpSnpgFwdUnknownType        OBJECT-TYPE
    SYNTAX      Counter32
    MAX-ACCESS  read-only
    STATUS      current
    DESCRIPTION
        "The value of the object sapIgmpSnpgFwdUnknownType indicates the number
         of IGMP unknown type packets forwarded on this SAP."
    ::= { sapIgmpSnpgStatsEntry 23 }

sapIgmpSnpgRxBadLenPkts          OBJECT-TYPE
    SYNTAX      Counter32
    MAX-ACCESS  read-only
    STATUS      current
    DESCRIPTION
        "The value of the object sapIgmpSnpgRxBadLenPkts indicates the number
         of IGMP packets dropped on this SAP because of a bad length."
    ::= { sapIgmpSnpgStatsEntry 24 }

sapIgmpSnpgRxBadIpChksmPkts      OBJECT-TYPE
    SYNTAX      Counter32
    MAX-ACCESS  read-only
    STATUS      current
    DESCRIPTION
        "The value of the object sapIgmpSnpgRxBadIpChksmPkts indicates the
         number of dropped IGMP packets on this SAP because of a bad IPv4
         header checksum."
    ::= { sapIgmpSnpgStatsEntry 25 }

sapIgmpSnpgRxBadIgmpChksmPkts    OBJECT-TYPE
    SYNTAX      Counter32
    MAX-ACCESS  read-only
    STATUS      current
    DESCRIPTION
        "The value of the object sapIgmpSnpgRxBadIgmpChksmPkts indicates the
         number of dropped IGMP packets on this SAP because of a bad IGMP
         header checksum."
    ::= { sapIgmpSnpgStatsEntry 26 }

sapIgmpSnpgRxBadEncodedPkts      OBJECT-TYPE
    SYNTAX      Counter32
    MAX-ACCESS  read-only
    STATUS      current
    DESCRIPTION
        "The value of the object sapIgmpSnpgRxBadEncodedPkts indicates the
         number of IGMP packets dropped on this SAP because of a bad encoding."
    ::= { sapIgmpSnpgStatsEntry 27 }

sapIgmpSnpgRxNoRtrAlertPkts      OBJECT-TYPE
    SYNTAX      Counter32
    MAX-ACCESS  read-only
    STATUS      current
    DESCRIPTION
        "The value of the object sapIgmpSnpgRxNoRtrAlertPkts indicates the
         number of IGMP packets dropped on this SAP because the Router Alert
         Option in the IP packet is not set."
    ::= { sapIgmpSnpgStatsEntry 28 }

sapIgmpSnpgRxZeroSrcAdrPkts      OBJECT-TYPE
    SYNTAX      Counter32
    MAX-ACCESS  read-only
    STATUS      current
    DESCRIPTION
        "The value of the object sapIgmpSnpgRxZeroSrcAdrPkts indicates the
         number of IGMP packets dropped on this SAP because they contain a zero
         source IPv4 address."
    ::= { sapIgmpSnpgStatsEntry 29 }

sapIgmpSnpgSendQueryCfgDrops     OBJECT-TYPE
    SYNTAX      Counter32
    MAX-ACCESS  read-only
    STATUS      current
    DESCRIPTION
        "The value of the object sapIgmpSnpgSendQueryCfgDrops indicates the
         number of times an IGMP Query is dropped because the object
         sapIgmpSnpgCfgSendQueries for this SAP is set to 'enabled(1)'."
    ::= { sapIgmpSnpgStatsEntry 30 }

sapIgmpSnpgImportPolicyDrops     OBJECT-TYPE
    SYNTAX      Counter32
    MAX-ACCESS  read-only
    STATUS      current
    DESCRIPTION
        "The value of the object sapIgmpSnpgImportPolicyDrops indicates the
         number of times an IGMP Group or Source is dropped because of applying
         an import policy on this SAP."
    ::= { sapIgmpSnpgStatsEntry 31 }

sapIgmpSnpgMaxNumGroupsDrops     OBJECT-TYPE
    SYNTAX      Counter32
    MAX-ACCESS  read-only
    STATUS      current
    DESCRIPTION
        "The value of the object sapIgmpSnpgMaxNumGroupsDrops indicates the
         number of times an IGMP Group is dropped because of exceeding the
         configured maximum number of groups on this SAP."
    ::= { sapIgmpSnpgStatsEntry 32 }

sapIgmpSnpgMvrFromVplsCfgDrops   OBJECT-TYPE
    SYNTAX      Counter32
    MAX-ACCESS  read-only
    STATUS      current
    DESCRIPTION
        "The value of the object sapIgmpSnpgMvrFromVplsCfgDrops indicates the
         number of times an IGMP Group or Query is dropped because of applying
         the sapIgmpSnpgCfgMvrFromVplsId configuration on this SAP."
    ::= { sapIgmpSnpgStatsEntry 33 }

sapIgmpSnpgMvrToSapCfgDrops      OBJECT-TYPE
    SYNTAX      Counter32
    MAX-ACCESS  read-only
    STATUS      current
    DESCRIPTION
        "The value of the object sapIgmpSnpgMvrToSapCfgDrops indicates the
         number times an IGMP Report or Query is dropped because of applying
         the sapIgmpSnpgCfgMvrToSapPortId and sapIgmpSnpgCfgMvrToSapEncapVal
         configuration on this SAP."
    ::= { sapIgmpSnpgStatsEntry 34 }

sapIgmpSnpgRxWrongVersionPkts    OBJECT-TYPE
    SYNTAX      Counter32
    MAX-ACCESS  read-only
    STATUS      current
    DESCRIPTION
        "The value of the object sapIgmpSnpgRxWrongVersionPkts indicates the
         total number of IGMP packets with a wrong version received on this
         SAP."
    ::= { sapIgmpSnpgStatsEntry 35 }

sapIgmpSnpgMcacPolicyDrops       OBJECT-TYPE
    SYNTAX      Counter32
    MAX-ACCESS  read-only
    STATUS      current
    DESCRIPTION
        "The value of the object sapIgmpSnpgMcacPolicyDrops indicates the
         number of times an IGMP Group is dropped because of applying a
         multicast CAC policy on this SAP."
    ::= { sapIgmpSnpgStatsEntry 36 }

sapIgmpSnpgMcsFailures           OBJECT-TYPE
    SYNTAX      Counter32
    MAX-ACCESS  read-only
    STATUS      current
    DESCRIPTION
        "The value of the object sapIgmpSnpgMcsFailures indicates the number of
         times an IGMP Group on this SAP could not be synced to the MCS
         (multi-chassis synchronization) database."
    ::= { sapIgmpSnpgStatsEntry 37 }

sapIgmpSnpgRxLocalScopePkts      OBJECT-TYPE
    SYNTAX      Counter32
    MAX-ACCESS  read-only
    STATUS      current
    DESCRIPTION
        "The value of the object sapIgmpSnpgRxLocalScopePkts indicates the
         number of IGMP packets received on the link-local scope IPv6 multicast
         address."
    ::= { sapIgmpSnpgStatsEntry 38 }

sapIgmpSnpgRxRsvdScopePkts       OBJECT-TYPE
    SYNTAX      Counter32
    MAX-ACCESS  read-only
    STATUS      current
    DESCRIPTION
        "The value of the object sapIgmpSnpgRxRsvdScopePkts indicates the
         number of IGMP packets received on the reserved scope IPv6 multicast
         address."
    ::= { sapIgmpSnpgStatsEntry 39 }

sapIgmpSnpgMaxNumSourcesDrops    OBJECT-TYPE
    SYNTAX      Counter32
    MAX-ACCESS  read-only
    STATUS      current
    DESCRIPTION
        "The value of the object sapIgmpSnpgMaxNumSourcesDrops indicates the
         number of times an IGMP Source is dropped because of exceeding the
         configured maximum number of sources per group on this SAP."
    ::= { sapIgmpSnpgStatsEntry 40 }

sapIgmpSnpgMaxNumGrpSrcsDrops    OBJECT-TYPE
    SYNTAX      Counter32
    MAX-ACCESS  read-only
    STATUS      current
    DESCRIPTION
        "The value of the object sapIgmpSnpgMaxNumGrpSrcsDrops indicates the
         number of times an IGMP Group Source is dropped because of exceeding
         the configured maximum number of group sources per group on this SAP."
    ::= { sapIgmpSnpgStatsEntry 41 }

sapIgmpSnpgMcacLevelTable        OBJECT-TYPE
    SYNTAX      SEQUENCE OF SapIgmpSnpgMcacLevelEntry
    MAX-ACCESS  not-accessible
    STATUS      current
    DESCRIPTION
        "The sapIgmpSnpgMcacLevelTable has an entry for each multicast CAC
         policy constraint level configured on this system."
    ::= { alxIgmpSnoopingSapObjs 6 }

sapIgmpSnpgMcacLevelEntry        OBJECT-TYPE
    SYNTAX      SapIgmpSnpgMcacLevelEntry
    MAX-ACCESS  not-accessible
    STATUS      current
    DESCRIPTION
        "Each row entry represents a particular multicast CAC policy bundle
         level constraints. Entries are created/deleted by the user."
    INDEX       {
        svcId,
        sapPortId,
        sapEncapValue,
        tmnxMcacLevelId
    }
    ::= { sapIgmpSnpgMcacLevelTable 1 }

SapIgmpSnpgMcacLevelEntry        ::= SEQUENCE
{
    sapIgmpSnpgCfgMcacLevelRowStat   RowStatus,
    sapIgmpSnpgCfgMcacLevelBW        Unsigned32,
    sapIgmpSnpgCfgMcacLevelLastChngT TimeStamp
}

sapIgmpSnpgCfgMcacLevelRowStat   OBJECT-TYPE
    SYNTAX      RowStatus
    MAX-ACCESS  read-create
    STATUS      current
    DESCRIPTION
        "The value of sapIgmpSnpgCfgMcacLevelRowStat is used for
         creation/deletion of level constraint in a CAC policy."
    ::= { sapIgmpSnpgMcacLevelEntry 1 }

sapIgmpSnpgCfgMcacLevelBW        OBJECT-TYPE
    SYNTAX      Unsigned32 (0..2147483647)
    UNITS       "kilobps"
    MAX-ACCESS  read-create
    STATUS      current
    DESCRIPTION
        "The value of sapIgmpSnpgCfgMcacLevelBW specifies the bandwidth in
         kilobits per second (kbps) for the level."
    DEFVAL      { 1 }
    ::= { sapIgmpSnpgMcacLevelEntry 2 }

sapIgmpSnpgCfgMcacLevelLastChngT OBJECT-TYPE
    SYNTAX      TimeStamp
    MAX-ACCESS  read-only
    STATUS      current
    DESCRIPTION
        "The value of the object sapIgmpSnpgCfgMcacLevelLastChngT indicates the
         sysUpTime at the time of the last modification of this entry."
    ::= { sapIgmpSnpgMcacLevelEntry 3 }

sapIgmpSnpgMcacLagTable          OBJECT-TYPE
    SYNTAX      SEQUENCE OF SapIgmpSnpgMcacLagEntry
    MAX-ACCESS  not-accessible
    STATUS      current
    DESCRIPTION
        "The sapIgmpSnpgMcacLagTable has an entry for each lag port configured
         for a multicast CAC policy bundle on this system."
    ::= { alxIgmpSnoopingSapObjs 7 }

sapIgmpSnpgMcacLagEntry          OBJECT-TYPE
    SYNTAX      SapIgmpSnpgMcacLagEntry
    MAX-ACCESS  not-accessible
    STATUS      current
    DESCRIPTION
        "Each row entry represents a particular multicast CAC lag port
         constraints. Entries are created/deleted by the user."
    INDEX       {
        svcId,
        sapPortId,
        sapEncapValue,
        tmnxMcacLagPortsDown
    }
    ::= { sapIgmpSnpgMcacLagTable 1 }

SapIgmpSnpgMcacLagEntry          ::= SEQUENCE
{
    sapIgmpSnpgCfgMcacLagRowStat     RowStatus,
    sapIgmpSnpgCfgMcacLagLevel       Unsigned32,
    sapIgmpSnpgCfgMcacLagLastChangeT TimeStamp
}

sapIgmpSnpgCfgMcacLagRowStat     OBJECT-TYPE
    SYNTAX      RowStatus
    MAX-ACCESS  read-create
    STATUS      current
    DESCRIPTION
        "The value of sapIgmpSnpgCfgMcacLagRowStat is used for
         creation/deletion of lag constraint in a CAC policy."
    ::= { sapIgmpSnpgMcacLagEntry 1 }

sapIgmpSnpgCfgMcacLagLevel       OBJECT-TYPE
    SYNTAX      Unsigned32 (1..8)
    MAX-ACCESS  read-create
    STATUS      current
    DESCRIPTION
        "The value of sapIgmpSnpgCfgMcacLagLevel specifies the level id to use
         when the value of tmnxMcacLagPortsDown matches the actual number of
         ports down in a lag.

         Using the value of sapIgmpSnpgCfgMcacLagLevel as an index, the
         operational SAP unconstrained bandwidth will be set to
         sapIgmpSnpgCfgMcacLevelBW.

         By default, for all lag constraints the link level will be set to 1 at
         row creation."
    DEFVAL      { 1 }
    ::= { sapIgmpSnpgMcacLagEntry 2 }

sapIgmpSnpgCfgMcacLagLastChangeT OBJECT-TYPE
    SYNTAX      TimeStamp
    MAX-ACCESS  read-only
    STATUS      current
    DESCRIPTION
        "The value of the object sapIgmpSnpgCfgMcacLagLastChangeT indicates the
         sysUpTime at the time of the last modification of this entry."
    ::= { sapIgmpSnpgMcacLagEntry 3 }

alxIgmpSnoopingSdpBindObjs       OBJECT IDENTIFIER ::= { alxIgmpSnoopingObjs 3 }

sdpBindIgmpSnpgConfigTable       OBJECT-TYPE
    SYNTAX      SEQUENCE OF SdpBindIgmpSnpgConfigEntry
    MAX-ACCESS  not-accessible
    STATUS      current
    DESCRIPTION
        "The table sdpBindIgmpSnpgConfigTable contains objects to configure the
         IGMP snooping feature on an SDP Bind within a Tls."
    ::= { alxIgmpSnoopingSdpBindObjs 1 }

sdpBindIgmpSnpgConfigEntry       OBJECT-TYPE
    SYNTAX      SdpBindIgmpSnpgConfigEntry
    MAX-ACCESS  not-accessible
    STATUS      current
    DESCRIPTION
        "Each row contains IGMP snooping configuration parameters for an SDP
         bind within a Tls. Entries in this table cannot be created or deleted
         via SNMP operations. An entry in this table will be created by the
         agent upon creation of a new SDP Bind (sdpBindTlsEntry). The entry is
         destroyed when the SDP or Tls service is removed."
    INDEX       {
        svcId,
        sdpBindId
    }
    ::= { sdpBindIgmpSnpgConfigTable 1 }

SdpBindIgmpSnpgConfigEntry       ::= SEQUENCE
{
    sdpBndIgmpSnpgCfgImportPlcy      TPolicyStatementNameOrEmpty,
    sdpBndIgmpSnpgCfgFastLeave       AlxIgmpSnpgAdminState,
    sdpBndIgmpSnpgCfgMRouter         TruthValue,
    sdpBndIgmpSnpgCfgSendQueries     AlxIgmpSnpgAdminState,
    sdpBndIgmpSnpgCfgGenQueryIntvl   Unsigned32,
    sdpBndIgmpSnpgCfgQueryRespIntvl  Unsigned32,
    sdpBndIgmpSnpgCfgRobustCount     Unsigned32,
    sdpBndIgmpSnpgCfgLastMembIntvl   Unsigned32,
    sdpBndIgmpSnpgCfgMaxNbrGrps      Integer32,
    sdpBndIgmpSnpgCfgVersion         TmnxIgmpVersion,
    sdpBndIgmpSnpgCfgMcacPolicyName  TPolicyStatementNameOrEmpty,
    sdpBndIgmpSnpgCfgMcacUnconstBW   Integer32,
    sdpBndIgmpSnpgCfgMcacPrRsvMndBW  Integer32,
    sdpBndIgmpSnpgCfgMcacinUseMndBw  Unsigned32,
    sdpBndIgmpSnpgCfgMcacinUseOplBw  Unsigned32,
    sdpBndIgmpSnpgCfgMcacAvailMndBw  Unsigned32,
    sdpBndIgmpSnpgCfgMcacAvailOplBw  Unsigned32,
    sdpBndIgmpSnpgCfgMcacValInTrans  TruthValue,
    sdpBndIgmpSnpgCfgLastChangeTime  TimeStamp,
    sdpBndIgmpSnpgCfgMaxNbrSrcs      Unsigned32,
    sdpBndIgmpSnpgCfgDisRtrAlertChk  TruthValue,
    sdpBndIgmpSnpgCfgMaxNbrGrpSrcs   Unsigned32,
    sdpBndIgmpSnpgCfgMcacIfPlcyName  TPolicyStatementNameOrEmpty
}

sdpBndIgmpSnpgCfgImportPlcy      OBJECT-TYPE
    SYNTAX      TPolicyStatementNameOrEmpty
    MAX-ACCESS  read-write
    STATUS      current
    DESCRIPTION
        "The value of the object sdpBndIgmpSnpgCfgImportPlcy specifies a policy
         statement that must be applied to all incoming IGMP messages on this
         SDP Bind."
    DEFVAL      { "" }
    ::= { sdpBindIgmpSnpgConfigEntry 1 }

sdpBndIgmpSnpgCfgFastLeave       OBJECT-TYPE
    SYNTAX      AlxIgmpSnpgAdminState
    MAX-ACCESS  read-write
    STATUS      current
    DESCRIPTION
        "The value of the object sdpBndIgmpSnpgCfgFastLeave specifies whether
         or not fastleave is allowed on this SDP bind.

         If set to 'enabled(1)', the system prunes the port on which an IGMP
         'leave' message has been received without waiting for the Group
         Specific Query to timeout."
    DEFVAL      { disabled }
    ::= { sdpBindIgmpSnpgConfigEntry 2 }

sdpBndIgmpSnpgCfgMRouter         OBJECT-TYPE
    SYNTAX      TruthValue
    MAX-ACCESS  read-write
    STATUS      current
    DESCRIPTION
        "The value of the object sdpBndIgmpSnpgCfgMRouter specifies whether
         whether a multicast router is attached behind this SDP.

         If sdpBndIgmpSnpgCfgSendQueries is set to 'enabled(1)', the system
         acts as if this object was set to 'false(2)'."
    DEFVAL      { false }
    ::= { sdpBindIgmpSnpgConfigEntry 3 }

sdpBndIgmpSnpgCfgSendQueries     OBJECT-TYPE
    SYNTAX      AlxIgmpSnpgAdminState
    MAX-ACCESS  read-write
    STATUS      current
    DESCRIPTION
        "The value of the object sdpBndIgmpSnpgCfgSendQueries specifies whether
         the system generates General Queries by itself on this SDP."
    DEFVAL      { disabled }
    ::= { sdpBindIgmpSnpgConfigEntry 4 }

sdpBndIgmpSnpgCfgGenQueryIntvl   OBJECT-TYPE
    SYNTAX      Unsigned32 (2..1024)
    UNITS       "seconds"
    MAX-ACCESS  read-write
    STATUS      current
    DESCRIPTION
        "The value of the object sdpBndIgmpSnpgCfgGenQueryIntvl specifies the
         interval (in seconds) between two consecutive general queries sent by
         the system on this SDP.

         The value of this object is only meaningful when the value of
         sdpBndIgmpSnpgCfgSendQueries is 'enabled(1)'."
    DEFVAL      { 125 }
    ::= { sdpBindIgmpSnpgConfigEntry 5 }

sdpBndIgmpSnpgCfgQueryRespIntvl  OBJECT-TYPE
    SYNTAX      Unsigned32 (1..1023)
    UNITS       "seconds"
    MAX-ACCESS  read-write
    STATUS      current
    DESCRIPTION
        "The value of the object sdpBndIgmpSnpgCfgQueryRespIntvl specifies the
         maximum response time (in seconds) advertised in IGMPv2/v3 queries.

         The value of this object is only meaningful when the value of
         sdpBndIgmpSnpgCfgSendQueries is 'enabled(1)'."
    DEFVAL      { 10 }
    ::= { sdpBindIgmpSnpgConfigEntry 6 }

sdpBndIgmpSnpgCfgRobustCount     OBJECT-TYPE
    SYNTAX      Unsigned32 (2..7)
    MAX-ACCESS  read-write
    STATUS      current
    DESCRIPTION
        "The value of the object sdpBndIgmpSnpgCfgRobustCount specifies the
         value of the Robust count.

         This object allows tuning for the expected packet loss on this SDP. If
         a SDP is expected to be lossy, the Robustness Variable may be
         increased. IGMP snooping is robust to (Robustness Variable-1) packet
         losses.

         The value of this object is only meaningful when the value of
         sdpBndIgmpSnpgCfgSendQueries is 'enabled(1)'."
    DEFVAL      { 2 }
    ::= { sdpBindIgmpSnpgConfigEntry 7 }

sdpBndIgmpSnpgCfgLastMembIntvl   OBJECT-TYPE
    SYNTAX      Unsigned32 (1..50)
    UNITS       "deciseconds"
    MAX-ACCESS  read-write
    STATUS      current
    DESCRIPTION
        "The value of the object sdpBndIgmpSnpgCfgLastMembIntvl specifies the
         Max Response Time (in deciseconds) used in Group-Specific and
         Group-Source-Specific Queries sent in response to 'leave' messages.
         This is also the amount of time between Group-Specific Query messages.

         This value may be tuned to modify the leave latency of the network. A
         reduced value results in reduced time to detect the loss of the last
         member of a group."
    DEFVAL      { 10 }
    ::= { sdpBindIgmpSnpgConfigEntry 8 }

sdpBndIgmpSnpgCfgMaxNbrGrps      OBJECT-TYPE
    SYNTAX      Integer32 (0..16000)
    MAX-ACCESS  read-write
    STATUS      current
    DESCRIPTION
        "The value of the object sdpBndIgmpSnpgCfgMaxNbrGrps specifies how many
         group addresses are allowed for this SDP bind. The value 0 means that
         no limit is imposed."
    DEFVAL      { 0 }
    ::= { sdpBindIgmpSnpgConfigEntry 9 }

sdpBndIgmpSnpgCfgVersion         OBJECT-TYPE
    SYNTAX      TmnxIgmpVersion
    MAX-ACCESS  read-write
    STATUS      current
    DESCRIPTION
        "The value of the object sdpBndIgmpSnpgCfgVersion specifies the version
         of IGMP running on this SDP bind."
    DEFVAL      { version3 }
    ::= { sdpBindIgmpSnpgConfigEntry 10 }

sdpBndIgmpSnpgCfgMcacPolicyName  OBJECT-TYPE
    SYNTAX      TPolicyStatementNameOrEmpty
    MAX-ACCESS  read-write
    STATUS      current
    DESCRIPTION
        "The value of sdpBndIgmpSnpgCfgMcacPolicyName indicates the name of the
         multicast CAC policy."
    DEFVAL      { "" }
    ::= { sdpBindIgmpSnpgConfigEntry 11 }

sdpBndIgmpSnpgCfgMcacUnconstBW   OBJECT-TYPE
    SYNTAX      Integer32 (-1..2147483647)
    UNITS       "kilobps"
    MAX-ACCESS  read-write
    STATUS      current
    DESCRIPTION
        "The value of sdpBndIgmpSnpgCfgMcacUnconstBW specifies the bandwidth
         assigned for interface's multicast CAC policy traffic in kilobits per
         second(kbps).

         If the default value of '-1' is set, there is no constraint on
         bandwidth allocated at the interface.

         If the value of sdpBndIgmpSnpgCfgMcacUnconstBW is set to '0' and if a
         multicast CAC policy is assigned on the interface, then no group
         (channel) from that policy is allowed on that interface."
    DEFVAL      { -1 }
    ::= { sdpBindIgmpSnpgConfigEntry 12 }

sdpBndIgmpSnpgCfgMcacPrRsvMndBW  OBJECT-TYPE
    SYNTAX      Integer32 (-1..2147483647)
    UNITS       "kilobps"
    MAX-ACCESS  read-write
    STATUS      current
    DESCRIPTION
        "The value of sdpBndIgmpSnpgCfgMcacPrRsvMndBW specifies the bandwidth
         pre-reserved for all the mandatory channels on a given interface in
         kilobits per second(kbps).

         If the value of sdpBndIgmpSnpgCfgMcacUnconstBW is '0', no mandatory
         channels are allowed. If the value of sdpBndIgmpSnpgCfgMcacUnconstBW
         is '-1', then all mandatory and optional channels are allowed.

         If the value of sdpBndIgmpSnpgCfgMcacPrRsvMndBW is equal to the value
         of sdpBndIgmpSnpgCfgMcacUnconstBW, then all the unconstrained
         bandwidth on a given interface is allocated to mandatory channels
         configured through multicast CAC policy on that interface and no
         optional groups (channels) are allowed.

         The value of sdpBndIgmpSnpgCfgMcacPrRsvMndBW should always be less
         than or equal to that of sdpBndIgmpSnpgCfgMcacUnconstBW. An attempt to
         set the value of sdpBndIgmpSnpgCfgMcacPrRsvMndBW greater than that of
         sdpBndIgmpSnpgCfgMcacUnconstBW will result in inconsistent value
         error."
    DEFVAL      { -1 }
    ::= { sdpBindIgmpSnpgConfigEntry 13 }

sdpBndIgmpSnpgCfgMcacinUseMndBw  OBJECT-TYPE
    SYNTAX      Unsigned32
    UNITS       "kilobps"
    MAX-ACCESS  read-only
    STATUS      current
    DESCRIPTION
        "The value of sdpBndIgmpSnpgCfgMcacinUseMndBw indicates the in-use
         bandwidth in kilobits per second(kbps) for the mandatory channels for
         this protocol interface instance."
    ::= { sdpBindIgmpSnpgConfigEntry 14 }

sdpBndIgmpSnpgCfgMcacinUseOplBw  OBJECT-TYPE
    SYNTAX      Unsigned32
    UNITS       "kilobps"
    MAX-ACCESS  read-only
    STATUS      current
    DESCRIPTION
        "The value of sdpBndIgmpSnpgCfgMcacinUseOplBw indicates the in-use
         bandwidth in kilobits per second(kbps) for the optional channels for
         this protocol interface instance."
    ::= { sdpBindIgmpSnpgConfigEntry 15 }

sdpBndIgmpSnpgCfgMcacAvailMndBw  OBJECT-TYPE
    SYNTAX      Unsigned32
    UNITS       "kilobps"
    MAX-ACCESS  read-only
    STATUS      current
    DESCRIPTION
        "The value of sdpBndIgmpSnpgCfgMcacAvailMndBw indicates the
         pre-reserved bandwidth in kilobits per second(kbps) for the mandatory
         channels for this interface instance."
    ::= { sdpBindIgmpSnpgConfigEntry 16 }

sdpBndIgmpSnpgCfgMcacAvailOplBw  OBJECT-TYPE
    SYNTAX      Unsigned32
    UNITS       "kilobps"
    MAX-ACCESS  read-only
    STATUS      current
    DESCRIPTION
        "The value of sdpBndIgmpSnpgCfgMcacAvailOplBw indicates the available
         bandwidth in kilobits per second(kbps) for this interface instance."
    ::= { sdpBindIgmpSnpgConfigEntry 17 }

sdpBndIgmpSnpgCfgMcacValInTrans  OBJECT-TYPE
    SYNTAX      TruthValue
    MAX-ACCESS  read-only
    STATUS      current
    DESCRIPTION
        "The value of sdpBndIgmpSnpgCfgMcacValInTrans indicates that the
         operational (available and in-use mandatory/optional) value for the
         following objects are in transition due to configuration change:

         sdpBndIgmpSnpgCfgMcacinUseMndBw sdpBndIgmpSnpgCfgMcacinUseOplBw
         sdpBndIgmpSnpgCfgMcacAvailMndBw sdpBndIgmpSnpgCfgMcacAvailOplBw

         When multicast CAC Policy is applied on the interface for the join of
         the next channel, the operational values will be recalculated and
         applied to the above objects and the value for
         sdpBndIgmpSnpgCfgMcacValInTrans will be set to 'false(2)'.

         If the value of sdpBndIgmpSnpgCfgMcacValInTrans is 'true(1)' then the
         values are in transition."
    ::= { sdpBindIgmpSnpgConfigEntry 18 }

sdpBndIgmpSnpgCfgLastChangeTime  OBJECT-TYPE
    SYNTAX      TimeStamp
    MAX-ACCESS  read-only
    STATUS      current
    DESCRIPTION
        "The value of the object sdpBndIgmpSnpgCfgLastChangeTime indicates the
         sysUpTime at the time of the last modification of this entry."
    ::= { sdpBindIgmpSnpgConfigEntry 19 }

sdpBndIgmpSnpgCfgMaxNbrSrcs      OBJECT-TYPE
    SYNTAX      Unsigned32 (0..1000)
    MAX-ACCESS  read-write
    STATUS      current
    DESCRIPTION
        "The value of the object sdpBndIgmpSnpgCfgMaxNbrSrcs specifies how many
         source addresses are allowed per group address for this SDP bind.

         The value 0 means that no limit is imposed."
    DEFVAL      { 0 }
    ::= { sdpBindIgmpSnpgConfigEntry 20 }

sdpBndIgmpSnpgCfgDisRtrAlertChk  OBJECT-TYPE
    SYNTAX      TruthValue
    MAX-ACCESS  read-write
    STATUS      current
    DESCRIPTION
        "sdpBndIgmpSnpgCfgDisRtrAlertChk is used to enable/disable router alert
         checking for IGMP messages received on this sdp.

         If this flag is set to 'true', checking is disabled."
    DEFVAL      { false }
    ::= { sdpBindIgmpSnpgConfigEntry 21 }

sdpBndIgmpSnpgCfgMaxNbrGrpSrcs   OBJECT-TYPE
    SYNTAX      Unsigned32 (0..32000)
    MAX-ACCESS  read-write
    STATUS      current
    DESCRIPTION
        "The value of the object sdpBndIgmpSnpgCfgMaxNbrGrpSrcs specifies how
         many group source addresses are allowed per group address for this SDP
         bind.

         The value 0 means that no limit is imposed."
    DEFVAL      { 0 }
    ::= { sdpBindIgmpSnpgConfigEntry 22 }

sdpBndIgmpSnpgCfgMcacIfPlcyName  OBJECT-TYPE
    SYNTAX      TPolicyStatementNameOrEmpty
    MAX-ACCESS  read-write
    STATUS      current
    DESCRIPTION
        "The value of sdpBndIgmpSnpgCfgMcacIfPlcyName indicates the name of the
         multicast CAC interface policy."
    DEFVAL      { "" }
    ::= { sdpBindIgmpSnpgConfigEntry 23 }

sdpBindIgmpSnpgGroupTable        OBJECT-TYPE
    SYNTAX      SEQUENCE OF SdpBindIgmpSnpgGroupEntry
    MAX-ACCESS  not-accessible
    STATUS      current
    DESCRIPTION
        "sdpBindIgmpSnpgGroupTable together with the table
         sdpBindIgmpSnpgGrpSrcTable contains multicast group address
         information collected by IGMP snooping for each SDP Bind."
    ::= { alxIgmpSnoopingSdpBindObjs 2 }

sdpBindIgmpSnpgGroupEntry        OBJECT-TYPE
    SYNTAX      SdpBindIgmpSnpgGroupEntry
    MAX-ACCESS  not-accessible
    STATUS      current
    DESCRIPTION
        "Each entry in this table indicates a multicast group
         address learned by IGMP snooping on this SDP Bind. If a
         Source list is present it is described in the
         corresponding entries of the  sdpBindIgmpSnpgGrpSrcTable
         table."
    INDEX       {
        svcId,
        sdpBindId,
        sdpBndIgmpSnpgGrpAddress
    }
    ::= { sdpBindIgmpSnpgGroupTable 1 }

SdpBindIgmpSnpgGroupEntry        ::= SEQUENCE
{
    sdpBndIgmpSnpgGrpAddress         IpAddress,
    sdpBndIgmpSnpgGrpType            TmnxIgmpGroupType,
    sdpBndIgmpSnpgGrpFilterMode      TmnxIgmpGroupFilterMode,
    sdpBndIgmpSnpgGrpUpTime          TimeTicks,
    sdpBndIgmpSnpgGrpExpiryTime      Unsigned32,
    sdpBndIgmpSnpgGrpCompatMode      Unsigned32,
    sdpBndIgmpSnpgGrpV1HostExpTime   Unsigned32,
    sdpBndIgmpSnpgGrpV2HostExpTime   Unsigned32
}

sdpBndIgmpSnpgGrpAddress         OBJECT-TYPE
    SYNTAX      IpAddress
    MAX-ACCESS  not-accessible
    STATUS      current
    DESCRIPTION
        "The value of the object sdpBndIgmpSnpgGrpAddress indicates the IPv4
         multicast group address for which this entry contains information."
    ::= { sdpBindIgmpSnpgGroupEntry 1 }

sdpBndIgmpSnpgGrpType            OBJECT-TYPE
    SYNTAX      TmnxIgmpGroupType
    MAX-ACCESS  read-only
    STATUS      current
    DESCRIPTION
        "The value of the object sdpBndIgmpSnpgGrpType indicates whether this
         entry was learned dynamically or was statically configured."
    ::= { sdpBindIgmpSnpgGroupEntry 2 }

sdpBndIgmpSnpgGrpFilterMode      OBJECT-TYPE
    SYNTAX      TmnxIgmpGroupFilterMode
    MAX-ACCESS  read-only
    STATUS      current
    DESCRIPTION
        "The value of the object sdpBndIgmpSnpgGrpFilterMode indicates the
         filter-mode for this group."
    ::= { sdpBindIgmpSnpgGroupEntry 3 }

sdpBndIgmpSnpgGrpUpTime          OBJECT-TYPE
    SYNTAX      TimeTicks
    MAX-ACCESS  read-only
    STATUS      current
    DESCRIPTION
        "The value of the object sdpBndIgmpSnpgGrpUpTime indicates how long (in
         centiseconds) that the group address already exists in the database
         for this SDP Bind."
    ::= { sdpBindIgmpSnpgGroupEntry 4 }

sdpBndIgmpSnpgGrpExpiryTime      OBJECT-TYPE
    SYNTAX      Unsigned32
    UNITS       "seconds"
    MAX-ACCESS  read-only
    STATUS      current
    DESCRIPTION
        "The value of the object sdpBndIgmpSnpgGrpExpiryTime indicates the
         amount of time remaining before this entry will be aged out."
    ::= { sdpBindIgmpSnpgGroupEntry 5 }

sdpBndIgmpSnpgGrpCompatMode      OBJECT-TYPE
    SYNTAX      Unsigned32
    MAX-ACCESS  read-only
    STATUS      current
    DESCRIPTION
        "The value of the object sdpBndIgmpSnpgGrpCompatMode indicates the IGMP
         version applicable on this SDP Bind for this multicast group address.
         This corresponds to the lowest version seen for this group address on
         this SDP Bind."
    ::= { sdpBindIgmpSnpgGroupEntry 6 }

sdpBndIgmpSnpgGrpV1HostExpTime   OBJECT-TYPE
    SYNTAX      Unsigned32
    UNITS       "seconds"
    MAX-ACCESS  read-only
    STATUS      current
    DESCRIPTION
        "The value of the object sdpBndIgmpSnpgGrpV1HostExpTime indicates the
         time remaining until the system will assume that there are no longer
         any IGMPv1 members on this SDP Bind.

         Upon hearing any IGMPv1 Membership Report, this value is reset to the
         group membership interval. While this time remaining is non-zero, the
         system ignores any IGMPv2 and IGMPv3 'leave' messages for this group
         that it receives on this SDP Bind."
    ::= { sdpBindIgmpSnpgGroupEntry 7 }

sdpBndIgmpSnpgGrpV2HostExpTime   OBJECT-TYPE
    SYNTAX      Unsigned32
    UNITS       "seconds"
    MAX-ACCESS  read-only
    STATUS      current
    DESCRIPTION
        "The value of the object sdpBndIgmpSnpgGrpV2HostExpTime indicates the
         time remaining until the system will assume that there are no longer
         any IGMPv2 members on the SDP Bind.

         Upon hearing any IGMPv2 Membership Report, this value is reset to the
         group membership interval. While this time remaining is non-zero, the
         system ignores any IGMPv3 'leave' messages for this group that it
         receives on this SDP Bind."
    ::= { sdpBindIgmpSnpgGroupEntry 8 }

sdpBindIgmpSnpgGrpSrcTable       OBJECT-TYPE
    SYNTAX      SEQUENCE OF SdpBindIgmpSnpgGrpSrcEntry
    MAX-ACCESS  not-accessible
    STATUS      current
    DESCRIPTION
        "sdpBindIgmpSnpgGrpSrcTable lists the IPv4 multicast Sources
         corresponding to the IPv4 multicast groups listed in the
         sdpBindIgmpSnpgGroupTable."
    ::= { alxIgmpSnoopingSdpBindObjs 3 }

sdpBindIgmpSnpgGrpSrcEntry       OBJECT-TYPE
    SYNTAX      SdpBindIgmpSnpgGrpSrcEntry
    MAX-ACCESS  not-accessible
    STATUS      current
    DESCRIPTION
        "An entry in the sdpBindIgmpSnpgGrpSrcTable. Each entry represents a
         Source address from which receivers are interested/not interested in
         receiving multicast traffic from."
    INDEX       {
        svcId,
        sdpBindId,
        sdpBndIgmpSnpgGrpAddress,
        sdpBndIgmpSnpgGrpSrcAddr
    }
    ::= { sdpBindIgmpSnpgGrpSrcTable 1 }

SdpBindIgmpSnpgGrpSrcEntry       ::= SEQUENCE
{
    sdpBndIgmpSnpgGrpSrcAddr         IpAddress,
    sdpBndIgmpSnpgGrpSrcType         TmnxIgmpGroupType,
    sdpBndIgmpSnpgGrpSrcUpTime       TimeTicks,
    sdpBndIgmpSnpgGrpSrcExpiryTime   Unsigned32
}

sdpBndIgmpSnpgGrpSrcAddr         OBJECT-TYPE
    SYNTAX      IpAddress
    MAX-ACCESS  not-accessible
    STATUS      current
    DESCRIPTION
        "The value of the object sdpBndIgmpSnpgGrpSrcAddr indicates the address
         of the Source sending multicast traffic to the group identified by
         sdpBndIgmpSnpgGrpAddress.

         If the value of sdpBndIgmpSnpgGrpFilterMode corresponding to this
         entry is 'include(1)', the receivers are interested in receiving
         traffic from this Source.

         If the value of sdpBndIgmpSnpgGrpFilterMode corresponding to this
         entry is 'exclude(2)', the receivers are not interested in receiving
         traffic from this Source."
    ::= { sdpBindIgmpSnpgGrpSrcEntry 1 }

sdpBndIgmpSnpgGrpSrcType         OBJECT-TYPE
    SYNTAX      TmnxIgmpGroupType
    MAX-ACCESS  read-only
    STATUS      current
    DESCRIPTION
        "The value of the object sdpBndIgmpSnpgGrpSrcType indicates how this
         source entry was learned.

         If this source entry was learned, it is set to 'dynamic(2)'. For
         statically configured sources, the value is set to 'static(1)'."
    ::= { sdpBindIgmpSnpgGrpSrcEntry 2 }

sdpBndIgmpSnpgGrpSrcUpTime       OBJECT-TYPE
    SYNTAX      TimeTicks
    MAX-ACCESS  read-only
    STATUS      current
    DESCRIPTION
        "The value of the object sdpBndIgmpSnpgGrpSrcUpTime indicates how long
         (in centiseconds) that the Source address already exists in the
         database for this SDP Bind."
    ::= { sdpBindIgmpSnpgGrpSrcEntry 3 }

sdpBndIgmpSnpgGrpSrcExpiryTime   OBJECT-TYPE
    SYNTAX      Unsigned32
    UNITS       "seconds"
    MAX-ACCESS  read-only
    STATUS      current
    DESCRIPTION
        "The value of the object sdpBndIgmpSnpgGrpSrcExpiryTime indicates the
         minimum amount of time remaining before this entry will be aged out.

         If  the value of sdpBndIgmpSnpgGrpSrcExpiryTime is non-zero and the
         value of sdpBndIgmpSnpgGrpFilterMode corresponding to this entry is
         'include(1)', it means that there are currently one or more systems
         which desire to receive multicast traffic for this Source.

         If this timer expires and the value of sdpBndIgmpSnpgGrpFilterMode is
         'include(1)', the system concludes that traffic from this particular
         Source is no longer desired on the attached network, and deletes this
         entry.

         If  the value of sdpBndIgmpSnpgGrpSrcExpiryTime is non-zero and the
         filter-mode for the group is 'exclude(2)', it means that at least one
         system desires to receive multicast traffic from this Source.

         If the value of sdpBndIgmpSnpgGrpSrcExpiryTime is zero and the
         filter-mode for the group is 'exclude(2)', it means that no system
         desires to receive multicast traffic from this Source."
    ::= { sdpBindIgmpSnpgGrpSrcEntry 4 }

sdpBindIgmpSnpgStaticGrpSrcTable OBJECT-TYPE
    SYNTAX      SEQUENCE OF SdpBindIgmpSnpgStatGrpSrcEntry
    MAX-ACCESS  not-accessible
    STATUS      current
    DESCRIPTION
        "The table sdpBindIgmpSnpgStaticGrpSrcTable contains statically
         configured (S,G) entries for each SDP Bind."
    ::= { alxIgmpSnoopingSdpBindObjs 4 }

sdpBindIgmpSnpgStatGrpSrcEntry   OBJECT-TYPE
    SYNTAX      SdpBindIgmpSnpgStatGrpSrcEntry
    MAX-ACCESS  not-accessible
    STATUS      current
    DESCRIPTION
        "An entry in the sdpBindIgmpSnpgStaticGrpSrcTable. Entries can be
         created or deleted by an SNMP SET request to
         sdpBndIgmpSnpgStaticRowstatus."
    INDEX       {
        svcId,
        sdpBindId,
        sdpBndIgmpSnpgStaticGroupAddr,
        sdpBndIgmpSnpgStaticSourceAddr
    }
    ::= { sdpBindIgmpSnpgStaticGrpSrcTable 1 }

SdpBindIgmpSnpgStatGrpSrcEntry   ::= SEQUENCE
{
    sdpBndIgmpSnpgStaticGroupAddr    IpAddress,
    sdpBndIgmpSnpgStaticSourceAddr   IpAddress,
    sdpBndIgmpSnpgStaticRowstatus    RowStatus,
    sdpBndIgmpSnpgStaticLastChange   TimeStamp
}

sdpBndIgmpSnpgStaticGroupAddr    OBJECT-TYPE
    SYNTAX      IpAddress
    MAX-ACCESS  not-accessible
    STATUS      current
    DESCRIPTION
        "The value of the object sdpBndIgmpSnpgStaticGroupAddr specifies the
         group multicast address for this statically configured (S,G) entry for
         this SDP Bind."
    ::= { sdpBindIgmpSnpgStatGrpSrcEntry 1 }

sdpBndIgmpSnpgStaticSourceAddr   OBJECT-TYPE
    SYNTAX      IpAddress
    MAX-ACCESS  not-accessible
    STATUS      current
    DESCRIPTION
        "The value of the object sdpBndIgmpSnpgStaticSourceAddr specifies the
         Source IP address for this statically configured (S,G) entry for this
         SDP Bind. For a (*,G) entry this object must be set to 0.0.0.0."
    ::= { sdpBindIgmpSnpgStatGrpSrcEntry 2 }

sdpBndIgmpSnpgStaticRowstatus    OBJECT-TYPE
    SYNTAX      RowStatus
    MAX-ACCESS  read-create
    STATUS      current
    DESCRIPTION
        "The value of the object sdpBndIgmpSnpgStaticRowstatus specifies the
         row status used for creation or deletion of
         sdpBindIgmpSnpgStaticGrpSrcTable entries."
    ::= { sdpBindIgmpSnpgStatGrpSrcEntry 3 }

sdpBndIgmpSnpgStaticLastChange   OBJECT-TYPE
    SYNTAX      TimeStamp
    MAX-ACCESS  read-only
    STATUS      current
    DESCRIPTION
        "The value of the object sdpBndIgmpSnpgStaticLastChange indicates the
         sysUpTime at the time of the last modification of this entry."
    ::= { sdpBindIgmpSnpgStatGrpSrcEntry 4 }

sdpBindIgmpSnpgStatsTable        OBJECT-TYPE
    SYNTAX      SEQUENCE OF SdpBindIgmpSnpgStatsEntry
    MAX-ACCESS  not-accessible
    STATUS      current
    DESCRIPTION
        "sdpBindIgmpSnpgStatsTable contains statistics on IGMP snooping per SDP
         Bind."
    ::= { alxIgmpSnoopingSdpBindObjs 5 }

sdpBindIgmpSnpgStatsEntry        OBJECT-TYPE
    SYNTAX      SdpBindIgmpSnpgStatsEntry
    MAX-ACCESS  not-accessible
    STATUS      current
    DESCRIPTION
        "sdpBindIgmpSnpgStatsEntry is an entry in the
         sdpBindIgmpSnpgStatsTable. Each entry contains IGMP snooping statics
         for a SDP Bind in a Tls."
    INDEX       {
        svcId,
        sdpBindId
    }
    ::= { sdpBindIgmpSnpgStatsTable 1 }

SdpBindIgmpSnpgStatsEntry        ::= SEQUENCE
{
    sdpBndIgmpSnpgTxGenQueries       Counter32,
    sdpBndIgmpSnpgTxGrpSpecQueries   Counter32,
    sdpBndIgmpSnpgTxSrcSpecQueries   Counter32,
    sdpBndIgmpSnpgTxV1Reports        Counter32,
    sdpBndIgmpSnpgTxV2Reports        Counter32,
    sdpBndIgmpSnpgTxV3Reports        Counter32,
    sdpBndIgmpSnpgTxV2Leaves         Counter32,
    sdpBndIgmpSnpgRxGenQueries       Counter32,
    sdpBndIgmpSnpgRxGrpSpecQueries   Counter32,
    sdpBndIgmpSnpgRxSrcSpecQueries   Counter32,
    sdpBndIgmpSnpgRxV1Reports        Counter32,
    sdpBndIgmpSnpgRxV2Reports        Counter32,
    sdpBndIgmpSnpgRxV3Reports        Counter32,
    sdpBndIgmpSnpgRxV2Leaves         Counter32,
    sdpBndIgmpSnpgRxUnknownType      Counter32,
    sdpBndIgmpSnpgFwdGenQueries      Counter32,
    sdpBndIgmpSnpgFwdGrpSpecQueries  Counter32,
    sdpBndIgmpSnpgFwdSrcSpecQueries  Counter32,
    sdpBndIgmpSnpgFwdV1Reports       Counter32,
    sdpBndIgmpSnpgFwdV2Reports       Counter32,
    sdpBndIgmpSnpgFwdV3Reports       Counter32,
    sdpBndIgmpSnpgFwdV2Leaves        Counter32,
    sdpBndIgmpSnpgFwdUnknownType     Counter32,
    sdpBndIgmpSnpgRxBadLenPkts       Counter32,
    sdpBndIgmpSnpgRxBadIpChksmPkts   Counter32,
    sdpBndIgmpSnpgRxBadIgmpChksmPkts Counter32,
    sdpBndIgmpSnpgRxBadEncodedPkts   Counter32,
    sdpBndIgmpSnpgRxNoRtrAlertPkts   Counter32,
    sdpBndIgmpSnpgRxZeroSrcAdrPkts   Counter32,
    sdpBndIgmpSnpgSendQueryCfgDrops  Counter32,
    sdpBndIgmpSnpgImportPolicyDrops  Counter32,
    sdpBndIgmpSnpgMaxNumGroupsDrops  Counter32,
    sdpBndIgmpSnpgRxWrongVersionPkts Counter32,
    sdpBndIgmpSnpgMcacPolicyDrops    Counter32,
    sdpBndIgmpSnpgRxLocalScopePkts   Counter32,
    sdpBndIgmpSnpgRxRsvdScopePkts    Counter32,
    sdpBndIgmpSnpgMaxNumSourcesDrops Counter32,
    sdpBndIgmpSnpgMaxNumGrpSrcsDrops Counter32
}

sdpBndIgmpSnpgTxGenQueries       OBJECT-TYPE
    SYNTAX      Counter32
    MAX-ACCESS  read-only
    STATUS      current
    DESCRIPTION
        "The value of the object sdpBndIgmpSnpgTxGenQueries indicates the
         number of IGMP General Queries transmitted on this SDP Bind."
    ::= { sdpBindIgmpSnpgStatsEntry 1 }

sdpBndIgmpSnpgTxGrpSpecQueries   OBJECT-TYPE
    SYNTAX      Counter32
    MAX-ACCESS  read-only
    STATUS      current
    DESCRIPTION
        "The value of the object sdpBndIgmpSnpgTxGrpSpecQueries indicates the
         number of IGMP Group-Specific Queries transmitted on this SDP Bind."
    ::= { sdpBindIgmpSnpgStatsEntry 2 }

sdpBndIgmpSnpgTxSrcSpecQueries   OBJECT-TYPE
    SYNTAX      Counter32
    MAX-ACCESS  read-only
    STATUS      current
    DESCRIPTION
        "The value of the object sdpBndIgmpSnpgTxSrcSpecQueries indicates the
         number of IGMP Group-And-Source-Specific Queries transmitted on this
         SDP Bind."
    ::= { sdpBindIgmpSnpgStatsEntry 3 }

sdpBndIgmpSnpgTxV1Reports        OBJECT-TYPE
    SYNTAX      Counter32
    MAX-ACCESS  read-only
    STATUS      current
    DESCRIPTION
        "The value of the object sdpBndIgmpSnpgTxV1Reports indicates the number
         of IGMPv1 Reports transmitted on this SDP Bind."
    ::= { sdpBindIgmpSnpgStatsEntry 4 }

sdpBndIgmpSnpgTxV2Reports        OBJECT-TYPE
    SYNTAX      Counter32
    MAX-ACCESS  read-only
    STATUS      current
    DESCRIPTION
        "The value of the object sdpBndIgmpSnpgTxV2Reports indicates the number
         of IGMPv2 Reports transmitted on this SDP Bind."
    ::= { sdpBindIgmpSnpgStatsEntry 5 }

sdpBndIgmpSnpgTxV3Reports        OBJECT-TYPE
    SYNTAX      Counter32
    MAX-ACCESS  read-only
    STATUS      current
    DESCRIPTION
        "The value of the object sdpBndIgmpSnpgTxV3Reports indicates the number
         of IGMPv3 Reports transmitted on this SDP Bind."
    ::= { sdpBindIgmpSnpgStatsEntry 6 }

sdpBndIgmpSnpgTxV2Leaves         OBJECT-TYPE
    SYNTAX      Counter32
    MAX-ACCESS  read-only
    STATUS      current
    DESCRIPTION
        "The value of the object sdpBndIgmpSnpgTxV2Leaves indicates the number
         of IGMPv2 Leaves transmitted on this SDP Bind."
    ::= { sdpBindIgmpSnpgStatsEntry 7 }

sdpBndIgmpSnpgRxGenQueries       OBJECT-TYPE
    SYNTAX      Counter32
    MAX-ACCESS  read-only
    STATUS      current
    DESCRIPTION
        "The value of the object sdpBndIgmpSnpgRxGenQueries indicates the
         number of IGMP General Queries received on this SDP Bind."
    ::= { sdpBindIgmpSnpgStatsEntry 8 }

sdpBndIgmpSnpgRxGrpSpecQueries   OBJECT-TYPE
    SYNTAX      Counter32
    MAX-ACCESS  read-only
    STATUS      current
    DESCRIPTION
        "The value of the object sdpBndIgmpSnpgRxGrpSpecQueries indicates the
         number of IGMP Group-Specific Queries received on this SDP Bind."
    ::= { sdpBindIgmpSnpgStatsEntry 9 }

sdpBndIgmpSnpgRxSrcSpecQueries   OBJECT-TYPE
    SYNTAX      Counter32
    MAX-ACCESS  read-only
    STATUS      current
    DESCRIPTION
        "The value of the object sdpBndIgmpSnpgRxSrcSpecQueries indicates the
         number of IGMP Group-And-Source-Specific Queries received on this SDP
         Bind."
    ::= { sdpBindIgmpSnpgStatsEntry 10 }

sdpBndIgmpSnpgRxV1Reports        OBJECT-TYPE
    SYNTAX      Counter32
    MAX-ACCESS  read-only
    STATUS      current
    DESCRIPTION
        "The value of the object sdpBndIgmpSnpgRxV1Reports indicates the number
         of IGMPv1 Reports received on this SDP Bind."
    ::= { sdpBindIgmpSnpgStatsEntry 11 }

sdpBndIgmpSnpgRxV2Reports        OBJECT-TYPE
    SYNTAX      Counter32
    MAX-ACCESS  read-only
    STATUS      current
    DESCRIPTION
        "The value of the object sdpBndIgmpSnpgRxV2Reports indicates the number
         of IGMPv2 Reports received on this SDP Bind."
    ::= { sdpBindIgmpSnpgStatsEntry 12 }

sdpBndIgmpSnpgRxV3Reports        OBJECT-TYPE
    SYNTAX      Counter32
    MAX-ACCESS  read-only
    STATUS      current
    DESCRIPTION
        "The value of the object sdpBndIgmpSnpgRxV3Reports indicates the number
         of IGMPv3 Reports received on this SDP Bind."
    ::= { sdpBindIgmpSnpgStatsEntry 13 }

sdpBndIgmpSnpgRxV2Leaves         OBJECT-TYPE
    SYNTAX      Counter32
    MAX-ACCESS  read-only
    STATUS      current
    DESCRIPTION
        "The value of the object sdpBndIgmpSnpgRxV2Leaves indicates the number
         of IGMPv2 Leaves received on this SDP Bind."
    ::= { sdpBindIgmpSnpgStatsEntry 14 }

sdpBndIgmpSnpgRxUnknownType      OBJECT-TYPE
    SYNTAX      Counter32
    MAX-ACCESS  read-only
    STATUS      current
    DESCRIPTION
        "The value of the object sdpBndIgmpSnpgRxUnknownType indicates the
         number of IGMP unknown type packets received on this SDP Bind."
    ::= { sdpBindIgmpSnpgStatsEntry 15 }

sdpBndIgmpSnpgFwdGenQueries      OBJECT-TYPE
    SYNTAX      Counter32
    MAX-ACCESS  read-only
    STATUS      current
    DESCRIPTION
        "The value of the object sdpBndIgmpSnpgFwdGenQueries indicates the
         number of IGMP General Queries forwarded on this SDP Bind."
    ::= { sdpBindIgmpSnpgStatsEntry 16 }

sdpBndIgmpSnpgFwdGrpSpecQueries  OBJECT-TYPE
    SYNTAX      Counter32
    MAX-ACCESS  read-only
    STATUS      current
    DESCRIPTION
        "The value of the object sdpBndIgmpSnpgFwdGrpSpecQueries indicates the
         number of IGMP Group-Specific Queries forwarded on this SDP Bind."
    ::= { sdpBindIgmpSnpgStatsEntry 17 }

sdpBndIgmpSnpgFwdSrcSpecQueries  OBJECT-TYPE
    SYNTAX      Counter32
    MAX-ACCESS  read-only
    STATUS      current
    DESCRIPTION
        "The value of the object sdpBndIgmpSnpgFwdSrcSpecQueries indicates the
         number of IGMP Group-And-Source-Specific Queries forwarded on this SDP
         Bind."
    ::= { sdpBindIgmpSnpgStatsEntry 18 }

sdpBndIgmpSnpgFwdV1Reports       OBJECT-TYPE
    SYNTAX      Counter32
    MAX-ACCESS  read-only
    STATUS      current
    DESCRIPTION
        "The value of the object sdpBndIgmpSnpgFwdV1Reports indicates the
         number of IGMPv1 Reports forwarded on this SDP Bind."
    ::= { sdpBindIgmpSnpgStatsEntry 19 }

sdpBndIgmpSnpgFwdV2Reports       OBJECT-TYPE
    SYNTAX      Counter32
    MAX-ACCESS  read-only
    STATUS      current
    DESCRIPTION
        "The value of the object sdpBndIgmpSnpgFwdV2Reports indicates
         the  number of IGMPv2 Reports forwarded on this SDP Bind."
    ::= { sdpBindIgmpSnpgStatsEntry 20 }

sdpBndIgmpSnpgFwdV3Reports       OBJECT-TYPE
    SYNTAX      Counter32
    MAX-ACCESS  read-only
    STATUS      current
    DESCRIPTION
        "The value of the object sdpBndIgmpSnpgFwdV3Reports indicates the
         number of IGMPv3 Reports forwarded on this SDP Bind."
    ::= { sdpBindIgmpSnpgStatsEntry 21 }

sdpBndIgmpSnpgFwdV2Leaves        OBJECT-TYPE
    SYNTAX      Counter32
    MAX-ACCESS  read-only
    STATUS      current
    DESCRIPTION
        "The value of the object sdpBndIgmpSnpgFwdV2Leaves indicates the number
         of IGMPv2 Leaves forwarded on this SDP Bind."
    ::= { sdpBindIgmpSnpgStatsEntry 22 }

sdpBndIgmpSnpgFwdUnknownType     OBJECT-TYPE
    SYNTAX      Counter32
    MAX-ACCESS  read-only
    STATUS      current
    DESCRIPTION
        "The value of the object sdpBndIgmpSnpgFwdUnknownType indicates the
         number of IGMP unknown type packets forwarded on this SDP Bind."
    ::= { sdpBindIgmpSnpgStatsEntry 23 }

sdpBndIgmpSnpgRxBadLenPkts       OBJECT-TYPE
    SYNTAX      Counter32
    MAX-ACCESS  read-only
    STATUS      current
    DESCRIPTION
        "The value of the object sdpBndIgmpSnpgRxBadLenPkts indicates the
         number of IGMP packets dropped on this SDP Bind because of a bad
         length."
    ::= { sdpBindIgmpSnpgStatsEntry 24 }

sdpBndIgmpSnpgRxBadIpChksmPkts   OBJECT-TYPE
    SYNTAX      Counter32
    MAX-ACCESS  read-only
    STATUS      current
    DESCRIPTION
        "The value of the object sdpBndIgmpSnpgRxBadIpChksmPkts indicates the
         number of dropped IGMP packets on this SDP Bind because of a bad IPv4
         header checksum."
    ::= { sdpBindIgmpSnpgStatsEntry 25 }

sdpBndIgmpSnpgRxBadIgmpChksmPkts OBJECT-TYPE
    SYNTAX      Counter32
    MAX-ACCESS  read-only
    STATUS      current
    DESCRIPTION
        "The value of the object sdpBndIgmpSnpgRxBadIgmpChksmPkts indicates
         the number of  dropped  IGMP packets on this SDP Bind because of a
         bad IGMP header checksum."
    ::= { sdpBindIgmpSnpgStatsEntry 26 }

sdpBndIgmpSnpgRxBadEncodedPkts   OBJECT-TYPE
    SYNTAX      Counter32
    MAX-ACCESS  read-only
    STATUS      current
    DESCRIPTION
        "The value of the object sdpBndIgmpSnpgRxBadEncodedPkts indicates the
         number of IGMP packets dropped on this SDP Bind because of a bad
         encoding."
    ::= { sdpBindIgmpSnpgStatsEntry 27 }

sdpBndIgmpSnpgRxNoRtrAlertPkts   OBJECT-TYPE
    SYNTAX      Counter32
    MAX-ACCESS  read-only
    STATUS      current
    DESCRIPTION
        "The value of the object sdpBndIgmpSnpgRxNoRtrAlertPkts indicates the
         number of IGMP packets dropped on this SDP Bind because the Router
         Alert Option in the IP packet is not set."
    ::= { sdpBindIgmpSnpgStatsEntry 28 }

sdpBndIgmpSnpgRxZeroSrcAdrPkts   OBJECT-TYPE
    SYNTAX      Counter32
    MAX-ACCESS  read-only
    STATUS      current
    DESCRIPTION
        "The value of the object sdpBndIgmpSnpgRxZeroSrcAdrPkts indicates the
         number of IGMP packets dropped on this SDP Bind because they contain a
         zero source IPv4 address."
    ::= { sdpBindIgmpSnpgStatsEntry 29 }

sdpBndIgmpSnpgSendQueryCfgDrops  OBJECT-TYPE
    SYNTAX      Counter32
    MAX-ACCESS  read-only
    STATUS      current
    DESCRIPTION
        "The  value of the object sdpBndIgmpSnpgSendQueryCfgDrops indicates
         the number of times an IGMP Query is dropped because the
         object sdpBndIgmpSnpgCfgSendQueries for this SDP Bind is set to
         'enabled(1)'."
    ::= { sdpBindIgmpSnpgStatsEntry 30 }

sdpBndIgmpSnpgImportPolicyDrops  OBJECT-TYPE
    SYNTAX      Counter32
    MAX-ACCESS  read-only
    STATUS      current
    DESCRIPTION
        "The  value of the object sdpBndIgmpSnpgImportPolicyDrops indicates
         the number of times an IGMP Group or Source is dropped
         because of applying an import policy on this SDP Bind."
    ::= { sdpBindIgmpSnpgStatsEntry 31 }

sdpBndIgmpSnpgMaxNumGroupsDrops  OBJECT-TYPE
    SYNTAX      Counter32
    MAX-ACCESS  read-only
    STATUS      current
    DESCRIPTION
        "The  value of the object sdpBndIgmpSnpgMaxNumGroupsDrops indicates
         the number of times an IGMP Group is dropped because of
         exceeding the configured maximum number of groups on this SDP
         Bind."
    ::= { sdpBindIgmpSnpgStatsEntry 32 }

sdpBndIgmpSnpgRxWrongVersionPkts OBJECT-TYPE
    SYNTAX      Counter32
    MAX-ACCESS  read-only
    STATUS      current
    DESCRIPTION
        "The value of the object sdpBndIgmpSnpgRxWrongVersionPkts indicates the
         total number of IGMP packets with a wrong version received on this SDP
         Bind."
    ::= { sdpBindIgmpSnpgStatsEntry 33 }

sdpBndIgmpSnpgMcacPolicyDrops    OBJECT-TYPE
    SYNTAX      Counter32
    MAX-ACCESS  read-only
    STATUS      current
    DESCRIPTION
        "The value of the object sdpBndIgmpSnpgMcacPolicyDrops indicates the
         number of times an IGMP Group is dropped because of applying a
         multicast CAC policy on this SDP Bind."
    ::= { sdpBindIgmpSnpgStatsEntry 34 }

sdpBndIgmpSnpgRxLocalScopePkts   OBJECT-TYPE
    SYNTAX      Counter32
    MAX-ACCESS  read-only
    STATUS      current
    DESCRIPTION
        "The value of the object sdpBndIgmpSnpgRxLocalScopePkts indicates the
         number of IGMP packets received on the link-local scope IPv6 multicast
         address."
    ::= { sdpBindIgmpSnpgStatsEntry 35 }

sdpBndIgmpSnpgRxRsvdScopePkts    OBJECT-TYPE
    SYNTAX      Counter32
    MAX-ACCESS  read-only
    STATUS      current
    DESCRIPTION
        "The value of the object sdpBndIgmpSnpgRxRsvdScopePkts indicates the
         number of IGMP packets received on the reserved scope IPv6 multicast
         address."
    ::= { sdpBindIgmpSnpgStatsEntry 36 }

sdpBndIgmpSnpgMaxNumSourcesDrops OBJECT-TYPE
    SYNTAX      Counter32
    MAX-ACCESS  read-only
    STATUS      current
    DESCRIPTION
        "The value of the object sdpBndIgmpSnpgMaxNumSourcesDrops indicates the
         number of times an IGMP Source is dropped because of exceeding the
         configured maximum number of sources per group on this SDP Bind."
    ::= { sdpBindIgmpSnpgStatsEntry 37 }

sdpBndIgmpSnpgMaxNumGrpSrcsDrops OBJECT-TYPE
    SYNTAX      Counter32
    MAX-ACCESS  read-only
    STATUS      current
    DESCRIPTION
        "The value of the object sdpBndIgmpSnpgMaxNumGrpSrcsDrops indicates the
         number of times an IGMP Group Source is dropped because of exceeding
         the configured maximum number of group sources per group on this SDP
         Bind."
    ::= { sdpBindIgmpSnpgStatsEntry 38 }

alxIgmpSnoopingNotificationObjs  OBJECT IDENTIFIER ::= { alxIgmpSnoopingObjs 4 }

alxIgmpSnpgGroupAddress          OBJECT-TYPE
    SYNTAX      IpAddress
    MAX-ACCESS  accessible-for-notify
    STATUS      current
    DESCRIPTION
        "The value of the object alxIgmpSnpgGroupAddress indicates an IP
         multicast group address."
    ::= { alxIgmpSnoopingNotificationObjs 1 }

alxIgmpSnpgMcsFailureReason      OBJECT-TYPE
    SYNTAX      DisplayString
    MAX-ACCESS  accessible-for-notify
    STATUS      current
    DESCRIPTION
        "The value of the object alxIgmpSnpgMcsFailureReason indicates the
         reason why the sapIgmpSnpgMcsFailure notification is sent."
    ::= { alxIgmpSnoopingNotificationObjs 2 }

alxIgmpSnpgSourceAddress         OBJECT-TYPE
    SYNTAX      IpAddress
    MAX-ACCESS  accessible-for-notify
    STATUS      current
    DESCRIPTION
        "The value of the object alxIgmpSnpgSourceAddress indicates an IP
         multicast source address."
    ::= { alxIgmpSnoopingNotificationObjs 3 }

alxIgmpSnpgDescription           OBJECT-TYPE
    SYNTAX      DisplayString
    MAX-ACCESS  accessible-for-notify
    STATUS      current
    DESCRIPTION
        "The object alxIgmpSnpgDescription is a printable character string."
    ::= { alxIgmpSnoopingNotificationObjs 4 }

alxIgmpSnpgEMplsTepAddressType   OBJECT-TYPE
    SYNTAX      InetAddressType
    MAX-ACCESS  accessible-for-notify
    STATUS      current
    DESCRIPTION
        "The value of the object alxIgmpSnpgEMplsTepAddressType indicates the
         type of alxIgmpSnpgEMplsTepAddress."
    ::= { alxIgmpSnoopingNotificationObjs 5 }

alxIgmpSnpgEMplsTepAddress       OBJECT-TYPE
    SYNTAX      InetAddress (SIZE (4|16))
    MAX-ACCESS  accessible-for-notify
    STATUS      current
    DESCRIPTION
        "The value of the object alxIgmpSnpgEMplsTepAddress indicates an
         evpn-mpls endpoint IP address."
    ::= { alxIgmpSnoopingNotificationObjs 6 }

alxIgmpSnpgEMplsTepLabel         OBJECT-TYPE
    SYNTAX      Unsigned32
    MAX-ACCESS  accessible-for-notify
    STATUS      current
    DESCRIPTION
        "The value of the object alxIgmpSnpgEMplsTepLabel indicates an
         evpn-mpls endpoint label."
    ::= { alxIgmpSnoopingNotificationObjs 7 }

alxIgmpSnoopingTimeStampObjs     OBJECT IDENTIFIER ::= { alxIgmpSnoopingObjs 5 }

tlsIgmpSnpgConfigTableLastChange OBJECT-TYPE
    SYNTAX      TimeStamp
    MAX-ACCESS  read-only
    STATUS      current
    DESCRIPTION
        "The value of the object tlsIgmpSnpgConfigTableLastChange indicates the
         value of sysUpTime at the time of the last modification of an entry in
         the tlsIgmpSnpgConfigTable."
    ::= { alxIgmpSnoopingTimeStampObjs 1 }

sapIgmpSnpgConfigTableLastChange OBJECT-TYPE
    SYNTAX      TimeStamp
    MAX-ACCESS  read-only
    STATUS      current
    DESCRIPTION
        "The value of the object sapIgmpSnpgConfigTableLastChange indicates the
         value of sysUpTime at the time of the last modification of an entry in
         the sapIgmpSnpgConfigTable."
    ::= { alxIgmpSnoopingTimeStampObjs 2 }

sapIgmpSnpgStaticGrpSrcTablLstCh OBJECT-TYPE
    SYNTAX      TimeStamp
    MAX-ACCESS  read-only
    STATUS      current
    DESCRIPTION
        "The value of the object sapIgmpSnpgStaticGrpSrcTablLstCh indicates the
         value of sysUpTime at the time of the last modification of an entry in
         the sapIgmpSnpgStaticGrpSrcTable."
    ::= { alxIgmpSnoopingTimeStampObjs 3 }

sapIgmpSnpgMcacLevelTableLstCh   OBJECT-TYPE
    SYNTAX      TimeStamp
    MAX-ACCESS  read-only
    STATUS      current
    DESCRIPTION
        "The value of the object sapIgmpSnpgMcacLevelTableLstCh indicates the
         value of sysUpTime at the time of the last modification of an entry in
         the sapIgmpSnpgMcacLevelTable."
    ::= { alxIgmpSnoopingTimeStampObjs 4 }

sapIgmpSnpgMcacLagTableLastChng  OBJECT-TYPE
    SYNTAX      TimeStamp
    MAX-ACCESS  read-only
    STATUS      current
    DESCRIPTION
        "The value of the object sapIgmpSnpgMcacLagTableLastChng indicates the
         value of sysUpTime at the time of the last modification of an entry in
         the sapIgmpSnpgMcacLagTable."
    ::= { alxIgmpSnoopingTimeStampObjs 5 }

sdpBindIgmpSnpgConfigTableLstCh  OBJECT-TYPE
    SYNTAX      TimeStamp
    MAX-ACCESS  read-only
    STATUS      current
    DESCRIPTION
        "The value of the object sdpBindIgmpSnpgConfigTableLstCh indicates the
         value of sysUpTime at the time of the last modification of an entry in
         the sdpBindIgmpSnpgConfigTable."
    ::= { alxIgmpSnoopingTimeStampObjs 6 }

sdpBindIgmpSnpgStaticGrpSrcTblLC OBJECT-TYPE
    SYNTAX      TimeStamp
    MAX-ACCESS  read-only
    STATUS      current
    DESCRIPTION
        "The value of the object sdpBindIgmpSnpgStaticGrpSrcTblLC indicates the
         value of sysUpTime at the time of the last modification of an entry in
         the sdpBindIgmpSnpgStaticGrpSrcTable."
    ::= { alxIgmpSnoopingTimeStampObjs 7 }

alxIgmpSnoopingVxlanObjs         OBJECT IDENTIFIER ::= { alxIgmpSnoopingObjs 6 }

vxlanIgmpSnpgGroupTable          OBJECT-TYPE
    SYNTAX      SEQUENCE OF VxlanIgmpSnpgGroupEntry
    MAX-ACCESS  not-accessible
    STATUS      current
    DESCRIPTION
        "vxlanIgmpSnpgGroupTable together with the table
         vxlanIgmpSnpgGrpSrcTable contains multicast group address information
         collected by IGMP snooping for each VXLAN."
    ::= { alxIgmpSnoopingVxlanObjs 1 }

vxlanIgmpSnpgGroupEntry          OBJECT-TYPE
    SYNTAX      VxlanIgmpSnpgGroupEntry
    MAX-ACCESS  not-accessible
    STATUS      current
    DESCRIPTION
        "Each entry in this table indicates a multicast group address learned
         by IGMP snooping on this VXLAN. If a Source list is present it is
         described in the corresponding entries of the vxlanIgmpSnpgGrpSrcTable
         table."
    INDEX       {
        svcId,
        vxlanVTEPAddr,
        vxlanVNI,
        vxlanIgmpSnpgGrpAddress
    }
    ::= { vxlanIgmpSnpgGroupTable 1 }

VxlanIgmpSnpgGroupEntry          ::= SEQUENCE
{
    vxlanVTEPAddr                    IpAddress,
    vxlanVNI                         Unsigned32,
    vxlanIgmpSnpgGrpAddress          IpAddress,
    vxlanIgmpSnpgGrpType             TmnxIgmpSnpgGroupType,
    vxlanIgmpSnpgGrpFilterMode       TmnxIgmpGroupFilterMode,
    vxlanIgmpSnpgGrpUpTime           TimeTicks,
    vxlanIgmpSnpgGrpExpiryTime       Unsigned32,
    vxlanIgmpSnpgGrpCompatMode       Unsigned32,
    vxlanIgmpSnpgGrpV1HostExpTime    Unsigned32,
    vxlanIgmpSnpgGrpV2HostExpTime    Unsigned32
}

vxlanVTEPAddr                    OBJECT-TYPE
    SYNTAX      IpAddress
    MAX-ACCESS  not-accessible
    STATUS      current
    DESCRIPTION
        "The value of the object vxlanVTEPAddr indicates the VXLAN (virtual
         extensible LAN) Tunnel Endpoint address of ethernet VPN (EVPN)
         destination on which the active Querier is detected."
    ::= { vxlanIgmpSnpgGroupEntry 1 }

vxlanVNI                         OBJECT-TYPE
    SYNTAX      Unsigned32
    MAX-ACCESS  not-accessible
    STATUS      current
    DESCRIPTION
        "The value of the object vxlanVNI indicates the VXLAN (virtual
         extensible LAN) Network Identifier (VNI) of the end-point of ethernet
         VPN (EVPN) destination interface on which the active Querier is
         detected."
    ::= { vxlanIgmpSnpgGroupEntry 2 }

vxlanIgmpSnpgGrpAddress          OBJECT-TYPE
    SYNTAX      IpAddress
    MAX-ACCESS  not-accessible
    STATUS      current
    DESCRIPTION
        "The value of the object vxlanIgmpSnpgGrpAddress indicates the IPv4
         multicast group address for which this entry contains information."
    ::= { vxlanIgmpSnpgGroupEntry 3 }

vxlanIgmpSnpgGrpType             OBJECT-TYPE
    SYNTAX      TmnxIgmpSnpgGroupType
    MAX-ACCESS  read-only
    STATUS      current
    DESCRIPTION
        "The value of the object vxlanIgmpSnpgGrpType indicates whether this
         entry was learned dynamically or was statically configured."
    ::= { vxlanIgmpSnpgGroupEntry 4 }

vxlanIgmpSnpgGrpFilterMode       OBJECT-TYPE
    SYNTAX      TmnxIgmpGroupFilterMode
    MAX-ACCESS  read-only
    STATUS      current
    DESCRIPTION
        "The value of the object vxlanIgmpSnpgGrpFilterMode indicates the
         filter-mode for this group."
    ::= { vxlanIgmpSnpgGroupEntry 5 }

vxlanIgmpSnpgGrpUpTime           OBJECT-TYPE
    SYNTAX      TimeTicks
    MAX-ACCESS  read-only
    STATUS      current
    DESCRIPTION
        "The value of the object vxlanIgmpSnpgGrpUpTime indicates how long (in
         centiseconds) that the group address already exists in the database
         for this VXLAN."
    ::= { vxlanIgmpSnpgGroupEntry 6 }

vxlanIgmpSnpgGrpExpiryTime       OBJECT-TYPE
    SYNTAX      Unsigned32
    UNITS       "seconds"
    MAX-ACCESS  read-only
    STATUS      current
    DESCRIPTION
        "The value of the object vxlanIgmpSnpgGrpExpiryTime indicates the
         amount of time remaining before this entry will be aged out."
    ::= { vxlanIgmpSnpgGroupEntry 7 }

vxlanIgmpSnpgGrpCompatMode       OBJECT-TYPE
    SYNTAX      Unsigned32
    MAX-ACCESS  read-only
    STATUS      current
    DESCRIPTION
        "The value of the object vxlanIgmpSnpgGrpCompatMode indicates the IGMP
         version applicable on this VXLAN for this multicast group address.
         This corresponds to the lowest version seen for this group address on
         this VXLAN."
    ::= { vxlanIgmpSnpgGroupEntry 8 }

vxlanIgmpSnpgGrpV1HostExpTime    OBJECT-TYPE
    SYNTAX      Unsigned32
    UNITS       "seconds"
    MAX-ACCESS  read-only
    STATUS      current
    DESCRIPTION
        "The value of the object vxlanIgmpSnpgGrpV1HostExpTime indicates the
         time remaining until the system will assume that there are no longer
         any IGMPv1 members on this VXLAN.

         Upon hearing any IGMPv1 Membership Report, this value is reset to the
         group membership interval. While this time remaining is non-zero, the
         system ignores any IGMPv2 and IGMPv3 'leave' messages for this group
         that it receives on this VXLAN."
    ::= { vxlanIgmpSnpgGroupEntry 9 }

vxlanIgmpSnpgGrpV2HostExpTime    OBJECT-TYPE
    SYNTAX      Unsigned32
    UNITS       "seconds"
    MAX-ACCESS  read-only
    STATUS      current
    DESCRIPTION
        "The value of the object vxlanIgmpSnpgGrpV2HostExpTime indicates the
         time remaining until the system will assume that there are no longer
         any IGMPv2 members on the VXLAN.

         Upon hearing any IGMPv2 Membership Report, this value is reset to the
         group membership interval. While this time remaining is non-zero, the
         system ignores any IGMPv3 'leave' messages for this group that it
         receives on this VXLAN."
    ::= { vxlanIgmpSnpgGroupEntry 10 }

vxlanIgmpSnpgGrpSrcTable         OBJECT-TYPE
    SYNTAX      SEQUENCE OF VxlanIgmpSnpgGrpSrcEntry
    MAX-ACCESS  not-accessible
    STATUS      current
    DESCRIPTION
        "vxlanIgmpSnpgGrpSrcTable lists the IPv4 multicast Sources
         corresponding to the IPv4 multicast groups listed in the
         vxlanIgmpSnpgGroupTable."
    ::= { alxIgmpSnoopingVxlanObjs 2 }

vxlanIgmpSnpgGrpSrcEntry         OBJECT-TYPE
    SYNTAX      VxlanIgmpSnpgGrpSrcEntry
    MAX-ACCESS  not-accessible
    STATUS      current
    DESCRIPTION
        "An entry in the vxlanIgmpSnpgGrpSrcTable. Each entry represents a
         Source address from which receivers are interested/not interested in
         receiving multicast traffic from."
    INDEX       {
        svcId,
        vxlanVTEPAddr,
        vxlanVNI,
        vxlanIgmpSnpgGrpAddress,
        vxlanIgmpSnpgGrpSrcAddr
    }
    ::= { vxlanIgmpSnpgGrpSrcTable 1 }

VxlanIgmpSnpgGrpSrcEntry         ::= SEQUENCE
{
    vxlanIgmpSnpgGrpSrcAddr          IpAddress,
    vxlanIgmpSnpgGrpSrcType          TmnxIgmpSnpgGroupType,
    vxlanIgmpSnpgGrpSrcUpTime        TimeTicks,
    vxlanIgmpSnpgGrpSrcExpiryTime    Unsigned32
}

vxlanIgmpSnpgGrpSrcAddr          OBJECT-TYPE
    SYNTAX      IpAddress
    MAX-ACCESS  not-accessible
    STATUS      current
    DESCRIPTION
        "The value of the object vxlanIgmpSnpgGrpSrcAddr indicates the address
         of the Source sending multicast traffic to the group identified by
         vxlanIgmpSnpgGrpAddress.

         If the value of vxlanIgmpSnpgGrpFilterMode corresponding to this entry
         is 'include(1)', the receivers are interested in receiving traffic
         from this Source.

         If the value of vxlanIgmpSnpgGrpFilterMode corresponding to this entry
         is 'exclude(2)', the receivers are not interested in receiving traffic
         from this Source."
    ::= { vxlanIgmpSnpgGrpSrcEntry 1 }

vxlanIgmpSnpgGrpSrcType          OBJECT-TYPE
    SYNTAX      TmnxIgmpSnpgGroupType
    MAX-ACCESS  read-only
    STATUS      current
    DESCRIPTION
        "The value of the object vxlanIgmpSnpgGrpSrcType indicates how this
         source entry was learned.

         If this source entry was learned, it is set to 'dynamic(2)'. For
         statically configured sources, the value is set to 'static(1)'."
    ::= { vxlanIgmpSnpgGrpSrcEntry 2 }

vxlanIgmpSnpgGrpSrcUpTime        OBJECT-TYPE
    SYNTAX      TimeTicks
    MAX-ACCESS  read-only
    STATUS      current
    DESCRIPTION
        "The value of the object vxlanIgmpSnpgGrpSrcUpTime indicates how long
         (in centiseconds) that the Source address already exists in the
         database for this SAP."
    ::= { vxlanIgmpSnpgGrpSrcEntry 3 }

vxlanIgmpSnpgGrpSrcExpiryTime    OBJECT-TYPE
    SYNTAX      Unsigned32
    UNITS       "seconds"
    MAX-ACCESS  read-only
    STATUS      current
    DESCRIPTION
        "The value of the object vxlanIgmpSnpgGrpSrcExpiryTime indicates the
         minimum amount of time remaining before this entry will be aged out.

         If the value of vxlanIgmpSnpgGrpSrcExpiryTime is non-zero and the
         value of vxlanIgmpSnpgGrpFilterMode corresponding to this entry is
         'include(1)', it means that there are currently one or more systems
         which desire to receive multicast traffic for this Source.

         If this timer expires and the value of vxlanIgmpSnpgGrpFilterMode is
         'include(1)', the system concludes that traffic from this particular
         Source is no longer desired on the attached network, and deletes this
         entry.

         If the value of vxlanIgmpSnpgGrpSrcExpiryTime is non-zero and the
         filter-mode for the group is 'exclude(2)', it means that at least one
         system desires to receive multicast traffic from this source.

         If the value of vxlanIgmpSnpgGrpSrcExpiryTime is zero and the
         filter-mode for the group is 'exclude(2)', it means that no system
         desires to receive multicast traffic from this Source."
    ::= { vxlanIgmpSnpgGrpSrcEntry 4 }

vxlanIgmpSnpgStatsTable          OBJECT-TYPE
    SYNTAX      SEQUENCE OF VxlanIgmpSnpgStatsEntry
    MAX-ACCESS  not-accessible
    STATUS      current
    DESCRIPTION
        "vxlanIgmpSnpgStatsTable contains statistics on IGMP snooping per
         VXLAN."
    ::= { alxIgmpSnoopingVxlanObjs 3 }

vxlanIgmpSnpgStatsEntry          OBJECT-TYPE
    SYNTAX      VxlanIgmpSnpgStatsEntry
    MAX-ACCESS  not-accessible
    STATUS      current
    DESCRIPTION
        "vxlanIgmpSnpgStatsEntry is an entry in the vxlanIgmpSnpgStatsTable.
         Each entry contains IGMP snooping statics for a VXLAN in a Tls."
    INDEX       {
        svcId,
        vxlanVTEPAddr,
        vxlanVNI
    }
    ::= { vxlanIgmpSnpgStatsTable 1 }

VxlanIgmpSnpgStatsEntry          ::= SEQUENCE
{
    vxlanIgmpSnpgTxGenQueries        Counter32,
    vxlanIgmpSnpgTxGrpSpecQueries    Counter32,
    vxlanIgmpSnpgTxSrcSpecQueries    Counter32,
    vxlanIgmpSnpgTxV1Reports         Counter32,
    vxlanIgmpSnpgTxV2Reports         Counter32,
    vxlanIgmpSnpgTxV3Reports         Counter32,
    vxlanIgmpSnpgTxV2Leaves          Counter32,
    vxlanIgmpSnpgRxGenQueries        Counter32,
    vxlanIgmpSnpgRxGrpSpecQueries    Counter32,
    vxlanIgmpSnpgRxSrcSpecQueries    Counter32,
    vxlanIgmpSnpgRxV1Reports         Counter32,
    vxlanIgmpSnpgRxV2Reports         Counter32,
    vxlanIgmpSnpgRxV3Reports         Counter32,
    vxlanIgmpSnpgRxV2Leaves          Counter32,
    vxlanIgmpSnpgRxUnknownType       Counter32,
    vxlanIgmpSnpgFwdGenQueries       Counter32,
    vxlanIgmpSnpgFwdGrpSpecQueries   Counter32,
    vxlanIgmpSnpgFwdSrcSpecQueries   Counter32,
    vxlanIgmpSnpgFwdV1Reports        Counter32,
    vxlanIgmpSnpgFwdV2Reports        Counter32,
    vxlanIgmpSnpgFwdV3Reports        Counter32,
    vxlanIgmpSnpgFwdV2Leaves         Counter32,
    vxlanIgmpSnpgFwdUnknownType      Counter32,
    vxlanIgmpSnpgRxBadLenPkts        Counter32,
    vxlanIgmpSnpgRxBadIpChksmPkts    Counter32,
    vxlanIgmpSnpgRxBadIgmpChksmPkts  Counter32,
    vxlanIgmpSnpgRxBadEncodedPkts    Counter32,
    vxlanIgmpSnpgRxNoRtrAlertPkts    Counter32,
    vxlanIgmpSnpgRxZeroSrcAdrPkts    Counter32,
    vxlanIgmpSnpgSendQueryCfgDrops   Counter32,
    vxlanIgmpSnpgImportPolicyDrops   Counter32,
    vxlanIgmpSnpgMaxNumGroupsDrops   Counter32,
    vxlanIgmpSnpgRxWrongVersionPkts  Counter32,
    vxlanIgmpSnpgMcacPolicyDrops     Counter32,
    vxlanIgmpSnpgMcsFailures         Counter32,
    vxlanIgmpSnpgRxLocalScopePkts    Counter32,
    vxlanIgmpSnpgRxRsvdScopePkts     Counter32,
    vxlanIgmpSnpgMaxNumSourcesDrops  Counter32,
    vxlanIgmpSnpgMaxNumGrpSrcsDrops  Counter32
}

vxlanIgmpSnpgTxGenQueries        OBJECT-TYPE
    SYNTAX      Counter32
    MAX-ACCESS  read-only
    STATUS      current
    DESCRIPTION
        "The value of the object vxlanIgmpSnpgTxGenQueries indicates the number
         of IGMP General Queries transmitted on this VXLAN."
    ::= { vxlanIgmpSnpgStatsEntry 1 }

vxlanIgmpSnpgTxGrpSpecQueries    OBJECT-TYPE
    SYNTAX      Counter32
    MAX-ACCESS  read-only
    STATUS      current
    DESCRIPTION
        "The value of the object vxlanIgmpSnpgTxGrpSpecQueries indicates the
         number of IGMP Group-Specific Queries transmitted on this VXLAN."
    ::= { vxlanIgmpSnpgStatsEntry 2 }

vxlanIgmpSnpgTxSrcSpecQueries    OBJECT-TYPE
    SYNTAX      Counter32
    MAX-ACCESS  read-only
    STATUS      current
    DESCRIPTION
        "The value of the object vxlanIgmpSnpgTxSrcSpecQueries indicates the
         number of IGMP Group-And-Source-Specific Queries transmitted on this
         VXLAN."
    ::= { vxlanIgmpSnpgStatsEntry 3 }

vxlanIgmpSnpgTxV1Reports         OBJECT-TYPE
    SYNTAX      Counter32
    MAX-ACCESS  read-only
    STATUS      current
    DESCRIPTION
        "The value of the object vxlanIgmpSnpgTxV1Reports indicates the number
         of IGMPv1 Reports transmitted on this VXLAN."
    ::= { vxlanIgmpSnpgStatsEntry 4 }

vxlanIgmpSnpgTxV2Reports         OBJECT-TYPE
    SYNTAX      Counter32
    MAX-ACCESS  read-only
    STATUS      current
    DESCRIPTION
        "The value of the object vxlanIgmpSnpgTxV2Reports indicates the number
         of IGMPv2 Reports transmitted on this VXLAN."
    ::= { vxlanIgmpSnpgStatsEntry 5 }

vxlanIgmpSnpgTxV3Reports         OBJECT-TYPE
    SYNTAX      Counter32
    MAX-ACCESS  read-only
    STATUS      current
    DESCRIPTION
        "The value of the object vxlanIgmpSnpgTxV3Reports indicates the number
         of IGMPv3 Reports transmitted on this VXLAN."
    ::= { vxlanIgmpSnpgStatsEntry 6 }

vxlanIgmpSnpgTxV2Leaves          OBJECT-TYPE
    SYNTAX      Counter32
    MAX-ACCESS  read-only
    STATUS      current
    DESCRIPTION
        "The value of the object vxlanIgmpSnpgTxV2Leaves indicates the number
         of IGMPv2 Leaves transmitted on this VXLAN."
    ::= { vxlanIgmpSnpgStatsEntry 7 }

vxlanIgmpSnpgRxGenQueries        OBJECT-TYPE
    SYNTAX      Counter32
    MAX-ACCESS  read-only
    STATUS      current
    DESCRIPTION
        "The value of the object vxlanIgmpSnpgRxGenQueries indicates the number
         of IGMP General Queries received on this VXLAN."
    ::= { vxlanIgmpSnpgStatsEntry 8 }

vxlanIgmpSnpgRxGrpSpecQueries    OBJECT-TYPE
    SYNTAX      Counter32
    MAX-ACCESS  read-only
    STATUS      current
    DESCRIPTION
        "The value of the object vxlanIgmpSnpgRxGrpSpecQueries indicates the
         number of IGMP Group-Specific Queries received on this VXLAN."
    ::= { vxlanIgmpSnpgStatsEntry 9 }

vxlanIgmpSnpgRxSrcSpecQueries    OBJECT-TYPE
    SYNTAX      Counter32
    MAX-ACCESS  read-only
    STATUS      current
    DESCRIPTION
        "The value of the object vxlanIgmpSnpgRxSrcSpecQueries indicates the
         number of IGMP Group-And-Source-Specific Queries received on this
         VXLAN."
    ::= { vxlanIgmpSnpgStatsEntry 10 }

vxlanIgmpSnpgRxV1Reports         OBJECT-TYPE
    SYNTAX      Counter32
    MAX-ACCESS  read-only
    STATUS      current
    DESCRIPTION
        "The value of the object vxlanIgmpSnpgRxV1Reports indicates the number
         of IGMPv1 Reports received on this SAP."
    ::= { vxlanIgmpSnpgStatsEntry 11 }

vxlanIgmpSnpgRxV2Reports         OBJECT-TYPE
    SYNTAX      Counter32
    MAX-ACCESS  read-only
    STATUS      current
    DESCRIPTION
        "The value of the object vxlanIgmpSnpgRxV2Reports indicates the number
         of IGMPv2 Reports received on this VXLAN."
    ::= { vxlanIgmpSnpgStatsEntry 12 }

vxlanIgmpSnpgRxV3Reports         OBJECT-TYPE
    SYNTAX      Counter32
    MAX-ACCESS  read-only
    STATUS      current
    DESCRIPTION
        "The value of the object vxlanIgmpSnpgRxV3Reports indicates the number
         of IGMPv3 Reports received on this SAP."
    ::= { vxlanIgmpSnpgStatsEntry 13 }

vxlanIgmpSnpgRxV2Leaves          OBJECT-TYPE
    SYNTAX      Counter32
    MAX-ACCESS  read-only
    STATUS      current
    DESCRIPTION
        "The value of the object vxlanIgmpSnpgRxV2Leaves indicates the number
         of IGMPv2 Leaves received on this VXLAN."
    ::= { vxlanIgmpSnpgStatsEntry 14 }

vxlanIgmpSnpgRxUnknownType       OBJECT-TYPE
    SYNTAX      Counter32
    MAX-ACCESS  read-only
    STATUS      current
    DESCRIPTION
        "The value of the object vxlanIgmpSnpgRxUnknownType indicates the
         number of IGMP unknown type packets received on this VXLAN."
    ::= { vxlanIgmpSnpgStatsEntry 15 }

vxlanIgmpSnpgFwdGenQueries       OBJECT-TYPE
    SYNTAX      Counter32
    MAX-ACCESS  read-only
    STATUS      current
    DESCRIPTION
        "The value of the object vxlanIgmpSnpgFwdGenQueries indicates the
         number of IGMP General Queries forwarded on this VXLAN."
    ::= { vxlanIgmpSnpgStatsEntry 16 }

vxlanIgmpSnpgFwdGrpSpecQueries   OBJECT-TYPE
    SYNTAX      Counter32
    MAX-ACCESS  read-only
    STATUS      current
    DESCRIPTION
        "The value of the object vxlanIgmpSnpgFwdGrpSpecQueries indicates the
         number of IGMP Group-Specific Queries forwarded on this VXLAN."
    ::= { vxlanIgmpSnpgStatsEntry 17 }

vxlanIgmpSnpgFwdSrcSpecQueries   OBJECT-TYPE
    SYNTAX      Counter32
    MAX-ACCESS  read-only
    STATUS      current
    DESCRIPTION
        "The value of the object vxlanIgmpSnpgFwdSrcSpecQueries indicates the
         number of IGMP Group-And-Source-Specific Queries forwarded on this
         VXLAN."
    ::= { vxlanIgmpSnpgStatsEntry 18 }

vxlanIgmpSnpgFwdV1Reports        OBJECT-TYPE
    SYNTAX      Counter32
    MAX-ACCESS  read-only
    STATUS      current
    DESCRIPTION
        "The value of the object vxlanIgmpSnpgFwdV1Reports indicates the number
         of IGMPv1 Reports forwarded on this VXLAN."
    ::= { vxlanIgmpSnpgStatsEntry 19 }

vxlanIgmpSnpgFwdV2Reports        OBJECT-TYPE
    SYNTAX      Counter32
    MAX-ACCESS  read-only
    STATUS      current
    DESCRIPTION
        "The value of the object vxlanIgmpSnpgFwdV2Reports indicates the number
         of IGMPv2 Reports forwarded on this VXLAN."
    ::= { vxlanIgmpSnpgStatsEntry 20 }

vxlanIgmpSnpgFwdV3Reports        OBJECT-TYPE
    SYNTAX      Counter32
    MAX-ACCESS  read-only
    STATUS      current
    DESCRIPTION
        "The value of the object vxlanIgmpSnpgFwdV3Reports indicates the number
         of IGMPv3 Reports forwarded on this VXLAN."
    ::= { vxlanIgmpSnpgStatsEntry 21 }

vxlanIgmpSnpgFwdV2Leaves         OBJECT-TYPE
    SYNTAX      Counter32
    MAX-ACCESS  read-only
    STATUS      current
    DESCRIPTION
        "The value of the object vxlanIgmpSnpgFwdV2Leaves indicates the number
         of IGMPv2 Leaves forwarded on this VXLAN."
    ::= { vxlanIgmpSnpgStatsEntry 22 }

vxlanIgmpSnpgFwdUnknownType      OBJECT-TYPE
    SYNTAX      Counter32
    MAX-ACCESS  read-only
    STATUS      current
    DESCRIPTION
        "The value of the object vxlanIgmpSnpgFwdUnknownType indicates the
         number of IGMP unknown type packets forwarded on this VXLAN."
    ::= { vxlanIgmpSnpgStatsEntry 23 }

vxlanIgmpSnpgRxBadLenPkts        OBJECT-TYPE
    SYNTAX      Counter32
    MAX-ACCESS  read-only
    STATUS      current
    DESCRIPTION
        "The value of the object vxlanIgmpSnpgRxBadLenPkts indicates the number
         of IGMP packets dropped on this VXLAN because of a bad length."
    ::= { vxlanIgmpSnpgStatsEntry 24 }

vxlanIgmpSnpgRxBadIpChksmPkts    OBJECT-TYPE
    SYNTAX      Counter32
    MAX-ACCESS  read-only
    STATUS      current
    DESCRIPTION
        "The value of the object vxlanIgmpSnpgRxBadIpChksmPkts indicates the
         number of dropped IGMP packets on this VXLAN because of a bad IPv4
         header checksum."
    ::= { vxlanIgmpSnpgStatsEntry 25 }

vxlanIgmpSnpgRxBadIgmpChksmPkts  OBJECT-TYPE
    SYNTAX      Counter32
    MAX-ACCESS  read-only
    STATUS      current
    DESCRIPTION
        "The value of the object vxlanIgmpSnpgRxBadIgmpChksmPkts indicates the
         number of dropped IGMP packets on this VXLAN because of a bad IGMP
         header checksum."
    ::= { vxlanIgmpSnpgStatsEntry 26 }

vxlanIgmpSnpgRxBadEncodedPkts    OBJECT-TYPE
    SYNTAX      Counter32
    MAX-ACCESS  read-only
    STATUS      current
    DESCRIPTION
        "The value of the object vxlanIgmpSnpgRxBadEncodedPkts indicates the
         number of IGMP packets dropped on this VXLAN because of a bad
         encoding."
    ::= { vxlanIgmpSnpgStatsEntry 27 }

vxlanIgmpSnpgRxNoRtrAlertPkts    OBJECT-TYPE
    SYNTAX      Counter32
    MAX-ACCESS  read-only
    STATUS      current
    DESCRIPTION
        "The value of the object vxlanIgmpSnpgRxNoRtrAlertPkts indicates the
         number of IGMP packets dropped on this VXLAN because the Router Alert
         Option in the IP packet is not set."
    ::= { vxlanIgmpSnpgStatsEntry 28 }

vxlanIgmpSnpgRxZeroSrcAdrPkts    OBJECT-TYPE
    SYNTAX      Counter32
    MAX-ACCESS  read-only
    STATUS      current
    DESCRIPTION
        "The value of the object vxlanIgmpSnpgRxZeroSrcAdrPkts indicates the
         number of IGMP packets dropped on this VXLAN because they contain a
         zero source IPv4 address."
    ::= { vxlanIgmpSnpgStatsEntry 29 }

vxlanIgmpSnpgSendQueryCfgDrops   OBJECT-TYPE
    SYNTAX      Counter32
    MAX-ACCESS  read-only
    STATUS      current
    DESCRIPTION
        "The value of the object vxlanIgmpSnpgSendQueryCfgDrops indicates the
         number of times an IGMP Query is dropped because the object
         sapIgmpSnpgCfgSendQueries for this VXLAN is set to 'enabled(1)'."
    ::= { vxlanIgmpSnpgStatsEntry 30 }

vxlanIgmpSnpgImportPolicyDrops   OBJECT-TYPE
    SYNTAX      Counter32
    MAX-ACCESS  read-only
    STATUS      current
    DESCRIPTION
        "The value of the object vxlanIgmpSnpgImportPolicyDrops indicates the
         number of times an IGMP Group or Source is dropped because of applying
         an import policy on this VXLAN."
    ::= { vxlanIgmpSnpgStatsEntry 31 }

vxlanIgmpSnpgMaxNumGroupsDrops   OBJECT-TYPE
    SYNTAX      Counter32
    MAX-ACCESS  read-only
    STATUS      current
    DESCRIPTION
        "The value of the object vxlanIgmpSnpgMaxNumGroupsDrops indicates the
         number of times an IGMP Group is dropped because of exceeding the
         configured maximum number of groups on this VXLAN."
    ::= { vxlanIgmpSnpgStatsEntry 32 }

vxlanIgmpSnpgRxWrongVersionPkts  OBJECT-TYPE
    SYNTAX      Counter32
    MAX-ACCESS  read-only
    STATUS      current
    DESCRIPTION
        "The value of the object vxlanIgmpSnpgRxWrongVersionPkts indicates the
         total number of IGMP packets with a wrong version received on this
         VXLAN."
    ::= { vxlanIgmpSnpgStatsEntry 33 }

vxlanIgmpSnpgMcacPolicyDrops     OBJECT-TYPE
    SYNTAX      Counter32
    MAX-ACCESS  read-only
    STATUS      current
    DESCRIPTION
        "The value of the object vxlanIgmpSnpgMcacPolicyDrops indicates the
         number of times an IGMP Group is dropped because of applying a
         multicast CAC policy on this VXLAN."
    ::= { vxlanIgmpSnpgStatsEntry 34 }

vxlanIgmpSnpgMcsFailures         OBJECT-TYPE
    SYNTAX      Counter32
    MAX-ACCESS  read-only
    STATUS      current
    DESCRIPTION
        "The value of the object vxlanIgmpSnpgMcsFailures indicates the number
         of times an IGMP Group on this VXLAN could not be synced to the MCS
         (multi-chassis synchronization) database."
    ::= { vxlanIgmpSnpgStatsEntry 35 }

vxlanIgmpSnpgRxLocalScopePkts    OBJECT-TYPE
    SYNTAX      Counter32
    MAX-ACCESS  read-only
    STATUS      current
    DESCRIPTION
        "The value of the object vxlanIgmpSnpgRxLocalScopePkts indicates the
         number of IGMP packets received on the link-local scope IPv6 multicast
         address."
    ::= { vxlanIgmpSnpgStatsEntry 36 }

vxlanIgmpSnpgRxRsvdScopePkts     OBJECT-TYPE
    SYNTAX      Counter32
    MAX-ACCESS  read-only
    STATUS      current
    DESCRIPTION
        "The value of the object vxlanIgmpSnpgRxRsvdScopePkts indicates the
         number of IGMP packets received on the reserved scope IPv6 multicast
         address."
    ::= { vxlanIgmpSnpgStatsEntry 37 }

vxlanIgmpSnpgMaxNumSourcesDrops  OBJECT-TYPE
    SYNTAX      Counter32
    MAX-ACCESS  read-only
    STATUS      current
    DESCRIPTION
        "The value of the object vxlanIgmpSnpgMaxNumSourcesDrops indicates the
         number of times an IGMP Source is dropped because of exceeding the
         configured maximum number of sources per group on this VXLAN."
    ::= { vxlanIgmpSnpgStatsEntry 38 }

vxlanIgmpSnpgMaxNumGrpSrcsDrops  OBJECT-TYPE
    SYNTAX      Counter32
    MAX-ACCESS  read-only
    STATUS      current
    DESCRIPTION
        "The value of the object vxlanIgmpSnpgMaxNumGrpSrcsDrops indicates the
         number of times an IGMP Group Source is dropped because of exceeding
         the configured maximum number of group sources per group on this
         VXLAN."
    ::= { vxlanIgmpSnpgStatsEntry 39 }

vxlanIgmpSnpgStateTable          OBJECT-TYPE
    SYNTAX      SEQUENCE OF VxlanIgmpSnpgStateEntry
    MAX-ACCESS  not-accessible
    STATUS      current
    DESCRIPTION
        "vxlanIgmpSnpgStatsTable contains states on IGMP snooping per VXLAN."
    ::= { alxIgmpSnoopingVxlanObjs 4 }

vxlanIgmpSnpgStateEntry          OBJECT-TYPE
    SYNTAX      VxlanIgmpSnpgStateEntry
    MAX-ACCESS  not-accessible
    STATUS      current
    DESCRIPTION
        ""
    INDEX       {
        svcId,
        vxlanVTEPAddrType,
        vxlanVTEPAddress,
        vxlanVNI
    }
    ::= { vxlanIgmpSnpgStateTable 1 }

VxlanIgmpSnpgStateEntry          ::= SEQUENCE
{
    vxlanVTEPAddrType                InetAddressType,
    vxlanVTEPAddress                 InetAddress,
    vxlanIgmpSnpgOperState           TmnxOperState,
    vxlanIgmpSnpgGroupCount          Unsigned32,
    vxlanIgmpIsSbd                   TruthValue,
    vxlanIgmpRxSmetRoutes            Unsigned32,
    vxlanIgmpDroppedSmetRoutes       Unsigned32,
    vxlanIgmpOrigAddrType            InetAddressType,
    vxlanIgmpOrigAddress             InetAddress
}

vxlanVTEPAddrType                OBJECT-TYPE
    SYNTAX      InetAddressType
    MAX-ACCESS  not-accessible
    STATUS      current
    DESCRIPTION
        "The value of the object vxlanVTEPAddrType indicates the type of the
         address associated with this VXLAN."
    ::= { vxlanIgmpSnpgStateEntry 1 }

vxlanVTEPAddress                 OBJECT-TYPE
    SYNTAX      InetAddress (SIZE (4|16))
    MAX-ACCESS  not-accessible
    STATUS      current
    DESCRIPTION
        "The value of the object vxlanVTEPAddress indicates the address
         associated with this VXLANr"
    ::= { vxlanIgmpSnpgStateEntry 2 }

vxlanIgmpSnpgOperState           OBJECT-TYPE
    SYNTAX      TmnxOperState
    MAX-ACCESS  read-only
    STATUS      current
    DESCRIPTION
        "The value of the object vxlanIgmpSnpgOperState indicates the current
         operating state of this VXLAN."
    ::= { vxlanIgmpSnpgStateEntry 4 }

vxlanIgmpSnpgGroupCount          OBJECT-TYPE
    SYNTAX      Unsigned32
    MAX-ACCESS  read-only
    STATUS      current
    DESCRIPTION
        "vxlanIgmpSnpgGroupCount is the number of multicast groups which have
         been learned on this VXLAN."
    ::= { vxlanIgmpSnpgStateEntry 5 }

vxlanIgmpIsSbd                   OBJECT-TYPE
    SYNTAX      TruthValue
    MAX-ACCESS  read-only
    STATUS      current
    DESCRIPTION
        "vxlanIgmpIsSbd indicates whether this VXLAN is from a  supplementary
         broadcast domain."
    ::= { vxlanIgmpSnpgStateEntry 6 }

vxlanIgmpRxSmetRoutes            OBJECT-TYPE
    SYNTAX      Unsigned32
    MAX-ACCESS  read-only
    STATUS      current
    DESCRIPTION
        "vxlanIgmpRxSmetRoutes is the number of received Smet routes on this
         VXLAN."
    ::= { vxlanIgmpSnpgStateEntry 7 }

vxlanIgmpDroppedSmetRoutes       OBJECT-TYPE
    SYNTAX      Unsigned32
    MAX-ACCESS  read-only
    STATUS      current
    DESCRIPTION
        "vxlanIgmpDroppedSmetRoutes is the number of dropped Smet routes on
         this VXLAN."
    ::= { vxlanIgmpSnpgStateEntry 8 }

vxlanIgmpOrigAddrType            OBJECT-TYPE
    SYNTAX      InetAddressType
    MAX-ACCESS  read-only
    STATUS      current
    DESCRIPTION
        ""
    ::= { vxlanIgmpSnpgStateEntry 9 }

vxlanIgmpOrigAddress             OBJECT-TYPE
    SYNTAX      InetAddress (SIZE (4|16))
    MAX-ACCESS  read-only
    STATUS      current
    DESCRIPTION
        ""
    ::= { vxlanIgmpSnpgStateEntry 10 }

alxIgmpSnoopingEMplsObjs         OBJECT IDENTIFIER ::= { alxIgmpSnoopingObjs 7 }

eMplsIgmpSnpgStatsTable          OBJECT-TYPE
    SYNTAX      SEQUENCE OF EMplsIgmpSnpgStatsEntry
    MAX-ACCESS  not-accessible
    STATUS      current
    DESCRIPTION
        "eMplsIgmpSnpgStatsTable contains statistics on IGMP snooping per
         evpn-mpls."
    ::= { alxIgmpSnoopingEMplsObjs 3 }

eMplsIgmpSnpgStatsEntry          OBJECT-TYPE
    SYNTAX      EMplsIgmpSnpgStatsEntry
    MAX-ACCESS  not-accessible
    STATUS      current
    DESCRIPTION
        "eMplsIgmpSnpgStatsEntry is an entry in the eMplsIgmpSnpgStatsTable.
         Each entry contains IGMP snooping statics for an evpn-mpls in a Tls."
    INDEX       { svcId }
    ::= { eMplsIgmpSnpgStatsTable 1 }

EMplsIgmpSnpgStatsEntry          ::= SEQUENCE
{
    eMplsIgmpSnpgTxGenQueries        Counter32,
    eMplsIgmpSnpgTxGrpSpecQueries    Counter32,
    eMplsIgmpSnpgTxSrcSpecQueries    Counter32,
    eMplsIgmpSnpgTxV1Reports         Counter32,
    eMplsIgmpSnpgTxV2Reports         Counter32,
    eMplsIgmpSnpgTxV3Reports         Counter32,
    eMplsIgmpSnpgTxV2Leaves          Counter32,
    eMplsIgmpSnpgRxGenQueries        Counter32,
    eMplsIgmpSnpgRxGrpSpecQueries    Counter32,
    eMplsIgmpSnpgRxSrcSpecQueries    Counter32,
    eMplsIgmpSnpgRxV1Reports         Counter32,
    eMplsIgmpSnpgRxV2Reports         Counter32,
    eMplsIgmpSnpgRxV3Reports         Counter32,
    eMplsIgmpSnpgRxV2Leaves          Counter32,
    eMplsIgmpSnpgRxUnknownType       Counter32,
    eMplsIgmpSnpgFwdGenQueries       Counter32,
    eMplsIgmpSnpgFwdGrpSpecQueries   Counter32,
    eMplsIgmpSnpgFwdSrcSpecQueries   Counter32,
    eMplsIgmpSnpgFwdV1Reports        Counter32,
    eMplsIgmpSnpgFwdV2Reports        Counter32,
    eMplsIgmpSnpgFwdV3Reports        Counter32,
    eMplsIgmpSnpgFwdV2Leaves         Counter32,
    eMplsIgmpSnpgFwdUnknownType      Counter32,
    eMplsIgmpSnpgRxBadLenPkts        Counter32,
    eMplsIgmpSnpgRxBadIpChksmPkts    Counter32,
    eMplsIgmpSnpgRxBadIgmpChksmPkts  Counter32,
    eMplsIgmpSnpgRxBadEncodedPkts    Counter32,
    eMplsIgmpSnpgRxNoRtrAlertPkts    Counter32,
    eMplsIgmpSnpgRxZeroSrcAdrPkts    Counter32,
    eMplsIgmpSnpgSendQueryCfgDrops   Counter32,
    eMplsIgmpSnpgImportPolicyDrops   Counter32,
    eMplsIgmpSnpgMaxNumGroupsDrops   Counter32,
    eMplsIgmpSnpgRxWrongVersionPkts  Counter32,
    eMplsIgmpSnpgMcacPolicyDrops     Counter32,
    eMplsIgmpSnpgMcsFailures         Counter32,
    eMplsIgmpSnpgRxLocalScopePkts    Counter32,
    eMplsIgmpSnpgRxRsvdScopePkts     Counter32,
    eMplsIgmpSnpgMaxNumSourcesDrops  Counter32,
    eMplsIgmpSnpgMaxNumGrpSrcsDrops  Counter32
}

eMplsIgmpSnpgTxGenQueries        OBJECT-TYPE
    SYNTAX      Counter32
    MAX-ACCESS  read-only
    STATUS      current
    DESCRIPTION
        "The value of the object eMplsIgmpSnpgTxGenQueries indicates the number
         of IGMP General Queries transmitted on this evpn-mpls."
    ::= { eMplsIgmpSnpgStatsEntry 1 }

eMplsIgmpSnpgTxGrpSpecQueries    OBJECT-TYPE
    SYNTAX      Counter32
    MAX-ACCESS  read-only
    STATUS      current
    DESCRIPTION
        "The value of the object eMplsIgmpSnpgTxGrpSpecQueries indicates the
         number of IGMP Group-Specific Queries transmitted on this evpn-mpls."
    ::= { eMplsIgmpSnpgStatsEntry 2 }

eMplsIgmpSnpgTxSrcSpecQueries    OBJECT-TYPE
    SYNTAX      Counter32
    MAX-ACCESS  read-only
    STATUS      current
    DESCRIPTION
        "The value of the object eMplsIgmpSnpgTxSrcSpecQueries indicates the
         number of IGMP Group-And-Source-Specific Queries transmitted on this
         evpn-mpls."
    ::= { eMplsIgmpSnpgStatsEntry 3 }

eMplsIgmpSnpgTxV1Reports         OBJECT-TYPE
    SYNTAX      Counter32
    MAX-ACCESS  read-only
    STATUS      current
    DESCRIPTION
        "The value of the object eMplsIgmpSnpgTxV1Reports indicates the number
         of IGMPv1 Reports transmitted on this evpn-mpls."
    ::= { eMplsIgmpSnpgStatsEntry 4 }

eMplsIgmpSnpgTxV2Reports         OBJECT-TYPE
    SYNTAX      Counter32
    MAX-ACCESS  read-only
    STATUS      current
    DESCRIPTION
        "The value of the object eMplsIgmpSnpgTxV2Reports indicates the number
         of IGMPv2 Reports transmitted on this evpn-mpls."
    ::= { eMplsIgmpSnpgStatsEntry 5 }

eMplsIgmpSnpgTxV3Reports         OBJECT-TYPE
    SYNTAX      Counter32
    MAX-ACCESS  read-only
    STATUS      current
    DESCRIPTION
        "The value of the object eMplsIgmpSnpgTxV3Reports indicates the number
         of IGMPv3 Reports transmitted on this evpn-mpls."
    ::= { eMplsIgmpSnpgStatsEntry 6 }

eMplsIgmpSnpgTxV2Leaves          OBJECT-TYPE
    SYNTAX      Counter32
    MAX-ACCESS  read-only
    STATUS      current
    DESCRIPTION
        "The value of the object eMplsIgmpSnpgTxV2Leaves indicates the number
         of IGMPv2 Leaves transmitted on this evpn-mpls."
    ::= { eMplsIgmpSnpgStatsEntry 7 }

eMplsIgmpSnpgRxGenQueries        OBJECT-TYPE
    SYNTAX      Counter32
    MAX-ACCESS  read-only
    STATUS      current
    DESCRIPTION
        "The value of the object eMplsIgmpSnpgRxGenQueries indicates the number
         of IGMP General Queries received on this evpn-mpls."
    ::= { eMplsIgmpSnpgStatsEntry 8 }

eMplsIgmpSnpgRxGrpSpecQueries    OBJECT-TYPE
    SYNTAX      Counter32
    MAX-ACCESS  read-only
    STATUS      current
    DESCRIPTION
        "The value of the object eMplsIgmpSnpgRxGrpSpecQueries indicates the
         number of IGMP Group-Specific Queries received on this evpn-mpls."
    ::= { eMplsIgmpSnpgStatsEntry 9 }

eMplsIgmpSnpgRxSrcSpecQueries    OBJECT-TYPE
    SYNTAX      Counter32
    MAX-ACCESS  read-only
    STATUS      current
    DESCRIPTION
        "The value of the object eMplsIgmpSnpgRxSrcSpecQueries indicates the
         number of IGMP Group-And-Source-Specific Queries received on this
         evpn-mpls."
    ::= { eMplsIgmpSnpgStatsEntry 10 }

eMplsIgmpSnpgRxV1Reports         OBJECT-TYPE
    SYNTAX      Counter32
    MAX-ACCESS  read-only
    STATUS      current
    DESCRIPTION
        "The value of the object eMplsIgmpSnpgRxV1Reports indicates the number
         of IGMPv1 Reports received on this evpn-mpls."
    ::= { eMplsIgmpSnpgStatsEntry 11 }

eMplsIgmpSnpgRxV2Reports         OBJECT-TYPE
    SYNTAX      Counter32
    MAX-ACCESS  read-only
    STATUS      current
    DESCRIPTION
        "The value of the object eMplsIgmpSnpgRxV2Reports indicates the number
         of IGMPv2 Reports received on this evpn-mpls."
    ::= { eMplsIgmpSnpgStatsEntry 12 }

eMplsIgmpSnpgRxV3Reports         OBJECT-TYPE
    SYNTAX      Counter32
    MAX-ACCESS  read-only
    STATUS      current
    DESCRIPTION
        "The value of the object eMplsIgmpSnpgRxV3Reports indicates the number
         of IGMPv3 Reports received on this evpn-mpls."
    ::= { eMplsIgmpSnpgStatsEntry 13 }

eMplsIgmpSnpgRxV2Leaves          OBJECT-TYPE
    SYNTAX      Counter32
    MAX-ACCESS  read-only
    STATUS      current
    DESCRIPTION
        "The value of the object eMplsIgmpSnpgRxV2Leaves indicates the number
         of IGMPv2 Leaves received on this evpn-mpls."
    ::= { eMplsIgmpSnpgStatsEntry 14 }

eMplsIgmpSnpgRxUnknownType       OBJECT-TYPE
    SYNTAX      Counter32
    MAX-ACCESS  read-only
    STATUS      current
    DESCRIPTION
        "The value of the object eMplsIgmpSnpgRxUnknownType indicates the
         number of IGMP unknown type packets received on this evpn-mpls."
    ::= { eMplsIgmpSnpgStatsEntry 15 }

eMplsIgmpSnpgFwdGenQueries       OBJECT-TYPE
    SYNTAX      Counter32
    MAX-ACCESS  read-only
    STATUS      current
    DESCRIPTION
        "The value of the object eMplsIgmpSnpgFwdGenQueries indicates the
         number of IGMP General Queries forwarded on this evpn-mpls."
    ::= { eMplsIgmpSnpgStatsEntry 16 }

eMplsIgmpSnpgFwdGrpSpecQueries   OBJECT-TYPE
    SYNTAX      Counter32
    MAX-ACCESS  read-only
    STATUS      current
    DESCRIPTION
        "The value of the object eMplsIgmpSnpgFwdGrpSpecQueries indicates the
         number of IGMP Group-Specific Queries forwarded on this evpn-mpls."
    ::= { eMplsIgmpSnpgStatsEntry 17 }

eMplsIgmpSnpgFwdSrcSpecQueries   OBJECT-TYPE
    SYNTAX      Counter32
    MAX-ACCESS  read-only
    STATUS      current
    DESCRIPTION
        "The value of the object eMplsIgmpSnpgFwdSrcSpecQueries indicates the
         number of IGMP Group-And-Source-Specific Queries forwarded on this
         evpn-mpls."
    ::= { eMplsIgmpSnpgStatsEntry 18 }

eMplsIgmpSnpgFwdV1Reports        OBJECT-TYPE
    SYNTAX      Counter32
    MAX-ACCESS  read-only
    STATUS      current
    DESCRIPTION
        "The value of the object eMplsIgmpSnpgFwdV1Reports indicates the number
         of IGMPv1 Reports forwarded on this evpn-mpls."
    ::= { eMplsIgmpSnpgStatsEntry 19 }

eMplsIgmpSnpgFwdV2Reports        OBJECT-TYPE
    SYNTAX      Counter32
    MAX-ACCESS  read-only
    STATUS      current
    DESCRIPTION
        "The value of the object eMplsIgmpSnpgFwdV2Reports indicates the number
         of IGMPv2 Reports forwarded on this evpn-mpls."
    ::= { eMplsIgmpSnpgStatsEntry 20 }

eMplsIgmpSnpgFwdV3Reports        OBJECT-TYPE
    SYNTAX      Counter32
    MAX-ACCESS  read-only
    STATUS      current
    DESCRIPTION
        "The value of the object eMplsIgmpSnpgFwdV3Reports indicates the number
         of IGMPv3 Reports forwarded on this evpn-mpls."
    ::= { eMplsIgmpSnpgStatsEntry 21 }

eMplsIgmpSnpgFwdV2Leaves         OBJECT-TYPE
    SYNTAX      Counter32
    MAX-ACCESS  read-only
    STATUS      current
    DESCRIPTION
        "The value of the object eMplsIgmpSnpgFwdV2Leaves indicates the number
         of IGMPv2 Leaves forwarded on this evpn-mpls."
    ::= { eMplsIgmpSnpgStatsEntry 22 }

eMplsIgmpSnpgFwdUnknownType      OBJECT-TYPE
    SYNTAX      Counter32
    MAX-ACCESS  read-only
    STATUS      current
    DESCRIPTION
        "The value of the object eMplsIgmpSnpgFwdUnknownType indicates the
         number of IGMP unknown type packets forwarded on this evpn-mpls."
    ::= { eMplsIgmpSnpgStatsEntry 23 }

eMplsIgmpSnpgRxBadLenPkts        OBJECT-TYPE
    SYNTAX      Counter32
    MAX-ACCESS  read-only
    STATUS      current
    DESCRIPTION
        "The value of the object eMplsIgmpSnpgRxBadLenPkts indicates the number
         of IGMP packets dropped on this evpn-mpls because of a bad length."
    ::= { eMplsIgmpSnpgStatsEntry 24 }

eMplsIgmpSnpgRxBadIpChksmPkts    OBJECT-TYPE
    SYNTAX      Counter32
    MAX-ACCESS  read-only
    STATUS      current
    DESCRIPTION
        "The value of the object eMplsIgmpSnpgRxBadIpChksmPkts indicates the
         number of dropped IGMP packets on this evpn-mpls because of a bad IPv4
         header checksum."
    ::= { eMplsIgmpSnpgStatsEntry 25 }

eMplsIgmpSnpgRxBadIgmpChksmPkts  OBJECT-TYPE
    SYNTAX      Counter32
    MAX-ACCESS  read-only
    STATUS      current
    DESCRIPTION
        "The value of the object eMplsIgmpSnpgRxBadIgmpChksmPkts indicates the
         number of dropped IGMP packets on this evpn-mpls because of a bad IGMP
         header checksum."
    ::= { eMplsIgmpSnpgStatsEntry 26 }

eMplsIgmpSnpgRxBadEncodedPkts    OBJECT-TYPE
    SYNTAX      Counter32
    MAX-ACCESS  read-only
    STATUS      current
    DESCRIPTION
        "The value of the object eMplsIgmpSnpgRxBadEncodedPkts indicates the
         number of IGMP packets dropped on this evpn-mpls because of a bad
         encoding."
    ::= { eMplsIgmpSnpgStatsEntry 27 }

eMplsIgmpSnpgRxNoRtrAlertPkts    OBJECT-TYPE
    SYNTAX      Counter32
    MAX-ACCESS  read-only
    STATUS      current
    DESCRIPTION
        "The value of the object eMplsIgmpSnpgRxNoRtrAlertPkts indicates the
         number of IGMP packets dropped on this evpn-mpls because the Router
         Alert Option in the IP packet is not set."
    ::= { eMplsIgmpSnpgStatsEntry 28 }

eMplsIgmpSnpgRxZeroSrcAdrPkts    OBJECT-TYPE
    SYNTAX      Counter32
    MAX-ACCESS  read-only
    STATUS      current
    DESCRIPTION
        "The value of the object eMplsIgmpSnpgRxZeroSrcAdrPkts indicates the
         number of IGMP packets dropped on this evpn-mpls because they contain
         a zero source IPv4 address."
    ::= { eMplsIgmpSnpgStatsEntry 29 }

eMplsIgmpSnpgSendQueryCfgDrops   OBJECT-TYPE
    SYNTAX      Counter32
    MAX-ACCESS  read-only
    STATUS      current
    DESCRIPTION
        "The value of the object eMplsIgmpSnpgSendQueryCfgDrops indicates the
         number of times an IGMP Query is dropped because the object
         sapIgmpSnpgCfgSendQueries for this evpn-mpls is set to 'enabled(1)'."
    ::= { eMplsIgmpSnpgStatsEntry 30 }

eMplsIgmpSnpgImportPolicyDrops   OBJECT-TYPE
    SYNTAX      Counter32
    MAX-ACCESS  read-only
    STATUS      current
    DESCRIPTION
        "The value of the object eMplsIgmpSnpgImportPolicyDrops indicates the
         number of times an IGMP Group or Source is dropped because of applying
         an import policy on this evpn-mpls."
    ::= { eMplsIgmpSnpgStatsEntry 31 }

eMplsIgmpSnpgMaxNumGroupsDrops   OBJECT-TYPE
    SYNTAX      Counter32
    MAX-ACCESS  read-only
    STATUS      current
    DESCRIPTION
        "The value of the object eMplsIgmpSnpgMaxNumGroupsDrops indicates the
         number of times an IGMP Group is dropped because of exceeding the
         configured maximum number of groups on this evpn-mpls."
    ::= { eMplsIgmpSnpgStatsEntry 32 }

eMplsIgmpSnpgRxWrongVersionPkts  OBJECT-TYPE
    SYNTAX      Counter32
    MAX-ACCESS  read-only
    STATUS      current
    DESCRIPTION
        "The value of the object eMplsIgmpSnpgRxWrongVersionPkts indicates the
         total number of IGMP packets with a wrong version received on this
         evpn-mpls."
    ::= { eMplsIgmpSnpgStatsEntry 33 }

eMplsIgmpSnpgMcacPolicyDrops     OBJECT-TYPE
    SYNTAX      Counter32
    MAX-ACCESS  read-only
    STATUS      current
    DESCRIPTION
        "The value of the object eMplsIgmpSnpgMcacPolicyDrops indicates the
         number of times an IGMP Group is dropped because of applying a
         multicast CAC policy on this evpn-mpls."
    ::= { eMplsIgmpSnpgStatsEntry 34 }

eMplsIgmpSnpgMcsFailures         OBJECT-TYPE
    SYNTAX      Counter32
    MAX-ACCESS  read-only
    STATUS      current
    DESCRIPTION
        "The value of the object eMplsIgmpSnpgMcsFailures indicates the number
         of times an IGMP Group on this evpn-mpls could not be synced to the
         MCS (multi-chassis synchronization) database."
    ::= { eMplsIgmpSnpgStatsEntry 35 }

eMplsIgmpSnpgRxLocalScopePkts    OBJECT-TYPE
    SYNTAX      Counter32
    MAX-ACCESS  read-only
    STATUS      current
    DESCRIPTION
        "The value of the object eMplsIgmpSnpgRxLocalScopePkts indicates the
         number of IGMP packets received on the link-local scope IPv6 multicast
         address."
    ::= { eMplsIgmpSnpgStatsEntry 36 }

eMplsIgmpSnpgRxRsvdScopePkts     OBJECT-TYPE
    SYNTAX      Counter32
    MAX-ACCESS  read-only
    STATUS      current
    DESCRIPTION
        "The value of the object eMplsIgmpSnpgRxRsvdScopePkts indicates the
         number of IGMP packets received on the reserved scope IPv6 multicast
         address."
    ::= { eMplsIgmpSnpgStatsEntry 37 }

eMplsIgmpSnpgMaxNumSourcesDrops  OBJECT-TYPE
    SYNTAX      Counter32
    MAX-ACCESS  read-only
    STATUS      current
    DESCRIPTION
        "The value of the object eMplsIgmpSnpgMaxNumSourcesDrops indicates the
         number of times an IGMP Source is dropped because of exceeding the
         configured maximum number of sources per group on this evpn-mpls."
    ::= { eMplsIgmpSnpgStatsEntry 38 }

eMplsIgmpSnpgMaxNumGrpSrcsDrops  OBJECT-TYPE
    SYNTAX      Counter32
    MAX-ACCESS  read-only
    STATUS      current
    DESCRIPTION
        "The value of the object eMplsIgmpSnpgMaxNumGrpSrcsDrops indicates the
         number of times an IGMP Group Source is dropped because of exceeding
         the configured maximum number of group sources per group on this
         evpn-mpls."
    ::= { eMplsIgmpSnpgStatsEntry 39 }

eMplsTEPLblIgmpSnpgGroupTable    OBJECT-TYPE
    SYNTAX      SEQUENCE OF EMplsTEPLblIgmpSnpgGroupEntry
    MAX-ACCESS  not-accessible
    STATUS      current
    DESCRIPTION
        "eMplsTEPLblIgmpSnpgGroupTable together with the table
         eMplsTEPLblIgmpSnpgGrpSrcTable contains multicast group address
         information collected by IGMP snooping for each BGP EVPN-MPLS TEP and
         egress label pair."
    ::= { alxIgmpSnoopingEMplsObjs 4 }

eMplsTEPLblIgmpSnpgGroupEntry    OBJECT-TYPE
    SYNTAX      EMplsTEPLblIgmpSnpgGroupEntry
    MAX-ACCESS  not-accessible
    STATUS      current
    DESCRIPTION
        "Each entry in this table indicates a multicast group address learned
         by IGMP snooping on this BGP EVPN-MPLS TEP and egress label pair. If a
         Source list is present it is described in the corresponding entries of
         the eMplsTEPLblIgmpSnpgGrpSrcTable table."
    INDEX       {
        svcId,
        eMplsTEPLblTEPAddrType,
        eMplsTEPLblTEPAddress,
        eMplsTEPLblTEPLabel,
        eMplsTEPLblIgmpSnpgGrpAddress
    }
    ::= { eMplsTEPLblIgmpSnpgGroupTable 1 }

EMplsTEPLblIgmpSnpgGroupEntry    ::= SEQUENCE
{
    eMplsTEPLblTEPAddrType           InetAddressType,
    eMplsTEPLblTEPAddress            InetAddress,
    eMplsTEPLblTEPLabel              Unsigned32,
    eMplsTEPLblIgmpSnpgGrpAddress    IpAddress,
    eMplsTEPLblIgmpSnpgGrpType       TmnxIgmpSnpgGroupType,
    eMplsTEPLblIgmpSnpgGrpFilterMode TmnxIgmpGroupFilterMode,
    eMplsTEPLblIgmpSnpgGrpUpTime     TimeTicks,
    eMplsTEPLblIgmpSnpgGrpExpiryTime Unsigned32,
    eMplsTEPLblIgmpSnpgGrpCompatMode Unsigned32,
    eMplsTEPLblIgmpSnpgGrpV1ExpTime  Unsigned32,
    eMplsTEPLblIgmpSnpgGrpV2ExpTime  Unsigned32
}

eMplsTEPLblTEPAddrType           OBJECT-TYPE
    SYNTAX      InetAddressType
    MAX-ACCESS  not-accessible
    STATUS      current
    DESCRIPTION
        "The value of the object eMplsTEPLblTEPAddrType indicates the type of
         the address associated with this BGP EVPN-MPLS TEP and egress label
         pair."
    ::= { eMplsTEPLblIgmpSnpgGroupEntry 1 }

eMplsTEPLblTEPAddress            OBJECT-TYPE
    SYNTAX      InetAddress (SIZE (4|16))
    MAX-ACCESS  not-accessible
    STATUS      current
    DESCRIPTION
        "The value of the object eMplsTEPLblTEPAddress indicates the address
         associated with this BGP EVPN-MPLS TEP and egress label pair."
    ::= { eMplsTEPLblIgmpSnpgGroupEntry 2 }

eMplsTEPLblTEPLabel              OBJECT-TYPE
    SYNTAX      Unsigned32
    MAX-ACCESS  not-accessible
    STATUS      current
    DESCRIPTION
        "The value of eMplsTEPLblTEPLabel indicates the egress label associated
         with this BGP EVPN-MPLS TEP and egress label pair."
    ::= { eMplsTEPLblIgmpSnpgGroupEntry 3 }

eMplsTEPLblIgmpSnpgGrpAddress    OBJECT-TYPE
    SYNTAX      IpAddress
    MAX-ACCESS  not-accessible
    STATUS      current
    DESCRIPTION
        "The value of the object eMplsTEPLblIgmpSnpgGrpAddress indicates the
         IPv4 multicast group address for which this entry contains
         information."
    ::= { eMplsTEPLblIgmpSnpgGroupEntry 4 }

eMplsTEPLblIgmpSnpgGrpType       OBJECT-TYPE
    SYNTAX      TmnxIgmpSnpgGroupType
    MAX-ACCESS  read-only
    STATUS      current
    DESCRIPTION
        "The value of the object eMplsTEPLblIgmpSnpgGrpType indicates whether
         this entry was learned dynamically or was statically configured."
    ::= { eMplsTEPLblIgmpSnpgGroupEntry 5 }

eMplsTEPLblIgmpSnpgGrpFilterMode OBJECT-TYPE
    SYNTAX      TmnxIgmpGroupFilterMode
    MAX-ACCESS  read-only
    STATUS      current
    DESCRIPTION
        "The value of the object eMplsTEPLblIgmpSnpgGrpFilterMode indicates the
         filter-mode for this group."
    ::= { eMplsTEPLblIgmpSnpgGroupEntry 6 }

eMplsTEPLblIgmpSnpgGrpUpTime     OBJECT-TYPE
    SYNTAX      TimeTicks
    MAX-ACCESS  read-only
    STATUS      current
    DESCRIPTION
        "The value of the object eMplsTEPLblIgmpSnpgGrpUpTime indicates how
         long (in centiseconds) that the group address already exists in the
         database for this BGP EVPN-MPLS TEP and egress label pair."
    ::= { eMplsTEPLblIgmpSnpgGroupEntry 7 }

eMplsTEPLblIgmpSnpgGrpExpiryTime OBJECT-TYPE
    SYNTAX      Unsigned32
    UNITS       "seconds"
    MAX-ACCESS  read-only
    STATUS      current
    DESCRIPTION
        "The value of the object eMplsTEPLblIgmpSnpgGrpExpiryTime indicates the
         amount of time remaining before this entry will be aged out."
    ::= { eMplsTEPLblIgmpSnpgGroupEntry 8 }

eMplsTEPLblIgmpSnpgGrpCompatMode OBJECT-TYPE
    SYNTAX      Unsigned32
    MAX-ACCESS  read-only
    STATUS      current
    DESCRIPTION
        "The value of the object eMplsTEPLblIgmpSnpgGrpCompatMode indicates the
         IGMP version applicable on this BGP EVPN-MPLS TEP and egress label
         pair for this multicast group address. This corresponds to the lowest
         version seen for this group address on this BGP EVPN-MPLS TEP and
         egress label pair."
    ::= { eMplsTEPLblIgmpSnpgGroupEntry 9 }

eMplsTEPLblIgmpSnpgGrpV1ExpTime  OBJECT-TYPE
    SYNTAX      Unsigned32
    UNITS       "seconds"
    MAX-ACCESS  read-only
    STATUS      current
    DESCRIPTION
        "The value of the object eMplsTEPLblIgmpSnpgGrpV1ExpTime indicates the
         time remaining until the system will assume that there are no longer
         any IGMPv1 members on this BGP EVPN-MPLS TEP and egress label pair.

         Upon hearing any IGMPv1 Membership Report, this value is reset to the
         group membership interval. While this time remaining is non-zero, the
         system ignores any IGMPv2 and IGMPv3 'leave' messages for this group
         that it receives on this BGP EVPN-MPLS TEP and egress label pair."
    ::= { eMplsTEPLblIgmpSnpgGroupEntry 10 }

eMplsTEPLblIgmpSnpgGrpV2ExpTime  OBJECT-TYPE
    SYNTAX      Unsigned32
    UNITS       "seconds"
    MAX-ACCESS  read-only
    STATUS      current
    DESCRIPTION
        "The value of the object eMplsTEPLblIgmpSnpgGrpV2ExpTime indicates the
         time remaining until the system will assume that there are no longer
         any IGMPv2 members on the BGP EVPN-MPLS TEP and egress label pair.

         Upon hearing any IGMPv2 Membership Report, this value is reset to the
         group membership interval. While this time remaining is non-zero, the
         system ignores any IGMPv3 'leave' messages for this group that it
         receives on this BGP EVPN-MPLS TEP and egress label pair."
    ::= { eMplsTEPLblIgmpSnpgGroupEntry 11 }

eMplsTEPLblIgmpSnpgGrpSrcTable   OBJECT-TYPE
    SYNTAX      SEQUENCE OF EMplsTEPLblIgmpSnpgGrpSrcEntry
    MAX-ACCESS  not-accessible
    STATUS      current
    DESCRIPTION
        "eMplsTEPLblIgmpSnpgGrpSrcTable lists the IPv4 multicast Sources
         corresponding to the IPv4 multicast groups listed in the
         eMplsTEPLblIgmpSnpgGroupTable."
    ::= { alxIgmpSnoopingEMplsObjs 5 }

eMplsTEPLblIgmpSnpgGrpSrcEntry   OBJECT-TYPE
    SYNTAX      EMplsTEPLblIgmpSnpgGrpSrcEntry
    MAX-ACCESS  not-accessible
    STATUS      current
    DESCRIPTION
        "An entry in the eMplsTEPLblIgmpSnpgGrpSrcTable. Each entry represents
         a Source address from which receivers are interested/not interested in
         receiving multicast traffic from."
    INDEX       {
        svcId,
        eMplsTEPLblTEPAddrType,
        eMplsTEPLblTEPAddress,
        eMplsTEPLblTEPLabel,
        eMplsTEPLblIgmpSnpgGrpAddress,
        eMplsTEPLblIgmpSnpgGrpSrcAddr
    }
    ::= { eMplsTEPLblIgmpSnpgGrpSrcTable 1 }

EMplsTEPLblIgmpSnpgGrpSrcEntry   ::= SEQUENCE
{
    eMplsTEPLblIgmpSnpgGrpSrcAddr    IpAddress,
    eMplsTEPLblIgmpSnpgGrpSrcType    TmnxIgmpSnpgGroupType,
    eMplsTEPLblIgmpSnpgGrpSrcUpTime  TimeTicks,
    eMplsTEPLblIgmpSnpgGrpSrcExpTime Unsigned32
}

eMplsTEPLblIgmpSnpgGrpSrcAddr    OBJECT-TYPE
    SYNTAX      IpAddress
    MAX-ACCESS  not-accessible
    STATUS      current
    DESCRIPTION
        "The value of the object eMplsTEPLblIgmpSnpgGrpSrcAddr indicates the
         address of the Source sending multicast traffic to the group
         identified by eMplsTEPLblIgmpSnpgGrpAddress.

         If the value of eMplsTEPLblIgmpSnpgGrpFilterMode corresponding to this
         entry is 'include(1)', the receivers are interested in receiving
         traffic from this Source.

         If the value of eMplsTEPLblIgmpSnpgGrpFilterMode corresponding to this
         entry is 'exclude(2)', the receivers are not interested in receiving
         traffic from this Source."
    ::= { eMplsTEPLblIgmpSnpgGrpSrcEntry 1 }

eMplsTEPLblIgmpSnpgGrpSrcType    OBJECT-TYPE
    SYNTAX      TmnxIgmpSnpgGroupType
    MAX-ACCESS  read-only
    STATUS      current
    DESCRIPTION
        "The value of the object eMplsTEPLblIgmpSnpgGrpSrcType indicates how
         this source entry was learned."
    ::= { eMplsTEPLblIgmpSnpgGrpSrcEntry 2 }

eMplsTEPLblIgmpSnpgGrpSrcUpTime  OBJECT-TYPE
    SYNTAX      TimeTicks
    MAX-ACCESS  read-only
    STATUS      current
    DESCRIPTION
        "The value of the object eMplsTEPLblIgmpSnpgGrpSrcUpTime indicates how
         long (in centiseconds) that the Source address already exists in the
         database for this SAP."
    ::= { eMplsTEPLblIgmpSnpgGrpSrcEntry 3 }

eMplsTEPLblIgmpSnpgGrpSrcExpTime OBJECT-TYPE
    SYNTAX      Unsigned32
    UNITS       "seconds"
    MAX-ACCESS  read-only
    STATUS      current
    DESCRIPTION
        "The value of the object eMplsTEPLblIgmpSnpgGrpSrcExpTime indicates the
         minimum amount of time remaining before this entry will be aged out.

         If the value of eMplsTEPLblIgmpSnpgGrpSrcExpTime is non-zero and the
         value of eMplsTEPLblIgmpSnpgGrpFilterMode corresponding to this entry
         is 'include(1)', it means that there are currently one or more systems
         which desire to receive multicast traffic for this Source.

         If this timer expires and the value of
         eMplsTEPLblIgmpSnpgGrpFilterMode is 'include(1)', the system concludes
         that traffic from this particular Source is no longer desired on the
         attached network, and deletes this entry.

         If the value of eMplsTEPLblIgmpSnpgGrpSrcExpTime is non-zero and the
         filter-mode for the group is 'exclude(2)', it means that at least one
         system desires to receive multicast traffic from this source.

         If the value of eMplsTEPLblIgmpSnpgGrpSrcExpTime is zero and the
         filter-mode for the group is 'exclude(2)', it means that no system
         desires to receive multicast traffic from this Source."
    ::= { eMplsTEPLblIgmpSnpgGrpSrcEntry 4 }

eMplsTEPLblIgmpSnpgStateTable    OBJECT-TYPE
    SYNTAX      SEQUENCE OF EMplsTEPLblIgmpSnpgStateEntry
    MAX-ACCESS  not-accessible
    STATUS      current
    DESCRIPTION
        "eMplsTEPLblIgmpSnpgStateTable contains statistics on IGMP snooping for
         each BGP EVPN-MPLS TEP and egress label pair."
    ::= { alxIgmpSnoopingEMplsObjs 6 }

eMplsTEPLblIgmpSnpgStateEntry    OBJECT-TYPE
    SYNTAX      EMplsTEPLblIgmpSnpgStateEntry
    MAX-ACCESS  not-accessible
    STATUS      current
    DESCRIPTION
        "eMplsTEPLblIgmpSnpgStateEntry is an entry in the
         eMplsTEPLblIgmpSnpgStateTable. Each entry contains IGMP snooping
         statics for a  BGP EVPN-MPLS TEP and egress label pair in a Tls."
    INDEX       {
        svcId,
        eMplsTEPLblTEPAddrType,
        eMplsTEPLblTEPAddress,
        eMplsTEPLblTEPLabel
    }
    ::= { eMplsTEPLblIgmpSnpgStateTable 1 }

EMplsTEPLblIgmpSnpgStateEntry    ::= SEQUENCE
{
    eMplsTEPLblIgmpSnpgOperState     TmnxOperState,
    eMplsTEPLblIgmpSnpgGroupCount    Unsigned32,
    eMplsTEPLblIgmpIsSbd             TruthValue,
    eMplsTEPLblIgmpRxSmetRoutes      Unsigned32,
    eMplsTEPLblIgmpDroppedSmetRoutes Unsigned32,
    eMplsTEPLblIgmpOrigAddrType      InetAddressType,
    eMplsTEPLblIgmpOrigAddress       InetAddress
}

eMplsTEPLblIgmpSnpgOperState     OBJECT-TYPE
    SYNTAX      TmnxOperState
    MAX-ACCESS  read-only
    STATUS      current
    DESCRIPTION
        "The value of the object eMplsTEPLblIgmpSnpgOperState indicates the
         current operating state of this BGP EVPN-MPLS TEP and egress label
         pair."
    ::= { eMplsTEPLblIgmpSnpgStateEntry 1 }

eMplsTEPLblIgmpSnpgGroupCount    OBJECT-TYPE
    SYNTAX      Unsigned32
    MAX-ACCESS  read-only
    STATUS      current
    DESCRIPTION
        "eMplsTEPLblIgmpSnpgGroupCount is the number of multicast groups which
         have been learned on this BGP EVPN-MPLS TEP and egress label pair."
    ::= { eMplsTEPLblIgmpSnpgStateEntry 2 }

eMplsTEPLblIgmpIsSbd             OBJECT-TYPE
    SYNTAX      TruthValue
    MAX-ACCESS  read-only
    STATUS      current
    DESCRIPTION
        "eMplsTEPLblIgmpIsSbd indicates whether this BGP EVPN-MPLS TEP and
         egress label pair is from a  supplementary broadcast domain."
    ::= { eMplsTEPLblIgmpSnpgStateEntry 3 }

eMplsTEPLblIgmpRxSmetRoutes      OBJECT-TYPE
    SYNTAX      Unsigned32
    MAX-ACCESS  read-only
    STATUS      current
    DESCRIPTION
        "eMplsTEPLblIgmpRxSmetRoutes is the number of received Smet routes on
         this BGP EVPN-MPLS TEP and egress label pair."
    ::= { eMplsTEPLblIgmpSnpgStateEntry 4 }

eMplsTEPLblIgmpDroppedSmetRoutes OBJECT-TYPE
    SYNTAX      Unsigned32
    MAX-ACCESS  read-only
    STATUS      current
    DESCRIPTION
        "eMplsTEPLblIgmpDroppedSmetRoutes is the number of dropped Smet routes
         on this BGP EVPN-MPLS TEP and egress label pair."
    ::= { eMplsTEPLblIgmpSnpgStateEntry 5 }

eMplsTEPLblIgmpOrigAddrType      OBJECT-TYPE
    SYNTAX      InetAddressType
    MAX-ACCESS  read-only
    STATUS      current
    DESCRIPTION
        ""
    ::= { eMplsTEPLblIgmpSnpgStateEntry 6 }

eMplsTEPLblIgmpOrigAddress       OBJECT-TYPE
    SYNTAX      InetAddress (SIZE (4|16))
    MAX-ACCESS  read-only
    STATUS      current
    DESCRIPTION
        ""
    ::= { eMplsTEPLblIgmpSnpgStateEntry 7 }

alxIgmpSnoopingConformance       OBJECT IDENTIFIER ::= { alcatelConformance 2 }

alxIgmpSnoopingTlsConformance    OBJECT IDENTIFIER ::= { alxIgmpSnoopingConformance 1 }

alxIgmpSnoopingTlsCompliancs     OBJECT IDENTIFIER ::= { alxIgmpSnoopingTlsConformance 1 }

alxIgmpSnoopingTlsCompliance     MODULE-COMPLIANCE
    STATUS      obsolete
    DESCRIPTION
        "The compliance statement for management of IGMP
         Snooping on  Tls  level  on Nokia 7x50 SR series
         systems."
    MODULE
        MANDATORY-GROUPS {
            alxTlsIgmpSnpgConfigV3v0Group,
            alxTlsIgmpSnpgQuerierV3v0Group,
            alxTlsIgmpSnpgProxyV3v0Group,
            alxTlsIgmpSnpgMRouterV3v0Group,
            alxTlsMvrConfigV3v0Group
        }
    ::= { alxIgmpSnoopingTlsCompliancs 1 }

alxIgmpSnoopingTlsV5v0Compliance MODULE-COMPLIANCE
    STATUS      obsolete
    DESCRIPTION
        "The compliance statement for management of IGMP
         Snooping on  Tls  level  on Nokia 7x50 SR series
         systems."
    MODULE
        MANDATORY-GROUPS {
            alxTlsIgmpSnpgConfigV3v0Group,
            alxTlsIgmpSnpgQuerierV3v0Group,
            alxTlsIgmpSnpgProxyV3v0Group,
            alxTlsIgmpSnpgMRouterV3v0Group,
            alxTlsMvrConfigV3v0Group
        }
    ::= { alxIgmpSnoopingTlsCompliancs 2 }

alxIgmpSnoopingTlsV6v0Compliance MODULE-COMPLIANCE
    STATUS      obsolete
    DESCRIPTION
        "The compliance statement for management of IGMP
         Snooping on  Tls  level  on Nokia 7x50 SR series
         systems."
    MODULE
        MANDATORY-GROUPS {
            alxTlsIgmpSnpgConfigV6v0Group,
            alxTlsIgmpSnpgQuerierV3v0Group,
            alxTlsIgmpSnpgProxyV3v0Group,
            alxTlsIgmpSnpgMRouterV3v0Group,
            alxTlsMvrConfigV3v0Group,
            alxTlsIgmpSnpgTimeStampGroup,
            alxSapIgmpSnpgTimeStampGroup,
            alxSdpBindIgmpSnpgTimeStampGroup
        }
    ::= { alxIgmpSnoopingTlsCompliancs 3 }

alxIgmpSnpgTlsV13v0Compliance    MODULE-COMPLIANCE
    STATUS      obsolete
    DESCRIPTION
        "The compliance statement for management of IGMP Snooping on Tls level
         on Nokia 7x50 SR series release 13.0 systems."
    MODULE
        MANDATORY-GROUPS {
            alxTlsIgmpSnpgConfigV6v0Group,
            alxTlsIgmpSnpgConfigV13v0Group,
            alxTlsIgmpSnpgQuerierV3v0Group,
            alxTlsIgmpSnpgQuerierV13v0Group,
            alxTlsIgmpSnpgProxyV3v0Group,
            alxTlsIgmpSnpgMRouterV3v0Group,
            alxTlsMvrConfigV3v0Group,
            alxTlsIgmpSnpgTimeStampGroup,
            alxSapIgmpSnpgTimeStampGroup,
            alxSdpBindIgmpSnpgTimeStampGroup
        }
    ::= { alxIgmpSnoopingTlsCompliancs 4 }

alxIgmpSnpgTlsV19v0Compliance    MODULE-COMPLIANCE
    STATUS      current
    DESCRIPTION
        "The compliance statement for management of IGMP Snooping on Tls level
         on Nokia 7x50 SR series release 19.0 systems."
    MODULE
        MANDATORY-GROUPS {
            alxTlsIgmpSnpgConfigV6v0Group,
            alxTlsIgmpSnpgConfigV13v0Group,
            alxTlsIgmpSnpgConfigV19v0Group,
            alxTlsIgmpSnpgQuerierV3v0Group,
            alxTlsIgmpSnpgQuerierV13v0Group,
            alxTlsIgmpSnpgProxyV3v0Group,
            alxTlsIgmpSnpgMRouterV3v0Group,
            alxTlsMvrConfigV3v0Group,
            alxTlsIgmpSnpgTimeStampGroup,
            alxSapIgmpSnpgTimeStampGroup,
            alxSdpBindIgmpSnpgTimeStampGroup
        }
    ::= { alxIgmpSnoopingTlsCompliancs 5 }

alxIgmpSnoopingTlsGroups         OBJECT IDENTIFIER ::= { alxIgmpSnoopingTlsConformance 2 }

alxTlsIgmpSnpgConfigV3v0Group    OBJECT-GROUP
    OBJECTS     {
        tlsIgmpSnpgCfgAdminState,
        tlsIgmpSnpgCfgGenQueryIntvl,
        tlsIgmpSnpgCfgRobustCount,
        tlsIgmpSnpgCfgReportSrcAddress
    }
    STATUS      obsolete
    DESCRIPTION
        "The group of objects supporting management of IGMP snooping on Tls
         level on Nokia 7x50 SR series systems."
    ::= { alxIgmpSnoopingTlsGroups 1 }

alxTlsIgmpSnpgQuerierV3v0Group   OBJECT-GROUP
    OBJECTS     {
        tlsIgmpSnpgQuerierVersion,
        tlsIgmpSnpgQuerierAddress,
        tlsIgmpSnpgQuerierLocale,
        tlsIgmpSnpgQuerierPortId,
        tlsIgmpSnpgQuerierEncapValue,
        tlsIgmpSnpgQuerierSdpId,
        tlsIgmpSnpgQuerierVcId,
        tlsIgmpSnpgQuerierUpTime,
        tlsIgmpSnpgQuerierExpiryTime,
        tlsIgmpSnpgQuerierGenQueryIntvl,
        tlsIgmpSnpgQuerierGenRespIntvl,
        tlsIgmpSnpgQuerierRobustCount,
        tlsIgmpSnpgQuerierVRtrId,
        tlsIgmpSnpgQuerierIfIndex
    }
    STATUS      current
    DESCRIPTION
        "The group of objects that allow to monitor the IGMP querier in the Tls
         service by the IGMP snooping device on Nokia 7x50 SR series systems."
    ::= { alxIgmpSnoopingTlsGroups 2 }

alxTlsIgmpSnpgProxyV3v0Group     OBJECT-GROUP
    OBJECTS     {
        tlsIgmpSnpgProxyGroupFilterMode,
        tlsIgmpSnpgProxyGroupUpTime,
        tlsIgmpSnpgProxyGrpSrcUpTime
    }
    STATUS      current
    DESCRIPTION
        "The group of objects that allow to monitor the IGMP snooping
         information that is being used by the system when it performs proxy
         reporting to the MRouter on Nokia 7x50 SR series systems."
    ::= { alxIgmpSnoopingTlsGroups 3 }

alxTlsIgmpSnpgMRouterV3v0Group   OBJECT-GROUP
    OBJECTS     {
        tlsIgmpSnpgMRouterAddress,
        tlsIgmpSnpgMRouterLocale,
        tlsIgmpSnpgMRouterPortId,
        tlsIgmpSnpgMRouterEncapValue,
        tlsIgmpSnpgMRouterSdpId,
        tlsIgmpSnpgMRouterVcId,
        tlsIgmpSnpgMRouterVersion,
        tlsIgmpSnpgMRouterExpiryTime,
        tlsIgmpSnpgMRouterUpTime,
        tlsIgmpSnpgMRouterGenQueryIntvl,
        tlsIgmpSnpgMRouterGenRespIntvl,
        tlsIgmpSnpgMRouterRobustCount,
        tlsIgmpSnpgMRouterVRtrId,
        tlsIgmpSnpgMRouterIfIndex
    }
    STATUS      current
    DESCRIPTION
        "The group of objects that allow to monitor the IGMP multicast routers
         in the Tls service by the IGMP snooping device on Nokia 7x50 SR series
         systems."
    ::= { alxIgmpSnoopingTlsGroups 4 }

alxTlsMvrConfigV3v0Group         OBJECT-GROUP
    OBJECTS     {
        tlsIgmpSnpgCfgMvrAdminState,
        tlsIgmpSnpgCfgMvrDescription,
        tlsIgmpSnpgCfgMvrPolicy
    }
    STATUS      current
    DESCRIPTION
        "The group of objects supporting management of MVR on Tls level on
         Nokia 7x50 SR series systems."
    ::= { alxIgmpSnoopingTlsGroups 5 }

alxTlsIgmpSnpgNotObjV5v0Group    OBJECT-GROUP
    OBJECTS     {
        alxIgmpSnpgGroupAddress,
        alxIgmpSnpgMcsFailureReason
    }
    STATUS      current
    DESCRIPTION
        "The group of notification objects supporting management of IGMP
         snooping on Nokia 7x50 SR series systems."
    ::= { alxIgmpSnoopingTlsGroups 6 }

alxTlsIgmpSnpgConfigV6v0Group    OBJECT-GROUP
    OBJECTS     {
        tlsIgmpSnpgCfgAdminState,
        tlsIgmpSnpgCfgGenQueryIntvl,
        tlsIgmpSnpgCfgRobustCount,
        tlsIgmpSnpgCfgReportSrcAddress,
        tlsIgmpSnpgCfgQuerySrcAddress,
        tlsIgmpSnpgCfgQuerySrcAddrType
    }
    STATUS      current
    DESCRIPTION
        "The group of objects supporting management of IGMP snooping on Tls
         level on Nokia 7x50 SR series systems."
    ::= { alxIgmpSnoopingTlsGroups 7 }

alxTlsIgmpSnpgTimeStampGroup     OBJECT-GROUP
    OBJECTS     {
        tlsIgmpSnpgCfgLastChangeTime,
        tlsIgmpSnpgConfigTableLastChange
    }
    STATUS      current
    DESCRIPTION
        "The group of last change timestamps for IGMP snooping on Tls level on
         Nokia 7x50 SR series systems."
    ::= { alxIgmpSnoopingTlsGroups 8 }

alxTlsIgmpSnpgNotifyObjsV6v1Grp  OBJECT-GROUP
    OBJECTS     {
        alxIgmpSnpgSourceAddress
    }
    STATUS      current
    DESCRIPTION
        "The group of notification objects supporting management of IGMP
         snooping on Nokia 7x50 SR series systems added in the 6.1R6 release."
    ::= { alxIgmpSnoopingTlsGroups 9 }

alxTlsIgmpSnpgNotifyObjsV12v0Grp OBJECT-GROUP
    OBJECTS     {
        alxIgmpSnpgDescription
    }
    STATUS      current
    DESCRIPTION
        "The group of notification objects supporting management of IGMP
         snooping on Nokia 7x50 SR series systems added in the 12.0 release."
    ::= { alxIgmpSnoopingTlsGroups 10 }

alxTlsIgmpSnpgQuerierV13v0Group  OBJECT-GROUP
    OBJECTS     {
        tlsIgmpSnpgQuerierVTEPAddr,
        tlsIgmpSnpgQuerierVNI,
        tlsIgmpSnpgMRouterVTEPAddr,
        tlsIgmpSnpgMRouterVNI
    }
    STATUS      current
    DESCRIPTION
        "The group of objects that allow to monitor the IGMP querier in the Tls
         service by the IGMP snooping device on Nokia 7x50 SR series release
         13.0 systems."
    ::= { alxIgmpSnoopingTlsGroups 11 }

alxTlsIgmpSnpgConfigV13v0Group   OBJECT-GROUP
    OBJECTS     {
        tlsIgmpSnpgCfgFwdIpv4McastToInt,
        tlsIgmpSnpgCfgRvplsMrouter
    }
    STATUS      current
    DESCRIPTION
        "The group of objects supporting management of IGMP-Snooping on TLS
         level on Nokia 7x50 SR release 13.0 series systems."
    ::= { alxIgmpSnoopingTlsGroups 12 }

alxTlsIgmpSnpgNotifyObjsV15v0Grp OBJECT-GROUP
    OBJECTS     {
        alxIgmpSnpgEMplsTepAddressType,
        alxIgmpSnpgEMplsTepAddress,
        alxIgmpSnpgEMplsTepLabel
    }
    STATUS      current
    DESCRIPTION
        "The group of notification objects supporting management of IGMP
         Snooping on Nokia 7x50 SR series systems added in release 15.0."
    ::= { alxIgmpSnoopingTlsGroups 13 }

alxTlsIgmpSnpgConfigV19v0Group   OBJECT-GROUP
    OBJECTS     {
        tlsIgmpSnpgCfgIpMcastEcmp,
        tlsIgmpSnpgCfgTxSmetRoutes
    }
    STATUS      current
    DESCRIPTION
        "The group of objects supporting management of IGMP-Snooping on TLS
         level on Nokia 7x50 SR release 19.0 series systems."
    ::= { alxIgmpSnoopingTlsGroups 14 }

alxIgmpSnoopingSapConformance    OBJECT IDENTIFIER ::= { alxIgmpSnoopingConformance 2 }

alxIgmpSnoopingSapCompliancs     OBJECT IDENTIFIER ::= { alxIgmpSnoopingSapConformance 1 }

alxIgmpSnoopingSapCompliance     MODULE-COMPLIANCE
    STATUS      obsolete
    DESCRIPTION
        "The  compliance  statement  for management of IGMP
         Snooping  on  SAP  level  on Nokia 7x50 SR series
         systems."
    MODULE
        MANDATORY-GROUPS {
            alxSapIgmpSnpgConfigV3v0Group,
            alxSapIgmpSnpgGroupV3v0,
            alxSapIgmpSnpgStaticV3v0Group,
            alxSapIgmpSnpgStatsV3v0Group,
            alxSapMvrV3v0Group
        }
    ::= { alxIgmpSnoopingSapCompliancs 1 }

alxIgmpSnoopingSapV5v0Compliance MODULE-COMPLIANCE
    STATUS      obsolete
    DESCRIPTION
        "The  compliance  statement  for management of IGMP
         Snooping  on  SAP  level  on Nokia 7x50 SR series
         systems release R5.0."
    MODULE
        MANDATORY-GROUPS {
            alxSapIgmpSnpgConfigV5v0Group,
            alxSapIgmpSnpgGroupV3v0,
            alxSapIgmpSnpgStaticV3v0Group,
            alxSapIgmpSnpgStatsV5v0Group,
            alxSapMvrV3v0Group,
            alxSapIgmpSnpgNotV5v0Group
        }
    ::= { alxIgmpSnoopingSapCompliancs 2 }

alxIgmpSnoopingSapV6v0Compliance MODULE-COMPLIANCE
    STATUS      obsolete
    DESCRIPTION
        "The  compliance  statement  for management of IGMP
         Snooping  on  SAP  level  on Nokia 7x50 SR series
         systems since release R6.0."
    MODULE
        MANDATORY-GROUPS {
            alxSapIgmpSnpgConfigV5v0Group,
            alxSapIgmpSnpgGroupV3v0,
            alxSapIgmpSnpgStaticV3v0Group,
            alxSapIgmpSnpgStatsV6v0Group,
            alxSapMvrV3v0Group,
            alxSapIgmpSnpgNotV5v0Group
        }
    ::= { alxIgmpSnoopingSapCompliancs 3 }

alxIgmpSnoopingSapV6v1Compliance MODULE-COMPLIANCE
    STATUS      current
    DESCRIPTION
        "The  compliance  statement  for management of IGMP
         Snooping  on  SAP  level  on Nokia 7x50 SR series
         systems since release R6.1."
    MODULE
        MANDATORY-GROUPS {
            alxSapIgmpSnpgConfigV5v0Group,
            alxSapIgmpSnpgGroupV3v0,
            alxSapIgmpSnpgStaticV3v0Group,
            alxSapIgmpSnpgStatsV6v0Group,
            alxSapMvrV3v0Group,
            alxSapIgmpSnpgMaxSrcsV6v1Group,
            alxTlsIgmpSnpgNotObjV5v0Group,
            alxTlsIgmpSnpgNotifyObjsV6v1Grp,
            alxSapIgmpSnpgNotV5v0Group,
            alxSapIgmpSnpgMaxSrcsNotV6v1Grp
        }
    ::= { alxIgmpSnoopingSapCompliancs 4 }

alxIgmpSnoopingSapV8v0Compliance MODULE-COMPLIANCE
    STATUS      obsolete
    DESCRIPTION
        "The  compliance  statement  for management of IGMP
         Snooping  on  SAP  level  on Nokia 7x50 SR series
         systems since release R8.0."
    MODULE
        MANDATORY-GROUPS {
            alxSapIgmpSnpgConfigV5v0Group,
            alxSapIgmpSnpgConfigV8v0Group,
            alxSapIgmpSnpgGroupV3v0,
            alxSapIgmpSnpgStaticV3v0Group,
            alxSapIgmpSnpgStatsV6v0Group,
            alxSapMvrV3v0Group,
            alxSapIgmpSnpgMaxSrcsV6v1Group,
            alxTlsIgmpSnpgNotObjV5v0Group,
            alxTlsIgmpSnpgNotifyObjsV6v1Grp,
            alxSapIgmpSnpgNotV5v0Group,
            alxSapIgmpSnpgMaxSrcsNotV6v1Grp
        }
    ::= { alxIgmpSnoopingSapCompliancs 5 }

alxIgmpSnoopingSapV11v0Complianc MODULE-COMPLIANCE
    STATUS      obsolete
    DESCRIPTION
        "The  compliance  statement  for management of IGMP
         Snooping  on  SAP  level  on Nokia 7x50 SR series
         systems since release R11.0."
    MODULE
        MANDATORY-GROUPS {
            alxSapIgmpSnpgConfigV5v0Group,
            alxSapIgmpSnpgConfigV8v0Group,
            alxSapIgmpSnpgConfigV11v0Group,
            alxSapIgmpSnpgGroupV3v0,
            alxSapIgmpSnpgStaticV3v0Group,
            alxSapIgmpSnpgStatsV6v0Group,
            alxSapIgmpSnpgStatsV11v0Group,
            alxSapMvrV3v0Group,
            alxSapIgmpSnpgMaxSrcsV6v1Group,
            alxTlsIgmpSnpgNotObjV5v0Group,
            alxTlsIgmpSnpgNotifyObjsV6v1Grp,
            alxSapIgmpSnpgNotV5v0Group,
            alxSapIgmpSnpgMaxSrcsNotV6v1Grp,
            alxSapIgmpSnpgMaxSrcsNotV11v0Grp
        }
    ::= { alxIgmpSnoopingSapCompliancs 6 }

alxIgmpSnoopingSapV12v0Complianc MODULE-COMPLIANCE
    STATUS      current
    DESCRIPTION
        "The  compliance  statement  for management of IGMP
         Snooping  on  SAP  level  on Nokia 7x50 SR series
         systems since release R12.0."
    MODULE
        MANDATORY-GROUPS {
            alxSapIgmpSnpgConfigV5v0Group,
            alxSapIgmpSnpgConfigV8v0Group,
            alxSapIgmpSnpgConfigV11v0Group,
            alxSapIgmpSnpgConfigV12v0Group,
            alxSapIgmpSnpgGroupV3v0,
            alxSapIgmpSnpgStaticV3v0Group,
            alxSapIgmpSnpgStatsV6v0Group,
            alxSapIgmpSnpgStatsV11v0Group,
            alxSapMvrV3v0Group,
            alxSapIgmpSnpgMaxSrcsV6v1Group,
            alxTlsIgmpSnpgNotObjV5v0Group,
            alxTlsIgmpSnpgNotifyObjsV6v1Grp,
            alxTlsIgmpSnpgNotifyObjsV12v0Grp,
            alxSapIgmpSnpgNotV5v0Group,
            alxSapIgmpSnpgMaxSrcsNotV6v1Grp,
            alxSapIgmpSnpgMaxSrcsNotV11v0Grp
        }
    ::= { alxIgmpSnoopingSapCompliancs 7 }

alxIgmpSnoopingSapV14v0Complianc MODULE-COMPLIANCE
    STATUS      current
    DESCRIPTION
        "The  compliance  statement  for management of IGMP
         Snooping  on  SAP  level  on Nokia 7x50 SR series
         systems since release R14.0."
    MODULE
        MANDATORY-GROUPS {
            alxSapIgmpSnpgConfigV5v0Group,
            alxSapIgmpSnpgConfigV8v0Group,
            alxSapIgmpSnpgConfigV11v0Group,
            alxSapIgmpSnpgConfigV12v0Group,
            alxSapIgmpSnpgConfigV14v0Group,
            alxSapIgmpSnpgGroupV3v0,
            alxSapIgmpSnpgStaticV3v0Group,
            alxSapIgmpSnpgStatsV6v0Group,
            alxSapIgmpSnpgStatsV11v0Group,
            alxSapMvrV3v0Group,
            alxSapIgmpSnpgMaxSrcsV6v1Group,
            alxTlsIgmpSnpgNotObjV5v0Group,
            alxTlsIgmpSnpgNotifyObjsV6v1Grp,
            alxTlsIgmpSnpgNotifyObjsV12v0Grp,
            alxSapIgmpSnpgNotV5v0Group,
            alxSapIgmpSnpgMaxSrcsNotV6v1Grp,
            alxSapIgmpSnpgMaxSrcsNotV11v0Grp
        }
    ::= { alxIgmpSnoopingSapCompliancs 8 }

alxIgmpSnoopingSapGroups         OBJECT IDENTIFIER ::= { alxIgmpSnoopingSapConformance 2 }

alxSapIgmpSnpgConfigV3v0Group    OBJECT-GROUP
    OBJECTS     {
        sapIgmpSnpgCfgImportPlcy,
        sapIgmpSnpgCfgFastLeave,
        sapIgmpSnpgCfgMRouter,
        sapIgmpSnpgCfgSendQueries,
        sapIgmpSnpgCfgGenQueryIntvl,
        sapIgmpSnpgCfgQueryRespIntvl,
        sapIgmpSnpgCfgRobustCount,
        sapIgmpSnpgCfgLastMembIntvl,
        sapIgmpSnpgCfgMaxNbrGrps
    }
    STATUS      obsolete
    DESCRIPTION
        "The group of objects that allow to configure IGMP snooping parameters
         per SAP on Nokia 7x50 SR series systems."
    ::= { alxIgmpSnoopingSapGroups 1 }

alxSapIgmpSnpgGroupV3v0          OBJECT-GROUP
    OBJECTS     {
        sapIgmpSnpgGrpType,
        sapIgmpSnpgGrpFilterMode,
        sapIgmpSnpgGrpUpTime,
        sapIgmpSnpgGrpExpiryTime,
        sapIgmpSnpgGrpCompatMode,
        sapIgmpSnpgGrpV1HostExpTime,
        sapIgmpSnpgGrpV2HostExpTime,
        sapIgmpSnpgGrpSrcType,
        sapIgmpSnpgGrpSrcUpTime,
        sapIgmpSnpgGrpSrcExpiryTime
    }
    STATUS      current
    DESCRIPTION
        "The group of objects that allow to monitor the IGMP snooping
         information that is collected for a given SAP on Nokia 7x50 SR series
         systems."
    ::= { alxIgmpSnoopingSapGroups 2 }

alxSapIgmpSnpgStaticV3v0Group    OBJECT-GROUP
    OBJECTS     {
        sapIgmpSnpgStaticRowstatus
    }
    STATUS      current
    DESCRIPTION
        "The group of objects that allow to statically configure (S,G)
         memberships on a SAP on Nokia 7x50 SR series systems."
    ::= { alxIgmpSnoopingSapGroups 3 }

alxSapIgmpSnpgStatsV3v0Group     OBJECT-GROUP
    OBJECTS     {
        sapIgmpSnpgTxGenQueries,
        sapIgmpSnpgTxGrpSpecQueries,
        sapIgmpSnpgTxSrcSpecQueries,
        sapIgmpSnpgTxV1Reports,
        sapIgmpSnpgTxV2Reports,
        sapIgmpSnpgTxV3Reports,
        sapIgmpSnpgTxV2Leaves,
        sapIgmpSnpgRxGenQueries,
        sapIgmpSnpgRxGrpSpecQueries,
        sapIgmpSnpgRxSrcSpecQueries,
        sapIgmpSnpgRxV1Reports,
        sapIgmpSnpgRxV2Reports,
        sapIgmpSnpgRxV3Reports,
        sapIgmpSnpgRxV2Leaves,
        sapIgmpSnpgRxUnknownType,
        sapIgmpSnpgFwdGenQueries,
        sapIgmpSnpgFwdGrpSpecQueries,
        sapIgmpSnpgFwdSrcSpecQueries,
        sapIgmpSnpgFwdV1Reports,
        sapIgmpSnpgFwdV2Reports,
        sapIgmpSnpgFwdV3Reports,
        sapIgmpSnpgFwdV2Leaves,
        sapIgmpSnpgFwdUnknownType,
        sapIgmpSnpgRxBadLenPkts,
        sapIgmpSnpgRxBadIpChksmPkts,
        sapIgmpSnpgRxBadIgmpChksmPkts,
        sapIgmpSnpgRxBadEncodedPkts,
        sapIgmpSnpgRxNoRtrAlertPkts,
        sapIgmpSnpgRxZeroSrcAdrPkts,
        sapIgmpSnpgSendQueryCfgDrops,
        sapIgmpSnpgImportPolicyDrops,
        sapIgmpSnpgMaxNumGroupsDrops
    }
    STATUS      obsolete
    DESCRIPTION
        "The group of objects that allow to view statistics for IGMP snooping
         on a SAP on Nokia 7x50 SR series systems."
    ::= { alxIgmpSnoopingSapGroups 4 }

alxSapMvrV3v0Group               OBJECT-GROUP
    OBJECTS     {
        sapIgmpSnpgCfgMvrFromVplsId,
        sapIgmpSnpgCfgMvrToSapPortId,
        sapIgmpSnpgCfgMvrToSapEncapVal,
        sapIgmpSnpgGrpMvrFromVplsId,
        sapIgmpSnpgGrpMvrToSapPortId,
        sapIgmpSnpgGrpMvrToSapEncapVal,
        sapIgmpSnpgMvrFromVplsCfgDrops,
        sapIgmpSnpgMvrToSapCfgDrops
    }
    STATUS      current
    DESCRIPTION
        "The group of objects needed to support the MVR feature on a SAP on
         Nokia 7x50 SR series systems."
    ::= { alxIgmpSnoopingSapGroups 5 }

alxSapIgmpSnpgConfigV5v0Group    OBJECT-GROUP
    OBJECTS     {
        sapIgmpSnpgCfgImportPlcy,
        sapIgmpSnpgCfgFastLeave,
        sapIgmpSnpgCfgMRouter,
        sapIgmpSnpgCfgSendQueries,
        sapIgmpSnpgCfgGenQueryIntvl,
        sapIgmpSnpgCfgQueryRespIntvl,
        sapIgmpSnpgCfgRobustCount,
        sapIgmpSnpgCfgLastMembIntvl,
        sapIgmpSnpgCfgMaxNbrGrps,
        sapIgmpSnpgCfgVersion,
        sapIgmpSnpgCfgMcacPolicyName,
        sapIgmpSnpgCfgMcacUnconstBW,
        sapIgmpSnpgCfgMcacConstAdmSt,
        sapIgmpSnpgCfgMcacLevelRowStat,
        sapIgmpSnpgCfgMcacLevelBW,
        sapIgmpSnpgCfgMcacLagRowStat,
        sapIgmpSnpgCfgMcacLagLevel,
        sapIgmpSnpgCfgMcacPrRsvMndBW,
        sapIgmpSnpgCfgMcacinUseMandBw,
        sapIgmpSnpgCfgMcacinUseOpnlBw,
        sapIgmpSnpgCfgMcacAvailMandBw,
        sapIgmpSnpgCfgMcacAvailOpnlBw,
        sapIgmpSnpgCfgMcacValInTrans
    }
    STATUS      current
    DESCRIPTION
        "The group of objects that allow to configure IGMP snooping parameters
         per SAP on Nokia 7x50 SR series systems."
    ::= { alxIgmpSnoopingSapGroups 6 }

alxSapIgmpSnpgStatsV5v0Group     OBJECT-GROUP
    OBJECTS     {
        sapIgmpSnpgTxGenQueries,
        sapIgmpSnpgTxGrpSpecQueries,
        sapIgmpSnpgTxSrcSpecQueries,
        sapIgmpSnpgTxV1Reports,
        sapIgmpSnpgTxV2Reports,
        sapIgmpSnpgTxV3Reports,
        sapIgmpSnpgTxV2Leaves,
        sapIgmpSnpgRxGenQueries,
        sapIgmpSnpgRxGrpSpecQueries,
        sapIgmpSnpgRxSrcSpecQueries,
        sapIgmpSnpgRxV1Reports,
        sapIgmpSnpgRxV2Reports,
        sapIgmpSnpgRxV3Reports,
        sapIgmpSnpgRxV2Leaves,
        sapIgmpSnpgRxUnknownType,
        sapIgmpSnpgFwdGenQueries,
        sapIgmpSnpgFwdGrpSpecQueries,
        sapIgmpSnpgFwdSrcSpecQueries,
        sapIgmpSnpgFwdV1Reports,
        sapIgmpSnpgFwdV2Reports,
        sapIgmpSnpgFwdV3Reports,
        sapIgmpSnpgFwdV2Leaves,
        sapIgmpSnpgFwdUnknownType,
        sapIgmpSnpgRxBadLenPkts,
        sapIgmpSnpgRxBadIpChksmPkts,
        sapIgmpSnpgRxBadIgmpChksmPkts,
        sapIgmpSnpgRxBadEncodedPkts,
        sapIgmpSnpgRxNoRtrAlertPkts,
        sapIgmpSnpgRxZeroSrcAdrPkts,
        sapIgmpSnpgSendQueryCfgDrops,
        sapIgmpSnpgImportPolicyDrops,
        sapIgmpSnpgMaxNumGroupsDrops,
        sapIgmpSnpgRxWrongVersionPkts,
        sapIgmpSnpgMcacPolicyDrops,
        sapIgmpSnpgMcsFailures
    }
    STATUS      obsolete
    DESCRIPTION
        "The group of objects that allow to view statistics for IGMP snooping
         on a SAP on Nokia 7x50 SR series systems."
    ::= { alxIgmpSnoopingSapGroups 7 }

alxSapIgmpSnpgNotV5v0Group       NOTIFICATION-GROUP
    NOTIFICATIONS {
        sapIgmpSnpgGrpLimitExceeded,
        sapIgmpSnpgMcacPlcyDropped,
        sapIgmpSnpgMcsFailure
    }
    STATUS      current
    DESCRIPTION
        "The group of notifications supporting IGMP snooping on a SAP on Nokia
         7x50 SR series systems."
    ::= { alxIgmpSnoopingSapGroups 8 }

alxSapIgmpSnpgTimeStampGroup     OBJECT-GROUP
    OBJECTS     {
        sapIgmpSnpgCfgLastChangeTime,
        sapIgmpSnpgStaticLastChangeTime,
        sapIgmpSnpgCfgMcacLevelLastChngT,
        sapIgmpSnpgCfgMcacLagLastChangeT,
        sapIgmpSnpgConfigTableLastChange,
        sapIgmpSnpgStaticGrpSrcTablLstCh,
        sapIgmpSnpgMcacLevelTableLstCh,
        sapIgmpSnpgMcacLagTableLastChng
    }
    STATUS      current
    DESCRIPTION
        "The group of last change timestamps for IGMP snooping on a SAP on
         Nokia 7x50 SR series systems."
    ::= { alxIgmpSnoopingSapGroups 9 }

alxSapIgmpSnpgStatsV6v0Group     OBJECT-GROUP
    OBJECTS     {
        sapIgmpSnpgTxGenQueries,
        sapIgmpSnpgTxGrpSpecQueries,
        sapIgmpSnpgTxSrcSpecQueries,
        sapIgmpSnpgTxV1Reports,
        sapIgmpSnpgTxV2Reports,
        sapIgmpSnpgTxV3Reports,
        sapIgmpSnpgTxV2Leaves,
        sapIgmpSnpgRxGenQueries,
        sapIgmpSnpgRxGrpSpecQueries,
        sapIgmpSnpgRxSrcSpecQueries,
        sapIgmpSnpgRxV1Reports,
        sapIgmpSnpgRxV2Reports,
        sapIgmpSnpgRxV3Reports,
        sapIgmpSnpgRxV2Leaves,
        sapIgmpSnpgRxUnknownType,
        sapIgmpSnpgFwdGenQueries,
        sapIgmpSnpgFwdGrpSpecQueries,
        sapIgmpSnpgFwdSrcSpecQueries,
        sapIgmpSnpgFwdV1Reports,
        sapIgmpSnpgFwdV2Reports,
        sapIgmpSnpgFwdV3Reports,
        sapIgmpSnpgFwdV2Leaves,
        sapIgmpSnpgFwdUnknownType,
        sapIgmpSnpgRxBadLenPkts,
        sapIgmpSnpgRxBadIpChksmPkts,
        sapIgmpSnpgRxBadIgmpChksmPkts,
        sapIgmpSnpgRxBadEncodedPkts,
        sapIgmpSnpgRxNoRtrAlertPkts,
        sapIgmpSnpgRxZeroSrcAdrPkts,
        sapIgmpSnpgSendQueryCfgDrops,
        sapIgmpSnpgImportPolicyDrops,
        sapIgmpSnpgMaxNumGroupsDrops,
        sapIgmpSnpgRxWrongVersionPkts,
        sapIgmpSnpgMcacPolicyDrops,
        sapIgmpSnpgMcsFailures,
        sapIgmpSnpgRxLocalScopePkts,
        sapIgmpSnpgRxRsvdScopePkts
    }
    STATUS      current
    DESCRIPTION
        "The group of objects that allow to view statistics for IGMP snooping
         on a SAP on Nokia 7x50 SR series systems."
    ::= { alxIgmpSnoopingSapGroups 10 }

alxSapIgmpSnpgMaxSrcsV6v1Group   OBJECT-GROUP
    OBJECTS     {
        sapIgmpSnpgCfgMaxNbrSrcs,
        sapIgmpSnpgMaxNumSourcesDrops
    }
    STATUS      current
    DESCRIPTION
        "The group of objects that allow to configure IGMP snooping parameters
         per SAP on Nokia 7x50 SR series systems."
    ::= { alxIgmpSnoopingSapGroups 11 }

alxSapIgmpSnpgMaxSrcsNotV6v1Grp  NOTIFICATION-GROUP
    NOTIFICATIONS {
        sapIgmpSnpgSrcLimitExceeded
    }
    STATUS      current
    DESCRIPTION
        "The group of notifications supporting IGMP snooping on a SAP on Nokia
         7x50 SR series systems."
    ::= { alxIgmpSnoopingSapGroups 12 }

alxSapIgmpSnpgConfigV8v0Group    OBJECT-GROUP
    OBJECTS     {
        sapIgmpSnpgCfgDisRtrAlertChk,
        sdpBndIgmpSnpgCfgDisRtrAlertChk
    }
    STATUS      current
    DESCRIPTION
        "The group of objects that allow to configure IGMP snooping parameters
         per SAP on release 8.0 Nokia 7x50 SR series systems."
    ::= { alxIgmpSnoopingSapGroups 13 }

alxSapIgmpSnpgConfigV11v0Group   OBJECT-GROUP
    OBJECTS     {
        sdpBndIgmpSnpgCfgMaxNbrGrpSrcs,
        sapIgmpSnpgCfgMaxNbrGrpSrcs
    }
    STATUS      current
    DESCRIPTION
        "The group of objects that allow to configure IGMP snooping parameters
         per SAP on release 11.0 Nokia 7x50 SR series systems."
    ::= { alxIgmpSnoopingSapGroups 14 }

alxSapIgmpSnpgStatsV11v0Group    OBJECT-GROUP
    OBJECTS     {
        sapIgmpSnpgMaxNumGrpSrcsDrops,
        sdpBndIgmpSnpgMaxNumGrpSrcsDrops
    }
    STATUS      current
    DESCRIPTION
        "The group of objects that allow to view statistics for IGMP snooping
         on a SAP on Nokia 7x50 SR series systems."
    ::= { alxIgmpSnoopingSapGroups 15 }

alxSapIgmpSnpgMaxSrcsNotV11v0Grp NOTIFICATION-GROUP
    NOTIFICATIONS {
        sapIgmpSnpgGrpSrcLimitExceeded
    }
    STATUS      current
    DESCRIPTION
        "The group of notifications supporting IGMP snooping on a SAP on Nokia
         7x50 SR series systems."
    ::= { alxIgmpSnoopingSapGroups 16 }

alxSapIgmpSnpgConfigV12v0Group   OBJECT-GROUP
    OBJECTS     {
        sapIgmpSnpgCfgMcacUseLagPortWt
    }
    STATUS      current
    DESCRIPTION
        "The group of objects that allow to configure IGMP snooping parameters
         per SAP added in release 12.0 Nokia 7xx0 SR series systems."
    ::= { alxIgmpSnoopingSapGroups 17 }

alxSapIgmpSnpgConfigV14v0Group   OBJECT-GROUP
    OBJECTS     {
        sapIgmpSnpgCfgMcacIfPolicyName
    }
    STATUS      current
    DESCRIPTION
        "The group of objects that allow to configure IGMP snooping parameters
         per SAP added in release 14.0 Nokia 7xx0 SR series systems."
    ::= { alxIgmpSnoopingSapGroups 18 }

alxIgmpSnoopingSdpBndConformance OBJECT IDENTIFIER ::= { alxIgmpSnoopingConformance 3 }

alxIgmpSnoopingSdpBndCompliancs  OBJECT IDENTIFIER ::= { alxIgmpSnoopingSdpBndConformance 1 }

alxIgmpSnoopingSdpBndCompliance  MODULE-COMPLIANCE
    STATUS      obsolete
    DESCRIPTION
        "The  compliance  statement  for management of IGMP
         Snooping  on  SDP  Bind  level  on  Nokia 7x50 SR
         series systems."
    MODULE
        MANDATORY-GROUPS {
            alxSdpBindIgmpSnpgConfV3v0Group,
            alxSdpBindIgmpSnpgV3v0Group,
            alxSdpBindIgmpSnpgStatV3v0Group,
            alxSdpBindIgmpSnpgStatsV3v0Grp
        }
    ::= { alxIgmpSnoopingSdpBndCompliancs 1 }

alxIgmpSnoopingSdpBndV5v0Compliance MODULE-COMPLIANCE
    STATUS      obsolete
    DESCRIPTION
        "The  compliance  statement  for management of IGMP
         Snooping  on  SDP  Bind  level  on  Nokia 7x50 SR
         series systems release R5.0."
    MODULE
        MANDATORY-GROUPS {
            alxSdpBindIgmpSnpgConfV5v0Group,
            alxSdpBindIgmpSnpgV3v0Group,
            alxSdpBindIgmpSnpgStatV3v0Group,
            alxSdpBindIgmpSnpgStatsV5v0Grp,
            alxSdpBindIgmpSnpgNotV5v0Group
        }
    ::= { alxIgmpSnoopingSdpBndCompliancs 2 }

alxIgmpSnoopingSdpBndV6v0Compliance MODULE-COMPLIANCE
    STATUS      obsolete
    DESCRIPTION
        "The  compliance  statement  for management of IGMP
         Snooping  on  SDP  Bind  level  on  Nokia 7x50 SR
         series systems since release R6.0."
    MODULE
        MANDATORY-GROUPS {
            alxSdpBindIgmpSnpgConfV5v0Group,
            alxSdpBindIgmpSnpgV3v0Group,
            alxSdpBindIgmpSnpgStatV3v0Group,
            alxSdpBindIgmpSnpgStatsV6v0Grp,
            alxSdpBindIgmpSnpgNotV5v0Group
        }
    ::= { alxIgmpSnoopingSdpBndCompliancs 3 }

alxIgmpSnoopingSdpBndV6v1Compliance MODULE-COMPLIANCE
    STATUS      obsolete
    DESCRIPTION
        "The  compliance  statement  for management of IGMP
         Snooping  on  SDP  Bind  level  on  Nokia 7x50 SR
         series systems since release R6.1."
    MODULE
        MANDATORY-GROUPS {
            alxSdpBindIgmpSnpgConfV5v0Group,
            alxSdpBindIgmpSnpgV3v0Group,
            alxSdpBindIgmpSnpgStatV3v0Group,
            alxSdpBindIgmpSnpgStatsV6v0Grp,
            alxSdpBindIgmpSnpgMaxSrcsV6v1Grp,
            alxTlsIgmpSnpgNotObjV5v0Group,
            alxTlsIgmpSnpgNotifyObjsV6v1Grp,
            alxSdpBindIgmpSnpgNotV5v0Group,
            alxSdpBindIgmpSnpgNotV6v1Group
        }
    ::= { alxIgmpSnoopingSdpBndCompliancs 4 }

alxIgmpSnpgSdpBndV11v0Compliance MODULE-COMPLIANCE
    STATUS      obsolete
    DESCRIPTION
        "The  compliance  statement  for management of IGMP
         Snooping  on  SDP  Bind  level  on  Nokia 7x50 SR
         series systems since release R11.0."
    MODULE
        MANDATORY-GROUPS {
            alxSdpBindIgmpSnpgConfV5v0Group,
            alxSdpBindIgmpSnpgV3v0Group,
            alxSdpBindIgmpSnpgStatV3v0Group,
            alxSdpBindIgmpSnpgStatsV6v0Grp,
            alxSdpBindIgmpSnpgMaxSrcsV6v1Grp,
            alxTlsIgmpSnpgNotObjV5v0Group,
            alxTlsIgmpSnpgNotifyObjsV6v1Grp,
            alxSdpBindIgmpSnpgNotV5v0Group,
            alxSdpBindIgmpSnpgNotV6v1Group,
            alxSdpBindIgmpSnpgNotV11v0Group
        }
    ::= { alxIgmpSnoopingSdpBndCompliancs 5 }

alxIgmpSnpgSdpBndV14v0Compliance MODULE-COMPLIANCE
    STATUS      current
    DESCRIPTION
        "The  compliance  statement  for management of IGMP
         Snooping  on  SDP  Bind  level  on  Nokia 7x50 SR
         series systems since release R14.0."
    MODULE
        MANDATORY-GROUPS {
            alxSdpBindIgmpSnpgConfV5v0Group,
            alxSdpBindIgmpSnpgConfV14v0Group,
            alxSdpBindIgmpSnpgV3v0Group,
            alxSdpBindIgmpSnpgStatV3v0Group,
            alxSdpBindIgmpSnpgStatsV6v0Grp,
            alxSdpBindIgmpSnpgMaxSrcsV6v1Grp,
            alxTlsIgmpSnpgNotObjV5v0Group,
            alxTlsIgmpSnpgNotifyObjsV6v1Grp,
            alxSdpBindIgmpSnpgNotV5v0Group,
            alxSdpBindIgmpSnpgNotV6v1Group,
            alxSdpBindIgmpSnpgNotV11v0Group
        }
    ::= { alxIgmpSnoopingSdpBndCompliancs 6 }

alxIgmpSnoopingSdpBndGroups      OBJECT IDENTIFIER ::= { alxIgmpSnoopingSdpBndConformance 2 }

alxSdpBindIgmpSnpgConfV3v0Group  OBJECT-GROUP
    OBJECTS     {
        sdpBndIgmpSnpgCfgImportPlcy,
        sdpBndIgmpSnpgCfgFastLeave,
        sdpBndIgmpSnpgCfgMRouter,
        sdpBndIgmpSnpgCfgSendQueries,
        sdpBndIgmpSnpgCfgGenQueryIntvl,
        sdpBndIgmpSnpgCfgQueryRespIntvl,
        sdpBndIgmpSnpgCfgRobustCount,
        sdpBndIgmpSnpgCfgLastMembIntvl,
        sdpBndIgmpSnpgCfgMaxNbrGrps
    }
    STATUS      obsolete
    DESCRIPTION
        "The group of objects that allow to configure IGMP snooping parameters
         per SDP bind on Nokia 7x50 SR series systems."
    ::= { alxIgmpSnoopingSdpBndGroups 1 }

alxSdpBindIgmpSnpgV3v0Group      OBJECT-GROUP
    OBJECTS     {
        sdpBndIgmpSnpgGrpType,
        sdpBndIgmpSnpgGrpFilterMode,
        sdpBndIgmpSnpgGrpUpTime,
        sdpBndIgmpSnpgGrpExpiryTime,
        sdpBndIgmpSnpgGrpCompatMode,
        sdpBndIgmpSnpgGrpV1HostExpTime,
        sdpBndIgmpSnpgGrpV2HostExpTime,
        sdpBndIgmpSnpgGrpSrcType,
        sdpBndIgmpSnpgGrpSrcUpTime,
        sdpBndIgmpSnpgGrpSrcExpiryTime
    }
    STATUS      current
    DESCRIPTION
        "The group of objects that allow to monitor the IGMP snooping
         information that is collected for a given SDP Bind on Nokia 7x50 SR
         series systems."
    ::= { alxIgmpSnoopingSdpBndGroups 2 }

alxSdpBindIgmpSnpgStatV3v0Group  OBJECT-GROUP
    OBJECTS     {
        sdpBndIgmpSnpgStaticRowstatus
    }
    STATUS      current
    DESCRIPTION
        "The  group  of objects that allow to statically
         configure (S,G) memberships on a SDP Bind on Nokia
         7x50 SR series systems."
    ::= { alxIgmpSnoopingSdpBndGroups 3 }

alxSdpBindIgmpSnpgStatsV3v0Grp   OBJECT-GROUP
    OBJECTS     {
        sdpBndIgmpSnpgTxGenQueries,
        sdpBndIgmpSnpgTxGrpSpecQueries,
        sdpBndIgmpSnpgTxSrcSpecQueries,
        sdpBndIgmpSnpgTxV1Reports,
        sdpBndIgmpSnpgTxV2Reports,
        sdpBndIgmpSnpgTxV3Reports,
        sdpBndIgmpSnpgTxV2Leaves,
        sdpBndIgmpSnpgRxGenQueries,
        sdpBndIgmpSnpgRxGrpSpecQueries,
        sdpBndIgmpSnpgRxSrcSpecQueries,
        sdpBndIgmpSnpgRxV1Reports,
        sdpBndIgmpSnpgRxV2Reports,
        sdpBndIgmpSnpgRxV3Reports,
        sdpBndIgmpSnpgRxV2Leaves,
        sdpBndIgmpSnpgRxUnknownType,
        sdpBndIgmpSnpgFwdGenQueries,
        sdpBndIgmpSnpgFwdGrpSpecQueries,
        sdpBndIgmpSnpgFwdSrcSpecQueries,
        sdpBndIgmpSnpgFwdV1Reports,
        sdpBndIgmpSnpgFwdV2Reports,
        sdpBndIgmpSnpgFwdV3Reports,
        sdpBndIgmpSnpgFwdV2Leaves,
        sdpBndIgmpSnpgFwdUnknownType,
        sdpBndIgmpSnpgRxBadLenPkts,
        sdpBndIgmpSnpgRxBadIpChksmPkts,
        sdpBndIgmpSnpgRxBadIgmpChksmPkts,
        sdpBndIgmpSnpgRxBadEncodedPkts,
        sdpBndIgmpSnpgRxNoRtrAlertPkts,
        sdpBndIgmpSnpgRxZeroSrcAdrPkts,
        sdpBndIgmpSnpgSendQueryCfgDrops,
        sdpBndIgmpSnpgImportPolicyDrops,
        sdpBndIgmpSnpgMaxNumGroupsDrops
    }
    STATUS      obsolete
    DESCRIPTION
        "The group of objects that allow to view statistics for IGMP snooping
         on a SDP Bind on Nokia 7x50 SR series systems."
    ::= { alxIgmpSnoopingSdpBndGroups 4 }

alxSdpBindIgmpSnpgConfV5v0Group  OBJECT-GROUP
    OBJECTS     {
        sdpBndIgmpSnpgCfgImportPlcy,
        sdpBndIgmpSnpgCfgFastLeave,
        sdpBndIgmpSnpgCfgMRouter,
        sdpBndIgmpSnpgCfgSendQueries,
        sdpBndIgmpSnpgCfgGenQueryIntvl,
        sdpBndIgmpSnpgCfgQueryRespIntvl,
        sdpBndIgmpSnpgCfgRobustCount,
        sdpBndIgmpSnpgCfgLastMembIntvl,
        sdpBndIgmpSnpgCfgMaxNbrGrps,
        sdpBndIgmpSnpgCfgVersion,
        sdpBndIgmpSnpgCfgMcacPolicyName,
        sdpBndIgmpSnpgCfgMcacUnconstBW,
        sdpBndIgmpSnpgCfgMcacPrRsvMndBW,
        sdpBndIgmpSnpgCfgMcacinUseMndBw,
        sdpBndIgmpSnpgCfgMcacinUseOplBw,
        sdpBndIgmpSnpgCfgMcacAvailMndBw,
        sdpBndIgmpSnpgCfgMcacAvailOplBw,
        sdpBndIgmpSnpgCfgMcacValInTrans
    }
    STATUS      current
    DESCRIPTION
        "The group of objects that allow to configure IGMP snooping parameters
         per SDP bind on Nokia 7x50 SR series systems."
    ::= { alxIgmpSnoopingSdpBndGroups 5 }

alxSdpBindIgmpSnpgStatsV5v0Grp   OBJECT-GROUP
    OBJECTS     {
        sdpBndIgmpSnpgTxGenQueries,
        sdpBndIgmpSnpgTxGrpSpecQueries,
        sdpBndIgmpSnpgTxSrcSpecQueries,
        sdpBndIgmpSnpgTxV1Reports,
        sdpBndIgmpSnpgTxV2Reports,
        sdpBndIgmpSnpgTxV3Reports,
        sdpBndIgmpSnpgTxV2Leaves,
        sdpBndIgmpSnpgRxGenQueries,
        sdpBndIgmpSnpgRxGrpSpecQueries,
        sdpBndIgmpSnpgRxSrcSpecQueries,
        sdpBndIgmpSnpgRxV1Reports,
        sdpBndIgmpSnpgRxV2Reports,
        sdpBndIgmpSnpgRxV3Reports,
        sdpBndIgmpSnpgRxV2Leaves,
        sdpBndIgmpSnpgRxUnknownType,
        sdpBndIgmpSnpgFwdGenQueries,
        sdpBndIgmpSnpgFwdGrpSpecQueries,
        sdpBndIgmpSnpgFwdSrcSpecQueries,
        sdpBndIgmpSnpgFwdV1Reports,
        sdpBndIgmpSnpgFwdV2Reports,
        sdpBndIgmpSnpgFwdV3Reports,
        sdpBndIgmpSnpgFwdV2Leaves,
        sdpBndIgmpSnpgFwdUnknownType,
        sdpBndIgmpSnpgRxBadLenPkts,
        sdpBndIgmpSnpgRxBadIpChksmPkts,
        sdpBndIgmpSnpgRxBadIgmpChksmPkts,
        sdpBndIgmpSnpgRxBadEncodedPkts,
        sdpBndIgmpSnpgRxNoRtrAlertPkts,
        sdpBndIgmpSnpgRxZeroSrcAdrPkts,
        sdpBndIgmpSnpgSendQueryCfgDrops,
        sdpBndIgmpSnpgImportPolicyDrops,
        sdpBndIgmpSnpgMaxNumGroupsDrops,
        sdpBndIgmpSnpgRxWrongVersionPkts,
        sdpBndIgmpSnpgMcacPolicyDrops
    }
    STATUS      obsolete
    DESCRIPTION
        "The group of objects that allow to view statistics for IGMP snooping
         on a SDP Bind on Nokia 7x50 SR series systems."
    ::= { alxIgmpSnoopingSdpBndGroups 6 }

alxSdpBindIgmpSnpgNotV5v0Group   NOTIFICATION-GROUP
    NOTIFICATIONS {
        sdpBndIgmpSnpgGrpLimitExceeded,
        sdpBndIgmpSnpgMcacPlcyDropped
    }
    STATUS      current
    DESCRIPTION
        "The group of notifications supporting IGMP snooping on an SDP Bind on
         Nokia 7x50 SR series systems."
    ::= { alxIgmpSnoopingSdpBndGroups 7 }

alxSdpBindIgmpSnpgTimeStampGroup OBJECT-GROUP
    OBJECTS     {
        sdpBndIgmpSnpgCfgLastChangeTime,
        sdpBndIgmpSnpgStaticLastChange,
        sdpBindIgmpSnpgConfigTableLstCh,
        sdpBindIgmpSnpgStaticGrpSrcTblLC
    }
    STATUS      current
    DESCRIPTION
        "The group of last change timestamps for IGMP snooping on an SDP Bind
         on Nokia 7x50 SR series systems."
    ::= { alxIgmpSnoopingSdpBndGroups 8 }

alxSdpBindIgmpSnpgStatsV6v0Grp   OBJECT-GROUP
    OBJECTS     {
        sdpBndIgmpSnpgTxGenQueries,
        sdpBndIgmpSnpgTxGrpSpecQueries,
        sdpBndIgmpSnpgTxSrcSpecQueries,
        sdpBndIgmpSnpgTxV1Reports,
        sdpBndIgmpSnpgTxV2Reports,
        sdpBndIgmpSnpgTxV3Reports,
        sdpBndIgmpSnpgTxV2Leaves,
        sdpBndIgmpSnpgRxGenQueries,
        sdpBndIgmpSnpgRxGrpSpecQueries,
        sdpBndIgmpSnpgRxSrcSpecQueries,
        sdpBndIgmpSnpgRxV1Reports,
        sdpBndIgmpSnpgRxV2Reports,
        sdpBndIgmpSnpgRxV3Reports,
        sdpBndIgmpSnpgRxV2Leaves,
        sdpBndIgmpSnpgRxUnknownType,
        sdpBndIgmpSnpgFwdGenQueries,
        sdpBndIgmpSnpgFwdGrpSpecQueries,
        sdpBndIgmpSnpgFwdSrcSpecQueries,
        sdpBndIgmpSnpgFwdV1Reports,
        sdpBndIgmpSnpgFwdV2Reports,
        sdpBndIgmpSnpgFwdV3Reports,
        sdpBndIgmpSnpgFwdV2Leaves,
        sdpBndIgmpSnpgFwdUnknownType,
        sdpBndIgmpSnpgRxBadLenPkts,
        sdpBndIgmpSnpgRxBadIpChksmPkts,
        sdpBndIgmpSnpgRxBadIgmpChksmPkts,
        sdpBndIgmpSnpgRxBadEncodedPkts,
        sdpBndIgmpSnpgRxNoRtrAlertPkts,
        sdpBndIgmpSnpgRxZeroSrcAdrPkts,
        sdpBndIgmpSnpgSendQueryCfgDrops,
        sdpBndIgmpSnpgImportPolicyDrops,
        sdpBndIgmpSnpgMaxNumGroupsDrops,
        sdpBndIgmpSnpgRxWrongVersionPkts,
        sdpBndIgmpSnpgMcacPolicyDrops,
        sdpBndIgmpSnpgRxLocalScopePkts,
        sdpBndIgmpSnpgRxRsvdScopePkts
    }
    STATUS      current
    DESCRIPTION
        "The group of objects that allow to view statistics for IGMP snooping
         on a SDP Bind on Nokia 7x50 SR series systems."
    ::= { alxIgmpSnoopingSdpBndGroups 9 }

alxSdpBindIgmpSnpgMaxSrcsV6v1Grp OBJECT-GROUP
    OBJECTS     {
        sdpBndIgmpSnpgCfgMaxNbrSrcs,
        sdpBndIgmpSnpgMaxNumSourcesDrops
    }
    STATUS      current
    DESCRIPTION
        "The group of objects that allow to configure IGMP snooping parameters
         per SDP bind on Nokia 7x50 SR series systems added in release 6.1R6."
    ::= { alxIgmpSnoopingSdpBndGroups 10 }

alxSdpBindIgmpSnpgNotV6v1Group   NOTIFICATION-GROUP
    NOTIFICATIONS {
        sdpBndIgmpSnpgSrcLimitExceeded
    }
    STATUS      current
    DESCRIPTION
        "The group of notifications supporting IGMP snooping on an SDP Bind on
         Nokia 7x50 SR series systems added in release 6.1R6."
    ::= { alxIgmpSnoopingSdpBndGroups 12 }

alxSdpBindIgmpSnpgNotV11v0Group  NOTIFICATION-GROUP
    NOTIFICATIONS {
        sdpBndIgmpSnpgGrpSrcLimitExceed
    }
    STATUS      current
    DESCRIPTION
        "The group of notifications supporting IGMP snooping on an SDP Bind on
         Nokia 7x50 SR series systems added in release 11.0."
    ::= { alxIgmpSnoopingSdpBndGroups 13 }

alxSdpBindIgmpSnpgConfV14v0Group OBJECT-GROUP
    OBJECTS     {
        sdpBndIgmpSnpgCfgMcacIfPlcyName
    }
    STATUS      current
    DESCRIPTION
        "The group of objects that allow to configure IGMP snooping parameters
         per SDP bind on Nokia 7x50 SR release 14.0 series systems."
    ::= { alxIgmpSnoopingSdpBndGroups 14 }

alxIgmpSnoopingVxlanConformance  OBJECT IDENTIFIER ::= { alxIgmpSnoopingConformance 4 }

alxIgmpSnoopingVxlanCompliancs   OBJECT IDENTIFIER ::= { alxIgmpSnoopingVxlanConformance 1 }

alxIgmpSnpgVxlanV13v0Compliance  MODULE-COMPLIANCE
    STATUS      current
    DESCRIPTION
        "The compliance statement for management of IGMP Snooping on VXLAN on
         Nokia 7x50 SR series release 13.0 systems."
    MODULE
        MANDATORY-GROUPS {
            alxVxlanIgmpSnpgGroupV13v0Grp,
            alxVxlanIgmpSnpgStatsV13v0Grp
        }
    ::= { alxIgmpSnoopingVxlanCompliancs 1 }

alxIgmpSnpgVxlanV20v0Compliance  MODULE-COMPLIANCE
    STATUS      current
    DESCRIPTION
        "The compliance statement for management of IGMP Snooping on VXLAN on
         Nokia 7x50 SR series release 20.0 systems."
    MODULE
        MANDATORY-GROUPS {
            alxVxlanIgmpSnpgStateV20v0Grp
        }
    ::= { alxIgmpSnoopingVxlanCompliancs 2 }

alxIgmpSnoopingVxlanGroups       OBJECT IDENTIFIER ::= { alxIgmpSnoopingVxlanConformance 2 }

alxVxlanIgmpSnpgGroupV13v0Grp    OBJECT-GROUP
    OBJECTS     {
        vxlanIgmpSnpgGrpType,
        vxlanIgmpSnpgGrpFilterMode,
        vxlanIgmpSnpgGrpUpTime,
        vxlanIgmpSnpgGrpExpiryTime,
        vxlanIgmpSnpgGrpCompatMode,
        vxlanIgmpSnpgGrpV1HostExpTime,
        vxlanIgmpSnpgGrpV2HostExpTime,
        vxlanIgmpSnpgGrpSrcType,
        vxlanIgmpSnpgGrpSrcUpTime,
        vxlanIgmpSnpgGrpSrcExpiryTime
    }
    STATUS      current
    DESCRIPTION
        "The group of objects that allow to monitor the IGMP snooping
         information that is collected for a given VXLAN on Nokia 7x50 SR
         series systems."
    ::= { alxIgmpSnoopingVxlanGroups 1 }

alxVxlanIgmpSnpgStatsV13v0Grp    OBJECT-GROUP
    OBJECTS     {
        vxlanIgmpSnpgTxGenQueries,
        vxlanIgmpSnpgTxGrpSpecQueries,
        vxlanIgmpSnpgTxSrcSpecQueries,
        vxlanIgmpSnpgTxV1Reports,
        vxlanIgmpSnpgTxV2Reports,
        vxlanIgmpSnpgTxV3Reports,
        vxlanIgmpSnpgTxV2Leaves,
        vxlanIgmpSnpgRxGenQueries,
        vxlanIgmpSnpgRxGrpSpecQueries,
        vxlanIgmpSnpgRxSrcSpecQueries,
        vxlanIgmpSnpgRxV1Reports,
        vxlanIgmpSnpgRxV2Reports,
        vxlanIgmpSnpgRxV3Reports,
        vxlanIgmpSnpgRxV2Leaves,
        vxlanIgmpSnpgRxUnknownType,
        vxlanIgmpSnpgFwdGenQueries,
        vxlanIgmpSnpgFwdGrpSpecQueries,
        vxlanIgmpSnpgFwdSrcSpecQueries,
        vxlanIgmpSnpgFwdV1Reports,
        vxlanIgmpSnpgFwdV2Reports,
        vxlanIgmpSnpgFwdV3Reports,
        vxlanIgmpSnpgFwdV2Leaves,
        vxlanIgmpSnpgFwdUnknownType,
        vxlanIgmpSnpgRxBadLenPkts,
        vxlanIgmpSnpgRxBadIpChksmPkts,
        vxlanIgmpSnpgRxBadIgmpChksmPkts,
        vxlanIgmpSnpgRxBadEncodedPkts,
        vxlanIgmpSnpgRxNoRtrAlertPkts,
        vxlanIgmpSnpgRxZeroSrcAdrPkts,
        vxlanIgmpSnpgSendQueryCfgDrops,
        vxlanIgmpSnpgImportPolicyDrops,
        vxlanIgmpSnpgMaxNumGroupsDrops,
        vxlanIgmpSnpgRxWrongVersionPkts,
        vxlanIgmpSnpgMcacPolicyDrops,
        vxlanIgmpSnpgMcsFailures,
        vxlanIgmpSnpgRxLocalScopePkts,
        vxlanIgmpSnpgRxRsvdScopePkts,
        vxlanIgmpSnpgMaxNumSourcesDrops,
        vxlanIgmpSnpgMaxNumGrpSrcsDrops
    }
    STATUS      current
    DESCRIPTION
        "The group of objects that allow to view statistics for IGMP snooping
         on a VXLAN on Nokia 7x50 SR series release 13.0 systems."
    ::= { alxIgmpSnoopingVxlanGroups 2 }

alxVxlanIgmpSnpgStateV20v0Grp    OBJECT-GROUP
    OBJECTS     {
        vxlanIgmpDroppedSmetRoutes,
        vxlanIgmpIsSbd,
        vxlanIgmpRxSmetRoutes,
        vxlanIgmpSnpgGroupCount,
        vxlanIgmpSnpgOperState,
        vxlanIgmpOrigAddrType,
        vxlanIgmpOrigAddress
    }
    STATUS      current
    DESCRIPTION
        "The group of objects that allow to view statistics for IGMP snooping
         on a VXLAN on Nokia 7x50 SR series release 20.0 systems."
    ::= { alxIgmpSnoopingVxlanGroups 3 }

alxIgmpSnoopingEMplsConformance  OBJECT IDENTIFIER ::= { alxIgmpSnoopingConformance 5 }

alxIgmpSnoopingEMplsCompliancs   OBJECT IDENTIFIER ::= { alxIgmpSnoopingEMplsConformance 1 }

alxIgmpSnpgEMplsV14v0Compliance  MODULE-COMPLIANCE
    STATUS      current
    DESCRIPTION
        "The compliance statement for management of IGMP Snooping on evpn-mpls
         on Nokia 7x50 SR series release 14.0 systems."
    MODULE
        MANDATORY-GROUPS {
            alxEMplsIgmpSnpgStatsV14v0Grp
        }
    ::= { alxIgmpSnoopingEMplsCompliancs 1 }

alxIgmpSnoopingEMplsCompliance   MODULE-COMPLIANCE
    STATUS      current
    DESCRIPTION
        "The  compliance  statement  for management of IGMP Snooping
         on  evpn-mpls  level  on  Nokia 7x50 SR series systems."
    MODULE
        MANDATORY-GROUPS {
            alxTlsIgmpSnpgNotifyObjsV15v0Grp,
            alxEMplsIgmpSnpgNotifyV15v0Group
        }
    ::= { alxIgmpSnoopingEMplsCompliancs 2 }

alxIgmpSnpgEMplsV19v0Compliance  MODULE-COMPLIANCE
    STATUS      current
    DESCRIPTION
        "The compliance statement for management of IGMP Snooping on evpn-mpls
         on Nokia 7x50 SR series release 19.0 systems."
    MODULE
        MANDATORY-GROUPS {
            alxEMplsIgmpSnpgStatsV19v0Grp
        }
    ::= { alxIgmpSnoopingEMplsCompliancs 3 }

alxIgmpSnoopingEMplsGroups       OBJECT IDENTIFIER ::= { alxIgmpSnoopingEMplsConformance 2 }

alxEMplsIgmpSnpgStatsV14v0Grp    OBJECT-GROUP
    OBJECTS     {
        eMplsIgmpSnpgTxGenQueries,
        eMplsIgmpSnpgTxGrpSpecQueries,
        eMplsIgmpSnpgTxSrcSpecQueries,
        eMplsIgmpSnpgTxV1Reports,
        eMplsIgmpSnpgTxV2Reports,
        eMplsIgmpSnpgTxV3Reports,
        eMplsIgmpSnpgTxV2Leaves,
        eMplsIgmpSnpgRxGenQueries,
        eMplsIgmpSnpgRxGrpSpecQueries,
        eMplsIgmpSnpgRxSrcSpecQueries,
        eMplsIgmpSnpgRxV1Reports,
        eMplsIgmpSnpgRxV2Reports,
        eMplsIgmpSnpgRxV3Reports,
        eMplsIgmpSnpgRxV2Leaves,
        eMplsIgmpSnpgRxUnknownType,
        eMplsIgmpSnpgFwdGenQueries,
        eMplsIgmpSnpgFwdGrpSpecQueries,
        eMplsIgmpSnpgFwdSrcSpecQueries,
        eMplsIgmpSnpgFwdV1Reports,
        eMplsIgmpSnpgFwdV2Reports,
        eMplsIgmpSnpgFwdV3Reports,
        eMplsIgmpSnpgFwdV2Leaves,
        eMplsIgmpSnpgFwdUnknownType,
        eMplsIgmpSnpgRxBadLenPkts,
        eMplsIgmpSnpgRxBadIpChksmPkts,
        eMplsIgmpSnpgRxBadIgmpChksmPkts,
        eMplsIgmpSnpgRxBadEncodedPkts,
        eMplsIgmpSnpgRxNoRtrAlertPkts,
        eMplsIgmpSnpgRxZeroSrcAdrPkts,
        eMplsIgmpSnpgSendQueryCfgDrops,
        eMplsIgmpSnpgImportPolicyDrops,
        eMplsIgmpSnpgMaxNumGroupsDrops,
        eMplsIgmpSnpgRxWrongVersionPkts,
        eMplsIgmpSnpgMcacPolicyDrops,
        eMplsIgmpSnpgMcsFailures,
        eMplsIgmpSnpgRxLocalScopePkts,
        eMplsIgmpSnpgRxRsvdScopePkts,
        eMplsIgmpSnpgMaxNumSourcesDrops,
        eMplsIgmpSnpgMaxNumGrpSrcsDrops
    }
    STATUS      current
    DESCRIPTION
        "The group of objects that allow to view statistics for IGMP snooping
         on an evpn-mpls on Nokia 7x50 SR series release 14.0 systems."
    ::= { alxIgmpSnoopingEMplsGroups 1 }

alxEMplsIgmpSnpgNotifyV15v0Group NOTIFICATION-GROUP
    NOTIFICATIONS {
        eMplsIgmpSnpgMfibFailure
    }
    STATUS      current
    DESCRIPTION
        "The group of notifications supporting IGMP Snooping on evpn-mpls level
         on Nokia 7x50 SR release 15.0 series systems."
    ::= { alxIgmpSnoopingEMplsGroups 2 }

alxEMplsIgmpSnpgStatsV19v0Grp    OBJECT-GROUP
    OBJECTS     {
        eMplsTEPLblIgmpSnpgGrpSrcType,
        eMplsTEPLblIgmpSnpgGrpSrcUpTime,
        eMplsTEPLblIgmpSnpgGrpType,
        eMplsTEPLblIgmpSnpgGrpUpTime,
        eMplsTEPLblIgmpSnpgGrpV1ExpTime,
        eMplsTEPLblIgmpSnpgGrpV2ExpTime,
        eMplsTEPLblIgmpSnpgGrpCompatMode,
        eMplsTEPLblIgmpSnpgGrpExpiryTime,
        eMplsTEPLblIgmpSnpgGrpFilterMode,
        eMplsTEPLblIgmpSnpgGrpSrcExpTime,
        eMplsTEPLblIgmpSnpgOperState,
        eMplsTEPLblIgmpSnpgGroupCount,
        eMplsTEPLblIgmpIsSbd,
        eMplsTEPLblIgmpRxSmetRoutes,
        eMplsTEPLblIgmpDroppedSmetRoutes,
        eMplsTEPLblIgmpOrigAddrType,
        eMplsTEPLblIgmpOrigAddress
    }
    STATUS      current
    DESCRIPTION
        "The group of objects that allow to view statistics for IGMP snooping
         on an evpn-mpls on Nokia 7x50 SR series release 19.0 systems."
    ::= { alxIgmpSnoopingEMplsGroups 3 }

alxIgmpSnoopingNotifyPrefix      OBJECT IDENTIFIER ::= { alcatelNotifyPrefix 2 }

alxIgmpSnoopingSapPrefix         OBJECT IDENTIFIER ::= { alxIgmpSnoopingNotifyPrefix 1 }

alxIgmpSnpgSapNotifications      OBJECT IDENTIFIER ::= { alxIgmpSnoopingSapPrefix 0 }

sapIgmpSnpgGrpLimitExceeded      NOTIFICATION-TYPE
    OBJECTS     {
        svcId,
        sapPortId,
        sapEncapValue,
        sapIgmpSnpgCfgMaxNbrGrps,
        alxIgmpSnpgGroupAddress
    }
    STATUS      current
    DESCRIPTION
        "The sapIgmpSnpgGrpLimitExceeded notification is generated when an IGMP
         group is dropped on a given SAP because a user configurable upper
         limit given by sapIgmpSnpgCfgMaxNbrGrps is reached."
    ::= { alxIgmpSnpgSapNotifications 1 }

sapIgmpSnpgMcacPlcyDropped       NOTIFICATION-TYPE
    OBJECTS     {
        svcId,
        sapPortId,
        sapEncapValue,
        sapIgmpSnpgCfgMcacPolicyName,
        alxIgmpSnpgGroupAddress,
        alxIgmpSnpgSourceAddress,
        alxIgmpSnpgDescription
    }
    STATUS      current
    DESCRIPTION
        "The sapIgmpSnpgMcacPlcyDropped notification is generated when an IGMP
         group is dropped on a given SAP because of applying a multicast CAC
         policy given by sapIgmpSnpgCfgMcacPolicyName."
    ::= { alxIgmpSnpgSapNotifications 2 }

sapIgmpSnpgMcsFailure            NOTIFICATION-TYPE
    OBJECTS     {
        svcId,
        sapPortId,
        sapEncapValue,
        alxIgmpSnpgGroupAddress,
        alxIgmpSnpgMcsFailureReason
    }
    STATUS      current
    DESCRIPTION
        "The sapIgmpSnpgMcsFailure notification is generated when an IGMP group
         on a given SAP could not be synced to the MCS (multi-chassis
         synchronization) database."
    ::= { alxIgmpSnpgSapNotifications 3 }

sapIgmpSnpgSrcLimitExceeded      NOTIFICATION-TYPE
    OBJECTS     {
        svcId,
        sapPortId,
        sapEncapValue,
        sapIgmpSnpgCfgMaxNbrSrcs,
        alxIgmpSnpgGroupAddress,
        alxIgmpSnpgSourceAddress
    }
    STATUS      current
    DESCRIPTION
        "The sapIgmpSnpgSrcLimitExceeded notification is generated when an IGMP
         source is dropped on a given SAP because a user configurable upper
         limit given by sapIgmpSnpgCfgMaxNbrSrcs is reached."
    ::= { alxIgmpSnpgSapNotifications 4 }

sapIgmpSnpgGrpSrcLimitExceeded   NOTIFICATION-TYPE
    OBJECTS     {
        svcId,
        sapPortId,
        sapEncapValue,
        sapIgmpSnpgCfgMaxNbrGrpSrcs,
        alxIgmpSnpgGroupAddress,
        alxIgmpSnpgSourceAddress
    }
    STATUS      current
    DESCRIPTION
        "The sapIgmpSnpgGrpSrcLimitExceeded notification is generated when an
         IGMP group or source is dropped on a given SAP because a user
         configurable upper limit given by sapIgmpSnpgCfgMaxNbrGrpSrcs is
         reached."
    ::= { alxIgmpSnpgSapNotifications 5 }

alxIgmpSnoopingSdpBndPrefix      OBJECT IDENTIFIER ::= { alxIgmpSnoopingNotifyPrefix 2 }

alxIgmpSnpgSdpBndNotifications   OBJECT IDENTIFIER ::= { alxIgmpSnoopingSdpBndPrefix 0 }

sdpBndIgmpSnpgGrpLimitExceeded   NOTIFICATION-TYPE
    OBJECTS     {
        svcId,
        sdpBindId,
        sdpBndIgmpSnpgCfgMaxNbrGrps,
        alxIgmpSnpgGroupAddress
    }
    STATUS      current
    DESCRIPTION
        "The sdpBndIgmpSnpgGrpLimitExceeded notification is generated when an
         IGMP group is dropped on a given SDP bind because a user configurable
         upper limit given by sdpBndIgmpSnpgCfgMaxNbrGrps is reached."
    ::= { alxIgmpSnpgSdpBndNotifications 1 }

sdpBndIgmpSnpgMcacPlcyDropped    NOTIFICATION-TYPE
    OBJECTS     {
        svcId,
        sdpBindId,
        sdpBndIgmpSnpgCfgMcacPolicyName,
        alxIgmpSnpgGroupAddress,
        alxIgmpSnpgSourceAddress,
        alxIgmpSnpgDescription
    }
    STATUS      current
    DESCRIPTION
        "The sdpBndIgmpSnpgMcacPlcyDropped notification is generated when an
         IGMP group is dropped on a given SDP bind because of applying a
         multicast CAC policy given by sdpBndIgmpSnpgCfgMcacPolicyName."
    ::= { alxIgmpSnpgSdpBndNotifications 2 }

sdpBndIgmpSnpgSrcLimitExceeded   NOTIFICATION-TYPE
    OBJECTS     {
        svcId,
        sdpBindId,
        sdpBndIgmpSnpgCfgMaxNbrSrcs,
        alxIgmpSnpgGroupAddress,
        alxIgmpSnpgSourceAddress
    }
    STATUS      current
    DESCRIPTION
        "The sdpBndIgmpSnpgSrcLimitExceeded notification is generated when an
         IGMP source is dropped on a given SDP Bind because a user configurable
         upper limit given by sdpBndIgmpSnpgCfgMaxNbrSrcs is reached."
    ::= { alxIgmpSnpgSdpBndNotifications 3 }

sdpBndIgmpSnpgGrpSrcLimitExceed  NOTIFICATION-TYPE
    OBJECTS     {
        svcId,
        sdpBindId,
        sdpBndIgmpSnpgCfgMaxNbrGrpSrcs,
        alxIgmpSnpgGroupAddress,
        alxIgmpSnpgSourceAddress
    }
    STATUS      current
    DESCRIPTION
        "The sdpBndIgmpSnpgGrpSrcLimitExceed notification is generated when an
         IGMP group or source is dropped on a given SDP Bind because a user
         configurable upper limit given by sdpBndIgmpSnpgCfgMaxNbrGrpSrcs is
         reached."
    ::= { alxIgmpSnpgSdpBndNotifications 4 }

alxIgmpSnoopingEMplsPrefix       OBJECT IDENTIFIER ::= { alxIgmpSnoopingNotifyPrefix 3 }

alxIgmpSnpgEMplsNotifications    OBJECT IDENTIFIER ::= { alxIgmpSnoopingEMplsPrefix 0 }

eMplsIgmpSnpgMfibFailure         NOTIFICATION-TYPE
    OBJECTS     {
        svcId,
        alxIgmpSnpgEMplsTepAddressType,
        alxIgmpSnpgEMplsTepAddress,
        alxIgmpSnpgEMplsTepLabel,
        alxIgmpSnpgDescription
    }
    STATUS      current
    DESCRIPTION
        "The eMplsIgmpSnpgMfibFailure notification is generated when an
         evpn-mpls binding fails to store an entry in the MFIB table.

         To resolve this, try to increase the svcTlsMfibTableSize or remove
         another entry from the MFIB table for this service."
    ::= { alxIgmpSnpgEMplsNotifications 1 }

END

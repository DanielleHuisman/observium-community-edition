ALU-IEEE8021-CFM-MIB DEFINITIONS ::= BEGIN

IMPORTS
        MODULE-IDENTITY, OBJECT-TYPE,
        NOTIFICATION-TYPE, Integer32, Unsigned32,
        Counter64, Counter32                         FROM SNMPv2-SMI

        MODULE-COMPLIANCE, NOTIFICATION-GROUP,
        OBJECT-GROUP                                 FROM SNMPv2-CONF

        TEXTUAL-CONVENTION, TimeStamp, 
        MacAddress, RowStatus, TruthValue            FROM SNMPv2-TC

        InterfaceIndex                               FROM IF-MIB

        dot1agCfmMdIndex, dot1agCfmMaIndex,
        dot1agCfmMepIdentifier,
        dot1agCfmMepEntry                            FROM IEEE8021-CFM-MIB
        
        tmnxDot1agCfmMepEntry                        FROM TIMETRA-IEEE8021-CFM-MIB

        timetraSRMIBModules, tmnxSRObjs,
        tmnxSRConfs, tmnxSRNotifyPrefix              FROM TIMETRA-GLOBAL-MIB
        
        aluSARMIBModules, aluSARObjs, 
        aluSARConfs, aluSARNotifyPrefix              FROM ALU-SAR-GLOBAL-MIB

        SdpId                                        FROM TIMETRA-SERV-MIB

        TmnxServId                                   FROM TIMETRA-TC-MIB
        ;

aluIEEE8021CfmMIBModule MODULE-IDENTITY
        LAST-UPDATED    "0909180000Z"
        ORGANIZATION    "Nokia"
        CONTACT-INFO    
            "Nokia 7x50 Support
             Web: http://www.nokia.com/comps/pages/carrier_support.jhtml"
        DESCRIPTION
        "This document is the SNMP MIB module to manage and provision the 
        hardware components of the Nokia 7x50 device.
        
        Copyright 2003-2011 Nokia.  All rights reserved.
        Reproduction of this document is authorized on the condition that
        the foregoing copyright notice is included.

        This SNMP MIB module (Specification) embodies Nokia's
        proprietary intellectual property.  Nokia retains 
        all title and ownership in the Specification, including any 
        revisions.

        Nokia grants all interested parties a non-exclusive 
        license to use and distribute an unmodified copy of this 
        Specification in connection with management of Nokia 
        products, and without fee, provided this copyright notice and 
        license appear on all copies.

        This Specification is supplied 'as is', and Nokia 
        makes no warranty, either express or implied, as to the use, 
        operation, condition, or performance of the Specification."

--
--  Revision History
--
        REVISION        "0909180000Z"
        DESCRIPTION     "Rev 1.0                18 Sep 2009 00:00 
                         1.0 release of the ALU-IEEE8021-CFM-MIB."

        ::= { aluSARMIBModules 9 }

aluDot1agObjs                    OBJECT IDENTIFIER ::= { aluSARObjs 10 }
aluDot1agCfmMepObjs              OBJECT IDENTIFIER ::= { aluDot1agObjs 1 }
aluDot1agCfmNotificationObjs     OBJECT IDENTIFIER ::= { aluDot1agObjs 2 }

aluDot1agCfmMIBConformance    OBJECT IDENTIFIER ::= { aluSARConfs 10 }
aluDot1agCfmConformance       OBJECT IDENTIFIER ::= { aluDot1agCfmMIBConformance 1 }

aluDot1agCfmNotifyPrefix         OBJECT IDENTIFIER ::= { aluSARNotifyPrefix 6 } 
aluDot1agCfmNotification         OBJECT IDENTIFIER ::= { aluDot1agCfmNotifyPrefix 0 } 
  

TLossRatioHundrethsOfPercent ::= TEXTUAL-CONVENTION
    STATUS      current
    DESCRIPTION
        "The Frame Loss Ratio expressed in Hundreds of Percentage"
    SYNTAX      Unsigned32 (0..10000)
--
--  Configuration of Loss Test
--

aluExtDot1agCfmMepTable OBJECT-TYPE
    SYNTAX       SEQUENCE OF AluExtDot1agCfmMepEntry
    MAX-ACCESS   not-accessible
    STATUS       current
    DESCRIPTION
        "Information about the Nokia 7705 SAR extensions to  
         table tmnxDot1agCfmMepTable."
    ::= { aluDot1agCfmMepObjs 1 }

aluExtDot1agCfmMepEntry OBJECT-TYPE
    SYNTAX       AluExtDot1agCfmMepEntry
    MAX-ACCESS   not-accessible
    STATUS       current
    DESCRIPTION
        "Information about the extensions of a particular CFM Mep  
        entry tmnxDot1agCfmMepEntry."
    AUGMENTS { dot1agCfmMepEntry }
    ::= { aluExtDot1agCfmMepTable 1 }

AluExtDot1agCfmMepEntry ::= SEQUENCE
    {
        aluExtDot1agCfmMepSingleLMMacAddress            MacAddress,
        aluExtDot1agCfmMepSingleLMPriority              Unsigned32,
        aluExtDot1agCfmMepSingleLMCount                 Unsigned32,
        aluExtDot1agCfmMepSingleLMInterval              Unsigned32,
        aluExtDot1agCfmMepDualLMEnable                  TruthValue,
        aluExtDot1agCfmMepDualLMAlarmThreshold          TLossRatioHundrethsOfPercent,
        aluExtDot1agCfmMepDmrRepliesSent                Counter32,
        aluExtDot1agCfmMepLmrRepliesSent                Counter32,
        aluExtDot1agCfmMepLbrOutNoTLV                   Counter32,
        aluExtDot1agCfmMepLbrOutWithTLV                 Counter32,
        aluExtDot1agCfmMepLbByMdaNum                    Unsigned32,
        aluExtDot1agCfmMepLmAlarmClearThreshold         TLossRatioHundrethsOfPercent,
        aluExtDot1agCfmMepLbrOutFastPath                Counter32,
        aluExtDot1agCfmMepLbrOutSlowPath                Counter32
    }

aluExtDot1agCfmMepSingleLMMacAddress   OBJECT-TYPE
    SYNTAX     MacAddress
    MAX-ACCESS read-write
    STATUS     current
    DESCRIPTION
        "The value of aluExtDot1agCfmMepSingleLMMacAddress specifies the peer MAC address used
        as a target for the Single-Ended Loss Measurement.

        Setting this object will trigger a Single-ended Loss Measurement test to the specified
        MAC address.
         
        Upon completion of the test, the MacAddress will revert to it's default value, 
        indicating that another test is possible."
         
    DEFVAL { '000000000000'H }
    ::= { aluExtDot1agCfmMepEntry 1 }

aluExtDot1agCfmMepSingleLMPriority     OBJECT-TYPE
    SYNTAX     Unsigned32 (0..7)
    MAX-ACCESS read-write
    STATUS     current
    DESCRIPTION
        "The value of aluExtDot1agCfmMepSingleLMPriority specifies the priority used in
        the generated test frame for the Single-Ended Loss Measurement test."
    DEFVAL { 7 }
    ::= { aluExtDot1agCfmMepEntry 2 }

aluExtDot1agCfmMepSingleLMCount    OBJECT-TYPE
    SYNTAX     Unsigned32 (2..5)
    MAX-ACCESS read-write
    STATUS     current
    DESCRIPTION
        "The value of aluExtDot1agCfmMepSingleLMCount specifies the number of frames with ETH-LM request 
        information to be sent to the peer MAC address for this Single-Ended Loss Measurement test"
    DEFVAL { 2 }
    ::= { aluExtDot1agCfmMepEntry 3 }
   
aluExtDot1agCfmMepSingleLMInterval    OBJECT-TYPE
    SYNTAX     Unsigned32 (100 | 1000)
    UNITS      "milliseconds"
    MAX-ACCESS read-write
    STATUS     current
    DESCRIPTION
        "The value of aluExtDot1agCfmMepSingleLMInterval specifies at what intervals
         to transmit ETH-LM frames for the Single-Ended Loss Measurement test.
         Currently Nokia 7705 SAR devices only support 100 and 1000 milli-second intervals."
    DEFVAL { 1000 }
    ::= { aluExtDot1agCfmMepEntry 4 }
        

aluExtDot1agCfmMepDualLMEnable OBJECT-TYPE
    SYNTAX      TruthValue
    MAX-ACCESS  read-write
    STATUS      current
    DESCRIPTION
         "The value of aluExtDot1agCfmMepDualLMEnable specifies whether to enable or disable the
         Dual-Ended Loss Measurement Test for the MEP. "
    DEFVAL { false } 
    ::= { aluExtDot1agCfmMepEntry 5 }


aluExtDot1agCfmMepDualLMAlarmThreshold   OBJECT-TYPE
    SYNTAX     TLossRatioHundrethsOfPercent
    UNITS      "hundredth of a percent"
    MAX-ACCESS read-write
    STATUS     current
    DESCRIPTION
        "aluExtDot1agCfmMepDualLMAlarmThreshold is the configuration of
        an alarm threshold, in unit of hundredths of a percentage, for a trap
        is raised when either a result of aluDot1agCfmMepLmLossRatioLocal or 
        aluDot1agCfmMepLmLossRatioPeer of a Dual-Ended-Loss-Test for this MEP
        has exceeded this alarm threshold.
        
        aluExtDot1agCfmMepLmAlarmClearThreshold cannot be configured to be more than 
        aluExtDot1agCfmMepDualLMAlarmThreshold.
       
        Set aluExtDot1agCfmMepDualLMAlarmThreshold to 0 to indicate no trap
        to be be raised base on results calculated for Dual-Ended-Loss-Test."
    DEFVAL { 25 }
    ::= { aluExtDot1agCfmMepEntry 6 }
    
aluExtDot1agCfmMepDmrRepliesSent OBJECT-TYPE
    SYNTAX      Counter32
    MAX-ACCESS  read-only
    STATUS      current
    DESCRIPTION
         "Totoal number DMR sent to reply to valid DMM frames received."
    ::= { aluExtDot1agCfmMepEntry 7 }
    
aluExtDot1agCfmMepLmrRepliesSent OBJECT-TYPE
    SYNTAX      Counter32
    MAX-ACCESS  read-only
    STATUS      current
    DESCRIPTION
         "Totoal number LMR sent to reply to valid LMM frames received."
    ::= { aluExtDot1agCfmMepEntry 8 }
    
aluExtDot1agCfmMepLbrOutNoTLV OBJECT-TYPE
    SYNTAX      Counter32
    MAX-ACCESS  read-only
    STATUS      obsolete
    DESCRIPTION
       "Total number of Loopback Replies transmitted without TLV."
    ::= { aluExtDot1agCfmMepEntry 9}
    
aluExtDot1agCfmMepLbrOutWithTLV OBJECT-TYPE
    SYNTAX      Counter32
    MAX-ACCESS  read-only
    STATUS      obsolete
    DESCRIPTION
       "Total number of Loopback Replies transmitted with TLV."
    ::= { aluExtDot1agCfmMepEntry 10 }
    
aluExtDot1agCfmMepLbByMdaNum  OBJECT-TYPE
    SYNTAX      Unsigned32
    MAX-ACCESS  read-only
    STATUS      current
    DESCRIPTION
        "aluExtDot1agCfmMepLbByMdaNum indicates the MDA that handles the incoming LBM's with no TLV's.
        aluExtDot1agCfmMepLbByMdaNum is set to 0 when there isn't any MDA's programmed to respond to incoming LBM's"
    ::= { aluExtDot1agCfmMepEntry 11}

aluExtDot1agCfmMepLmAlarmClearThreshold   OBJECT-TYPE
    SYNTAX     TLossRatioHundrethsOfPercent
    UNITS      "hundredth of a percent"
    MAX-ACCESS read-write
    STATUS     current
    DESCRIPTION
        "After aluDot1agCfmMepLmAlarm trap is sent, if aluExtDot1agCfmMepLmAlarmClearThreshold
        is non-zero, and both aluDot1agCfmMepLmLossRatioLocal and aluDot1agCfmMepLmLossRatioPeer 
        are dropped to or below the configured aluExtDot1agCfmMepLmAlarmClearThreshold,
        the aluDot1agCfmMepLmAlarmClear trap is sent.
        
        aluExtDot1agCfmMepLmAlarmClearThreshold cannot be configured to be more than 
        aluExtDot1agCfmMepDualLMAlarmThreshold."
    DEFVAL { 0 }
    ::= { aluExtDot1agCfmMepEntry 12 }

aluExtDot1agCfmMepLbrOutFastPath OBJECT-TYPE
    SYNTAX      Counter32
    MAX-ACCESS  read-only
    STATUS      current
    DESCRIPTION
       "Number of Ethernet Loopback Replies transmitted by hardware in response to
        valid Ethernet Loopback frames that either do not have any TLV's or have only
        one data TLV."
    ::= { aluExtDot1agCfmMepEntry 13}
    
aluExtDot1agCfmMepLbrOutSlowPath OBJECT-TYPE
    SYNTAX      Counter32
    MAX-ACCESS  read-only
    STATUS      current
    DESCRIPTION
       "Total number of Ethernet Loopback Replies transmitted by software in response to
        valid Ethernet Loopback frames that are not replied by harware."

    ::= { aluExtDot1agCfmMepEntry 14 }

--
-- Dual-ended/Single-Ended Frame Loss Result Table
--
aluDot1agCfmMepLossRsltTable   OBJECT-TYPE
    SYNTAX     SEQUENCE OF AluDot1agCfmMepLossRsltEntry
    MAX-ACCESS not-accessible
    STATUS     current
    DESCRIPTION
       "The aluDot1agCfmMepLossRsltTable indicates the results of
        all the Single-Ended/Dual-Ended Loss Tests, from one specific MEP to a
        specific destination MAC address.
       
        This table is not persistent over reboots of the chassis."
        
    ::= { aluDot1agCfmMepObjs 2 }

aluDot1agCfmMepLossRsltEntry   OBJECT-TYPE
    SYNTAX     AluDot1agCfmMepLossRsltEntry
    MAX-ACCESS not-accessible
    STATUS     current
    DESCRIPTION
       "An entry in aluDot1agCfmMepLossRsltTable represents the latest result of a Y1731 Loss Measurement, 
       if the test was started.  Each row stores the result for a either Single-Ended or Dual-Ended Loss test indicated
       by aluDot1agCfmMepLmType, the originating MEP of dot1agCfmMdIndex, dot1agCfmMaIndex, dot1agCfmMepIdentifier, 
       toward destination MAC address aluDot1agCfmMepLmMacAddr."
    INDEX { 
              dot1agCfmMdIndex,
              dot1agCfmMaIndex,
              dot1agCfmMepIdentifier,
              aluDot1agCfmMepLmMacAddr,
              aluDot1agCfmMepLmType
          }
    ::= { aluDot1agCfmMepLossRsltTable 1 }      

AluDot1agCfmMepLossRsltEntry   ::= SEQUENCE {
    aluDot1agCfmMepLmMacAddr           MacAddress,
    aluDot1agCfmMepLmType              INTEGER,
    aluDot1agCfmMepLmEnableDuration    Unsigned32,
    aluDot1agCfmMepLmChangeCount       Unsigned32,
    aluDot1agCfmMepLmLatestChangeTime  TimeStamp,
    aluDot1agCfmMepLmFramesRxLocal     Counter64,
    aluDot1agCfmMepLmFramesRxPeer      Counter64,  
    aluDot1agCfmMepLmFramesTxLocal     Counter64,
    aluDot1agCfmMepLmFramesTxPeer      Counter64,
    aluDot1agCfmMepLmFramesLossLocal   Counter64,
    aluDot1agCfmMepLmFramesLossPeer    Counter64, 
    aluDot1agCfmMepLmLossRatioLocal    TLossRatioHundrethsOfPercent, 
    aluDot1agCfmMepLmLossRatioPeer     TLossRatioHundrethsOfPercent,
    aluDot1agCfmMepLmPrevTxLocal       Counter32,
    aluDot1agCfmMepLmPrevRxLocal       Counter32,
    aluDot1agCfmMepLmPrevTxPeer        Counter32,
    aluDot1agCfmMepLmPrevRxPeer        Counter32,
    aluDot1agCfmMepLmCurrTxLocal       Counter32,
    aluDot1agCfmMepLmCurrRxLocal       Counter32,
    aluDot1agCfmMepLmCurrTxPeer        Counter32,
    aluDot1agCfmMepLmCurrRxPeer        Counter32
}

aluDot1agCfmMepLmMacAddr  OBJECT-TYPE
    SYNTAX     MacAddress
    MAX-ACCESS not-accessible
    STATUS     current
    DESCRIPTION
        "The value of aluDot1agCfmMepLmMacAddr indicates the destination MAC address of the the test."
    ::= { aluDot1agCfmMepLossRsltEntry 1 }

aluDot1agCfmMepLmType    OBJECT-TYPE
    SYNTAX     INTEGER {
                   singleEndedLm (1),
                   dualEndedLm   (2)
               }
    MAX-ACCESS not-accessible
    STATUS     current
    DESCRIPTION
        "The value of aluDot1agCfmMepLmType indicates the type of the Y1731 Loss Measurement test,
        either Single-ended or Dual-Ended."
    ::= { aluDot1agCfmMepLossRsltEntry 2 }

aluDot1agCfmMepLmEnableDuration  OBJECT-TYPE
    SYNTAX     Unsigned32
    UNITS      "seconds"
    MAX-ACCESS read-only
    STATUS     current
    DESCRIPTION
        "The value of aluDot1agCfmMepLmEnableDuration is the accumulation of time, 
        expressed in seconds, during which the loss-test is enabled.  
         
        For Single-Ended loss-tests, the value of aluDot1agCfmMepLmEnableDuration is counted 
        from when it's initiated until when it's ended.  It is not accumulative from one 
        single-ended test to the next.  
         
        However for Dual-Ended loss-test, this is the accumulated time that the Dual-Tested
        is enabled for this MEP, i.e. accumulated time for aluExtDot1agCfmMepDualLMEnable
        being set to TRUE, starting at the creation time of this row."
    ::= { aluDot1agCfmMepLossRsltEntry 3 }
    
aluDot1agCfmMepLmChangeCount OBJECT-TYPE
    SYNTAX      Unsigned32
    MAX-ACCESS  read-only
    STATUS      current
    DESCRIPTION
        "The Value of aluDot1agCfmMepLmChangeCount is the number of frames, either the received
        ETH-LMR or CCM frames, that were used for the calculation of loss measurement results 
        of this AluDot1agCfmMepLossRsltEntry row for this MEP."
    ::= { aluDot1agCfmMepLossRsltEntry 4 }
    
aluDot1agCfmMepLmLatestChangeTime OBJECT-TYPE
    SYNTAX      TimeStamp
    MAX-ACCESS  read-only
    STATUS      current
    DESCRIPTION
        "aluDot1agCfmMepLmLatestChangeTime contains the sysUpTime at the most recently
        writable variable in the AluDot1agCfmMepLossRsltEntry row was modified for this MEP."
    ::= { aluDot1agCfmMepLossRsltEntry 5 }

aluDot1agCfmMepLmFramesRxLocal   OBJECT-TYPE
    SYNTAX     Counter64
    MAX-ACCESS read-only
    STATUS     current
    DESCRIPTION
        "The Value of aluDot1agCfmMepLmFramesRxLocal is the accumulated number of frames received
        at the local service endpoint of this MEP, and within the loss test duration of
        aluDot1agCfmMepLmEnableDuration. "
    ::= { aluDot1agCfmMepLossRsltEntry 6 }
          
aluDot1agCfmMepLmFramesRxPeer   OBJECT-TYPE
    SYNTAX     Counter64
    MAX-ACCESS read-only
    STATUS     current
    DESCRIPTION
        "The Value of aluDot1agCfmMepLmFramesRxPeer is the accumulated number of frames received
        at the far-end service endpoint associated with aluDot1agCfmMepLmMacAddr, and within the loss
        test duration of aluDot1agCfmMepLmEnableDuration. "
    ::= { aluDot1agCfmMepLossRsltEntry 7 }

aluDot1agCfmMepLmFramesTxLocal   OBJECT-TYPE
    SYNTAX     Counter64
    MAX-ACCESS read-only
    STATUS     current
    DESCRIPTION
        "The Value of aluDot1agCfmMepLmFramesTxLocal is the accumulated number of frames transmitted
        at the local service endpoint of this MEP, and within the loss test duration of
        aluDot1agCfmMepLmEnableDuration. "
    ::= { aluDot1agCfmMepLossRsltEntry 8 }
          
aluDot1agCfmMepLmFramesTxPeer   OBJECT-TYPE
    SYNTAX     Counter64
    MAX-ACCESS read-only
    STATUS     current
    DESCRIPTION
        "The Value of aluDot1agCfmMepLmFramesTxPeer is the accumulated number of frames transmitted
        at the far-end service endpoint associated with aluDot1agCfmMepLmMacAddr, and within the loss
        test duration of aluDot1agCfmMepLmEnableDuration. "
    ::= { aluDot1agCfmMepLossRsltEntry 9 }
    
aluDot1agCfmMepLmFramesLossLocal   OBJECT-TYPE
    SYNTAX     Counter64
    MAX-ACCESS read-only
    STATUS     current
    DESCRIPTION
        "The Value of aluDot1agCfmMepLmFramesLossLocal is the accumulated number of loss frames
        at the local service endpoint of this MEP, and within the loss test duration of
        aluDot1agCfmMepLmEnableDuration. "
    ::= { aluDot1agCfmMepLossRsltEntry 10 }
          
aluDot1agCfmMepLmFramesLossPeer   OBJECT-TYPE
    SYNTAX     Counter64
    MAX-ACCESS read-only
    STATUS     current
    DESCRIPTION
        "The Value of aluDot1agCfmMepLmFramesLossPeer is the accumulated number of loss frames
        at the far-end service endpoint associated with aluDot1agCfmMepLmMacAddr, and within the loss
        test duration of aluDot1agCfmMepLmEnableDuration. "
    ::= { aluDot1agCfmMepLossRsltEntry 11 }

aluDot1agCfmMepLmLossRatioLocal   OBJECT-TYPE
    SYNTAX     TLossRatioHundrethsOfPercent
    UNITS      "hundredth of a percent"
    MAX-ACCESS read-only
    STATUS     current
    DESCRIPTION
        "The Value of aluDot1agCfmMepLmLossRatioLocal is the accumulated Loss Ratio, at the local
        service endpoint of this MEP, and within the loss test duration of aluDot1agCfmMepLmEnableDuration.
        aluDot1agCfmMepLmLossRatioLocal is expressed in hundredth of a percent accuracy.  
        It is calculated as followed:  
        (aluDot1agCfmMepLmFramesLossLocal * 10000) / aluDot1agCfmMepLmFramesTxPeer."

    ::= { aluDot1agCfmMepLossRsltEntry 12 }
          
aluDot1agCfmMepLmLossRatioPeer   OBJECT-TYPE
    SYNTAX     TLossRatioHundrethsOfPercent
    UNITS      "hundredth of a percent"
    MAX-ACCESS read-only
    STATUS     current
    DESCRIPTION
        "The Value of aluDot1agCfmMepLmLossRatioPeer is the accumulated Loss Ratio, at 
        the far-end service endpoint associated with aluDot1agCfmMepLmMacAddr, and within 
        the loss test duration of aluDot1agCfmMepLmEnableDuration.
        
        aluDot1agCfmMepLmLossRatioPeer is expressed in hundredth of a percent accuracy.  
        It is calculated as followed:
        (aluDot1agCfmMepLmFramesLossPeer * 10000) / aluDot1agCfmMepLmFramesTxLocal."
    ::= { aluDot1agCfmMepLossRsltEntry 13 }

aluDot1agCfmMepLmPrevTxLocal   OBJECT-TYPE
    SYNTAX     Counter32
    MAX-ACCESS read-only
    STATUS     current
    DESCRIPTION
        "If aluDot1agCfmMepLmType is singleEndedLm, aluDot1agCfmMepLmPrevTxLocal is the value of TxFCf 
        in the second latest ETH-LMR frame this local MEP has received.
        
        If aluDot1agCfmMepLmType is dualEndedLm, then aluDot1agCfmMepLmPrevTxLocal is the value of TxFCb
        in the second latest ETH-CCM frame this local MEP has received."
    ::= { aluDot1agCfmMepLossRsltEntry 14 }
    
aluDot1agCfmMepLmPrevRxLocal   OBJECT-TYPE
    SYNTAX     Counter32
    MAX-ACCESS read-only
    STATUS     current
    DESCRIPTION
        "If aluDot1agCfmMepLmType is singleEndedLm, aluDot1agCfmMepLmPrevRxLocal is the counter of frames 
        received at the service end point of this local MEP at the time the second latest ETH-LMR frame is
        received and being processed.
        
        If aluDot1agCfmMepLmType is dualEndedLm, aluDot1agCfmMepLmPrevRxLocal is the counter of frames 
        received at the service end point of this local MEP at the time the second latest ETH-CCM frame is
        received and being processed."
        
    ::= { aluDot1agCfmMepLossRsltEntry 15 }

aluDot1agCfmMepLmPrevTxPeer   OBJECT-TYPE
    SYNTAX     Counter32
    MAX-ACCESS read-only
    STATUS     current
    DESCRIPTION
        "If aluDot1agCfmMepLmType is singleEndedLm, aluDot1agCfmMepLmPrevTxPeer is the value of TxFCb 
        in the second latest ETH-LMR frame this local MEP has received.
        
        If aluDot1agCfmMepLmType is dualEndedLm, then aluDot1agCfmMepLmPrevTxPeer is the value of TxFCf
        in the second latest ETH-CCM frame this local MEP has received."
    ::= { aluDot1agCfmMepLossRsltEntry 16 }
    
aluDot1agCfmMepLmPrevRxPeer   OBJECT-TYPE
    SYNTAX     Counter32
    MAX-ACCESS read-only
    STATUS     current
    DESCRIPTION
        "If aluDot1agCfmMepLmType is singleEndedLm, aluDot1agCfmMepLmPrevRxPeer is the value of 'RxFCf' 
        in the second latest ETH-LMR frame this local MEP has received.
        
        If aluDot1agCfmMepLmType is dualEndedLm, then aluDot1agCfmMepLmPrevRxPeer is the value of 'RxFCb'
        in the second latest ETH-CCM frame this local MEP has received."
    ::= { aluDot1agCfmMepLossRsltEntry 17 }

aluDot1agCfmMepLmCurrTxLocal   OBJECT-TYPE
    SYNTAX     Counter32
    MAX-ACCESS read-only
    STATUS     current
    DESCRIPTION
        "If aluDot1agCfmMepLmType is singleEndedLm, aluDot1agCfmMepLmCurrTxLocal is the value of 'TxFCf' 
        in the latest ETH-LMR frame this local MEP has received.
        
        If aluDot1agCfmMepLmType is dualEndedLm, then aluDot1agCfmMepLmCurrTxLocal is the value of 'TxFCb'
        in the latest ETH-CCM frame this local MEP has received."
    ::= { aluDot1agCfmMepLossRsltEntry 18 }
    
aluDot1agCfmMepLmCurrRxLocal   OBJECT-TYPE
    SYNTAX     Counter32
    MAX-ACCESS read-only
    STATUS     current
    DESCRIPTION
        "If aluDot1agCfmMepLmType is singleEndedLm, aluDot1agCfmMepLmCurrRxLocal is the counter of frames 
        received at the service end point of this local MEP at the time the latest ETH-LMR frame is
        received and being processed.
        
        If aluDot1agCfmMepLmType is dualEndedLm, aluDot1agCfmMepLmCurrRxLocal is the counter of frames 
        received at the service end point of this local MEP at the time the latest ETH-CCM frame is
        received and being processed."
    ::= { aluDot1agCfmMepLossRsltEntry 19 }

aluDot1agCfmMepLmCurrTxPeer   OBJECT-TYPE
    SYNTAX     Counter32
    MAX-ACCESS read-only
    STATUS     current
    DESCRIPTION
         "If aluDot1agCfmMepLmType is singleEndedLm, aluDot1agCfmMepLmCurrTxPeer is the value of 'TxFCb' 
        in the lastest ETH-LMR frame this local MEP has received.
        
        If aluDot1agCfmMepLmType is dualEndedLm, then aluDot1agCfmMepLmCurrTxPeer is the value of 'TxFCf'
        in the latest ETH-CCM frame this local MEP has received."
    ::= { aluDot1agCfmMepLossRsltEntry 20 }
    
aluDot1agCfmMepLmCurrRxPeer   OBJECT-TYPE
    SYNTAX     Counter32
    MAX-ACCESS read-only
    STATUS     current
    DESCRIPTION
        "If aluDot1agCfmMepLmType is singleEndedLm, aluDot1agCfmMepLmCurrRxPeer is the value of 'RxFCf' 
        in the latest ETH-LMR frame this local MEP has received.
        
        If aluDot1agCfmMepLmType is dualEndedLm, then aluDot1agCfmMepLmCurrRxPeer is the value of 'RxFCb'
        in the latest ETH-CCM frame this local MEP has received."
    ::= { aluDot1agCfmMepLossRsltEntry 21 }


--
-- Notifications
--

aluDot1agCfmMepLmComplete NOTIFICATION-TYPE
    OBJECTS { 
                aluDot1agCfmMepLmLossRatioLocal, 
                aluDot1agCfmMepLmLossRatioPeer    
            }
    STATUS     current
    DESCRIPTION        
        "The aluDot1agCfmMepLmComplete notification indicates the frame 
        loss ratio result for the local MEP and the Far-end MEP after a single-ended test
        is completed.  
        
        The test is considered successfully completed when the last expected Reply frame (LMR)
        was received and all of its test result info is calculated and saved in 
        aluDot1agCfmMepLossRsltEntry within the 10 seconds since the start of
        the test.  Otherwise, at the end of the 10 second timeout period, if the test
        cannot be completed successfully then the test is automatically terminated, and
        the notification is still sent."

    ::= { aluDot1agCfmNotification 1 }

aluDot1agCfmMepLmAlarm NOTIFICATION-TYPE
    OBJECTS { 
                aluDot1agCfmMepLmLossRatioLocal, 
                aluDot1agCfmMepLmLossRatioPeer 
            }
    STATUS     current
    DESCRIPTION
        "Generated for a dual-ended loss test when the loss ratio of either local 
        and/or peer MEP is above the configured aluExtDot1agCfmMepDualLMAlarmThreshold."

    ::= { aluDot1agCfmNotification 2 }

aluDot1agCfmMepLmAlarmClear NOTIFICATION-TYPE
    OBJECTS { 
                aluDot1agCfmMepLmLossRatioLocal, 
                aluDot1agCfmMepLmLossRatioPeer 
            }
    STATUS     current
    DESCRIPTION
        "aluDot1agCfmMepLmAlarmClear trap notification is generated when the alarm condition for a
        dual-ended loss test is cleared, i.e. when either one of the following conditions is met:
        1)  If aluExtDot1agCfmMepLmAlarmClearThreshold is 0, both local and peer loss ratios
        are no longer above aluExtDot1agCfmMepDualLMAlarmThreshold.
        2)  If aluExtDot1agCfmMepLmAlarmClearThreshold > 0, both local and peer loss ratios 
        are no longer above aluExtDot1agCfmMepLmAlarmClearThreshold."

    ::= { aluDot1agCfmNotification 3 }

--%%%%%%%%%%%%%%%%%%%%%%%%%%%%%%%%%%%%%%%%%%%%%%%%%%%%%%%%%%%%%%%%%%%%%
--
--      The compliance specifications.
--

aluDot1agCfmCompliances     OBJECT IDENTIFIER ::= { aluDot1agCfmConformance 1 }
aluDot1agCfmGroups          OBJECT IDENTIFIER ::= { aluDot1agCfmConformance 2 }

aluDot1agComp7705           OBJECT IDENTIFIER ::= { aluDot1agCfmCompliances 1 }

aluDot1agComp7705V1v0   MODULE-COMPLIANCE
    STATUS  obsolete
    DESCRIPTION
            "The compliance statement for revision 1.0 of ALU-IEEE801-CFM-MIB."
    MODULE  -- this module
        MANDATORY-GROUPS {
            aluY1731CfmNotificationGroup,
            aluDot1agCfmMepGroup
        }
    ::= { aluDot1agComp7705 1 }

aluDot1agComp7705V5v0   MODULE-COMPLIANCE
    STATUS  current
    DESCRIPTION
            "The compliance statement for revision 5.0 of ALU-IEEE801-CFM-MIB."
    MODULE  -- this module
        MANDATORY-GROUPS {
            aluY1731CfmNotificationGroup,
            aluDot1agCfmMepGroupV5v0
        }
    ::= { aluDot1agComp7705 2 }

-- units of conformance
    
aluY1731CfmNotificationGroup NOTIFICATION-GROUP 
    NOTIFICATIONS { 
        aluDot1agCfmMepLmComplete,
        aluDot1agCfmMepLmAlarm,
        aluDot1agCfmMepLmAlarmClear
    }
    STATUS     current
    DESCRIPTION
       "The group of objects for management of Y.1731 Notifications applicable
        to implementing CFM on the Nokia 7705."
    ::= {aluDot1agCfmGroups 1 }

aluDot1agCfmMepGroup OBJECT-GROUP 
    OBJECTS {
          aluExtDot1agCfmMepSingleLMMacAddress,
          aluExtDot1agCfmMepSingleLMPriority,
          aluExtDot1agCfmMepSingleLMCount,
          aluExtDot1agCfmMepSingleLMInterval,
          aluExtDot1agCfmMepDualLMEnable,
          aluExtDot1agCfmMepDualLMAlarmThreshold,
          aluExtDot1agCfmMepDmrRepliesSent,
          aluExtDot1agCfmMepLmrRepliesSent,
          aluDot1agCfmMepLmEnableDuration,
          aluDot1agCfmMepLmChangeCount,
          aluDot1agCfmMepLmLatestChangeTime,
          aluDot1agCfmMepLmFramesRxLocal,
          aluDot1agCfmMepLmFramesRxPeer,
          aluDot1agCfmMepLmFramesTxLocal,
          aluDot1agCfmMepLmFramesTxPeer,
          aluDot1agCfmMepLmFramesLossLocal,
          aluDot1agCfmMepLmFramesLossPeer,
          aluDot1agCfmMepLmLossRatioLocal,
          aluDot1agCfmMepLmLossRatioPeer,
          aluDot1agCfmMepLmPrevTxLocal,
          aluDot1agCfmMepLmPrevRxLocal,
          aluDot1agCfmMepLmPrevTxPeer,
          aluDot1agCfmMepLmPrevRxPeer,
          aluDot1agCfmMepLmCurrTxLocal,
          aluDot1agCfmMepLmCurrRxLocal,
          aluDot1agCfmMepLmCurrTxPeer,
          aluDot1agCfmMepLmCurrRxPeer,
          aluExtDot1agCfmMepLbrOutNoTLV,
          aluExtDot1agCfmMepLbrOutWithTLV,
          aluExtDot1agCfmMepLbByMdaNum,
          aluExtDot1agCfmMepLmAlarmClearThreshold
    }
    STATUS     obsolete
    DESCRIPTION
       "The group of objects for management dot1ag and Y.1731 tables applicable
        to implementing MEPs on the Nokia 7705."
    ::= { aluDot1agCfmGroups 2 }

aluDot1agCfmMepGroupV5v0 OBJECT-GROUP 
    OBJECTS {
          aluExtDot1agCfmMepSingleLMMacAddress,
          aluExtDot1agCfmMepSingleLMPriority,
          aluExtDot1agCfmMepSingleLMCount,
          aluExtDot1agCfmMepSingleLMInterval,
          aluExtDot1agCfmMepDualLMEnable,
          aluExtDot1agCfmMepDualLMAlarmThreshold,
          aluExtDot1agCfmMepDmrRepliesSent,
          aluExtDot1agCfmMepLmrRepliesSent,
          aluDot1agCfmMepLmEnableDuration,
          aluDot1agCfmMepLmChangeCount,
          aluDot1agCfmMepLmLatestChangeTime,
          aluDot1agCfmMepLmFramesRxLocal,
          aluDot1agCfmMepLmFramesRxPeer,
          aluDot1agCfmMepLmFramesTxLocal,
          aluDot1agCfmMepLmFramesTxPeer,
          aluDot1agCfmMepLmFramesLossLocal,
          aluDot1agCfmMepLmFramesLossPeer,
          aluDot1agCfmMepLmLossRatioLocal,
          aluDot1agCfmMepLmLossRatioPeer,
          aluDot1agCfmMepLmPrevTxLocal,
          aluDot1agCfmMepLmPrevRxLocal,
          aluDot1agCfmMepLmPrevTxPeer,
          aluDot1agCfmMepLmPrevRxPeer,
          aluDot1agCfmMepLmCurrTxLocal,
          aluDot1agCfmMepLmCurrRxLocal,
          aluDot1agCfmMepLmCurrTxPeer,
          aluDot1agCfmMepLmCurrRxPeer,
          aluExtDot1agCfmMepLbrOutFastPath,
          aluExtDot1agCfmMepLbrOutSlowPath,
          aluExtDot1agCfmMepLbByMdaNum,
          aluExtDot1agCfmMepLmAlarmClearThreshold
    }
    STATUS     current
    DESCRIPTION
       "The group of objects for management dot1ag and Y.1731 tables applicable
        to implementing MEPs for revision 5.0 on Nokia 7705 series
           systems."
    ::= { aluDot1agCfmGroups 3 }
    
aluDot1agCfmMepObsoletedGroup    OBJECT-GROUP
	OBJECTS {  
		aluExtDot1agCfmMepLbrOutNoTLV,
    	aluExtDot1agCfmMepLbrOutWithTLV
    }
    STATUS      current
    DESCRIPTION
        "The group of objects obsoleted in the 7705 SAR series 5.0 release"
    ::= { aluDot1agCfmGroups 4 }

END

TIMETRA-GSMP-MIB DEFINITIONS ::= BEGIN

IMPORTS
    InetAddress, InetAddressType
                                                         FROM INET-ADDRESS-MIB
    MODULE-COMPLIANCE, NOTIFICATION-GROUP,
    OBJECT-GROUP
                                                         FROM SNMPv2-CONF
    Counter32, Integer32, MODULE-IDENTITY,
    NOTIFICATION-TYPE, OBJECT-TYPE,
    Unsigned32
                                                         FROM SNMPv2-SMI
    DisplayString, RowStatus, TimeStamp,
    TruthValue
                                                         FROM SNMPv2-TC
    timetraSRMIBModules, tmnxSRConfs,
    tmnxSRNotifyPrefix, tmnxSRObjs
                                                         FROM TIMETRA-GLOBAL-MIB
    sapEncapValue, sapPortId
                                                         FROM TIMETRA-SAP-MIB
    custId, custMultSvcSiteName, svcId
                                                         FROM TIMETRA-SERV-MIB
    tmnxSubInfoSubIdent, tmnxSubProfileEntry
                                                         FROM TIMETRA-SUBSCRIBER-MGMT-MIB
    TDSCPNameOrEmpty, TEgrRateModType,
    TItemDescription, TNamedItem,
    TNamedItemOrEmpty,
    TPIRAggRateLimitOverride,
    TPIRRateOverride, TPrecValueOrNone,
    TRemarkType, TmnxAdminState,
    TmnxAncpString, TmnxCustId,
    TmnxEncapVal, TmnxPortID, TmnxServId
                                                         FROM TIMETRA-TC-MIB
    ;

tmnxGsmpMIBModule                MODULE-IDENTITY
    LAST-UPDATED "201501010000Z"
    ORGANIZATION "Nokia"
    CONTACT-INFO
        "Nokia SROS Support
         Web: http://www.nokia.com"
    DESCRIPTION
        "This document contains the SNMP MIB module for handling GSMP (General
         Switch Management Protocol) for the Nokia SROS device.

         Copyright 2006-2018 Nokia. All rights reserved. Reproduction of this
         document is authorized on the condition that the foregoing copyright
         notice is included.

         This SNMP MIB module (Specification) embodies Nokia's proprietary
         intellectual property. Nokia retains all title and ownership in the
         Specification, including any revisions.

         Nokia grants all interested parties a non-exclusive license to use and
         distribute an unmodified copy of this Specification in connection with
         management of Nokia products, and without fee, provided this copyright
         notice and license appear on all copies.

         This Specification is supplied 'as is', and Nokia makes no warranty,
         either express or implied, as to the use, operation, condition, or
         performance of the Specification."

    REVISION    "201501010000Z"
    DESCRIPTION
        "Rev 13.0               01 Jan 2015 00:00
         13.0 release of the TIMETRA-GSMP-MIB."

    REVISION    "201206010000Z"
    DESCRIPTION
        "Rev 11.0               01 Jun 2012 00:00
         11.0 release of the TIMETRA-GSMP-MIB."

    REVISION    "200902280000Z"
    DESCRIPTION
        "Rev 7.0                28 Feb 2009 00:00
         7.0 release of the TIMETRA-GSMP-MIB."

    REVISION    "200607100000Z"
    DESCRIPTION
        "Rev 1.0                10 Jul 2006 00:00
         1.0 release of the TIMETRA-GSMP-MIB."

    ::= { timetraSRMIBModules 39 }

tmnxGsmpObjects                  OBJECT IDENTIFIER ::= { tmnxSRObjs 39 }

tmnxGsmpNotifyObjects            OBJECT IDENTIFIER ::= { tmnxGsmpObjects 1 }

tmnxNotifAncpString              OBJECT-TYPE
    SYNTAX      DisplayString (SIZE (1..64))
    MAX-ACCESS  accessible-for-notify
    STATUS      current
    DESCRIPTION
        "The value of tmnxNotifAncpString indicates the ASCII representation of
         the DSLAM circuit-id name for which this notification is generated."
    ::= { tmnxGsmpNotifyObjects 1 }

tmnxNotifAncpPolicyName          OBJECT-TYPE
    SYNTAX      TNamedItem
    MAX-ACCESS  accessible-for-notify
    STATUS      current
    DESCRIPTION
        "The value of tmnxNotifAncpPolicyName specifies the name of the ANCP
         policy defined in this row."
    ::= { tmnxGsmpNotifyObjects 2 }

tmnxNotifAncpPlcyActualRate      OBJECT-TYPE
    SYNTAX      Unsigned32
    UNITS       "kilobps"
    MAX-ACCESS  accessible-for-notify
    STATUS      current
    DESCRIPTION
        "The value of tmnxNotifAncpPlcyActualRate specifies the current rate"
    ::= { tmnxGsmpNotifyObjects 3 }

tmnxAncpRejectReason             OBJECT-TYPE
    SYNTAX      DisplayString
    MAX-ACCESS  accessible-for-notify
    STATUS      current
    DESCRIPTION
        "The value of tmnxAncpRejectReason indicates the reason why the ANCP
         session, or ANCP-string is being rejected by the system."
    ::= { tmnxGsmpNotifyObjects 4 }

tmnxGsmpConfigTableLastChange    OBJECT-TYPE
    SYNTAX      TimeStamp
    MAX-ACCESS  read-only
    STATUS      current
    DESCRIPTION
        "The value of tmnxGsmpConfigTableLastChange indicates the sysUpTime at
         the time of the last modification of an entry in the
         tmnxGsmpConfigTable.

         If no changes were made to the table since the last re-initialization
         of the local network management subsystem, then this object contains a
         zero value."
    ::= { tmnxGsmpObjects 2 }

tmnxGsmpConfigTable              OBJECT-TYPE
    SYNTAX      SEQUENCE OF TmnxGsmpConfigEntry
    MAX-ACCESS  not-accessible
    STATUS      current
    DESCRIPTION
        "The table tmnxGsmpConfigTable contains a row for each service defined
         in the system on which GSMP can be enabled."
    ::= { tmnxGsmpObjects 3 }

tmnxGsmpConfigEntry              OBJECT-TYPE
    SYNTAX      TmnxGsmpConfigEntry
    MAX-ACCESS  not-accessible
    STATUS      current
    DESCRIPTION
        "Each row contains objects that allow GSMP to be configured in the
         scope of a service. Rows cannot be created or deleted by the user.

         A row will be created by the system for each service in the system on
         which GSMP can be enabled."
    INDEX       { svcId }
    ::= { tmnxGsmpConfigTable 1 }

TmnxGsmpConfigEntry              ::= SEQUENCE
{
    tmnxGsmpCfgLastChange            TimeStamp,
    tmnxGsmpCfgAdminState            TmnxAdminState
}

tmnxGsmpCfgLastChange            OBJECT-TYPE
    SYNTAX      TimeStamp
    MAX-ACCESS  read-only
    STATUS      current
    DESCRIPTION
        "The value of tmnxGsmpCfgLastChange indicates the sysUpTime at the time
         of the last modification of this entry.

         If no changes were made to the entry since the last re-initialization
         of the local network management subsystem, then this object contains a
         zero value."
    ::= { tmnxGsmpConfigEntry 1 }

tmnxGsmpCfgAdminState            OBJECT-TYPE
    SYNTAX      TmnxAdminState
    MAX-ACCESS  read-write
    STATUS      current
    DESCRIPTION
        "The value of tmnxGsmpCfgAdminState specifies the administrative state
         of the GSMP protocol in this service."
    DEFVAL      { outOfService }
    ::= { tmnxGsmpConfigEntry 2 }

tmnxGsmpGroupConfigTableLastChange OBJECT-TYPE
    SYNTAX      TimeStamp
    MAX-ACCESS  read-only
    STATUS      current
    DESCRIPTION
        "The value of tmnxGsmpGroupConfigTableLastChange indicates the
         sysUpTime at the time of the last modification of an entry in the
         tmnxGsmpGroupConfigTable.

         If no changes were made to the table since the last re-initialization
         of the local network management subsystem, then this object contains a
         zero value."
    ::= { tmnxGsmpObjects 4 }

tmnxGsmpGroupConfigTable         OBJECT-TYPE
    SYNTAX      SEQUENCE OF TmnxGsmpGroupConfigEntry
    MAX-ACCESS  not-accessible
    STATUS      current
    DESCRIPTION
        "The table tmnxGsmpGroupConfigTable contains a row for each GSMP group
         defined in a service on which GSMP can be enabled."
    ::= { tmnxGsmpObjects 5 }

tmnxGsmpGroupConfigEntry         OBJECT-TYPE
    SYNTAX      TmnxGsmpGroupConfigEntry
    MAX-ACCESS  not-accessible
    STATUS      current
    DESCRIPTION
        "Each row contains objects that allow configuration of GSMP groups in
         the scope of a service.

         A GSMP group defines a set of GSMP neighbors which have the same
         properties.

         Rows can be created, modified, and deleted by the operator. A row can
         only be deleted if the tmnxGsmpGrpCfgAdminState of that row is set to
         disabled(2)."
    INDEX       {
        svcId,
        tmnxGsmpGroupName
    }
    ::= { tmnxGsmpGroupConfigTable 1 }

TmnxGsmpGroupConfigEntry         ::= SEQUENCE
{
    tmnxGsmpGroupName                TNamedItem,
    tmnxGsmpGrpCfgLastChange         TimeStamp,
    tmnxGsmpGrpCfgRowStatus          RowStatus,
    tmnxGsmpGrpCfgAdminState         TmnxAdminState,
    tmnxGsmpGrpCfgKeepalive          Unsigned32,
    tmnxGsmpGrpCfgHoldMultiplier     Unsigned32,
    tmnxGsmpGrpCfgDescription        TItemDescription,
    tmnxGsmpGrpCfgAncpOamCap         TmnxAdminState,
    tmnxGsmpGrpCfgAncpDynTopoDiscCap TmnxAdminState,
    tmnxGsmpGrpCfgPersistencyDb      TmnxAdminState,
    tmnxGsmpGrpCfgIdleFilter         TmnxAdminState
}

tmnxGsmpGroupName                OBJECT-TYPE
    SYNTAX      TNamedItem
    MAX-ACCESS  not-accessible
    STATUS      current
    DESCRIPTION
        "The value of tmnxGsmpGroupName specifies, together with the object
         svcId, the key for this row. A GSMP group name is unique only within
         the scope of the service in which it is defined."
    ::= { tmnxGsmpGroupConfigEntry 1 }

tmnxGsmpGrpCfgLastChange         OBJECT-TYPE
    SYNTAX      TimeStamp
    MAX-ACCESS  read-only
    STATUS      current
    DESCRIPTION
        "The value of tmnxGsmpGrpCfgLastChange indicates the sysUpTime at the
         time of the last modification of this entry.

         If no changes were made to the entry since the last re-initialization
         of the local network management subsystem, then this object contains a
         zero value."
    ::= { tmnxGsmpGroupConfigEntry 2 }

tmnxGsmpGrpCfgRowStatus          OBJECT-TYPE
    SYNTAX      RowStatus
    MAX-ACCESS  read-create
    STATUS      current
    DESCRIPTION
        "The value of tmnxGsmpGrpCfgRowStatus specifies the row status of this
         row."
    ::= { tmnxGsmpGroupConfigEntry 3 }

tmnxGsmpGrpCfgAdminState         OBJECT-TYPE
    SYNTAX      TmnxAdminState
    MAX-ACCESS  read-create
    STATUS      current
    DESCRIPTION
        "The value of tmnxGsmpGrpCfgAdminState specifies the administrative
         state of the GSMP group. The value noop(3) is never allowed."
    DEFVAL      { outOfService }
    ::= { tmnxGsmpGroupConfigEntry 4 }

tmnxGsmpGrpCfgKeepalive          OBJECT-TYPE
    SYNTAX      Unsigned32 (1..25)
    UNITS       "seconds"
    MAX-ACCESS  read-create
    STATUS      current
    DESCRIPTION
        "The value of tmnxGsmpGrpCfgKeepalive specifies the GSMP keepalive
         timer value."
    DEFVAL      { 10 }
    ::= { tmnxGsmpGroupConfigEntry 5 }

tmnxGsmpGrpCfgHoldMultiplier     OBJECT-TYPE
    SYNTAX      Unsigned32 (1..100)
    MAX-ACCESS  read-create
    STATUS      current
    DESCRIPTION
        "The value of tmnxGsmpGrpCfgHoldMultiplier specifies the GSMP hold
         multiplier value. The actual hold time becomes:
         tmnxGsmpGrpCfgHoldMultiplier * tmnxGsmpGrpCfgKeepalive."
    DEFVAL      { 3 }
    ::= { tmnxGsmpGroupConfigEntry 6 }

tmnxGsmpGrpCfgDescription        OBJECT-TYPE
    SYNTAX      TItemDescription
    MAX-ACCESS  read-create
    STATUS      current
    DESCRIPTION
        "The value of tmnxGsmpGrpCfgDescription specifies a user provided
         description string for this GSMP group. It can consist of any
         printable, seven-bit ASCII characters up to 80 characters in length."
    DEFVAL      { "" }
    ::= { tmnxGsmpGroupConfigEntry 7 }

tmnxGsmpGrpCfgAncpOamCap         OBJECT-TYPE
    SYNTAX      TmnxAdminState
    MAX-ACCESS  read-create
    STATUS      current
    DESCRIPTION
        "The value of tmnxGsmpGrpCfgAncpOamCap specifies whether or not the
         GSMP Access Node Control Protocol (ANCP) OAM capability should be
         negotiated at startup of the GSMP connection. The value noop(3) is
         never allowed."
    DEFVAL      { outOfService }
    ::= { tmnxGsmpGroupConfigEntry 8 }

tmnxGsmpGrpCfgAncpDynTopoDiscCap OBJECT-TYPE
    SYNTAX      TmnxAdminState
    MAX-ACCESS  read-create
    STATUS      current
    DESCRIPTION
        "The value of tmnxGsmpGrpCfgAncpDynTopoDiscCap specifies whether or not
         the GSMP ANCP dynamic topology discovery capability should be
         negotiated at startup of the GSMP connection. The value noop(3) is
         never allowed."
    DEFVAL      { inService }
    ::= { tmnxGsmpGroupConfigEntry 9 }

tmnxGsmpGrpCfgPersistencyDb      OBJECT-TYPE
    SYNTAX      TmnxAdminState
    MAX-ACCESS  read-create
    STATUS      current
    DESCRIPTION
        "The value of tmnxGsmpGrpCfgPersistencyDb specifies whether or not the
         DSL line information is kept when the GSMP connection terminates. The
         value noop(3) is never allowed."
    DEFVAL      { outOfService }
    ::= { tmnxGsmpGroupConfigEntry 10 }

tmnxGsmpGrpCfgIdleFilter         OBJECT-TYPE
    SYNTAX      TmnxAdminState
    MAX-ACCESS  read-create
    STATUS      current
    DESCRIPTION
        "The value of tmnxGsmpGrpCfgIdleFilter specifies whether or not the DSL
         line information is ignored when the DSL-Line-State TLV is present in
         this information and the TLV has as value IDLE. The value noop(3) is
         never allowed."
    DEFVAL      { outOfService }
    ::= { tmnxGsmpGroupConfigEntry 11 }

tmnxGsmpGroupNbrTableLastChange  OBJECT-TYPE
    SYNTAX      TimeStamp
    MAX-ACCESS  read-only
    STATUS      current
    DESCRIPTION
        "The value of tmnxGsmpGroupNbrTableLastChange indicates the sysUpTime
         at the time of the last modification of an entry in the
         tmnxGsmpGroupNeighborTable.

         If no changes were made to the table since the last re-initialization
         of the local network management subsystem, then this object contains a
         zero value."
    ::= { tmnxGsmpObjects 6 }

tmnxGsmpGroupNeighborTable       OBJECT-TYPE
    SYNTAX      SEQUENCE OF TmnxGsmpGroupNeighborEntry
    MAX-ACCESS  not-accessible
    STATUS      current
    DESCRIPTION
        "The table tmnxGsmpGroupConfigTable contains a row for each neighbor
         defined in the GSMP group defined in a service on which GSMP can be
         enabled."
    ::= { tmnxGsmpObjects 7 }

tmnxGsmpGroupNeighborEntry       OBJECT-TYPE
    SYNTAX      TmnxGsmpGroupNeighborEntry
    MAX-ACCESS  not-accessible
    STATUS      current
    DESCRIPTION
        "Each row contains objects that allow configuration of a GSMP group
         neighbor in the scope of a service.

         Rows can be created, modified, and deleted by the operator. A row can
         only be deleted if the tmnxGsmpGrpNbrAdminState of that row is set to
         disabled(2)."
    INDEX       {
        svcId,
        tmnxGsmpGroupName,
        tmnxGsmpGrpNbrAddressType,
        tmnxGsmpGrpNbrAddress
    }
    ::= { tmnxGsmpGroupNeighborTable 1 }

TmnxGsmpGroupNeighborEntry       ::= SEQUENCE
{
    tmnxGsmpGrpNbrAddressType        InetAddressType,
    tmnxGsmpGrpNbrAddress            InetAddress,
    tmnxGsmpGrpNbrLastChange         TimeStamp,
    tmnxGsmpGrpNbrRowStatus          RowStatus,
    tmnxGsmpGrpNbrAdminState         TmnxAdminState,
    tmnxGsmpGrpNbrLocalAddrType      InetAddressType,
    tmnxGsmpGrpNbrLocalAddr          InetAddress,
    tmnxGsmpGrpNbrDescription        TItemDescription,
    tmnxGsmpGrpNbrPrioMarkType       TRemarkType,
    tmnxGsmpGrpNbrPrioMarkPrec       TPrecValueOrNone,
    tmnxGsmpGrpNbrPrioMarkDscp       TDSCPNameOrEmpty
}

tmnxGsmpGrpNbrAddressType        OBJECT-TYPE
    SYNTAX      InetAddressType
    MAX-ACCESS  not-accessible
    STATUS      current
    DESCRIPTION
        "The value of tmnxGsmpGrpNbrAddressType specifies, together with the
         object tmnxGsmpGrpNbrAddress, the IP address of the neighbor."
    ::= { tmnxGsmpGroupNeighborEntry 1 }

tmnxGsmpGrpNbrAddress            OBJECT-TYPE
    SYNTAX      InetAddress (SIZE (4|16))
    MAX-ACCESS  not-accessible
    STATUS      current
    DESCRIPTION
        "The value of tmnxGsmpGrpNbrAddress specifies, together with the object
         tmnxGsmpGrpNbrAddressType, the IP address of the neighbor."
    ::= { tmnxGsmpGroupNeighborEntry 2 }

tmnxGsmpGrpNbrLastChange         OBJECT-TYPE
    SYNTAX      TimeStamp
    MAX-ACCESS  read-only
    STATUS      current
    DESCRIPTION
        "The value of tmnxGsmpGrpNbrLastChange indicates the sysUpTime at the
         time of the last modification of this entry.

         If no changes were made to the entry since the last re-initialization
         of the local network management subsystem, then this object contains a
         zero value."
    ::= { tmnxGsmpGroupNeighborEntry 3 }

tmnxGsmpGrpNbrRowStatus          OBJECT-TYPE
    SYNTAX      RowStatus
    MAX-ACCESS  read-create
    STATUS      current
    DESCRIPTION
        "The value of tmnxGsmpGrpNbrRowStatus specifies the row status of this
         row."
    ::= { tmnxGsmpGroupNeighborEntry 4 }

tmnxGsmpGrpNbrAdminState         OBJECT-TYPE
    SYNTAX      TmnxAdminState
    MAX-ACCESS  read-create
    STATUS      current
    DESCRIPTION
        "The value of tmnxGsmpGrpNbrAdminState specifies the administrative
         state of this neighbor."
    DEFVAL      { outOfService }
    ::= { tmnxGsmpGroupNeighborEntry 5 }

tmnxGsmpGrpNbrLocalAddrType      OBJECT-TYPE
    SYNTAX      InetAddressType
    MAX-ACCESS  read-create
    STATUS      current
    DESCRIPTION
        "The value of tmnxGsmpGrpNbrLocalAddrType specifies, together with the
         object tmnxGsmpGrpNbrLocalAddr, the source IP address used in the
         connection towards the neighbor."
    DEFVAL      { unknown }
    ::= { tmnxGsmpGroupNeighborEntry 6 }

tmnxGsmpGrpNbrLocalAddr          OBJECT-TYPE
    SYNTAX      InetAddress (SIZE (0|4))
    MAX-ACCESS  read-create
    STATUS      current
    DESCRIPTION
        "The value of tmnxGsmpGrpNbrLocalAddr specifies, together with the
         object tmnxGsmpGrpNbrLocalAddrType, the source IP address used in the
         connection towards the neighbor."
    DEFVAL      { ''H }
    ::= { tmnxGsmpGroupNeighborEntry 7 }

tmnxGsmpGrpNbrDescription        OBJECT-TYPE
    SYNTAX      TItemDescription
    MAX-ACCESS  read-create
    STATUS      current
    DESCRIPTION
        "The value of tmnxGsmpGrpNbrDescription specifies a user provided
         description string for this neighbor. It can consist of any printable,
         seven-bit ASCII characters up to 80 characters in length."
    DEFVAL      { "" }
    ::= { tmnxGsmpGroupNeighborEntry 8 }

tmnxGsmpGrpNbrPrioMarkType       OBJECT-TYPE
    SYNTAX      TRemarkType
    MAX-ACCESS  read-create
    STATUS      current
    DESCRIPTION
        "The value of tmnxGsmpGrpNbrPrioMarkType specifies the priority
         remarking type to be used.

         If 'dscp' is specified the dscp code-point to be used is specified by
         the object tmnxGsmpGrpNbrPrioMarkDscp.

         If 'prec' is specified, the precedence value to be used is specified
         by the object tmnxGsmpGrpNbrPrioMarkPrec. "
    DEFVAL      { none }
    ::= { tmnxGsmpGroupNeighborEntry 9 }

tmnxGsmpGrpNbrPrioMarkPrec       OBJECT-TYPE
    SYNTAX      TPrecValueOrNone
    MAX-ACCESS  read-create
    STATUS      current
    DESCRIPTION
        "The value of tmnxGsmpGrpNbrPrioMarkPrec specifies the precedence
         priority  marking that is to be applied if tmnxGsmpGrpNbrPrioMarkType
         is set to 'prec'.

         If the value of tmnxGsmpGrpNbrPrioMarkType is changed from 'prec' to
         something else, the value of tmnxGsmpGrpNbrPrioMarkPrec is set to its
         default value."
    DEFVAL      { -1 }
    ::= { tmnxGsmpGroupNeighborEntry 10 }

tmnxGsmpGrpNbrPrioMarkDscp       OBJECT-TYPE
    SYNTAX      TDSCPNameOrEmpty
    MAX-ACCESS  read-create
    STATUS      current
    DESCRIPTION
        "The value of tmnxGsmpGrpNbrPrioMarkDscp specifies the DSCP to be used
         while remarking the in profile packets when the in-profile remarking
         type, tmnxGsmpGrpNbrPrioMarkType, is specified to be 'dscp'.

         If the value of tmnxGsmpGrpNbrPrioMarkType is changed from 'dscp' to
         something else, the value of tmnxGsmpGrpNbrPrioMarkDscp is set to its
         default value."
    DEFVAL      { "" }
    ::= { tmnxGsmpGroupNeighborEntry 11 }

tmnxAncpStaticMapSapTblLastChg   OBJECT-TYPE
    SYNTAX      TimeStamp
    MAX-ACCESS  read-only
    STATUS      current
    DESCRIPTION
        "The value of tmnxAncpStaticMapSapTblLastChg indicates the sysUpTime at
         the time of the last modification of an entry in the
         tmnxAncpStaticMapSapTable.

         If no changes were made to the table since the last re-initialization
         of the local network management subsystem, then this object contains a
         zero value."
    ::= { tmnxGsmpObjects 8 }

tmnxAncpStaticMapSapTable        OBJECT-TYPE
    SYNTAX      SEQUENCE OF TmnxAncpStaticMapSapEntry
    MAX-ACCESS  not-accessible
    STATUS      current
    DESCRIPTION
        "The table tmnxAncpStaticMapSapTable contains a row for each static
         ANCP entry, where the pair (ANCP-string - SAPid) is mapped onto an
         ANCP policy."
    ::= { tmnxGsmpObjects 9 }

tmnxAncpStaticMapSapEntry        OBJECT-TYPE
    SYNTAX      TmnxAncpStaticMapSapEntry
    MAX-ACCESS  not-accessible
    STATUS      current
    DESCRIPTION
        "Each row contains a static mapping from the pair (ANCP-string - SAPid)
         onto an ANCP policy. Rows can be created, modified, and deleted by the
         operator."
    INDEX       {
        sapPortId,
        sapEncapValue,
        tmnxAncpStaticMapSapString
    }
    ::= { tmnxAncpStaticMapSapTable 1 }

TmnxAncpStaticMapSapEntry        ::= SEQUENCE
{
    tmnxAncpStaticMapSapString       TmnxAncpString,
    tmnxAncpStaticMapSapLastChange   TimeStamp,
    tmnxAncpStaticMapSapRowStatus    RowStatus,
    tmnxAncpStaticMapSapAncpPolName  TNamedItem
}

tmnxAncpStaticMapSapString       OBJECT-TYPE
    SYNTAX      TmnxAncpString
    MAX-ACCESS  not-accessible
    STATUS      current
    DESCRIPTION
        "The value of tmnxAncpStaticMapSapString specifies, together with the
         SAP-id the key of this row. The value corresponds to the ASCII
         representation of the DSLAM circuit-id name."
    ::= { tmnxAncpStaticMapSapEntry 1 }

tmnxAncpStaticMapSapLastChange   OBJECT-TYPE
    SYNTAX      TimeStamp
    MAX-ACCESS  read-only
    STATUS      current
    DESCRIPTION
        "The value of tmnxAncpStaticMapSapLastChange indicates the sysUpTime at
         the time of the last modification of this entry.

         If no changes were made to the entry since the last re-initialization
         of the local network management subsystem, then this object contains a
         zero value."
    ::= { tmnxAncpStaticMapSapEntry 2 }

tmnxAncpStaticMapSapRowStatus    OBJECT-TYPE
    SYNTAX      RowStatus
    MAX-ACCESS  read-create
    STATUS      current
    DESCRIPTION
        "The value of tmnxAncpStaticMapSapRowStatus specifies the row status of
         this row."
    ::= { tmnxAncpStaticMapSapEntry 3 }

tmnxAncpStaticMapSapAncpPolName  OBJECT-TYPE
    SYNTAX      TNamedItem
    MAX-ACCESS  read-create
    STATUS      current
    DESCRIPTION
        "The value of tmnxAncpStaticMapSapAncpPolName specifies the ANCP policy
         as defined in the tmnxAncpPolicyTable associated with this
         (ANCP-string - SAPid) pair."
    ::= { tmnxAncpStaticMapSapEntry 4 }

tmnxAncpStaticMapMssTblLastChg   OBJECT-TYPE
    SYNTAX      TimeStamp
    MAX-ACCESS  read-only
    STATUS      current
    DESCRIPTION
        "The value of tmnxAncpStaticMapMssTblLastChg indicates the sysUpTime at
         the time of the last modification of an entry in the
         tmnxAncpStaticMapMssTable.

         If no changes were made to the table since the last re-initialization
         of the local network management subsystem, then this object contains a
         zero value."
    ::= { tmnxGsmpObjects 10 }

tmnxAncpStaticMapMssTable        OBJECT-TYPE
    SYNTAX      SEQUENCE OF TmnxAncpStaticMapMssEntry
    MAX-ACCESS  not-accessible
    STATUS      current
    DESCRIPTION
        "The table tmnxAncpStaticMapMssTable contains a row for each static
         ANCP entry, where the pair (ANCP-string - cust-id-MSS) is mapped onto
         an ANCP policy. (MSS = Multi Service Site)."
    ::= { tmnxGsmpObjects 11 }

tmnxAncpStaticMapMssEntry        OBJECT-TYPE
    SYNTAX      TmnxAncpStaticMapMssEntry
    MAX-ACCESS  not-accessible
    STATUS      current
    DESCRIPTION
        "Each row contains a static mapping from the triplet (ANCP-string -
         cust-id - MSS) onto an ANCP policy.

         Rows can be created, modified, and deleted by the operator."
    INDEX       {
        custId,
        custMultSvcSiteName,
        tmnxAncpStaticMapMssString
    }
    ::= { tmnxAncpStaticMapMssTable 1 }

TmnxAncpStaticMapMssEntry        ::= SEQUENCE
{
    tmnxAncpStaticMapMssString       TmnxAncpString,
    tmnxAncpStaticMapMssLastChange   TimeStamp,
    tmnxAncpStaticMapMssRowStatus    RowStatus,
    tmnxAncpStaticMapMssAncpPolName  TNamedItem
}

tmnxAncpStaticMapMssString       OBJECT-TYPE
    SYNTAX      TmnxAncpString
    MAX-ACCESS  not-accessible
    STATUS      current
    DESCRIPTION
        "The value of tmnxAncpStaticMapMssString specifies, together with the
         custId and the custMultSvcSiteName, the key of this row. The value
         corresponds to the ASCII representation of the DSLAM circuit-id name."
    ::= { tmnxAncpStaticMapMssEntry 1 }

tmnxAncpStaticMapMssLastChange   OBJECT-TYPE
    SYNTAX      TimeStamp
    MAX-ACCESS  read-only
    STATUS      current
    DESCRIPTION
        "The value of tmnxAncpStaticMapMssLastChange indicates the sysUpTime at
         the time of the last modification of this entry.

         If no changes were made to the entry since the last re-initialization
         of the local network management subsystem, then this object contains a
         zero value."
    ::= { tmnxAncpStaticMapMssEntry 2 }

tmnxAncpStaticMapMssRowStatus    OBJECT-TYPE
    SYNTAX      RowStatus
    MAX-ACCESS  read-create
    STATUS      current
    DESCRIPTION
        "The value of tmnxAncpStaticMapMssRowStatus specifies the row status of
         this row."
    ::= { tmnxAncpStaticMapMssEntry 3 }

tmnxAncpStaticMapMssAncpPolName  OBJECT-TYPE
    SYNTAX      TNamedItem
    MAX-ACCESS  read-create
    STATUS      current
    DESCRIPTION
        "The value of tmnxAncpStaticMapMssAncpPolName specifies the ANCP policy
         as defined in the tmnxAncpPolicyTable for this row."
    ::= { tmnxAncpStaticMapMssEntry 4 }

tmnxAncpSubProfileTblLastChange  OBJECT-TYPE
    SYNTAX      TimeStamp
    MAX-ACCESS  read-only
    STATUS      current
    DESCRIPTION
        "The value of tmnxAncpSubProfileTblLastChange indicates the sysUpTime
         at the time of the last modification of an entry in the
         tmnxAncpSubProfileTable.

         If no changes were made to the table since the last re-initialization
         of the local network management subsystem, then this object contains a
         zero value."
    ::= { tmnxGsmpObjects 12 }

tmnxAncpSubProfileTable          OBJECT-TYPE
    SYNTAX      SEQUENCE OF TmnxAncpSubProfileEntry
    MAX-ACCESS  not-accessible
    STATUS      current
    DESCRIPTION
        "The table tmnxAncpSubProfileTable augments the table
         TIMETRA-SUBSCRIBER-MGMT-MIB::tmnxSubProfileTable.

         More specifically this table allows the assignment of an ANCP-policy
         to a subscriber profile."
    ::= { tmnxGsmpObjects 13 }

tmnxAncpSubProfileEntry          OBJECT-TYPE
    SYNTAX      TmnxAncpSubProfileEntry
    MAX-ACCESS  not-accessible
    STATUS      current
    DESCRIPTION
        "Each row allows to assign an ANCP-policy to an existing subscriber
         profile"
    AUGMENTS    { tmnxSubProfileEntry }
    ::= { tmnxAncpSubProfileTable 1 }

TmnxAncpSubProfileEntry          ::= SEQUENCE
{ tmnxAncpSubProfileAncpPolicy     TNamedItemOrEmpty }

tmnxAncpSubProfileAncpPolicy     OBJECT-TYPE
    SYNTAX      TNamedItemOrEmpty
    MAX-ACCESS  read-create
    STATUS      current
    DESCRIPTION
        "The value of tmnxAncpSubProfileAncpPolicy specifies the ANCP policy as
         defined in the tmnxAncpPolicyTable for this sub profile."
    DEFVAL      { "" }
    ::= { tmnxAncpSubProfileEntry 1 }

tmnxAncpPolicyTableLastChange    OBJECT-TYPE
    SYNTAX      TimeStamp
    MAX-ACCESS  read-only
    STATUS      current
    DESCRIPTION
        "The value of tmnxAncpPolicyTableLastChange indicates the sysUpTime at
         the time of the last modification of an entry in the
         tmnxAncpPolicyTable.

         If no changes were made to the table since the last re-initialization
         of the local network management subsystem, then this object contains a
         zero value."
    ::= { tmnxGsmpObjects 14 }

tmnxAncpPolicyTable              OBJECT-TYPE
    SYNTAX      SEQUENCE OF TmnxAncpPolicyEntry
    MAX-ACCESS  not-accessible
    STATUS      current
    DESCRIPTION
        "The table tmnxAncpPolicyTable allows configuration of ANCP policies."
    ::= { tmnxGsmpObjects 15 }

tmnxAncpPolicyEntry              OBJECT-TYPE
    SYNTAX      TmnxAncpPolicyEntry
    MAX-ACCESS  not-accessible
    STATUS      current
    DESCRIPTION
        "Each row contains a definition of an ANCP policy.

         Rows can be created, modified, and deleted by the operator."
    INDEX       { tmnxAncpPolicyName }
    ::= { tmnxAncpPolicyTable 1 }

TmnxAncpPolicyEntry              ::= SEQUENCE
{
    tmnxAncpPolicyName               TNamedItem,
    tmnxAncpPlcyLastChange           TimeStamp,
    tmnxAncpPlcyRowStatus            RowStatus,
    tmnxAncpPlcyIngRateAdjustment    Unsigned32,
    tmnxAncpPlcyIngRateReduction     Unsigned32,
    tmnxAncpPlcyIngRateMonitor       Unsigned32,
    tmnxAncpPlcyIngRateMonitorNtf    TruthValue,
    tmnxAncpPlcyIngRateModType       INTEGER,
    tmnxAncpPlcyIngRateModSched      TNamedItemOrEmpty,
    tmnxAncpPlcyEgrRateAdjustment    Unsigned32,
    tmnxAncpPlcyEgrRateReduction     Unsigned32,
    tmnxAncpPlcyEgrRateMonitor       Unsigned32,
    tmnxAncpPlcyEgrRateMonitorNtf    TruthValue,
    tmnxAncpPlcyEgrRateModType       TEgrRateModType,
    tmnxAncpPlcyEgrRateModSched      TNamedItemOrEmpty,
    tmnxAncpPlcyDisableShcv          TruthValue,
    tmnxAncpPlcyDisableShcvHldTime   Unsigned32,
    tmnxAncpPlcyDisableShcvNtf       TruthValue
}

tmnxAncpPolicyName               OBJECT-TYPE
    SYNTAX      TNamedItem
    MAX-ACCESS  not-accessible
    STATUS      current
    DESCRIPTION
        "The value of tmnxAncpPolicyName specifies the name of the ANCP policy
         defined in this row."
    ::= { tmnxAncpPolicyEntry 1 }

tmnxAncpPlcyLastChange           OBJECT-TYPE
    SYNTAX      TimeStamp
    MAX-ACCESS  read-only
    STATUS      current
    DESCRIPTION
        "The value of tmnxAncpPlcyLastChange indicates the sysUpTime at the
         time of the last modification of this entry.

         If no changes were made to the entry since the last re-initialization
         of the local network management subsystem, then this object contains a
         zero value."
    ::= { tmnxAncpPolicyEntry 2 }

tmnxAncpPlcyRowStatus            OBJECT-TYPE
    SYNTAX      RowStatus
    MAX-ACCESS  read-create
    STATUS      current
    DESCRIPTION
        "The value of tmnxAncpPlcyRowStatus specifies the row status of this
         row."
    ::= { tmnxAncpPolicyEntry 3 }

tmnxAncpPlcyIngRateAdjustment    OBJECT-TYPE
    SYNTAX      Unsigned32 (1..200)
    MAX-ACCESS  read-create
    STATUS      current
    DESCRIPTION
        "The value of tmnxAncpPlcyIngRateAdjustment specifies the rate
         adjustment for the scheduler. This object should be used when the rate
         returned by the the DSLAM is calculated with a different encapsulation
         than the 7xxx. The node will adjust the rate by the indicated percent
         as: DSLAM_RATE * tmnxAncpPlcyIngRateAdjustment/100 -
         tmnxAncpPlcyIngRateReduction."
    DEFVAL      { 100 }
    ::= { tmnxAncpPolicyEntry 4 }

tmnxAncpPlcyIngRateReduction     OBJECT-TYPE
    SYNTAX      Unsigned32
    UNITS       "kilobps"
    MAX-ACCESS  read-create
    STATUS      current
    DESCRIPTION
        "The value of tmnxAncpPlcyIngRateReduction specifies the rate
         adjustment for the scheduler. This object should be used when the rate
         returned by the the DSLAM is calculated with a different encapsulation
         than the 7xxx. The node will adjust the rate by the indicated percent
         as: DSLAM_RATE * tmnxAncpPlcyIngRateAdjustment/100 -
         tmnxAncpPlcyIngRateReduction."
    DEFVAL      { 0 }
    ::= { tmnxAncpPolicyEntry 5 }

tmnxAncpPlcyIngRateMonitor       OBJECT-TYPE
    SYNTAX      Unsigned32
    UNITS       "kilobps"
    MAX-ACCESS  read-create
    STATUS      current
    DESCRIPTION
        "The value of tmnxAncpPlcyIngRateMonitor specifies the rate below which
         the system will generate an event. If tmnxAncpPlcyIngRateMonitorNtf is
         true, an SNMP Notification is generated. If set to 0, no rate
         monitoring is active."
    DEFVAL      { 0 }
    ::= { tmnxAncpPolicyEntry 6 }

tmnxAncpPlcyIngRateMonitorNtf    OBJECT-TYPE
    SYNTAX      TruthValue
    MAX-ACCESS  read-create
    STATUS      current
    DESCRIPTION
        "The value of tmnxAncpPlcyIngRateMonitorNtf specifies whether or not an
         SNMP Notification is generated if a monitor event is raised."
    DEFVAL      { false }
    ::= { tmnxAncpPolicyEntry 7 }

tmnxAncpPlcyIngRateModType       OBJECT-TYPE
    SYNTAX      INTEGER {
        none           (1),
        namedScheduler (2)
    }
    MAX-ACCESS  read-create
    STATUS      current
    DESCRIPTION
        "The value of tmnxAncpPlcyIngRateModType specifies the ingress-rate
         modification that is to be applied. If set to 'namedScheduler', then
         the scheduler as defined in tmnxAncpPlcyIngRateModSched is used."
    DEFVAL      { none }
    ::= { tmnxAncpPolicyEntry 8 }

tmnxAncpPlcyIngRateModSched      OBJECT-TYPE
    SYNTAX      TNamedItemOrEmpty
    MAX-ACCESS  read-create
    STATUS      current
    DESCRIPTION
        "The value of tmnxAncpPlcyIngRateModSched specifies the scheduler to be
         applied for ingress rate modification. The value is only considered if
         tmnxAncpPlcyIngRateModSched is set to 'namedScheduler'."
    DEFVAL      { "" }
    ::= { tmnxAncpPolicyEntry 9 }

tmnxAncpPlcyEgrRateAdjustment    OBJECT-TYPE
    SYNTAX      Unsigned32 (1..200)
    MAX-ACCESS  read-create
    STATUS      current
    DESCRIPTION
        "The value of tmnxAncpPlcyEgrRateAdjustment specifies the rate
         adjustment for the scheduler. This object should be used when the rate
         returned by the the DSLAM is calculated with a different encapsulation
         than the 7xxx. The node will adjust the rate by the indicated percent
         as: DSLAM_RATE * tmnxAncpPlcyEgrRateAdjustment/100 -
         tmnxAncpPlcyEgrRateReduction."
    DEFVAL      { 100 }
    ::= { tmnxAncpPolicyEntry 10 }

tmnxAncpPlcyEgrRateReduction     OBJECT-TYPE
    SYNTAX      Unsigned32
    UNITS       "kilobps"
    MAX-ACCESS  read-create
    STATUS      current
    DESCRIPTION
        "The value of tmnxAncpPlcyEgrRateReduction specifies the rate
         adjustment for the scheduler. This object should be used when the rate
         returned by the the DSLAM is calculated with a different encapsulation
         than the 7xxx. The node will adjust the rate by the indicated percent
         as: DSLAM_RATE * tmnxAncpPlcyEgrRateAdjustment/100 -
         tmnxAncpPlcyEgrRateReduction."
    DEFVAL      { 0 }
    ::= { tmnxAncpPolicyEntry 11 }

tmnxAncpPlcyEgrRateMonitor       OBJECT-TYPE
    SYNTAX      Unsigned32
    UNITS       "kilobps"
    MAX-ACCESS  read-create
    STATUS      current
    DESCRIPTION
        "The value of tmnxAncpPlcyEgrRateMonitor specifies the rate below which
         the system will generate an event. If tmnxAncpPlcyEgrRateMonitorNtf is
         true, an SNMP notification is generated. If set to 0, no rate
         monitoring is active."
    DEFVAL      { 0 }
    ::= { tmnxAncpPolicyEntry 12 }

tmnxAncpPlcyEgrRateMonitorNtf    OBJECT-TYPE
    SYNTAX      TruthValue
    MAX-ACCESS  read-create
    STATUS      current
    DESCRIPTION
        "The value of tmnxAncpPlcyEgrRateMonitorNtf specifies whether or not an
         SNMP Notification is generated if the monitor event is raised."
    DEFVAL      { false }
    ::= { tmnxAncpPolicyEntry 13 }

tmnxAncpPlcyEgrRateModType       OBJECT-TYPE
    SYNTAX      TEgrRateModType
    MAX-ACCESS  read-create
    STATUS      current
    DESCRIPTION
        "The value of tmnxAncpPlcyEgrRateModType specifies the egress-rate
         modification that is to be applied. If set to 'other-namedScheduler',
         then the scheduler as defined in tmnxAncpPlcyEgrRateModSched is used."
    DEFVAL      { none }
    ::= { tmnxAncpPolicyEntry 14 }

tmnxAncpPlcyEgrRateModSched      OBJECT-TYPE
    SYNTAX      TNamedItemOrEmpty
    MAX-ACCESS  read-create
    STATUS      current
    DESCRIPTION
        "The value of tmnxAncpPlcyEgrRateModSched specifies the scheduler to be
         applied for egress rate modification. The value is only considered if
         tmnxAncpPlcyEgrRateModType is set to 'namedScheduler'."
    DEFVAL      { "" }
    ::= { tmnxAncpPolicyEntry 15 }

tmnxAncpPlcyDisableShcv          OBJECT-TYPE
    SYNTAX      TruthValue
    MAX-ACCESS  read-create
    STATUS      current
    DESCRIPTION
        "The value of tmnxAncpPlcyDisableShcv specifies whether or not the node
         will suspend SHCV (Subscriber Host Connectivity Verification) for the
         hosts defined with this ANCP policy when a port-down message is
         received, until the access node sends a port-up message.

         If tmnxAncpPlcyDisableShcvHldTime is non zero, the node will suspend
         SHCV for the period of time defined. If tmnxAncpPlcyDisableShcvHldTime
         is zero, SHCV is suspended until a port-up message is received."
    DEFVAL      { false }
    ::= { tmnxAncpPolicyEntry 16 }

tmnxAncpPlcyDisableShcvHldTime   OBJECT-TYPE
    SYNTAX      Unsigned32 (0..7200)
    UNITS       "seconds"
    MAX-ACCESS  read-create
    STATUS      current
    DESCRIPTION
        "The value of tmnxAncpPlcyDisableShcvHldTime specifies how long SHCV is
         suspended until the access node sends a port-up message. If
         tmnxAncpPlcyDisableShcvHldTime is non zero, the node will suspend SHCV
         for the period of time defined. If tmnxAncpPlcyDisableShcvHldTime is
         zero, SHCV is suspended until a port-up message is received."
    DEFVAL      { 0 }
    ::= { tmnxAncpPolicyEntry 17 }

tmnxAncpPlcyDisableShcvNtf       OBJECT-TYPE
    SYNTAX      TruthValue
    MAX-ACCESS  read-create
    STATUS      current
    DESCRIPTION
        "The value of tmnxAncpPlcyDisableShcvNtf specifies whether or not the
         system should generate a notification before suspending SHCV on the
         node."
    DEFVAL      { false }
    ::= { tmnxAncpPolicyEntry 18 }

tmnxAncpStringInfoTable          OBJECT-TYPE
    SYNTAX      SEQUENCE OF TmnxAncpStringInfoEntry
    MAX-ACCESS  not-accessible
    STATUS      current
    DESCRIPTION
        "The table tmnxAncpStringInfoTable contains runtime information about
         all ANCP-strings known to the system."
    ::= { tmnxGsmpObjects 16 }

tmnxAncpStringInfoEntry          OBJECT-TYPE
    SYNTAX      TmnxAncpStringInfoEntry
    MAX-ACCESS  not-accessible
    STATUS      current
    DESCRIPTION
        "Each row contains information about an ANCP-string known to the
         system. Rows are created/deleted automatically by the system.

         The table contains read-only information only."
    INDEX       { tmnxAncpStrInfAncpString }
    ::= { tmnxAncpStringInfoTable 1 }

TmnxAncpStringInfoEntry          ::= SEQUENCE
{
    tmnxAncpStrInfAncpString         DisplayString,
    tmnxAncpStrInfAssociation        INTEGER,
    tmnxAncpStrInfSapPortId          TmnxPortID,
    tmnxAncpStrInfSapEncapValue      TmnxEncapVal,
    tmnxAncpStrInfMultSvcSiteName    TNamedItemOrEmpty,
    tmnxAncpStrInfMultSvcSiteCust    TmnxCustId,
    tmnxAncpStrInfSubscrIdent        DisplayString,
    tmnxAncpStrInfLineState          INTEGER,
    tmnxAncpStrInfAncpPolicyName     TNamedItemOrEmpty,
    tmnxAncpStrInfIngrRate           TPIRRateOverride,
    tmnxAncpStrInfAdjustedIngrRate   TPIRRateOverride,
    tmnxAncpStrInfEgrRate            TPIRRateOverride,
    tmnxAncpStrInfAdjustedEgrRate    TPIRRateOverride,
    tmnxAncpStrInfServId             TmnxServId,
    tmnxAncpStrInfNeighborAddrType   InetAddressType,
    tmnxAncpStrInfNeighborAddr       InetAddress,
    tmnxAncpStrInfTcpPort            Unsigned32,
    tmnxAncpStrInfGroupName          TNamedItemOrEmpty,
    tmnxAncpStrInfPersistKey         Unsigned32
}

tmnxAncpStrInfAncpString         OBJECT-TYPE
    SYNTAX      DisplayString (SIZE (1..64))
    MAX-ACCESS  not-accessible
    STATUS      current
    DESCRIPTION
        "The value of tmnxAncpStrInfAncpString indicates the ANCP-string for
         which this row entry contains information."
    ::= { tmnxAncpStringInfoEntry 1 }

tmnxAncpStrInfAssociation        OBJECT-TYPE
    SYNTAX      INTEGER {
        none          (1),
        sap           (2),
        multiServSite (3),
        subscriberId  (4)
    }
    MAX-ACCESS  read-only
    STATUS      current
    DESCRIPTION
        "The value of tmnxAncpStrInfAssociation indicates to what object the
         ANCP-string is associated.

         If set to sap(2), the associated sap can be found in
         tmnxAncpStrInfSapPortId and tmnxAncpStrInfSapEncapValue.

         If set to multiServSite (3), the associated multi-service site can be
         found in (tmnxAncpStrInfMultSvcSiteName
         tmnxAncpStrInfMultSvcSiteCust).

         If set to subscriberId (4), the associated subscriber-Id can be found
         in the object tmnxAncpStrInfSubscrIdent.

         If set to none (1), no association is currently known for the ANCP
         string."
    ::= { tmnxAncpStringInfoEntry 2 }

tmnxAncpStrInfSapPortId          OBJECT-TYPE
    SYNTAX      TmnxPortID
    MAX-ACCESS  read-only
    STATUS      current
    DESCRIPTION
        "The value of tmnxAncpStrInfSapPortId indicates, together with the
         object tmnxAncpStrInfSapEncapValue the SAP-id to which the ANCP-string
         defined in tmnxAncpStrInfAncpString is associated.

         The value of this object is only meaningful when the value of the
         object tmnxAncpStrInfAssociation is set to sap(2)."
    ::= { tmnxAncpStringInfoEntry 3 }

tmnxAncpStrInfSapEncapValue      OBJECT-TYPE
    SYNTAX      TmnxEncapVal
    MAX-ACCESS  read-only
    STATUS      current
    DESCRIPTION
        "The value of tmnxAncpStrInfSapEncapValue indicates, together with the
         object tmnxAncpStrInfSapPortId the SAP id to which the ANCP-string
         defined in tmnxAncpStrInfAncpString is associated.

         The value of this object is only meaningful when the value of the
         object tmnxAncpStrInfAssociation is set to sap(2)."
    ::= { tmnxAncpStringInfoEntry 4 }

tmnxAncpStrInfMultSvcSiteName    OBJECT-TYPE
    SYNTAX      TNamedItemOrEmpty
    MAX-ACCESS  read-only
    STATUS      current
    DESCRIPTION
        "The value of tmnxAncpStrInfMultSvcSiteName indicates, together with
         the object tmnxAncpStrInfMultSvcSiteCust the MSS site to which the
         ANCP-string defined in tmnxAncpStrInfAncpString is associated.

         The value of this object is only meaningful when the value of the
         object tmnxAncpStrInfAssociation is set to multiServSite(3)."
    ::= { tmnxAncpStringInfoEntry 5 }

tmnxAncpStrInfMultSvcSiteCust    OBJECT-TYPE
    SYNTAX      TmnxCustId
    MAX-ACCESS  read-only
    STATUS      current
    DESCRIPTION
        "The value of tmnxAncpStrInfMultSvcSiteCust indicates, together with
         the object tmnxAncpStrInfMultSvcSiteName the MSS site to which the
         ANCP-string defined in tmnxAncpStrInfAncpString is associated.

         The value of this object is only meaningful when the value of the
         object tmnxAncpStrInfAssociation is set to multiServSite(3)."
    ::= { tmnxAncpStringInfoEntry 6 }

tmnxAncpStrInfSubscrIdent        OBJECT-TYPE
    SYNTAX      DisplayString
    MAX-ACCESS  read-only
    STATUS      current
    DESCRIPTION
        "The value of tmnxAncpStrInfSubscrIdent indicates, the subscriber ID to
         which the ANCP-string defined in tmnxAncpStrInfAncpString is
         associated.

         The value of this object is only meaningful when the value of the
         object tmnxAncpStrInfAssociation is set to subscriberId(4)."
    ::= { tmnxAncpStringInfoEntry 7 }

tmnxAncpStrInfLineState          OBJECT-TYPE
    SYNTAX      INTEGER {
        unknown (1),
        down    (2),
        up      (3)
    }
    MAX-ACCESS  read-only
    STATUS      current
    DESCRIPTION
        "The value of tmnxAncpStrInfLineState indicates the state of the DSL
         line identified the ANCP-string."
    ::= { tmnxAncpStringInfoEntry 8 }

tmnxAncpStrInfAncpPolicyName     OBJECT-TYPE
    SYNTAX      TNamedItemOrEmpty
    MAX-ACCESS  read-only
    STATUS      current
    DESCRIPTION
        "The value of tmnxAncpStrInfAncpPolicyName indicates the ANCP-policy
         name associated with this ANCP-string if any."
    ::= { tmnxAncpStringInfoEntry 9 }

tmnxAncpStrInfIngrRate           OBJECT-TYPE
    SYNTAX      TPIRRateOverride
    MAX-ACCESS  read-only
    STATUS      current
    DESCRIPTION
        "The value of tmnxAncpStrInfIngrRate indicates the ingress line rate
         for the DSL line as reported by the access device.

         The value is meaningful only if the linkstate
         (tmnxAncpStrInfLineState) is in state up(3)."
    ::= { tmnxAncpStringInfoEntry 10 }

tmnxAncpStrInfAdjustedIngrRate   OBJECT-TYPE
    SYNTAX      TPIRRateOverride
    MAX-ACCESS  read-only
    STATUS      current
    DESCRIPTION
        "The value of tmnxAncpStrInfAdjustedIngrRate indicates the adjusted
         ingress line rate for the DSL line as reported by the access device.

         The value is meaningful only if the linkstate
         (tmnxAncpStrInfLineState) is in state up(3)."
    ::= { tmnxAncpStringInfoEntry 11 }

tmnxAncpStrInfEgrRate            OBJECT-TYPE
    SYNTAX      TPIRRateOverride
    MAX-ACCESS  read-only
    STATUS      current
    DESCRIPTION
        "The value of tmnxAncpStrInfEgrRate indicates the egress line rate for
         the DSL line as reported by the access device.

         The value is meaningful only if the linkstate
         (tmnxAncpStrInfLineState) is in state up(3)."
    ::= { tmnxAncpStringInfoEntry 12 }

tmnxAncpStrInfAdjustedEgrRate    OBJECT-TYPE
    SYNTAX      TPIRRateOverride
    MAX-ACCESS  read-only
    STATUS      current
    DESCRIPTION
        "The value of tmnxAncpStrInfAdjustedEgrRate indicates the
         adjusted egress line rate  for the DSL line as reported by the
         access device.

         The value is meaningful only if the linkstate
         (tmnxAncpStrInfLineState) is in state up(3)."
    ::= { tmnxAncpStringInfoEntry 13 }

tmnxAncpStrInfServId             OBJECT-TYPE
    SYNTAX      TmnxServId
    MAX-ACCESS  read-only
    STATUS      current
    DESCRIPTION
        "The value of tmnxAncpStrInfServId indicates (if different from 0) the
         service in which the ANCP session is running.

         The 3 objects tmnxAncpStrInfServId,tmnxAncpStrInfNeighborAddr, and
         tmnxAncpStrInfTcpPort uniquely identify the ANCP session."
    ::= { tmnxAncpStringInfoEntry 14 }

tmnxAncpStrInfNeighborAddrType   OBJECT-TYPE
    SYNTAX      InetAddressType
    MAX-ACCESS  read-only
    STATUS      current
    DESCRIPTION
        "The value of tmnxAncpStrInfNeighborAddrType indicates the type of
         address contained in tmnxAncpStrInfNeighborAddr if any."
    ::= { tmnxAncpStringInfoEntry 15 }

tmnxAncpStrInfNeighborAddr       OBJECT-TYPE
    SYNTAX      InetAddress
    MAX-ACCESS  read-only
    STATUS      current
    DESCRIPTION
        "The value of tmnxAncpStrInfNeighborAddr indicates (if different from
         0) the ANCP neighbor IP address.

          The 3 objects tmnxAncpStrInfServId,tmnxAncpStrInfNeighborAddr, and
          tmnxAncpStrInfTcpPort uniquely identify the ANCP session."
    ::= { tmnxAncpStringInfoEntry 16 }

tmnxAncpStrInfTcpPort            OBJECT-TYPE
    SYNTAX      Unsigned32
    MAX-ACCESS  read-only
    STATUS      current
    DESCRIPTION
        "The value of tmnxAncpStrInfTcpPort indicates (if different from 0) the
         ANCP neighbor sessions TCP port number.

         The 3 objects tmnxAncpStrInfServId, tmnxAncpStrInfNeighborAddr, and
         tmnxAncpStrInfTcpPort uniquely identify the ANCP session."
    ::= { tmnxAncpStringInfoEntry 17 }

tmnxAncpStrInfGroupName          OBJECT-TYPE
    SYNTAX      TNamedItemOrEmpty
    MAX-ACCESS  read-only
    STATUS      current
    DESCRIPTION
        "The value of tmnxAncpStrInfGroupName indicates the GSMP group in which
         the neighbor is defined. This value is configurable using the object:
         tmnxGsmpGroupName."
    ::= { tmnxAncpStringInfoEntry 18 }

tmnxAncpStrInfPersistKey         OBJECT-TYPE
    SYNTAX      Unsigned32
    MAX-ACCESS  read-only
    STATUS      current
    DESCRIPTION
        "The value of tmnxAncpStrInfPersistKey indicates a key value that can
         be used to track the ANCP-string in the persistence file."
    ::= { tmnxAncpStringInfoEntry 19 }

tmnxAncpSessionTable             OBJECT-TYPE
    SYNTAX      SEQUENCE OF TmnxAncpSessionEntry
    MAX-ACCESS  not-accessible
    STATUS      current
    DESCRIPTION
        "The table tmnxAncpSessionTable contains runtime information about all
         ANCP sessions known to the system."
    ::= { tmnxGsmpObjects 17 }

tmnxAncpSessionEntry             OBJECT-TYPE
    SYNTAX      TmnxAncpSessionEntry
    MAX-ACCESS  not-accessible
    STATUS      current
    DESCRIPTION
        "Each row contains information about an ANCP session known to the
         system. Rows are created/deleted automatically by the system.

         The table contains read-only information only."
    INDEX       {
        tmnxAncpSesServiceId,
        tmnxAncpSesNbrAddressType,
        tmnxAncpSesNbrAddress,
        tmnxAncpSesNbrTcpPort
    }
    ::= { tmnxAncpSessionTable 1 }

TmnxAncpSessionEntry             ::= SEQUENCE
{
    tmnxAncpSesServiceId             TmnxServId,
    tmnxAncpSesNbrAddressType        InetAddressType,
    tmnxAncpSesNbrAddress            InetAddress,
    tmnxAncpSesNbrTcpPort            Unsigned32,
    tmnxAncpSesNbrPeerInstance       Unsigned32,
    tmnxAncpSesNbrPeerPort           Unsigned32,
    tmnxAncpSesNbrPeerName           OCTET STRING,
    tmnxAncpSesSenderInstance        Unsigned32,
    tmnxAncpSesSenderPort            Unsigned32,
    tmnxAncpSesSenderName            OCTET STRING,
    tmnxAncpSesNbrTimeouts           Unsigned32,
    tmnxAncpSesNbrMaxNbrOfTimeouts   Unsigned32,
    tmnxAncpSesNbrTimer              Unsigned32,
    tmnxAncpSesSenderTimer           Unsigned32,
    tmnxAncpSesNegotiatedCaps        BITS,
    tmnxAncpSesConfiguredCaps        BITS,
    tmnxAncpSesGroupName             TNamedItem,
    tmnxAncpSesState                 INTEGER,
    tmnxAncpSesLocalAddrType         InetAddressType,
    tmnxAncpSesLocalAddr             InetAddress,
    tmnxAncpSesVersion               INTEGER,
    tmnxAncpSesPartitionID           Integer32
}

tmnxAncpSesServiceId             OBJECT-TYPE
    SYNTAX      TmnxServId
    MAX-ACCESS  not-accessible
    STATUS      current
    DESCRIPTION
        "The value of tmnxAncpSesServiceId indicates the service-id of the
         service in which this ANCP session is running."
    ::= { tmnxAncpSessionEntry 1 }

tmnxAncpSesNbrAddressType        OBJECT-TYPE
    SYNTAX      InetAddressType
    MAX-ACCESS  not-accessible
    STATUS      current
    DESCRIPTION
        "The value of tmnxAncpSesNbrAddressType indicates the address type of
         the address contained in tmnxAncpSesNbrAddress."
    ::= { tmnxAncpSessionEntry 2 }

tmnxAncpSesNbrAddress            OBJECT-TYPE
    SYNTAX      InetAddress
    MAX-ACCESS  not-accessible
    STATUS      current
    DESCRIPTION
        "The value of tmnxAncpSesNbrAddress indicates the IP address of the
         neighbor in this ANCP session."
    ::= { tmnxAncpSessionEntry 3 }

tmnxAncpSesNbrTcpPort            OBJECT-TYPE
    SYNTAX      Unsigned32
    MAX-ACCESS  not-accessible
    STATUS      current
    DESCRIPTION
        "The value of tmnxAncpSesNbrTcpPort indicates the neighbor TCP port
         number use for this ANCP session."
    ::= { tmnxAncpSessionEntry 4 }

tmnxAncpSesNbrPeerInstance       OBJECT-TYPE
    SYNTAX      Unsigned32
    MAX-ACCESS  read-only
    STATUS      current
    DESCRIPTION
        "The value of tmnxAncpSesNbrPeerInstance indicates the sender-instance
         value received from the ANCP session neighbor."
    ::= { tmnxAncpSessionEntry 5 }

tmnxAncpSesNbrPeerPort           OBJECT-TYPE
    SYNTAX      Unsigned32
    MAX-ACCESS  read-only
    STATUS      current
    DESCRIPTION
        "The value of tmnxAncpSesNbrPeerPort indicates the sender-port value
         received from the ANCP session neighbor."
    ::= { tmnxAncpSessionEntry 6 }

tmnxAncpSesNbrPeerName           OBJECT-TYPE
    SYNTAX      OCTET STRING (SIZE (6))
    MAX-ACCESS  read-only
    STATUS      current
    DESCRIPTION
        "The value of tmnxAncpSesNbrPeerName indicates the sender-name value
         received from the ANCP session neighbor."
    ::= { tmnxAncpSessionEntry 7 }

tmnxAncpSesSenderInstance        OBJECT-TYPE
    SYNTAX      Unsigned32
    MAX-ACCESS  read-only
    STATUS      current
    DESCRIPTION
        "The value of tmnxAncpSesSenderInstance indicates the sender-instance
         value sent to the ANCP neighbor in this ANCP session."
    ::= { tmnxAncpSessionEntry 8 }

tmnxAncpSesSenderPort            OBJECT-TYPE
    SYNTAX      Unsigned32
    MAX-ACCESS  read-only
    STATUS      current
    DESCRIPTION
        "The value of tmnxAncpSesSenderPort indicates the sender-port value
         sent to the ANCP neighbor in this ANCP session."
    ::= { tmnxAncpSessionEntry 9 }

tmnxAncpSesSenderName            OBJECT-TYPE
    SYNTAX      OCTET STRING (SIZE (6))
    MAX-ACCESS  read-only
    STATUS      current
    DESCRIPTION
        "The value of tmnxAncpSesSenderName indicates the sender-name value
         sent to the ANCP neighbor in this ANCP session."
    ::= { tmnxAncpSessionEntry 10 }

tmnxAncpSesNbrTimeouts           OBJECT-TYPE
    SYNTAX      Unsigned32
    MAX-ACCESS  read-only
    STATUS      current
    DESCRIPTION
        "The value of tmnxAncpSesNbrTimeouts indicates how many times the
         system has timed out while waiting for an ACK from the neighbor. Each
         time an answer is received from the neighbor the value is reset to 0."
    ::= { tmnxAncpSessionEntry 11 }

tmnxAncpSesNbrMaxNbrOfTimeouts   OBJECT-TYPE
    SYNTAX      Unsigned32
    MAX-ACCESS  read-only
    STATUS      current
    DESCRIPTION
        "The value of tmnxAncpSesNbrMaxNbrOfTimeouts indicates the max number
         of timeouts the system will allow before the ANCP session is closed.

         The current number of timeouts is stored in tmnxAncpSesNbrTimeouts.
         The tmnxAncpSesNbrMaxNbrOfTimeouts is configurable by modifying the
         object tmnxGsmpGrpCfgHoldMultiplier."
    ::= { tmnxAncpSessionEntry 12 }

tmnxAncpSesNbrTimer              OBJECT-TYPE
    SYNTAX      Unsigned32
    MAX-ACCESS  read-only
    STATUS      current
    DESCRIPTION
        "The value of tmnxAncpSesNbrTimer indicates the timeout value used by
         the system when waiting for an ACK from the ANCP neighbor.

         The value of tmnxAncpSesNbrTimer is received from the ANCP neighbor."
    ::= { tmnxAncpSessionEntry 13 }

tmnxAncpSesSenderTimer           OBJECT-TYPE
    SYNTAX      Unsigned32
    MAX-ACCESS  read-only
    STATUS      current
    DESCRIPTION
        "The value of tmnxAncpSesSenderTimer indicates the timeout value that
         will be announced towards the ANCP neighbor.

         The ANCP neighbor will use this timeout value while waiting for a ACK
         from this system.

         The tmnxAncpSesNbrTimer is configurable by modifying the object
         tmnxGsmpGrpCfgKeepalive."
    ::= { tmnxAncpSessionEntry 14 }

tmnxAncpSesNegotiatedCaps        OBJECT-TYPE
    SYNTAX      BITS {
        oamCap         (0),
        dynTopoDiscCap (1)
    }
    MAX-ACCESS  read-only
    STATUS      current
    DESCRIPTION
        "The value of tmnxAncpSesNegotiatedCaps indicates which capabilities
         are successfully negotiated in the ANCP session."
    ::= { tmnxAncpSessionEntry 15 }

tmnxAncpSesConfiguredCaps        OBJECT-TYPE
    SYNTAX      BITS {
        oamCap         (0),
        dynTopoDiscCap (1)
    }
    MAX-ACCESS  read-only
    STATUS      current
    DESCRIPTION
        "The value of tmnxAncpSesConfiguredCaps indicates which capabilities
         were requested when the session was first established."
    ::= { tmnxAncpSessionEntry 16 }

tmnxAncpSesGroupName             OBJECT-TYPE
    SYNTAX      TNamedItem
    MAX-ACCESS  read-only
    STATUS      current
    DESCRIPTION
        "The value of tmnxAncpSesGroupName indicates the GSMP group in which
         the neighbor is defined. This value is configurable using the object:
         tmnxGsmpGroupName."
    ::= { tmnxAncpSessionEntry 17 }

tmnxAncpSesState                 OBJECT-TYPE
    SYNTAX      INTEGER {
        synSent     (1),
        synReceived (2),
        established (3)
    }
    MAX-ACCESS  read-only
    STATUS      current
    DESCRIPTION
        "The value of tmnxAncpSesState indicates  the state this gsmp
         session is in."
    ::= { tmnxAncpSessionEntry 18 }

tmnxAncpSesLocalAddrType         OBJECT-TYPE
    SYNTAX      InetAddressType
    MAX-ACCESS  read-only
    STATUS      current
    DESCRIPTION
        "The value of tmnxAncpSesLocalAddrType indicates the address type of
         the address contained in tmnxAncpSesLocalAddr."
    ::= { tmnxAncpSessionEntry 19 }

tmnxAncpSesLocalAddr             OBJECT-TYPE
    SYNTAX      InetAddress
    MAX-ACCESS  read-only
    STATUS      current
    DESCRIPTION
        "The value of tmnxAncpSesLocalAddr indicates the INET address that was
         used by the neighbor to identify the endpoint of the ANCP session he
         wants to establish."
    ::= { tmnxAncpSessionEntry 20 }

tmnxAncpSesVersion               OBJECT-TYPE
    SYNTAX      INTEGER {
        gsmp (1),
        ancp (2)
    }
    MAX-ACCESS  read-only
    STATUS      current
    DESCRIPTION
        "The value of tmnxAncpSesVersion indicates the ANCP version negotiated
         for this session."
    ::= { tmnxAncpSessionEntry 21 }

tmnxAncpSesPartitionID           OBJECT-TYPE
    SYNTAX      Integer32 (0 | 1..255)
    MAX-ACCESS  read-only
    STATUS      current
    DESCRIPTION
        "The value of tmnxAncpSesPartitionID indicates the partition ID
         negotiated for this session."
    ::= { tmnxAncpSessionEntry 22 }

tmnxAncpSessionStatsTable        OBJECT-TYPE
    SYNTAX      SEQUENCE OF TmnxAncpSessionStatsEntry
    MAX-ACCESS  not-accessible
    STATUS      current
    DESCRIPTION
        "The table tmnxAncpSessionStatsTable contains statistic information for
         every ANCP session known to the system."
    ::= { tmnxGsmpObjects 18 }

tmnxAncpSessionStatsEntry        OBJECT-TYPE
    SYNTAX      TmnxAncpSessionStatsEntry
    MAX-ACCESS  not-accessible
    STATUS      current
    DESCRIPTION
        "Each row contains statistics information about an ANCP session known
         to the system. Rows are created/deleted automatically by the system.

         The table contains read-only information only."
    INDEX       {
        tmnxAncpSesServiceId,
        tmnxAncpSesNbrAddressType,
        tmnxAncpSesNbrAddress,
        tmnxAncpSesNbrTcpPort
    }
    ::= { tmnxAncpSessionStatsTable 1 }

TmnxAncpSessionStatsEntry        ::= SEQUENCE
{
    tmnxAncpSesStatLastChanged       TimeStamp,
    tmnxAncpSesStatRxDrop            Counter32,
    tmnxAncpSesStatTxDrop            Counter32,
    tmnxAncpSesStatRxSyn             Counter32,
    tmnxAncpSesStatTxSyn             Counter32,
    tmnxAncpSesStatRxSynAck          Counter32,
    tmnxAncpSesStatTxSynAck          Counter32,
    tmnxAncpSesStatRxAck             Counter32,
    tmnxAncpSesStatTxAck             Counter32,
    tmnxAncpSesStatRxRstAck          Counter32,
    tmnxAncpSesStatTxRstAck          Counter32,
    tmnxAncpSesStatRxPortUp          Counter32,
    tmnxAncpSesStatTxPortUp          Counter32,
    tmnxAncpSesStatRxPortDown        Counter32,
    tmnxAncpSesStatTxPortDown        Counter32,
    tmnxAncpSesStatRxLoopback        Counter32,
    tmnxAncpSesStatTxLoopback        Counter32
}

tmnxAncpSesStatLastChanged       OBJECT-TYPE
    SYNTAX      TimeStamp
    MAX-ACCESS  read-only
    STATUS      current
    DESCRIPTION
        "The value of tmnxAncpSesStatLastChanged indicates the sysUpTime of the
         last time the counters in this row where reset (to zero).

         If no counter resets have occurred since the last re-initialization of
         the local network management subsystem, then this object contains a
         zero value."
    ::= { tmnxAncpSessionStatsEntry 1 }

tmnxAncpSesStatRxDrop            OBJECT-TYPE
    SYNTAX      Counter32
    MAX-ACCESS  read-only
    STATUS      current
    DESCRIPTION
        "The value of tmnxAncpSesStatRxDrop indicates the number of GSMP
         protocol messages that have been received and then dropped by the
         system without further processing them."
    ::= { tmnxAncpSessionStatsEntry 2 }

tmnxAncpSesStatTxDrop            OBJECT-TYPE
    SYNTAX      Counter32
    MAX-ACCESS  read-only
    STATUS      current
    DESCRIPTION
        "The value of tmnxAncpSesStatTxDrop indicates the number of GSMP
         protocol messages that were created by the system in order for them to
         be sent to the ANCP neighbor, but were never transmitted."
    ::= { tmnxAncpSessionStatsEntry 3 }

tmnxAncpSesStatRxSyn             OBJECT-TYPE
    SYNTAX      Counter32
    MAX-ACCESS  read-only
    STATUS      current
    DESCRIPTION
        "The value of tmnxAncpSesStatRxSyn indicates the number of GSMP SYN
         messages received in this ANCP session."
    ::= { tmnxAncpSessionStatsEntry 4 }

tmnxAncpSesStatTxSyn             OBJECT-TYPE
    SYNTAX      Counter32
    MAX-ACCESS  read-only
    STATUS      current
    DESCRIPTION
        "The value of tmnxAncpSesStatTxSyn indicates the number of GSMP SYN
         messages that were transmitted to the ANCP neighbor in this ANCP
         session."
    ::= { tmnxAncpSessionStatsEntry 5 }

tmnxAncpSesStatRxSynAck          OBJECT-TYPE
    SYNTAX      Counter32
    MAX-ACCESS  read-only
    STATUS      current
    DESCRIPTION
        "The value of tmnxAncpSesStatRxSynAck indicates the number of GSMP SYN
         ACK messages received in this ANCP session."
    ::= { tmnxAncpSessionStatsEntry 6 }

tmnxAncpSesStatTxSynAck          OBJECT-TYPE
    SYNTAX      Counter32
    MAX-ACCESS  read-only
    STATUS      current
    DESCRIPTION
        "The value of tmnxAncpSesStatTxSynAck indicates the number of GSMP SYN
         ACK messages that were transmitted to the ANCP neighbor in this ANCP
         session."
    ::= { tmnxAncpSessionStatsEntry 7 }

tmnxAncpSesStatRxAck             OBJECT-TYPE
    SYNTAX      Counter32
    MAX-ACCESS  read-only
    STATUS      current
    DESCRIPTION
        "The value of tmnxAncpSesStatRxAck indicates the number of GSMP ACK
         messages received in this ANCP session."
    ::= { tmnxAncpSessionStatsEntry 8 }

tmnxAncpSesStatTxAck             OBJECT-TYPE
    SYNTAX      Counter32
    MAX-ACCESS  read-only
    STATUS      current
    DESCRIPTION
        "The value of tmnxAncpSesStatTxAck indicates the number of GSMP ACK
         messages that were transmitted to the ANCP neighbor in this ANCP
         session."
    ::= { tmnxAncpSessionStatsEntry 9 }

tmnxAncpSesStatRxRstAck          OBJECT-TYPE
    SYNTAX      Counter32
    MAX-ACCESS  read-only
    STATUS      current
    DESCRIPTION
        "The value of tmnxAncpSesStatRxRstAck indicates the number of GSMP RST
         ACK messages received in this ANCP session."
    ::= { tmnxAncpSessionStatsEntry 10 }

tmnxAncpSesStatTxRstAck          OBJECT-TYPE
    SYNTAX      Counter32
    MAX-ACCESS  read-only
    STATUS      current
    DESCRIPTION
        "The value of tmnxAncpSesStatTxRstAck indicates the number of GSMP RST
         ACK messages that were transmitted to the ANCP neighbor in this
         session."
    ::= { tmnxAncpSessionStatsEntry 11 }

tmnxAncpSesStatRxPortUp          OBJECT-TYPE
    SYNTAX      Counter32
    MAX-ACCESS  read-only
    STATUS      current
    DESCRIPTION
        "The value of tmnxAncpSesStatRxPortUp indicates the number of GSMP
         'PortUp' messages received in this ANCP session."
    ::= { tmnxAncpSessionStatsEntry 12 }

tmnxAncpSesStatTxPortUp          OBJECT-TYPE
    SYNTAX      Counter32
    MAX-ACCESS  read-only
    STATUS      current
    DESCRIPTION
        "The value of tmnxAncpSesStatTxPortUp indicates the number of GSMP
         'PortUp' messages that were transmitted to the ANCP neighbor in this
         session."
    ::= { tmnxAncpSessionStatsEntry 13 }

tmnxAncpSesStatRxPortDown        OBJECT-TYPE
    SYNTAX      Counter32
    MAX-ACCESS  read-only
    STATUS      current
    DESCRIPTION
        "The value of tmnxAncpSesStatRxPortDown indicates the number of GSMP
         'PortDown' messages received in this ANCP session."
    ::= { tmnxAncpSessionStatsEntry 14 }

tmnxAncpSesStatTxPortDown        OBJECT-TYPE
    SYNTAX      Counter32
    MAX-ACCESS  read-only
    STATUS      current
    DESCRIPTION
        "The value of tmnxAncpSesStatTxPortDown indicates the number of GSMP
         'PortDown' messages that were transmitted to the ANCP neighbor in this
         session."
    ::= { tmnxAncpSessionStatsEntry 15 }

tmnxAncpSesStatRxLoopback        OBJECT-TYPE
    SYNTAX      Counter32
    MAX-ACCESS  read-only
    STATUS      current
    DESCRIPTION
        "The value of tmnxAncpSesStatRxLoopback indicates the number of GSMP
         Loopback messages received in this ANCP session."
    ::= { tmnxAncpSessionStatsEntry 16 }

tmnxAncpSesStatTxLoopback        OBJECT-TYPE
    SYNTAX      Counter32
    MAX-ACCESS  read-only
    STATUS      current
    DESCRIPTION
        "The value of tmnxAncpSesStatTxLoopback indicates the number of GSMP
         Loopback messages that were transmitted to the ANCP neighbor in this
         ANCP session."
    ::= { tmnxAncpSessionStatsEntry 17 }

tmnxAncpSapMonitorTable          OBJECT-TYPE
    SYNTAX      SEQUENCE OF TmnxAncpSapMonitorEntry
    MAX-ACCESS  not-accessible
    STATUS      current
    DESCRIPTION
        "The table tmnxAncpSapMonitorTable contains ANCP information for every
         SAP that maps on an known ANCP string."
    ::= { tmnxGsmpObjects 19 }

tmnxAncpSapMonitorEntry          OBJECT-TYPE
    SYNTAX      TmnxAncpSapMonitorEntry
    MAX-ACCESS  not-accessible
    STATUS      current
    DESCRIPTION
        "Each row contains statistics information about ANCP for every SAP that
         maps on an known ANCP string.

         Rows are created/deleted automatically by the system. The table
         contains read-only information only."
    INDEX       {
        svcId,
        sapPortId,
        sapEncapValue
    }
    ::= { tmnxAncpSapMonitorTable 1 }

TmnxAncpSapMonitorEntry          ::= SEQUENCE
{
    tmnxAncpSapMntrEgrAggRateLimit   TPIRAggRateLimitOverride,
    tmnxAncpSapMntrAncpString        TmnxAncpString,
    tmnxAncpSapMntrEgrAggRateLmt     Unsigned32
}

tmnxAncpSapMntrEgrAggRateLimit   OBJECT-TYPE
    SYNTAX      TPIRAggRateLimitOverride
    MAX-ACCESS  read-only
    STATUS      obsolete
    DESCRIPTION
        "The value of tmnxAncpSapMntrEgrAggRateLimit indicates the Qos
         Scheduler aggregate rate limit. This value is received via ANCP,
         potentially modified by the system using the ANCP policy.

         This object is obsoleted in 13.0 release and replaced by
         tmnxAncpSapMntrEgrAggRateLmt."
    ::= { tmnxAncpSapMonitorEntry 1 }

tmnxAncpSapMntrAncpString        OBJECT-TYPE
    SYNTAX      TmnxAncpString
    MAX-ACCESS  read-only
    STATUS      current
    DESCRIPTION
        "The value of tmnxAncpSapMntrAncpString indicates the ANCP-string
         received in the GSMP 'PortUp' message which contains the aggregate
         rate limit as described in tmnxAncpSapMntrEgrAggRateLmt."
    ::= { tmnxAncpSapMonitorEntry 2 }

tmnxAncpSapMntrEgrAggRateLmt     OBJECT-TYPE
    SYNTAX      Unsigned32 (1..3200000000 | 4294967295)
    MAX-ACCESS  read-only
    STATUS      current
    DESCRIPTION
        "The value of tmnxAncpSapMntrEgrAggRateLmt indicates the Qos Scheduler
         aggregate rate limit. This value is received via ANCP, potentially
         modified by the system using the ANCP policy.

         The value of 4294967295 (0xFFFFFFFF) specifies max rate and value of
         4294967294 (0xFFFFFFFE) specifies no override."
    ::= { tmnxAncpSapMonitorEntry 4 }

tmnxAncpSapIngSchedMonitorTable  OBJECT-TYPE
    SYNTAX      SEQUENCE OF TmnxAncpSapIngSchedMonitorEntry
    MAX-ACCESS  not-accessible
    STATUS      current
    DESCRIPTION
        "The table tmnxAncpSapIngSchedMonitorTable contains ANCP ingress
         information for every SAP that maps on an known ANCP string."
    ::= { tmnxGsmpObjects 20 }

tmnxAncpSapIngSchedMonitorEntry  OBJECT-TYPE
    SYNTAX      TmnxAncpSapIngSchedMonitorEntry
    MAX-ACCESS  not-accessible
    STATUS      current
    DESCRIPTION
        "Each row contains statistics information about ANCP for every SAP that
         maps on an known ANCP string.

         Rows are created/deleted automatically by the system. The table
         contains read-only information only."
    INDEX       {
        svcId,
        sapPortId,
        sapEncapValue,
        tmnxAncpSapIngMntrQosShedName
    }
    ::= { tmnxAncpSapIngSchedMonitorTable 1 }

TmnxAncpSapIngSchedMonitorEntry  ::= SEQUENCE
{
    tmnxAncpSapIngMntrQosShedName    TNamedItem,
    tmnxAncpSapIngMntrQosShedPIR     TPIRRateOverride,
    tmnxAncpSapIngMntrAncpString     TmnxAncpString,
    tmnxAncpSapIngMntrQosShedPIRHi   Unsigned32,
    tmnxAncpSapIngMntrQosShedPIRLo   Unsigned32
}

tmnxAncpSapIngMntrQosShedName    OBJECT-TYPE
    SYNTAX      TNamedItem
    MAX-ACCESS  not-accessible
    STATUS      current
    DESCRIPTION
        "The value of tmnxAncpSapIngMntrQosShedName indicates the ingress Qos
         Scheduler name (defined in the table
         TIMETRA-QOS-MIB::tVirtualSchedulerTable applied to this SAP."
    ::= { tmnxAncpSapIngSchedMonitorEntry 1 }

tmnxAncpSapIngMntrQosShedPIR     OBJECT-TYPE
    SYNTAX      TPIRRateOverride
    MAX-ACCESS  read-only
    STATUS      obsolete
    DESCRIPTION
        "The value of tmnxAncpSapIngMntrQosShedPIR indicates the ingress Qos
         Scheduler PIR (Peak Info rate). This value is received via ANCP, and
         potentially modified by the system using the ANCP policy.

         This object is obsoleted in 11.0 Release. It is replaced by
         tmnxAncpSapIngMntrQosShedPIRHi and tmnxAncpSapIngMntrQosShedPIRLo."
    ::= { tmnxAncpSapIngSchedMonitorEntry 2 }

tmnxAncpSapIngMntrAncpString     OBJECT-TYPE
    SYNTAX      TmnxAncpString
    MAX-ACCESS  read-only
    STATUS      current
    DESCRIPTION
        "The value of tmnxAncpSapIngMntrAncpString indicates the ANCP-string
         received in the GSMP 'PortUp' message which contains the PIR value as
         described in tmnxAncpSapIngMntrQosShedPIR."
    ::= { tmnxAncpSapIngSchedMonitorEntry 3 }

tmnxAncpSapIngMntrQosShedPIRHi   OBJECT-TYPE
    SYNTAX      Unsigned32 (0 | 4294967295)
    UNITS       "kilobps"
    MAX-ACCESS  read-only
    STATUS      current
    DESCRIPTION
        "The value of tmnxAncpSapIngMntrQosShedPIRHi indicates upper 32 bits of
         the ingress Qos Scheduler PIR (Peak Info rate). This value is received
         via ANCP, and potentially modified by the system using the ANCP
         policy.

         When the value of tmnxAncpSapIngMntrQosShedPIRHi along with the value
         of tmnxAncpSapIngMntrQosShedPIRLo is equal to 4294967295 (0xFFFFFFFF),
         rate for this scheduler indicates maximum rate.

         The value of tmnxAncpSapIngMntrQosShedPIRHi equal to 4294967295
         (0xFFFFFFFF) and the value of tmnxAncpSapIngMntrQosShedPIRLo equal to
         4294967294 (0xFFFFFFFE) indicates no overrides."
    ::= { tmnxAncpSapIngSchedMonitorEntry 4 }

tmnxAncpSapIngMntrQosShedPIRLo   OBJECT-TYPE
    SYNTAX      Unsigned32 (1..3200000000 | 4294967294 | 4294967295)
    UNITS       "kilobps"
    MAX-ACCESS  read-only
    STATUS      current
    DESCRIPTION
        "The value of tmnxAncpSapIngMntrQosShedPIRLo indicates lower 32 bits of
         the ingress Qos Scheduler PIR (Peak Info rate). This value is received
         via ANCP, and potentially modified by the system using the ANCP
         policy.

         When the value of tmnxAncpSapIngMntrQosShedPIRHi along with the value
         of tmnxAncpSapIngMntrQosShedPIRLo is equal to 4294967295 (0xFFFFFFFF),
         rate for this scheduler indicates maximum rate.

         The value of tmnxAncpSapIngMntrQosShedPIRHi equal to 4294967295
         (0xFFFFFFFF) and the value of tmnxAncpSapIngMntrQosShedPIRLo equal to
         4294967294 (0xFFFFFFFE) indicates no overrides."
    ::= { tmnxAncpSapIngSchedMonitorEntry 5 }

tmnxAncpSapEgrSchedMonitorTable  OBJECT-TYPE
    SYNTAX      SEQUENCE OF TmnxAncpSapEgrSchedMonitorEntry
    MAX-ACCESS  not-accessible
    STATUS      current
    DESCRIPTION
        "The table tmnxAncpSapEgrSchedMonitorTable contains ANCP ingress
         information for every SAP that maps on an known ANCP string."
    ::= { tmnxGsmpObjects 21 }

tmnxAncpSapEgrSchedMonitorEntry  OBJECT-TYPE
    SYNTAX      TmnxAncpSapEgrSchedMonitorEntry
    MAX-ACCESS  not-accessible
    STATUS      current
    DESCRIPTION
        "Each row contains statistics information about ANCP for every SAP that
         maps on an known ANCP string.

         Rows are created/deleted automatically by the system. The table
         contains read-only information only."
    INDEX       {
        svcId,
        sapPortId,
        sapEncapValue,
        tmnxAncpSapEgrMntrQosShedName
    }
    ::= { tmnxAncpSapEgrSchedMonitorTable 1 }

TmnxAncpSapEgrSchedMonitorEntry  ::= SEQUENCE
{
    tmnxAncpSapEgrMntrQosShedName    TNamedItem,
    tmnxAncpSapEgrMntrQosShedPIR     TPIRRateOverride,
    tmnxAncpSapEgrMntrAncpString     TmnxAncpString,
    tmnxAncpSapEgrMntrQosShedPIRHi   Unsigned32,
    tmnxAncpSapEgrMntrQosShedPIRLo   Unsigned32
}

tmnxAncpSapEgrMntrQosShedName    OBJECT-TYPE
    SYNTAX      TNamedItem
    MAX-ACCESS  not-accessible
    STATUS      current
    DESCRIPTION
        "The value of tmnxAncpSapEgrMntrQosShedName indicates the ingress Qos
         Scheduler name (defined in the table
         TIMETRA-QOS-MIB::tVirtualSchedulerTable applied to this SAP."
    ::= { tmnxAncpSapEgrSchedMonitorEntry 1 }

tmnxAncpSapEgrMntrQosShedPIR     OBJECT-TYPE
    SYNTAX      TPIRRateOverride
    MAX-ACCESS  read-only
    STATUS      obsolete
    DESCRIPTION
        "The value of tmnxAncpSapEgrMntrQosShedPIR indicates the ingress Qos
         Scheduler PIR (Peak Info rate). This value is received via ANCP, and
         potentially modified by the system using the ANCP policy.

         This object is obsoleted in 11.0 Release. It is replaced by
         tmnxAncpSapEgrMntrQosShedPIRHi and tmnxAncpSapEgrMntrQosShedPIRLo."
    ::= { tmnxAncpSapEgrSchedMonitorEntry 2 }

tmnxAncpSapEgrMntrAncpString     OBJECT-TYPE
    SYNTAX      TmnxAncpString
    MAX-ACCESS  read-only
    STATUS      current
    DESCRIPTION
        "The value of tmnxAncpSapEgrMntrAncpString indicates the ANCP-string
         received in the GSMP 'PortUp' message which contains the PIR value as
         described in tmnxAncpSapEgrMntrQosShedPIR."
    ::= { tmnxAncpSapEgrSchedMonitorEntry 3 }

tmnxAncpSapEgrMntrQosShedPIRHi   OBJECT-TYPE
    SYNTAX      Unsigned32 (0 | 4294967295)
    UNITS       "kilobps"
    MAX-ACCESS  read-only
    STATUS      current
    DESCRIPTION
        "The value of tmnxAncpSapEgrMntrQosShedPIRHi indicates upper 32 bits of
         the egress Qos Scheduler PIR (Peak Info rate). This value is received
         via ANCP, and potentially modified by the system using the ANCP
         policy.

         When the value of tmnxAncpSapEgrMntrQosShedPIRHi along with the value
         of tmnxAncpSapEgrMntrQosShedPIRLo is equal to 4294967295 (0xFFFFFFFF),
         rate for this scheduler indicates maximum rate.

         The value of tmnxAncpSapEgrMntrQosShedPIRHi equal to 4294967295
         (0xFFFFFFFF) and the value of tmnxAncpSapEgrMntrQosShedPIRLo equal to
         4294967294 (0xFFFFFFFE) indicates no overrides."
    ::= { tmnxAncpSapEgrSchedMonitorEntry 4 }

tmnxAncpSapEgrMntrQosShedPIRLo   OBJECT-TYPE
    SYNTAX      Unsigned32 (1..3200000000 | 4294967294 | 4294967295)
    UNITS       "kilobps"
    MAX-ACCESS  read-only
    STATUS      current
    DESCRIPTION
        "The value of tmnxAncpSapEgrMntrQosShedPIRLo indicates lower 32 bits of
         the egress Qos Scheduler PIR (Peak Info rate). This value is received
         via ANCP, and potentially modified by the system using the ANCP
         policy.

         When the value of tmnxAncpSapIngMntrQosShedPIRHi along with the value
         of tmnxAncpSapIngMntrQosShedPIRLo is equal to 4294967295 (0xFFFFFFFF),
         rate for this scheduler indicates maximum rate.

         The value of tmnxAncpSapIngMntrQosShedPIRHi equal to 4294967295
         (0xFFFFFFFF) and the value of tmnxAncpSapIngMntrQosShedPIRLo equal to
         4294967294 (0xFFFFFFFE) indicates no overrides."
    ::= { tmnxAncpSapEgrSchedMonitorEntry 5 }

tmnxAncpMssMonitorTable          OBJECT-TYPE
    SYNTAX      SEQUENCE OF TmnxAncpMssMonitorEntry
    MAX-ACCESS  not-accessible
    STATUS      current
    DESCRIPTION
        "The table tmnxAncpMssMonitorTable contains ANCP information for every
         MSS that maps on an known ANCP string."
    ::= { tmnxGsmpObjects 22 }

tmnxAncpMssMonitorEntry          OBJECT-TYPE
    SYNTAX      TmnxAncpMssMonitorEntry
    MAX-ACCESS  not-accessible
    STATUS      current
    DESCRIPTION
        "Each row contains statistics information about ANCP for every MSS that
         maps on an known ANCP string.

         Rows are created/deleted automatically by the system. The table
         contains read-only information only."
    INDEX       {
        custId,
        custMultSvcSiteName
    }
    ::= { tmnxAncpMssMonitorTable 1 }

TmnxAncpMssMonitorEntry          ::= SEQUENCE
{
    tmnxAncpMssMntrEgrAggRateLimit   TPIRAggRateLimitOverride,
    tmnxAncpMssMntrAncpString        TmnxAncpString,
    tmnxAncpMssMntrEgrAggRateLmt     Unsigned32
}

tmnxAncpMssMntrEgrAggRateLimit   OBJECT-TYPE
    SYNTAX      TPIRAggRateLimitOverride
    MAX-ACCESS  read-only
    STATUS      obsolete
    DESCRIPTION
        "The value of tmnxAncpMssMntrEgrAggRateLimit indicates the Qos
         Scheduler rate limit. This value is received via ANCP, potentially
         modified by the system using the ANCP policy.

         This object is obsoleted in 13.0 release and replaced by
         tmnxAncpMssMntrEgrAggRateLmt."
    ::= { tmnxAncpMssMonitorEntry 1 }

tmnxAncpMssMntrAncpString        OBJECT-TYPE
    SYNTAX      TmnxAncpString
    MAX-ACCESS  read-only
    STATUS      current
    DESCRIPTION
        "The value of tmnxAncpMssMntrAncpString indicates the ANCP-string
         received in the GSMP 'PortUp' message which contains the Scheduler
         rate limit as described in tmnxAncpMssMntrEgrAggRateLmt."
    ::= { tmnxAncpMssMonitorEntry 2 }

tmnxAncpMssMntrEgrAggRateLmt     OBJECT-TYPE
    SYNTAX      Unsigned32 (1..3200000000 | 4294967295)
    MAX-ACCESS  read-only
    STATUS      current
    DESCRIPTION
        "The value of tmnxAncpMssMntrEgrAggRateLmt indicates the Qos Scheduler
         aggregate rate limit. This value is received via ANCP, potentially
         modified by the system using the ANCP policy.

         The value of 4294967295 (0xFFFFFFFF) specifies max rate and value of
         4294967294 (0xFFFFFFFE) specifies no override."
    ::= { tmnxAncpMssMonitorEntry 4 }

tmnxAncpMssIngMonitorTable       OBJECT-TYPE
    SYNTAX      SEQUENCE OF TmnxAncpMssIngMonitorEntry
    MAX-ACCESS  not-accessible
    STATUS      current
    DESCRIPTION
        "The table tmnxAncpMssIngMonitorTable contains ingress ANCP information
         for every MSS that maps on an known ANCP string."
    ::= { tmnxGsmpObjects 23 }

tmnxAncpMssIngMonitorEntry       OBJECT-TYPE
    SYNTAX      TmnxAncpMssIngMonitorEntry
    MAX-ACCESS  not-accessible
    STATUS      current
    DESCRIPTION
        "Each row contains statistics information about ANCP for every MSS that
         maps on an known ANCP string.

         Rows are created/deleted automatically by the system. The table
         contains read-only information only."
    INDEX       {
        custId,
        custMultSvcSiteName,
        tmnxAncpMssIngMntrQosShedName
    }
    ::= { tmnxAncpMssIngMonitorTable 1 }

TmnxAncpMssIngMonitorEntry       ::= SEQUENCE
{
    tmnxAncpMssIngMntrQosShedName    TNamedItem,
    tmnxAncpMssIngMntrQosShedPIR     TPIRRateOverride,
    tmnxAncpMssIngMntrAncpString     TmnxAncpString,
    tmnxAncpMssIngMntrQosShedPIRHi   Unsigned32,
    tmnxAncpMssIngMntrQosShedPIRLo   Unsigned32
}

tmnxAncpMssIngMntrQosShedName    OBJECT-TYPE
    SYNTAX      TNamedItem
    MAX-ACCESS  not-accessible
    STATUS      current
    DESCRIPTION
        "The value of tmnxAncpMssIngMntrQosShedName indicates the ingress Qos
         Scheduler name (defined in the table
         TIMETRA-QOS-MIB::tVirtualSchedulerTable applied to this MSS."
    ::= { tmnxAncpMssIngMonitorEntry 1 }

tmnxAncpMssIngMntrQosShedPIR     OBJECT-TYPE
    SYNTAX      TPIRRateOverride
    MAX-ACCESS  read-only
    STATUS      obsolete
    DESCRIPTION
        "The value of tmnxAncpMssIngMntrQosShedPIR indicates the ingress Qos
         Scheduler PIR (Peak Info rate). This value is received via ANCP, and
         potentially modified by the system using the ANCP policy.

         This object is obsoleted in 11.0 Release. It is replaced by
         tmnxAncpMssIngMntrQosShedPIRHi and tmnxAncpMssIngMntrQosShedPIRLo."
    ::= { tmnxAncpMssIngMonitorEntry 2 }

tmnxAncpMssIngMntrAncpString     OBJECT-TYPE
    SYNTAX      TmnxAncpString
    MAX-ACCESS  read-only
    STATUS      current
    DESCRIPTION
        "The value of tmnxAncpMssIngMntrAncpString indicates the ANCP-string
         received in the GSMP 'PortUp' message which contains the PIR value as
         described in tmnxAncpMssIngMntrQosShedPIR."
    ::= { tmnxAncpMssIngMonitorEntry 3 }

tmnxAncpMssIngMntrQosShedPIRHi   OBJECT-TYPE
    SYNTAX      Unsigned32 (0 | 4294967295)
    UNITS       "kilobps"
    MAX-ACCESS  read-only
    STATUS      current
    DESCRIPTION
        "The value of tmnxAncpMssIngMntrQosShedPIRHi indicates upper 32 bits of
         the ingress Qos Scheduler PIR (Peak Info rate). This value is received
         via ANCP, and potentially modified by the system using the ANCP
         policy.

         When the value of tmnxAncpMssIngMntrQosShedPIRHi along with the value
         of tmnxAncpMssIngMntrQosShedPIRLo is equal to 4294967295 (0xFFFFFFFF),
         rate for this scheduler indicates maximum rate.

         The value of tmnxAncpMssIngMntrQosShedPIRHi equal to 4294967295
         (0xFFFFFFFF) and the value of tmnxAncpMssIngMntrQosShedPIRLo equal to
         4294967294 (0xFFFFFFFE) indicates no overrides."
    ::= { tmnxAncpMssIngMonitorEntry 4 }

tmnxAncpMssIngMntrQosShedPIRLo   OBJECT-TYPE
    SYNTAX      Unsigned32 (1..3200000000 | 4294967294 | 4294967295)
    UNITS       "kilobps"
    MAX-ACCESS  read-only
    STATUS      current
    DESCRIPTION
        "The value of tmnxAncpMssIngMntrQosShedPIRLo indicates lower 32 bits of
         the ingress Qos Scheduler PIR (Peak Info rate). This value is received
         via ANCP, and potentially modified by the system using the ANCP
         policy.

         When the value of tmnxAncpMssIngMntrQosShedPIRHi along with the value
         of tmnxAncpMssIngMntrQosShedPIRLo is equal to 4294967295 (0xFFFFFFFF),
         rate for this scheduler indicates maximum rate.

         The value of tmnxAncpMssIngMntrQosShedPIRHi equal to 4294967295
         (0xFFFFFFFF) and the value of tmnxAncpMssIngMntrQosShedPIRLo equal to
         4294967294 (0xFFFFFFFE) indicates no overrides."
    ::= { tmnxAncpMssIngMonitorEntry 5 }

tmnxAncpMssEgrMonitorTable       OBJECT-TYPE
    SYNTAX      SEQUENCE OF TmnxAncpMssEgrMonitorEntry
    MAX-ACCESS  not-accessible
    STATUS      current
    DESCRIPTION
        "The table tmnxAncpMssEgrMonitorTable contains ingress ANCP information
         for every MSS that maps on an known ANCP string."
    ::= { tmnxGsmpObjects 24 }

tmnxAncpMssEgrMonitorEntry       OBJECT-TYPE
    SYNTAX      TmnxAncpMssEgrMonitorEntry
    MAX-ACCESS  not-accessible
    STATUS      current
    DESCRIPTION
        "Each row contains statistics information about ANCP for every MSS that
         maps on an known ANCP string.

         Rows are created/deleted automatically by the system. The table
         contains read-only information only."
    INDEX       {
        custId,
        custMultSvcSiteName,
        tmnxAncpMssEgrMntrQosShedName
    }
    ::= { tmnxAncpMssEgrMonitorTable 1 }

TmnxAncpMssEgrMonitorEntry       ::= SEQUENCE
{
    tmnxAncpMssEgrMntrQosShedName    TNamedItem,
    tmnxAncpMssEgrMntrQosShedPIR     TPIRRateOverride,
    tmnxAncpMssEgrMntrAncpString     TmnxAncpString,
    tmnxAncpMssEgrMntrQosShedPIRHi   Unsigned32,
    tmnxAncpMssEgrMntrQosShedPIRLo   Unsigned32
}

tmnxAncpMssEgrMntrQosShedName    OBJECT-TYPE
    SYNTAX      TNamedItem
    MAX-ACCESS  not-accessible
    STATUS      current
    DESCRIPTION
        "The value of tmnxAncpMssEgrMntrQosShedName indicates the ingress Qos
         Scheduler name (defined in the table
         TIMETRA-QOS-MIB::tVirtualSchedulerTable applied to this MSS."
    ::= { tmnxAncpMssEgrMonitorEntry 1 }

tmnxAncpMssEgrMntrQosShedPIR     OBJECT-TYPE
    SYNTAX      TPIRRateOverride
    MAX-ACCESS  read-only
    STATUS      obsolete
    DESCRIPTION
        "The value of tmnxAncpMssEgrMntrQosShedPIR indicates the ingress Qos
         Scheduler PIR (Peak Info rate). This value is received via ANCP, and
         potentially modified by the system using the ANCP policy.

         This object is obsoleted in 11.0 Release. It is replaced by
         tmnxAncpMssEgrMntrQosShedPIRHi and tmnxAncpMssEgrMntrQosShedPIRLo."
    ::= { tmnxAncpMssEgrMonitorEntry 2 }

tmnxAncpMssEgrMntrAncpString     OBJECT-TYPE
    SYNTAX      TmnxAncpString
    MAX-ACCESS  read-only
    STATUS      current
    DESCRIPTION
        "The value of tmnxAncpMssEgrMntrAncpString indicates the ANCP-string
         received in the GSMP 'PortUp' message which contains the PIR value as
         described in tmnxAncpMssEgrMntrQosShedPIR."
    ::= { tmnxAncpMssEgrMonitorEntry 3 }

tmnxAncpMssEgrMntrQosShedPIRHi   OBJECT-TYPE
    SYNTAX      Unsigned32 (0 | 4294967295)
    UNITS       "kilobps"
    MAX-ACCESS  read-only
    STATUS      current
    DESCRIPTION
        "The value of tmnxAncpMssEgrMntrQosShedPIRHi indicates upper 32 bits of
         the egress Qos Scheduler PIR (Peak Info rate). This value is received
         via ANCP, and potentially modified by the system using the ANCP
         policy.

         When the value of tmnxAncpMssEgrMntrQosShedPIRHi along with the value
         of tmnxAncpMssEgrMntrQosShedPIRLo is equal to 4294967295 (0xFFFFFFFF),
         rate for this scheduler indicates maximum rate.

         The value of tmnxAncpMssEgrMntrQosShedPIRHi equal to 4294967295
         (0xFFFFFFFF) and the value of tmnxAncpMssEgrMntrQosShedPIRLo equal to
         4294967294 (0xFFFFFFFE) indicates no overrides."
    ::= { tmnxAncpMssEgrMonitorEntry 4 }

tmnxAncpMssEgrMntrQosShedPIRLo   OBJECT-TYPE
    SYNTAX      Unsigned32 (1..3200000000 | 4294967294 | 4294967295)
    UNITS       "kilobps"
    MAX-ACCESS  read-only
    STATUS      current
    DESCRIPTION
        "The value of tmnxAncpMssEgrMntrQosShedPIRLo indicates lower 32 bits of
         the egress Qos Scheduler PIR (Peak Info rate). This value is received
         via ANCP, and potentially modified by the system using the ANCP
         policy.

         When the value of tmnxAncpMssEgrMntrQosShedPIRHi along with the value
         of tmnxAncpMssEgrMntrQosShedPIRLo is equal to 4294967295 (0xFFFFFFFF),
         rate for this scheduler indicates maximum rate.

         The value of tmnxAncpMssEgrMntrQosShedPIRHi equal to 4294967295
         (0xFFFFFFFF) and the value of tmnxAncpMssEgrMntrQosShedPIRLo equal to
         4294967294 (0xFFFFFFFE) indicates no overrides."
    ::= { tmnxAncpMssEgrMonitorEntry 5 }

tmnxAncpSubMonitorTable          OBJECT-TYPE
    SYNTAX      SEQUENCE OF TmnxAncpSubMonitorEntry
    MAX-ACCESS  not-accessible
    STATUS      current
    DESCRIPTION
        "The table tmnxAncpSubMonitorTable contains ANCP information for every
         subscriber that maps on an known ANCP string."
    ::= { tmnxGsmpObjects 25 }

tmnxAncpSubMonitorEntry          OBJECT-TYPE
    SYNTAX      TmnxAncpSubMonitorEntry
    MAX-ACCESS  not-accessible
    STATUS      current
    DESCRIPTION
        "Each row contains statistics information about ANCP for every
         subscriber that maps on an known ANCP string.

         Rows are created/deleted automatically by the system. The table
         contains read-only information only."
    INDEX       { IMPLIED tmnxSubInfoSubIdent }
    ::= { tmnxAncpSubMonitorTable 1 }

TmnxAncpSubMonitorEntry          ::= SEQUENCE
{
    tmnxAncpSubMntrIngQosShedName    TNamedItem,
    tmnxAncpSubMntrIngQosShedPIR     TPIRRateOverride,
    tmnxAncpSubMntrEgrQosShedName    TNamedItem,
    tmnxAncpSubMntrEgrQosShedPIR     TPIRRateOverride,
    tmnxAncpSubMntrEgrAggRateLimit   TPIRAggRateLimitOverride,
    tmnxAncpSubMntrIngQosShedPIRHi   Unsigned32,
    tmnxAncpSubMntrIngQosShedPIRLo   Unsigned32,
    tmnxAncpSubMntrEgrQosShedPIRHi   Unsigned32,
    tmnxAncpSubMntrEgrQosShedPIRLo   Unsigned32
}

tmnxAncpSubMntrIngQosShedName    OBJECT-TYPE
    SYNTAX      TNamedItem
    MAX-ACCESS  read-only
    STATUS      current
    DESCRIPTION
        "The value of tmnxAncpSubMntrIngQosShedName indicates the ingress Qos
         Scheduler name (defined in the table
         TIMETRA-QOS-MIB::tVirtualSchedulerTable applied to this subscriber."
    ::= { tmnxAncpSubMonitorEntry 1 }

tmnxAncpSubMntrIngQosShedPIR     OBJECT-TYPE
    SYNTAX      TPIRRateOverride
    MAX-ACCESS  read-only
    STATUS      obsolete
    DESCRIPTION
        "The value of tmnxAncpSubMntrIngQosShedPIR indicates the ingress Qos
         Scheduler PIR (Peak Info rate). This value is received via ANCP, and
         potentially modified by the system using the ANCP policy.

         This object is obsoleted in 11.0 Release. It is replaced by
         tmnxAncpSubMntrIngQosShedPIRHi and tmnxAncpSubMntrIngQosShedPIRLo."
    ::= { tmnxAncpSubMonitorEntry 2 }

tmnxAncpSubMntrEgrQosShedName    OBJECT-TYPE
    SYNTAX      TNamedItem
    MAX-ACCESS  read-only
    STATUS      current
    DESCRIPTION
        "The value of tmnxAncpSubMntrEgrQosShedName indicates the egress Qos
         Scheduler name (defined in the table
         TIMETRA-QOS-MIB::tVirtualSchedulerTable applied to this subscriber."
    ::= { tmnxAncpSubMonitorEntry 3 }

tmnxAncpSubMntrEgrQosShedPIR     OBJECT-TYPE
    SYNTAX      TPIRRateOverride
    MAX-ACCESS  read-only
    STATUS      obsolete
    DESCRIPTION
        "The value of tmnxAncpSubMntrEgrQosShedPIR indicates the egress Qos
         Scheduler PIR (Peak Info rate). This value is received via ANCP, and
         potentially modified by the system using the ANCP policy.

         This object is obsoleted in 11.0 Release. It is replaced by
         tmnxAncpSubMntrEgrQosShedPIRHi and tmnxAncpSubMntrEgrQosShedPIRLo."
    ::= { tmnxAncpSubMonitorEntry 4 }

tmnxAncpSubMntrEgrAggRateLimit   OBJECT-TYPE
    SYNTAX      TPIRAggRateLimitOverride
    MAX-ACCESS  read-only
    STATUS      current
    DESCRIPTION
        "The value of tmnxAncpSubMntrEgrAggRateLimit indicates the Qos
         Scheduler rate limit. This value is received via ANCP, potentially
         modified by the system using the ANCP policy."
    ::= { tmnxAncpSubMonitorEntry 5 }

tmnxAncpSubMntrIngQosShedPIRHi   OBJECT-TYPE
    SYNTAX      Unsigned32 (0 | 4294967295)
    UNITS       "kilobps"
    MAX-ACCESS  read-only
    STATUS      current
    DESCRIPTION
        "The value of tmnxAncpSubMntrIngQosShedPIRHi indicates upper 32 bits of
         the ingress Qos Scheduler PIR (Peak Info rate). This value is received
         via ANCP, and potentially modified by the system using the ANCP
         policy.

         When the value of tmnxAncpSubMntrIngQosShedPIRHi along with the value
         of tmnxAncpSubMntrIngQosShedPIRLo is equal to 4294967295 (0xFFFFFFFF),
         rate for this scheduler indicates maximum rate.

         The value of tmnxAncpSubMntrIngQosShedPIRHi equal to 4294967295
         (0xFFFFFFFF) and the value of tmnxAncpSubMntrIngQosShedPIRLo equal to
         4294967294 (0xFFFFFFFE) indicates no overrides."
    ::= { tmnxAncpSubMonitorEntry 6 }

tmnxAncpSubMntrIngQosShedPIRLo   OBJECT-TYPE
    SYNTAX      Unsigned32 (1..3200000000 | 4294967294 | 4294967295)
    UNITS       "kilobps"
    MAX-ACCESS  read-only
    STATUS      current
    DESCRIPTION
        "The value of tmnxAncpSubMntrIngQosShedPIRLo indicates lower 32 bits of
         the ingress Qos Scheduler PIR (Peak Info rate). This value is received
         via ANCP, and potentially modified by the system using the ANCP
         policy.

         When the value of tmnxAncpSubMntrIngQosShedPIRHi along with the value
         of tmnxAncpSubMntrIngQosShedPIRLo is equal to 4294967295 (0xFFFFFFFF),
         rate for this scheduler indicates maximum rate.

         The value of tmnxAncpSubMntrIngQosShedPIRHi equal to 4294967295
         (0xFFFFFFFF) and the value of tmnxAncpSubMntrIngQosShedPIRLo equal to
         4294967294 (0xFFFFFFFE) indicates no overrides."
    ::= { tmnxAncpSubMonitorEntry 7 }

tmnxAncpSubMntrEgrQosShedPIRHi   OBJECT-TYPE
    SYNTAX      Unsigned32 (0 | 4294967295)
    UNITS       "kilobps"
    MAX-ACCESS  read-only
    STATUS      current
    DESCRIPTION
        "The value of tmnxAncpSubMntrEgrQosShedPIRHi indicates upper 32 bits of
         the egress Qos Scheduler PIR (Peak Info rate). This value is received
         via ANCP, and potentially modified by the system using the ANCP
         policy.

         When the value of tmnxAncpSubMntrEgrQosShedPIRHi along with the value
         of tmnxAncpSubMntrEgrQosShedPIRLo is equal to 4294967295 (0xFFFFFFFF),
         rate for this scheduler indicates maximum rate.

         The value of tmnxAncpSubMntrEgrQosShedPIRHi equal to 4294967295
         (0xFFFFFFFF) and the value of tmnxAncpSubMntrEgrQosShedPIRLo equal to
         4294967294 (0xFFFFFFFE) indicates no overrides."
    ::= { tmnxAncpSubMonitorEntry 8 }

tmnxAncpSubMntrEgrQosShedPIRLo   OBJECT-TYPE
    SYNTAX      Unsigned32 (1..3200000000 | 4294967294 | 4294967295)
    UNITS       "kilobps"
    MAX-ACCESS  read-only
    STATUS      current
    DESCRIPTION
        "The value of tmnxAncpSubMntrEgrQosShedPIRLo indicates lower 32 bits of
         the egress Qos Scheduler PIR (Peak Info rate). This value is received
         via ANCP, and potentially modified by the system using the ANCP
         policy.

         When the value of tmnxAncpSubMntrEgrQosShedPIRHi along with the value
         of tmnxAncpSubMntrEgrQosShedPIRLo is equal to 4294967295 (0xFFFFFFFF),
         rate for this scheduler indicates maximum rate.

         The value of tmnxAncpSubMntrEgrQosShedPIRHi equal to 4294967295
         (0xFFFFFFFF) and the value of tmnxAncpSubMntrEgrQosShedPIRLo equal to
         4294967294 (0xFFFFFFFE) indicates no overrides."
    ::= { tmnxAncpSubMonitorEntry 9 }

tmnxAncpStringDslLineInfoTable   OBJECT-TYPE
    SYNTAX      SEQUENCE OF TmnxAncpStringDslLineInfoEntry
    MAX-ACCESS  not-accessible
    STATUS      current
    DESCRIPTION
        "The table tmnxAncpStringDslLineInfoTable contains DSL line information
         about all ANCP-strings known to the system."
    ::= { tmnxGsmpObjects 26 }

tmnxAncpStringDslLineInfoEntry   OBJECT-TYPE
    SYNTAX      TmnxAncpStringDslLineInfoEntry
    MAX-ACCESS  not-accessible
    STATUS      current
    DESCRIPTION
        "Each row contains DSL line information about an ANCP-string known to
         the system. Rows are created/deleted automatically by the system.

         The table contains read-only information only."
    INDEX       {
        tmnxAncpStringLineInfoAncpString,
        tmnxAncpStringLineInfoType
    }
    ::= { tmnxAncpStringDslLineInfoTable 1 }

TmnxAncpStringDslLineInfoEntry   ::= SEQUENCE
{
    tmnxAncpStringLineInfoAncpString DisplayString,
    tmnxAncpStringLineInfoType       INTEGER,
    tmnxAncpStringLineInfoValue      Unsigned32
}

tmnxAncpStringLineInfoAncpString OBJECT-TYPE
    SYNTAX      DisplayString (SIZE (1..64))
    MAX-ACCESS  not-accessible
    STATUS      current
    DESCRIPTION
        "The value of tmnxAncpStringLineInfoAncpString indicates the
         ANCP-string for which this row entry contains information."
    ::= { tmnxAncpStringDslLineInfoEntry 1 }

tmnxAncpStringLineInfoType       OBJECT-TYPE
    SYNTAX      INTEGER {
        actualNetDataRateUpstream            (129),
        actualNetDataRateDownstream          (130),
        minimumNetDataRateUpstream           (131),
        minimumNetDataRateDownstream         (132),
        attainableNetDataRateUpstream        (133),
        attainableNetDataRateDownstream      (134),
        maximumNetDataRateUpstream           (135),
        maximumNetDataRateDownstream         (136),
        minimumNetLowPowerDataRateUpstream   (137),
        minimumNetLowPowerDataRateDownstream (138),
        maximumInterleavingDelayUpstream     (139),
        actualInterleavingDelayUpstream      (140),
        maximumInterleavingDelayDownstream   (141),
        actualInterleavingDelayDownstream    (142),
        dslLineState                         (143),
        accessLoopEncapsulation              (144),
        dslType                              (145)
    }
    MAX-ACCESS  not-accessible
    STATUS      current
    DESCRIPTION
        "The value of tmnxAncpStringLineInfoType indicates the type of the DSL
         line information attribute for which this row entry contains
         information."
    ::= { tmnxAncpStringDslLineInfoEntry 2 }

tmnxAncpStringLineInfoValue      OBJECT-TYPE
    SYNTAX      Unsigned32
    MAX-ACCESS  read-only
    STATUS      current
    DESCRIPTION
        "The value of tmnxAncpStringLineInfoValue contains the value of the DSL
         line information attribute for which this row entry contains
         information."
    ::= { tmnxAncpStringDslLineInfoEntry 3 }

tmnxGsmpCompliance               OBJECT IDENTIFIER ::= { tmnxSRConfs 39 }

tmnxGsmpCompliances              OBJECT IDENTIFIER ::= { tmnxGsmpCompliance 1 }

tmnxGsmpV5v0MIBCompliance        MODULE-COMPLIANCE
    STATUS      obsolete
    DESCRIPTION
        "The compliance statement for GSMP objects in TIMETRA-GSMP-MIB."
    MODULE
        MANDATORY-GROUPS {
            tmnxGsmpV5v0Group,
            tmnxGsmpV5v0GNotificationGroup
        }
    ::= { tmnxGsmpCompliances 1 }

tmnxGsmpV11v0MIBCompliance       MODULE-COMPLIANCE
    STATUS      obsolete
    DESCRIPTION
        "The compliance statement for GSMP objects in TIMETRA-GSMP-MIB on Nokia
         7x50 SR series systems release 11.0."
    MODULE
        MANDATORY-GROUPS {
            tmnxGsmpV11v0Group,
            tmnxGsmpV5v0GNotificationGroup,
            tmnxGsmpSchedulerRateV11v0Group
        }
    ::= { tmnxGsmpCompliances 2 }

tmnxGsmpV13v0MIBCompliance       MODULE-COMPLIANCE
    STATUS      current
    DESCRIPTION
        "The compliance statement for GSMP objects in TIMETRA-GSMP-MIB on Nokia
         7x50 SR series systems release 13.0."
    MODULE
        MANDATORY-GROUPS {
            tmnxGsmpV5v0GNotificationGroup,
            tmnxGsmpSchedulerRateV11v0Group,
            tmnxGsmpQosV13v0Group,
            tmnxGsmpV13v0Group
        }
    ::= { tmnxGsmpCompliances 4 }

tmnxGsmpGroups                   OBJECT IDENTIFIER ::= { tmnxGsmpCompliance 2 }

tmnxGsmpV5v0Group                OBJECT-GROUP
    OBJECTS     {
        tmnxGsmpConfigTableLastChange,
        tmnxGsmpGroupConfigTableLastChange,
        tmnxGsmpGroupNbrTableLastChange,
        tmnxAncpStaticMapSapTblLastChg,
        tmnxAncpStaticMapMssTblLastChg,
        tmnxAncpSubProfileTblLastChange,
        tmnxAncpPolicyTableLastChange,
        tmnxGsmpCfgLastChange,
        tmnxGsmpCfgAdminState,
        tmnxGsmpGrpCfgLastChange,
        tmnxGsmpGrpCfgRowStatus,
        tmnxGsmpGrpCfgAdminState,
        tmnxGsmpGrpCfgKeepalive,
        tmnxGsmpGrpCfgHoldMultiplier,
        tmnxGsmpGrpCfgDescription,
        tmnxGsmpGrpCfgAncpOamCap,
        tmnxGsmpGrpCfgAncpDynTopoDiscCap,
        tmnxGsmpGrpNbrLastChange,
        tmnxGsmpGrpNbrRowStatus,
        tmnxGsmpGrpNbrAdminState,
        tmnxGsmpGrpNbrLocalAddrType,
        tmnxGsmpGrpNbrLocalAddr,
        tmnxGsmpGrpNbrDescription,
        tmnxGsmpGrpNbrPrioMarkType,
        tmnxGsmpGrpNbrPrioMarkPrec,
        tmnxGsmpGrpNbrPrioMarkDscp,
        tmnxAncpStaticMapSapLastChange,
        tmnxAncpStaticMapSapRowStatus,
        tmnxAncpStaticMapSapAncpPolName,
        tmnxAncpStaticMapMssLastChange,
        tmnxAncpStaticMapMssRowStatus,
        tmnxAncpStaticMapMssAncpPolName,
        tmnxAncpSubProfileAncpPolicy,
        tmnxAncpPlcyLastChange,
        tmnxAncpPlcyRowStatus,
        tmnxAncpPlcyIngRateAdjustment,
        tmnxAncpPlcyIngRateReduction,
        tmnxAncpPlcyIngRateMonitor,
        tmnxAncpPlcyIngRateMonitorNtf,
        tmnxAncpPlcyIngRateModType,
        tmnxAncpPlcyIngRateModSched,
        tmnxAncpPlcyEgrRateAdjustment,
        tmnxAncpPlcyEgrRateReduction,
        tmnxAncpPlcyEgrRateMonitor,
        tmnxAncpPlcyEgrRateMonitorNtf,
        tmnxAncpPlcyEgrRateModType,
        tmnxAncpPlcyEgrRateModSched,
        tmnxAncpPlcyDisableShcv,
        tmnxAncpPlcyDisableShcvHldTime,
        tmnxAncpPlcyDisableShcvNtf,
        tmnxAncpStrInfAssociation,
        tmnxAncpStrInfSapPortId,
        tmnxAncpStrInfSapEncapValue,
        tmnxAncpStrInfMultSvcSiteName,
        tmnxAncpStrInfMultSvcSiteCust,
        tmnxAncpStrInfSubscrIdent,
        tmnxAncpStrInfLineState,
        tmnxAncpStrInfAncpPolicyName,
        tmnxAncpStrInfIngrRate,
        tmnxAncpStrInfAdjustedIngrRate,
        tmnxAncpStrInfEgrRate,
        tmnxAncpStrInfAdjustedEgrRate,
        tmnxAncpStrInfServId,
        tmnxAncpStrInfNeighborAddrType,
        tmnxAncpStrInfNeighborAddr,
        tmnxAncpStrInfTcpPort,
        tmnxAncpStrInfGroupName,
        tmnxAncpSesNbrPeerInstance,
        tmnxAncpSesNbrPeerPort,
        tmnxAncpSesNbrPeerName,
        tmnxAncpSesSenderInstance,
        tmnxAncpSesSenderPort,
        tmnxAncpSesSenderName,
        tmnxAncpSesNbrTimeouts,
        tmnxAncpSesNbrMaxNbrOfTimeouts,
        tmnxAncpSesNbrTimer,
        tmnxAncpSesSenderTimer,
        tmnxAncpSesNegotiatedCaps,
        tmnxAncpSesConfiguredCaps,
        tmnxAncpSesGroupName,
        tmnxAncpSesState,
        tmnxAncpSesLocalAddrType,
        tmnxAncpSesLocalAddr,
        tmnxAncpSesStatLastChanged,
        tmnxAncpSesStatRxDrop,
        tmnxAncpSesStatTxDrop,
        tmnxAncpSesStatRxSyn,
        tmnxAncpSesStatTxSyn,
        tmnxAncpSesStatRxSynAck,
        tmnxAncpSesStatTxSynAck,
        tmnxAncpSesStatRxAck,
        tmnxAncpSesStatTxAck,
        tmnxAncpSesStatRxRstAck,
        tmnxAncpSesStatTxRstAck,
        tmnxAncpSesStatRxPortUp,
        tmnxAncpSesStatTxPortUp,
        tmnxAncpSesStatRxPortDown,
        tmnxAncpSesStatTxPortDown,
        tmnxAncpSesStatRxLoopback,
        tmnxAncpSesStatTxLoopback,
        tmnxAncpSapMntrEgrAggRateLimit,
        tmnxAncpSapMntrAncpString,
        tmnxAncpSapIngMntrQosShedPIR,
        tmnxAncpSapIngMntrAncpString,
        tmnxAncpSapEgrMntrQosShedPIR,
        tmnxAncpSapEgrMntrAncpString,
        tmnxAncpMssMntrEgrAggRateLimit,
        tmnxAncpMssMntrAncpString,
        tmnxAncpMssIngMntrQosShedPIR,
        tmnxAncpMssIngMntrAncpString,
        tmnxAncpMssEgrMntrQosShedPIR,
        tmnxAncpMssEgrMntrAncpString,
        tmnxAncpSubMntrIngQosShedName,
        tmnxAncpSubMntrIngQosShedPIR,
        tmnxAncpSubMntrEgrQosShedName,
        tmnxAncpSubMntrEgrQosShedPIR,
        tmnxAncpSubMntrEgrAggRateLimit
    }
    STATUS      obsolete
    DESCRIPTION
        "The group of objects supporting management of the GSMP feature on
         Nokia 7x50 SR series systems."
    ::= { tmnxGsmpGroups 1 }

tmnxGsmpV5v0GNotificationGroup   NOTIFICATION-GROUP
    NOTIFICATIONS {
        tmnxAncpIngRateMonitorEvent,
        tmnxAncpEgrRateMonitorEvent,
        tmnxAncpShcvDisabledEvent,
        tmnxAncpSesRejected,
        tmnxAncpStringRejected
    }
    STATUS      current
    DESCRIPTION
        "The group of notifications supporting management of the GSMP feature
         on Nokia 7x50 SR series systems."
    ::= { tmnxGsmpGroups 2 }

tmnxGsmpNotificationObjV5v0Group OBJECT-GROUP
    OBJECTS     {
        tmnxNotifAncpString,
        tmnxNotifAncpPolicyName,
        tmnxNotifAncpPlcyActualRate,
        tmnxAncpRejectReason
    }
    STATUS      current
    DESCRIPTION
        "The group of objects supporting management of GSMP notification
         objects on Nokia 7x50 SR series systems."
    ::= { tmnxGsmpGroups 3 }

tmnxGsmpV11v0Group               OBJECT-GROUP
    OBJECTS     {
        tmnxGsmpConfigTableLastChange,
        tmnxGsmpGroupConfigTableLastChange,
        tmnxGsmpGroupNbrTableLastChange,
        tmnxAncpStaticMapSapTblLastChg,
        tmnxAncpStaticMapMssTblLastChg,
        tmnxAncpSubProfileTblLastChange,
        tmnxAncpPolicyTableLastChange,
        tmnxGsmpCfgLastChange,
        tmnxGsmpCfgAdminState,
        tmnxGsmpGrpCfgLastChange,
        tmnxGsmpGrpCfgRowStatus,
        tmnxGsmpGrpCfgAdminState,
        tmnxGsmpGrpCfgKeepalive,
        tmnxGsmpGrpCfgHoldMultiplier,
        tmnxGsmpGrpCfgDescription,
        tmnxGsmpGrpCfgAncpOamCap,
        tmnxGsmpGrpCfgAncpDynTopoDiscCap,
        tmnxGsmpGrpNbrLastChange,
        tmnxGsmpGrpNbrRowStatus,
        tmnxGsmpGrpNbrAdminState,
        tmnxGsmpGrpNbrLocalAddrType,
        tmnxGsmpGrpNbrLocalAddr,
        tmnxGsmpGrpNbrDescription,
        tmnxGsmpGrpNbrPrioMarkType,
        tmnxGsmpGrpNbrPrioMarkPrec,
        tmnxGsmpGrpNbrPrioMarkDscp,
        tmnxAncpStaticMapSapLastChange,
        tmnxAncpStaticMapSapRowStatus,
        tmnxAncpStaticMapSapAncpPolName,
        tmnxAncpStaticMapMssLastChange,
        tmnxAncpStaticMapMssRowStatus,
        tmnxAncpStaticMapMssAncpPolName,
        tmnxAncpSubProfileAncpPolicy,
        tmnxAncpPlcyLastChange,
        tmnxAncpPlcyRowStatus,
        tmnxAncpPlcyIngRateAdjustment,
        tmnxAncpPlcyIngRateReduction,
        tmnxAncpPlcyIngRateMonitor,
        tmnxAncpPlcyIngRateMonitorNtf,
        tmnxAncpPlcyIngRateModType,
        tmnxAncpPlcyIngRateModSched,
        tmnxAncpPlcyEgrRateAdjustment,
        tmnxAncpPlcyEgrRateReduction,
        tmnxAncpPlcyEgrRateMonitor,
        tmnxAncpPlcyEgrRateMonitorNtf,
        tmnxAncpPlcyEgrRateModType,
        tmnxAncpPlcyEgrRateModSched,
        tmnxAncpPlcyDisableShcv,
        tmnxAncpPlcyDisableShcvHldTime,
        tmnxAncpPlcyDisableShcvNtf,
        tmnxAncpStrInfAssociation,
        tmnxAncpStrInfSapPortId,
        tmnxAncpStrInfSapEncapValue,
        tmnxAncpStrInfMultSvcSiteName,
        tmnxAncpStrInfMultSvcSiteCust,
        tmnxAncpStrInfSubscrIdent,
        tmnxAncpStrInfLineState,
        tmnxAncpStrInfAncpPolicyName,
        tmnxAncpStrInfIngrRate,
        tmnxAncpStrInfAdjustedIngrRate,
        tmnxAncpStrInfEgrRate,
        tmnxAncpStrInfAdjustedEgrRate,
        tmnxAncpStrInfServId,
        tmnxAncpStrInfNeighborAddrType,
        tmnxAncpStrInfNeighborAddr,
        tmnxAncpStrInfTcpPort,
        tmnxAncpStrInfGroupName,
        tmnxAncpSesNbrPeerInstance,
        tmnxAncpSesNbrPeerPort,
        tmnxAncpSesNbrPeerName,
        tmnxAncpSesSenderInstance,
        tmnxAncpSesSenderPort,
        tmnxAncpSesSenderName,
        tmnxAncpSesNbrTimeouts,
        tmnxAncpSesNbrMaxNbrOfTimeouts,
        tmnxAncpSesNbrTimer,
        tmnxAncpSesSenderTimer,
        tmnxAncpSesNegotiatedCaps,
        tmnxAncpSesConfiguredCaps,
        tmnxAncpSesGroupName,
        tmnxAncpSesState,
        tmnxAncpSesLocalAddrType,
        tmnxAncpSesLocalAddr,
        tmnxAncpSesStatLastChanged,
        tmnxAncpSesStatRxDrop,
        tmnxAncpSesStatTxDrop,
        tmnxAncpSesStatRxSyn,
        tmnxAncpSesStatTxSyn,
        tmnxAncpSesStatRxSynAck,
        tmnxAncpSesStatTxSynAck,
        tmnxAncpSesStatRxAck,
        tmnxAncpSesStatTxAck,
        tmnxAncpSesStatRxRstAck,
        tmnxAncpSesStatTxRstAck,
        tmnxAncpSesStatRxPortUp,
        tmnxAncpSesStatTxPortUp,
        tmnxAncpSesStatRxPortDown,
        tmnxAncpSesStatTxPortDown,
        tmnxAncpSesStatRxLoopback,
        tmnxAncpSesStatTxLoopback,
        tmnxAncpSapMntrEgrAggRateLimit,
        tmnxAncpSapMntrAncpString,
        tmnxAncpSapIngMntrAncpString,
        tmnxAncpSapEgrMntrAncpString,
        tmnxAncpMssMntrEgrAggRateLimit,
        tmnxAncpMssMntrAncpString,
        tmnxAncpMssIngMntrAncpString,
        tmnxAncpMssEgrMntrAncpString,
        tmnxAncpSubMntrIngQosShedName,
        tmnxAncpSubMntrEgrQosShedName,
        tmnxAncpSubMntrEgrAggRateLimit,
        tmnxAncpSesVersion,
        tmnxAncpSesPartitionID,
        tmnxGsmpGrpCfgPersistencyDb,
        tmnxGsmpGrpCfgIdleFilter,
        tmnxAncpStringLineInfoValue,
        tmnxAncpStrInfPersistKey
    }
    STATUS      obsolete
    DESCRIPTION
        "The group of objects supporting management of the GSMP feature on
         Nokia 7x50 SR series systems release 11.0."
    ::= { tmnxGsmpGroups 4 }

tmnxGsmpSchedulerRateV11v0Group  OBJECT-GROUP
    OBJECTS     {
        tmnxAncpSapIngMntrQosShedPIRHi,
        tmnxAncpSapIngMntrQosShedPIRLo,
        tmnxAncpSapEgrMntrQosShedPIRHi,
        tmnxAncpSapEgrMntrQosShedPIRLo,
        tmnxAncpMssIngMntrQosShedPIRHi,
        tmnxAncpMssIngMntrQosShedPIRLo,
        tmnxAncpMssEgrMntrQosShedPIRHi,
        tmnxAncpMssEgrMntrQosShedPIRLo,
        tmnxAncpSubMntrIngQosShedPIRHi,
        tmnxAncpSubMntrIngQosShedPIRLo,
        tmnxAncpSubMntrEgrQosShedPIRHi,
        tmnxAncpSubMntrEgrQosShedPIRLo
    }
    STATUS      current
    DESCRIPTION
        "The group of objects supporting management of Scheduler policies on
         GSMP feature for Nokia SROS series systems release 11.0."
    ::= { tmnxGsmpGroups 5 }

tmnxGsmpObsoletedV11v0Group      OBJECT-GROUP
    OBJECTS     {
        tmnxAncpMssIngMntrQosShedPIR,
        tmnxAncpMssEgrMntrQosShedPIR,
        tmnxAncpSapIngMntrQosShedPIR,
        tmnxAncpSapEgrMntrQosShedPIR,
        tmnxAncpSubMntrIngQosShedPIR,
        tmnxAncpSubMntrEgrQosShedPIR
    }
    STATUS      current
    DESCRIPTION
        "The group of objects obsoleted supporting management of GSMP feature
         on Nokia SROS series systems release 11.0."
    ::= { tmnxGsmpGroups 6 }

tmnxGsmpQosV13v0Group            OBJECT-GROUP
    OBJECTS     {
        tmnxAncpSapMntrEgrAggRateLmt,
        tmnxAncpMssMntrEgrAggRateLmt
    }
    STATUS      current
    DESCRIPTION
        "The group of objects supporting management of GSMP feature for Nokia
         SROS series systems release 13.0."
    ::= { tmnxGsmpGroups 7 }

tmnxGsmpV13v0Group               OBJECT-GROUP
    OBJECTS     {
        tmnxGsmpConfigTableLastChange,
        tmnxGsmpGroupConfigTableLastChange,
        tmnxGsmpGroupNbrTableLastChange,
        tmnxAncpStaticMapSapTblLastChg,
        tmnxAncpStaticMapMssTblLastChg,
        tmnxAncpSubProfileTblLastChange,
        tmnxAncpPolicyTableLastChange,
        tmnxGsmpCfgLastChange,
        tmnxGsmpCfgAdminState,
        tmnxGsmpGrpCfgLastChange,
        tmnxGsmpGrpCfgRowStatus,
        tmnxGsmpGrpCfgAdminState,
        tmnxGsmpGrpCfgKeepalive,
        tmnxGsmpGrpCfgHoldMultiplier,
        tmnxGsmpGrpCfgDescription,
        tmnxGsmpGrpCfgAncpOamCap,
        tmnxGsmpGrpCfgAncpDynTopoDiscCap,
        tmnxGsmpGrpNbrLastChange,
        tmnxGsmpGrpNbrRowStatus,
        tmnxGsmpGrpNbrAdminState,
        tmnxGsmpGrpNbrLocalAddrType,
        tmnxGsmpGrpNbrLocalAddr,
        tmnxGsmpGrpNbrDescription,
        tmnxGsmpGrpNbrPrioMarkType,
        tmnxGsmpGrpNbrPrioMarkPrec,
        tmnxGsmpGrpNbrPrioMarkDscp,
        tmnxAncpStaticMapSapLastChange,
        tmnxAncpStaticMapSapRowStatus,
        tmnxAncpStaticMapSapAncpPolName,
        tmnxAncpStaticMapMssLastChange,
        tmnxAncpStaticMapMssRowStatus,
        tmnxAncpStaticMapMssAncpPolName,
        tmnxAncpSubProfileAncpPolicy,
        tmnxAncpPlcyLastChange,
        tmnxAncpPlcyRowStatus,
        tmnxAncpPlcyIngRateAdjustment,
        tmnxAncpPlcyIngRateReduction,
        tmnxAncpPlcyIngRateMonitor,
        tmnxAncpPlcyIngRateMonitorNtf,
        tmnxAncpPlcyIngRateModType,
        tmnxAncpPlcyIngRateModSched,
        tmnxAncpPlcyEgrRateAdjustment,
        tmnxAncpPlcyEgrRateReduction,
        tmnxAncpPlcyEgrRateMonitor,
        tmnxAncpPlcyEgrRateMonitorNtf,
        tmnxAncpPlcyEgrRateModType,
        tmnxAncpPlcyEgrRateModSched,
        tmnxAncpPlcyDisableShcv,
        tmnxAncpPlcyDisableShcvHldTime,
        tmnxAncpPlcyDisableShcvNtf,
        tmnxAncpStrInfAssociation,
        tmnxAncpStrInfSapPortId,
        tmnxAncpStrInfSapEncapValue,
        tmnxAncpStrInfMultSvcSiteName,
        tmnxAncpStrInfMultSvcSiteCust,
        tmnxAncpStrInfSubscrIdent,
        tmnxAncpStrInfLineState,
        tmnxAncpStrInfAncpPolicyName,
        tmnxAncpStrInfIngrRate,
        tmnxAncpStrInfAdjustedIngrRate,
        tmnxAncpStrInfEgrRate,
        tmnxAncpStrInfAdjustedEgrRate,
        tmnxAncpStrInfServId,
        tmnxAncpStrInfNeighborAddrType,
        tmnxAncpStrInfNeighborAddr,
        tmnxAncpStrInfTcpPort,
        tmnxAncpStrInfGroupName,
        tmnxAncpSesNbrPeerInstance,
        tmnxAncpSesNbrPeerPort,
        tmnxAncpSesNbrPeerName,
        tmnxAncpSesSenderInstance,
        tmnxAncpSesSenderPort,
        tmnxAncpSesSenderName,
        tmnxAncpSesNbrTimeouts,
        tmnxAncpSesNbrMaxNbrOfTimeouts,
        tmnxAncpSesNbrTimer,
        tmnxAncpSesSenderTimer,
        tmnxAncpSesNegotiatedCaps,
        tmnxAncpSesConfiguredCaps,
        tmnxAncpSesGroupName,
        tmnxAncpSesState,
        tmnxAncpSesLocalAddrType,
        tmnxAncpSesLocalAddr,
        tmnxAncpSesStatLastChanged,
        tmnxAncpSesStatRxDrop,
        tmnxAncpSesStatTxDrop,
        tmnxAncpSesStatRxSyn,
        tmnxAncpSesStatTxSyn,
        tmnxAncpSesStatRxSynAck,
        tmnxAncpSesStatTxSynAck,
        tmnxAncpSesStatRxAck,
        tmnxAncpSesStatTxAck,
        tmnxAncpSesStatRxRstAck,
        tmnxAncpSesStatTxRstAck,
        tmnxAncpSesStatRxPortUp,
        tmnxAncpSesStatTxPortUp,
        tmnxAncpSesStatRxPortDown,
        tmnxAncpSesStatTxPortDown,
        tmnxAncpSesStatRxLoopback,
        tmnxAncpSesStatTxLoopback,
        tmnxAncpSapMntrAncpString,
        tmnxAncpSapIngMntrAncpString,
        tmnxAncpSapEgrMntrAncpString,
        tmnxAncpMssMntrAncpString,
        tmnxAncpMssIngMntrAncpString,
        tmnxAncpMssEgrMntrAncpString,
        tmnxAncpSubMntrIngQosShedName,
        tmnxAncpSubMntrEgrQosShedName,
        tmnxAncpSubMntrEgrAggRateLimit,
        tmnxAncpSesVersion,
        tmnxAncpSesPartitionID,
        tmnxGsmpGrpCfgPersistencyDb,
        tmnxGsmpGrpCfgIdleFilter,
        tmnxAncpStringLineInfoValue,
        tmnxAncpStrInfPersistKey
    }
    STATUS      current
    DESCRIPTION
        "The group of objects supporting management of the GSMP feature on
         Nokia 7x50 SR series systems release 13.0."
    ::= { tmnxGsmpGroups 8 }

tmnxGsmpObsoletedV13v0Group      OBJECT-GROUP
    OBJECTS     {
        tmnxAncpSapMntrEgrAggRateLimit,
        tmnxAncpMssMntrEgrAggRateLimit
    }
    STATUS      current
    DESCRIPTION
        "The group of objects supporting management of the GSMP feature on
         Nokia 7x50 SR series systems release 13.0."
    ::= { tmnxGsmpGroups 9 }

tmnxGsmpNotifyPrefix             OBJECT IDENTIFIER ::= { tmnxSRNotifyPrefix 39 }

tmnxGsmpNotifications            OBJECT IDENTIFIER ::= { tmnxGsmpNotifyPrefix 0 }

tmnxAncpIngRateMonitorEvent      NOTIFICATION-TYPE
    OBJECTS     {
        tmnxNotifAncpString,
        tmnxNotifAncpPolicyName,
        tmnxNotifAncpPlcyActualRate
    }
    STATUS      current
    DESCRIPTION
        "This Notification is sent when the ingress rate monitor function for
         the port identified by tmnxNotifAncpString detects that the scheduler
         rate has dropped below tmnxAncpPlcyIngRateMonitor."
    ::= { tmnxGsmpNotifications 1 }

tmnxAncpEgrRateMonitorEvent      NOTIFICATION-TYPE
    OBJECTS     {
        tmnxNotifAncpString,
        tmnxNotifAncpPolicyName,
        tmnxNotifAncpPlcyActualRate
    }
    STATUS      current
    DESCRIPTION
        "This Notification is sent when the egress rate monitor function for
         the port identified by tmnxNotifAncpString detects that the scheduler
         rate has dropped below tmnxAncpPlcyEgrRateMonitor."
    ::= { tmnxGsmpNotifications 2 }

tmnxAncpShcvDisabledEvent        NOTIFICATION-TYPE
    OBJECTS     {
        tmnxNotifAncpString,
        tmnxNotifAncpPolicyName
    }
    STATUS      current
    DESCRIPTION
        "This Notification is sent when the shcv (subscriber host connectivity
         verification) is disabled for all hosts of the subscriber associated
         with the tmnxNotifAncpString when a port-down event was received for
         the tmnxNotifAncpString."
    ::= { tmnxGsmpNotifications 3 }

tmnxAncpSesRejected              NOTIFICATION-TYPE
    OBJECTS     {
        tmnxAncpRejectReason
    }
    STATUS      current
    DESCRIPTION
        "The tmnxAncpSesRejected notification is sent when an incoming ANCP
         session is rejected by the system. Details on why this happened are
         specified in tmnxAncpRejectReason."
    ::= { tmnxGsmpNotifications 4 }

tmnxAncpStringRejected           NOTIFICATION-TYPE
    OBJECTS     {
        tmnxAncpRejectReason
    }
    STATUS      current
    DESCRIPTION
        "The tmnxAncpStringRejected notification is sent when an incoming ANCP
         string received on an established ANCP session is rejected by the
         system. Details on why this happened are specified in
         tmnxAncpRejectReason."
    ::= { tmnxGsmpNotifications 5 }

END

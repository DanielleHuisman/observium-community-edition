TIMETRA-ISIS-MIB DEFINITIONS ::= BEGIN

IMPORTS
    InterfaceIndex
                                                         FROM IF-MIB
    InetAddress, InetAddressPrefixLength,
    InetAddressType
                                                         FROM INET-ADDRESS-MIB
    SNPAAddress, SystemID, isisISAdjEntry,
    isisISAdjState,
    isisManAreaAddrExistState,
    isisSysInstance, isisSysL1State,
    isisSysL2State
                                                         FROM ISIS-MIB
    MODULE-COMPLIANCE, NOTIFICATION-GROUP,
    OBJECT-GROUP
                                                         FROM SNMPv2-CONF
    Counter32, Gauge32, Integer32,
    IpAddress, MODULE-IDENTITY,
    NOTIFICATION-TYPE, OBJECT-TYPE,
    TimeTicks, Unsigned32
                                                         FROM SNMPv2-SMI
    DisplayString, MacAddress, RowStatus,
    TEXTUAL-CONVENTION, TimeInterval,
    TimeStamp, TruthValue
                                                         FROM SNMPv2-TC
    timetraSRMIBModules, tmnxSRConfs,
    tmnxSRNotifyPrefix, tmnxSRObjs
                                                         FROM TIMETRA-GLOBAL-MIB
    TNamedItem, TNamedItemOrEmpty,
    TmnxAdminState, TmnxEnabledDisabled,
    TmnxOperState, TmnxReferenceBandwidth,
    TmnxSpbFid
                                                         FROM TIMETRA-TC-MIB
    TmnxInetCidrNextHopOwner,
    TmnxInetCidrNextHopType, vRtrID,
    vRtrIfIndex
                                                         FROM TIMETRA-VRTR-MIB
    ;

timetraIsisMIBModule             MODULE-IDENTITY
    LAST-UPDATED "201504010000Z"
    ORGANIZATION "Nokia"
    CONTACT-INFO
        "Nokia SROS Support
         Web: http://www.nokia.com"
    DESCRIPTION
        "This document is the SNMP MIB module to manage and provision the
         extensions to the ISIS routing protocol for the Nokia SROS device.

         Copyright 2003-2018 Nokia. All rights reserved. Reproduction of this
         document is authorized on the condition that the foregoing copyright
         notice is included.

         This SNMP MIB module (Specification) embodies Nokia's
         proprietary intellectual property.  Nokia retains
         all title and ownership in the Specification, including any
         revisions.

         Nokia grants all interested parties a non-exclusive license to use and
         distribute an unmodified copy of this Specification in connection with
         management of Nokia products, and without fee, provided this copyright
         notice and license appear on all copies.

         This Specification is supplied 'as is', and Nokia makes no warranty,
         either express or implied, as to the use, operation, condition, or
         performance of the Specification."

    REVISION    "201504010000Z"
    DESCRIPTION
        "Rev 14.0               1 Apr 2015 00:00
         14.0 release of the TIMETRA-ISIS-MIB."

    REVISION    "201501010000Z"
    DESCRIPTION
        "Rev 13.0               1 Jan 2015 00:00
         13.0 release of the TIMETRA-ISIS-MIB."

    REVISION    "201401010000Z"
    DESCRIPTION
        "Rev 12.0               1 Jan 2014 00:00
         12.0 release of the TIMETRA-ISIS-MIB."

    REVISION    "201102010000Z"
    DESCRIPTION
        "Rev 9.0                1 Feb 2011 00:00
         9.0 release of the TIMETRA-ISIS-MIB."

    REVISION    "200902280000Z"
    DESCRIPTION
        "Rev 7.0                28 Feb 2009 00:00
         7.0 release of the TIMETRA-ISIS-MIB."

    REVISION    "200807010000Z"
    DESCRIPTION
        "Rev 6.1                01 Jul 2008 00:00
         6.1 release of the TIMETRA-ISIS-MIB."

    REVISION    "200801010000Z"
    DESCRIPTION
        "Rev 6.0                01 Jan 2008 00:00
         6.0 release of the TIMETRA-ISIS-MIB."

    REVISION    "200701010000Z"
    DESCRIPTION
        "Rev 5.0                01 Jan 2007 00:00
         5.0 release of the TIMETRA-ISIS-MIB."

    REVISION    "200603150000Z"
    DESCRIPTION
        "Rev 4.0                15 Mar 2006 00:00
         4.0 release of the TIMETRA-ISIS-MIB."

    REVISION    "200508310000Z"
    DESCRIPTION
        "Rev 3.0                31 Aug 2005 00:00
         3.0 release of the TIMETRA-ISIS-MIB."

    REVISION    "200501240000Z"
    DESCRIPTION
        "Rev 2.1                24 Jan 2005 00:00
         2.1 release of the TIMETRA-ISIS-MIB."

    REVISION    "200406020000Z"
    DESCRIPTION
        "Rev 2.1                02 Jun 2004 00:00
         2.1 release of the TIMETRA-ISIS-MIB."

    REVISION    "200401150000Z"
    DESCRIPTION
        "Rev 2.0                15 Jan 2004 00:00
         2.0 release of the TIMETRA-ISIS-MIB."

    REVISION    "200308150000Z"
    DESCRIPTION
        "Rev 1.2                15 Aug 2003 00:00
         1.2 release of the TIMETRA-ISIS-MIB."

    REVISION    "200301200000Z"
    DESCRIPTION
        "Rev 1.0                20 Jan 2003 00:00
         1.0 Release of the TIMETRA-ISIS-MIB."

    REVISION    "200109210000Z"
    DESCRIPTION
        "Rev 0.1                21 Sep 2001 00:00
         Initial version of the TIMETRA-ISIS-MIB."

    ::= { timetraSRMIBModules 10 }

TmnxLSPBuffSize                  ::= TEXTUAL-CONVENTION
    STATUS      current
    DESCRIPTION
        "TmnxLSPBuffSize is the extended integer sub range for LSP size."
    SYNTAX      Integer32 (490..9190)

IsisRoutingTopology              ::= TEXTUAL-CONVENTION
    STATUS      current
    DESCRIPTION
        "IsisRoutingTopology specifies the isis routing topology.

         native(1) - Indicates standard topology.

         mt(2) - Indicates multi-topology for IPv4/Ipv6 unicast/multicast
         routing."
    SYNTAX      INTEGER {
        none   (0),
        native (1),
        mt     (2)
    }

vRtrIsisObjs                     OBJECT IDENTIFIER ::= { tmnxSRObjs 10 }

vRtrIsisSystemObjs               OBJECT IDENTIFIER ::= { vRtrIsisObjs 1 }

vRtrIsisTable                    OBJECT-TYPE
    SYNTAX      SEQUENCE OF VRtrIsisEntry
    MAX-ACCESS  not-accessible
    STATUS      obsolete
    DESCRIPTION
        "The vRtrIsisTable provides an extension of the isisSysTable in the
         ISIS-MIB.

         This table is obsolete and replaced by tmnxIsisTable in
         TIMETRA-ISIS-NG-MIB."
    ::= { vRtrIsisSystemObjs 1 }

vRtrIsisEntry                    OBJECT-TYPE
    SYNTAX      VRtrIsisEntry
    MAX-ACCESS  not-accessible
    STATUS      obsolete
    DESCRIPTION
        "Each row entry in the vRtrIsisTable represents additional columns for
         attributes specific to the Nokia SROS series IS-IS protocol instance
         on this router."
    INDEX       { isisSysInstance }
    ::= { vRtrIsisTable 1 }

VRtrIsisEntry                    ::= SEQUENCE
{
    vRtrIsisLastEnabledTime          TimeStamp,
    vRtrIsisAuthKey                  OCTET STRING,
    vRtrIsisAuthType                 INTEGER,
    vRtrIsisAuthCheck                TruthValue,
    vRtrIsisExportPolicy1            TNamedItemOrEmpty,
    vRtrIsisExportPolicy2            TNamedItemOrEmpty,
    vRtrIsisExportPolicy3            TNamedItemOrEmpty,
    vRtrIsisExportPolicy4            TNamedItemOrEmpty,
    vRtrIsisExportPolicy5            TNamedItemOrEmpty,
    vRtrIsisLspLifetime              Unsigned32,
    vRtrIsisOverloadTimeout          Unsigned32,
    vRtrIsisOperState                TmnxOperState,
    vRtrIsisReferenceBw              TmnxReferenceBandwidth,
    vRtrIsisTrafficEng               TruthValue,
    vRtrIsisShortCuts                TruthValue,
    vRtrIsisSpfHoldTime              Integer32,
    vRtrIsisLastSpfRun               TimeStamp,
    vRtrIsisGracefulRestart          TruthValue,
    vRtrIsisOverloadOnBoot           INTEGER,
    vRtrIsisOverloadOnBootTimeout    Unsigned32,
    vRtrIsisSpfWait                  Unsigned32,
    vRtrIsisSpfInitialWait           Unsigned32,
    vRtrIsisSpfSecondWait            Unsigned32,
    vRtrIsisLspMaxWait               Unsigned32,
    vRtrIsisLspInitialWait           Unsigned32,
    vRtrIsisLspSecondWait            Unsigned32,
    vRtrIsisCsnpAuthentication       TruthValue,
    vRtrIsisHelloAuthentication      TruthValue,
    vRtrIsisPsnpAuthentication       TruthValue,
    vRtrIsisGRRestartDuration        Unsigned32,
    vRtrIsisGRHelperMode             TruthValue,
    vRtrIsisEnableIPv6               TruthValue,
    vRtrIsisEnableIPv4               TruthValue,
    vRtrIsisUnicastImport            TruthValue,
    vRtrIsisMulticastImport          TruthValue,
    vRtrIsisStrictAdjacencyCheck     TruthValue,
    vRtrIsisManualSpfTrigger         INTEGER,
    vRtrIsisMultiTopology            TruthValue,
    vRtrIsisMultiTopoIPv6Ucast       TruthValue,
    vRtrIsisIPv6RoutingTopo          INTEGER,
    vRtrIsisSysOrigL1LSPBuffSize     TmnxLSPBuffSize,
    vRtrIsisSysOrigL2LSPBuffSize     TmnxLSPBuffSize,
    vRtrIsisLdpSyncAdminState        TruthValue,
    vRtrIsisIPv6UnicastImport        TruthValue,
    vRtrIsisIPv6MulticastImport      TruthValue,
    vRtrIsisAdvertisePassiveOnly     TruthValue,
    vRtrIsisDefaultRouteTag          Unsigned32,
    vRtrIsisSuppressDefault          TruthValue,
    vRtrIsisLdpOverRsvp              TmnxEnabledDisabled,
    vRtrIsisExportLimit              Unsigned32,
    vRtrIsisExportLimitLogPercent    Unsigned32,
    vRtrIsisTotalL1ExportedRoutes    Gauge32,
    vRtrIsisTotalL2ExportedRoutes    Gauge32,
    vRtrIsisRsvpShortcut             TruthValue,
    vRtrIsisAdvertiseTunnelLink      TruthValue,
    vRtrIsisIidTlv                   TmnxEnabledDisabled,
    vRtrIsisL1MacAddress             MacAddress,
    vRtrIsisL2MacAddress             MacAddress,
    vRtrIsisSysOperL1LSPBuffSize     TmnxLSPBuffSize,
    vRtrIsisSysOperL2LSPBuffSize     TmnxLSPBuffSize,
    vRtrIsisLoopfreeAlternate        TruthValue,
    vRtrIsisIPv4McastRoutingTopo     IsisRoutingTopology,
    vRtrIsisIPv6McastRoutingTopo     IsisRoutingTopology,
    vRtrIsisMultiTopoIPv4Mcast       TruthValue,
    vRtrIsisMultiTopoIPv6Mcast       TruthValue,
    vRtrIsisOverloadMaxMetric        TruthValue,
    vRtrIsisOverloadOnBootMaxMetric  TruthValue,
    vRtrIsisRouterId                 Unsigned32,
    vRtrIsisAdvRtrCapability         INTEGER,
    vRtrIsisHelloPadding             INTEGER,
    vRtrIsisOperRouterId             Unsigned32,
    vRtrIsisIgnoreLspErrors          TruthValue
}

vRtrIsisLastEnabledTime          OBJECT-TYPE
    SYNTAX      TimeStamp
    MAX-ACCESS  read-only
    STATUS      obsolete
    DESCRIPTION
        "The vRtrIsisLastEnabledTime variable contains the sysUpTime value when
         isisSysAdminState was last set to enabled (1) to run the IS-IS
         protocol in the router."
    ::= { vRtrIsisEntry 1 }

vRtrIsisAuthKey                  OBJECT-TYPE
    SYNTAX      OCTET STRING (SIZE (0..254))
    MAX-ACCESS  read-only
    STATUS      obsolete
    DESCRIPTION
        "vRtrIsisAuthKey is the authentication key string used to verify
         the authenticity of packets sent by neighboring routers on an
         IS-IS interface.  For authentication to succeed both the
         authentication key and the authentication type defined by the
         vRtrIsisAuthType variable must match.  If vRtrIsisAuthType
         is set to 'password', vRtrIsisAuthKey can include any ASCII
         character.

         Authentication can be configured globally and applied to all ISIS
         levels or it can be configured on a per level basis. The most specific
         value is used.

         When read, vRtrIsisAuthKey always returns an Octet String of length
         zero."
    DEFVAL      { ''H }
    ::= { vRtrIsisEntry 2 }

vRtrIsisAuthType                 OBJECT-TYPE
    SYNTAX      INTEGER {
        none     (1),
        password (2),
        md5      (3)
    }
    MAX-ACCESS  read-only
    STATUS      obsolete
    DESCRIPTION
        "The value of vRtrIsisAuthType indicates the method of
         authentication used to verify the authenticity of packets sent
         by neighboring routers on an IS-IS interface.  For authentication
         to succeed both the authentication key defined in the
         vRtrIsisAuthKey variable and the authentication type must match.

         Authentication can be configured globally and applied to all
         ISIS levels or it can be configured on a per level basis.  The
         most specific value is used."
    DEFVAL      { none }
    ::= { vRtrIsisEntry 3 }

vRtrIsisAuthCheck                OBJECT-TYPE
    SYNTAX      TruthValue
    MAX-ACCESS  read-only
    STATUS      obsolete
    DESCRIPTION
        "When vRtrIsisAuthCheck has a value of 'true', all IS-IS protocol
         packets that have a mismatch on either the authentication type,
         specified by the value of vRtrIsisAuthType, or the authentication key,
         given in vRtrIsisAuthKey are rejected.

         When vRtrIsisAuthCheck has a value of 'false', authentication is
         performed on received IS-IS protocol packets but mismatched packets
         are not rejected."
    DEFVAL      { true }
    ::= { vRtrIsisEntry 4 }

vRtrIsisExportPolicy1            OBJECT-TYPE
    SYNTAX      TNamedItemOrEmpty
    MAX-ACCESS  read-only
    STATUS      obsolete
    DESCRIPTION
        "The value of vRtrIsisExportPolicy1 is the name of the first
         policy to be used for determining which routes are exported from
         the routing table to IS-IS.  If no export policy is defined,
         non IS-IS router will not be exported from the routing table
         manager to IS-IS.

         If multiple policy names are specified, the policies are evaluated
         in the order they are specified.  The first policy that matches
         is applied.

         The export policy name list, vRtrIsisExportPolicy1 through
         vRtrIsisExportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrIsisEntry 5 }

vRtrIsisExportPolicy2            OBJECT-TYPE
    SYNTAX      TNamedItemOrEmpty
    MAX-ACCESS  read-only
    STATUS      obsolete
    DESCRIPTION
        "The value of vRtrIsisExportPolicy2 is the name of the second
         policy to be used for determining which routes are exported from
         the routing table to IS-IS.  If no export policy is defined,
         non IS-IS router will not be exported from the routing table
         manager to IS-IS.

         If multiple policy names are specified, the policies are evaluated
         in the order they are specified.  The first policy that matches
         is applied.

         The export policy name list, vRtrIsisExportPolicy1 through
         vRtrIsisExportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrIsisEntry 6 }

vRtrIsisExportPolicy3            OBJECT-TYPE
    SYNTAX      TNamedItemOrEmpty
    MAX-ACCESS  read-only
    STATUS      obsolete
    DESCRIPTION
        "The value of vRtrIsisExportPolicy3 is the name of the third
         policy to be used for determining which routes are exported from
         the routing table to IS-IS.  If no export policy is defined,
         non IS-IS router will not be exported from the routing table
         manager to IS-IS.

         If multiple policy names are specified, the policies are evaluated
         in the order they are specified.  The first policy that matches
         is applied.

         The export policy name list, vRtrIsisExportPolicy1 through
         vRtrIsisExportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrIsisEntry 7 }

vRtrIsisExportPolicy4            OBJECT-TYPE
    SYNTAX      TNamedItemOrEmpty
    MAX-ACCESS  read-only
    STATUS      obsolete
    DESCRIPTION
        "The value of vRtrIsisExportPolicy4 is the name of the fourth
         policy to be used for determining which routes are exported from
         the routing table to IS-IS.  If no export policy is defined,
         non IS-IS router will not be exported from the routing table
         manager to IS-IS.

         If multiple policy names are specified, the policies are evaluated
         in the order they are specified.  The first policy that matches
         is applied.

         The export policy name list, vRtrIsisExportPolicy1 through
         vRtrIsisExportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrIsisEntry 8 }

vRtrIsisExportPolicy5            OBJECT-TYPE
    SYNTAX      TNamedItemOrEmpty
    MAX-ACCESS  read-only
    STATUS      obsolete
    DESCRIPTION
        "The value of vRtrIsisExportPolicy5 is the name of the fifth
         policy to be used for determining which routes are exported from
         the routing table to IS-IS.  If no export policy is defined,
         non IS-IS router will not be exported from the routing table
         manager to IS-IS.

         If multiple policy names are specified, the policies are evaluated
         in the order they are specified.  The first policy that matches
         is applied.

         The export policy name list, vRtrIsisExportPolicy1 through
         vRtrIsisExportPolicy5, is handled by the SNMP agent as a single
         entity.  When an SNMP SET request is received to modify one or
         more of the policy names, all the policy variables are first
         set to the empty string, ''H, and then the new names are set
         into the specified policy variables within a single SNMP SET PDU."
    DEFVAL      { ''H }
    ::= { vRtrIsisEntry 9 }

vRtrIsisLspLifetime              OBJECT-TYPE
    SYNTAX      Unsigned32 (350..65535)
    UNITS       "seconds"
    MAX-ACCESS  read-only
    STATUS      obsolete
    DESCRIPTION
        "The value of vRtrIsisLspLifetime specifies how long, in seconds,
         a given LSP is considered valid without the originating router
         having refreshed the LSP.  The actual LSP refresh timer is the
         value of vRtrIsisLspLifetime minus 317 seconds."
    DEFVAL      { 1200 }
    ::= { vRtrIsisEntry 10 }

vRtrIsisOverloadTimeout          OBJECT-TYPE
    SYNTAX      Unsigned32 (0 | 60..1800)
    UNITS       "seconds"
    MAX-ACCESS  read-only
    STATUS      obsolete
    DESCRIPTION
        "The value of vRtrIsisOverloadTimeout is the amount of time, in
         seconds, the router operates in the overload state before
         attempting to reestablish normal operations.  While in overload
         state, this IS-IS router will only be used if the destination is
         only reachable via this router; it is not used for other transit
         traffic.  Operationally placing the router into the overload
         state is often used as a precursor to shutting down the IS-IS
         protocol operation.
         This variable is an extension to the isisSysWaitTime to accept an
         additional value of 0. This value means the router is in overload
         infinitely."
    DEFVAL      { 0 }
    ::= { vRtrIsisEntry 11 }

vRtrIsisOperState                OBJECT-TYPE
    SYNTAX      TmnxOperState
    MAX-ACCESS  read-only
    STATUS      obsolete
    DESCRIPTION
        "vRtrIsisOperState indicates the current operating state of this IS-IS
         protocol instance on this router."
    ::= { vRtrIsisEntry 12 }

vRtrIsisReferenceBw              OBJECT-TYPE
    SYNTAX      TmnxReferenceBandwidth
    UNITS       "kilobps"
    MAX-ACCESS  read-only
    STATUS      obsolete
    DESCRIPTION
        "Reference bandwidth - In order to calculate the lowest cost
         to reach a given destination each configured level on each
         interface must have a cost.  If the reference-bandwidth is
         defined then the cost is calculated using the following
         formula:
             Cost = reference-bandwidth / bandwidth.
         If the reference bandwidth is configured as Ten Gig
         (10,000,000,000) a 100-Mbps interface has a default metric of
         100. In order for metrics in excess of 63 to be configured
         wide metrics must be deployed.

         A value of '0' means that the reference bandwidth is not defined."
    DEFVAL      { 0 }
    ::= { vRtrIsisEntry 13 }

vRtrIsisTrafficEng               OBJECT-TYPE
    SYNTAX      TruthValue
    MAX-ACCESS  read-only
    STATUS      obsolete
    DESCRIPTION
        "When the value of vRtrIsisTrafficEng is 'true', traffic
         engineering is enabled for the router.  When the value of
         vRtrIsisTrafficEng is 'false', traffic engineering is disabled
         so that te-metrics are not generated and are ignored when received
         by this node."
    DEFVAL      { true }
    ::= { vRtrIsisEntry 14 }

vRtrIsisShortCuts                OBJECT-TYPE
    SYNTAX      TruthValue
    MAX-ACCESS  read-only
    STATUS      obsolete
    DESCRIPTION
        "When the value of vRtrIsisShortCuts is 'true', MPLS label switched
         paths of LSPs are used as next hops whenever BGP need to resolve
         the next hop within the IS-IS domain.  When the value of
         vRtrIsisShortCuts is 'false', IGP shortcuts are not required by
         BGP. This doesn't have any meaning if vRtrIsisTrafficEng is set to
         false."
    DEFVAL      { false }
    ::= { vRtrIsisEntry 15 }

vRtrIsisSpfHoldTime              OBJECT-TYPE
    SYNTAX      Integer32 (0..65535)
    UNITS       "seconds"
    MAX-ACCESS  read-only
    STATUS      obsolete
    DESCRIPTION
        "Time interval at which SPF is run."
    DEFVAL      { 10 }
    ::= { vRtrIsisEntry 16 }

vRtrIsisLastSpfRun               OBJECT-TYPE
    SYNTAX      TimeStamp
    MAX-ACCESS  read-only
    STATUS      obsolete
    DESCRIPTION
        "The vRtrIsisLastSpfRun contains the sysUpTime value when the last SPF
         run was performed for this instance of the IS-IS protocol in the
         router."
    ::= { vRtrIsisEntry 17 }

vRtrIsisGracefulRestart          OBJECT-TYPE
    SYNTAX      TruthValue
    MAX-ACCESS  read-only
    STATUS      obsolete
    DESCRIPTION
        "The value of vRtrIsisGracefulRestart specifies whether the graceful
         restart is enabled or disabled for this instance of IS-IS on the
         router."
    DEFVAL      { false }
    ::= { vRtrIsisEntry 18 }

vRtrIsisOverloadOnBoot           OBJECT-TYPE
    SYNTAX      INTEGER {
        disabled          (1),
        enabled           (2),
        enabledWaitForBgp (3)
    }
    MAX-ACCESS  read-only
    STATUS      obsolete
    DESCRIPTION
        "The value of vRtrIsisOverloadOnBoot specifies if the router should be
         in overload state right after the boot up process. If the
         vRtrIsisOverloadOnBoot is set to 'enabled' the overload timeout is
         maintained by vRtrIsisOverloadOnBootTimeout."
    DEFVAL      { disabled }
    ::= { vRtrIsisEntry 19 }

vRtrIsisOverloadOnBootTimeout    OBJECT-TYPE
    SYNTAX      Unsigned32 (0 | 60..1800)
    UNITS       "seconds"
    MAX-ACCESS  read-only
    STATUS      obsolete
    DESCRIPTION
        "The value of vRtrIsisOverloadOnBootTimeout is the amount of time, in
         seconds for which the router operates in the overload state before
         attempting to reestablish normal operations when the system comes up
         after a fresh boot. While in overload state, this IS-IS router will
         only be used if the destination is only reachable via this router; it
         is not used for other transit traffic."
    DEFVAL      { 0 }
    ::= { vRtrIsisEntry 20 }

vRtrIsisSpfWait                  OBJECT-TYPE
    SYNTAX      Unsigned32 (1..120)
    UNITS       "seconds"
    MAX-ACCESS  read-only
    STATUS      obsolete
    DESCRIPTION
        "The value of vRtrIsisSpfWait defines the Maximum interval between two
         consecutive spf calculations in seconds."
    DEFVAL      { 10 }
    ::= { vRtrIsisEntry 21 }

vRtrIsisSpfInitialWait           OBJECT-TYPE
    SYNTAX      Unsigned32 (10..100000)
    UNITS       "milliseconds"
    MAX-ACCESS  read-only
    STATUS      obsolete
    DESCRIPTION
        "The value of vRtrIsisSpfInitialWait defines the initial SPF
         calculation delay (in milliseconds) after a topology change."
    DEFVAL      { 1000 }
    ::= { vRtrIsisEntry 22 }

vRtrIsisSpfSecondWait            OBJECT-TYPE
    SYNTAX      Unsigned32 (1..100000)
    UNITS       "milliseconds"
    MAX-ACCESS  read-only
    STATUS      obsolete
    DESCRIPTION
        "The value of vRtrIsisSpfSecondWait defines the hold time between the
         first and second SPF calculation (in milliseconds).

         Subsequent SPF runs will occur at exponentially increasing intervals
         of spf-second-wait i.e. if spf-second-wait is 1000, then the next SPF
         will run after 2000 msec, the next one at 4000 msec etc until it is
         capped off at spf-wait value.

         The SPF interval will stay at spf-wait value until there are no more
         SPF runs scheduled in that interval. After a full interval without any
         SPF runs, the SPF interval will drop back to spf-initial-wait."
    DEFVAL      { 1000 }
    ::= { vRtrIsisEntry 23 }

vRtrIsisLspMaxWait               OBJECT-TYPE
    SYNTAX      Unsigned32 (1..120)
    UNITS       "seconds"
    MAX-ACCESS  read-only
    STATUS      obsolete
    DESCRIPTION
        "The value of vRtrIsisLspMaxWait defines the maximum interval (in
         seconds) between two consecutive occurrences of an LSP being
         generated."
    DEFVAL      { 5 }
    ::= { vRtrIsisEntry 24 }

vRtrIsisLspInitialWait           OBJECT-TYPE
    SYNTAX      Unsigned32 (0..100)
    UNITS       "seconds"
    MAX-ACCESS  read-only
    STATUS      obsolete
    DESCRIPTION
        "The value of vRtrIsisLspInitialWait defines the initial LSP generation
         delay (in seconds)."
    DEFVAL      { 0 }
    ::= { vRtrIsisEntry 25 }

vRtrIsisLspSecondWait            OBJECT-TYPE
    SYNTAX      Unsigned32 (1..100)
    UNITS       "seconds"
    MAX-ACCESS  read-only
    STATUS      obsolete
    DESCRIPTION
        "The value of vRtrIsisLspSecondWait defines the hold time between the
         first and second LSP generation (in seconds)."
    DEFVAL      { 1 }
    ::= { vRtrIsisEntry 26 }

vRtrIsisCsnpAuthentication       OBJECT-TYPE
    SYNTAX      TruthValue
    MAX-ACCESS  read-only
    STATUS      obsolete
    DESCRIPTION
        "When vRtrIsisCsnpAuthentication has a value of 'true', enables
         authentication of individual ISIS packets of CSNP type. The value of
         'false'

         When vRtrIsisCsnpAuthentication has a value of 'false', suppresses
         authentication of CSNP packets."
    DEFVAL      { true }
    ::= { vRtrIsisEntry 27 }

vRtrIsisHelloAuthentication      OBJECT-TYPE
    SYNTAX      TruthValue
    MAX-ACCESS  read-only
    STATUS      obsolete
    DESCRIPTION
        "When vRtrIsisHelloAuthentication has a value of 'true', enables
         authentication of individual ISIS packets of HELLO type. The value of
         'false'

         When vRtrIsisHelloAuthentication has a value of 'false', suppresses
         authentication of HELLO packets."
    DEFVAL      { true }
    ::= { vRtrIsisEntry 28 }

vRtrIsisPsnpAuthentication       OBJECT-TYPE
    SYNTAX      TruthValue
    MAX-ACCESS  read-only
    STATUS      obsolete
    DESCRIPTION
        "When vRtrIsisPsnpAuthentication has a value of 'true', enables
         authentication of individual ISIS packets of PSNP type. The value of
         'false'

         When vRtrIsisPsnpAuthentication has a value of 'false', suppresses
         authentication of PSNP packets."
    DEFVAL      { true }
    ::= { vRtrIsisEntry 29 }

vRtrIsisGRRestartDuration        OBJECT-TYPE
    SYNTAX      Unsigned32 (1..3600)
    UNITS       "seconds"
    MAX-ACCESS  read-only
    STATUS      obsolete
    DESCRIPTION
        "The value of vRtrIsisGRRestartDuration specifies the maximum amount of
         time, in seconds, needed to re-establish ISIS adjacencies in all
         areas."
    DEFVAL      { 180 }
    ::= { vRtrIsisEntry 30 }

vRtrIsisGRHelperMode             OBJECT-TYPE
    SYNTAX      TruthValue
    MAX-ACCESS  read-only
    STATUS      obsolete
    DESCRIPTION
        "The value of vRtrIsisGRHelperMode specifies whether the graceful
         restart helper mode is enabled or disabled for this instance of IS-IS
         on the router. vRtrIsisGRHelperMode is valid only if the value of
         vRtrIsisGracefulRestart is 'true'.

         When vRtrIsisGRHelperMode has a value of 'true' graceful
         restart helper capabilities are enabled.  When it has a value
         of 'false' the graceful restart helper capabilities are disabled."
    DEFVAL      { false }
    ::= { vRtrIsisEntry 31 }

vRtrIsisEnableIPv6               OBJECT-TYPE
    SYNTAX      TruthValue
    MAX-ACCESS  read-only
    STATUS      obsolete
    DESCRIPTION
        "The value of vRtrIsisEnableIPv6 specifies whether this IS-IS instance
         supports IPv6.

         When vRtrIsisEnableIPv6 has a value of 'true', the IS-IS instance
         supports IPv6, and when it has a value of 'false', it does not."
    DEFVAL      { false }
    ::= { vRtrIsisEntry 32 }

vRtrIsisEnableIPv4               OBJECT-TYPE
    SYNTAX      TruthValue
    MAX-ACCESS  read-only
    STATUS      obsolete
    DESCRIPTION
        "The value of vRtrIsisEnableIPv4 specifies whether this IS-IS instance
         supports IPv4.

         When vRtrIsisEnableIPv4 has a value of 'true', the IS-IS instance
         supports IPv4, and when it has a value of 'false', it does not."
    DEFVAL      { true }
    ::= { vRtrIsisEntry 33 }

vRtrIsisUnicastImport            OBJECT-TYPE
    SYNTAX      TruthValue
    MAX-ACCESS  read-only
    STATUS      obsolete
    DESCRIPTION
        "The value of vRtrIsisUnicastImport specifies whether ISIS protocol
         will submit routes into the unicast Route Table Manage(RTM).

         When vRtrIsisUnicastImport has a value of 'true', the IS-IS instance
         submits routes into the unicast RTM, and when it has a value of
         'false', it does not."
    DEFVAL      { true }
    ::= { vRtrIsisEntry 34 }

vRtrIsisMulticastImport          OBJECT-TYPE
    SYNTAX      TruthValue
    MAX-ACCESS  read-only
    STATUS      obsolete
    DESCRIPTION
        "The value of vRtrIsisMulticastImport specifies whether ISIS protocol
         will submit routes into the multicast Reverse Path Forwarding(RPF)
         Route Table Manage(RTM).

         When vRtrIsisMulticastImport has a value of 'true', ISIS protocol
         submits routes into the multicast RPF RTM and when it has a value of
         'false', it does not."
    DEFVAL      { false }
    ::= { vRtrIsisEntry 35 }

vRtrIsisStrictAdjacencyCheck     OBJECT-TYPE
    SYNTAX      TruthValue
    MAX-ACCESS  read-only
    STATUS      obsolete
    DESCRIPTION
        "The value of vRtrIsisStrictAdjacencyCheck specifies whether an ISIS
         adjacency can be formed when two routers do not run the same IP
         versions.

         When the value is 'true', both routers have to run the same IP
         versions in the ISIS protocol. When it is 'false', having one common
         IP version running is enough to form an adjacency."
    DEFVAL      { false }
    ::= { vRtrIsisEntry 36 }

vRtrIsisManualSpfTrigger         OBJECT-TYPE
    SYNTAX      INTEGER {
        noAction    (1),
        runTotalSpf (2)
    }
    MAX-ACCESS  read-only
    STATUS      obsolete
    DESCRIPTION
        "The value of vRtrIsisManualSpfTrigger specifies a manual Dijkstra SPF
         calculation trigger.

         When vRtrIsisManualSpfTrigger is set to 'runTotalSpf' a normal
         Dijkstra SPF calculation is performed.

         GETs and GETNEXTs on this variable return 'noAction'."
    DEFVAL      { noAction }
    ::= { vRtrIsisEntry 37 }

vRtrIsisMultiTopology            OBJECT-TYPE
    SYNTAX      TruthValue
    MAX-ACCESS  read-only
    STATUS      obsolete
    DESCRIPTION
        "The value of vRtrIsisMultiTopology specifies if the multi topology for
         ISIS is enabled."
    DEFVAL      { false }
    ::= { vRtrIsisEntry 38 }

vRtrIsisMultiTopoIPv6Ucast       OBJECT-TYPE
    SYNTAX      TruthValue
    MAX-ACCESS  read-only
    STATUS      obsolete
    DESCRIPTION
        "The value of vRtrIsisMultiTopoIPv6Ucast specifies if IPv6 unicast is
         enabled for ISIS multi topology.

         To enable IPv6 unicast on ISIS, vRtrIsisMultiTopology should be set to
         'true'."
    DEFVAL      { false }
    ::= { vRtrIsisEntry 39 }

vRtrIsisIPv6RoutingTopo          OBJECT-TYPE
    SYNTAX      INTEGER {
        none   (0),
        native (1),
        mt     (2)
    }
    MAX-ACCESS  read-only
    STATUS      obsolete
    DESCRIPTION
        "The value of vRtrIsisIPv6RoutingTopo specifies the routing topology
         for IPv6.

         If the value of vRtrIsisIPv6RoutingTopo is set to 'mt', multi topology
         for ipv6 routing is in effect only if vRtrIsisMultiTopoIPv6Ucast is
         set to 'true'."
    DEFVAL      { none }
    ::= { vRtrIsisEntry 40 }

vRtrIsisSysOrigL1LSPBuffSize     OBJECT-TYPE
    SYNTAX      TmnxLSPBuffSize
    MAX-ACCESS  read-only
    STATUS      obsolete
    DESCRIPTION
        "The value of vRtrIsisSysOrigL1LSPBuffSize specifies the maximum size
         of Level 1 LSPs and SNPs originated by this instance.

         This object may only be modified when the ISIS-MIB::isisSysAdminState
         member of the corresponding entry in the ISIS-MIB::isisSysTable table
         has a value of 'outOfService (3)'.

         This object replaces the ISIS-MIB::isisSysOrigL1LSPBuffSize member of
         the ISIS-MIB::isisSysTable table."
    DEFVAL      { 1492 }
    ::= { vRtrIsisEntry 41 }

vRtrIsisSysOrigL2LSPBuffSize     OBJECT-TYPE
    SYNTAX      TmnxLSPBuffSize
    MAX-ACCESS  read-only
    STATUS      obsolete
    DESCRIPTION
        "The value of vRtrIsisSysOrigL2LSPBuffSize specifies the maximum size
         of Level 2 LSPs and SNPs originated by this system.

         This object may only be modified when the ISIS-MIB::isisSysAdminState
         member of the corresponding entry in the ISIS-MIB::isisSysTable table
         has a value of 'outOfService (3)'.

         This object replaces the ISIS-MIB::isisSysOrigL2LSPBuffSize member of
         the ISIS-MIB::isisSysTable table."
    DEFVAL      { 1492 }
    ::= { vRtrIsisEntry 42 }

vRtrIsisLdpSyncAdminState        OBJECT-TYPE
    SYNTAX      TruthValue
    MAX-ACCESS  read-only
    STATUS      obsolete
    DESCRIPTION
        "The value of vRtrIsisLdpSyncAdminState specifies whether the IGP-LDP
         synchronization feature is enabled or disabled on all interfaces
         participating in the ISIS routing protocol.

         When the value is set to 'false', IGP immediately advertises the
         actual value of the link cost for all interfaces which have the
         IGP-LDP synchronization enabled if the currently advertised cost is
         different. It will then disable IGP-LDP synchronization for all
         interfaces."
    DEFVAL      { true }
    ::= { vRtrIsisEntry 43 }

vRtrIsisIPv6UnicastImport        OBJECT-TYPE
    SYNTAX      TruthValue
    MAX-ACCESS  read-only
    STATUS      obsolete
    DESCRIPTION
        "The value of vRtrIsisIPv6UnicastImport specifies whether ISIS protocol
         will submit routes into the unicast IPv6 Route Table Manage(RTM).

         When vRtrIsisUnicastImport has a value of 'true', the IS-IS instance
         submits routes into the unicast IPv6 RTM, and when it has a value of
         'false', it does not."
    DEFVAL      { true }
    ::= { vRtrIsisEntry 44 }

vRtrIsisIPv6MulticastImport      OBJECT-TYPE
    SYNTAX      TruthValue
    MAX-ACCESS  read-only
    STATUS      obsolete
    DESCRIPTION
        "The value of vRtrIsisIPv6MulticastImport specifies whether ISIS
         protocol will submit routes into the multicast IPv6 Reverse Path
         Forwarding(RPF) Route Table Manage(RTM).

         When vRtrIsisMulticastImport has a value of 'true', ISIS protocol
         submits routes into the multicast IPv6 RPF RTM and when it has a value
         of 'false', it does not."
    DEFVAL      { false }
    ::= { vRtrIsisEntry 45 }

vRtrIsisAdvertisePassiveOnly     OBJECT-TYPE
    SYNTAX      TruthValue
    MAX-ACCESS  read-only
    STATUS      obsolete
    DESCRIPTION
        "The value of vRtrIsisAdvertisePassiveOnly specifies whether ISIS
         protocol will advertise only prefixes that belong to passive
         interfaces.

         When vRtrIsisAdvertisePassiveOnly is set to 'true', ISIS protocol
         advertises only prefixes that belong to passive interfaces."
    DEFVAL      { false }
    ::= { vRtrIsisEntry 46 }

vRtrIsisDefaultRouteTag          OBJECT-TYPE
    SYNTAX      Unsigned32
    MAX-ACCESS  read-only
    STATUS      obsolete
    DESCRIPTION
        "The value of vRtrIsisDefaultRouteTag specifies a 32-bit integer tag
         for the ISIS default route. This tag can be used to apply
         administrative policy. A value of 0 indicates that the tag has not
         been set."
    DEFVAL      { 0 }
    ::= { vRtrIsisEntry 47 }

vRtrIsisSuppressDefault          OBJECT-TYPE
    SYNTAX      TruthValue
    MAX-ACCESS  read-only
    STATUS      obsolete
    DESCRIPTION
        "The value of vRtrIsisSuppressDefault specifies whether ISIS protocol
         will suppress the installation of the default routes on L1 router.

         When vRtrIsisSuppressDefault is set to 'true', ISIS protocol will
         suppress the installation of the default routes."
    DEFVAL      { false }
    ::= { vRtrIsisEntry 48 }

vRtrIsisLdpOverRsvp              OBJECT-TYPE
    SYNTAX      TmnxEnabledDisabled
    MAX-ACCESS  read-only
    STATUS      obsolete
    DESCRIPTION
        "The value of vRtrIsisLdpOverRsvp specifies whether LDP-over-RSVP
         feature is enabled or disabled for ISIS.

         When vRtrIsisLdpOverRsvp is enabled, ISIS will select the endpoint
         that is closest to the destination for further selection of
         LDP-over-RSVP tunnels to that endpoint."
    DEFVAL      { disabled }
    ::= { vRtrIsisEntry 49 }

vRtrIsisExportLimit              OBJECT-TYPE
    SYNTAX      Unsigned32
    MAX-ACCESS  read-only
    STATUS      obsolete
    DESCRIPTION
        "The value of vRtrIsisExportLimit specifies the maximum number of
         routes or prefixes that can be exported into ISIS from the route
         table.

         A value of 0 indicates that the export limit for routes or prefixes
         has been disabled."
    DEFVAL      { 0 }
    ::= { vRtrIsisEntry 50 }

vRtrIsisExportLimitLogPercent    OBJECT-TYPE
    SYNTAX      Unsigned32 (0..100)
    UNITS       "percent"
    MAX-ACCESS  read-only
    STATUS      obsolete
    DESCRIPTION
        "The value of vRtrIsisExportLimitLogPercent specifies the percentage of
         the export-limit at which a warning log message and SNMP notification
         would be sent. This would only be a warning and additional routes will
         be learned up to 100% of vRtrIsisExportLimit.

         A value of 0 indicates that vRtrIsisExportLimitLogPercent is disabled
         and no log message or SNMP notification would be sent."
    DEFVAL      { 0 }
    ::= { vRtrIsisEntry 51 }

vRtrIsisTotalL1ExportedRoutes    OBJECT-TYPE
    SYNTAX      Gauge32
    MAX-ACCESS  read-only
    STATUS      obsolete
    DESCRIPTION
        "The value of vRtrIsisTotalL1ExportedRoutes indicates the total number
         of routes exported into ISIS level 1 from the route table manager when
         an export policy is configured.

         Value of vRtrIsisTotalL1ExportedRoutes would be 0 when no export
         policy is configured."
    ::= { vRtrIsisEntry 52 }

vRtrIsisTotalL2ExportedRoutes    OBJECT-TYPE
    SYNTAX      Gauge32
    MAX-ACCESS  read-only
    STATUS      obsolete
    DESCRIPTION
        "The value of vRtrIsisTotalL2ExportedRoutes indicates the total number
         of routes exported into ISIS level 2 from the route table manager when
         an export policy is configured.

         Value of vRtrIsisTotalL2ExportedRoutes would be 0 when no export
         policy is configured."
    ::= { vRtrIsisEntry 53 }

vRtrIsisRsvpShortcut             OBJECT-TYPE
    SYNTAX      TruthValue
    MAX-ACCESS  read-only
    STATUS      obsolete
    DESCRIPTION
        "The value of vRtrIsisRsvpShortcut specifies whether RSVP-TE shortcut
         for resolving IGP routes has been enabled or disabled for IS-IS.

         When the value of vRtrIsisRsvpShortcut is set to true RSVP-TE shortcut
         is enabled and when vRtrIsisRsvpShortcut is set to false RSVP-TE
         shortcut is disabled for IS-IS."
    DEFVAL      { false }
    ::= { vRtrIsisEntry 54 }

vRtrIsisAdvertiseTunnelLink      OBJECT-TYPE
    SYNTAX      TruthValue
    MAX-ACCESS  read-only
    STATUS      obsolete
    DESCRIPTION
        "The value of vRtrIsisAdvertiseTunnelLink specifies whether
         advertisement of LSP shortcuts into IGP has been enabled or disabled
         for IS-IS.

         When the value of vRtrIsisAdvertiseTunnelLink is set to true LSP  shortcut
         advertisement into IGP is enabled and when vRtrIsisAdvertiseTunnelLink is
         set to false LSP shortcut advertisement into IGP is disabled."
    DEFVAL      { false }
    ::= { vRtrIsisEntry 55 }

vRtrIsisIidTlv                   OBJECT-TYPE
    SYNTAX      TmnxEnabledDisabled
    MAX-ACCESS  read-only
    STATUS      obsolete
    DESCRIPTION
        "The value of vRtrIsisIidTlv specifies whether Instance Identifier
         (IID) TLV has been enabled or disabled for this ISIS instance.

         When the value of vRtrIsisIidTlv is 'enabled', each ISIS instance
         marks its packets with the IID TLV containing its unique 16-bit IID
         for the for the routing domain."
    DEFVAL      { disabled }
    ::= { vRtrIsisEntry 56 }

vRtrIsisL1MacAddress             OBJECT-TYPE
    SYNTAX      MacAddress
    MAX-ACCESS  read-only
    STATUS      obsolete
    DESCRIPTION
        "The value of vRtrIsisL1MacAddress specifies the destination MAC
         address for all L1 ISIS neighbors on the link for this ISIS instance."
    DEFVAL      { '0180C2000014'H }
    ::= { vRtrIsisEntry 57 }

vRtrIsisL2MacAddress             OBJECT-TYPE
    SYNTAX      MacAddress
    MAX-ACCESS  read-only
    STATUS      obsolete
    DESCRIPTION
        "The value of vRtrIsisL2MacAddress specifies the destination MAC
         address for all L2 ISIS neighbors on the link for this ISIS instance."
    DEFVAL      { '0180C2000015'H }
    ::= { vRtrIsisEntry 58 }

vRtrIsisSysOperL1LSPBuffSize     OBJECT-TYPE
    SYNTAX      TmnxLSPBuffSize
    MAX-ACCESS  read-only
    STATUS      obsolete
    DESCRIPTION
        "The value of vRtrIsisSysOperL1LSPBuffSize indicates the operational
         size of Level 1 LSPs and SNPs originated by this instance."
    ::= { vRtrIsisEntry 59 }

vRtrIsisSysOperL2LSPBuffSize     OBJECT-TYPE
    SYNTAX      TmnxLSPBuffSize
    MAX-ACCESS  read-only
    STATUS      obsolete
    DESCRIPTION
        "The value of vRtrIsisSysOperL2LSPBuffSize indicates the operational
         size of Level 2 LSPs and SNPs originated by this instance."
    ::= { vRtrIsisEntry 60 }

vRtrIsisLoopfreeAlternate        OBJECT-TYPE
    SYNTAX      TruthValue
    MAX-ACCESS  read-only
    STATUS      obsolete
    DESCRIPTION
        "The value of vRtrIsisLoopfreeAlternate specifies whether to enable or
         disable IP fast reroute capability for ISIS.

         When the value of vRtrIsisLoopfreeAlternate is set to 'true' IP fast
         reroute capability for ISIS is enabled and when
         vRtrIsisLoopfreeAlternate is set to 'false' IP fast reroute capability
         for ISIS is disabled."
    DEFVAL      { false }
    ::= { vRtrIsisEntry 61 }

vRtrIsisIPv4McastRoutingTopo     OBJECT-TYPE
    SYNTAX      IsisRoutingTopology
    MAX-ACCESS  read-only
    STATUS      obsolete
    DESCRIPTION
        "The value of vRtrIsisIPv4McastRoutingTopo specifies which multicast
         topology (MT) is enabled.

         If the value of vRtrIsisIPv4McastRoutingTopo is 'native' then MT 0
         IPv4 topology is enabled and ISIS protocol will add routes to the
         multicast RTM. If the value of vRtrIsisIPv4McastRoutingTopo is 'mt'
         then MT 3 IPv4 topology is enabled and routes will be added to the
         multicast RTM. If the value of vRtrIsisIPv4McastRoutingTopo is 'none'
         then nothing is added to the multicast RTM."
    DEFVAL      { native }
    ::= { vRtrIsisEntry 62 }

vRtrIsisIPv6McastRoutingTopo     OBJECT-TYPE
    SYNTAX      IsisRoutingTopology
    MAX-ACCESS  read-only
    STATUS      obsolete
    DESCRIPTION
        "The value of vRtrIsisIPv6McastRoutingTopo specifies which multicast
         topology (MT) is enabled.

         If the value of vRtrIsisIPv6McastRoutingTopo is 'native' then MT 0
         IPv6 topology is enabled and ISIS protocol will add routes to the
         multicast RTM. If the value of vRtrIsisIPv6McastRoutingTopo is 'mt'
         then MT 4 IPv6 topology is enabled and routes will be added to the
         multicast RTM. If the value of vRtrIsisIPv6McastRoutingTopo is 'none'
         then nothing is added to the multicast RTM."
    DEFVAL      { native }
    ::= { vRtrIsisEntry 63 }

vRtrIsisMultiTopoIPv4Mcast       OBJECT-TYPE
    SYNTAX      TruthValue
    MAX-ACCESS  read-only
    STATUS      obsolete
    DESCRIPTION
        "The value of vRtrIsisMultiTopoIPv4Mcast specifies if IPv4 multicast is
         enabled for ISIS multi topology.

         To enable IPv4 multicast on ISIS, vRtrIsisMultiTopology should be set
         to 'true'."
    DEFVAL      { false }
    ::= { vRtrIsisEntry 64 }

vRtrIsisMultiTopoIPv6Mcast       OBJECT-TYPE
    SYNTAX      TruthValue
    MAX-ACCESS  read-only
    STATUS      obsolete
    DESCRIPTION
        "The value of vRtrIsisMultiTopoIPv6Mcast specifies if IPv6 multicast is
         enabled for ISIS multi topology.

         To enable IPv6 multicast on ISIS, vRtrIsisMultiTopology should be set
         to 'true'."
    DEFVAL      { false }
    ::= { vRtrIsisEntry 65 }

vRtrIsisOverloadMaxMetric        OBJECT-TYPE
    SYNTAX      TruthValue
    MAX-ACCESS  read-only
    STATUS      obsolete
    DESCRIPTION
        "The value of vRtrIsisOverloadMaxMetric specifies whether max-metric is
         enabled or disabled for this instance of IS-IS on the router.

         If the value of vRtrIsisOverloadMaxMetric set to 'true', the SROS
         router would not set the overload bit but would instead set all
         transit links to the maximum value of '0xFFFFFE'."
    DEFVAL      { false }
    ::= { vRtrIsisEntry 66 }

vRtrIsisOverloadOnBootMaxMetric  OBJECT-TYPE
    SYNTAX      TruthValue
    MAX-ACCESS  read-only
    STATUS      obsolete
    DESCRIPTION
        "The value of vRtrIsisOverloadOnBootMaxMetric specifies whether
         max-metric is enabled or disabled for this instance of IS-IS on the
         router.

         If the value of vRtrIsisOverloadOnBootMaxMetric set to 'true', the
         SROS router would not set the overload bit but would instead set all
         transit links to the maximum value of '0xFFFFFE'."
    DEFVAL      { false }
    ::= { vRtrIsisEntry 67 }

vRtrIsisRouterId                 OBJECT-TYPE
    SYNTAX      Unsigned32
    MAX-ACCESS  read-only
    STATUS      obsolete
    DESCRIPTION
        "The value of vRtrIsisRouterId specifies a 32-bit integer uniquely
         identifying the router in the Autonomous System."
    DEFVAL      { 0 }
    ::= { vRtrIsisEntry 68 }

vRtrIsisAdvRtrCapability         OBJECT-TYPE
    SYNTAX      INTEGER {
        disable (0),
        area    (2),
        as      (3)
    }
    MAX-ACCESS  read-only
    STATUS      obsolete
    DESCRIPTION
        "The value of vRtrIsisAdvRtrCapability specifies the ISIS advertise
         router capabilities."
    DEFVAL      { disable }
    ::= { vRtrIsisEntry 69 }

vRtrIsisHelloPadding             OBJECT-TYPE
    SYNTAX      INTEGER {
        disable  (0),
        adaptive (1),
        loose    (2),
        strict   (3)
    }
    MAX-ACCESS  read-only
    STATUS      obsolete
    DESCRIPTION
        "The value of vRtrIsisHelloPadding specifies whether padding should be
         configured on the ISIS hello packets.

         If the value of vRtrIsisHelloPadding is set to disable, the padding is
         disabled on all types of interfaces for all adjacency states.

         If the value of vRtrIsisHelloPadding is set to adaptive, the padding
         is configured until the state of the neighbor adjacency is up.

         If the value of vRtrIsisHelloPadding is set to loose, the padding is
         configured until the state of the neighbor adjacency is initialized.

         If the value of vRtrIsisHelloPadding is set to strict, the padding is
         configured for all adjacency states."
    DEFVAL      { disable }
    ::= { vRtrIsisEntry 70 }

vRtrIsisOperRouterId             OBJECT-TYPE
    SYNTAX      Unsigned32
    MAX-ACCESS  read-only
    STATUS      obsolete
    DESCRIPTION
        "The value of vRtrIsisOperRouterId indicates a 32-bit integer uniquely
         identifying the router in the Autonomous System."
    ::= { vRtrIsisEntry 71 }

vRtrIsisIgnoreLspErrors          OBJECT-TYPE
    SYNTAX      TruthValue
    MAX-ACCESS  read-only
    STATUS      obsolete
    DESCRIPTION
        "The value of the object vRtrIsisIgnoreLspErrors specifies whether
         checksum errors are ignored or not.

         If the value of vRtrIsisIgnoreLspErrors is set to 'false' lsp packets
         (CSNP/PSNP) with checksum errors will purge the corresponding lsp
         entry in the database; if the value is set to 'true', the packet will
         get discarded."
    DEFVAL      { false }
    ::= { vRtrIsisEntry 72 }

vRtrIsisLevelTable               OBJECT-TYPE
    SYNTAX      SEQUENCE OF VRtrIsisLevelEntry
    MAX-ACCESS  not-accessible
    STATUS      obsolete
    DESCRIPTION
        "The vRtrIsisLevelTable provides attributes to be applied on a specific
         IS-IS protocol level.

         This table is obsolete and replaced by tmnxIsisLevelTable in
         TIMETRA-ISIS-NG-MIB."
    ::= { vRtrIsisSystemObjs 2 }

vRtrIsisLevelEntry               OBJECT-TYPE
    SYNTAX      VRtrIsisLevelEntry
    MAX-ACCESS  not-accessible
    STATUS      obsolete
    DESCRIPTION
        "Each row entry in the vRtrIsisLevelTable represents IS-IS level
         default global attributes to be used with interfaces belonging to
         a specific IS-IS protocol instance on a specific
         router instance.  The rows in this table cannot be created nor
         destroyed by SNMP SET requests.  There are always two rows in this
         table that are created by the agent with default values upon system
         initialization."
    INDEX       {
        isisSysInstance,
        vRtrIsisLevel
    }
    ::= { vRtrIsisLevelTable 1 }

VRtrIsisLevelEntry               ::= SEQUENCE
{
    vRtrIsisLevel                    INTEGER,
    vRtrIsisLevelAuthKey             OCTET STRING,
    vRtrIsisLevelAuthType            INTEGER,
    vRtrIsisLevelExtPreference       Unsigned32,
    vRtrIsisLevelPreference          Unsigned32,
    vRtrIsisLevelWideMetricsOnly     TruthValue,
    vRtrIsisLevelOverloadStatus      INTEGER,
    vRtrIsisLevelOverloadTimeLeft    TimeInterval,
    vRtrIsisLevelNumLSPs             Unsigned32,
    vRtrIsisLevelCsnpAuthentication  TruthValue,
    vRtrIsisLevelHelloAuthentication TruthValue,
    vRtrIsisLevelPsnpAuthentication  TruthValue,
    vRtrIsisLevelDefMetric           Unsigned32,
    vRtrIsisLevelIPv6DefMetric       Unsigned32,
    vRtrIsisLevelLoopfreeAltExclude  TruthValue,
    vRtrIsisLevelDefIPv4McastMetric  Unsigned32,
    vRtrIsisLevelDefIPv6McastMetric  Unsigned32,
    vRtrIsisLevelAdvRtrCapability    TruthValue
}

vRtrIsisLevel                    OBJECT-TYPE
    SYNTAX      INTEGER {
        level1 (1),
        level2 (2)
    }
    MAX-ACCESS  not-accessible
    STATUS      obsolete
    DESCRIPTION
        "The value of vRtrIsisLevel indicates the IS-IS protocol level to which
         these row attributes are applied."
    ::= { vRtrIsisLevelEntry 1 }

vRtrIsisLevelAuthKey             OBJECT-TYPE
    SYNTAX      OCTET STRING (SIZE (0..254))
    MAX-ACCESS  read-only
    STATUS      obsolete
    DESCRIPTION
        "vRtrIsisLevelAuthKey is the authentication key string used to
         verify the authenticity of packets sent by neighboring routers on
         an IS-IS interface at this level.  For authentication to succeed
         both the authentication key and the authentication type defined
         by the vRtrIsisLevelAuthType variable must match.  If
         vRtrIsisLevelAuthType is set to 'password', vRtrIsisLevelAuthKey
         can include any ASCII character.

         When read, vRtrIsisLevelAuthKey always returns an Octet String of
         length zero."
    DEFVAL      { ''H }
    ::= { vRtrIsisLevelEntry 2 }

vRtrIsisLevelAuthType            OBJECT-TYPE
    SYNTAX      INTEGER {
        useGlobal (0),
        none      (1),
        password  (2),
        md5       (3)
    }
    MAX-ACCESS  read-only
    STATUS      obsolete
    DESCRIPTION
        "The value of vRtrIsisLevelAuthType indicates the method of
         authentication used to verify the authenticity of packets sent
         by neighboring routers on an IS-IS interface at this level.  For
         authentication to succeed both the authentication key defined in
         the vRtrIsisLevelAuthKey variable and the authentication type
         must match."
    DEFVAL      { none }
    ::= { vRtrIsisLevelEntry 3 }

vRtrIsisLevelExtPreference       OBJECT-TYPE
    SYNTAX      Unsigned32 (1..255)
    MAX-ACCESS  read-only
    STATUS      obsolete
    DESCRIPTION
        "The value of vRtrIsisLevelExtPreference specifies the preference
         level to be used with external routes at this IS-IS level.  A
         route can be learned from different routing protocols supported
         in the system, in which case their costs are not comparable.  In
         this case the preference value is used to decide which route to
         use.

         The initial default external preference value for IS-IS level 1
         is 160.  The initial default external preference value for IS-IS
         level 2 is 165."
    ::= { vRtrIsisLevelEntry 4 }

vRtrIsisLevelPreference          OBJECT-TYPE
    SYNTAX      Unsigned32 (1..255)
    MAX-ACCESS  read-only
    STATUS      obsolete
    DESCRIPTION
        "The value of vRtrIsisLevelPreference specifies the preference
         level to be used with internal routes at this IS-IS level.  A
         route can be learned from different routing protocols supported
         in the system, in which case their costs are not comparable.  In
         this case the preference value is used to decide which route to
         use.

         The initial default internal preference value for IS-IS level 1
         is 15.  The initial default internal preference value for IS-IS
         level 2 is 18."
    ::= { vRtrIsisLevelEntry 5 }

vRtrIsisLevelWideMetricsOnly     OBJECT-TYPE
    SYNTAX      TruthValue
    MAX-ACCESS  read-only
    STATUS      obsolete
    DESCRIPTION
        "IS-IS metrics can have values between 1 and 63, referred to as
         small metrics.  IS-IS generates two TLVs: one for the adjacency
         and one for the IP prefix.  In order to support traffic
         engineering, wider metrics are required; a second pair of TLVs
         are also generated.

         When vRtrIsisLevelWideMetricsOnly has a value of 'false', both the
         small and wide metric pairs of TLVs are generated.

         When vRtrIsisLevelWideMetricsOnly has a value of 'true', only the wide
         metric pair of TLVs is generated."
    DEFVAL      { false }
    ::= { vRtrIsisLevelEntry 6 }

vRtrIsisLevelOverloadStatus      OBJECT-TYPE
    SYNTAX      INTEGER {
        notInOverload (1),
        dynamic       (2),
        manual        (3),
        manualOnBoot  (4),
        singleSfm     (5)
    }
    MAX-ACCESS  read-only
    STATUS      obsolete
    DESCRIPTION
        "The value of vRtrIsisLevelOverloadStatus indicates whether or not
         this level is in overload state.  When has the value
         'notInOverload', the IS-IS level is normal state.  When the value
         is 'dynamic', the level is in the overload state because of
         insufficient memory to add additional entries to the IS-IS
         database for this level.  When the value is 'manual', the level
         has been put into the overload state administratively as a result
         of the isisSysSetOverload object in the ISIS-MIB having been set.

         When the value is 'singleSfm', this level is in overload because there
         is only a single SFM functioning, while the value of the
         single-SFM-overload state  (referred to as
         TIMETRA-VRTR-MIB::vRtrSingleSfmOverloadAdminState) is equal to
         'inService' for this router instance."
    ::= { vRtrIsisLevelEntry 7 }

vRtrIsisLevelOverloadTimeLeft    OBJECT-TYPE
    SYNTAX      TimeInterval
    MAX-ACCESS  read-only
    STATUS      obsolete
    DESCRIPTION
        "The value of vRtrIsisLevelOverloadTimeLeft indicates the remaining
         time, measured in units of centiseconds, before this level will
         attempt to enter its normal state.

         If vRtrIsisLevelOverloadStatus has a value of 'notInOverload', then a
         read of vRtrIsisLevelOverloadTimeLeft returns zero (0)."
    ::= { vRtrIsisLevelEntry 8 }

vRtrIsisLevelNumLSPs             OBJECT-TYPE
    SYNTAX      Unsigned32
    MAX-ACCESS  read-only
    STATUS      obsolete
    DESCRIPTION
        "The value of vRtrIsisLevelNumLSPs indicates the number of LSPs
         existing in the system for the particular level."
    ::= { vRtrIsisLevelEntry 9 }

vRtrIsisLevelCsnpAuthentication  OBJECT-TYPE
    SYNTAX      TruthValue
    MAX-ACCESS  read-only
    STATUS      obsolete
    DESCRIPTION
        "When vRtrIsisLevelCsnpAuthentication has a value of 'true', enables
         authentication of individual ISIS packets of CSNP type at this level.
         The value of 'false'

         When vRtrIsisLevelCsnpAuthentication has a value of 'false',
         suppresses authentication of CSNP packets at this level."
    DEFVAL      { true }
    ::= { vRtrIsisLevelEntry 10 }

vRtrIsisLevelHelloAuthentication OBJECT-TYPE
    SYNTAX      TruthValue
    MAX-ACCESS  read-only
    STATUS      obsolete
    DESCRIPTION
        "When vRtrIsisLevelHelloAuthentication has a value of 'true', enables
         authentication of individual ISIS packets of HELLO type at this level.
         The value of 'false'

         When vRtrIsisLevelHelloAuthentication has a value of 'false',
         suppresses authentication of HELLO packets at this level."
    DEFVAL      { true }
    ::= { vRtrIsisLevelEntry 11 }

vRtrIsisLevelPsnpAuthentication  OBJECT-TYPE
    SYNTAX      TruthValue
    MAX-ACCESS  read-only
    STATUS      obsolete
    DESCRIPTION
        "When vRtrIsisLevelPsnpAuthentication has a value of 'true', enables
         authentication of individual ISIS packets of PSNP type at this level.
         The value of 'false'

         When vRtrIsisLevelPsnpAuthentication has a value of 'false',
         suppresses authentication of PSNP packets at this level."
    DEFVAL      { true }
    ::= { vRtrIsisLevelEntry 12 }

vRtrIsisLevelDefMetric           OBJECT-TYPE
    SYNTAX      Unsigned32 (0..16777215)
    MAX-ACCESS  read-only
    STATUS      obsolete
    DESCRIPTION
        "The value of vRtrIsisLevelDefMetric specifies the configurable default
         metric used for all IS-IS interfaces on this level.

         The value of vRtrIsisLevelDefMetric will not be used if
         vRtrIsisIfLevelAdminMetric is configured for an interface."
    DEFVAL      { 10 }
    ::= { vRtrIsisLevelEntry 13 }

vRtrIsisLevelIPv6DefMetric       OBJECT-TYPE
    SYNTAX      Unsigned32 (0..16777215)
    MAX-ACCESS  read-only
    STATUS      obsolete
    DESCRIPTION
        "The value of vRtrIsisLevelIPv6DefMetric specifies the configurable
         default metric used for all IS-IS interfaces on this level for IPv6.

         The value of vRtrIsisLevelIPv6DefMetric will not be used if
         vRtrIsisIfLvlIPv6UcastAdmMet is configured for an interface."
    DEFVAL      { 10 }
    ::= { vRtrIsisLevelEntry 14 }

vRtrIsisLevelLoopfreeAltExclude  OBJECT-TYPE
    SYNTAX      TruthValue
    MAX-ACCESS  read-only
    STATUS      obsolete
    DESCRIPTION
        "The value of vRtrIsisLevelLoopfreeAltExclude specifies whether or not
         the ISIS level should be excluded during LFA calculations. If the
         value is 'true', the ISIS level is excluded from LFA calculations. If
         the value is 'false', the ISIS level is included in LFA calculations.

         The value of vRtrIsisLevelLoopfreeAltExclude is only valid when
         vRtrIsisLoopfreeAlternate has a value of 'true'."
    DEFVAL      { false }
    ::= { vRtrIsisLevelEntry 15 }

vRtrIsisLevelDefIPv4McastMetric  OBJECT-TYPE
    SYNTAX      Unsigned32 (0..16777215)
    MAX-ACCESS  read-only
    STATUS      obsolete
    DESCRIPTION
        "The value of vRtrIsisLevelDefIPv4McastMetric specifies the
         configurable default IPv4 multicast metric used for all IS-IS
         interfaces on this level."
    DEFVAL      { 10 }
    ::= { vRtrIsisLevelEntry 16 }

vRtrIsisLevelDefIPv6McastMetric  OBJECT-TYPE
    SYNTAX      Unsigned32 (0..16777215)
    MAX-ACCESS  read-only
    STATUS      obsolete
    DESCRIPTION
        "The value of vRtrIsisLevelDefIPv6McastMetric specifies the
         configurable default IPv6 multicast metric used for all IS-IS
         interfaces on this level."
    DEFVAL      { 10 }
    ::= { vRtrIsisLevelEntry 17 }

vRtrIsisLevelAdvRtrCapability    OBJECT-TYPE
    SYNTAX      TruthValue
    MAX-ACCESS  read-only
    STATUS      obsolete
    DESCRIPTION
        "The value of vRtrIsisLevelAdvRtrCapability specifies whether or not
         advertise-router-capabilities are enabled at IS-IS instance L1 or L2
         level."
    DEFVAL      { true }
    ::= { vRtrIsisLevelEntry 18 }

vRtrIsisStatsTable               OBJECT-TYPE
    SYNTAX      SEQUENCE OF VRtrIsisStatsEntry
    MAX-ACCESS  not-accessible
    STATUS      obsolete
    DESCRIPTION
        "The vRtrIsisStatsTable provides statistics for each instance of IS-IS
         protocol configured. There is a one-to-one dependent relationship
         between the tables vRtrIsisTable and vRtrIsisStatsTable.

         This table is obsolete and replaced by tmnxIsisStatsTable in
         TIMETRA-ISIS-NG-MIB."
    ::= { vRtrIsisSystemObjs 3 }

vRtrIsisStatsEntry               OBJECT-TYPE
    SYNTAX      VRtrIsisStatsEntry
    MAX-ACCESS  not-accessible
    STATUS      obsolete
    DESCRIPTION
        "Each row entry in the vRtrIsisStatsTable stores statistics for an
         instance of IS-IS protocol configured."
    INDEX       { isisSysInstance }
    ::= { vRtrIsisStatsTable 1 }

VRtrIsisStatsEntry               ::= SEQUENCE
{
    vRtrIsisSpfRuns                  Counter32,
    vRtrIsisLSPRegenerations         Counter32,
    vRtrIsisInitiatedPurges          Counter32,
    vRtrIsisLSPRecd                  Counter32,
    vRtrIsisLSPDrop                  Counter32,
    vRtrIsisLSPSent                  Counter32,
    vRtrIsisLSPRetrans               Counter32,
    vRtrIsisIIHRecd                  Counter32,
    vRtrIsisIIHDrop                  Counter32,
    vRtrIsisIIHSent                  Counter32,
    vRtrIsisIIHRetrans               Counter32,
    vRtrIsisCSNPRecd                 Counter32,
    vRtrIsisCSNPDrop                 Counter32,
    vRtrIsisCSNPSent                 Counter32,
    vRtrIsisCSNPRetrans              Counter32,
    vRtrIsisPSNPRecd                 Counter32,
    vRtrIsisPSNPDrop                 Counter32,
    vRtrIsisPSNPSent                 Counter32,
    vRtrIsisPSNPRetrans              Counter32,
    vRtrIsisUnknownRecd              Counter32,
    vRtrIsisUnknownDrop              Counter32,
    vRtrIsisUnknownSent              Counter32,
    vRtrIsisUnknownRetrans           Counter32,
    vRtrIsisCSPFRequests             Counter32,
    vRtrIsisCSPFDroppedRequests      Counter32,
    vRtrIsisCSPFPathsFound           Counter32,
    vRtrIsisCSPFPathsNotFound        Counter32,
    vRtrIsisLfaRuns                  Counter32
}

vRtrIsisSpfRuns                  OBJECT-TYPE
    SYNTAX      Counter32
    MAX-ACCESS  read-only
    STATUS      obsolete
    DESCRIPTION
        "The value of vRtrIsisSpfRuns indicates the number of times shortest
         path first calculations have been made."
    ::= { vRtrIsisStatsEntry 1 }

vRtrIsisLSPRegenerations         OBJECT-TYPE
    SYNTAX      Counter32
    MAX-ACCESS  read-only
    STATUS      obsolete
    DESCRIPTION
        "The value of vRtrIsisLSPRegenerations maintains the count of LSP
         regenerations."
    ::= { vRtrIsisStatsEntry 2 }

vRtrIsisInitiatedPurges          OBJECT-TYPE
    SYNTAX      Counter32
    MAX-ACCESS  read-only
    STATUS      obsolete
    DESCRIPTION
        "The value of vRtrIsisInitiatedPurges counts the number of times purges
         have been initiated."
    ::= { vRtrIsisStatsEntry 3 }

vRtrIsisLSPRecd                  OBJECT-TYPE
    SYNTAX      Counter32
    MAX-ACCESS  read-only
    STATUS      obsolete
    DESCRIPTION
        "The count of link state PDUs received by this instance of the protocol
         is maintained by vRtrIsisLSPRecd."
    ::= { vRtrIsisStatsEntry 4 }

vRtrIsisLSPDrop                  OBJECT-TYPE
    SYNTAX      Counter32
    MAX-ACCESS  read-only
    STATUS      obsolete
    DESCRIPTION
        "The count of link state PDUs dropped by this instance of the protocol
         is maintained by vRtrIsisLSPDrop."
    ::= { vRtrIsisStatsEntry 5 }

vRtrIsisLSPSent                  OBJECT-TYPE
    SYNTAX      Counter32
    MAX-ACCESS  read-only
    STATUS      obsolete
    DESCRIPTION
        "The count of link state PDUs sent out by this instance of the protocol
         is maintained by vRtrIsisLSPSent."
    ::= { vRtrIsisStatsEntry 6 }

vRtrIsisLSPRetrans               OBJECT-TYPE
    SYNTAX      Counter32
    MAX-ACCESS  read-only
    STATUS      obsolete
    DESCRIPTION
        "The count of link state PDUs that had to be retransmitted by this
         instance of the protocol is maintained by vRtrIsisLSPRetrans."
    ::= { vRtrIsisStatsEntry 7 }

vRtrIsisIIHRecd                  OBJECT-TYPE
    SYNTAX      Counter32
    MAX-ACCESS  read-only
    STATUS      obsolete
    DESCRIPTION
        "The count of link state PDUs received by this instance of the protocol
         is maintained by vRtrIsisIIHRecd."
    ::= { vRtrIsisStatsEntry 8 }

vRtrIsisIIHDrop                  OBJECT-TYPE
    SYNTAX      Counter32
    MAX-ACCESS  read-only
    STATUS      obsolete
    DESCRIPTION
        "The count of link state PDUs dropped by this instance of the protocol
         is maintained by vRtrIsisIIHDrop."
    ::= { vRtrIsisStatsEntry 9 }

vRtrIsisIIHSent                  OBJECT-TYPE
    SYNTAX      Counter32
    MAX-ACCESS  read-only
    STATUS      obsolete
    DESCRIPTION
        "The count of link state PDUs sent out by this instance of the protocol
         is maintained by vRtrIsisIIHSent."
    ::= { vRtrIsisStatsEntry 10 }

vRtrIsisIIHRetrans               OBJECT-TYPE
    SYNTAX      Counter32
    MAX-ACCESS  read-only
    STATUS      obsolete
    DESCRIPTION
        "The count of link state PDUs that had to be retransmitted by this
         instance of the protocol is maintained by vRtrIsisIIHRetrans."
    ::= { vRtrIsisStatsEntry 11 }

vRtrIsisCSNPRecd                 OBJECT-TYPE
    SYNTAX      Counter32
    MAX-ACCESS  read-only
    STATUS      obsolete
    DESCRIPTION
        "The count of link state PDUs received by this instance of the protocol
         is maintained by vRtrIsisCSNPRecd."
    ::= { vRtrIsisStatsEntry 12 }

vRtrIsisCSNPDrop                 OBJECT-TYPE
    SYNTAX      Counter32
    MAX-ACCESS  read-only
    STATUS      obsolete
    DESCRIPTION
        "The count of link state PDUs dropped by this instance of the protocol
         is maintained by vRtrIsisCSNPDrop."
    ::= { vRtrIsisStatsEntry 13 }

vRtrIsisCSNPSent                 OBJECT-TYPE
    SYNTAX      Counter32
    MAX-ACCESS  read-only
    STATUS      obsolete
    DESCRIPTION
        "The count of link state PDUs sent out by this instance of the protocol
         is maintained by vRtrIsisCSNPSent."
    ::= { vRtrIsisStatsEntry 14 }

vRtrIsisCSNPRetrans              OBJECT-TYPE
    SYNTAX      Counter32
    MAX-ACCESS  read-only
    STATUS      obsolete
    DESCRIPTION
        "The count of link state PDUs that had to be retransmitted by this
         instance of the protocol is maintained by vRtrIsisCSNPRetrans."
    ::= { vRtrIsisStatsEntry 15 }

vRtrIsisPSNPRecd                 OBJECT-TYPE
    SYNTAX      Counter32
    MAX-ACCESS  read-only
    STATUS      obsolete
    DESCRIPTION
        "The count of link state PDUs received by this instance of the protocol
         is maintained by vRtrIsisPSNPRecd."
    ::= { vRtrIsisStatsEntry 16 }

vRtrIsisPSNPDrop                 OBJECT-TYPE
    SYNTAX      Counter32
    MAX-ACCESS  read-only
    STATUS      obsolete
    DESCRIPTION
        "The count of link state PDUs dropped by this instance of the protocol
         is maintained by vRtrIsisPSNPDrop."
    ::= { vRtrIsisStatsEntry 17 }

vRtrIsisPSNPSent                 OBJECT-TYPE
    SYNTAX      Counter32
    MAX-ACCESS  read-only
    STATUS      obsolete
    DESCRIPTION
        "The count of link state PDUs sent out by this instance of the protocol
         is maintained by vRtrIsisPSNPSent."
    ::= { vRtrIsisStatsEntry 18 }

vRtrIsisPSNPRetrans              OBJECT-TYPE
    SYNTAX      Counter32
    MAX-ACCESS  read-only
    STATUS      obsolete
    DESCRIPTION
        "The count of link state PDUs that had to be retransmitted by this
         instance of the protocol is maintained by vRtrIsisPSNPRetrans."
    ::= { vRtrIsisStatsEntry 19 }

vRtrIsisUnknownRecd              OBJECT-TYPE
    SYNTAX      Counter32
    MAX-ACCESS  read-only
    STATUS      obsolete
    DESCRIPTION
        "The count of link state PDUs received by this instance of the protocol
         is maintained by vRtrIsisUnknownRecd."
    ::= { vRtrIsisStatsEntry 20 }

vRtrIsisUnknownDrop              OBJECT-TYPE
    SYNTAX      Counter32
    MAX-ACCESS  read-only
    STATUS      obsolete
    DESCRIPTION
        "The count of link state PDUs dropped by this instance of the protocol
         is maintained by vRtrIsisUnknownDrop."
    ::= { vRtrIsisStatsEntry 21 }

vRtrIsisUnknownSent              OBJECT-TYPE
    SYNTAX      Counter32
    MAX-ACCESS  read-only
    STATUS      obsolete
    DESCRIPTION
        "The count of link state PDUs sent out by this instance of the protocol
         is maintained by vRtrIsisUnknownSent."
    ::= { vRtrIsisStatsEntry 22 }

vRtrIsisUnknownRetrans           OBJECT-TYPE
    SYNTAX      Counter32
    MAX-ACCESS  read-only
    STATUS      obsolete
    DESCRIPTION
        "The count of link state PDUs that had to be retransmitted by this
         instance of the protocol is maintained by vRtrIsisUnknownRetrans."
    ::= { vRtrIsisStatsEntry 23 }

vRtrIsisCSPFRequests             OBJECT-TYPE
    SYNTAX      Counter32
    MAX-ACCESS  read-only
    STATUS      obsolete
    DESCRIPTION
        "vRtrIsisCSPFRequests maintains the number of CSPF requests made to the
         protocol."
    ::= { vRtrIsisStatsEntry 24 }

vRtrIsisCSPFDroppedRequests      OBJECT-TYPE
    SYNTAX      Counter32
    MAX-ACCESS  read-only
    STATUS      obsolete
    DESCRIPTION
        "vRtrIsisCSPFDroppedRequests maintains the number of dropped CSPF
         requests by the protocol."
    ::= { vRtrIsisStatsEntry 25 }

vRtrIsisCSPFPathsFound           OBJECT-TYPE
    SYNTAX      Counter32
    MAX-ACCESS  read-only
    STATUS      obsolete
    DESCRIPTION
        "vRtrIsisCSPFPathsFound maintains the number of responses to CSPF
         requests for which paths satisfying the constraints were found."
    ::= { vRtrIsisStatsEntry 26 }

vRtrIsisCSPFPathsNotFound        OBJECT-TYPE
    SYNTAX      Counter32
    MAX-ACCESS  read-only
    STATUS      obsolete
    DESCRIPTION
        "vRtrIsisCSPFPathsFound maintains the number of responses to CSPF
         requests for which no paths satisfying the constraints were found."
    ::= { vRtrIsisStatsEntry 27 }

vRtrIsisLfaRuns                  OBJECT-TYPE
    SYNTAX      Counter32
    MAX-ACCESS  read-only
    STATUS      obsolete
    DESCRIPTION
        "The value of vRtrIsisLfaRuns indicates the number of times
         loopfree-alternate calculations have been made."
    ::= { vRtrIsisStatsEntry 28 }

vRtrIsisHostnameTable            OBJECT-TYPE
    SYNTAX      SEQUENCE OF VRtrIsisHostnameEntry
    MAX-ACCESS  not-accessible
    STATUS      obsolete
    DESCRIPTION
        "The vRtrIsisHostnameTable provides the mapping of a system-id for an
         IS to the hostname as provided by the system. This table may not have
         mapping of all system-id to hostname as it is not mandatory to
         exchange hostnames.

         This table is obsolete and replaced by tmnxIsisHostTable in
         TIMETRA-ISIS-NG-MIB."
    ::= { vRtrIsisSystemObjs 4 }

vRtrIsisHostnameEntry            OBJECT-TYPE
    SYNTAX      VRtrIsisHostnameEntry
    MAX-ACCESS  not-accessible
    STATUS      obsolete
    DESCRIPTION
        "Each row entry in the vRtrIsisHostnameTable stores the mapping of a
         system-id to a hostname."
    INDEX       {
        isisSysInstance,
        vRtrIsisSysID
    }
    ::= { vRtrIsisHostnameTable 1 }

VRtrIsisHostnameEntry            ::= SEQUENCE
{
    vRtrIsisSysID                    SystemID,
    vRtrIsisHostname                 DisplayString
}

vRtrIsisSysID                    OBJECT-TYPE
    SYNTAX      SystemID
    MAX-ACCESS  not-accessible
    STATUS      obsolete
    DESCRIPTION
        "vRtrIsisSysID is the system-id for which we map the hostname in the
         object vRtrIsisHostname."
    ::= { vRtrIsisHostnameEntry 1 }

vRtrIsisHostname                 OBJECT-TYPE
    SYNTAX      DisplayString
    MAX-ACCESS  read-only
    STATUS      obsolete
    DESCRIPTION
        "vRtrIsisHostname maps the hostname for the corresponding system-id as
         stored in."
    ::= { vRtrIsisHostnameEntry 2 }

vRtrIsisRouteTable               OBJECT-TYPE
    SYNTAX      SEQUENCE OF VRtrIsisRouteEntry
    MAX-ACCESS  not-accessible
    STATUS      obsolete
    DESCRIPTION
        "The vRtrIsisRouteTable maintain the routes learned by an instance of
         IS-IS protocol.

         This table is obsolete and replaced by tmnxIsisRouteTable in
         TIMETRA-ISIS-NG-MIB."
    ::= { vRtrIsisSystemObjs 5 }

vRtrIsisRouteEntry               OBJECT-TYPE
    SYNTAX      VRtrIsisRouteEntry
    MAX-ACCESS  not-accessible
    STATUS      obsolete
    DESCRIPTION
        "Each row entry in the vRtrIsisRouteTable stores a route for a given
         instance of the IS-IS protocol."
    INDEX       {
        isisSysInstance,
        vRtrIsisRouteDest,
        vRtrIsisRouteMask,
        vRtrIsisRouteNexthopIP
    }
    ::= { vRtrIsisRouteTable 1 }

VRtrIsisRouteEntry               ::= SEQUENCE
{
    vRtrIsisRouteDest                IpAddress,
    vRtrIsisRouteMask                IpAddress,
    vRtrIsisRouteNexthopIP           IpAddress,
    vRtrIsisRouteLevel               INTEGER,
    vRtrIsisRouteSpfVersion          Counter32,
    vRtrIsisRouteMetric              Unsigned32,
    vRtrIsisRouteType                INTEGER,
    vRtrIsisRouteNHopSysID           SystemID
}

vRtrIsisRouteDest                OBJECT-TYPE
    SYNTAX      IpAddress
    MAX-ACCESS  not-accessible
    STATUS      obsolete
    DESCRIPTION
        "vRtrIsisRouteDest is the destination IP address of this route.

         This object may not have any Multicast (Class D) address value.

         Any instance of this object should be used in conjunction with the
         corresponding instance of vRtrIsisRouteMask object. The prefix is
         obtained by bitwise logical-AND of the two specified objects."
    ::= { vRtrIsisRouteEntry 1 }

vRtrIsisRouteMask                OBJECT-TYPE
    SYNTAX      IpAddress
    MAX-ACCESS  not-accessible
    STATUS      obsolete
    DESCRIPTION
        "vRtrIsisRouteMask indicates the mask to be logical-ANDed with the
         destination address to get the network prefix."
    ::= { vRtrIsisRouteEntry 2 }

vRtrIsisRouteNexthopIP           OBJECT-TYPE
    SYNTAX      IpAddress
    MAX-ACCESS  not-accessible
    STATUS      obsolete
    DESCRIPTION
        "vRtrIsisRouteNexthopIP refers to the IP address of the nexthop for
         this route."
    ::= { vRtrIsisRouteEntry 3 }

vRtrIsisRouteLevel               OBJECT-TYPE
    SYNTAX      INTEGER {
        level1IS (1),
        level2IS (2)
    }
    MAX-ACCESS  read-only
    STATUS      obsolete
    DESCRIPTION
        "vRtrIsisRouteLevel maintains the IS-IS Level at which the prefix was
         learned."
    ::= { vRtrIsisRouteEntry 4 }

vRtrIsisRouteSpfVersion          OBJECT-TYPE
    SYNTAX      Counter32
    MAX-ACCESS  read-only
    STATUS      obsolete
    DESCRIPTION
        "The version of spf calculation in which this route was selected is
         maintained by an instance of vRtrIsisRouteSpfVersion."
    ::= { vRtrIsisRouteEntry 5 }

vRtrIsisRouteMetric              OBJECT-TYPE
    SYNTAX      Unsigned32
    MAX-ACCESS  read-only
    STATUS      obsolete
    DESCRIPTION
        "vRtrIsisRouteMetric associates a metric value with the route. This is
         obtained by the SPF calculations and is used by the instance of the
         protocol. For a given prefix, the route with the lower metric is the
         shorter route."
    ::= { vRtrIsisRouteEntry 6 }

vRtrIsisRouteType                OBJECT-TYPE
    SYNTAX      INTEGER {
        internal (1),
        external (2)
    }
    MAX-ACCESS  read-only
    STATUS      obsolete
    DESCRIPTION
        "The value of vRtrIsisRouteType indicates the type of route represented
         by this row entry."
    ::= { vRtrIsisRouteEntry 7 }

vRtrIsisRouteNHopSysID           OBJECT-TYPE
    SYNTAX      SystemID
    MAX-ACCESS  read-only
    STATUS      obsolete
    DESCRIPTION
        "vRtrIsisRouteNHopSysID maintains the system-id of one nexthop IS
         through which this route is reachable."
    ::= { vRtrIsisRouteEntry 8 }

vRtrIsisPathTable                OBJECT-TYPE
    SYNTAX      SEQUENCE OF VRtrIsisPathEntry
    MAX-ACCESS  not-accessible
    STATUS      obsolete
    DESCRIPTION
        "The vRtrIsisPathTable maintains information regarding SPF and LFA
         calculations for each instance of IS-IS protocol.

         This table is obsolete and replaced by tmnxIsisPathTable in
         TIMETRA-ISIS-NG-MIB."
    ::= { vRtrIsisSystemObjs 6 }

vRtrIsisPathEntry                OBJECT-TYPE
    SYNTAX      VRtrIsisPathEntry
    MAX-ACCESS  not-accessible
    STATUS      obsolete
    DESCRIPTION
        "Each row entry in the vRtrIsisPathTable"
    INDEX       {
        isisSysInstance,
        vRtrIsisLevel,
        vRtrIsisPathID,
        vRtrIsisPathIfIndex,
        vRtrIsisPathNHopSysID
    }
    ::= { vRtrIsisPathTable 1 }

VRtrIsisPathEntry                ::= SEQUENCE
{
    vRtrIsisPathID                   OCTET STRING,
    vRtrIsisPathIfIndex              InterfaceIndex,
    vRtrIsisPathNHopSysID            SystemID,
    vRtrIsisPathMetric               Unsigned32,
    vRtrIsisPathSNPA                 SNPAAddress,
    vRtrIsisPathLfaIfIndex           InterfaceIndex,
    vRtrIsisPathLfaNHop              SystemID,
    vRtrIsisPathLfaMetric            Unsigned32,
    vRtrIsisPathLfaType              INTEGER,
    vRtrIsisPathRouteType            INTEGER
}

vRtrIsisPathID                   OBJECT-TYPE
    SYNTAX      OCTET STRING (SIZE (0..7))
    MAX-ACCESS  not-accessible
    STATUS      obsolete
    DESCRIPTION
        "The path identifier is maintained by vRtrIsisPathID. It has first 6
         octets as the system-id followed by one octet of the Lan-ID."
    ::= { vRtrIsisPathEntry 1 }

vRtrIsisPathIfIndex              OBJECT-TYPE
    SYNTAX      InterfaceIndex
    MAX-ACCESS  not-accessible
    STATUS      obsolete
    DESCRIPTION
        "vRtrIsisPathIfIndex maintains the ifIndex of the outgoing interface
         for the path."
    ::= { vRtrIsisPathEntry 2 }

vRtrIsisPathNHopSysID            OBJECT-TYPE
    SYNTAX      SystemID
    MAX-ACCESS  not-accessible
    STATUS      obsolete
    DESCRIPTION
        "The nexthop IS for this route is referenced by the system-id of the
         nexthop and is maintained in the instance of vRtrIsisPathNHopSysID."
    ::= { vRtrIsisPathEntry 3 }

vRtrIsisPathMetric               OBJECT-TYPE
    SYNTAX      Unsigned32
    MAX-ACCESS  read-only
    STATUS      obsolete
    DESCRIPTION
        "The metric assigned to this entry after SPF calculations is stored in
         vRtrIsisPathMetric. The lower the metric value, the shorter is the
         path and hence more preferred by the protocol."
    ::= { vRtrIsisPathEntry 4 }

vRtrIsisPathSNPA                 OBJECT-TYPE
    SYNTAX      SNPAAddress
    MAX-ACCESS  read-only
    STATUS      obsolete
    DESCRIPTION
        "vRtrIsisPathSNPA stores the subnet point of attachment for this path."
    ::= { vRtrIsisPathEntry 5 }

vRtrIsisPathLfaIfIndex           OBJECT-TYPE
    SYNTAX      InterfaceIndex
    MAX-ACCESS  read-only
    STATUS      obsolete
    DESCRIPTION
        "The value of vRtrIsisPathLfaIfIndex indicates the loopfree-alternate
         ifIndex of the outgoing interface for the path."
    ::= { vRtrIsisPathEntry 6 }

vRtrIsisPathLfaNHop              OBJECT-TYPE
    SYNTAX      SystemID
    MAX-ACCESS  read-only
    STATUS      obsolete
    DESCRIPTION
        "The value of vRtrIsisPathLfaNHop indicates the loopfree-alternate
         nexthop and is referenced by the system-id."
    ::= { vRtrIsisPathEntry 7 }

vRtrIsisPathLfaMetric            OBJECT-TYPE
    SYNTAX      Unsigned32
    MAX-ACCESS  read-only
    STATUS      obsolete
    DESCRIPTION
        "The value of vRtrIsisPathLfaMetric indicates the metric assigned to
         this entry which are a result of loopfree-alternate calculations. The
         lower the metric value, the shorter is the path and hence more
         preferred by the protocol. The value of vRtrIsisPathLfaMetric is valid
         only if vRtrIsisPathLfaNHop has a non-zero value."
    ::= { vRtrIsisPathEntry 8 }

vRtrIsisPathLfaType              OBJECT-TYPE
    SYNTAX      INTEGER {
        noProtection   (0),
        nodeProtection (1),
        linkProtection (2)
    }
    MAX-ACCESS  read-only
    STATUS      obsolete
    DESCRIPTION
        "The value of vRtrIsisPathLfaType indicates the type of LFA represented
         by this row entry. The value of vRtrIsisPathLfaType is valid only if
         vRtrIsisPathLfaNHop has a non-zero value."
    ::= { vRtrIsisPathEntry 9 }

vRtrIsisPathRouteType            OBJECT-TYPE
    SYNTAX      INTEGER {
        spf (0),
        lfa (1)
    }
    MAX-ACCESS  read-only
    STATUS      obsolete
    DESCRIPTION
        "The value of vRtrIsisPathRouteType indicates whether a backup route
         exists for this row entry."
    ::= { vRtrIsisPathEntry 10 }

vRtrIsisLSPTable                 OBJECT-TYPE
    SYNTAX      SEQUENCE OF VRtrIsisLSPEntry
    MAX-ACCESS  not-accessible
    STATUS      obsolete
    DESCRIPTION
        "The vRtrIsisLSPTable maintain information regarding all the LSPs in
         the LSP database of each instance of IS-IS protocol for a given level.

         This table is obsolete and replaced by tmnxIsisLSPTable in
         TIMETRA-ISIS-NG-MIB."
    ::= { vRtrIsisSystemObjs 7 }

vRtrIsisLSPEntry                 OBJECT-TYPE
    SYNTAX      VRtrIsisLSPEntry
    MAX-ACCESS  not-accessible
    STATUS      obsolete
    DESCRIPTION
        "Each row entry in the vRtrIsisLSPTable represents an LSP in the LSP
         database."
    INDEX       {
        isisSysInstance,
        vRtrIsisLevel,
        vRtrIsisLSPId
    }
    ::= { vRtrIsisLSPTable 1 }

VRtrIsisLSPEntry                 ::= SEQUENCE
{
    vRtrIsisLSPId                    OCTET STRING,
    vRtrIsisLSPSeq                   Counter32,
    vRtrIsisLSPChecksum              Integer32,
    vRtrIsisLSPLifetimeRemain        Integer32,
    vRtrIsisLSPVersion               Integer32,
    vRtrIsisLSPPktType               Integer32,
    vRtrIsisLSPPktVersion            Integer32,
    vRtrIsisLSPMaxArea               Integer32,
    vRtrIsisLSPSysIdLen              Integer32,
    vRtrIsisLSPAttributes            Integer32,
    vRtrIsisLSPUsedLen               Integer32,
    vRtrIsisLSPAllocLen              Integer32,
    vRtrIsisLSPBuff                  OCTET STRING,
    vRtrIsisLSPZeroRLT               TruthValue
}

vRtrIsisLSPId                    OBJECT-TYPE
    SYNTAX      OCTET STRING (SIZE (0..8))
    MAX-ACCESS  not-accessible
    STATUS      obsolete
    DESCRIPTION
        "The LSP Id. The format of the vRtrIsisLSPId is given as 6 octets of
         adjacency system-id followed by 1 octet Lan-ID and 1 octet LSP Number."
    ::= { vRtrIsisLSPEntry 1 }

vRtrIsisLSPSeq                   OBJECT-TYPE
    SYNTAX      Counter32
    MAX-ACCESS  read-only
    STATUS      obsolete
    DESCRIPTION
        "The sequence number of an LSP. The sequence number is a four byte
         quantity that represents the version of an LSP. The higher the
         sequence number, the more up to date the information. The sequence
         number is always incremented by the system that originated the LSP and
         ensures that there is only one version of that LSP in the entire
         network."
    ::= { vRtrIsisLSPEntry 2 }

vRtrIsisLSPChecksum              OBJECT-TYPE
    SYNTAX      Integer32 (0..65535)
    MAX-ACCESS  read-only
    STATUS      obsolete
    DESCRIPTION
        "vRtrIsisLSPChecksum is the checksum of contents of LSP from the
         SourceID field in the LSP till the end. The checksum is computed using
         the Fletcher checksum algorithm. "
    ::= { vRtrIsisLSPEntry 3 }

vRtrIsisLSPLifetimeRemain        OBJECT-TYPE
    SYNTAX      Integer32 (0..65535)
    UNITS       "seconds"
    MAX-ACCESS  read-only
    STATUS      obsolete
    DESCRIPTION
        "Remaining lifetime of this LSP. This is stored in
         vRtrIsisLSPLifetimeRemain which is a decrementing counter that
         decrements in seconds starting from the value as received in the LSP
         if not self-originated OR from vRtrIsisLspLifetime for self originated
         LSPs. When the remaining lifetime becomes zero, the contents of the
         LSP should not be considered for SPF calculation."
    ::= { vRtrIsisLSPEntry 4 }

vRtrIsisLSPVersion               OBJECT-TYPE
    SYNTAX      Integer32
    MAX-ACCESS  read-only
    STATUS      obsolete
    DESCRIPTION
        "vRtrIsisLSPVersion stores the version of the ISIS protocol that has
         generated the LSP"
    ::= { vRtrIsisLSPEntry 5 }

vRtrIsisLSPPktType               OBJECT-TYPE
    SYNTAX      Integer32
    MAX-ACCESS  read-only
    STATUS      obsolete
    DESCRIPTION
        "Packet type for instance Hello PDUs, LSPs, CSNPs OR PSNPs at both
         IS-IS protocol levels i.e. L1 and L2 as maintained in
         vRtrIsisLSPPktType. "
    ::= { vRtrIsisLSPEntry 6 }

vRtrIsisLSPPktVersion            OBJECT-TYPE
    SYNTAX      Integer32
    MAX-ACCESS  read-only
    STATUS      obsolete
    DESCRIPTION
        "vRtrIsisLSPVersion stores the version of the ISIS protocol that has
         generated the Packet."
    ::= { vRtrIsisLSPEntry 7 }

vRtrIsisLSPMaxArea               OBJECT-TYPE
    SYNTAX      Integer32
    MAX-ACCESS  read-only
    STATUS      obsolete
    DESCRIPTION
        "Maximum number of areas supported by the originator of the LSP. A
         value of 0 for vRtrIsisLSPMaxArea indicates a default of 3 areas. "
    ::= { vRtrIsisLSPEntry 8 }

vRtrIsisLSPSysIdLen              OBJECT-TYPE
    SYNTAX      Integer32
    MAX-ACCESS  read-only
    STATUS      obsolete
    DESCRIPTION
        "vRtrIsisLSPSysIdLen is the length of the system-id as used by the
         originator."
    ::= { vRtrIsisLSPEntry 9 }

vRtrIsisLSPAttributes            OBJECT-TYPE
    SYNTAX      Integer32
    MAX-ACCESS  read-only
    STATUS      obsolete
    DESCRIPTION
        "Attributes associated with the LSP. These include the attached bit,
         overload bit, IS type of the system originating the LSP and the
         partition repair capability. The attached bit and the overload bit are
         of significance only when present in the LSP numbered zero and should
         be ignored on receipt in any other LSP."
    ::= { vRtrIsisLSPEntry 10 }

vRtrIsisLSPUsedLen               OBJECT-TYPE
    SYNTAX      Integer32
    MAX-ACCESS  read-only
    STATUS      obsolete
    DESCRIPTION
        "The used length for the LSP. For an LSP that is not self originated,
         the used length is always equal to vRtrIsisLSPAllocLen. For self
         originated LSPs, the used length is less than or equal to
         vRtrIsisLSPAllocLen."
    ::= { vRtrIsisLSPEntry 11 }

vRtrIsisLSPAllocLen              OBJECT-TYPE
    SYNTAX      Integer32
    MAX-ACCESS  read-only
    STATUS      obsolete
    DESCRIPTION
        "The length allocated for the LSP to be stored. This size is stored in
         vRtrIsisLSPAllocLen."
    ::= { vRtrIsisLSPEntry 12 }

vRtrIsisLSPBuff                  OBJECT-TYPE
    SYNTAX      OCTET STRING (SIZE (27..9190))
    MAX-ACCESS  read-only
    STATUS      obsolete
    DESCRIPTION
        "vRtrIsisLSPBuff stores the LSP as existing in the LSP database."
    ::= { vRtrIsisLSPEntry 13 }

vRtrIsisLSPZeroRLT               OBJECT-TYPE
    SYNTAX      TruthValue
    MAX-ACCESS  read-only
    STATUS      obsolete
    DESCRIPTION
        "vRtrIsisLSPZeroRLT stores the LSP state if it has once reached zero
         remaining lifetime. If this object is 'true' then the object
         vRtrIsisLSPLifetimeRemain will maintain the time remaining after which
         this LSP will be discarded."
    ::= { vRtrIsisLSPEntry 14 }

vRtrIsisSpfLogTable              OBJECT-TYPE
    SYNTAX      SEQUENCE OF VRtrIsisSpfLogEntry
    MAX-ACCESS  not-accessible
    STATUS      obsolete
    DESCRIPTION
        "The vRtrIsisSpfLogTable maintains information regarding SPF runs for
         each instance of IS-IS protocol.

         There is a maximum of 20 log entries stored per IS-IS protocol
         instance.

         This table is obsolete and replaced by tmnxIsisSpfLogTable in
         TIMETRA-ISIS-NG-MIB."
    ::= { vRtrIsisSystemObjs 8 }

vRtrIsisSpfLogEntry              OBJECT-TYPE
    SYNTAX      VRtrIsisSpfLogEntry
    MAX-ACCESS  not-accessible
    STATUS      obsolete
    DESCRIPTION
        "Each entry maintains log information about a specific SPF run made on
         a particular IS-IS protocol instance."
    INDEX       {
        isisSysInstance,
        vRtrIsisSpfTimeStamp
    }
    ::= { vRtrIsisSpfLogTable 1 }

VRtrIsisSpfLogEntry              ::= SEQUENCE
{
    vRtrIsisSpfTimeStamp             TimeStamp,
    vRtrIsisSpfRunTime               TimeTicks,
    vRtrIsisSpfL1Nodes               Unsigned32,
    vRtrIsisSpfL2Nodes               Unsigned32,
    vRtrIsisSpfEventCount            Unsigned32,
    vRtrIsisSpfLastTriggerLSPId      OCTET STRING,
    vRtrIsisSpfTriggerReason         BITS,
    vRtrIsisSpfType                  INTEGER
}

vRtrIsisSpfTimeStamp             OBJECT-TYPE
    SYNTAX      TimeStamp
    MAX-ACCESS  not-accessible
    STATUS      obsolete
    DESCRIPTION
        "vRtrIsisSpfTimeStamp maintains the timestamp when the SPF run started
         on the system."
    ::= { vRtrIsisSpfLogEntry 1 }

vRtrIsisSpfRunTime               OBJECT-TYPE
    SYNTAX      TimeTicks
    MAX-ACCESS  read-only
    STATUS      obsolete
    DESCRIPTION
        "vRtrIsisSpfRunTime maintains the time (in hundredths of a second)
         required to complete the SPF run "
    ::= { vRtrIsisSpfLogEntry 2 }

vRtrIsisSpfL1Nodes               OBJECT-TYPE
    SYNTAX      Unsigned32
    MAX-ACCESS  read-only
    STATUS      obsolete
    DESCRIPTION
        "vRtrIsisSpfL1Nodes maintains the number of level 1 nodes involved in
         the SPF run."
    ::= { vRtrIsisSpfLogEntry 3 }

vRtrIsisSpfL2Nodes               OBJECT-TYPE
    SYNTAX      Unsigned32
    MAX-ACCESS  read-only
    STATUS      obsolete
    DESCRIPTION
        "vRtrIsisSpfL2Nodes maintains the number of level 2 nodes involved in
         the SPF run."
    ::= { vRtrIsisSpfLogEntry 4 }

vRtrIsisSpfEventCount            OBJECT-TYPE
    SYNTAX      Unsigned32
    MAX-ACCESS  read-only
    STATUS      obsolete
    DESCRIPTION
        "The value of vRtrIsisSpfEventCount indicates the number of SPF events
         that triggered the SPF calculation."
    ::= { vRtrIsisSpfLogEntry 5 }

vRtrIsisSpfLastTriggerLSPId      OBJECT-TYPE
    SYNTAX      OCTET STRING (SIZE (0..8))
    MAX-ACCESS  read-only
    STATUS      obsolete
    DESCRIPTION
        "vRtrIsisSpfLastTriggerLSPId maintains the LSPId of the last LSP
         processed before the SPF run."
    ::= { vRtrIsisSpfLogEntry 6 }

vRtrIsisSpfTriggerReason         OBJECT-TYPE
    SYNTAX      BITS {
        newAdjacency    (0),
        newLSP          (1),
        newArea         (2),
        reach           (3),
        ecmpChanged     (4),
        newMetric       (5),
        teChanged       (6),
        restart         (7),
        lspExpired      (8),
        lspDbChanged    (9),
        lspChanged      (10),
        newPreference   (11),
        newNLPID        (12),
        manualRun       (13),
        adminTagChanged (14),
        tunnelChanged   (15),
        throttleEnd     (16),
        lfaChanged      (17)
    }
    MAX-ACCESS  read-only
    STATUS      obsolete
    DESCRIPTION
        "The value of vRtrIsisSpfTriggerReason indicates the reasons that
         triggered this SPF run.

         newAdjacency (0)    - a new adjacency was formed.
         newLSP (1)          - a new LSP was received.
         newArea (2)         - a new area was joined.
         reach (3)           - a new prefix can be reached.
         ecmpChanged (4)     - the number of ecmp routes to a destination
                               changed.
         newMetric (5)       - a route has a new metric.
         teChanged (6)       - traffic engineering changed.
         restart (7)         - the IS-IS router was restarted.
         lspExpired (8)      - an LSP expired.
         lspDbChanged (9)    - the IS-IS LSP database was cleared.
         lspChanged (10)     - an LSP changed.
         newPreference (11)  - a route preference changed.
         newNLPID (12)       - a Network Layer Protocol was added to the
                               IS-IS router protocol set.
         manualRun (13)      - Manual request issued.
         adminTagChanged (14)- admin tag has changed.
         tunnelChanged (15)  - list of tunnels has changed.
         throttleEnd (16)    - throttling of SPF ended.
         lfaChanged (17)     - lfa changed."
    ::= { vRtrIsisSpfLogEntry 7 }

vRtrIsisSpfType                  OBJECT-TYPE
    SYNTAX      INTEGER {
        regular (0),
        lfa     (1)
    }
    MAX-ACCESS  read-only
    STATUS      obsolete
    DESCRIPTION
        "The value of vRtrIsisSpfType indicates the type of SPF calculation."
    ::= { vRtrIsisSpfLogEntry 8 }

vRtrIsisSummaryTable             OBJECT-TYPE
    SYNTAX      SEQUENCE OF VRtrIsisSummaryEntry
    MAX-ACCESS  not-accessible
    STATUS      obsolete
    DESCRIPTION
        "The vRtrIsisSummaryTable maintains the summary prefixes for a specific
         instance of IS-IS protocol.

         This table is obsolete and replaced by tmnxIsisSummaryTable in
         TIMETRA-ISIS-NG-MIB."
    ::= { vRtrIsisSystemObjs 9 }

vRtrIsisSummaryEntry             OBJECT-TYPE
    SYNTAX      VRtrIsisSummaryEntry
    MAX-ACCESS  not-accessible
    STATUS      obsolete
    DESCRIPTION
        "Each row entry in the vRtrIsisSummaryTable stores a summary prefix for
         a specific instance of the IS-IS protocol."
    INDEX       {
        isisSysInstance,
        vRtrIsisSummPrefix,
        vRtrIsisSummMask
    }
    ::= { vRtrIsisSummaryTable 1 }

VRtrIsisSummaryEntry             ::= SEQUENCE
{
    vRtrIsisSummPrefix               IpAddress,
    vRtrIsisSummMask                 IpAddress,
    vRtrIsisSummRowStatus            RowStatus,
    vRtrIsisSummLevel                INTEGER
}

vRtrIsisSummPrefix               OBJECT-TYPE
    SYNTAX      IpAddress
    MAX-ACCESS  not-accessible
    STATUS      obsolete
    DESCRIPTION
        "vRtrIsisSummPrefix specifies the prefix for the summary address entry.

         Any instance of this object should be used in conjunction with the
         corresponding instance of vRtrIsisSummMask object. The prefix is
         obtained by bitwise logical-AND of the two specified objects."
    ::= { vRtrIsisSummaryEntry 1 }

vRtrIsisSummMask                 OBJECT-TYPE
    SYNTAX      IpAddress
    MAX-ACCESS  not-accessible
    STATUS      obsolete
    DESCRIPTION
        "vRtrIsisSummMask specifies the mask for the summary address entry.

         Any instance of this object should be used in conjunction with the
         corresponding instance of vRtrIsisSummPrefix object. The prefix is
         obtained by bitwise logical-AND of the two specified objects."
    ::= { vRtrIsisSummaryEntry 2 }

vRtrIsisSummRowStatus            OBJECT-TYPE
    SYNTAX      RowStatus
    MAX-ACCESS  read-only
    STATUS      obsolete
    DESCRIPTION
        "vRtrIsisSummRowStatus is used to create an entry in this table."
    ::= { vRtrIsisSummaryEntry 3 }

vRtrIsisSummLevel                OBJECT-TYPE
    SYNTAX      INTEGER {
        level1   (1),
        level2   (2),
        level1L2 (3)
    }
    MAX-ACCESS  read-only
    STATUS      obsolete
    DESCRIPTION
        "vRtrIsisSummLevel specifies the IS-IS Level from which the prefix
         should be summarized."
    DEFVAL      { level1L2 }
    ::= { vRtrIsisSummaryEntry 4 }

vRtrIsisInetRouteTable           OBJECT-TYPE
    SYNTAX      SEQUENCE OF VRtrIsisInetRouteEntry
    MAX-ACCESS  not-accessible
    STATUS      obsolete
    DESCRIPTION
        "The vRtrIsisInetRouteTable maintains the routes learned by an instance
         of IS-IS protocol.

         This table is obsolete and replaced by tmnxIsisRouteTable in
         IMETRA-ISIS-NG-MIB."
    ::= { vRtrIsisSystemObjs 10 }

vRtrIsisInetRouteEntry           OBJECT-TYPE
    SYNTAX      VRtrIsisInetRouteEntry
    MAX-ACCESS  not-accessible
    STATUS      obsolete
    DESCRIPTION
        "Each row entry in the vRtrIsisInetRouteTable stores a route for a
         given instance of the IS-IS protocol."
    INDEX       {
        isisSysInstance,
        vRtrIsisInetRouteDestType,
        vRtrIsisInetRouteDest,
        vRtrIsisInetRoutePrefixLength,
        vRtrIsisInetRouteNexthopIPType,
        vRtrIsisInetRouteNexthopIP
    }
    ::= { vRtrIsisInetRouteTable 1 }

VRtrIsisInetRouteEntry           ::= SEQUENCE
{
    vRtrIsisInetRouteDestType        InetAddressType,
    vRtrIsisInetRouteDest            InetAddress,
    vRtrIsisInetRoutePrefixLength    InetAddressPrefixLength,
    vRtrIsisInetRouteNexthopIPType   InetAddressType,
    vRtrIsisInetRouteNexthopIP       InetAddress,
    vRtrIsisInetRouteLevel           INTEGER,
    vRtrIsisInetRouteSpfRunNumber    Counter32,
    vRtrIsisInetRouteMetric          Unsigned32,
    vRtrIsisInetRouteType            INTEGER,
    vRtrIsisInetRouteNHopSysID       SystemID
}

vRtrIsisInetRouteDestType        OBJECT-TYPE
    SYNTAX      InetAddressType
    MAX-ACCESS  not-accessible
    STATUS      obsolete
    DESCRIPTION
        "The value of vRtrIsisInetRouteDestType indicates the IP address type
         for vRtrIsisInetRouteDest."
    ::= { vRtrIsisInetRouteEntry 1 }

vRtrIsisInetRouteDest            OBJECT-TYPE
    SYNTAX      InetAddress (SIZE (4|16|20))
    MAX-ACCESS  not-accessible
    STATUS      obsolete
    DESCRIPTION
        "The value of vRtrIsisInetRouteDest indicates the destination IP
         address of this route. The address type of vRtrIsisInetRouteDest is
         indicated by vRtrIsisInetRouteDestType."
    ::= { vRtrIsisInetRouteEntry 2 }

vRtrIsisInetRoutePrefixLength    OBJECT-TYPE
    SYNTAX      InetAddressPrefixLength
    MAX-ACCESS  not-accessible
    STATUS      obsolete
    DESCRIPTION
        "The value of vRtrIsisInetRoutePrefixLength indicates the prefix length
         to be used with vRtrIsisInetRouteDest to get the network prefix."
    ::= { vRtrIsisInetRouteEntry 3 }

vRtrIsisInetRouteNexthopIPType   OBJECT-TYPE
    SYNTAX      InetAddressType
    MAX-ACCESS  not-accessible
    STATUS      obsolete
    DESCRIPTION
        "The value of vRtrIsisInetRouteNexthopIPType indicates the IP address
         type for vRtrIsisInetRouteNexthopIP."
    ::= { vRtrIsisInetRouteEntry 4 }

vRtrIsisInetRouteNexthopIP       OBJECT-TYPE
    SYNTAX      InetAddress (SIZE (4|16|20))
    MAX-ACCESS  not-accessible
    STATUS      obsolete
    DESCRIPTION
        "The value of vRtrIsisInetRouteNexthopIP indicates the IP address of
         the nexthop for this route. The address type of
         vRtrIsisInetRouteNexthopIP is indicated by
         vRtrIsisInetRouteNexthopIPType."
    ::= { vRtrIsisInetRouteEntry 5 }

vRtrIsisInetRouteLevel           OBJECT-TYPE
    SYNTAX      INTEGER {
        level1IS (1),
        level2IS (2)
    }
    MAX-ACCESS  read-only
    STATUS      obsolete
    DESCRIPTION
        "The value of vRtrIsisInetRouteLevel indicates the IS-IS Level at which
         the destination prefix was learned."
    ::= { vRtrIsisInetRouteEntry 6 }

vRtrIsisInetRouteSpfRunNumber    OBJECT-TYPE
    SYNTAX      Counter32
    MAX-ACCESS  read-only
    STATUS      obsolete
    DESCRIPTION
        "The value of vRtrIsisInetRouteSpfRunNumber indicates the run of spf
         calculation in which this route was selected."
    ::= { vRtrIsisInetRouteEntry 7 }

vRtrIsisInetRouteMetric          OBJECT-TYPE
    SYNTAX      Unsigned32
    MAX-ACCESS  read-only
    STATUS      obsolete
    DESCRIPTION
        "The value of vRtrIsisInetRouteMetric indicates the metric value
         associated with the route. This is obtained by the SPF calculations
         and is used by the instance of the protocol. For a given destination
         prefix, the route with the lower metric is the shorter route."
    ::= { vRtrIsisInetRouteEntry 8 }

vRtrIsisInetRouteType            OBJECT-TYPE
    SYNTAX      INTEGER {
        internal (1),
        external (2)
    }
    MAX-ACCESS  read-only
    STATUS      obsolete
    DESCRIPTION
        "The value of vRtrIsisInetRouteType indicates the type of route
         represented by this row entry."
    ::= { vRtrIsisInetRouteEntry 9 }

vRtrIsisInetRouteNHopSysID       OBJECT-TYPE
    SYNTAX      SystemID
    MAX-ACCESS  read-only
    STATUS      obsolete
    DESCRIPTION
        "The value of vRtrIsisInetRouteNHopSysID indicates the system-id of the
         nexthop IS through which this route is reachable."
    ::= { vRtrIsisInetRouteEntry 10 }

vRtrIsisInetSummaryTable         OBJECT-TYPE
    SYNTAX      SEQUENCE OF VRtrIsisInetSummaryEntry
    MAX-ACCESS  not-accessible
    STATUS      obsolete
    DESCRIPTION
        "The vRtrIsisInetSummaryTable maintains the summary prefixes for a
         specific instance of the IS-IS protocol.

         This table is obsolete and replaced by tmnxIsisSummaryTable in
         IMETRA-ISIS-NG-MIB."
    ::= { vRtrIsisSystemObjs 11 }

vRtrIsisInetSummaryEntry         OBJECT-TYPE
    SYNTAX      VRtrIsisInetSummaryEntry
    MAX-ACCESS  not-accessible
    STATUS      obsolete
    DESCRIPTION
        "Each row entry in the vRtrIsisInetSummaryTable stores a summary prefix
         for a specific instance of the IS-IS protocol."
    INDEX       {
        isisSysInstance,
        vRtrIsisInetSummPrefixType,
        vRtrIsisInetSummPrefix,
        vRtrIsisInetSummPrefixLength
    }
    ::= { vRtrIsisInetSummaryTable 1 }

VRtrIsisInetSummaryEntry         ::= SEQUENCE
{
    vRtrIsisInetSummPrefixType       InetAddressType,
    vRtrIsisInetSummPrefix           InetAddress,
    vRtrIsisInetSummPrefixLength     InetAddressPrefixLength,
    vRtrIsisInetSummRowStatus        RowStatus,
    vRtrIsisInetSummLevel            INTEGER,
    vRtrIsisInetSummRouteTag         Unsigned32
}

vRtrIsisInetSummPrefixType       OBJECT-TYPE
    SYNTAX      InetAddressType
    MAX-ACCESS  not-accessible
    STATUS      obsolete
    DESCRIPTION
        "The value of vRtrIsisInetSummPrefixType indicates the IP address type
         of vRtrIsisInetSummPrefix."
    ::= { vRtrIsisInetSummaryEntry 1 }

vRtrIsisInetSummPrefix           OBJECT-TYPE
    SYNTAX      InetAddress (SIZE (4|16|20))
    MAX-ACCESS  not-accessible
    STATUS      obsolete
    DESCRIPTION
        "The value of vRtrIsisInetSummPrefix indicates the prefix for this
         summary address entry."
    ::= { vRtrIsisInetSummaryEntry 2 }

vRtrIsisInetSummPrefixLength     OBJECT-TYPE
    SYNTAX      InetAddressPrefixLength
    MAX-ACCESS  not-accessible
    STATUS      obsolete
    DESCRIPTION
        "The value of vRtrIsisInetSummPrefixLength indicates the prefix length
         to be used with vRtrIsisInetSummPrefix to get the network prefix."
    ::= { vRtrIsisInetSummaryEntry 3 }

vRtrIsisInetSummRowStatus        OBJECT-TYPE
    SYNTAX      RowStatus
    MAX-ACCESS  read-only
    STATUS      obsolete
    DESCRIPTION
        "The value of vRtrIsisInetSummRowStatus specifies the row status. It
         allows entries to be created and deleted in the
         vRtrIsisInetSummaryTable."
    ::= { vRtrIsisInetSummaryEntry 4 }

vRtrIsisInetSummLevel            OBJECT-TYPE
    SYNTAX      INTEGER {
        level1   (1),
        level2   (2),
        level1L2 (3)
    }
    MAX-ACCESS  read-only
    STATUS      obsolete
    DESCRIPTION
        "The value of vRtrIsisInetSummLevel specifies the IS-IS Level from
         which the prefix should be summarized."
    DEFVAL      { level1L2 }
    ::= { vRtrIsisInetSummaryEntry 5 }

vRtrIsisInetSummRouteTag         OBJECT-TYPE
    SYNTAX      Unsigned32
    MAX-ACCESS  read-only
    STATUS      obsolete
    DESCRIPTION
        "The value of vRtrIsisInetSummRouteTag specifies a 32-bit integer tag
         for the ISIS summary address. This tag can be used to apply
         administrative policy. A value of 0 indicates that the tag has not
         been set."
    DEFVAL      { 0 }
    ::= { vRtrIsisInetSummaryEntry 6 }

vRtrIsisInetMtRouteTable         OBJECT-TYPE
    SYNTAX      SEQUENCE OF VRtrIsisInetMtRouteEntry
    MAX-ACCESS  not-accessible
    STATUS      obsolete
    DESCRIPTION
        "The vRtrIsisInetMtRouteTable maintains the routes learned by an
         instance of IS-IS protocol for a specific multi topology id.

         This table is obsolete and replaced by tmnxIsisRouteTable in
         IMETRA-ISIS-NG-MIB."
    ::= { vRtrIsisSystemObjs 12 }

vRtrIsisInetMtRouteEntry         OBJECT-TYPE
    SYNTAX      VRtrIsisInetMtRouteEntry
    MAX-ACCESS  not-accessible
    STATUS      obsolete
    DESCRIPTION
        "Each row entry in the vRtrIsisInetMtRouteTable stores a route for a
         given instance of the IS-IS protocol for a specific multi topology id."
    INDEX       {
        isisSysInstance,
        vRtrIsisInetMtRouteMtId,
        vRtrIsisInetMtRouteDestType,
        vRtrIsisInetMtRouteDest,
        vRtrIsisInetMtRoutePrefixLength,
        vRtrIsisInetMtRouteNexthopIPType,
        vRtrIsisInetMtRouteNexthopIP
    }
    ::= { vRtrIsisInetMtRouteTable 1 }

VRtrIsisInetMtRouteEntry         ::= SEQUENCE
{
    vRtrIsisInetMtRouteMtId          Unsigned32,
    vRtrIsisInetMtRouteDestType      InetAddressType,
    vRtrIsisInetMtRouteDest          InetAddress,
    vRtrIsisInetMtRoutePrefixLength  InetAddressPrefixLength,
    vRtrIsisInetMtRouteNexthopIPType InetAddressType,
    vRtrIsisInetMtRouteNexthopIP     InetAddress,
    vRtrIsisInetMtRouteLevel         INTEGER,
    vRtrIsisInetMtRouteSpfRunNumber  Counter32,
    vRtrIsisInetMtRouteMetric        Unsigned32,
    vRtrIsisInetMtRouteType          INTEGER,
    vRtrIsisInetMtRouteNHopSysID     SystemID,
    vRtrIsisInetMtRouteTag           Unsigned32,
    vRtrIsisInetMtRouteBkupFlags     INTEGER,
    vRtrIsisInetMtRouteBkupNextHopTy INTEGER,
    vRtrIsisInetMtRouteBkupNextHop   InetAddress,
    vRtrIsisInetMtRouteBkupMetric    Unsigned32,
    vRtrIsisRouteNextHopType         TmnxInetCidrNextHopType,
    vRtrIsisNextHopOwner             TmnxInetCidrNextHopOwner,
    vRtrIsisRouteNHOwnerAuxInfo      Unsigned32,
    vRtrIsisRouteBkupNHType          TmnxInetCidrNextHopType,
    vRtrIsisRouteBkupNHOwner         TmnxInetCidrNextHopOwner,
    vRtrIsisRouteBkupNHOwnAxInfo     Unsigned32
}

vRtrIsisInetMtRouteMtId          OBJECT-TYPE
    SYNTAX      Unsigned32
    MAX-ACCESS  not-accessible
    STATUS      obsolete
    DESCRIPTION
        "The value of vRtrIsisInetMtRouteMtId indicates the multi topology id
         number for this route. If multi-topology is not supported for then the
         value of vRtrIsisInetMtRouteMtId should be 0."
    ::= { vRtrIsisInetMtRouteEntry 1 }

vRtrIsisInetMtRouteDestType      OBJECT-TYPE
    SYNTAX      InetAddressType
    MAX-ACCESS  not-accessible
    STATUS      obsolete
    DESCRIPTION
        "The value of vRtrIsisInetMtRouteDestType indicates the IP address type
         for vRtrIsisInetMtRouteDest."
    ::= { vRtrIsisInetMtRouteEntry 2 }

vRtrIsisInetMtRouteDest          OBJECT-TYPE
    SYNTAX      InetAddress (SIZE (4|16|20))
    MAX-ACCESS  not-accessible
    STATUS      obsolete
    DESCRIPTION
        "The value of vRtrIsisInetMtRouteDest indicates the destination IP
         address of this route. The address type of vRtrIsisInetMtRouteDest is
         indicated by vRtrIsisInetMtRouteDestType."
    ::= { vRtrIsisInetMtRouteEntry 3 }

vRtrIsisInetMtRoutePrefixLength  OBJECT-TYPE
    SYNTAX      InetAddressPrefixLength
    MAX-ACCESS  not-accessible
    STATUS      obsolete
    DESCRIPTION
        "The value of vRtrIsisInetMtRoutePrefixLength indicates the prefix
         length to be used with vRtrIsisInetMtRouteDest to get the network
         prefix."
    ::= { vRtrIsisInetMtRouteEntry 4 }

vRtrIsisInetMtRouteNexthopIPType OBJECT-TYPE
    SYNTAX      InetAddressType
    MAX-ACCESS  not-accessible
    STATUS      obsolete
    DESCRIPTION
        "The value of vRtrIsisInetMtRouteNexthopIPType indicates the IP address
         type for vRtrIsisInetMtRouteNexthopIP."
    ::= { vRtrIsisInetMtRouteEntry 5 }

vRtrIsisInetMtRouteNexthopIP     OBJECT-TYPE
    SYNTAX      InetAddress (SIZE (4|16|20))
    MAX-ACCESS  not-accessible
    STATUS      obsolete
    DESCRIPTION
        "The value of vRtrIsisInetMtRouteNexthopIP indicates the IP address of
         the nexthop for this route. The address type of
         vRtrIsisInetMtRouteNexthopIP is indicated by
         vRtrIsisInetMtRouteNexthopIPType"
    ::= { vRtrIsisInetMtRouteEntry 6 }

vRtrIsisInetMtRouteLevel         OBJECT-TYPE
    SYNTAX      INTEGER {
        level1IS (1),
        level2IS (2)
    }
    MAX-ACCESS  read-only
    STATUS      obsolete
    DESCRIPTION
        "The value of vRtrIsisInetMtRouteLevel indicates the IS-IS Level at
         which the destination prefix was learned."
    ::= { vRtrIsisInetMtRouteEntry 7 }

vRtrIsisInetMtRouteSpfRunNumber  OBJECT-TYPE
    SYNTAX      Counter32
    MAX-ACCESS  read-only
    STATUS      obsolete
    DESCRIPTION
        "The value of vRtrIsisInetMtRouteSpfRunNumber indicates the run of spf
         calculation in which this route was selected."
    ::= { vRtrIsisInetMtRouteEntry 8 }

vRtrIsisInetMtRouteMetric        OBJECT-TYPE
    SYNTAX      Unsigned32
    MAX-ACCESS  read-only
    STATUS      obsolete
    DESCRIPTION
        "The value of vRtrIsisInetMtRouteMetric indicates the metric value
         associated with the route. This is obtained by the SPF calculations
         and is used by the instance of the protocol. For a given destination
         prefix, the route with the lower metric is the shorter route."
    ::= { vRtrIsisInetMtRouteEntry 9 }

vRtrIsisInetMtRouteType          OBJECT-TYPE
    SYNTAX      INTEGER {
        internal (1),
        external (2)
    }
    MAX-ACCESS  read-only
    STATUS      obsolete
    DESCRIPTION
        "The value of vRtrIsisInetMtRouteType indicates the type of route
         represented by this row entry."
    ::= { vRtrIsisInetMtRouteEntry 10 }

vRtrIsisInetMtRouteNHopSysID     OBJECT-TYPE
    SYNTAX      SystemID
    MAX-ACCESS  read-only
    STATUS      obsolete
    DESCRIPTION
        "The value of vRtrIsisInetMtRouteNHopSysID indicates the system-id of
         the nexthop IS through which this route is reachable."
    ::= { vRtrIsisInetMtRouteEntry 11 }

vRtrIsisInetMtRouteTag           OBJECT-TYPE
    SYNTAX      Unsigned32
    MAX-ACCESS  read-only
    STATUS      obsolete
    DESCRIPTION
        "The value of vRtrIsisInetMtRouteTag indicates a 32-bit integer route
         tag for this route. A value of 0 indicates that the tag has not been
         set."
    DEFVAL      { 0 }
    ::= { vRtrIsisInetMtRouteEntry 12 }

vRtrIsisInetMtRouteBkupFlags     OBJECT-TYPE
    SYNTAX      INTEGER {
        none   (0),
        hasLfa (1)
    }
    MAX-ACCESS  read-only
    STATUS      obsolete
    DESCRIPTION
        "The value of vRtrIsisInetMtRouteBkupFlags indicates the presence or
         absence of LFA next-hops.

         'none' indicates that no next-hop is present. 'hasLfa' indicates that
         an LFA next-hop is present in addition to the regular next-hop."
    ::= { vRtrIsisInetMtRouteEntry 13 }

vRtrIsisInetMtRouteBkupNextHopTy OBJECT-TYPE
    SYNTAX      INTEGER {
        notApplicable  (0),
        nodeProtection (1),
        linkProtection (2)
    }
    MAX-ACCESS  read-only
    STATUS      obsolete
    DESCRIPTION
        "The value of vRtrIsisInetMtRouteBkupNextHopTy indicates the type of
         protection used by the backup next-hop.

         'notApplicable' indicates that the backup next-hop type is not
         applicable. 'nodeProtection' indicates that the backup next-hop uses a
         node-protection mechanism. 'linkProtection' indicates that the backup
         next-hop uses link-protection mechanism."
    ::= { vRtrIsisInetMtRouteEntry 14 }

vRtrIsisInetMtRouteBkupNextHop   OBJECT-TYPE
    SYNTAX      InetAddress
    MAX-ACCESS  read-only
    STATUS      obsolete
    DESCRIPTION
        "The value of vRtrIsisInetMtRouteBkupNextHop indicates the IP address
         of a backup next-hop. The value of vRtrIsisInetMtRouteBkupNextHop is
         only valid when vRtrIsisInetMtRouteBkupFlags has a value of 'hasLfa'.

         The address type of vRtrIsisInetMtRouteBkupNextHop is indicated by the
         value of vRtrIsisInetMtRouteNexthopIPType."
    ::= { vRtrIsisInetMtRouteEntry 15 }

vRtrIsisInetMtRouteBkupMetric    OBJECT-TYPE
    SYNTAX      Unsigned32
    MAX-ACCESS  read-only
    STATUS      obsolete
    DESCRIPTION
        "The value of vRtrIsisInetMtRouteBkupMetric indicates the routing
         metric  for a backup route. The semantics of this metric are determined
         by the routing-protocol specified in the route's ipCidrRouteProto
         value. The value of vRtrIsisInetMtRouteBkupMetric is only
         valid when vRtrIsisInetMtRouteBkupFlags has a value of 'hasLfa'."
    ::= { vRtrIsisInetMtRouteEntry 16 }

vRtrIsisRouteNextHopType         OBJECT-TYPE
    SYNTAX      TmnxInetCidrNextHopType
    MAX-ACCESS  read-only
    STATUS      obsolete
    DESCRIPTION
        "The value of vRtrIsisRouteNextHopType indicates the type of next hop
         for this route."
    ::= { vRtrIsisInetMtRouteEntry 17 }

vRtrIsisNextHopOwner             OBJECT-TYPE
    SYNTAX      TmnxInetCidrNextHopOwner
    MAX-ACCESS  read-only
    STATUS      obsolete
    DESCRIPTION
        "The value of vRtrIsisNextHopOwner indicates the owner of next hop for
         this route."
    ::= { vRtrIsisInetMtRouteEntry 18 }

vRtrIsisRouteNHOwnerAuxInfo      OBJECT-TYPE
    SYNTAX      Unsigned32
    MAX-ACCESS  read-only
    STATUS      obsolete
    DESCRIPTION
        "The value of vRtrIsisRouteNHOwnerAuxInfo indicates the auxiliary
         information for next hop owner as indicated by vRtrIsisNextHopOwner.

         The value of vRtrIsisRouteNHOwnerAuxInfo indicates the tunnel id
         existing for this next hop type and owner."
    ::= { vRtrIsisInetMtRouteEntry 19 }

vRtrIsisRouteBkupNHType          OBJECT-TYPE
    SYNTAX      TmnxInetCidrNextHopType
    MAX-ACCESS  read-only
    STATUS      obsolete
    DESCRIPTION
        "The value of vRtrIsisRouteBkupNHType indicates the type of next hop
         for this backup route."
    ::= { vRtrIsisInetMtRouteEntry 20 }

vRtrIsisRouteBkupNHOwner         OBJECT-TYPE
    SYNTAX      TmnxInetCidrNextHopOwner
    MAX-ACCESS  read-only
    STATUS      obsolete
    DESCRIPTION
        "The value of vRtrIsisRouteBkupNHOwner indicates the owner of next hop
         for this backup route."
    ::= { vRtrIsisInetMtRouteEntry 21 }

vRtrIsisRouteBkupNHOwnAxInfo     OBJECT-TYPE
    SYNTAX      Unsigned32
    MAX-ACCESS  read-only
    STATUS      obsolete
    DESCRIPTION
        "The value of vRtrIsisRouteBkupNHOwnAxInfo indicates the auxiliary
         information for next hop owner as indicated by
         vRtrIsisRouteBkupNHOwner.

         The value of vRtrIsisRouteBkupNHOwnAxInfo indicates the tunnel id
         existing for this backup next hop type and owner."
    ::= { vRtrIsisInetMtRouteEntry 22 }

vRtrIsisMtPathTable              OBJECT-TYPE
    SYNTAX      SEQUENCE OF VRtrIsisMtPathEntry
    MAX-ACCESS  not-accessible
    STATUS      obsolete
    DESCRIPTION
        "The vRtrIsisMtPathTable maintains information regarding SPF
         calculation for each instance of IS-IS protocol.

         This table is obsolete and replaced by tmnxIsisPathTable in
         IMETRA-ISIS-NG-MIB."
    ::= { vRtrIsisSystemObjs 13 }

vRtrIsisMtPathEntry              OBJECT-TYPE
    SYNTAX      VRtrIsisMtPathEntry
    MAX-ACCESS  not-accessible
    STATUS      obsolete
    DESCRIPTION
        "Each row entry in the vRtrIsisMtPathTable represents the ISIS path for
         an instance, level, multi topology id, path identifier and the path
         outgoing interface."
    INDEX       {
        isisSysInstance,
        vRtrIsisLevel,
        vRtrIsisMtPathMtID,
        vRtrIsisMtPathID,
        vRtrIsisMtPathIfIndex,
        vRtrIsisMtPathNHopSysID
    }
    ::= { vRtrIsisMtPathTable 1 }

VRtrIsisMtPathEntry              ::= SEQUENCE
{
    vRtrIsisMtPathMtID               Unsigned32,
    vRtrIsisMtPathID                 OCTET STRING,
    vRtrIsisMtPathIfIndex            InterfaceIndex,
    vRtrIsisMtPathNHopSysID          SystemID,
    vRtrIsisMtPathMetric             Unsigned32,
    vRtrIsisMtPathSNPA               SNPAAddress,
    vRtrIsisMtPathLfaIfIndex         InterfaceIndex,
    vRtrIsisMtPathLfaNHop            SystemID,
    vRtrIsisMtPathLfaMetric          Unsigned32,
    vRtrIsisMtPathLfaType            INTEGER,
    vRtrIsisMtPathRouteType          INTEGER
}

vRtrIsisMtPathMtID               OBJECT-TYPE
    SYNTAX      Unsigned32
    MAX-ACCESS  not-accessible
    STATUS      obsolete
    DESCRIPTION
        "The value of vRtrIsisMtPathMtID indicates the multi-topology id number
         for the path. If multi-topology is not supported for the path then the
         value of vRtrIsisMtPathMtID should be 0."
    ::= { vRtrIsisMtPathEntry 1 }

vRtrIsisMtPathID                 OBJECT-TYPE
    SYNTAX      OCTET STRING (SIZE (7))
    MAX-ACCESS  not-accessible
    STATUS      obsolete
    DESCRIPTION
        "The value of vRtrIsisMtPathID indicates the path identifier. It has
         first 6 octets as the system-id followed by one octet of the Lan-ID."
    ::= { vRtrIsisMtPathEntry 2 }

vRtrIsisMtPathIfIndex            OBJECT-TYPE
    SYNTAX      InterfaceIndex
    MAX-ACCESS  not-accessible
    STATUS      obsolete
    DESCRIPTION
        "The value of vRtrIsisMtPathIfIndex indicates the ifIndex of the
         outgoing interface for the path."
    ::= { vRtrIsisMtPathEntry 3 }

vRtrIsisMtPathNHopSysID          OBJECT-TYPE
    SYNTAX      SystemID
    MAX-ACCESS  not-accessible
    STATUS      obsolete
    DESCRIPTION
        "The value of vRtrIsisMtPathNHopSysID indicates the system-id of the
         nexthop and is used to reference the nexthop for this route."
    ::= { vRtrIsisMtPathEntry 4 }

vRtrIsisMtPathMetric             OBJECT-TYPE
    SYNTAX      Unsigned32
    MAX-ACCESS  read-only
    STATUS      obsolete
    DESCRIPTION
        "The value of vRtrIsisMtPathMetric indicates the metric assigned to
         this path entry after SPF calculations. The lower the metric value,
         the shorter is the path and hence more preferred by the protocol."
    ::= { vRtrIsisMtPathEntry 5 }

vRtrIsisMtPathSNPA               OBJECT-TYPE
    SYNTAX      SNPAAddress
    MAX-ACCESS  read-only
    STATUS      obsolete
    DESCRIPTION
        "The value of vRtrIsisMtPathSNPA indicates the subnet point of
         attachment for this path."
    ::= { vRtrIsisMtPathEntry 6 }

vRtrIsisMtPathLfaIfIndex         OBJECT-TYPE
    SYNTAX      InterfaceIndex
    MAX-ACCESS  read-only
    STATUS      obsolete
    DESCRIPTION
        "The value of vRtrIsisMtPathLfaIfIndex indicates the loopfree-alternate
         ifIndex of the outgoing interface for the path."
    ::= { vRtrIsisMtPathEntry 7 }

vRtrIsisMtPathLfaNHop            OBJECT-TYPE
    SYNTAX      SystemID
    MAX-ACCESS  read-only
    STATUS      obsolete
    DESCRIPTION
        "The value of vRtrIsisMtPathLfaNHop indicates the loopfree-alternate
         nexthop and is referenced by the system-id."
    ::= { vRtrIsisMtPathEntry 8 }

vRtrIsisMtPathLfaMetric          OBJECT-TYPE
    SYNTAX      Unsigned32
    MAX-ACCESS  read-only
    STATUS      obsolete
    DESCRIPTION
        "The value of vRtrIsisMtPathLfaMetric indicates the metric assigned to
         this entry which are a result of loopfree-alternate calculations. The
         lower the metric value, the shorter is the path and hence more
         preferred by the protocol."
    ::= { vRtrIsisMtPathEntry 9 }

vRtrIsisMtPathLfaType            OBJECT-TYPE
    SYNTAX      INTEGER {
        none     (0),
        nodeLink (1),
        pathLink (2)
    }
    MAX-ACCESS  read-only
    STATUS      obsolete
    DESCRIPTION
        "The value of vRtrIsisMtPathLfaType indicates the type of route
         represented by this row entry."
    ::= { vRtrIsisMtPathEntry 10 }

vRtrIsisMtPathRouteType          OBJECT-TYPE
    SYNTAX      INTEGER {
        spf (0),
        lfa (1)
    }
    MAX-ACCESS  read-only
    STATUS      obsolete
    DESCRIPTION
        "The value of vRtrIsisMtPathRouteType indicates whether a backup route
         exists for this row entry."
    ::= { vRtrIsisMtPathEntry 11 }

vRtrIsisLfaTable                 OBJECT-TYPE
    SYNTAX      SEQUENCE OF VRtrIsisLfaEntry
    MAX-ACCESS  not-accessible
    STATUS      obsolete
    DESCRIPTION
        "The vRtrIsisLfaTable maintains information on loopfree-alternate (LFA)
         coverage for each instance of IS-IS protocol.

         This table is obsolete and replaced by tmnxIsisLfaTable in
         IMETRA-ISIS-NG-MIB."
    ::= { vRtrIsisSystemObjs 14 }

vRtrIsisLfaEntry                 OBJECT-TYPE
    SYNTAX      VRtrIsisLfaEntry
    MAX-ACCESS  not-accessible
    STATUS      obsolete
    DESCRIPTION
        "Each row entry in the vRtrIsisLfaTable represents information on LFA
         coverage for various topologies of the system."
    INDEX       {
        isisSysInstance,
        vRtrIsisLevel,
        vRtrIsisLfaFamilyCoverage
    }
    ::= { vRtrIsisLfaTable 1 }

VRtrIsisLfaEntry                 ::= SEQUENCE
{
    vRtrIsisLfaFamilyCoverage        INTEGER,
    vRtrIsisLfaNodesCovered          Unsigned32,
    vRtrIsisLfaTotalNodes            Unsigned32,
    vRtrIsisLfaNodeCoverage          Unsigned32,
    vRtrIsisLfaIpv4NodesCovered      Unsigned32,
    vRtrIsisLfaIpv4TotalNodes        Unsigned32,
    vRtrIsisLfaIpv4Coverage          Unsigned32,
    vRtrIsisLfaIpv6NodesCovered      Unsigned32,
    vRtrIsisLfaIpv6TotalNodes        Unsigned32,
    vRtrIsisLfaIpv6Coverage          Unsigned32
}

vRtrIsisLfaFamilyCoverage        OBJECT-TYPE
    SYNTAX      INTEGER {
        ipv4      (0),
        ipv6      (1),
        ipv4Mcast (2),
        ipv6Mcast (3)
    }
    MAX-ACCESS  not-accessible
    STATUS      obsolete
    DESCRIPTION
        "The value of vRtrIsisLfaFamilyCoverage indicates the multi topology
         (MTs) for which LFA coverage has been computed.

         Possible values are:

         ipv4(0)      - indicates MT0 or standard topology
         ipv6(1)      - indicates MT2 or IPv6 routing topology
         ipv4Mcast(2) - indicates MT3 or IPv4 multicast routing topology
         ipv6Mcast(3) - indicates MT4 or IPv6 multicast routing topology."
    ::= { vRtrIsisLfaEntry 1 }

vRtrIsisLfaNodesCovered          OBJECT-TYPE
    SYNTAX      Unsigned32
    MAX-ACCESS  read-only
    STATUS      obsolete
    DESCRIPTION
        "The value of vRtrIsisLfaNodesCovered indicates in absolute numbers how
         much LFA coverage is being obtained for the available routes."
    ::= { vRtrIsisLfaEntry 2 }

vRtrIsisLfaTotalNodes            OBJECT-TYPE
    SYNTAX      Unsigned32
    MAX-ACCESS  read-only
    STATUS      obsolete
    DESCRIPTION
        "The value of vRtrIsisLfaTotalNodes indicates in absolute numbers how
         much LFA coverage can be obtained for the available routes."
    ::= { vRtrIsisLfaEntry 3 }

vRtrIsisLfaNodeCoverage          OBJECT-TYPE
    SYNTAX      Unsigned32 (0..10000)
    UNITS       "centipercent"
    MAX-ACCESS  read-only
    STATUS      obsolete
    DESCRIPTION
        "The value of vRtrIsisLfaNodeCoverage indicates how much LFA coverage
         is being obtained for the set of available nodes."
    ::= { vRtrIsisLfaEntry 4 }

vRtrIsisLfaIpv4NodesCovered      OBJECT-TYPE
    SYNTAX      Unsigned32
    MAX-ACCESS  read-only
    STATUS      obsolete
    DESCRIPTION
        "The value of vRtrIsisLfaIpv4NodesCovered indicates in absolute numbers
         how much LFA coverage is being obtained for the available Ipv4 routes."
    ::= { vRtrIsisLfaEntry 5 }

vRtrIsisLfaIpv4TotalNodes        OBJECT-TYPE
    SYNTAX      Unsigned32
    MAX-ACCESS  read-only
    STATUS      obsolete
    DESCRIPTION
        "The value of vRtrIsisLfaIpv4TotalNodes indicates in absolute numbers
         how much LFA coverage can be obtained for the available Ipv4 routes."
    ::= { vRtrIsisLfaEntry 6 }

vRtrIsisLfaIpv4Coverage          OBJECT-TYPE
    SYNTAX      Unsigned32 (0..10000)
    UNITS       "centipercent"
    MAX-ACCESS  read-only
    STATUS      obsolete
    DESCRIPTION
        "The value of vRtrIsisLfaIpv4Coverage indicates how much LFA coverage
         is being obtained for the available Ipv4 routes."
    ::= { vRtrIsisLfaEntry 7 }

vRtrIsisLfaIpv6NodesCovered      OBJECT-TYPE
    SYNTAX      Unsigned32
    MAX-ACCESS  read-only
    STATUS      obsolete
    DESCRIPTION
        "The value of vRtrIsisLfaIpv6NodesCovered indicates in absolute numbers
         how much LFA coverage is being obtained for available Ipv6 routes."
    ::= { vRtrIsisLfaEntry 8 }

vRtrIsisLfaIpv6TotalNodes        OBJECT-TYPE
    SYNTAX      Unsigned32
    MAX-ACCESS  read-only
    STATUS      obsolete
    DESCRIPTION
        "The value of vRtrIsisLfaIpv6TotalNodes indicates in absolute numbers
         how much LFA coverage can be obtained for the available Ipv6 routes."
    ::= { vRtrIsisLfaEntry 9 }

vRtrIsisLfaIpv6Coverage          OBJECT-TYPE
    SYNTAX      Unsigned32 (0..10000)
    UNITS       "centipercent"
    MAX-ACCESS  read-only
    STATUS      obsolete
    DESCRIPTION
        "The value of vRtrIsisLfaIpv6Coverage indicates how much LFA coverage
         is being obtained for the available Ipv6 routes."
    ::= { vRtrIsisLfaEntry 10 }

vRtrSpbEctFidTableLastChanged    OBJECT-TYPE
    SYNTAX      TimeStamp
    MAX-ACCESS  read-only
    STATUS      current
    DESCRIPTION
        "The value of vRtrSpbEctFidTableLastChanged indicates the sysUpTime at
         the time of the last modification of vRtrSpbEctFidTable.

         If no changes were made to the entry since the last re-initialization
         of the local network management subsystem, then this object contains a
         zero value."
    ::= { vRtrIsisSystemObjs 15 }

vRtrSpbEctFidTable               OBJECT-TYPE
    SYNTAX      SEQUENCE OF VRtrSpbEctFidEntry
    MAX-ACCESS  not-accessible
    STATUS      current
    DESCRIPTION
        "The vRtrSpbEctFidTable contains entries for Shortest Path Bridging
         Equal Cost Tree (ECT) algorithm mapping to Forwarding database
         identifiers (FID).

         System will automatically create entries in this table when SPB is
         created on the isisSysInstance."
    REFERENCE
        "IEEE 802.1aq draft"
    ::= { vRtrIsisSystemObjs 16 }

vRtrSpbEctFidEntry               OBJECT-TYPE
    SYNTAX      VRtrSpbEctFidEntry
    MAX-ACCESS  not-accessible
    STATUS      current
    DESCRIPTION
        "A Shortest Path Bridging (SPB) Equal Cost Tree (ECT) algorithm mapping
         to Forwarding database identifier (FID) entry in the
         vRtrSpbEctFidTable."
    REFERENCE
        "IEEE 802.1aq draft"
    INDEX       {
        isisSysInstance,
        vRtrIsisLevel,
        vRtrSpbEctFid
    }
    ::= { vRtrSpbEctFidTable 1 }

VRtrSpbEctFidEntry               ::= SEQUENCE
{
    vRtrSpbEctFid                    TmnxSpbFid,
    vRtrSpbEctFidLastChanged         TimeStamp,
    vRtrSpbEctFidAlgorithm           INTEGER
}

vRtrSpbEctFid                    OBJECT-TYPE
    SYNTAX      TmnxSpbFid
    MAX-ACCESS  not-accessible
    STATUS      current
    DESCRIPTION
        "The value of vRtrSpbEctFid indicates forwarding database identifier
         for ECT algorithm in this IS-IS instance."
    REFERENCE
        "IEEE 802.1aq draft"
    ::= { vRtrSpbEctFidEntry 1 }

vRtrSpbEctFidLastChanged         OBJECT-TYPE
    SYNTAX      TimeStamp
    MAX-ACCESS  read-only
    STATUS      current
    DESCRIPTION
        "The value of vRtrSpbEctFidLastChanged indicates the sysUpTime at the
         time of the last modification of this entry.

         If no changes were made to the entry since the last re-initialization
         of the local network management subsystem, then this object contains a
         zero value."
    ::= { vRtrSpbEctFidEntry 2 }

vRtrSpbEctFidAlgorithm           OBJECT-TYPE
    SYNTAX      INTEGER {
        lowPathId  (0),
        highPathId (1)
    }
    MAX-ACCESS  read-create
    STATUS      current
    DESCRIPTION
        "The value of vRtrSpbEctFidAlgorithm specifies the algorithm used by
         the entry."
    DEFVAL      { lowPathId }
    ::= { vRtrSpbEctFidEntry 3 }

vRtrSpbPathTable                 OBJECT-TYPE
    SYNTAX      SEQUENCE OF VRtrSpbPathEntry
    MAX-ACCESS  not-accessible
    STATUS      current
    DESCRIPTION
        "The vRtrSpbPathTable maintains information regarding SPF calculations
         for each instance of IS-IS protocol associated with Shortest Path
         Bridging Equal Cost Tree (ECT) algorithm."
    ::= { vRtrIsisSystemObjs 17 }

vRtrSpbPathEntry                 OBJECT-TYPE
    SYNTAX      VRtrSpbPathEntry
    MAX-ACCESS  not-accessible
    STATUS      current
    DESCRIPTION
        "The vRtrSpbPathEntry maintains path information regarding SPF
         calculations for each instance of IS-IS protocol associated with
         Shortest Path Bridging Equal Cost Tree (ECT) algorithm."
    INDEX       {
        isisSysInstance,
        vRtrIsisLevel,
        vRtrSpbPathFwdTree,
        vRtrSpbEctFidAlgorithm,
        vRtrIsisPathID
    }
    ::= { vRtrSpbPathTable 1 }

VRtrSpbPathEntry                 ::= SEQUENCE
{
    vRtrSpbPathFwdTree               INTEGER,
    vRtrSpbPathIfIndex               InterfaceIndex,
    vRtrSpbPathNHopSysID             SystemID,
    vRtrSpbPathMetric                Unsigned32,
    vRtrSpbPathSNPA                  SNPAAddress
}

vRtrSpbPathFwdTree               OBJECT-TYPE
    SYNTAX      INTEGER {
        unicast   (1),
        multicast (2)
    }
    MAX-ACCESS  not-accessible
    STATUS      current
    DESCRIPTION
        "The value of vRtrSpbPathFwdTree indicates the forwarding-tree traffic
         type associated with this entry."
    ::= { vRtrSpbPathEntry 1 }

vRtrSpbPathIfIndex               OBJECT-TYPE
    SYNTAX      InterfaceIndex
    MAX-ACCESS  read-only
    STATUS      current
    DESCRIPTION
        "The vRtrSpbPathIfIndex indicates the ifIndex of the outgoing interface
         for the path."
    ::= { vRtrSpbPathEntry 2 }

vRtrSpbPathNHopSysID             OBJECT-TYPE
    SYNTAX      SystemID
    MAX-ACCESS  read-only
    STATUS      current
    DESCRIPTION
        "The vRtrSpbPathNHopSysID indicates the system-identifier for the next
         hop for this path."
    ::= { vRtrSpbPathEntry 3 }

vRtrSpbPathMetric                OBJECT-TYPE
    SYNTAX      Unsigned32
    MAX-ACCESS  read-only
    STATUS      current
    DESCRIPTION
        "The value of vRtrSpbPathMetric indicates the metric assigned to this
         entry after SPF calculations is stored in vRtrSpbPathMetric.

         The lower the metric value, the shorter is the path and hence more
         preferred by the protocol."
    ::= { vRtrSpbPathEntry 4 }

vRtrSpbPathSNPA                  OBJECT-TYPE
    SYNTAX      SNPAAddress
    MAX-ACCESS  read-only
    STATUS      current
    DESCRIPTION
        "The value of vRtrSpbPathSNPA indicates the subnet point of attachment
         for this path."
    ::= { vRtrSpbPathEntry 5 }

vRtrSpbRouteMacTable             OBJECT-TYPE
    SYNTAX      SEQUENCE OF VRtrSpbRouteMacEntry
    MAX-ACCESS  not-accessible
    STATUS      current
    DESCRIPTION
        "The vRtrSpbRouteMacTable maintains the routes learned by an instance
         of IS-IS protocol associated with Shortest Path Bridging (SPB)
         Forwarding database identifiers (FID) for destination ISIDs."
    ::= { vRtrIsisSystemObjs 18 }

vRtrSpbRouteMacEntry             OBJECT-TYPE
    SYNTAX      VRtrSpbRouteMacEntry
    MAX-ACCESS  not-accessible
    STATUS      current
    DESCRIPTION
        "Each row entry in the vRtrSpbRouteMacTable stores a route for a given
         of IS-IS protocol associated with Shortest Path Bridging (SPB)
         Forwarding database identifiers (FID) for a destination ISID."
    INDEX       {
        isisSysInstance,
        vRtrSpbPathFwdTree,
        vRtrSpbEctFid,
        vRtrSpbRouteMacDestMac
    }
    ::= { vRtrSpbRouteMacTable 1 }

VRtrSpbRouteMacEntry             ::= SEQUENCE
{
    vRtrSpbRouteMacDestMac           MacAddress,
    vRtrSpbRouteMacIfIndex           InterfaceIndex,
    vRtrSpbRouteMacSpfRunNumber      Counter32,
    vRtrSpbRouteMacMetric            Unsigned32,
    vRtrSpbRouteMacNHopSysID         SystemID,
    vRtrSpbRouteMacMetricType        INTEGER
}

vRtrSpbRouteMacDestMac           OBJECT-TYPE
    SYNTAX      MacAddress
    MAX-ACCESS  not-accessible
    STATUS      current
    DESCRIPTION
        "The value of vRtrSpbRouteMacDestMac indicates the destination MAC
         address for this entry."
    ::= { vRtrSpbRouteMacEntry 1 }

vRtrSpbRouteMacIfIndex           OBJECT-TYPE
    SYNTAX      InterfaceIndex
    MAX-ACCESS  read-only
    STATUS      current
    DESCRIPTION
        "vRtrSpbRouteMacIfIndex maintains the ifIndex of the outgoing interface
         for the route."
    ::= { vRtrSpbRouteMacEntry 2 }

vRtrSpbRouteMacSpfRunNumber      OBJECT-TYPE
    SYNTAX      Counter32
    MAX-ACCESS  read-only
    STATUS      current
    DESCRIPTION
        "The value of vRtrSpbRouteMacSpfRunNumber indicates the run of spf
         calculation in which this route was selected."
    ::= { vRtrSpbRouteMacEntry 3 }

vRtrSpbRouteMacMetric            OBJECT-TYPE
    SYNTAX      Unsigned32
    MAX-ACCESS  read-only
    STATUS      current
    DESCRIPTION
        "The value of vRtrSpbRouteMacMetric indicates the metric value
         associated with the route. This is obtained by the SPF calculations
         and is used by the instance of the protocol. For a given destination
         prefix, the route with the lower metric is the shorter route."
    ::= { vRtrSpbRouteMacEntry 4 }

vRtrSpbRouteMacNHopSysID         OBJECT-TYPE
    SYNTAX      SystemID
    MAX-ACCESS  read-only
    STATUS      current
    DESCRIPTION
        "The value of vRtrSpbRouteMacNHopSysID indicates the system-id of the
         nexthop IS through which this route is reachable."
    ::= { vRtrSpbRouteMacEntry 5 }

vRtrSpbRouteMacMetricType        OBJECT-TYPE
    SYNTAX      INTEGER {
        exact      (0),
        lowerBound (1)
    }
    MAX-ACCESS  read-only
    STATUS      current
    DESCRIPTION
        "The value of vRtrSpbRouteMacMetricType indicates the type of metric
         associated with the value of vRtrSpbRouteMacMetric whether it is a
         lower bound or the exact value."
    ::= { vRtrSpbRouteMacEntry 6 }

vRtrSpbRouteIsidTable            OBJECT-TYPE
    SYNTAX      SEQUENCE OF VRtrSpbRouteIsidEntry
    MAX-ACCESS  not-accessible
    STATUS      current
    DESCRIPTION
        "The vRtrSpbRouteIsidTable maintains the routes learned by an instance
         of IS-IS protocol associated with Shortest Path Bridging Forwarding
         database identifiers (FID) for destination ISIDs."
    ::= { vRtrIsisSystemObjs 19 }

vRtrSpbRouteIsidEntry            OBJECT-TYPE
    SYNTAX      VRtrSpbRouteIsidEntry
    MAX-ACCESS  not-accessible
    STATUS      current
    DESCRIPTION
        "Each row entry in the vRtrSpbRouteIsidTable stores a route for a given
         instance of IS-IS protocol associated with Shortest Path Bridging
         Forwarding database identifiers (FID) for a destination ISID."
    INDEX       {
        isisSysInstance,
        vRtrSpbEctFid,
        vRtrSpbRouteIsidDestIsid,
        vRtrSpbRouteIsidIfIndex
    }
    ::= { vRtrSpbRouteIsidTable 1 }

VRtrSpbRouteIsidEntry            ::= SEQUENCE
{
    vRtrSpbRouteIsidDestIsid         Unsigned32,
    vRtrSpbRouteIsidIfIndex          InterfaceIndex,
    vRtrSpbRouteIsidSpfRunNumber     Counter32,
    vRtrSpbRouteIsidNHopSysID        SystemID,
    vRtrSpbRouteIsidInMfib           TruthValue
}

vRtrSpbRouteIsidDestIsid         OBJECT-TYPE
    SYNTAX      Unsigned32
    MAX-ACCESS  not-accessible
    STATUS      current
    DESCRIPTION
        "The value of vRtrSpbRouteIsidDestIsid indicates the destination ISID
         value associated with this entry."
    ::= { vRtrSpbRouteIsidEntry 1 }

vRtrSpbRouteIsidIfIndex          OBJECT-TYPE
    SYNTAX      InterfaceIndex
    MAX-ACCESS  not-accessible
    STATUS      current
    DESCRIPTION
        "The vRtrSpbRouteIsidIfIndex maintains the ifIndex of the outgoing
         interface for the route."
    ::= { vRtrSpbRouteIsidEntry 2 }

vRtrSpbRouteIsidSpfRunNumber     OBJECT-TYPE
    SYNTAX      Counter32
    MAX-ACCESS  read-only
    STATUS      current
    DESCRIPTION
        "The value of vRtrSpbRouteIsidSpfRunNumber indicates the run of spf
         calculation in which this route was selected."
    ::= { vRtrSpbRouteIsidEntry 3 }

vRtrSpbRouteIsidNHopSysID        OBJECT-TYPE
    SYNTAX      SystemID
    MAX-ACCESS  read-only
    STATUS      current
    DESCRIPTION
        "The value of vRtrSpbRouteIsidNHopSysID indicates the system-id of the
         nexthop IS through which this route is reachable."
    ::= { vRtrSpbRouteIsidEntry 4 }

vRtrSpbRouteIsidInMfib           OBJECT-TYPE
    SYNTAX      TruthValue
    MAX-ACCESS  read-only
    STATUS      current
    DESCRIPTION
        "The value of vRtrSpbRouteIsidInMfib indicates whether the route needs
         an entry programmed in the MFIB table.

         An ISID route needs an MFIB entry only if:
         - the ISID is local and there is at least one remote site with the ISID,
         or
         - the ISID is not local but this node is a transit node for two or more
         remote sites with the ISID."
    ::= { vRtrSpbRouteIsidEntry 5 }

vRtrSpbEctFidRangeTable          OBJECT-TYPE
    SYNTAX      SEQUENCE OF VRtrSpbEctFidRangeEntry
    MAX-ACCESS  not-accessible
    STATUS      current
    DESCRIPTION
        "The vRtrSpbEctFidRangeTable contains entries for Shortest Path
         Bridging Equal Cost Tree (ECT) algorithm mapping to Forwarding
         database identifiers (FID) ranges.

         System will automatically create entries in this table when SPB is
         created on the isisSysInstance."
    ::= { vRtrIsisSystemObjs 20 }

vRtrSpbEctFidRangeEntry          OBJECT-TYPE
    SYNTAX      VRtrSpbEctFidRangeEntry
    MAX-ACCESS  not-accessible
    STATUS      current
    DESCRIPTION
        "A Shortest Path Bridging (SPB) Equal Cost Tree (ECT) algorithm mapping
         to Forwarding database identifier (FID) range entry in the
         vRtrSpbEctFidRangeTable."
    INDEX       {
        isisSysInstance,
        vRtrIsisLevel,
        vRtrSpbEctFid
    }
    ::= { vRtrSpbEctFidRangeTable 1 }

VRtrSpbEctFidRangeEntry          ::= SEQUENCE
{
    vRtrSpbEctFidRangeEnd            TmnxSpbFid,
    vRtrSpbEctFidRangeAlgorithm      INTEGER
}

vRtrSpbEctFidRangeEnd            OBJECT-TYPE
    SYNTAX      TmnxSpbFid
    MAX-ACCESS  read-only
    STATUS      current
    DESCRIPTION
        "The value of vRtrSpbEctFidRangeEnd indicates the last forwarding
         database identifier for ECT algorithm in this FID range."
    ::= { vRtrSpbEctFidRangeEntry 1 }

vRtrSpbEctFidRangeAlgorithm      OBJECT-TYPE
    SYNTAX      INTEGER {
        lowPathId  (0),
        highPathId (1)
    }
    MAX-ACCESS  read-only
    STATUS      current
    DESCRIPTION
        "The value of vRtrSpbEctFidRangeAlgorithm indicates the algorithm used
         by the entry."
    ::= { vRtrSpbEctFidRangeEntry 2 }

vRtrIsisLgTableLastChanged       OBJECT-TYPE
    SYNTAX      TimeStamp
    MAX-ACCESS  read-only
    STATUS      current
    DESCRIPTION
        "The value of vRtrIsisLgTableLastChanged indicates the sysUpTime at the
         time of the last modification of vRtrIsisLgTable.

         If no changes were made to the entry since the last re-initialization
         of the local network management subsystem, then this object contains a
         zero value."
    ::= { vRtrIsisSystemObjs 21 }

vRtrIsisLgTable                  OBJECT-TYPE
    SYNTAX      SEQUENCE OF VRtrIsisLgEntry
    MAX-ACCESS  not-accessible
    STATUS      current
    DESCRIPTION
        "The vRtrIsisLgTable contains entries for link groups on this router
         that participate in the IS-IS protocol."
    ::= { vRtrIsisSystemObjs 22 }

vRtrIsisLgEntry                  OBJECT-TYPE
    SYNTAX      VRtrIsisLgEntry
    MAX-ACCESS  not-accessible
    STATUS      current
    DESCRIPTION
        "Each row entry in the vRtrIsisLgTable represents a link group on this
         router that participates in the IS-IS protocol. An entry in this table
         can be created or destroyed by an SNMP SET request to
         vRtrIsisLgRowStatus. The value of vRtrID is currently restricted to
         the base instance."
    INDEX       {
        vRtrID,
        isisSysInstance,
        vRtrIsisLgName
    }
    ::= { vRtrIsisLgTable 1 }

VRtrIsisLgEntry                  ::= SEQUENCE
{
    vRtrIsisLgName                   TNamedItem,
    vRtrIsisLgRowStatus              RowStatus,
    vRtrIsisLgDescription            DisplayString,
    vRtrIsisLgRowLastChanged         TimeStamp
}

vRtrIsisLgName                   OBJECT-TYPE
    SYNTAX      TNamedItem
    MAX-ACCESS  not-accessible
    STATUS      current
    DESCRIPTION
        "The value of vRtrIsisLgName specifies the link group name on this
         router that participates in the IS-IS protocol."
    ::= { vRtrIsisLgEntry 1 }

vRtrIsisLgRowStatus              OBJECT-TYPE
    SYNTAX      RowStatus
    MAX-ACCESS  read-create
    STATUS      current
    DESCRIPTION
        "The value of vRtrIsisLgRowStatus specifies the row status of this
         conceptual row. An attempt to destroy this row will fail if
         vRtrIsisIfAdminState has not been first set to 'outOfService'."
    ::= { vRtrIsisLgEntry 2 }

vRtrIsisLgDescription            OBJECT-TYPE
    SYNTAX      DisplayString
    MAX-ACCESS  read-create
    STATUS      current
    DESCRIPTION
        "The value of vRtrIsisLgDescription specifies the description for the
         associated link group indicated by vRtrIsisLgName."
    ::= { vRtrIsisLgEntry 3 }

vRtrIsisLgRowLastChanged         OBJECT-TYPE
    SYNTAX      TimeStamp
    MAX-ACCESS  read-only
    STATUS      current
    DESCRIPTION
        "The value of the object vRtrIsisLgRowLastChanged indicates the
         sysUpTime when this row was last modified."
    ::= { vRtrIsisLgEntry 4 }

vRtrIsisLgLevelTableLastChanged  OBJECT-TYPE
    SYNTAX      TimeStamp
    MAX-ACCESS  read-only
    STATUS      current
    DESCRIPTION
        "The value of vRtrIsisLgLevelTableLastChanged indicates the sysUpTime
         at the time of the last modification of vRtrIsisLgLevelTable.

         If no changes were made to the entry since the last re-initialization
         of the local network management subsystem, then this object contains a
         zero value."
    ::= { vRtrIsisSystemObjs 23 }

vRtrIsisLgLevelTable             OBJECT-TYPE
    SYNTAX      SEQUENCE OF VRtrIsisLgLevelEntry
    MAX-ACCESS  not-accessible
    STATUS      current
    DESCRIPTION
        "The vRtrIsisLgLevelTable contains entries that provide attributes to
         be applied on a specific IS-IS link group operating at a specific
         IS-IS protocol level."
    ::= { vRtrIsisSystemObjs 24 }

vRtrIsisLgLevelEntry             OBJECT-TYPE
    SYNTAX      VRtrIsisLgLevelEntry
    MAX-ACCESS  not-accessible
    STATUS      current
    DESCRIPTION
        "Each row entry in the vRtrIsisLgLevelTable represents IS-IS level
         attributes to be used with a link group belonging to a specific IS-IS
         protocol instance on a specific router instance. The value of vRtrID
         is currently restricted to the base instance."
    INDEX       {
        vRtrID,
        isisSysInstance,
        vRtrIsisLgName,
        vRtrIsisLgLevelLvl
    }
    ::= { vRtrIsisLgLevelTable 1 }

VRtrIsisLgLevelEntry             ::= SEQUENCE
{
    vRtrIsisLgLevelLvl               INTEGER,
    vRtrIsisLgLevelOperMembers       Unsigned32,
    vRtrIsisLgLevelRevertMembers     Unsigned32,
    vRtrIsisLgLevelIPv4UcastMetric   Unsigned32,
    vRtrIsisLgLevelIPv6UcastMetric   Unsigned32,
    vRtrIsisLgLevelIPv4McastMetric   Unsigned32,
    vRtrIsisLgLevelIPv6McastMetric   Unsigned32,
    vRtrIsisLgLevelLastChanged       TimeStamp
}

vRtrIsisLgLevelLvl               OBJECT-TYPE
    SYNTAX      INTEGER {
        level1 (1),
        level2 (2)
    }
    MAX-ACCESS  not-accessible
    STATUS      current
    DESCRIPTION
        "The value of vRtrIsisLgLevelLvl indicates the IS-IS protocol level to
         which these row attributes are applied."
    ::= { vRtrIsisLgLevelEntry 1 }

vRtrIsisLgLevelOperMembers       OBJECT-TYPE
    SYNTAX      Unsigned32 (0..8)
    MAX-ACCESS  read-write
    STATUS      current
    DESCRIPTION
        "The value of vRtrIsisLgLevelOperMembers specifies the number of
         operational links below which the metric of the member interfaces is
         increased by the configured offsets."
    DEFVAL      { 0 }
    ::= { vRtrIsisLgLevelEntry 2 }

vRtrIsisLgLevelRevertMembers     OBJECT-TYPE
    SYNTAX      Unsigned32 (0..8)
    MAX-ACCESS  read-write
    STATUS      current
    DESCRIPTION
        "The value of vRtrIsisLgLevelRevertMembers specifies the minimum number
         of links that must be operational after the offsets were applied in
         order for the metrics of the member interfaces to be returned to
         normal."
    DEFVAL      { 0 }
    ::= { vRtrIsisLgLevelEntry 3 }

vRtrIsisLgLevelIPv4UcastMetric   OBJECT-TYPE
    SYNTAX      Unsigned32 (0..16777215)
    MAX-ACCESS  read-write
    STATUS      current
    DESCRIPTION
        "The value of vRtrIsisLgLevelIPv4UcastMetric specifies the amount by
         which IS-IS IPv4 unicast metric should be increased once the number of
         operational links becomes less than the number specified by
         vRtrIsisLgLevelOperMembers."
    DEFVAL      { 0 }
    ::= { vRtrIsisLgLevelEntry 4 }

vRtrIsisLgLevelIPv6UcastMetric   OBJECT-TYPE
    SYNTAX      Unsigned32 (0..16777215)
    MAX-ACCESS  read-write
    STATUS      current
    DESCRIPTION
        "The value of vRtrIsisLgLevelIPv6UcastMetric specifies the amount by
         which IS-IS IPv6 unicast metric should be increased once the number of
         operational links becomes less than the number specified by
         vRtrIsisLgLevelOperMembers."
    DEFVAL      { 0 }
    ::= { vRtrIsisLgLevelEntry 5 }

vRtrIsisLgLevelIPv4McastMetric   OBJECT-TYPE
    SYNTAX      Unsigned32 (0..16777215)
    MAX-ACCESS  read-write
    STATUS      current
    DESCRIPTION
        "The value of vRtrIsisLgLevelIPv4McastMetric specifies the amount by
         which IS-IS IPv4 multicast metric should be increased once the number
         of operational links becomes less than the number specified by
         vRtrIsisLgLevelOperMembers."
    DEFVAL      { 0 }
    ::= { vRtrIsisLgLevelEntry 6 }

vRtrIsisLgLevelIPv6McastMetric   OBJECT-TYPE
    SYNTAX      Unsigned32 (0..16777215)
    MAX-ACCESS  read-write
    STATUS      current
    DESCRIPTION
        "The value of vRtrIsisLgLevelIPv6McastMetric specifies the amount by
         which IS-IS IPv6 multicast metric should be increased once the number
         of operational links becomes less than the number specified by
         vRtrIsisLgLevelOperMembers."
    DEFVAL      { 0 }
    ::= { vRtrIsisLgLevelEntry 7 }

vRtrIsisLgLevelLastChanged       OBJECT-TYPE
    SYNTAX      TimeStamp
    MAX-ACCESS  read-only
    STATUS      current
    DESCRIPTION
        "The value of the object vRtrIsisLgLevelLastChanged indicates the
         sysUpTime when this row was last modified."
    ::= { vRtrIsisLgLevelEntry 8 }

vRtrIsisLgLevelOperTable         OBJECT-TYPE
    SYNTAX      SEQUENCE OF VRtrIsisLgLevelOperEntry
    MAX-ACCESS  not-accessible
    STATUS      current
    DESCRIPTION
        "The vRtrIsisLgLevelOperEntry provides additional operational
         information on an IS-IS link group operating at a specific IS-IS
         protocol level."
    ::= { vRtrIsisSystemObjs 25 }

vRtrIsisLgLevelOperEntry         OBJECT-TYPE
    SYNTAX      VRtrIsisLgLevelOperEntry
    MAX-ACCESS  not-accessible
    STATUS      current
    DESCRIPTION
        "Each row entry in the vRtrIsisLgLevelOperTable represents operational
         values of IS-IS level attributes used with a link group belonging to a
         specific IS-IS protocol instance on a specific router instance. The
         value of vRtrID is currently restricted to the base instance."
    INDEX       {
        vRtrID,
        isisSysInstance,
        vRtrIsisLgName,
        vRtrIsisLgLevelLvl
    }
    ::= { vRtrIsisLgLevelOperTable 1 }

VRtrIsisLgLevelOperEntry         ::= SEQUENCE
{
    vRtrIsisLgLevelOpOperMembers     Unsigned32,
    vRtrIsisLgLevelOperRevertMembers Unsigned32,
    vRtrIsisLgLevelOperMembersCount  Unsigned32,
    vRtrIsisLgLevelOperActiveMembers Unsigned32,
    vRtrIsisLgLevelOperState         INTEGER
}

vRtrIsisLgLevelOpOperMembers     OBJECT-TYPE
    SYNTAX      Unsigned32
    MAX-ACCESS  read-only
    STATUS      current
    DESCRIPTION
        "The value of the object vRtrIsisLgLevelOpOperMembers indicates the
         operational value of the number of operational links below which the
         metric of the member interfaces is increased by the configured
         offsets."
    ::= { vRtrIsisLgLevelOperEntry 1 }

vRtrIsisLgLevelOperRevertMembers OBJECT-TYPE
    SYNTAX      Unsigned32
    MAX-ACCESS  read-only
    STATUS      current
    DESCRIPTION
        "The value of the object vRtrIsisLgLevelOperRevertMembers indicates the
         operational value of the minimum number of links that must be
         operational after the offsets were applied in order for the metrics of
         the member interfaces to be returned to normal."
    ::= { vRtrIsisLgLevelOperEntry 2 }

vRtrIsisLgLevelOperMembersCount  OBJECT-TYPE
    SYNTAX      Unsigned32
    MAX-ACCESS  read-only
    STATUS      current
    DESCRIPTION
        "The value of the object vRtrIsisLgLevelOperMembersCount indicates the
         number of interfaces that are a member of the link group indicated by
         vRtrIsisLgName at this IS-IS level."
    ::= { vRtrIsisLgLevelOperEntry 3 }

vRtrIsisLgLevelOperActiveMembers OBJECT-TYPE
    SYNTAX      Unsigned32
    MAX-ACCESS  read-only
    STATUS      current
    DESCRIPTION
        "The value of the object vRtrIsisLgLevelOperActiveMembers indicates the
         number of active interfaces that are a member of the link group
         indicated by vRtrIsisLgName at this IS-IS level."
    ::= { vRtrIsisLgLevelOperEntry 4 }

vRtrIsisLgLevelOperState         OBJECT-TYPE
    SYNTAX      INTEGER {
        normal        (1),
        offsetApplied (2)
    }
    MAX-ACCESS  read-only
    STATUS      current
    DESCRIPTION
        "The value of the object vRtrIsisLgLevelOperState indicates the state
         of the link group at this IS-IS level."
    ::= { vRtrIsisLgLevelOperEntry 5 }

vRtrIsisLgLevelMembersOperTable  OBJECT-TYPE
    SYNTAX      SEQUENCE OF VRtrIsisLgLevelMembersOperEntry
    MAX-ACCESS  not-accessible
    STATUS      current
    DESCRIPTION
        "The vRtrIsisLgLevelMembersOperTable provides additional operational
         information related to a specific IS-IS interface associated with a
         specific IS-IS link group operating at a specific IS-IS protocol
         level."
    ::= { vRtrIsisSystemObjs 27 }

vRtrIsisLgLevelMembersOperEntry  OBJECT-TYPE
    SYNTAX      VRtrIsisLgLevelMembersOperEntry
    MAX-ACCESS  not-accessible
    STATUS      current
    DESCRIPTION
        "Each row entry in the vRtrIsisLgLevelMembersOperTable represents
         operational values of an IS-IS interface associated with a specific
         IS-IS link group operating at a specific IS-IS protocol level. The
         value of vRtrID is currently restricted to the base instance."
    INDEX       {
        vRtrID,
        isisSysInstance,
        vRtrIsisLgName,
        vRtrIsisLgLevelLvl,
        vRtrIfIndex
    }
    ::= { vRtrIsisLgLevelMembersOperTable 1 }

VRtrIsisLgLevelMembersOperEntry  ::= SEQUENCE
{ vRtrIsisLgLevelMembersOperState  INTEGER }

vRtrIsisLgLevelMembersOperState  OBJECT-TYPE
    SYNTAX      INTEGER {
        up           (1),
        down         (2),
        bitErrorRate (3)
    }
    MAX-ACCESS  read-only
    STATUS      current
    DESCRIPTION
        "The value of vRtrIsisLgLevelMembersOperState indicates the state of
         this interface at this IS-IS level associated with the link group
         indicated by vRtrIsisLgName."
    ::= { vRtrIsisLgLevelMembersOperEntry 1 }

vRtrIsisIfObjs                   OBJECT IDENTIFIER ::= { vRtrIsisObjs 2 }

vRtrIsisIfTable                  OBJECT-TYPE
    SYNTAX      SEQUENCE OF VRtrIsisIfEntry
    MAX-ACCESS  not-accessible
    STATUS      obsolete
    DESCRIPTION
        "The vRtrIsisIfTable has an entry for each router interface configured
         for the IS-IS protocol.

         This table is obsolete and replaced by tmnxIsisIfTable in
         TIMETRA-ISIS-NG-MIB."
    ::= { vRtrIsisIfObjs 1 }

vRtrIsisIfEntry                  OBJECT-TYPE
    SYNTAX      VRtrIsisIfEntry
    MAX-ACCESS  not-accessible
    STATUS      obsolete
    DESCRIPTION
        "Each row entry in the vRtrIsisIfTable represents an interface on
         this router that participates in the IS-IS protocol.  An entry in
         this table can be created or destroyed by an SNMP SET request to
         vRtrIsisIfRowStatus.  An attempt to destroy a row will fail if
         vRtrIsisIfAdminState has not first been set to 'outOfService'."
    INDEX       {
        isisSysInstance,
        vRtrIfIndex
    }
    ::= { vRtrIsisIfTable 1 }

VRtrIsisIfEntry                  ::= SEQUENCE
{
    vRtrIsisIfRowStatus              RowStatus,
    vRtrIsisIfLastChangeTime         TimeStamp,
    vRtrIsisIfAdminState             TmnxAdminState,
    vRtrIsisIfOperState              TmnxOperState,
    vRtrIsisIfCsnpInterval           Unsigned32,
    vRtrIsisIfHelloAuthKey           OCTET STRING,
    vRtrIsisIfHelloAuthType          INTEGER,
    vRtrIsisIfLspPacingInterval      Unsigned32,
    vRtrIsisIfCircIndex              Integer32,
    vRtrIsisIfRetransmitInterval     Unsigned32,
    vRtrIsisIfTypeDefault            TruthValue,
    vRtrIsisIfEnableBfd              TruthValue,
    vRtrIsisIfIPv6Unicast            TruthValue,
    vRtrIsisIfTeMetric               Unsigned32,
    vRtrIsisIfTeState                TmnxOperState,
    vRtrIsisIfAdminGroup             Unsigned32,
    vRtrIsisIfLdpSyncState           TmnxOperState,
    vRtrIsisIfLdpSyncMaxMetric       TruthValue,
    vRtrIsisIfLdpSyncTimerState      INTEGER,
    vRtrIsisIfLdpSyncTimeLeft        Unsigned32,
    vRtrIsisIfRouteTag               Unsigned32,
    vRtrIsisIfIpv6EnableBfd          TruthValue,
    vRtrIsisIfHelloAuthentication    TruthValue,
    vRtrIsisIfLoopfreeAltExclude     TruthValue,
    vRtrIsisIfOperType               INTEGER,
    vRtrIsisIfIPv4Mcast              TruthValue,
    vRtrIsisIfIPv6Mcast              TruthValue,
    vRtrIsisIfBerState               INTEGER
}

vRtrIsisIfRowStatus              OBJECT-TYPE
    SYNTAX      RowStatus
    MAX-ACCESS  read-only
    STATUS      obsolete
    DESCRIPTION
        "The row status used for creation, deletion, or control of
         vRtrIsisIfTable entries.  Before this row can be destroyed,
         vRtrIsisIfAdminState must have been set to 'outOfService'."
    ::= { vRtrIsisIfEntry 1 }

vRtrIsisIfLastChangeTime         OBJECT-TYPE
    SYNTAX      TimeStamp
    MAX-ACCESS  read-only
    STATUS      obsolete
    DESCRIPTION
        "The sysUpTime when this row was last modified."
    ::= { vRtrIsisIfEntry 2 }

vRtrIsisIfAdminState             OBJECT-TYPE
    SYNTAX      TmnxAdminState
    MAX-ACCESS  read-only
    STATUS      obsolete
    DESCRIPTION
        "The desired administrative state for IS-IS protocol on this interface."
    DEFVAL      { outOfService }
    ::= { vRtrIsisIfEntry 3 }

vRtrIsisIfOperState              OBJECT-TYPE
    SYNTAX      TmnxOperState
    MAX-ACCESS  read-only
    STATUS      obsolete
    DESCRIPTION
        "The obsolete operational state of IS-IS protocol on this interface."
    ::= { vRtrIsisIfEntry 4 }

vRtrIsisIfCsnpInterval           OBJECT-TYPE
    SYNTAX      Unsigned32 (1..65535)
    UNITS       "seconds"
    MAX-ACCESS  read-only
    STATUS      obsolete
    DESCRIPTION
        "The value of vRtrIsisIfCsnpInterval specifies the interval of
         time, in seconds, between transmission of Complete Sequence
         Number PDUs (CSNP).  If the value of isisCircType for this
         interface is 'broadcast' and this router is the designated router
         on a LAN, the default frequency is ten seconds.  if the value of
         isisCircType for this  interface is 'ptToPt', point-to-point,
         the default frequency is every five seconds."
    DEFVAL      { 10 }
    ::= { vRtrIsisIfEntry 5 }

vRtrIsisIfHelloAuthKey           OBJECT-TYPE
    SYNTAX      OCTET STRING (SIZE (0..254))
    MAX-ACCESS  read-only
    STATUS      obsolete
    DESCRIPTION
        "vRtrIsisIfHelloAuthKey is the authentication key string used to
         verify the authenticity of packets sent by neighboring routers on
         this IS-IS interface.  For authentication to succeed both the
         authentication key and the authentication type defined by the
         vRtrIsisIfHelloAuthType variable must match.  If
         vRtrIsisIfHelloAuthType is set to 'password',
         vRtrIsisIfHelloAuthKey can include any ASCII character.

         Authentication can be configured globally and applied to all
         ISIS levels running on this interface or it can be configured
         on a per level basis.  The most specific value is used.

         When read, vRtrIsisIfHelloAuthKey always returns an Octet String of
         length zero."
    DEFVAL      { ''H }
    ::= { vRtrIsisIfEntry 6 }

vRtrIsisIfHelloAuthType          OBJECT-TYPE
    SYNTAX      INTEGER {
        none     (1),
        password (2),
        md5      (3)
    }
    MAX-ACCESS  read-only
    STATUS      obsolete
    DESCRIPTION
        "The value of vRtrIsisIfHelloAuthType specifies the method of
         authentication used to verify the authenticity of packets sent
         by neighboring routers on this IS-IS interface.  For
         authentication to succeed both the authentication key defined in
         the vRtrIsisIfHelloAuthKey variable and the authentication type
         must match.

         Authentication can be configured globally and applied to all
         ISIS levels running on this interface or it can be configured on
         a per level basis.  The most specific value is used."
    DEFVAL      { none }
    ::= { vRtrIsisIfEntry 7 }

vRtrIsisIfLspPacingInterval      OBJECT-TYPE
    SYNTAX      Unsigned32 (0..65535)
    UNITS       "milliseconds"
    MAX-ACCESS  read-only
    STATUS      obsolete
    DESCRIPTION
        "The value of vRtrIsisIfLspPacingInterval specifies the minimal
         interval of time, in milliseconds, between transmission of Link State
         PDUs (LSPs) for all ISIS levels running on this interface.

         If the value of vRtrIsisIfLspPacingInterval is zero (0), no LSPs will
         be sent on this interface."
    DEFVAL      { 100 }
    ::= { vRtrIsisIfEntry 8 }

vRtrIsisIfCircIndex              OBJECT-TYPE
    SYNTAX      Integer32 (1..2000000000)
    MAX-ACCESS  read-only
    STATUS      obsolete
    DESCRIPTION
        "The value of vRtrIsisIfCircIndex is a cross reference index to the
         isisCircTable."
    ::= { vRtrIsisIfEntry 9 }

vRtrIsisIfRetransmitInterval     OBJECT-TYPE
    SYNTAX      Unsigned32 (1..65535)
    UNITS       "seconds"
    MAX-ACCESS  read-only
    STATUS      obsolete
    DESCRIPTION
        "The value of vRtrIsisIfRetransmitInterval specifies the minimal
         interval of time, in seconds between retransmission of an LSP on
         point-to-point interfaces."
    DEFVAL      { 5 }
    ::= { vRtrIsisIfEntry 10 }

vRtrIsisIfTypeDefault            OBJECT-TYPE
    SYNTAX      TruthValue
    MAX-ACCESS  read-only
    STATUS      obsolete
    DESCRIPTION
        "The value of vRtrIsisIfTypeDefault complements the object
         isisCircType. It indicates if the circuit type is default or has been
         modified. Setting vRtrIsisIfTypeDefault to 'true' resets isisCircType
         to the default for that interface. Similarly any modification to the
         object isisCircType triggers this object to become 'false'. There is
         no effect of setting this object to 'false'."
    DEFVAL      { true }
    ::= { vRtrIsisIfEntry 11 }

vRtrIsisIfEnableBfd              OBJECT-TYPE
    SYNTAX      TruthValue
    MAX-ACCESS  read-only
    STATUS      obsolete
    DESCRIPTION
        "The value of vRtrIsisIfEnableBfd specifies whether Bi-directional
         Forwarding Detection is enabled for Ipv4 on this IS-IS interface.

         When the value is 'true', this IS-IS interface can establish BFD
         sessions and use BFD as a signaling mechanism for forming adjacencies.
         When it is 'false', it cannot use BFD for Ipv4."
    DEFVAL      { false }
    ::= { vRtrIsisIfEntry 12 }

vRtrIsisIfIPv6Unicast            OBJECT-TYPE
    SYNTAX      TruthValue
    MAX-ACCESS  read-only
    STATUS      obsolete
    DESCRIPTION
        "The value of vRtrIsisIfIPv6Unicast specifies if IPv6 unicast routing
         is enabled for the interface.

         By default IPv6 unicast on all interfaces is set to true. However,
         IPv6 unicast routing on ISIS is in effect when the object
         'vRtrIsisMultiTopoIPv6Ucast' is set to 'true'."
    DEFVAL      { true }
    ::= { vRtrIsisIfEntry 13 }

vRtrIsisIfTeMetric               OBJECT-TYPE
    SYNTAX      Unsigned32 (0..16777215)
    MAX-ACCESS  read-only
    STATUS      obsolete
    DESCRIPTION
        "The value of vRtrIsisIfTeMetric indicates the MPLS TE metric
         configured for this interface. This metric is flooded out in the TE
         metric sub-tlv in the ISIS LSPs. Depending on the configuration,
         either the TE metric value or the native ISIS metric values are used
         in CSPF computations."
    ::= { vRtrIsisIfEntry 14 }

vRtrIsisIfTeState                OBJECT-TYPE
    SYNTAX      TmnxOperState
    MAX-ACCESS  read-only
    STATUS      obsolete
    DESCRIPTION
        "The value of vRtrIsisIfTeState indicates the MPLS interface TE status
         from the ISIS standpoint."
    ::= { vRtrIsisIfEntry 15 }

vRtrIsisIfAdminGroup             OBJECT-TYPE
    SYNTAX      Unsigned32
    MAX-ACCESS  read-only
    STATUS      obsolete
    DESCRIPTION
        "The value of vRtrIsisIfAdminGroup indicates the bit-map inherited from
         MPLS interface that identifies the admin groups to which the interface
         belongs. If bit 'n' is set, then the interface belongs to the admin
         group with value 'n'."
    ::= { vRtrIsisIfEntry 16 }

vRtrIsisIfLdpSyncState           OBJECT-TYPE
    SYNTAX      TmnxOperState
    MAX-ACCESS  read-only
    STATUS      obsolete
    DESCRIPTION
        "The value of vRtrIsisIfLdpSyncState indicates if IGP-LDP
         synchronization is enabled on this interface. vRtrIsisIfLdpSyncState
         is derived from vRtrIsisLdpSyncAdminState and also whether it was
         enabled at the IP layer from ISIS standpoint."
    ::= { vRtrIsisIfEntry 17 }

vRtrIsisIfLdpSyncMaxMetric       OBJECT-TYPE
    SYNTAX      TruthValue
    MAX-ACCESS  read-only
    STATUS      obsolete
    DESCRIPTION
        "The value of vRtrIsisIfLdpSyncMaxMetric indicates if ISIS advertised
         maximum metric value for the interface, depending on whether
         vRtrIsisIfLdpSyncState is enabled on this interface."
    ::= { vRtrIsisIfEntry 18 }

vRtrIsisIfLdpSyncTimerState      OBJECT-TYPE
    SYNTAX      INTEGER {
        waitForLdpAdj (1),
        timerActive   (2),
        ldpExchgDone  (3),
        timerExpired  (4),
        manualExit    (5),
        disabled      (6)
    }
    MAX-ACCESS  read-only
    STATUS      obsolete
    DESCRIPTION
        "The value of vRtrIsisIfLdpSyncTimerState indicates the state of the
         vRtrIsisIfLdpSyncTimeLeft on this ISIS interface."
    ::= { vRtrIsisIfEntry 19 }

vRtrIsisIfLdpSyncTimeLeft        OBJECT-TYPE
    SYNTAX      Unsigned32 (0 | 1..1800)
    UNITS       "seconds"
    MAX-ACCESS  read-only
    STATUS      obsolete
    DESCRIPTION
        "The value of vRtrIsisIfLdpSyncTimeLeft indicates the time left before
         ISIS reverts back to advertising normal metric for this interface.
         This is applicable only when vRtrIsisIfLdpSyncMaxMetric is 'true'."
    ::= { vRtrIsisIfEntry 20 }

vRtrIsisIfRouteTag               OBJECT-TYPE
    SYNTAX      Unsigned32
    MAX-ACCESS  read-only
    STATUS      obsolete
    DESCRIPTION
        "The value of vRtrIsisIfRouteTag specifies a 32-bit integer tag for the
         IP addresses of an interface. This tag can be used to apply
         administrative policy. A value of 0 indicates that the tag has not
         been set."
    DEFVAL      { 0 }
    ::= { vRtrIsisIfEntry 21 }

vRtrIsisIfIpv6EnableBfd          OBJECT-TYPE
    SYNTAX      TruthValue
    MAX-ACCESS  read-only
    STATUS      obsolete
    DESCRIPTION
        "The value of vRtrIsisIfIpv6EnableBfd specifies whether Bi-directional
         Forwarding Detection is enabled for Ipv6 on this IS-IS interface.

         When the value is 'true', this IS-IS interface can establish BFD
         sessions and use BFD as a signaling mechanism for forming adjacencies.
         When it is 'false', it cannot use BFD for Ipv6."
    DEFVAL      { false }
    ::= { vRtrIsisIfEntry 22 }

vRtrIsisIfHelloAuthentication    OBJECT-TYPE
    SYNTAX      TruthValue
    MAX-ACCESS  read-only
    STATUS      obsolete
    DESCRIPTION
        "The value of vRtrIsisIfHelloAuthentication specifies whether ISIS
         hello-authentication is enabled or disabled on this IS-IS interface.

         When vRtrIsisIfHelloAuthentication is set to 'true',
         hello-authentication is enabled on this IS-IS interface.

         When vRtrIsisIfHelloAuthentication is set to 'false',
         hello-authentication is disabled on this IS-IS interface and
         the values of the following MIB objects are no longer applicable:
         - vRtrIsisIfHelloAuthKey and vRtrIsisIfHelloAuthType at a global
           interface level
         - vRtrIsisIfLevelHelloAuthKey and vRtrIsisIfLevelHelloAuthType at the
           specific L1/L2 interface level
         - vRtrIsisAuthKey and vRtrIsisAuthType at the ISIS level."
    DEFVAL      { true }
    ::= { vRtrIsisIfEntry 23 }

vRtrIsisIfLoopfreeAltExclude     OBJECT-TYPE
    SYNTAX      TruthValue
    MAX-ACCESS  read-only
    STATUS      obsolete
    DESCRIPTION
        "The value of vRtrIsisIfLoopfreeAltExclude specifies whether or not the
         ISIS interface should be excluded during LFA calculations. If the
         value is 'true', the ISIS interface is excluded from LFA calculations.
         If the value is 'false', the ISIS interface is included in LFA
         calculations.

         The value of vRtrIsisIfLoopfreeAltExclude for an interface is only
         valid when both conditions are met - vRtrIsisLoopfreeAlternate has a
         value of 'true' and vRtrIsisLevelLoopfreeAltExclude has a value of
         'false'."
    DEFVAL      { false }
    ::= { vRtrIsisIfEntry 24 }

vRtrIsisIfOperType               OBJECT-TYPE
    SYNTAX      INTEGER {
        broadcast (1),
        ptToPt    (2)
    }
    MAX-ACCESS  read-only
    STATUS      obsolete
    DESCRIPTION
        "The value of vRtrIsisIfOperType specifies the operational type on this
         ISIS interface."
    ::= { vRtrIsisIfEntry 25 }

vRtrIsisIfIPv4Mcast              OBJECT-TYPE
    SYNTAX      TruthValue
    MAX-ACCESS  read-only
    STATUS      obsolete
    DESCRIPTION
        "The value of vRtrIsisIfIPv4Mcast specifies if IPv4 multicast routing
         is enabled for the interface."
    DEFVAL      { true }
    ::= { vRtrIsisIfEntry 26 }

vRtrIsisIfIPv6Mcast              OBJECT-TYPE
    SYNTAX      TruthValue
    MAX-ACCESS  read-only
    STATUS      obsolete
    DESCRIPTION
        "The value of vRtrIsisIfIPv6Mcast specifies if IPv6 multicast routing
         is enabled for the interface."
    DEFVAL      { true }
    ::= { vRtrIsisIfEntry 27 }

vRtrIsisIfBerState               OBJECT-TYPE
    SYNTAX      INTEGER {
        none (0),
        sd   (1),
        sf   (2)
    }
    MAX-ACCESS  read-only
    STATUS      obsolete
    DESCRIPTION
        "The value of vRtrIsisIfBerState indicates the BER (Bit Error Rate)
         state of this interface."
    ::= { vRtrIsisIfEntry 28 }

vRtrIsisIfLevelTable             OBJECT-TYPE
    SYNTAX      SEQUENCE OF VRtrIsisIfLevelEntry
    MAX-ACCESS  not-accessible
    STATUS      obsolete
    DESCRIPTION
        "The vRtrIsisIfLevelTable provides attributes to be applied on a
         specific IS-IS interface operating at a specific IS-IS protocol level.

         This table is obsolete and replaced by tmnxIsisIfLevelTable in
         TIMETRA-ISIS-NG-MIB."
    ::= { vRtrIsisIfObjs 2 }

vRtrIsisIfLevelEntry             OBJECT-TYPE
    SYNTAX      VRtrIsisIfLevelEntry
    MAX-ACCESS  not-accessible
    STATUS      obsolete
    DESCRIPTION
        "Each row entry in the vRtrIsisIfLevelTable represents IS-IS level
         attributes to be used with an interface belonging to a specific IS-IS
         protocol instance on a specific router instance. Rows for Level 1 and
         2 are created as an action of creating a row in the vRtrIsisIfTable."
    INDEX       {
        isisSysInstance,
        vRtrIfIndex,
        vRtrIsisIfLevel
    }
    ::= { vRtrIsisIfLevelTable 1 }

VRtrIsisIfLevelEntry             ::= SEQUENCE
{
    vRtrIsisIfLevel                  INTEGER,
    vRtrIsisIfLevelLastChangeTime    TimeStamp,
    vRtrIsisIfLevelHelloAuthKey      OCTET STRING,
    vRtrIsisIfLevelHelloAuthType     INTEGER,
    vRtrIsisIfLevelPassive           TruthValue,
    vRtrIsisIfLevelTeMetric          Unsigned32,
    vRtrIsisIfLevelNumAdjacencies    Unsigned32,
    vRtrIsisIfLevelISPriority        Unsigned32,
    vRtrIsisIfLevelHelloTimer        Unsigned32,
    vRtrIsisIfLevelAdminMetric       Unsigned32,
    vRtrIsisIfLevelOperMetric        Unsigned32,
    vRtrIsisIfLvlIPv6UcastAdmMet     Unsigned32,
    vRtrIsisIfLvlIPv6UcastOperMet    Unsigned32,
    vRtrIsisIfLvlIPv4McastAdmMetric  Unsigned32,
    vRtrIsisIfLvlIPv6McastAdmMetric  Unsigned32,
    vRtrIsisIfLevelLinkGroupName     TNamedItemOrEmpty,
    vRtrIsisIfLevelSdOffset          Unsigned32,
    vRtrIsisIfLevelSfOffset          Unsigned32,
    vRtrIsisIfLvlIPv4McastOperMetric Unsigned32,
    vRtrIsisIfLvlIPv6McastOperMetric Unsigned32
}

vRtrIsisIfLevel                  OBJECT-TYPE
    SYNTAX      INTEGER {
        level1 (1),
        level2 (2)
    }
    MAX-ACCESS  not-accessible
    STATUS      obsolete
    DESCRIPTION
        "The value of vRtrIsisIfLevel specifies the IS-IS protocol level that
         this row entry describes."
    ::= { vRtrIsisIfLevelEntry 1 }

vRtrIsisIfLevelLastChangeTime    OBJECT-TYPE
    SYNTAX      TimeStamp
    MAX-ACCESS  read-only
    STATUS      obsolete
    DESCRIPTION
        "The sysUpTime when this row was last modified."
    ::= { vRtrIsisIfLevelEntry 2 }

vRtrIsisIfLevelHelloAuthKey      OBJECT-TYPE
    SYNTAX      OCTET STRING (SIZE (0..254))
    MAX-ACCESS  read-only
    STATUS      obsolete
    DESCRIPTION
        "vRtrIsisIfLevelHelloAuthKey is the authentication key string used
         to verify the authenticity of packets sent by neighboring routers
         on this IS-IS interface at this level.  For authentication to
         succeed both the authentication key and the authentication type
         defined by the vRtrIsisIfLevelHelloAuthType variable must match.
         If vRtrIsisIfLevelHelloAuthType is set to 'password',
         vRtrIsisIfLevelHelloAuthKey can include any ASCII character.

         Authentication can be configured globally and applied to all
         ISIS levels or it can be configured on a per level basis.
         The most specific value is used.  If the value of
         vRtrIsisIfLevelHelloAuthType is 'useGlobal', then the global
         values, if any, defined in vRtrIsisIfHelloAuthKey and
         vRtrIsisIfHelloAuthType are used instead.

         When read, vRtrIsisIfLevelHelloAuthKey always returns an Octet String
         of length zero."
    DEFVAL      { ''H }
    ::= { vRtrIsisIfLevelEntry 3 }

vRtrIsisIfLevelHelloAuthType     OBJECT-TYPE
    SYNTAX      INTEGER {
        useGlobal (0),
        none      (1),
        password  (2),
        md5       (3)
    }
    MAX-ACCESS  read-only
    STATUS      obsolete
    DESCRIPTION
        "The value of vRtrIsisIfLevelHelloAuthType specifies the method of
         authentication used to verify the authenticity of packets sent by
         neighboring routers on this IS-IS interface at this level. For
         authentication to succeed both the authentication key defined in the
         vRtrIsisIfLevelHelloAuthKey variable and the authentication type must
         match.

         Authentication can be configured globally and applied to all
         ISIS levels running on this interface or it can be configured on
         a per level basis.  The most specific value is used.  When
         vRtrIsisIfLevelHelloAuthType has a value of 'useGlobal', the
         values of vRtrIsisIfLevelHelloAuthKey and
         vRtrIsisIfLevelHelloAuthType are applied to the interfaces for
         this level."
    DEFVAL      { useGlobal }
    ::= { vRtrIsisIfLevelEntry 4 }

vRtrIsisIfLevelPassive           OBJECT-TYPE
    SYNTAX      TruthValue
    MAX-ACCESS  read-only
    STATUS      obsolete
    DESCRIPTION
        "If vRtrIsisIfLevelPassive has a value of 'true', this interface
         address is advertised for this level without running the IS-IS
         protocol on this interface level.  While in passive mode, the
         interface level ignores ingress IS-IS protocol packets and does
         not transmit any IS-IS protocol packets.

         If the value of vRtrIsisIfLevelPassive is 'false', this interface
         address is advertised at this IS-IS level only if it is configured as
         with the IS-IS protocol as enabled."
    DEFVAL      { false }
    ::= { vRtrIsisIfLevelEntry 5 }

vRtrIsisIfLevelTeMetric          OBJECT-TYPE
    SYNTAX      Unsigned32 (0..4261412864)
    MAX-ACCESS  read-only
    STATUS      obsolete
    DESCRIPTION
        "The value of vRtrIsisIfLevelTeMetric specifies the metric that is used
         exclusively by IS-IS traffic engineered traffic.

         Normal IS-IS traffic specifies metrics values between 1 and 63.
         Wider metrics are needed to support traffic engineering.  See
         vRtrIsisLevelWideMetricsOnly description for more details..

         The value '0' means not configured."
    DEFVAL      { 0 }
    ::= { vRtrIsisIfLevelEntry 6 }

vRtrIsisIfLevelNumAdjacencies    OBJECT-TYPE
    SYNTAX      Unsigned32
    MAX-ACCESS  read-only
    STATUS      obsolete
    DESCRIPTION
        "vRtrIsisIfLevelNumAdjacencies maintains the number of adjacencies on
         this particular level of the interface."
    ::= { vRtrIsisIfLevelEntry 7 }

vRtrIsisIfLevelISPriority        OBJECT-TYPE
    SYNTAX      Unsigned32 (0..127)
    MAX-ACCESS  read-only
    STATUS      obsolete
    DESCRIPTION
        "vRtrIsisIfLevelISPriority shadows the object isisCircLevelISPriority
         to have an additional accepted value of 0."
    ::= { vRtrIsisIfLevelEntry 8 }

vRtrIsisIfLevelHelloTimer        OBJECT-TYPE
    SYNTAX      Unsigned32 (1..20000)
    MAX-ACCESS  read-only
    STATUS      obsolete
    DESCRIPTION
        "vRtrIsisIfLevelHelloTimer shadows isisCircLevelHelloTimer to have
         store the values of hello timer in seconds."
    ::= { vRtrIsisIfLevelEntry 9 }

vRtrIsisIfLevelAdminMetric       OBJECT-TYPE
    SYNTAX      Unsigned32 (0..16777215)
    MAX-ACCESS  read-only
    STATUS      obsolete
    DESCRIPTION
        "The default metric value of this circuit for this level.

         A value of 0 means that the metric is not configured. In such a case
         if the vRtrIsisReferenceBw is configured, the value of the metric
         should be calculated using the formula :

            Metric = reference-bandwidth / bandwidth.

         If the vRtrIsisReferenceBw is configured as Ten Gig (10,000,000,000) a
         100-Mbps interface has a default metric of 100. In order for metrics
         in excess of 63 to be configured wide metrics must be deployed.

         If the reference bandwidth is not configured then all levels will have
         a default metric of 10.

         System and loopback interface levels will always have a metric value
         of 0.

         The operational value of the metric is maintained in the object
         vRtrIsisIfLevelOperMetric."
    DEFVAL      { 0 }
    ::= { vRtrIsisIfLevelEntry 10 }

vRtrIsisIfLevelOperMetric        OBJECT-TYPE
    SYNTAX      Unsigned32 (0..16777215)
    MAX-ACCESS  read-only
    STATUS      obsolete
    DESCRIPTION
        "The operational value of the metric being used in this circuit for
         this level.

         System and loop back interface levels will have metric value of 0"
    ::= { vRtrIsisIfLevelEntry 11 }

vRtrIsisIfLvlIPv6UcastAdmMet     OBJECT-TYPE
    SYNTAX      Unsigned32 (0..16777215)
    MAX-ACCESS  read-only
    STATUS      obsolete
    DESCRIPTION
        "The value of vRtrIsisIfLvlIPv6UcastAdmMet specifies the interface
         level metric for IPv6 unicast."
    DEFVAL      { 0 }
    ::= { vRtrIsisIfLevelEntry 12 }

vRtrIsisIfLvlIPv6UcastOperMet    OBJECT-TYPE
    SYNTAX      Unsigned32 (0..16777215)
    MAX-ACCESS  read-only
    STATUS      obsolete
    DESCRIPTION
        "The operational value of the IPv6 unicast metric being used with this
         interface level."
    ::= { vRtrIsisIfLevelEntry 13 }

vRtrIsisIfLvlIPv4McastAdmMetric  OBJECT-TYPE
    SYNTAX      Unsigned32 (0..16777215)
    MAX-ACCESS  read-only
    STATUS      obsolete
    DESCRIPTION
        "The value of vRtrIsisIfLvlIPv4McastAdmMetric specifies the interface
         level metric for IPv4 multicast."
    DEFVAL      { 0 }
    ::= { vRtrIsisIfLevelEntry 14 }

vRtrIsisIfLvlIPv6McastAdmMetric  OBJECT-TYPE
    SYNTAX      Unsigned32 (0..16777215)
    MAX-ACCESS  read-only
    STATUS      obsolete
    DESCRIPTION
        "The value of vRtrIsisIfLvlIPv6McastAdmMetric specifies the interface
         level metric for IPv6 multicast."
    DEFVAL      { 0 }
    ::= { vRtrIsisIfLevelEntry 15 }

vRtrIsisIfLevelLinkGroupName     OBJECT-TYPE
    SYNTAX      TNamedItemOrEmpty
    MAX-ACCESS  read-only
    STATUS      obsolete
    DESCRIPTION
        "The value of vRtrIsisIfLevelLinkGroupName specifies the ISIS link
         group associated with this particular level of the interface."
    DEFVAL      { ''H }
    ::= { vRtrIsisIfLevelEntry 16 }

vRtrIsisIfLevelSdOffset          OBJECT-TYPE
    SYNTAX      Unsigned32 (0..16777215)
    MAX-ACCESS  read-only
    STATUS      obsolete
    DESCRIPTION
        "The value of vRtrIsisIfLevelSdOffset specifies the offset by which the
         IS-IS interface metric should be increased upon receiving the signal
         degrade threshold event."
    DEFVAL      { 0 }
    ::= { vRtrIsisIfLevelEntry 17 }

vRtrIsisIfLevelSfOffset          OBJECT-TYPE
    SYNTAX      Unsigned32 (0..16777215)
    MAX-ACCESS  read-only
    STATUS      obsolete
    DESCRIPTION
        "The value of vRtrIsisIfLevelSfOffset specifies the offset by which the
         IS-IS interface metric should be further increased in addition to the
         offset specified by vRtrIsisIfLevelSdOffset upon receiving the signal
         fail threshold event."
    DEFVAL      { 0 }
    ::= { vRtrIsisIfLevelEntry 18 }

vRtrIsisIfLvlIPv4McastOperMetric OBJECT-TYPE
    SYNTAX      Unsigned32 (0..16777215)
    MAX-ACCESS  read-only
    STATUS      obsolete
    DESCRIPTION
        "The value of vRtrIsisIfLvlIPv4McastOperMetric indicates the
         operational value of the interface level metric for IPv4 multicast."
    ::= { vRtrIsisIfLevelEntry 19 }

vRtrIsisIfLvlIPv6McastOperMetric OBJECT-TYPE
    SYNTAX      Unsigned32 (0..16777215)
    MAX-ACCESS  read-only
    STATUS      obsolete
    DESCRIPTION
        "The value of vRtrIsisIfLvlIPv6McastOperMetric indicates the
         operational value of the interface level metric for IPv6 multicast."
    ::= { vRtrIsisIfLevelEntry 20 }

vRtrIsisAdjObjs                  OBJECT IDENTIFIER ::= { vRtrIsisObjs 3 }

vRtrIsisISAdjTable               OBJECT-TYPE
    SYNTAX      SEQUENCE OF VRtrIsisISAdjEntry
    MAX-ACCESS  not-accessible
    STATUS      obsolete
    DESCRIPTION
        "vRtrIsisISAdjTable is the table of adjacencies to Intermediate Systems
         and their operational status information.

          This table is obsolete and replaced by tmnxIsisISAdjTable in
          TIMETRA-ISIS-NG-MIB."
    ::= { vRtrIsisAdjObjs 1 }

vRtrIsisISAdjEntry               OBJECT-TYPE
    SYNTAX      VRtrIsisISAdjEntry
    MAX-ACCESS  not-accessible
    STATUS      obsolete
    DESCRIPTION
        "Each row entry in the vRtrIsisISAdjTable represents additional columns
         for attributes specific to the Nokia SROS series ISIS implementation."
    AUGMENTS    { isisISAdjEntry }
    ::= { vRtrIsisISAdjTable 1 }

VRtrIsisISAdjEntry               ::= SEQUENCE
{
    vRtrIsisISAdjExpiresIn           Integer32,
    vRtrIsisISAdjCircLevel           INTEGER,
    vRtrIsisISAdjNeighborIP          IpAddress,
    vRtrIsisISAdjRestartSupport      TruthValue,
    vRtrIsisISAdjRestartStatus       INTEGER,
    vRtrIsisISAdjRestartSupressed    TruthValue,
    vRtrIsisISAdjNumRestarts         Unsigned32,
    vRtrIsisISAdjLastRestartTime     TimeStamp,
    vRtrIsisISAdjNeighborIPv6Type    InetAddressType,
    vRtrIsisISAdjNeighborIpv6        InetAddress,
    vRtrIsisISAdjMtEnabled           TruthValue,
    vRtrIsisISAdjMtId0               TruthValue,
    vRtrIsisISAdjMtId2               TruthValue,
    vRtrIsisISAdjMtId3               TruthValue,
    vRtrIsisISAdjMtId4               TruthValue
}

vRtrIsisISAdjExpiresIn           OBJECT-TYPE
    SYNTAX      Integer32 (1..65535)
    UNITS       "seconds"
    MAX-ACCESS  read-only
    STATUS      obsolete
    DESCRIPTION
        "vRtrIsisISAdjExpiresIn maintains the time in which the adjacency will
         expire if no hello packets are received."
    ::= { vRtrIsisISAdjEntry 1 }

vRtrIsisISAdjCircLevel           OBJECT-TYPE
    SYNTAX      INTEGER {
        level1   (1),
        level2   (2),
        level1L2 (3),
        unknown  (4)
    }
    MAX-ACCESS  read-only
    STATUS      obsolete
    DESCRIPTION
        "The value of vRtrIsisISAdjCircLevel indicates the circuit type of the
         adjacency as advertised."
    DEFVAL      { unknown }
    ::= { vRtrIsisISAdjEntry 2 }

vRtrIsisISAdjNeighborIP          OBJECT-TYPE
    SYNTAX      IpAddress
    MAX-ACCESS  read-only
    STATUS      obsolete
    DESCRIPTION
        "The IP address of the neighbor with which adjacency is formed is
         maintained in vRtrIsisISAdjNeighborIP."
    ::= { vRtrIsisISAdjEntry 3 }

vRtrIsisISAdjRestartSupport      OBJECT-TYPE
    SYNTAX      TruthValue
    MAX-ACCESS  read-only
    STATUS      obsolete
    DESCRIPTION
        "vRtrIsisISAdjRestartSupport indicates whether adjacency supports ISIS
         graceful restart. If vRtrIsisISAdjRestartSupport has a value of 'true'
         the adjacency supports graceful restart."
    ::= { vRtrIsisISAdjEntry 4 }

vRtrIsisISAdjRestartStatus       OBJECT-TYPE
    SYNTAX      INTEGER {
        notHelping       (1),
        restarting       (2),
        restart-complete (3),
        helping          (4)
    }
    MAX-ACCESS  read-only
    STATUS      obsolete
    DESCRIPTION
        "vRtrIsisISAdjRestartStatus indicates the graceful restart status of
         the adjacency."
    ::= { vRtrIsisISAdjEntry 5 }

vRtrIsisISAdjRestartSupressed    OBJECT-TYPE
    SYNTAX      TruthValue
    MAX-ACCESS  read-only
    STATUS      obsolete
    DESCRIPTION
        "vRtrIsisISAdjRestartSupressed indicates if the adjacency has requested
         this router to suppress advertisement of the adjacency in this
         router's LSPs. If vRtrIsisISAdjRestartSupressed has a value of 'true'
         the adjacency has requested to suppress advertisement of the LSPs."
    ::= { vRtrIsisISAdjEntry 6 }

vRtrIsisISAdjNumRestarts         OBJECT-TYPE
    SYNTAX      Unsigned32
    MAX-ACCESS  read-only
    STATUS      obsolete
    DESCRIPTION
        "vRtrIsisISAdjNumRestarts indicates the number of times the adjacency
         has attempted restart."
    ::= { vRtrIsisISAdjEntry 7 }

vRtrIsisISAdjLastRestartTime     OBJECT-TYPE
    SYNTAX      TimeStamp
    MAX-ACCESS  read-only
    STATUS      obsolete
    DESCRIPTION
        "vRtrIsisISAdjLastRestartTime indicates the last time the adjacency
         attempted restart."
    ::= { vRtrIsisISAdjEntry 8 }

vRtrIsisISAdjNeighborIPv6Type    OBJECT-TYPE
    SYNTAX      InetAddressType
    MAX-ACCESS  read-only
    STATUS      obsolete
    DESCRIPTION
        "The value of vRtrIsisISAdjNeighborIPv6Type indicates the IP address
         type of vRtrIsisISAdjNeighborIpv6. It will be 'ipv6', 'ipv6z' or
         'unknown'."
    ::= { vRtrIsisISAdjEntry 9 }

vRtrIsisISAdjNeighborIpv6        OBJECT-TYPE
    SYNTAX      InetAddress (SIZE (0|16|20))
    MAX-ACCESS  read-only
    STATUS      obsolete
    DESCRIPTION
        "The value of vRtrIsisISAdjNeighborIpv6 indicates the IP address of the
         neighbor with which an IPv6-adjacency is formed. This will always be
         an IPv6 address."
    ::= { vRtrIsisISAdjEntry 10 }

vRtrIsisISAdjMtEnabled           OBJECT-TYPE
    SYNTAX      TruthValue
    MAX-ACCESS  read-only
    STATUS      obsolete
    DESCRIPTION
        "vRtrIsisISAdjMtEnabled indicates if the ISIS multi-topology protocol
         is supported on the neighbor.

         If the value of vRtrIsisISAdjMtEnabled is 'true', ISIS multi-topology
         protocol is enabled on the neighbor."
    ::= { vRtrIsisISAdjEntry 11 }

vRtrIsisISAdjMtId0               OBJECT-TYPE
    SYNTAX      TruthValue
    MAX-ACCESS  read-only
    STATUS      obsolete
    DESCRIPTION
        "vRtrIsisISAdjMtId0 indicates if the native topology is supported on
         the neighbor.

         If the value of vRtrIsisISAdjMtId0 is 'true', native topology is
         supported on the neighbor."
    ::= { vRtrIsisISAdjEntry 12 }

vRtrIsisISAdjMtId2               OBJECT-TYPE
    SYNTAX      TruthValue
    MAX-ACCESS  read-only
    STATUS      obsolete
    DESCRIPTION
        "vRtrIsisISAdjMtId2 indicates if the multi-topology for IPv6 is
         supported on the neighbor.

         If the value of vRtrIsisISAdjMtId2 is 'true', multi-topology for IPv6
         is supported on the neighbor."
    ::= { vRtrIsisISAdjEntry 13 }

vRtrIsisISAdjMtId3               OBJECT-TYPE
    SYNTAX      TruthValue
    MAX-ACCESS  read-only
    STATUS      obsolete
    DESCRIPTION
        "vRtrIsisISAdjMtId3 indicates if the MT 3 IPv4 topology is supported on
         the neighbor.

         If the value of vRtrIsisISAdjMtId3 is 'true', MT 3 IPv4 topology is
         supported on the neighbor."
    ::= { vRtrIsisISAdjEntry 14 }

vRtrIsisISAdjMtId4               OBJECT-TYPE
    SYNTAX      TruthValue
    MAX-ACCESS  read-only
    STATUS      obsolete
    DESCRIPTION
        "vRtrIsisISAdjMtId4 indicates if the MT 4 IPv6 topology is supported on
         the neighbor.

         If the value of vRtrIsisISAdjMtId4 is 'true', MT 4 IPv6 topology is
         supported on the neighbor."
    ::= { vRtrIsisISAdjEntry 15 }

vRtrIsisNotificationObjs         OBJECT IDENTIFIER ::= { vRtrIsisObjs 4 }

vRtrIsisNotificationTable        OBJECT-TYPE
    SYNTAX      SEQUENCE OF VRtrIsisNotificationEntry
    MAX-ACCESS  not-accessible
    STATUS      current
    DESCRIPTION
        "Objects seen in the most recent notification this instance of the
         IS-IS protocol.

         Most objects in this table are obsolete and replaced with objects in
         tmnxIsisNotificationTable."
    ::= { vRtrIsisNotificationObjs 1 }

vRtrIsisNotificationEntry        OBJECT-TYPE
    SYNTAX      VRtrIsisNotificationEntry
    MAX-ACCESS  not-accessible
    STATUS      current
    DESCRIPTION
        "Each entry defines variables relevant to notifications for one
         instance of the IS-IS protocol."
    INDEX       { isisSysInstance }
    ::= { vRtrIsisNotificationTable 1 }

VRtrIsisNotificationEntry        ::= SEQUENCE
{
    vRtrIsisTrapLSPID                OCTET STRING,
    vRtrIsisSystemLevel              INTEGER,
    vRtrIsisPDUFragment              OCTET STRING,
    vRtrIsisFieldLen                 Integer32,
    vRtrIsisMaxAreaAddress           Integer32,
    vRtrIsisProtocolVersion          Integer32,
    vRtrIsisLSPSize                  Integer32,
    vRtrIsisOriginatingBufferSize    Integer32,
    vRtrIsisProtocolsSupported       OCTET STRING,
    vRtrIsisNbrSysId                 OCTET STRING
}

vRtrIsisTrapLSPID                OBJECT-TYPE
    SYNTAX      OCTET STRING (SIZE (0|8))
    MAX-ACCESS  accessible-for-notify
    STATUS      obsolete
    DESCRIPTION
        "An Octet String that uniquely identifies a Link State PDU."
    ::= { vRtrIsisNotificationEntry 1 }

vRtrIsisSystemLevel              OBJECT-TYPE
    SYNTAX      INTEGER {
        l1   (1),
        l2   (2),
        l1l2 (3)
    }
    MAX-ACCESS  accessible-for-notify
    STATUS      obsolete
    DESCRIPTION
        "Identifies the level the notification applies to."
    ::= { vRtrIsisNotificationEntry 2 }

vRtrIsisPDUFragment              OBJECT-TYPE
    SYNTAX      OCTET STRING (SIZE (0..64))
    MAX-ACCESS  accessible-for-notify
    STATUS      obsolete
    DESCRIPTION
        "Holds up to the first 64 bytes of a PDU that triggered the
         notification."
    ::= { vRtrIsisNotificationEntry 3 }

vRtrIsisFieldLen                 OBJECT-TYPE
    SYNTAX      Integer32 (0..255)
    MAX-ACCESS  accessible-for-notify
    STATUS      obsolete
    DESCRIPTION
        "Holds the System ID length reported in PDU we received."
    ::= { vRtrIsisNotificationEntry 4 }

vRtrIsisMaxAreaAddress           OBJECT-TYPE
    SYNTAX      Integer32 (0..255)
    MAX-ACCESS  accessible-for-notify
    STATUS      obsolete
    DESCRIPTION
        "Holds the Max Area Addresses reported in a PDU we received."
    ::= { vRtrIsisNotificationEntry 5 }

vRtrIsisProtocolVersion          OBJECT-TYPE
    SYNTAX      Integer32 (0..255)
    MAX-ACCESS  accessible-for-notify
    STATUS      obsolete
    DESCRIPTION
        "Holds the Protocol version reported in PDU we received."
    ::= { vRtrIsisNotificationEntry 6 }

vRtrIsisLSPSize                  OBJECT-TYPE
    SYNTAX      Integer32 (0..2147483647)
    MAX-ACCESS  accessible-for-notify
    STATUS      obsolete
    DESCRIPTION
        "Holds the size of LSP we received that is too big to forward."
    ::= { vRtrIsisNotificationEntry 7 }

vRtrIsisOriginatingBufferSize    OBJECT-TYPE
    SYNTAX      Integer32 (0..2147483647)
    MAX-ACCESS  accessible-for-notify
    STATUS      obsolete
    DESCRIPTION
        "Holds the size of vRtrIsisSysOrigL1LSPBuffSize or
         vRtrIsisSysOrigL2LSPBuffSize advertised by peer in TLV."
    ::= { vRtrIsisNotificationEntry 8 }

vRtrIsisProtocolsSupported       OBJECT-TYPE
    SYNTAX      OCTET STRING (SIZE (0..255))
    MAX-ACCESS  accessible-for-notify
    STATUS      obsolete
    DESCRIPTION
        "The list of protocols supported by an adjacent system.  This
         may be empty."
    ::= { vRtrIsisNotificationEntry 9 }

vRtrIsisNbrSysId                 OBJECT-TYPE
    SYNTAX      OCTET STRING (SIZE (0..6))
    MAX-ACCESS  accessible-for-notify
    STATUS      current
    DESCRIPTION
        "The value of vRtrIsisNbrSysId indicates the system-id of the neighbor
         associated with the notification."
    ::= { vRtrIsisNotificationEntry 10 }

vRtrSpbEctFidStart               OBJECT-TYPE
    SYNTAX      TmnxSpbFid
    MAX-ACCESS  accessible-for-notify
    STATUS      current
    DESCRIPTION
        "The value of vRtrSpbEctFidStart indicates the forwarding database
         starting identifier associated with vRtrSpbEctFidCfgChg notification."
    ::= { vRtrIsisNotificationObjs 2 }

vRtrSpbEctFidEnd                 OBJECT-TYPE
    SYNTAX      TmnxSpbFid
    MAX-ACCESS  accessible-for-notify
    STATUS      current
    DESCRIPTION
        "The value of vRtrSpbEctFidEnd indicates the forwarding database ending
         identifier associated with vRtrSpbEctFidCfgChg notification."
    ::= { vRtrIsisNotificationObjs 3 }

vRtrIsisFailureReasonCode        OBJECT-TYPE
    SYNTAX      INTEGER {
        outOfResources (1)
    }
    MAX-ACCESS  accessible-for-notify
    STATUS      obsolete
    DESCRIPTION
        "The value of vRtrIsisFailureReasonCode indicates the reason for the
         last ISIS failure which resulted in it being marked operationally
         down.This object is used by the vRtrIsisFailureDisabled notification.

         This object is obsoleted in release 12.0. It is replaced with
         tmnxIsisFailureReasonCode."
    ::= { vRtrIsisNotificationObjs 4 }

vRtrIsisMIBConformance           OBJECT IDENTIFIER ::= { tmnxSRConfs 10 }

vRtrIsisMIBConformances          OBJECT IDENTIFIER ::= { vRtrIsisMIBConformance 1 }

vRtrIsisMIBV4v0Compliance        MODULE-COMPLIANCE
    STATUS      obsolete
    DESCRIPTION
        "The compliance statement for revision 4.0 of TIMETRA-ISIS-MIB."
    MODULE
        MANDATORY-GROUPS {
            vRtrIsisV4v0Group,
            vRtrIsisHostGroup,
            vRtrIsisRouteV4v0Group,
            vRtrIsisLSPGroup,
            vRtrIsisIfV4v0Group,
            vRtrIsisAdjV4v0Group,
            vRtrIsisNotificationV3v0Group,
            vRtrIsisSpfGroup,
            vRtrIsisPathGroup,
            vRtrIsisSummaryV4v0Group
        }
    ::= { vRtrIsisMIBConformances 4 }

vRtrIsisMIBV5v0Compliance        MODULE-COMPLIANCE
    STATUS      obsolete
    DESCRIPTION
        "The compliance statement for revision 5.0 of TIMETRA-ISIS-MIB."
    MODULE
        MANDATORY-GROUPS {
            vRtrIsisV5v0Group,
            vRtrIsisHostGroup,
            vRtrIsisRouteV5v0Group,
            vRtrIsisLSPGroup,
            vRtrIsisIfV5v0Group,
            vRtrIsisAdjV5v0Group,
            vRtrIsisNotificationV3v0Group,
            vRtrIsisSpfGroup,
            vRtrIsisPathV5v0Group,
            vRtrIsisSummaryV4v0Group
        }
    ::= { vRtrIsisMIBConformances 5 }

vRtrIsisMIBV6v0Compliance        MODULE-COMPLIANCE
    STATUS      obsolete
    DESCRIPTION
        "The compliance statement for revision 6.0 of TIMETRA-ISIS-MIB."
    MODULE
        MANDATORY-GROUPS {
            vRtrIsisV5v0Group,
            vRtrIsisHostGroup,
            vRtrIsisRouteV5v0Group,
            vRtrIsisLSPGroup,
            vRtrIsisIfV5v0Group,
            vRtrIsisAdjV5v0Group,
            vRtrIsisNotificationV3v0Group,
            vRtrIsisSpfGroup,
            vRtrIsisPathV5v0Group,
            vRtrIsisSummaryV4v0Group,
            vRtrIsisIfV6v0Group,
            vRtrIsisV6v0Group,
            vRtrIsisNotificationV6v0Group,
            vRtrIsisLspMtuV6v0Group
        }
    ::= { vRtrIsisMIBConformances 6 }

vRtrIsisMIBV6v1Compliance        MODULE-COMPLIANCE
    STATUS      obsolete
    DESCRIPTION
        "The compliance statement for revision 6.1 of TIMETRA-ISIS-MIB."
    MODULE
        MANDATORY-GROUPS {
            vRtrIsisV5v0Group,
            vRtrIsisHostGroup,
            vRtrIsisRouteV5v0Group,
            vRtrIsisLSPGroup,
            vRtrIsisIfV5v0Group,
            vRtrIsisAdjV5v0Group,
            vRtrIsisNotificationV3v0Group,
            vRtrIsisSpfGroup,
            vRtrIsisPathV5v0Group,
            vRtrIsisSummaryV4v0Group,
            vRtrIsisIfV6v0Group,
            vRtrIsisV6v0Group,
            vRtrIsisNotificationV6v0Group,
            vRtrIsisLspMtuV6v0Group,
            vRtrIsisV6v1Group,
            vRtrIsisIfV6v1Group,
            vRtrIsisSummaryV6v1Group,
            vRtrIsisRouteV6v1Group
        }
    ::= { vRtrIsisMIBConformances 7 }

vRtrIsisMIBV7v0Compliance        MODULE-COMPLIANCE
    STATUS      obsolete
    DESCRIPTION
        "The compliance statement for revision 7.0 of TIMETRA-ISIS-MIB."
    MODULE
        MANDATORY-GROUPS {
            vRtrIsisV5v0Group,
            vRtrIsisHostGroup,
            vRtrIsisRouteV5v0Group,
            vRtrIsisLSPGroup,
            vRtrIsisIfV5v0Group,
            vRtrIsisAdjV5v0Group,
            vRtrIsisNotificationV3v0Group,
            vRtrIsisSpfGroup,
            vRtrIsisPathV5v0Group,
            vRtrIsisSummaryV4v0Group,
            vRtrIsisIfV6v0Group,
            vRtrIsisV6v0Group,
            vRtrIsisNotificationV6v0Group,
            vRtrIsisLspMtuV6v0Group,
            vRtrIsisV6v1Group,
            vRtrIsisIfV6v1Group,
            vRtrIsisSummaryV6v1Group,
            vRtrIsisRouteV6v1Group,
            vRtrIsisV7v0Group,
            vRtrIsisNotificationV7v0Group
        }
    ::= { vRtrIsisMIBConformances 8 }

vRtrIsisMIBV8v0Compliance        MODULE-COMPLIANCE
    STATUS      obsolete
    DESCRIPTION
        "The compliance statement for revision 8.0 of TIMETRA-ISIS-MIB."
    MODULE
        MANDATORY-GROUPS {
            vRtrIsisV5v0Group,
            vRtrIsisHostGroup,
            vRtrIsisRouteV5v0Group,
            vRtrIsisLSPGroup,
            vRtrIsisIfV5v0Group,
            vRtrIsisAdjV5v0Group,
            vRtrIsisNotificationV3v0Group,
            vRtrIsisSpfGroup,
            vRtrIsisPathV5v0Group,
            vRtrIsisSummaryV4v0Group,
            vRtrIsisIfV6v0Group,
            vRtrIsisV6v0Group,
            vRtrIsisNotificationV6v0Group,
            vRtrIsisLspMtuV6v0Group,
            vRtrIsisV6v1Group,
            vRtrIsisIfV6v1Group,
            vRtrIsisSummaryV6v1Group,
            vRtrIsisRouteV6v1Group,
            vRtrIsisV7v0Group,
            vRtrIsisNotificationV7v0Group,
            vRtrIsisV8v0Group
        }
    ::= { vRtrIsisMIBConformances 9 }

vRtrIsisMIBV9v0Compliance        MODULE-COMPLIANCE
    STATUS      obsolete
    DESCRIPTION
        "The compliance statement for revision 9.0 of TIMETRA-ISIS-MIB."
    MODULE
        MANDATORY-GROUPS {
            vRtrIsisV5v0Group,
            vRtrIsisHostGroup,
            vRtrIsisRouteV5v0Group,
            vRtrIsisLSPGroup,
            vRtrIsisIfV5v0Group,
            vRtrIsisAdjV5v0Group,
            vRtrIsisNotificationV3v0Group,
            vRtrIsisSpfGroup,
            vRtrIsisPathV5v0Group,
            vRtrIsisSummaryV4v0Group,
            vRtrIsisIfV6v0Group,
            vRtrIsisV6v0Group,
            vRtrIsisNotificationV6v0Group,
            vRtrIsisLspMtuV6v0Group,
            vRtrIsisV6v1Group,
            vRtrIsisIfV6v1Group,
            vRtrIsisSummaryV6v1Group,
            vRtrIsisRouteV6v1Group,
            vRtrIsisV7v0Group,
            vRtrIsisNotificationV7v0Group,
            vRtrIsisV8v0Group,
            vRtrIsisV9v0Group,
            vRtrIsisIfV9v0Group,
            vRtrIsisV9v0R4Group
        }
    ::= { vRtrIsisMIBConformances 10 }

vRtrIsisMIBV10v0Compliance       MODULE-COMPLIANCE
    STATUS      obsolete
    DESCRIPTION
        "The compliance statement for revision 10.0 of TIMETRA-ISIS-MIB."
    MODULE
        MANDATORY-GROUPS {
            vRtrIsisV5v0Group,
            vRtrIsisHostGroup,
            vRtrIsisRouteV5v0Group,
            vRtrIsisLSPGroup,
            vRtrIsisIfV5v0Group,
            vRtrIsisAdjV5v0Group,
            vRtrIsisNotificationV3v0Group,
            vRtrIsisSpfGroup,
            vRtrIsisPathV5v0Group,
            vRtrIsisSummaryV4v0Group,
            vRtrIsisIfV6v0Group,
            vRtrIsisV6v0Group,
            vRtrIsisNotificationV6v0Group,
            vRtrIsisLspMtuV6v0Group,
            vRtrIsisV6v1Group,
            vRtrIsisIfV6v1Group,
            vRtrIsisSummaryV6v1Group,
            vRtrIsisRouteV6v1Group,
            vRtrIsisV7v0Group,
            vRtrIsisNotificationV7v0Group,
            vRtrIsisV8v0Group,
            vRtrIsisV9v0Group,
            vRtrIsisIfV9v0Group,
            vRtrIsisV9v0R4Group,
            vRtrSpbEctFidGroup,
            vRtrIsisNotifyObjsV10v0Group,
            vRtrIsisNotifyV10v0Group,
            vRtrIsisV10v0Group
        }
    ::= { vRtrIsisMIBConformances 11 }

vRtrIsisMIBV11v0Compliance       MODULE-COMPLIANCE
    STATUS      obsolete
    DESCRIPTION
        "The compliance statement for revision 11.0 of TIMETRA-ISIS-MIB."
    MODULE
        MANDATORY-GROUPS {
            vRtrIsisV5v0Group,
            vRtrIsisHostGroup,
            vRtrIsisRouteV5v0Group,
            vRtrIsisLSPGroup,
            vRtrIsisIfV5v0Group,
            vRtrIsisAdjV5v0Group,
            vRtrIsisNotificationV3v0Group,
            vRtrIsisSpfGroup,
            vRtrIsisPathV5v0Group,
            vRtrIsisSummaryV4v0Group,
            vRtrIsisIfV6v0Group,
            vRtrIsisV6v0Group,
            vRtrIsisNotificationV6v0Group,
            vRtrIsisLspMtuV6v0Group,
            vRtrIsisV6v1Group,
            vRtrIsisIfV6v1Group,
            vRtrIsisSummaryV6v1Group,
            vRtrIsisRouteV6v1Group,
            vRtrIsisV7v0Group,
            vRtrIsisNotificationV7v0Group,
            vRtrIsisV8v0Group,
            vRtrIsisV9v0Group,
            vRtrIsisIfV9v0Group,
            vRtrIsisV9v0R4Group,
            vRtrSpbEctFidGroup,
            vRtrIsisNotifyObjsV10v0Group,
            vRtrIsisNotifyV10v0Group,
            vRtrIsisV10v0Group,
            vRtrIsisV11v0Group,
            vRtrIsisV11R4v0Group,
            vRtrIsisOvrMaxMetricGroup,
            vRtrIsisLgGroup,
            vRtrIsisRouterIdGroup,
            vRtrIsisLspGroup
        }
    ::= { vRtrIsisMIBConformances 12 }

vRtrIsisMIBV12v0Compliance       MODULE-COMPLIANCE
    STATUS      current
    DESCRIPTION
        "The compliance statement for revision 12.0 of TIMETRA-ISIS-MIB."
    MODULE
        MANDATORY-GROUPS {
            vRtrSpbEctFidGroup,
            vRtrIsisNotifyObjsV10v0Group,
            vRtrIsisNotifyV10v0Group,
            vRtrIsisLgV12v0Group,
            vRtrIsisObsoletedV12v0Group
        }
    ::= { vRtrIsisMIBConformances 13 }

vRtrIsisMIBGroups                OBJECT IDENTIFIER ::= { vRtrIsisMIBConformance 2 }

vRtrIsisHostGroup                OBJECT-GROUP
    OBJECTS     {
        vRtrIsisHostname
    }
    STATUS      obsolete
    DESCRIPTION
        "The group of objects supporting management of ISIS hostname objects on
         Nokia SROS series systems."
    ::= { vRtrIsisMIBGroups 2 }

vRtrIsisPathGroup                OBJECT-GROUP
    OBJECTS     {
        vRtrIsisPathMetric,
        vRtrIsisPathSNPA
    }
    STATUS      obsolete
    DESCRIPTION
        "The group of objects supporting management of ISIS path objects on
         Nokia SROS series systems."
    ::= { vRtrIsisMIBGroups 4 }

vRtrIsisLSPGroup                 OBJECT-GROUP
    OBJECTS     {
        vRtrIsisLSPSeq,
        vRtrIsisLSPChecksum,
        vRtrIsisLSPLifetimeRemain,
        vRtrIsisLSPVersion,
        vRtrIsisLSPPktType,
        vRtrIsisLSPPktVersion,
        vRtrIsisLSPMaxArea,
        vRtrIsisLSPSysIdLen,
        vRtrIsisLSPAttributes,
        vRtrIsisLSPUsedLen,
        vRtrIsisLSPAllocLen,
        vRtrIsisLSPBuff,
        vRtrIsisLSPZeroRLT
    }
    STATUS      obsolete
    DESCRIPTION
        "The group of objects supporting management of ISIS LSP objects on
         Nokia SROS series systems."
    ::= { vRtrIsisMIBGroups 5 }

vRtrIsisNotificationObjGroup     OBJECT-GROUP
    OBJECTS     {
        vRtrIsisTrapLSPID,
        vRtrIsisSystemLevel,
        vRtrIsisPDUFragment,
        vRtrIsisFieldLen,
        vRtrIsisMaxAreaAddress,
        vRtrIsisProtocolVersion,
        vRtrIsisLSPSize,
        vRtrIsisOriginatingBufferSize,
        vRtrIsisProtocolsSupported
    }
    STATUS      obsolete
    DESCRIPTION
        "The group of objects supporting management of ISIS notification
         objects on Nokia SROS series systems."
    ::= { vRtrIsisMIBGroups 8 }

vRtrIsisSpfGroup                 OBJECT-GROUP
    OBJECTS     {
        vRtrIsisSpfRunTime,
        vRtrIsisSpfL1Nodes,
        vRtrIsisSpfL2Nodes,
        vRtrIsisSpfEventCount,
        vRtrIsisSpfLastTriggerLSPId,
        vRtrIsisSpfTriggerReason
    }
    STATUS      obsolete
    DESCRIPTION
        "The group of objects supporting management of ISIS SPF objects on
         Nokia SROS series systems."
    ::= { vRtrIsisMIBGroups 10 }

vRtrIsisNotificationV3v0Group    NOTIFICATION-GROUP
    NOTIFICATIONS {
        vRtrIsisDatabaseOverload,
        vRtrIsisManualAddressDrops,
        vRtrIsisCorruptedLSPDetected,
        vRtrIsisMaxSeqExceedAttempt,
        vRtrIsisIDLenMismatch,
        vRtrIsisMaxAreaAddrsMismatch,
        vRtrIsisOwnLSPPurge,
        vRtrIsisSequenceNumberSkip,
        vRtrIsisAutTypeFail,
        vRtrIsisAuthFail,
        vRtrIsisVersionSkew,
        vRtrIsisAreaMismatch,
        vRtrIsisRejectedAdjacency,
        vRtrIsisLSPTooLargeToPropagate,
        vRtrIsisOrigLSPBufSizeMismatch,
        vRtrIsisProtoSuppMismatch,
        vRtrIsisAdjacencyChange,
        vRtrIsisCircIdExhausted,
        vRtrIsisAdjRestartStatusChange
    }
    STATUS      obsolete
    DESCRIPTION
        "The group of notifications supporting management of ISIS notifications
         on Nokia SROS series systems."
    ::= { vRtrIsisMIBGroups 15 }

vRtrIsisV4v0Group                OBJECT-GROUP
    OBJECTS     {
        vRtrIsisLastEnabledTime,
        vRtrIsisAuthKey,
        vRtrIsisAuthType,
        vRtrIsisAuthCheck,
        vRtrIsisExportPolicy1,
        vRtrIsisExportPolicy2,
        vRtrIsisExportPolicy3,
        vRtrIsisExportPolicy4,
        vRtrIsisExportPolicy5,
        vRtrIsisLspLifetime,
        vRtrIsisOverloadTimeout,
        vRtrIsisOperState,
        vRtrIsisReferenceBw,
        vRtrIsisTrafficEng,
        vRtrIsisShortCuts,
        vRtrIsisSpfHoldTime,
        vRtrIsisLastSpfRun,
        vRtrIsisGracefulRestart,
        vRtrIsisOverloadOnBoot,
        vRtrIsisOverloadOnBootTimeout,
        vRtrIsisSpfWait,
        vRtrIsisSpfInitialWait,
        vRtrIsisSpfSecondWait,
        vRtrIsisLspMaxWait,
        vRtrIsisLspInitialWait,
        vRtrIsisLspSecondWait,
        vRtrIsisCsnpAuthentication,
        vRtrIsisHelloAuthentication,
        vRtrIsisPsnpAuthentication,
        vRtrIsisGRRestartDuration,
        vRtrIsisGRHelperMode,
        vRtrIsisEnableIPv6,
        vRtrIsisEnableIPv4,
        vRtrIsisUnicastImport,
        vRtrIsisMulticastImport,
        vRtrIsisStrictAdjacencyCheck,
        vRtrIsisLevelAuthKey,
        vRtrIsisLevelAuthType,
        vRtrIsisLevelExtPreference,
        vRtrIsisLevelPreference,
        vRtrIsisLevelWideMetricsOnly,
        vRtrIsisLevelOverloadStatus,
        vRtrIsisLevelOverloadTimeLeft,
        vRtrIsisLevelNumLSPs,
        vRtrIsisLevelCsnpAuthentication,
        vRtrIsisLevelHelloAuthentication,
        vRtrIsisLevelPsnpAuthentication,
        vRtrIsisSpfRuns,
        vRtrIsisLSPRegenerations,
        vRtrIsisInitiatedPurges,
        vRtrIsisLSPRecd,
        vRtrIsisLSPDrop,
        vRtrIsisLSPSent,
        vRtrIsisLSPRetrans,
        vRtrIsisIIHRecd,
        vRtrIsisIIHDrop,
        vRtrIsisIIHSent,
        vRtrIsisIIHRetrans,
        vRtrIsisCSNPRecd,
        vRtrIsisCSNPDrop,
        vRtrIsisCSNPSent,
        vRtrIsisCSNPRetrans,
        vRtrIsisPSNPRecd,
        vRtrIsisPSNPDrop,
        vRtrIsisPSNPSent,
        vRtrIsisPSNPRetrans,
        vRtrIsisUnknownRecd,
        vRtrIsisUnknownDrop,
        vRtrIsisUnknownSent,
        vRtrIsisUnknownRetrans,
        vRtrIsisCSPFRequests,
        vRtrIsisCSPFDroppedRequests,
        vRtrIsisCSPFPathsFound,
        vRtrIsisCSPFPathsNotFound
    }
    STATUS      obsolete
    DESCRIPTION
        "The group of objects supporting management of ISIS system objects on
         Nokia SROS series systems."
    ::= { vRtrIsisMIBGroups 16 }

vRtrIsisRouteV4v0Group           OBJECT-GROUP
    OBJECTS     {
        vRtrIsisRouteLevel,
        vRtrIsisRouteSpfVersion,
        vRtrIsisRouteMetric,
        vRtrIsisRouteType,
        vRtrIsisRouteNHopSysID,
        vRtrIsisInetRouteLevel,
        vRtrIsisInetRouteSpfRunNumber,
        vRtrIsisInetRouteMetric,
        vRtrIsisInetRouteType,
        vRtrIsisInetRouteNHopSysID
    }
    STATUS      obsolete
    DESCRIPTION
        "The group of objects supporting management of ISIS route objects on
         Nokia SROS series systems."
    ::= { vRtrIsisMIBGroups 17 }

vRtrIsisSummaryV4v0Group         OBJECT-GROUP
    OBJECTS     {
        vRtrIsisSummRowStatus,
        vRtrIsisSummLevel,
        vRtrIsisInetSummRowStatus,
        vRtrIsisInetSummLevel
    }
    STATUS      obsolete
    DESCRIPTION
        "The group of objects supporting management of ISIS Summary Addresses
         on Nokia SROS series systems."
    ::= { vRtrIsisMIBGroups 18 }

vRtrIsisAdjV4v0Group             OBJECT-GROUP
    OBJECTS     {
        vRtrIsisISAdjExpiresIn,
        vRtrIsisISAdjCircLevel,
        vRtrIsisISAdjNeighborIP,
        vRtrIsisISAdjRestartSupport,
        vRtrIsisISAdjRestartStatus,
        vRtrIsisISAdjRestartSupressed,
        vRtrIsisISAdjNumRestarts,
        vRtrIsisISAdjLastRestartTime,
        vRtrIsisISAdjNeighborIPv6Type,
        vRtrIsisISAdjNeighborIpv6
    }
    STATUS      obsolete
    DESCRIPTION
        "The group of objects supporting management of ISIS adjacency objects
         on Nokia SROS 4.0 series systems."
    ::= { vRtrIsisMIBGroups 19 }

vRtrIsisIfV4v0Group              OBJECT-GROUP
    OBJECTS     {
        vRtrIsisIfRowStatus,
        vRtrIsisIfLastChangeTime,
        vRtrIsisIfAdminState,
        vRtrIsisIfOperState,
        vRtrIsisIfCsnpInterval,
        vRtrIsisIfHelloAuthKey,
        vRtrIsisIfHelloAuthType,
        vRtrIsisIfLspPacingInterval,
        vRtrIsisIfCircIndex,
        vRtrIsisIfRetransmitInterval,
        vRtrIsisIfTypeDefault,
        vRtrIsisIfEnableBfd,
        vRtrIsisIfLevelLastChangeTime,
        vRtrIsisIfLevelHelloAuthKey,
        vRtrIsisIfLevelHelloAuthType,
        vRtrIsisIfLevelPassive,
        vRtrIsisIfLevelTeMetric,
        vRtrIsisIfLevelNumAdjacencies,
        vRtrIsisIfLevelISPriority,
        vRtrIsisIfLevelHelloTimer,
        vRtrIsisIfLevelAdminMetric,
        vRtrIsisIfLevelOperMetric
    }
    STATUS      obsolete
    DESCRIPTION
        "The group of objects supporting management of ISIS interface objects
         on Nokia SROS 4.0 series systems."
    ::= { vRtrIsisMIBGroups 20 }

vRtrIsisV5v0Group                OBJECT-GROUP
    OBJECTS     {
        vRtrIsisLastEnabledTime,
        vRtrIsisAuthKey,
        vRtrIsisAuthType,
        vRtrIsisAuthCheck,
        vRtrIsisExportPolicy1,
        vRtrIsisExportPolicy2,
        vRtrIsisExportPolicy3,
        vRtrIsisExportPolicy4,
        vRtrIsisExportPolicy5,
        vRtrIsisLspLifetime,
        vRtrIsisOverloadTimeout,
        vRtrIsisOperState,
        vRtrIsisReferenceBw,
        vRtrIsisTrafficEng,
        vRtrIsisShortCuts,
        vRtrIsisSpfHoldTime,
        vRtrIsisLastSpfRun,
        vRtrIsisGracefulRestart,
        vRtrIsisOverloadOnBoot,
        vRtrIsisOverloadOnBootTimeout,
        vRtrIsisSpfWait,
        vRtrIsisSpfInitialWait,
        vRtrIsisSpfSecondWait,
        vRtrIsisLspMaxWait,
        vRtrIsisLspInitialWait,
        vRtrIsisLspSecondWait,
        vRtrIsisCsnpAuthentication,
        vRtrIsisHelloAuthentication,
        vRtrIsisPsnpAuthentication,
        vRtrIsisGRRestartDuration,
        vRtrIsisGRHelperMode,
        vRtrIsisEnableIPv4,
        vRtrIsisUnicastImport,
        vRtrIsisMulticastImport,
        vRtrIsisStrictAdjacencyCheck,
        vRtrIsisManualSpfTrigger,
        vRtrIsisMultiTopology,
        vRtrIsisIPv6RoutingTopo,
        vRtrIsisMultiTopoIPv6Ucast,
        vRtrIsisLevelAuthKey,
        vRtrIsisLevelAuthType,
        vRtrIsisLevelExtPreference,
        vRtrIsisLevelPreference,
        vRtrIsisLevelWideMetricsOnly,
        vRtrIsisLevelOverloadStatus,
        vRtrIsisLevelOverloadTimeLeft,
        vRtrIsisLevelNumLSPs,
        vRtrIsisLevelCsnpAuthentication,
        vRtrIsisLevelHelloAuthentication,
        vRtrIsisLevelPsnpAuthentication,
        vRtrIsisSpfRuns,
        vRtrIsisLSPRegenerations,
        vRtrIsisInitiatedPurges,
        vRtrIsisLSPRecd,
        vRtrIsisLSPDrop,
        vRtrIsisLSPSent,
        vRtrIsisLSPRetrans,
        vRtrIsisIIHRecd,
        vRtrIsisIIHDrop,
        vRtrIsisIIHSent,
        vRtrIsisIIHRetrans,
        vRtrIsisCSNPRecd,
        vRtrIsisCSNPDrop,
        vRtrIsisCSNPSent,
        vRtrIsisCSNPRetrans,
        vRtrIsisPSNPRecd,
        vRtrIsisPSNPDrop,
        vRtrIsisPSNPSent,
        vRtrIsisPSNPRetrans,
        vRtrIsisUnknownRecd,
        vRtrIsisUnknownDrop,
        vRtrIsisUnknownSent,
        vRtrIsisUnknownRetrans,
        vRtrIsisCSPFRequests,
        vRtrIsisCSPFDroppedRequests,
        vRtrIsisCSPFPathsFound,
        vRtrIsisCSPFPathsNotFound
    }
    STATUS      obsolete
    DESCRIPTION
        "The group of objects supporting management of ISIS system objects on
         Nokia SROS 5.0 series systems."
    ::= { vRtrIsisMIBGroups 21 }

vRtrIsisIfV5v0Group              OBJECT-GROUP
    OBJECTS     {
        vRtrIsisIfRowStatus,
        vRtrIsisIfLastChangeTime,
        vRtrIsisIfAdminState,
        vRtrIsisIfOperState,
        vRtrIsisIfCsnpInterval,
        vRtrIsisIfHelloAuthKey,
        vRtrIsisIfHelloAuthType,
        vRtrIsisIfLspPacingInterval,
        vRtrIsisIfCircIndex,
        vRtrIsisIfRetransmitInterval,
        vRtrIsisIfTypeDefault,
        vRtrIsisIfEnableBfd,
        vRtrIsisIfIPv6Unicast,
        vRtrIsisIfLevelLastChangeTime,
        vRtrIsisIfLevelHelloAuthKey,
        vRtrIsisIfLevelHelloAuthType,
        vRtrIsisIfLevelPassive,
        vRtrIsisIfLevelTeMetric,
        vRtrIsisIfLevelNumAdjacencies,
        vRtrIsisIfLevelISPriority,
        vRtrIsisIfLevelHelloTimer,
        vRtrIsisIfLevelAdminMetric,
        vRtrIsisIfLevelOperMetric,
        vRtrIsisIfLvlIPv6UcastAdmMet,
        vRtrIsisIfLvlIPv6UcastOperMet
    }
    STATUS      obsolete
    DESCRIPTION
        "The group of objects supporting management of ISIS interface objects
         on Nokia 7xx0 SR 5.0 series systems."
    ::= { vRtrIsisMIBGroups 22 }

vRtrIsisRouteV5v0Group           OBJECT-GROUP
    OBJECTS     {
        vRtrIsisRouteLevel,
        vRtrIsisRouteSpfVersion,
        vRtrIsisRouteMetric,
        vRtrIsisRouteType,
        vRtrIsisRouteNHopSysID,
        vRtrIsisInetRouteLevel,
        vRtrIsisInetRouteSpfRunNumber,
        vRtrIsisInetRouteMetric,
        vRtrIsisInetRouteType,
        vRtrIsisInetRouteNHopSysID,
        vRtrIsisInetMtRouteLevel,
        vRtrIsisInetMtRouteSpfRunNumber,
        vRtrIsisInetMtRouteMetric,
        vRtrIsisInetMtRouteType,
        vRtrIsisInetMtRouteNHopSysID
    }
    STATUS      obsolete
    DESCRIPTION
        "The group of objects supporting management of ISIS route objects on
         Nokia SROS series systems."
    ::= { vRtrIsisMIBGroups 23 }

vRtrIsisPathV5v0Group            OBJECT-GROUP
    OBJECTS     {
        vRtrIsisPathMetric,
        vRtrIsisPathSNPA,
        vRtrIsisMtPathMetric,
        vRtrIsisMtPathSNPA
    }
    STATUS      obsolete
    DESCRIPTION
        "The group of objects supporting management of ISIS path objects on
         Nokia SROS series systems."
    ::= { vRtrIsisMIBGroups 24 }

vRtrIsisObsoleteV5v0Group        OBJECT-GROUP
    OBJECTS     {
        vRtrIsisEnableIPv6
    }
    STATUS      current
    DESCRIPTION
        "The group of objects in TIMETRA-ISIS-MIB which are obsoleted."
    ::= { vRtrIsisMIBGroups 25 }

vRtrIsisAdjV5v0Group             OBJECT-GROUP
    OBJECTS     {
        vRtrIsisISAdjExpiresIn,
        vRtrIsisISAdjCircLevel,
        vRtrIsisISAdjNeighborIP,
        vRtrIsisISAdjRestartSupport,
        vRtrIsisISAdjRestartStatus,
        vRtrIsisISAdjRestartSupressed,
        vRtrIsisISAdjNumRestarts,
        vRtrIsisISAdjLastRestartTime,
        vRtrIsisISAdjNeighborIPv6Type,
        vRtrIsisISAdjNeighborIpv6,
        vRtrIsisISAdjMtEnabled,
        vRtrIsisISAdjMtId0,
        vRtrIsisISAdjMtId2
    }
    STATUS      obsolete
    DESCRIPTION
        "The group of objects supporting management of ISIS adjacency objects
         on Nokia SROS 5.0 series systems."
    ::= { vRtrIsisMIBGroups 26 }

vRtrIsisLspMtuV6v0Group          OBJECT-GROUP
    OBJECTS     {
        vRtrIsisSysOrigL1LSPBuffSize,
        vRtrIsisSysOrigL2LSPBuffSize
    }
    STATUS      obsolete
    DESCRIPTION
        "The group of objects supporting management of LSP-MTU sizes for ISIS
         on Nokia SROS 6.0 series systems."
    ::= { vRtrIsisMIBGroups 27 }

vRtrIsisIfV6v0Group              OBJECT-GROUP
    OBJECTS     {
        vRtrIsisIfTeMetric,
        vRtrIsisIfTeState,
        vRtrIsisIfAdminGroup,
        vRtrIsisIfLdpSyncState,
        vRtrIsisIfLdpSyncMaxMetric,
        vRtrIsisIfLdpSyncTimerState,
        vRtrIsisIfLdpSyncTimeLeft
    }
    STATUS      obsolete
    DESCRIPTION
        "The group of objects supporting management of ISIS interfaces on Nokia
         6.0 release of SROS series systems."
    ::= { vRtrIsisMIBGroups 28 }

vRtrIsisV6v0Group                OBJECT-GROUP
    OBJECTS     {
        vRtrIsisLdpSyncAdminState,
        vRtrIsisIPv6UnicastImport,
        vRtrIsisIPv6MulticastImport
    }
    STATUS      obsolete
    DESCRIPTION
        "The group of objects supporting management of ISIS system objects on
         Nokia 6.0 release of SROS series systems."
    ::= { vRtrIsisMIBGroups 29 }

vRtrIsisNotificationV6v0Group    NOTIFICATION-GROUP
    NOTIFICATIONS {
        vRtrIsisLdpSyncTimerStarted,
        vRtrIsisLdpSyncExit
    }
    STATUS      obsolete
    DESCRIPTION
        "The group of notifications supporting management of ISIS notifications
         on 6.0 release of Nokia SROS series systems."
    ::= { vRtrIsisMIBGroups 30 }

vRtrIsisV6v1Group                OBJECT-GROUP
    OBJECTS     {
        vRtrIsisAdvertisePassiveOnly,
        vRtrIsisDefaultRouteTag,
        vRtrIsisSuppressDefault
    }
    STATUS      obsolete
    DESCRIPTION
        "The group of objects supporting management of ISIS system objects on
         Nokia 6.1 release of SROS series systems."
    ::= { vRtrIsisMIBGroups 31 }

vRtrIsisIfV6v1Group              OBJECT-GROUP
    OBJECTS     {
        vRtrIsisIfRouteTag
    }
    STATUS      obsolete
    DESCRIPTION
        "The group of objects supporting management of ISIS admin tags feature
         on ISIS interfaces on 6.1 release of Nokia SROS series systems."
    ::= { vRtrIsisMIBGroups 32 }

vRtrIsisSummaryV6v1Group         OBJECT-GROUP
    OBJECTS     {
        vRtrIsisInetSummRouteTag
    }
    STATUS      obsolete
    DESCRIPTION
        "The group of objects supporting management of ISIS Summary Addresses
         on 6.1 release of Nokia SROS series systems."
    ::= { vRtrIsisMIBGroups 33 }

vRtrIsisRouteV6v1Group           OBJECT-GROUP
    OBJECTS     {
        vRtrIsisInetMtRouteTag
    }
    STATUS      obsolete
    DESCRIPTION
        "The group of objects supporting management of ISIS route objects on
         6.1 release of Nokia SROS series systems."
    ::= { vRtrIsisMIBGroups 34 }

vRtrIsisV7v0Group                OBJECT-GROUP
    OBJECTS     {
        vRtrIsisLdpOverRsvp,
        vRtrIsisExportLimit,
        vRtrIsisExportLimitLogPercent,
        vRtrIsisTotalL1ExportedRoutes,
        vRtrIsisTotalL2ExportedRoutes
    }
    STATUS      obsolete
    DESCRIPTION
        "The group of objects supporting management of ISIS system objects
         added in the 7.0 release of Nokia SROS series systems."
    ::= { vRtrIsisMIBGroups 35 }

vRtrIsisNotificationV7v0Group    NOTIFICATION-GROUP
    NOTIFICATIONS {
        vRtrIsisExportLimitReached,
        vRtrIsisExportLimitWarning,
        vRtrIsisRoutesExpLmtDropped
    }
    STATUS      obsolete
    DESCRIPTION
        "The group of notifications supporting management of ISIS on 7.0
         release of Nokia SROS series systems."
    ::= { vRtrIsisMIBGroups 36 }

vRtrIsisV8v0Group                OBJECT-GROUP
    OBJECTS     {
        vRtrIsisRsvpShortcut,
        vRtrIsisAdvertiseTunnelLink,
        vRtrIsisIidTlv,
        vRtrIsisL1MacAddress,
        vRtrIsisL2MacAddress,
        vRtrIsisLevelDefMetric,
        vRtrIsisLevelIPv6DefMetric
    }
    STATUS      obsolete
    DESCRIPTION
        "The group of objects supporting management of ISIS system objects
         added in the 8.0 release of Nokia SROS series systems."
    ::= { vRtrIsisMIBGroups 37 }

vRtrIsisV9v0Group                OBJECT-GROUP
    OBJECTS     {
        vRtrIsisSysOperL1LSPBuffSize,
        vRtrIsisSysOperL2LSPBuffSize
    }
    STATUS      obsolete
    DESCRIPTION
        "The group of objects supporting management of ISIS system objects
         added in the 9.0 release of Nokia SROS series systems."
    ::= { vRtrIsisMIBGroups 38 }

vRtrIsisIfV9v0Group              OBJECT-GROUP
    OBJECTS     {
        vRtrIsisIfIpv6EnableBfd
    }
    STATUS      obsolete
    DESCRIPTION
        "The group of objects supporting management of ISIS interface objects
         on Nokia SROS 9.0 series systems."
    ::= { vRtrIsisMIBGroups 39 }

vRtrIsisV9v0R4Group              OBJECT-GROUP
    OBJECTS     {
        vRtrIsisLoopfreeAlternate,
        vRtrIsisIfHelloAuthentication,
        vRtrIsisLfaRuns,
        vRtrIsisPathLfaIfIndex,
        vRtrIsisPathLfaNHop,
        vRtrIsisPathLfaMetric,
        vRtrIsisPathLfaType,
        vRtrIsisPathRouteType,
        vRtrIsisLfaNodesCovered,
        vRtrIsisLfaTotalNodes,
        vRtrIsisLfaNodeCoverage,
        vRtrIsisLfaIpv4NodesCovered,
        vRtrIsisLfaIpv4TotalNodes,
        vRtrIsisLfaIpv4Coverage,
        vRtrIsisLfaIpv6NodesCovered,
        vRtrIsisLfaIpv6TotalNodes,
        vRtrIsisLfaIpv6Coverage,
        vRtrIsisMtPathLfaIfIndex,
        vRtrIsisMtPathLfaNHop,
        vRtrIsisMtPathLfaMetric,
        vRtrIsisMtPathLfaType,
        vRtrIsisMtPathRouteType,
        vRtrIsisInetMtRouteBkupFlags,
        vRtrIsisInetMtRouteBkupNextHopTy,
        vRtrIsisInetMtRouteBkupNextHop,
        vRtrIsisInetMtRouteBkupMetric,
        vRtrIsisSpfType
    }
    STATUS      obsolete
    DESCRIPTION
        "The group of objects supporting management of ISIS system objects
         added in the 9.0R4 release of Nokia SROS series systems."
    ::= { vRtrIsisMIBGroups 40 }

vRtrSpbEctFidGroup               OBJECT-GROUP
    OBJECTS     {
        vRtrSpbRouteIsidNHopSysID,
        vRtrSpbRouteIsidSpfRunNumber,
        vRtrSpbRouteIsidInMfib,
        vRtrSpbRouteMacMetric,
        vRtrSpbRouteMacMetricType,
        vRtrSpbRouteMacNHopSysID,
        vRtrSpbRouteMacSpfRunNumber,
        vRtrSpbRouteMacIfIndex,
        vRtrSpbPathIfIndex,
        vRtrSpbPathNHopSysID,
        vRtrSpbPathMetric,
        vRtrSpbPathSNPA,
        vRtrSpbEctFidRangeEnd,
        vRtrSpbEctFidRangeAlgorithm,
        vRtrSpbEctFidLastChanged,
        vRtrSpbEctFidAlgorithm,
        vRtrSpbEctFidTableLastChanged
    }
    STATUS      current
    DESCRIPTION
        "The group of objects supporting management of ISIS Shortest Path
         Bridging objects in the Nokia SROS series systems."
    ::= { vRtrIsisMIBGroups 41 }

vRtrIsisV10v0Group               OBJECT-GROUP
    OBJECTS     {
        vRtrIsisLevelLoopfreeAltExclude,
        vRtrIsisIfLoopfreeAltExclude,
        vRtrIsisRouteNextHopType,
        vRtrIsisNextHopOwner,
        vRtrIsisRouteNHOwnerAuxInfo,
        vRtrIsisRouteBkupNHType,
        vRtrIsisRouteBkupNHOwner,
        vRtrIsisRouteBkupNHOwnAxInfo
    }
    STATUS      obsolete
    DESCRIPTION
        "The group of objects supporting management of ISIS system objects
         added in the 10.0 release of Nokia SROS series systems."
    ::= { vRtrIsisMIBGroups 42 }

vRtrIsisNotifyObjsV10v0Group     OBJECT-GROUP
    OBJECTS     {
        vRtrSpbEctFidStart,
        vRtrSpbEctFidEnd,
        vRtrIsisNbrSysId
    }
    STATUS      current
    DESCRIPTION
        "The group of objects supporting management of ISIS notification
         objects on Nokia SROS series systems."
    ::= { vRtrIsisMIBGroups 43 }

vRtrIsisNotifyV10v0Group         NOTIFICATION-GROUP
    NOTIFICATIONS {
        vRtrSpbEctFidCfgChg,
        vRtrIsisSpbNbrMultAdjExists,
        vRtrIsisSpbNbrMultAdjExistsClear
    }
    STATUS      current
    DESCRIPTION
        "The group of notifications supporting management of ISIS on 10.0
         release of Nokia SROS series systems."
    ::= { vRtrIsisMIBGroups 44 }

vRtrIsisV11v0Group               OBJECT-GROUP
    OBJECTS     {
        vRtrIsisIfOperType
    }
    STATUS      obsolete
    DESCRIPTION
        "The group of objects supporting management of ISIS system objects on
         Nokia 11.0 release of SROS series systems."
    ::= { vRtrIsisMIBGroups 45 }

vRtrIsisV11R4v0Group             OBJECT-GROUP
    OBJECTS     {
        vRtrIsisIPv4McastRoutingTopo,
        vRtrIsisIPv6McastRoutingTopo,
        vRtrIsisLevelDefIPv4McastMetric,
        vRtrIsisLevelDefIPv6McastMetric,
        vRtrIsisIfIPv4Mcast,
        vRtrIsisIfIPv6Mcast,
        vRtrIsisIfLvlIPv4McastAdmMetric,
        vRtrIsisIfLvlIPv6McastAdmMetric,
        vRtrIsisMultiTopoIPv4Mcast,
        vRtrIsisMultiTopoIPv6Mcast,
        vRtrIsisISAdjMtId3,
        vRtrIsisISAdjMtId4,
        vRtrIsisIfLvlIPv4McastOperMetric,
        vRtrIsisIfLvlIPv6McastOperMetric
    }
    STATUS      obsolete
    DESCRIPTION
        "The group of objects supporting management of ISIS system objects on
         Nokia 11.0 release of SROS series systems."
    ::= { vRtrIsisMIBGroups 46 }

vRtrIsisOvrMaxMetricGroup        OBJECT-GROUP
    OBJECTS     {
        vRtrIsisOverloadMaxMetric,
        vRtrIsisOverloadOnBootMaxMetric
    }
    STATUS      obsolete
    DESCRIPTION
        "The group of objects supporting management of ISIS system objects on
         Nokia 11.0 release of SROS series systems."
    ::= { vRtrIsisMIBGroups 47 }

vRtrIsisLgGroup                  OBJECT-GROUP
    OBJECTS     {
        vRtrIsisLgRowStatus,
        vRtrIsisLgRowLastChanged,
        vRtrIsisLgTableLastChanged,
        vRtrIsisLgLevelOperMembers,
        vRtrIsisLgLevelRevertMembers,
        vRtrIsisLgLevelIPv4UcastMetric,
        vRtrIsisLgLevelIPv6UcastMetric,
        vRtrIsisLgLevelIPv4McastMetric,
        vRtrIsisLgLevelIPv6McastMetric,
        vRtrIsisLgLevelTableLastChanged,
        vRtrIsisLgLevelLastChanged,
        vRtrIsisIfLevelLinkGroupName,
        vRtrIsisLgLevelOpOperMembers,
        vRtrIsisLgLevelOperRevertMembers,
        vRtrIsisLgLevelOperMembersCount,
        vRtrIsisLgLevelOperActiveMembers,
        vRtrIsisLgLevelOperState,
        vRtrIsisIfBerState,
        vRtrIsisIfLevelSdOffset,
        vRtrIsisIfLevelSfOffset,
        vRtrIsisLgLevelMembersOperState,
        vRtrIsisLgDescription
    }
    STATUS      obsolete
    DESCRIPTION
        "The group of objects supporting management of ISIS system objects on
         Nokia 11.0 release of SROS series systems."
    ::= { vRtrIsisMIBGroups 48 }

vRtrIsisRouterIdGroup            OBJECT-GROUP
    OBJECTS     {
        vRtrIsisRouterId,
        vRtrIsisOperRouterId
    }
    STATUS      obsolete
    DESCRIPTION
        "The group of objects supporting management of ISIS system objects on
         Nokia 11.0 release of SROS series systems."
    ::= { vRtrIsisMIBGroups 49 }

vRtrIsisHelloPaddingGroup        OBJECT-GROUP
    OBJECTS     {
        vRtrIsisHelloPadding
    }
    STATUS      obsolete
    DESCRIPTION
        "The group of objects supporting management of ISIS system objects on
         Nokia 12.0 release of SROS series systems."
    ::= { vRtrIsisMIBGroups 50 }

vRtrIsisLspGroup                 OBJECT-GROUP
    OBJECTS     {
        vRtrIsisIgnoreLspErrors
    }
    STATUS      obsolete
    DESCRIPTION
        "The group of objects supporting management of ISIS system objects on
         Nokia 11.0 release of SROS series systems."
    ::= { vRtrIsisMIBGroups 51 }

vRtrIsisObsoleteNotifyObjsGroup  OBJECT-GROUP
    OBJECTS     {
        vRtrIsisFailureReasonCode,
        vRtrIsisTrapLSPID,
        vRtrIsisSystemLevel,
        vRtrIsisPDUFragment,
        vRtrIsisFieldLen,
        vRtrIsisMaxAreaAddress,
        vRtrIsisProtocolVersion,
        vRtrIsisLSPSize,
        vRtrIsisOriginatingBufferSize,
        vRtrIsisProtocolsSupported
    }
    STATUS      current
    DESCRIPTION
        "The group of objects in TIMETRA-ISIS-MIB which are obsoleted in Nokia
         SROS 12.0 series systems."
    ::= { vRtrIsisMIBGroups 53 }

vRtrIsisObsoleteNotifyGroup      NOTIFICATION-GROUP
    NOTIFICATIONS {
        vRtrIsisFailureDisabled,
        vRtrIsisDatabaseOverload,
        vRtrIsisManualAddressDrops,
        vRtrIsisCorruptedLSPDetected,
        vRtrIsisMaxSeqExceedAttempt,
        vRtrIsisIDLenMismatch,
        vRtrIsisMaxAreaAddrsMismatch,
        vRtrIsisOwnLSPPurge,
        vRtrIsisSequenceNumberSkip,
        vRtrIsisAutTypeFail,
        vRtrIsisAuthFail,
        vRtrIsisVersionSkew,
        vRtrIsisAreaMismatch,
        vRtrIsisRejectedAdjacency,
        vRtrIsisLSPTooLargeToPropagate,
        vRtrIsisOrigLSPBufSizeMismatch,
        vRtrIsisProtoSuppMismatch,
        vRtrIsisAdjacencyChange,
        vRtrIsisCircIdExhausted,
        vRtrIsisAdjRestartStatusChange,
        vRtrIsisLdpSyncTimerStarted,
        vRtrIsisLdpSyncExit,
        vRtrIsisExportLimitReached,
        vRtrIsisExportLimitWarning,
        vRtrIsisRoutesExpLmtDropped
    }
    STATUS      current
    DESCRIPTION
        "The group of objects in TIMETRA-ISIS-MIB which are obsoleted in Nokia
         SROS 12.0 series systems."
    ::= { vRtrIsisMIBGroups 54 }

vRtrIsisAdvRtrCapaGroup          OBJECT-GROUP
    OBJECTS     {
        vRtrIsisAdvRtrCapability,
        vRtrIsisLevelAdvRtrCapability
    }
    STATUS      obsolete
    DESCRIPTION
        "The group of objects supporting management of ISIS system objects on
         Nokia 12.0 release of SROS series systems."
    ::= { vRtrIsisMIBGroups 55 }

vRtrIsisObsoletedV12v0Group      OBJECT-GROUP
    OBJECTS     {
        vRtrIsisLastEnabledTime,
        vRtrIsisAuthKey,
        vRtrIsisAuthType,
        vRtrIsisAuthCheck,
        vRtrIsisExportPolicy1,
        vRtrIsisExportPolicy2,
        vRtrIsisExportPolicy3,
        vRtrIsisExportPolicy4,
        vRtrIsisExportPolicy5,
        vRtrIsisLspLifetime,
        vRtrIsisOverloadTimeout,
        vRtrIsisOperState,
        vRtrIsisReferenceBw,
        vRtrIsisTrafficEng,
        vRtrIsisShortCuts,
        vRtrIsisSpfHoldTime,
        vRtrIsisLastSpfRun,
        vRtrIsisGracefulRestart,
        vRtrIsisOverloadOnBoot,
        vRtrIsisOverloadOnBootTimeout,
        vRtrIsisSpfWait,
        vRtrIsisSpfInitialWait,
        vRtrIsisSpfSecondWait,
        vRtrIsisLspMaxWait,
        vRtrIsisLspInitialWait,
        vRtrIsisLspSecondWait,
        vRtrIsisCsnpAuthentication,
        vRtrIsisHelloAuthentication,
        vRtrIsisPsnpAuthentication,
        vRtrIsisGRRestartDuration,
        vRtrIsisGRHelperMode,
        vRtrIsisEnableIPv6,
        vRtrIsisEnableIPv4,
        vRtrIsisUnicastImport,
        vRtrIsisMulticastImport,
        vRtrIsisStrictAdjacencyCheck,
        vRtrIsisManualSpfTrigger,
        vRtrIsisMultiTopology,
        vRtrIsisMultiTopoIPv6Ucast,
        vRtrIsisIPv6RoutingTopo,
        vRtrIsisSysOrigL1LSPBuffSize,
        vRtrIsisSysOrigL2LSPBuffSize,
        vRtrIsisLdpSyncAdminState,
        vRtrIsisIPv6UnicastImport,
        vRtrIsisIPv6MulticastImport,
        vRtrIsisAdvertisePassiveOnly,
        vRtrIsisDefaultRouteTag,
        vRtrIsisSuppressDefault,
        vRtrIsisLdpOverRsvp,
        vRtrIsisExportLimit,
        vRtrIsisExportLimitLogPercent,
        vRtrIsisTotalL1ExportedRoutes,
        vRtrIsisTotalL2ExportedRoutes,
        vRtrIsisRsvpShortcut,
        vRtrIsisAdvertiseTunnelLink,
        vRtrIsisIidTlv,
        vRtrIsisL1MacAddress,
        vRtrIsisL2MacAddress,
        vRtrIsisSysOperL1LSPBuffSize,
        vRtrIsisSysOperL2LSPBuffSize,
        vRtrIsisLoopfreeAlternate,
        vRtrIsisIPv4McastRoutingTopo,
        vRtrIsisIPv6McastRoutingTopo,
        vRtrIsisMultiTopoIPv4Mcast,
        vRtrIsisMultiTopoIPv6Mcast,
        vRtrIsisOverloadMaxMetric,
        vRtrIsisOverloadOnBootMaxMetric,
        vRtrIsisRouterId,
        vRtrIsisAdvRtrCapability,
        vRtrIsisHelloPadding,
        vRtrIsisOperRouterId,
        vRtrIsisIgnoreLspErrors,
        vRtrIsisLevelAuthKey,
        vRtrIsisLevelAuthType,
        vRtrIsisLevelExtPreference,
        vRtrIsisLevelPreference,
        vRtrIsisLevelWideMetricsOnly,
        vRtrIsisLevelOverloadStatus,
        vRtrIsisLevelOverloadTimeLeft,
        vRtrIsisLevelNumLSPs,
        vRtrIsisLevelCsnpAuthentication,
        vRtrIsisLevelHelloAuthentication,
        vRtrIsisLevelPsnpAuthentication,
        vRtrIsisLevelDefMetric,
        vRtrIsisLevelIPv6DefMetric,
        vRtrIsisLevelLoopfreeAltExclude,
        vRtrIsisLevelDefIPv4McastMetric,
        vRtrIsisLevelDefIPv6McastMetric,
        vRtrIsisLevelAdvRtrCapability,
        vRtrIsisSpfRuns,
        vRtrIsisLSPRegenerations,
        vRtrIsisInitiatedPurges,
        vRtrIsisLSPRecd,
        vRtrIsisLSPDrop,
        vRtrIsisLSPSent,
        vRtrIsisLSPRetrans,
        vRtrIsisIIHRecd,
        vRtrIsisIIHDrop,
        vRtrIsisIIHSent,
        vRtrIsisIIHRetrans,
        vRtrIsisCSNPRecd,
        vRtrIsisCSNPDrop,
        vRtrIsisCSNPSent,
        vRtrIsisCSNPRetrans,
        vRtrIsisPSNPRecd,
        vRtrIsisPSNPDrop,
        vRtrIsisPSNPSent,
        vRtrIsisPSNPRetrans,
        vRtrIsisUnknownRecd,
        vRtrIsisUnknownDrop,
        vRtrIsisUnknownSent,
        vRtrIsisUnknownRetrans,
        vRtrIsisCSPFRequests,
        vRtrIsisCSPFDroppedRequests,
        vRtrIsisCSPFPathsFound,
        vRtrIsisCSPFPathsNotFound,
        vRtrIsisLfaRuns,
        vRtrIsisHostname,
        vRtrIsisRouteLevel,
        vRtrIsisRouteSpfVersion,
        vRtrIsisRouteMetric,
        vRtrIsisRouteType,
        vRtrIsisRouteNHopSysID,
        vRtrIsisPathMetric,
        vRtrIsisPathSNPA,
        vRtrIsisPathLfaIfIndex,
        vRtrIsisPathLfaNHop,
        vRtrIsisPathLfaMetric,
        vRtrIsisPathLfaType,
        vRtrIsisPathRouteType,
        vRtrIsisLSPSeq,
        vRtrIsisLSPChecksum,
        vRtrIsisLSPLifetimeRemain,
        vRtrIsisLSPVersion,
        vRtrIsisLSPPktType,
        vRtrIsisLSPPktVersion,
        vRtrIsisLSPMaxArea,
        vRtrIsisLSPSysIdLen,
        vRtrIsisLSPAttributes,
        vRtrIsisLSPUsedLen,
        vRtrIsisLSPAllocLen,
        vRtrIsisLSPBuff,
        vRtrIsisLSPZeroRLT,
        vRtrIsisSpfRunTime,
        vRtrIsisSpfL1Nodes,
        vRtrIsisSpfL2Nodes,
        vRtrIsisSpfEventCount,
        vRtrIsisSpfLastTriggerLSPId,
        vRtrIsisSpfTriggerReason,
        vRtrIsisSpfType,
        vRtrIsisSummRowStatus,
        vRtrIsisSummLevel,
        vRtrIsisInetRouteLevel,
        vRtrIsisInetRouteSpfRunNumber,
        vRtrIsisInetRouteMetric,
        vRtrIsisInetRouteType,
        vRtrIsisInetRouteNHopSysID,
        vRtrIsisInetSummRowStatus,
        vRtrIsisInetSummLevel,
        vRtrIsisInetSummRouteTag,
        vRtrIsisInetMtRouteLevel,
        vRtrIsisInetMtRouteSpfRunNumber,
        vRtrIsisInetMtRouteMetric,
        vRtrIsisInetMtRouteType,
        vRtrIsisInetMtRouteNHopSysID,
        vRtrIsisInetMtRouteTag,
        vRtrIsisInetMtRouteBkupFlags,
        vRtrIsisInetMtRouteBkupNextHopTy,
        vRtrIsisInetMtRouteBkupNextHop,
        vRtrIsisInetMtRouteBkupMetric,
        vRtrIsisRouteNextHopType,
        vRtrIsisNextHopOwner,
        vRtrIsisRouteNHOwnerAuxInfo,
        vRtrIsisRouteBkupNHType,
        vRtrIsisRouteBkupNHOwner,
        vRtrIsisRouteBkupNHOwnAxInfo,
        vRtrIsisMtPathMetric,
        vRtrIsisMtPathSNPA,
        vRtrIsisMtPathLfaIfIndex,
        vRtrIsisMtPathLfaNHop,
        vRtrIsisMtPathLfaMetric,
        vRtrIsisMtPathLfaType,
        vRtrIsisMtPathRouteType,
        vRtrIsisLfaNodesCovered,
        vRtrIsisLfaTotalNodes,
        vRtrIsisLfaNodeCoverage,
        vRtrIsisLfaIpv4NodesCovered,
        vRtrIsisLfaIpv4TotalNodes,
        vRtrIsisLfaIpv4Coverage,
        vRtrIsisLfaIpv6NodesCovered,
        vRtrIsisLfaIpv6TotalNodes,
        vRtrIsisLfaIpv6Coverage,
        vRtrIsisIfRowStatus,
        vRtrIsisIfLastChangeTime,
        vRtrIsisIfAdminState,
        vRtrIsisIfOperState,
        vRtrIsisIfCsnpInterval,
        vRtrIsisIfHelloAuthKey,
        vRtrIsisIfHelloAuthType,
        vRtrIsisIfLspPacingInterval,
        vRtrIsisIfCircIndex,
        vRtrIsisIfRetransmitInterval,
        vRtrIsisIfTypeDefault,
        vRtrIsisIfEnableBfd,
        vRtrIsisIfIPv6Unicast,
        vRtrIsisIfTeMetric,
        vRtrIsisIfTeState,
        vRtrIsisIfAdminGroup,
        vRtrIsisIfLdpSyncState,
        vRtrIsisIfLdpSyncMaxMetric,
        vRtrIsisIfLdpSyncTimerState,
        vRtrIsisIfLdpSyncTimeLeft,
        vRtrIsisIfRouteTag,
        vRtrIsisIfIpv6EnableBfd,
        vRtrIsisIfHelloAuthentication,
        vRtrIsisIfLoopfreeAltExclude,
        vRtrIsisIfOperType,
        vRtrIsisIfIPv4Mcast,
        vRtrIsisIfIPv6Mcast,
        vRtrIsisIfBerState,
        vRtrIsisIfLevelLastChangeTime,
        vRtrIsisIfLevelHelloAuthKey,
        vRtrIsisIfLevelHelloAuthType,
        vRtrIsisIfLevelPassive,
        vRtrIsisIfLevelTeMetric,
        vRtrIsisIfLevelNumAdjacencies,
        vRtrIsisIfLevelISPriority,
        vRtrIsisIfLevelHelloTimer,
        vRtrIsisIfLevelAdminMetric,
        vRtrIsisIfLevelOperMetric,
        vRtrIsisIfLvlIPv6UcastAdmMet,
        vRtrIsisIfLvlIPv6UcastOperMet,
        vRtrIsisIfLvlIPv4McastAdmMetric,
        vRtrIsisIfLvlIPv6McastAdmMetric,
        vRtrIsisIfLevelLinkGroupName,
        vRtrIsisIfLevelSdOffset,
        vRtrIsisIfLevelSfOffset,
        vRtrIsisIfLvlIPv4McastOperMetric,
        vRtrIsisIfLvlIPv6McastOperMetric,
        vRtrIsisISAdjExpiresIn,
        vRtrIsisISAdjCircLevel,
        vRtrIsisISAdjNeighborIP,
        vRtrIsisISAdjRestartSupport,
        vRtrIsisISAdjRestartStatus,
        vRtrIsisISAdjRestartSupressed,
        vRtrIsisISAdjNumRestarts,
        vRtrIsisISAdjLastRestartTime,
        vRtrIsisISAdjNeighborIPv6Type,
        vRtrIsisISAdjNeighborIpv6,
        vRtrIsisISAdjMtEnabled,
        vRtrIsisISAdjMtId0,
        vRtrIsisISAdjMtId2,
        vRtrIsisISAdjMtId3,
        vRtrIsisISAdjMtId4
    }
    STATUS      current
    DESCRIPTION
        "The group of objects in TIMETRA-ISIS-MIB which are obsoleted in Nokia
         SROS 12.0 series systems."
    ::= { vRtrIsisMIBGroups 56 }

vRtrIsisLgV12v0Group             OBJECT-GROUP
    OBJECTS     {
        vRtrIsisLgRowStatus,
        vRtrIsisLgRowLastChanged,
        vRtrIsisLgTableLastChanged,
        vRtrIsisLgLevelOperMembers,
        vRtrIsisLgLevelRevertMembers,
        vRtrIsisLgLevelIPv4UcastMetric,
        vRtrIsisLgLevelIPv6UcastMetric,
        vRtrIsisLgLevelIPv4McastMetric,
        vRtrIsisLgLevelIPv6McastMetric,
        vRtrIsisLgLevelTableLastChanged,
        vRtrIsisLgLevelLastChanged,
        vRtrIsisLgLevelOpOperMembers,
        vRtrIsisLgLevelOperRevertMembers,
        vRtrIsisLgLevelOperMembersCount,
        vRtrIsisLgLevelOperActiveMembers,
        vRtrIsisLgLevelOperState,
        vRtrIsisLgLevelMembersOperState,
        vRtrIsisLgDescription
    }
    STATUS      current
    DESCRIPTION
        "The group of objects supporting management of ISIS system objects on
         Nokia 12.0 release of SROS series systems."
    ::= { vRtrIsisMIBGroups 57 }

vRtrIsisMIBDCConformances        OBJECT IDENTIFIER ::= { vRtrIsisMIBConformance 3 }

vRtrIsisDCMIBGroups              OBJECT IDENTIFIER ::= { vRtrIsisMIBConformance 4 }

vRtrIsisNotifyPrefix             OBJECT IDENTIFIER ::= { tmnxSRNotifyPrefix 10 }

vRtrIsisNotifications            OBJECT IDENTIFIER ::= { vRtrIsisNotifyPrefix 0 }

vRtrIsisDatabaseOverload         NOTIFICATION-TYPE
    OBJECTS     {
        vRtrIsisSystemLevel,
        isisSysL1State,
        isisSysL2State
    }
    STATUS      obsolete
    DESCRIPTION
        "This notification is obsoleted in release 12.0. It is replaced with
         tmnxIsisDatabaseOverload."
    ::= { vRtrIsisNotifications 1 }

vRtrIsisManualAddressDrops       NOTIFICATION-TYPE
    OBJECTS     {
        isisManAreaAddrExistState
    }
    STATUS      obsolete
    DESCRIPTION
        "This notification is obsoleted in release 12.0. It is replaced with
         tmnxIsisManualAddressDrops."
    ::= { vRtrIsisNotifications 2 }

vRtrIsisCorruptedLSPDetected     NOTIFICATION-TYPE
    OBJECTS     {
        vRtrIsisSystemLevel,
        vRtrIsisTrapLSPID
    }
    STATUS      obsolete
    DESCRIPTION
        "This notification is obsoleted in release 12.0. It is replaced with
         tmnxIsisCorruptedLSPDetected."
    ::= { vRtrIsisNotifications 3 }

vRtrIsisMaxSeqExceedAttempt      NOTIFICATION-TYPE
    OBJECTS     {
        vRtrIsisSystemLevel,
        vRtrIsisTrapLSPID
    }
    STATUS      obsolete
    DESCRIPTION
        "This notification is obsoleted in release 12.0. It is replaced with
         tmnxIsisMaxSeqExceedAttempt."
    ::= { vRtrIsisNotifications 4 }

vRtrIsisIDLenMismatch            NOTIFICATION-TYPE
    OBJECTS     {
        vRtrIsisFieldLen,
        vRtrIfIndex,
        vRtrIsisPDUFragment
    }
    STATUS      obsolete
    DESCRIPTION
        "This notification is obsoleted in release 12.0. It is replaced with
         tmnxIsisIDLenMismatch."
    ::= { vRtrIsisNotifications 5 }

vRtrIsisMaxAreaAddrsMismatch     NOTIFICATION-TYPE
    OBJECTS     {
        vRtrIsisMaxAreaAddress,
        vRtrIfIndex,
        vRtrIsisPDUFragment
    }
    STATUS      obsolete
    DESCRIPTION
        "This notification is obsoleted in release 12.0. It is replaced with
         tmnxIsisMaxAreaAddrsMismatch."
    ::= { vRtrIsisNotifications 6 }

vRtrIsisOwnLSPPurge              NOTIFICATION-TYPE
    OBJECTS     {
        vRtrIfIndex,
        vRtrIsisTrapLSPID,
        vRtrIsisSystemLevel
    }
    STATUS      obsolete
    DESCRIPTION
        "This notification is obsoleted in release 12.0. It is replaced with
         tmnxIsisOwnLSPPurge."
    ::= { vRtrIsisNotifications 7 }

vRtrIsisSequenceNumberSkip       NOTIFICATION-TYPE
    OBJECTS     {
        vRtrIsisTrapLSPID,
        vRtrIfIndex,
        vRtrIsisSystemLevel
    }
    STATUS      obsolete
    DESCRIPTION
        "This notification is obsoleted in release 12.0. It is replaced with
         tmnxIsisSequenceNumberSkip."
    ::= { vRtrIsisNotifications 8 }

vRtrIsisAutTypeFail              NOTIFICATION-TYPE
    OBJECTS     {
        vRtrIsisSystemLevel,
        vRtrIsisPDUFragment,
        vRtrIfIndex
    }
    STATUS      obsolete
    DESCRIPTION
        "This notification is obsoleted in release 12.0. It is replaced with
         tmnxIsisAutTypeFail."
    ::= { vRtrIsisNotifications 9 }

vRtrIsisAuthFail                 NOTIFICATION-TYPE
    OBJECTS     {
        vRtrIsisSystemLevel,
        vRtrIsisPDUFragment,
        vRtrIfIndex
    }
    STATUS      obsolete
    DESCRIPTION
        "This notification is obsoleted in release 12.0. It is replaced with
         tmnxIsisAuthFail."
    ::= { vRtrIsisNotifications 10 }

vRtrIsisVersionSkew              NOTIFICATION-TYPE
    OBJECTS     {
        vRtrIsisProtocolVersion,
        vRtrIsisSystemLevel,
        vRtrIsisPDUFragment,
        vRtrIfIndex
    }
    STATUS      obsolete
    DESCRIPTION
        "This notification is obsoleted in release 12.0. It is replaced with
         tmnxIsisVersionSkew."
    ::= { vRtrIsisNotifications 11 }

vRtrIsisAreaMismatch             NOTIFICATION-TYPE
    OBJECTS     {
        vRtrIsisLSPSize,
        vRtrIsisSystemLevel,
        vRtrIfIndex,
        vRtrIsisPDUFragment
    }
    STATUS      obsolete
    DESCRIPTION
        "This notification is obsoleted in release 12.0. It is replaced with
         tmnxIsisAreaMismatch."
    ::= { vRtrIsisNotifications 12 }

vRtrIsisRejectedAdjacency        NOTIFICATION-TYPE
    OBJECTS     {
        vRtrIsisSystemLevel,
        vRtrIfIndex
    }
    STATUS      obsolete
    DESCRIPTION
        "This notification is obsoleted in release 12.0. It is replaced with
         tmnxIsisRejectedAdjacency."
    ::= { vRtrIsisNotifications 13 }

vRtrIsisLSPTooLargeToPropagate   NOTIFICATION-TYPE
    OBJECTS     {
        vRtrIsisLSPSize,
        vRtrIsisSystemLevel,
        vRtrIsisTrapLSPID,
        vRtrIfIndex
    }
    STATUS      obsolete
    DESCRIPTION
        "This notification is obsoleted in release 12.0. It is replaced with
         tmnxIsisLSPTooLargeToPropagate."
    ::= { vRtrIsisNotifications 14 }

vRtrIsisOrigLSPBufSizeMismatch   NOTIFICATION-TYPE
    OBJECTS     {
        vRtrIsisOriginatingBufferSize,
        vRtrIsisSystemLevel,
        vRtrIsisTrapLSPID,
        vRtrIfIndex
    }
    STATUS      obsolete
    DESCRIPTION
        "This notification is obsoleted in release 12.0. It is replaced with
         tmnxIsisOrigLSPBufSizeMismatch."
    ::= { vRtrIsisNotifications 15 }

vRtrIsisProtoSuppMismatch        NOTIFICATION-TYPE
    OBJECTS     {
        vRtrIsisProtocolsSupported,
        vRtrIsisSystemLevel,
        vRtrIsisTrapLSPID,
        vRtrIfIndex
    }
    STATUS      obsolete
    DESCRIPTION
        "This notification is obsoleted in release 12.0. It is replaced with
         tmnxIsisProtoSuppMismatch."
    ::= { vRtrIsisNotifications 16 }

vRtrIsisAdjacencyChange          NOTIFICATION-TYPE
    OBJECTS     {
        vRtrIsisSystemLevel,
        vRtrIfIndex,
        vRtrIsisTrapLSPID,
        isisISAdjState
    }
    STATUS      obsolete
    DESCRIPTION
        "This notification is obsoleted in release 12.0. It is replaced with
         tmnxIsisAdjacencyChange."
    ::= { vRtrIsisNotifications 17 }

vRtrIsisCircIdExhausted          NOTIFICATION-TYPE
    OBJECTS     {
        vRtrIfIndex,
        vRtrIsisSystemLevel
    }
    STATUS      obsolete
    DESCRIPTION
        "This notification is obsoleted in release 12.0. It is replaced with
         tmnxIsisCircIdExhausted."
    ::= { vRtrIsisNotifications 18 }

vRtrIsisAdjRestartStatusChange   NOTIFICATION-TYPE
    OBJECTS     {
        vRtrIsisSystemLevel,
        vRtrIfIndex,
        vRtrIsisISAdjRestartStatus
    }
    STATUS      obsolete
    DESCRIPTION
        "This notification is obsoleted in release 12.0. It is replaced with
         tmnxIsisAdjRestartStatusChange."
    ::= { vRtrIsisNotifications 19 }

vRtrIsisLdpSyncTimerStarted      NOTIFICATION-TYPE
    OBJECTS     {
        vRtrIfIndex,
        vRtrIsisIfLdpSyncTimerState
    }
    STATUS      obsolete
    DESCRIPTION
        "This notification is obsoleted in release 12.0. It is replaced with
         tmnxIsisLdpSyncTimerStarted."
    ::= { vRtrIsisNotifications 20 }

vRtrIsisLdpSyncExit              NOTIFICATION-TYPE
    OBJECTS     {
        vRtrIfIndex,
        vRtrIsisIfLdpSyncTimerState
    }
    STATUS      obsolete
    DESCRIPTION
        "This notification is obsoleted in release 12.0. It is replaced with
         tmnxIsisLdpSyncExit."
    ::= { vRtrIsisNotifications 21 }

vRtrIsisExportLimitReached       NOTIFICATION-TYPE
    OBJECTS     {
        vRtrIsisSystemLevel,
        vRtrIsisExportLimit
    }
    STATUS      obsolete
    DESCRIPTION
        "This notification is obsoleted in release 12.0. It is replaced with
         tmnxIsisExportLimitReached."
    ::= { vRtrIsisNotifications 22 }

vRtrIsisExportLimitWarning       NOTIFICATION-TYPE
    OBJECTS     {
        vRtrIsisSystemLevel,
        vRtrIsisExportLimit,
        vRtrIsisExportLimitLogPercent
    }
    STATUS      obsolete
    DESCRIPTION
        "This notification is obsoleted in release 12.0. It is replaced with
         tmnxIsisExportLimitWarning."
    ::= { vRtrIsisNotifications 23 }

vRtrIsisRoutesExpLmtDropped      NOTIFICATION-TYPE
    OBJECTS     {
        vRtrIsisSystemLevel,
        vRtrIsisExportLimit
    }
    STATUS      obsolete
    DESCRIPTION
        "This notification is obsoleted in release 12.0. It is replaced with
         tmnxIsisRoutesExpLmtDropped."
    ::= { vRtrIsisNotifications 24 }

vRtrIsisSpbNbrMultAdjExists      NOTIFICATION-TYPE
    OBJECTS     {
        vRtrIfIndex,
        vRtrIsisSystemLevel,
        vRtrIsisNbrSysId
    }
    STATUS      current
    DESCRIPTION
        "[CAUSE] A vRtrIsisSpbNbrMultAdjExists notification is sent when IS-IS
         SPB instance detects a neighbor to which it already has a direct
         adjacency on another interface.

         [EFFECT] During SPF IS-IS SPB instance will have incorrect neighbor
         information and hence path computations will be incorrect.

         [RECOVERY] Check number of links to neighbor to make sure there is
         only one link."
    ::= { vRtrIsisNotifications 25 }

vRtrIsisSpbNbrMultAdjExistsClear NOTIFICATION-TYPE
    OBJECTS     {
        vRtrIfIndex,
        vRtrIsisSystemLevel,
        vRtrIsisNbrSysId
    }
    STATUS      current
    DESCRIPTION
        "[CAUSE] A vRtrIsisSpbNbrMultAdjExistsClear notification is sent when
         an IS-IS SPB instance clears the condition raised by
         vRtrIsisSpbNbrMultAdjExists notification.

         [EFFECT] During SPF IS-IS SPB instance will have correct neighbor
         information and hence path computations will be correct.

         [RECOVERY] None required."
    ::= { vRtrIsisNotifications 26 }

vRtrSpbEctFidCfgChg              NOTIFICATION-TYPE
    OBJECTS     {
        vRtrSpbEctFidStart,
        vRtrSpbEctFidEnd,
        vRtrSpbEctFidAlgorithm
    }
    STATUS      current
    DESCRIPTION
        "[CAUSE] A vRtrSpbEctFidCfgChg notification is sent when a
         configuration change is made to vRtrSpbEctFidTable affecting
         forwarding database identifiers in the range from vRtrSpbEctFidStart
         to vRtrSpbEctFidEnd.

         [EFFECT] There are changes in the vRtrSpbEctFidTable which may be
         out-of-sync with management application.

         [RECOVERY] Management application may need to synchronize with changes
         in the vRtrSpbEctFidTable."
    ::= { vRtrIsisNotifications 27 }

vRtrIsisFailureDisabled          NOTIFICATION-TYPE
    OBJECTS     {
        vRtrIsisFailureReasonCode
    }
    STATUS      obsolete
    DESCRIPTION
        "[CAUSE] A vRtrIsisFailureDisabled notification is generated when ISIS
         is operationally brought down. Reason for the failure is indicated by
         vRtrIsisFailureReasonCode.

         [EFFECT] ISIS is now operationally down.

         [RECOVERY] ISIS will auto restart."
    ::= { vRtrIsisNotifications 28 }

END

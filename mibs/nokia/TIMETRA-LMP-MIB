TIMETRA-LMP-MIB DEFINITIONS ::= BEGIN

IMPORTS
    InetAddress, InetAddressType
                                                         FROM INET-ADDRESS-MIB
    MODULE-COMPLIANCE, NOTIFICATION-GROUP,
    OBJECT-GROUP
                                                         FROM SNMPv2-CONF
    Counter32, MODULE-IDENTITY,
    NOTIFICATION-TYPE, OBJECT-TYPE,
    Unsigned32
                                                         FROM SNMPv2-SMI
    RowStatus, TimeStamp, TruthValue
                                                         FROM SNMPv2-TC
    timetraSRMIBModules, tmnxSRConfs,
    tmnxSRNotifyPrefix, tmnxSRObjs
                                                         FROM TIMETRA-GLOBAL-MIB
    TNamedItemOrEmpty, TmnxAdminState,
    TmnxPortID, TmnxVRtrID
                                                         FROM TIMETRA-TC-MIB
    vRtrID
                                                         FROM TIMETRA-VRTR-MIB
    ;

timetraLmpMIBModule              MODULE-IDENTITY
    LAST-UPDATED "201701010000Z"
    ORGANIZATION "Nokia"
    CONTACT-INFO
        "Nokia SROS Support
         Web: http://www.nokia.com"
    DESCRIPTION
        "This document is the SNMP MIB module to manage and provision the Link
         Management Protocol (LMP) components of the Nokia SROS device.

         Copyright (c) 2014-2018 Nokia. All rights reserved. Reproduction of
         this document is authorized on the condition that the foregoing
         copyright notice is included.

         This SNMP MIB module (Specification) embodies Nokia's
         proprietary intellectual property.  Nokia retains all
         title and ownership in the Specification, including any
         revisions.

         Nokia grants all interested parties a non-exclusive license to use and
         distribute an unmodified copy of this Specification in connection with
         management of Nokia products, and without fee, provided this copyright
         notice and license appear on all copies.

         This Specification is supplied `as is', and Nokia makes no warranty,
         either express or implied, as to the use, operation, condition, or
         performance of the Specification."

    REVISION    "201701010000Z"
    DESCRIPTION
        "Rev 15.0              01 Jan 2017 00:00
         15.0 release of the TIMETRA-LMP-MIB."

    REVISION    "201404240000Z"
    DESCRIPTION
        "Rev 0.1               24 Apr 2014 00:00
         Initial version of the TIMETRA-LMP-MIB."

    ::= { timetraSRMIBModules 100 }

tmnxLmpObjs                      OBJECT IDENTIFIER ::= { tmnxSRObjs 100 }

tmnxLmpConfigTimeStamps          OBJECT IDENTIFIER ::= { tmnxLmpObjs 1 }

tmnxLmpVRtrTableLastChanged      OBJECT-TYPE
    SYNTAX      TimeStamp
    MAX-ACCESS  read-only
    STATUS      current
    DESCRIPTION
        "The value of tmnxLmpVRtrTableLastChanged indicates the time, since
         system startup, when tmnxLmpVRtrTable last changed configuration."
    ::= { tmnxLmpConfigTimeStamps 1 }

tmnxLmpVRtrPeerTableLastChanged  OBJECT-TYPE
    SYNTAX      TimeStamp
    MAX-ACCESS  read-only
    STATUS      current
    DESCRIPTION
        "The value of tmnxLmpVRtrPeerTableLastChanged indicates the time, since
         system startup, when tmnxLmpVRtrPeerTable last changed configuration."
    ::= { tmnxLmpConfigTimeStamps 2 }

tmnxLmpVRtrCcTableLastChanged    OBJECT-TYPE
    SYNTAX      TimeStamp
    MAX-ACCESS  read-only
    STATUS      current
    DESCRIPTION
        "The value of tmnxLmpVRtrCcTableLastChanged indicates the time, since
         system startup, when tmnxLmpVRtrControlChannelTable last changed
         configuration."
    ::= { tmnxLmpConfigTimeStamps 3 }

tmnxLmpVRtrTeLinkTableLastChange OBJECT-TYPE
    SYNTAX      TimeStamp
    MAX-ACCESS  read-only
    STATUS      current
    DESCRIPTION
        "The value of tmnxLmpVRtrTeLinkTableLastChange indicates the time,
         since system startup, when tmnxLmpVRtrTeLinkTable last changed
         configuration."
    ::= { tmnxLmpConfigTimeStamps 4 }

tmnxLmpVRtrDbLinkTableLastChange OBJECT-TYPE
    SYNTAX      TimeStamp
    MAX-ACCESS  read-only
    STATUS      current
    DESCRIPTION
        "The value of tmnxLmpVRtrDbLinkTableLastChange indicates the time,
         since system startup, when tmnxLmpVRtrDbLinkTable last changed
         configuration."
    ::= { tmnxLmpConfigTimeStamps 5 }

tmnxLmpConfigurations            OBJECT IDENTIFIER ::= { tmnxLmpObjs 2 }

tmnxLmpVRtrTable                 OBJECT-TYPE
    SYNTAX      SEQUENCE OF TmnxLmpVRtrEntry
    MAX-ACCESS  not-accessible
    STATUS      current
    DESCRIPTION
        "The tmnxLmpVRtrTable contains the Link Management Protocol (LMP)
         configuration information for the virtual router instances."
    ::= { tmnxLmpConfigurations 1 }

tmnxLmpVRtrEntry                 OBJECT-TYPE
    SYNTAX      TmnxLmpVRtrEntry
    MAX-ACCESS  not-accessible
    STATUS      current
    DESCRIPTION
        "The tmnxLmpVRtrEntry consists of the LMP configurable objects for a
         virtual router instance."
    INDEX       { vRtrID }
    ::= { tmnxLmpVRtrTable 1 }

TmnxLmpVRtrEntry                 ::= SEQUENCE
{
    tmnxLmpVRtrRowStatus             RowStatus,
    tmnxLmpVRtrLastChanged           TimeStamp,
    tmnxLmpVRtrAdminState            TmnxAdminState,
    tmnxLmpVRtrOperState             INTEGER,
    tmnxLmpVRtrGmplsLoopbackAddrType InetAddressType,
    tmnxLmpVRtrGmplsLoopbackAddress  InetAddress
}

tmnxLmpVRtrRowStatus             OBJECT-TYPE
    SYNTAX      RowStatus
    MAX-ACCESS  read-create
    STATUS      current
    DESCRIPTION
        "The value of tmnxLmpVRtrRowStatus specifies the row status. It allows
         the creation and deletion of the LMP on the virtual router instance."
    ::= { tmnxLmpVRtrEntry 1 }

tmnxLmpVRtrLastChanged           OBJECT-TYPE
    SYNTAX      TimeStamp
    MAX-ACCESS  read-only
    STATUS      current
    DESCRIPTION
        "The value of tmnxLmpVRtrLastChanged indicates the time, since system
         startup, that the configuration of the LMP on the virtual router
         instance was created or modified."
    ::= { tmnxLmpVRtrEntry 2 }

tmnxLmpVRtrAdminState            OBJECT-TYPE
    SYNTAX      TmnxAdminState
    MAX-ACCESS  read-create
    STATUS      current
    DESCRIPTION
        "The value of tmnxLmpVRtrAdminState specifies the administrative state
         of the LMP on the virtual router instance."
    DEFVAL      { outOfService }
    ::= { tmnxLmpVRtrEntry 3 }

tmnxLmpVRtrOperState             OBJECT-TYPE
    SYNTAX      INTEGER {
        up   (1),
        down (2)
    }
    MAX-ACCESS  read-only
    STATUS      current
    DESCRIPTION
        "The value of tmnxLmpVRtrOperState indicates the operational state of
         the LMP on the virtual router instance."
    ::= { tmnxLmpVRtrEntry 4 }

tmnxLmpVRtrGmplsLoopbackAddrType OBJECT-TYPE
    SYNTAX      InetAddressType
    MAX-ACCESS  read-create
    STATUS      current
    DESCRIPTION
        "The value of tmnxLmpVRtrGmplsLoopbackAddrType specifies the address
         type of tmnxLmpVRtrGmplsLoopbackAddress."
    DEFVAL      { unknown }
    ::= { tmnxLmpVRtrEntry 5 }

tmnxLmpVRtrGmplsLoopbackAddress  OBJECT-TYPE
    SYNTAX      InetAddress (SIZE (0|4|16))
    MAX-ACCESS  read-create
    STATUS      current
    DESCRIPTION
        "The value of tmnxLmpVRtrGmplsLoopbackAddress specifies the GMPLS
         loopback address for the virtual router instance."
    DEFVAL      { ''H }
    ::= { tmnxLmpVRtrEntry 6 }

tmnxLmpVRtrPeerTable             OBJECT-TYPE
    SYNTAX      SEQUENCE OF TmnxLmpVRtrPeerEntry
    MAX-ACCESS  not-accessible
    STATUS      current
    DESCRIPTION
        "The tmnxLmpVRtrPeerTable contains the peer node(s) to which control
         channels may be established."
    REFERENCE
        "Link Management Protocol, RFC 4204."
    ::= { tmnxLmpConfigurations 2 }

tmnxLmpVRtrPeerEntry             OBJECT-TYPE
    SYNTAX      TmnxLmpVRtrPeerEntry
    MAX-ACCESS  not-accessible
    STATUS      current
    DESCRIPTION
        "The tmnxLmpVRtrPeerEntry consists of every pair of nodes that can
         establish control channels on a given virtual router instance."
    INDEX       {
        vRtrID,
        tmnxLmpVRtrPeerNodeId
    }
    ::= { tmnxLmpVRtrPeerTable 1 }

TmnxLmpVRtrPeerEntry             ::= SEQUENCE
{
    tmnxLmpVRtrPeerNodeId            Unsigned32,
    tmnxLmpVRtrPeerRowStatus         RowStatus,
    tmnxLmpVRtrPeerLastChanged       TimeStamp,
    tmnxLmpVRtrPeerAdminState        TmnxAdminState,
    tmnxLmpVRtrPeerOperState         INTEGER,
    tmnxLmpVRtrPeerLoopbackAddrType  InetAddressType,
    tmnxLmpVRtrPeerLoopbackAddress   InetAddress,
    tmnxLmpVRtrPeerRetransmitIntvl   Unsigned32,
    tmnxLmpVRtrPeerRetryLimit        Unsigned32,
    tmnxLmpVRtrPeerRetransmitDelta   Unsigned32,
    tmnxLmpVRtrPeerCcVRtrId          TmnxVRtrID,
    tmnxLmpVRtrPeerGmplsLpbkAddrType InetAddressType,
    tmnxLmpVRtrPeerGmplsLpbkAddress  InetAddress
}

tmnxLmpVRtrPeerNodeId            OBJECT-TYPE
    SYNTAX      Unsigned32 (1..4294967295)
    MAX-ACCESS  not-accessible
    STATUS      current
    DESCRIPTION
        "The value of tmnxLmpVRtrPeerNodeId specifies the unique node
         identifier of this remote node on the given virtual router instance."
    ::= { tmnxLmpVRtrPeerEntry 1 }

tmnxLmpVRtrPeerRowStatus         OBJECT-TYPE
    SYNTAX      RowStatus
    MAX-ACCESS  read-create
    STATUS      current
    DESCRIPTION
        "The value of tmnxLmpVRtrPeerRowStatus specifies the row status. It
         allows the creation and deletion of this remote node on the given
         virtual router instance."
    ::= { tmnxLmpVRtrPeerEntry 2 }

tmnxLmpVRtrPeerLastChanged       OBJECT-TYPE
    SYNTAX      TimeStamp
    MAX-ACCESS  read-only
    STATUS      current
    DESCRIPTION
        "The value of tmnxLmpVRtrPeerLastChanged indicates the time, since
         system startup, that the configuration of this remote node was created
         or modified."
    ::= { tmnxLmpVRtrPeerEntry 3 }

tmnxLmpVRtrPeerAdminState        OBJECT-TYPE
    SYNTAX      TmnxAdminState
    MAX-ACCESS  read-create
    STATUS      current
    DESCRIPTION
        "The value of tmnxLmpVRtrPeerAdminState specifies the administrative
         state of LMP on this remote node."
    DEFVAL      { outOfService }
    ::= { tmnxLmpVRtrPeerEntry 4 }

tmnxLmpVRtrPeerOperState         OBJECT-TYPE
    SYNTAX      INTEGER {
        up   (1),
        down (2)
    }
    MAX-ACCESS  read-only
    STATUS      current
    DESCRIPTION
        "The value of tmnxLmpVRtrPeerOperState indicates the operational state
         of LMP on this remote node."
    ::= { tmnxLmpVRtrPeerEntry 5 }

tmnxLmpVRtrPeerLoopbackAddrType  OBJECT-TYPE
    SYNTAX      InetAddressType
    MAX-ACCESS  read-create
    STATUS      current
    DESCRIPTION
        "The value of tmnxLmpVRtrPeerLoopbackAddrType specifies the address
         type of tmnxLmpVRtrPeerLoopbackAddress."
    DEFVAL      { unknown }
    ::= { tmnxLmpVRtrPeerEntry 6 }

tmnxLmpVRtrPeerLoopbackAddress   OBJECT-TYPE
    SYNTAX      InetAddress (SIZE (0|4|16))
    MAX-ACCESS  read-create
    STATUS      current
    DESCRIPTION
        "The value of tmnxLmpVRtrPeerLoopbackAddress specifies the loopback
         address for this remote node."
    DEFVAL      { ''H }
    ::= { tmnxLmpVRtrPeerEntry 7 }

tmnxLmpVRtrPeerRetransmitIntvl   OBJECT-TYPE
    SYNTAX      Unsigned32 (10..60000)
    UNITS       "milliseconds"
    MAX-ACCESS  read-create
    STATUS      current
    DESCRIPTION
        "The value of tmnxLmpVRtrPeerRetransmitIntvl specifies the initial
         retransmission interval that is used for the retransmission of
         messages that require acknowledgement. This object, along with
         tmnxLmpVRtrPeerRetryLimit, is used to implement the
         congestion-handling mechanism defined in Section 10 of the Link
         Management Protocol specification, which is based on RFC 2914."
    REFERENCE
        "Link Management Protocol, RFC 4204.
         Congestion Control Principles, RFC 2914."
    DEFVAL      { 500 }
    ::= { tmnxLmpVRtrPeerEntry 8 }

tmnxLmpVRtrPeerRetryLimit        OBJECT-TYPE
    SYNTAX      Unsigned32
    MAX-ACCESS  read-create
    STATUS      current
    DESCRIPTION
        "The value of tmnxLmpVRtrPeerRetryLimit specifies the maximum number of
         times a message is transmitted without being acknowledged. A value of
         0 is used to indicate that a node should never stop retransmission.
         This object, along with tmnxLmpVRtrPeerRetransmitIntvl, is used to
         implement the congestion-handling mechanism as defined in Section 10
         of the Link Management Protocol specification, which is based on RFC
         2914."
    REFERENCE
        "Link Management Protocol, RFC 4204.
         Congestion Control Principles, RFC 2914."
    DEFVAL      { 0 }
    ::= { tmnxLmpVRtrPeerEntry 9 }

tmnxLmpVRtrPeerRetransmitDelta   OBJECT-TYPE
    SYNTAX      Unsigned32
    MAX-ACCESS  read-only
    STATUS      current
    DESCRIPTION
        "The value of tmnxLmpVRtrPeerRetransmitDelta indicates the speed with
         which the sender increases the retransmission interval, as explained
         in Section 10 of the Link Management Protocol specification, which is
         based on RFC 2914. The ratio of two successive retransmission
         intervals is (1 + Delta)."
    REFERENCE
        "Link Management Protocol, RFC 4204.
         Congestion Control Principles, RFC 2914."
    ::= { tmnxLmpVRtrPeerEntry 10 }

tmnxLmpVRtrPeerCcVRtrId          OBJECT-TYPE
    SYNTAX      TmnxVRtrID
    MAX-ACCESS  read-create
    STATUS      current
    DESCRIPTION
        "The value of tmnxLmpVRtrPeerCcVRtrId specifies the virtual router
         instance used by the peer's control channels.

         This object must be set in the same SNMP set PDU as
         tmnxLmpVRtrPeerGmplsLpbkAddress, and tmnxLmpVRtrPeerGmplsLpbkAddrType."
    DEFVAL      { 1 }
    ::= { tmnxLmpVRtrPeerEntry 11 }

tmnxLmpVRtrPeerGmplsLpbkAddrType OBJECT-TYPE
    SYNTAX      InetAddressType
    MAX-ACCESS  read-create
    STATUS      current
    DESCRIPTION
        "The value of tmnxLmpVRtrPeerGmplsLpbkAddrType specifies the address
         type of tmnxLmpVRtrPeerGmplsLpbkAddress.

         This object must be set in the same SNMP set PDU as
         tmnxLmpVRtrPeerGmplsLpbkAddress, and tmnxLmpVRtrPeerCcVRtrId."
    DEFVAL      { unknown }
    ::= { tmnxLmpVRtrPeerEntry 12 }

tmnxLmpVRtrPeerGmplsLpbkAddress  OBJECT-TYPE
    SYNTAX      InetAddress (SIZE (0|4|16))
    MAX-ACCESS  read-create
    STATUS      current
    DESCRIPTION
        "The value of tmnxLmpVRtrPeerGmplsLpbkAddress specifies the GMPLS
         loopback address used be the peer.

         This object is only valid when the value of tmnxLmpVRtrPeerCcVRtrId is
         not 1.

         This object must be set in the same SNMP set PDU as
         tmnxLmpVRtrPeerGmplsLpbkAddrType, and tmnxLmpVRtrPeerCcVRtrId."
    DEFVAL      { ''H }
    ::= { tmnxLmpVRtrPeerEntry 13 }

tmnxLmpVRtrControlChannelTable   OBJECT-TYPE
    SYNTAX      SEQUENCE OF TmnxLmpVRtrControlChannelEntry
    MAX-ACCESS  not-accessible
    STATUS      current
    DESCRIPTION
        "The tmnxLmpVRtrControlChannelTable contains LMP control channel
         information."
    REFERENCE
        "Link Management Protocol, RFC 4204."
    ::= { tmnxLmpConfigurations 3 }

tmnxLmpVRtrControlChannelEntry   OBJECT-TYPE
    SYNTAX      TmnxLmpVRtrControlChannelEntry
    MAX-ACCESS  not-accessible
    STATUS      current
    DESCRIPTION
        "The tmnxLmpVRtrControlChannelEntry consists of the configurable
         objects for a control channel on a given peer and virtual router
         instance."
    INDEX       {
        vRtrID,
        tmnxLmpVRtrPeerNodeId,
        tmnxLmpVRtrCcId
    }
    ::= { tmnxLmpVRtrControlChannelTable 1 }

TmnxLmpVRtrControlChannelEntry   ::= SEQUENCE
{
    tmnxLmpVRtrCcId                  Unsigned32,
    tmnxLmpVRtrCcRowStatus           RowStatus,
    tmnxLmpVRtrCcLastChanged         TimeStamp,
    tmnxLmpVRtrCcAdminState          TmnxAdminState,
    tmnxLmpVRtrCcOperState           INTEGER,
    tmnxLmpVRtrCcRemoteId            Unsigned32,
    tmnxLmpVRtrCcPeerIfAddressType   InetAddressType,
    tmnxLmpVRtrCcPeerIfAddress       InetAddress,
    tmnxLmpVRtrCcSetupRole           INTEGER,
    tmnxLmpVRtrCcHelloInterval       Unsigned32,
    tmnxLmpVRtrCcHelloIntvNeg        Unsigned32,
    tmnxLmpVRtrCcHelloDeadInterval   Unsigned32,
    tmnxLmpVRtrCcHelloDeadIntvNeg    Unsigned32,
    tmnxLmpVRtrCcTtl                 Unsigned32,
    tmnxLmpVRtrCcIsTunneled          TruthValue
}

tmnxLmpVRtrCcId                  OBJECT-TYPE
    SYNTAX      Unsigned32 (1..4294967295)
    MAX-ACCESS  not-accessible
    STATUS      current
    DESCRIPTION
        "The value of tmnxLmpVRtrCcId specifies a unique value which identifies
         the control channel on the given virtual router instance."
    ::= { tmnxLmpVRtrControlChannelEntry 1 }

tmnxLmpVRtrCcRowStatus           OBJECT-TYPE
    SYNTAX      RowStatus
    MAX-ACCESS  read-create
    STATUS      current
    DESCRIPTION
        "The value of tmnxLmpVRtrCcRowStatus specifies the row status. It
         allows the creation and deletion of this control channel on the given
         virtual router instance."
    ::= { tmnxLmpVRtrControlChannelEntry 2 }

tmnxLmpVRtrCcLastChanged         OBJECT-TYPE
    SYNTAX      TimeStamp
    MAX-ACCESS  read-only
    STATUS      current
    DESCRIPTION
        "The value of tmnxLmpVRtrCcLastChanged indicates the time, since system
         startup, that the configuration of this control channel was created or
         modified."
    ::= { tmnxLmpVRtrControlChannelEntry 3 }

tmnxLmpVRtrCcAdminState          OBJECT-TYPE
    SYNTAX      TmnxAdminState
    MAX-ACCESS  read-create
    STATUS      current
    DESCRIPTION
        "The value of tmnxLmpVRtrCcAdminState specifies the administrative
         state of this control channel."
    DEFVAL      { outOfService }
    ::= { tmnxLmpVRtrControlChannelEntry 4 }

tmnxLmpVRtrCcOperState           OBJECT-TYPE
    SYNTAX      INTEGER {
        up        (1),
        down      (2),
        configSnd (3),
        configRcv (4),
        active    (5),
        goingDown (6)
    }
    MAX-ACCESS  read-only
    STATUS      current
    DESCRIPTION
        "The value of tmnxLmpVRtrCcOperState indicates the operational state of
         this control channel."
    ::= { tmnxLmpVRtrControlChannelEntry 5 }

tmnxLmpVRtrCcRemoteId            OBJECT-TYPE
    SYNTAX      Unsigned32
    MAX-ACCESS  read-only
    STATUS      current
    DESCRIPTION
        "The value of tmnxLmpVRtrCcRemoteId indicates the remote control
         channel identifier. It is determined during the negotiation phase. A
         value of zero means that the remote control channel identifier has not
         yet been learned."
    ::= { tmnxLmpVRtrControlChannelEntry 6 }

tmnxLmpVRtrCcPeerIfAddressType   OBJECT-TYPE
    SYNTAX      InetAddressType
    MAX-ACCESS  read-create
    STATUS      current
    DESCRIPTION
        "The value of tmnxLmpVRtrCcPeerIfAddressType specifies the remote
         control channel IP address type. In point-to-point configuration, this
         value can be set to 'unknown (0)'."
    DEFVAL      { unknown }
    ::= { tmnxLmpVRtrControlChannelEntry 7 }

tmnxLmpVRtrCcPeerIfAddress       OBJECT-TYPE
    SYNTAX      InetAddress (SIZE (0|4|16))
    MAX-ACCESS  read-create
    STATUS      current
    DESCRIPTION
        "The value of tmnxLmpVRtrCcPeerIfAddress specifies the remote control
         channel Internet address for numbered control channel. The type of
         this address is determined by tmnxLmpVRtrCcPeerIfAddressType. The
         control channel must be numbered on non-point-to-point configuration.
         For point-to-point configuration, the remote control channel address
         can be of type 'unknown (0)', in which case this object must be a
         zero-length string. The tmnxLmpVRtrCcRemoteId object then identifies
         the unnumbered address. "
    DEFVAL      { ''H }
    ::= { tmnxLmpVRtrControlChannelEntry 8 }

tmnxLmpVRtrCcSetupRole           OBJECT-TYPE
    SYNTAX      INTEGER {
        active  (1),
        passive (2)
    }
    MAX-ACCESS  read-create
    STATUS      current
    DESCRIPTION
        "The value of tmnxLmpVRtrCcSetupRole specifies the role that this node
         should take during establishment of this control channel. An active
         node will initiate establishment. A passive node will wait for the
         remote node to initiate. A pair of nodes that both take the passive
         role will never establish communications."
    DEFVAL      { active }
    ::= { tmnxLmpVRtrControlChannelEntry 9 }

tmnxLmpVRtrCcHelloInterval       OBJECT-TYPE
    SYNTAX      Unsigned32 (1000..65535)
    UNITS       "milliseconds"
    MAX-ACCESS  read-create
    STATUS      current
    DESCRIPTION
        "The value of tmnxLmpVRtrCcHelloInterval specifies the value of the
         HelloInterval parameter."
    DEFVAL      { 1000 }
    ::= { tmnxLmpVRtrControlChannelEntry 10 }

tmnxLmpVRtrCcHelloIntvNeg        OBJECT-TYPE
    SYNTAX      Unsigned32
    UNITS       "milliseconds"
    MAX-ACCESS  read-only
    STATUS      current
    DESCRIPTION
        "The value of tmnxLmpVRtrCcHelloIntvNeg indicates the negotiated
         HelloInterval value when the control channel is active."
    ::= { tmnxLmpVRtrControlChannelEntry 11 }

tmnxLmpVRtrCcHelloDeadInterval   OBJECT-TYPE
    SYNTAX      Unsigned32 (3000..65535)
    UNITS       "milliseconds"
    MAX-ACCESS  read-create
    STATUS      current
    DESCRIPTION
        "The value of tmnxLmpVRtrCcHelloDeadInterval specifies the value of the
         HelloDeadInterval parameter."
    DEFVAL      { 4000 }
    ::= { tmnxLmpVRtrControlChannelEntry 12 }

tmnxLmpVRtrCcHelloDeadIntvNeg    OBJECT-TYPE
    SYNTAX      Unsigned32
    MAX-ACCESS  read-only
    STATUS      current
    DESCRIPTION
        "The value of tmnxLmpVRtrCcHelloDeadIntvNeg indicates the negotiated
         HelloDeadInterval value when the control channel is active."
    ::= { tmnxLmpVRtrControlChannelEntry 13 }

tmnxLmpVRtrCcTtl                 OBJECT-TYPE
    SYNTAX      Unsigned32 (1..255)
    UNITS       "hops"
    MAX-ACCESS  read-create
    STATUS      current
    DESCRIPTION
        "The value of tmnxLmpVRtrCcTtl specifies the Time-To-Live (TTL) value
         used in the LMP and RSVP control packet IP header."
    DEFVAL      { 1 }
    ::= { tmnxLmpVRtrControlChannelEntry 14 }

tmnxLmpVRtrCcIsTunneled          OBJECT-TYPE
    SYNTAX      TruthValue
    MAX-ACCESS  read-only
    STATUS      current
    DESCRIPTION
        "The value of tmnxLmpVRtrCcIsTunneled indicates whether the control
         channel on a given peer and virtual router instance is tunneled."
    ::= { tmnxLmpVRtrControlChannelEntry 15 }

tmnxLmpVRtrTeLinkTable           OBJECT-TYPE
    SYNTAX      SEQUENCE OF TmnxLmpVRtrTeLinkEntry
    MAX-ACCESS  not-accessible
    STATUS      current
    DESCRIPTION
        "The tmnxLmpVRtrTeLinkTable contains the Traffic Engineering (TE) link
         managed by the LMP."
    REFERENCE
        "Link Management Protocol, RFC 4204."
    ::= { tmnxLmpConfigurations 4 }

tmnxLmpVRtrTeLinkEntry           OBJECT-TYPE
    SYNTAX      TmnxLmpVRtrTeLinkEntry
    MAX-ACCESS  not-accessible
    STATUS      current
    DESCRIPTION
        "The tmnxLmpVRtrEntry consists of the configurable objects for a TE
         link on a given virtual router instance."
    INDEX       {
        vRtrID,
        tmnxLmpVRtrTeLinkId
    }
    ::= { tmnxLmpVRtrTeLinkTable 1 }

TmnxLmpVRtrTeLinkEntry           ::= SEQUENCE
{
    tmnxLmpVRtrTeLinkId              Unsigned32,
    tmnxLmpVRtrTeLinkRowStatus       RowStatus,
    tmnxLmpVRtrTeLinkLastChanged     TimeStamp,
    tmnxLmpVRtrTeLinkAdminState      TmnxAdminState,
    tmnxLmpVRtrTeLinkOperState       INTEGER,
    tmnxLmpVRtrTeLinkName            TNamedItemOrEmpty,
    tmnxLmpVRtrTeLinkRemoteId        Unsigned32,
    tmnxLmpVRtrTeLinkPeerNodeId      Unsigned32
}

tmnxLmpVRtrTeLinkId              OBJECT-TYPE
    SYNTAX      Unsigned32 (1..4294967295)
    MAX-ACCESS  not-accessible
    STATUS      current
    DESCRIPTION
        "The value of tmnxLmpVRtrTeLinkId specifies a unique value which
         identifies this TE link on the given virtual router instance.

         The identifiers for TE links (tmnxLmpVRtrTeLinkId) and DB links
         (tmnxLmpVRtrDbLinkId) cannot be the same for a particular virtual
         router instance."
    ::= { tmnxLmpVRtrTeLinkEntry 1 }

tmnxLmpVRtrTeLinkRowStatus       OBJECT-TYPE
    SYNTAX      RowStatus
    MAX-ACCESS  read-create
    STATUS      current
    DESCRIPTION
        "The value of tmnxLmpVRtrTeLinkRowStatus specifies the row status. It
         allows the creation and deletion of this TE link on the given virtual
         router instance."
    ::= { tmnxLmpVRtrTeLinkEntry 2 }

tmnxLmpVRtrTeLinkLastChanged     OBJECT-TYPE
    SYNTAX      TimeStamp
    MAX-ACCESS  read-only
    STATUS      current
    DESCRIPTION
        "The value of tmnxLmpVRtrTeLinkLastChanged indicates the time, since
         system startup, that the configuration of this TE link was created or
         modified."
    ::= { tmnxLmpVRtrTeLinkEntry 3 }

tmnxLmpVRtrTeLinkAdminState      OBJECT-TYPE
    SYNTAX      TmnxAdminState
    MAX-ACCESS  read-create
    STATUS      current
    DESCRIPTION
        "The value of tmnxLmpVRtrTeLinkAdminState specifies the administrative
         state of this TE link."
    DEFVAL      { outOfService }
    ::= { tmnxLmpVRtrTeLinkEntry 4 }

tmnxLmpVRtrTeLinkOperState       OBJECT-TYPE
    SYNTAX      INTEGER {
        up       (1),
        down     (2),
        testing  (3),
        init     (4),
        degraded (5)
    }
    MAX-ACCESS  read-only
    STATUS      current
    DESCRIPTION
        "The value of tmnxLmpVRtrTeLinkOperState indicates the operational
         state of this TE link."
    ::= { tmnxLmpVRtrTeLinkEntry 5 }

tmnxLmpVRtrTeLinkName            OBJECT-TYPE
    SYNTAX      TNamedItemOrEmpty
    MAX-ACCESS  read-create
    STATUS      current
    DESCRIPTION
        "The value of tmnxLmpVRtrTeLinkName specifies a unique name for this TE
         link on the given virtual router instance."
    DEFVAL      { ''H }
    ::= { tmnxLmpVRtrTeLinkEntry 6 }

tmnxLmpVRtrTeLinkRemoteId        OBJECT-TYPE
    SYNTAX      Unsigned32
    MAX-ACCESS  read-create
    STATUS      current
    DESCRIPTION
        "The value of tmnxLmpVRtrTeLinkRemoteId specifies the identifier for
         the remote endpoint of this TE link.

         Zero indicates this object has not been configured."
    DEFVAL      { 0 }
    ::= { tmnxLmpVRtrTeLinkEntry 7 }

tmnxLmpVRtrTeLinkPeerNodeId      OBJECT-TYPE
    SYNTAX      Unsigned32
    MAX-ACCESS  read-create
    STATUS      current
    DESCRIPTION
        "The value of tmnxLmpVRtrTeLinkPeerNodeId specifies the node identifier
         of the remote node for this TE link.

         Zero indicates that this object is not configured."
    DEFVAL      { 0 }
    ::= { tmnxLmpVRtrTeLinkEntry 8 }

tmnxLmpVRtrDbLinkTable           OBJECT-TYPE
    SYNTAX      SEQUENCE OF TmnxLmpVRtrDbLinkEntry
    MAX-ACCESS  not-accessible
    STATUS      current
    DESCRIPTION
        "The tmnxLmpVRtrDbLinkTable contains the Data Bearing (DB) links
         managed by the LMP."
    REFERENCE
        "Link Management Protocol, RFC 4204."
    ::= { tmnxLmpConfigurations 5 }

tmnxLmpVRtrDbLinkEntry           OBJECT-TYPE
    SYNTAX      TmnxLmpVRtrDbLinkEntry
    MAX-ACCESS  not-accessible
    STATUS      current
    DESCRIPTION
        "The tmnxLmpVRtrDbLinkEntry consists of the configurable objects for a
         DB link on a given TE link and virtual router instance."
    INDEX       {
        vRtrID,
        tmnxLmpVRtrTeLinkId,
        tmnxLmpVRtrDbLinkId
    }
    ::= { tmnxLmpVRtrDbLinkTable 1 }

TmnxLmpVRtrDbLinkEntry           ::= SEQUENCE
{
    tmnxLmpVRtrDbLinkId              Unsigned32,
    tmnxLmpVRtrDbLinkRowStatus       RowStatus,
    tmnxLmpVRtrDbLinkLastChanged     TimeStamp,
    tmnxLmpVRtrDbLinkAdminState      TmnxAdminState,
    tmnxLmpVRtrDbLinkOperState       INTEGER,
    tmnxLmpVRtrDbLinkPortId          TmnxPortID,
    tmnxLmpVRtrDbLinkRemoteId        Unsigned32,
    tmnxLmpVRtrDbLinkReasonDownFlags BITS
}

tmnxLmpVRtrDbLinkId              OBJECT-TYPE
    SYNTAX      Unsigned32 (1..4294967295)
    MAX-ACCESS  not-accessible
    STATUS      current
    DESCRIPTION
        "The value of tmnxLmpVRtrDbLinkId specifies a unique value which
         identifies this DB link on the given virtual router instance.

         The identifiers for TE links (tmnxLmpVRtrTeLinkId) and DB links
         (tmnxLmpVRtrDbLinkId) cannot be the same for a particular virtual
         router instance."
    ::= { tmnxLmpVRtrDbLinkEntry 1 }

tmnxLmpVRtrDbLinkRowStatus       OBJECT-TYPE
    SYNTAX      RowStatus
    MAX-ACCESS  read-create
    STATUS      current
    DESCRIPTION
        "The value of tmnxLmpVRtrDbLinkRowStatus specifies the row status. It
         allows the creation and deletion of this DB link on the given TE link
         and virtual router instance."
    ::= { tmnxLmpVRtrDbLinkEntry 2 }

tmnxLmpVRtrDbLinkLastChanged     OBJECT-TYPE
    SYNTAX      TimeStamp
    MAX-ACCESS  read-only
    STATUS      current
    DESCRIPTION
        "The value of tmnxLmpVRtrDbLinkLastChanged indicates the time, since
         system startup, that the configuration of this DB link was created or
         modified."
    ::= { tmnxLmpVRtrDbLinkEntry 3 }

tmnxLmpVRtrDbLinkAdminState      OBJECT-TYPE
    SYNTAX      TmnxAdminState
    MAX-ACCESS  read-create
    STATUS      current
    DESCRIPTION
        "The value of tmnxLmpVRtrDbLinkAdminState specifies the administrative
         state of this DB link."
    DEFVAL      { outOfService }
    ::= { tmnxLmpVRtrDbLinkEntry 4 }

tmnxLmpVRtrDbLinkOperState       OBJECT-TYPE
    SYNTAX      INTEGER {
        upAlloc (1),
        upFree  (2),
        down    (3),
        testing (4)
    }
    MAX-ACCESS  read-only
    STATUS      current
    DESCRIPTION
        "The value of tmnxLmpVRtrDbLinkOperState indicates the operational
         state of this DB link."
    ::= { tmnxLmpVRtrDbLinkEntry 5 }

tmnxLmpVRtrDbLinkPortId          OBJECT-TYPE
    SYNTAX      TmnxPortID
    MAX-ACCESS  read-create
    STATUS      current
    DESCRIPTION
        "The value of tmnxLmpVRtrDbLinkPortId specifies the port identifier of
         the port associated to this DB link.

         A value of '1e000000'H indicates this object has not been configured."
    DEFVAL      { '1e000000'H }
    ::= { tmnxLmpVRtrDbLinkEntry 6 }

tmnxLmpVRtrDbLinkRemoteId        OBJECT-TYPE
    SYNTAX      Unsigned32
    MAX-ACCESS  read-create
    STATUS      current
    DESCRIPTION
        "The value of tmnxLmpVRtrDbLinkRemoteId specifies the identifier of the
         remote endpoint for this DB link.

         Zero indicates this object has not been configured."
    DEFVAL      { 0 }
    ::= { tmnxLmpVRtrDbLinkEntry 7 }

tmnxLmpVRtrDbLinkReasonDownFlags OBJECT-TYPE
    SYNTAX      BITS {
        unknown       (0),
        adminDn       (1),
        lpcFault      (2),
        remoteLkFault (3),
        portAdminDn   (4),
        portFault     (5),
        gmplsTeDn     (6)
    }
    MAX-ACCESS  read-only
    STATUS      current
    DESCRIPTION
        "The value of tmnxLmpVRtrDbLinkReasonDownFlags indicates the reason(s)
         why this DB link is operationally down.

         The recognized BIT values are:
             unknown       (0) - unspecified or unknown
             adminDn       (1) - the DB link or related LMP entity (i.e. TE
                                 link, peer, etc.) is administratively down, or
                               - parent TE link is not associated with any peer
             lpcFault      (2) - the link property correlation failed
             remoteLkFault (3) - the DB Link Summary message received had the
                                 'Failed Link' flag set by the peer
             portAdminDn   (4) - the port or associated MDA/IOM is
                                 administratively down
             portFault     (5) - the port is either not present, or the DB link
                                 detected a signal failure (e.g. loss of light)
             gmplsTeDn     (6) - the GMPLS TE link (vRtrGmplsTeLinkEntry) is
                                 either not present or administratively down"
    ::= { tmnxLmpVRtrDbLinkEntry 8 }

tmnxLmpStatistics                OBJECT IDENTIFIER ::= { tmnxLmpObjs 3 }

tmnxLmpVRtrControlChanStatsTable OBJECT-TYPE
    SYNTAX      SEQUENCE OF TmnxLmpVRtrControlChanStatsEntry
    MAX-ACCESS  not-accessible
    STATUS      current
    DESCRIPTION
        "The tmnxLmpVRtrControlChanStatsTable contains the LMP control channel
         statistics counters for a virtual router instance."
    ::= { tmnxLmpStatistics 1 }

tmnxLmpVRtrControlChanStatsEntry OBJECT-TYPE
    SYNTAX      TmnxLmpVRtrControlChanStatsEntry
    MAX-ACCESS  not-accessible
    STATUS      current
    DESCRIPTION
        "The tmnxLmpVRtrControlChanStatsEntry consists of statistical
         information about a control channel for a virtual router instance."
    INDEX       {
        vRtrID,
        tmnxLmpVRtrPeerNodeId,
        tmnxLmpVRtrCcId
    }
    ::= { tmnxLmpVRtrControlChanStatsTable 1 }

TmnxLmpVRtrControlChanStatsEntry ::= SEQUENCE
{
    tmnxLmpVRtrCcInErrors            Counter32,
    tmnxLmpVRtrCcOutErrors           Counter32,
    tmnxLmpVRtrCcConfigReceived      Counter32,
    tmnxLmpVRtrCcConfigSent          Counter32,
    tmnxLmpVRtrCcConfigRetransmit    Counter32,
    tmnxLmpVRtrCcConfigAckReceived   Counter32,
    tmnxLmpVRtrCcConfigAckSent       Counter32,
    tmnxLmpVRtrCcConfigNackReceived  Counter32,
    tmnxLmpVRtrCcConfigNackSent      Counter32,
    tmnxLmpVRtrCcHelloReceived       Counter32,
    tmnxLmpVRtrCcHelloSent           Counter32,
    tmnxLmpVRtrCcLinkSumReceived     Counter32,
    tmnxLmpVRtrCcLinkSumSent         Counter32,
    tmnxLmpVRtrCcLinkSumRetransmit   Counter32,
    tmnxLmpVRtrCcLinkSumAckReceived  Counter32,
    tmnxLmpVRtrCcLinkSumAckSent      Counter32,
    tmnxLmpVRtrCcLinkSumNackReceived Counter32,
    tmnxLmpVRtrCcLinkSumNackSent     Counter32,
    tmnxLmpVRtrCcDiscontinuityTime   TimeStamp
}

tmnxLmpVRtrCcInErrors            OBJECT-TYPE
    SYNTAX      Counter32
    MAX-ACCESS  read-only
    STATUS      current
    DESCRIPTION
        "The value of tmnxLmpVRtrCcInErrors indicates the number of inbound
         packets that contained errors preventing them from being processed by
         LMP.

         Discontinuities in the value of this counter can occur at
         re-initialization of the management system, and at other times as
         indicated by the value of tmnxLmpVRtrCcDiscontinuityTime."
    ::= { tmnxLmpVRtrControlChanStatsEntry 1 }

tmnxLmpVRtrCcOutErrors           OBJECT-TYPE
    SYNTAX      Counter32
    MAX-ACCESS  read-only
    STATUS      current
    DESCRIPTION
        "The value of tmnxLmpVRtrCcOutErrors indicates the number of outbound
         packets that could not be transmitted because of errors.

         Discontinuities in the value of this counter can occur at
         re-initialization of the management system, and at other times as
         indicated by the value of tmnxLmpVRtrCcDiscontinuityTime."
    ::= { tmnxLmpVRtrControlChanStatsEntry 2 }

tmnxLmpVRtrCcConfigReceived      OBJECT-TYPE
    SYNTAX      Counter32
    MAX-ACCESS  read-only
    STATUS      current
    DESCRIPTION
        "The value of tmnxLmpVRtrCcConfigReceived indicates the number of
         Config messages that have been received on this control channel.

         Discontinuities in the value of this counter can occur at
         re-initialization of the management system, and at other times as
         indicated by the value of tmnxLmpVRtrCcDiscontinuityTime."
    ::= { tmnxLmpVRtrControlChanStatsEntry 3 }

tmnxLmpVRtrCcConfigSent          OBJECT-TYPE
    SYNTAX      Counter32
    MAX-ACCESS  read-only
    STATUS      current
    DESCRIPTION
        "The value of tmnxLmpVRtrCcConfigSent indicates the number of Config
         messages that have been sent on this control channel.

         Discontinuities in the value of this counter can occur at
         re-initialization of the management system, and at other times as
         indicated by the value of tmnxLmpVRtrCcDiscontinuityTime."
    ::= { tmnxLmpVRtrControlChanStatsEntry 4 }

tmnxLmpVRtrCcConfigRetransmit    OBJECT-TYPE
    SYNTAX      Counter32
    MAX-ACCESS  read-only
    STATUS      current
    DESCRIPTION
        "The value of tmnxLmpVRtrCcConfigRetransmit indicates the number of
         Config messages that have been retransmitted over this control
         channel.

         Discontinuities in the value of this counter can occur at
         re-initialization of the management system, and at other times as
         indicated by the value of tmnxLmpVRtrCcDiscontinuityTime."
    ::= { tmnxLmpVRtrControlChanStatsEntry 5 }

tmnxLmpVRtrCcConfigAckReceived   OBJECT-TYPE
    SYNTAX      Counter32
    MAX-ACCESS  read-only
    STATUS      current
    DESCRIPTION
        "The value of tmnxLmpVRtrCcConfigAckReceived indicates the number of
         ConfigAck messages that have been received on this control channel.

         Discontinuities in the value of this counter can occur at
         re-initialization of the management system, and at other times as
         indicated by the value of tmnxLmpVRtrCcDiscontinuityTime."
    ::= { tmnxLmpVRtrControlChanStatsEntry 6 }

tmnxLmpVRtrCcConfigAckSent       OBJECT-TYPE
    SYNTAX      Counter32
    MAX-ACCESS  read-only
    STATUS      current
    DESCRIPTION
        "The value of tmnxLmpVRtrCcConfigAckSent indicates the number of
         ConfigAck messages that have been sent on this control channel.

         Discontinuities in the value of this counter can occur at
         re-initialization of the management system, and at other times as
         indicated by the value of tmnxLmpVRtrCcDiscontinuityTime."
    ::= { tmnxLmpVRtrControlChanStatsEntry 7 }

tmnxLmpVRtrCcConfigNackReceived  OBJECT-TYPE
    SYNTAX      Counter32
    MAX-ACCESS  read-only
    STATUS      current
    DESCRIPTION
        "The value of tmnxLmpVRtrCcConfigNackReceived indicates the number of
         ConfigNack messages that have been received on this control channel.

         Discontinuities in the value of this counter can occur at
         re-initialization of the management system, and at other times as
         indicated by the value of tmnxLmpVRtrCcDiscontinuityTime."
    ::= { tmnxLmpVRtrControlChanStatsEntry 8 }

tmnxLmpVRtrCcConfigNackSent      OBJECT-TYPE
    SYNTAX      Counter32
    MAX-ACCESS  read-only
    STATUS      current
    DESCRIPTION
        "The value of tmnxLmpVRtrCcConfigNackSent indicates the number of
         ConfigNack messages that have been sent on this control channel.

         Discontinuities in the value of this counter can occur at
         re-initialization of the management system, and at other times as
         indicated by the value of tmnxLmpVRtrCcDiscontinuityTime."
    ::= { tmnxLmpVRtrControlChanStatsEntry 9 }

tmnxLmpVRtrCcHelloReceived       OBJECT-TYPE
    SYNTAX      Counter32
    MAX-ACCESS  read-only
    STATUS      current
    DESCRIPTION
        "The value of tmnxLmpVRtrCcHelloReceived indicates the number of Hello
         messages that have been received on this control channel.

         Discontinuities in the value of this counter can occur at
         re-initialization of the management system, and at other times as
         indicated by the value of tmnxLmpVRtrCcDiscontinuityTime."
    ::= { tmnxLmpVRtrControlChanStatsEntry 10 }

tmnxLmpVRtrCcHelloSent           OBJECT-TYPE
    SYNTAX      Counter32
    MAX-ACCESS  read-only
    STATUS      current
    DESCRIPTION
        "The value of tmnxLmpVRtrCcHelloSent indicates the number of Hello
         messages that have been sent on this control channel.

         Discontinuities in the value of this counter can occur at
         re-initialization of the management system, and at other times as
         indicated by the value of tmnxLmpVRtrCcDiscontinuityTime."
    ::= { tmnxLmpVRtrControlChanStatsEntry 12 }

tmnxLmpVRtrCcLinkSumReceived     OBJECT-TYPE
    SYNTAX      Counter32
    MAX-ACCESS  read-only
    STATUS      current
    DESCRIPTION
        "The value of tmnxLmpVRtrCcLinkSumReceived indicates the number of
         LinkSummary messages that have been received on this control channel.

         Discontinuities in the value of this counter can occur at
         re-initialization of the management system, and at other times as
         indicated by the value of tmnxLmpVRtrCcDiscontinuityTime."
    ::= { tmnxLmpVRtrControlChanStatsEntry 13 }

tmnxLmpVRtrCcLinkSumSent         OBJECT-TYPE
    SYNTAX      Counter32
    MAX-ACCESS  read-only
    STATUS      current
    DESCRIPTION
        "The value of tmnxLmpVRtrCcLinkSumSent indicates the number of
         LinkSummary messages that have been sent on this control channel.

         Discontinuities in the value of this counter can occur at
         re-initialization of the management system, and at other times as
         indicated by the value of tmnxLmpVRtrCcDiscontinuityTime."
    ::= { tmnxLmpVRtrControlChanStatsEntry 14 }

tmnxLmpVRtrCcLinkSumRetransmit   OBJECT-TYPE
    SYNTAX      Counter32
    MAX-ACCESS  read-only
    STATUS      current
    DESCRIPTION
        "The value of tmnxLmpVRtrCcLinkSumRetransmit indicates the number of
         LinkSummary messages that have been retransmitted over this control
         channel.

         Discontinuities in the value of this counter can occur at
         re-initialization of the management system, and at other times as
         indicated by the value of tmnxLmpVRtrCcDiscontinuityTime."
    ::= { tmnxLmpVRtrControlChanStatsEntry 15 }

tmnxLmpVRtrCcLinkSumAckReceived  OBJECT-TYPE
    SYNTAX      Counter32
    MAX-ACCESS  read-only
    STATUS      current
    DESCRIPTION
        "The value of tmnxLmpVRtrCcLinkSumAckReceived indicates the number of
         LinkSummaryAck messages that have been received on this control
         channel.

         Discontinuities in the value of this counter can occur at
         re-initialization of the management system, and at other times as
         indicated by the value of tmnxLmpVRtrCcDiscontinuityTime."
    ::= { tmnxLmpVRtrControlChanStatsEntry 16 }

tmnxLmpVRtrCcLinkSumAckSent      OBJECT-TYPE
    SYNTAX      Counter32
    MAX-ACCESS  read-only
    STATUS      current
    DESCRIPTION
        "The value of tmnxLmpVRtrCcLinkSumAckSent indicates the number of
         LinkSummaryAck messages that have been sent on this control channel.

         Discontinuities in the value of this counter can occur at
         re-initialization of the management system, and at other times as
         indicated by the value of tmnxLmpVRtrCcDiscontinuityTime."
    ::= { tmnxLmpVRtrControlChanStatsEntry 17 }

tmnxLmpVRtrCcLinkSumNackReceived OBJECT-TYPE
    SYNTAX      Counter32
    MAX-ACCESS  read-only
    STATUS      current
    DESCRIPTION
        "The value of tmnxLmpVRtrCcLinkSumNackReceived indicates the number of
         LinkSummaryNack messages that have been received on this control
         channel.

         Discontinuities in the value of this counter can occur at
         re-initialization of the management system, and at other times as
         indicated by the value of tmnxLmpVRtrCcDiscontinuityTime."
    ::= { tmnxLmpVRtrControlChanStatsEntry 18 }

tmnxLmpVRtrCcLinkSumNackSent     OBJECT-TYPE
    SYNTAX      Counter32
    MAX-ACCESS  read-only
    STATUS      current
    DESCRIPTION
        "The value of tmnxLmpVRtrCcLinkSumNackSent indicates the number of
         LinkSummaryNack messages that have been sent on this control channel.

         Discontinuities in the value of this counter can occur at
         re-initialization of the management system, and at other times as
         indicated by the value of tmnxLmpVRtrCcDiscontinuityTime."
    ::= { tmnxLmpVRtrControlChanStatsEntry 19 }

tmnxLmpVRtrCcDiscontinuityTime   OBJECT-TYPE
    SYNTAX      TimeStamp
    MAX-ACCESS  read-only
    STATUS      current
    DESCRIPTION
        "The value of tmnxLmpVRtrCcDiscontinuityTime indicates the sysUpTime on
         the most recent occasion at which one or more of this control
         channel's counters suffered a discontinuity. The relevant counters are
         the specific instances associated with this control channel of any
         Counter32 object contained in the tmnxLmpVRtrControlChanStatsTable. If
         no such discontinuities have occurred since the last re-initialization
         of the local management subsystem, then this object contains a zero
         value."
    ::= { tmnxLmpVRtrControlChanStatsEntry 20 }

tmnxLmpVRtrTeLinkStatsTable      OBJECT-TYPE
    SYNTAX      SEQUENCE OF TmnxLmpVRtrTeLinkStatsEntry
    MAX-ACCESS  not-accessible
    STATUS      current
    DESCRIPTION
        "The tmnxLmpVRtrTeLinkStatsTable contains the LMP Traffic Engineering
         (TE) link statistics counters for a virtual router instance."
    ::= { tmnxLmpStatistics 2 }

tmnxLmpVRtrTeLinkStatsEntry      OBJECT-TYPE
    SYNTAX      TmnxLmpVRtrTeLinkStatsEntry
    MAX-ACCESS  not-accessible
    STATUS      current
    DESCRIPTION
        "The tmnxLmpVRtrTeLinkStatsEntry consists of statistical information
         about a TE link for a virtual router instance."
    INDEX       {
        vRtrID,
        tmnxLmpVRtrTeLinkId
    }
    ::= { tmnxLmpVRtrTeLinkStatsTable 1 }

TmnxLmpVRtrTeLinkStatsEntry      ::= SEQUENCE
{
    tmnxLmpVRtrTeLinkSumReceived     Counter32,
    tmnxLmpVRtrTeLinkSumSent         Counter32,
    tmnxLmpVRtrTeLinkSumRetransmit   Counter32,
    tmnxLmpVRtrTeLinkSumAckReceived  Counter32,
    tmnxLmpVRtrTeLinkSumAckSent      Counter32,
    tmnxLmpVRtrTeLinkSumNackReceived Counter32,
    tmnxLmpVRtrTeLinkSumNackSent     Counter32,
    tmnxLmpVRtrTeLinkDiscntnuityTime TimeStamp
}

tmnxLmpVRtrTeLinkSumReceived     OBJECT-TYPE
    SYNTAX      Counter32
    MAX-ACCESS  read-only
    STATUS      current
    DESCRIPTION
        "The value of tmnxLmpVRtrTeLinkSumReceived indicates the number of
         LinkSummary messages that have been received for this TE link.

         Discontinuities in the value of this counter can occur at
         re-initialization of the management system, and at other times as
         indicated by the value of tmnxLmpVRtrTeLinkDiscntnuityTime."
    ::= { tmnxLmpVRtrTeLinkStatsEntry 1 }

tmnxLmpVRtrTeLinkSumSent         OBJECT-TYPE
    SYNTAX      Counter32
    MAX-ACCESS  read-only
    STATUS      current
    DESCRIPTION
        "The value of tmnxLmpVRtrTeLinkSumSent indicates the number of
         LinkSummary messages that have been sent for this TE link.

         Discontinuities in the value of this counter can occur at
         re-initialization of the management system, and at other times as
         indicated by the value of tmnxLmpVRtrTeLinkDiscntnuityTime."
    ::= { tmnxLmpVRtrTeLinkStatsEntry 2 }

tmnxLmpVRtrTeLinkSumRetransmit   OBJECT-TYPE
    SYNTAX      Counter32
    MAX-ACCESS  read-only
    STATUS      current
    DESCRIPTION
        "The value of tmnxLmpVRtrTeLinkSumRetransmit indicates the number of
         LinkSummary messages that have been retransmitted for this TE link.

         Discontinuities in the value of this counter can occur at
         re-initialization of the management system, and at other times as
         indicated by the value of tmnxLmpVRtrTeLinkDiscntnuityTime."
    ::= { tmnxLmpVRtrTeLinkStatsEntry 3 }

tmnxLmpVRtrTeLinkSumAckReceived  OBJECT-TYPE
    SYNTAX      Counter32
    MAX-ACCESS  read-only
    STATUS      current
    DESCRIPTION
        "The value of tmnxLmpVRtrTeLinkSumAckReceived indicates the number of
         LinkSummaryAck messages that have been received for this TE link.

         Discontinuities in the value of this counter can occur at
         re-initialization of the management system, and at other times as
         indicated by the value of tmnxLmpVRtrTeLinkDiscntnuityTime."
    ::= { tmnxLmpVRtrTeLinkStatsEntry 4 }

tmnxLmpVRtrTeLinkSumAckSent      OBJECT-TYPE
    SYNTAX      Counter32
    MAX-ACCESS  read-only
    STATUS      current
    DESCRIPTION
        "The value of tmnxLmpVRtrTeLinkSumAckSent indicates the number of
         LinkSummaryAck messages that have been sent for this TE link.

         Discontinuities in the value of this counter can occur at
         re-initialization of the management system, and at other times as
         indicated by the value of tmnxLmpVRtrTeLinkDiscntnuityTime."
    ::= { tmnxLmpVRtrTeLinkStatsEntry 5 }

tmnxLmpVRtrTeLinkSumNackReceived OBJECT-TYPE
    SYNTAX      Counter32
    MAX-ACCESS  read-only
    STATUS      current
    DESCRIPTION
        "The value of tmnxLmpVRtrTeLinkSumNackReceived indicates the number of
         LinkSummaryNack messages that have been received for this TE link.

         Discontinuities in the value of this counter can occur at
         re-initialization of the management system, and at other times as
         indicated by the value of tmnxLmpVRtrTeLinkDiscntnuityTime."
    ::= { tmnxLmpVRtrTeLinkStatsEntry 6 }

tmnxLmpVRtrTeLinkSumNackSent     OBJECT-TYPE
    SYNTAX      Counter32
    MAX-ACCESS  read-only
    STATUS      current
    DESCRIPTION
        "The value of tmnxLmpVRtrTeLinkSumNackSent indicates the number of
         LinkSummaryNack messages that have been sent for this TE link.

         Discontinuities in the value of this counter can occur at
         re-initialization of the management system, and at other times as
         indicated by the value of tmnxLmpVRtrTeLinkDiscntnuityTime."
    ::= { tmnxLmpVRtrTeLinkStatsEntry 7 }

tmnxLmpVRtrTeLinkDiscntnuityTime OBJECT-TYPE
    SYNTAX      TimeStamp
    MAX-ACCESS  read-only
    STATUS      current
    DESCRIPTION
        "The value of tmnxLmpVRtrTeLinkDiscntnuityTime indicates the sysUpTime
         on the most recent occasion at which one or more of this TE link's
         counters suffered a discontinuity. The relevant counters are the
         specific instances associated with this TE link of any Counter32
         object contained in the tmnxLmpVRtrTeLinkStatsTable. If no such
         discontinuities have occurred since the last re-initialization of the
         local management subsystem, then this object contains a zero value."
    ::= { tmnxLmpVRtrTeLinkStatsEntry 8 }

tmnxLmpNotifyObjects             OBJECT IDENTIFIER ::= { tmnxLmpObjs 4 }

tmnxLmpConformance               OBJECT IDENTIFIER ::= { tmnxSRConfs 100 }

tmnxLmpCompliances               OBJECT IDENTIFIER ::= { tmnxLmpConformance 1 }

tmnxLmpComplianceV13v0           MODULE-COMPLIANCE
    STATUS      current
    DESCRIPTION
        "The compliance statement for the management of the Link Management
         Protocol for Release 13.0 on Nokia SROS series systems."
    MODULE
        MANDATORY-GROUPS {
            tmnxLmpVRtrGroupV13v0,
            tmnxLmpVRtrPeerGroupV13v0,
            tmnxLmpVRtrCcGroupV13v0,
            tmnxLmpVRtrTeLinkGroupV13v0,
            tmnxLmpVRtrDbLinkGroupV13v0,
            tmnxLmpVRtrCcStatsGroupV13v0,
            tmnxLmpVRtrTeLinkStatsGroupV13v0,
            tmnxLmpVRtrNotifGroupV13v0
        }
    ::= { tmnxLmpCompliances 1 }

tmnxLmpComplianceV15v0           MODULE-COMPLIANCE
    STATUS      current
    DESCRIPTION
        "The compliance statement for the management of the Link Management
         Protocol for Release 15.0 on Nokia SROS series systems."
    MODULE
        MANDATORY-GROUPS {
            tmnxLmpVRtrPeerGroupV15v0,
            tmnxLmpVRtrCtrlChannelGroupV15v0
        }
    ::= { tmnxLmpCompliances 2 }

tmnxLmpGroups                    OBJECT IDENTIFIER ::= { tmnxLmpConformance 2 }

tmnxLmpV13v0Groups               OBJECT IDENTIFIER ::= { tmnxLmpGroups 1 }

tmnxLmpVRtrGroupV13v0            OBJECT-GROUP
    OBJECTS     {
        tmnxLmpVRtrTableLastChanged,
        tmnxLmpVRtrRowStatus,
        tmnxLmpVRtrLastChanged,
        tmnxLmpVRtrAdminState,
        tmnxLmpVRtrOperState,
        tmnxLmpVRtrGmplsLoopbackAddrType,
        tmnxLmpVRtrGmplsLoopbackAddress
    }
    STATUS      current
    DESCRIPTION
        "The group of objects maintaining the Link Management Protocol (LMP)
         configuration for the virtual router instances on Nokia SROS series
         systems for Release 13.0."
    ::= { tmnxLmpV13v0Groups 1 }

tmnxLmpVRtrPeerGroupV13v0        OBJECT-GROUP
    OBJECTS     {
        tmnxLmpVRtrPeerTableLastChanged,
        tmnxLmpVRtrPeerRowStatus,
        tmnxLmpVRtrPeerLastChanged,
        tmnxLmpVRtrPeerAdminState,
        tmnxLmpVRtrPeerOperState,
        tmnxLmpVRtrPeerLoopbackAddrType,
        tmnxLmpVRtrPeerLoopbackAddress,
        tmnxLmpVRtrPeerRetransmitIntvl,
        tmnxLmpVRtrPeerRetryLimit,
        tmnxLmpVRtrPeerRetransmitDelta
    }
    STATUS      current
    DESCRIPTION
        "The group of objects maintaining the Link Management Protocol (LMP)
         Peer configuration for the virtual router instances on Nokia SROS
         series systems for Release 13.0."
    ::= { tmnxLmpV13v0Groups 2 }

tmnxLmpVRtrCcGroupV13v0          OBJECT-GROUP
    OBJECTS     {
        tmnxLmpVRtrCcTableLastChanged,
        tmnxLmpVRtrCcRowStatus,
        tmnxLmpVRtrCcLastChanged,
        tmnxLmpVRtrCcAdminState,
        tmnxLmpVRtrCcOperState,
        tmnxLmpVRtrCcRemoteId,
        tmnxLmpVRtrCcPeerIfAddressType,
        tmnxLmpVRtrCcPeerIfAddress,
        tmnxLmpVRtrCcSetupRole,
        tmnxLmpVRtrCcHelloInterval,
        tmnxLmpVRtrCcHelloIntvNeg,
        tmnxLmpVRtrCcHelloDeadInterval,
        tmnxLmpVRtrCcHelloDeadIntvNeg,
        tmnxLmpVRtrCcTtl
    }
    STATUS      current
    DESCRIPTION
        "The group of objects maintaining the Link Management Protocol (LMP)
         Control Channel configuration for the virtual router instances on
         Nokia SROS series systems for Release 13.0."
    ::= { tmnxLmpV13v0Groups 3 }

tmnxLmpVRtrTeLinkGroupV13v0      OBJECT-GROUP
    OBJECTS     {
        tmnxLmpVRtrTeLinkTableLastChange,
        tmnxLmpVRtrTeLinkRowStatus,
        tmnxLmpVRtrTeLinkLastChanged,
        tmnxLmpVRtrTeLinkAdminState,
        tmnxLmpVRtrTeLinkOperState,
        tmnxLmpVRtrTeLinkName,
        tmnxLmpVRtrTeLinkRemoteId,
        tmnxLmpVRtrTeLinkPeerNodeId
    }
    STATUS      current
    DESCRIPTION
        "The group of objects maintaining the Link Management Protocol (LMP)
         Traffic Engineering (TE) Links configuration for the virtual router
         instances on Nokia SROS series systems for Release 13.0."
    ::= { tmnxLmpV13v0Groups 4 }

tmnxLmpVRtrDbLinkGroupV13v0      OBJECT-GROUP
    OBJECTS     {
        tmnxLmpVRtrDbLinkTableLastChange,
        tmnxLmpVRtrDbLinkRowStatus,
        tmnxLmpVRtrDbLinkLastChanged,
        tmnxLmpVRtrDbLinkAdminState,
        tmnxLmpVRtrDbLinkOperState,
        tmnxLmpVRtrDbLinkPortId,
        tmnxLmpVRtrDbLinkRemoteId,
        tmnxLmpVRtrDbLinkReasonDownFlags
    }
    STATUS      current
    DESCRIPTION
        "The group of objects maintaining the Link Management Protocol (LMP)
         Data Bearing (DB) Links configuration for the virtual router instances
         on Nokia SROS series systems for Release 13.0."
    ::= { tmnxLmpV13v0Groups 5 }

tmnxLmpVRtrCcStatsGroupV13v0     OBJECT-GROUP
    OBJECTS     {
        tmnxLmpVRtrCcInErrors,
        tmnxLmpVRtrCcOutErrors,
        tmnxLmpVRtrCcConfigReceived,
        tmnxLmpVRtrCcConfigSent,
        tmnxLmpVRtrCcConfigRetransmit,
        tmnxLmpVRtrCcConfigAckReceived,
        tmnxLmpVRtrCcConfigAckSent,
        tmnxLmpVRtrCcConfigNackReceived,
        tmnxLmpVRtrCcConfigNackSent,
        tmnxLmpVRtrCcHelloReceived,
        tmnxLmpVRtrCcHelloSent,
        tmnxLmpVRtrCcLinkSumReceived,
        tmnxLmpVRtrCcLinkSumSent,
        tmnxLmpVRtrCcLinkSumRetransmit,
        tmnxLmpVRtrCcLinkSumAckReceived,
        tmnxLmpVRtrCcLinkSumAckSent,
        tmnxLmpVRtrCcLinkSumNackReceived,
        tmnxLmpVRtrCcLinkSumNackSent,
        tmnxLmpVRtrCcDiscontinuityTime
    }
    STATUS      current
    DESCRIPTION
        "The group of objects maintaining the Link Management Protocol (LMP)
         Control Channel Statistics for the virtual router instances on Nokia
         SROS series systems for Release 13.0."
    ::= { tmnxLmpV13v0Groups 6 }

tmnxLmpVRtrTeLinkStatsGroupV13v0 OBJECT-GROUP
    OBJECTS     {
        tmnxLmpVRtrTeLinkSumReceived,
        tmnxLmpVRtrTeLinkSumSent,
        tmnxLmpVRtrTeLinkSumRetransmit,
        tmnxLmpVRtrTeLinkSumAckReceived,
        tmnxLmpVRtrTeLinkSumAckSent,
        tmnxLmpVRtrTeLinkSumNackReceived,
        tmnxLmpVRtrTeLinkSumNackSent,
        tmnxLmpVRtrTeLinkDiscntnuityTime
    }
    STATUS      current
    DESCRIPTION
        "The group of objects maintaining the Link Management Protocol (LMP)
         Traffic Engineering (TE) Link Statistics for the virtual router
         instances on Nokia SROS series systems for Release 13.0."
    ::= { tmnxLmpV13v0Groups 7 }

tmnxLmpVRtrNotifGroupV13v0       NOTIFICATION-GROUP
    NOTIFICATIONS {
        tmnxLmpVRtrTeLinkPropMismatch,
        tmnxLmpVRtrTeLinkPropMismatchClr,
        tmnxLmpVRtrDbLinkPropMismatch,
        tmnxLmpVRtrDbLinkPropMismatchClr,
        tmnxLmpVRtrControlChannelState,
        tmnxLmpVRtrTeLinkState
    }
    STATUS      current
    DESCRIPTION
        "The group of notifications supporting the Link Management Protocol
         (LMP) configuration for the virtual router instances on Nokia SROS
         series systems for Release 13.0."
    ::= { tmnxLmpV13v0Groups 8 }

tmnxLmpV15v0Groups               OBJECT IDENTIFIER ::= { tmnxLmpGroups 2 }

tmnxLmpVRtrPeerGroupV15v0        OBJECT-GROUP
    OBJECTS     {
        tmnxLmpVRtrPeerCcVRtrId,
        tmnxLmpVRtrPeerGmplsLpbkAddrType,
        tmnxLmpVRtrPeerGmplsLpbkAddress
    }
    STATUS      current
    DESCRIPTION
        "The group of additional objects maintaining the Link Management
         Protocol (LMP) Peer configuration for the virtual router instances on
         Nokia SROS series systems for Release 15.0."
    ::= { tmnxLmpV15v0Groups 1 }

tmnxLmpVRtrCtrlChannelGroupV15v0 OBJECT-GROUP
    OBJECTS     {
        tmnxLmpVRtrCcIsTunneled
    }
    STATUS      current
    DESCRIPTION
        "The group of additional objects maintaining the Link Management
         Protocol (LMP) control channel configuration for virtual router
         instances on Nokia SROS series systems for Release 15.0."
    ::= { tmnxLmpV15v0Groups 2 }

tmnxLmpNotifyPrefix              OBJECT IDENTIFIER ::= { tmnxSRNotifyPrefix 100 }

tmnxLmpNotification              OBJECT IDENTIFIER ::= { tmnxLmpNotifyPrefix 0 }

tmnxLmpVRtrTeLinkPropMismatch    NOTIFICATION-TYPE
    OBJECTS     {
        tmnxLmpVRtrTeLinkRemoteId,
        tmnxLmpVRtrTeLinkPeerNodeId
    }
    STATUS      current
    DESCRIPTION
        "[CAUSE] The tmnxLmpVRtrTeLinkPropMismatch notification is generated
         when a TE link property mismatch is detected on the node. This
         notification is only generated the first time a mismatch is detected.

         [EFFECT] The TE link is operationally down when a mismatch is
         detected.

         [RECOVERY] Ensure the TE link configuration between the local node and
         the peer node is consistent."
    ::= { tmnxLmpNotification 1 }

tmnxLmpVRtrTeLinkPropMismatchClr NOTIFICATION-TYPE
    OBJECTS     {
        tmnxLmpVRtrTeLinkRemoteId,
        tmnxLmpVRtrTeLinkPeerNodeId
    }
    STATUS      current
    DESCRIPTION
        "[CAUSE] The tmnxLmpVRtrTeLinkPropMismatchClr notification is generated
         when a TE link property mismatch is cleared.

         [EFFECT] The TE link can now service traffic.

         [RECOVERY] There is no recovery required for this notification."
    ::= { tmnxLmpNotification 2 }

tmnxLmpVRtrDbLinkPropMismatch    NOTIFICATION-TYPE
    OBJECTS     {
        tmnxLmpVRtrDbLinkRemoteId
    }
    STATUS      current
    DESCRIPTION
        "[CAUSE] The tmnxLmpVRtrDbLinkPropMismatch notification is generated
         when a DB link property mismatch is detected on the node. This
         notification is only generated the first time a mismatch is detected.

         [EFFECT] The DB link is operationally down when a mismatch is
         detected.

         [RECOVERY] Ensure the DB link configuration between the local node and
         the peer node is consistent."
    ::= { tmnxLmpNotification 3 }

tmnxLmpVRtrDbLinkPropMismatchClr NOTIFICATION-TYPE
    OBJECTS     {
        tmnxLmpVRtrDbLinkRemoteId
    }
    STATUS      current
    DESCRIPTION
        "[CAUSE] The tmnxLmpVRtrDbLinkPropMismatchClr notification is generated
         when the DB link property mismatch is cleared.

         [EFFECT] The DB link can now service traffic.

         [RECOVERY] There is no recovery required for this notification."
    ::= { tmnxLmpNotification 4 }

tmnxLmpVRtrControlChannelState   NOTIFICATION-TYPE
    OBJECTS     {
        tmnxLmpVRtrCcOperState
    }
    STATUS      current
    DESCRIPTION
        "[CAUSE] The tmnxLmpVRtrControlChannelState notification is generated
         when a control channel transitions to or from the 'up (1)' operational
         state.

         [EFFECT] If no control channels to the peer-node are up, the related
         TE links cannot be used to set up new GMPLS label-switched paths
         (LSPs).

         [RECOVERY] Ensure the control channel peer-interface is reachable."
    ::= { tmnxLmpNotification 5 }

tmnxLmpVRtrTeLinkState           NOTIFICATION-TYPE
    OBJECTS     {
        tmnxLmpVRtrTeLinkOperState
    }
    STATUS      current
    DESCRIPTION
        "[CAUSE] The tmnxLmpVRtrTeLinkState notification is generated when a TE
         link's operational state changes.

         [EFFECT] When tmnxLmpVRtrTeLinkOperState is not 'up (1)', no new GMPLS
         LSPs can be set up using this TE link.

         [RECOVERY] When tmnxLmpVRtrTeLinkOperState is 'degraded (5)', bring up
         at least one control channel with the relevant peer node."
    ::= { tmnxLmpNotification 6 }

END

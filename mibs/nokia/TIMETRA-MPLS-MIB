TIMETRA-MPLS-MIB DEFINITIONS ::= BEGIN

IMPORTS
    InterfaceIndexOrZero
                                                         FROM IF-MIB
    InetAddress, InetAddressIPv6,
    InetAddressType
                                                         FROM INET-ADDRESS-MIB
    MplsLSPID, MplsLabel,
    mplsInSegmentEntry, mplsOutSegmentEntry,
    mplsXCLspId
                                                         FROM MPLS-LSR-MIB
    MplsTunnelIndex, mplsTunnelARHopEntry,
    mplsTunnelIndex, mplsTunnelIngressLSRId,
    mplsTunnelInstance
                                                         FROM MPLS-TE-MIB
    MODULE-COMPLIANCE, NOTIFICATION-GROUP,
    OBJECT-GROUP
                                                         FROM SNMPv2-CONF
    Counter32, Counter64, Gauge32,
    Integer32, IpAddress, MODULE-IDENTITY,
    NOTIFICATION-TYPE, OBJECT-TYPE,
    Unsigned32
                                                         FROM SNMPv2-SMI
    DisplayString, RowPointer, RowStatus,
    TEXTUAL-CONVENTION, TestAndIncr,
    TimeInterval, TimeStamp, TruthValue
                                                         FROM SNMPv2-TC
    timetraSRMIBModules, tmnxSRConfs,
    tmnxSRNotifyPrefix, tmnxSRObjs
                                                         FROM TIMETRA-GLOBAL-MIB
    TFCType, TLNamedItem,
    TLNamedItemOrEmpty, TNamedItem,
    TNamedItemOrEmpty,
    TPolicyStatementNameOrEmpty,
    TmnxActionType, TmnxAdminState,
    TmnxCBFClasses, TmnxEnabledDisabled,
    TmnxMplsLabel, TmnxMplsLabelOrZero,
    TmnxMplsLspBandwidth,
    TmnxMplsTpGlobalID, TmnxMplsTpNodeID,
    TmnxNhgDownReason, TmnxOperState,
    TmnxRsvpDSTEClassType, TmnxTimeInterval,
    TmnxVRtrMplsLspID
                                                         FROM TIMETRA-TC-MIB
    vRtrID, vRtrIfIndex
                                                         FROM TIMETRA-VRTR-MIB
    ;

timetraMplsMIBModule             MODULE-IDENTITY
    LAST-UPDATED "201701010000Z"
    ORGANIZATION "Nokia"
    CONTACT-INFO
        "Nokia SROS Support
         Web: http://www.nokia.com"
    DESCRIPTION
        "This document is the SNMP MIB module to manage and provision the MPLS
         extensions for the Nokia SROS device.

         Copyright 2003-2018 Nokia. All rights reserved. Reproduction of this
         document is authorized on the condition that the foregoing copyright
         notice is included.

         This SNMP MIB module (Specification) embodies Nokia's
         proprietary intellectual property.  Nokia retains
         all title and ownership in the Specification, including any
         revisions.

         Nokia grants all interested parties a non-exclusive license to use and
         distribute an unmodified copy of this Specification in connection with
         management of Nokia products, and without fee, provided this copyright
         notice and license appear on all copies.

         This Specification is supplied 'as is', and Nokia makes no warranty,
         either express or implied, as to the use, operation, condition, or
         performance of the Specification."

    REVISION    "201701010000Z"
    DESCRIPTION
        "Rev 15.0               1 Jan 2017 00:00
         15.0 release of the TIMETRA-MPLS-MIB."

    REVISION    "201601010000Z"
    DESCRIPTION
        "Rev 14.0               1 Jan 2016 00:00
         14.0 release of the TIMETRA-MPLS-MIB."

    REVISION    "201501010000Z"
    DESCRIPTION
        "Rev 13.0               1 Jan 2015 00:00
         13.0 release of the TIMETRA-MPLS-MIB."

    REVISION    "201401010000Z"
    DESCRIPTION
        "Rev 12.0               1 Jan 2014 00:00
         12.0 release of the TIMETRA-MPLS-MIB."

    REVISION    "201102010000Z"
    DESCRIPTION
        "Rev 9.0                1 Feb 2011 00:00
         9.0 release of the TIMETRA-MPLS-MIB."

    REVISION    "200902280000Z"
    DESCRIPTION
        "Rev 7.0                28 Feb 2009 00:00
         7.0 release of the TIMETRA-MPLS-MIB."

    REVISION    "200807010000Z"
    DESCRIPTION
        "Rev 6.1                01 Jul 2008 00:00
         6.1 release of the TIMETRA-MPLS-MIB."

    REVISION    "200801010000Z"
    DESCRIPTION
        "Rev 6.0                01 Jan 2008 00:00
         6.0 release of the TIMETRA-MPLS-MIB."

    REVISION    "200701010000Z"
    DESCRIPTION
        "Rev 5.0                01 Jan 2007 00:00
         5.0 release of the TIMETRA-MPLS-MIB."

    REVISION    "200603230000Z"
    DESCRIPTION
        "Rev 4.0                23 Mar 2006 00:00
         4.0 release of the TIMETRA-MPLS-MIB."

    REVISION    "200508310000Z"
    DESCRIPTION
        "Rev 3.0                31 Aug 2005 00:00
         3.0 release of the TIMETRA-MPLS-MIB."

    REVISION    "200501240000Z"
    DESCRIPTION
        "Rev 2.1                24 Jan 2005 00:00
         2.1 release of the TIMETRA-MPLS-MIB."

    REVISION    "200401150000Z"
    DESCRIPTION
        "Rev 2.0                15 Jan 2004 00:00
         2.0 release of the TIMETRA-MPLS-MIB."

    REVISION    "200308150000Z"
    DESCRIPTION
        "Rev 1.2                15 Aug 2003 00:00
         1.2 release of the TIMETRA-MPLS-MIB."

    REVISION    "200009070000Z"
    DESCRIPTION
        "Rev 1.0                20 Jan 2003 00:00
         1.0 Release of the TIMETRA-MPLS-MIB."

    REVISION    "200008140000Z"
    DESCRIPTION
        "Rev 0.1                14 Aug 2000 00:00
         Initial version of the TIMETRA-MPLS-MIB."

    ::= { timetraSRMIBModules 6 }

TmnxMplsLspFailCode              ::= TEXTUAL-CONVENTION
    STATUS      current
    DESCRIPTION
        "TmnxMplsLspFailCode is an enumerated integer that defines the reason
         for LSP Path and LSP Crossconnect failure."
    SYNTAX      INTEGER {
        noError                    (0),
        admissionControlError      (1),
        noRouteToDestination       (2),
        trafficControlSystemError  (3),
        routingError               (4),
        noResourcesAvailable       (5),
        badNode                    (6),
        routingLoop                (7),
        labelAllocationError       (8),
        badL3PID                   (9),
        tunnelLocallyRepaired      (10),
        unknownObjectClass         (11),
        unknownCType               (12),
        noEgressMplsInterface      (13),
        noEgressRsvpInterface      (14),
        looseHopsInFRRLsp          (15),
        unknown                    (16),
        retryExceeded              (17),
        noCspfRouteOwner           (18),
        noCspfRouteToDestination   (19),
        hopLimitExceeded           (20),
        looseHopsInManualBypassLsp (21),
        emptyPathInManualBypassLsp (22),
        lspFlowControlled          (23),
        srlgSecondaryNotDisjoint   (24),
        srlgPrimaryCspfDisabled    (25),
        srlgPrimaryPathDown        (26),
        localLinkMaintenance       (27),
        unexpectedCtObject         (28),
        unsupportedCt              (29),
        invalidCt                  (30),
        invCtAndSetupPri           (31),
        invCtAndHoldPri            (32),
        invCtAndSetupAndHoldPri    (33),
        localNodeMaintenance       (34),
        softPreemption             (35),
        p2mpNotSupported           (36),
        badXro                     (37),
        localNodeInXro             (38),
        routeBlockedByXro          (39),
        xroTooComplex              (40),
        rsvpNotSupported           (41),
        conflictingAdminGroups     (42),
        nodeInIgpOverload          (43),
        srTunnelDown               (44),
        fibAddFailed               (45),
        labelStackExceeded         (46),
        pccDown                    (47),
        pccError                   (48),
        pceDown                    (49),
        pceError                   (50),
        pceUpdateWithEmptyEro      (51),
        pceInitLspDisabled         (52),
        adminDown                  (53),
        sidHopsInRsvpLsp           (54),
        ipv6HopsInRsvpLsp          (55),
        ipv4HopsInIpv6Lsp          (56),
        ipv6HopsInIpv4Lsp          (57),
        sidHopsInIpv6Lsp           (58),
        srlgPathWithSidHops        (59),
        mplsV4Down                 (60),
        mplsV6Down                 (61),
        lspAdminDown               (62),
        pathAdminDown              (63),
        templateAdminDown          (64)
    }

TmnxMplsLabelOwner               ::= TEXTUAL-CONVENTION
    STATUS      current
    DESCRIPTION
        "TmnxMplsLabelOwner is an enumerated integer that specifies the module
         that owns a particular MPLS label."
    SYNTAX      INTEGER {
        none   (0),
        rsvp   (1),
        tldp   (2),
        ildp   (3),
        svcmgr (4),
        bgp    (5),
        mirror (6),
        static (7),
        vprn   (8),
        sr     (9)
    }

TmnxMplsOperDownReasonCode       ::= TEXTUAL-CONVENTION
    STATUS      current
    DESCRIPTION
        "TmnxMplsOperDownReasonCode is an enumerated integer that specifies the
         reason that the MPLS instance is operationally down."
    SYNTAX      INTEGER {
        operUp               (0),
        adminDown            (1),
        noResources          (2),
        systemIpDown         (3),
        iomFailure           (4),
        clearDown            (5),
        ipv6TeRtrDown        (6),
        ipv6TeRtrAddrChanged (7),
        ipv6TeRtrIdIntfDown  (8)
    }

TmnxMplsMBBType                  ::= TEXTUAL-CONVENTION
    STATUS      current
    DESCRIPTION
        "TmnxMplsMBBType is an enumerated integer that specifies the type of
         make-before-break (MBB)."
    SYNTAX      INTEGER {
        none               (0),
        configChange       (1),
        timerBasedResignal (2),
        manualResignal     (3),
        globalRevert       (4),
        delayedRetry       (5),
        gracefulShutdown   (6),
        softPreemption     (7),
        pathChange         (8),
        autoBandwidth      (9),
        pceLspUpdate       (10)
    }

TmnxMplsP2mpInstFailCode         ::= TEXTUAL-CONVENTION
    STATUS      current
    DESCRIPTION
        "TmnxMplsP2mpInstFailCode is an enumerated integer that defines the
         reason for P2MP instance going down."
    SYNTAX      INTEGER {
        noError          (0),
        noS2LOperational (1)
    }

TmnxMplsRouterId                 ::= TEXTUAL-CONVENTION
    DISPLAY-HINT "d"
    STATUS      current
    DESCRIPTION
        "The value of TmnxMplsRouterId provides a 32-bit, unsigned integer
         uniquely identifying the router in the Autonomous System. To ensure
         uniqueness, this may default to the value of one of the router's IPv4
         host addresses if IPv4 is configured on the router."
    SYNTAX      Unsigned32 (0..4294967295)

TmnxMplsLspAutoBWLastAdjCause    ::= TEXTUAL-CONVENTION
    STATUS      current
    DESCRIPTION
        "TmnxMplsLspAutoBWLastAdjCause is an enumerated integer that specifies
         cause of auto-bandwidth last adjustment."
    SYNTAX      INTEGER {
        none             (0),
        manual           (1),
        normal           (2),
        overflow         (3),
        vllCAC           (4),
        underflow        (5),
        activePathChange (6)
    }

TmnxMplsLspBgpRSVPLSPTunState    ::= TEXTUAL-CONVENTION
    STATUS      current
    DESCRIPTION
        "TmnxMplsLspBgpRSVPLSPTunState is an enumerated integer that specifies
         whether an RSVP LSP is allowed or blocked in its usage as a transport
         LSP for BGP tunnel routes.

         In 'include(1)' mode, an RSVP LSPs is allowed to be used as transport
         LSP for BGP tunnel routes.

         In 'exclude(2)' mode, an RSVP LSP is not allowed to be used as a
         transport LSP for BGP tunnel routes."
    SYNTAX      INTEGER {
        include (1),
        exclude (2)
    }

TmnxMplsLspAddrType              ::= TEXTUAL-CONVENTION
    STATUS      current
    DESCRIPTION
        "TmnxMplsLspAddrType is an enumerated integer that specifies the
         address type for an MPLS LSP."
    SYNTAX      INTEGER {
        unknown (0),
        ipv4    (1),
        nodeId  (2),
        ipv6    (3)
    }

tmnxMplsObjs                     OBJECT IDENTIFIER ::= { tmnxSRObjs 6 }

vRtrMplsLspTable                 OBJECT-TYPE
    SYNTAX      SEQUENCE OF VRtrMplsLspEntry
    MAX-ACCESS  not-accessible
    STATUS      current
    DESCRIPTION
        "The vRtrMplsLspTable has an entry for each Labeled Switch Path (LSP)
         configured for a virtual router in the system."
    ::= { tmnxMplsObjs 1 }

vRtrMplsLspEntry                 OBJECT-TYPE
    SYNTAX      VRtrMplsLspEntry
    MAX-ACCESS  not-accessible
    STATUS      current
    DESCRIPTION
        "Each row entry represents a Labeled Switch Path (LSP) configured
         for a virtual router in the system.  Entries can be created and
         deleted via SNMP SET operations.  Setting RowStatus to 'active'
         requires vRtrMplsLspName to have been assigned a valid value."
    INDEX       {
        vRtrID,
        vRtrMplsLspIndex
    }
    ::= { vRtrMplsLspTable 1 }

VRtrMplsLspEntry                 ::= SEQUENCE
{
    vRtrMplsLspIndex                 TmnxVRtrMplsLspID,
    vRtrMplsLspRowStatus             RowStatus,
    vRtrMplsLspLastChange            TimeStamp,
    vRtrMplsLspName                  TLNamedItemOrEmpty,
    vRtrMplsLspAdminState            TmnxAdminState,
    vRtrMplsLspOperState             TmnxOperState,
    vRtrMplsLspFromAddr              IpAddress,
    vRtrMplsLspToAddr                IpAddress,
    vRtrMplsLspType                  INTEGER,
    vRtrMplsLspOutSegIndx            Integer32,
    vRtrMplsLspRetryTimer            Unsigned32,
    vRtrMplsLspRetryLimit            Unsigned32,
    vRtrMplsLspMetric                Unsigned32,
    vRtrMplsLspDecrementTtl          TruthValue,
    vRtrMplsLspCspf                  TruthValue,
    vRtrMplsLspFastReroute           TruthValue,
    vRtrMplsLspFRHopLimit            Unsigned32,
    vRtrMplsLspFRBandwidth           Unsigned32,
    vRtrMplsLspClassOfService        TNamedItemOrEmpty,
    vRtrMplsLspSetupPriority         Unsigned32,
    vRtrMplsLspHoldPriority          Unsigned32,
    vRtrMplsLspRecord                TruthValue,
    vRtrMplsLspPreference            Unsigned32,
    vRtrMplsLspBandwidth             Integer32,
    vRtrMplsLspBwProtect             TruthValue,
    vRtrMplsLspHopLimit              Unsigned32,
    vRtrMplsLspNegotiatedMTU         Unsigned32,
    vRtrMplsLspRsvpResvStyle         INTEGER,
    vRtrMplsLspRsvpAdspec            TruthValue,
    vRtrMplsLspFRMethod              INTEGER,
    vRtrMplsLspFRNodeProtect         TruthValue,
    vRtrMplsLspAdminGroupInclude     Unsigned32,
    vRtrMplsLspAdminGroupExclude     Unsigned32,
    vRtrMplsLspAdaptive              TruthValue,
    vRtrMplsLspInheritance           Unsigned32,
    vRtrMplsLspOptimizeTimer         Unsigned32,
    vRtrMplsLspOperFastReroute       TruthValue,
    vRtrMplsLspFRObject              TruthValue,
    vRtrMplsLspHoldTimer             Unsigned32,
    vRtrMplsLspCspfTeMetricEnabled   TruthValue,
    vRtrMplsLspP2mpId                Unsigned32,
    vRtrMplsLspClassType             TmnxRsvpDSTEClassType,
    vRtrMplsLspOperMetric            Unsigned32,
    vRtrMplsLspLdpOverRsvpInclude    TruthValue,
    vRtrMplsLspLeastFill             TruthValue,
    vRtrMplsLspVprnAutoBindInclude   TruthValue,
    vRtrMplsLspMainCTRetryLimit      Unsigned32,
    vRtrMplsLspIgpShortcut           TruthValue,
    vRtrMplsLspOriginTemplate        TNamedItemOrEmpty,
    vRtrMplsLspAutoBandwidth         TruthValue,
    vRtrMplsLspCspfToFirstLoose      TruthValue,
    vRtrMplsLspPropAdminGroup        TruthValue,
    vRtrMplsLspBgpShortcut           TruthValue,
    vRtrMplsLspBgpTransportTunnel    TmnxMplsLspBgpRSVPLSPTunState,
    vRtrMplsLspSwitchStbyPath        TmnxActionType,
    vRtrMplsLspSwitchStbyPathIndex   MplsTunnelIndex,
    vRtrMplsLspSwitchStbyPathForce   TruthValue,
    vRtrMplsLspExcludeNodeAddrType   InetAddressType,
    vRtrMplsLspExcludeNodeAddr       InetAddress,
    vRtrMplsLspIgpShortcutLfaType    INTEGER,
    vRtrMplsLspToAddrType            TmnxMplsLspAddrType,
    vRtrMplsLspFromAddrType          TmnxMplsLspAddrType,
    vRtrMplsLspToNodeId              TmnxMplsTpNodeID,
    vRtrMplsLspFromNodeId            TmnxMplsTpNodeID,
    vRtrMplsLspDestGlobalId          TmnxMplsTpGlobalID,
    vRtrMplsLspDestTunnelNum         Unsigned32,
    vRtrMplsLspFRPropAdminGroup      TruthValue,
    vRtrMplsLspIgpShortcutRelOffset  Integer32,
    vRtrMplsLspRevertTimer           Unsigned32,
    vRtrMplsLspRevertTimeRemain      Unsigned32,
    vRtrMplsLspLoadBalancingWeight   Unsigned32,
    vRtrMplsLspClassFwdingEnabled    TruthValue,
    vRtrMplsLspFC                    TmnxCBFClasses,
    vRtrMplsLspBfdTemplateName       TNamedItemOrEmpty,
    vRtrMplsLspBfdEnable             TruthValue,
    vRtrMplsLspBfdPingIntvl          Unsigned32,
    vRtrMplsLspNgFromAddr            InetAddress,
    vRtrMplsLspNgToAddr              InetAddress
}

vRtrMplsLspIndex                 OBJECT-TYPE
    SYNTAX      TmnxVRtrMplsLspID
    MAX-ACCESS  accessible-for-notify
    STATUS      current
    DESCRIPTION
        "The value of vRtrMplsLspIndex specifies the Labeled Switch
         Path (LSP) index for this virtual router in the Nokia
         SROS system.  It is a unique value among entries with the
         same value of vRtrID."
    ::= { vRtrMplsLspEntry 1 }

vRtrMplsLspRowStatus             OBJECT-TYPE
    SYNTAX      RowStatus
    MAX-ACCESS  read-create
    STATUS      current
    DESCRIPTION
        "The row status used for creation, deletion, or control
         of vRtrMplsLspTable entries.  Before the row can be
         placed into the 'active' state vRtrMplsLspName must
         have been assigned a valid value."
    ::= { vRtrMplsLspEntry 2 }

vRtrMplsLspLastChange            OBJECT-TYPE
    SYNTAX      TimeStamp
    MAX-ACCESS  read-only
    STATUS      current
    DESCRIPTION
        "The sysUpTime when this row was last modified."
    ::= { vRtrMplsLspEntry 3 }

vRtrMplsLspName                  OBJECT-TYPE
    SYNTAX      TLNamedItemOrEmpty
    MAX-ACCESS  read-create
    STATUS      current
    DESCRIPTION
        "Administrative name for this Labeled Switch Path. The vRtrMplsLspName
         must be unique within a virtual router instance.

         When the value of the object vRtrMplsLspType is 'p2mpAuto', LSPs
         are auto-created dynamically by the system using LSP template values
         configured in the associated row entry of  vRtrMplsLspTemplateTable.
         For auto-created LSPs, vRtrMplsLspName can have a maximum of
         64 characters which consists of vRtrMplsLspTemplateName, vRtrID
         and MTTM(Multicast Tunnel Table Manager)Identifier.

         If vRtrMplsLspType is not 'p2mpAuto', 'meshP2p' or 'oneHopP2p',
         vRtrMplsLspName can have a maximum of 32 characters. "
    ::= { vRtrMplsLspEntry 4 }

vRtrMplsLspAdminState            OBJECT-TYPE
    SYNTAX      TmnxAdminState
    MAX-ACCESS  read-create
    STATUS      current
    DESCRIPTION
        "The desired administrative state for this LSP."
    DEFVAL      { outOfService }
    ::= { vRtrMplsLspEntry 5 }

vRtrMplsLspOperState             OBJECT-TYPE
    SYNTAX      TmnxOperState
    MAX-ACCESS  read-only
    STATUS      current
    DESCRIPTION
        "The current operational state of this LSP."
    ::= { vRtrMplsLspEntry 6 }

vRtrMplsLspFromAddr              OBJECT-TYPE
    SYNTAX      IpAddress
    MAX-ACCESS  read-create
    STATUS      obsolete
    DESCRIPTION
        "The vRtrMplsLspFromAddr specifies the source address of this LSP.

         When vRtrMplsLspFromAddrType is 'ipv4', vRtrMplsLspFromAddr should
         also be specified.

         If vRtrMplsLspFromAddr has not been explicitly set, the system IP
         address will be used.

         vRtrMplsLspFromAddr is obsoleted in 20.0, replaced by
         vRtrMplsLspNgFromAddr"
    ::= { vRtrMplsLspEntry 7 }

vRtrMplsLspToAddr                OBJECT-TYPE
    SYNTAX      IpAddress
    MAX-ACCESS  read-create
    STATUS      obsolete
    DESCRIPTION
        "The vRtrMplsLspToAddr specifies the destination address of this LSP.

         When vRtrMplsLspToAddrType is 'ipv4', vRtrMplsLspToAddr should also be
         specified.

         When vRtrMplsLspToAddrType is 'ipv6', vRtrMplsLspNgToAddr should also
         be specified.

         vRtrMplsLspToAddr is obsoleted in 20.0, replaced by
         vRtrMplsLspNgToAddr"
    ::= { vRtrMplsLspEntry 8 }

vRtrMplsLspType                  OBJECT-TYPE
    SYNTAX      INTEGER {
        unknown        (1),
        dynamic        (2),
        static         (3),
        bypassOnly     (4),
        p2mpLsp        (5),
        p2mpAuto       (6),
        mplsTp         (7),
        meshP2p        (8),
        oneHopP2p      (9),
        srTe           (10),
        meshP2pSrTe    (11),
        oneHopP2pSrTe  (12),
        pceInitP2pSrTe (13)
    }
    MAX-ACCESS  read-create
    STATUS      current
    DESCRIPTION
        "The value of object vRtrMplsLspType specifies whether the label value
         is statically or dynamically assigned or whether the LSP will be used
         exclusively for bypass protection. The value 'p2mpLsp' will be used to
         indicate point to multipoint LSPs used for multicast traffic.

         When the value of the vRtrMplsLspType is 'p2mpAuto', it specifies that
         the LSP is auto-created dynamically by the system and the row entry
         is dynamically created by the system  using LSP Template values
         configured in the associated row entry of vRtrMplsLspTemplateTable.

         The value 'mplsTp' specifies that the LSP is an MPLS-TP Static LSP.

         When the value of the vRtrMplsLspType is 'meshP2p', it specifies that
         the LSP is a mesh point-to-point created dynamically by the system and
         the row entry is dynamically created by the system  using Mesh LSP
         Template values configured in the associated row entry of
         vRtrMplsLspTemplateTable.

         When the value of the vRtrMplsLspType is 'oneHopP2p', it specifies
         that the LSP is a one-hop point-to-point LSP created dynamically by
         the system and the row entry is dynamically created by the system
         using One-Hop LSP Template values configured in the associated row
         entry of vRtrMplsLspTemplateTable.

         When the value of vRtrMplsLspType is set to 'segmentRouting', it
         specifies that the LSP is used for segment routing and vRtrMplsLspType
         can only be set to 'segmentRouting' when the value of vRtrMplsLspIndex
         is greater than 65535.

         A 'wrongValue' error is returned if an attempt is made to set an
         object in the row entry where the value of vRtrMplsLspType is
         'p2mpAuto'.

         When value of the vRtrMplsLspType is 'meshP2pSrTe', it specifies that
         the segment routing LSP is a mesh point-to-point created dynamically
         by the system and the row entry is dynamically created by the system
         using meshP2PSrTe LSP Template values configured in the associated row
         entry of vRtrMplsLspTemplateTable.

         When the value of the vRtrMplsLspType is 'oneHopP2pSrTe', it specifies
         that the LSP is a one-hop point-to-point segment routing LSP created
         dynamically by the system and the row entry is dynamically created by
         the system using onehopP2PSrTe LSP Template values configured in the
         associated row entry of vRtrMplsLspTemplateTable.

         When value of the vRtrMplsLspType is 'pceInitP2pSrTe', it specifies
         that the point-to-point segment routing LSP is created dynamically on
         receiving a PCE-Initiated Message from PCC, using pceInitP2pSrTe LSP
         Template values configured in the associated row entry of
         vRtrMplsLspTemplateTable."
    DEFVAL      { dynamic }
    ::= { vRtrMplsLspEntry 9 }

vRtrMplsLspOutSegIndx            OBJECT-TYPE
    SYNTAX      Integer32 (0..2147483647)
    MAX-ACCESS  read-create
    STATUS      current
    DESCRIPTION
        "The vRtrMplsLspOutSegIndx is the index value of the entry in
         the mplsOutSegmentTable associated with this vRtrMplsLspEntry
         when vRtrMplsLspType is 'static'.  If vRtrMplsLspType is
         'dynamic', the value of this object will be zero (0)."
    DEFVAL      { 0 }
    ::= { vRtrMplsLspEntry 10 }

vRtrMplsLspRetryTimer            OBJECT-TYPE
    SYNTAX      Unsigned32 (1..600)
    UNITS       "seconds"
    MAX-ACCESS  read-create
    STATUS      current
    DESCRIPTION
        "The value of vRtrMplsLspRetryTimer specifies the time in seconds the
         software will wait before attempting the establish the failed LSP."
    DEFVAL      { 30 }
    ::= { vRtrMplsLspEntry 11 }

vRtrMplsLspRetryLimit            OBJECT-TYPE
    SYNTAX      Unsigned32 (0..10000)
    MAX-ACCESS  read-create
    STATUS      current
    DESCRIPTION
        "The value of vRtrMplsLspRetryLimit specifies the number of
         attempts the software should make to reestablish a failed LSP
         before the LSP is disabled.  A value of 0 indicates that an
         infinite number of retry attempts should be made."
    DEFVAL      { 0 }
    ::= { vRtrMplsLspEntry 12 }

vRtrMplsLspMetric                OBJECT-TYPE
    SYNTAX      Unsigned32 (0 | 1..16777215)
    MAX-ACCESS  read-create
    STATUS      current
    DESCRIPTION
        "The value of vRtrMplsLspMetric specifies the metric for this
         LSP which is used to select an LSP among a set of LSPs which are
         destined to the same egress 7x50 router.  The LSP with the lowest
         metric will be selected.

         In LDP-over-RSVP, LDP performs a lookup in the Routing Table
         Manager (RTM) which provides the next hop to the destination PE
         and the advertising router (ABR or destination PE itself).  If the
         advertising router matches the targeted LDP peer, LDP then
         performs a second lookup for the advertising router in the Tunnel
         Table Manager (TTM). This lookup returns the best RSVP LSP to use
         to forward packets for an LDP FEC learned through the targeted
         LDP session.  The lookup returns the LSP with the lowest metric.
         If multiple LSPs have the same metric, then the result of the
         lookup will be to select the first one available in the TTM.

         A value of '0' indicates metric is not to be used."
    DEFVAL      { 0 }
    ::= { vRtrMplsLspEntry 13 }

vRtrMplsLspDecrementTtl          OBJECT-TYPE
    SYNTAX      TruthValue
    MAX-ACCESS  read-create
    STATUS      obsolete
    DESCRIPTION
        "When the value of vRtrMplsLspDecrementTtl is 'true', the ingress
         ESR writes the TTL of the IP packet into the label and each
         transit ESR decrements the TTL in the label.  At the egress ESR
         the TTL value from the label is written into the IP packet.

         When the value of vRtrMplsLspDecrementTtl is 'false', the ingress ESR
         ignores the IP packet TTL and writes the value of 255 into the label;
         and the egress ESR does not write the label's TTL into the IP packet.

         This object was made obsolete in release 11.0."
    DEFVAL      { true }
    ::= { vRtrMplsLspEntry 14 }

vRtrMplsLspCspf                  OBJECT-TYPE
    SYNTAX      TruthValue
    MAX-ACCESS  read-create
    STATUS      obsolete
    DESCRIPTION
        "When the value of vRtrMplsLspCspf is 'true', CSPF computation
         for constrained-path LSP is enabled.  When the value of
         vRtrMplsLspCspf is 'false' CSPF computation is disabled."
    DEFVAL      { false }
    ::= { vRtrMplsLspEntry 15 }

vRtrMplsLspFastReroute           OBJECT-TYPE
    SYNTAX      TruthValue
    MAX-ACCESS  read-create
    STATUS      current
    DESCRIPTION
        "When the value of vRtrMplsLspFastReroute is 'true', fast reroute
         is enabled.  A pre-computed detour LSP is created from each node
         in the primary path of this LSP.  In case of a failure of a link
         or LSP between two nodes, traffic is immediately rerouted on the
         pre-computed detour LSP thus avoiding packet loss.  Each node
         along the primary path of the LSP tries to establish a detour LSP
         as follows:  Each upstream node will setup a detour LSP that
         avoids only the immediate downstream node and merges back onto
         the actual path of the LSP as soon as possible.  The detour LSP
         may take one or more hops (up to the value of vRtrMplsLspFRHopLimit)
         before merging back onto the main LSP path.

         When the upstream node detects a downstream link or node failure, it
         immediately send traffic for that LSP on the detour path and at the
         same time signals back to the ingress ESR about the failure.

         Fast reroute applies only to the primary path of this LSP. No
         configuration is required on the transit hops of the LSP. The ingress
         ESR will signal all intermediate ESRs using RSVP to setup their
         detours.

         When the value of vRtrMplsLspFastReroute is 'false', fast rerouting is
         disabled."
    DEFVAL      { false }
    ::= { vRtrMplsLspEntry 16 }

vRtrMplsLspFRHopLimit            OBJECT-TYPE
    SYNTAX      Unsigned32 (0..255)
    MAX-ACCESS  read-create
    STATUS      current
    DESCRIPTION
        "The value of vRtrMplsLspFRHopLimit specifies the total number of hops
         a detour LSP can take before merging back onto the main LSP path."
    DEFVAL      { 16 }
    ::= { vRtrMplsLspEntry 17 }

vRtrMplsLspFRBandwidth           OBJECT-TYPE
    SYNTAX      Unsigned32
    UNITS       "megabps"
    MAX-ACCESS  read-create
    STATUS      current
    DESCRIPTION
        "The value of vRtrMplsLspFRBandwidth specified the amount of bandwidth
         in megabits per second (Mbps) to be reserved for the detour LSP. A
         value of zero (0) indicates that no bandwidth is reserved."
    DEFVAL      { 0 }
    ::= { vRtrMplsLspEntry 18 }

vRtrMplsLspClassOfService        OBJECT-TYPE
    SYNTAX      TNamedItemOrEmpty
    MAX-ACCESS  read-create
    STATUS      obsolete
    DESCRIPTION
        "The name of the class of service value to be assigned to all
         packets on the LSP is specified with vRtrMplsLspClassOfService.
         The EXP bits in the MPLS header are set based on the global
         mapping table that specified the mapping between the forwarding
         class and the EXP bits.  When class of service is specified,
         all packets will be marked with the same EXP bits that match
         the vRtrMplsLspClassOfService name in the mapping table.

         An empty string, ''H, specifies no class of service.  Packets
         are assigned EXP bits based on the same mapping table, however
         each packet is marked with EXP bits based on the forwarding
         class from which it is serviced.

         When the value of vRtrMplsLspPathCosSource is set to 'inherit', the
         value of vRtrMplsLspClassOfService is applied to that specific
         LSP/path.

         This object was made obsolete in release 11.0."
    DEFVAL      { ''H }
    ::= { vRtrMplsLspEntry 19 }

vRtrMplsLspSetupPriority         OBJECT-TYPE
    SYNTAX      Unsigned32 (0..7)
    MAX-ACCESS  read-create
    STATUS      current
    DESCRIPTION
        "The value of vRtrMplsLspSetupPriority specifies the setup priority
         to use when insufficient bandwidth is available to setup a LSP.
         The setup priority is compared against the hold priority of
         existing LSPs.  If the setup priority is higher than the hold
         priority of the established LSPs, this LSP may preempt the other
         LSPs.  A value of zero (0) is the highest priority and a value
         of seven (7) is the lowest priority.

         When the value of vRtrMplsLspPathSetupPriority is set to '-1', the
         value of vRtrMplsLspSetupPriority is applied to that specific
         LSP/path."
    DEFVAL      { 7 }
    ::= { vRtrMplsLspEntry 20 }

vRtrMplsLspHoldPriority          OBJECT-TYPE
    SYNTAX      Unsigned32 (0..7)
    MAX-ACCESS  read-create
    STATUS      current
    DESCRIPTION
        "The value of vRtrMplsLspHoldPriority specifies the hold priority
         to use when insufficient bandwidth is available to setup a LSP.
         The setup priority is compared against the hold priority of
         existing LSPs.  If the setup priority is higher than the hold
         priority of the established LSPs, this LSP may preempt the other
         LSPs.  A value of zero (0) is the highest priority and a value
         of seven (7) is the lowest priority.

         When the value of vRtrMplsLspPathHoldPriority is set to '-1', the
         value of vRtrMplsLspHoldPriority is applied to that specific LSP/path."
    DEFVAL      { 0 }
    ::= { vRtrMplsLspEntry 21 }

vRtrMplsLspRecord                OBJECT-TYPE
    SYNTAX      TruthValue
    MAX-ACCESS  read-create
    STATUS      current
    DESCRIPTION
        "When the value of vRtrMplsLspRecord is 'true', recording of all the
         hops that a LSP traverses is enabled.

         When the value of vRtrMplsLspRecord is 'false, recording of all the
         hops that a LSP traverses is disabled."
    DEFVAL      { true }
    ::= { vRtrMplsLspEntry 22 }

vRtrMplsLspPreference            OBJECT-TYPE
    SYNTAX      Unsigned32 (1..255)
    MAX-ACCESS  read-create
    STATUS      obsolete
    DESCRIPTION
        "The value of vRtrMplsLspPreference specifies the preference for
         the LSP.  This value is used for load balancing between multiple
         LSPs that exist between the same ingress and egress routers.
         By default, traffic is load balanced among the LSPs, since all
         LSPs have the same preference.  To prefer one LSP over another,
         change the preference value for that LSP.  The LSP with the
         lowest preference is used.

         This object was made obsolete in release 11.0."
    DEFVAL      { 255 }
    ::= { vRtrMplsLspEntry 23 }

vRtrMplsLspBandwidth             OBJECT-TYPE
    SYNTAX      Integer32
    UNITS       "megabps"
    MAX-ACCESS  read-create
    STATUS      obsolete
    DESCRIPTION
        "The value of vRtrMplsLspBandwidth specifies the amount of bandwidth in
         megabits per second (Mbps) to be reserved for the LSP. A value of zero
         (0) indicates that no bandwidth is reserved.

         When vRtrMplsLspPathBandwidth is set to -1, the value of
         vRtrMplsLspBandwidth is applied to that specific LSP/path."
    DEFVAL      { 0 }
    ::= { vRtrMplsLspEntry 24 }

vRtrMplsLspBwProtect             OBJECT-TYPE
    SYNTAX      TruthValue
    MAX-ACCESS  read-create
    STATUS      obsolete
    DESCRIPTION
        "When vRtrMplsLspBwProtect has a value of 'true', bandwidth
         protection is enabled on a LSP.  LSPs that reserve bandwidth
         will be used for EF services where customers need guaranteed
         bandwidth.  It is expected that multiple EF services will be
         assigned to a single LSP.  When bandwidth protection is
         enabled on an LSP, each time this LSP is used for a certain
         service the bandwidth allocated on that service is deducted
         from the bandwidth reserved for the LSP.  Once the bandwidth is
         exhausted on the LSP, the ESR will provide feedback to the
         provider indicating that this LSP has exhausted its resources.

         This object was made obsolete in release 11.0."
    DEFVAL      { false }
    ::= { vRtrMplsLspEntry 25 }

vRtrMplsLspHopLimit              OBJECT-TYPE
    SYNTAX      Unsigned32 (2..255)
    MAX-ACCESS  read-create
    STATUS      current
    DESCRIPTION
        "The value of vRtrMplsLspHopLimit specifies the maximum number
         of hops that a LSP will traverse including the ingress and
         egress ESRs.  A LSP will not be setup if the hop limit is
         exceeded.

         When the value of vRtrMplsLspPathHopLimit is set to zero (0), the
         value of vRtrMplsLspHopLimit is applied to that specific LSP/path."
    DEFVAL      { 255 }
    ::= { vRtrMplsLspEntry 26 }

vRtrMplsLspNegotiatedMTU         OBJECT-TYPE
    SYNTAX      Unsigned32
    MAX-ACCESS  read-only
    STATUS      current
    DESCRIPTION
        "The value of vRtrMplsLspNegotiatedMTU specifies the size for the
         Maximum transmission unit (MTU) that is negotiated during LSP
         establishment."
    DEFVAL      { 0 }
    ::= { vRtrMplsLspEntry 27 }

vRtrMplsLspRsvpResvStyle         OBJECT-TYPE
    SYNTAX      INTEGER {
        se (1),
        ff (2)
    }
    MAX-ACCESS  read-create
    STATUS      current
    DESCRIPTION
        "The value of vRtrMplsLspRsvpResvStyle specifies the reservation style
         for RSVP. The reservation style can be set to 'Shared- Explicit' (se)
         or 'Fixed-Filter' (ff)."
    DEFVAL      { se }
    ::= { vRtrMplsLspEntry 28 }

vRtrMplsLspRsvpAdspec            OBJECT-TYPE
    SYNTAX      TruthValue
    MAX-ACCESS  read-create
    STATUS      current
    DESCRIPTION
        "When the value of vRtrMplsLspRsvpAdspec is 'true', the ADSPEC object
         will be included in RSVP messages. When the value of
         vRtrMplsLspRsvpAdspec is 'false', the ADSPEC object will not be
         included in RSVP messages."
    DEFVAL      { false }
    ::= { vRtrMplsLspEntry 29 }

vRtrMplsLspFRMethod              OBJECT-TYPE
    SYNTAX      INTEGER {
        oneToOneBackup (1),
        facilityBackup (2)
    }
    MAX-ACCESS  read-create
    STATUS      current
    DESCRIPTION
        "The value of vRtrMplsLspFRMethod specifies the fast reroute method
         used.

         In the 'One-to-one Backup' method, a backup LSP is established which
         will intersect the original LSP somewhere downstream of the point of
         link or node failure. For each LSP that is backed up, a separate
         backup LSP is established.

         In the 'Facility Backup' method, instead of creating a separate LSP
         for every LSP that is to be backed up, a single LSP is created which
         serves as a backup for a set of LSPs. Such an LSP tunnel is called a
         'bypass tunnel'."
    DEFVAL      { oneToOneBackup }
    ::= { vRtrMplsLspEntry 30 }

vRtrMplsLspFRNodeProtect         OBJECT-TYPE
    SYNTAX      TruthValue
    MAX-ACCESS  read-create
    STATUS      current
    DESCRIPTION
        "Setting the value of vRtrMplsLspFRNodeProtect to 'true' enables node
         protection i.e. protection against the failure of a node on the LSP.

         Setting the value to 'false' disables node protection."
    DEFVAL      { true }
    ::= { vRtrMplsLspEntry 31 }

vRtrMplsLspAdminGroupInclude     OBJECT-TYPE
    SYNTAX      Unsigned32
    MAX-ACCESS  read-create
    STATUS      current
    DESCRIPTION
        "The value of vRtrMplsLspAdminGroupInclude is a bit-map that specifies
         a list of admin groups that should be included when this LSP is setup.
         If bit 'n' is set, then the admin group with value 'n' is included for
         this LSP. This implies that each link that this LSP goes through must
         be associated with at least one of the admin groups in the include
         list.

         By default, all admin groups are in the include list."
    DEFVAL      { '00000000'H }
    ::= { vRtrMplsLspEntry 32 }

vRtrMplsLspAdminGroupExclude     OBJECT-TYPE
    SYNTAX      Unsigned32
    MAX-ACCESS  read-create
    STATUS      current
    DESCRIPTION
        "The value of vRtrMplsLspAdminGroupExclude is a bit-map that specifies
         a list of admin groups that should be excluded when this LSP is setup.
         If bit 'n' is set, then the admin group with value 'n' is excluded for
         this LSP. This implies that each link that this LSP goes through must
         not be associated with any of the admin groups in the exclude list.

         By default, no admin groups are in the exclude list."
    DEFVAL      { '00000000'H }
    ::= { vRtrMplsLspEntry 33 }

vRtrMplsLspAdaptive              OBJECT-TYPE
    SYNTAX      TruthValue
    MAX-ACCESS  read-create
    STATUS      current
    DESCRIPTION
        "Setting the value of vRtrMplsLspAdaptive to 'true' enables
         make-before-break functionality for the LSP. When the attributes of an
         already established LSP are changed, either through manual
         configuration or due to a change in network topology,
         make-before-break functionality ensures that the resources of the
         existing LSP will not be released until a new path (with the same LSP
         Id) has been established and traffic flowing over the existing path is
         seamlessly transferred to the new path.

         Setting the value to 'false' disables make-before-break functionality."
    DEFVAL      { true }
    ::= { vRtrMplsLspEntry 34 }

vRtrMplsLspInheritance           OBJECT-TYPE
    SYNTAX      Unsigned32
    MAX-ACCESS  read-create
    STATUS      current
    DESCRIPTION
        "For each writable object in this row that can be configured to inherit
         its value from the corresponding object in the vRtrMplsGeneralTable,
         there is bit within vRtrMplsLspInheritance that controls whether to
         inherit the operational value of the object or use the
         administratively set value.

         Non mask bits will always have value of zero.

         This object is a bit-mask, with the following positions:

         vRtrMplsLspOptimizeTimer                0x1
         vRtrMplsLspFRObject                     0x2
         vRtrMplsLspHoldTimer                    0x4
         vRtrMplsLspDestGlobalId                 0x8

         When the bit for an object is set to one, then the object's
         administrative and operational value are whatever the DEFVAL or most
         recently SET value is.

         When the bit for an object is set to zero, then the object's
         administrative and operational value are inherited from the
         corresponding object in vRtrMplsGeneralTable or vRtrMplsTpSystemTable."
    DEFVAL      { 0 }
    ::= { vRtrMplsLspEntry 35 }

vRtrMplsLspOptimizeTimer         OBJECT-TYPE
    SYNTAX      Unsigned32 (0..65535)
    UNITS       "seconds"
    MAX-ACCESS  read-create
    STATUS      current
    DESCRIPTION
        "The value of vRtrMplsLspOptimizeTimer specifies the time, in seconds,
         the software will wait before attempting to re-optimize the LSP.

         When CSPF is enabled, changes in the network topology may cause the
         existing path of a loose-hop LSP to become sub-optimal. Such LSPs can
         be re-optimized and rerouted through more optimal paths by
         recalculating the path for the LSP at periodic intervals. This
         interval is controlled by the optimize timer.

         A value of 0 indicates that optimization has been disabled.

         When the vRtrMplsLspOptimizeTimer bit in vRtrMplsLspInheritance is
         cleared (0), the value returned in the GET request is inherited from
         vRtrMplsGeneralOptimizeTimer."
    DEFVAL      { 0 }
    ::= { vRtrMplsLspEntry 36 }

vRtrMplsLspOperFastReroute       OBJECT-TYPE
    SYNTAX      TruthValue
    MAX-ACCESS  read-only
    STATUS      current
    DESCRIPTION
        "The value of vRtrMplsLspOperFastReroute indicates whether the
         operational LSP has fast reroute enabled or disabled.

         When make-before-break functionality for the LSP is enabled and if the
         fast reroute setting is changed, the resources for the existing LSP
         will not be released until a new path with the new attribute settings
         has been established. While a new path is being signaled, the
         administrative value and the operational values of fast reroute
         setting for the LSP may differ. The value of vRtrMplsLspFastReroute
         specifies the setting used for the new LSP path trying to be
         established whereas the value of vRtrMplsLspOperFastReroute specifies
         the setting for the existing LSP path."
    ::= { vRtrMplsLspEntry 37 }

vRtrMplsLspFRObject              OBJECT-TYPE
    SYNTAX      TruthValue
    MAX-ACCESS  read-create
    STATUS      current
    DESCRIPTION
        "The value of vRtrMplsLspFRObject specifies whether fast reroute, for
         LSPs using 'Facility Backup', is signalled with or without the fast
         reroute object. The value of vRtrMplsLspFRObject is ignored if fast
         reroute is disabled for the LSP or if the LSP is using 'One-to-one
         Backup'.

         When the vRtrMplsLspFRObject bit in vRtrMplsLspInheritance is cleared
         (0), the value returned in the GET request is inherited from
         vRtrMplsGeneralFRObject."
    DEFVAL      { true }
    ::= { vRtrMplsLspEntry 38 }

vRtrMplsLspHoldTimer             OBJECT-TYPE
    SYNTAX      Unsigned32 (0..10)
    UNITS       "seconds"
    MAX-ACCESS  read-only
    STATUS      current
    DESCRIPTION
        "The value of vRtrMplsLspHoldTimer specifies the time, in seconds, for
         which the ingress node holds a bit before programming its data plane
         and declaring the lsp up to the service module.

         The value of vRtrMplsLspHoldTimer is inherited from the value of
         vRtrMplsGeneralHoldTimer."
    DEFVAL      { 1 }
    ::= { vRtrMplsLspEntry 39 }

vRtrMplsLspCspfTeMetricEnabled   OBJECT-TYPE
    SYNTAX      TruthValue
    MAX-ACCESS  read-create
    STATUS      obsolete
    DESCRIPTION
        "The value of vRtrMplsLspCspfTeMetricEnabled specifies whether the TE
         metric would be used for the purpose of the LSP path computation by
         CSPF. When the value of this object is 'false', the IGP metric is used
         to compute the path of the LSP by CSPF."
    DEFVAL      { false }
    ::= { vRtrMplsLspEntry 40 }

vRtrMplsLspP2mpId                OBJECT-TYPE
    SYNTAX      Unsigned32 (0 | 1..65535)
    MAX-ACCESS  read-create
    STATUS      current
    DESCRIPTION
        "The value of vRtrMplsLspP2mpId specifies a unique identifier known as
         point to multipoint (P2MP) identifier (ID)."
    DEFVAL      { 0 }
    ::= { vRtrMplsLspEntry 41 }

vRtrMplsLspClassType             OBJECT-TYPE
    SYNTAX      TmnxRsvpDSTEClassType
    MAX-ACCESS  read-create
    STATUS      current
    DESCRIPTION
        "The value of vRtrMplsLspClassType specifies the class type (CT)
         associated with this LSP."
    DEFVAL      { 0 }
    ::= { vRtrMplsLspEntry 42 }

vRtrMplsLspOperMetric            OBJECT-TYPE
    SYNTAX      Unsigned32
    MAX-ACCESS  read-only
    STATUS      current
    DESCRIPTION
        "The value of vRtrMplsLspOperMetric indicates the operational metric
         for the LSP."
    ::= { vRtrMplsLspEntry 43 }

vRtrMplsLspLdpOverRsvpInclude    OBJECT-TYPE
    SYNTAX      TruthValue
    MAX-ACCESS  read-create
    STATUS      current
    DESCRIPTION
        "The value of vRtrMplsLspLdpOverRsvpInclude specifies that this LSP can
         be included by IGP to calculate its SPF tree.  The IGP (OSPF or ISIS)
         will subsequently provide LDP with all ECMP IGP next-hops and tunnel
         endpoints that it considers to be the lowest cost path to the
         destination.  If an IGP calculation and an LDP over RSVP produce the
         same cost then LDP will always prefer an LDP over RSVP tunnel over an
         IGP route.

         By default, static and dynamic LSPs will be included when they are
         created. The default value for p2mp and bypass-only LSPs will be
         'false'."
    DEFVAL      { true }
    ::= { vRtrMplsLspEntry 44 }

vRtrMplsLspLeastFill             OBJECT-TYPE
    SYNTAX      TruthValue
    MAX-ACCESS  read-create
    STATUS      current
    DESCRIPTION
        "The value of vRtrMplsLspLeastFill specifies whether the use of the
         least-fill path selection method for the computation of the path of
         this LSP is enabled.

         By default, the path of an LSP is randomly chosen among a set of equal
         cost paths."
    DEFVAL      { false }
    ::= { vRtrMplsLspEntry 45 }

vRtrMplsLspVprnAutoBindInclude   OBJECT-TYPE
    SYNTAX      TruthValue
    MAX-ACCESS  read-create
    STATUS      current
    DESCRIPTION
        "The value of vRtrMplsLspVprnAutoBindInclude specifies whether the LSP
         can be used as part of the auto-bind feature for VPRN services. By
         default a LSP is available for inclusion to be used for the auto-bind
         feature.

         By default, static and dynamic LSPs will be included when they are
         created.  The default value for p2mp and bypass-only LSPs will
         be 'false'."
    DEFVAL      { true }
    ::= { vRtrMplsLspEntry 46 }

vRtrMplsLspMainCTRetryLimit      OBJECT-TYPE
    SYNTAX      Unsigned32 (0..10000)
    MAX-ACCESS  read-create
    STATUS      current
    DESCRIPTION
        "The value of vRtrMplsLspMainCTRetryLimit specifies the number of
         attempts the software should make before it can start using the backup
         class type."
    DEFVAL      { 0 }
    ::= { vRtrMplsLspEntry 47 }

vRtrMplsLspIgpShortcut           OBJECT-TYPE
    SYNTAX      TruthValue
    MAX-ACCESS  read-create
    STATUS      current
    DESCRIPTION
        "The value of vRtrMplsLspIgpShortcut specifies whether to exclude or
         include a RSVP LSP from being used as a shortcut while resolving IGP
         routes.

         When the value of vRtrMplsLspIgpShortcut is set to 'true' the RSVP LSP
         is used as a shortcut while resolving IGP routes. When the value of
         vRtrMplsLspIgpShortcut is set to 'false' the RSVP LSP is not used as a
         shortcut while resolving IGP routes.

         When the value of vRtrMplsLspIgpShortcut is changed, the value of
         vRtrMplsLspIgpShortcutLfaType is reset to its default value."
    DEFVAL      { true }
    ::= { vRtrMplsLspEntry 48 }

vRtrMplsLspOriginTemplate        OBJECT-TYPE
    SYNTAX      TNamedItemOrEmpty
    MAX-ACCESS  read-only
    STATUS      current
    DESCRIPTION
        "When the value of the vRtrMplsLspType is 'p2mpAuto', the value of
         vRtrMplsLspOriginTemplate indicates the LSP Template which was used to
         create this LSP.

         For all other types of LSPs, the value of vRtrMplsLspOriginTemplate is
         an empty string."
    ::= { vRtrMplsLspEntry 49 }

vRtrMplsLspAutoBandwidth         OBJECT-TYPE
    SYNTAX      TruthValue
    MAX-ACCESS  read-create
    STATUS      current
    DESCRIPTION
        "The value of the vRtrMplsLspAutoBandwidth specifies whether automatic
         bandwidth adjustment has been enabled or disabled for this LSP.

         A value of 'true' specifies that automatic bandwidth adjustment has
         been enabled for this LSP and a value of 'false' specifies that
         automatic bandwidth adjustment has been disabled for this LSP."
    DEFVAL      { false }
    ::= { vRtrMplsLspEntry 50 }

vRtrMplsLspCspfToFirstLoose      OBJECT-TYPE
    SYNTAX      TruthValue
    MAX-ACCESS  read-create
    STATUS      obsolete
    DESCRIPTION
        "The value of the vRtrMplsLspCspfToFirstLoose specifies whether the
         CSPF calculation till the first loose hop on ingress Label Edge Router
         (LER) is enabled or disabled for this Labeled Switched Path(LSP).

         By default, the value of vRtrMplsLspCspfToFirstLoose is 'false' which
         specifies that the CSPF calculation is done to the destination of LSP.

         This object was deprecated in the 11.0 release."
    DEFVAL      { false }
    ::= { vRtrMplsLspEntry 51 }

vRtrMplsLspPropAdminGroup        OBJECT-TYPE
    SYNTAX      TruthValue
    MAX-ACCESS  read-create
    STATUS      current
    DESCRIPTION
        "The value of the vRtrMplsLspPropAdminGroup specifies whether the
         propagation of session attribute object with resource affinity (C-type
         1) in PATH message is enabled.

         By default, the value of vRtrMplsLspPropAdminGroup is 'false' which
         specifies the session attribute object without resource affinity
         (C-Type 7) is propagated in PATH message and the admin groups are
         ignored on Label Switched Router(LSR) while doing CSPF calculation."
    DEFVAL      { false }
    ::= { vRtrMplsLspEntry 52 }

vRtrMplsLspBgpShortcut           OBJECT-TYPE
    SYNTAX      TruthValue
    MAX-ACCESS  read-create
    STATUS      current
    DESCRIPTION
        "The value of vRtrMplsLspBgpShortcut specifies whether to exclude or
         include a RSVP LSP from being used as a shortcut while resolving BGP
         routes.

         When the value of vRtrMplsLspBgpShortcut is set to 'true' the RSVP LSP
         is used as a shortcut while resolving BGP routes. When the value of
         vRtrMplsLspBgpShortcut is set to 'false' the RSVP LSP is not used as a
         shortcut while resolving BGP routes."
    DEFVAL      { true }
    ::= { vRtrMplsLspEntry 53 }

vRtrMplsLspBgpTransportTunnel    OBJECT-TYPE
    SYNTAX      TmnxMplsLspBgpRSVPLSPTunState
    MAX-ACCESS  read-create
    STATUS      current
    DESCRIPTION
        "The value of vRtrMplsLspBgpTransportTunnel specifies whether an RSVP
         LSP is allowed or blocked in its usage as a transport LSP for BGP
         tunnel routes.

         When the value of vRtrMplsLspBgpTransportTunnel is set to 'include' an
         RSVP LSP is allowed to be used as a transport LSP for BGP tunnel
         routes. When the value of vRtrMplsLspBgpTransportTunnel is set to
         'exclude' an RSVP LSP is not allowed to be used as a transport LSP for
         BGP tunnel routes."
    DEFVAL      { include }
    ::= { vRtrMplsLspEntry 54 }

vRtrMplsLspSwitchStbyPath        OBJECT-TYPE
    SYNTAX      TmnxActionType
    MAX-ACCESS  read-create
    STATUS      current
    DESCRIPTION
        "The value of vRtrMplsLspSwitchStbyPath specifies whether to trigger
         the switch from the current active standby LSP path to a new LSP path
         as specified by vRtrMplsLspSwitchStbyPathIndex.

         When SET to the value of 'doAction', if the LSP path is actively on a
         current standby path, signaling will be initiated to switch to the new
         path.

         If a signal is triggered while a resignaling is already in progress,
         the old transient state will be destroyed and a new transaction will
         be triggered.

         This variable must be set along with vRtrMplsLspSwitchStbyPathIndex to
         indicate the specific path index to switch to.

         An SNMP GET request on this object should return 'notApplicable'."
    ::= { vRtrMplsLspEntry 55 }

vRtrMplsLspSwitchStbyPathIndex   OBJECT-TYPE
    SYNTAX      MplsTunnelIndex
    MAX-ACCESS  read-create
    STATUS      current
    DESCRIPTION
        "The value of vRtrMplsLspSwitchStbyPathIndex specifies the index for
         the new standby LSP path in mplsTunnelTable.

         vRtrMplsLspSwitchStbyPath must also be set to 'doAction' for the new
         standby LSP path to be selected.

         A value of 0 specifies that the best active path will be selected."
    DEFVAL      { 0 }
    ::= { vRtrMplsLspEntry 56 }

vRtrMplsLspSwitchStbyPathForce   OBJECT-TYPE
    SYNTAX      TruthValue
    MAX-ACCESS  read-create
    STATUS      current
    DESCRIPTION
        "The value of vRtrMplsLspSwitchStbyPathForce specifies whether to force
         a switch from an active LSP path to a new standby path as specified by
         the values of vRtrMplsLspSwitchStbyPathIndex and
         vRtrMplsLspSwitchStbyPath.

         When vRtrMplsLspSwitchStbyPathForce variable is specified
         vRtrMplsLspSwitchStbyPathIndex and vRtrMplsLspSwitchStbyPath must be
         also be specified.

         A value of 'true' for vRtrMplsLspSwitchStbyPathForce specifies
         a forced switch.  A value of 'false' specifies no forced switch."
    DEFVAL      { false }
    ::= { vRtrMplsLspEntry 57 }

vRtrMplsLspExcludeNodeAddrType   OBJECT-TYPE
    SYNTAX      InetAddressType
    MAX-ACCESS  read-create
    STATUS      current
    DESCRIPTION
        "The value of vRtrMplsLspExcludeNodeAddrType specifies the type of
         vRtrMplsLspExcludeNodeAddr."
    ::= { vRtrMplsLspEntry 58 }

vRtrMplsLspExcludeNodeAddr       OBJECT-TYPE
    SYNTAX      InetAddress (SIZE (0|4))
    MAX-ACCESS  read-create
    STATUS      current
    DESCRIPTION
        "When vRtrMplsLspExcludeNodeAddr is set to non-zero value, XRO (Exclude
         Routers) object will be included in bypass path message with supplied
         IP address.

         SET the value to 0.0.0.0 to disable."
    ::= { vRtrMplsLspEntry 59 }

vRtrMplsLspIgpShortcutLfaType    OBJECT-TYPE
    SYNTAX      INTEGER {
        none       (0),
        lfaProtect (1),
        lfaOnly    (2)
    }
    MAX-ACCESS  read-create
    STATUS      current
    DESCRIPTION
        "The value of vRtrMplsLspIgpShortcutLfaType specifies whether to
         exclude or include a RSVP LSP from being used as a shortcut while
         resolving IGP routes in LFA SPF or whether to exclude or include a
         RSVP LSP from being used as a LFA SPF.

         When the value of vRtrMplsLspIgpShortcutLfaType is set to 'lfaProtect'
         the RSVP LSP is used as a shortcut while resolving IGP routes in LFA
         SPF as well.

         When the value of vRtrMplsLspIgpShortcutLfaType is set to 'lfaOnly'
         the RSVP LSP is used as a LFA SPF and not used as igp shortcut in
         regular SPF.

         An 'inconsistentValue' error is returned if an attempt is made to set
         this object to a non-default value when the value of the object
         vRtrMplsLspIgpShortcut is not set to 'true'."
    DEFVAL      { none }
    ::= { vRtrMplsLspEntry 60 }

vRtrMplsLspToAddrType            OBJECT-TYPE
    SYNTAX      TmnxMplsLspAddrType
    MAX-ACCESS  read-create
    STATUS      current
    DESCRIPTION
        "The vRtrMplsLspToAddrType object is an enumerated value that specifies
         the destination address type of the LSP.

         The value of 'ipv4' specifies an IPv4 address and vRtrMplsLspToAddr
         should be configured.

         The value of 'nodeId' specifies an MPLS-TP node id and
         vRtrMplsLspToNodeId should be configured."
    DEFVAL      { unknown }
    ::= { vRtrMplsLspEntry 61 }

vRtrMplsLspFromAddrType          OBJECT-TYPE
    SYNTAX      TmnxMplsLspAddrType
    MAX-ACCESS  read-create
    STATUS      current
    DESCRIPTION
        "The vRtrMplsLspFromAddrType object is an enumerated value that
         specifies the source address type of the LSP.

         When the value of vRtrMplsLspFromAddrType is 'ipv4', it specifies an
         IPv4 address type and vRtrMplsLspFromAddr should be configured.

         When the value of vRtrMplsLspFromAddrType is 'ipv6', it specifies an
         IPv6 address type and vRtrMplsLspNgFromAddr should be configured.

         When the value of vRtrMplsLspFromAddrType is 'nodeId', it specifies an
         MPLS-TP node id type."
    DEFVAL      { unknown }
    ::= { vRtrMplsLspEntry 62 }

vRtrMplsLspToNodeId              OBJECT-TYPE
    SYNTAX      TmnxMplsTpNodeID
    MAX-ACCESS  read-create
    STATUS      current
    DESCRIPTION
        "The value of vRtrMplsLspToNodeId specifies the destination node id of
         an MPLS-TP Static LSP.

         vRtrMplsLspToNodeId is configured when vRtrMplsLspToAddrType is set to
         'nodeId'."
    DEFVAL      { 0 }
    ::= { vRtrMplsLspEntry 63 }

vRtrMplsLspFromNodeId            OBJECT-TYPE
    SYNTAX      TmnxMplsTpNodeID
    MAX-ACCESS  read-only
    STATUS      current
    DESCRIPTION
        "The value of vRtrMplsLspFromNodeId indicates the source node id of an
         MPLS-TP Static LSP."
    ::= { vRtrMplsLspEntry 64 }

vRtrMplsLspDestGlobalId          OBJECT-TYPE
    SYNTAX      TmnxMplsTpGlobalID
    MAX-ACCESS  read-create
    STATUS      current
    DESCRIPTION
        "The value of vRtrMplsLspDestGlobalId specifies the destination global
         identifier for an MPLS-TP Static LSP.

         When the vRtrMplsLspDestGlobalId bit in vRtrMplsLspInheritance is
         cleared (0), the administrative and operational value for destination
         global identifier is inherited from vRtrMplsTpGlobalId in the
         vRtrMplsTpSystemTable."
    DEFVAL      { 0 }
    ::= { vRtrMplsLspEntry 65 }

vRtrMplsLspDestTunnelNum         OBJECT-TYPE
    SYNTAX      Unsigned32 (0 | 1..61440)
    MAX-ACCESS  read-create
    STATUS      current
    DESCRIPTION
        "The value of vRtrMplsLspDestTunnelNum specifies the destination tunnel
         number of an MPLS-TP Static LSP.

         A value of 0 indicates that vRtrMplsLspIndex is to be used as the
         destination tunnel number."
    DEFVAL      { 0 }
    ::= { vRtrMplsLspEntry 66 }

vRtrMplsLspFRPropAdminGroup      OBJECT-TYPE
    SYNTAX      TruthValue
    MAX-ACCESS  read-create
    STATUS      current
    DESCRIPTION
        "The value of vRtrMplsLspFRPropAdminGroup specifies whether or not the
         use of administrative group constraints on a FRR backup LSP is
         enabled.

         If vRtrMplsLspFastReroute is set to 'true', the value of
         vRtrMplsLspFRPropAdminGroup specifies whether or not the
         administrative group constraints are signaled in the
         vRtrMplsLspFastReroute object.

         If vRtrMplsLspFastReroute is set to 'false', the value of
         vRtrMplsLspFRPropAdminGroup is ignored."
    DEFVAL      { false }
    ::= { vRtrMplsLspEntry 67 }

vRtrMplsLspIgpShortcutRelOffset  OBJECT-TYPE
    SYNTAX      Integer32 (-10..10 | 2147483647)
    MAX-ACCESS  read-create
    STATUS      current
    DESCRIPTION
        "The value of vRtrMplsLspIgpShortcutRelOffset specifies the the
         relative offset to the IGP metric on the SPF tree.

         The SPF tree is updated with the current IGP metric of the path
         between the endpoints of the LSP minus the value of
         vRtrMplsLspIgpShortcutRelOffset.

         The default value of 2147483647 indicates the relative metric offset
         is not to be considered."
    DEFVAL      { 2147483647 }
    ::= { vRtrMplsLspEntry 68 }

vRtrMplsLspRevertTimer           OBJECT-TYPE
    SYNTAX      Unsigned32 (0 | 1..4320)
    UNITS       "minutes"
    MAX-ACCESS  read-create
    STATUS      current
    DESCRIPTION
        "The value of vRtrMplsLspRevertTimer specifies a revert timer for a
         Labeled Switch Path (LSP).

         When the value of vRtrMplsLspRevertTimer is set to '0', it cancels any
         revert timer that is currently running and causes the Labeled Switch
         Path (LSP) to revert to the primary path immediately if it is up.

         When the value of vRtrMplsLspRevertTimer is set to any non-zero value
         of revert interval, the Labeled Switch Path (LSP) will be switched to
         the primary path only after the revert interval is over."
    DEFVAL      { 0 }
    ::= { vRtrMplsLspEntry 69 }

vRtrMplsLspRevertTimeRemain      OBJECT-TYPE
    SYNTAX      Unsigned32
    UNITS       "minutes"
    MAX-ACCESS  read-only
    STATUS      current
    DESCRIPTION
        "The value of vRtrMplsLspRevertTimeRemain indicates the time remaining
         in minutes before the revert timer would expire causing an lsp revert
         to primary path."
    ::= { vRtrMplsLspEntry 70 }

vRtrMplsLspLoadBalancingWeight   OBJECT-TYPE
    SYNTAX      Unsigned32 (0 | 1..4294967295)
    MAX-ACCESS  read-create
    STATUS      current
    DESCRIPTION
        "The value of vRtrMplsLspLoadBalancingWeight specifies the load
         balancing weight applied to this Labeled Switch Path(LSP). When a
         system level load-balancing command is enabled, packets forwarded to a
         set of ECMP tunnel next-hops will be sprayed using this weight
         configured for this LSP."
    DEFVAL      { 0 }
    ::= { vRtrMplsLspEntry 71 }

vRtrMplsLspClassFwdingEnabled    OBJECT-TYPE
    SYNTAX      TruthValue
    MAX-ACCESS  read-create
    STATUS      current
    DESCRIPTION
        "The value of vRtrMplsLspClassFwdingEnabled specifies whether class
         based forwarding over this MPLS LSP is enabled or not."
    DEFVAL      { false }
    ::= { vRtrMplsLspEntry 72 }

vRtrMplsLspFC                    OBJECT-TYPE
    SYNTAX      TmnxCBFClasses
    MAX-ACCESS  read-create
    STATUS      obsolete
    DESCRIPTION
        "The value of vRtrMplsLspFC specifies a set of forwarding classes
         configured for this LSP expressed as a bit map. If a bit from 0
         through 7 is set, then the corresponding forwarding class has been
         configured for this LSP. If bit 8 is set, the LSP has been designated
         as the default forwarding LSP."
    DEFVAL      { {} }
    ::= { vRtrMplsLspEntry 73 }

vRtrMplsLspBfdTemplateName       OBJECT-TYPE
    SYNTAX      TNamedItemOrEmpty
    MAX-ACCESS  read-create
    STATUS      current
    DESCRIPTION
        "The value of vRtrMplsLspBfdTemplateName specifies the
         TIMETRA-BFD-MIB::tmnxBfdAdminTemplateName used by this LSP."
    ::= { vRtrMplsLspEntry 74 }

vRtrMplsLspBfdEnable             OBJECT-TYPE
    SYNTAX      TruthValue
    MAX-ACCESS  read-create
    STATUS      current
    DESCRIPTION
        "The value of vRtrMplsLspBfdEnable specifies whether BFD is enabled or
         not for this LSP."
    DEFVAL      { false }
    ::= { vRtrMplsLspEntry 75 }

vRtrMplsLspBfdPingIntvl          OBJECT-TYPE
    SYNTAX      Unsigned32 (0 | 60..300)
    UNITS       "seconds"
    MAX-ACCESS  read-create
    STATUS      current
    DESCRIPTION
        "The value of vRtrMplsLspBfdPingIntvl specifies the time interval for
         periodic LSP ping for BFD bootstrapping.

         The object vRtrMplsLspBfdPingIntvl is applicable to LSPs with
         vRtrMplsLspType set to 'dynamic'.

         When the value of vRtrMplsLspBfdPingIntvl is set to '0', it disables
         LSP pings for BFD bootstrapping."
    DEFVAL      { 60 }
    ::= { vRtrMplsLspEntry 76 }

vRtrMplsLspNgFromAddr            OBJECT-TYPE
    SYNTAX      InetAddress (SIZE (4|16))
    MAX-ACCESS  read-create
    STATUS      current
    DESCRIPTION
        "The value of vRtrMplsLspNgFromAddr specifices the source address of
         this LSP."
    ::= { vRtrMplsLspEntry 77 }

vRtrMplsLspNgToAddr              OBJECT-TYPE
    SYNTAX      InetAddress (SIZE (4|16))
    MAX-ACCESS  read-create
    STATUS      current
    DESCRIPTION
        "The value of vRtrMplsLspNgToAddr specifices the destination address of
         this LSP."
    ::= { vRtrMplsLspEntry 78 }

vRtrMplsLspStatTable             OBJECT-TYPE
    SYNTAX      SEQUENCE OF VRtrMplsLspStatEntry
    MAX-ACCESS  not-accessible
    STATUS      current
    DESCRIPTION
        "The vRtrMplsLspStatTable has an entry for each Labeled Switch Path
         (LSP) configured for a virtual router in the system."
    ::= { tmnxMplsObjs 2 }

vRtrMplsLspStatEntry             OBJECT-TYPE
    SYNTAX      VRtrMplsLspStatEntry
    MAX-ACCESS  not-accessible
    STATUS      current
    DESCRIPTION
        "Each row entry represents a collection of statistics for a Labeled
         Switch Path (LSP) configured for a virtual router in the system.

         Entries cannot be created and deleted via SNMP SET operations."
    AUGMENTS    { vRtrMplsLspEntry }
    ::= { vRtrMplsLspStatTable 1 }

VRtrMplsLspStatEntry             ::= SEQUENCE
{
    vRtrMplsLspOctets                Counter64,
    vRtrMplsLspPackets               Counter64,
    vRtrMplsLspAge                   TmnxTimeInterval,
    vRtrMplsLspTimeUp                TmnxTimeInterval,
    vRtrMplsLspTimeDown              TmnxTimeInterval,
    vRtrMplsLspPrimaryTimeUp         TmnxTimeInterval,
    vRtrMplsLspTransitions           Counter32,
    vRtrMplsLspLastTransition        TmnxTimeInterval,
    vRtrMplsLspPathChanges           Counter32,
    vRtrMplsLspLastPathChange        TmnxTimeInterval,
    vRtrMplsLspConfiguredPaths       Integer32,
    vRtrMplsLspStandbyPaths          Integer32,
    vRtrMplsLspOperationalPaths      Integer32,
    vRtrMplsLspConfP2mpInstances     Gauge32,
    vRtrMplsLspStatsEgrIndexUnAvail  TruthValue,
    vRtrMplsLspSelfPingTimeouts      Counter32
}

vRtrMplsLspOctets                OBJECT-TYPE
    SYNTAX      Counter64
    MAX-ACCESS  read-only
    STATUS      obsolete
    DESCRIPTION
        "The number of octets that have been forwarded over current
         LSP active path. The number reported is not realtime, may
         be subject to several minutes delay.  The delay is controllable
         by MPLS statistics gathering interval, which by default is
         once every 5 minutes.  If MPLS statistics gathering is not
         enabled, this number will not increment."
    ::= { vRtrMplsLspStatEntry 1 }

vRtrMplsLspPackets               OBJECT-TYPE
    SYNTAX      Counter64
    MAX-ACCESS  read-only
    STATUS      obsolete
    DESCRIPTION
        "The number of packets that have been forwarded over current
         LSP active path. The number reported is not realtime, may
         be subject to several minutes delay.  The delay is controllable
         by MPLS statistics gathering interval, which by default is
         once every 5 minutes.  If MPLS statistics gathering is not
         enabled, this number will not increment."
    ::= { vRtrMplsLspStatEntry 2 }

vRtrMplsLspAge                   OBJECT-TYPE
    SYNTAX      TmnxTimeInterval
    MAX-ACCESS  read-only
    STATUS      current
    DESCRIPTION
        "The age (i.e., time from creation till now) of this LSP in
         10-millisecond periods."
    ::= { vRtrMplsLspStatEntry 3 }

vRtrMplsLspTimeUp                OBJECT-TYPE
    SYNTAX      TmnxTimeInterval
    MAX-ACCESS  read-only
    STATUS      current
    DESCRIPTION
        "The total time in 10-millisecond units that this LSP has been
         been operational.  For example, the percentage up time can be
         determined by computing (vRtrMplsLspTimeUp/vRtrMplsLspAge * 100 %)."
    ::= { vRtrMplsLspStatEntry 4 }

vRtrMplsLspTimeDown              OBJECT-TYPE
    SYNTAX      TmnxTimeInterval
    MAX-ACCESS  read-only
    STATUS      current
    DESCRIPTION
        "The total time in 10-millisecond units that this LSP has not been
         operational."
    ::= { vRtrMplsLspStatEntry 5 }

vRtrMplsLspPrimaryTimeUp         OBJECT-TYPE
    SYNTAX      TmnxTimeInterval
    MAX-ACCESS  read-only
    STATUS      current
    DESCRIPTION
        "The total time in 10-millisecond units that this LSP's primary
         path has been operational.  For example, the percentage
         contribution of the primary path to the operational time is
         given by (vRtrMplsLspPrimaryTimeUp/vRtrMplsLspTimeUp * 100) %."
    ::= { vRtrMplsLspStatEntry 6 }

vRtrMplsLspTransitions           OBJECT-TYPE
    SYNTAX      Counter32
    MAX-ACCESS  read-only
    STATUS      current
    DESCRIPTION
        "The number of state transitions (up -> down and down -> up) this LSP
         has undergone."
    ::= { vRtrMplsLspStatEntry 7 }

vRtrMplsLspLastTransition        OBJECT-TYPE
    SYNTAX      TmnxTimeInterval
    MAX-ACCESS  read-only
    STATUS      current
    DESCRIPTION
        "The time in 10-millisecond units since the last transition occurred on
         this LSP."
    ::= { vRtrMplsLspStatEntry 8 }

vRtrMplsLspPathChanges           OBJECT-TYPE
    SYNTAX      Counter32
    MAX-ACCESS  read-only
    STATUS      current
    DESCRIPTION
        "The number of path changes this LSP has had. For every path change
         (path down, path up, path change), a corresponding syslog/trap (if
         enabled) is generated for it."
    ::= { vRtrMplsLspStatEntry 9 }

vRtrMplsLspLastPathChange        OBJECT-TYPE
    SYNTAX      TmnxTimeInterval
    MAX-ACCESS  read-only
    STATUS      current
    DESCRIPTION
        "The time in 10-millisecond units since the last change occurred on
         this LSP."
    ::= { vRtrMplsLspStatEntry 10 }

vRtrMplsLspConfiguredPaths       OBJECT-TYPE
    SYNTAX      Integer32
    MAX-ACCESS  read-only
    STATUS      current
    DESCRIPTION
        "The number of paths configured for this LSP."
    ::= { vRtrMplsLspStatEntry 11 }

vRtrMplsLspStandbyPaths          OBJECT-TYPE
    SYNTAX      Integer32
    MAX-ACCESS  read-only
    STATUS      current
    DESCRIPTION
        "The number of standby paths configured for this LSP."
    ::= { vRtrMplsLspStatEntry 12 }

vRtrMplsLspOperationalPaths      OBJECT-TYPE
    SYNTAX      Integer32
    MAX-ACCESS  read-only
    STATUS      current
    DESCRIPTION
        "The number of operational paths for this LSP. This includes the path
         currently active, as well as operational standby paths."
    ::= { vRtrMplsLspStatEntry 13 }

vRtrMplsLspConfP2mpInstances     OBJECT-TYPE
    SYNTAX      Gauge32
    MAX-ACCESS  read-only
    STATUS      current
    DESCRIPTION
        "The value of vRtrMplsLspConfP2mpInstances indicates the number of p2mp
         instances configured for this LSP."
    ::= { vRtrMplsLspStatEntry 14 }

vRtrMplsLspStatsEgrIndexUnAvail  OBJECT-TYPE
    SYNTAX      TruthValue
    MAX-ACCESS  read-only
    STATUS      current
    DESCRIPTION
        "The value of vRtrMplsLspStatsEgrIndexUnAvail indicates whether an MPLS
         LSP egress statistics index is available or not for the egress
         statistics."
    ::= { vRtrMplsLspStatEntry 15 }

vRtrMplsLspSelfPingTimeouts      OBJECT-TYPE
    SYNTAX      Counter32
    MAX-ACCESS  read-only
    STATUS      current
    DESCRIPTION
        "The value of vRtrMplsLspSelfPingTimeouts indicate the number of times
         self-ping has timed out for paths in this LSP."
    ::= { vRtrMplsLspStatEntry 16 }

vRtrMplsLspPathTableSpinlock     OBJECT-TYPE
    SYNTAX      TestAndIncr
    MAX-ACCESS  read-write
    STATUS      current
    DESCRIPTION
        "voluntary serialization control for vRtrMplsLspPathTable. Primarily
         used by SNMP manager to coordinate changes to
         vRtrMplsLspPathInheritance."
    DEFVAL      { 0 }
    ::= { tmnxMplsObjs 3 }

vRtrMplsLspPathTable             OBJECT-TYPE
    SYNTAX      SEQUENCE OF VRtrMplsLspPathEntry
    MAX-ACCESS  not-accessible
    STATUS      current
    DESCRIPTION
        "The vRtrMplsLspPathTable provides an association between an
         LSP and a path.  An LSP can have more than one path association,
         but only one of those paths can be specified as the primary
         path type.  Paths are defined in as Tunnel entries in the
         mplsTunnelTable in the MPLS-TE-MIB."
    ::= { tmnxMplsObjs 4 }

vRtrMplsLspPathEntry             OBJECT-TYPE
    SYNTAX      VRtrMplsLspPathEntry
    MAX-ACCESS  not-accessible
    STATUS      current
    DESCRIPTION
        "Each row entry represents an association between a Labeled Switch
         Path (LSP) in the vRtrMplsLspTable and a path (or tunnel) entry in
         the mplsTunnelTable.  Entries in this table can be created and
         deleted via SNMP SET operations.  Setting RowStatus to 'active'
         requires vRtrMplsLspPathType to have been assigned a valid value."
    INDEX       {
        vRtrID,
        vRtrMplsLspIndex,
        mplsTunnelIndex,
        mplsTunnelInstance,
        mplsTunnelIngressLSRId
    }
    ::= { vRtrMplsLspPathTable 1 }

VRtrMplsLspPathEntry             ::= SEQUENCE
{
    vRtrMplsLspPathRowStatus         RowStatus,
    vRtrMplsLspPathLastChange        TimeStamp,
    vRtrMplsLspPathType              INTEGER,
    vRtrMplsLspPathCos               Integer32,
    vRtrMplsLspPathProperties        BITS,
    vRtrMplsLspPathBandwidth         Integer32,
    vRtrMplsLspPathBwProtect         TruthValue,
    vRtrMplsLspPathState             INTEGER,
    vRtrMplsLspPathPreference        Integer32,
    vRtrMplsLspPathCosSource         TruthValue,
    vRtrMplsLspPathClassOfService    TNamedItemOrEmpty,
    vRtrMplsLspPathSetupPriority     Unsigned32,
    vRtrMplsLspPathHoldPriority      Unsigned32,
    vRtrMplsLspPathRecord            INTEGER,
    vRtrMplsLspPathHopLimit          Unsigned32,
    vRtrMplsLspPathSharing           TruthValue,
    vRtrMplsLspPathAdminState        TmnxAdminState,
    vRtrMplsLspPathOperState         TmnxOperState,
    vRtrMplsLspPathInheritance       Unsigned32,
    vRtrMplsLspPathLspId             MplsLSPID,
    vRtrMplsLspPathRetryTimeRemaining Unsigned32,
    vRtrMplsLspPathTunnelARHopListIndex Integer32,
    vRtrMplsLspPathNegotiatedMTU     Unsigned32,
    vRtrMplsLspPathFailCode          TmnxMplsLspFailCode,
    vRtrMplsLspPathFailNodeAddr      IpAddress,
    vRtrMplsLspPathAdminGroupInclude Unsigned32,
    vRtrMplsLspPathAdminGroupExclude Unsigned32,
    vRtrMplsLspPathAdaptive          TruthValue,
    vRtrMplsLspPathOptimizeTimer     Unsigned32,
    vRtrMplsLspPathNextOptimize      Unsigned32,
    vRtrMplsLspPathOperBandwidth     Integer32,
    vRtrMplsLspPathMBBState          INTEGER,
    vRtrMplsLspPathResignal          TmnxActionType,
    vRtrMplsLspPathTunnelCRHopListIndex Integer32,
    vRtrMplsLspPathOperMTU           Unsigned32,
    vRtrMplsLspPathRecordLabel       INTEGER,
    vRtrMplsLspPathSrlg              TruthValue,
    vRtrMplsLspPathSrlgDisjoint      TruthValue,
    vRtrMplsLspPathLastResigAttempt  TimeStamp,
    vRtrMplsLspPathMetric            Unsigned32,
    vRtrMplsLspPathLastMBBType       TmnxMplsMBBType,
    vRtrMplsLspPathLastMBBEnd        TimeStamp,
    vRtrMplsLspPathLastMBBMetric     Unsigned32,
    vRtrMplsLspPathLastMBBState      INTEGER,
    vRtrMplsLspPathMBBTypeInProg     TmnxMplsMBBType,
    vRtrMplsLspPathMBBStarted        TimeStamp,
    vRtrMplsLspPathMBBNextRetry      Unsigned32,
    vRtrMplsLspPathMBBRetryAttempts  Unsigned32,
    vRtrMplsLspPathMBBFailCode       TmnxMplsLspFailCode,
    vRtrMplsLspPathMBBFailNodeArType InetAddressType,
    vRtrMplsLspPathMBBFailNodeAddr   InetAddress,
    vRtrMplsLspPathClassType         TmnxRsvpDSTEClassType,
    vRtrMplsLspPathOperMetric        Unsigned32,
    vRtrMplsLspPathResignalEligible  TruthValue,
    vRtrMplsLspPathIsFastRetry       TruthValue,
    vRtrMplsLspPathBackupCT          Integer32,
    vRtrMplsLspPathMainCTRetryRem    Unsigned32,
    vRtrMplsLspPathOperCT            Integer32,
    vRtrMplsLspPathNewPathIndex      MplsTunnelIndex,
    vRtrMplsLspPathMBBMainCTRetryRem Unsigned32,
    vRtrMplsLspPathSigBWMBBInProg    Unsigned32,
    vRtrMplsLspPathSigBWLastMBB      Unsigned32,
    vRtrMplsLspPathActiveByManual    INTEGER,
    vRtrMplsLspPathTimeoutIn         Unsigned32,
    vRtrMplsLspPathMBBTimeoutIn      Unsigned32,
    vRtrMplsLspPathBfdTemplateName   TNamedItemOrEmpty,
    vRtrMplsLspPathBfdEnable         TruthValue,
    vRtrMplsLspPathBfdPingIntvl      Unsigned32,
    vRtrMplsLspPathLastUpdateTime    TimeStamp,
    vRtrMplsLspPathLastUpdateId      Unsigned32,
    vRtrMplsLspPathLastUpdateState   INTEGER,
    vRtrMplsLspPathLastUpdFailCode   TmnxMplsLspFailCode,
    vRtrMplsLspPathBfdUpWaitTimer    Unsigned32,
    vRtrMplsLspPathBfdUpWaitTmLeft   Unsigned32,
    vRtrMplsLspPathBfdState          INTEGER,
    vRtrMplsLspPathBfdStartFailRsn   DisplayString,
    vRtrMplsLspPathBfdOperUpWaitTmr  Unsigned32,
    vRtrMplsLspPathSelfPingOprState  TmnxOperState
}

vRtrMplsLspPathRowStatus         OBJECT-TYPE
    SYNTAX      RowStatus
    MAX-ACCESS  read-create
    STATUS      current
    DESCRIPTION
        "The row status used for creation, deletion, or control
         of vRtrMplsLspPathTable entries.  Before the row can be
         placed into the 'active' state vRtrMplsLspPathType must
         have been assigned a valid value."
    ::= { vRtrMplsLspPathEntry 1 }

vRtrMplsLspPathLastChange        OBJECT-TYPE
    SYNTAX      TimeStamp
    MAX-ACCESS  read-only
    STATUS      current
    DESCRIPTION
        "The sysUpTime when this row was last modified."
    ::= { vRtrMplsLspPathEntry 2 }

vRtrMplsLspPathType              OBJECT-TYPE
    SYNTAX      INTEGER {
        other     (1),
        primary   (2),
        standby   (3),
        secondary (4)
    }
    MAX-ACCESS  read-create
    STATUS      current
    DESCRIPTION
        "This variable is an enum that represents the role this path is taking
         within this LSP."
    ::= { vRtrMplsLspPathEntry 3 }

vRtrMplsLspPathCos               OBJECT-TYPE
    SYNTAX      Integer32 (0..7 | 255)
    MAX-ACCESS  read-create
    STATUS      obsolete
    DESCRIPTION
        "The configured Class Of Service (COS) for this path.  If
         the value is between 0 and 7 inclusive, this value
         will be inserted in the 3 bit COS field in the label.
         If the value is 255, the value in the COS field of
         the label will depend on other factors.

         This object was made obsolete in release 11.0."
    DEFVAL      { 255 }
    ::= { vRtrMplsLspPathEntry 4 }

vRtrMplsLspPathProperties        OBJECT-TYPE
    SYNTAX      BITS {
        record-route   (0),
        adaptive       (1),
        cspf           (2),
        mergeable      (3),
        fast-reroute   (4),
        pce-reported   (5),
        pce-controlled (6),
        pce-computed   (7)
    }
    MAX-ACCESS  read-only
    STATUS      current
    DESCRIPTION
        "The set of configured properties for this path expressed
         as a bit map.  For example, if the path is an adaptive
         path, the bit corresponding to bit value 1 is set."
    ::= { vRtrMplsLspPathEntry 5 }

vRtrMplsLspPathBandwidth         OBJECT-TYPE
    SYNTAX      Integer32 (0..6400000)
    UNITS       "megabps"
    MAX-ACCESS  read-create
    STATUS      current
    DESCRIPTION
        "The value of vRtrMplsLspPathBandwidth specifies the amount
         of bandwidth in megabits per seconds (Mbps) to be reserved
         for this LSP path.  A value of zero (0) indicates that no
         bandwidth is reserved."
    DEFVAL      { 0 }
    ::= { vRtrMplsLspPathEntry 6 }

vRtrMplsLspPathBwProtect         OBJECT-TYPE
    SYNTAX      TruthValue
    MAX-ACCESS  read-create
    STATUS      obsolete
    DESCRIPTION
        "When vRtrMplsLspPathBwProtect has a value of 'true', bandwidth
         protection is enabled on a LSP.  LSPs that reserve bandwidth
         will be used for EF services where customers need guaranteed
         bandwidth.  It is expected that multiple EF services will be
         assigned to a single LSP.  When bandwidth protection is
         enabled on an LSP, each time this LSP is used for a certain
         service the bandwidth allocated on that service is deducted
         from the bandwidth reserved for the LSP.  Once the bandwidth is
         exhausted on the LSP, the ESR will provide feedback to the
         provider indicating that this LSP has exhausted its resources.

         This object was made obsolete in release 11.0."
    DEFVAL      { false }
    ::= { vRtrMplsLspPathEntry 7 }

vRtrMplsLspPathState             OBJECT-TYPE
    SYNTAX      INTEGER {
        unknown  (1),
        active   (2),
        inactive (3)
    }
    MAX-ACCESS  read-only
    STATUS      current
    DESCRIPTION
        "The current working state of this path within this LSP."
    DEFVAL      { unknown }
    ::= { vRtrMplsLspPathEntry 8 }

vRtrMplsLspPathPreference        OBJECT-TYPE
    SYNTAX      Integer32 (0..255)
    MAX-ACCESS  read-create
    STATUS      current
    DESCRIPTION
        "When there is no path in the LSP with vRtrMplsLspPathType
         value of 'primary', 'secondary' type paths of this LSP
         with the same value of vRtrMplsLspPathPreference are used
         for load sharing.  When a 'primary' type path exists in
         the LSP, vRtrMplsLspPathPreference is used to denote at
         which priority one 'secondary' path will supersede another
         when the 'primary' fails. 1 indicates the highest priority
         value.

         For LSP with vRtrMplsLspPathType value of 'standby' type paths the
         value of vRtrMplsLspPathPreference is in the range of (1..255). For
         path type 'primary' the value of vRtrMplsLspPathPreference is set to
         0. For path type 'secondary' the value of vRtrMplsLspPathPreference is
         set to 255."
    DEFVAL      { 255 }
    ::= { vRtrMplsLspPathEntry 9 }

vRtrMplsLspPathCosSource         OBJECT-TYPE
    SYNTAX      TruthValue
    MAX-ACCESS  read-create
    STATUS      obsolete
    DESCRIPTION
        "When vRtrMplsLspPathCosSource is set to 'true', the value of
         vRtrMplsLspPathClassOfService overrides vRtrMplsLspClassOfService.
         When 'false', the value of vRtrMplsLspClassOfService is used.

         This object was made obsolete in release 11.0."
    DEFVAL      { false }
    ::= { vRtrMplsLspPathEntry 10 }

vRtrMplsLspPathClassOfService    OBJECT-TYPE
    SYNTAX      TNamedItemOrEmpty
    MAX-ACCESS  read-create
    STATUS      obsolete
    DESCRIPTION
        "The name of the class of service value to be assigned to all
         packets on the LSP is specified with vRtrMplsLspPathClassOfService.
         The EXP bits in the MPLS header are set based on the global
         mapping table that specified the mapping between the forwarding
         class and the EXP bits.  When class of service is specified,
         all packets will be marked with the same EXP bits that match
         the vRtrMplsLspPathClassOfService name in the mapping table.

         An empty string, ''H, specifies no class of service.  Packets
         are assigned EXP bits based on the same mapping table, however
         each packet is marked with EXP bits based on the forwarding
         class from which it is serviced.

         This object was made obsolete in release 11.0."
    DEFVAL      { ''H }
    ::= { vRtrMplsLspPathEntry 11 }

vRtrMplsLspPathSetupPriority     OBJECT-TYPE
    SYNTAX      Unsigned32 (0..7)
    MAX-ACCESS  read-create
    STATUS      current
    DESCRIPTION
        "The value of vRtrMplsLspPathSetupPriority specifies the setup
         priority to use when insufficient bandwidth is available to setup
         a LSP.  The setup priority is compared against the hold priority of
         existing LSPs.  If the setup priority is higher than the hold
         priority of the established LSPs, this LSP may preempt the other
         LSPs.  A value of zero (0) is the highest priority and a value
         of seven (7) is the lowest priority."
    DEFVAL      { 7 }
    ::= { vRtrMplsLspPathEntry 12 }

vRtrMplsLspPathHoldPriority      OBJECT-TYPE
    SYNTAX      Unsigned32 (0..7)
    MAX-ACCESS  read-create
    STATUS      current
    DESCRIPTION
        "The value of vRtrMplsLspPathHoldPriority specifies the hold
         priority to use when insufficient bandwidth is available to setup
         a LSP.  The setup priority is compared against the hold priority of
         existing LSPs.  If the setup priority is higher than the hold
         priority of the established LSPs, this LSP may preempt the other
         LSPs.  A value of zero (0) is the highest priority and a value
         of seven (7) is the lowest priority."
    DEFVAL      { 0 }
    ::= { vRtrMplsLspPathEntry 13 }

vRtrMplsLspPathRecord            OBJECT-TYPE
    SYNTAX      INTEGER {
        record   (1),
        noRecord (2)
    }
    MAX-ACCESS  read-create
    STATUS      current
    DESCRIPTION
        "When the value of vRtrMplsLspPathRecord is 'record', recording of all
         the hops that a LSP traverses is enabled.

         When the value of vRtrMplsLspPathRecord is 'noRecord', recording of
         all the hops that a LSP traverses is disabled."
    DEFVAL      { record }
    ::= { vRtrMplsLspPathEntry 14 }

vRtrMplsLspPathHopLimit          OBJECT-TYPE
    SYNTAX      Unsigned32 (2..255)
    MAX-ACCESS  read-create
    STATUS      current
    DESCRIPTION
        "The value of vRtrMplsLspPathHopLimit specifies the maximum number
         of hops that a LSP will traverse including the ingress and
         egress ESRs.  A LSP will not be setup if the hop limit is
         exceeded.

         When the vRtrMplsLspPathHopLimit bit in vRtrMplsLspPathInheritance is
         cleared (0), the value returned to a GET request is inherited from
         vRtrMplsLspHopLimit."
    DEFVAL      { 255 }
    ::= { vRtrMplsLspPathEntry 15 }

vRtrMplsLspPathSharing           OBJECT-TYPE
    SYNTAX      TruthValue
    MAX-ACCESS  read-create
    STATUS      obsolete
    DESCRIPTION
        "When vRtrMplsLspPathSharing has a value of 'true', path-sharing
         is enabled for the secondary path.  Path-sharing is used to
         control the hops of the secondary path.

         When vRtrMplsLspPathSharing have a value of 'false', CSPF attempts to
         find a path for the secondary that does not include any node or link
         that is common to the active primary path.

         This variable is valid only if vRtrMplsLspPathType is set to
         'secondary'.

         This object was made obsolete in release 11.0."
    DEFVAL      { false }
    ::= { vRtrMplsLspPathEntry 16 }

vRtrMplsLspPathAdminState        OBJECT-TYPE
    SYNTAX      TmnxAdminState
    MAX-ACCESS  read-create
    STATUS      current
    DESCRIPTION
        "The desired administrative state for this LSP path."
    DEFVAL      { inService }
    ::= { vRtrMplsLspPathEntry 17 }

vRtrMplsLspPathOperState         OBJECT-TYPE
    SYNTAX      TmnxOperState
    MAX-ACCESS  read-only
    STATUS      current
    DESCRIPTION
        "The current operational state of this LSP path."
    ::= { vRtrMplsLspPathEntry 18 }

vRtrMplsLspPathInheritance       OBJECT-TYPE
    SYNTAX      Unsigned32
    MAX-ACCESS  read-create
    STATUS      current
    DESCRIPTION
        "For each writable object in this row that can be configured to inherit
         its value from its corresponding object in the vRtrMplsLspTable,
         controls whether to inherit the operational value of that object, or
         use the administratively set value.

         Non mask bits will always have value of zero, and any attempt to
         change the value will be silently discarded.

         This object is a bit-mask, with the following positions:

         vRtrMplsLspPathHopLimit              0x2000
         vRtrMplsLspPathAdminGroupInclude    0x20000
         vRtrMplsLspPathAdminGroupExclude    0x40000
         vRtrMplsLspPathAdaptive             0x80000
         vRtrMplsLspPathOptimizeTimer       0x100000
         vRtrMplsLspPathClassType           0x1000000

         When the bit for an object is set to one, then the object's
         administrative and operational value are whatever the DEFVAL or most
         recently SET value is. The corresponding mask bit will be changed to
         one when SNMP SET is performed on any of the inherited objects
         (vRtrMplsLspPathHopLimit, vRtrMplsLspPathAdminGroupInclude, etc).

         When the bit for an object is set to zero, then the object's
         administrative and operational value are inherited from the
         corresponding object in vRtrMplsLspTable."
    DEFVAL      { 0 }
    ::= { vRtrMplsLspPathEntry 19 }

vRtrMplsLspPathLspId             OBJECT-TYPE
    SYNTAX      MplsLSPID
    MAX-ACCESS  read-only
    STATUS      current
    DESCRIPTION
        "This value identifies the label switched path that is signaled for
         this entry."
    ::= { vRtrMplsLspPathEntry 20 }

vRtrMplsLspPathRetryTimeRemaining OBJECT-TYPE
    SYNTAX      Unsigned32
    MAX-ACCESS  read-only
    STATUS      current
    DESCRIPTION
        "The time in 10-millisecond units to signal this path."
    ::= { vRtrMplsLspPathEntry 21 }

vRtrMplsLspPathTunnelARHopListIndex OBJECT-TYPE
    SYNTAX      Integer32 (0 | 1..2147483647)
    MAX-ACCESS  read-only
    STATUS      current
    DESCRIPTION
        "Primary index into the mplsTunnelARHopTable identifying a particular
         recorded hop list. A value of 0 implies that there is no recorded hop
         list associated with this LSP path."
    ::= { vRtrMplsLspPathEntry 22 }

vRtrMplsLspPathNegotiatedMTU     OBJECT-TYPE
    SYNTAX      Unsigned32
    MAX-ACCESS  read-only
    STATUS      current
    DESCRIPTION
        "The value of vRtrMplsLspPathNegotiatedMTU specifies the size for the
         Maximum transmission unit (MTU) that is negotiated during
         establishment of this LSP Path."
    DEFVAL      { 0 }
    ::= { vRtrMplsLspPathEntry 23 }

vRtrMplsLspPathFailCode          OBJECT-TYPE
    SYNTAX      TmnxMplsLspFailCode
    MAX-ACCESS  read-only
    STATUS      current
    DESCRIPTION
        "The value of vRtrMplsLspPathFailCode indicates the reason code for LSP
         Path failure. A value of 0 indicates that no failure has occurred."
    ::= { vRtrMplsLspPathEntry 24 }

vRtrMplsLspPathFailNodeAddr      OBJECT-TYPE
    SYNTAX      IpAddress
    MAX-ACCESS  read-only
    STATUS      current
    DESCRIPTION
        "The value of vRtrMplsLspPathFailNodeAddr indicates the IP address of
         the node in the LSP path at which the LSP path failed. When no failure
         has occurred, this value is 0."
    ::= { vRtrMplsLspPathEntry 25 }

vRtrMplsLspPathAdminGroupInclude OBJECT-TYPE
    SYNTAX      Unsigned32
    MAX-ACCESS  read-create
    STATUS      current
    DESCRIPTION
        "The value of vRtrMplsLspPathAdminGroupInclude is a bit-map that
         specifies a list of admin groups that should be included when this LSP
         path is setup. If bit 'n' is set, then the admin group with value 'n'
         is included for this LSP path. This implies that each link that this
         LSP path goes through must be associated with at least one of the
         admin groups in the include list.

         When the vRtrMplsLspPathAdminGroupInclude bit in
         vRtrMplsLspPathInheritance is cleared (0), the value returned to a GET
         request is inherited from vRtrMplsLspAdminGroupInclude."
    DEFVAL      { '00000000'H }
    ::= { vRtrMplsLspPathEntry 26 }

vRtrMplsLspPathAdminGroupExclude OBJECT-TYPE
    SYNTAX      Unsigned32
    MAX-ACCESS  read-create
    STATUS      current
    DESCRIPTION
        "The value of vRtrMplsLspPathAdminGroupExclude is a bit-map that
         specifies a list of admin groups that should be excluded when this LSP
         path is setup. If bit 'n' is set, then the admin group with value 'n'
         is excluded for this LSP path. This implies that each link that this
         LSP path goes through must not be associated with any of the admin
         groups in the exclude list.

         When the vRtrMplsLspPathAdminGroupExclude bit in
         vRtrMplsLspPathInheritance is cleared (0), the value returned to a GET
         request is inherited from vRtrMplsLspAdminGroupExclude."
    DEFVAL      { '00000000'H }
    ::= { vRtrMplsLspPathEntry 27 }

vRtrMplsLspPathAdaptive          OBJECT-TYPE
    SYNTAX      TruthValue
    MAX-ACCESS  read-create
    STATUS      current
    DESCRIPTION
        "Setting the value of vRtrMplsLspPathAdaptive to 'true', enables
         make-before-break functionality for the LSP path.

         Setting the value to 'false', disables make-before-break functionality
         for the path.

         When the vRtrMplsLspPathAdaptive bit in vRtrMplsLspPathInheritance is
         cleared (0), the value returned to a GET request is inherited from
         vRtrMplsLspAdaptive."
    DEFVAL      { true }
    ::= { vRtrMplsLspPathEntry 28 }

vRtrMplsLspPathOptimizeTimer     OBJECT-TYPE
    SYNTAX      Unsigned32 (0..65535)
    UNITS       "seconds"
    MAX-ACCESS  read-create
    STATUS      current
    DESCRIPTION
        "The value of vRtrMplsLspPathOptimizeTimer specifies the time, in
         seconds, the software will wait before attempting to re-optimize the
         LSP path.

         When CSPF is enabled, changes in the network topology may cause the
         existing path of a loose-hop LSP to become sub-optimal. Such LSPs can
         be re-optimized and rerouted through more optimal paths by
         recalculating the path for the LSP at periodic intervals. This
         interval is controlled by the optimize timer.

         A value of 0 indicates that optimization has been disabled.

         When the vRtrMplsLspPathOptimizeTimer bit in
         vRtrMplsLspPathInheritance is cleared (0), the value returned in the
         GET request is inherited from vRtrMplsLspOptimizeTimer."
    DEFVAL      { 0 }
    ::= { vRtrMplsLspPathEntry 29 }

vRtrMplsLspPathNextOptimize      OBJECT-TYPE
    SYNTAX      Unsigned32 (0..65535)
    UNITS       "seconds"
    MAX-ACCESS  read-only
    STATUS      current
    DESCRIPTION
        "The value of vRtrMplsLspPathNextOptimize indicates the current value
         of the optimize timer. This is the time, in seconds, remaining till
         the optimize timer will expire and optimization will be started for
         the LSP path."
    ::= { vRtrMplsLspPathEntry 30 }

vRtrMplsLspPathOperBandwidth     OBJECT-TYPE
    SYNTAX      Integer32
    UNITS       "megabps"
    MAX-ACCESS  read-only
    STATUS      current
    DESCRIPTION
        "The value of vRtrMplsLspPathOperBandwidth indicates the amount of
         bandwidth in megabits per seconds (Mbps) that has been reserved for
         the operational LSP path.

         When make-before-break functionality for the LSP is enabled and if the
         path bandwidth is changed, the resources allocated to the existing LSP
         paths will not be released until a new path with the new bandwidth
         settings has been established. While a new path is being signaled, the
         administrative value and the operational values of the path bandwidth
         may differ. The value of vRtrMplsLspPathBandwidth specifies the
         bandwidth requirements for the new LSP path trying to be established
         whereas the value of vRtrMplsLspPathOperBandwidth specifies the
         bandwidth reserved for the existing LSP path."
    ::= { vRtrMplsLspPathEntry 31 }

vRtrMplsLspPathMBBState          OBJECT-TYPE
    SYNTAX      INTEGER {
        none       (1),
        success    (2),
        inProgress (3),
        fail       (4)
    }
    MAX-ACCESS  read-only
    STATUS      obsolete
    DESCRIPTION
        "The value of vRtrMplsLspPathMBBState indicates the state of the most
         recent invocation of the make-before-break functionality.

         Possible states are:

         none (1)        - no make-before-break invoked
         success (2)     - make-before-break successful
         inProgress (3)  - make-before-break in progress
         fail (4)        - make-before-break failed.

         This object was made obsolete in release 6.0 R4 and replaced with
         vRtrMplsLspPathLastMBBState."
    ::= { vRtrMplsLspPathEntry 32 }

vRtrMplsLspPathResignal          OBJECT-TYPE
    SYNTAX      TmnxActionType
    MAX-ACCESS  read-create
    STATUS      current
    DESCRIPTION
        "Setting the value of vRtrMplsLspPathResignal to 'doAction' triggers
         the resignaling of the LSP path.

         If the LSP path is operationally down either due to network failure or
         due to the retry attempts count being exceeded, setting this variable
         to 'doAction' will initiate the signaling for the path. A
         make-before-break signaling for the path will be initiated if the LSP
         is operationally up but the make-before-break retry attempts count was
         exceeded. Make-before-break signaling will also be initiated for any
         LSP that is operationally up. This may be used to cause a loose-hop
         LSP to be optimized.

         If a resignal is triggered while a resignaling is already in progress,
         the old transient state will be destroyed and a new transaction being
         triggered.

         An SNMP GET request on this object should return 'notApplicable'."
    ::= { vRtrMplsLspPathEntry 33 }

vRtrMplsLspPathTunnelCRHopListIndex OBJECT-TYPE
    SYNTAX      Integer32 (0 | 1..2147483647)
    MAX-ACCESS  read-only
    STATUS      current
    DESCRIPTION
        "Primary index into the vRtrMplsTunnelCHopTable identifying a
         particular computed hop list. A value of 0 implies that there is no
         computed hop list associated with this LSP path."
    ::= { vRtrMplsLspPathEntry 34 }

vRtrMplsLspPathOperMTU           OBJECT-TYPE
    SYNTAX      Unsigned32
    MAX-ACCESS  read-only
    STATUS      current
    DESCRIPTION
        "The value of vRtrMplsLspPathOperMTU indicates the size for the Maximum
         transmission unit (MTU) that is currently operation for this LSP Path."
    ::= { vRtrMplsLspPathEntry 35 }

vRtrMplsLspPathRecordLabel       OBJECT-TYPE
    SYNTAX      INTEGER {
        record   (1),
        noRecord (2)
    }
    MAX-ACCESS  read-create
    STATUS      current
    DESCRIPTION
        "When the value of vRtrMplsLspPathRecordLabel is 'record', recording of
         labels at each node that a LSP traverses is enabled.

         When the value of vRtrMplsLspPathRecordLabel is 'noRecord', recording
         of labels at each node that a LSP traverses is disabled."
    DEFVAL      { record }
    ::= { vRtrMplsLspPathEntry 36 }

vRtrMplsLspPathSrlg              OBJECT-TYPE
    SYNTAX      TruthValue
    MAX-ACCESS  read-create
    STATUS      current
    DESCRIPTION
        "The value of vRtrMplsLspPathSrlg specifies whether the use of SRLG
         constraint in the computation of a secondary path for an LSP at the
         head-end Label Edge Router (LER) is enabled.

         The value vRtrMplsLspPathSrlg is used only when the value of
         vRtrMplsLspPathType is 'secondary'.  When the value of
         vRtrMplsLspPathSrlg is true, the use of SRLG constraint in the
         computation of a secondary path is enabled."
    DEFVAL      { false }
    ::= { vRtrMplsLspPathEntry 37 }

vRtrMplsLspPathSrlgDisjoint      OBJECT-TYPE
    SYNTAX      TruthValue
    MAX-ACCESS  read-only
    STATUS      current
    DESCRIPTION
        "The value of vRtrMplsLspPathSrlgDisjoint indicates whether the
         relevant standby lsp path is SRLG disjoint from the associated primary
         lsp path for an LSP at the head-end Label Edge Router (LER).

         The value vRtrMplsLspPathSrlgDisjoint is used only when the
         value of vRtrMplsLspPathType is 'standby'.  When the value of
         vRtrMplsLspPathSrlgDisjoint is 'true', primary and standby lsp
         path do not have SRLG membership in common.  When the value of
         vRtrMplsLspPathSrlgDisjoint is 'false', primary and standby lsp
         path have SRLG membership in common."
    ::= { vRtrMplsLspPathEntry 38 }

vRtrMplsLspPathLastResigAttempt  OBJECT-TYPE
    SYNTAX      TimeStamp
    MAX-ACCESS  read-only
    STATUS      current
    DESCRIPTION
        "The value of vRtrMplsLspPathLastResigAttempt indicates the sysUpTime
         when the last attempt to resignal this LSP was made."
    ::= { vRtrMplsLspPathEntry 39 }

vRtrMplsLspPathMetric            OBJECT-TYPE
    SYNTAX      Unsigned32
    MAX-ACCESS  read-only
    STATUS      current
    DESCRIPTION
        "The value of vRtrMplsLspPathMetric indicates the cost of the traffic
         engineered path returned by the IGP."
    ::= { vRtrMplsLspPathEntry 40 }

vRtrMplsLspPathLastMBBType       OBJECT-TYPE
    SYNTAX      TmnxMplsMBBType
    MAX-ACCESS  read-only
    STATUS      current
    DESCRIPTION
        "The value of vRtrMplsLspPathLastMBBType indicates the type of
         last Make-before-break (MBB).  If 'none', then no MBB has been
         attempted."
    ::= { vRtrMplsLspPathEntry 41 }

vRtrMplsLspPathLastMBBEnd        OBJECT-TYPE
    SYNTAX      TimeStamp
    MAX-ACCESS  read-only
    STATUS      current
    DESCRIPTION
        "The value of vRtrMplsLspPathLastMBBEnd indicates the sysUpTime when
         the last MBB ended."
    ::= { vRtrMplsLspPathEntry 42 }

vRtrMplsLspPathLastMBBMetric     OBJECT-TYPE
    SYNTAX      Unsigned32
    MAX-ACCESS  read-only
    STATUS      current
    DESCRIPTION
        "The value of vRtrMplsLspPathLastMBBMetric  indicates  the
         cost of the traffic engineered path for the LSP path prior to MBB."
    ::= { vRtrMplsLspPathEntry 43 }

vRtrMplsLspPathLastMBBState      OBJECT-TYPE
    SYNTAX      INTEGER {
        none    (1),
        success (2),
        fail    (3)
    }
    MAX-ACCESS  read-only
    STATUS      current
    DESCRIPTION
        "The value of vRtrMplsLspPathLastMBBState indicates whether the last
         Make-before-break was successful or failed.
         Possible states are:
         none (1)        - no make-before-break invoked
         success (2)     - make-before-break successful
         fail (3)        - make-before-break failed."
    ::= { vRtrMplsLspPathEntry 44 }

vRtrMplsLspPathMBBTypeInProg     OBJECT-TYPE
    SYNTAX      TmnxMplsMBBType
    MAX-ACCESS  read-only
    STATUS      current
    DESCRIPTION
        "The value of vRtrMplsLspPathMBBTypeInProg indicates the type of the
         Make-before-break (MBB) that is in progress. If 'none', then no MBB is
         in progress."
    ::= { vRtrMplsLspPathEntry 45 }

vRtrMplsLspPathMBBStarted        OBJECT-TYPE
    SYNTAX      TimeStamp
    MAX-ACCESS  read-only
    STATUS      current
    DESCRIPTION
        "The value of vRtrMplsLspPathMBBStarted indicates the sysUpTime when
         the in-progress MBB started."
    ::= { vRtrMplsLspPathEntry 46 }

vRtrMplsLspPathMBBNextRetry      OBJECT-TYPE
    SYNTAX      Unsigned32
    UNITS       "seconds"
    MAX-ACCESS  read-only
    STATUS      current
    DESCRIPTION
        "The value of vRtrMplsLspPathMBBNextRetry indicates the amount of time
         remaining in seconds before the next attempt is made to retry the
         in-progress MBB."
    ::= { vRtrMplsLspPathEntry 47 }

vRtrMplsLspPathMBBRetryAttempts  OBJECT-TYPE
    SYNTAX      Unsigned32
    MAX-ACCESS  read-only
    STATUS      current
    DESCRIPTION
        "The value of vRtrMplsLspPathMBBRetryAttempts indicates 'n' where nth
         attempt for the MBB is in progress."
    ::= { vRtrMplsLspPathEntry 48 }

vRtrMplsLspPathMBBFailCode       OBJECT-TYPE
    SYNTAX      TmnxMplsLspFailCode
    MAX-ACCESS  read-only
    STATUS      current
    DESCRIPTION
        "The value of vRtrMplsLspPathMBBFailCode indicates the reason code for
         in-progress MBB failure. A value of 'none' indicates that no failure
         has occurred."
    ::= { vRtrMplsLspPathEntry 49 }

vRtrMplsLspPathMBBFailNodeArType OBJECT-TYPE
    SYNTAX      InetAddressType
    MAX-ACCESS  read-only
    STATUS      current
    DESCRIPTION
        "The value of vRtrMplsLspPathMBBFailNodeArType indicates the type of
         vRtrMplsLspPathMBBFailNodeAddr. A value of 'unknown' indicates that no
         failure has occurred."
    ::= { vRtrMplsLspPathEntry 50 }

vRtrMplsLspPathMBBFailNodeAddr   OBJECT-TYPE
    SYNTAX      InetAddress (SIZE (0|4))
    MAX-ACCESS  read-only
    STATUS      current
    DESCRIPTION
        "The value of vRtrMplsLspPathMBBFailNodeAddr indicates the IP address
         of the node in the LSP path at which the in-progress MBB failed. A
         value of 'unknown' for vRtrMplsLspPathMBBFailNodeArType and empty
         string for vRtrMplsLspPathMBBFailNodeAddr indicates that no failure
         has occurred."
    ::= { vRtrMplsLspPathEntry 51 }

vRtrMplsLspPathClassType         OBJECT-TYPE
    SYNTAX      TmnxRsvpDSTEClassType
    MAX-ACCESS  read-create
    STATUS      current
    DESCRIPTION
        "The value of vRtrMplsLspPathClassType specifies the class type (CT)
         associated with this LSP path.   When the vRtrMplsLspPathClassType
         bit in vRtrMplsLspPathInheritance is cleared (0), the value returned to
         a GET request is inherited from vRtrMplsLspClassType."
    DEFVAL      { 0 }
    ::= { vRtrMplsLspPathEntry 52 }

vRtrMplsLspPathOperMetric        OBJECT-TYPE
    SYNTAX      Unsigned32
    MAX-ACCESS  read-only
    STATUS      current
    DESCRIPTION
        "The value of vRtrMplsLspPathOperMetric indicates the operational
         metric for the LSP path."
    ::= { vRtrMplsLspPathEntry 53 }

vRtrMplsLspPathResignalEligible  OBJECT-TYPE
    SYNTAX      TruthValue
    MAX-ACCESS  read-only
    STATUS      current
    DESCRIPTION
        "The value of vRtrMplsLspPathResignalEligible indicates that the LSP
         path is eligible for resignaling on the basis of available bandwidth."
    ::= { vRtrMplsLspPathEntry 54 }

vRtrMplsLspPathIsFastRetry       OBJECT-TYPE
    SYNTAX      TruthValue
    MAX-ACCESS  read-only
    STATUS      current
    DESCRIPTION
        "The value of vRtrMplsLspPathIsFastRetry indicates which retry timer is
         being referred to by vRtrMplsLspPathRetryTimeRemaining.

         When the value of vRtrMplsLspPathIsFastRetry is set to 'true',
         vRtrMplsLspPathRetryTimeRemaining is referring to either the P2P
         active path fast timer, vRtrMplsGenP2pActPathFastRetry or the
         secondary fast retry timer, vRtrMplsGeneralSecFastRetryTimer.

         When the value of vRtrMplsLspPathIsFastRetry is set to 'false',
         vRtrMplsLspPathRetryTimeRemaining is referring to the LSP retry timer,
         vRtrMplsLspRetryTimer."
    ::= { vRtrMplsLspPathEntry 55 }

vRtrMplsLspPathBackupCT          OBJECT-TYPE
    SYNTAX      Integer32 (-1 | 0..7)
    MAX-ACCESS  read-create
    STATUS      current
    DESCRIPTION
        "The value of vRtrMplsLspPathBackupCT specifies the backup class type
         (CT) associated with the LSP. A value of -1 indicates that no backup
         class type has been configured for the LSP."
    DEFVAL      { -1 }
    ::= { vRtrMplsLspPathEntry 56 }

vRtrMplsLspPathMainCTRetryRem    OBJECT-TYPE
    SYNTAX      Unsigned32
    MAX-ACCESS  read-only
    STATUS      current
    DESCRIPTION
        "The value of vRtrMplsLspPathMainCTRetryRem indicates the number of
         remaining attempts the software should make before it can start using
         the backup class type for the LSP."
    ::= { vRtrMplsLspPathEntry 57 }

vRtrMplsLspPathOperCT            OBJECT-TYPE
    SYNTAX      Integer32 (-1 | 0..7)
    MAX-ACCESS  read-only
    STATUS      current
    DESCRIPTION
        "The value of vRtrMplsLspPathOperCT indicates operational class type
         (CT) associated with the LSP. A value of -1 indicates that no
         operational class type has been configured for the LSP"
    ::= { vRtrMplsLspPathEntry 58 }

vRtrMplsLspPathNewPathIndex      OBJECT-TYPE
    SYNTAX      MplsTunnelIndex
    MAX-ACCESS  read-create
    STATUS      current
    DESCRIPTION
        "The value of vRtrMplsLspPathNewPathIndex specifies the index for the
         new path in mplsTunnelTable."
    DEFVAL      { 0 }
    ::= { vRtrMplsLspPathEntry 59 }

vRtrMplsLspPathMBBMainCTRetryRem OBJECT-TYPE
    SYNTAX      Unsigned32
    MAX-ACCESS  read-only
    STATUS      current
    DESCRIPTION
        "The value of vRtrMplsLspPathMBBMainCTRetryRem indicates the number of
         remaining attempts the software should make before it can start using
         the backup class type for the LSP."
    ::= { vRtrMplsLspPathEntry 60 }

vRtrMplsLspPathSigBWMBBInProg    OBJECT-TYPE
    SYNTAX      Unsigned32
    MAX-ACCESS  read-only
    STATUS      current
    DESCRIPTION
        "The value of vRtrMplsLspPathSigBWMBBInProg indicates the bandwidth
         used to signal the MBB currently in progress."
    ::= { vRtrMplsLspPathEntry 61 }

vRtrMplsLspPathSigBWLastMBB      OBJECT-TYPE
    SYNTAX      Unsigned32
    MAX-ACCESS  read-only
    STATUS      current
    DESCRIPTION
        "The value of vRtrMplsLspPathSigBWLastMBB indicates the bandwidth used
         to signal the last MBB that occurred."
    ::= { vRtrMplsLspPathEntry 62 }

vRtrMplsLspPathActiveByManual    OBJECT-TYPE
    SYNTAX      INTEGER {
        notApplicable (0),
        noForce       (1),
        force         (2)
    }
    MAX-ACCESS  read-only
    STATUS      current
    DESCRIPTION
        "The value of vRtrMplsLspPathActiveByManual indicates whether
         a secondary standby path has become the active LSP path
         due to manual intervention.  When vRtrMplsLspSwitchStbyPath is set
         to 'doAction' a manual switch is attempted. When
         vRtrMplsLspSwitchStbyPathForce is set to 'true' the manual switch is
         forced.

         When the value of vRtrMplsLspPathActiveByManual is set to
         'notApplicable', the LSP path is active but not due to any manual
         intervention.

         When the value of vRtrMplsLspPathActiveByManual is set to 'noForce',
         the LSP path has become active by a manual switch specified by the
         user.

         When the value of vRtrMplsLspPathActiveByManual is set to 'force', the
         LSP path has become active by a forced manual switch executed by the
         user."
    ::= { vRtrMplsLspPathEntry 63 }

vRtrMplsLspPathTimeoutIn         OBJECT-TYPE
    SYNTAX      Unsigned32
    UNITS       "seconds"
    MAX-ACCESS  read-only
    STATUS      current
    DESCRIPTION
        "The value of vRtrMplsLspPathTimeoutIn indicates the amount of time
         remaining, in seconds, for the LSP path state to time out after the
         initial PATH message has been sent. If the timer expires and the LSP
         path has not become operationally up, the LSP path is torn down and
         the retry timer is started to schedule a new retry cycle."
    ::= { vRtrMplsLspPathEntry 64 }

vRtrMplsLspPathMBBTimeoutIn      OBJECT-TYPE
    SYNTAX      Unsigned32
    UNITS       "seconds"
    MAX-ACCESS  read-only
    STATUS      current
    DESCRIPTION
        "The value of vRtrMplsLspPathMBBTimeoutIn indicates the amount of time
         remaining, in seconds, for the in-progress MBB path state to time out
         after the initial PATH message has been sent. If the timer expires and
         the in-progress MBB path has not become operationally up, the MBB path
         is torn down and the retry timer is started to schedule a new retry
         cycle."
    ::= { vRtrMplsLspPathEntry 65 }

vRtrMplsLspPathBfdTemplateName   OBJECT-TYPE
    SYNTAX      TNamedItemOrEmpty
    MAX-ACCESS  read-create
    STATUS      current
    DESCRIPTION
        "The value of vRtrMplsLspPathBfdTemplateName specifies the
         TIMETRA-BFD-MIB::tmnxBfdAdminTemplateName used by this LSP path."
    ::= { vRtrMplsLspPathEntry 66 }

vRtrMplsLspPathBfdEnable         OBJECT-TYPE
    SYNTAX      TruthValue
    MAX-ACCESS  read-create
    STATUS      current
    DESCRIPTION
        "The value of vRtrMplsLspPathBfdEnable specifies whether BFD is enabled
         or not for this LSP path."
    DEFVAL      { false }
    ::= { vRtrMplsLspPathEntry 67 }

vRtrMplsLspPathBfdPingIntvl      OBJECT-TYPE
    SYNTAX      Unsigned32 (0 | 60..300)
    UNITS       "seconds"
    MAX-ACCESS  read-create
    STATUS      current
    DESCRIPTION
        "The value of vRtrMplsLspPathBfdPingIntvl specifies the time interval
         for periodic LSP ping for BFD bootstrapping.

         The object vRtrMplsLspPathBfdPingIntvl is applicable to LSPs with
         vRtrMplsLspType set to 'dynamic'.

         When the value of vRtrMplsLspPathBfdPingIntvl is set to '0', it
         disables LSP pings for BFD bootstrapping."
    DEFVAL      { 60 }
    ::= { vRtrMplsLspPathEntry 68 }

vRtrMplsLspPathLastUpdateTime    OBJECT-TYPE
    SYNTAX      TimeStamp
    MAX-ACCESS  read-only
    STATUS      current
    DESCRIPTION
        "The value of vRtrMplsLspPathLastUpdateTime indicates the sysUpTime
         when the last update occurred"
    ::= { vRtrMplsLspPathEntry 69 }

vRtrMplsLspPathLastUpdateId      OBJECT-TYPE
    SYNTAX      Unsigned32
    MAX-ACCESS  read-only
    STATUS      current
    DESCRIPTION
        "The value of vRtrMplsLspPathLastUpdateId indicates the last update ID
         which was processed."
    ::= { vRtrMplsLspPathEntry 70 }

vRtrMplsLspPathLastUpdateState   OBJECT-TYPE
    SYNTAX      INTEGER {
        none    (1),
        success (2),
        fail    (3)
    }
    MAX-ACCESS  read-only
    STATUS      current
    DESCRIPTION
        "The value of vRtrMplsLspPathLastUpdateState indicates whether the last
         update was successful or failed.

         Possible states are
         none (1)   - no update invoked
         success (2) - update successful
         fail   (3) - updated failed"
    ::= { vRtrMplsLspPathEntry 71 }

vRtrMplsLspPathLastUpdFailCode   OBJECT-TYPE
    SYNTAX      TmnxMplsLspFailCode
    MAX-ACCESS  read-only
    STATUS      current
    DESCRIPTION
        "The value of vRtrMplsLspPathLastUpdFailCode indicates the reason code
         for in-progress update failure.

         A value of 'none' indicates that no failure has occurred."
    ::= { vRtrMplsLspPathEntry 72 }

vRtrMplsLspPathBfdUpWaitTimer    OBJECT-TYPE
    SYNTAX      Unsigned32 (1..60)
    UNITS       "seconds"
    MAX-ACCESS  read-create
    STATUS      current
    DESCRIPTION
        "The value of vRtrMplsLspPathBfdUpWaitTimer specifies the time in
         seconds the software will wait for the BFD session to come up.

         The timer object is applicable for LSPs with vRtrMplsLspType set to
         'srTe'.

         The timer is started when BFD is first enabled on a path or BFD
         transitions from up to down. When this timer expires and if BFD
         session has  not yet come up, the path is torn down by removing it
         from TTM and  the IOM and the retry timer is started."
    DEFVAL      { 4 }
    ::= { vRtrMplsLspPathEntry 73 }

vRtrMplsLspPathBfdUpWaitTmLeft   OBJECT-TYPE
    SYNTAX      Unsigned32 (1..60)
    UNITS       "seconds"
    MAX-ACCESS  read-only
    STATUS      current
    DESCRIPTION
        "The value of vRtrMplsLspPathBfdUpWaitTmLeft indicates the time in
         seconds remaining in the vRtrMplsLspPathBfdUpWaitTimer."
    ::= { vRtrMplsLspPathEntry 74 }

vRtrMplsLspPathBfdState          OBJECT-TYPE
    SYNTAX      INTEGER {
        notApplicable (0),
        down          (1),
        up            (2),
        awaitToUp     (3),
        failToStart   (4)
    }
    MAX-ACCESS  read-only
    STATUS      current
    DESCRIPTION
        "The value of vRtrMplsLspPathBfdState indicates state of the BFD
         session  on the LSP path."
    ::= { vRtrMplsLspPathEntry 75 }

vRtrMplsLspPathBfdStartFailRsn   OBJECT-TYPE
    SYNTAX      DisplayString (SIZE (0..80))
    MAX-ACCESS  read-only
    STATUS      current
    DESCRIPTION
        "The value of vRtrMplsLspPathBfdStartFailRsn indicates the failure
         reason when vRtrMplsLspPathBfdState is value 'failToStart'."
    ::= { vRtrMplsLspPathEntry 76 }

vRtrMplsLspPathBfdOperUpWaitTmr  OBJECT-TYPE
    SYNTAX      Unsigned32 (1..60)
    UNITS       "seconds"
    MAX-ACCESS  read-only
    STATUS      current
    DESCRIPTION
        "The value of vRtrMplsLspPathBfdOperUpWaitTmr indicates operational
         value of the time in seconds the software will wait for the BFD
         session to come up.

         When value of vRtrMplsLspPathBfdEnable to 'true',
         vRtrMplsLspPathBfdOperUpWaitTmr  will be set to
         vRtrMplsLspPathBfdUpWaitTimer.

         When value of vRtrMplsLspBfdEnable to 'true',
         vRtrMplsLspPathBfdOperUpWaitTmr  will be set to
         vRtrMplsLspExtBfdUpWaitTimer.

         When vRtrMplsLspPathBfdEnable and vRtrMplsLspBfdEnable are set to
         'false',  the value of vRtrMplsLspPathBfdOperUpWaitTmr is set to 0."
    ::= { vRtrMplsLspPathEntry 77 }

vRtrMplsLspPathSelfPingOprState  OBJECT-TYPE
    SYNTAX      TmnxOperState
    MAX-ACCESS  read-only
    STATUS      current
    DESCRIPTION
        "The current operational state for self-ping for this LSP path."
    ::= { vRtrMplsLspPathEntry 78 }

vRtrMplsLspPathStatTable         OBJECT-TYPE
    SYNTAX      SEQUENCE OF VRtrMplsLspPathStatEntry
    MAX-ACCESS  not-accessible
    STATUS      current
    DESCRIPTION
        "The vRtrMplsLspPathStatTable has an entry for an association between a
         Labeled Switch Path (LSP) in the vRtrMplsLspTable and a path (or
         tunnel) entry in the mplsTunnelTable."
    ::= { tmnxMplsObjs 5 }

vRtrMplsLspPathStatEntry         OBJECT-TYPE
    SYNTAX      VRtrMplsLspPathStatEntry
    MAX-ACCESS  not-accessible
    STATUS      current
    DESCRIPTION
        "Each row entry represents a collection of statistics for an
         association between a Labeled Switch Path (LSP) in the
         vRtrMplsLspTable and a path (or tunnel) entry in the mplsTunnelTable.

         Entries cannot be created and deleted via SNMP SET operations."
    AUGMENTS    { vRtrMplsLspPathEntry }
    ::= { vRtrMplsLspPathStatTable 1 }

VRtrMplsLspPathStatEntry         ::= SEQUENCE
{
    vRtrMplsLspPathTimeUp            TimeInterval,
    vRtrMplsLspPathTimeDown          TimeInterval,
    vRtrMplsLspPathRetryAttempts     Unsigned32,
    vRtrMplsLspPathTransitionCount   Counter32,
    vRtrMplsLspPathCspfQueries       Counter32
}

vRtrMplsLspPathTimeUp            OBJECT-TYPE
    SYNTAX      TimeInterval
    MAX-ACCESS  read-only
    STATUS      current
    DESCRIPTION
        "The total time in 10-millisecond units that this LSP path has
         been operational.  For example, the percentage up time can be
         determined by computing (vRtrMplsLspPathTimeUp/vRtrMplsLspAge * 100 %)."
    ::= { vRtrMplsLspPathStatEntry 1 }

vRtrMplsLspPathTimeDown          OBJECT-TYPE
    SYNTAX      TimeInterval
    MAX-ACCESS  read-only
    STATUS      current
    DESCRIPTION
        "The total time in 10-millisecond units that this LSP Path has not been
         operational."
    ::= { vRtrMplsLspPathStatEntry 2 }

vRtrMplsLspPathRetryAttempts     OBJECT-TYPE
    SYNTAX      Unsigned32
    MAX-ACCESS  read-only
    STATUS      current
    DESCRIPTION
        "The number of unsuccessful attempts which have been made to signal
         this path. As soon as the path gets signalled, this is set to 0."
    ::= { vRtrMplsLspPathStatEntry 3 }

vRtrMplsLspPathTransitionCount   OBJECT-TYPE
    SYNTAX      Counter32
    MAX-ACCESS  read-only
    STATUS      current
    DESCRIPTION
        "The object vRtrMplsLspPathTransitionCount maintains the number of
         transitions that have occurred for this LSP."
    ::= { vRtrMplsLspPathStatEntry 4 }

vRtrMplsLspPathCspfQueries       OBJECT-TYPE
    SYNTAX      Counter32
    MAX-ACCESS  read-only
    STATUS      current
    DESCRIPTION
        "The value of vRtrMplsLspPathCspfQueries indicates the number of CSPF
         queries that have been made for this LSP path."
    ::= { vRtrMplsLspPathStatEntry 5 }

vRtrMplsXCTable                  OBJECT-TYPE
    SYNTAX      SEQUENCE OF VRtrMplsXCEntry
    MAX-ACCESS  not-accessible
    STATUS      current
    DESCRIPTION
        "This table has an entry for each mplsXCEntry
         in the mplsXCTable.  It serves as an another
         indirect index to the mplsXCTable."
    ::= { tmnxMplsObjs 6 }

vRtrMplsXCEntry                  OBJECT-TYPE
    SYNTAX      VRtrMplsXCEntry
    MAX-ACCESS  not-accessible
    STATUS      current
    DESCRIPTION
        "An entry in this table represents the indices to be used to search the
         mplsXCTable."
    INDEX       { mplsXCLspId }
    ::= { vRtrMplsXCTable 1 }

VRtrMplsXCEntry                  ::= SEQUENCE
{
    vRtrMplsXCIndex                  Integer32,
    vRtrMplsInSegmentIfIndex         InterfaceIndexOrZero,
    vRtrMplsInSegmentLabel           MplsLabel,
    vRtrMplsOutSegmentIndex          Integer32,
    vRtrMplsERHopTunnelIndex         Integer32,
    vRtrMplsARHopTunnelIndex         Integer32,
    vRtrMplsRsvpSessionIndex         Unsigned32,
    vRtrMplsXCFailCode               TmnxMplsLspFailCode,
    vRtrMplsXCCHopTableIndex         Integer32
}

vRtrMplsXCIndex                  OBJECT-TYPE
    SYNTAX      Integer32 (1..2147483647)
    MAX-ACCESS  read-only
    STATUS      current
    DESCRIPTION
        "An index of the mplsXCTable. It represents mplsXCIndex, a field of the
         mplsXCTable."
    ::= { vRtrMplsXCEntry 1 }

vRtrMplsInSegmentIfIndex         OBJECT-TYPE
    SYNTAX      InterfaceIndexOrZero
    MAX-ACCESS  read-only
    STATUS      current
    DESCRIPTION
        "An index of the mplsXCTable.  It represents
         mplsInSegmentIfIndex of the mplsInSegmentTable."
    ::= { vRtrMplsXCEntry 2 }

vRtrMplsInSegmentLabel           OBJECT-TYPE
    SYNTAX      MplsLabel
    MAX-ACCESS  read-only
    STATUS      current
    DESCRIPTION
        "An index of the mplsXCTable. It represents mplsInSegmentLabel of the
         mplsInSegmentTable."
    ::= { vRtrMplsXCEntry 3 }

vRtrMplsOutSegmentIndex          OBJECT-TYPE
    SYNTAX      Integer32 (0..2147483647)
    MAX-ACCESS  read-only
    STATUS      current
    DESCRIPTION
        "An index of the mplsXCTable. It represents mplsOutSegmentIndex of the
         mplsOutSegmentTable."
    ::= { vRtrMplsXCEntry 4 }

vRtrMplsERHopTunnelIndex         OBJECT-TYPE
    SYNTAX      Integer32
    MAX-ACCESS  read-only
    STATUS      current
    DESCRIPTION
        "Primary index into the mplsTunnelHopTable identifying a particular
         recorded hop list (stores ERO in LSR)."
    ::= { vRtrMplsXCEntry 5 }

vRtrMplsARHopTunnelIndex         OBJECT-TYPE
    SYNTAX      Integer32
    MAX-ACCESS  read-only
    STATUS      current
    DESCRIPTION
        "Primary index into the mplsTunnelARHopTable identifying a particular
         recorded hop list (stores RRO in LSR)."
    ::= { vRtrMplsXCEntry 6 }

vRtrMplsRsvpSessionIndex         OBJECT-TYPE
    SYNTAX      Unsigned32
    MAX-ACCESS  read-only
    STATUS      current
    DESCRIPTION
        "An index into the TIMETRA-RSVP-MIB::vRtrRsvpSessionTable identifying a
         particular RSVP session."
    ::= { vRtrMplsXCEntry 7 }

vRtrMplsXCFailCode               OBJECT-TYPE
    SYNTAX      TmnxMplsLspFailCode
    MAX-ACCESS  read-only
    STATUS      current
    DESCRIPTION
        "The value of vRtrMplsXCFailCode indicates the reason code for
         cross-connect failure. A value of 0 indicates that no failure
         occurred."
    ::= { vRtrMplsXCEntry 8 }

vRtrMplsXCCHopTableIndex         OBJECT-TYPE
    SYNTAX      Integer32
    MAX-ACCESS  read-only
    STATUS      current
    DESCRIPTION
        "Index to the vRtrMplsTunnelCHopTable entries that specify the hops for
         the CSPF path for a detour LSP for this tunnel."
    ::= { vRtrMplsXCEntry 9 }

vRtrMplsGeneralTable             OBJECT-TYPE
    SYNTAX      SEQUENCE OF VRtrMplsGeneralEntry
    MAX-ACCESS  not-accessible
    STATUS      current
    DESCRIPTION
        "The vRtrMplsGeneralTable contains objects for general control and
         management of an MPLS protocol instance within a virtual router."
    ::= { tmnxMplsObjs 7 }

vRtrMplsGeneralEntry             OBJECT-TYPE
    SYNTAX      VRtrMplsGeneralEntry
    MAX-ACCESS  not-accessible
    STATUS      current
    DESCRIPTION
        "Each row entry represents an instance of the MPLS protocol running
         within a virtual router.  Entries in this table cannot be
         created and deleted via SNMP SET operations.  An entry in this table
         is created by the agent when vRtrMplsStatus in the vRtrConfTable is
         set to 'create'.  The entry is destroyed when vRtrMplsStatus is set
         to 'delete'"
    INDEX       { vRtrID }
    ::= { vRtrMplsGeneralTable 1 }

VRtrMplsGeneralEntry             ::= SEQUENCE
{
    vRtrMplsGeneralLastChange        TimeStamp,
    vRtrMplsGeneralAdminState        TmnxAdminState,
    vRtrMplsGeneralOperState         TmnxOperState,
    vRtrMplsGeneralPropagateTtl      TruthValue,
    vRtrMplsGeneralTE                INTEGER,
    vRtrMplsGeneralNewLspIndex       TestAndIncr,
    vRtrMplsGeneralOptimizeTimer     Unsigned32,
    vRtrMplsGeneralFRObject          TruthValue,
    vRtrMplsGeneralResignalTimer     Unsigned32,
    vRtrMplsGeneralHoldTimer         Unsigned32,
    vRtrMplsGeneralDynamicBypass     TruthValue,
    vRtrMplsGeneralNextResignal      Unsigned32,
    vRtrMplsGeneralOperDownReason    TmnxMplsOperDownReasonCode,
    vRtrMplsGeneralSrlgFrr           TruthValue,
    vRtrMplsGeneralSrlgFrrStrict     TruthValue,
    vRtrMplsGeneralNewP2mpInstIndex  TestAndIncr,
    vRtrMplsGeneralLeastFillMinThd   Unsigned32,
    vRtrMplsGenLeastFillReoptiThd    Unsigned32,
    vRtrMplsGeneralUseSrlgDB         TruthValue,
    vRtrMplsGeneralP2mpResigTimer    Unsigned32,
    vRtrMplsGeneralP2mpNextResignal  Unsigned32,
    vRtrMplsGeneralSecFastRetryTimer Unsigned32,
    vRtrMplsGeneralShortTTLPropLocal TruthValue,
    vRtrMplsGeneralShortTTLPropTrans TruthValue,
    vRtrMplsGeneralStaticLspFRTimer  Unsigned32,
    vRtrMplsGeneralAutoBWDefSampMul  Unsigned32,
    vRtrMplsGeneralAutoBWDefAdjMul   Unsigned32,
    vRtrMplsGeneralExpBackoffRetry   TruthValue,
    vRtrMplsGeneralCspfOnLooseHop    TruthValue,
    vRtrMplsGeneralP2PMaxByPassAssoc Unsigned32,
    vRtrMplsGenP2pActPathFastRetry   Unsigned32,
    vRtrMplsGenP2mpS2lFastRetry      Unsigned32,
    vRtrMplsGenLspInitRetryTimeout   Unsigned32,
    vRtrMplsLoggerEventBundling      TruthValue,
    vRtrMplsGenIssuMplsLockdown      TruthValue,
    vRtrMplsGenFRAdminGroup          TruthValue,
    vRtrMplsGenRetryOnIgpOverload    TruthValue,
    vRtrMplsGenMbbPrefCurrentHops    TruthValue,
    vRtrMplsGeneralBypassResigTimer  Unsigned32,
    vRtrMplsGenBypassNextResignal    Unsigned32,
    vRtrMplsGeneralNewLspSRIndex     TestAndIncr,
    vRtrMplsGeneralPceReport         BITS,
    vRtrMplsGeneralEntropyLblRsvpTe  INTEGER,
    vRtrMplsGeneralEntropyLblSrTe    INTEGER,
    vRtrMplsGeneralAuxStats          BITS,
    vRtrMplsGenSrTeResignalTimer     Unsigned32,
    vRtrMplsGenMaxBypassPlrAssoc     Unsigned32,
    vRtrMplsGenLspSelfPingInterval   TimeInterval,
    vRtrMplsGenLspSelfPingTimeout    TimeInterval,
    vRtrMplsGenLspSelfPingRsvpTe     INTEGER,
    vRtrMplsGenSrTeResigOnIgpEvent   TruthValue,
    vRtrMplsGeneralV6OperState       TmnxOperState,
    vRtrMplsGeneralV6OperDownReason  TmnxMplsOperDownReasonCode,
    vRtrMplsGenSrteNextResignal      Unsigned32
}

vRtrMplsGeneralLastChange        OBJECT-TYPE
    SYNTAX      TimeStamp
    MAX-ACCESS  read-only
    STATUS      current
    DESCRIPTION
        "The sysUpTime when this row was last modified."
    ::= { vRtrMplsGeneralEntry 1 }

vRtrMplsGeneralAdminState        OBJECT-TYPE
    SYNTAX      TmnxAdminState
    MAX-ACCESS  read-create
    STATUS      current
    DESCRIPTION
        "When vRtrMplsGeneralAdminState is set to 'inService', the agent
         attempts to enable the MPLS protocol instance on this router.

         When vRtrMplsGeneralAdminState is set to 'outOfService', the agent
         attempts to disable the MPLS protocol instance on this router."
    DEFVAL      { outOfService }
    ::= { vRtrMplsGeneralEntry 2 }

vRtrMplsGeneralOperState         OBJECT-TYPE
    SYNTAX      TmnxOperState
    MAX-ACCESS  read-only
    STATUS      current
    DESCRIPTION
        "vRtrMplsGeneralOperState indicates the current operating state of this
         MPLS protocol instance on this router."
    ::= { vRtrMplsGeneralEntry 3 }

vRtrMplsGeneralPropagateTtl      OBJECT-TYPE
    SYNTAX      TruthValue
    MAX-ACCESS  read-create
    STATUS      obsolete
    DESCRIPTION
        "When vRtrMplsGeneralPropagateTtl is set to 'true', for all LSPs,
         the ingress ESR writes the TTL of the IP packet in the label and
         each transit ESR decrements the TTL in the label.  At the egress
         ESR the TTL value from the label is written into the IP packet.

         When vRtrMplsGeneralPropagateTtl is set to 'false', the ingress
         ESR ignores the IP packet TTl and writes the value of 255 into
         the label, while the egress ESR does not write the label TTL
         into the IP packet.  This assumes that all ESRs have been
         configured to have vRtrMplsGeneralPropagateTtl set to 'false',
         or this may result in unpredictable behavior.

         This object was made obsolete in release 11.0."
    DEFVAL      { true }
    ::= { vRtrMplsGeneralEntry 4 }

vRtrMplsGeneralTE                OBJECT-TYPE
    SYNTAX      INTEGER {
        none   (1),
        bgp    (2),
        bgpigp (3)
    }
    MAX-ACCESS  read-create
    STATUS      obsolete
    DESCRIPTION
        "The value of vRtrMplsGeneralTE specifies the type of traffic
         engineering used with this MPLS instance.

         This object was made obsolete in release 11.0."
    DEFVAL      { none }
    ::= { vRtrMplsGeneralEntry 5 }

vRtrMplsGeneralNewLspIndex       OBJECT-TYPE
    SYNTAX      TestAndIncr
    MAX-ACCESS  read-only
    STATUS      current
    DESCRIPTION
        "This object is used to assign values to vRtrMplsLspIndex as
         described in 'Textual Conventions for SNMPv2'.  The network
         manager reads the object, and then writes the value back
         in the SET request that creates a new instance of
         vRtrMplsLspEntry.  If the SET fails with the code
         'inconsistentValue', then the process must be repeated.
         If the the SET succeeds, then the object is incremented
         and the new instance is created according to the manager's
         directions."
    ::= { vRtrMplsGeneralEntry 6 }

vRtrMplsGeneralOptimizeTimer     OBJECT-TYPE
    SYNTAX      Unsigned32 (0..65535)
    UNITS       "seconds"
    MAX-ACCESS  read-create
    STATUS      current
    DESCRIPTION
        "The value of vRtrMplsGeneralOptimizeTimer specifies the time, in
         seconds, the software will wait before attempting to re-optimize the
         LSPs.

         When CSPF is enabled, changes in the network topology may cause the
         existing path of a loose-hop LSP to become sub-optimal. Such LSPs can
         be re-optimized and rerouted through more optimal paths by
         recalculating the path for the LSP at periodic intervals. This
         interval is controlled by the optimize timer.

         A value of 0 indicates that optimization has been disabled.

         The value for vRtrMplsGeneralOptimizeTimer is by default inherited by
         all LSPs and their paths."
    DEFVAL      { 0 }
    ::= { vRtrMplsGeneralEntry 7 }

vRtrMplsGeneralFRObject          OBJECT-TYPE
    SYNTAX      TruthValue
    MAX-ACCESS  read-create
    STATUS      current
    DESCRIPTION
        "The value of vRtrMplsGeneralFRObject specifies whether fast reroute,
         for LSPs using 'Facility Backup', is signalled with or without the
         fast reroute object. The value of vRtrMplsGeneralFRObject is ignored
         if fast reroute is disabled for the LSP or if the LSP is using
         'One-to-one Backup'.

         The value for vRtrMplsGeneralFRObject is by default inherited by all
         LSPs."
    DEFVAL      { true }
    ::= { vRtrMplsGeneralEntry 8 }

vRtrMplsGeneralResignalTimer     OBJECT-TYPE
    SYNTAX      Unsigned32 (0 | 30..10080)
    UNITS       "minutes"
    MAX-ACCESS  read-create
    STATUS      current
    DESCRIPTION
        "The value of vRtrMplsGeneralResignalTimer specifies the value for the
         P2P (point-to-point) LSP resignal timer, that is the time, in minutes,
         the software will wait before attempting to resignal the P2P LSPs.

         When the resignal timer expires, if the new recorded hop list (RRO)
         for an P2P LSP has a better metric than the current recorded hop list,
         an attempt will be made to resignal that P2P LSP using the
         make-before-break mechanism. If the attempt to resignal an P2P LSP
         fails, the P2P LSP will continue to use the existing path and a
         resignal will be attempted the next time the timer expires.

         A value of 0 for the resignal timer indicates that timer-based P2P LSP
         resignalling has been disabled."
    DEFVAL      { 0 }
    ::= { vRtrMplsGeneralEntry 9 }

vRtrMplsGeneralHoldTimer         OBJECT-TYPE
    SYNTAX      Unsigned32 (0..10)
    UNITS       "seconds"
    MAX-ACCESS  read-create
    STATUS      current
    DESCRIPTION
        "The value of vRtrMplsGeneralHoldTimer specifies the time, in seconds,
         for which the ingress node holds a bit before programming its data
         plane and declaring the lsp up to the service module.

         A value of 0 indicates that the hold timer has been disabled."
    DEFVAL      { 1 }
    ::= { vRtrMplsGeneralEntry 10 }

vRtrMplsGeneralDynamicBypass     OBJECT-TYPE
    SYNTAX      TruthValue
    MAX-ACCESS  read-create
    STATUS      current
    DESCRIPTION
        "The value of vRtrMplsGeneralDynamicBypass specifies whether dynamic
         bypass tunnels are enabled.

         By default, dynamic bypass tunnels are enabled."
    DEFVAL      { true }
    ::= { vRtrMplsGeneralEntry 11 }

vRtrMplsGeneralNextResignal      OBJECT-TYPE
    SYNTAX      Unsigned32
    MAX-ACCESS  read-only
    STATUS      current
    DESCRIPTION
        "The value of vRtrMplsGeneralNextResignal indicates the time remaining,
         in minutes, for the vRtrMplsGeneralResignalTimer to expire."
    ::= { vRtrMplsGeneralEntry 12 }

vRtrMplsGeneralOperDownReason    OBJECT-TYPE
    SYNTAX      TmnxMplsOperDownReasonCode
    MAX-ACCESS  read-only
    STATUS      current
    DESCRIPTION
        "The value of vRtrMplsGeneralOperDownReason indicates the reason due to
         which the MPLS instance is operationally down."
    ::= { vRtrMplsGeneralEntry 13 }

vRtrMplsGeneralSrlgFrr           OBJECT-TYPE
    SYNTAX      TruthValue
    MAX-ACCESS  read-create
    STATUS      current
    DESCRIPTION
        "The value of vRtrMplsGeneralSrlgFrr specifies whether Shared Risk
         Link Group (SRLG) constraint will be used in the computation of
         FRR bypass or detour to be associated with any primary LSP path
         on the system.  When the value of vRtrMplsGeneralSrlgFrr is
         'true' the use of SRLG constraint is enabled.

         By default, the use of SRLG constraint is disabled."
    DEFVAL      { false }
    ::= { vRtrMplsGeneralEntry 14 }

vRtrMplsGeneralSrlgFrrStrict     OBJECT-TYPE
    SYNTAX      TruthValue
    MAX-ACCESS  read-create
    STATUS      current
    DESCRIPTION
        "The value of vRtrMplsGeneralSrlgFrrStrict specifies whether
         to associate the LSP with a bypass or signal a detour if a
         bypass or detour satisfies all other constraints except the SRLG
         constraints.  When the value of vRtrMplsGeneralSrlgFrrStrict is
         'true' and a path that meets SRLG constraints is not found, the
         bypass or detour is not setup. If this value is set to 'true'
         when vRtrMplsGeneralSrlgFrr is set to 'false', vRtrMplsGeneralSrlgFrr
         is set to 'true' also.

         By default, the value of vRtrMplsGeneralSrlgFrrStrict is 'false'."
    DEFVAL      { false }
    ::= { vRtrMplsGeneralEntry 15 }

vRtrMplsGeneralNewP2mpInstIndex  OBJECT-TYPE
    SYNTAX      TestAndIncr
    MAX-ACCESS  read-only
    STATUS      current
    DESCRIPTION
        "The value of vRtrMplsGeneralNewP2mpInstIndex specifies the object that is used to assign
         values to vRtrMplsP2mpInstIndex as described in 'Textual Conventions for SNMPv2'.  The
         network manager reads the object, and then writes the value back in the SET request that
         creates a new instance of vRtrMplsP2mpInstEntry.  If the SET fails with the code
         'inconsistentValue', then the process must be repeated.  If the the SET succeeds, then the
         object is incremented and the new instance is created according to the manager's
         directions."
    ::= { vRtrMplsGeneralEntry 16 }

vRtrMplsGeneralLeastFillMinThd   OBJECT-TYPE
    SYNTAX      Unsigned32 (1..100)
    MAX-ACCESS  read-create
    STATUS      current
    DESCRIPTION
        "The value of vRtrMplsGeneralLeastFillMinThd specifies in percentage
         the least minimum threshold parameter used in the least-fill path
         selection process. When comparing the percentage of least available
         link bandwidth across the sorted paths, whenever two percentages
         differ by less than the value configured as the
         vRtrMplsGeneralLeastFillMinThd, CSPF will consider them equal and will
         apply a random number generator to select the path among these paths. "
    DEFVAL      { 5 }
    ::= { vRtrMplsGeneralEntry 17 }

vRtrMplsGenLeastFillReoptiThd    OBJECT-TYPE
    SYNTAX      Unsigned32 (1..100)
    MAX-ACCESS  read-create
    STATUS      current
    DESCRIPTION
        "The value of vRtrMplsGenLeastFillReoptiThd specifies in percentage the
         least reoptimization threshold parameter used in the least-fill path
         selection process.

         During a timer-based resignaling of an LSP path which has
         vRtrMplsLspLeastFill enabled, CSPF will first update the
         least-available bandwidth figure for the current path of this LSP. It
         then applies the least-fill path selection method to select a new path
         for this LSP. If the new computed path has the same cost as the
         current path, it will compare the least-available bandwidth figures of
         the two paths and if the difference exceeds
         vRtrMplsGenLeastFillReoptiThd, a trap will be generated to indicate
         that a better least-fill path is available for this LSP. "
    DEFVAL      { 10 }
    ::= { vRtrMplsGeneralEntry 18 }

vRtrMplsGeneralUseSrlgDB         OBJECT-TYPE
    SYNTAX      TruthValue
    MAX-ACCESS  read-create
    STATUS      current
    DESCRIPTION
        "The value of vRtrMplsGeneralUseSrlgDB specifies whether the use of the
         user SRLG database by CSPF is enabled."
    DEFVAL      { false }
    ::= { vRtrMplsGeneralEntry 19 }

vRtrMplsGeneralP2mpResigTimer    OBJECT-TYPE
    SYNTAX      Unsigned32 (0 | 60..10080)
    UNITS       "minutes"
    MAX-ACCESS  read-create
    STATUS      current
    DESCRIPTION
        "The value of vRtrMplsGeneralP2mpResigTimer specifies the value for the
         P2MP (point to multi point) LSP resignal timer, that is the time, in
         minutes, the software will wait before attempting to resignal the P2MP
         LSPs.

         When the resignal timer expires, an attempt to resignal the entire
         P2MP instance comprising all source to leaf (S2Ls) are done, the IGP
         or TE metric of the S2Ls are not taken into consideration.

         If the attempt to resignal an P2MP LSP fails, the P2MP LSP will
         continue to use the existing S2Ls and a resignal will be attempted the
         next time the timer expires.

         A value of 0 for the resignal timer indicates that timer-based P2MP
         LSP resignalling has been disabled."
    DEFVAL      { 0 }
    ::= { vRtrMplsGeneralEntry 20 }

vRtrMplsGeneralP2mpNextResignal  OBJECT-TYPE
    SYNTAX      Unsigned32
    MAX-ACCESS  read-only
    STATUS      current
    DESCRIPTION
        "The value of vRtrMplsGeneralP2mpNextResignal indicates the time
         remaining, in minutes, for the vRtrMplsGeneralP2mpResigTimer to
         expire."
    ::= { vRtrMplsGeneralEntry 21 }

vRtrMplsGeneralSecFastRetryTimer OBJECT-TYPE
    SYNTAX      Unsigned32 (0..10)
    UNITS       "seconds"
    MAX-ACCESS  read-create
    STATUS      current
    DESCRIPTION
        "The value of vRtrMplsGeneralSecFastRetryTimer specifies the value, in
         seconds, used as fast retry timer for a secondary path. If the first
         attempt to setup a secondary path fails due to a path error, the fast
         retry timer will be started for the secondary path so that the path
         can be retried sooner. If the next attempt also fails, further retries
         for the path will use the configured value for LSP retry timer,
         vRtrMplsLspRetryTimer.

         If retry timer for the LSP is configured to be less than the MPLS
         secondary-fast-retry-timer, all retries for the secondary path will
         use the LSP retry timer.

         A value of 0 indicates that fast retry for secondary paths has been
         disabled."
    DEFVAL      { 0 }
    ::= { vRtrMplsGeneralEntry 22 }

vRtrMplsGeneralShortTTLPropLocal OBJECT-TYPE
    SYNTAX      TruthValue
    MAX-ACCESS  read-create
    STATUS      current
    DESCRIPTION
        "The value of vRtrMplsGeneralShortTTLPropLocal specifies whether or not
         to enable the propagation of time to live (TTL) from the IP packet
         header into the header of the resulting MPLS packet for all local
         packets forwarded over a LSP shortcut. When the value is 'true' TTL is
         propagated from the IP packet header into the header of the resulting
         MPLS packet."
    DEFVAL      { true }
    ::= { vRtrMplsGeneralEntry 23 }

vRtrMplsGeneralShortTTLPropTrans OBJECT-TYPE
    SYNTAX      TruthValue
    MAX-ACCESS  read-create
    STATUS      current
    DESCRIPTION
        "The value of vRtrMplsGeneralShortTTLPropTrans specifies whether or not
         to enable the propagation of time to live (TTL) from the IP packet
         header into the header of the resulting MPLS packet for all transit
         packets forwarded over a LSP shortcut. When the value is 'true' TTL is
         propagated from the IP packet header into the header of the resulting
         MPLS packet."
    DEFVAL      { true }
    ::= { vRtrMplsGeneralEntry 24 }

vRtrMplsGeneralStaticLspFRTimer  OBJECT-TYPE
    SYNTAX      Unsigned32 (1..30)
    UNITS       "seconds"
    MAX-ACCESS  read-create
    STATUS      current
    DESCRIPTION
        "The value of vRtrMplsGeneralStaticLspFRTimer specifies the audit time
         for static LSPs which are not currently up."
    DEFVAL      { 30 }
    ::= { vRtrMplsGeneralEntry 25 }

vRtrMplsGeneralAutoBWDefSampMul  OBJECT-TYPE
    SYNTAX      Unsigned32 (1..511)
    MAX-ACCESS  read-create
    STATUS      current
    DESCRIPTION
        "The value of vRtrMplsGeneralAutoBWDefSampMul specifies the global
         default for collection intervals in a sample interval."
    DEFVAL      { 1 }
    ::= { vRtrMplsGeneralEntry 26 }

vRtrMplsGeneralAutoBWDefAdjMul   OBJECT-TYPE
    SYNTAX      Unsigned32 (1..16383)
    MAX-ACCESS  read-create
    STATUS      current
    DESCRIPTION
        "The value of vRtrMplsGeneralAutoBWDefAdjMul specifies the global
         default for collection intervals in an adjust interval."
    DEFVAL      { 288 }
    ::= { vRtrMplsGeneralEntry 27 }

vRtrMplsGeneralExpBackoffRetry   OBJECT-TYPE
    SYNTAX      TruthValue
    MAX-ACCESS  read-create
    STATUS      current
    DESCRIPTION
        "The value of vRtrMplsGeneralExpBackoffRetry specifies the state of
         Exponential Backoff Retry mechanism."
    DEFVAL      { false }
    ::= { vRtrMplsGeneralEntry 28 }

vRtrMplsGeneralCspfOnLooseHop    OBJECT-TYPE
    SYNTAX      TruthValue
    MAX-ACCESS  read-create
    STATUS      current
    DESCRIPTION
        "The value of vRtrMplsGeneralCspfOnLooseHop specifies whether the
         Constrained Shortest Path First (CSPF) calculation till the next loose
         hop is enabled or not."
    DEFVAL      { false }
    ::= { vRtrMplsGeneralEntry 29 }

vRtrMplsGeneralP2PMaxByPassAssoc OBJECT-TYPE
    SYNTAX      Unsigned32 (100..131072)
    MAX-ACCESS  read-create
    STATUS      current
    DESCRIPTION
        "The value of vRtrMplsGeneralP2PMaxByPassAssoc specifies the maximum
         number of LSP primary paths that can associate with each manual or
         dynamic bypass point-to-point (P2P) LSP."
    DEFVAL      { 1000 }
    ::= { vRtrMplsGeneralEntry 30 }

vRtrMplsGenP2pActPathFastRetry   OBJECT-TYPE
    SYNTAX      Unsigned32 (0..10)
    UNITS       "seconds"
    MAX-ACCESS  read-create
    STATUS      current
    DESCRIPTION
        "The value of vRtrMplsGenP2pActPathFastRetry specifies the time, in
         seconds, active path point-to-point (P2P) LSP waits before it attempts
         to re-establish itself. This timer is started after first attempt to
         setup active path P2P LSP fails.

         When vRtrMplsGenP2pActPathFastRetry is set to 0, fast retry timer for
         active path P2P LSP is disabled."
    DEFVAL      { 0 }
    ::= { vRtrMplsGeneralEntry 31 }

vRtrMplsGenP2mpS2lFastRetry      OBJECT-TYPE
    SYNTAX      Unsigned32 (0..10)
    UNITS       "seconds"
    MAX-ACCESS  read-create
    STATUS      current
    DESCRIPTION
        "The value of vRtrMplsGenP2mpS2lFastRetry specifies the time, in
         seconds, active path point to multipoint (P2MP) source to leaf (S2L)
         LSP waits before it attempts to re-establish itself. This timer is
         started after first attempt to setup active path P2MP S2L LSP fails.

         When vRtrMplsGenP2mpS2lFastRetry is set to 0, fast retry timer for
         active path P2MP S2L LSP is disabled."
    DEFVAL      { 0 }
    ::= { vRtrMplsGeneralEntry 32 }

vRtrMplsGenLspInitRetryTimeout   OBJECT-TYPE
    SYNTAX      Unsigned32 (10..600)
    UNITS       "seconds"
    MAX-ACCESS  read-create
    STATUS      current
    DESCRIPTION
        "The value of vRtrMplsGenLspInitRetryTimeout specifies the amount of
         time in seconds the software waits for an LSP path to come up after
         sending out the initial Path message. If the initial retry timeout
         period expires and the LSP path is not up, it is torn down and the LSP
         retry timer is started to schedule a new retry cycle using a new
         LSPId."
    DEFVAL      { 30 }
    ::= { vRtrMplsGeneralEntry 33 }

vRtrMplsLoggerEventBundling      OBJECT-TYPE
    SYNTAX      TruthValue
    MAX-ACCESS  read-create
    STATUS      current
    DESCRIPTION
        "The value of vRtrMplsLoggerEventBundling specifies whether or not the
         notification bundling mechanism is enabled.

         When the value of vRtrMplsLoggerEventBundling is set to 'true', all
         TIMETRA-SYSTEM-MIB::tmnxConfigCreate and
         TIMETRA-SYSTEM-MIB::tmnxConfigDelete notifications that are generated
         because of creation or deletion of entries in the vRtrMplsXCTable
         during quiet period of 2 minutes are bundled in a single notification.

         An entry is created or deleted in vRtrMplsXCTable when a RSVP session
         is created or deleted on this ingress, transit or egress router
         instance causing creation or deletion of an entry in
         TIMETRA-RSVP-MIB::vRtrRsvpSessionTable.

         A vRtrMplsXCBundleChange notification is generated after every quiet
         interval of 2 minutes if one or more RSVP session changed state and
         retained that state during the quiet interval. However if the state of
         the RSVP sessions does not remain stable for an entire quiet interval,
         the notification is generated after the maximum interval period of 10
         minutes has elapsed."
    DEFVAL      { false }
    ::= { vRtrMplsGeneralEntry 34 }

vRtrMplsGenIssuMplsLockdown      OBJECT-TYPE
    SYNTAX      TruthValue
    MAX-ACCESS  read-only
    STATUS      current
    DESCRIPTION
        "The value of vRtrMplsGenIssuMplsLockdown indicates if MPLS has entered
         the state of not accepting new requests for creation of LSPs
         (local/transit) during the minor ISSU(In Service Software Update)
         operation."
    ::= { vRtrMplsGeneralEntry 39 }

vRtrMplsGenFRAdminGroup          OBJECT-TYPE
    SYNTAX      TruthValue
    MAX-ACCESS  read-create
    STATUS      current
    DESCRIPTION
        "The value of vRtrMplsGenFRAdminGroup specifies whether or not the use
         of administrative group constraints on a FRR backup LSP at a
         Point-of-Local Repair(PLR) node is enabled.

         When the value of vRtrMplsGenFRAdminGroup is set to 'true', each PLR
         node reads the admin group constraints in the FAST_REROUTE object in
         the Path message of the LSP primary path.

         If the FAST_REROUTE object is not included in the Path message, then
         the PLR will read the admin group constraints from the Session
         Attribute object in the Path message."
    DEFVAL      { false }
    ::= { vRtrMplsGeneralEntry 40 }

vRtrMplsGenRetryOnIgpOverload    OBJECT-TYPE
    SYNTAX      TruthValue
    MAX-ACCESS  read-create
    STATUS      current
    DESCRIPTION
        "The value of vRtrMplsGenRetryOnIgpOverload specifies whether or not to
         teardown LSPs transiting through nodes that are in IGP overload state.

         When the value of vRtrMplsGenRetryOnIgpOverload is set to 'true' and a
         node is reporting that it is in IGP overload state, MPLS will tear-
         down and retry LSP paths that are transiting through the overloaded
         node.

         When the value of vRtrMplsGenRetryOnIgpOverload is set to 'false' and
         a node is reporting that it is in IGP overload state, MPLS will not
         tear down LSP paths that are transiting through the overloaded node."
    DEFVAL      { false }
    ::= { vRtrMplsGeneralEntry 41 }

vRtrMplsGenMbbPrefCurrentHops    OBJECT-TYPE
    SYNTAX      TruthValue
    MAX-ACCESS  read-create
    STATUS      current
    DESCRIPTION
        "The value of vRtrMplsGenMbbPrefCurrentHops specifies whether or not
         Constrained Shortest Path First (CSPF) for a Make-before-break (MBB)
         path should give preference to hops/links used by the current Labeled
         Switch Path (LSP)."
    DEFVAL      { false }
    ::= { vRtrMplsGeneralEntry 42 }

vRtrMplsGeneralBypassResigTimer  OBJECT-TYPE
    SYNTAX      Unsigned32 (0 | 30..10080)
    UNITS       "minutes"
    MAX-ACCESS  read-create
    STATUS      current
    DESCRIPTION
        "The value of vRtrMplsGeneralBypassResigTimer specifies the value for
         the Bypass LSP resignal timer, that is the time, in minutes, the
         software will wait before attempting to resignal Bypass LSPs.

         When the resignal timer expires, if the new CSPF path for a Bypass LSP
         has a better metric than the current CSPF path, an attempt will be
         made to resignal that Bypass LSP. If the attempt to resignal the
         Bypass LSP fails, the FRR LSPs protected by that Bypass LSP will
         continue to use that Bypass LSP and a resignal will be attempted the
         next time the timer expires.

         A value of 0 for the resignal timer indicates that timer-based Bypass
         LSP resignalling has been disabled."
    DEFVAL      { 0 }
    ::= { vRtrMplsGeneralEntry 43 }

vRtrMplsGenBypassNextResignal    OBJECT-TYPE
    SYNTAX      Unsigned32
    UNITS       "minutes"
    MAX-ACCESS  read-only
    STATUS      current
    DESCRIPTION
        "The value of vRtrMplsGenBypassNextResignal indicates the time
         remaining, in minutes, for the vRtrMplsGeneralBypassResigTimer to
         expire."
    ::= { vRtrMplsGeneralEntry 44 }

vRtrMplsGeneralNewLspSRIndex     OBJECT-TYPE
    SYNTAX      TestAndIncr
    MAX-ACCESS  read-only
    STATUS      current
    DESCRIPTION
        "The value of vRtrMplsGeneralNewLspSRIndex is used to specify values
         assigned to vRtrMplsLspIndex for Segment Routing LSPs.

         The network manager reads the object, and then writes the value back
         in the SET request that creates a new instance of vRtrMplsLspEntry.
         If the SET fails with the code 'inconsistentValue', then the process
         must be repeated.  If the the SET succeeds, then the object is incremented
         and the new instance is created according to the manager's
         directions.

         The range for Segment Routing LSPs is as specified in the textual
         convention for vRtrMplsLspIndex."
    ::= { vRtrMplsGeneralEntry 45 }

vRtrMplsGeneralPceReport         OBJECT-TYPE
    SYNTAX      BITS {
        srTe   (0),
        rsvpTe (1)
    }
    MAX-ACCESS  read-create
    STATUS      current
    DESCRIPTION
        "The set of configured TE properties for this LSP expressed as a bit
         map."
    DEFVAL      { {} }
    ::= { vRtrMplsGeneralEntry 46 }

vRtrMplsGeneralEntropyLblRsvpTe  OBJECT-TYPE
    SYNTAX      INTEGER {
        forceDisable (1),
        enable       (2)
    }
    MAX-ACCESS  read-create
    STATUS      current
    DESCRIPTION
        "The value of vRtrMplsGeneralEntropyLblRsvpTe specifies whether the
         application takes into account the value of Entropy Label and Entropy
         Label Capability in the label stack for RSVP-TE LSPs.

         When the value of vRtrMplsGeneralEntropyLblRsvpTe is set to 'enable',
         the application will account for EL/ELC in the label stack without
         taking into consideration the value of the enabled ELC.

         When the value of vRtrMplsGeneralEntropyLblRsvpTe is set to
         'force-disable', the application will ignore the value of enabled ELC.

         When the value of vRtrMplsGeneralEntropyLblRsvpTe is modified, Entropy
         Label will become operational when this LSP is resignalled.

         The default value of vRtrMplsGeneralEntropyLblRsvpTe is set to
         'enable'."
    DEFVAL      { enable }
    ::= { vRtrMplsGeneralEntry 47 }

vRtrMplsGeneralEntropyLblSrTe    OBJECT-TYPE
    SYNTAX      INTEGER {
        forceDisable (1),
        enable       (2)
    }
    MAX-ACCESS  read-create
    STATUS      current
    DESCRIPTION
        "The value of vRtrMplsGeneralEntropyLblSrTe specifies whether the
         application takes into account the value of Entropy Label and Entropy
         Label Capability in the label stack for SR-TE LSPs.

         When the value of vRtrMplsGeneralEntropyLblSrTe is set to 'enable',
         the application will account for EL/ELC in the label stack without
         taking into consideration the value of the enabled ELC.

         When the value of vRtrMplsGeneralEntropyLblSrTe is set to
         'force-disable', the application will ignore the value of enabled ELC.

         When the value of vRtrMplsGeneralEntropyLblSrTe is modified, Entropy
         Label will become operational when this LSP is resignalled.

         The default value of vRtrMplsGeneralEntropyLblSrTe is set to 'enable'."
    DEFVAL      { enable }
    ::= { vRtrMplsGeneralEntry 48 }

vRtrMplsGeneralAuxStats          OBJECT-TYPE
    SYNTAX      BITS {
        sr (0)
    }
    MAX-ACCESS  read-create
    STATUS      current
    DESCRIPTION
        "The value of vRtrMplsGeneralAuxStats specifies  which types of labeled
         traffic are counted in the MPLS auxiliary statistics table.

         By default, all labeled traffic is counted in the default MPLS
         statistics table.

         If the 'sr' bit is set,  Segment Routing traffic is counted in the
         MPLS auxiliary statistics table."
    DEFVAL      { {} }
    ::= { vRtrMplsGeneralEntry 49 }

vRtrMplsGenSrTeResignalTimer     OBJECT-TYPE
    SYNTAX      Unsigned32 (0 | 30..10080)
    UNITS       "minutes"
    MAX-ACCESS  read-create
    STATUS      current
    DESCRIPTION
        "The value of vRtrMplsGenSrTeResignalTimer specifies the value for the
         SR-TE LSPs resignal timer, that is the time, in minutes, the software
         will wait before attempting to resignal the SR-TE LSPs.

         When the resignal timer expires, if the new recorded hop list (RRO)
         for an SR-TE LSP has a better metric than the current recorded hop
         list, an attempt will be made to resignal that LSP using the
         make-before-break mechanism. If the attempt to resignal an SR-TE LSP
         fails, the LSP will continue to use the existing path and a resignal
         will be attempted the next time the timer expires.

         A value of 0 for the resignal timer indicates that timer-based SR-TE
         LSP resignalling has been disabled."
    DEFVAL      { 0 }
    ::= { vRtrMplsGeneralEntry 50 }

vRtrMplsGenMaxBypassPlrAssoc     OBJECT-TYPE
    SYNTAX      Unsigned32 (1..16)
    MAX-ACCESS  read-create
    STATUS      current
    DESCRIPTION
        "The value of vRtrMplsGenMaxBypassPlrAssoc specifies the maxiumum
         bypass PLR assocations."
    DEFVAL      { 16 }
    ::= { vRtrMplsGeneralEntry 51 }

vRtrMplsGenLspSelfPingInterval   OBJECT-TYPE
    SYNTAX      TimeInterval (1..10)
    UNITS       "seconds"
    MAX-ACCESS  read-create
    STATUS      current
    DESCRIPTION
        "The value of vRtrMplsGenLspSelfPingInterval specifies the interval
         duration at which LSP self ping packets are sent until a reply is
         received from the far end of the session ID."
    DEFVAL      { 1 }
    ::= { vRtrMplsGeneralEntry 52 }

vRtrMplsGenLspSelfPingTimeout    OBJECT-TYPE
    SYNTAX      TimeInterval (3..3600)
    UNITS       "seconds"
    MAX-ACCESS  read-create
    STATUS      current
    DESCRIPTION
        "The value of vRtrMplsGenLspSelfPingTimeout specifies the value of
         timeout expiry duration up to which the lsp-self-ping packets will be
         sent. If the timeout expires before an LSP self ping has been
         received, then the system should tear down the path and go back to
         CSPF for a new path"
    DEFVAL      { 300 }
    ::= { vRtrMplsGeneralEntry 53 }

vRtrMplsGenLspSelfPingRsvpTe     OBJECT-TYPE
    SYNTAX      INTEGER {
        enable  (1),
        disable (2)
    }
    MAX-ACCESS  read-create
    STATUS      current
    DESCRIPTION
        "The value of vRtrMplsGenLspSelfPingRsvpTe specifies whether the
         application takes into account the value of Self Ping in the label
         stack of RSVP-TE LSPs.

         When the value of vRtrMplsGenLspSelfPingRsvpTe is set to 'enable', the
         application will take into consideration the values of
         vRtrMplsGenLspSelfPingInterval and vRtrMplsGenLspSelfPingTimeout.

         When the value of vRtrMplsGenLspSelfPingRsvpTe is set to 'disable',
         the application will not take into consideration the values of
         vRtrMplsGenLspSelfPingInterval and vRtrMplsGenLspSelfPingTimeout."
    DEFVAL      { disable }
    ::= { vRtrMplsGeneralEntry 54 }

vRtrMplsGenSrTeResigOnIgpEvent   OBJECT-TYPE
    SYNTAX      TruthValue
    MAX-ACCESS  read-create
    STATUS      current
    DESCRIPTION
        "The value of vRtrMplsGenSrTeResigOnIgpEvent specifies re-optimization
         of SR-TE LSPs triggered by IGP events is enabled or disabled."
    DEFVAL      { false }
    ::= { vRtrMplsGeneralEntry 55 }

vRtrMplsGeneralV6OperState       OBJECT-TYPE
    SYNTAX      TmnxOperState
    MAX-ACCESS  read-only
    STATUS      current
    DESCRIPTION
        "vRtrMplsGeneralV6OperState indicates the current operating state of
         MPLS protocol instance on this router for srte ipv6."
    ::= { vRtrMplsGeneralEntry 56 }

vRtrMplsGeneralV6OperDownReason  OBJECT-TYPE
    SYNTAX      TmnxMplsOperDownReasonCode
    MAX-ACCESS  read-only
    STATUS      current
    DESCRIPTION
        "The value of vRtrMplsGeneralV6OperDownReason indicates the reason due
         to which the MPLS instance is operationally down for srte ipv6."
    ::= { vRtrMplsGeneralEntry 57 }

vRtrMplsGenSrteNextResignal      OBJECT-TYPE
    SYNTAX      Unsigned32
    MAX-ACCESS  read-only
    STATUS      current
    DESCRIPTION
        "The value of vRtrMplsGenSrteNextResignal indicates the time remaining,
         in minutes, for the vRtrMplsGenSrTeResignalTimer to expire."
    ::= { vRtrMplsGeneralEntry 58 }

vRtrMplsGeneralStatTable         OBJECT-TYPE
    SYNTAX      SEQUENCE OF VRtrMplsGeneralStatEntry
    MAX-ACCESS  not-accessible
    STATUS      current
    DESCRIPTION
        "The vRtrMplsGeneralStatTable contains statistics for an MPLS protocol
         instance within a virtual router."
    ::= { tmnxMplsObjs 8 }

vRtrMplsGeneralStatEntry         OBJECT-TYPE
    SYNTAX      VRtrMplsGeneralStatEntry
    MAX-ACCESS  not-accessible
    STATUS      current
    DESCRIPTION
        "Each row entry represents a collection of statistics for an instance
         of the MPLS protocol running within a virtual router.

         Entries cannot be created and deleted via SNMP SET operations."
    AUGMENTS    { vRtrMplsGeneralEntry }
    ::= { vRtrMplsGeneralStatTable 1 }

VRtrMplsGeneralStatEntry         ::= SEQUENCE
{
    vRtrMplsGeneralStaticLspOriginate Gauge32,
    vRtrMplsGeneralStaticLspTransit  Gauge32,
    vRtrMplsGeneralStaticLspTerminate Gauge32,
    vRtrMplsGeneralDynamicLspOriginate Gauge32,
    vRtrMplsGeneralDynamicLspTransit Gauge32,
    vRtrMplsGeneralDynamicLspTerminate Gauge32,
    vRtrMplsGeneralDetourLspOriginate Gauge32,
    vRtrMplsGeneralDetourLspTransit  Gauge32,
    vRtrMplsGeneralDetourLspTerminate Gauge32,
    vRtrMplsGeneralS2lOriginate      Gauge32,
    vRtrMplsGeneralS2lTransit        Gauge32,
    vRtrMplsGeneralS2lTerminate      Gauge32,
    vRtrMplsGeneralLspEgrStatCount   Counter32,
    vRtrMplsGeneralLspIgrStatCount   Counter32,
    vRtrMplsGenMplsTpLspOriginate    Gauge32,
    vRtrMplsGenMplsTpLspTransit      Gauge32,
    vRtrMplsGenMplsTpLspTerminate    Gauge32,
    vRtrMplsGenMplsTpOrigPathInst    Gauge32,
    vRtrMplsGenMplsTpTranPathInst    Gauge32,
    vRtrMplsGenMplsTpTermPathInst    Gauge32,
    vRtrMplsGeneralMeshP2pOriginate  Gauge32,
    vRtrMplsGeneralOneHopP2pOrigin   Gauge32,
    vRtrMplsGeneralSrTeLspOriginate  Gauge32,
    vRtrMplsGenMeshP2PSrTeLspOrig    Gauge32,
    vRtrMplsGenOneHopP2PSrTeLspOrig  Gauge32,
    vRtrMplsGenPceInitP2PSrTeLspOrig Gauge32,
    vRtrMplsGenLspSelfPingTimeouts   Counter32
}

vRtrMplsGeneralStaticLspOriginate OBJECT-TYPE
    SYNTAX      Gauge32
    MAX-ACCESS  read-only
    STATUS      current
    DESCRIPTION
        "The value of vRtrMplsGeneralStaticLspOriginate indicates the number of
         static LSPs that originate at this virtual router."
    ::= { vRtrMplsGeneralStatEntry 1 }

vRtrMplsGeneralStaticLspTransit  OBJECT-TYPE
    SYNTAX      Gauge32
    MAX-ACCESS  read-only
    STATUS      current
    DESCRIPTION
        "The value of vRtrMplsGeneralStaticLspTransit indicates the number of
         static LSPs that transit through this virtual router."
    ::= { vRtrMplsGeneralStatEntry 2 }

vRtrMplsGeneralStaticLspTerminate OBJECT-TYPE
    SYNTAX      Gauge32
    MAX-ACCESS  read-only
    STATUS      current
    DESCRIPTION
        "The value of vRtrMplsGeneralStaticLspTerminate indicates the number of
         static LSPs that terminate at this virtual router."
    ::= { vRtrMplsGeneralStatEntry 3 }

vRtrMplsGeneralDynamicLspOriginate OBJECT-TYPE
    SYNTAX      Gauge32
    MAX-ACCESS  read-only
    STATUS      current
    DESCRIPTION
        "The value of vRtrMplsGeneralDynamicLspOriginate indicates the number
         of dynamic LSPs that originate at this virtual router."
    ::= { vRtrMplsGeneralStatEntry 4 }

vRtrMplsGeneralDynamicLspTransit OBJECT-TYPE
    SYNTAX      Gauge32
    MAX-ACCESS  read-only
    STATUS      current
    DESCRIPTION
        "The value of vRtrMplsGeneralDynamicLspTransit indicates the number of dynamic LSPs
         that transit  through this virtual router."
    ::= { vRtrMplsGeneralStatEntry 5 }

vRtrMplsGeneralDynamicLspTerminate OBJECT-TYPE
    SYNTAX      Gauge32
    MAX-ACCESS  read-only
    STATUS      current
    DESCRIPTION
        "The value of vRtrMplsGeneralDynamicLspTerminate indicates the number
         of dynamic LSPs that terminate at this virtual router."
    ::= { vRtrMplsGeneralStatEntry 6 }

vRtrMplsGeneralDetourLspOriginate OBJECT-TYPE
    SYNTAX      Gauge32
    MAX-ACCESS  read-only
    STATUS      current
    DESCRIPTION
        "The value of vRtrMplsGeneralDetourLspOriginate indicates the number of
         detour LSPs that originate at this virtual router."
    ::= { vRtrMplsGeneralStatEntry 7 }

vRtrMplsGeneralDetourLspTransit  OBJECT-TYPE
    SYNTAX      Gauge32
    MAX-ACCESS  read-only
    STATUS      current
    DESCRIPTION
        "The value of vRtrMplsGeneralDetourLspTransit indicates the number of
         detour LSPs that transit through this virtual router."
    ::= { vRtrMplsGeneralStatEntry 8 }

vRtrMplsGeneralDetourLspTerminate OBJECT-TYPE
    SYNTAX      Gauge32
    MAX-ACCESS  read-only
    STATUS      current
    DESCRIPTION
        "The value of vRtrMplsGeneralDetourLspTerminate indicates the number of
         detour LSPs that terminate at this virtual router."
    ::= { vRtrMplsGeneralStatEntry 9 }

vRtrMplsGeneralS2lOriginate      OBJECT-TYPE
    SYNTAX      Gauge32
    MAX-ACCESS  read-only
    STATUS      current
    DESCRIPTION
        "The value of vRtrMplsGeneralS2lOriginate indicates the number of
         source to leaf (S2L) sub LSP path called as S2L here that originate at
         this virtual router."
    ::= { vRtrMplsGeneralStatEntry 10 }

vRtrMplsGeneralS2lTransit        OBJECT-TYPE
    SYNTAX      Gauge32
    MAX-ACCESS  read-only
    STATUS      current
    DESCRIPTION
        "The value of vRtrMplsGeneralS2lTransit indicates the number of S2Ls
         that transit through this virtual router."
    ::= { vRtrMplsGeneralStatEntry 11 }

vRtrMplsGeneralS2lTerminate      OBJECT-TYPE
    SYNTAX      Gauge32
    MAX-ACCESS  read-only
    STATUS      current
    DESCRIPTION
        "The value of vRtrMplsGeneralS2lTerminate indicates the number of S2Ls
         that terminate at this virtual router."
    ::= { vRtrMplsGeneralStatEntry 12 }

vRtrMplsGeneralLspEgrStatCount   OBJECT-TYPE
    SYNTAX      Counter32
    MAX-ACCESS  read-only
    STATUS      current
    DESCRIPTION
        "The value of vRtrMplsGeneralLspEgrStatCount indicates the number of
         LSP egress statistics configured on this virtual router."
    ::= { vRtrMplsGeneralStatEntry 13 }

vRtrMplsGeneralLspIgrStatCount   OBJECT-TYPE
    SYNTAX      Counter32
    MAX-ACCESS  read-only
    STATUS      current
    DESCRIPTION
        "The value of vRtrMplsGeneralLspIgrStatCount indicates the number of
         LSP ingress statistics configured on this virtual router."
    ::= { vRtrMplsGeneralStatEntry 14 }

vRtrMplsGenMplsTpLspOriginate    OBJECT-TYPE
    SYNTAX      Gauge32
    MAX-ACCESS  read-only
    STATUS      current
    DESCRIPTION
        "The value of vRtrMplsGenMplsTpLspOriginate indicates the number of
         MPLS TP LSPs that originate at this virtual router."
    ::= { vRtrMplsGeneralStatEntry 15 }

vRtrMplsGenMplsTpLspTransit      OBJECT-TYPE
    SYNTAX      Gauge32
    MAX-ACCESS  read-only
    STATUS      current
    DESCRIPTION
        "The value of vRtrMplsGenMplsTpLspTransit indicates the number of MPLS
         TP LSPs that transit through this virtual router."
    ::= { vRtrMplsGeneralStatEntry 16 }

vRtrMplsGenMplsTpLspTerminate    OBJECT-TYPE
    SYNTAX      Gauge32
    MAX-ACCESS  read-only
    STATUS      current
    DESCRIPTION
        "The value of vRtrMplsGenMplsTpLspTerminate indicates the number of
         MPLS TP LSPs that terminate at this virtual router."
    ::= { vRtrMplsGeneralStatEntry 17 }

vRtrMplsGenMplsTpOrigPathInst    OBJECT-TYPE
    SYNTAX      Gauge32
    MAX-ACCESS  read-only
    STATUS      current
    DESCRIPTION
        "The value of vRtrMplsGenMplsTpOrigPathInst indicates the number of
         MPLS TP LSPs originate path instances."
    ::= { vRtrMplsGeneralStatEntry 18 }

vRtrMplsGenMplsTpTranPathInst    OBJECT-TYPE
    SYNTAX      Gauge32
    MAX-ACCESS  read-only
    STATUS      current
    DESCRIPTION
        "The value of vRtrMplsGenMplsTpTranPathInst indicates the number of
         MPLS TP LSPs transit path instances."
    ::= { vRtrMplsGeneralStatEntry 19 }

vRtrMplsGenMplsTpTermPathInst    OBJECT-TYPE
    SYNTAX      Gauge32
    MAX-ACCESS  read-only
    STATUS      current
    DESCRIPTION
        "The value of vRtrMplsGenMplsTpTermPathInst indicates the number of
         MPLS TP LSPs terminated path instances."
    ::= { vRtrMplsGeneralStatEntry 20 }

vRtrMplsGeneralMeshP2pOriginate  OBJECT-TYPE
    SYNTAX      Gauge32
    MAX-ACCESS  read-only
    STATUS      current
    DESCRIPTION
        "The value of vRtrMplsGeneralMeshP2pOriginate indicates the number of
         Mesh P2P LSPs originating at this virtual router."
    ::= { vRtrMplsGeneralStatEntry 21 }

vRtrMplsGeneralOneHopP2pOrigin   OBJECT-TYPE
    SYNTAX      Gauge32
    MAX-ACCESS  read-only
    STATUS      current
    DESCRIPTION
        "The value of vRtrMplsGeneralOneHopP2pOrigin indicates the number of
         One Hop P2P LSPs originating at this virtual router."
    ::= { vRtrMplsGeneralStatEntry 22 }

vRtrMplsGeneralSrTeLspOriginate  OBJECT-TYPE
    SYNTAX      Gauge32
    MAX-ACCESS  read-only
    STATUS      current
    DESCRIPTION
        "The value of vRtrMplsGeneralSrTeLspOriginate indicates the number of
         Segment Routing TE LSPs that are originating at this virtual router."
    ::= { vRtrMplsGeneralStatEntry 23 }

vRtrMplsGenMeshP2PSrTeLspOrig    OBJECT-TYPE
    SYNTAX      Gauge32
    MAX-ACCESS  read-only
    STATUS      current
    DESCRIPTION
        "The value of vRtrMplsGenMeshP2PSrTeLspOrig indicates the number of
         Mesh P2P Segment Routing TE LSPs that are originating at this virtual
         router."
    ::= { vRtrMplsGeneralStatEntry 24 }

vRtrMplsGenOneHopP2PSrTeLspOrig  OBJECT-TYPE
    SYNTAX      Gauge32
    MAX-ACCESS  read-only
    STATUS      current
    DESCRIPTION
        "The value of vRtrMplsGenOneHopP2PSrTeLspOrig indicates the number of
         One-Hop P2P Segment Routing TE LSPs that are originating at this
         virtual router."
    ::= { vRtrMplsGeneralStatEntry 25 }

vRtrMplsGenPceInitP2PSrTeLspOrig OBJECT-TYPE
    SYNTAX      Gauge32
    MAX-ACCESS  read-only
    STATUS      current
    DESCRIPTION
        "The value of vRtrMplsGenPceInitP2PSrTeLspOrig indicates the number of
         PCE Init P2P Segment Routing TE LSPs that are originating at this
         virtual router."
    ::= { vRtrMplsGeneralStatEntry 26 }

vRtrMplsGenLspSelfPingTimeouts   OBJECT-TYPE
    SYNTAX      Counter32
    MAX-ACCESS  read-only
    STATUS      current
    DESCRIPTION
        "The value of vRtrMplsGenLspSelfPingTimeouts indicate the number of LSP
         self-ping timeouts for LSPs originating at this virtual router."
    ::= { vRtrMplsGeneralStatEntry 27 }

vRtrMplsIfTable                  OBJECT-TYPE
    SYNTAX      SEQUENCE OF VRtrMplsIfEntry
    MAX-ACCESS  not-accessible
    STATUS      current
    DESCRIPTION
        "The vRtrMplsIfTable has an entry for each router interface configured
         for MPLS in the system."
    ::= { tmnxMplsObjs 9 }

vRtrMplsIfEntry                  OBJECT-TYPE
    SYNTAX      VRtrMplsIfEntry
    MAX-ACCESS  not-accessible
    STATUS      current
    DESCRIPTION
        "Each row entry represents an interface on this virtual router
         that participates in the MPLS protocol.  A row cannot be created
         or deleted via SNMP SET requests.  A row with default attribute
         values is created by setting the vRtrIfEntry attribute,
         vRtrIfMplsStatus, to 'create'.  A row is removed if
         vRtrIfMplsStatus is set to 'delete'.  However, an attempt to
         destroy a row will fail if vRtrMplsIfAdminState has
         not first been set to 'outOfService'."
    INDEX       {
        vRtrID,
        vRtrIfIndex
    }
    ::= { vRtrMplsIfTable 1 }

VRtrMplsIfEntry                  ::= SEQUENCE
{
    vRtrMplsIfAdminState             TmnxAdminState,
    vRtrMplsIfOperState              TmnxOperState,
    vRtrMplsIfAdminGroup             Unsigned32,
    vRtrMplsIfTeMetric               Unsigned32,
    vRtrMplsIfV6OperState            TmnxOperState
}

vRtrMplsIfAdminState             OBJECT-TYPE
    SYNTAX      TmnxAdminState
    MAX-ACCESS  read-create
    STATUS      current
    DESCRIPTION
        "The desired administrative state for the MPLS protocol running on this
         MPLS interface."
    DEFVAL      { outOfService }
    ::= { vRtrMplsIfEntry 1 }

vRtrMplsIfOperState              OBJECT-TYPE
    SYNTAX      TmnxOperState
    MAX-ACCESS  read-only
    STATUS      current
    DESCRIPTION
        "This variable indicates the current status of the MPLS protocol
         running on this MPLS interface. When the
         TIMETRA-VRTR-MIB::vRtrIfPortID object of this interface is set to a
         loopback port identifier, the operational state is not relevant and an
         SNMP GET request on this object will return 'unknown'."
    ::= { vRtrMplsIfEntry 2 }

vRtrMplsIfAdminGroup             OBJECT-TYPE
    SYNTAX      Unsigned32
    MAX-ACCESS  read-create
    STATUS      current
    DESCRIPTION
        "The value of vRtrMplsIfAdminGroup is a bit-map that identifies the
         admin groups to which the interface belongs. If bit 'n' is set, then
         the interface belongs to the admin group with value 'n'.

         By default, the interface does not belong to any admin groups."
    DEFVAL      { '00000000'H }
    ::= { vRtrMplsIfEntry 3 }

vRtrMplsIfTeMetric               OBJECT-TYPE
    SYNTAX      Unsigned32 (0 | 1..16777215)
    MAX-ACCESS  read-create
    STATUS      current
    DESCRIPTION
        "The value of vRtrMplsIfTeMetric specifies the traffic engineering
         metric for this interface. The TE metric is exchanged in addition to
         the IGP metric by the IGPs. Depending on the value configured for
         vRtrMplsLspCspfTeMetricEnabled, either the TE metric or the native IGP
         metric is used in CSPF computations of the LSP paths. The maximum
         value that can be configured is a 24 bit value."
    DEFVAL      { 0 }
    ::= { vRtrMplsIfEntry 4 }

vRtrMplsIfV6OperState            OBJECT-TYPE
    SYNTAX      TmnxOperState
    MAX-ACCESS  read-only
    STATUS      current
    DESCRIPTION
        "This variable indicates the current status of the MPLS protocol
         running on this MPLS interface for srte ipv6. When the
         TIMETRA-VRTR-MIB::vRtrIfPortID object of this interface is set to a
         loopback port identifier, the operational state is not relevant and an
         SNMP GET request on this object will return 'unknown'."
    ::= { vRtrMplsIfEntry 5 }

vRtrMplsIfStatTable              OBJECT-TYPE
    SYNTAX      SEQUENCE OF VRtrMplsIfStatEntry
    MAX-ACCESS  not-accessible
    STATUS      current
    DESCRIPTION
        "The vRtrMplsIfStatTable has an entry for each router interface
         configured for MPLS in the system."
    ::= { tmnxMplsObjs 10 }

vRtrMplsIfStatEntry              OBJECT-TYPE
    SYNTAX      VRtrMplsIfStatEntry
    MAX-ACCESS  not-accessible
    STATUS      current
    DESCRIPTION
        "Each row entry represents a collection of statistics for an interface
         on this virtual router that participates in the MPLS protocol.

         Entries cannot be created and deleted via SNMP SET operations."
    AUGMENTS    { vRtrMplsIfEntry }
    ::= { vRtrMplsIfStatTable 1 }

VRtrMplsIfStatEntry              ::= SEQUENCE
{
    vRtrMplsIfTxPktCount             Counter64,
    vRtrMplsIfRxPktCount             Counter64,
    vRtrMplsIfTxOctetCount           Counter64,
    vRtrMplsIfRxOctetCount           Counter64,
    vRtrMplsIfAltTxPktCount          Counter64,
    vRtrMplsIfAltRxPktCount          Counter64,
    vRtrMplsIfAltTxOctetCount        Counter64,
    vRtrMplsIfAltRxOctetCount        Counter64
}

vRtrMplsIfTxPktCount             OBJECT-TYPE
    SYNTAX      Counter64
    MAX-ACCESS  read-only
    STATUS      current
    DESCRIPTION
        "The total number of MPLS labeled packets transmitted from this
         interface."
    ::= { vRtrMplsIfStatEntry 1 }

vRtrMplsIfRxPktCount             OBJECT-TYPE
    SYNTAX      Counter64
    MAX-ACCESS  read-only
    STATUS      current
    DESCRIPTION
        "The total number of MPLS labeled packets received on this interface."
    ::= { vRtrMplsIfStatEntry 2 }

vRtrMplsIfTxOctetCount           OBJECT-TYPE
    SYNTAX      Counter64
    MAX-ACCESS  read-only
    STATUS      current
    DESCRIPTION
        "The total number of bytes in MPLS labeled packets transmitted on this
         interface."
    ::= { vRtrMplsIfStatEntry 3 }

vRtrMplsIfRxOctetCount           OBJECT-TYPE
    SYNTAX      Counter64
    MAX-ACCESS  read-only
    STATUS      current
    DESCRIPTION
        "The total number of bytes in MPLS labeled packets received on this
         interface."
    ::= { vRtrMplsIfStatEntry 4 }

vRtrMplsIfAltTxPktCount          OBJECT-TYPE
    SYNTAX      Counter64
    MAX-ACCESS  read-only
    STATUS      current
    DESCRIPTION
        "The total number of SR-MPLS labeled packets transmitted from this
         interface."
    ::= { vRtrMplsIfStatEntry 5 }

vRtrMplsIfAltRxPktCount          OBJECT-TYPE
    SYNTAX      Counter64
    MAX-ACCESS  read-only
    STATUS      current
    DESCRIPTION
        "The total number of SR-MPLS labeled packets received on this
         interface."
    ::= { vRtrMplsIfStatEntry 6 }

vRtrMplsIfAltTxOctetCount        OBJECT-TYPE
    SYNTAX      Counter64
    MAX-ACCESS  read-only
    STATUS      current
    DESCRIPTION
        "The total number of bytes in SR-MPLS labeled packets transmitted on
         this interface."
    ::= { vRtrMplsIfStatEntry 7 }

vRtrMplsIfAltRxOctetCount        OBJECT-TYPE
    SYNTAX      Counter64
    MAX-ACCESS  read-only
    STATUS      current
    DESCRIPTION
        "The total number of bytes in SR-MPLS labeled packets received on this
         interface."
    ::= { vRtrMplsIfStatEntry 8 }

vRtrMplsTunnelARHopTable         OBJECT-TYPE
    SYNTAX      SEQUENCE OF VRtrMplsTunnelARHopEntry
    MAX-ACCESS  not-accessible
    STATUS      current
    DESCRIPTION
        "The vRtrMplsTunnelARHopTable augments the mplsTunnelARHopEntry in the
         MPLS-TE-MIB."
    ::= { tmnxMplsObjs 11 }

vRtrMplsTunnelARHopEntry         OBJECT-TYPE
    SYNTAX      VRtrMplsTunnelARHopEntry
    MAX-ACCESS  not-accessible
    STATUS      current
    DESCRIPTION
        "A row entry in this table corresponds to a row entry in the
         mplsTunnelARHopTable and adds to the information contained in that
         table"
    AUGMENTS    { mplsTunnelARHopEntry }
    ::= { vRtrMplsTunnelARHopTable 1 }

VRtrMplsTunnelARHopEntry         ::= SEQUENCE
{
    vRtrMplsTunnelARHopProtection    BITS,
    vRtrMplsTunnelARHopRecordLabel   MplsLabel,
    vRtrMplsTunnelARHopRouterId      IpAddress,
    vRtrMplsTunnelARHopUnnumIfID     Unsigned32,
    vRtrMplsTunnelARHopSIDType       INTEGER,
    vRtrMplsTunnelARHopNgRouterId    InetAddress,
    vRtrMplsTunnelARHopNgRtrIdType   InetAddressType
}

vRtrMplsTunnelARHopProtection    OBJECT-TYPE
    SYNTAX      BITS {
        localAvailable     (0),
        localInUse         (1),
        bandwidthProtected (2),
        nodeProtected      (3),
        preemptionPending  (4),
        nodeId             (5)
    }
    MAX-ACCESS  read-only
    STATUS      current
    DESCRIPTION
        "If the 'localAvailable' bit is set, it indicates that the link
         downstream of this node has been protected by means of a local repair
         mechanism. This mechanism can be either the one-to-one backup method
         or the facility backup method.

         If the 'localInUse' bit is set, then it indicates that the local
         protection mechanism is being used to maintain this tunnel.

         If the 'bandwidthProtected' bit is set, then it indicates that the
         backup path is guaranteed to provide the desired bandwidth.

         If the 'nodeProtected' bit is set, then it indicates that the backup
         path provides protection against the failure of the next LSR along the
         LSP.

         If the 'nodeId' bit is set, it indicates that the address specified in
         the Record Route Object's IPv4 or IPv6 sub-object is a nodeId address."
    ::= { vRtrMplsTunnelARHopEntry 1 }

vRtrMplsTunnelARHopRecordLabel   OBJECT-TYPE
    SYNTAX      MplsLabel
    MAX-ACCESS  read-only
    STATUS      current
    DESCRIPTION
        "If label recording is enabled, vRtrMplsTunnelARHopRecordLabel
         specifies the label that is advertised to the previous hop in the hop
         list. If label recording is disabled, vRtrMplsTunnelARHopRecordLabel
         will have a value of 4294967295"
    ::= { vRtrMplsTunnelARHopEntry 2 }

vRtrMplsTunnelARHopRouterId      OBJECT-TYPE
    SYNTAX      IpAddress
    MAX-ACCESS  read-only
    STATUS      obsolete
    DESCRIPTION
        "vRtrMplsTunnelARHopRouterId indicates the router ID of the node
         corresponding to this hop.

         vRtrMplsTunnelARHopRouterId is obsoleted in 20.0,  replaced by
         vRtrMplsTunnelARHopNgRouterId"
    ::= { vRtrMplsTunnelARHopEntry 3 }

vRtrMplsTunnelARHopUnnumIfID     OBJECT-TYPE
    SYNTAX      Unsigned32
    MAX-ACCESS  read-only
    STATUS      current
    DESCRIPTION
        "The value of vRtrMplsTunnelARHopUnnumIfID indicates the unnumbered
         interface identifier of this hop.

         This object should be used in conjunction with
         vRtrMplsTunnelARHopNgRouterId which would contain the LSR Router ID
         for the unnumbered interface.

         If mplsTunnelARHopAddrType is set to unnum(100), then this entry is
         valid."
    ::= { vRtrMplsTunnelARHopEntry 4 }

vRtrMplsTunnelARHopSIDType       OBJECT-TYPE
    SYNTAX      INTEGER {
        notApplicable (1),
        nodeSid       (2),
        adjacencySid  (3)
    }
    MAX-ACCESS  read-only
    STATUS      current
    DESCRIPTION
        "The value of vRtrMplsTunnelARHopSIDType indicates the type of SID for
         this hop.

         When the value of vRtrMplsTunnelARHopSIDType is 'notApplicable', it
         indicates that this hop is not associated with an SR-TE LSP and hence
         SID type does not apply for this hop.

         When the value of vRtrMplsTunnelARHopSIDType is 'nodeSid', it
         indicates that this hop is associated with an SR-TE LSP and represents
         a Node SID.

         When the value of vRtrMplsTunnelARHopSIDType is 'adjacencySid', it
         indicates that this hop is associated with an SR-TE LSP and represents
         an Adjacency SID."
    ::= { vRtrMplsTunnelARHopEntry 5 }

vRtrMplsTunnelARHopNgRouterId    OBJECT-TYPE
    SYNTAX      InetAddress (SIZE (0|4|16))
    MAX-ACCESS  read-only
    STATUS      current
    DESCRIPTION
        "The value of vRtrMplsTunnelARHopNgRouterId indicates the Router ID of
         the node corresponding to this hop. Currently IPV6 Router ID is
         supported by this object.

         The IP address type of vRtrMplsTunnelARHopNgRouterId is specified by
         the value of mplsTunnelARHopAddrType. Currently value of 'ipv6' is
         supported."
    ::= { vRtrMplsTunnelARHopEntry 6 }

vRtrMplsTunnelARHopNgRtrIdType   OBJECT-TYPE
    SYNTAX      InetAddressType
    MAX-ACCESS  read-only
    STATUS      current
    DESCRIPTION
        "The value of vRtrMplsTunnelARHopNgRtrIdType indicates the type of
         address for this router-id.

         When the value of vRtrMplsTunnelARHopNgRtrIdType is 'ipv4', it
         indicates that vRtrMplsTunnelARHopNgRouterId of this hop is of ipv4
         type.

         When the value of vRtrMplsTunnelARHopNgRtrIdType is 'ipv6', it
         indicates that vRtrMplsTunnelARHopNgRouterId of this hop is of ipv6
         type."
    ::= { vRtrMplsTunnelARHopEntry 7 }

vRtrMplsTunnelCHopTable          OBJECT-TYPE
    SYNTAX      SEQUENCE OF VRtrMplsTunnelCHopEntry
    MAX-ACCESS  not-accessible
    STATUS      current
    DESCRIPTION
        "The vRtrMplsTunnelCHopTable is used to hold the CSPF path for a detour
         LSP. Each entry indicates a single hop.

         Primary index is the vRtrMplsTunnelCHopListIndex which associates
         multiple entries (hops) in the vRtrMplsTunnelCHopTable to a single
         mplsTunnelEntry specified in the mplsTunnelTable.

         The first row in the table is the first hop after the origination
         point of the tunnel."
    ::= { tmnxMplsObjs 12 }

vRtrMplsTunnelCHopEntry          OBJECT-TYPE
    SYNTAX      VRtrMplsTunnelCHopEntry
    MAX-ACCESS  not-accessible
    STATUS      current
    DESCRIPTION
        "An entry in this table represents a CSPF tunnel hop. Entries are
         created and deleted by the system."
    INDEX       {
        vRtrMplsTunnelCHopListIndex,
        vRtrMplsTunnelCHopIndex
    }
    ::= { vRtrMplsTunnelCHopTable 1 }

VRtrMplsTunnelCHopEntry          ::= SEQUENCE
{
    vRtrMplsTunnelCHopListIndex      Integer32,
    vRtrMplsTunnelCHopIndex          Integer32,
    vRtrMplsTunnelCHopAddrType       INTEGER,
    vRtrMplsTunnelCHopIpv4Addr       IpAddress,
    vRtrMplsTunnelCHopIpv4PrefixLen  Integer32,
    vRtrMplsTunnelCHopIpv6Addr       InetAddressIPv6,
    vRtrMplsTunnelCHopIpv6PrefixLen  Integer32,
    vRtrMplsTunnelCHopAsNumber       Integer32,
    vRtrMplsTunnelCHopLspId          MplsLSPID,
    vRtrMplsTunnelCHopStrictOrLoose  INTEGER,
    vRtrMplsTunnelCHopEgressAdmGrp   Unsigned32,
    vRtrMplsTunnelCHopUnnumIfID      Unsigned32,
    vRtrMplsTunnelCHopRtrID          IpAddress,
    vRtrMplsTunnelCHopIsABR          TruthValue
}

vRtrMplsTunnelCHopListIndex      OBJECT-TYPE
    SYNTAX      Integer32 (1..2147483647)
    MAX-ACCESS  not-accessible
    STATUS      current
    DESCRIPTION
        "Primary index into this table identifying a particular explicit route
         object."
    ::= { vRtrMplsTunnelCHopEntry 1 }

vRtrMplsTunnelCHopIndex          OBJECT-TYPE
    SYNTAX      Integer32 (1..2147483647)
    MAX-ACCESS  not-accessible
    STATUS      current
    DESCRIPTION
        "Secondary index into this table identifying a particular hop."
    ::= { vRtrMplsTunnelCHopEntry 2 }

vRtrMplsTunnelCHopAddrType       OBJECT-TYPE
    SYNTAX      INTEGER {
        unknown  (0),
        ipV4     (1),
        ipV6     (2),
        asNumber (3),
        lspid    (4),
        unnum    (5)
    }
    MAX-ACCESS  read-only
    STATUS      current
    DESCRIPTION
        "The value of vRtrMplsTunnelCHopAddrType specifies the address type of
         this tunnel hop.

         When the value of vRtrMplsTunnelCHopAddrType is 'ipv4', it specifies
         an IPv4 address type and vRtrMplsTunnelCHopIpv4Addr should be
         configured.

         When the value of vRtrMplsTunnelCHopAddrType is 'ipv6', it specifies
         an IPv6 address type and vRtrMplsTunnelCHopIpv6Addr should be
         configured.

         When the value of vRtrMplsTunnelCHopAddrType is 'asNumber', it
         specifies an AS number and vRtrMplsTunnelCHopAsNumber should be
         configured.

         When the value of vRtrMplsTunnelCHopAddrType is 'lspid', it specifies
         an LSP ID and vRtrMplsTunnelCHopLspId should be configured.

         When the value of vRtrMplsTunnelCHopAddrType is 'unnum', it specifies
         an unnumbered interface identifier and vRtrMplsTunnelCHopUnnumIfID
         should be configured."
    DEFVAL      { ipV4 }
    ::= { vRtrMplsTunnelCHopEntry 3 }

vRtrMplsTunnelCHopIpv4Addr       OBJECT-TYPE
    SYNTAX      IpAddress
    MAX-ACCESS  read-only
    STATUS      current
    DESCRIPTION
        "If vRtrMplsTunnelCHopAddrType is set to ipV4(1), then this value will
         contain the IPv4 address of this hop. This object is otherwise
         insignificant and should contain a value of 0."
    ::= { vRtrMplsTunnelCHopEntry 4 }

vRtrMplsTunnelCHopIpv4PrefixLen  OBJECT-TYPE
    SYNTAX      Integer32 (1..32)
    MAX-ACCESS  read-only
    STATUS      current
    DESCRIPTION
        "If vRtrMplsTunnelCHopAddrType is ipV4(1), then the prefix length for
         this hop's IPv4 address is contained herein. This object is otherwise
         insignificant and should contain a value of 0."
    ::= { vRtrMplsTunnelCHopEntry 5 }

vRtrMplsTunnelCHopIpv6Addr       OBJECT-TYPE
    SYNTAX      InetAddressIPv6
    MAX-ACCESS  read-only
    STATUS      current
    DESCRIPTION
        "If the vRtrMplsTunnelCHopAddrType is set to ipV6(2), then this
         variable contains the IPv6 address of this hop. This object is
         otherwise insignificant and should contain a value of 0."
    ::= { vRtrMplsTunnelCHopEntry 6 }

vRtrMplsTunnelCHopIpv6PrefixLen  OBJECT-TYPE
    SYNTAX      Integer32 (1..128)
    MAX-ACCESS  read-only
    STATUS      current
    DESCRIPTION
        "If vRtrMplsTunnelCHopAddrType is set to ipV6(2), this value will
         contain the prefix length for this hop's IPv6 address. This object is
         otherwise insignificant and should contain a value of 0."
    ::= { vRtrMplsTunnelCHopEntry 7 }

vRtrMplsTunnelCHopAsNumber       OBJECT-TYPE
    SYNTAX      Integer32 (0..65535)
    MAX-ACCESS  read-only
    STATUS      current
    DESCRIPTION
        "If vRtrMplsTunnelCHopAddrType is set to asNumber(3), then this value
         will contain the AS number of this hop. This object is otherwise
         insignificant and should contain a value of 0 to indicate this fact."
    ::= { vRtrMplsTunnelCHopEntry 8 }

vRtrMplsTunnelCHopLspId          OBJECT-TYPE
    SYNTAX      MplsLSPID
    MAX-ACCESS  read-only
    STATUS      current
    DESCRIPTION
        "If vRtrMplsTunnelCHopAddrType is set to lspid(4), then this value will
         contain the LSPID of a tunnel of this hop. The present tunnel being
         configured is tunneled through this hop (using label stacking). This
         object is otherwise insignificant and should contain a value of 0 to
         indicate this fact."
    ::= { vRtrMplsTunnelCHopEntry 9 }

vRtrMplsTunnelCHopStrictOrLoose  OBJECT-TYPE
    SYNTAX      INTEGER {
        strict (1),
        loose  (2)
    }
    MAX-ACCESS  read-only
    STATUS      current
    DESCRIPTION
        "Denotes whether this tunnel hop is routed in a strict or loose
         fashion."
    ::= { vRtrMplsTunnelCHopEntry 10 }

vRtrMplsTunnelCHopEgressAdmGrp   OBJECT-TYPE
    SYNTAX      Unsigned32
    MAX-ACCESS  read-only
    STATUS      current
    DESCRIPTION
        "The value of vRtrMplsTunnelCHopEgressAdmGrp indicates administrative
         groups on the egressing interface at the current hop."
    ::= { vRtrMplsTunnelCHopEntry 11 }

vRtrMplsTunnelCHopUnnumIfID      OBJECT-TYPE
    SYNTAX      Unsigned32
    MAX-ACCESS  read-only
    STATUS      current
    DESCRIPTION
        "The value of vRtrMplsTunnelCHopUnnumIfID indicates the unnumbered
         interface identifier of this hop.

         This object should be used in conjunction with vRtrMplsTunnelCHopRtrID
         which would contain the LSR Router ID for the unnumbered interface.

         If vRtrMplsTunnelCHopAddrType is set to unnum(5), then this entry is
         valid.

         This object is otherwise insignificant and should contain a value of 0
         to indicate this fact."
    ::= { vRtrMplsTunnelCHopEntry 12 }

vRtrMplsTunnelCHopRtrID          OBJECT-TYPE
    SYNTAX      IpAddress
    MAX-ACCESS  read-only
    STATUS      current
    DESCRIPTION
        "The value of vRtrMplsTunnelCHopRtrID indicates value of the Router ID
         for the node when vRtrMplsTunnelCHopAddrType is set to ipV4(1) or
         unnum(5)."
    ::= { vRtrMplsTunnelCHopEntry 13 }

vRtrMplsTunnelCHopIsABR          OBJECT-TYPE
    SYNTAX      TruthValue
    MAX-ACCESS  read-only
    STATUS      current
    DESCRIPTION
        "The value of vRtrMplsTunnelCHopIsABR indicates whether the current hop
         is an Area Border Router (ABR) or not."
    ::= { vRtrMplsTunnelCHopEntry 14 }

vRtrMplsAdminGroupTable          OBJECT-TYPE
    SYNTAX      SEQUENCE OF VRtrMplsAdminGroupEntry
    MAX-ACCESS  not-accessible
    STATUS      obsolete
    DESCRIPTION
        "The vRtrMplsAdminGroupTable has an entry for each administrative group
         configured for the virtual router in the system.

         Administrative groups are resource constructs that define a link color
         or resource class. They provide the ability to classify network
         resources (links) into groups or colors based on zones, geographic
         location, link location, etc. By doing so, network administrators are
         able to do more granular traffic engineering of LSPs."
    ::= { tmnxMplsObjs 13 }

vRtrMplsAdminGroupEntry          OBJECT-TYPE
    SYNTAX      VRtrMplsAdminGroupEntry
    MAX-ACCESS  not-accessible
    STATUS      obsolete
    DESCRIPTION
        "Each row entry in the vRtrMplsAdminGroupTable represents an
         administrative group which is simply a mapping between a group name
         (an ASCII string) and a group value (a number in the range 0 to 31).

         Entries in this table are created and deleted via SNMP SET operations.
         An entry is created by setting the value of
         vRtrMplsAdminGroupRowStatus to 'createAndWait'. The row status for
         this entry can be set to active only once the value of
         vRtrMplsAdminGroupValue has been set to a valid number in the range 0
         to 31. The entry is destroyed when vRtrMplsAdminGroupRowStatus is set
         to 'destroy'."
    INDEX       {
        vRtrID,
        IMPLIED vRtrMplsAdminGroupName
    }
    ::= { vRtrMplsAdminGroupTable 1 }

VRtrMplsAdminGroupEntry          ::= SEQUENCE
{
    vRtrMplsAdminGroupName           TNamedItem,
    vRtrMplsAdminGroupRowStatus      RowStatus,
    vRtrMplsAdminGroupValue          Integer32
}

vRtrMplsAdminGroupName           OBJECT-TYPE
    SYNTAX      TNamedItem
    MAX-ACCESS  not-accessible
    STATUS      obsolete
    DESCRIPTION
        "The value of vRtrMplsAdminGroupName uniquely identifies the name of
         the administrative group within a virtual router instance."
    ::= { vRtrMplsAdminGroupEntry 1 }

vRtrMplsAdminGroupRowStatus      OBJECT-TYPE
    SYNTAX      RowStatus
    MAX-ACCESS  read-create
    STATUS      obsolete
    DESCRIPTION
        "vRtrMplsAdminGroupRowStatus is used to create, delete or control
         entries in the vRtrMplsAdminGroupTable. To create a row entry, the row
         status should be set to 'createAndWait'. Before the row can be placed
         into the 'active' state, vRtrMplsAdminGroupValue must be set to a
         value between 0 and 31. To delete a row entry, the row status should
         be set to 'destroy'"
    ::= { vRtrMplsAdminGroupEntry 2 }

vRtrMplsAdminGroupValue          OBJECT-TYPE
    SYNTAX      Integer32 (-1 | 0..31)
    MAX-ACCESS  read-create
    STATUS      obsolete
    DESCRIPTION
        "The value of vRtrMplsAdminGroupValue specifies the group value
         associated with this administrative group. This value is unique within
         a virtual router instance.

         A value of -1 indicates that the group value for this entry has not
         been set."
    ::= { vRtrMplsAdminGroupEntry 3 }

vRtrMplsFSGroupTable             OBJECT-TYPE
    SYNTAX      SEQUENCE OF VRtrMplsFSGroupEntry
    MAX-ACCESS  not-accessible
    STATUS      obsolete
    DESCRIPTION
        "The vRtrMplsFSGroupTable has an entry for each group that is a part of
         the fate sharing database configured for the virtual router in the
         system.

         A fate sharing group is used to define a group of links and nodes in
         the network that share common risk attributes. To minimize a single
         point of failure, backup paths can be created that not only avoid the
         nodes and links of the primary path but also any other nodes and links
         that share risk with the nodes and links of the primary path."
    ::= { tmnxMplsObjs 14 }

vRtrMplsFSGroupEntry             OBJECT-TYPE
    SYNTAX      VRtrMplsFSGroupEntry
    MAX-ACCESS  not-accessible
    STATUS      obsolete
    DESCRIPTION
        "Each row entry in the vRtrMplsFSGroupTable represents a fate sharing
         group which is a database of nodes and links that share common risk
         attributes.

         Entries in this table are created and deleted via SNMP SET operations.
         An entry is created by setting the value of vRtrMplsFSGroupRowStatus
         to 'createAndGo'. An entry can be deleted by setting
         vRtrMplsFSGroupRowStatus to 'destroy'."
    INDEX       {
        vRtrID,
        vRtrMplsFSGroupName
    }
    ::= { vRtrMplsFSGroupTable 1 }

VRtrMplsFSGroupEntry             ::= SEQUENCE
{
    vRtrMplsFSGroupName              TNamedItem,
    vRtrMplsFSGroupRowStatus         RowStatus,
    vRtrMplsFSGroupCost              Unsigned32
}

vRtrMplsFSGroupName              OBJECT-TYPE
    SYNTAX      TNamedItem
    MAX-ACCESS  not-accessible
    STATUS      obsolete
    DESCRIPTION
        "The value of vRtrMplsFSGroupName uniquely identifies the name of the
         fate sharing group within a virtual router instance."
    ::= { vRtrMplsFSGroupEntry 1 }

vRtrMplsFSGroupRowStatus         OBJECT-TYPE
    SYNTAX      RowStatus
    MAX-ACCESS  read-create
    STATUS      obsolete
    DESCRIPTION
        "vRtrMplsFSGroupRowStatus is used to create, delete or control entries
         in the vRtrMplsFSGroupTable. To create a row entry, the row status
         should be set to 'createAndGo'. To delete a row entry, the row status
         should be set to 'destroy'"
    ::= { vRtrMplsFSGroupEntry 2 }

vRtrMplsFSGroupCost              OBJECT-TYPE
    SYNTAX      Unsigned32 (1..65535)
    MAX-ACCESS  read-create
    STATUS      obsolete
    DESCRIPTION
        "The value of vRtrMplsFSGroupCost specifies the cost assigned to the
         fate sharing group. This cost is applied to all nodes and links that
         are part of this group and used for CSPF calculations. The higher the
         cost of the node or link, the lesser its chance of being selected as
         part of the path."
    DEFVAL      { 1 }
    ::= { vRtrMplsFSGroupEntry 3 }

vRtrMplsFSGroupParamsTable       OBJECT-TYPE
    SYNTAX      SEQUENCE OF VRtrMplsFSGroupParamsEntry
    MAX-ACCESS  not-accessible
    STATUS      obsolete
    DESCRIPTION
        "The vRtrMplsFSGroupParamsTable has an entry for each node or link that
         is part of a fate sharing group on this virtual router."
    ::= { tmnxMplsObjs 15 }

vRtrMplsFSGroupParamsEntry       OBJECT-TYPE
    SYNTAX      VRtrMplsFSGroupParamsEntry
    MAX-ACCESS  not-accessible
    STATUS      obsolete
    DESCRIPTION
        "Each row entry in the vRtrMplsFSGroupParamsTable represents either a
         node or a link that is a part of a fate sharing group defined in the
         vRtrMplsFSGroupTable.

         Entries in this table are created and deleted via SNMP SET operations.
         An entry is created by setting the value of
         vRtrMplsFSGroupParamsRowStatus to 'createAndGo'. An entry can be
         deleted by setting vRtrMplsFSGroupParamsRowStatus to 'destroy'.

         To configure a node to be part of the group, create an entry in this
         table with vRtrMplsFSGroupParamsFromAddr set to a valid non-zero IP
         address and vRtrMplsFSGroupParamsToAddr set to 0. To configure a link
         to be part of the group, create an entry in this table with both
         vRtrMplsFSGroupParamsFromAddr and vRtrMplsFSGroupParamsToAddr set to
         valid non-zero IP addresses."
    INDEX       {
        vRtrID,
        vRtrMplsFSGroupName,
        vRtrMplsFSGroupParamsFromAddr,
        vRtrMplsFSGroupParamsToAddr
    }
    ::= { vRtrMplsFSGroupParamsTable 1 }

VRtrMplsFSGroupParamsEntry       ::= SEQUENCE
{
    vRtrMplsFSGroupParamsFromAddr    IpAddress,
    vRtrMplsFSGroupParamsToAddr      IpAddress,
    vRtrMplsFSGroupParamsRowStatus   RowStatus
}

vRtrMplsFSGroupParamsFromAddr    OBJECT-TYPE
    SYNTAX      IpAddress
    MAX-ACCESS  not-accessible
    STATUS      obsolete
    DESCRIPTION
        "The value of vRtrMplsFSGroupParamsFromAddr along with the value of
         vRtrMplsFSGroupParamsToAddr uniquely identifies a link or node within
         a fate sharing group.

         This value must be non-zero for all row entries whether it represents
         a node or a link."
    ::= { vRtrMplsFSGroupParamsEntry 1 }

vRtrMplsFSGroupParamsToAddr      OBJECT-TYPE
    SYNTAX      IpAddress
    MAX-ACCESS  not-accessible
    STATUS      obsolete
    DESCRIPTION
        "The value of vRtrMplsFSGroupParamsToAddr along with the value of
         vRtrMplsFSGroupParamsFromAddr uniquely identifies a link or node
         within a fate sharing group.

         This value must be 0 for row entries that represent a node and must be
         non-zero for row entries that represent a link."
    ::= { vRtrMplsFSGroupParamsEntry 2 }

vRtrMplsFSGroupParamsRowStatus   OBJECT-TYPE
    SYNTAX      RowStatus
    MAX-ACCESS  read-create
    STATUS      obsolete
    DESCRIPTION
        "vRtrMplsFSGroupParamsRowStatus is used to create, delete or control
         entries in the vRtrMplsFSGroupParamsTable. To create a row entry, the
         row status should be set to 'createAndGo'. To delete a row entry, the
         row status should be set to 'destroy'"
    ::= { vRtrMplsFSGroupParamsEntry 3 }

tmnxMplsNotificationObjects      OBJECT IDENTIFIER ::= { tmnxMplsObjs 16 }

vRtrMplsLspNotificationReasonCode OBJECT-TYPE
    SYNTAX      INTEGER {
        noError             (0),
        noPathIsOperational (1)
    }
    MAX-ACCESS  accessible-for-notify
    STATUS      current
    DESCRIPTION
        "Used by vRtrMplsLspDown, the value indicates the reason for the LSP
         going down."
    ::= { tmnxMplsNotificationObjects 1 }

vRtrMplsLspPathNotificationReasonCode OBJECT-TYPE
    SYNTAX      TmnxMplsLspFailCode
    MAX-ACCESS  accessible-for-notify
    STATUS      current
    DESCRIPTION
        "Used by vRtrMplsLspPathDown, the value indicates the reason for the
         LSP path going down."
    ::= { tmnxMplsNotificationObjects 2 }

vRtrMplsNotifyRow                OBJECT-TYPE
    SYNTAX      RowPointer
    MAX-ACCESS  accessible-for-notify
    STATUS      current
    DESCRIPTION
        "used by Nokia SROS series MPLS Configuration change Notifications, the
         object ID indicates the MPLS table and entry."
    ::= { tmnxMplsNotificationObjects 3 }

vRtrMplsP2mpInstNotifIndex       OBJECT-TYPE
    SYNTAX      TmnxVRtrMplsLspID
    MAX-ACCESS  accessible-for-notify
    STATUS      current
    DESCRIPTION
        "The unique value which identifies this Point to Multipoint Labeled
         Switch Path (P2MP LSP) for this virtual router in the Nokia
         SROS system.  It is a unique value among entries with the
         same value of vRtrID."
    ::= { tmnxMplsNotificationObjects 4 }

vRtrMplsP2mpInstNotifReasonCode  OBJECT-TYPE
    SYNTAX      TmnxMplsP2mpInstFailCode
    MAX-ACCESS  accessible-for-notify
    STATUS      current
    DESCRIPTION
        "Used by vRtrMplsP2mpInstanceDown, the value indicates the reason for
         the P2MP instance going down."
    ::= { tmnxMplsNotificationObjects 5 }

vRtrMplsS2lSubLspNtDstAddrType   OBJECT-TYPE
    SYNTAX      InetAddressType
    MAX-ACCESS  accessible-for-notify
    STATUS      current
    DESCRIPTION
        "The value of vRtrMplsS2lSubLspNtDstAddrType indicates the type of
         vRtrMplsS2lSubLspNtDstAddr."
    ::= { tmnxMplsNotificationObjects 6 }

vRtrMplsS2lSubLspNtDstAddr       OBJECT-TYPE
    SYNTAX      InetAddress (SIZE (0|4))
    MAX-ACCESS  accessible-for-notify
    STATUS      current
    DESCRIPTION
        "The value of vRtrMplsS2lSubLspNtDstAddr indicates the IP address of
         the destination address of the S2L sub LSP. "
    ::= { tmnxMplsNotificationObjects 7 }

vRtrMplsLspPathCongChgPercent    OBJECT-TYPE
    SYNTAX      Unsigned32
    MAX-ACCESS  accessible-for-notify
    STATUS      current
    DESCRIPTION
        "The value of vRtrMplsLspPathCongChgPercent indicates the percentage
         change in congestion. "
    ::= { tmnxMplsNotificationObjects 8 }

vRtrMplsLspPathMbbStatus         OBJECT-TYPE
    SYNTAX      INTEGER {
        successful (0),
        failed     (1),
        aborted    (2),
        ignored    (3)
    }
    MAX-ACCESS  accessible-for-notify
    STATUS      current
    DESCRIPTION
        "The value of vRtrMplsLspPathMbbStatus indicates the status of the
         make-before-break (MBB) operation for the LSP path."
    ::= { tmnxMplsNotificationObjects 9 }

vRtrMplsLspPathMbbReasonCode     OBJECT-TYPE
    SYNTAX      INTEGER {
        none                (0),
        mbbRetryExceeded    (1),
        lspPathGoingDown    (2),
        startingHighPriMbb  (3),
        restartingMbb       (4),
        mbbAlreadyInProg    (5),
        lspPceControlled    (6),
        lspNotPceControlled (7),
        lspTypeNotSupported (8)
    }
    MAX-ACCESS  accessible-for-notify
    STATUS      current
    DESCRIPTION
        "The value of vRtrMplsLspPathMbbReasonCode indicates the reason code
         for the make-before-break (MBB) operation of the LSP path. It
         indicates whether the operation is failed, aborted or ignored."
    ::= { tmnxMplsNotificationObjects 10 }

vRtrMplsLspSwitchStbyReasonCode  OBJECT-TYPE
    SYNTAX      INTEGER {
        none                          (0),
        lspIsDown                     (1),
        lspIsNotDynamic               (2),
        lspHasNoActivePath            (3),
        lspActivePathIsNotStandby     (4),
        pathSpecifiedIsNotLspPath     (5),
        pathSpecifiedIsNotStandby     (6),
        pathSpecifiedIsDown           (7),
        pathHasDiffPrefThanActLspPath (8),
        lspHoldTimerIsRunning         (9),
        currentLspPathActiveByForce   (10),
        lspPathInPreemption           (11),
        lspActivePathIsPrimary        (12),
        currentActivePathIsBest       (13),
        betterPathFound               (14),
        currentActivePathWentDown     (15)
    }
    MAX-ACCESS  accessible-for-notify
    STATUS      current
    DESCRIPTION
        "The value of vRtrMplsLspSwitchStbyReasonCode indicates the reason for
         the failure of switch to a new standby path from the current active
         standby path."
    ::= { tmnxMplsNotificationObjects 13 }

vRtrMplsLspOldTunnelIndex        OBJECT-TYPE
    SYNTAX      MplsTunnelIndex
    MAX-ACCESS  accessible-for-notify
    STATUS      current
    DESCRIPTION
        "The value of vRtrMplsLspOldTunnelIndex indicates the tunnel index of
         of the old LSP path."
    ::= { tmnxMplsNotificationObjects 14 }

vRtrMplsXCNotifRednIndicesBitMap OBJECT-TYPE
    SYNTAX      OCTET STRING (SIZE (0..1000))
    MAX-ACCESS  accessible-for-notify
    STATUS      current
    DESCRIPTION
        "The value of vRtrMplsXCNotifRednIndicesBitMap indicates the RSVP
         sessions that either changed state and retained the changed state for
         the entire quiet interval of 2 minutes or the RSVP sessions that
         changed state during multiple intervals until a maximum interval of 10
         minutes has elapsed.

         Each bit location in vRtrMplsXCNotifRednIndicesBitMap corresponds to a
         created or deleted row entry in vRtrMplsXCTable as identified by the
         value of vRtrMplsXCIndex. This index is same as the value of
         TIMETRA-RSVP-MIB::vRtrRsvpSessionIndex which corresponds to a created
         or deleted RSVP session entry in
         TIMETRA-RSVP-MIB::vRtrRsvpSessionTable.

         The value of vRtrMplsXCNotifyRednStartIndex indicates the index value
         of the first affected row entry represented by bit 0, the most
         significant bit.

         If the value of vRtrMplsXCNotifyRednBundlingType is set to 'create
         (2)', all the bits set in vRtrMplsXCNotifRednIndicesBitMap represent
         created RSVP sessions. If the value of
         vRtrMplsXCNotifyRednBundlingType is set to 'delete (1)', all the bits
         set in vRtrMplsXCNotifRednIndicesBitMap represent deleted RSVP
         sessions."
    ::= { tmnxMplsNotificationObjects 15 }

vRtrMplsXCNotifyRednBundlingType OBJECT-TYPE
    SYNTAX      INTEGER {
        delete (1),
        create (2)
    }
    MAX-ACCESS  accessible-for-notify
    STATUS      current
    DESCRIPTION
        "The value of vRtrMplsXCNotifyRednBundlingType indicates whether this
         notification is generated for deletion or creation of RSVP sessions on
         this ingress, transit or egress router instance."
    ::= { tmnxMplsNotificationObjects 16 }

vRtrMplsXCNotifyRednNumOfBitsSet OBJECT-TYPE
    SYNTAX      Unsigned32
    MAX-ACCESS  accessible-for-notify
    STATUS      current
    DESCRIPTION
        "The value of vRtrMplsXCNotifyRednNumOfBitsSet indicates the total
         number of bits set in vRtrMplsXCNotifRednIndicesBitMap."
    ::= { tmnxMplsNotificationObjects 17 }

vRtrMplsXCNotifyRednStartIndex   OBJECT-TYPE
    SYNTAX      Unsigned32
    MAX-ACCESS  accessible-for-notify
    STATUS      current
    DESCRIPTION
        "The value of vRtrMplsXCNotifyRednStartIndex indicates which
         vRtrMplsXCIndex is represented by the first bit in
         vRtrMplsXCNotifRednIndicesBitMap."
    ::= { tmnxMplsNotificationObjects 18 }

vRtrMplsXCNotifyRednEndIndex     OBJECT-TYPE
    SYNTAX      Unsigned32
    MAX-ACCESS  accessible-for-notify
    STATUS      current
    DESCRIPTION
        "The value of vRtrMplsXCNotifyRednEndIndex indicates which
         vRtrMplsXCIndex is represented by the last bit in
         vRtrMplsXCNotifRednIndicesBitMap.

         The value vRtrMplsXCNotifyRednEndIndex can be useful for a sanity
         check of vRtrMplsXCNotifyRednNumOfBitsSet.

         vRtrMplsXCNotifyRednNumOfBitsSet. = (vRtrMplsXCNotifyRednEndIndex -
         vRtrMplsXCNotifyRednStartIndex + 1)."
    ::= { tmnxMplsNotificationObjects 19 }

vRtrMplsIgpOverloadRtrAddrType   OBJECT-TYPE
    SYNTAX      InetAddressType
    MAX-ACCESS  accessible-for-notify
    STATUS      current
    DESCRIPTION
        "The value of vRtrMplsIgpOverloadRtrAddrType indicates the address type
         of vRtrMplsIgpOverloadRtrAddr."
    ::= { tmnxMplsNotificationObjects 20 }

vRtrMplsIgpOverloadRtrAddr       OBJECT-TYPE
    SYNTAX      InetAddress (SIZE (0|4|16))
    MAX-ACCESS  accessible-for-notify
    STATUS      current
    DESCRIPTION
        "The value of vRtrMplsIgpOverloadRtrAddr indicates the IP address of
         the router that is in IGP overload state."
    ::= { tmnxMplsNotificationObjects 21 }

vRtrMplsIgpOverloadIgpType       OBJECT-TYPE
    SYNTAX      INTEGER {
        isis (1),
        ospf (2)
    }
    MAX-ACCESS  accessible-for-notify
    STATUS      current
    DESCRIPTION
        "The value of vRtrMplsIgpOverloadIgpType indicates IGP which is
         notifying MPLS that a node is in the overload state."
    ::= { tmnxMplsNotificationObjects 22 }

vRtrMplsResourceType             OBJECT-TYPE
    SYNTAX      INTEGER {
        egressStatistics (1)
    }
    MAX-ACCESS  accessible-for-notify
    STATUS      current
    DESCRIPTION
        "The value of vRtrMplsResourceType indicates various CPM/IOM resource
         used by MPLS."
    ::= { tmnxMplsNotificationObjects 23 }

vRtrMplsLabelRangeTable          OBJECT-TYPE
    SYNTAX      SEQUENCE OF VRtrMplsLabelRangeEntry
    MAX-ACCESS  not-accessible
    STATUS      current
    DESCRIPTION
        "The vRtrMplsLabelRangeTable has an entry for each type of label, the
         minimum and maximum value in the label range and information on total
         available and aging labels in each range.

         This is a read-only table."
    ::= { tmnxMplsObjs 17 }

vRtrMplsLabelRangeEntry          OBJECT-TYPE
    SYNTAX      VRtrMplsLabelRangeEntry
    MAX-ACCESS  not-accessible
    STATUS      current
    DESCRIPTION
        "Each row entry in the vRtrMplsLabelRangeTable represents a type of
         label. Each entry contains the label range used by that label type and
         the number of aging and allocated labels in the range."
    INDEX       { vRtrMplsLabelType }
    ::= { vRtrMplsLabelRangeTable 1 }

VRtrMplsLabelRangeEntry          ::= SEQUENCE
{
    vRtrMplsLabelType                INTEGER,
    vRtrMplsLabelRangeMin            Unsigned32,
    vRtrMplsLabelRangeMax            Unsigned32,
    vRtrMplsLabelRangeAging          Unsigned32,
    vRtrMplsLabelRangeAvailable      Unsigned32
}

vRtrMplsLabelType                OBJECT-TYPE
    SYNTAX      INTEGER {
        staticLsp    (1),
        staticSvc    (2),
        dynamic      (3),
        segmentRoute (4),
        static       (5)
    }
    MAX-ACCESS  not-accessible
    STATUS      current
    DESCRIPTION
        "The value of vRtrMplsLabelType specifies the type of label and is the
         index for this table."
    ::= { vRtrMplsLabelRangeEntry 1 }

vRtrMplsLabelRangeMin            OBJECT-TYPE
    SYNTAX      Unsigned32
    MAX-ACCESS  read-only
    STATUS      current
    DESCRIPTION
        "The value of vRtrMplsLabelRangeMin indicates the minimum label value
         in the range for a particular label type."
    ::= { vRtrMplsLabelRangeEntry 2 }

vRtrMplsLabelRangeMax            OBJECT-TYPE
    SYNTAX      Unsigned32
    MAX-ACCESS  read-only
    STATUS      current
    DESCRIPTION
        "The value of vRtrMplsLabelRangeMax indicates the maximum label value
         in the range for a particular label type."
    ::= { vRtrMplsLabelRangeEntry 3 }

vRtrMplsLabelRangeAging          OBJECT-TYPE
    SYNTAX      Unsigned32
    MAX-ACCESS  read-only
    STATUS      current
    DESCRIPTION
        "The value of vRtrMplsLabelRangeAging represents the number of labels
         that are currently allocated and aging."
    ::= { vRtrMplsLabelRangeEntry 4 }

vRtrMplsLabelRangeAvailable      OBJECT-TYPE
    SYNTAX      Unsigned32
    MAX-ACCESS  read-only
    STATUS      current
    DESCRIPTION
        "The value of vRtrMplsLabelRangeAvailable represents the number of
         labels that are currently available for each label type."
    ::= { vRtrMplsLabelRangeEntry 5 }

vRtrMplsStaticLSPLabelTable      OBJECT-TYPE
    SYNTAX      SEQUENCE OF VRtrMplsStaticLSPLabelEntry
    MAX-ACCESS  not-accessible
    STATUS      current
    DESCRIPTION
        "The vRtrMplsStaticLSPLabelTable has an entry for each allocated label
         that is part of the static LSP label range. This is a read-only table."
    ::= { tmnxMplsObjs 18 }

vRtrMplsStaticLSPLabelEntry      OBJECT-TYPE
    SYNTAX      VRtrMplsStaticLSPLabelEntry
    MAX-ACCESS  not-accessible
    STATUS      current
    DESCRIPTION
        "Each row entry in the vRtrMplsStaticLSPLabelTable represents a label
         of type static LSP that is currently allocated. The entry includes
         information about the current owner for that label."
    INDEX       { vRtrMplsStaticLSPLabel }
    ::= { vRtrMplsStaticLSPLabelTable 1 }

VRtrMplsStaticLSPLabelEntry      ::= SEQUENCE
{
    vRtrMplsStaticLSPLabel           MplsLabel,
    vRtrMplsStaticLSPLabelOwner      TmnxMplsLabelOwner
}

vRtrMplsStaticLSPLabel           OBJECT-TYPE
    SYNTAX      MplsLabel (32..262112)
    MAX-ACCESS  not-accessible
    STATUS      current
    DESCRIPTION
        "The value of vRtrMplsStaticLSPLabel specifies the label value for a
         static LSP.

         The range of vRtrMplsStaticLSPLabel is dynamic and depends on the
         value of vRtrMplsLabelStaticLabelRange.

         The normal range of vRtrMplsStaticLSPLabel starts at 32 and ends at
         the value of vRtrMplsLabelStaticLabelRange + 32."
    ::= { vRtrMplsStaticLSPLabelEntry 1 }

vRtrMplsStaticLSPLabelOwner      OBJECT-TYPE
    SYNTAX      TmnxMplsLabelOwner
    MAX-ACCESS  read-only
    STATUS      current
    DESCRIPTION
        "The value of vRtrMplsStaticLSPLabelOwner indicates the owner for the
         label value vRtrMplsStaticLSPLabel."
    ::= { vRtrMplsStaticLSPLabelEntry 2 }

vRtrMplsStaticSvcLabelTable      OBJECT-TYPE
    SYNTAX      SEQUENCE OF VRtrMplsStaticSvcLabelEntry
    MAX-ACCESS  not-accessible
    STATUS      current
    DESCRIPTION
        "The vRtrMplsStaticSvcLabelTable has an entry for each allocated label
         that is part of the static service label range. This is a read-only
         table."
    ::= { tmnxMplsObjs 19 }

vRtrMplsStaticSvcLabelEntry      OBJECT-TYPE
    SYNTAX      VRtrMplsStaticSvcLabelEntry
    MAX-ACCESS  not-accessible
    STATUS      current
    DESCRIPTION
        "Each row entry in the vRtrMplsStaticSvcLabelTable represents a label
         of type static-svc that is currently allocated. The entry includes
         information about the current owner for that label."
    INDEX       { vRtrMplsStaticSvcLabel }
    ::= { vRtrMplsStaticSvcLabelTable 1 }

VRtrMplsStaticSvcLabelEntry      ::= SEQUENCE
{
    vRtrMplsStaticSvcLabel           MplsLabel,
    vRtrMplsStaticSvcLabelOwner      TmnxMplsLabelOwner
}

vRtrMplsStaticSvcLabel           OBJECT-TYPE
    SYNTAX      MplsLabel (32..262112)
    MAX-ACCESS  not-accessible
    STATUS      current
    DESCRIPTION
        "The value of vRtrMplsStaticSvcLabel specifies the label value for a
         static SVC.

         The range of vRtrMplsStaticSvcLabel is dynamic and depends on the
         value of vRtrMplsLabelStaticLabelRange.

         The range for vRtrMplsStaticSvcLabel starts at 32 and ends at 32 +
         vRtrMplsLabelStaticLabelRange."
    ::= { vRtrMplsStaticSvcLabelEntry 1 }

vRtrMplsStaticSvcLabelOwner      OBJECT-TYPE
    SYNTAX      TmnxMplsLabelOwner
    MAX-ACCESS  read-only
    STATUS      current
    DESCRIPTION
        "The value of vRtrMplsStaticSvcLabelOwner specifies the owner for the
         label value vRtrMplsStaticSvcLabel."
    DEFVAL      { none }
    ::= { vRtrMplsStaticSvcLabelEntry 2 }

vRtrMplsSrlgGrpTableLastChanged  OBJECT-TYPE
    SYNTAX      TimeStamp
    MAX-ACCESS  read-only
    STATUS      obsolete
    DESCRIPTION
        "The value of vRtrMplsSrlgGrpTableLastChanged indicates the sysUpTime
         at the time of the last modification to vRtrMplsSrlgGrpTable by
         adding, deleting an entry or change to a writable object in the table.

         If no changes were made to the table since the last re-initialization
         of the local network management subsystem, then this object contains a
         zero value."
    ::= { tmnxMplsObjs 20 }

vRtrMplsSrlgGrpTable             OBJECT-TYPE
    SYNTAX      SEQUENCE OF VRtrMplsSrlgGrpEntry
    MAX-ACCESS  not-accessible
    STATUS      obsolete
    DESCRIPTION
        "The vRtrMplsSrlgGrpTable has an entry for each Shared Risk Link Groups
         (SRLG) group configured for MPLS in the system."
    ::= { tmnxMplsObjs 21 }

vRtrMplsSrlgGrpEntry             OBJECT-TYPE
    SYNTAX      VRtrMplsSrlgGrpEntry
    MAX-ACCESS  not-accessible
    STATUS      obsolete
    DESCRIPTION
        "Each row entry represents a SRLG group on this virtual router
         that participates in the MPLS protocol.  A row can be created
         or deleted via SNMP SET requests."
    INDEX       {
        vRtrID,
        IMPLIED vRtrMplsSrlgGrpName
    }
    ::= { vRtrMplsSrlgGrpTable 1 }

VRtrMplsSrlgGrpEntry             ::= SEQUENCE
{
    vRtrMplsSrlgGrpName              TNamedItem,
    vRtrMplsSrlgGrpRowStatus         RowStatus,
    vRtrMplsSrlgGrpLastChanged       TimeStamp,
    vRtrMplsSrlgGrpValue             Unsigned32
}

vRtrMplsSrlgGrpName              OBJECT-TYPE
    SYNTAX      TNamedItem
    MAX-ACCESS  not-accessible
    STATUS      obsolete
    DESCRIPTION
        "The value of vRtrMplsSrlgGrpName indicates the SRLG group name."
    ::= { vRtrMplsSrlgGrpEntry 1 }

vRtrMplsSrlgGrpRowStatus         OBJECT-TYPE
    SYNTAX      RowStatus
    MAX-ACCESS  read-create
    STATUS      obsolete
    DESCRIPTION
        "vRtrMplsSrlgGrpRowStatus is used to create, delete or
         control entries in the vRtrMplsSrlgGrpTable.  A value must
         also be set for vRtrMplsSrlgGrpValue before the row entry can
         transition to the 'active' state."
    ::= { vRtrMplsSrlgGrpEntry 2 }

vRtrMplsSrlgGrpLastChanged       OBJECT-TYPE
    SYNTAX      TimeStamp
    MAX-ACCESS  read-only
    STATUS      obsolete
    DESCRIPTION
        "The value of vRtrMplsSrlgGrpLastChanged indicates the timestamp of
         last change to this row in vRtrMplsSrlgGrpTable."
    ::= { vRtrMplsSrlgGrpEntry 3 }

vRtrMplsSrlgGrpValue             OBJECT-TYPE
    SYNTAX      Unsigned32
    MAX-ACCESS  read-create
    STATUS      obsolete
    DESCRIPTION
        "The value of vRtrMplsSrlgGrpValue specifies the group value
         associated with vRtrMplsSrlgGrpName.  This value is unique
         within a virtual router instance.

         At the time of row creation, a value for vRtrMplsSrlgGrpValue must be
         specified or else row creation would fail."
    ::= { vRtrMplsSrlgGrpEntry 4 }

vRtrMplsIfSrlgGrpTblLastChanged  OBJECT-TYPE
    SYNTAX      TimeStamp
    MAX-ACCESS  read-only
    STATUS      current
    DESCRIPTION
        "The value of vRtrMplsIfSrlgGrpTblLastChanged indicates the sysUpTime
         at the time of the last modification to vRtrMplsIfSrlgGrpTable by
         adding, deleting an entry or change to a writable object in the table.

         If no changes were made to the table since the last re-initialization
         of the local network management subsystem, then this object contains a
         zero value."
    ::= { tmnxMplsObjs 22 }

vRtrMplsIfSrlgGrpTable           OBJECT-TYPE
    SYNTAX      SEQUENCE OF VRtrMplsIfSrlgGrpEntry
    MAX-ACCESS  not-accessible
    STATUS      current
    DESCRIPTION
        "The vRtrMplsIfSrlgGrpTable has an entry for each Shared Risk Link
         Group (SRLG) groups associated with a router interface configured for
         MPLS in the system."
    ::= { tmnxMplsObjs 23 }

vRtrMplsIfSrlgGrpEntry           OBJECT-TYPE
    SYNTAX      VRtrMplsIfSrlgGrpEntry
    MAX-ACCESS  not-accessible
    STATUS      current
    DESCRIPTION
        "Each row entry represents an SRLG group associated with a interface on
         this virtual router that participates in the MPLS protocol.

         A row can be created or deleted via SNMP SET requests."
    INDEX       {
        vRtrID,
        vRtrIfIndex,
        IMPLIED vRtrMplsIfSrlgGrpName
    }
    ::= { vRtrMplsIfSrlgGrpTable 1 }

VRtrMplsIfSrlgGrpEntry           ::= SEQUENCE
{
    vRtrMplsIfSrlgGrpName            TNamedItem,
    vRtrMplsIfSrlgGrpRowStatus       RowStatus,
    vRtrMplsIfSrlgGrpLastChanged     TimeStamp
}

vRtrMplsIfSrlgGrpName            OBJECT-TYPE
    SYNTAX      TNamedItem
    MAX-ACCESS  not-accessible
    STATUS      current
    DESCRIPTION
        "The value of vRtrMplsIfSrlgGrpName indicates the SRLG group name."
    ::= { vRtrMplsIfSrlgGrpEntry 1 }

vRtrMplsIfSrlgGrpRowStatus       OBJECT-TYPE
    SYNTAX      RowStatus
    MAX-ACCESS  read-create
    STATUS      current
    DESCRIPTION
        "vRtrMplsIfSrlgGrpRowStatus is used to create, delete or control
         entries in the vRtrMplsIfSrlgGrpTable."
    ::= { vRtrMplsIfSrlgGrpEntry 2 }

vRtrMplsIfSrlgGrpLastChanged     OBJECT-TYPE
    SYNTAX      TimeStamp
    MAX-ACCESS  read-only
    STATUS      current
    DESCRIPTION
        "The value of vRtrMplsIfSrlgGrpLastChanged indicates the timestamp of
         last change to this row in vRtrMplsIfSrlgGrpTable."
    ::= { vRtrMplsIfSrlgGrpEntry 3 }

vRtrMplsP2mpInstTblLastChanged   OBJECT-TYPE
    SYNTAX      TimeStamp
    MAX-ACCESS  read-only
    STATUS      current
    DESCRIPTION
        "The value of vRtrMplsP2mpInstTblLastChanged indicates the sysUpTime at
         the time of the last modification to vRtrMplsP2mpInstTable by adding,
         deleting an entry or change to a writable object in the table.

         If no changes were made to the table since the last re-initialization
         of the local network management subsystem, then this object contains a
         zero value."
    ::= { tmnxMplsObjs 24 }

vRtrMplsP2mpInstTable            OBJECT-TYPE
    SYNTAX      SEQUENCE OF VRtrMplsP2mpInstEntry
    MAX-ACCESS  not-accessible
    STATUS      current
    DESCRIPTION
        "vRtrMplsP2mpInstTable contains configuration information for the Mpls
         Point to Multipoint (P2MP) Instance on a virtual router."
    ::= { tmnxMplsObjs 25 }

vRtrMplsP2mpInstEntry            OBJECT-TYPE
    SYNTAX      VRtrMplsP2mpInstEntry
    MAX-ACCESS  not-accessible
    STATUS      current
    DESCRIPTION
        "vRtrMplsP2mpInstEntry is an entry (conceptual row) in the
         vRtrMplsP2mpInstTable. Each entry represents the configuration for a
         Mpls Point to Multipoint (P2MP) Instance.

         Entries in this table can be created and deleted via SNMP SET
         operations. "
    INDEX       {
        vRtrID,
        vRtrMplsLspIndex,
        vRtrMplsP2mpInstIndex
    }
    ::= { vRtrMplsP2mpInstTable 1 }

VRtrMplsP2mpInstEntry            ::= SEQUENCE
{
    vRtrMplsP2mpInstIndex            TmnxVRtrMplsLspID,
    vRtrMplsP2mpInstRowStatus        RowStatus,
    vRtrMplsP2mpInstLastChange       TimeStamp,
    vRtrMplsP2mpInstName             TNamedItemOrEmpty,
    vRtrMplsP2mpInstType             INTEGER,
    vRtrMplsP2mpInstProperties       BITS,
    vRtrMplsP2mpInstBandwidth        TmnxMplsLspBandwidth,
    vRtrMplsP2mpInstState            INTEGER,
    vRtrMplsP2mpInstSetupPriority    Unsigned32,
    vRtrMplsP2mpInstHoldPriority     Unsigned32,
    vRtrMplsP2mpInstRecord           TruthValue,
    vRtrMplsP2mpInstHopLimit         Unsigned32,
    vRtrMplsP2mpInstAdminState       TmnxAdminState,
    vRtrMplsP2mpInstOperState        TmnxOperState,
    vRtrMplsP2mpInstInheritance      Unsigned32,
    vRtrMplsP2mpInstLspId            MplsLSPID,
    vRtrMplsP2mpInstNegotiatedMTU    Unsigned32,
    vRtrMplsP2mpInstFailCode         TmnxMplsLspFailCode,
    vRtrMplsP2mpInstFailNodeArType   InetAddressType,
    vRtrMplsP2mpInstFailNodeAddr     InetAddress,
    vRtrMplsP2mpInstAdminGrpInclude  Unsigned32,
    vRtrMplsP2mpInstAdminGrpExclude  Unsigned32,
    vRtrMplsP2mpInstAdaptive         TruthValue,
    vRtrMplsP2mpInstOperBandwidth    Integer32,
    vRtrMplsP2mpInstResignal         TmnxActionType,
    vRtrMplsP2mpInstOperMTU          Unsigned32,
    vRtrMplsP2mpInstRecordLabel      INTEGER,
    vRtrMplsP2mpInstLastResigAttpt   TimeStamp,
    vRtrMplsP2mpInstMetric           Unsigned32,
    vRtrMplsP2mpInstLastMBBType      TmnxMplsMBBType,
    vRtrMplsP2mpInstLastMBBEnd       TimeStamp,
    vRtrMplsP2mpInstLastMBBMetric    Unsigned32,
    vRtrMplsP2mpInstLastMBBState     INTEGER,
    vRtrMplsP2mpInstMBBTypeInProg    TmnxMplsMBBType,
    vRtrMplsP2mpInstMBBStarted       TimeStamp,
    vRtrMplsP2mpInstMBBNextRetry     Unsigned32,
    vRtrMplsP2mpInstMBBRetryAttpts   Unsigned32,
    vRtrMplsP2mpInstMBBFailCode      TmnxMplsLspFailCode,
    vRtrMplsP2mpInstMBBFailNodeType  InetAddressType,
    vRtrMplsP2mpInstMBBFailNodeAddr  InetAddress
}

vRtrMplsP2mpInstIndex            OBJECT-TYPE
    SYNTAX      TmnxVRtrMplsLspID
    MAX-ACCESS  not-accessible
    STATUS      current
    DESCRIPTION
        "The unique value which identifies this Point to Multipoint Labeled
         Switch Path (P2MP LSP) for this virtual router in the Nokia
         SROS system.  It is a unique value among entries with the
         same value of vRtrID."
    ::= { vRtrMplsP2mpInstEntry 1 }

vRtrMplsP2mpInstRowStatus        OBJECT-TYPE
    SYNTAX      RowStatus
    MAX-ACCESS  read-create
    STATUS      current
    DESCRIPTION
        "vRtrMplsP2mpInstRowStatus is used to create, delete or control entries
         in the vRtrMplsP2mpInstTable."
    ::= { vRtrMplsP2mpInstEntry 2 }

vRtrMplsP2mpInstLastChange       OBJECT-TYPE
    SYNTAX      TimeStamp
    MAX-ACCESS  read-only
    STATUS      current
    DESCRIPTION
        "The value of vRtrMplsP2mpInstLastChange indicates the timestamp of
         last change to this row in vRtrMplsP2mpInstTable."
    ::= { vRtrMplsP2mpInstEntry 3 }

vRtrMplsP2mpInstName             OBJECT-TYPE
    SYNTAX      TNamedItemOrEmpty
    MAX-ACCESS  read-create
    STATUS      current
    DESCRIPTION
        "The value of vRtrMplsP2mpInstName specifies the administrative name
         for the P2MP instance which must be unique within a virtual router
         instance."
    ::= { vRtrMplsP2mpInstEntry 4 }

vRtrMplsP2mpInstType             OBJECT-TYPE
    SYNTAX      INTEGER {
        other   (1),
        primary (2)
    }
    MAX-ACCESS  read-create
    STATUS      current
    DESCRIPTION
        "The value of vRtrMplsP2mpInstType specifies the type of P2MP LSP
         instance."
    DEFVAL      { primary }
    ::= { vRtrMplsP2mpInstEntry 5 }

vRtrMplsP2mpInstProperties       OBJECT-TYPE
    SYNTAX      BITS {
        recordRoute (0),
        adaptive    (1),
        cspf        (2),
        mergeable   (3),
        fastReroute (4)
    }
    MAX-ACCESS  read-only
    STATUS      current
    DESCRIPTION
        "The value of vRtrMplsP2mpInstProperties indicates the set of configured
         properties for this path expressed as a bit map.  For example, if the
         path is an adaptive path, the bit corresponding to bit value 1 is set."
    ::= { vRtrMplsP2mpInstEntry 6 }

vRtrMplsP2mpInstBandwidth        OBJECT-TYPE
    SYNTAX      TmnxMplsLspBandwidth
    UNITS       "megabps"
    MAX-ACCESS  read-create
    STATUS      current
    DESCRIPTION
        "The value of vRtrMplsP2mpInstBandwidth specifies the amount of
         bandwidth in megabits per second (Mbps) to be reserved for the P2MP
         LSP."
    DEFVAL      { 0 }
    ::= { vRtrMplsP2mpInstEntry 7 }

vRtrMplsP2mpInstState            OBJECT-TYPE
    SYNTAX      INTEGER {
        unknown  (1),
        active   (2),
        inactive (3)
    }
    MAX-ACCESS  read-only
    STATUS      current
    DESCRIPTION
        "The value of vRtrMplsP2mpInstState indicates the current working state
         of this path within this P2MP LSP."
    ::= { vRtrMplsP2mpInstEntry 8 }

vRtrMplsP2mpInstSetupPriority    OBJECT-TYPE
    SYNTAX      Unsigned32 (0..7)
    MAX-ACCESS  read-only
    STATUS      current
    DESCRIPTION
        "The value of vRtrMplsP2mpInstSetupPriority indicates the setup
         priority to use when insufficient bandwidth is available to setup
         a P2MP LSP.  The setup priority is compared against the hold priority
         of existing LSPs.  If the setup priority is higher than the hold
         priority of the established LSPs, this P2MP LSP may preempt the other
         LSPs.  A value of zero (0) is the highest priority and a value
         of seven (7) is the lowest priority.

         When the vRtrMplsP2mpInstHopLimit bit in vRtrMplsP2mpInstInheritance
         is cleared (0), the value returned to a GET request is inherited from
         vRtrMplsLspHopLimit."
    ::= { vRtrMplsP2mpInstEntry 9 }

vRtrMplsP2mpInstHoldPriority     OBJECT-TYPE
    SYNTAX      Unsigned32 (0..7)
    MAX-ACCESS  read-only
    STATUS      current
    DESCRIPTION
        "The value of vRtrMplsP2mpInstHoldPriority indicates the hold
         priority to use when insufficient bandwidth is available to setup
         a P2MP LSP.  The setup priority is compared against the hold priority
         of existing LSPs.  If the setup priority is higher than the hold
         priority of the established LSPs, this P2MP LSP may preempt the other
         LSPs.  A value of zero (0) is the highest priority and a value
         of seven (7) is the lowest priority.

         When the vRtrMplsP2mpInstHopLimit bit in vRtrMplsP2mpInstInheritance
         is cleared (0), the value returned to a GET request is inherited from
         vRtrMplsLspHopLimit."
    ::= { vRtrMplsP2mpInstEntry 10 }

vRtrMplsP2mpInstRecord           OBJECT-TYPE
    SYNTAX      TruthValue
    MAX-ACCESS  read-create
    STATUS      current
    DESCRIPTION
        "The value of vRtrMplsP2mpInstRecord specifies whether recording of all
         hops that a P2MP LSP traverses is enabled. When the value of
         vRtrMplsP2mpInstRecord is 'true', recording of all the hops that a
         P2MP LSP traverses is enabled.

         When the value of vRtrMplsP2mpInstRecord is 'false, recording of all
         the hops that a P2MP LSP traverses is disabled."
    DEFVAL      { true }
    ::= { vRtrMplsP2mpInstEntry 11 }

vRtrMplsP2mpInstHopLimit         OBJECT-TYPE
    SYNTAX      Unsigned32 (2..255)
    MAX-ACCESS  read-create
    STATUS      current
    DESCRIPTION
        "The value of vRtrMplsP2mpInstHopLimit specifies the maximum number
         of hops that a P2MP LSP will traverse including the ingress and
         egress ESRs.  A P2MP LSP will not be setup if the hop limit is
         exceeded.

         When the vRtrMplsP2mpInstHopLimit bit in vRtrMplsP2mpInstInheritance
         is cleared (0), the value returned to a GET request is inherited from
         vRtrMplsLspHopLimit."
    DEFVAL      { 255 }
    ::= { vRtrMplsP2mpInstEntry 12 }

vRtrMplsP2mpInstAdminState       OBJECT-TYPE
    SYNTAX      TmnxAdminState
    MAX-ACCESS  read-create
    STATUS      current
    DESCRIPTION
        "The value of vRtrMplsP2mpInstAdminState specifies desired
         administrative state for this P2MP LSP."
    DEFVAL      { inService }
    ::= { vRtrMplsP2mpInstEntry 13 }

vRtrMplsP2mpInstOperState        OBJECT-TYPE
    SYNTAX      TmnxOperState
    MAX-ACCESS  read-only
    STATUS      current
    DESCRIPTION
        "The value of vRtrMplsP2mpInstOperState indicates the current
         operational state of this P2MP LSP."
    ::= { vRtrMplsP2mpInstEntry 14 }

vRtrMplsP2mpInstInheritance      OBJECT-TYPE
    SYNTAX      Unsigned32
    MAX-ACCESS  read-create
    STATUS      current
    DESCRIPTION
        "The value of vRtrMplsP2mpInstInheritance specifies whether or not
         each writable object in this row inherits its value from its
         corresponding object in the vRtrMplsLspTable.  This object controls
         whether to inherit the operational value of that associated object,
         or use the administrative value configured in this row.

         Non mask bits will always have value of zero, and any attempt to
         change the value will be silently discarded.

         This object is a bit-mask, with the following positions:

         vRtrMplsP2mpInstHopLimit              0x40
         vRtrMplsP2mpInstAdminGrpInclude       0x200
         vRtrMplsP2mpInstAdminGrpExclude       0x400
         vRtrMplsP2mpInstAdaptive              0x800

         When the bit for an object is set to one, then the object's
         administrative and operational value are whatever the DEFVAL or most
         recently SET value is. The corresponding mask bit will be changed to
         one when SNMP SET is performed on any of the inherited objects
         (vRtrMplsP2mpInstHopLimit, vRtrMplsP2mpInstAdminGrpInclude, etc).

         When the bit for an object is set to zero, then the object's
         administrative and operational value are inherited from the
         corresponding object in vRtrMplsLspTable."
    DEFVAL      { 0 }
    ::= { vRtrMplsP2mpInstEntry 15 }

vRtrMplsP2mpInstLspId            OBJECT-TYPE
    SYNTAX      MplsLSPID
    MAX-ACCESS  read-only
    STATUS      current
    DESCRIPTION
        "The value of vRtrMplsP2mpInstLspId indicates the value which
         identifies the label switched path that is signaled for this entry."
    ::= { vRtrMplsP2mpInstEntry 16 }

vRtrMplsP2mpInstNegotiatedMTU    OBJECT-TYPE
    SYNTAX      Unsigned32
    MAX-ACCESS  read-only
    STATUS      current
    DESCRIPTION
        "The value of vRtrMplsP2mpInstNegotiatedMTU indicates the size for the
         Maximum transmission unit (MTU) that is negotiated during
         establishment of this P2MP LSP path."
    ::= { vRtrMplsP2mpInstEntry 17 }

vRtrMplsP2mpInstFailCode         OBJECT-TYPE
    SYNTAX      TmnxMplsLspFailCode
    MAX-ACCESS  read-only
    STATUS      current
    DESCRIPTION
        "The value of vRtrMplsP2mpInstFailCode indicates the reason code for
         P2MP LSP Path failure. A value of 0 indicates that no failure has
         occurred."
    ::= { vRtrMplsP2mpInstEntry 18 }

vRtrMplsP2mpInstFailNodeArType   OBJECT-TYPE
    SYNTAX      InetAddressType
    MAX-ACCESS  read-only
    STATUS      current
    DESCRIPTION
        "The value of vRtrMplsP2mpInstFailNodeArType indicates the type of
         vRtrMplsP2mpInstFailNodeAddr.  When no failure has occurred,
         vRtrMplsP2mpInstFailNodeArType is 0."
    ::= { vRtrMplsP2mpInstEntry 19 }

vRtrMplsP2mpInstFailNodeAddr     OBJECT-TYPE
    SYNTAX      InetAddress (SIZE (0|4))
    MAX-ACCESS  read-only
    STATUS      current
    DESCRIPTION
        "The value of vRtrMplsP2mpInstFailNodeAddr indicates the IP address of
         the node in the P2MP LSP path at which the P2MP LSP path failed."
    ::= { vRtrMplsP2mpInstEntry 20 }

vRtrMplsP2mpInstAdminGrpInclude  OBJECT-TYPE
    SYNTAX      Unsigned32
    MAX-ACCESS  read-create
    STATUS      current
    DESCRIPTION
        "The value of vRtrMplsP2mpInstAdminGrpInclude is a bit-map that
         specifies a list of admin groups that should be included when this
         P2MP LSP is setup. If bit 'n' is set, then the admin group with value
         'n' is included for this P2MP LSP. This implies that each link that
         this P2MP LSP goes through must be associated with at least one of the
         admin groups in the include list.

         By default, all admin groups are in the include list."
    DEFVAL      { '00000000'H }
    ::= { vRtrMplsP2mpInstEntry 21 }

vRtrMplsP2mpInstAdminGrpExclude  OBJECT-TYPE
    SYNTAX      Unsigned32
    MAX-ACCESS  read-create
    STATUS      current
    DESCRIPTION
        "The value of vRtrMplsP2mpInstAdminGrpExclude is a bit-map that
         specifies a list of admin groups that should be excluded when this
         P2MP LSP is setup. If bit 'n' is set, then the admin group with value
         'n' is excluded for this P2MP LSP. This implies that each link that
         this P2MP LSP goes through must not be associated with any of the
         admin groups in the exclude list.

         By default, no admin groups are in the exclude list."
    DEFVAL      { '00000000'H }
    ::= { vRtrMplsP2mpInstEntry 22 }

vRtrMplsP2mpInstAdaptive         OBJECT-TYPE
    SYNTAX      TruthValue
    MAX-ACCESS  read-create
    STATUS      current
    DESCRIPTION
        "The value of vRtrMplsP2mpInstAdaptive specifies whether
         make-before-break functionality is enabled. If the value of
         vRtrMplsP2mpInstAdaptive is set to 'true', it enables
         make-before-break functionality for the P2MP LSP.

         When the attributes of an already established P2MP LSP are changed,
         either through manual configuration or due to a change in network
         topology, make-before-break functionality ensures that the resources
         of the existing P2MP LSP will not be released until a new path (with
         the same P2MP LSP Id) has been established and traffic flowing over
         the existing path is seamlessly transferred to the new path.

         If the value of vRtrMplsP2mpInstAdaptive is set to 'false', it
         disables make-before-break functionality."
    DEFVAL      { true }
    ::= { vRtrMplsP2mpInstEntry 23 }

vRtrMplsP2mpInstOperBandwidth    OBJECT-TYPE
    SYNTAX      Integer32
    UNITS       "megabps"
    MAX-ACCESS  read-only
    STATUS      current
    DESCRIPTION
        "The value of vRtrMplsP2mpInstOperBandwidth indicates the amount of
         bandwidth in megabits per seconds (Mbps) that has been reserved for
         the operational P2MP LSP path.

         When make-before-break functionality for the P2MP LSP is enabled and
         if the path bandwidth is changed, the resources allocated to the
         existing P2MP LSP paths will not be released until a new path with the
         new bandwidth settings has been established. While a new path is being
         signaled, the administrative value and the operational values of the
         path bandwidth may differ. The value of vRtrMplsP2mpInstBandwidth
         specifies the bandwidth requirements for the new P2MP LSP path trying
         to be established whereas the value of vRtrMplsP2mpInstOperBandwidth
         specifies the bandwidth reserved for the existing P2MP LSP path."
    ::= { vRtrMplsP2mpInstEntry 24 }

vRtrMplsP2mpInstResignal         OBJECT-TYPE
    SYNTAX      TmnxActionType
    MAX-ACCESS  read-create
    STATUS      current
    DESCRIPTION
        "Setting the value of vRtrMplsP2mpInstResignal to 'doAction' triggers
         the resignaling of the P2MP LSP path.

         If the P2MP LSP path is operationally down either due to network
         failure or due to the retry attempts count being exceeded, setting
         this variable to 'doAction' will initiate the signaling for the path.
         A make-before-break signaling for the path will be initiated if the
         P2MP LSP is operationally up but the make-before-break retry attempts
         count was exceeded. Make-before-break signaling will also be initiated
         for any P2MP LSP that is operationally up. This may be used to cause a
         loose-hop P2MP LSP to be optimized.

         If a resignal is triggered while a resignaling is already in progress,
         the old transient state will be destroyed and a new transaction being
         triggered.

         An SNMP GET request on this object should return 'notApplicable'."
    DEFVAL      { notApplicable }
    ::= { vRtrMplsP2mpInstEntry 25 }

vRtrMplsP2mpInstOperMTU          OBJECT-TYPE
    SYNTAX      Unsigned32
    MAX-ACCESS  read-only
    STATUS      current
    DESCRIPTION
        "The value of vRtrMplsP2mpInstOperMTU indicates the size for the
         Maximum transmission unit (MTU) that is currently in operation for
         this P2MP LSP Path."
    ::= { vRtrMplsP2mpInstEntry 26 }

vRtrMplsP2mpInstRecordLabel      OBJECT-TYPE
    SYNTAX      INTEGER {
        record   (1),
        noRecord (2)
    }
    MAX-ACCESS  read-create
    STATUS      current
    DESCRIPTION
        "The value of vRtrMplsP2mpInstRecordLabel specifies when the value of
         vRtrMplsP2mpInstRecordLabel is 'record', recording of labels at each
         node that a P2MP LSP traverses is enabled.

         When the value of vRtrMplsP2mpInstRecordLabel is 'noRecord', recording
         of labels at each node that a P2MP LSP traverses is disabled."
    DEFVAL      { record }
    ::= { vRtrMplsP2mpInstEntry 27 }

vRtrMplsP2mpInstLastResigAttpt   OBJECT-TYPE
    SYNTAX      TimeStamp
    MAX-ACCESS  read-only
    STATUS      current
    DESCRIPTION
        "The value of vRtrMplsP2mpInstLastResigAttpt indicates the sysUpTime
         when the last attempt to resignal this P2MP LSP was made."
    ::= { vRtrMplsP2mpInstEntry 28 }

vRtrMplsP2mpInstMetric           OBJECT-TYPE
    SYNTAX      Unsigned32
    MAX-ACCESS  read-only
    STATUS      current
    DESCRIPTION
        "The value of vRtrMplsP2mpInstMetric indicates the cost of the traffic
         engineered path returned by the IGP."
    ::= { vRtrMplsP2mpInstEntry 29 }

vRtrMplsP2mpInstLastMBBType      OBJECT-TYPE
    SYNTAX      TmnxMplsMBBType
    MAX-ACCESS  read-only
    STATUS      current
    DESCRIPTION
        "The value of vRtrMplsP2mpInstLastMBBType indicates the type of
         last Make-before-break (MBB).  If 'none', then no MBB has been
         attempted."
    ::= { vRtrMplsP2mpInstEntry 30 }

vRtrMplsP2mpInstLastMBBEnd       OBJECT-TYPE
    SYNTAX      TimeStamp
    MAX-ACCESS  read-only
    STATUS      current
    DESCRIPTION
        "The value of vRtrMplsP2mpInstLastMBBEnd indicates the sysUpTime when
         the last MBB ended."
    ::= { vRtrMplsP2mpInstEntry 31 }

vRtrMplsP2mpInstLastMBBMetric    OBJECT-TYPE
    SYNTAX      Unsigned32
    MAX-ACCESS  read-only
    STATUS      current
    DESCRIPTION
        "The value of vRtrMplsP2mpInstLastMBBMetric  indicates  the
         cost of the traffic engineered path for the P2MP LSP path prior to
         MBB."
    ::= { vRtrMplsP2mpInstEntry 32 }

vRtrMplsP2mpInstLastMBBState     OBJECT-TYPE
    SYNTAX      INTEGER {
        none    (1),
        success (2),
        fail    (3)
    }
    MAX-ACCESS  read-only
    STATUS      current
    DESCRIPTION
        "The value of vRtrMplsP2mpInstLastMBBState indicates whether the last
         Make-before-break was successful or failed.
         Possible states are:
         none (1)        - no make-before-break invoked
         success (2)     - make-before-break successful
         fail (3)        - make-before-break failed."
    ::= { vRtrMplsP2mpInstEntry 33 }

vRtrMplsP2mpInstMBBTypeInProg    OBJECT-TYPE
    SYNTAX      TmnxMplsMBBType
    MAX-ACCESS  read-only
    STATUS      current
    DESCRIPTION
        "The value of vRtrMplsP2mpInstMBBTypeInProg indicates the type of the
         Make-before-break (MBB) that is in progress. If 'none', then no MBB is
         in progress."
    ::= { vRtrMplsP2mpInstEntry 34 }

vRtrMplsP2mpInstMBBStarted       OBJECT-TYPE
    SYNTAX      TimeStamp
    MAX-ACCESS  read-only
    STATUS      current
    DESCRIPTION
        "The value of vRtrMplsP2mpInstMBBStarted indicates the sysUpTime when
         the in-progress MBB started."
    ::= { vRtrMplsP2mpInstEntry 35 }

vRtrMplsP2mpInstMBBNextRetry     OBJECT-TYPE
    SYNTAX      Unsigned32
    UNITS       "seconds"
    MAX-ACCESS  read-only
    STATUS      current
    DESCRIPTION
        "The value of vRtrMplsP2mpInstMBBNextRetry indicates the amount of time
         remaining in seconds before the next attempt is made to retry the
         in-progress MBB."
    ::= { vRtrMplsP2mpInstEntry 36 }

vRtrMplsP2mpInstMBBRetryAttpts   OBJECT-TYPE
    SYNTAX      Unsigned32
    MAX-ACCESS  read-only
    STATUS      current
    DESCRIPTION
        "The value of vRtrMplsP2mpInstMBBRetryAttpts indicates 'n' where nth
         attempt for the MBB is in progress."
    ::= { vRtrMplsP2mpInstEntry 37 }

vRtrMplsP2mpInstMBBFailCode      OBJECT-TYPE
    SYNTAX      TmnxMplsLspFailCode
    MAX-ACCESS  read-only
    STATUS      current
    DESCRIPTION
        "The value of vRtrMplsP2mpInstMBBFailCode indicates the reason code for
         in-progress MBB failure. A value of 'none' indicates that no failure
         has occurred."
    ::= { vRtrMplsP2mpInstEntry 38 }

vRtrMplsP2mpInstMBBFailNodeType  OBJECT-TYPE
    SYNTAX      InetAddressType
    MAX-ACCESS  read-only
    STATUS      current
    DESCRIPTION
        "The value of vRtrMplsP2mpInstMBBFailNodeType indicates the type of
         vRtrMplsP2mpInstMBBFailNodeAddr. A value of 'unknown' indicates that
         no failure has occurred."
    ::= { vRtrMplsP2mpInstEntry 39 }

vRtrMplsP2mpInstMBBFailNodeAddr  OBJECT-TYPE
    SYNTAX      InetAddress (SIZE (0|4))
    MAX-ACCESS  read-only
    STATUS      current
    DESCRIPTION
        "The value of vRtrMplsP2mpInstMBBFailNodeAddr indicates the IP address
         of the node in the P2MP LSP path at which the in-progress MBB failed.
         A value of 'unknown' for vRtrMplsP2mpInstMBBFailNodeType and empty
         string for vRtrMplsP2mpInstMBBFailNodeAddr indicates that no failure
         has occurred."
    ::= { vRtrMplsP2mpInstEntry 40 }

vRtrMplsP2mpInstStatTable        OBJECT-TYPE
    SYNTAX      SEQUENCE OF VRtrMplsP2mpInstStatEntry
    MAX-ACCESS  not-accessible
    STATUS      current
    DESCRIPTION
        "The vRtrMplsP2mpInstStatTable has an entry for each Labeled Switch
         Path (LSP) configured for a virtual router in the system."
    ::= { tmnxMplsObjs 26 }

vRtrMplsP2mpInstStatEntry        OBJECT-TYPE
    SYNTAX      VRtrMplsP2mpInstStatEntry
    MAX-ACCESS  not-accessible
    STATUS      current
    DESCRIPTION
        "Each row entry represents a collection of statistics for a P2MP
         Labeled Switch Path (LSP) configured for a virtual router in the
         system.

         Entries cannot be created and deleted via SNMP SET operations."
    AUGMENTS    { vRtrMplsP2mpInstEntry }
    ::= { vRtrMplsP2mpInstStatTable 1 }

VRtrMplsP2mpInstStatEntry        ::= SEQUENCE
{
    vRtrMplsP2mpInstStatS2lChanges   Counter32,
    vRtrMplsP2mpInstStatLastS2lChange TimeInterval,
    vRtrMplsP2mpInstStatConfiguredS2ls Gauge32,
    vRtrMplsP2mpInstStatOperationalS2ls Gauge32,
    vRtrMplsP2mpInstStatLastS2lTimeUp TimeInterval,
    vRtrMplsP2mpInstStatLastS2lTimeDown TimeInterval,
    vRtrMplsP2mpInstStatTimeUp       TimeInterval,
    vRtrMplsP2mpInstStatTimeDown     TimeInterval,
    vRtrMplsP2mpInstStatTransitions  Counter32,
    vRtrMplsP2mpInstStatLastTrans    TimeInterval
}

vRtrMplsP2mpInstStatS2lChanges   OBJECT-TYPE
    SYNTAX      Counter32
    MAX-ACCESS  read-only
    STATUS      current
    DESCRIPTION
        "The value of vRtrMplsP2mpInstStatS2lChanges indicates the number of
         S2l changes this P2MP LSP has had. For every S2l change (S2l down, S2l
         up, S2l change), a corresponding syslog/trap (if enabled) is generated
         for it."
    ::= { vRtrMplsP2mpInstStatEntry 1 }

vRtrMplsP2mpInstStatLastS2lChange OBJECT-TYPE
    SYNTAX      TimeInterval
    UNITS       "centiseconds"
    MAX-ACCESS  read-only
    STATUS      current
    DESCRIPTION
        "The value of vRtrMplsP2mpInstStatLastS2lChange indicates the time
         since the last change occurred on this P2MP LSP."
    ::= { vRtrMplsP2mpInstStatEntry 2 }

vRtrMplsP2mpInstStatConfiguredS2ls OBJECT-TYPE
    SYNTAX      Gauge32
    MAX-ACCESS  read-only
    STATUS      current
    DESCRIPTION
        "The value of vRtrMplsP2mpInstStatConfiguredS2ls indicates the number
         of S2ls configured for this P2MP LSP."
    ::= { vRtrMplsP2mpInstStatEntry 3 }

vRtrMplsP2mpInstStatOperationalS2ls OBJECT-TYPE
    SYNTAX      Gauge32
    MAX-ACCESS  read-only
    STATUS      current
    DESCRIPTION
        "The value of vRtrMplsP2mpInstStatOperationalS2ls indicates the number
         of operational S2ls for this P2MP LSP. This includes the S2ls
         currently active."
    ::= { vRtrMplsP2mpInstStatEntry 4 }

vRtrMplsP2mpInstStatLastS2lTimeUp OBJECT-TYPE
    SYNTAX      TimeInterval
    UNITS       "centiseconds"
    MAX-ACCESS  read-only
    STATUS      current
    DESCRIPTION
        "The value of vRtrMplsP2mpInstStatLastS2lTimeUp indicates the total
         time that this S2l has been operational."
    ::= { vRtrMplsP2mpInstStatEntry 5 }

vRtrMplsP2mpInstStatLastS2lTimeDown OBJECT-TYPE
    SYNTAX      TimeInterval
    MAX-ACCESS  read-only
    STATUS      current
    DESCRIPTION
        "The value of vRtrMplsP2mpInstStatLastS2lTimeDown indicates the total
         time that this S2l has not been operational."
    ::= { vRtrMplsP2mpInstStatEntry 6 }

vRtrMplsP2mpInstStatTimeUp       OBJECT-TYPE
    SYNTAX      TimeInterval
    UNITS       "centiseconds"
    MAX-ACCESS  read-only
    STATUS      current
    DESCRIPTION
        "The value of vRtrMplsP2mpInstStatTimeUp indicates the total time that
         this P2MP instance has been operational."
    ::= { vRtrMplsP2mpInstStatEntry 7 }

vRtrMplsP2mpInstStatTimeDown     OBJECT-TYPE
    SYNTAX      TimeInterval
    MAX-ACCESS  read-only
    STATUS      current
    DESCRIPTION
        "The value of vRtrMplsP2mpInstStatTimeDown indicates the total time
         that this P2MP instance has not been operational."
    ::= { vRtrMplsP2mpInstStatEntry 8 }

vRtrMplsP2mpInstStatTransitions  OBJECT-TYPE
    SYNTAX      Counter32
    MAX-ACCESS  read-only
    STATUS      current
    DESCRIPTION
        "The The value of vRtrMplsP2mpInstStatTransitions indicates the number
         of state transitions (up -> down and down -> up) this P2mp instance
         has undergone."
    ::= { vRtrMplsP2mpInstStatEntry 9 }

vRtrMplsP2mpInstStatLastTrans    OBJECT-TYPE
    SYNTAX      TimeInterval
    UNITS       "ten-milliseconds"
    MAX-ACCESS  read-only
    STATUS      current
    DESCRIPTION
        "The value of vRtrMplsP2mpInstStatLastTrans indicates the time since
         the last transition occurred on this P2mp instance."
    ::= { vRtrMplsP2mpInstStatEntry 10 }

vRtrMplsS2lSubLspTblLastChanged  OBJECT-TYPE
    SYNTAX      TimeStamp
    MAX-ACCESS  read-only
    STATUS      current
    DESCRIPTION
        "The value of vRtrMplsS2lSubLspTblLastChanged indicates the sysUpTime
         at the time of the last modification to vRtrMplsS2lSubLspTable by
         adding, deleting an entry or change to a writable object in the table.

         If no changes were made to the table since the last re-initialization
         of the local network management subsystem, then this object contains a
         zero value."
    ::= { tmnxMplsObjs 27 }

vRtrMplsS2lSubLspTable           OBJECT-TYPE
    SYNTAX      SEQUENCE OF VRtrMplsS2lSubLspEntry
    MAX-ACCESS  not-accessible
    STATUS      current
    DESCRIPTION
        "The vRtrMplsS2lSubLspTable provides an association between an P2MP LSP
         and a source to leaf (S2L) sub LSP path called as S2L here. A P2MP LSP
         can have more than one S2L sub LSP association."
    ::= { tmnxMplsObjs 28 }

vRtrMplsS2lSubLspEntry           OBJECT-TYPE
    SYNTAX      VRtrMplsS2lSubLspEntry
    MAX-ACCESS  not-accessible
    STATUS      current
    DESCRIPTION
        "Each row entry represents an association between a Labeled Switch
         Path (P2MP LSP) in the vRtrMplsP2mpInstTable and a S2L sub LSP entry in
         the vRtrMplsS2lSubLspTable.  Entries in this table can be created and
         deleted via SNMP SET operations.  Setting RowStatus to 'active'
         requires vRtrMplsS2lSubLspType to have been assigned a valid value."
    INDEX       {
        vRtrID,
        vRtrMplsLspIndex,
        vRtrMplsP2mpInstIndex,
        mplsTunnelIndex,
        mplsTunnelInstance,
        mplsTunnelIngressLSRId,
        vRtrMplsS2lSubLspDstAddrType,
        vRtrMplsS2lSubLspDstAddr
    }
    ::= { vRtrMplsS2lSubLspTable 1 }

VRtrMplsS2lSubLspEntry           ::= SEQUENCE
{
    vRtrMplsS2lSubLspDstAddrType     InetAddressType,
    vRtrMplsS2lSubLspDstAddr         InetAddress,
    vRtrMplsS2lSubLspRowStatus       RowStatus,
    vRtrMplsS2lSubLspLastChange      TimeStamp,
    vRtrMplsS2lSubLspType            INTEGER,
    vRtrMplsS2lSubLspProperties      BITS,
    vRtrMplsS2lSubLspState           INTEGER,
    vRtrMplsS2lSubLspAdminState      TmnxAdminState,
    vRtrMplsS2lSubLspOperState       TmnxOperState,
    vRtrMplsS2lSubGroupId            Unsigned32,
    vRtrMplsS2lSubLspId              MplsLSPID,
    vRtrMplsS2lSubLspRetryTimeRemain Unsigned32,
    vRtrMplsS2lSubLspTunARHopLtIndex Integer32,
    vRtrMplsS2lSubLspNegotiatedMTU   Unsigned32,
    vRtrMplsS2lSubLspFailCode        TmnxMplsLspFailCode,
    vRtrMplsS2lSubLspFailNodeArType  InetAddressType,
    vRtrMplsS2lSubLspFailNodeAddr    InetAddress,
    vRtrMplsS2lSubLspOperBandwidth   Integer32,
    vRtrMplsS2lSubLspTunCRHopLtIndex Integer32,
    vRtrMplsS2lSubLspOperMTU         Unsigned32,
    vRtrMplsS2lSubLspLastResigAttpt  TimeStamp,
    vRtrMplsS2lSubLspLastMBBType     TmnxMplsMBBType,
    vRtrMplsS2lSubLspLastMBBEnd      TimeStamp,
    vRtrMplsS2lSubLspLastMBBMetric   Unsigned32,
    vRtrMplsS2lSubLspLastMBBState    INTEGER,
    vRtrMplsS2lSubLspMBBTypeInProg   TmnxMplsMBBType,
    vRtrMplsS2lSubLspMBBStarted      TimeStamp,
    vRtrMplsS2lSubLspMBBNextRetry    Unsigned32,
    vRtrMplsS2lSubLspMBBRetryAttpts  Unsigned32,
    vRtrMplsS2lSubLspMBBFailCode     TmnxMplsLspFailCode,
    vRtrMplsS2lSubLspMBBFailNodeType InetAddressType,
    vRtrMplsS2lSubLspMBBFailNodeAddr InetAddress,
    vRtrMplsS2lSubLspUpTime          TimeStamp,
    vRtrMplsS2lSubLspDownTime        TimeStamp,
    vRtrMplsS2lSubLspIsFastRetry     TruthValue,
    vRtrMplsS2lSubLspTimeoutIn       Unsigned32,
    vRtrMplsS2lSubLspMBBTimeoutIn    Unsigned32,
    vRtrMplsS2lSubLspInterArea       TruthValue
}

vRtrMplsS2lSubLspDstAddrType     OBJECT-TYPE
    SYNTAX      InetAddressType
    MAX-ACCESS  not-accessible
    STATUS      current
    DESCRIPTION
        "The value of vRtrMplsS2lSubLspDstAddrType indicates the type of
         vRtrMplsS2lSubLspDstAddr."
    ::= { vRtrMplsS2lSubLspEntry 1 }

vRtrMplsS2lSubLspDstAddr         OBJECT-TYPE
    SYNTAX      InetAddress (SIZE (0|4))
    MAX-ACCESS  not-accessible
    STATUS      current
    DESCRIPTION
        "The value of vRtrMplsS2lSubLspDstAddr indicates the IP address of the
         destination address of the S2L sub LSP. "
    ::= { vRtrMplsS2lSubLspEntry 2 }

vRtrMplsS2lSubLspRowStatus       OBJECT-TYPE
    SYNTAX      RowStatus
    MAX-ACCESS  read-create
    STATUS      current
    DESCRIPTION
        "The value of vRtrMplsS2lSubLspRowStatus specifies row status used for
         creation, deletion, or control of vRtrMplsLspPathTable entries.  Before
         the row can be placed into the 'active' state vRtrMplsS2lSubLspType must
         have been assigned a valid value."
    ::= { vRtrMplsS2lSubLspEntry 3 }

vRtrMplsS2lSubLspLastChange      OBJECT-TYPE
    SYNTAX      TimeStamp
    MAX-ACCESS  read-only
    STATUS      current
    DESCRIPTION
        "The value of vRtrMplsS2lSubLspLastChange indicates the sysUpTime when
         this row was last modified."
    ::= { vRtrMplsS2lSubLspEntry 4 }

vRtrMplsS2lSubLspType            OBJECT-TYPE
    SYNTAX      INTEGER {
        s2lPath (1)
    }
    MAX-ACCESS  read-only
    STATUS      current
    DESCRIPTION
        "The value of vRtrMplsS2lSubLspType indicates the value that represents
         the role this S2L sub LSP is taking within this P2MP LSP."
    ::= { vRtrMplsS2lSubLspEntry 5 }

vRtrMplsS2lSubLspProperties      OBJECT-TYPE
    SYNTAX      BITS {
        recordRoute (0),
        adaptive    (1),
        cspf        (2),
        mergeable   (3),
        fastReroute (4)
    }
    MAX-ACCESS  read-only
    STATUS      current
    DESCRIPTION
        "The value of vRtrMplsS2lSubLspProperties indicates the set of
         configured properties.  For example, if the S2L sub LSP is an adaptive
         S2L sub LSP, the bit corresponding to bit value 1 is set."
    ::= { vRtrMplsS2lSubLspEntry 6 }

vRtrMplsS2lSubLspState           OBJECT-TYPE
    SYNTAX      INTEGER {
        unknown  (1),
        active   (2),
        inactive (3)
    }
    MAX-ACCESS  read-only
    STATUS      current
    DESCRIPTION
        "The value of vRtrMplsS2lSubLspState indicates the  current working
         state of this S2L sub LSP within this LSP."
    DEFVAL      { unknown }
    ::= { vRtrMplsS2lSubLspEntry 7 }

vRtrMplsS2lSubLspAdminState      OBJECT-TYPE
    SYNTAX      TmnxAdminState
    MAX-ACCESS  read-create
    STATUS      current
    DESCRIPTION
        "The value of vRtrMplsS2lSubLspAdminState specifies the desired
         administrative state for this P2MP S2L sub LSP."
    DEFVAL      { inService }
    ::= { vRtrMplsS2lSubLspEntry 8 }

vRtrMplsS2lSubLspOperState       OBJECT-TYPE
    SYNTAX      TmnxOperState
    MAX-ACCESS  read-only
    STATUS      current
    DESCRIPTION
        "The value of vRtrMplsS2lSubLspOperState indicates the current
         operational state of this P2MP S2L sub LSP."
    ::= { vRtrMplsS2lSubLspEntry 9 }

vRtrMplsS2lSubGroupId            OBJECT-TYPE
    SYNTAX      Unsigned32
    MAX-ACCESS  read-only
    STATUS      current
    DESCRIPTION
        "The value of vRtrMplsS2lSubGroupId indicates the value which
         identifies the group for this entry."
    ::= { vRtrMplsS2lSubLspEntry 10 }

vRtrMplsS2lSubLspId              OBJECT-TYPE
    SYNTAX      MplsLSPID
    MAX-ACCESS  read-only
    STATUS      current
    DESCRIPTION
        "The value of vRtrMplsS2lSubLspId indicates the value which identifies
         the label switched path that is signaled for this entry."
    ::= { vRtrMplsS2lSubLspEntry 11 }

vRtrMplsS2lSubLspRetryTimeRemain OBJECT-TYPE
    SYNTAX      Unsigned32
    UNITS       "centiseconds"
    MAX-ACCESS  read-only
    STATUS      current
    DESCRIPTION
        "The value of vRtrMplsS2lSubLspRetryTimeRemain indicates the time to
         signal this S2L sub LSP."
    ::= { vRtrMplsS2lSubLspEntry 12 }

vRtrMplsS2lSubLspTunARHopLtIndex OBJECT-TYPE
    SYNTAX      Integer32 (0 | 1..2147483647)
    MAX-ACCESS  read-only
    STATUS      current
    DESCRIPTION
        "The value of vRtrMplsS2lSubLspTunARHopLtIndex indicates Primary index
         into the mplsTunnelARHopTable identifying a particular recorded hop
         list. A value of 0 implies that there is no recorded hop list
         associated with this P2MP LSP path."
    ::= { vRtrMplsS2lSubLspEntry 13 }

vRtrMplsS2lSubLspNegotiatedMTU   OBJECT-TYPE
    SYNTAX      Unsigned32
    MAX-ACCESS  read-only
    STATUS      current
    DESCRIPTION
        "The value of vRtrMplsS2lSubLspNegotiatedMTU indicates the size for the
         Maximum transmission unit (MTU) that is negotiated during
         establishment of this P2MP LSP Path."
    DEFVAL      { 0 }
    ::= { vRtrMplsS2lSubLspEntry 14 }

vRtrMplsS2lSubLspFailCode        OBJECT-TYPE
    SYNTAX      TmnxMplsLspFailCode
    MAX-ACCESS  read-only
    STATUS      current
    DESCRIPTION
        "The value of vRtrMplsS2lSubLspFailCode indicates the reason code for
         P2MP LSP Path failure. A value of 0 indicates that no failure has
         occurred."
    ::= { vRtrMplsS2lSubLspEntry 15 }

vRtrMplsS2lSubLspFailNodeArType  OBJECT-TYPE
    SYNTAX      InetAddressType
    MAX-ACCESS  read-only
    STATUS      current
    DESCRIPTION
        "The value of vRtrMplsS2lSubLspFailNodeArType indicates type of
         vRtrMplsS2lSubLspFailNodeAddr. When no failure has occurred, this
         value is 0."
    ::= { vRtrMplsS2lSubLspEntry 16 }

vRtrMplsS2lSubLspFailNodeAddr    OBJECT-TYPE
    SYNTAX      InetAddress (SIZE (0|4))
    MAX-ACCESS  read-only
    STATUS      current
    DESCRIPTION
        "The value of vRtrMplsS2lSubLspFailNodeAddr indicates the IP address of
         the node in the P2MP S2L sub LSP at which the P2MP S2L sub LSP failed."
    ::= { vRtrMplsS2lSubLspEntry 17 }

vRtrMplsS2lSubLspOperBandwidth   OBJECT-TYPE
    SYNTAX      Integer32
    UNITS       "megabps"
    MAX-ACCESS  read-only
    STATUS      current
    DESCRIPTION
        "The value of vRtrMplsS2lSubLspOperBandwidth indicates the amount of
         bandwidth in megabits per seconds (Mbps) that has been reserved for
         the operational P2MP S2L sub LSP.

         When make-before-break functionality for the P2MP LSP is enabled and
         if the S2L sub LSP bandwidth is changed, the resources allocated to
         the existing P2MP LSP paths will not be released until a new S2L sub
         LSP with the new bandwidth settings has been established. While a new
         S2L sub LSP is being signaled, the administrative value and the
         operational values of the S2L sub LSP bandwidth may differ. The value
         of vRtrMplsS2lSubLspOperBandwidth specifies the bandwidth requirements
         for the new P2MP S2L sub LSP trying to be established whereas the
         value of vRtrMplsS2lSubLspOperBandwidth specifies the bandwidth
         reserved for the existing P2MP S2L sub LSP."
    ::= { vRtrMplsS2lSubLspEntry 18 }

vRtrMplsS2lSubLspTunCRHopLtIndex OBJECT-TYPE
    SYNTAX      Integer32 (0 | 1..2147483647)
    MAX-ACCESS  read-only
    STATUS      current
    DESCRIPTION
        "The value of vRtrMplsS2lSubLspTunCRHopLtIndex indicates primary index
         into the vRtrMplsTunnelCHopTable identifying a particular computed hop
         list. A value of 0 implies that there is no computed hop list
         associated with this LSP path."
    ::= { vRtrMplsS2lSubLspEntry 19 }

vRtrMplsS2lSubLspOperMTU         OBJECT-TYPE
    SYNTAX      Unsigned32
    MAX-ACCESS  read-only
    STATUS      current
    DESCRIPTION
        "The value of vRtrMplsS2lSubLspOperMTU indicates the size for the
         Maximum transmission unit (MTU) that is currently operation for this
         P2MP LSP Path."
    ::= { vRtrMplsS2lSubLspEntry 20 }

vRtrMplsS2lSubLspLastResigAttpt  OBJECT-TYPE
    SYNTAX      TimeStamp
    MAX-ACCESS  read-only
    STATUS      current
    DESCRIPTION
        "The value of vRtrMplsS2lSubLspLastResigAttpt indicates the sysUpTime
         when the last attempt to resignal this LSP was made."
    ::= { vRtrMplsS2lSubLspEntry 21 }

vRtrMplsS2lSubLspLastMBBType     OBJECT-TYPE
    SYNTAX      TmnxMplsMBBType
    MAX-ACCESS  read-only
    STATUS      current
    DESCRIPTION
        "The value of vRtrMplsS2lSubLspLastMBBType indicates the type of
         last Make-before-break (MBB).  If 'none', then no MBB has been
         attempted."
    ::= { vRtrMplsS2lSubLspEntry 22 }

vRtrMplsS2lSubLspLastMBBEnd      OBJECT-TYPE
    SYNTAX      TimeStamp
    MAX-ACCESS  read-only
    STATUS      current
    DESCRIPTION
        "The value of vRtrMplsS2lSubLspLastMBBEnd indicates the sysUpTime when
         the last MBB ended."
    ::= { vRtrMplsS2lSubLspEntry 23 }

vRtrMplsS2lSubLspLastMBBMetric   OBJECT-TYPE
    SYNTAX      Unsigned32
    MAX-ACCESS  read-only
    STATUS      current
    DESCRIPTION
        "The value of vRtrMplsS2lSubLspLastMBBMetric  indicates  the
         cost of the traffic engineered S2L sub LSP for the S2L sub LSP
         prior to MBB."
    ::= { vRtrMplsS2lSubLspEntry 24 }

vRtrMplsS2lSubLspLastMBBState    OBJECT-TYPE
    SYNTAX      INTEGER {
        none    (1),
        success (2),
        fail    (3)
    }
    MAX-ACCESS  read-only
    STATUS      current
    DESCRIPTION
        "The value of vRtrMplsS2lSubLspLastMBBState indicates whether the last
         Make-before-break was successful or failed.
         Possible states are:
         none (1)        - no make-before-break invoked
         success (2)     - make-before-break successful
         fail (3)        - make-before-break failed."
    ::= { vRtrMplsS2lSubLspEntry 25 }

vRtrMplsS2lSubLspMBBTypeInProg   OBJECT-TYPE
    SYNTAX      TmnxMplsMBBType
    MAX-ACCESS  read-only
    STATUS      current
    DESCRIPTION
        "The value of vRtrMplsS2lSubLspMBBTypeInProg indicates the type of the
         Make-before-break (MBB) that is in progress. If 'none', then no MBB is
         in progress."
    ::= { vRtrMplsS2lSubLspEntry 26 }

vRtrMplsS2lSubLspMBBStarted      OBJECT-TYPE
    SYNTAX      TimeStamp
    MAX-ACCESS  read-only
    STATUS      current
    DESCRIPTION
        "The value of vRtrMplsS2lSubLspMBBStarted indicates the sysUpTime when
         the in-progress MBB started."
    ::= { vRtrMplsS2lSubLspEntry 27 }

vRtrMplsS2lSubLspMBBNextRetry    OBJECT-TYPE
    SYNTAX      Unsigned32
    UNITS       "seconds"
    MAX-ACCESS  read-only
    STATUS      current
    DESCRIPTION
        "The value of vRtrMplsS2lSubLspMBBNextRetry indicates the amount of
         time remaining in seconds before the next attempt is made to retry the
         in-progress MBB."
    ::= { vRtrMplsS2lSubLspEntry 28 }

vRtrMplsS2lSubLspMBBRetryAttpts  OBJECT-TYPE
    SYNTAX      Unsigned32
    MAX-ACCESS  read-only
    STATUS      current
    DESCRIPTION
        "The value of vRtrMplsS2lSubLspMBBRetryAttpts indicates 'n' where nth
         attempt for the MBB is in progress."
    ::= { vRtrMplsS2lSubLspEntry 29 }

vRtrMplsS2lSubLspMBBFailCode     OBJECT-TYPE
    SYNTAX      TmnxMplsLspFailCode
    MAX-ACCESS  read-only
    STATUS      current
    DESCRIPTION
        "The value of vRtrMplsS2lSubLspMBBFailCode indicates the reason code
         for in-progress MBB failure. A value of 'none' indicates that no
         failure has occurred."
    ::= { vRtrMplsS2lSubLspEntry 30 }

vRtrMplsS2lSubLspMBBFailNodeType OBJECT-TYPE
    SYNTAX      InetAddressType
    MAX-ACCESS  read-only
    STATUS      current
    DESCRIPTION
        "The value of vRtrMplsS2lSubLspMBBFailNodeType indicates the type of
         vRtrMplsS2lSubLspMBBFailNodeAddr. A value of 'unknown' indicates that
         no failure has occurred."
    ::= { vRtrMplsS2lSubLspEntry 31 }

vRtrMplsS2lSubLspMBBFailNodeAddr OBJECT-TYPE
    SYNTAX      InetAddress (SIZE (0|4))
    MAX-ACCESS  read-only
    STATUS      current
    DESCRIPTION
        "The value of vRtrMplsS2lSubLspMBBFailNodeAddr indicates the IP address
         of the node in the S2L sub LSP at which the in-progress MBB failed. A
         value of 'unknown' for vRtrMplsS2lSubLspMBBFailNodeType and empty
         string for vRtrMplsS2lSubLspMBBFailNodeAddr indicates that no failure
         has occurred."
    ::= { vRtrMplsS2lSubLspEntry 32 }

vRtrMplsS2lSubLspUpTime          OBJECT-TYPE
    SYNTAX      TimeStamp
    MAX-ACCESS  read-only
    STATUS      current
    DESCRIPTION
        "The value of vRtrMplsS2lSubLspUpTime indicates the timestamp when the
         S2l came up."
    ::= { vRtrMplsS2lSubLspEntry 33 }

vRtrMplsS2lSubLspDownTime        OBJECT-TYPE
    SYNTAX      TimeStamp
    MAX-ACCESS  read-only
    STATUS      current
    DESCRIPTION
        "The value of vRtrMplsS2lSubLspDownTime indicates the timestamp when
         the S2l went down."
    ::= { vRtrMplsS2lSubLspEntry 34 }

vRtrMplsS2lSubLspIsFastRetry     OBJECT-TYPE
    SYNTAX      TruthValue
    MAX-ACCESS  read-only
    STATUS      current
    DESCRIPTION
        "The value of vRtrMplsS2lSubLspIsFastRetry indicates which retry timer
         is being referred to by vRtrMplsS2lSubLspRetryTimeRemain.

         When the value of vRtrMplsLspPathIsFastRetry is set to 'true',
         vRtrMplsLspPathRetryTimeRemaining is referring to the P2MP S2L path
         fast timer, vRtrMplsGenP2mpS2lFastRetry.

         When the value of vRtrMplsLspPathIsFastRetry is set to 'false',
         vRtrMplsS2lSubLspRetryTimeRemain is referring to the LSP retry timer,
         vRtrMplsLspRetryTimer."
    ::= { vRtrMplsS2lSubLspEntry 35 }

vRtrMplsS2lSubLspTimeoutIn       OBJECT-TYPE
    SYNTAX      Unsigned32
    UNITS       "seconds"
    MAX-ACCESS  read-only
    STATUS      current
    DESCRIPTION
        "The value of vRtrMplsS2lSubLspTimeoutIn indicates the amount of time
         remaining, in seconds, for the S2L path state to time out after the
         initial PATH message has been sent. If the timer expires and the S2L
         path has not become operationally up, the S2L path is torn down and
         the retry timer is started to schedule a new retry cycle."
    ::= { vRtrMplsS2lSubLspEntry 36 }

vRtrMplsS2lSubLspMBBTimeoutIn    OBJECT-TYPE
    SYNTAX      Unsigned32
    UNITS       "seconds"
    MAX-ACCESS  read-only
    STATUS      current
    DESCRIPTION
        "The value of vRtrMplsS2lSubLspMBBTimeoutIn indicates the amount of
         time remaining, in seconds, for the in-progress S2L MBB path state to
         time out after the initial PATH message has been sent. If the timer
         expires and the in-progress S2L MBB path has not become operationally
         up, the S2L MBB path is torn down and the retry timer is started to
         schedule a new retry cycle."
    ::= { vRtrMplsS2lSubLspEntry 37 }

vRtrMplsS2lSubLspInterArea       OBJECT-TYPE
    SYNTAX      TruthValue
    MAX-ACCESS  read-only
    STATUS      current
    DESCRIPTION
        "The value of vRtrMplsS2lSubLspInterArea indicates whether the LSP path
         is either inter-area or intra-area."
    ::= { vRtrMplsS2lSubLspEntry 38 }

vRtrMplsS2lSubLspStatTable       OBJECT-TYPE
    SYNTAX      SEQUENCE OF VRtrMplsS2lSubLspStatEntry
    MAX-ACCESS  not-accessible
    STATUS      current
    DESCRIPTION
        "The vRtrMplsS2lSubLspStatTable has an entry for each Labeled Switch
         Path (LSP) configured for a virtual router in the system."
    ::= { tmnxMplsObjs 29 }

vRtrMplsS2lSubLspStatEntry       OBJECT-TYPE
    SYNTAX      VRtrMplsS2lSubLspStatEntry
    MAX-ACCESS  not-accessible
    STATUS      current
    DESCRIPTION
        "Each row entry represents a collection of statistics for a P2MP Source
         to Leaf (S2L) Sub Labeled Switch Path (LSP) configured for a i virtual
         router in the system.

         Entries cannot be created and deleted via SNMP SET operations."
    AUGMENTS    { vRtrMplsS2lSubLspEntry }
    ::= { vRtrMplsS2lSubLspStatTable 1 }

VRtrMplsS2lSubLspStatEntry       ::= SEQUENCE
{
    vRtrMplsS2lSubLspTimeUp          TimeInterval,
    vRtrMplsS2lSubLspTimeDown        TimeInterval,
    vRtrMplsS2lSubLspRetryAttempts   Counter32,
    vRtrMplsS2lSubLspTransitionCount Counter32,
    vRtrMplsS2lSubLspCspfQueries     Counter32
}

vRtrMplsS2lSubLspTimeUp          OBJECT-TYPE
    SYNTAX      TimeInterval
    UNITS       "centiseconds"
    MAX-ACCESS  read-only
    STATUS      current
    DESCRIPTION
        "The value of vRtrMplsS2lSubLspTimeUp indicates the total time that
         this LSP S2l has been operational.  For example, the percentage up
         time can be determined by computing
         (vRtrMplsS2lSubLspTimeUp/vRtrMplsLspAge * 100 %)."
    ::= { vRtrMplsS2lSubLspStatEntry 1 }

vRtrMplsS2lSubLspTimeDown        OBJECT-TYPE
    SYNTAX      TimeInterval
    UNITS       "centiseconds"
    MAX-ACCESS  read-only
    STATUS      current
    DESCRIPTION
        "The value of vRtrMplsS2lSubLspTimeDown indicates the total time that
         this LSP S2l has not been operational."
    ::= { vRtrMplsS2lSubLspStatEntry 2 }

vRtrMplsS2lSubLspRetryAttempts   OBJECT-TYPE
    SYNTAX      Counter32
    MAX-ACCESS  read-only
    STATUS      current
    DESCRIPTION
        "The value of vRtrMplsS2lSubLspRetryAttempts indicates the number of
         unsuccessful attempts which have been made to signal this S2l. As soon
         as the S2l gets signalled, this is set to 0."
    ::= { vRtrMplsS2lSubLspStatEntry 3 }

vRtrMplsS2lSubLspTransitionCount OBJECT-TYPE
    SYNTAX      Counter32
    MAX-ACCESS  read-only
    STATUS      current
    DESCRIPTION
        "The value of vRtrMplsS2lSubLspTransitionCount indicates the number of
         transitions that have occurred for this LSP."
    ::= { vRtrMplsS2lSubLspStatEntry 4 }

vRtrMplsS2lSubLspCspfQueries     OBJECT-TYPE
    SYNTAX      Counter32
    MAX-ACCESS  read-only
    STATUS      current
    DESCRIPTION
        "The value of vRtrMplsS2lSubLspCspfQueries indicates the number of CSPF
         queries that have been made for this LSP S2l."
    ::= { vRtrMplsS2lSubLspStatEntry 5 }

vRtrMplsSrlgDBRtrIdTblLastChg    OBJECT-TYPE
    SYNTAX      TimeStamp
    MAX-ACCESS  read-only
    STATUS      current
    DESCRIPTION
        "The value of vRtrMplsSrlgDBRtrIdTblLastChg indicates the sysUpTime at
         the time of the last modification to vRtrMplsSrlgDBRtrIdTable by
         adding, deleting an entry or change to a writable object in the table.

         If no changes were made to the table since the last re-initialization
         of the local network management subsystem, then this object contains a
         zero value."
    ::= { tmnxMplsObjs 30 }

vRtrMplsSrlgDBRtrIdTable         OBJECT-TYPE
    SYNTAX      SEQUENCE OF VRtrMplsSrlgDBRtrIdEntry
    MAX-ACCESS  not-accessible
    STATUS      current
    DESCRIPTION
        "The vRtrMplsSrlgDBRtrIdTable has an entry for each router-id
         configured under user Shared Risk Link Group (SRLG) database. The user
          manually enters the SRLG membership information for any link
          in the network, into the user SRLG database."
    ::= { tmnxMplsObjs 31 }

vRtrMplsSrlgDBRtrIdEntry         OBJECT-TYPE
    SYNTAX      VRtrMplsSrlgDBRtrIdEntry
    MAX-ACCESS  not-accessible
    STATUS      current
    DESCRIPTION
        "Each row entry represents a router ID under which interface entries
         would be configured for the SRLG database table.

          A row can be created or deleted via SNMP SET requests."
    INDEX       {
        vRtrID,
        vRtrMplsSrlgDBRtrIdRouterID
    }
    ::= { vRtrMplsSrlgDBRtrIdTable 1 }

VRtrMplsSrlgDBRtrIdEntry         ::= SEQUENCE
{
    vRtrMplsSrlgDBRtrIdRouterID      TmnxMplsRouterId,
    vRtrMplsSrlgDBRtrIdRowStatus     RowStatus,
    vRtrMplsSrlgDBRtrIdAdminState    TmnxAdminState,
    vRtrMplsSrlgDBRtrIdLastChanged   TimeStamp
}

vRtrMplsSrlgDBRtrIdRouterID      OBJECT-TYPE
    SYNTAX      TmnxMplsRouterId
    MAX-ACCESS  not-accessible
    STATUS      current
    DESCRIPTION
        "The value of vRtrMplsSrlgDBRtrIdRouterID specifies a 32-bit integer uniquely
         identifying the router in the Autonomous System.  By convention
         to ensure uniqueness, this may default to the value of one of the
         router's IPv4 host addresses, represented as a 32-bit unsigned
         integer, if IPv4 is configured on the router. The router-id can be
         either the local one or some remote router."
    ::= { vRtrMplsSrlgDBRtrIdEntry 1 }

vRtrMplsSrlgDBRtrIdRowStatus     OBJECT-TYPE
    SYNTAX      RowStatus
    MAX-ACCESS  read-create
    STATUS      current
    DESCRIPTION
        "vRtrMplsSrlgDBRtrIdRowStatus is used to create, delete or control
         entries in the vRtrMplsSrlgDBRtrIdTable."
    ::= { vRtrMplsSrlgDBRtrIdEntry 2 }

vRtrMplsSrlgDBRtrIdAdminState    OBJECT-TYPE
    SYNTAX      TmnxAdminState
    MAX-ACCESS  read-create
    STATUS      current
    DESCRIPTION
        "The value of vRtrMplsSrlgDBRtrIdAdminState specifies the desired
         administrative state for the router-id entry in the
         vRtrMplsSrlgDBRtrIdTable."
    DEFVAL      { outOfService }
    ::= { vRtrMplsSrlgDBRtrIdEntry 3 }

vRtrMplsSrlgDBRtrIdLastChanged   OBJECT-TYPE
    SYNTAX      TimeStamp
    MAX-ACCESS  read-only
    STATUS      current
    DESCRIPTION
        "The value of vRtrMplsSrlgDBRtrIdLastChanged indicates the timestamp of
         last change to this row in vRtrMplsSrlgDBRtrIdTable."
    ::= { vRtrMplsSrlgDBRtrIdEntry 4 }

vRtrMplsSrlgDBIfTblLastChanged   OBJECT-TYPE
    SYNTAX      TimeStamp
    MAX-ACCESS  read-only
    STATUS      current
    DESCRIPTION
        "The value of vRtrMplsSrlgDBIfTblLastChanged indicates the sysUpTime at
         the time of the last modification to vRtrMplsSrlgDBIfTable by adding,
         deleting an entry or change to a writable object in the table.

         If no changes were made to the table since the last re-initialization
         of the local network management subsystem, then this object contains a
         zero value."
    ::= { tmnxMplsObjs 32 }

vRtrMplsSrlgDBIfTable            OBJECT-TYPE
    SYNTAX      SEQUENCE OF VRtrMplsSrlgDBIfEntry
    MAX-ACCESS  not-accessible
    STATUS      current
    DESCRIPTION
        "The vRtrMplsSrlgDBIfTable has an entry for each Shared Risk Link Group
         (SRLG) groups associated with a interface which is validated as part
         of a router ID in the routing table. The user manually enters the SRLG
         membership information for any link in the network, into the user SRLG
         database."
    ::= { tmnxMplsObjs 33 }

vRtrMplsSrlgDBIfEntry            OBJECT-TYPE
    SYNTAX      VRtrMplsSrlgDBIfEntry
    MAX-ACCESS  not-accessible
    STATUS      current
    DESCRIPTION
        "Each row entry represents an SRLG group associated with a interface
         which is validated as part of a router ID in the routing table.

         A row can be created or deleted via SNMP SET requests."
    INDEX       {
        vRtrID,
        vRtrMplsSrlgDBRtrIdRouterID,
        vRtrMplsSrlgDBIfIntIpAddrType,
        vRtrMplsSrlgDBIfIntIpAddr,
        IMPLIED vRtrMplsSrlgDBIfSrlgGroupName
    }
    ::= { vRtrMplsSrlgDBIfTable 1 }

VRtrMplsSrlgDBIfEntry            ::= SEQUENCE
{
    vRtrMplsSrlgDBIfIntIpAddrType    InetAddressType,
    vRtrMplsSrlgDBIfIntIpAddr        InetAddress,
    vRtrMplsSrlgDBIfSrlgGroupName    TNamedItem,
    vRtrMplsSrlgDBIfRowStatus        RowStatus,
    vRtrMplsSrlgDBIfLastChanged      TimeStamp
}

vRtrMplsSrlgDBIfIntIpAddrType    OBJECT-TYPE
    SYNTAX      InetAddressType
    MAX-ACCESS  not-accessible
    STATUS      current
    DESCRIPTION
        "The value of vRtrMplsSrlgDBIfIntIpAddrType indicates the type of
         vRtrMplsSrlgDBIfIntIpAddr."
    ::= { vRtrMplsSrlgDBIfEntry 1 }

vRtrMplsSrlgDBIfIntIpAddr        OBJECT-TYPE
    SYNTAX      InetAddress (SIZE (0|4))
    MAX-ACCESS  not-accessible
    STATUS      current
    DESCRIPTION
        "The value of vRtrMplsSrlgDBIfIntIpAddr indicates the IP address of the
         interface."
    ::= { vRtrMplsSrlgDBIfEntry 2 }

vRtrMplsSrlgDBIfSrlgGroupName    OBJECT-TYPE
    SYNTAX      TNamedItem
    MAX-ACCESS  not-accessible
    STATUS      current
    DESCRIPTION
        "The value of vRtrMplsSrlgDBIfSrlgGroupName indicates the SRLG group
         name."
    ::= { vRtrMplsSrlgDBIfEntry 3 }

vRtrMplsSrlgDBIfRowStatus        OBJECT-TYPE
    SYNTAX      RowStatus
    MAX-ACCESS  read-create
    STATUS      current
    DESCRIPTION
        "vRtrMplsSrlgDBIfRowStatus is used to create, delete or control entries
         in the vRtrMplsSrlgDBIfTable."
    ::= { vRtrMplsSrlgDBIfEntry 4 }

vRtrMplsSrlgDBIfLastChanged      OBJECT-TYPE
    SYNTAX      TimeStamp
    MAX-ACCESS  read-only
    STATUS      current
    DESCRIPTION
        "The value of vRtrMplsSrlgDBIfLastChanged indicates the timestamp of
         last change to this row in vRtrMplsSrlgDBIfTable."
    ::= { vRtrMplsSrlgDBIfEntry 5 }

vRtrMplsInSegmentTable           OBJECT-TYPE
    SYNTAX      SEQUENCE OF VRtrMplsInSegmentEntry
    MAX-ACCESS  not-accessible
    STATUS      current
    DESCRIPTION
        "The vRtrMplsInSegmentTable augments the mplsInSegmentTable in the
         MPLS-LSR-MIB."
    ::= { tmnxMplsObjs 34 }

vRtrMplsInSegmentEntry           OBJECT-TYPE
    SYNTAX      VRtrMplsInSegmentEntry
    MAX-ACCESS  not-accessible
    STATUS      current
    DESCRIPTION
        "A row entry in this table corresponds to a row entry in the
         mplsInSegmentTable and adds to the information contained in that
         table."
    AUGMENTS    { mplsInSegmentEntry }
    ::= { vRtrMplsInSegmentTable 1 }

VRtrMplsInSegmentEntry           ::= SEQUENCE
{ vRtrMplsInSegmentNumS2ls         Unsigned32 }

vRtrMplsInSegmentNumS2ls         OBJECT-TYPE
    SYNTAX      Unsigned32
    MAX-ACCESS  read-only
    STATUS      current
    DESCRIPTION
        "The value of vRtrMplsInSegmentNumS2ls indicates number of S2Ls on the
         insegment."
    ::= { vRtrMplsInSegmentEntry 1 }

vRtrMplsOutSegmentTable          OBJECT-TYPE
    SYNTAX      SEQUENCE OF VRtrMplsOutSegmentEntry
    MAX-ACCESS  not-accessible
    STATUS      current
    DESCRIPTION
        "The vRtrMplsOutSegmentTable augments the mplsOutSegmentTable in the
         MPLS-LSR-MIB."
    ::= { tmnxMplsObjs 35 }

vRtrMplsOutSegmentEntry          OBJECT-TYPE
    SYNTAX      VRtrMplsOutSegmentEntry
    MAX-ACCESS  not-accessible
    STATUS      current
    DESCRIPTION
        "A row entry in this table corresponds to a row entry in the
         mplsOutSegmentTable and adds to the information contained in that
         table."
    AUGMENTS    { mplsOutSegmentEntry }
    ::= { vRtrMplsOutSegmentTable 1 }

VRtrMplsOutSegmentEntry          ::= SEQUENCE
{ vRtrMplsOutSegmentNumS2ls        Unsigned32 }

vRtrMplsOutSegmentNumS2ls        OBJECT-TYPE
    SYNTAX      Unsigned32
    MAX-ACCESS  read-only
    STATUS      current
    DESCRIPTION
        "The value of vRtrMplsOutSegmentNumS2ls indicates number of S2Ls on the
         outsegment."
    ::= { vRtrMplsOutSegmentEntry 1 }

vRtrMplsLspStatsTblLastChgd      OBJECT-TYPE
    SYNTAX      TimeStamp
    MAX-ACCESS  read-only
    STATUS      current
    DESCRIPTION
        "Timestamp of the last change to the vRtrMplsLspStatsTable either from
         adding a row or removing a row."
    ::= { tmnxMplsObjs 37 }

vRtrMplsLspStatsTable            OBJECT-TYPE
    SYNTAX      SEQUENCE OF VRtrMplsLspStatsEntry
    MAX-ACCESS  not-accessible
    STATUS      current
    DESCRIPTION
        "vRtrMplsLspStatsTable controls Statistics in the ess data path at the
         ingress Label Switched Path (LSP) for an Mpls-Lsp FEC."
    ::= { tmnxMplsObjs 38 }

vRtrMplsLspStatsEntry            OBJECT-TYPE
    SYNTAX      VRtrMplsLspStatsEntry
    MAX-ACCESS  not-accessible
    STATUS      current
    DESCRIPTION
        "A row in this table represents information about the Statistics
         collection per MPLS LSP."
    INDEX       {
        vRtrID,
        vRtrMplsLspStatsType,
        vRtrMplsLspStatsSenderAddrType,
        vRtrMplsLspStatsSenderAddr,
        vRtrMplsLspStatsLspName
    }
    ::= { vRtrMplsLspStatsTable 1 }

VRtrMplsLspStatsEntry            ::= SEQUENCE
{
    vRtrMplsLspStatsType             INTEGER,
    vRtrMplsLspStatsSenderAddrType   InetAddressType,
    vRtrMplsLspStatsSenderAddr       InetAddress,
    vRtrMplsLspStatsLspName          TLNamedItem,
    vRtrMplsLspStatsRowStatus        RowStatus,
    vRtrMplsLspStatsLastChanged      TimeStamp,
    vRtrMplsLspStatsCollectStats     TruthValue,
    vRtrMplsLspStatsAccntingPolicy   Unsigned32,
    vRtrMplsLspStatsAdminState       TmnxAdminState
}

vRtrMplsLspStatsType             OBJECT-TYPE
    SYNTAX      INTEGER {
        egress     (0),
        ingress    (1),
        srTeEgress (2)
    }
    MAX-ACCESS  not-accessible
    STATUS      current
    DESCRIPTION
        "The value of vRtrMplsLspStatsType indicates the type of statistics."
    ::= { vRtrMplsLspStatsEntry 1 }

vRtrMplsLspStatsSenderAddrType   OBJECT-TYPE
    SYNTAX      InetAddressType
    MAX-ACCESS  not-accessible
    STATUS      current
    DESCRIPTION
        "The value of vRtrMplsLspStatsSenderAddrType indicates address type of
         vRtrMplsLspStatsSenderAddr."
    ::= { vRtrMplsLspStatsEntry 2 }

vRtrMplsLspStatsSenderAddr       OBJECT-TYPE
    SYNTAX      InetAddress (SIZE (0|4))
    MAX-ACCESS  not-accessible
    STATUS      current
    DESCRIPTION
        "The value of vRtrMplsLspStatsSenderAddr indicates the sender address."
    ::= { vRtrMplsLspStatsEntry 3 }

vRtrMplsLspStatsLspName          OBJECT-TYPE
    SYNTAX      TLNamedItem
    MAX-ACCESS  not-accessible
    STATUS      current
    DESCRIPTION
        "The value of vRtrMplsLspStatsLspName indicates the lsp name.

         If vRtrMplsLspType is not 'meshP2p' or 'oneHopP2p',
         vRtrMplsLspStatsLspName can have a maximum  of 32 characters."
    ::= { vRtrMplsLspStatsEntry 4 }

vRtrMplsLspStatsRowStatus        OBJECT-TYPE
    SYNTAX      RowStatus
    MAX-ACCESS  read-create
    STATUS      current
    DESCRIPTION
        "vRtrMplsLspStatsRowStatus is used for the creation or deletion of
         entries in the vRtrMplsLspStatsTable."
    ::= { vRtrMplsLspStatsEntry 5 }

vRtrMplsLspStatsLastChanged      OBJECT-TYPE
    SYNTAX      TimeStamp
    MAX-ACCESS  read-only
    STATUS      current
    DESCRIPTION
        "The value of vRtrMplsLspStatsLastChanged indicates the time stamp of
         the last change to this row of this table."
    ::= { vRtrMplsLspStatsEntry 6 }

vRtrMplsLspStatsCollectStats     OBJECT-TYPE
    SYNTAX      TruthValue
    MAX-ACCESS  read-create
    STATUS      current
    DESCRIPTION
        "The value of vRtrMplsLspStatsCollectStats specifies whether to collect
         statistics for this prefix."
    DEFVAL      { false }
    ::= { vRtrMplsLspStatsEntry 7 }

vRtrMplsLspStatsAccntingPolicy   OBJECT-TYPE
    SYNTAX      Unsigned32 (0 | 1..99)
    MAX-ACCESS  read-create
    STATUS      current
    DESCRIPTION
        "The value of vRtrMplsLspStatsAccntingPolicy specifies the accounting
         policy to be used for this entry.

         A value of zero indicates that the default accounting policy should be
         used."
    DEFVAL      { 0 }
    ::= { vRtrMplsLspStatsEntry 8 }

vRtrMplsLspStatsAdminState       OBJECT-TYPE
    SYNTAX      TmnxAdminState
    MAX-ACCESS  read-create
    STATUS      current
    DESCRIPTION
        "The value of vRtrMplsLspStatsAdminState specifies whether egress
         statistics are enabled for this lsp."
    DEFVAL      { outOfService }
    ::= { vRtrMplsLspStatsEntry 9 }

vRtrMplsLspStatisticsTable       OBJECT-TYPE
    SYNTAX      SEQUENCE OF VRtrMplsLspStatisticsEntry
    MAX-ACCESS  not-accessible
    STATUS      current
    DESCRIPTION
        "The vRtrMplsLspStatisticsTable has an entry for each Labeled Switch
         Path (LSP) configured for a virtual router in the system."
    ::= { tmnxMplsObjs 39 }

vRtrMplsLspStatisticsEntry       OBJECT-TYPE
    SYNTAX      VRtrMplsLspStatisticsEntry
    MAX-ACCESS  not-accessible
    STATUS      current
    DESCRIPTION
        "Each row entry represents a collection of statistics for a Labeled
         Switch Path (LSP) configured for a virtual router in the system.

         Entries cannot be created and deleted via SNMP SET operations."
    AUGMENTS    { vRtrMplsLspStatsEntry }
    ::= { vRtrMplsLspStatisticsTable 1 }

VRtrMplsLspStatisticsEntry       ::= SEQUENCE
{
    vRtrMplsInProfilePktsFc0         Counter64,
    vRtrMplsInProfilePktsFc0Low32    Counter32,
    vRtrMplsInProfilePktsFc0High32   Counter32,
    vRtrMplsInProfilePktsFc1         Counter64,
    vRtrMplsInProfilePktsFc1Low32    Counter32,
    vRtrMplsInProfilePktsFc1High32   Counter32,
    vRtrMplsInProfilePktsFc2         Counter64,
    vRtrMplsInProfilePktsFc2Low32    Counter32,
    vRtrMplsInProfilePktsFc2High32   Counter32,
    vRtrMplsInProfilePktsFc3         Counter64,
    vRtrMplsInProfilePktsFc3Low32    Counter32,
    vRtrMplsInProfilePktsFc3High32   Counter32,
    vRtrMplsInProfilePktsFc4         Counter64,
    vRtrMplsInProfilePktsFc4Low32    Counter32,
    vRtrMplsInProfilePktsFc4High32   Counter32,
    vRtrMplsInProfilePktsFc5         Counter64,
    vRtrMplsInProfilePktsFc5Low32    Counter32,
    vRtrMplsInProfilePktsFc5High32   Counter32,
    vRtrMplsInProfilePktsFc6         Counter64,
    vRtrMplsInProfilePktsFc6Low32    Counter32,
    vRtrMplsInProfilePktsFc6High32   Counter32,
    vRtrMplsInProfilePktsFc7         Counter64,
    vRtrMplsInProfilePktsFc7Low32    Counter32,
    vRtrMplsInProfilePktsFc7High32   Counter32,
    vRtrMplsInProfileOctetsFc0       Counter64,
    vRtrMplsInProfileOctetsFc0Low32  Counter32,
    vRtrMplsInProfileOctetsFc0High32 Counter32,
    vRtrMplsInProfileOctetsFc1       Counter64,
    vRtrMplsInProfileOctetsFc1Low32  Counter32,
    vRtrMplsInProfileOctetsFc1High32 Counter32,
    vRtrMplsInProfileOctetsFc2       Counter64,
    vRtrMplsInProfileOctetsFc2Low32  Counter32,
    vRtrMplsInProfileOctetsFc2High32 Counter32,
    vRtrMplsInProfileOctetsFc3       Counter64,
    vRtrMplsInProfileOctetsFc3Low32  Counter32,
    vRtrMplsInProfileOctetsFc3High32 Counter32,
    vRtrMplsInProfileOctetsFc4       Counter64,
    vRtrMplsInProfileOctetsFc4Low32  Counter32,
    vRtrMplsInProfileOctetsFc4High32 Counter32,
    vRtrMplsInProfileOctetsFc5       Counter64,
    vRtrMplsInProfileOctetsFc5Low32  Counter32,
    vRtrMplsInProfileOctetsFc5High32 Counter32,
    vRtrMplsInProfileOctetsFc6       Counter64,
    vRtrMplsInProfileOctetsFc6Low32  Counter32,
    vRtrMplsInProfileOctetsFc6High32 Counter32,
    vRtrMplsInProfileOctetsFc7       Counter64,
    vRtrMplsInProfileOctetsFc7Low32  Counter32,
    vRtrMplsInProfileOctetsFc7High32 Counter32,
    vRtrMplsOutOfProfPktsFc0         Counter64,
    vRtrMplsOutOfProfPktsFc0Low32    Counter32,
    vRtrMplsOutOfProfPktsFc0High32   Counter32,
    vRtrMplsOutOfProfPktsFc1         Counter64,
    vRtrMplsOutOfProfPktsFc1Low32    Counter32,
    vRtrMplsOutOfProfPktsFc1High32   Counter32,
    vRtrMplsOutOfProfPktsFc2         Counter64,
    vRtrMplsOutOfProfPktsFc2Low32    Counter32,
    vRtrMplsOutOfProfPktsFc2High32   Counter32,
    vRtrMplsOutOfProfPktsFc3         Counter64,
    vRtrMplsOutOfProfPktsFc3Low32    Counter32,
    vRtrMplsOutOfProfPktsFc3High32   Counter32,
    vRtrMplsOutOfProfPktsFc4         Counter64,
    vRtrMplsOutOfProfPktsFc4Low32    Counter32,
    vRtrMplsOutOfProfPktsFc4High32   Counter32,
    vRtrMplsOutOfProfPktsFc5         Counter64,
    vRtrMplsOutOfProfPktsFc5Low32    Counter32,
    vRtrMplsOutOfProfPktsFc5High32   Counter32,
    vRtrMplsOutOfProfPktsFc6         Counter64,
    vRtrMplsOutOfProfPktsFc6Low32    Counter32,
    vRtrMplsOutOfProfPktsFc6High32   Counter32,
    vRtrMplsOutOfProfPktsFc7         Counter64,
    vRtrMplsOutOfProfPktsFc7Low32    Counter32,
    vRtrMplsOutOfProfPktsFc7High32   Counter32,
    vRtrMplsOutOfProfOctetsFc0       Counter64,
    vRtrMplsOutOfProfOctetsFc0Low32  Counter32,
    vRtrMplsOutOfProfOctetsFc0High32 Counter32,
    vRtrMplsOutOfProfOctetsFc1       Counter64,
    vRtrMplsOutOfProfOctetsFc1Low32  Counter32,
    vRtrMplsOutOfProfOctetsFc1High32 Counter32,
    vRtrMplsOutOfProfOctetsFc2       Counter64,
    vRtrMplsOutOfProfOctetsFc2Low32  Counter32,
    vRtrMplsOutOfProfOctetsFc2High32 Counter32,
    vRtrMplsOutOfProfOctetsFc3       Counter64,
    vRtrMplsOutOfProfOctetsFc3Low32  Counter32,
    vRtrMplsOutOfProfOctetsFc3High32 Counter32,
    vRtrMplsOutOfProfOctetsFc4       Counter64,
    vRtrMplsOutOfProfOctetsFc4Low32  Counter32,
    vRtrMplsOutOfProfOctetsFc4High32 Counter32,
    vRtrMplsOutOfProfOctetsFc5       Counter64,
    vRtrMplsOutOfProfOctetsFc5Low32  Counter32,
    vRtrMplsOutOfProfOctetsFc5High32 Counter32,
    vRtrMplsOutOfProfOctetsFc6       Counter64,
    vRtrMplsOutOfProfOctetsFc6Low32  Counter32,
    vRtrMplsOutOfProfOctetsFc6High32 Counter32,
    vRtrMplsOutOfProfOctetsFc7       Counter64,
    vRtrMplsOutOfProfOctetsFc7Low32  Counter32,
    vRtrMplsOutOfProfOctetsFc7High32 Counter32,
    vRtrMplsLspStatsPSBMatch         TruthValue,
    vRtrMplsLspStatsTpOnly           TruthValue,
    vRtrMplsLspStatsLspType          INTEGER,
    vRtrMplsLspAggregatePkts         Counter64,
    vRtrMplsLspAggregateOctets       Counter64
}

vRtrMplsInProfilePktsFc0         OBJECT-TYPE
    SYNTAX      Counter64
    MAX-ACCESS  read-only
    STATUS      current
    DESCRIPTION
        "The value of vRtrMplsInProfilePktsFc0 indicates the number of in
         profile packets received for Forwarding Class 0."
    ::= { vRtrMplsLspStatisticsEntry 1 }

vRtrMplsInProfilePktsFc0Low32    OBJECT-TYPE
    SYNTAX      Counter32
    MAX-ACCESS  read-only
    STATUS      current
    DESCRIPTION
        "The value of vRtrMplsInProfilePktsFc0Low32 indicates the lower 32 bits
         of the value of vRtrMplsInProfilePktsFc0."
    ::= { vRtrMplsLspStatisticsEntry 2 }

vRtrMplsInProfilePktsFc0High32   OBJECT-TYPE
    SYNTAX      Counter32
    MAX-ACCESS  read-only
    STATUS      current
    DESCRIPTION
        "The value of vRtrMplsInProfilePktsFc0High32 indicates the higher 32
         bits of the value of vRtrMplsInProfilePktsFc0."
    ::= { vRtrMplsLspStatisticsEntry 3 }

vRtrMplsInProfilePktsFc1         OBJECT-TYPE
    SYNTAX      Counter64
    MAX-ACCESS  read-only
    STATUS      current
    DESCRIPTION
        "The value of vRtrMplsInProfilePktsFc1 indicates the number of in
         profile packets received for Forwarding Class 1."
    ::= { vRtrMplsLspStatisticsEntry 4 }

vRtrMplsInProfilePktsFc1Low32    OBJECT-TYPE
    SYNTAX      Counter32
    MAX-ACCESS  read-only
    STATUS      current
    DESCRIPTION
        "The value of vRtrMplsInProfilePktsFc1Low32 indicates the lower 32 bits
         of the value of vRtrMplsInProfilePktsFc1."
    ::= { vRtrMplsLspStatisticsEntry 5 }

vRtrMplsInProfilePktsFc1High32   OBJECT-TYPE
    SYNTAX      Counter32
    MAX-ACCESS  read-only
    STATUS      current
    DESCRIPTION
        "The value of vRtrMplsInProfilePktsFc1High32 indicates the higher 32
         bits of the value of vRtrMplsInProfilePktsFc1."
    ::= { vRtrMplsLspStatisticsEntry 6 }

vRtrMplsInProfilePktsFc2         OBJECT-TYPE
    SYNTAX      Counter64
    MAX-ACCESS  read-only
    STATUS      current
    DESCRIPTION
        "The value of vRtrMplsInProfilePktsFc2 indicates the number of in
         profile packets received for Forwarding Class 2."
    ::= { vRtrMplsLspStatisticsEntry 7 }

vRtrMplsInProfilePktsFc2Low32    OBJECT-TYPE
    SYNTAX      Counter32
    MAX-ACCESS  read-only
    STATUS      current
    DESCRIPTION
        "The value of vRtrMplsInProfilePktsFc2Low32 indicates the lower 32 bits
         of the value of vRtrMplsInProfilePktsFc2."
    ::= { vRtrMplsLspStatisticsEntry 8 }

vRtrMplsInProfilePktsFc2High32   OBJECT-TYPE
    SYNTAX      Counter32
    MAX-ACCESS  read-only
    STATUS      current
    DESCRIPTION
        "The value of vRtrMplsInProfilePktsFc2High32 indicates the higher 32
         bits of the value of vRtrMplsInProfilePktsFc2."
    ::= { vRtrMplsLspStatisticsEntry 9 }

vRtrMplsInProfilePktsFc3         OBJECT-TYPE
    SYNTAX      Counter64
    MAX-ACCESS  read-only
    STATUS      current
    DESCRIPTION
        "The value of vRtrMplsInProfilePktsFc3 indicates the number of in
         profile packets received for Forwarding Class 3."
    ::= { vRtrMplsLspStatisticsEntry 10 }

vRtrMplsInProfilePktsFc3Low32    OBJECT-TYPE
    SYNTAX      Counter32
    MAX-ACCESS  read-only
    STATUS      current
    DESCRIPTION
        "The value of vRtrMplsInProfilePktsFc3Low32 indicates the lower 32 bits
         of the value of vRtrMplsInProfilePktsFc3."
    ::= { vRtrMplsLspStatisticsEntry 11 }

vRtrMplsInProfilePktsFc3High32   OBJECT-TYPE
    SYNTAX      Counter32
    MAX-ACCESS  read-only
    STATUS      current
    DESCRIPTION
        "The value of vRtrMplsInProfilePktsFc3High32 indicates the higher 32
         bits of the value of vRtrMplsInProfilePktsFc3."
    ::= { vRtrMplsLspStatisticsEntry 12 }

vRtrMplsInProfilePktsFc4         OBJECT-TYPE
    SYNTAX      Counter64
    MAX-ACCESS  read-only
    STATUS      current
    DESCRIPTION
        "The value of vRtrMplsInProfilePktsFc4 indicates the number of in
         profile packets received for Forwarding Class 4."
    ::= { vRtrMplsLspStatisticsEntry 13 }

vRtrMplsInProfilePktsFc4Low32    OBJECT-TYPE
    SYNTAX      Counter32
    MAX-ACCESS  read-only
    STATUS      current
    DESCRIPTION
        "The value of vRtrMplsInProfilePktsFc4Low32 indicates the lower 32 bits
         of the value of vRtrMplsInProfilePktsFc4."
    ::= { vRtrMplsLspStatisticsEntry 14 }

vRtrMplsInProfilePktsFc4High32   OBJECT-TYPE
    SYNTAX      Counter32
    MAX-ACCESS  read-only
    STATUS      current
    DESCRIPTION
        "The value of vRtrMplsInProfilePktsFc4High32 indicates the higher 32
         bits of the value of vRtrMplsInProfilePktsFc4."
    ::= { vRtrMplsLspStatisticsEntry 15 }

vRtrMplsInProfilePktsFc5         OBJECT-TYPE
    SYNTAX      Counter64
    MAX-ACCESS  read-only
    STATUS      current
    DESCRIPTION
        "The value of vRtrMplsInProfilePktsFc5 indicates the number of in
         profile packets received for Forwarding Class 5."
    ::= { vRtrMplsLspStatisticsEntry 16 }

vRtrMplsInProfilePktsFc5Low32    OBJECT-TYPE
    SYNTAX      Counter32
    MAX-ACCESS  read-only
    STATUS      current
    DESCRIPTION
        "The value of vRtrMplsInProfilePktsFc5Low32 indicates the lower 32 bits
         of the value of vRtrMplsInProfilePktsFc5."
    ::= { vRtrMplsLspStatisticsEntry 17 }

vRtrMplsInProfilePktsFc5High32   OBJECT-TYPE
    SYNTAX      Counter32
    MAX-ACCESS  read-only
    STATUS      current
    DESCRIPTION
        "The value of vRtrMplsInProfilePktsFc5High32 indicates the higher 32
         bits of the value of vRtrMplsInProfilePktsFc5."
    ::= { vRtrMplsLspStatisticsEntry 18 }

vRtrMplsInProfilePktsFc6         OBJECT-TYPE
    SYNTAX      Counter64
    MAX-ACCESS  read-only
    STATUS      current
    DESCRIPTION
        "The value of vRtrMplsInProfilePktsFc6 indicates the number of in
         profile packets received for Forwarding Class 6."
    ::= { vRtrMplsLspStatisticsEntry 19 }

vRtrMplsInProfilePktsFc6Low32    OBJECT-TYPE
    SYNTAX      Counter32
    MAX-ACCESS  read-only
    STATUS      current
    DESCRIPTION
        "The value of vRtrMplsInProfilePktsFc6Low32 indicates the lower 32 bits
         of the value of vRtrMplsInProfilePktsFc6."
    ::= { vRtrMplsLspStatisticsEntry 20 }

vRtrMplsInProfilePktsFc6High32   OBJECT-TYPE
    SYNTAX      Counter32
    MAX-ACCESS  read-only
    STATUS      current
    DESCRIPTION
        "The value of vRtrMplsInProfilePktsFc6High32 indicates the higher 32
         bits of the value of vRtrMplsInProfilePktsFc6."
    ::= { vRtrMplsLspStatisticsEntry 21 }

vRtrMplsInProfilePktsFc7         OBJECT-TYPE
    SYNTAX      Counter64
    MAX-ACCESS  read-only
    STATUS      current
    DESCRIPTION
        "The value of vRtrMplsInProfilePktsFc7 indicates the number of in
         profile packets received for Forwarding Class 7."
    ::= { vRtrMplsLspStatisticsEntry 22 }

vRtrMplsInProfilePktsFc7Low32    OBJECT-TYPE
    SYNTAX      Counter32
    MAX-ACCESS  read-only
    STATUS      current
    DESCRIPTION
        "The value of vRtrMplsInProfilePktsFc7Low32 indicates the lower 32 bits
         of the value of vRtrMplsInProfilePktsFc7."
    ::= { vRtrMplsLspStatisticsEntry 23 }

vRtrMplsInProfilePktsFc7High32   OBJECT-TYPE
    SYNTAX      Counter32
    MAX-ACCESS  read-only
    STATUS      current
    DESCRIPTION
        "The value of vRtrMplsInProfilePktsFc7High32 indicates the higher 32
         bits of the value of vRtrMplsInProfilePktsFc7."
    ::= { vRtrMplsLspStatisticsEntry 24 }

vRtrMplsInProfileOctetsFc0       OBJECT-TYPE
    SYNTAX      Counter64
    MAX-ACCESS  read-only
    STATUS      current
    DESCRIPTION
        "The value of vRtrMplsInProfileOctetsFc0 indicates the number of in
         profile octets received for Forwarding Class 0."
    ::= { vRtrMplsLspStatisticsEntry 25 }

vRtrMplsInProfileOctetsFc0Low32  OBJECT-TYPE
    SYNTAX      Counter32
    MAX-ACCESS  read-only
    STATUS      current
    DESCRIPTION
        "The value of vRtrMplsInProfileOctetsFc0Low32 indicates the lower 32
         bits of the value of vRtrMplsInProfileOctetsFc0."
    ::= { vRtrMplsLspStatisticsEntry 26 }

vRtrMplsInProfileOctetsFc0High32 OBJECT-TYPE
    SYNTAX      Counter32
    MAX-ACCESS  read-only
    STATUS      current
    DESCRIPTION
        "The value of vRtrMplsInProfileOctetsFc0High32 indicates the higher 32
         bits of the value of vRtrMplsInProfileOctetsFc0."
    ::= { vRtrMplsLspStatisticsEntry 27 }

vRtrMplsInProfileOctetsFc1       OBJECT-TYPE
    SYNTAX      Counter64
    MAX-ACCESS  read-only
    STATUS      current
    DESCRIPTION
        "The value of vRtrMplsInProfileOctetsFc1 indicates the number of in
         profile octets received for Forwarding Class 1."
    ::= { vRtrMplsLspStatisticsEntry 28 }

vRtrMplsInProfileOctetsFc1Low32  OBJECT-TYPE
    SYNTAX      Counter32
    MAX-ACCESS  read-only
    STATUS      current
    DESCRIPTION
        "The value of vRtrMplsInProfileOctetsFc1Low32 indicates the lower 32
         bits of the value of vRtrMplsInProfileOctetsFc1."
    ::= { vRtrMplsLspStatisticsEntry 29 }

vRtrMplsInProfileOctetsFc1High32 OBJECT-TYPE
    SYNTAX      Counter32
    MAX-ACCESS  read-only
    STATUS      current
    DESCRIPTION
        "The value of vRtrMplsInProfileOctetsFc1High32 indicates the higher 32
         bits of the value of vRtrMplsInProfileOctetsFc1."
    ::= { vRtrMplsLspStatisticsEntry 30 }

vRtrMplsInProfileOctetsFc2       OBJECT-TYPE
    SYNTAX      Counter64
    MAX-ACCESS  read-only
    STATUS      current
    DESCRIPTION
        "The value of vRtrMplsInProfileOctetsFc2 indicates the number of in
         profile octets received for Forwarding Class 2."
    ::= { vRtrMplsLspStatisticsEntry 31 }

vRtrMplsInProfileOctetsFc2Low32  OBJECT-TYPE
    SYNTAX      Counter32
    MAX-ACCESS  read-only
    STATUS      current
    DESCRIPTION
        "The value of vRtrMplsInProfileOctetsFc2Low32 indicates the lower 32
         bits of the value of vRtrMplsInProfileOctetsFc2."
    ::= { vRtrMplsLspStatisticsEntry 32 }

vRtrMplsInProfileOctetsFc2High32 OBJECT-TYPE
    SYNTAX      Counter32
    MAX-ACCESS  read-only
    STATUS      current
    DESCRIPTION
        "The value of vRtrMplsInProfileOctetsFc2High32 indicates the higher 32
         bits of the value of vRtrMplsInProfileOctetsFc2."
    ::= { vRtrMplsLspStatisticsEntry 33 }

vRtrMplsInProfileOctetsFc3       OBJECT-TYPE
    SYNTAX      Counter64
    MAX-ACCESS  read-only
    STATUS      current
    DESCRIPTION
        "The value of vRtrMplsInProfileOctetsFc3 indicates the number of in
         profile octets received for Forwarding Class 3."
    ::= { vRtrMplsLspStatisticsEntry 34 }

vRtrMplsInProfileOctetsFc3Low32  OBJECT-TYPE
    SYNTAX      Counter32
    MAX-ACCESS  read-only
    STATUS      current
    DESCRIPTION
        "The value of vRtrMplsInProfileOctetsFc3Low32 indicates the lower 32
         bits of the value of vRtrMplsInProfileOctetsFc3."
    ::= { vRtrMplsLspStatisticsEntry 35 }

vRtrMplsInProfileOctetsFc3High32 OBJECT-TYPE
    SYNTAX      Counter32
    MAX-ACCESS  read-only
    STATUS      current
    DESCRIPTION
        "The value of vRtrMplsInProfileOctetsFc3High32 indicates the higher 32
         bits of the value of vRtrMplsInProfileOctetsFc3."
    ::= { vRtrMplsLspStatisticsEntry 36 }

vRtrMplsInProfileOctetsFc4       OBJECT-TYPE
    SYNTAX      Counter64
    MAX-ACCESS  read-only
    STATUS      current
    DESCRIPTION
        "The value of vRtrMplsInProfileOctetsFc4 indicates the number of in
         profile octets received for Forwarding Class 4."
    ::= { vRtrMplsLspStatisticsEntry 37 }

vRtrMplsInProfileOctetsFc4Low32  OBJECT-TYPE
    SYNTAX      Counter32
    MAX-ACCESS  read-only
    STATUS      current
    DESCRIPTION
        "The value of vRtrMplsInProfileOctetsFc4Low32 indicates the lower 32
         bits of the value of vRtrMplsInProfileOctetsFc4."
    ::= { vRtrMplsLspStatisticsEntry 38 }

vRtrMplsInProfileOctetsFc4High32 OBJECT-TYPE
    SYNTAX      Counter32
    MAX-ACCESS  read-only
    STATUS      current
    DESCRIPTION
        "The value of vRtrMplsInProfileOctetsFc4High32 indicates the higher 32
         bits of the value of vRtrMplsInProfileOctetsFc4."
    ::= { vRtrMplsLspStatisticsEntry 39 }

vRtrMplsInProfileOctetsFc5       OBJECT-TYPE
    SYNTAX      Counter64
    MAX-ACCESS  read-only
    STATUS      current
    DESCRIPTION
        "The value of vRtrMplsInProfileOctetsFc5 indicates the number of in
         profile octets received for Forwarding Class 5."
    ::= { vRtrMplsLspStatisticsEntry 40 }

vRtrMplsInProfileOctetsFc5Low32  OBJECT-TYPE
    SYNTAX      Counter32
    MAX-ACCESS  read-only
    STATUS      current
    DESCRIPTION
        "The value of vRtrMplsInProfileOctetsFc5Low32 indicates the lower 32
         bits of the value of vRtrMplsInProfileOctetsFc5."
    ::= { vRtrMplsLspStatisticsEntry 41 }

vRtrMplsInProfileOctetsFc5High32 OBJECT-TYPE
    SYNTAX      Counter32
    MAX-ACCESS  read-only
    STATUS      current
    DESCRIPTION
        "The value of vRtrMplsInProfileOctetsFc5High32 indicates the higher 32
         bits of the value of vRtrMplsInProfileOctetsFc5."
    ::= { vRtrMplsLspStatisticsEntry 42 }

vRtrMplsInProfileOctetsFc6       OBJECT-TYPE
    SYNTAX      Counter64
    MAX-ACCESS  read-only
    STATUS      current
    DESCRIPTION
        "The value of vRtrMplsInProfileOctetsFc6 indicates the number of in
         profile octets received for Forwarding Class 6."
    ::= { vRtrMplsLspStatisticsEntry 43 }

vRtrMplsInProfileOctetsFc6Low32  OBJECT-TYPE
    SYNTAX      Counter32
    MAX-ACCESS  read-only
    STATUS      current
    DESCRIPTION
        "The value of vRtrMplsInProfileOctetsFc6Low32 indicates the lower 32
         bits of the value of vRtrMplsInProfileOctetsFc6."
    ::= { vRtrMplsLspStatisticsEntry 44 }

vRtrMplsInProfileOctetsFc6High32 OBJECT-TYPE
    SYNTAX      Counter32
    MAX-ACCESS  read-only
    STATUS      current
    DESCRIPTION
        "The value of vRtrMplsInProfileOctetsFc6High32 indicates the higher 32
         bits of the value of vRtrMplsInProfileOctetsFc6."
    ::= { vRtrMplsLspStatisticsEntry 45 }

vRtrMplsInProfileOctetsFc7       OBJECT-TYPE
    SYNTAX      Counter64
    MAX-ACCESS  read-only
    STATUS      current
    DESCRIPTION
        "The value of vRtrMplsInProfileOctetsFc7 indicates the number of in
         profile octets received for Forwarding Class 7."
    ::= { vRtrMplsLspStatisticsEntry 46 }

vRtrMplsInProfileOctetsFc7Low32  OBJECT-TYPE
    SYNTAX      Counter32
    MAX-ACCESS  read-only
    STATUS      current
    DESCRIPTION
        "The value of vRtrMplsInProfileOctetsFc7Low32 indicates the lower 32
         bits of the value of vRtrMplsInProfileOctetsFc7."
    ::= { vRtrMplsLspStatisticsEntry 47 }

vRtrMplsInProfileOctetsFc7High32 OBJECT-TYPE
    SYNTAX      Counter32
    MAX-ACCESS  read-only
    STATUS      current
    DESCRIPTION
        "The value of vRtrMplsInProfileOctetsFc7High32 indicates the higher 32
         bits of the value of vRtrMplsInProfileOctetsFc7."
    ::= { vRtrMplsLspStatisticsEntry 48 }

vRtrMplsOutOfProfPktsFc0         OBJECT-TYPE
    SYNTAX      Counter64
    MAX-ACCESS  read-only
    STATUS      current
    DESCRIPTION
        "The value of vRtrMplsOutOfProfPktsFc0 indicates the number of out of
         profile packets received for Forwarding Class 0."
    ::= { vRtrMplsLspStatisticsEntry 49 }

vRtrMplsOutOfProfPktsFc0Low32    OBJECT-TYPE
    SYNTAX      Counter32
    MAX-ACCESS  read-only
    STATUS      current
    DESCRIPTION
        "The value of vRtrMplsOutOfProfPktsFc0Low32 indicates the lower 32 bits
         of the value of vRtrMplsOutOfProfPktsFc0."
    ::= { vRtrMplsLspStatisticsEntry 50 }

vRtrMplsOutOfProfPktsFc0High32   OBJECT-TYPE
    SYNTAX      Counter32
    MAX-ACCESS  read-only
    STATUS      current
    DESCRIPTION
        "The value of vRtrMplsOutOfProfPktsFc0High32 indicates the higher 32
         bits of the value of vRtrMplsOutOfProfPktsFc0."
    ::= { vRtrMplsLspStatisticsEntry 51 }

vRtrMplsOutOfProfPktsFc1         OBJECT-TYPE
    SYNTAX      Counter64
    MAX-ACCESS  read-only
    STATUS      current
    DESCRIPTION
        "The value of vRtrMplsOutOfProfPktsFc1 indicates the number of out of
         profile packets received for Forwarding Class 1."
    ::= { vRtrMplsLspStatisticsEntry 52 }

vRtrMplsOutOfProfPktsFc1Low32    OBJECT-TYPE
    SYNTAX      Counter32
    MAX-ACCESS  read-only
    STATUS      current
    DESCRIPTION
        "The value of vRtrMplsOutOfProfPktsFc1Low32 indicates the lower 32 bits
         of the value of vRtrMplsOutOfProfPktsFc1."
    ::= { vRtrMplsLspStatisticsEntry 53 }

vRtrMplsOutOfProfPktsFc1High32   OBJECT-TYPE
    SYNTAX      Counter32
    MAX-ACCESS  read-only
    STATUS      current
    DESCRIPTION
        "The value of vRtrMplsOutOfProfPktsFc1High32 indicates the higher 32
         bits of the value of vRtrMplsOutOfProfPktsFc1."
    ::= { vRtrMplsLspStatisticsEntry 54 }

vRtrMplsOutOfProfPktsFc2         OBJECT-TYPE
    SYNTAX      Counter64
    MAX-ACCESS  read-only
    STATUS      current
    DESCRIPTION
        "The value of vRtrMplsOutOfProfPktsFc2 indicates the number of out of
         profile packets received for Forwarding Class 2."
    ::= { vRtrMplsLspStatisticsEntry 55 }

vRtrMplsOutOfProfPktsFc2Low32    OBJECT-TYPE
    SYNTAX      Counter32
    MAX-ACCESS  read-only
    STATUS      current
    DESCRIPTION
        "The value of vRtrMplsOutOfProfPktsFc2Low32 indicates the lower 32 bits
         of the value of vRtrMplsOutOfProfPktsFc2."
    ::= { vRtrMplsLspStatisticsEntry 56 }

vRtrMplsOutOfProfPktsFc2High32   OBJECT-TYPE
    SYNTAX      Counter32
    MAX-ACCESS  read-only
    STATUS      current
    DESCRIPTION
        "The value of vRtrMplsOutOfProfPktsFc2High32 indicates the higher 32
         bits of the value of vRtrMplsOutOfProfPktsFc2."
    ::= { vRtrMplsLspStatisticsEntry 57 }

vRtrMplsOutOfProfPktsFc3         OBJECT-TYPE
    SYNTAX      Counter64
    MAX-ACCESS  read-only
    STATUS      current
    DESCRIPTION
        "The value of vRtrMplsOutOfProfPktsFc3 indicates the number of out of
         profile packets received for Forwarding Class 3."
    ::= { vRtrMplsLspStatisticsEntry 58 }

vRtrMplsOutOfProfPktsFc3Low32    OBJECT-TYPE
    SYNTAX      Counter32
    MAX-ACCESS  read-only
    STATUS      current
    DESCRIPTION
        "The value of vRtrMplsOutOfProfPktsFc3Low32 indicates the lower 32 bits
         of the value of vRtrMplsOutOfProfPktsFc3."
    ::= { vRtrMplsLspStatisticsEntry 59 }

vRtrMplsOutOfProfPktsFc3High32   OBJECT-TYPE
    SYNTAX      Counter32
    MAX-ACCESS  read-only
    STATUS      current
    DESCRIPTION
        "The value of vRtrMplsOutOfProfPktsFc3High32 indicates the higher 32
         bits of the value of vRtrMplsOutOfProfPktsFc3."
    ::= { vRtrMplsLspStatisticsEntry 60 }

vRtrMplsOutOfProfPktsFc4         OBJECT-TYPE
    SYNTAX      Counter64
    MAX-ACCESS  read-only
    STATUS      current
    DESCRIPTION
        "The value of vRtrMplsOutOfProfPktsFc4 indicates the number of out of
         profile packets received for Forwarding Class 4."
    ::= { vRtrMplsLspStatisticsEntry 61 }

vRtrMplsOutOfProfPktsFc4Low32    OBJECT-TYPE
    SYNTAX      Counter32
    MAX-ACCESS  read-only
    STATUS      current
    DESCRIPTION
        "The value of vRtrMplsOutOfProfPktsFc4Low32 indicates the lower 32 bits
         of the value of vRtrMplsOutOfProfPktsFc4."
    ::= { vRtrMplsLspStatisticsEntry 62 }

vRtrMplsOutOfProfPktsFc4High32   OBJECT-TYPE
    SYNTAX      Counter32
    MAX-ACCESS  read-only
    STATUS      current
    DESCRIPTION
        "The value of vRtrMplsOutOfProfPktsFc4High32 indicates the higher 32
         bits of the value of vRtrMplsOutOfProfPktsFc4."
    ::= { vRtrMplsLspStatisticsEntry 63 }

vRtrMplsOutOfProfPktsFc5         OBJECT-TYPE
    SYNTAX      Counter64
    MAX-ACCESS  read-only
    STATUS      current
    DESCRIPTION
        "The value of vRtrMplsOutOfProfPktsFc5 indicates the number of out of
         profile packets received for Forwarding Class 5."
    ::= { vRtrMplsLspStatisticsEntry 64 }

vRtrMplsOutOfProfPktsFc5Low32    OBJECT-TYPE
    SYNTAX      Counter32
    MAX-ACCESS  read-only
    STATUS      current
    DESCRIPTION
        "The value of vRtrMplsOutOfProfPktsFc5Low32 indicates the lower 32 bits
         of the value of vRtrMplsOutOfProfPktsFc5."
    ::= { vRtrMplsLspStatisticsEntry 65 }

vRtrMplsOutOfProfPktsFc5High32   OBJECT-TYPE
    SYNTAX      Counter32
    MAX-ACCESS  read-only
    STATUS      current
    DESCRIPTION
        "The value of vRtrMplsOutOfProfPktsFc5High32 indicates the higher 32
         bits of the value of vRtrMplsOutOfProfPktsFc5."
    ::= { vRtrMplsLspStatisticsEntry 66 }

vRtrMplsOutOfProfPktsFc6         OBJECT-TYPE
    SYNTAX      Counter64
    MAX-ACCESS  read-only
    STATUS      current
    DESCRIPTION
        "The value of vRtrMplsOutOfProfPktsFc6 indicates the number of out of
         profile packets received for Forwarding Class 6."
    ::= { vRtrMplsLspStatisticsEntry 67 }

vRtrMplsOutOfProfPktsFc6Low32    OBJECT-TYPE
    SYNTAX      Counter32
    MAX-ACCESS  read-only
    STATUS      current
    DESCRIPTION
        "The value of vRtrMplsOutOfProfPktsFc6Low32 indicates the lower 32 bits
         of the value of vRtrMplsOutOfProfPktsFc6."
    ::= { vRtrMplsLspStatisticsEntry 68 }

vRtrMplsOutOfProfPktsFc6High32   OBJECT-TYPE
    SYNTAX      Counter32
    MAX-ACCESS  read-only
    STATUS      current
    DESCRIPTION
        "The value of vRtrMplsOutOfProfPktsFc6High32 indicates the higher 32
         bits of the value of vRtrMplsOutOfProfPktsFc6."
    ::= { vRtrMplsLspStatisticsEntry 69 }

vRtrMplsOutOfProfPktsFc7         OBJECT-TYPE
    SYNTAX      Counter64
    MAX-ACCESS  read-only
    STATUS      current
    DESCRIPTION
        "The value of vRtrMplsOutOfProfPktsFc7 indicates the number of out of
         profile packets received for Forwarding Class 7."
    ::= { vRtrMplsLspStatisticsEntry 70 }

vRtrMplsOutOfProfPktsFc7Low32    OBJECT-TYPE
    SYNTAX      Counter32
    MAX-ACCESS  read-only
    STATUS      current
    DESCRIPTION
        "The value of vRtrMplsOutOfProfPktsFc7Low32 indicates the lower 32 bits
         of the value of vRtrMplsOutOfProfPktsFc7."
    ::= { vRtrMplsLspStatisticsEntry 71 }

vRtrMplsOutOfProfPktsFc7High32   OBJECT-TYPE
    SYNTAX      Counter32
    MAX-ACCESS  read-only
    STATUS      current
    DESCRIPTION
        "The value of vRtrMplsOutOfProfPktsFc7High32 indicates the higher 32
         bits of the value of vRtrMplsOutOfProfPktsFc7."
    ::= { vRtrMplsLspStatisticsEntry 72 }

vRtrMplsOutOfProfOctetsFc0       OBJECT-TYPE
    SYNTAX      Counter64
    MAX-ACCESS  read-only
    STATUS      current
    DESCRIPTION
        "The value of vRtrMplsOutOfProfOctetsFc0 indicates the number of out of
         profile octets received for Forwarding Class 0."
    ::= { vRtrMplsLspStatisticsEntry 73 }

vRtrMplsOutOfProfOctetsFc0Low32  OBJECT-TYPE
    SYNTAX      Counter32
    MAX-ACCESS  read-only
    STATUS      current
    DESCRIPTION
        "The value of vRtrMplsOutOfProfOctetsFc0Low32 indicates the lower 32
         bits of the value of vRtrMplsOutOfProfOctetsFc0."
    ::= { vRtrMplsLspStatisticsEntry 74 }

vRtrMplsOutOfProfOctetsFc0High32 OBJECT-TYPE
    SYNTAX      Counter32
    MAX-ACCESS  read-only
    STATUS      current
    DESCRIPTION
        "The value of vRtrMplsOutOfProfOctetsFc0High32 indicates the higher 32
         bits of the value of vRtrMplsOutOfProfOctetsFc0."
    ::= { vRtrMplsLspStatisticsEntry 75 }

vRtrMplsOutOfProfOctetsFc1       OBJECT-TYPE
    SYNTAX      Counter64
    MAX-ACCESS  read-only
    STATUS      current
    DESCRIPTION
        "The value of vRtrMplsOutOfProfOctetsFc1 indicates the number of out of
         profile octets received for Forwarding Class 1."
    ::= { vRtrMplsLspStatisticsEntry 76 }

vRtrMplsOutOfProfOctetsFc1Low32  OBJECT-TYPE
    SYNTAX      Counter32
    MAX-ACCESS  read-only
    STATUS      current
    DESCRIPTION
        "The value of vRtrMplsOutOfProfOctetsFc1Low32 indicates the lower 32
         bits of the value of vRtrMplsOutOfProfOctetsFc1."
    ::= { vRtrMplsLspStatisticsEntry 77 }

vRtrMplsOutOfProfOctetsFc1High32 OBJECT-TYPE
    SYNTAX      Counter32
    MAX-ACCESS  read-only
    STATUS      current
    DESCRIPTION
        "The value of vRtrMplsOutOfProfOctetsFc1High32 indicates the higher 32
         bits of the value of vRtrMplsOutOfProfOctetsFc1."
    ::= { vRtrMplsLspStatisticsEntry 78 }

vRtrMplsOutOfProfOctetsFc2       OBJECT-TYPE
    SYNTAX      Counter64
    MAX-ACCESS  read-only
    STATUS      current
    DESCRIPTION
        "The value of vRtrMplsOutOfProfOctetsFc2 indicates the number of out of
         profile octets received for Forwarding Class 2."
    ::= { vRtrMplsLspStatisticsEntry 79 }

vRtrMplsOutOfProfOctetsFc2Low32  OBJECT-TYPE
    SYNTAX      Counter32
    MAX-ACCESS  read-only
    STATUS      current
    DESCRIPTION
        "The value of vRtrMplsOutOfProfOctetsFc2Low32 indicates the lower 32
         bits of the value of vRtrMplsOutOfProfOctetsFc2."
    ::= { vRtrMplsLspStatisticsEntry 80 }

vRtrMplsOutOfProfOctetsFc2High32 OBJECT-TYPE
    SYNTAX      Counter32
    MAX-ACCESS  read-only
    STATUS      current
    DESCRIPTION
        "The value of vRtrMplsOutOfProfOctetsFc2High32 indicates the higher 32
         bits of the value of vRtrMplsOutOfProfOctetsFc2."
    ::= { vRtrMplsLspStatisticsEntry 81 }

vRtrMplsOutOfProfOctetsFc3       OBJECT-TYPE
    SYNTAX      Counter64
    MAX-ACCESS  read-only
    STATUS      current
    DESCRIPTION
        "The value of vRtrMplsOutOfProfOctetsFc3 indicates the number of out of
         profile octets received for Forwarding Class 3."
    ::= { vRtrMplsLspStatisticsEntry 82 }

vRtrMplsOutOfProfOctetsFc3Low32  OBJECT-TYPE
    SYNTAX      Counter32
    MAX-ACCESS  read-only
    STATUS      current
    DESCRIPTION
        "The value of vRtrMplsOutOfProfOctetsFc3Low32 indicates the lower 32
         bits of the value of vRtrMplsOutOfProfOctetsFc3."
    ::= { vRtrMplsLspStatisticsEntry 83 }

vRtrMplsOutOfProfOctetsFc3High32 OBJECT-TYPE
    SYNTAX      Counter32
    MAX-ACCESS  read-only
    STATUS      current
    DESCRIPTION
        "The value of vRtrMplsOutOfProfOctetsFc3High32 indicates the higher 32
         bits of the value of vRtrMplsOutOfProfOctetsFc3."
    ::= { vRtrMplsLspStatisticsEntry 84 }

vRtrMplsOutOfProfOctetsFc4       OBJECT-TYPE
    SYNTAX      Counter64
    MAX-ACCESS  read-only
    STATUS      current
    DESCRIPTION
        "The value of vRtrMplsOutOfProfOctetsFc4 indicates the number of out of
         profile octets received for Forwarding Class 4."
    ::= { vRtrMplsLspStatisticsEntry 85 }

vRtrMplsOutOfProfOctetsFc4Low32  OBJECT-TYPE
    SYNTAX      Counter32
    MAX-ACCESS  read-only
    STATUS      current
    DESCRIPTION
        "The value of vRtrMplsOutOfProfOctetsFc4Low32 indicates the lower 32
         bits of the value of vRtrMplsOutOfProfOctetsFc4."
    ::= { vRtrMplsLspStatisticsEntry 86 }

vRtrMplsOutOfProfOctetsFc4High32 OBJECT-TYPE
    SYNTAX      Counter32
    MAX-ACCESS  read-only
    STATUS      current
    DESCRIPTION
        "The value of vRtrMplsOutOfProfOctetsFc4High32 indicates the higher 32
         bits of the value of vRtrMplsOutOfProfOctetsFc4."
    ::= { vRtrMplsLspStatisticsEntry 87 }

vRtrMplsOutOfProfOctetsFc5       OBJECT-TYPE
    SYNTAX      Counter64
    MAX-ACCESS  read-only
    STATUS      current
    DESCRIPTION
        "The value of vRtrMplsOutOfProfOctetsFc5 indicates the number of out of
         profile octets received for Forwarding Class 5."
    ::= { vRtrMplsLspStatisticsEntry 88 }

vRtrMplsOutOfProfOctetsFc5Low32  OBJECT-TYPE
    SYNTAX      Counter32
    MAX-ACCESS  read-only
    STATUS      current
    DESCRIPTION
        "The value of vRtrMplsOutOfProfOctetsFc5Low32 indicates the lower 32
         bits of the value of vRtrMplsOutOfProfOctetsFc5."
    ::= { vRtrMplsLspStatisticsEntry 89 }

vRtrMplsOutOfProfOctetsFc5High32 OBJECT-TYPE
    SYNTAX      Counter32
    MAX-ACCESS  read-only
    STATUS      current
    DESCRIPTION
        "The value of vRtrMplsOutOfProfOctetsFc5High32 indicates the higher 32
         bits of the value of vRtrMplsOutOfProfOctetsFc5."
    ::= { vRtrMplsLspStatisticsEntry 90 }

vRtrMplsOutOfProfOctetsFc6       OBJECT-TYPE
    SYNTAX      Counter64
    MAX-ACCESS  read-only
    STATUS      current
    DESCRIPTION
        "The value of vRtrMplsOutOfProfOctetsFc6 indicates the number of out of
         profile octets received for Forwarding Class 6."
    ::= { vRtrMplsLspStatisticsEntry 91 }

vRtrMplsOutOfProfOctetsFc6Low32  OBJECT-TYPE
    SYNTAX      Counter32
    MAX-ACCESS  read-only
    STATUS      current
    DESCRIPTION
        "The value of vRtrMplsOutOfProfOctetsFc6Low32 indicates the lower 32
         bits of the value of vRtrMplsOutOfProfOctetsFc6."
    ::= { vRtrMplsLspStatisticsEntry 92 }

vRtrMplsOutOfProfOctetsFc6High32 OBJECT-TYPE
    SYNTAX      Counter32
    MAX-ACCESS  read-only
    STATUS      current
    DESCRIPTION
        "The value of vRtrMplsOutOfProfOctetsFc6High32 indicates the higher 32
         bits of the value of vRtrMplsOutOfProfOctetsFc6."
    ::= { vRtrMplsLspStatisticsEntry 93 }

vRtrMplsOutOfProfOctetsFc7       OBJECT-TYPE
    SYNTAX      Counter64
    MAX-ACCESS  read-only
    STATUS      current
    DESCRIPTION
        "The value of vRtrMplsOutOfProfOctetsFc7 indicates the number of out of
         profile octets received for Forwarding Class 7."
    ::= { vRtrMplsLspStatisticsEntry 94 }

vRtrMplsOutOfProfOctetsFc7Low32  OBJECT-TYPE
    SYNTAX      Counter32
    MAX-ACCESS  read-only
    STATUS      current
    DESCRIPTION
        "The value of vRtrMplsOutOfProfOctetsFc7Low32 indicates the lower 32
         bits of the value of vRtrMplsOutOfProfOctetsFc7."
    ::= { vRtrMplsLspStatisticsEntry 95 }

vRtrMplsOutOfProfOctetsFc7High32 OBJECT-TYPE
    SYNTAX      Counter32
    MAX-ACCESS  read-only
    STATUS      current
    DESCRIPTION
        "The value of vRtrMplsOutOfProfOctetsFc7High32 indicates the higher 32
         bits of the value of vRtrMplsOutOfProfOctetsFc7."
    ::= { vRtrMplsLspStatisticsEntry 96 }

vRtrMplsLspStatsPSBMatch         OBJECT-TYPE
    SYNTAX      TruthValue
    MAX-ACCESS  read-only
    STATUS      current
    DESCRIPTION
        "The value of vRtrMplsLspStatsPSBMatch indicates if a path state block
         (PSB) match was made against this LSP name."
    ::= { vRtrMplsLspStatisticsEntry 97 }

vRtrMplsLspStatsTpOnly           OBJECT-TYPE
    SYNTAX      TruthValue
    MAX-ACCESS  read-only
    STATUS      current
    DESCRIPTION
        "The value of vRtrMplsLspStatsTpOnly indicates whether the statistics
         apply to mpls-tp lsp or for regular rsvp-te signalled terminating LSP.

         The value of 'true' indicates the statistics apply to mpls-tp LSP
         only.

         The value of 'false' indicates the statistics apply for regular
         rsvp-te signalled terminating LSP."
    ::= { vRtrMplsLspStatisticsEntry 98 }

vRtrMplsLspStatsLspType          OBJECT-TYPE
    SYNTAX      INTEGER {
        unknown     (0),
        p2p         (1),
        p2mp        (2),
        autoP2p     (3),
        autoP2mp    (4),
        tpLsp       (5),
        srTe        (6),
        autoSrTe    (7),
        pceInitSrTe (8)
    }
    MAX-ACCESS  read-only
    STATUS      current
    DESCRIPTION
        "The value of vRtrMplsLspStatsLspType indicates whether the statistics
         apply to MPLS-TP, P2P, P2MP, SR-TE, PCE-INIT SR-TE, Auto P2P, Auto
         SR-TE  or Auto P2MP LSP.

         When the value of vRtrMplsLspStatsTpOnly is 'true', the statistics
         apply for MPLS-TP LSP only and vRtrMplsLspStatsLspType is set to
         'tpLsp'.

         When the value of vRtrMplsLspStatsTpOnly is 'false', the statistics
         apply for regular RSVP-TE signalled terminating LSP and the value of
         vRtrMplsLspStatsLspType can be set to either p2p, p2mp, srTE,
         pceInitSrTe, autoP2p, autoSrTe or autoP2mp."
    ::= { vRtrMplsLspStatisticsEntry 99 }

vRtrMplsLspAggregatePkts         OBJECT-TYPE
    SYNTAX      Counter64
    MAX-ACCESS  read-only
    STATUS      current
    DESCRIPTION
        "The value of vRtrMplsLspAggregatePkts indicates the sum total of all
         in profile  and out profile packets received for all Forwarding
         Classes."
    ::= { vRtrMplsLspStatisticsEntry 100 }

vRtrMplsLspAggregateOctets       OBJECT-TYPE
    SYNTAX      Counter64
    MAX-ACCESS  read-only
    STATUS      current
    DESCRIPTION
        "The value of vRtrMplsLspAggregateOctets indicates the sum total of all
         in profile  and out profile octets received for all Forwarding
         Classes."
    ::= { vRtrMplsLspStatisticsEntry 101 }

vRtrMplsLspTemplateTblLastChgd   OBJECT-TYPE
    SYNTAX      TimeStamp
    MAX-ACCESS  read-only
    STATUS      current
    DESCRIPTION
        "The value of vRtrMplsLspTemplateTblLastChgd indicates the sysUpTime at
         the time of the last modification of an entry in the
         vRtrMplsLspTemplateTable.

         If no changes were made to the table since the last re-initialization
         of the local network management subsystem, then this object contains a
         zero value."
    ::= { tmnxMplsObjs 40 }

vRtrMplsLspTemplateTable         OBJECT-TYPE
    SYNTAX      SEQUENCE OF VRtrMplsLspTemplateEntry
    MAX-ACCESS  not-accessible
    STATUS      current
    DESCRIPTION
        "The vRtrMplsLspTemplateTable has an entry for each Labeled Switch Path
         Template(LSP Template) configured for a virtual router in the system.

         The table contains a list of LSP Templates that are referenced when
         dynamic LSP creation is required."
    ::= { tmnxMplsObjs 41 }

vRtrMplsLspTemplateEntry         OBJECT-TYPE
    SYNTAX      VRtrMplsLspTemplateEntry
    MAX-ACCESS  not-accessible
    STATUS      current
    DESCRIPTION
        "Each row entry represents a Labeled Switch Path Template (LSP
         Template) configured for a virtual router in the system.

         Entries in this table can be created and deleted via SNMP SET
         operations."
    INDEX       {
        vRtrID,
        vRtrMplsLspTemplateName
    }
    ::= { vRtrMplsLspTemplateTable 1 }

VRtrMplsLspTemplateEntry         ::= SEQUENCE
{
    vRtrMplsLspTemplateName          TNamedItem,
    vRtrMplsLspTemplateRowStatus     RowStatus,
    vRtrMplsLspTemplateLastChanged   TimeStamp,
    vRtrMplsLspTemplateAdminState    TmnxAdminState,
    vRtrMplsLspTemplateType          INTEGER,
    vRtrMplsLspTemplateAdaptive      TruthValue,
    vRtrMplsLspTemplateBandwidth     Integer32,
    vRtrMplsLspTemplateCspf          TruthValue,
    vRtrMplsLspTemplateDefaultPath   MplsTunnelIndex,
    vRtrMplsLspTemplateAdmGrpIncl    Unsigned32,
    vRtrMplsLspTemplateAdmGrpExcl    Unsigned32,
    vRtrMplsLspTemplateFastReroute   TruthValue,
    vRtrMplsLspTemplateFRMethod      INTEGER,
    vRtrMplsLspTemplateFRHopLimit    Unsigned32,
    vRtrMplsLspTemplateHopLimit      Unsigned32,
    vRtrMplsLspTemplateRecord        INTEGER,
    vRtrMplsLspTemplateRecordLabel   INTEGER,
    vRtrMplsLspTemplateRetryLimit    Unsigned32,
    vRtrMplsLspTemplateRetryTimer    Unsigned32,
    vRtrMplsLspTemplateCspfTeMetric  TruthValue,
    vRtrMplsLspTemplateLspCount      Gauge32,
    vRtrMplsLspTemplateMvpnRefCount  Gauge32,
    vRtrMplsLspTemplateFRPropAdmGrp  TruthValue,
    vRtrMplsLspTemplatePropAdmGrp    TruthValue,
    vRtrMplsLspTemplateBgpShortcut   TruthValue,
    vRtrMplsLspTemplateIgpShortcut   TruthValue,
    vRtrMplsLspTemplateLdpOverRsvp   TruthValue,
    vRtrMplsLspTemplateLeastFill     TruthValue,
    vRtrMplsLspTemplateMetric        Unsigned32,
    vRtrMplsLspTemplateSetupPriority Unsigned32,
    vRtrMplsLspTemplateHoldPriority  Unsigned32,
    vRtrMplsLspTemplateVprnAutoBind  TruthValue,
    vRtrMplsLspTempIgpSCutLfaType    INTEGER,
    vRtrMplsLspTempIgpSCutRelOffset  Integer32,
    vRtrMplsLspTempAutoBandwidth     TruthValue,
    vRtrMplsLspTempFRNodeProtect     TruthValue,
    vRtrMplsLspTemplateEgrStats      TruthValue,
    vRtrMplsLspTempCollectStats      TruthValue,
    vRtrMplsLspTempAccntingPolicy    Unsigned32,
    vRtrMplsLspTemplateFromAddrType  InetAddressType,
    vRtrMplsLspTemplateFromAddr      InetAddress,
    vRtrMplsLspTemplateClassType     TmnxRsvpDSTEClassType,
    vRtrMplsLspTempBkupClassType     TmnxRsvpDSTEClassType,
    vRtrMplsLspTempBgpTransportTunn  TmnxMplsLspBgpRSVPLSPTunState,
    vRtrMplsLspTempMainCTRetryLimit  Unsigned32,
    vRtrMplsLspTemplateRsvpAdspec    TruthValue,
    vRtrMplsLspTempLoadBalancingWt   Unsigned32,
    vRtrMplsLspTempClassFwdEnabled   TruthValue,
    vRtrMplsLspTempFC                TmnxCBFClasses,
    vRtrMplsLspTempBfdTemplateName   TNamedItemOrEmpty,
    vRtrMplsLspTempBfdEnable         TruthValue,
    vRtrMplsLspTempBfdPingIntvl      Unsigned32,
    vRtrMplsLspTempEntropyLabel      INTEGER,
    vRtrMplsLspTemplatePceReport     INTEGER,
    vRtrMplsLspTempMaxSrLabels       Unsigned32,
    vRtrMplsLspTempFrrOverheadLabel  Unsigned32,
    vRtrMplsLspTempBfdFailureAction  INTEGER,
    vRtrMplsLspTempCbfFwdingPlcy     TNamedItemOrEmpty,
    vRtrMplsLspTempCbfFwdingSet      Unsigned32,
    vRtrMplsLspTemplateId            Unsigned32,
    vRtrMplsLspTempPathCompMeth      INTEGER,
    vRtrMplsLspTempMetricType        INTEGER,
    vRtrMplsLspTempLocalSrProt       INTEGER,
    vRtrMplsLspTempLabelStackRed     TruthValue,
    vRtrMplsLspTempBfdUpWaitTimer    Unsigned32,
    vRtrMplsLspTempSelfPing          INTEGER
}

vRtrMplsLspTemplateName          OBJECT-TYPE
    SYNTAX      TNamedItem
    MAX-ACCESS  not-accessible
    STATUS      current
    DESCRIPTION
        "The value of the object vRtrMplsLspTemplateName specifies the name of
         the LSP Template which is used as a guideline to create and signal
         multiple LSP instances when dynamic LSP creation is required."
    ::= { vRtrMplsLspTemplateEntry 1 }

vRtrMplsLspTemplateRowStatus     OBJECT-TYPE
    SYNTAX      RowStatus
    MAX-ACCESS  read-create
    STATUS      current
    DESCRIPTION
        "The value of vRtrMplsLspTemplateRowStatus specifies the Row Status for
         this entry."
    ::= { vRtrMplsLspTemplateEntry 2 }

vRtrMplsLspTemplateLastChanged   OBJECT-TYPE
    SYNTAX      TimeStamp
    MAX-ACCESS  read-only
    STATUS      current
    DESCRIPTION
        "The value of vRtrMplsLspTemplateLastChanged indicates the timestamp of
         last change to this row in vRtrMplsLspTemplateTable."
    ::= { vRtrMplsLspTemplateEntry 3 }

vRtrMplsLspTemplateAdminState    OBJECT-TYPE
    SYNTAX      TmnxAdminState
    MAX-ACCESS  read-create
    STATUS      current
    DESCRIPTION
        "The value of vRtrMplsLspTemplateAdminState specifies the current
         administrative state of the LSP Template."
    DEFVAL      { outOfService }
    ::= { vRtrMplsLspTemplateEntry 4 }

vRtrMplsLspTemplateType          OBJECT-TYPE
    SYNTAX      INTEGER {
        unknown        (0),
        p2mp           (1),
        onehopP2P      (2),
        meshP2P        (3),
        onehopP2PSrTe  (4),
        meshP2PSrTe    (5),
        pceInitP2PSrTe (6)
    }
    MAX-ACCESS  read-create
    STATUS      current
    DESCRIPTION
        "The value of vRtrMplsLspTemplateType specifies the type of the LSP
         template.

         The value of vRtrMplsLspTemplateType means:
         'p2mp (1)'         - auto creation of P2MP LSPs.
         'onehopP2P (2)'    - auto creation of one-Hop P2P LSPs.
         'meshP2P (3)'      - auto creation of mesh P2P LSPs.
         'onehopP2PSrTe (4)'- auto creation of one-Hop P2P SrTe LSPs.
         'meshP2PSrTe (5)'  - auto creation of mesh P2P SrTe LSPs.
         'pceInitP2PSrTe (6)'- auto creation of PCE-Initiated P2P SR-Te LSPs."
    DEFVAL      { unknown }
    ::= { vRtrMplsLspTemplateEntry 5 }

vRtrMplsLspTemplateAdaptive      OBJECT-TYPE
    SYNTAX      TruthValue
    MAX-ACCESS  read-create
    STATUS      current
    DESCRIPTION
        "The value of vRtrMplsLspTemplateAdaptive specifies whether the
         make-before-break functionality is enabled for the LSPs that are
         dynamically created using this LSP template.

         When the value of vRtrMplsLspTemplateAdaptive is set to 'true',
         make-before-break functionality is enabled. When the value is set to
         'false' make-before-break functionality is disabled."
    DEFVAL      { true }
    ::= { vRtrMplsLspTemplateEntry 6 }

vRtrMplsLspTemplateBandwidth     OBJECT-TYPE
    SYNTAX      Integer32 (0..6400000)
    UNITS       "megabps"
    MAX-ACCESS  read-create
    STATUS      current
    DESCRIPTION
        "The value of vRtrMplsLspTemplateBandwidth specifies the amount of
         bandwidth in megabits per seconds (Mbps) to be reserved for the LSPs
         that are dynamically created using this LSP template. A value of zero
         (0) indicates that no bandwidth is reserved."
    DEFVAL      { 0 }
    ::= { vRtrMplsLspTemplateEntry 7 }

vRtrMplsLspTemplateCspf          OBJECT-TYPE
    SYNTAX      TruthValue
    MAX-ACCESS  read-create
    STATUS      obsolete
    DESCRIPTION
        "The value of vRtrMplsLspTemplateCspf specifies whether the CSPF
         computation for constrained-path LSP is enabled for the LSPs that are
         dynamically created using this LSP template.

         When the value of vRtrMplsLspTemplateCspf is set to 'true', CSPF
         computation for constrained-path is enabled. When the value is set to
         'false', CSPF computation for constrained-path is disabled."
    DEFVAL      { false }
    ::= { vRtrMplsLspTemplateEntry 8 }

vRtrMplsLspTemplateDefaultPath   OBJECT-TYPE
    SYNTAX      MplsTunnelIndex
    MAX-ACCESS  read-create
    STATUS      current
    DESCRIPTION
        "The value of vRtrMplsLspTemplateDefaultPath specifies the default path
         used to signal LSPs that are dynamically created using this LSP
         template.

         If a corresponding index does not exist in
         MPLS-TE-MIB::mplsTunnelTable, an 'inconsistentValue' error will be
         returned. "
    DEFVAL      { 0 }
    ::= { vRtrMplsLspTemplateEntry 9 }

vRtrMplsLspTemplateAdmGrpIncl    OBJECT-TYPE
    SYNTAX      Unsigned32
    MAX-ACCESS  read-create
    STATUS      current
    DESCRIPTION
        "The value of vRtrMplsLspTemplateAdmGrpIncl specifies a bit-map of
         admin groups that are included when the dynamically created LSPs using
         this template are setup .

         If bit 'n' is set, then the admin group with value 'n' is included.
         This implies that each link that the LSP goes through must be
         associated with at least one of the admin groups in the include list.

         By default, all admin groups are in the include list."
    DEFVAL      { '00000000'H }
    ::= { vRtrMplsLspTemplateEntry 10 }

vRtrMplsLspTemplateAdmGrpExcl    OBJECT-TYPE
    SYNTAX      Unsigned32
    MAX-ACCESS  read-create
    STATUS      current
    DESCRIPTION
        "The value of vRtrMplsLspTemplateAdmGrpExcl specifies a bit-map of
         admin groups that are excluded when the dynamically created LSPs using
         this template are setup.

         If bit 'n' is set, then the admin group with value 'n' is excluded.
         This implies that each link that the LSP goes through must not be
         associated with any of the admin groups in the exclude list.

         By default, no admin groups are in the exclude list."
    DEFVAL      { '00000000'H }
    ::= { vRtrMplsLspTemplateEntry 11 }

vRtrMplsLspTemplateFastReroute   OBJECT-TYPE
    SYNTAX      TruthValue
    MAX-ACCESS  read-create
    STATUS      current
    DESCRIPTION
        "The value of vRtrMplsLspTemplateFastReroute specifies whether fast
         reroute is enabled for the LSPs that are dynamically created using
         this LSP template.

         When the value of vRtrMplsLspTemplateFastReroute is set to 'true',
         fast reroute is enabled for the LSP. When the value of
         vRtrMplsLspTemplateFastReroute is set to 'false', fast reroute is
         disabled."
    DEFVAL      { false }
    ::= { vRtrMplsLspTemplateEntry 12 }

vRtrMplsLspTemplateFRMethod      OBJECT-TYPE
    SYNTAX      INTEGER {
        oneToOneBackup (1),
        facilityBackup (2)
    }
    MAX-ACCESS  read-create
    STATUS      current
    DESCRIPTION
        "The value of vRtrMplsLspTemplateFRMethod specifies the fast reroute
         method used for the LSPs that are dynamically created using this LSP
         template.

         When the value of vRtrMplsLspTemplateFRMethod is set to
         'oneToOneBackup', a backup LSP is established which will intersect the
         original LSP somewhere downstream of the point of link or node
         failure. For each LSP that is backed up, a separate backup LSP is
         established.

         When the value of vRtrMplsLspTemplateFRMethod is set to
         'facilityBackup', Instead of creating a separate LSP for every LSP
         that is to be backed up, a single LSP is created which serves as a
         backup for a set of LSPs.

         For LSP templates of type P2MP, oneToOneBackup is not supported."
    DEFVAL      { facilityBackup }
    ::= { vRtrMplsLspTemplateEntry 13 }

vRtrMplsLspTemplateFRHopLimit    OBJECT-TYPE
    SYNTAX      Unsigned32 (0..255)
    MAX-ACCESS  read-create
    STATUS      current
    DESCRIPTION
        "The value of vRtrMplsLspTemplateFRHopLimit specifies the total number
         of hops a detour or backup LSP can take before merging back onto the
         main LSP path."
    DEFVAL      { 16 }
    ::= { vRtrMplsLspTemplateEntry 14 }

vRtrMplsLspTemplateHopLimit      OBJECT-TYPE
    SYNTAX      Unsigned32 (2..255)
    MAX-ACCESS  read-create
    STATUS      current
    DESCRIPTION
        "The value of vRtrMplsLspTemplateHopLimit specifies the maximum number
         of hops that a dynamically created LSP will traverse including the
         ingress and egress ESRs. A LSP will not be set up if the hop limit is
         exceeded."
    DEFVAL      { 255 }
    ::= { vRtrMplsLspTemplateEntry 15 }

vRtrMplsLspTemplateRecord        OBJECT-TYPE
    SYNTAX      INTEGER {
        record   (1),
        noRecord (2)
    }
    MAX-ACCESS  read-create
    STATUS      current
    DESCRIPTION
        "The value of vRtrMplsLspTemplateRecord  specifies whether the
         recording of all the hops is enabled for LSPs that are dynamically
         created using this template.

         When the value of vRtrMplsLspTemplateRecord is set to 'record',
         recording of all the hops that a LSP traverses is enabled. When the
         value of vRtrMplsLspTemplateRecord is set to 'noRecord', recording of
         all the hops that a LSP traverses is disabled."
    DEFVAL      { record }
    ::= { vRtrMplsLspTemplateEntry 16 }

vRtrMplsLspTemplateRecordLabel   OBJECT-TYPE
    SYNTAX      INTEGER {
        record   (1),
        noRecord (2)
    }
    MAX-ACCESS  read-create
    STATUS      current
    DESCRIPTION
        "The value of vRtrMplsLspTemplateRecordLabel specifies whether the
         recording of labels is enabled for LSPs that are dynamically created
         using this LSP template .

         When the value of vRtrMplsLspTemplateRecordLabel is set to 'record',
         recording of labels at each node that a LSP traverses is enabled. When
         the value of vRtrMplsLspTemplateRecordLabel is set to 'noRecord',
         recording of labels at each node that a LSP traverses is disabled."
    DEFVAL      { record }
    ::= { vRtrMplsLspTemplateEntry 17 }

vRtrMplsLspTemplateRetryLimit    OBJECT-TYPE
    SYNTAX      Unsigned32 (0..10000)
    MAX-ACCESS  read-create
    STATUS      current
    DESCRIPTION
        "The value of vRtrMplsLspTemplateRetryLimit specifies the maximum
         number of attempts made to establish an LSP that is dynamically
         created using this template. A value of zero(0) specifies that an
         infinite number of retry attempts should be made."
    DEFVAL      { 0 }
    ::= { vRtrMplsLspTemplateEntry 18 }

vRtrMplsLspTemplateRetryTimer    OBJECT-TYPE
    SYNTAX      Unsigned32 (1..600)
    UNITS       "seconds"
    MAX-ACCESS  read-create
    STATUS      current
    DESCRIPTION
        "The value of vRtrMplsLspTemplateRetryTimer specifies the time in
         seconds a dynamically created Lsp waits before it attempts to
         re-establish itself."
    DEFVAL      { 30 }
    ::= { vRtrMplsLspTemplateEntry 19 }

vRtrMplsLspTemplateCspfTeMetric  OBJECT-TYPE
    SYNTAX      TruthValue
    MAX-ACCESS  read-create
    STATUS      obsolete
    DESCRIPTION
        "The value of vRtrMplsLspTemplateCspfTeMetric specifies whether the TE
         metric is used for the purpose of the LSP path computation by CSPF
         (Constrained Shortest Path First).

         When the value of vRtrMplsLspTemplateCspfTeMetric  is set to 'true', the
         TE metric is used to compute the path of the LSP by CSPF. When the value of
         vRtrMplsLspTemplateCspfTeMetric  is set to 'false', IGP metric is used to
         compute the path of the LSP by CSPF."
    DEFVAL      { false }
    ::= { vRtrMplsLspTemplateEntry 20 }

vRtrMplsLspTemplateLspCount      OBJECT-TYPE
    SYNTAX      Gauge32
    MAX-ACCESS  read-only
    STATUS      current
    DESCRIPTION
        "The value of vRtrMplsLspTemplateLspCount indicates the number of LSPs
         of type 'p2mpAuto' that are created using this template."
    ::= { vRtrMplsLspTemplateEntry 21 }

vRtrMplsLspTemplateMvpnRefCount  OBJECT-TYPE
    SYNTAX      Gauge32
    MAX-ACCESS  read-only
    STATUS      current
    DESCRIPTION
        "The value of vRtrMplsLspTemplateMvpnRefCount indicates the number of
         MVPNs as well as number of P2MP LSP users associated to this template."
    ::= { vRtrMplsLspTemplateEntry 22 }

vRtrMplsLspTemplateFRPropAdmGrp  OBJECT-TYPE
    SYNTAX      TruthValue
    MAX-ACCESS  read-create
    STATUS      current
    DESCRIPTION
        "The value of vRtrMplsLspTemplateFRPropAdmGrp specifies whether or not
         the use of administrative group constraints on a FRR backup LSP is
         enabled.

         If vRtrMplsLspTemplateFastReroute is set to 'true', the value of
         vRtrMplsLspTemplateFRPropAdmGrp specifies whether or not the
         administrative group constraints are signaled in the
         vRtrMplsLspTemplateFastReroute object.

         If vRtrMplsLspTemplateFastReroute is set to 'false', the value of
         vRtrMplsLspTemplateFRPropAdmGrp is insignificant."
    DEFVAL      { false }
    ::= { vRtrMplsLspTemplateEntry 23 }

vRtrMplsLspTemplatePropAdmGrp    OBJECT-TYPE
    SYNTAX      TruthValue
    MAX-ACCESS  read-create
    STATUS      current
    DESCRIPTION
        "The value of vRtrMplsLspTemplatePropAdmGrp specifies whether the
         propagation of session attribute object with resource affinity
         (C-type 1) in PATH message is enabled for  the LSPs that
         are dynamically created using this LSP template.

         By default, the value of vRtrMplsLspTemplatePropAdmGrp is 'false'
         which specifies the session attribute object without resource affinity
         (C-Type 7) is propagated in PATH message and the admin groups are
         ignored on Label Switched Router(LSR) while doing CSPF calculation."
    DEFVAL      { false }
    ::= { vRtrMplsLspTemplateEntry 24 }

vRtrMplsLspTemplateBgpShortcut   OBJECT-TYPE
    SYNTAX      TruthValue
    MAX-ACCESS  read-create
    STATUS      current
    DESCRIPTION
        "The value of vRtrMplsLspTemplateBgpShortcut specifies whether to
         exclude or include a RSVP LSP from being used as a shortcut while
         resolving BGP routes.

         When the value of vRtrMplsLspTemplateBgpShortcut is set to 'true' the
         RSVP LSP is used as a shortcut while resolving BGP routes.

         When the value of vRtrMplsLspTemplateBgpShortcut is set to 'false' the
         RSVP LSP is not used as a shortcut while resolving BGP routes."
    DEFVAL      { true }
    ::= { vRtrMplsLspTemplateEntry 25 }

vRtrMplsLspTemplateIgpShortcut   OBJECT-TYPE
    SYNTAX      TruthValue
    MAX-ACCESS  read-create
    STATUS      current
    DESCRIPTION
        "The value of vRtrMplsLspTemplateIgpShortcut specifies whether to
         exclude or include a RSVP LSP from being used as a shortcut while
         resolving IGP routes.

         When the value of vRtrMplsLspTemplateIgpShortcut is set to 'true' the
         RSVP LSP is used as a shortcut while resolving IGP routes.

         When the value of vRtrMplsLspTemplateIgpShortcut is set to 'false' the
         RSVP LSP is not used as a shortcut while resolving IGP routes."
    DEFVAL      { true }
    ::= { vRtrMplsLspTemplateEntry 26 }

vRtrMplsLspTemplateLdpOverRsvp   OBJECT-TYPE
    SYNTAX      TruthValue
    MAX-ACCESS  read-create
    STATUS      current
    DESCRIPTION
        "The value of vRtrMplsLspTemplateLdpOverRsvp specifies that this LSP can
         be included by IGP to calculate its SPF tree.  The IGP (OSPF or ISIS)
         will subsequently provide LDP with all ECMP IGP next-hops and tunnel
         endpoints that it considers to be the lowest cost path to the
         destination.  If an IGP calculation and an LDP over RSVP produce the
         same cost then LDP will always prefer an LDP over RSVP tunnel over an
         IGP route.

         By default, static and dynamic LSPs will be included when they are
         created. The default value for p2mp and bypass-only LSPs will be
         'false'."
    DEFVAL      { true }
    ::= { vRtrMplsLspTemplateEntry 27 }

vRtrMplsLspTemplateLeastFill     OBJECT-TYPE
    SYNTAX      TruthValue
    MAX-ACCESS  read-create
    STATUS      current
    DESCRIPTION
        "The value of vRtrMplsLspTemplateLeastFill specifies whether the use of
         the least-fill path selection method for the computation of the path
         of this LSP template is enabled.

         By default, the path of an LSP is randomly chosen among a set of equal
         cost paths."
    DEFVAL      { false }
    ::= { vRtrMplsLspTemplateEntry 28 }

vRtrMplsLspTemplateMetric        OBJECT-TYPE
    SYNTAX      Unsigned32 (0 | 1..16777215)
    MAX-ACCESS  read-create
    STATUS      current
    DESCRIPTION
        "The value of vRtrMplsLspTemplateMetric specifies the metric for this
         LSP which is used to select an LSP among a set of LSPs which are
         destined to the same egress 7x50 router.  The LSP with the lowest
         metric will be selected.

         In LDP-over-RSVP, LDP performs a lookup in the Routing Table
         Manager (RTM) which provides the next hop to the destination PE
         and the advertising router (ABR or destination PE itself).  If the
         advertising router matches the targeted LDP peer, LDP then
         performs a second lookup for the advertising router in the Tunnel
         Table Manager (TTM). This lookup returns the best RSVP LSP to use
         to forward packets for an LDP FEC learned through the targeted
         LDP session.  The lookup returns the LSP with the lowest metric.
         If multiple LSPs have the same metric, then the result of the
         lookup will be to select the first one available in the TTM.

         A value of '0' indicates metric is not to be used."
    DEFVAL      { 0 }
    ::= { vRtrMplsLspTemplateEntry 29 }

vRtrMplsLspTemplateSetupPriority OBJECT-TYPE
    SYNTAX      Unsigned32 (0..7)
    MAX-ACCESS  read-create
    STATUS      current
    DESCRIPTION
        "The value of vRtrMplsLspTemplateSetupPriority specifies the setup
         priority to use when insufficient bandwidth is available to setup a LSP.
         The setup priority is compared against the hold priority of
         existing LSPs.  If the setup priority is higher than the hold
         priority of the established LSPs, this LSP may preempt the other
         LSPs.  A value of zero (0) is the highest priority and a value
         of seven (7) is the lowest priority."
    DEFVAL      { 7 }
    ::= { vRtrMplsLspTemplateEntry 30 }

vRtrMplsLspTemplateHoldPriority  OBJECT-TYPE
    SYNTAX      Unsigned32 (0..7)
    MAX-ACCESS  read-create
    STATUS      current
    DESCRIPTION
        "The value of vRtrMplsLspTemplateHoldPriority specifies the hold
         priority to use when insufficient bandwidth is available to setup a
         LSP. The setup priority is compared against the hold priority of
         existing LSPs.  If the setup priority is higher than the hold
         priority of the established LSPs, this LSP may preempt the other
         LSPs.  A value of zero (0) is the highest priority and a value
         of seven (7) is the lowest priority."
    DEFVAL      { 0 }
    ::= { vRtrMplsLspTemplateEntry 31 }

vRtrMplsLspTemplateVprnAutoBind  OBJECT-TYPE
    SYNTAX      TruthValue
    MAX-ACCESS  read-create
    STATUS      current
    DESCRIPTION
        "The value of vRtrMplsLspTemplateVprnAutoBind specifies whether the LSP
         can be used as part of the auto-bind feature for VPRN services. By
         default a LSP is available for inclusion to be used for the auto-bind
         feature.

         By default, static and dynamic LSPs will be included when they are
         created.  The default value for p2mp and bypass-only LSPs will
         be 'false'."
    DEFVAL      { true }
    ::= { vRtrMplsLspTemplateEntry 32 }

vRtrMplsLspTempIgpSCutLfaType    OBJECT-TYPE
    SYNTAX      INTEGER {
        none       (0),
        lfaProtect (1),
        lfaOnly    (2)
    }
    MAX-ACCESS  read-create
    STATUS      current
    DESCRIPTION
        "The value of vRtrMplsLspTempIgpSCutLfaType specifies whether to
         exclude or include a RSVP LSP from being used as a shortcut while
         resolving IGP routes in LFA SPF or whether to exclude or include a
         RSVP LSP from being used as a LFA SPF.

         When the value of vRtrMplsLspTempIgpSCutLfaType is set to 'lfaProtect'
         the RSVP LSP is used as a shortcut while resolving IGP routes in LFA
         SPF as well.

         When the value of vRtrMplsLspTempIgpSCutLfaType is set to 'lfaOnly'
         the RSVP LSP is used as a LFA SPF and not used as igp shortcut in
         regular SPF.

         An 'inconsistentValue' error is returned if an attempt is made to set
         this object to a non-default value when the value of the object
         vRtrMplsLspTemplateIgpShortcut is not set to 'true'."
    DEFVAL      { none }
    ::= { vRtrMplsLspTemplateEntry 33 }

vRtrMplsLspTempIgpSCutRelOffset  OBJECT-TYPE
    SYNTAX      Integer32 (-10..10 | 2147483647)
    MAX-ACCESS  read-create
    STATUS      current
    DESCRIPTION
        "The value of vRtrMplsLspTempIgpSCutRelOffset specifies the the
         relative offset to the IGP metric on the SPF tree.

         The SPF tree is updated with the current IGP metric of the path
         between the endpoints of the LSP minus the value of
         vRtrMplsLspTempIgpSCutRelOffset.

         The default value of 2147483647 indicates the relative metric offset
         is not to be considered."
    DEFVAL      { 2147483647 }
    ::= { vRtrMplsLspTemplateEntry 34 }

vRtrMplsLspTempAutoBandwidth     OBJECT-TYPE
    SYNTAX      TruthValue
    MAX-ACCESS  read-create
    STATUS      current
    DESCRIPTION
        "The value of the vRtrMplsLspTempAutoBandwidth specifies whether
         automatic bandwidth adjustment has been enabled or disabled for this
         LSP template.

         A value of 'true' specifies that automatic bandwidth adjustment has
         been enabled for this LSP template and a value of 'false' specifies
         that automatic bandwidth adjustment has been disabled for this LSP
         template."
    DEFVAL      { false }
    ::= { vRtrMplsLspTemplateEntry 35 }

vRtrMplsLspTempFRNodeProtect     OBJECT-TYPE
    SYNTAX      TruthValue
    MAX-ACCESS  read-create
    STATUS      current
    DESCRIPTION
        "The value of vRtrMplsLspTempFRNodeProtect specifies whether node
         protect has been enabled or disabled for this LSP template.

         A value of 'true' specifies that node protection i.e. protection
         against the failure of a node on the LSP template is enabled.

         A value of 'false' specifies that node protection is disabled."
    DEFVAL      { false }
    ::= { vRtrMplsLspTemplateEntry 36 }

vRtrMplsLspTemplateEgrStats      OBJECT-TYPE
    SYNTAX      TruthValue
    MAX-ACCESS  read-create
    STATUS      current
    DESCRIPTION
        "The value of vRtrMplsLspTemplateEgrStats specifies whether egress
         statistics has been enabled or disabled for this LSP template.

         A value of 'true' specifies egress statistics is enabled on this LSP
         template.

         A value of 'false' specifies that egress statistics is disabled on
         this LSP template."
    DEFVAL      { false }
    ::= { vRtrMplsLspTemplateEntry 37 }

vRtrMplsLspTempCollectStats      OBJECT-TYPE
    SYNTAX      TruthValue
    MAX-ACCESS  read-create
    STATUS      current
    DESCRIPTION
        "The value of vRtrMplsLspTempCollectStats specifies whether to collect
         statistics for this prefix."
    DEFVAL      { false }
    ::= { vRtrMplsLspTemplateEntry 38 }

vRtrMplsLspTempAccntingPolicy    OBJECT-TYPE
    SYNTAX      Unsigned32 (0 | 1..99)
    MAX-ACCESS  read-create
    STATUS      current
    DESCRIPTION
        "The value of vRtrMplsLspTempAccntingPolicy specifies the accounting
         policy to be used for this entry.

         A value of zero indicates that the default accounting policy should be
         used."
    DEFVAL      { 0 }
    ::= { vRtrMplsLspTemplateEntry 39 }

vRtrMplsLspTemplateFromAddrType  OBJECT-TYPE
    SYNTAX      InetAddressType
    MAX-ACCESS  read-create
    STATUS      current
    DESCRIPTION
        "The value of vRtrMplsLspTemplateFromAddrType specifies the IP address
         type of vRtrMplsLspTemplateFromAddr."
    DEFVAL      { unknown }
    ::= { vRtrMplsLspTemplateEntry 40 }

vRtrMplsLspTemplateFromAddr      OBJECT-TYPE
    SYNTAX      InetAddress (SIZE (0|4|16))
    MAX-ACCESS  read-create
    STATUS      current
    DESCRIPTION
        "The vRtrMplsLspTemplateFromAddr specifies the source address of this
         LSP template.

         The address type  of  vRtrMplsLspTemplateFromAddr is specified by
         vRtrMplsLspTemplateFromAddrType.

         When vRtrMplsLspTemplateFromAddr has not been explicitly set, the
         system IP address will be used."
    DEFVAL      { ''H }
    ::= { vRtrMplsLspTemplateEntry 41 }

vRtrMplsLspTemplateClassType     OBJECT-TYPE
    SYNTAX      TmnxRsvpDSTEClassType
    MAX-ACCESS  read-create
    STATUS      current
    DESCRIPTION
        "The value of vRtrMplsLspTemplateClassType specifies the class type
         (CT) associated with this LSP template."
    DEFVAL      { 0 }
    ::= { vRtrMplsLspTemplateEntry 42 }

vRtrMplsLspTempBkupClassType     OBJECT-TYPE
    SYNTAX      TmnxRsvpDSTEClassType
    MAX-ACCESS  read-create
    STATUS      current
    DESCRIPTION
        "The value of vRtrMplsLspTempBkupClassType specifies the backup class
         type (CT) associated with this LSP template."
    DEFVAL      { 0 }
    ::= { vRtrMplsLspTemplateEntry 43 }

vRtrMplsLspTempBgpTransportTunn  OBJECT-TYPE
    SYNTAX      TmnxMplsLspBgpRSVPLSPTunState
    MAX-ACCESS  read-create
    STATUS      current
    DESCRIPTION
        "The value of vRtrMplsLspTempBgpTransportTunn specifies whether an RSVP
         LSP is allowed or blocked in its usage as a transport LSP for BGP
         tunnel routes.

         When the value of vRtrMplsLspTempBgpTransportTunn is set to 'include'
         an RSVP LSP is allowed to be used as a transport LSP for BGP tunnel
         routes. When the value of vRtrMplsLspTempBgpTransportTunn is set to
         'exclude' an RSVP LSP is not allowed to be used as a transport LSP for
         BGP tunnel routes."
    DEFVAL      { include }
    ::= { vRtrMplsLspTemplateEntry 44 }

vRtrMplsLspTempMainCTRetryLimit  OBJECT-TYPE
    SYNTAX      Unsigned32 (0..10000)
    MAX-ACCESS  read-create
    STATUS      current
    DESCRIPTION
        "The value of vRtrMplsLspTempMainCTRetryLimit specifies the number of
         attempts the software should make before it can start using the backup
         class type."
    DEFVAL      { 0 }
    ::= { vRtrMplsLspTemplateEntry 45 }

vRtrMplsLspTemplateRsvpAdspec    OBJECT-TYPE
    SYNTAX      TruthValue
    MAX-ACCESS  read-create
    STATUS      current
    DESCRIPTION
        "The value of vRtrMplsLspTemplateRsvpAdspec specifies whether or not
         the ADSPEC object will be included in RSVP messages.

         When the value of vRtrMplsLspTemplateRsvpAdspec is 'true', the ADSPEC
         object will be included in RSVP messages.

         When the value of vRtrMplsLspTemplateRsvpAdspec is 'false', the ADSPEC
         object will not be included in RSVP messages."
    DEFVAL      { false }
    ::= { vRtrMplsLspTemplateEntry 46 }

vRtrMplsLspTempLoadBalancingWt   OBJECT-TYPE
    SYNTAX      Unsigned32 (0 | 1..4294967295)
    MAX-ACCESS  read-create
    STATUS      current
    DESCRIPTION
        "The value of vRtrMplsLspTempLoadBalancingWt specifies the load
         balancing weight applied to this Labeled Switch Path(LSP) template.
         When a system level load-balancing command is enabled, packets
         forwarded to a set of ECMP tunnel next-hops will be sprayed using this
         weight configured for this LSP template."
    DEFVAL      { 0 }
    ::= { vRtrMplsLspTemplateEntry 47 }

vRtrMplsLspTempClassFwdEnabled   OBJECT-TYPE
    SYNTAX      TruthValue
    MAX-ACCESS  read-create
    STATUS      current
    DESCRIPTION
        "The value of vRtrMplsLspTempClassFwdEnabled specifies whether class
         based forwarding over this MPLS LSP template is enabled or not."
    DEFVAL      { false }
    ::= { vRtrMplsLspTemplateEntry 48 }

vRtrMplsLspTempFC                OBJECT-TYPE
    SYNTAX      TmnxCBFClasses
    MAX-ACCESS  read-create
    STATUS      obsolete
    DESCRIPTION
        "The value of vRtrMplsLspTempFC specifies a set of forwarding classes
         configured for this LSP template expressed as a bit map. If a bit from
         0 through 7 is set, then the corresponding forwarding class has been
         configured for this LSP template. If bit 8 is set, this LSP template
         has been designated as the default forwarding LSP."
    DEFVAL      { {} }
    ::= { vRtrMplsLspTemplateEntry 49 }

vRtrMplsLspTempBfdTemplateName   OBJECT-TYPE
    SYNTAX      TNamedItemOrEmpty
    MAX-ACCESS  read-create
    STATUS      current
    DESCRIPTION
        "The value of vRtrMplsLspTempBfdTemplateName specifies the
         TIMETRA-BFD-MIB::tmnxBfdAdminTemplateName used by this LSP template."
    ::= { vRtrMplsLspTemplateEntry 50 }

vRtrMplsLspTempBfdEnable         OBJECT-TYPE
    SYNTAX      TruthValue
    MAX-ACCESS  read-create
    STATUS      current
    DESCRIPTION
        "The value of vRtrMplsLspTempBfdEnable specifies whether BFD is enabled
         or not for this LSP template."
    DEFVAL      { false }
    ::= { vRtrMplsLspTemplateEntry 51 }

vRtrMplsLspTempBfdPingIntvl      OBJECT-TYPE
    SYNTAX      Unsigned32 (0 | 60..300)
    UNITS       "seconds"
    MAX-ACCESS  read-create
    STATUS      current
    DESCRIPTION
        "The value of vRtrMplsLspTempBfdPingIntvl specifies the time interval
         for periodic LSP ping for BFD bootstrapping.

         The object vRtrMplsLspTempBfdPingIntvl is applicable to LSP templates
         with  vRtrMplsLspTemplateType set to 'oneHopP2P' or 'meshP2P'.

         When the value of vRtrMplsLspTempBfdPingIntvl is set to '0', it
         disables LSP pings for BFD bootstrapping."
    DEFVAL      { 60 }
    ::= { vRtrMplsLspTemplateEntry 52 }

vRtrMplsLspTempEntropyLabel      OBJECT-TYPE
    SYNTAX      INTEGER {
        forceDisable (1),
        enable       (2),
        inherit      (3)
    }
    MAX-ACCESS  read-create
    STATUS      current
    DESCRIPTION
        "The value of vRtrMplsLspTempEntropyLabel specifies whether the
         application takes into account the value of Entropy Label and Entropy
         Label Capability in the label stack for this LSP template.

         When the value of vRtrMplsLspTempEntropyLabel is set to 'enable', the
         application will account for EL/ELC in the label stack without taking
         into consideration the value of the enabled ELC.

         When the value of vRtrMplsLspTempEntropyLabel is set to
         'force-disable' , the application will ignore the value of enabled
         ELC.

         When the value of vRtrMplsLspTempEntropyLabel is modified, Entropy
         Label will become operational when this LSP template is resignalled.

         By default, if this LSP template is of type RSVP-TE it will inherit
         the behavior as set by vRtrMplsGeneralEntropyLblRsvpTe, or if the LSP
         template is of type SR-TE  it will inherit from
         vRtrMplsGeneralEntropyLblSrTe."
    DEFVAL      { inherit }
    ::= { vRtrMplsLspTemplateEntry 53 }

vRtrMplsLspTemplatePceReport     OBJECT-TYPE
    SYNTAX      INTEGER {
        enable  (1),
        disable (2),
        inherit (3)
    }
    MAX-ACCESS  read-create
    STATUS      current
    DESCRIPTION
        "The value of vRtrMplsLspTemplatePceReport specifies whether to
         override the global configuration of reporting of LSP Template to PCE.

         If the value of vRtrMplsLspTemplatePceReport is 'disabled' for an LSP
         Template either due to inheritance or due to LSP template level
         configuration, the value of vRtrMplsLspTemplatePceReport has no
         effect. "
    DEFVAL      { inherit }
    ::= { vRtrMplsLspTemplateEntry 54 }

vRtrMplsLspTempMaxSrLabels       OBJECT-TYPE
    SYNTAX      Unsigned32 (1..11)
    MAX-ACCESS  read-create
    STATUS      current
    DESCRIPTION
        "The value of vRtrMplsLspTempMaxSrLabels specifies maximum segment
         routing label stack size for this LSP template.

          The default IXR platform is 3 and maximum value supported is 5."
    DEFVAL      { 6 }
    ::= { vRtrMplsLspTemplateEntry 55 }

vRtrMplsLspTempFrrOverheadLabel  OBJECT-TYPE
    SYNTAX      Unsigned32 (0..4)
    MAX-ACCESS  read-create
    STATUS      current
    DESCRIPTION
        "The value of vRtrMplsLspTempFrrOverheadLabel specifies maximum
         additional overhead labels for this LSP template."
    DEFVAL      { 1 }
    ::= { vRtrMplsLspTemplateEntry 56 }

vRtrMplsLspTempBfdFailureAction  OBJECT-TYPE
    SYNTAX      INTEGER {
        none           (0),
        down           (1),
        failoverOrDown (2)
    }
    MAX-ACCESS  read-create
    STATUS      current
    DESCRIPTION
        "The value of vRtrMplsLspTempBfdFailureAction specifies the actions to
         be taken when this LSP template session fails.

         When vRtrMplsLspTempBfdFailureAction is set to down, it prevents the
         LSP template from being made available as a transport for any user.

         When vRtrMplsLspTempBfdFailureAction is set to failoverOrDown, and the
         BFD session associated with the active-path of a related LSP goes
         down, the LSP will switch  to the standby-path if applicable. When the
         LSP cannot switchover, the LSP will  go operationally down."
    DEFVAL      { none }
    ::= { vRtrMplsLspTemplateEntry 57 }

vRtrMplsLspTempCbfFwdingPlcy     OBJECT-TYPE
    SYNTAX      TNamedItemOrEmpty
    MAX-ACCESS  read-create
    STATUS      current
    DESCRIPTION
        "The value of vRtrMplsLspTempCbfFwdingPlcy specifies the name of the
         Class Forwarding Policy for this LSP Template instance."
    DEFVAL      { "" }
    ::= { vRtrMplsLspTemplateEntry 58 }

vRtrMplsLspTempCbfFwdingSet      OBJECT-TYPE
    SYNTAX      Unsigned32 (0..6)
    MAX-ACCESS  read-create
    STATUS      current
    DESCRIPTION
        "The value of vRtrMplsLspTempCbfFwdingSet specifies the Class
         Forwarding Set ID for this LSP Template instance. If system profile is
         profile-b then valid range is 0..6 else 0..4"
    DEFVAL      { 0 }
    ::= { vRtrMplsLspTemplateEntry 59 }

vRtrMplsLspTemplateId            OBJECT-TYPE
    SYNTAX      Unsigned32 (0 | 1..4294967295)
    MAX-ACCESS  read-create
    STATUS      current
    DESCRIPTION
        "The value of vRtrMplsLspTemplateId specifies the identifier
         for pce-init LSPs using this template are setup."
    DEFVAL      { 0 }
    ::= { vRtrMplsLspTemplateEntry 60 }

vRtrMplsLspTempPathCompMeth      OBJECT-TYPE
    SYNTAX      INTEGER {
        none      (1),
        localCspf (2)
    }
    MAX-ACCESS  read-create
    STATUS      current
    DESCRIPTION
        "The value of vRtrMplsLspTempPathCompMeth specifies LSP path
         computation method.

         If the value of vRtrMplsLspTempPathCompMeth is 'localCspf' for an LSP
         the path uses local CSPF.


         The default value for vRtrMplsLspTempPathCompMeth is 'none'."
    DEFVAL      { none }
    ::= { vRtrMplsLspTemplateEntry 61 }

vRtrMplsLspTempMetricType        OBJECT-TYPE
    SYNTAX      INTEGER {
        igp (1),
        te  (2)
    }
    MAX-ACCESS  read-create
    STATUS      current
    DESCRIPTION
        "The value of vRtrMplsLspTempMetricType specifies metric type.

         If the value of vRtrMplsLspTempMetricType is 'igp', the metric used is
         IGP.

         If the value of vRtrMplsLspTempMetricType is 'te', the metric used is
         TE.

         The default value for vRtrMplsLspTempMetricType is 'igp'."
    DEFVAL      { igp }
    ::= { vRtrMplsLspTemplateEntry 62 }

vRtrMplsLspTempLocalSrProt       OBJECT-TYPE
    SYNTAX      INTEGER {
        none      (1),
        preferred (2),
        mandatory (3)
    }
    MAX-ACCESS  read-create
    STATUS      current
    DESCRIPTION
        "The value of vRtrMplsLspTempLocalSrProt specifies the local SR
         protection.

         If the value of vRtrMplsLspTempLocalSrProt is 'none', there is no
         protection.

         If the value of vRtrMplsLspTempLocalSrProt is 'preferred', the
         protection is preferred.

         If the value of vRtrMplsLspTempLocalSrProt is 'mandatory', the
         protection is mandatory.

         The default value for vRtrMplsLspTempLocalSrProt is 'none'."
    DEFVAL      { preferred }
    ::= { vRtrMplsLspTemplateEntry 63 }

vRtrMplsLspTempLabelStackRed     OBJECT-TYPE
    SYNTAX      TruthValue
    MAX-ACCESS  read-create
    STATUS      current
    DESCRIPTION
        "The value of vRtrMplsLspTempLabelStackRed specifies whether label
         stack reduction is enabled."
    DEFVAL      { false }
    ::= { vRtrMplsLspTemplateEntry 64 }

vRtrMplsLspTempBfdUpWaitTimer    OBJECT-TYPE
    SYNTAX      Unsigned32 (1..60)
    UNITS       "seconds"
    MAX-ACCESS  read-create
    STATUS      current
    DESCRIPTION
        "The value of vRtrMplsLspTempBfdUpWaitTimer specifies the time in
         seconds the software will wait for BFD to come up.

         The timer object is applicable only when
         vRtrMplsLspTempBfdFailureAction  is set to 'failoverOrDown'.

         The timer object is applicable for LSP templates with
         vRtrMplsLspTemplateType set to 'oneHopP2PSrTe', 'meshP2PSrTe' or
         pceInitP2PSrte'.

         The timer is started when BFD is first enabled on a path or BFD
         transitions from up to down. When this timer expires and if BFD has
         not yet come up, the path is torn down by removing it from TTM and
         the IOM and the retry timer is started."
    DEFVAL      { 4 }
    ::= { vRtrMplsLspTemplateEntry 65 }

vRtrMplsLspTempSelfPing          OBJECT-TYPE
    SYNTAX      INTEGER {
        enable  (1),
        disable (2),
        inherit (3)
    }
    MAX-ACCESS  read-create
    STATUS      current
    DESCRIPTION
        "The value of vRtrMplsLspTempSelfPing specifies whether to override the
         global configuration of Self Ping.

         If the value of vRtrMplsLspTempSelfPing is 'disabled' for an LSP
         template entry either due to inheritance or due to lsp template level
         configuration, the value of vRtrMplsLspTempSelfPing has no affect.

         The default value for vRtrMplsLspTempSelfPing is 'inherit'."
    DEFVAL      { inherit }
    ::= { vRtrMplsLspTemplateEntry 66 }

vRtrMplsLspAutoBWTableLastChg    OBJECT-TYPE
    SYNTAX      TimeStamp
    MAX-ACCESS  read-only
    STATUS      current
    DESCRIPTION
        "The value of vRtrMplsLspAutoBWTableLastChg indicates the sysUpTime at
         the time of the last modification to vRtrMplsLspAutoBandwidthTable by
         adding, deleting an entry or change to a writable object in the table.

         If no changes were made to the table since the last re-initialization
         of the local network management subsystem, then this object contains a
         zero value."
    ::= { tmnxMplsObjs 42 }

vRtrMplsLspAutoBandwidthTable    OBJECT-TYPE
    SYNTAX      SEQUENCE OF VRtrMplsLspAutoBandwidthEntry
    MAX-ACCESS  not-accessible
    STATUS      current
    DESCRIPTION
        "The vRtrMplsLspAutoBandwidthTable has an entry for auto bandwidth
         configuration for each Labeled Switch Path (LSP) configured for a
         virtual router in the system."
    ::= { tmnxMplsObjs 43 }

vRtrMplsLspAutoBandwidthEntry    OBJECT-TYPE
    SYNTAX      VRtrMplsLspAutoBandwidthEntry
    MAX-ACCESS  not-accessible
    STATUS      current
    DESCRIPTION
        "Each row entry represents auto bandwidth configuration for a Labeled
         Switch Path (LSP) configured for a virtual router in the system."
    INDEX       {
        vRtrID,
        vRtrMplsLspAutoBWLspName
    }
    ::= { vRtrMplsLspAutoBandwidthTable 1 }

VRtrMplsLspAutoBandwidthEntry    ::= SEQUENCE
{
    vRtrMplsLspAutoBWLspName         TLNamedItem,
    vRtrMplsLspAutoBWLastChange      TimeStamp,
    vRtrMplsLspAutoBWAdjDNPercent    Unsigned32,
    vRtrMplsLspAutoBWAdjDNMbps       TmnxMplsLspBandwidth,
    vRtrMplsLspAutoBWAdjMultiplier   Unsigned32,
    vRtrMplsLspAutoBWAdjUPPercent    Unsigned32,
    vRtrMplsLspAutoBWAdjUPMbps       TmnxMplsLspBandwidth,
    vRtrMplsLspAutoBWMaxBW           TmnxMplsLspBandwidth,
    vRtrMplsLspAutoBWMinBW           TmnxMplsLspBandwidth,
    vRtrMplsLspAutoBWMonitorBW       TruthValue,
    vRtrMplsLspAutoBWOverFlow        Unsigned32,
    vRtrMplsLspAutoBWOvrFlwThreshold Unsigned32,
    vRtrMplsLspAutoBWOvrFlwBW        TmnxMplsLspBandwidth,
    vRtrMplsLspAutoBWSampMultiplier  Unsigned32,
    vRtrMplsLspAutoBWSampTime        Unsigned32,
    vRtrMplsLspAutoBWLastAdj         TimeStamp,
    vRtrMplsLspAutoBWLastAdjCause    TmnxMplsLspAutoBWLastAdjCause,
    vRtrMplsLspAutoBWNextAdj         Unsigned32,
    vRtrMplsLspAutoBWMaxAvgRate      Unsigned32,
    vRtrMplsLspAutoBWLastAvgRate     Unsigned32,
    vRtrMplsLspAutoBWInheritance     Unsigned32,
    vRtrMplsLspAutoBWCurrentBW       Unsigned32,
    vRtrMplsLspAutoBWAdjTime         Unsigned32,
    vRtrMplsLspAutoBWOvrFlwCount     Unsigned32,
    vRtrMplsLspAutoBWSampCount       Unsigned32,
    vRtrMplsLspAutoBWAdjCount        Unsigned32,
    vRtrMplsLspAutoBWOperState       TmnxEnabledDisabled,
    vRtrMplsLspAutoBWSampInterval    Unsigned32,
    vRtrMplsLspAutoBWBeWeight        Unsigned32,
    vRtrMplsLspAutoBWL2Weight        Unsigned32,
    vRtrMplsLspAutoBWAfWeight        Unsigned32,
    vRtrMplsLspAutoBWL1Weight        Unsigned32,
    vRtrMplsLspAutoBWH2Weight        Unsigned32,
    vRtrMplsLspAutoBWEfWeight        Unsigned32,
    vRtrMplsLspAutoBWH1Weight        Unsigned32,
    vRtrMplsLspAutoBWNcWeight        Unsigned32,
    vRtrMplsLspAutoBWUnderFlow       Unsigned32,
    vRtrMplsLspAutoBWUndFlwThreshold Unsigned32,
    vRtrMplsLspAutoBWUndFlwBW        TmnxMplsLspBandwidth,
    vRtrMplsLspAutoBWUndFlwCount     Counter32,
    vRtrMplsLspAutoBWMaxUndFlwBw     Unsigned32,
    vRtrMplsLspAutoBWUseLastAdjBW    TruthValue,
    vRtrMplsLspAutoBWSecRetryLimit   Unsigned32,
    vRtrMplsLspAutoBWLastAdjBW       Integer32
}

vRtrMplsLspAutoBWLspName         OBJECT-TYPE
    SYNTAX      TLNamedItem
    MAX-ACCESS  not-accessible
    STATUS      current
    DESCRIPTION
        "The value of vRtrMplsLspAutoBWLspName uniquely identifies a row in the
         vRtrMplsLspAutoBandwidthTable.

         If vRtrMplsLspType is not 'meshP2p' or 'oneHopP2p',
         vRtrMplsLspAutoBWLspName can have a maximum of 32 characters."
    ::= { vRtrMplsLspAutoBandwidthEntry 1 }

vRtrMplsLspAutoBWLastChange      OBJECT-TYPE
    SYNTAX      TimeStamp
    MAX-ACCESS  read-only
    STATUS      current
    DESCRIPTION
        "The sysUpTime when this row was last modified."
    ::= { vRtrMplsLspAutoBandwidthEntry 2 }

vRtrMplsLspAutoBWAdjDNPercent    OBJECT-TYPE
    SYNTAX      Unsigned32 (0..100)
    UNITS       "percent"
    MAX-ACCESS  read-write
    STATUS      current
    DESCRIPTION
        "The value of vRtrMplsLspAutoBWAdjDNPercent specifies minimum
         difference between the current bandwidth reservation of the LSP and
         the (measured) maximum average data rate, expressed as a percentage of
         the current bandwidth, for decreasing the bandwidth of the LSP. At the
         adjust interval expiry, if the measured bandwidth falls below the
         current bandwidth by the value of vRtrMplsLspAutoBWAdjDNPercent it can
         cause a resignaling attempt for the LSP

         When the value of vRtrMplsLspAutoBWAdjDNPercent is 0 it means that
         this threshold check is always true for any measured bandwidth less
         than current bandwidth"
    DEFVAL      { 5 }
    ::= { vRtrMplsLspAutoBandwidthEntry 3 }

vRtrMplsLspAutoBWAdjDNMbps       OBJECT-TYPE
    SYNTAX      TmnxMplsLspBandwidth
    UNITS       "megabps"
    MAX-ACCESS  read-write
    STATUS      current
    DESCRIPTION
        "The value of vRtrMplsLspAutoBWAdjDNMbps specifies the minimum
         difference between the current bandwidth reservation of the LSP and
         the (measured) maximum average data rate, expressed as an absolute
         bandwidth (Mbps), for decreasing the bandwidth of the LSP."
    DEFVAL      { 0 }
    ::= { vRtrMplsLspAutoBandwidthEntry 4 }

vRtrMplsLspAutoBWAdjMultiplier   OBJECT-TYPE
    SYNTAX      Unsigned32 (1..16383)
    MAX-ACCESS  read-write
    STATUS      current
    DESCRIPTION
        "The value of vRtrMplsLspAutoBWAdjMultiplier specifies the number of
         collection intervals in the adjust interval.

         The default value is derived from vRtrMplsGeneralAutoBWDefAdjMul and
         vRtrMplsLspAutoBWAdjCount."
    DEFVAL      { 288 }
    ::= { vRtrMplsLspAutoBandwidthEntry 5 }

vRtrMplsLspAutoBWAdjUPPercent    OBJECT-TYPE
    SYNTAX      Unsigned32 (0..100)
    UNITS       "percent"
    MAX-ACCESS  read-write
    STATUS      current
    DESCRIPTION
        "The value of vRtrMplsLspAutoBWAdjUPPercent specifies minimum
         difference between the current bandwidth reservation of the LSP and
         the (measured) maximum average data rate, expressed as a percentage of
         the current bandwidth, for increasing the bandwidth of the LSP. At the
         adjust interval expiry, if the measured bandwidth exceeds the current
         bandwidth by the value of vRtrMplsLspAutoBWAdjUPPercent it can cause a
         resignaling attempt for the LSP

         When the value of vRtrMplsLspAutoBWAdjUPPercent is 0 it means that
         this threshold check is always true for any measured bandwidth greater
         than current bandwidth"
    DEFVAL      { 5 }
    ::= { vRtrMplsLspAutoBandwidthEntry 6 }

vRtrMplsLspAutoBWAdjUPMbps       OBJECT-TYPE
    SYNTAX      TmnxMplsLspBandwidth
    UNITS       "megabps"
    MAX-ACCESS  read-write
    STATUS      current
    DESCRIPTION
        "The value of vRtrMplsLspAutoBWAdjUPMbps specifies the minimum
         difference between the current bandwidth reservation of the LSP and
         the (measured) maximum average data rate, expressed as an absolute
         bandwidth (Mbps), for increasing the bandwidth of the LSP."
    DEFVAL      { 0 }
    ::= { vRtrMplsLspAutoBandwidthEntry 7 }

vRtrMplsLspAutoBWMaxBW           OBJECT-TYPE
    SYNTAX      TmnxMplsLspBandwidth
    UNITS       "megabps"
    MAX-ACCESS  read-write
    STATUS      current
    DESCRIPTION
        "The value of vRtrMplsLspAutoBWMaxBW specifies the maximum that
         auto-bandwidth allocation is allowed to request for a LSP."
    DEFVAL      { 100000 }
    ::= { vRtrMplsLspAutoBandwidthEntry 8 }

vRtrMplsLspAutoBWMinBW           OBJECT-TYPE
    SYNTAX      TmnxMplsLspBandwidth
    UNITS       "megabps"
    MAX-ACCESS  read-write
    STATUS      current
    DESCRIPTION
        "The value of vRtrMplsLspAutoBWMinBW specifies the minimum that
         auto-bandwidth allocation is allowed to request for a LSP."
    DEFVAL      { 0 }
    ::= { vRtrMplsLspAutoBandwidthEntry 9 }

vRtrMplsLspAutoBWMonitorBW       OBJECT-TYPE
    SYNTAX      TruthValue
    UNITS       "megabps"
    MAX-ACCESS  read-write
    STATUS      current
    DESCRIPTION
        "The value of vRtrMplsLspAutoBWMonitorBW specifies whether the
         collection and display of auto-bandwidth measurements is enabled or
         disabled for the LSP.

         When the value of vRtrMplsLspAutoBWMonitorBW is 'true' the collection
         and display of auto-bandwidth measurements is enabled and when the
         value is 'false' it is disabled."
    DEFVAL      { false }
    ::= { vRtrMplsLspAutoBandwidthEntry 10 }

vRtrMplsLspAutoBWOverFlow        OBJECT-TYPE
    SYNTAX      Unsigned32 (0 | 1..10)
    MAX-ACCESS  read-write
    STATUS      current
    DESCRIPTION
        "The value of vRtrMplsLspAutoBWOverFlow specifies number of overflow
         samples that triggers an overflow auto-bandwidth adjustment attempt."
    DEFVAL      { 0 }
    ::= { vRtrMplsLspAutoBandwidthEntry 11 }

vRtrMplsLspAutoBWOvrFlwThreshold OBJECT-TYPE
    SYNTAX      Unsigned32 (0..100)
    UNITS       "percent"
    MAX-ACCESS  read-write
    STATUS      current
    DESCRIPTION
        "The value of vRtrMplsLspAutoBWOvrFlwThreshold specifies the minimum
         difference between the current bandwidth of the LSP and the sampled
         data rate, expressed as a percentage of the current bandwidth, for
         counting an overflow sample."
    DEFVAL      { 0 }
    ::= { vRtrMplsLspAutoBandwidthEntry 12 }

vRtrMplsLspAutoBWOvrFlwBW        OBJECT-TYPE
    SYNTAX      TmnxMplsLspBandwidth
    UNITS       "megabps"
    MAX-ACCESS  read-write
    STATUS      current
    DESCRIPTION
        "The value of vRtrMplsLspAutoBWOvrFlwBW specifies the minimum
         difference between the current bandwidth of the LSP and the sampled
         data rate, expressed as an absolute bandwidth (Mbps), for counting an
         overflow sample."
    DEFVAL      { 0 }
    ::= { vRtrMplsLspAutoBandwidthEntry 13 }

vRtrMplsLspAutoBWSampMultiplier  OBJECT-TYPE
    SYNTAX      Unsigned32 (1..511)
    MAX-ACCESS  read-write
    STATUS      current
    DESCRIPTION
        "The value of vRtrMplsLspAutoBWSampMultiplier specifies the multiplier
         for collection intervals in a sample interval."
    DEFVAL      { 1 }
    ::= { vRtrMplsLspAutoBandwidthEntry 14 }

vRtrMplsLspAutoBWSampTime        OBJECT-TYPE
    SYNTAX      Unsigned32
    UNITS       "minutes"
    MAX-ACCESS  read-only
    STATUS      current
    DESCRIPTION
        "The value of vRtrMplsLspAutoBWSampTime indicates the sample multiplier
         times the collection interval."
    ::= { vRtrMplsLspAutoBandwidthEntry 15 }

vRtrMplsLspAutoBWLastAdj         OBJECT-TYPE
    SYNTAX      TimeStamp
    MAX-ACCESS  read-only
    STATUS      current
    DESCRIPTION
        "The value of vRtrMplsLspAutoBWLastAdj indicates the system time for
         the last auto-bandwidth adjustment."
    ::= { vRtrMplsLspAutoBandwidthEntry 16 }

vRtrMplsLspAutoBWLastAdjCause    OBJECT-TYPE
    SYNTAX      TmnxMplsLspAutoBWLastAdjCause
    MAX-ACCESS  read-only
    STATUS      current
    DESCRIPTION
        "The value of vRtrMplsLspAutoBWLastAdjCause indicates the cause for the
         last auto-bandwidth adjustment."
    ::= { vRtrMplsLspAutoBandwidthEntry 17 }

vRtrMplsLspAutoBWNextAdj         OBJECT-TYPE
    SYNTAX      Unsigned32
    UNITS       "minutes"
    MAX-ACCESS  read-only
    STATUS      current
    DESCRIPTION
        "The value of vRtrMplsLspAutoBWNextAdj indicates the system time when
         then adjust-timer will expire."
    ::= { vRtrMplsLspAutoBandwidthEntry 18 }

vRtrMplsLspAutoBWMaxAvgRate      OBJECT-TYPE
    SYNTAX      Unsigned32
    UNITS       "megabps"
    MAX-ACCESS  read-only
    STATUS      current
    DESCRIPTION
        "The value of vRtrMplsLspAutoBWMaxAvgRate indicates the maximum average
         data rate in any sample interval of the current adjust interval."
    ::= { vRtrMplsLspAutoBandwidthEntry 19 }

vRtrMplsLspAutoBWLastAvgRate     OBJECT-TYPE
    SYNTAX      Unsigned32
    UNITS       "megabps"
    MAX-ACCESS  read-only
    STATUS      current
    DESCRIPTION
        "The value of vRtrMplsLspAutoBWLastAvgRate indicates the average data
         rate in the sample interval that ended most recently."
    ::= { vRtrMplsLspAutoBandwidthEntry 20 }

vRtrMplsLspAutoBWInheritance     OBJECT-TYPE
    SYNTAX      Unsigned32
    MAX-ACCESS  read-write
    STATUS      current
    DESCRIPTION
        "For each writable object in this row that can be configured to inherit
         its value from the corresponding object in the vRtrMplsGeneralTable,
         there is bit within vRtrMplsLspAutoBWInheritance that controls whether
         to inherit the operational value of the object or use the
         administratively set value.

         This object is a bit-mask, with the following positions:

         vRtrMplsLspAutoBWAdjMultiplier          0x1
         vRtrMplsLspAutoBWSampMultiplier         0x2

         When the bit for an object is set to one, then the object's
         administrative and operational value are whatever the DEFVAL or most
         recently SET value is.

         When the bit for an object is set to zero, then the object's
         administrative and operational value are inherited from the
         corresponding object in vRtrMplsGeneralTable."
    DEFVAL      { 0 }
    ::= { vRtrMplsLspAutoBandwidthEntry 21 }

vRtrMplsLspAutoBWCurrentBW       OBJECT-TYPE
    SYNTAX      Unsigned32
    UNITS       "megabps"
    MAX-ACCESS  read-only
    STATUS      current
    DESCRIPTION
        "The value of vRtrMplsLspAutoBWCurrentBW indicates the current
         bandwidth reserved along the primary path."
    ::= { vRtrMplsLspAutoBandwidthEntry 22 }

vRtrMplsLspAutoBWAdjTime         OBJECT-TYPE
    SYNTAX      Unsigned32
    UNITS       "minutes"
    MAX-ACCESS  read-only
    STATUS      current
    DESCRIPTION
        "The value of vRtrMplsLspAutoBWAdjTime indicates the adjust multiplier
         times the collection interval."
    ::= { vRtrMplsLspAutoBandwidthEntry 23 }

vRtrMplsLspAutoBWOvrFlwCount     OBJECT-TYPE
    SYNTAX      Unsigned32
    MAX-ACCESS  read-only
    STATUS      current
    DESCRIPTION
        "The value of vRtrMplsLspAutoBWOvrFlwCount indicates the number of
         overflow samples since the last reset."
    ::= { vRtrMplsLspAutoBandwidthEntry 24 }

vRtrMplsLspAutoBWSampCount       OBJECT-TYPE
    SYNTAX      Unsigned32
    MAX-ACCESS  read-only
    STATUS      current
    DESCRIPTION
        "The value of vRtrMplsLspAutoBWSampCount indicates the count in the
         sample interval."
    ::= { vRtrMplsLspAutoBandwidthEntry 25 }

vRtrMplsLspAutoBWAdjCount        OBJECT-TYPE
    SYNTAX      Unsigned32
    MAX-ACCESS  read-only
    STATUS      current
    DESCRIPTION
        "The value of vRtrMplsLspAutoBWAdjCount indicates the count in the
         adjust interval."
    ::= { vRtrMplsLspAutoBandwidthEntry 26 }

vRtrMplsLspAutoBWOperState       OBJECT-TYPE
    SYNTAX      TmnxEnabledDisabled
    MAX-ACCESS  read-only
    STATUS      current
    DESCRIPTION
        "The value of vRtrMplsLspAutoBWOperState indicates the operational
         status for the LSP."
    ::= { vRtrMplsLspAutoBandwidthEntry 27 }

vRtrMplsLspAutoBWSampInterval    OBJECT-TYPE
    SYNTAX      Unsigned32
    MAX-ACCESS  read-only
    STATUS      current
    DESCRIPTION
        "The value of vRtrMplsLspAutoBWSampInterval indicates the number of
         sample intervals."
    ::= { vRtrMplsLspAutoBandwidthEntry 28 }

vRtrMplsLspAutoBWBeWeight        OBJECT-TYPE
    SYNTAX      Unsigned32 (0..100)
    UNITS       "percent"
    MAX-ACCESS  read-write
    STATUS      current
    DESCRIPTION
        "The value of vRtrMplsLspAutoBWBeWeight specifies the weight in percent
         for forwarding class 'BE' for the LSP."
    DEFVAL      { 100 }
    ::= { vRtrMplsLspAutoBandwidthEntry 29 }

vRtrMplsLspAutoBWL2Weight        OBJECT-TYPE
    SYNTAX      Unsigned32 (0..100)
    UNITS       "percent"
    MAX-ACCESS  read-write
    STATUS      current
    DESCRIPTION
        "The value of vRtrMplsLspAutoBWL2Weight specifies the weight in percent
         for forwarding class 'L2' for the LSP."
    DEFVAL      { 100 }
    ::= { vRtrMplsLspAutoBandwidthEntry 30 }

vRtrMplsLspAutoBWAfWeight        OBJECT-TYPE
    SYNTAX      Unsigned32 (0..100)
    UNITS       "percent"
    MAX-ACCESS  read-write
    STATUS      current
    DESCRIPTION
        "The value of vRtrMplsLspAutoBWAfWeight specifies the weight in percent
         for forwarding class 'AF' for the LSP."
    DEFVAL      { 100 }
    ::= { vRtrMplsLspAutoBandwidthEntry 31 }

vRtrMplsLspAutoBWL1Weight        OBJECT-TYPE
    SYNTAX      Unsigned32 (0..100)
    UNITS       "percent"
    MAX-ACCESS  read-write
    STATUS      current
    DESCRIPTION
        "The value of vRtrMplsLspAutoBWL1Weight specifies the weight in percent
         for forwarding class 'L1' for the LSP."
    DEFVAL      { 100 }
    ::= { vRtrMplsLspAutoBandwidthEntry 32 }

vRtrMplsLspAutoBWH2Weight        OBJECT-TYPE
    SYNTAX      Unsigned32 (0..100)
    UNITS       "percent"
    MAX-ACCESS  read-write
    STATUS      current
    DESCRIPTION
        "The value of vRtrMplsLspAutoBWH2Weight specifies the weight in percent
         for forwarding class 'H2' for the LSP."
    DEFVAL      { 100 }
    ::= { vRtrMplsLspAutoBandwidthEntry 33 }

vRtrMplsLspAutoBWEfWeight        OBJECT-TYPE
    SYNTAX      Unsigned32 (0..100)
    UNITS       "percent"
    MAX-ACCESS  read-write
    STATUS      current
    DESCRIPTION
        "The value of vRtrMplsLspAutoBWEfWeight specifies the weight in percent
         for forwarding class 'EF' for the LSP."
    DEFVAL      { 100 }
    ::= { vRtrMplsLspAutoBandwidthEntry 34 }

vRtrMplsLspAutoBWH1Weight        OBJECT-TYPE
    SYNTAX      Unsigned32 (0..100)
    UNITS       "percent"
    MAX-ACCESS  read-write
    STATUS      current
    DESCRIPTION
        "The value of vRtrMplsLspAutoBWH1Weight specifies the weight in percent
         for forwarding class 'H1' for the LSP."
    DEFVAL      { 100 }
    ::= { vRtrMplsLspAutoBandwidthEntry 35 }

vRtrMplsLspAutoBWNcWeight        OBJECT-TYPE
    SYNTAX      Unsigned32 (0..100)
    UNITS       "percent"
    MAX-ACCESS  read-write
    STATUS      current
    DESCRIPTION
        "The value of vRtrMplsLspAutoBWNcWeight specifies the weight in percent
         for forwarding class 'NC' for the LSP."
    DEFVAL      { 100 }
    ::= { vRtrMplsLspAutoBandwidthEntry 36 }

vRtrMplsLspAutoBWUnderFlow       OBJECT-TYPE
    SYNTAX      Unsigned32 (0 | 1..10)
    MAX-ACCESS  read-write
    STATUS      current
    DESCRIPTION
        "The value of vRtrMplsLspAutoBWUnderFlow specifies the number of
         underflow samples that triggers an underflow auto-bandwidth adjustment
         attempt."
    DEFVAL      { 0 }
    ::= { vRtrMplsLspAutoBandwidthEntry 37 }

vRtrMplsLspAutoBWUndFlwThreshold OBJECT-TYPE
    SYNTAX      Unsigned32 (0 | 1..100)
    UNITS       "percent"
    MAX-ACCESS  read-write
    STATUS      current
    DESCRIPTION
        "The value of vRtrMplsLspAutoBWUndFlwThreshold specifies the minimum
         difference between the current bandwidth of the LSP and the sampled
         data rate, expressed as a percentage of the current bandwidth, for
         counting an underflow sample."
    DEFVAL      { 0 }
    ::= { vRtrMplsLspAutoBandwidthEntry 38 }

vRtrMplsLspAutoBWUndFlwBW        OBJECT-TYPE
    SYNTAX      TmnxMplsLspBandwidth
    UNITS       "megabps"
    MAX-ACCESS  read-write
    STATUS      current
    DESCRIPTION
        "The value of vRtrMplsLspAutoBWUndFlwBW specifies the minimum
         difference between the current bandwidth of the LSP and the sampled
         data rate, expressed as an absolute bandwidth (Mbps), for counting an
         underflow sample."
    DEFVAL      { 0 }
    ::= { vRtrMplsLspAutoBandwidthEntry 39 }

vRtrMplsLspAutoBWUndFlwCount     OBJECT-TYPE
    SYNTAX      Counter32
    MAX-ACCESS  read-only
    STATUS      current
    DESCRIPTION
        "The value of vRtrMplsLspAutoBWUndFlwCount indicates the number of
         underflow samples since the last reset."
    ::= { vRtrMplsLspAutoBandwidthEntry 40 }

vRtrMplsLspAutoBWMaxUndFlwBw     OBJECT-TYPE
    SYNTAX      Unsigned32
    UNITS       "megabps"
    MAX-ACCESS  read-only
    STATUS      current
    DESCRIPTION
        "The value of vRtrMplsLspAutoBWMaxUndFlwBw indicates the maximum
         sampled bandwidth in the most recent consecutive underflow samples."
    ::= { vRtrMplsLspAutoBandwidthEntry 41 }

vRtrMplsLspAutoBWUseLastAdjBW    OBJECT-TYPE
    SYNTAX      TruthValue
    MAX-ACCESS  read-write
    STATUS      current
    DESCRIPTION
        "The value of vRtrMplsLspAutoBWUseLastAdjBW specifies whether use of
         last adjusted bandwidth is enabled or diabled.

         When the value is 'true' the use of last adjusted bandwidth is
         enabled, and LSP paths will be signalled with the last adjusted
         bandwidth of the LSP and not the configured bandwidth."
    DEFVAL      { false }
    ::= { vRtrMplsLspAutoBandwidthEntry 42 }

vRtrMplsLspAutoBWSecRetryLimit   OBJECT-TYPE
    SYNTAX      Unsigned32 (0..10000)
    MAX-ACCESS  read-write
    STATUS      current
    DESCRIPTION
        "The value of vRtrMplsLspAutoBWSecRetryLimit specifies the max number
         of retry attempts that will be made to signal the secondary path with
         the last adjusted bandwidth. After the number of retry attempts is
         exceeded, no more attempts will be made to resignal the secondary path
         and the path will remain operationally down. A value of zero(0)
         specifies that the retry limit is infinite.

         This variable is valid only if vRtrMplsLspAutoBWUseLastAdjBW is set to
         'enabled'."
    DEFVAL      { 5 }
    ::= { vRtrMplsLspAutoBandwidthEntry 43 }

vRtrMplsLspAutoBWLastAdjBW       OBJECT-TYPE
    SYNTAX      Integer32
    UNITS       "megabps"
    MAX-ACCESS  read-only
    STATUS      current
    DESCRIPTION
        "The value of vRtrMplsLspAutoBWLastAdjBW indicates the last adjusted
         bandwidth for the LSP. A value of -1 indicates that this value is
         invalid"
    ::= { vRtrMplsLspAutoBandwidthEntry 44 }

vRtrMplsLspPathOperTable         OBJECT-TYPE
    SYNTAX      SEQUENCE OF VRtrMplsLspPathOperEntry
    MAX-ACCESS  not-accessible
    STATUS      current
    DESCRIPTION
        "The vRtrMplsLspPathOperTable has an entry for an association between a
         Labeled Switch Path (LSP) in the vRtrMplsLspTable and a path (or
         tunnel) entry in the mplsTunnelTable."
    ::= { tmnxMplsObjs 44 }

vRtrMplsLspPathOperEntry         OBJECT-TYPE
    SYNTAX      VRtrMplsLspPathOperEntry
    MAX-ACCESS  not-accessible
    STATUS      current
    DESCRIPTION
        "Each row entry represents an operational status for an association
         between a Labeled Switch Path (LSP) in the vRtrMplsLspTable and a path
         (or tunnel) entry in the mplsTunnelTable.

         Entries cannot be created and deleted via SNMP SET operations.

         A row entry will have valid operational status info when
         vRtrMplsLspPathOperState is set to inService."
    AUGMENTS    { vRtrMplsLspPathEntry }
    ::= { vRtrMplsLspPathOperTable 1 }

VRtrMplsLspPathOperEntry         ::= SEQUENCE
{
    vRtrMplsLspPathOperSetupPriority Unsigned32,
    vRtrMplsLspPathOperHoldPriority  Unsigned32,
    vRtrMplsLspPathOperRecord        INTEGER,
    vRtrMplsLspPathOperRecordLabel   INTEGER,
    vRtrMplsLspPathOperHopLimit      Unsigned32,
    vRtrMplsLspPathOperAdminGrpIncl  Unsigned32,
    vRtrMplsLspPathOperAdminGrExcld  Unsigned32,
    vRtrMplsLspPathOperCspf          TruthValue,
    vRtrMplsLspPathOperCspfToFrstLs  TruthValue,
    vRtrMplsLspPathOperLeastFill     TruthValue,
    vRtrMplsLspPathOperRsvpAdspec    TruthValue,
    vRtrMplsLspPathOperFRNodeProtect TruthValue,
    vRtrMplsLspPathOperPropAdminGrp  TruthValue,
    vRtrMplsLspPathOperFRHopLimit    Unsigned32,
    vRtrMplsLspPathOperFRPropAdmGrp  TruthValue,
    vRtrMplsLspPathOperInterArea     TruthValue,
    vRtrMplsLspPathOperCompMeth      INTEGER,
    vRtrMplsLspPathOperMetricType    INTEGER,
    vRtrMplsLspPathOperLocalSrProt   INTEGER,
    vRtrMplsLspPathOperLabelStackRed INTEGER,
    vRtrMplsLspPathNgFNAddrType      InetAddressType,
    vRtrMplsLspPathNgFNAddr          InetAddress
}

vRtrMplsLspPathOperSetupPriority OBJECT-TYPE
    SYNTAX      Unsigned32 (0..7)
    MAX-ACCESS  read-only
    STATUS      current
    DESCRIPTION
        "The value of vRtrMplsLspPathOperSetupPriority indicates the setup
         priority used by the operational LSP path.

         When make-before-break functionality for the LSP is enabled and if the
         path setup priority is changed, the resources allocated to the
         existing LSP paths will not be released until a new path with the new
         setup priority settings has been established. While a new path is
         being signaled, the administrative value and the operational values of
         the path setup priority may differ. The value of
         vRtrMplsLspPathSetupPriority specifies the setup priority for the new
         LSP path trying to be established whereas the value of
         vRtrMplsLspPathOperSetupPriority specifies the setup priority for the
         existing LSP path."
    ::= { vRtrMplsLspPathOperEntry 1 }

vRtrMplsLspPathOperHoldPriority  OBJECT-TYPE
    SYNTAX      Unsigned32 (0..7)
    MAX-ACCESS  read-only
    STATUS      current
    DESCRIPTION
        "The value of vRtrMplsLspPathOperHoldPriority indicates the hold
         priority used by the operational LSP path.

         When make-before-break functionality for the LSP is enabled and if the
         path hold priority is changed, the resources allocated to the existing
         LSP paths will not be released until a new path with the new hold
         priority settings has been established. While a new path is being
         signaled, the administrative value and the operational values of the
         path hold priority may differ. The value of
         vRtrMplsLspPathHoldPriority specifies the hold priority for the new
         LSP path trying to be established whereas the value of
         vRtrMplsLspPathOperHoldPriority specifies the hold priority for the
         existing LSP path."
    ::= { vRtrMplsLspPathOperEntry 2 }

vRtrMplsLspPathOperRecord        OBJECT-TYPE
    SYNTAX      INTEGER {
        record   (1),
        noRecord (2)
    }
    MAX-ACCESS  read-only
    STATUS      current
    DESCRIPTION
        "The value of vRtrMplsLspPathOperRecord indicates whether the
         operational LSP path is recording or not recording all the traversed
         hops.

         When make-before-break functionality for the LSP is enabled and if the
         path hops recording setting is changed, the resources allocated to the
         existing LSP paths will not be released until a new path with the new
         settings has been established. While a new path is being signaled, the
         administrative value and the operational values of hops recording
         setting of the path may differ. The value of vRtrMplsLspPathRecord
         specifies the hops recording setting for the new LSP path trying to be
         established whereas the value of vRtrMplsLspPathOperRecord specifies
         the hops recording setting for the existing LSP path."
    ::= { vRtrMplsLspPathOperEntry 3 }

vRtrMplsLspPathOperRecordLabel   OBJECT-TYPE
    SYNTAX      INTEGER {
        record   (1),
        noRecord (2)
    }
    MAX-ACCESS  read-only
    STATUS      current
    DESCRIPTION
        "The value of vRtrMplsLspPathOperRecordLabel indicates whether the
         currently operational LSP path is recording or not recording the label
         allocated at each traversed node.

         When make-before-break functionality for the LSP is enabled and if the
         path label recording setting is changed, the resources allocated to
         the existing LSP paths will not be released until a new path with the
         new settings has been established. While a new path is being signaled,
         the administrative value and the operational values of label recording
         setting of the path may differ. The value of
         vRtrMplsLspPathRecordLabel specifies the label recording setting for
         the new LSP path trying to be established whereas the value of
         vRtrMplsLspPathOperRecordLabel specifies the label recording setting
         for the existing LSP path."
    ::= { vRtrMplsLspPathOperEntry 4 }

vRtrMplsLspPathOperHopLimit      OBJECT-TYPE
    SYNTAX      Unsigned32 (2..255)
    MAX-ACCESS  read-only
    STATUS      current
    DESCRIPTION
        "The value of vRtrMplsLspPathOperHopLimit indicates the maximum hops
         limit used by the currently operational LSP path.

         When make-before-break functionality for the LSP is enabled and if the
         hop limit is changed at either LSP or LSP path level, the resources
         allocated to the existing LSP paths will not be released until a new
         path with the new settings has been established. While a new path is
         being signaled, the administrative value and the operational values of
         the path hop limit may differ. The value of either vRtrMplsLspHopLimit
         or vRtrMplsLspPathHopLimit specifies the hop limit for the new LSP
         path trying to be established whereas the value of
         vRtrMplsLspPathOperHopLimit specifies the hop limit for the existing
         LSP path."
    ::= { vRtrMplsLspPathOperEntry 5 }

vRtrMplsLspPathOperAdminGrpIncl  OBJECT-TYPE
    SYNTAX      Unsigned32
    MAX-ACCESS  read-only
    STATUS      current
    DESCRIPTION
        "The value of vRtrMplsLspPathOperAdminGrpIncl is a bit-map which
         indicates a list of admin groups included by the currently operational
         LSP path.

         When make-before-break functionality for the LSP is enabled and if
         the list of included admin groups is changed at either LSP or LSP
         path level, the resources allocated to the existing LSP paths will
         not be released until a new path with the new settings has been
         established.  While a new path is being signaled, the
         administrative value and the operational values of the path may
         differ. The value of either vRtrMplsLspAdminGroupInclude or
         vRtrMplsLspPathAdminGroupInclude specifies the include admin groups
         bit-map for the new LSP path trying to be established whereas the
         value of vRtrMplsLspPathOperAdminGrpIncl specifies the include admin
         groups bit-map for the existing LSP path."
    ::= { vRtrMplsLspPathOperEntry 6 }

vRtrMplsLspPathOperAdminGrExcld  OBJECT-TYPE
    SYNTAX      Unsigned32
    MAX-ACCESS  read-only
    STATUS      current
    DESCRIPTION
        "The value of vRtrMplsLspPathOperAdminGrExcld is a bit-map which
         indicates a list of admin groups excluded by the currently operational
         LSP path.

         When make-before-break functionality for the LSP is enabled and if the
         list of excluded admin groups is changed at either LSP or LSP path
         level, the resources allocated to the existing LSP paths will not be
         released until a new path with the new settings has been established.
         While a new path is being signaled, the administrative value and the
         operational values of the path may differ. The value of either
         vRtrMplsLspAdminGroupExclude or vRtrMplsLspPathAdminGroupExclude
         specifies the exclude admin groups bit-map for the new LSP path trying
         to be established whereas the value of vRtrMplsLspPathOperAdminGrExcld
         specifies the exclude admin groups bit-map for the existing LSP path."
    ::= { vRtrMplsLspPathOperEntry 7 }

vRtrMplsLspPathOperCspf          OBJECT-TYPE
    SYNTAX      TruthValue
    MAX-ACCESS  read-only
    STATUS      obsolete
    DESCRIPTION
        "The value of vRtrMplsLspPathOperCspf indicates whether the currently
         operational LSP path has used CSPF computation for constrained-path
         enabled or disabled.

         When make-before-break functionality for the LSP is enabled and if the
         LSP CSPF setting is changed, the resources allocated to the existing
         LSP paths will not be released until a new path with the new settings
         has been established. While a new path is being signaled, the
         administrative value and the operational values of the path may
         differ. The value of vRtrMplsLspCspf specifies the CSPF setting for
         the new LSP path trying to be established whereas the value of
         vRtrMplsLspPathOperCspf specifies the CSPF setting for the existing
         LSP path."
    ::= { vRtrMplsLspPathOperEntry 8 }

vRtrMplsLspPathOperCspfToFrstLs  OBJECT-TYPE
    SYNTAX      TruthValue
    MAX-ACCESS  read-only
    STATUS      obsolete
    DESCRIPTION
        "The value of vRtrMplsLspPathOperCspfToFrstLs indicates whether the
         currently operational LSP path had CSPF to first loose hop enabled or
         disabled.

         When make-before-break functionality for the LSP is enabled and if the
         LSP CSPF to First Loose Hop setting is changed, the resources
         allocated to the existing LSP paths will not be released until a new
         path with the new settings has been established. While a new path is
         being signaled, the administrative value and the operational values of
         the path may differ. The value of vRtrMplsLspCspfToFirstLoose
         specifies the CSPF to First Loose Hop setting for the new LSP path
         trying to be established whereas the value of
         vRtrMplsLspPathOperCspfToFrstLs specifies the CSPF to First Loose Hop
         setting for the existing LSP path.

         This object was deprecated in the 11.0 release."
    ::= { vRtrMplsLspPathOperEntry 9 }

vRtrMplsLspPathOperLeastFill     OBJECT-TYPE
    SYNTAX      TruthValue
    MAX-ACCESS  read-only
    STATUS      current
    DESCRIPTION
        "The value of vRtrMplsLspPathOperLeastFill indicates whether the
         currently operational LSP path was computed with the least-fill path
         selection method.

         When make-before-break functionality for the LSP is enabled and if the
         LSP least-fill setting is changed, the resources allocated to the
         existing LSP paths will not be released until a new path with the new
         settings has been established. While a new path is being signaled, the
         administrative value and the operational values of the path may
         differ. The value of vRtrMplsLspLeastFill specifies the least-fill
         setting for the new LSP path trying to be established whereas the
         value of vRtrMplsLspPathOperLeastFill specifies the least-fill setting
         for the existing LSP path."
    ::= { vRtrMplsLspPathOperEntry 10 }

vRtrMplsLspPathOperRsvpAdspec    OBJECT-TYPE
    SYNTAX      TruthValue
    MAX-ACCESS  read-only
    STATUS      current
    DESCRIPTION
        "The value of vRtrMplsLspPathOperRsvpAdspec indicates whether the
         currently operational LSP path has ADSPEC object included in RSVP
         messages or not.

         When make-before-break functionality for the LSP is enabled and if the
         LSP adspec setting is changed, the resources allocated to the existing
         LSP paths will not be released until a new path with the new settings
         has been established. While a new path is being signaled, the
         administrative value and the operational values of the path may
         differ. The value of vRtrMplsLspRsvpAdspec specifies the adspec
         setting for the new LSP path trying to be established whereas the
         value of vRtrMplsLspPathOperRsvpAdspec specifies the adspec setting
         for the existing LSP path."
    ::= { vRtrMplsLspPathOperEntry 11 }

vRtrMplsLspPathOperFRNodeProtect OBJECT-TYPE
    SYNTAX      TruthValue
    MAX-ACCESS  read-only
    STATUS      current
    DESCRIPTION
        "The value of vRtrMplsLspPathOperFRNodeProtect indicates whether the
         currently operational LSP path has node protection enabled or
         disabled.

         When make-before-break functionality for the LSP is enabled and if the
         LSP node protection setting is changed, the resources allocated to the
         existing LSP paths will not be released until a new path with the new
         settings has been established. While a new path is being signaled, the
         administrative value and the operational values of the path may
         differ. The value of vRtrMplsLspFRNodeProtect specifies the node
         protection setting for the new LSP path trying to be established
         whereas the value of vRtrMplsLspPathOperFRNodeProtect specifies the
         node protection setting for the existing LSP path."
    ::= { vRtrMplsLspPathOperEntry 12 }

vRtrMplsLspPathOperPropAdminGrp  OBJECT-TYPE
    SYNTAX      TruthValue
    MAX-ACCESS  read-only
    STATUS      current
    DESCRIPTION
        "The value of vRtrMplsLspPathOperPropAdminGrp indicates whether the
         currently operational LSP path has propagation admin groups enabled or
         disabled.

         When make-before-break functionality for the LSP is enabled and if the
         LSP propagate admin groups setting is changed, the resources allocated
         to the existing LSP paths will not be released until a new path with
         the new settings has been established. While a new path is being
         signaled, the administrative value and the operational values of the
         path may differ. The value of vRtrMplsLspPropAdminGroup specifies the
         propagate admin groups setting for the new LSP path trying to be
         established whereas the value of vRtrMplsLspPathOperPropAdminGrp
         specifies the propagate admin groups setting for the existing LSP
         path."
    ::= { vRtrMplsLspPathOperEntry 13 }

vRtrMplsLspPathOperFRHopLimit    OBJECT-TYPE
    SYNTAX      Unsigned32 (0..255)
    MAX-ACCESS  read-only
    STATUS      current
    DESCRIPTION
        "The value of vRtrMplsLspPathOperFRHopLimit indicates the total number
         of hops to be used by detour LSP before merging to currently
         operational LSP path.

         When make-before-break functionality for the LSP is enabled and if the
         LSP FR Hop Limit setting is changed, the resources allocated to the
         existing LSP paths will not be released until a new path with the new
         settings has been established. While a new path is being signaled, the
         administrative value and the operational values of the path may
         differ. The value of vRtrMplsLspFRHopLimit specifies the FR Hop Limit
         setting for the new LSP path trying to be established whereas the
         value of vRtrMplsLspPathOperFRHopLimit specifies the FR Hop Limit
         setting for the existing LSP path."
    ::= { vRtrMplsLspPathOperEntry 14 }

vRtrMplsLspPathOperFRPropAdmGrp  OBJECT-TYPE
    SYNTAX      TruthValue
    MAX-ACCESS  read-only
    STATUS      current
    DESCRIPTION
        "The value of vRtrMplsLspPathOperFRPropAdmGrp indicates whether the
         currently operational LSP path has propagation of admin groups in the
         FAST_REROUTE object enabled or disabled.

         When make-before-break functionality for the LSP is enabled and if the
         LSP FR propagate admin groups is changed, the resources allocated to
         the existing LSP paths will not be released until a new path with the
         new settings has been established. While a new path is being signaled,
         the administrative value and the operational values of the path may
         differ. The value of vRtrMplsLspFRPropAdminGroup specifies the FR
         propagate admin group setting for the new LSP path trying to be
         established whereas the value of vRtrMplsLspPathOperFRPropAdmGrp
         specifies the FR propagate admin group setting for the existing LSP
         path."
    ::= { vRtrMplsLspPathOperEntry 15 }

vRtrMplsLspPathOperInterArea     OBJECT-TYPE
    SYNTAX      TruthValue
    MAX-ACCESS  read-only
    STATUS      current
    DESCRIPTION
        "The value of vRtrMplsLspPathOperInterArea indicates whether the
         operational LSP path is either inter-area or intra-area."
    ::= { vRtrMplsLspPathOperEntry 16 }

vRtrMplsLspPathOperCompMeth      OBJECT-TYPE
    SYNTAX      INTEGER {
        notApplicable (0),
        none          (1),
        localCspf     (2),
        pce           (3)
    }
    MAX-ACCESS  read-only
    STATUS      current
    DESCRIPTION
        "The value of vRtrMplsLspPathOperCompMeth indicates the path
         computation method that was used for the  currently operational LSP
         path.

         A value of 'notApplicable' indicates that the LSP path is
         operationally down or path list is SID."
    ::= { vRtrMplsLspPathOperEntry 17 }

vRtrMplsLspPathOperMetricType    OBJECT-TYPE
    SYNTAX      INTEGER {
        notApplicable (0),
        igp           (1),
        te            (2)
    }
    MAX-ACCESS  read-only
    STATUS      current
    DESCRIPTION
        "The value of vRtrMplsLspPathOperMetricType indicates the metric type
         used for the currently operational  LSP path.

         A value of 'notApplicable' indicates that the LSP path is
         operationally down."
    ::= { vRtrMplsLspPathOperEntry 18 }

vRtrMplsLspPathOperLocalSrProt   OBJECT-TYPE
    SYNTAX      INTEGER {
        notApplicable (0),
        none          (1),
        preferred     (2),
        mandatory     (3)
    }
    MAX-ACCESS  read-only
    STATUS      current
    DESCRIPTION
        "The value of vRtrMplsLspPathOperLocalSrProt indicates the local SR
         protection used for the currently operational  LSP path.

         A value of 'notApplicable' indicates that the LSP path is
         operationally down."
    ::= { vRtrMplsLspPathOperEntry 19 }

vRtrMplsLspPathOperLabelStackRed OBJECT-TYPE
    SYNTAX      INTEGER {
        notApplicable (0),
        true          (1),
        false         (2)
    }
    MAX-ACCESS  read-only
    STATUS      current
    DESCRIPTION
        "The value of vRtrMplsLspPathOperLabelStackRed indicates whether label
         stack reduction is used for the  currently operational LSP path.

         A value of 'notApplicable' indicates that the LSP path is
         operationally down."
    ::= { vRtrMplsLspPathOperEntry 20 }

vRtrMplsLspPathNgFNAddrType      OBJECT-TYPE
    SYNTAX      InetAddressType
    MAX-ACCESS  read-only
    STATUS      current
    DESCRIPTION
        "The vRtrMplsLspPathNgFNAddrType object is an  enumerated value that
         specifies the destination address type  of the node in the LSP path at
         which the LSP path failed."
    ::= { vRtrMplsLspPathOperEntry 21 }

vRtrMplsLspPathNgFNAddr          OBJECT-TYPE
    SYNTAX      InetAddress (SIZE (4|16))
    MAX-ACCESS  read-only
    STATUS      current
    DESCRIPTION
        "The value of vRtrMplsLspPathNgFNAddr indicates the IP address of the
         node in the LSP path at which the LSP path failed."
    ::= { vRtrMplsLspPathOperEntry 22 }

vRtrMplsLabelObjs                OBJECT IDENTIFIER ::= { tmnxMplsObjs 45 }

vRtrMplsLabelMaxStaticLspLabels  OBJECT-TYPE
    SYNTAX      Unsigned32 (0..262112)
    MAX-ACCESS  read-write
    STATUS      obsolete
    DESCRIPTION
        "The value of vRtrMplsLabelMaxStaticLspLabels specifies the maximum
         number of Static LSP labels available on the system.

         vRtrMplsLabelMaxStaticLspLabels must be set along with
         vRtrMplsLabelMaxStaticSvcLabels. The total of both values should equal
         the maximum value allowed of 131040 or 262112 depending on the system.

         The maximum value of vRtrMplsLabelMaxStaticLspLabels value for most
         systems is 113040 labels (128 * 1024 less 32 reserved labels).

         The maximum value of vRtrMplsLabelMaxStaticLspLabels value for chassis
         mode D systems is 262112 labels (256 * 1024 less 32 reserved labels).

         vRtrMplsLabelMaxStaticLspLabels is obsoleted in 13.0, replaced by
         vRtrMplsLabelStaticLabelRange."
    DEFVAL      { 2016 }
    ::= { vRtrMplsLabelObjs 1 }

vRtrMplsLabelMaxStaticSvcLabels  OBJECT-TYPE
    SYNTAX      Unsigned32 (0..262112)
    MAX-ACCESS  read-write
    STATUS      obsolete
    DESCRIPTION
        "The value of vRtrMplsLabelMaxStaticSvcLabels specifies the maximum
         number of Static SVC labels available on the system.

         vRtrMplsLabelMaxStaticSvcLabels must be set along with
         vRtrMplsLabelMaxStaticLspLabels. The total of both values should equal
         the maximum value allowed of 113040 or 262112 depending on the system.

         The maximum value of vRtrMplsLabelMaxStaticLspLabels value for most
         systems is 113040 labels (128 * 1024 less 32 reserved labels).

         The maximum value of vRtrMplsLabelMaxStaticLspLabels value for chassis
         mode D systems is 262112 labels (256 * 1024 less 32 reserved labels).

         vRtrMplsLabelMaxStaticSvcLabels is obsoleted in 13.0, replaced by
         vRtrMplsLabelStaticLabelRange."
    DEFVAL      { 16384 }
    ::= { vRtrMplsLabelObjs 2 }

vRtrMplsLabelBgpLabelsHoldTimer  OBJECT-TYPE
    SYNTAX      Unsigned32 (0..255)
    UNITS       "seconds"
    MAX-ACCESS  read-write
    STATUS      current
    DESCRIPTION
        "The value of vRtrMplsLabelBgpLabelsHoldTimer specifies the number of
         seconds to wait before deleting a BGP label entry based on the
         next-hop from IOM."
    DEFVAL      { 0 }
    ::= { vRtrMplsLabelObjs 3 }

vRtrMplsLabelSegRouteStartLabel  OBJECT-TYPE
    SYNTAX      TmnxMplsLabelOrZero
    MAX-ACCESS  read-write
    STATUS      current
    DESCRIPTION
        "The value of vRtrMplsLabelSegRouteStartLabel specifies the start value
         label available for Segment Routing on the system.

         vRtrMplsLabelSegRouteStartLabel must be set along with
         vRtrMplsLabelSegRouteEndLabel."
    DEFVAL      { 0 }
    ::= { vRtrMplsLabelObjs 4 }

vRtrMplsLabelSegRouteEndLabel    OBJECT-TYPE
    SYNTAX      TmnxMplsLabelOrZero
    MAX-ACCESS  read-write
    STATUS      current
    DESCRIPTION
        "The value of vRtrMplsLabelSegRouteEndLabel specifies the end value
         label available for Segment Routing on the system.

         vRtrMplsLabelSegRouteStartLabel must be set along with
         vRtrMplsLabelSegRouteEndLabel."
    DEFVAL      { 0 }
    ::= { vRtrMplsLabelObjs 5 }

vRtrMplsLabelStaticLabelRange    OBJECT-TYPE
    SYNTAX      Unsigned32 (0..1048544)
    MAX-ACCESS  read-write
    STATUS      current
    DESCRIPTION
        "The value of vRtrMplsLabelStaticLabelRange specifies the range of the
         Static labels available on the system.

         vRtrMplsLabelStaticLabelRange maximum value can be 524256 or 1048544
         depending on the system profile value (tmnxChassisSystemProfile).

         For a system configured with system profile as 'profileB', the maximum
         value of  vRtrMplsLabelStaticLabelRange is 1048544 labels (1024 * 1024
         less 32 reserved labels).

         Otherwise, the maximum value of vRtrMplsLabelStaticLabelRange
          is 524256 labels (512 * 1024 less 32 reserved labels). "
    DEFVAL      { 18400 }
    ::= { vRtrMplsLabelObjs 6 }

vRtrMplsLspTempAutoBWTblLastChg  OBJECT-TYPE
    SYNTAX      TimeStamp
    MAX-ACCESS  read-only
    STATUS      current
    DESCRIPTION
        "The value of vRtrMplsLspTempAutoBWTblLastChg indicates the sysUpTime
         at the time of the last modification to vRtrMplsLspTempAutoBWTable by
         adding, deleting an entry or change to a writable object in the table.

         If no changes were made to the table since the last re-initialization
         of the local network management subsystem, then this object contains a
         zero value."
    ::= { tmnxMplsObjs 46 }

vRtrMplsLspTempAutoBWTable       OBJECT-TYPE
    SYNTAX      SEQUENCE OF VRtrMplsLspTempAutoBWEntry
    MAX-ACCESS  not-accessible
    STATUS      current
    DESCRIPTION
        "The vRtrMplsLspTempAutoBWTable has an entry for auto bandwidth
         configuration for each Labeled Switch Path (LSP) template configured
         for a virtual router in the system."
    ::= { tmnxMplsObjs 47 }

vRtrMplsLspTempAutoBWEntry       OBJECT-TYPE
    SYNTAX      VRtrMplsLspTempAutoBWEntry
    MAX-ACCESS  not-accessible
    STATUS      current
    DESCRIPTION
        "Each row entry represents auto bandwidth configuration for a Labeled
         Switch Path (LSP) Template configured for a virtual router in the
         system."
    INDEX       {
        vRtrID,
        vRtrMplsLspTemplateName
    }
    ::= { vRtrMplsLspTempAutoBWTable 1 }

VRtrMplsLspTempAutoBWEntry       ::= SEQUENCE
{
    vRtrMplsLspTempAutoBWLastChg     TimeStamp,
    vRtrMplsLspTempAutoBWAdjDNPer    Unsigned32,
    vRtrMplsLspTempAutoBWAdjDNMbps   TmnxMplsLspBandwidth,
    vRtrMplsLspTempAutoBWAdjUPPer    Unsigned32,
    vRtrMplsLspTempAutoBWAdjUPMbps   TmnxMplsLspBandwidth,
    vRtrMplsLspTempAutoBWMaxBW       TmnxMplsLspBandwidth,
    vRtrMplsLspTempAutoBWMinBW       TmnxMplsLspBandwidth,
    vRtrMplsLspTempAutoBWMntrBW      TruthValue,
    vRtrMplsLspTempAutoBWAdjMult     Unsigned32,
    vRtrMplsLspTempAutoBWOverFlow    Unsigned32,
    vRtrMplsLspTempAutoBWOvrFlwThr   Unsigned32,
    vRtrMplsLspTempAutoBWOvrFlwBW    TmnxMplsLspBandwidth,
    vRtrMplsLspTempAutoBWSampMult    Unsigned32,
    vRtrMplsLspTempAutoBWSampTime    Unsigned32,
    vRtrMplsLspTempAutoBWInherit     Unsigned32,
    vRtrMplsLspTempAutoBWBeWeight    Unsigned32,
    vRtrMplsLspTempAutoBWL2Weight    Unsigned32,
    vRtrMplsLspTempAutoBWAfWeight    Unsigned32,
    vRtrMplsLspTempAutoBWL1Weight    Unsigned32,
    vRtrMplsLspTempAutoBWH2Weight    Unsigned32,
    vRtrMplsLspTempAutoBWEfWeight    Unsigned32,
    vRtrMplsLspTempAutoBWH1Weight    Unsigned32,
    vRtrMplsLspTempAutoBWNcWeight    Unsigned32,
    vRtrMplsLspTempAutoBWUnderFlow   Unsigned32,
    vRtrMplsLspTempAutoBWUndFlwThr   Unsigned32,
    vRtrMplsLspTempAutoBWUndFlwBW    TmnxMplsLspBandwidth
}

vRtrMplsLspTempAutoBWLastChg     OBJECT-TYPE
    SYNTAX      TimeStamp
    MAX-ACCESS  read-only
    STATUS      current
    DESCRIPTION
        "The value of vRtrMplsLspTempAutoBWLastChg indicates the sysUpTime when
         this row was last modified."
    ::= { vRtrMplsLspTempAutoBWEntry 1 }

vRtrMplsLspTempAutoBWAdjDNPer    OBJECT-TYPE
    SYNTAX      Unsigned32 (0..100)
    UNITS       "percent"
    MAX-ACCESS  read-write
    STATUS      current
    DESCRIPTION
        "The value of vRtrMplsLspTempAutoBWAdjDNPer specifies minimum
         difference between the current bandwidth reservation of the LSP
         template and the (measured) maximum average data rate, expressed as a
         percentage of the current bandwidth, for decreasing the bandwidth of
         the LSP template. At the adjust interval expiry, if the measured
         bandwidth falls below the current bandwidth by the value of
         vRtrMplsLspTempAutoBWAdjDNPer it can cause a resignaling attempt for
         the LSP template.

         A value of zero for this object indicates that the threshold check is
         always true for any measured bandwidth less than current bandwidth."
    DEFVAL      { 5 }
    ::= { vRtrMplsLspTempAutoBWEntry 2 }

vRtrMplsLspTempAutoBWAdjDNMbps   OBJECT-TYPE
    SYNTAX      TmnxMplsLspBandwidth
    UNITS       "megabps"
    MAX-ACCESS  read-write
    STATUS      current
    DESCRIPTION
        "The value of vRtrMplsLspTempAutoBWAdjDNMbps specifies the minimum
         difference between the current bandwidth reservation of the LSP
         template and the (measured) maximum average data rate, expressed as an
         absolute bandwidth (Mbps), for decreasing the bandwidth of the LSP
         template."
    DEFVAL      { 0 }
    ::= { vRtrMplsLspTempAutoBWEntry 3 }

vRtrMplsLspTempAutoBWAdjUPPer    OBJECT-TYPE
    SYNTAX      Unsigned32 (0..100)
    UNITS       "percent"
    MAX-ACCESS  read-write
    STATUS      current
    DESCRIPTION
        "The value of vRtrMplsLspTempAutoBWAdjUPPer specifies minimum
         difference between the current bandwidth reservation of the LSP
         template and the (measured) maximum average data rate, expressed as a
         percentage of the current bandwidth, for increasing the bandwidth of
         the LSP template. At the adjust interval expiry, if the measured
         bandwidth exceeds the current bandwidth by the value of
         vRtrMplsLspTempAutoBWAdjUPPer it can cause a resignaling attempt for
         the LSP template.

         When the value of vRtrMplsLspTempAutoBWAdjUPPer is 0 it means that
         this threshold check is always true for any measured bandwidth greater
         than current bandwidth"
    DEFVAL      { 5 }
    ::= { vRtrMplsLspTempAutoBWEntry 4 }

vRtrMplsLspTempAutoBWAdjUPMbps   OBJECT-TYPE
    SYNTAX      TmnxMplsLspBandwidth
    UNITS       "megabps"
    MAX-ACCESS  read-write
    STATUS      current
    DESCRIPTION
        "The value of vRtrMplsLspTempAutoBWAdjUPMbps specifies the minimum
         difference between the current bandwidth reservation of the LSP
         template and the (measured) maximum average data rate, expressed as an
         absolute bandwidth (Mbps), for increasing the bandwidth of the LSP
         template."
    DEFVAL      { 0 }
    ::= { vRtrMplsLspTempAutoBWEntry 5 }

vRtrMplsLspTempAutoBWMaxBW       OBJECT-TYPE
    SYNTAX      TmnxMplsLspBandwidth
    UNITS       "megabps"
    MAX-ACCESS  read-write
    STATUS      current
    DESCRIPTION
        "The value of vRtrMplsLspTempAutoBWMaxBW specifies the maximum that
         auto-bandwidth allocation is allowed to request for a LSP template."
    DEFVAL      { 100000 }
    ::= { vRtrMplsLspTempAutoBWEntry 6 }

vRtrMplsLspTempAutoBWMinBW       OBJECT-TYPE
    SYNTAX      TmnxMplsLspBandwidth
    UNITS       "megabps"
    MAX-ACCESS  read-write
    STATUS      current
    DESCRIPTION
        "The value of vRtrMplsLspTempAutoBWMinBW specifies the minimum that
         auto-bandwidth allocation is allowed to request for a LSP template."
    DEFVAL      { 0 }
    ::= { vRtrMplsLspTempAutoBWEntry 7 }

vRtrMplsLspTempAutoBWMntrBW      OBJECT-TYPE
    SYNTAX      TruthValue
    UNITS       "megabps"
    MAX-ACCESS  read-write
    STATUS      current
    DESCRIPTION
        "The value of vRtrMplsLspTempAutoBWMntrBW specifies whether the
         collection and display of auto-bandwidth measurements is enabled or
         disabled for the LSP template.

         When the value of vRtrMplsLspTempAutoBWMntrBW is 'true' the collection
         and display of auto-bandwidth measurements is enabled and when the
         value is 'false' it is disabled."
    DEFVAL      { false }
    ::= { vRtrMplsLspTempAutoBWEntry 8 }

vRtrMplsLspTempAutoBWAdjMult     OBJECT-TYPE
    SYNTAX      Unsigned32 (1..16383)
    MAX-ACCESS  read-write
    STATUS      current
    DESCRIPTION
        "The value of vRtrMplsLspTempAutoBWAdjMult specifies the number of
         collection intervals in the adjust interval.

         The default value is derived from vRtrMplsGeneralAutoBWDefAdjMul and
         vRtrMplsLspAutoBWAdjCount."
    DEFVAL      { 288 }
    ::= { vRtrMplsLspTempAutoBWEntry 9 }

vRtrMplsLspTempAutoBWOverFlow    OBJECT-TYPE
    SYNTAX      Unsigned32 (0 | 1..10)
    MAX-ACCESS  read-write
    STATUS      current
    DESCRIPTION
        "The value of vRtrMplsLspTempAutoBWOverFlow specifies number of
         overflow samples that triggers an overflow auto-bandwidth adjustment
         attempt."
    DEFVAL      { 0 }
    ::= { vRtrMplsLspTempAutoBWEntry 10 }

vRtrMplsLspTempAutoBWOvrFlwThr   OBJECT-TYPE
    SYNTAX      Unsigned32 (0 | 1..100)
    UNITS       "percent"
    MAX-ACCESS  read-write
    STATUS      current
    DESCRIPTION
        "The value of vRtrMplsLspTempAutoBWOvrFlwThr specifies the minimum
         difference between the current bandwidth of the LSP and the sampled
         data rate, expressed as a percentage of the current bandwidth, for
         counting an overflow sample."
    DEFVAL      { 0 }
    ::= { vRtrMplsLspTempAutoBWEntry 11 }

vRtrMplsLspTempAutoBWOvrFlwBW    OBJECT-TYPE
    SYNTAX      TmnxMplsLspBandwidth
    UNITS       "megabps"
    MAX-ACCESS  read-write
    STATUS      current
    DESCRIPTION
        "The value of vRtrMplsLspTempAutoBWOvrFlwBW specifies the minimum
         difference between the current bandwidth of the LSP template and the
         sampled data rate, expressed as an absolute bandwidth (Mbps), for
         counting an overflow sample."
    DEFVAL      { 0 }
    ::= { vRtrMplsLspTempAutoBWEntry 12 }

vRtrMplsLspTempAutoBWSampMult    OBJECT-TYPE
    SYNTAX      Unsigned32 (1..511)
    MAX-ACCESS  read-write
    STATUS      current
    DESCRIPTION
        "The value of vRtrMplsLspTempAutoBWSampMult specifies the multiplier
         for collection intervals in a sample interval."
    DEFVAL      { 1 }
    ::= { vRtrMplsLspTempAutoBWEntry 13 }

vRtrMplsLspTempAutoBWSampTime    OBJECT-TYPE
    SYNTAX      Unsigned32
    UNITS       "minutes"
    MAX-ACCESS  read-only
    STATUS      current
    DESCRIPTION
        "The value of vRtrMplsLspTempAutoBWSampTime indicates the sample
         multiplier times the collection interval."
    ::= { vRtrMplsLspTempAutoBWEntry 14 }

vRtrMplsLspTempAutoBWInherit     OBJECT-TYPE
    SYNTAX      Unsigned32
    MAX-ACCESS  read-write
    STATUS      current
    DESCRIPTION
        "For each writable object in this row that can be configured to inherit
         its value from the corresponding object in the vRtrMplsGeneralTable,
         there is bit within vRtrMplsLspTempAutoBWInherit that controls whether
         to inherit the operational value of the object or use the
         administratively set value.

         This object is a bit-mask, with the following positions:

         vRtrMplsLspTempAutoBWAdjMult          0x1
         vRtrMplsLspTempAutoBWSampMult         0x2

         When the bit for an object is set to one, then the object's
         administrative and operational value are whatever the DEFVAL or most
         recently SET value is.

         When the bit for an object is set to zero, then the object's
         administrative and operational value are inherited from the
         corresponding object in vRtrMplsGeneralTable."
    DEFVAL      { 0 }
    ::= { vRtrMplsLspTempAutoBWEntry 15 }

vRtrMplsLspTempAutoBWBeWeight    OBJECT-TYPE
    SYNTAX      Unsigned32 (0..100)
    UNITS       "percent"
    MAX-ACCESS  read-write
    STATUS      current
    DESCRIPTION
        "The value of vRtrMplsLspTempAutoBWBeWeight specifies the weight in
         percent for forwarding class 'BE' for the LSP template."
    DEFVAL      { 100 }
    ::= { vRtrMplsLspTempAutoBWEntry 16 }

vRtrMplsLspTempAutoBWL2Weight    OBJECT-TYPE
    SYNTAX      Unsigned32 (0..100)
    UNITS       "percent"
    MAX-ACCESS  read-write
    STATUS      current
    DESCRIPTION
        "The value of vRtrMplsLspTempAutoBWL2Weight specifies the weight in
         percent for forwarding class 'L2' for the LSP template."
    DEFVAL      { 100 }
    ::= { vRtrMplsLspTempAutoBWEntry 17 }

vRtrMplsLspTempAutoBWAfWeight    OBJECT-TYPE
    SYNTAX      Unsigned32 (0..100)
    UNITS       "percent"
    MAX-ACCESS  read-write
    STATUS      current
    DESCRIPTION
        "The value of vRtrMplsLspTempAutoBWAfWeight specifies the weight in
         percent for forwarding class 'AF' for the LSP template."
    DEFVAL      { 100 }
    ::= { vRtrMplsLspTempAutoBWEntry 18 }

vRtrMplsLspTempAutoBWL1Weight    OBJECT-TYPE
    SYNTAX      Unsigned32 (0..100)
    UNITS       "percent"
    MAX-ACCESS  read-write
    STATUS      current
    DESCRIPTION
        "The value of vRtrMplsLspTempAutoBWL1Weight specifies the weight in
         percent for forwarding class 'L1' for the LSP template."
    DEFVAL      { 100 }
    ::= { vRtrMplsLspTempAutoBWEntry 19 }

vRtrMplsLspTempAutoBWH2Weight    OBJECT-TYPE
    SYNTAX      Unsigned32 (0..100)
    UNITS       "percent"
    MAX-ACCESS  read-write
    STATUS      current
    DESCRIPTION
        "The value of vRtrMplsLspTempAutoBWH2Weight specifies the weight in
         percent for forwarding class 'H2' for the LSP template."
    DEFVAL      { 100 }
    ::= { vRtrMplsLspTempAutoBWEntry 20 }

vRtrMplsLspTempAutoBWEfWeight    OBJECT-TYPE
    SYNTAX      Unsigned32 (0..100)
    UNITS       "percent"
    MAX-ACCESS  read-write
    STATUS      current
    DESCRIPTION
        "The value of vRtrMplsLspTempAutoBWEfWeight specifies the weight in
         percent for forwarding class 'EF' for the LSP template."
    DEFVAL      { 100 }
    ::= { vRtrMplsLspTempAutoBWEntry 21 }

vRtrMplsLspTempAutoBWH1Weight    OBJECT-TYPE
    SYNTAX      Unsigned32 (0..100)
    UNITS       "percent"
    MAX-ACCESS  read-write
    STATUS      current
    DESCRIPTION
        "The value of vRtrMplsLspTempAutoBWH1Weight specifies the weight in
         percent for forwarding class 'H1' for the LSP template."
    DEFVAL      { 100 }
    ::= { vRtrMplsLspTempAutoBWEntry 22 }

vRtrMplsLspTempAutoBWNcWeight    OBJECT-TYPE
    SYNTAX      Unsigned32 (0..100)
    UNITS       "percent"
    MAX-ACCESS  read-write
    STATUS      current
    DESCRIPTION
        "The value of vRtrMplsLspTempAutoBWNcWeight specifies the weight in
         percent for forwarding class 'NC' for the LSP template."
    DEFVAL      { 100 }
    ::= { vRtrMplsLspTempAutoBWEntry 23 }

vRtrMplsLspTempAutoBWUnderFlow   OBJECT-TYPE
    SYNTAX      Unsigned32 (0 | 1..10)
    MAX-ACCESS  read-write
    STATUS      current
    DESCRIPTION
        "The value of vRtrMplsLspTempAutoBWUnderFlow specifies the number of
         underflow samples that trigger an underflow auto-bandwidth adjustment
         attempt."
    DEFVAL      { 0 }
    ::= { vRtrMplsLspTempAutoBWEntry 24 }

vRtrMplsLspTempAutoBWUndFlwThr   OBJECT-TYPE
    SYNTAX      Unsigned32 (0 | 1..100)
    UNITS       "percent"
    MAX-ACCESS  read-write
    STATUS      current
    DESCRIPTION
        "The value of vRtrMplsLspTempAutoBWUndFlwThr specifies the minimum
         difference between the current bandwidth of the LSP and the sampled
         data rate, expressed as a percentage of the current bandwidth, for
         counting an underflow sample."
    DEFVAL      { 0 }
    ::= { vRtrMplsLspTempAutoBWEntry 25 }

vRtrMplsLspTempAutoBWUndFlwBW    OBJECT-TYPE
    SYNTAX      TmnxMplsLspBandwidth
    UNITS       "megabps"
    MAX-ACCESS  read-write
    STATUS      current
    DESCRIPTION
        "The value of vRtrMplsLspTempAutoBWUndFlwBW specifies the minimum
         difference between the current bandwidth of the LSP template and the
         sampled data rate, expressed as an absolute bandwidth (Mbps), for
         counting an underflow sample."
    DEFVAL      { 0 }
    ::= { vRtrMplsLspTempAutoBWEntry 26 }

vRtrMplsTemplPlcyBindTblLastChg  OBJECT-TYPE
    SYNTAX      TimeStamp
    MAX-ACCESS  read-only
    STATUS      current
    DESCRIPTION
        "The value of vRtrMplsTemplPlcyBindTblLastChg indicates the sysUpTime
         at the time of the last modification to vRtrMplsLspTemplPlcyBindTable
         by adding, deleting an entry or change to a writable object in the
         table.

         If no changes were made to the table since the last re-initialization
         of the local network management subsystem, then this object contains a
         zero value."
    ::= { tmnxMplsObjs 48 }

vRtrMplsLspTemplPlcyBindTable    OBJECT-TYPE
    SYNTAX      SEQUENCE OF VRtrMplsLspTemplPlcyBindEntry
    MAX-ACCESS  not-accessible
    STATUS      current
    DESCRIPTION
        "The vRtrMplsLspTemplPlcyBindTable has an entry for each policy bound
         to each Labeled Switch Path (LSP) template configured for a virtual
         router in the system."
    ::= { tmnxMplsObjs 49 }

vRtrMplsLspTemplPlcyBindEntry    OBJECT-TYPE
    SYNTAX      VRtrMplsLspTemplPlcyBindEntry
    MAX-ACCESS  not-accessible
    STATUS      current
    DESCRIPTION
        "Each row entry represents a policy bound to a Labeled Switch Path
         (LSP) Template configured for a virtual router in the system."
    INDEX       {
        vRtrID,
        vRtrMplsLspTemplateName
    }
    ::= { vRtrMplsLspTemplPlcyBindTable 1 }

VRtrMplsLspTemplPlcyBindEntry    ::= SEQUENCE
{
    vRtrMplsLspTemplPlcyBindLastChg  TimeStamp,
    vRtrMplsLspTemplPlcyBindRowStat  RowStatus,
    vRtrMplsLspTemplPlcyBind1        TPolicyStatementNameOrEmpty,
    vRtrMplsLspTemplPlcyBind2        TPolicyStatementNameOrEmpty,
    vRtrMplsLspTemplPlcyBind3        TPolicyStatementNameOrEmpty,
    vRtrMplsLspTemplPlcyBind4        TPolicyStatementNameOrEmpty,
    vRtrMplsLspTemplPlcyBind5        TPolicyStatementNameOrEmpty,
    vRtrMplsLspTemplPlcyBindOneHop   TruthValue
}

vRtrMplsLspTemplPlcyBindLastChg  OBJECT-TYPE
    SYNTAX      TimeStamp
    MAX-ACCESS  read-only
    STATUS      current
    DESCRIPTION
        "The value of the object vRtrMplsLspTemplPlcyBindLastChg indicates the
         value of the sysUpTime when this entry was last modified."
    ::= { vRtrMplsLspTemplPlcyBindEntry 1 }

vRtrMplsLspTemplPlcyBindRowStat  OBJECT-TYPE
    SYNTAX      RowStatus
    MAX-ACCESS  read-create
    STATUS      current
    DESCRIPTION
        "The value of the object vRtrMplsLspTemplPlcyBindRowStat specifies the
         RowStatus for Policy bound entry."
    ::= { vRtrMplsLspTemplPlcyBindEntry 2 }

vRtrMplsLspTemplPlcyBind1        OBJECT-TYPE
    SYNTAX      TPolicyStatementNameOrEmpty
    MAX-ACCESS  read-create
    STATUS      current
    DESCRIPTION
        "The value of vRtrMplsLspTemplPlcyBind1 specifies the name of the first
         mpls lsp template policy.

         This object will be set to its default value when
         vRtrMplsLspTemplPlcyBindOneHop is set to true."
    DEFVAL      { ''H }
    ::= { vRtrMplsLspTemplPlcyBindEntry 3 }

vRtrMplsLspTemplPlcyBind2        OBJECT-TYPE
    SYNTAX      TPolicyStatementNameOrEmpty
    MAX-ACCESS  read-create
    STATUS      current
    DESCRIPTION
        "The value of vRtrMplsLspTemplPlcyBind2 specifies the name of the
         second mpls lsp template policy.

         This object will be set to its default value when
         vRtrMplsLspTemplPlcyBindOneHop is set to true."
    DEFVAL      { ''H }
    ::= { vRtrMplsLspTemplPlcyBindEntry 4 }

vRtrMplsLspTemplPlcyBind3        OBJECT-TYPE
    SYNTAX      TPolicyStatementNameOrEmpty
    MAX-ACCESS  read-create
    STATUS      current
    DESCRIPTION
        "The value of vRtrMplsLspTemplPlcyBind3 specifies the name of the third
         mpls lsp template policy.

         This object will be set to its default value when
         vRtrMplsLspTemplPlcyBindOneHop is set to true."
    DEFVAL      { ''H }
    ::= { vRtrMplsLspTemplPlcyBindEntry 5 }

vRtrMplsLspTemplPlcyBind4        OBJECT-TYPE
    SYNTAX      TPolicyStatementNameOrEmpty
    MAX-ACCESS  read-create
    STATUS      current
    DESCRIPTION
        "The value of vRtrMplsLspTemplPlcyBind4 specifies the name of the
         fourth mpls lsp template policy.

         This object will be set to its default value when
         vRtrMplsLspTemplPlcyBindOneHop is set to true."
    DEFVAL      { ''H }
    ::= { vRtrMplsLspTemplPlcyBindEntry 6 }

vRtrMplsLspTemplPlcyBind5        OBJECT-TYPE
    SYNTAX      TPolicyStatementNameOrEmpty
    MAX-ACCESS  read-create
    STATUS      current
    DESCRIPTION
        "The value of vRtrMplsLspTemplPlcyBind5 specifies the name of the fifth
         mpls lsp template policy.

         This object will be set to its default value when
         vRtrMplsLspTemplPlcyBindOneHop is set to true."
    DEFVAL      { ''H }
    ::= { vRtrMplsLspTemplPlcyBindEntry 7 }

vRtrMplsLspTemplPlcyBindOneHop   OBJECT-TYPE
    SYNTAX      TruthValue
    MAX-ACCESS  read-create
    STATUS      current
    DESCRIPTION
        "The value of vRtrMplsLspTemplPlcyBindOneHop specifies whether the
         one-hop-p2p has been enabled for auto-lsp or not.

         This object will be set to false when any one of the policy for mpls
         lsp template is set to its non-default value."
    DEFVAL      { false }
    ::= { vRtrMplsLspTemplPlcyBindEntry 8 }

vRtrMplsLspTempInStatTblLstChg   OBJECT-TYPE
    SYNTAX      TimeStamp
    MAX-ACCESS  read-only
    STATUS      current
    DESCRIPTION
        "Timestamp of the last change to the vRtrMplsLspTempInStatTblLstChg
         either from adding a row or removing a row."
    ::= { tmnxMplsObjs 50 }

vRtrMplsLspTempInStatTable       OBJECT-TYPE
    SYNTAX      SEQUENCE OF VRtrMplsLspTempInStatEntry
    MAX-ACCESS  not-accessible
    STATUS      current
    DESCRIPTION
        "vRtrMplsLspTempInStatTable controls Ingress Statistics for Template
         based Label Switched Path (LSP)."
    ::= { tmnxMplsObjs 51 }

vRtrMplsLspTempInStatEntry       OBJECT-TYPE
    SYNTAX      VRtrMplsLspTempInStatEntry
    MAX-ACCESS  not-accessible
    STATUS      current
    DESCRIPTION
        "A row in this table represents information about the ingress
         statistics collection for Template based LSP."
    INDEX       {
        vRtrID,
        vRtrMplsLspTempInStatType,
        vRtrMplsLspTempInStatSndrAddrTyp,
        vRtrMplsLspTempInStatSndrAddr,
        vRtrMplsLspTempInStatLspNamePref
    }
    ::= { vRtrMplsLspTempInStatTable 1 }

VRtrMplsLspTempInStatEntry       ::= SEQUENCE
{
    vRtrMplsLspTempInStatType        INTEGER,
    vRtrMplsLspTempInStatSndrAddrTyp InetAddressType,
    vRtrMplsLspTempInStatSndrAddr    InetAddress,
    vRtrMplsLspTempInStatLspNamePref TLNamedItem,
    vRtrMplsLspTempInStatRowStatus   RowStatus,
    vRtrMplsLspTempInStatLastChanged TimeStamp,
    vRtrMplsLspTempInStatCollectStat TruthValue,
    vRtrMplsLspTempInStatAccntPolicy Unsigned32,
    vRtrMplsLspTempInStatAdminState  TmnxAdminState,
    vRtrMplsLspTempInStatMaxStats    Unsigned32,
    vRtrMplsLspTempInStatTotlSession Unsigned32
}

vRtrMplsLspTempInStatType        OBJECT-TYPE
    SYNTAX      INTEGER {
        unknown (0),
        p2p     (1),
        p2mp    (2)
    }
    MAX-ACCESS  not-accessible
    STATUS      current
    DESCRIPTION
        "The value of vRtrMplsLspTempInStatType indicates the type of template
         based Label Switched Path (LSP)."
    ::= { vRtrMplsLspTempInStatEntry 1 }

vRtrMplsLspTempInStatSndrAddrTyp OBJECT-TYPE
    SYNTAX      InetAddressType
    MAX-ACCESS  not-accessible
    STATUS      current
    DESCRIPTION
        "The value of vRtrMplsLspTempInStatSndrAddrTyp indicates address type
         of vRtrMplsLspTempInStatSndrAddr."
    ::= { vRtrMplsLspTempInStatEntry 2 }

vRtrMplsLspTempInStatSndrAddr    OBJECT-TYPE
    SYNTAX      InetAddress (SIZE (4|16))
    MAX-ACCESS  not-accessible
    STATUS      current
    DESCRIPTION
        "The value of vRtrMplsLspTempInStatSndrAddr indicates the sender
         address."
    ::= { vRtrMplsLspTempInStatEntry 3 }

vRtrMplsLspTempInStatLspNamePref OBJECT-TYPE
    SYNTAX      TLNamedItem
    MAX-ACCESS  not-accessible
    STATUS      current
    DESCRIPTION
        "The value of vRtrMplsLspTempInStatLspNamePref indicates the prefix
         against which to match the LSP name."
    ::= { vRtrMplsLspTempInStatEntry 4 }

vRtrMplsLspTempInStatRowStatus   OBJECT-TYPE
    SYNTAX      RowStatus
    MAX-ACCESS  read-create
    STATUS      current
    DESCRIPTION
        "vRtrMplsLspTempInStatRowStatus is used for the creation or deletion of
         entries in the vRtrMplsLspTempInStatTable."
    ::= { vRtrMplsLspTempInStatEntry 5 }

vRtrMplsLspTempInStatLastChanged OBJECT-TYPE
    SYNTAX      TimeStamp
    MAX-ACCESS  read-only
    STATUS      current
    DESCRIPTION
        "The value of vRtrMplsLspTempInStatLastChanged indicates the time stamp
         of the last change to this row of this table."
    ::= { vRtrMplsLspTempInStatEntry 6 }

vRtrMplsLspTempInStatCollectStat OBJECT-TYPE
    SYNTAX      TruthValue
    MAX-ACCESS  read-create
    STATUS      current
    DESCRIPTION
        "The value of vRtrMplsLspTempInStatCollectStat specifies whether to
         collect statistics for this prefix."
    DEFVAL      { false }
    ::= { vRtrMplsLspTempInStatEntry 7 }

vRtrMplsLspTempInStatAccntPolicy OBJECT-TYPE
    SYNTAX      Unsigned32 (0 | 1..99)
    MAX-ACCESS  read-create
    STATUS      current
    DESCRIPTION
        "The value of vRtrMplsLspTempInStatAccntPolicy specifies the accounting
         policy to be used for this entry.

         A value of zero indicates that the default accounting policy should be
         used."
    DEFVAL      { 0 }
    ::= { vRtrMplsLspTempInStatEntry 8 }

vRtrMplsLspTempInStatAdminState  OBJECT-TYPE
    SYNTAX      TmnxAdminState
    MAX-ACCESS  read-create
    STATUS      current
    DESCRIPTION
        "The value of vRtrMplsLspTempInStatAdminState specifies whether ingress
         statistics is enabled for this Label Switched Path (LSP) template."
    DEFVAL      { outOfService }
    ::= { vRtrMplsLspTempInStatEntry 9 }

vRtrMplsLspTempInStatMaxStats    OBJECT-TYPE
    SYNTAX      Unsigned32 (1..8191)
    MAX-ACCESS  read-create
    STATUS      current
    DESCRIPTION
        "The value of vRtrMplsLspTempInStatMaxStats specifies the maximum
         number of stat indices assigned to this Label Switched Path (LSP)
         template session."
    DEFVAL      { 8191 }
    ::= { vRtrMplsLspTempInStatEntry 10 }

vRtrMplsLspTempInStatTotlSession OBJECT-TYPE
    SYNTAX      Unsigned32
    MAX-ACCESS  read-only
    STATUS      current
    DESCRIPTION
        "The value of vRtrMplsLspTempInStatTotlSession indicates the total
         number of sessions associated with this Label Switched Path (LSP)
         template statistics."
    ::= { vRtrMplsLspTempInStatEntry 11 }

vRtrMplsLspExtTable              OBJECT-TYPE
    SYNTAX      SEQUENCE OF VRtrMplsLspExtEntry
    MAX-ACCESS  not-accessible
    STATUS      current
    DESCRIPTION
        "The vRtrMplsLspTable has an entry for each Labeled Switch Path (LSP)
         configured for a virtual router in the system. This table augments the
         vRtrMplsLspTable."
    ::= { tmnxMplsObjs 52 }

vRtrMplsLspExtEntry              OBJECT-TYPE
    SYNTAX      VRtrMplsLspExtEntry
    MAX-ACCESS  not-accessible
    STATUS      current
    DESCRIPTION
        "Each row entry represents a Labeled Switch Path (LSP) configured
         for a virtual router in the system.  Entries can be created and
         deleted via SNMP SET operations.  Each row entry represents a Labeled
         Switch Path (LSP) configured for a virtual router in the system.
         Entries can be created and deleted via SNMP SET operations using the
         vRtrMplsLspRowStatus variable."
    AUGMENTS    { vRtrMplsLspEntry }
    ::= { vRtrMplsLspExtTable 1 }

VRtrMplsLspExtEntry              ::= SEQUENCE
{
    vRtrMplsLspExtPceCompute         TruthValue,
    vRtrMplsLspExtPceControl         TruthValue,
    vRtrMplsLspExtPceReport          INTEGER,
    vRtrMplsLspExtTtmTunnelId        Unsigned32,
    vRtrMplsLspExtMaxSrLabels        Unsigned32,
    vRtrMplsLspExtTunnelId           Unsigned32,
    vRtrMplsLspExtEntropyLabel       INTEGER,
    vRtrMplsLspExtOperEntropyLabel   INTEGER,
    vRtrMplsLspExtFrrOverheadLabel   Unsigned32,
    vRtrMplsLspExtNegEntropyLbl      INTEGER,
    vRtrMplsLspExtBfdFailureAction   INTEGER,
    vRtrMplsLspExtCbfFwdingPlcy      TNamedItemOrEmpty,
    vRtrMplsLspExtCbfFwdingSet       Unsigned32,
    vRtrMplsLspExtPathCompMeth       INTEGER,
    vRtrMplsLspExtMetricType         INTEGER,
    vRtrMplsLspExtLocalSrProt        INTEGER,
    vRtrMplsLspExtLabelStackRed      TruthValue,
    vRtrMplsLspExtBfdUpWaitTimer     Unsigned32,
    vRtrMplsLspExtSelfPing           INTEGER
}

vRtrMplsLspExtPceCompute         OBJECT-TYPE
    SYNTAX      TruthValue
    MAX-ACCESS  read-create
    STATUS      obsolete
    DESCRIPTION
        "The value of vRtrMplsLspExtPceCompute specifies whether the LSP path
         computation request is sent to local CSPF or to PCE. When the value of
         this object is 'true', the LSP makes a request to PCE to compute the
         path. When the value of this object is 'false', the path for this LSP
         is computed locally using CSPF."
    DEFVAL      { false }
    ::= { vRtrMplsLspExtEntry 1 }

vRtrMplsLspExtPceControl         OBJECT-TYPE
    SYNTAX      TruthValue
    MAX-ACCESS  read-create
    STATUS      current
    DESCRIPTION
        "The value of vRtrMplsLspExtPceControl specifies whether the control of
         path (delegation) to Path Computation Engine (PCE). Path delegation
         can be done on locally computed paths and paths computed using PCE."
    DEFVAL      { false }
    ::= { vRtrMplsLspExtEntry 2 }

vRtrMplsLspExtPceReport          OBJECT-TYPE
    SYNTAX      INTEGER {
        enable  (1),
        disable (2),
        inherit (3)
    }
    MAX-ACCESS  read-create
    STATUS      current
    DESCRIPTION
        "The value of vRtrMplsLspExtPceReport specifies whether to override the
         global configuration of reporting of LSP to PCE.

         If the value of vRtrMplsLspExtPceReport is 'disabled' for an LSP
         either due to inheritance or due to LSP level configuration, the value
         of vRtrMplsLspExtPceControl has no affect.

         The default value for vRtrMplsLspExtPceReport is 'inherit'."
    DEFVAL      { inherit }
    ::= { vRtrMplsLspExtEntry 3 }

vRtrMplsLspExtTtmTunnelId        OBJECT-TYPE
    SYNTAX      Unsigned32
    MAX-ACCESS  read-only
    STATUS      current
    DESCRIPTION
        "The value of vRtrMplsLspExtTtmTunnelId indicates the tunnel id sent to
         TTM for Segment Routing Tunnels on this SROS system."
    ::= { vRtrMplsLspExtEntry 4 }

vRtrMplsLspExtMaxSrLabels        OBJECT-TYPE
    SYNTAX      Unsigned32 (1..11)
    MAX-ACCESS  read-create
    STATUS      current
    DESCRIPTION
        "The value of vRtrMplsLspExtMaxSrLabels specifies maximum segment
         routing label stack size for this LSP.

         The default IXR platform is 3 and maximum value supported is 5."
    DEFVAL      { 6 }
    ::= { vRtrMplsLspExtEntry 5 }

vRtrMplsLspExtTunnelId           OBJECT-TYPE
    SYNTAX      Unsigned32
    MAX-ACCESS  read-only
    STATUS      current
    DESCRIPTION
        "The value of vRtrMplsLspExtTunnelId indicates the tunnel id used to
         uniquely identify tunnels on this SROS system."
    ::= { vRtrMplsLspExtEntry 6 }

vRtrMplsLspExtEntropyLabel       OBJECT-TYPE
    SYNTAX      INTEGER {
        forceDisable (1),
        enable       (2),
        inherit      (3)
    }
    MAX-ACCESS  read-create
    STATUS      current
    DESCRIPTION
        "The value of vRtrMplsLspExtEntropyLabel specifies whether the
         application takes into account the value of Entropy Label and Entropy
         Label Capability in the label stack for this LSP.

         When the value of vRtrMplsLspExtEntropyLabel is set to 'enable', the
         application will account for EL/ELC in the label stack without taking
         into consideration the value of the enabled ELC.

         When the value of vRtrMplsLspExtEntropyLabel is set to
         'force-disable', the application will ignore the value of enabled ELC.

         When the value of vRtrMplsLspExtEntropyLabel is modified, Entropy
         Label will become operational when this LSP is resignalled.

         By default, if this LSP is of type RSVP-TE it will inherit the
         behavior as set by vRtrMplsGeneralEntropyLblRsvpTe, or if the LSP is
         of type SR-TE it will inherit from vRtrMplsGeneralEntropyLblSrTe."
    DEFVAL      { inherit }
    ::= { vRtrMplsLspExtEntry 7 }

vRtrMplsLspExtOperEntropyLabel   OBJECT-TYPE
    SYNTAX      INTEGER {
        forceDisable (1),
        enable       (2)
    }
    MAX-ACCESS  read-only
    STATUS      current
    DESCRIPTION
        "The value of vRtrMplsLspExtOperEntropyLabel indicates the operational
         value of Entropy Label for this LSP.

         When the value of vRtrMplsLspExtOperEntropyLabel is modified, Entropy
         Label will become operational when this LSP is resignalled.

         By default, this LSP will have Entropy Label set to 'force-disable'."
    ::= { vRtrMplsLspExtEntry 8 }

vRtrMplsLspExtFrrOverheadLabel   OBJECT-TYPE
    SYNTAX      Unsigned32 (0..4)
    MAX-ACCESS  read-create
    STATUS      current
    DESCRIPTION
        "The value of vRtrMplsLspExtFrrOverheadLabel specifies maximum
         additional overhead labels for this LSP."
    DEFVAL      { 1 }
    ::= { vRtrMplsLspExtEntry 9 }

vRtrMplsLspExtNegEntropyLbl      OBJECT-TYPE
    SYNTAX      INTEGER {
        forceDisable (1),
        enable       (2)
    }
    MAX-ACCESS  read-only
    STATUS      current
    DESCRIPTION
        "The value of vRtrMplsLspExtNegEntropyLbl indicates the combination of
         Entropy Label configured at head end for this LSP and the Entropy
         Label Capability signalled from the far end."
    ::= { vRtrMplsLspExtEntry 10 }

vRtrMplsLspExtBfdFailureAction   OBJECT-TYPE
    SYNTAX      INTEGER {
        none           (0),
        down           (1),
        failover       (2),
        failoverOrDown (3)
    }
    MAX-ACCESS  read-create
    STATUS      current
    DESCRIPTION
        "The value of vRtrMplsLspExtBfdFailureAction specifies the actions to
         be taken when this LSP BFD session fails.

         When vRtrMplsLspExtBfdFailureAction is set to down, it prevents the
         LSP from being made available as a transport for any user.

         When vRtrMplsLspExtBfdFailureAction is set to failover, the Lsp is
         always  marked as usable, regardless of the BFD session state.

         When vRtrMplsLspExtBfdFailureAction is set to failoverOrDown and the
         BFD session  associated with the active-path of the LSP goes down, the
         LSP will switch to the  standby-path if applicable. When the LSP
         cannot switchover, the LSP will go  operationally down."
    DEFVAL      { none }
    ::= { vRtrMplsLspExtEntry 11 }

vRtrMplsLspExtCbfFwdingPlcy      OBJECT-TYPE
    SYNTAX      TNamedItemOrEmpty
    MAX-ACCESS  read-create
    STATUS      current
    DESCRIPTION
        "The value of vRtrMplsLspExtCbfFwdingPlcy specifies the name of the
         Class Forwarding Policy for this LSP instance."
    DEFVAL      { "" }
    ::= { vRtrMplsLspExtEntry 12 }

vRtrMplsLspExtCbfFwdingSet       OBJECT-TYPE
    SYNTAX      Unsigned32 (0..6)
    MAX-ACCESS  read-create
    STATUS      current
    DESCRIPTION
        "The value of vRtrMplsLspExtCbfFwdingSet specifies the Class Forwarding
         Set ID for this LSP instance. If system profile is profile-b then
         valid range is 0..6 else 0..4"
    DEFVAL      { 0 }
    ::= { vRtrMplsLspExtEntry 13 }

vRtrMplsLspExtPathCompMeth       OBJECT-TYPE
    SYNTAX      INTEGER {
        none      (1),
        localCspf (2),
        pce       (3)
    }
    MAX-ACCESS  read-create
    STATUS      current
    DESCRIPTION
        "The value of vRtrMplsLspExtPathCompMeth specifies LSP path
         computation method.

         If the value of vRtrMplsLspExtPathCompMeth is 'localCspf' for an LSP
         the path uses local CSPF.

         If the value of vRtrMplsLspExtPathCompMeth is 'pce' for an LSP the
         path uses PCE;

         The default value for vRtrMplsLspExtPathCompMeth is 'none'."
    DEFVAL      { none }
    ::= { vRtrMplsLspExtEntry 14 }

vRtrMplsLspExtMetricType         OBJECT-TYPE
    SYNTAX      INTEGER {
        igp (1),
        te  (2)
    }
    MAX-ACCESS  read-create
    STATUS      current
    DESCRIPTION
        "The value of vRtrMplsLspExtMetricType specifies metric type.

         If the value of vRtrMplsLspExtMetricType is 'igp', the metric used is
         IGP.

         If the value of vRtrMplsLspExtMetricType is 'te', the metric used is
         TE.

         The default value for vRtrMplsLspExtPceReport is 'igp'."
    DEFVAL      { igp }
    ::= { vRtrMplsLspExtEntry 15 }

vRtrMplsLspExtLocalSrProt        OBJECT-TYPE
    SYNTAX      INTEGER {
        none      (1),
        preferred (2),
        mandatory (3)
    }
    MAX-ACCESS  read-create
    STATUS      current
    DESCRIPTION
        "The value of vRtrMplsLspExtLocalSrProt specifies the local SR
         protection.

         If the value of vRtrMplsLspExtLocalSrProt is 'none', there is no
         protection.

         If the value of vRtrMplsLspExtLocalSrProt is 'preferred', the
         protection is preferred.

         If the value of vRtrMplsLspExtLocalSrProt is 'mandatory', the
         protection is mandatory.

         The default value for vRtrMplsLspExtLocalSrProt is 'none'."
    DEFVAL      { preferred }
    ::= { vRtrMplsLspExtEntry 16 }

vRtrMplsLspExtLabelStackRed      OBJECT-TYPE
    SYNTAX      TruthValue
    MAX-ACCESS  read-create
    STATUS      current
    DESCRIPTION
        "The value of vRtrMplsLspExtLabelStackRed specifies whether label stack
         reduction is enabled."
    DEFVAL      { false }
    ::= { vRtrMplsLspExtEntry 17 }

vRtrMplsLspExtBfdUpWaitTimer     OBJECT-TYPE
    SYNTAX      Unsigned32 (1..60)
    UNITS       "seconds"
    MAX-ACCESS  read-create
    STATUS      current
    DESCRIPTION
        "The value of vRtrMplsLspExtBfdUpWaitTimer specifies the time in
         seconds the software will wait for BFD to come up.

         The timer object is applicable only when
         vRtrMplsLspExtBfdFailureAction  is set to 'failoverOrDown'.

         The timer object is applicable for LSPs with vRtrMplsLspType set to
         'srTe'.

         The timer is started when BFD is first enabled on a path or BFD
         transitions from up to down. When this timer expires and if BFD has
         not yet come up, the path is torn down by removing it from TTM and
         the IOM and the retry timer is started."
    DEFVAL      { 4 }
    ::= { vRtrMplsLspExtEntry 18 }

vRtrMplsLspExtSelfPing           OBJECT-TYPE
    SYNTAX      INTEGER {
        enable  (1),
        disable (2),
        inherit (3)
    }
    MAX-ACCESS  read-create
    STATUS      current
    DESCRIPTION
        "The value of vRtrMplsLspExtSelfPing specifies whether to override the
         global configuration of Self Ping.

         If the value of vRtrMplsLspExtSelfPing is 'disabled' for an LSP either
         due to inheritance or due to LSP level configuration, the value of
         vRtrMplsLspExtSelfPing has no affect.

         The default value for vRtrMplsLspExtSelfPing is 'inherit'."
    DEFVAL      { inherit }
    ::= { vRtrMplsLspExtEntry 19 }

vRtrMplsLspPathProfTblLstChg     OBJECT-TYPE
    SYNTAX      TimeStamp
    MAX-ACCESS  read-only
    STATUS      current
    DESCRIPTION
        "Timestamp of the last change to the vRtrMplsLspPathProfTblLstChg
         either from adding a row or removing a row."
    ::= { tmnxMplsObjs 53 }

vRtrMplsLspPathProfTable         OBJECT-TYPE
    SYNTAX      SEQUENCE OF VRtrMplsLspPathProfEntry
    MAX-ACCESS  not-accessible
    STATUS      current
    DESCRIPTION
        "The vRtrMplsLspPathProfTable has an entry for each Labeled Switch Path
         (LSP) configured for a virtual router in the system."
    ::= { tmnxMplsObjs 54 }

vRtrMplsLspPathProfEntry         OBJECT-TYPE
    SYNTAX      VRtrMplsLspPathProfEntry
    MAX-ACCESS  not-accessible
    STATUS      current
    DESCRIPTION
        "Each row entry represents a Labeled Switch Path (LSP) configured
         for a virtual router in the system.  Entries can be created and
         deleted via SNMP SET operations.  Setting RowStatus to 'active'
         requires vRtrMplsLspPathProfId to have been assigned a valid value."
    INDEX       {
        vRtrID,
        vRtrMplsLspIndex,
        vRtrMplsLspPathProfId
    }
    ::= { vRtrMplsLspPathProfTable 1 }

VRtrMplsLspPathProfEntry         ::= SEQUENCE
{
    vRtrMplsLspPathProfId            Unsigned32,
    vRtrMplsLspPathProfRowStatus     RowStatus,
    vRtrMplsLspPathProfLastChange    TimeStamp,
    vRtrMplsLspPathProfGroupId       Unsigned32
}

vRtrMplsLspPathProfId            OBJECT-TYPE
    SYNTAX      Unsigned32 (0..4294967295)
    MAX-ACCESS  not-accessible
    STATUS      current
    DESCRIPTION
        "The value of vRtrMplsLspPathProfId specifies the profile id of for the
         specified LSP."
    DEFVAL      { 0 }
    ::= { vRtrMplsLspPathProfEntry 1 }

vRtrMplsLspPathProfRowStatus     OBJECT-TYPE
    SYNTAX      RowStatus
    MAX-ACCESS  read-create
    STATUS      current
    DESCRIPTION
        "The row status used for creation, deletion, or control
         of vRtrMplsLspPathProfTable entries.  Before the row can be
         placed into the 'active' state vRtrMplsLspName must
         have been assigned a valid value."
    ::= { vRtrMplsLspPathProfEntry 2 }

vRtrMplsLspPathProfLastChange    OBJECT-TYPE
    SYNTAX      TimeStamp
    MAX-ACCESS  read-only
    STATUS      current
    DESCRIPTION
        "The sysUpTime when this row was last modified."
    ::= { vRtrMplsLspPathProfEntry 3 }

vRtrMplsLspPathProfGroupId       OBJECT-TYPE
    SYNTAX      Unsigned32 (0 | 1..4294967295)
    MAX-ACCESS  read-create
    STATUS      current
    DESCRIPTION
        "The value of vRtrMplsLspPathProfGroupId specifies the group id used by
         the path profile for the specified LSP."
    DEFVAL      { 0 }
    ::= { vRtrMplsLspPathProfEntry 4 }

vRtrMplsClassFwdPlcyTblLstChg    OBJECT-TYPE
    SYNTAX      TimeStamp
    MAX-ACCESS  read-only
    STATUS      current
    DESCRIPTION
        "The value of vRtrMplsClassFwdPlcyTblLstChg indicates the sysUpTime at
         the time of the last modification of an entry in the
         vRtrMplsClassFwdPlcyTable."
    ::= { tmnxMplsObjs 55 }

vRtrMplsClassFwdPlcyTable        OBJECT-TYPE
    SYNTAX      SEQUENCE OF VRtrMplsClassFwdPlcyEntry
    MAX-ACCESS  not-accessible
    STATUS      current
    DESCRIPTION
        "The vRtrMplsClassFwdPlcyTable has an entry for each Forwarding Class
         Policy configured for a virtual router in the system."
    ::= { tmnxMplsObjs 56 }

vRtrMplsClassFwdPlcyEntry        OBJECT-TYPE
    SYNTAX      VRtrMplsClassFwdPlcyEntry
    MAX-ACCESS  not-accessible
    STATUS      current
    DESCRIPTION
        "Each row entry represents a configuration of a Forwarding Class Policy
         in the MPLS protocol for a virtual router in the system.

         Entries can be created and deleted via SNMP SET operations."
    INDEX       {
        vRtrID,
        vRtrMplsClassFwdPlcyName
    }
    ::= { vRtrMplsClassFwdPlcyTable 1 }

VRtrMplsClassFwdPlcyEntry        ::= SEQUENCE
{
    vRtrMplsClassFwdPlcyName         TNamedItem,
    vRtrMplsClassFwdPlcyRowStatus    RowStatus,
    vRtrMplsClassFwdPlcyLastChanged  TimeStamp,
    vRtrMplsClassFwdPlcyDefSetId     Unsigned32,
    vRtrMplsClassFwdPlcyRefCount     Gauge32
}

vRtrMplsClassFwdPlcyName         OBJECT-TYPE
    SYNTAX      TNamedItem
    MAX-ACCESS  not-accessible
    STATUS      current
    DESCRIPTION
        "The value of vRtrMplsClassFwdPlcyName specifies the name for the class
         forwarding policy."
    ::= { vRtrMplsClassFwdPlcyEntry 1 }

vRtrMplsClassFwdPlcyRowStatus    OBJECT-TYPE
    SYNTAX      RowStatus
    MAX-ACCESS  read-create
    STATUS      current
    DESCRIPTION
        "The value of vRtrMplsClassFwdPlcyRowStatus controls the creation and
         deletion of rows in the table."
    ::= { vRtrMplsClassFwdPlcyEntry 2 }

vRtrMplsClassFwdPlcyLastChanged  OBJECT-TYPE
    SYNTAX      TimeStamp
    MAX-ACCESS  read-only
    STATUS      current
    DESCRIPTION
        "The value of vRtrMplsClassFwdPlcyLastChanged indicates the sysUpTime
         when this row was last modified."
    ::= { vRtrMplsClassFwdPlcyEntry 3 }

vRtrMplsClassFwdPlcyDefSetId     OBJECT-TYPE
    SYNTAX      Unsigned32 (1..6)
    MAX-ACCESS  read-create
    STATUS      current
    DESCRIPTION
        "The value of vRtrMplsClassFwdPlcyDefSetId specifies default forwarding
         set ID when no forwarding class is specified for Lsp or Lsp Template
         instance. If system profile is profile-b then valid range is 1..6 else
         1..4"
    DEFVAL      { 1 }
    ::= { vRtrMplsClassFwdPlcyEntry 4 }

vRtrMplsClassFwdPlcyRefCount     OBJECT-TYPE
    SYNTAX      Gauge32
    MAX-ACCESS  read-only
    STATUS      current
    DESCRIPTION
        "The value of vRtrMplsClassFwdPlcyRefCount indicates the number of LSPs
         or LSP templates that are referencing this class forwarding policy."
    ::= { vRtrMplsClassFwdPlcyEntry 5 }

vRtrMplsClassFwdPlcyFCTblLstChg  OBJECT-TYPE
    SYNTAX      TimeStamp
    MAX-ACCESS  read-only
    STATUS      current
    DESCRIPTION
        "The value of vRtrMplsClassFwdPlcyFCTblLstChg indicates the sysUpTime
         at the time of the last modification of an entry in the
         vRtrMplsClassFwdPlcyFCTable."
    ::= { tmnxMplsObjs 57 }

vRtrMplsClassFwdPlcyFCTable      OBJECT-TYPE
    SYNTAX      SEQUENCE OF VRtrMplsClassFwdPlcyFCEntry
    MAX-ACCESS  not-accessible
    STATUS      current
    DESCRIPTION
        "The vRtrMplsClassFwdPlcyFCTable has an entry for each type of
         Forwarding Class and its corresponding forwarding set id."
    ::= { tmnxMplsObjs 58 }

vRtrMplsClassFwdPlcyFCEntry      OBJECT-TYPE
    SYNTAX      VRtrMplsClassFwdPlcyFCEntry
    MAX-ACCESS  not-accessible
    STATUS      current
    DESCRIPTION
        "Each row entry represents a configuration of a Forwarding Class and
         forwarding set id in the MPLS protocol for a virtual router in the
         system.

         Entries can be created and deleted via SNMP SET operations."
    INDEX       {
        vRtrID,
        vRtrMplsClassFwdPlcyName,
        vRtrMplsClassFwdPlcyFC
    }
    ::= { vRtrMplsClassFwdPlcyFCTable 1 }

VRtrMplsClassFwdPlcyFCEntry      ::= SEQUENCE
{
    vRtrMplsClassFwdPlcyFC           TFCType,
    vRtrMplsClassFwdPlcyFCSetId      Unsigned32
}

vRtrMplsClassFwdPlcyFC           OBJECT-TYPE
    SYNTAX      TFCType
    MAX-ACCESS  not-accessible
    STATUS      current
    DESCRIPTION
        "The value of vRtrMplsClassFwdPlcyFC specifies the name of the
         forwarding class assigned to the policy name specified by
         vRtrMplsClassFwdPlcyName."
    ::= { vRtrMplsClassFwdPlcyFCEntry 1 }

vRtrMplsClassFwdPlcyFCSetId      OBJECT-TYPE
    SYNTAX      Unsigned32 (1..6)
    MAX-ACCESS  read-create
    STATUS      current
    DESCRIPTION
        "The value of vRtrMplsClassFwdPlcyFCSetId specifies the forwarding set
         ID to which forwarding class specified by vRtrMplsClassFwdPlcyFC is
         mapped to. If system profile is profile-b then valid range is 1..6
         else 1..4"
    DEFVAL      { 1 }
    ::= { vRtrMplsClassFwdPlcyFCEntry 2 }

vRtrMplsReservedLblBlkTblLastChg OBJECT-TYPE
    SYNTAX      TimeStamp
    MAX-ACCESS  read-only
    STATUS      current
    DESCRIPTION
        "The value of vRtrMplsReservedLblBlkTblLastChg indicates the sysUpTime
         at the time of the last modification of an entry in the
         vRtrMplsReservedLblBlkTable."
    ::= { tmnxMplsObjs 59 }

vRtrMplsReservedLblBlkTable      OBJECT-TYPE
    SYNTAX      SEQUENCE OF VRtrMplsReservedLblBlkEntry
    MAX-ACCESS  not-accessible
    STATUS      current
    DESCRIPTION
        "The vRtrMplsReservedLblBlkTable has an entry for each reserved label
         block."
    ::= { tmnxMplsObjs 60 }

vRtrMplsReservedLblBlkEntry      OBJECT-TYPE
    SYNTAX      VRtrMplsReservedLblBlkEntry
    MAX-ACCESS  not-accessible
    STATUS      current
    DESCRIPTION
        "Each row entry represents a configuration of a reserved label block in
         the MPLS protocol for a virtual router in the system.

         Entries can be created and deleted via SNMP SET operations."
    INDEX       { vRtrMplsReservedLblBlkName }
    ::= { vRtrMplsReservedLblBlkTable 1 }

VRtrMplsReservedLblBlkEntry      ::= SEQUENCE
{
    vRtrMplsReservedLblBlkName       TLNamedItem,
    vRtrMplsReservedLblBlkRowStatus  RowStatus,
    vRtrMplsReservedLblBlkLastChg    TimeStamp,
    vRtrMplsReservedLblBlkStartLbl   TmnxMplsLabelOrZero,
    vRtrMplsReservedLblBlkEndLbl     TmnxMplsLabelOrZero
}

vRtrMplsReservedLblBlkName       OBJECT-TYPE
    SYNTAX      TLNamedItem
    MAX-ACCESS  not-accessible
    STATUS      current
    DESCRIPTION
        "The value of vRtrMplsReservedLblBlkName specifies the name identifying
         the reserved label block."
    ::= { vRtrMplsReservedLblBlkEntry 1 }

vRtrMplsReservedLblBlkRowStatus  OBJECT-TYPE
    SYNTAX      RowStatus
    MAX-ACCESS  read-create
    STATUS      current
    DESCRIPTION
        "The row status used for creation, deletion, or control of
         vRtrMplsReservedLblBlkTable entries."
    ::= { vRtrMplsReservedLblBlkEntry 2 }

vRtrMplsReservedLblBlkLastChg    OBJECT-TYPE
    SYNTAX      TimeStamp
    MAX-ACCESS  read-only
    STATUS      current
    DESCRIPTION
        "The value of vRtrMplsReservedLblBlkLastChg indicates the sysUpTime
         when this row was last modified."
    ::= { vRtrMplsReservedLblBlkEntry 3 }

vRtrMplsReservedLblBlkStartLbl   OBJECT-TYPE
    SYNTAX      TmnxMplsLabelOrZero
    MAX-ACCESS  read-create
    STATUS      current
    DESCRIPTION
        "The value of vRtrMplsReservedLblBlkStartLbl specifies the start value
         of the reserved label available on the system.

         vRtrMplsReservedLblBlkStartLbl must be set along with
         vRtrMplsReservedLblBlkEndLbl."
    ::= { vRtrMplsReservedLblBlkEntry 4 }

vRtrMplsReservedLblBlkEndLbl     OBJECT-TYPE
    SYNTAX      TmnxMplsLabelOrZero
    MAX-ACCESS  read-create
    STATUS      current
    DESCRIPTION
        "The value of vRtrMplsReservedLblBlkEndLbl specifies the end value of
         the reserved label available on the system.

         vRtrMplsReservedLblBlkEndLbl must be set along with
         vRtrMplsReservedLblBlkStartLbl."
    ::= { vRtrMplsReservedLblBlkEntry 5 }

vRtrMplsLspAdminTagTblLastChg    OBJECT-TYPE
    SYNTAX      TimeStamp
    MAX-ACCESS  read-only
    STATUS      current
    DESCRIPTION
        "The value of vRtrMplsLspAdminTagTblLastChg indicates the sysUpTime at
         the time of the last modification of an entry in the
         vRtrMplsLspAdminTagTable."
    ::= { tmnxMplsObjs 61 }

vRtrMplsLspAdminTagTable         OBJECT-TYPE
    SYNTAX      SEQUENCE OF VRtrMplsLspAdminTagEntry
    MAX-ACCESS  not-accessible
    STATUS      current
    DESCRIPTION
        "The vRtrMplsLspAdminTagTable has an entry for each admin-tag
         configured in the system."
    ::= { tmnxMplsObjs 62 }

vRtrMplsLspAdminTagEntry         OBJECT-TYPE
    SYNTAX      VRtrMplsLspAdminTagEntry
    MAX-ACCESS  not-accessible
    STATUS      current
    DESCRIPTION
        "Each row entry represents a configuration of an admin-tag name in LSP
         for a virtual router in the system.

         Entries can be created and deleted via SNMP SET operations."
    INDEX       {
        vRtrID,
        vRtrMplsLspIndex,
        vRtrMplsLspAdminTagName
    }
    ::= { vRtrMplsLspAdminTagTable 1 }

VRtrMplsLspAdminTagEntry         ::= SEQUENCE
{
    vRtrMplsLspAdminTagName          TNamedItem,
    vRtrMplsLspAdminTagRowStatus     RowStatus,
    vRtrMplsLspAdminTagLastChanged   TimeStamp
}

vRtrMplsLspAdminTagName          OBJECT-TYPE
    SYNTAX      TNamedItem
    MAX-ACCESS  not-accessible
    STATUS      current
    DESCRIPTION
        "The value of vRtrMplsLspAdminTagName specifies the name of the admin
         tag."
    ::= { vRtrMplsLspAdminTagEntry 1 }

vRtrMplsLspAdminTagRowStatus     OBJECT-TYPE
    SYNTAX      RowStatus
    MAX-ACCESS  read-create
    STATUS      current
    DESCRIPTION
        "The row status used for creation, deletion, or control of
         vRtrMplsLspAdminTagTable entries."
    ::= { vRtrMplsLspAdminTagEntry 2 }

vRtrMplsLspAdminTagLastChanged   OBJECT-TYPE
    SYNTAX      TimeStamp
    MAX-ACCESS  read-only
    STATUS      current
    DESCRIPTION
        "The value of vRtrMplsLspAdminTagLastChanged indicates the sysUpTime
         when this row was last modified."
    ::= { vRtrMplsLspAdminTagEntry 3 }

vRtrMplsLspTempAdminTagTblLstChg OBJECT-TYPE
    SYNTAX      TimeStamp
    MAX-ACCESS  read-only
    STATUS      current
    DESCRIPTION
        "The value of vRtrMplsLspTempAdminTagTblLstChg indicates the sysUpTime
         at the time of the last modification of an entry in the
         vRtrMplsLspTempAdminTagTable."
    ::= { tmnxMplsObjs 63 }

vRtrMplsLspTempAdminTagTable     OBJECT-TYPE
    SYNTAX      SEQUENCE OF VRtrMplsLspTempAdminTagEntry
    MAX-ACCESS  not-accessible
    STATUS      current
    DESCRIPTION
        "The vRtrMplsLspTempAdminTagTable has an entry for each admin-tag
         configured in the system."
    ::= { tmnxMplsObjs 64 }

vRtrMplsLspTempAdminTagEntry     OBJECT-TYPE
    SYNTAX      VRtrMplsLspTempAdminTagEntry
    MAX-ACCESS  not-accessible
    STATUS      current
    DESCRIPTION
        "Each row entry represents a configuration of an admin-tag name in LSP
         for a virtual router in the system.

         Entries can be created and deleted via SNMP SET operations."
    INDEX       {
        vRtrID,
        vRtrMplsLspTemplateName,
        vRtrMplsLspTempAdminTagName
    }
    ::= { vRtrMplsLspTempAdminTagTable 1 }

VRtrMplsLspTempAdminTagEntry     ::= SEQUENCE
{
    vRtrMplsLspTempAdminTagName      TNamedItem,
    vRtrMplsLspTempAdminTagRowStatus RowStatus,
    vRtrMplsLspTempAdminTagLastChg   TimeStamp
}

vRtrMplsLspTempAdminTagName      OBJECT-TYPE
    SYNTAX      TNamedItem
    MAX-ACCESS  not-accessible
    STATUS      current
    DESCRIPTION
        "The value of vRtrMplsLspTempAdminTagName specifies the name of the
         admin tag."
    ::= { vRtrMplsLspTempAdminTagEntry 1 }

vRtrMplsLspTempAdminTagRowStatus OBJECT-TYPE
    SYNTAX      RowStatus
    MAX-ACCESS  read-create
    STATUS      current
    DESCRIPTION
        "The row status used for creation, deletion, or control of
         vRtrMplsLspTempAdminTagTable entries."
    ::= { vRtrMplsLspTempAdminTagEntry 2 }

vRtrMplsLspTempAdminTagLastChg   OBJECT-TYPE
    SYNTAX      TimeStamp
    MAX-ACCESS  read-only
    STATUS      current
    DESCRIPTION
        "The value of vRtrMplsLspTempAdminTagLastChg indicates the sysUpTime
         when this row was last modified."
    ::= { vRtrMplsLspTempAdminTagEntry 3 }

vRtrMplsFwdPlcyTblLastChg        OBJECT-TYPE
    SYNTAX      TimeStamp
    MAX-ACCESS  read-only
    STATUS      current
    DESCRIPTION
        "The value of vRtrMplsFwdPlcyTblLastChg indicates the sysUpTime at the
         time of the last modification of an entry in the vRtrMplsFwdPlcyTable."
    ::= { tmnxMplsObjs 65 }

vRtrMplsFwdPlcyTable             OBJECT-TYPE
    SYNTAX      SEQUENCE OF VRtrMplsFwdPlcyEntry
    MAX-ACCESS  not-accessible
    STATUS      current
    DESCRIPTION
        "The vRtrMplsFwdPlcyTable has an entry for each Forwarding Policy
         configured for a virtual router in the system."
    ::= { tmnxMplsObjs 66 }

vRtrMplsFwdPlcyEntry             OBJECT-TYPE
    SYNTAX      VRtrMplsFwdPlcyEntry
    MAX-ACCESS  not-accessible
    STATUS      current
    DESCRIPTION
        "Each row entry represents a configuration of a Forwarding Policy in
         the MPLS protocol for a virtual router in the system.

         Entries can be created and deleted via SNMP SET operations."
    INDEX       {
        vRtrID,
        vRtrMplsFwdPlcyName
    }
    ::= { vRtrMplsFwdPlcyTable 1 }

VRtrMplsFwdPlcyEntry             ::= SEQUENCE
{
    vRtrMplsFwdPlcyName              TLNamedItem,
    vRtrMplsFwdPlcyRowStatus         RowStatus,
    vRtrMplsFwdPlcyLastChanged       TimeStamp,
    vRtrMplsFwdPlcyAdminState        TmnxAdminState,
    vRtrMplsFwdPlcyOperState         TmnxOperState,
    vRtrMplsFwdPlcyBindingLabel      TmnxMplsLabelOrZero,
    vRtrMplsFwdPlcyEndpointAddrType  InetAddressType,
    vRtrMplsFwdPlcyEndpointAddr      InetAddress,
    vRtrMplsFwdPlcyRevertTimer       Unsigned32,
    vRtrMplsFwdPlcyPreference        Unsigned32,
    vRtrMplsFwdPlcyMetric            Unsigned32,
    vRtrMplsFwdPlcyTtmPreference     Unsigned32
}

vRtrMplsFwdPlcyName              OBJECT-TYPE
    SYNTAX      TLNamedItem
    MAX-ACCESS  not-accessible
    STATUS      current
    DESCRIPTION
        "The value of the vRtrMplsFwdPlcyName specifies the name for the
         forwarding policy."
    ::= { vRtrMplsFwdPlcyEntry 1 }

vRtrMplsFwdPlcyRowStatus         OBJECT-TYPE
    SYNTAX      RowStatus
    MAX-ACCESS  read-create
    STATUS      current
    DESCRIPTION
        "The value of vRtrMplsFwdPlcyRowStatus controls the creation and
         deletion of rows in the table."
    ::= { vRtrMplsFwdPlcyEntry 2 }

vRtrMplsFwdPlcyLastChanged       OBJECT-TYPE
    SYNTAX      TimeStamp
    MAX-ACCESS  read-only
    STATUS      current
    DESCRIPTION
        "The value of vRtrMplsFwdPlcyLastChanged indicates the sysUpTime when
         this row was last modified."
    ::= { vRtrMplsFwdPlcyEntry 3 }

vRtrMplsFwdPlcyAdminState        OBJECT-TYPE
    SYNTAX      TmnxAdminState
    MAX-ACCESS  read-create
    STATUS      current
    DESCRIPTION
        "The value of vRtrMplsFwdPlcyAdminState specifies the current
         administrative state of the forwarding policy."
    DEFVAL      { outOfService }
    ::= { vRtrMplsFwdPlcyEntry 4 }

vRtrMplsFwdPlcyOperState         OBJECT-TYPE
    SYNTAX      TmnxOperState
    MAX-ACCESS  read-only
    STATUS      current
    DESCRIPTION
        "The value of vRtrMplsFwdPlcyOperState indicates the current
         operational state of the forwarding policy."
    ::= { vRtrMplsFwdPlcyEntry 5 }

vRtrMplsFwdPlcyBindingLabel      OBJECT-TYPE
    SYNTAX      TmnxMplsLabelOrZero
    MAX-ACCESS  read-create
    STATUS      current
    DESCRIPTION
        "The value of vRtrMplsFwdPlcyBindingLabel specifies the binding label
         for the forwarding policy."
    DEFVAL      { 0 }
    ::= { vRtrMplsFwdPlcyEntry 6 }

vRtrMplsFwdPlcyEndpointAddrType  OBJECT-TYPE
    SYNTAX      InetAddressType
    MAX-ACCESS  read-create
    STATUS      current
    DESCRIPTION
        "The value of vRtrMplsFwdPlcyEndpointAddrType specifies the type of
         vRtrMplsFwdPlcyEndpointAddr."
    DEFVAL      { unknown }
    ::= { vRtrMplsFwdPlcyEntry 7 }

vRtrMplsFwdPlcyEndpointAddr      OBJECT-TYPE
    SYNTAX      InetAddress (SIZE (0|4|16))
    MAX-ACCESS  read-create
    STATUS      current
    DESCRIPTION
        "The value of vRtrMplsFwdPlcyEndpointAddr specifies the endpoint
         address for the forwarding policy."
    DEFVAL      { ''H }
    ::= { vRtrMplsFwdPlcyEntry 8 }

vRtrMplsFwdPlcyRevertTimer       OBJECT-TYPE
    SYNTAX      Unsigned32 (0..600)
    UNITS       "seconds"
    MAX-ACCESS  read-create
    STATUS      current
    DESCRIPTION
        "The value of vRtrMplsFwdPlcyRevertTimer specifies the revert timer for
         the forwarding policy."
    DEFVAL      { 0 }
    ::= { vRtrMplsFwdPlcyEntry 9 }

vRtrMplsFwdPlcyPreference        OBJECT-TYPE
    SYNTAX      Unsigned32 (1..255)
    MAX-ACCESS  read-create
    STATUS      current
    DESCRIPTION
        "The value of vRtrMplsFwdPlcyPreference specifies the forwarding policy
         preference number."
    DEFVAL      { 255 }
    ::= { vRtrMplsFwdPlcyEntry 10 }

vRtrMplsFwdPlcyMetric            OBJECT-TYPE
    SYNTAX      Unsigned32 (0..16777215)
    MAX-ACCESS  read-create
    STATUS      current
    DESCRIPTION
        "This value of vRtrMplsFwdPlcyMetric specifies the metric of this
         tunnel in the tunnel table."
    DEFVAL      { 0 }
    ::= { vRtrMplsFwdPlcyEntry 11 }

vRtrMplsFwdPlcyTtmPreference     OBJECT-TYPE
    SYNTAX      Unsigned32 (1..255)
    MAX-ACCESS  read-create
    STATUS      current
    DESCRIPTION
        "This value of vRtrMplsFwdPlcyTtmPreference specifies the preference of
         this tunnel in the tunnel table."
    DEFVAL      { 255 }
    ::= { vRtrMplsFwdPlcyEntry 12 }

vRtrMplsFwdPlcyNHGrpTblLastChg   OBJECT-TYPE
    SYNTAX      TimeStamp
    MAX-ACCESS  read-only
    STATUS      current
    DESCRIPTION
        "The value of vRtrMplsFwdPlcyNHGrpTblLastChg indicates the sysUpTime at
         the time of the last modification of an entry in the
         vRtrMplsFwdPlcyNHGrpTable."
    ::= { tmnxMplsObjs 67 }

vRtrMplsFwdPlcyNHGrpTable        OBJECT-TYPE
    SYNTAX      SEQUENCE OF VRtrMplsFwdPlcyNHGrpEntry
    MAX-ACCESS  not-accessible
    STATUS      current
    DESCRIPTION
        "The vRtrMplsFwdPlcyNHGrpTable has an entry for each Forwarding Policy
         next-hop group configured for a virtual router in the system."
    ::= { tmnxMplsObjs 68 }

vRtrMplsFwdPlcyNHGrpEntry        OBJECT-TYPE
    SYNTAX      VRtrMplsFwdPlcyNHGrpEntry
    MAX-ACCESS  not-accessible
    STATUS      current
    DESCRIPTION
        "Each row entry represents a configuration of a Forwarding Policy
         next-hop group in the MPLS protocol for a virtual router in the
         system.

         Entries can be created and deleted via SNMP SET operations."
    INDEX       {
        vRtrID,
        vRtrMplsFwdPlcyName,
        vRtrMplsFwdPlcyNHGrpIdx
    }
    ::= { vRtrMplsFwdPlcyNHGrpTable 1 }

VRtrMplsFwdPlcyNHGrpEntry        ::= SEQUENCE
{
    vRtrMplsFwdPlcyNHGrpIdx          Unsigned32,
    vRtrMplsFwdPlcyNHGrpRowStatus    RowStatus,
    vRtrMplsFwdPlcyNHGrpLastChanged  TimeStamp,
    vRtrMplsFwdPlcyNHGrpAdminState   TmnxAdminState,
    vRtrMplsFwdPlcyNHGrpOperState    TmnxOperState,
    vRtrMplsFwdPlcyNHGrpResType      INTEGER,
    vRtrMplsFwdPlcyNHGrpLoadBalWt    Unsigned32
}

vRtrMplsFwdPlcyNHGrpIdx          OBJECT-TYPE
    SYNTAX      Unsigned32 (1..32)
    MAX-ACCESS  not-accessible
    STATUS      current
    DESCRIPTION
        "The value of the vRtrMplsFwdPlcyNHGrpIdx specifies the index for the
         next-hop group."
    ::= { vRtrMplsFwdPlcyNHGrpEntry 1 }

vRtrMplsFwdPlcyNHGrpRowStatus    OBJECT-TYPE
    SYNTAX      RowStatus
    MAX-ACCESS  read-create
    STATUS      current
    DESCRIPTION
        "The value of vRtrMplsFwdPlcyNHGrpRowStatus controls the creation and
         deletion of rows in the table."
    ::= { vRtrMplsFwdPlcyNHGrpEntry 2 }

vRtrMplsFwdPlcyNHGrpLastChanged  OBJECT-TYPE
    SYNTAX      TimeStamp
    MAX-ACCESS  read-only
    STATUS      current
    DESCRIPTION
        "The value of vRtrMplsFwdPlcyNHGrpLastChanged indicates the sysUpTime
         when this row was last modified."
    ::= { vRtrMplsFwdPlcyNHGrpEntry 3 }

vRtrMplsFwdPlcyNHGrpAdminState   OBJECT-TYPE
    SYNTAX      TmnxAdminState
    MAX-ACCESS  read-create
    STATUS      current
    DESCRIPTION
        "The value of vRtrMplsFwdPlcyNHGrpAdminState specifies the current
         administrative state of the next-hop group."
    DEFVAL      { outOfService }
    ::= { vRtrMplsFwdPlcyNHGrpEntry 4 }

vRtrMplsFwdPlcyNHGrpOperState    OBJECT-TYPE
    SYNTAX      TmnxOperState
    MAX-ACCESS  read-only
    STATUS      current
    DESCRIPTION
        "The value of vRtrMplsFwdPlcyNHGrpOperState indicates the current
         operational state of the next-hop group."
    ::= { vRtrMplsFwdPlcyNHGrpEntry 5 }

vRtrMplsFwdPlcyNHGrpResType      OBJECT-TYPE
    SYNTAX      INTEGER {
        direct   (1),
        indirect (2)
    }
    MAX-ACCESS  read-create
    STATUS      current
    DESCRIPTION
        "The value of vRtrMplsFwdPlcyNHGrpResType specifies the resolution
         type of the next-hop group.

         When the value of vRtrMplsFwdPlcyNHGrpResType is set to 'direct', the
         next-hops in this group must resolve to direct routes for for them to
         be operational.

         When the value of vRtrMplsFwdPlcyNHGrpResType is set to 'indirect',
         the next-hops in this group must resolve to indirect routes for for
         them to be operational."
    ::= { vRtrMplsFwdPlcyNHGrpEntry 6 }

vRtrMplsFwdPlcyNHGrpLoadBalWt    OBJECT-TYPE
    SYNTAX      Unsigned32 (0 | 1..4294967295)
    MAX-ACCESS  read-create
    STATUS      current
    DESCRIPTION
        "The value of vRtrMplsFwdPlcyNHGrpLoadBalWt specifies the load
         balancing weight for this next-hop group."
    DEFVAL      { 0 }
    ::= { vRtrMplsFwdPlcyNHGrpEntry 7 }

vRtrMplsFwdPlcyNhgNHTblLastChg   OBJECT-TYPE
    SYNTAX      TimeStamp
    MAX-ACCESS  read-only
    STATUS      current
    DESCRIPTION
        "The value of vRtrMplsFwdPlcyNhgNHTblLastChg indicates the sysUpTime at
         the time of the last modification of an entry in the
         vRtrMplsFwdPlcyNhgNHTable."
    ::= { tmnxMplsObjs 69 }

vRtrMplsFwdPlcyNhgNHTable        OBJECT-TYPE
    SYNTAX      SEQUENCE OF VRtrMplsFwdPlcyNhgNHEntry
    MAX-ACCESS  not-accessible
    STATUS      current
    DESCRIPTION
        "The vRtrMplsFwdPlcyNhgNHTable has an entry for each next-hop
         configured in a Forwarding Policy next-hop group."
    ::= { tmnxMplsObjs 70 }

vRtrMplsFwdPlcyNhgNHEntry        OBJECT-TYPE
    SYNTAX      VRtrMplsFwdPlcyNhgNHEntry
    MAX-ACCESS  not-accessible
    STATUS      current
    DESCRIPTION
        "Each row entry represents a configuration of a next-hop in a
         Forwarding Policy next-hop group.

         Entries can be created and deleted via SNMP SET operations."
    INDEX       {
        vRtrID,
        vRtrMplsFwdPlcyName,
        vRtrMplsFwdPlcyNHGrpIdx,
        vRtrMplsFwdPlcyNhgNHType
    }
    ::= { vRtrMplsFwdPlcyNhgNHTable 1 }

VRtrMplsFwdPlcyNhgNHEntry        ::= SEQUENCE
{
    vRtrMplsFwdPlcyNhgNHType         INTEGER,
    vRtrMplsFwdPlcyNhgNHRowStatus    RowStatus,
    vRtrMplsFwdPlcyNhgNHLastChanged  TimeStamp,
    vRtrMplsFwdPlcyNhgNHOperState    TmnxOperState,
    vRtrMplsFwdPlcyNhgNHAddrType     InetAddressType,
    vRtrMplsFwdPlcyNhgNHAddr         InetAddress
}

vRtrMplsFwdPlcyNhgNHType         OBJECT-TYPE
    SYNTAX      INTEGER {
        primary (1),
        backup  (2)
    }
    MAX-ACCESS  not-accessible
    STATUS      current
    DESCRIPTION
        "The value of vRtrMplsFwdPlcyNhgNHType specifies the type of next-hop.

         When the value of vRtrMplsFwdPlcyNhgNHType is set to 'primary', this
         next-hop will be the primary next-hop in the next-hop group.

         When the value of vRtrMplsFwdPlcyNhgNHType is set to 'backup', this
         next-hop will be the backup next-hop in the next-hop group."
    ::= { vRtrMplsFwdPlcyNhgNHEntry 1 }

vRtrMplsFwdPlcyNhgNHRowStatus    OBJECT-TYPE
    SYNTAX      RowStatus
    MAX-ACCESS  read-create
    STATUS      current
    DESCRIPTION
        "The value of vRtrMplsFwdPlcyNhgNHRowStatus controls the creation and
         deletion of rows in the table."
    ::= { vRtrMplsFwdPlcyNhgNHEntry 2 }

vRtrMplsFwdPlcyNhgNHLastChanged  OBJECT-TYPE
    SYNTAX      TimeStamp
    MAX-ACCESS  read-only
    STATUS      current
    DESCRIPTION
        "The value of vRtrMplsFwdPlcyNhgNHLastChanged indicates the sysUpTime
         when this row was last modified."
    ::= { vRtrMplsFwdPlcyNhgNHEntry 3 }

vRtrMplsFwdPlcyNhgNHOperState    OBJECT-TYPE
    SYNTAX      TmnxOperState
    MAX-ACCESS  read-only
    STATUS      current
    DESCRIPTION
        "The value of vRtrMplsFwdPlcyNhgNHOperState indicates the current
         operational state of the next-hop."
    ::= { vRtrMplsFwdPlcyNhgNHEntry 4 }

vRtrMplsFwdPlcyNhgNHAddrType     OBJECT-TYPE
    SYNTAX      InetAddressType
    MAX-ACCESS  read-create
    STATUS      current
    DESCRIPTION
        "The value of vRtrMplsFwdPlcyNhgNHAddrType specifies the type of
         vRtrMplsFwdPlcyNhgNHAddr."
    DEFVAL      { unknown }
    ::= { vRtrMplsFwdPlcyNhgNHEntry 5 }

vRtrMplsFwdPlcyNhgNHAddr         OBJECT-TYPE
    SYNTAX      InetAddress (SIZE (0|4|16))
    MAX-ACCESS  read-create
    STATUS      current
    DESCRIPTION
        "The value of vRtrMplsFwdPlcyNhgNHAddr specifies the next-hop address."
    DEFVAL      { ''H }
    ::= { vRtrMplsFwdPlcyNhgNHEntry 6 }

vRtrMplsFwdPlcyGenTblLastChg     OBJECT-TYPE
    SYNTAX      TimeStamp
    MAX-ACCESS  read-only
    STATUS      current
    DESCRIPTION
        "The value of vRtrMplsFwdPlcyGenTblLastChg indicates the sysUpTime at
         the time of the last modification of an entry in the
         vRtrMplsFwdPlcyGenTable."
    ::= { tmnxMplsObjs 71 }

vRtrMplsFwdPlcyGenTable          OBJECT-TYPE
    SYNTAX      SEQUENCE OF VRtrMplsFwdPlcyGenEntry
    MAX-ACCESS  not-accessible
    STATUS      current
    DESCRIPTION
        "The vRtrMplsFwdPlcyGenTable contains objects for general control and
         management of MPLS Forwarding Policies within a virtual router."
    ::= { tmnxMplsObjs 72 }

vRtrMplsFwdPlcyGenEntry          OBJECT-TYPE
    SYNTAX      VRtrMplsFwdPlcyGenEntry
    MAX-ACCESS  not-accessible
    STATUS      current
    DESCRIPTION
        "Each row entry contains objects for general control and management of
         MPLS Forwarding Policies within a virtual router.

         Entries can be created and deleted via SNMP SET operations."
    INDEX       { vRtrID }
    ::= { vRtrMplsFwdPlcyGenTable 1 }

VRtrMplsFwdPlcyGenEntry          ::= SEQUENCE
{
    vRtrMplsFwdPlcyGenRowStatus      RowStatus,
    vRtrMplsFwdPlcyGenLastChanged    TimeStamp,
    vRtrMplsFwdPlcyGenAdminState     TmnxAdminState,
    vRtrMplsFwdPlcyGenOperState      TmnxOperState,
    vRtrMplsFwdPlcyGenOperDownReason INTEGER,
    vRtrMplsFwdPlcyGenReservedLblBlk TLNamedItemOrEmpty
}

vRtrMplsFwdPlcyGenRowStatus      OBJECT-TYPE
    SYNTAX      RowStatus
    MAX-ACCESS  read-create
    STATUS      current
    DESCRIPTION
        "The value of vRtrMplsFwdPlcyGenRowStatus controls the creation and
         deletion of rows in the table."
    ::= { vRtrMplsFwdPlcyGenEntry 1 }

vRtrMplsFwdPlcyGenLastChanged    OBJECT-TYPE
    SYNTAX      TimeStamp
    MAX-ACCESS  read-only
    STATUS      current
    DESCRIPTION
        "The value of vRtrMplsFwdPlcyGenLastChanged indicates the sysUpTime
         when this row was last modified."
    ::= { vRtrMplsFwdPlcyGenEntry 2 }

vRtrMplsFwdPlcyGenAdminState     OBJECT-TYPE
    SYNTAX      TmnxAdminState
    MAX-ACCESS  read-create
    STATUS      current
    DESCRIPTION
        "The value of vRtrMplsFwdPlcyGenAdminState specifies the current
         administrative state for Forwarding Policies configuration."
    DEFVAL      { outOfService }
    ::= { vRtrMplsFwdPlcyGenEntry 3 }

vRtrMplsFwdPlcyGenOperState      OBJECT-TYPE
    SYNTAX      TmnxOperState
    MAX-ACCESS  read-only
    STATUS      current
    DESCRIPTION
        "The value of vRtrMplsFwdPlcyGenOperState indicates the current
         operational state of Forwarding Policies."
    ::= { vRtrMplsFwdPlcyGenEntry 4 }

vRtrMplsFwdPlcyGenOperDownReason OBJECT-TYPE
    SYNTAX      INTEGER {
        notApplicable (0),
        adminDown     (1),
        mplsOperDown  (2)
    }
    MAX-ACCESS  read-only
    STATUS      current
    DESCRIPTION
        "The value of vRtrMplsFwdPlcyGenOperDownReason indicates the reason due
         to which Forwarding Policies is operationally down."
    ::= { vRtrMplsFwdPlcyGenEntry 5 }

vRtrMplsFwdPlcyGenReservedLblBlk OBJECT-TYPE
    SYNTAX      TLNamedItemOrEmpty
    MAX-ACCESS  read-create
    STATUS      current
    DESCRIPTION
        "The value of vRtrMplsFwdPlcyGenReservedLblBlk identifies the reserved
         label block used by Forwarding Policies."
    DEFVAL      { "" }
    ::= { vRtrMplsFwdPlcyGenEntry 6 }

vRtrMplsFwdPlcyStatsTblLastChg   OBJECT-TYPE
    SYNTAX      TimeStamp
    MAX-ACCESS  read-only
    STATUS      current
    DESCRIPTION
        "The value of vRtrMplsFwdPlcyStatsTblLastChg indicates the sysUpTime at
         the time of the last modification of an entry in the
         vRtrMplsFwdPlcyStatsTable."
    ::= { tmnxMplsObjs 73 }

vRtrMplsFwdPlcyStatsTable        OBJECT-TYPE
    SYNTAX      SEQUENCE OF VRtrMplsFwdPlcyStatsEntry
    MAX-ACCESS  not-accessible
    STATUS      current
    DESCRIPTION
        "The vRtrMplsFwdPlcyStatsTable contains objects for general control and
          management of Statistics for MPLS Forwarding Policies within a
         virtual router."
    ::= { tmnxMplsObjs 74 }

vRtrMplsFwdPlcyStatsEntry        OBJECT-TYPE
    SYNTAX      VRtrMplsFwdPlcyStatsEntry
    MAX-ACCESS  not-accessible
    STATUS      current
    DESCRIPTION
        "Each row entry contains objects for general control and management of
         Statistics for MPLS Forwarding Policies within a virtual router.

         Entries can be created and deleted via SNMP SET operations."
    INDEX       {
        vRtrID,
        vRtrMplsFwdPlcyName,
        vRtrMplsFwdPlcyStatsType
    }
    ::= { vRtrMplsFwdPlcyStatsTable 1 }

VRtrMplsFwdPlcyStatsEntry        ::= SEQUENCE
{
    vRtrMplsFwdPlcyStatsType         INTEGER,
    vRtrMplsFwdPlcyStatsRowStatus    RowStatus,
    vRtrMplsFwdPlcyStatsLastChanged  TimeStamp,
    vRtrMplsFwdPlcyStatsAdminState   TmnxAdminState
}

vRtrMplsFwdPlcyStatsType         OBJECT-TYPE
    SYNTAX      INTEGER {
        ingress (1),
        egress  (2)
    }
    MAX-ACCESS  not-accessible
    STATUS      current
    DESCRIPTION
        "The value of vRtrMplsFwdPlcyStatsType specifies whether the type of
         statistics is ingress or egress."
    ::= { vRtrMplsFwdPlcyStatsEntry 1 }

vRtrMplsFwdPlcyStatsRowStatus    OBJECT-TYPE
    SYNTAX      RowStatus
    MAX-ACCESS  read-create
    STATUS      current
    DESCRIPTION
        "The value of vRtrMplsFwdPlcyStatsRowStatus controls the creation and
         deletion of rows in the table."
    ::= { vRtrMplsFwdPlcyStatsEntry 2 }

vRtrMplsFwdPlcyStatsLastChanged  OBJECT-TYPE
    SYNTAX      TimeStamp
    MAX-ACCESS  read-only
    STATUS      current
    DESCRIPTION
        "The value of vRtrMplsFwdPlcyStatsLastChanged indicates the sysUpTime
         when this row was last modified."
    ::= { vRtrMplsFwdPlcyStatsEntry 3 }

vRtrMplsFwdPlcyStatsAdminState   OBJECT-TYPE
    SYNTAX      TmnxAdminState
    MAX-ACCESS  read-create
    STATUS      current
    DESCRIPTION
        "The value of vRtrMplsFwdPlcyStatsAdminState specifies the current
         administrative state for Forwarding Policy statistics configuration."
    DEFVAL      { outOfService }
    ::= { vRtrMplsFwdPlcyStatsEntry 4 }

vRtrMplsBindLblPathTable         OBJECT-TYPE
    SYNTAX      SEQUENCE OF VRtrMplsBindLblPathEntry
    MAX-ACCESS  not-accessible
    STATUS      current
    DESCRIPTION
        "The vRtrMplsBindLblPathTable has an entry for each forwarding path
         associated with a binding label for a virtual router in the system."
    ::= { tmnxMplsObjs 75 }

vRtrMplsBindLblPathEntry         OBJECT-TYPE
    SYNTAX      VRtrMplsBindLblPathEntry
    MAX-ACCESS  not-accessible
    STATUS      current
    DESCRIPTION
        "Each row entry represents a forwarding path associated with a binding
         label.

         Entries cannot be created and deleted via SNMP SET operations."
    INDEX       {
        vRtrMplsBindLblPathOwner,
        vRtrID,
        vRtrMplsBindLbl,
        vRtrMplsBindLblPathId
    }
    ::= { vRtrMplsBindLblPathTable 1 }

VRtrMplsBindLblPathEntry         ::= SEQUENCE
{
    vRtrMplsBindLbl                  TmnxMplsLabel,
    vRtrMplsBindLblPathId            Unsigned32,
    vRtrMplsBindLblPathOwner         INTEGER,
    vRtrMplsBindLblPathName          TLNamedItem,
    vRtrMplsBindLblPathOperState     TmnxOperState,
    vRtrMplsBindLblPathLastOperChg   TimeStamp,
    vRtrMplsBindLblOperDownReason    INTEGER,
    vRtrMplsBindLblPathNumNHGrpCnt   Unsigned32,
    vRtrMplsBindLblPathRetryCount    Counter32,
    vRtrMplsBindLblPathRetryTimeRem  Unsigned32,
    vRtrMplsBindLblPathRevertTimer   Unsigned32,
    vRtrMplsBindLblPathIngStatsEnabl TruthValue,
    vRtrMplsBindLblPathPref          Unsigned32,
    vRtrMplsBLPathIngStatOperState   TmnxOperState,
    vRtrMplsBindLblPathEgrStatsEnabl TruthValue,
    vRtrMplsBLPathEgrStatOperState   TmnxOperState
}

vRtrMplsBindLbl                  OBJECT-TYPE
    SYNTAX      TmnxMplsLabel
    MAX-ACCESS  not-accessible
    STATUS      current
    DESCRIPTION
        "The value of vRtrMplsBindLbl specifies the binding label for the
         forwarding path."
    ::= { vRtrMplsBindLblPathEntry 1 }

vRtrMplsBindLblPathId            OBJECT-TYPE
    SYNTAX      Unsigned32
    MAX-ACCESS  not-accessible
    STATUS      current
    DESCRIPTION
        "The value of vRtrMplsBindLblPathId specifies the path ID for the
         forwarding path. Path ID will be unique amongst path associated with
         the same binding label."
    ::= { vRtrMplsBindLblPathEntry 2 }

vRtrMplsBindLblPathOwner         OBJECT-TYPE
    SYNTAX      INTEGER {
        mplsFwdPlcy (1)
    }
    MAX-ACCESS  not-accessible
    STATUS      current
    DESCRIPTION
        "The value of vRtrMplsBindLblPathOwner indicates the owner for this
         path."
    ::= { vRtrMplsBindLblPathEntry 3 }

vRtrMplsBindLblPathName          OBJECT-TYPE
    SYNTAX      TLNamedItem
    MAX-ACCESS  read-only
    STATUS      current
    DESCRIPTION
        "The value of vRtrMplsBindLblPathName indicates the name for this path."
    ::= { vRtrMplsBindLblPathEntry 4 }

vRtrMplsBindLblPathOperState     OBJECT-TYPE
    SYNTAX      TmnxOperState
    MAX-ACCESS  read-only
    STATUS      current
    DESCRIPTION
        "The value of vRtrMplsBindLblPathOperState indicates the operational
         state for this path."
    ::= { vRtrMplsBindLblPathEntry 5 }

vRtrMplsBindLblPathLastOperChg   OBJECT-TYPE
    SYNTAX      TimeStamp
    MAX-ACCESS  read-only
    STATUS      current
    DESCRIPTION
        "The value of vRtrMplsBindLblPathLastOperChg indicates the timestamp
         when the operational state last changed."
    ::= { vRtrMplsBindLblPathEntry 6 }

vRtrMplsBindLblOperDownReason    OBJECT-TYPE
    SYNTAX      INTEGER {
        notApplicable       (0),
        memAllocFailed      (1),
        invEndPointAddr     (2),
        invBindingLbl       (3),
        duplicatePlcy       (4),
        invalidNextHop      (5),
        iomPgmFailed        (6),
        backpressured       (7),
        higherPrefPlcyPgmed (8),
        lblNotAvailable     (9),
        statsAllocFailed    (10),
        maxPlcyExceeded     (11)
    }
    MAX-ACCESS  read-only
    STATUS      current
    DESCRIPTION
        "The value of vRtrMplsBindLblOperDownReason indicates the reason for
         the path being operationally down."
    ::= { vRtrMplsBindLblPathEntry 7 }

vRtrMplsBindLblPathNumNHGrpCnt   OBJECT-TYPE
    SYNTAX      Unsigned32 (0..32)
    MAX-ACCESS  read-only
    STATUS      current
    DESCRIPTION
        "The value of vRtrMplsBindLblPathNumNHGrpCnt indicates the number of
         next-hop groups for this path."
    ::= { vRtrMplsBindLblPathEntry 8 }

vRtrMplsBindLblPathRetryCount    OBJECT-TYPE
    SYNTAX      Counter32
    MAX-ACCESS  read-only
    STATUS      current
    DESCRIPTION
        "The value of vRtrMplsBindLblPathRetryCount indicates the number of
         retry attempts to bring up this path."
    ::= { vRtrMplsBindLblPathEntry 9 }

vRtrMplsBindLblPathRetryTimeRem  OBJECT-TYPE
    SYNTAX      Unsigned32
    UNITS       "seconds"
    MAX-ACCESS  read-only
    STATUS      current
    DESCRIPTION
        "The value of vRtrMplsBindLblPathRetryTimeRem indicates the time
         remaining till the next retry to bring up this path."
    ::= { vRtrMplsBindLblPathEntry 10 }

vRtrMplsBindLblPathRevertTimer   OBJECT-TYPE
    SYNTAX      Unsigned32 (0..600)
    UNITS       "minutes"
    MAX-ACCESS  read-only
    STATUS      current
    DESCRIPTION
        "The value of vRtrMplsBindLblPathRevertTimer indicates the revert timer
         for the path."
    ::= { vRtrMplsBindLblPathEntry 11 }

vRtrMplsBindLblPathIngStatsEnabl OBJECT-TYPE
    SYNTAX      TruthValue
    MAX-ACCESS  read-only
    STATUS      current
    DESCRIPTION
        "The value of vRtrMplsBindLblPathIngStatsEnabl indicates whether
         ingress statistics are enabled for this path."
    ::= { vRtrMplsBindLblPathEntry 12 }

vRtrMplsBindLblPathPref          OBJECT-TYPE
    SYNTAX      Unsigned32 (1..255)
    MAX-ACCESS  read-only
    STATUS      current
    DESCRIPTION
        "The value of vRtrMplsBindLblPathPref indicates the preference for this
         path."
    ::= { vRtrMplsBindLblPathEntry 13 }

vRtrMplsBLPathIngStatOperState   OBJECT-TYPE
    SYNTAX      TmnxOperState
    MAX-ACCESS  read-only
    STATUS      current
    DESCRIPTION
        "The value of vRtrMplsBLPathIngStatOperState indicates the operational
         state of ingress statistics for this path."
    ::= { vRtrMplsBindLblPathEntry 14 }

vRtrMplsBindLblPathEgrStatsEnabl OBJECT-TYPE
    SYNTAX      TruthValue
    MAX-ACCESS  read-only
    STATUS      current
    DESCRIPTION
        "The value of vRtrMplsBindLblPathEgrStatsEnabl indicates whether egress
         statistics are enabled for this path."
    ::= { vRtrMplsBindLblPathEntry 15 }

vRtrMplsBLPathEgrStatOperState   OBJECT-TYPE
    SYNTAX      TmnxOperState
    MAX-ACCESS  read-only
    STATUS      current
    DESCRIPTION
        "The value of vRtrMplsBLPathEgrStatOperState indicates the operational
         state of egress statistics for this path."
    ::= { vRtrMplsBindLblPathEntry 16 }

vRtrMplsBindLblPathNhgTable      OBJECT-TYPE
    SYNTAX      SEQUENCE OF VRtrMplsBindLblPathNhgEntry
    MAX-ACCESS  not-accessible
    STATUS      current
    DESCRIPTION
        "The vRtrMplsBindLblPathNhgTable has an entry for each  next-hop group
         associated with a binding label path."
    ::= { tmnxMplsObjs 76 }

vRtrMplsBindLblPathNhgEntry      OBJECT-TYPE
    SYNTAX      VRtrMplsBindLblPathNhgEntry
    MAX-ACCESS  not-accessible
    STATUS      current
    DESCRIPTION
        "Each row entry represents a next-hop group associated with a binding
         label path.

         Entries cannot be created and deleted via SNMP SET operations."
    INDEX       {
        vRtrMplsBindLblPathOwner,
        vRtrID,
        vRtrMplsBindLbl,
        vRtrMplsBindLblPathId,
        vRtrMplsBindLblPathNhgIndex
    }
    ::= { vRtrMplsBindLblPathNhgTable 1 }

VRtrMplsBindLblPathNhgEntry      ::= SEQUENCE
{
    vRtrMplsBindLblPathNhgIndex      Unsigned32,
    vRtrMplsBindLblPathNhgOperState  TmnxOperState,
    vRtrMplsBindLblPathNHgResType    INTEGER,
    vRtrMplsBindLblPathNhgLoadBalWt  Unsigned32,
    vRtrMplsBindLblPathNhgFailovrCnt Counter32,
    vRtrMplsBindLblPathNhgRevertCnt  Counter32,
    vRtrMplsBindLblPathNhgRevTimeRem Counter32,
    vRtrMplsBindLblPathNhgDownReason INTEGER,
    vRtrMplsBindLblPathNhgWeights    Unsigned32
}

vRtrMplsBindLblPathNhgIndex      OBJECT-TYPE
    SYNTAX      Unsigned32 (1..32)
    MAX-ACCESS  not-accessible
    STATUS      current
    DESCRIPTION
        "The value of vRtrMplsBindLblPathNhgIndex indicates the next-hop group
         index."
    ::= { vRtrMplsBindLblPathNhgEntry 1 }

vRtrMplsBindLblPathNhgOperState  OBJECT-TYPE
    SYNTAX      TmnxOperState
    MAX-ACCESS  read-only
    STATUS      current
    DESCRIPTION
        "The value of vRtrMplsBindLblPathNhgOperState indicates the operational
         state of this next-hop group."
    ::= { vRtrMplsBindLblPathNhgEntry 2 }

vRtrMplsBindLblPathNHgResType    OBJECT-TYPE
    SYNTAX      INTEGER {
        direct   (1),
        indirect (2)
    }
    MAX-ACCESS  read-only
    STATUS      current
    DESCRIPTION
        "The value of vRtrMplsBindLblPathNHgResType indicates the resolution
         type of next-hop group.

         When the value of vRtrMplsBindLblPathNHgResType is 'direct', the
         next-hops in this group must resolve to direct routes for for them to
         be operational.

         When the value of vRtrMplsBindLblPathNHgResType is 'indirect', the
         next-hops in this group must resolve to indirect routes for for them
         to be operational."
    ::= { vRtrMplsBindLblPathNhgEntry 3 }

vRtrMplsBindLblPathNhgLoadBalWt  OBJECT-TYPE
    SYNTAX      Unsigned32
    MAX-ACCESS  read-only
    STATUS      current
    DESCRIPTION
        "The value of vRtrMplsBindLblPathNhgLoadBalWt indicates the
         load-balancing weight for this next-hop group."
    ::= { vRtrMplsBindLblPathNhgEntry 4 }

vRtrMplsBindLblPathNhgFailovrCnt OBJECT-TYPE
    SYNTAX      Counter32
    MAX-ACCESS  read-only
    STATUS      current
    DESCRIPTION
        "The value of vRtrMplsBindLblPathNhgFailovrCnt indicates the number of
         failovers from primary to backup next-hop for this next-hop group"
    ::= { vRtrMplsBindLblPathNhgEntry 5 }

vRtrMplsBindLblPathNhgRevertCnt  OBJECT-TYPE
    SYNTAX      Counter32
    MAX-ACCESS  read-only
    STATUS      current
    DESCRIPTION
        "The value of vRtrMplsBindLblPathNhgRevertCnt indicates the number of
         reverts from backup to primary next-hop for this next-hop group."
    ::= { vRtrMplsBindLblPathNhgEntry 6 }

vRtrMplsBindLblPathNhgRevTimeRem OBJECT-TYPE
    SYNTAX      Counter32
    MAX-ACCESS  read-only
    STATUS      current
    DESCRIPTION
        "The value of vRtrMplsBindLblPathNhgRevTimeRem indicates the time
         remaining to revert from backup to primary  next-hop."
    ::= { vRtrMplsBindLblPathNhgEntry 7 }

vRtrMplsBindLblPathNhgDownReason OBJECT-TYPE
    SYNTAX      INTEGER {
        notApplicable      (0),
        nextHopNotResolved (1),
        nextHopIsLocal     (3),
        nextHopIsMcast     (4),
        resTypeMismatch    (5)
    }
    MAX-ACCESS  read-only
    STATUS      current
    DESCRIPTION
        "The value of vRtrMplsBindLblPathNhgDownReason indicates the reason for
         the path NHG being operationally down."
    ::= { vRtrMplsBindLblPathNhgEntry 8 }

vRtrMplsBindLblPathNhgWeights    OBJECT-TYPE
    SYNTAX      Unsigned32
    MAX-ACCESS  read-only
    STATUS      current
    DESCRIPTION
        "The value of vRtrMplsBindLblPathNhgWeights indicates the weights for
         the path next hop group."
    ::= { vRtrMplsBindLblPathNhgEntry 9 }

vRtrMplsBindLblPathNhgNHTable    OBJECT-TYPE
    SYNTAX      SEQUENCE OF VRtrMplsBindLblPathNhgNHEntry
    MAX-ACCESS  not-accessible
    STATUS      current
    DESCRIPTION
        "The vRtrMplsBindLblPathNhgNHTable has an entry for each next-hop in a
         next-hop group associated with a binding  label path."
    ::= { tmnxMplsObjs 77 }

vRtrMplsBindLblPathNhgNHEntry    OBJECT-TYPE
    SYNTAX      VRtrMplsBindLblPathNhgNHEntry
    MAX-ACCESS  not-accessible
    STATUS      current
    DESCRIPTION
        "Each row entry represents a next-hop for a next-hop  group associated
         with a binding label path.

         Entries cannot be created and deleted via SNMP SET operations."
    INDEX       {
        vRtrMplsBindLblPathOwner,
        vRtrID,
        vRtrMplsBindLbl,
        vRtrMplsBindLblPathId,
        vRtrMplsBindLblPathNhgIndex,
        vRtrMplsBindLblPathNhgNHType
    }
    ::= { vRtrMplsBindLblPathNhgNHTable 1 }

VRtrMplsBindLblPathNhgNHEntry    ::= SEQUENCE
{
    vRtrMplsBindLblPathNhgNHType     INTEGER,
    vRtrMplsBindLblPathNhgNHAddrType InetAddressType,
    vRtrMplsBindLblPathNhgNHAddr     InetAddress,
    vRtrMplsBindLblPathNhgNHResolved TruthValue,
    vRtrMplsBindLblPathNhgNHOutIf    InterfaceIndexOrZero,
    vRtrMplsBindLblPathNhgNHDownCode INTEGER,
    vRtrMplsBindLblPathNhgNHEgrOper  TmnxOperState
}

vRtrMplsBindLblPathNhgNHType     OBJECT-TYPE
    SYNTAX      INTEGER {
        primary (1),
        backup  (2)
    }
    MAX-ACCESS  not-accessible
    STATUS      current
    DESCRIPTION
        "The value of vRtrMplsBindLblPathNhgNHType specifies the type of
         next-hop.

         When the value of vRtrMplsBindLblPathNhgNHType is set to 'primary',
         this next-hop will be the primary next-hop in the next-hop group.

         When the value of vRtrMplsBindLblPathNhgNHType is set to 'backup',
         this next-hop will be the backup next-hop in the next-hop group."
    ::= { vRtrMplsBindLblPathNhgNHEntry 1 }

vRtrMplsBindLblPathNhgNHAddrType OBJECT-TYPE
    SYNTAX      InetAddressType
    MAX-ACCESS  read-only
    STATUS      current
    DESCRIPTION
        "The value of vRtrMplsBindLblPathNhgNHAddrType indicates the address
         type of the next-hop."
    ::= { vRtrMplsBindLblPathNhgNHEntry 2 }

vRtrMplsBindLblPathNhgNHAddr     OBJECT-TYPE
    SYNTAX      InetAddress (SIZE (0|4|16))
    MAX-ACCESS  read-only
    STATUS      current
    DESCRIPTION
        "The value of vRtrMplsBindLblPathNhgNHAddr indicates the address of the
         next-hop."
    ::= { vRtrMplsBindLblPathNhgNHEntry 3 }

vRtrMplsBindLblPathNhgNHResolved OBJECT-TYPE
    SYNTAX      TruthValue
    MAX-ACCESS  read-only
    STATUS      current
    DESCRIPTION
        "The value of vRtrMplsBindLblPathNhgNHResolved indicates if next-hop is
         resolved or not."
    ::= { vRtrMplsBindLblPathNhgNHEntry 4 }

vRtrMplsBindLblPathNhgNHOutIf    OBJECT-TYPE
    SYNTAX      InterfaceIndexOrZero
    MAX-ACCESS  read-only
    STATUS      current
    DESCRIPTION
        "The value of vRtrMplsBindLblPathNhgNHOutIf indicates the index of the
         outgoing interface that the next-hop resolved to if it is a direct
         next-hop.

         A value of 0 indicates that either the next-hop is not resolved or
         that the next-hop is indirect."
    ::= { vRtrMplsBindLblPathNhgNHEntry 5 }

vRtrMplsBindLblPathNhgNHDownCode OBJECT-TYPE
    SYNTAX      INTEGER {
        notApplicable      (0),
        nextHopNotResolved (1),
        nextHopIsLocal     (3),
        nextHopIsMcast     (4),
        resTypeMismatch    (5)
    }
    MAX-ACCESS  read-only
    STATUS      current
    DESCRIPTION
        "The value of vRtrMplsBindLblPathNhgNHDownCode indicates the reason for
         the path NHG NH being not resolved."
    ::= { vRtrMplsBindLblPathNhgNHEntry 6 }

vRtrMplsBindLblPathNhgNHEgrOper  OBJECT-TYPE
    SYNTAX      TmnxOperState
    MAX-ACCESS  read-only
    STATUS      current
    DESCRIPTION
        "The value of vRtrMplsBindLblPathNhgNHEgrOper indicates the operational
         state of the egress stats in this next-hop group next hop."
    ::= { vRtrMplsBindLblPathNhgNHEntry 7 }

vRtrMplsBindLblIngrStatsTable    OBJECT-TYPE
    SYNTAX      SEQUENCE OF VRtrMplsBindLblIngrStatsEntry
    MAX-ACCESS  not-accessible
    STATUS      current
    DESCRIPTION
        "The vRtrMplsBindLblIngrStatsTable has an entry for ingress statistics
         associated with a binding label path."
    ::= { tmnxMplsObjs 78 }

vRtrMplsBindLblIngrStatsEntry    OBJECT-TYPE
    SYNTAX      VRtrMplsBindLblIngrStatsEntry
    MAX-ACCESS  not-accessible
    STATUS      current
    DESCRIPTION
        "Each row entry represents ingress statistics collected for a binding
         label path.

         Entries cannot be created and deleted via SNMP SET operations."
    INDEX       {
        vRtrID,
        vRtrMplsBindLblPathOwner,
        vRtrMplsBindLbl
    }
    ::= { vRtrMplsBindLblIngrStatsTable 1 }

VRtrMplsBindLblIngrStatsEntry    ::= SEQUENCE
{
    vRtrMplsBindLblIngrAggPkts       Counter64,
    vRtrMplsBindLblIngrAggOctets     Counter64
}

vRtrMplsBindLblIngrAggPkts       OBJECT-TYPE
    SYNTAX      Counter64
    MAX-ACCESS  read-only
    STATUS      current
    DESCRIPTION
        "The total of number of ingress packets for this binding label path."
    ::= { vRtrMplsBindLblIngrStatsEntry 1 }

vRtrMplsBindLblIngrAggOctets     OBJECT-TYPE
    SYNTAX      Counter64
    MAX-ACCESS  read-only
    STATUS      current
    DESCRIPTION
        "The total of number of ingress octets for this binding label path.."
    ::= { vRtrMplsBindLblIngrStatsEntry 2 }

vRtrMplsEndptPathTable           OBJECT-TYPE
    SYNTAX      SEQUENCE OF VRtrMplsEndptPathEntry
    MAX-ACCESS  not-accessible
    STATUS      current
    DESCRIPTION
        "The vRtrMplsEndptPathTable has an entry for each forwarding path
         associated with an endpoint address for a virtual router in the
         system."
    ::= { tmnxMplsObjs 79 }

vRtrMplsEndptPathEntry           OBJECT-TYPE
    SYNTAX      VRtrMplsEndptPathEntry
    MAX-ACCESS  not-accessible
    STATUS      current
    DESCRIPTION
        "Each row entry represents a forwarding path associated  with an
         endpoint path.

         Entries cannot be created and deleted via SNMP SET operations."
    INDEX       {
        vRtrMplsEndptPathOwner,
        vRtrID,
        vRtrMplsEndptAddrType,
        vRtrMplsEndptAddress,
        vRtrMplsEndptPathId
    }
    ::= { vRtrMplsEndptPathTable 1 }

VRtrMplsEndptPathEntry           ::= SEQUENCE
{
    vRtrMplsEndptAddrType            InetAddressType,
    vRtrMplsEndptAddress             InetAddress,
    vRtrMplsEndptPathId              Unsigned32,
    vRtrMplsEndptPathOwner           INTEGER,
    vRtrMplsEndptPathName            TLNamedItem,
    vRtrMplsEndptPathOperState       TmnxOperState,
    vRtrMplsEndptPathLastOperChg     TimeStamp,
    vRtrMplsEndptPathOperDownReason  INTEGER,
    vRtrMplsEndptPathNHGrpCnt        Unsigned32,
    vRtrMplsEndptPathRetryCount      Counter32,
    vRtrMplsEndptPathRetryTimeRem    Unsigned32,
    vRtrMplsEndptPathRevertTimer     Unsigned32,
    vRtrMplsEndptPathPref            Unsigned32,
    vRtrMplsEndptPathTTMPref         Unsigned32,
    vRtrMplsEndptPathMetric          Unsigned32,
    vRtrMplsEndptPathEgrStatsEnabl   TruthValue,
    vRtrMplsEndptPathEgrStatsOper    TmnxOperState
}

vRtrMplsEndptAddrType            OBJECT-TYPE
    SYNTAX      InetAddressType
    MAX-ACCESS  not-accessible
    STATUS      current
    DESCRIPTION
        "The value of vRtrMplsEndptAddrType indicates the  address type of the
         endpoint."
    ::= { vRtrMplsEndptPathEntry 1 }

vRtrMplsEndptAddress             OBJECT-TYPE
    SYNTAX      InetAddress (SIZE (0|4|16))
    MAX-ACCESS  not-accessible
    STATUS      current
    DESCRIPTION
        "The value of vRtrMplsEndptAddress indicates the address of the
         endpoint."
    ::= { vRtrMplsEndptPathEntry 2 }

vRtrMplsEndptPathId              OBJECT-TYPE
    SYNTAX      Unsigned32
    MAX-ACCESS  not-accessible
    STATUS      current
    DESCRIPTION
        "The value of vRtrMplsEndptPathId indicates the path ID for the
         forwarding path. Path ID will be unique amongst path associated with
         the same endpoint address."
    ::= { vRtrMplsEndptPathEntry 3 }

vRtrMplsEndptPathOwner           OBJECT-TYPE
    SYNTAX      INTEGER {
        mplsFwdPlcy (1)
    }
    MAX-ACCESS  not-accessible
    STATUS      current
    DESCRIPTION
        "The value of vRtrMplsEndptPathOwner indicates the owner for this path."
    ::= { vRtrMplsEndptPathEntry 4 }

vRtrMplsEndptPathName            OBJECT-TYPE
    SYNTAX      TLNamedItem
    MAX-ACCESS  read-only
    STATUS      current
    DESCRIPTION
        "The value of vRtrMplsEndptPathName indicates the name for this path."
    ::= { vRtrMplsEndptPathEntry 5 }

vRtrMplsEndptPathOperState       OBJECT-TYPE
    SYNTAX      TmnxOperState
    MAX-ACCESS  read-only
    STATUS      current
    DESCRIPTION
        "The value of vRtrMplsEndptPathOperState indicates the operational
         state for this path."
    ::= { vRtrMplsEndptPathEntry 6 }

vRtrMplsEndptPathLastOperChg     OBJECT-TYPE
    SYNTAX      TimeStamp
    MAX-ACCESS  read-only
    STATUS      current
    DESCRIPTION
        "The value of vRtrMplsEndptPathLastOperChg indicates the timestamp when
         the operational state last changed."
    ::= { vRtrMplsEndptPathEntry 7 }

vRtrMplsEndptPathOperDownReason  OBJECT-TYPE
    SYNTAX      INTEGER {
        notApplicable       (0),
        memAllocFailed      (1),
        invEndPointAddr     (2),
        duplicatePlcy       (3),
        invalidNextHop      (4),
        iomPgmFailed        (5),
        backpressured       (6),
        higherPrefPlcyPgmed (7),
        statsAllocFailed    (8),
        maxPlcyExceeded     (9),
        noNextHops          (10)
    }
    MAX-ACCESS  read-only
    STATUS      current
    DESCRIPTION
        "The value of vRtrMplsEndptPathOperDownReason indicates the reason for
         the path being operationally down."
    ::= { vRtrMplsEndptPathEntry 8 }

vRtrMplsEndptPathNHGrpCnt        OBJECT-TYPE
    SYNTAX      Unsigned32 (0..32)
    MAX-ACCESS  read-only
    STATUS      current
    DESCRIPTION
        "The value of vRtrMplsEndptPathNHGrpCnt indicates the number of
         next-hop groups for this path."
    ::= { vRtrMplsEndptPathEntry 9 }

vRtrMplsEndptPathRetryCount      OBJECT-TYPE
    SYNTAX      Counter32
    MAX-ACCESS  read-only
    STATUS      current
    DESCRIPTION
        "The value of vRtrMplsEndptPathRetryCount indicates the number of retry
         attempts to bring up this path."
    ::= { vRtrMplsEndptPathEntry 10 }

vRtrMplsEndptPathRetryTimeRem    OBJECT-TYPE
    SYNTAX      Unsigned32
    UNITS       "seconds"
    MAX-ACCESS  read-only
    STATUS      current
    DESCRIPTION
        "The value of vRtrMplsEndptPathRetryTimeRem indicates the time
         remaining till the next retry to bring up this path."
    ::= { vRtrMplsEndptPathEntry 11 }

vRtrMplsEndptPathRevertTimer     OBJECT-TYPE
    SYNTAX      Unsigned32 (0..600)
    UNITS       "minutes"
    MAX-ACCESS  read-only
    STATUS      current
    DESCRIPTION
        "The value of vRtrMplsEndptPathRevertTimer indicates the revert timer
         for the path."
    ::= { vRtrMplsEndptPathEntry 12 }

vRtrMplsEndptPathPref            OBJECT-TYPE
    SYNTAX      Unsigned32 (1..255)
    MAX-ACCESS  read-only
    STATUS      current
    DESCRIPTION
        "The value of vRtrMplsEndptPathPref indicates the preference for this
         path."
    ::= { vRtrMplsEndptPathEntry 13 }

vRtrMplsEndptPathTTMPref         OBJECT-TYPE
    SYNTAX      Unsigned32 (1..255)
    MAX-ACCESS  read-only
    STATUS      current
    DESCRIPTION
        "The value of vRtrMplsEndptPathTTMPref indicates the TTM preference for
         endpoint config."
    ::= { vRtrMplsEndptPathEntry 14 }

vRtrMplsEndptPathMetric          OBJECT-TYPE
    SYNTAX      Unsigned32 (0..16777215)
    MAX-ACCESS  read-only
    STATUS      current
    DESCRIPTION
        "This value of vRtrMplsEndptPathMetric indicates the metric for
         endpoint config."
    ::= { vRtrMplsEndptPathEntry 15 }

vRtrMplsEndptPathEgrStatsEnabl   OBJECT-TYPE
    SYNTAX      TruthValue
    MAX-ACCESS  read-only
    STATUS      current
    DESCRIPTION
        "The value of vRtrMplsEndptPathEgrStatsEnabl indicates whether egress
         statistics are enabled for endpoint config."
    ::= { vRtrMplsEndptPathEntry 16 }

vRtrMplsEndptPathEgrStatsOper    OBJECT-TYPE
    SYNTAX      TmnxOperState
    MAX-ACCESS  read-only
    STATUS      current
    DESCRIPTION
        "The value of vRtrMplsEndptPathEgrStatsOper indicates the operational
         state of egress statistics for endpoint config."
    ::= { vRtrMplsEndptPathEntry 17 }

vRtrMplsEndptPathNhgTable        OBJECT-TYPE
    SYNTAX      SEQUENCE OF VRtrMplsEndptPathNhgEntry
    MAX-ACCESS  not-accessible
    STATUS      current
    DESCRIPTION
        "The vRtrMplsEndptPathNhgTable has an entry for each next-hop group
         associated with an endpoint path."
    ::= { tmnxMplsObjs 80 }

vRtrMplsEndptPathNhgEntry        OBJECT-TYPE
    SYNTAX      VRtrMplsEndptPathNhgEntry
    MAX-ACCESS  not-accessible
    STATUS      current
    DESCRIPTION
        "Each row entry represents a next-hop group associated with an endpoint
         path.

         Entries cannot be created and deleted via SNMP SET operations."
    INDEX       {
        vRtrMplsEndptPathOwner,
        vRtrID,
        vRtrMplsEndptAddrType,
        vRtrMplsEndptAddress,
        vRtrMplsEndptPathId,
        vRtrMplsEndptPathNhgIndex
    }
    ::= { vRtrMplsEndptPathNhgTable 1 }

VRtrMplsEndptPathNhgEntry        ::= SEQUENCE
{
    vRtrMplsEndptPathNhgIndex        Unsigned32,
    vRtrMplsEndptPathNhgOperState    TmnxOperState,
    vRtrMplsEndptPathNhgResType      INTEGER,
    vRtrMplsEndptPathNhgLoadBalWt    Unsigned32,
    vRtrMplsEndptPathNhgFailovrCnt   Counter32,
    vRtrMplsEndptPathNhgRevertCnt    Counter32,
    vRtrMplsEndptPathNhgRevTimeRem   Counter32,
    vRtrMplsEndptPathNhgDownReason   TmnxNhgDownReason,
    vRtrMplsEndptPathNhgWeights      Unsigned32
}

vRtrMplsEndptPathNhgIndex        OBJECT-TYPE
    SYNTAX      Unsigned32 (1..32)
    MAX-ACCESS  not-accessible
    STATUS      current
    DESCRIPTION
        "The value of vRtrMplsEndptPathNhgIndex indicates the next-hop group
         index."
    ::= { vRtrMplsEndptPathNhgEntry 1 }

vRtrMplsEndptPathNhgOperState    OBJECT-TYPE
    SYNTAX      TmnxOperState
    MAX-ACCESS  read-only
    STATUS      current
    DESCRIPTION
        "The value of vRtrMplsEndptPathNhgOperState indicates the operational
         state of this next-hop group."
    ::= { vRtrMplsEndptPathNhgEntry 2 }

vRtrMplsEndptPathNhgResType      OBJECT-TYPE
    SYNTAX      INTEGER {
        direct   (1),
        indirect (2)
    }
    MAX-ACCESS  read-only
    STATUS      current
    DESCRIPTION
        "The value of vRtrMplsEndptPathNhgResType indicates the resolution type
         of next-hop group.

         When the value of vRtrMplsEndptPathNhgResType is 'direct', the
         next-hops in this group must resolve to direct routes for for them to
         be operational.

         When the value of vRtrMplsEndptPathNhgResType is 'indirect', the
         next-hops in this group must resolve to indirect routes for for them
         to be operational."
    ::= { vRtrMplsEndptPathNhgEntry 3 }

vRtrMplsEndptPathNhgLoadBalWt    OBJECT-TYPE
    SYNTAX      Unsigned32
    MAX-ACCESS  read-only
    STATUS      current
    DESCRIPTION
        "The value of vRtrMplsEndptPathNhgLoadBalWt indicates the
         load-balancing weight for this next-hop group."
    ::= { vRtrMplsEndptPathNhgEntry 4 }

vRtrMplsEndptPathNhgFailovrCnt   OBJECT-TYPE
    SYNTAX      Counter32
    MAX-ACCESS  read-only
    STATUS      current
    DESCRIPTION
        "The value of vRtrMplsEndptPathNhgFailovrCnt indicates the number of
         failovers from primary to backup next-hop for this next-hop group"
    ::= { vRtrMplsEndptPathNhgEntry 5 }

vRtrMplsEndptPathNhgRevertCnt    OBJECT-TYPE
    SYNTAX      Counter32
    MAX-ACCESS  read-only
    STATUS      current
    DESCRIPTION
        "The value of vRtrMplsEndptPathNhgRevertCnt indicates the number of
         reverts from backup to primary next-hop for this next-hop group."
    ::= { vRtrMplsEndptPathNhgEntry 6 }

vRtrMplsEndptPathNhgRevTimeRem   OBJECT-TYPE
    SYNTAX      Counter32
    MAX-ACCESS  read-only
    STATUS      current
    DESCRIPTION
        "The value of vRtrMplsEndptPathNhgRevTimeRem indicates the time
         remaining to revert from backup to primary  next-hop."
    ::= { vRtrMplsEndptPathNhgEntry 7 }

vRtrMplsEndptPathNhgDownReason   OBJECT-TYPE
    SYNTAX      TmnxNhgDownReason
    MAX-ACCESS  read-only
    STATUS      current
    DESCRIPTION
        "The value of vRtrMplsEndptPathNhgDownReason indicates the reason for
         the path NHG being operationally down."
    ::= { vRtrMplsEndptPathNhgEntry 8 }

vRtrMplsEndptPathNhgWeights      OBJECT-TYPE
    SYNTAX      Unsigned32
    MAX-ACCESS  read-only
    STATUS      current
    DESCRIPTION
        "The value of vRtrMplsEndptPathNhgWeights indicates the weights for the
         path next hop group."
    ::= { vRtrMplsEndptPathNhgEntry 9 }

vRtrMplsEndptPathNhgNHTable      OBJECT-TYPE
    SYNTAX      SEQUENCE OF VRtrMplsEndptPathNhgNHEntry
    MAX-ACCESS  not-accessible
    STATUS      current
    DESCRIPTION
        "The vRtrMplsEndptPathNhgNHTable has an entry for each next-hop in a
         next-hop group associated with an endpoint path."
    ::= { tmnxMplsObjs 81 }

vRtrMplsEndptPathNhgNHEntry      OBJECT-TYPE
    SYNTAX      VRtrMplsEndptPathNhgNHEntry
    MAX-ACCESS  not-accessible
    STATUS      current
    DESCRIPTION
        "Each row entry represents a next-hop for a next-hop  group associated
         with an endpoint path.

         Entries cannot be created and deleted via SNMP SET operations."
    INDEX       {
        vRtrMplsEndptPathOwner,
        vRtrID,
        vRtrMplsEndptAddrType,
        vRtrMplsEndptAddress,
        vRtrMplsEndptPathId,
        vRtrMplsEndptPathNhgIndex,
        vRtrMplsEndptPathNhgNHType
    }
    ::= { vRtrMplsEndptPathNhgNHTable 1 }

VRtrMplsEndptPathNhgNHEntry      ::= SEQUENCE
{
    vRtrMplsEndptPathNhgNHType       INTEGER,
    vRtrMplsEndptPathNhgNHAddrType   InetAddressType,
    vRtrMplsEndptPathNhgNHAddr       InetAddress,
    vRtrMplsEndptPathNhgNHResolved   TruthValue,
    vRtrMplsEndptPathNhgNHOutIf      InterfaceIndexOrZero,
    vRtrMplsEndptPathNhgNHDownCode   TmnxNhgDownReason,
    vRtrMplsEndptPathNhgNHEgrOper    TmnxOperState
}

vRtrMplsEndptPathNhgNHType       OBJECT-TYPE
    SYNTAX      INTEGER {
        primary (1),
        backup  (2)
    }
    MAX-ACCESS  not-accessible
    STATUS      current
    DESCRIPTION
        "The value of vRtrMplsEndptPathNhgNHType specifies the type of
         next-hop.

         When the value of vRtrMplsEndptPathNhgNHType is set to 'primary', this
         next-hop will be the primary next-hop in the next-hop group.

         When the value of vRtrMplsEndptPathNhgNHType is set to 'backup', this
         next-hop will be the backup next-hop in the next-hop group."
    ::= { vRtrMplsEndptPathNhgNHEntry 1 }

vRtrMplsEndptPathNhgNHAddrType   OBJECT-TYPE
    SYNTAX      InetAddressType
    MAX-ACCESS  read-only
    STATUS      current
    DESCRIPTION
        "The value of vRtrMplsEndptPathNhgNHAddrType indicates the address type
         of the next-hop."
    ::= { vRtrMplsEndptPathNhgNHEntry 2 }

vRtrMplsEndptPathNhgNHAddr       OBJECT-TYPE
    SYNTAX      InetAddress (SIZE (0|4|16))
    MAX-ACCESS  read-only
    STATUS      current
    DESCRIPTION
        "The value of vRtrMplsEndptPathNhgNHAddr indicates the address of the
         next-hop."
    ::= { vRtrMplsEndptPathNhgNHEntry 3 }

vRtrMplsEndptPathNhgNHResolved   OBJECT-TYPE
    SYNTAX      TruthValue
    MAX-ACCESS  read-only
    STATUS      current
    DESCRIPTION
        "The value of vRtrMplsEndptPathNhgNHResolved indicates if next-hop is
         resolved or not."
    ::= { vRtrMplsEndptPathNhgNHEntry 4 }

vRtrMplsEndptPathNhgNHOutIf      OBJECT-TYPE
    SYNTAX      InterfaceIndexOrZero
    MAX-ACCESS  read-only
    STATUS      current
    DESCRIPTION
        "The value of vRtrMplsEndptPathNhgNHOutIf indicates the index of the
         outgoing interface that the next-hop resolved to if it is a direct
         next-hop.

         A value of 0 indicates that either the next-hop is not resolved or
         that the next-hop is indirect."
    ::= { vRtrMplsEndptPathNhgNHEntry 5 }

vRtrMplsEndptPathNhgNHDownCode   OBJECT-TYPE
    SYNTAX      TmnxNhgDownReason
    MAX-ACCESS  read-only
    STATUS      current
    DESCRIPTION
        "The value of vRtrMplsEndptPathNhgNHDownCode indicates the reason for
         the path NHG NH being not resolved."
    ::= { vRtrMplsEndptPathNhgNHEntry 6 }

vRtrMplsEndptPathNhgNHEgrOper    OBJECT-TYPE
    SYNTAX      TmnxOperState
    MAX-ACCESS  read-only
    STATUS      current
    DESCRIPTION
        "The value of vRtrMplsEndptPathNhgNHEgrOper indicates the operational
         state of the egress stats in this next-hop group next hop."
    ::= { vRtrMplsEndptPathNhgNHEntry 7 }

vRtrMplsFwdPlcyNhgNHPushLblTable OBJECT-TYPE
    SYNTAX      SEQUENCE OF VRtrMplsFwdPlcyNhgNHPushLblEntry
    MAX-ACCESS  not-accessible
    STATUS      current
    DESCRIPTION
        "The vRtrMplsFwdPlcyNhgNHPushLblTable has an entry for each label to be
         pushed onto the packet on the nexthop configured in the system. This
         table augments the vRtrMplsFwdPlcyNhgNHTable."
    ::= { tmnxMplsObjs 82 }

vRtrMplsFwdPlcyNhgNHPushLblEntry OBJECT-TYPE
    SYNTAX      VRtrMplsFwdPlcyNhgNHPushLblEntry
    MAX-ACCESS  not-accessible
    STATUS      current
    DESCRIPTION
        "Each row entry represents a label to be pushed onto the packet  on the
         nexthop configured for a virtual router in the system.

         Entries can be created and deleted via SNMP SET operations."
    AUGMENTS    { vRtrMplsFwdPlcyNhgNHEntry }
    ::= { vRtrMplsFwdPlcyNhgNHPushLblTable 1 }

VRtrMplsFwdPlcyNhgNHPushLblEntry ::= SEQUENCE
{
    vRtrMplsFwdPlcyNhgNHPushLabel1   Unsigned32,
    vRtrMplsFwdPlcyNhgNHPushLabel2   Unsigned32,
    vRtrMplsFwdPlcyNhgNHPushLabel3   Unsigned32,
    vRtrMplsFwdPlcyNhgNHPushLabel4   Unsigned32,
    vRtrMplsFwdPlcyNhgNHPushLabel5   Unsigned32,
    vRtrMplsFwdPlcyNhgNHPushLabel6   Unsigned32,
    vRtrMplsFwdPlcyNhgNHPushLabel7   Unsigned32,
    vRtrMplsFwdPlcyNhgNHPushLabel8   Unsigned32,
    vRtrMplsFwdPlcyNhgNHPushLabel9   Unsigned32,
    vRtrMplsFwdPlcyNhgNHPushLabel10  Unsigned32
}

vRtrMplsFwdPlcyNhgNHPushLabel1   OBJECT-TYPE
    SYNTAX      Unsigned32
    MAX-ACCESS  read-create
    STATUS      current
    DESCRIPTION
        "The value of vRtrMplsFwdPlcyNhgNHPushLabel1 indicates the 10th label
         to be pushed onto the packet on this nexthop."
    DEFVAL      { 0 }
    ::= { vRtrMplsFwdPlcyNhgNHPushLblEntry 1 }

vRtrMplsFwdPlcyNhgNHPushLabel2   OBJECT-TYPE
    SYNTAX      Unsigned32
    MAX-ACCESS  read-create
    STATUS      current
    DESCRIPTION
        "The value of vRtrMplsFwdPlcyNhgNHPushLabel2 indicates the 9th label to
         be pushed onto the packet on this nexthop."
    DEFVAL      { 0 }
    ::= { vRtrMplsFwdPlcyNhgNHPushLblEntry 2 }

vRtrMplsFwdPlcyNhgNHPushLabel3   OBJECT-TYPE
    SYNTAX      Unsigned32
    MAX-ACCESS  read-create
    STATUS      current
    DESCRIPTION
        "The value of vRtrMplsFwdPlcyNhgNHPushLabel3 indicates the 8th label to
         be pushed onto the packet on this nexthop."
    DEFVAL      { 0 }
    ::= { vRtrMplsFwdPlcyNhgNHPushLblEntry 3 }

vRtrMplsFwdPlcyNhgNHPushLabel4   OBJECT-TYPE
    SYNTAX      Unsigned32
    MAX-ACCESS  read-create
    STATUS      current
    DESCRIPTION
        "The value of vRtrMplsFwdPlcyNhgNHPushLabel4 indicates the 7th label to
         be pushed onto the packet on this nexthop."
    DEFVAL      { 0 }
    ::= { vRtrMplsFwdPlcyNhgNHPushLblEntry 4 }

vRtrMplsFwdPlcyNhgNHPushLabel5   OBJECT-TYPE
    SYNTAX      Unsigned32
    MAX-ACCESS  read-create
    STATUS      current
    DESCRIPTION
        "The value of vRtrMplsFwdPlcyNhgNHPushLabel5 indicates the 6th label to
         be pushed onto the packet on this nexthop."
    DEFVAL      { 0 }
    ::= { vRtrMplsFwdPlcyNhgNHPushLblEntry 5 }

vRtrMplsFwdPlcyNhgNHPushLabel6   OBJECT-TYPE
    SYNTAX      Unsigned32
    MAX-ACCESS  read-create
    STATUS      current
    DESCRIPTION
        "The value of vRtrMplsFwdPlcyNhgNHPushLabel6 indicates the 5th label to
         be pushed onto the packet on this nexthop."
    DEFVAL      { 0 }
    ::= { vRtrMplsFwdPlcyNhgNHPushLblEntry 6 }

vRtrMplsFwdPlcyNhgNHPushLabel7   OBJECT-TYPE
    SYNTAX      Unsigned32
    MAX-ACCESS  read-create
    STATUS      current
    DESCRIPTION
        "The value of vRtrMplsFwdPlcyNhgNHPushLabel7 indicates the 4th label to
         be pushed onto the packet on this nexthop."
    DEFVAL      { 0 }
    ::= { vRtrMplsFwdPlcyNhgNHPushLblEntry 7 }

vRtrMplsFwdPlcyNhgNHPushLabel8   OBJECT-TYPE
    SYNTAX      Unsigned32
    MAX-ACCESS  read-create
    STATUS      current
    DESCRIPTION
        "The value of vRtrMplsFwdPlcyNhgNHPushLabel8 indicates the 3rd label to
         be pushed onto the packet on this nexthop."
    DEFVAL      { 0 }
    ::= { vRtrMplsFwdPlcyNhgNHPushLblEntry 8 }

vRtrMplsFwdPlcyNhgNHPushLabel9   OBJECT-TYPE
    SYNTAX      Unsigned32
    MAX-ACCESS  read-create
    STATUS      current
    DESCRIPTION
        "The value of vRtrMplsFwdPlcyNhgNHPushLabel9 indicates the 2nd label to
         be pushed onto the packet on this nexthop."
    DEFVAL      { 0 }
    ::= { vRtrMplsFwdPlcyNhgNHPushLblEntry 9 }

vRtrMplsFwdPlcyNhgNHPushLabel10  OBJECT-TYPE
    SYNTAX      Unsigned32
    MAX-ACCESS  read-create
    STATUS      current
    DESCRIPTION
        "The value of vRtrMplsFwdPlcyNhgNHPushLabel10 indicates the 1st label
         to be pushed onto the packet on this nexthop."
    DEFVAL      { 0 }
    ::= { vRtrMplsFwdPlcyNhgNHPushLblEntry 10 }

vRtrMplsBindLblPathNhgNHPLTable  OBJECT-TYPE
    SYNTAX      SEQUENCE OF VRtrMplsBindLblPathNhgNHPLEntry
    MAX-ACCESS  not-accessible
    STATUS      current
    DESCRIPTION
        "The vRtrMplsBindLblPathNhgNHPLTable has an entry for each push label
         for a next-hop type associated with next-hop group with a binding
         label path configured in the system."
    ::= { tmnxMplsObjs 83 }

vRtrMplsBindLblPathNhgNHPLEntry  OBJECT-TYPE
    SYNTAX      VRtrMplsBindLblPathNhgNHPLEntry
    MAX-ACCESS  not-accessible
    STATUS      current
    DESCRIPTION
        "Each row entry represents a push label for a next-hop type associated
         with next-hop group with a binding label path, configured for a
         virtual router in the system."
    INDEX       {
        vRtrMplsBindLblPathOwner,
        vRtrID,
        vRtrMplsBindLbl,
        vRtrMplsBindLblPathId,
        vRtrMplsBindLblPathNhgIndex,
        vRtrMplsBindLblPathNhgNHType,
        vRtrMplsBindLblPathNHgNHPLIndex
    }
    ::= { vRtrMplsBindLblPathNhgNHPLTable 1 }

VRtrMplsBindLblPathNhgNHPLEntry  ::= SEQUENCE
{
    vRtrMplsBindLblPathNHgNHPLIndex  Unsigned32,
    vRtrMplsBindLblPathNHgNHPLabel   Unsigned32
}

vRtrMplsBindLblPathNHgNHPLIndex  OBJECT-TYPE
    SYNTAX      Unsigned32
    MAX-ACCESS  not-accessible
    STATUS      current
    DESCRIPTION
        "The value of vRtrMplsBindLblPathNHgNHPLIndex specifies  the index
         associated with the push label."
    ::= { vRtrMplsBindLblPathNhgNHPLEntry 1 }

vRtrMplsBindLblPathNHgNHPLabel   OBJECT-TYPE
    SYNTAX      Unsigned32
    MAX-ACCESS  read-only
    STATUS      current
    DESCRIPTION
        "The value of vRtrMplsBindLblPathNHgNHPLabel specifies  the label
         number for push label."
    ::= { vRtrMplsBindLblPathNhgNHPLEntry 2 }

vRtrMplsEndptPathNhgNHPLlbTable  OBJECT-TYPE
    SYNTAX      SEQUENCE OF VRtrMplsEndptPathNhgNHPLlbEntry
    MAX-ACCESS  not-accessible
    STATUS      current
    DESCRIPTION
        "The vRtrMplsEndptPathNhgNHPLlbTable has an entry for each push label
         for a next-hop type associated with next-hop group with an endpoint
         address configured in the system."
    ::= { tmnxMplsObjs 84 }

vRtrMplsEndptPathNhgNHPLlbEntry  OBJECT-TYPE
    SYNTAX      VRtrMplsEndptPathNhgNHPLlbEntry
    MAX-ACCESS  not-accessible
    STATUS      current
    DESCRIPTION
        "Each row entry represents a push label for a next-hop type associated
         with next-hop group with an endpoint address, configured for a virtual
         router in the system."
    INDEX       {
        vRtrMplsEndptPathOwner,
        vRtrID,
        vRtrMplsEndptAddrType,
        vRtrMplsEndptAddress,
        vRtrMplsEndptPathId,
        vRtrMplsEndptPathNhgIndex,
        vRtrMplsEndptPathNhgNHType,
        vRtrMplsEndptPathNhgNHPLblIndex
    }
    ::= { vRtrMplsEndptPathNhgNHPLlbTable 1 }

VRtrMplsEndptPathNhgNHPLlbEntry  ::= SEQUENCE
{
    vRtrMplsEndptPathNhgNHPLblIndex  Unsigned32,
    vRtrMplsEndptPathNhgNHPLabel     Unsigned32
}

vRtrMplsEndptPathNhgNHPLblIndex  OBJECT-TYPE
    SYNTAX      Unsigned32
    MAX-ACCESS  not-accessible
    STATUS      current
    DESCRIPTION
        "The value of vRtrMplsEndptPathNhgNHPLblIndex specifies  the index
         associated with the push label."
    ::= { vRtrMplsEndptPathNhgNHPLlbEntry 1 }

vRtrMplsEndptPathNhgNHPLabel     OBJECT-TYPE
    SYNTAX      Unsigned32
    MAX-ACCESS  read-only
    STATUS      current
    DESCRIPTION
        "The value of vRtrMplsEndptPathNhgNHPLabel specifies  the label number
         for push label."
    ::= { vRtrMplsEndptPathNhgNHPLlbEntry 2 }

vRtrMplsPceInitGenTblLastChg     OBJECT-TYPE
    SYNTAX      TimeStamp
    MAX-ACCESS  read-only
    STATUS      current
    DESCRIPTION
        "The value of vRtrMplsPceInitGenTblLastChg indicates the sysUpTime at
         the time of the last modification of an entry in the
         vRtrMplsPceInitGenTable."
    ::= { tmnxMplsObjs 85 }

vRtrMplsPceInitGenTable          OBJECT-TYPE
    SYNTAX      SEQUENCE OF VRtrMplsPceInitGenEntry
    MAX-ACCESS  not-accessible
    STATUS      current
    DESCRIPTION
        "The vRtrMplsPceInitGenTable has an entry for per router instance  for
         PCE initiated LSPs on the system."
    ::= { tmnxMplsObjs 86 }

vRtrMplsPceInitGenEntry          OBJECT-TYPE
    SYNTAX      VRtrMplsPceInitGenEntry
    MAX-ACCESS  not-accessible
    STATUS      current
    DESCRIPTION
        "Each entry represents paramters for PCE initiated LSPs on  the system.

         Entries can be created and deleted via SNMP SET operations."
    INDEX       { vRtrID }
    ::= { vRtrMplsPceInitGenTable 1 }

VRtrMplsPceInitGenEntry          ::= SEQUENCE
{
    vRtrMplsPceInitGenRowStatus      RowStatus,
    vRtrMplsPceInitGenSrte           TruthValue,
    vRtrMplsPceInitGenSrteAdminState TmnxAdminState,
    vRtrMplsPceInitGenSrteOperState  TmnxOperState,
    vRtrMplsPceInitGenSrteOperDnRsn  INTEGER
}

vRtrMplsPceInitGenRowStatus      OBJECT-TYPE
    SYNTAX      RowStatus
    MAX-ACCESS  read-create
    STATUS      current
    DESCRIPTION
        "The row status used for creation, deletion, or control of
         vRtrMplsPceInitGenTable entries."
    ::= { vRtrMplsPceInitGenEntry 1 }

vRtrMplsPceInitGenSrte           OBJECT-TYPE
    SYNTAX      TruthValue
    MAX-ACCESS  read-create
    STATUS      current
    DESCRIPTION
        "The value of vRtrMplsPceInitGenSrte specifies if PCE initiated  SR-TE
         LSPs are supported on the system"
    DEFVAL      { false }
    ::= { vRtrMplsPceInitGenEntry 2 }

vRtrMplsPceInitGenSrteAdminState OBJECT-TYPE
    SYNTAX      TmnxAdminState
    MAX-ACCESS  read-create
    STATUS      current
    DESCRIPTION
        "The value of vRtrMplsPceInitGenSrteAdminState specifies the
         administrative state of PCE initiated SR-TE LSPs on the system.

         The value of vRtrMplsPceInitGenSrteAdminState is valid only if the
         value of vRtrMplsPceInitGenSrte is set to 'true'."
    DEFVAL      { outOfService }
    ::= { vRtrMplsPceInitGenEntry 3 }

vRtrMplsPceInitGenSrteOperState  OBJECT-TYPE
    SYNTAX      TmnxOperState
    MAX-ACCESS  read-only
    STATUS      current
    DESCRIPTION
        "The value of vRtrMplsPceInitGenSrteOperState indicates  the
         operational state of PCE initiated SR-TE LSPs on the system.

         The value of vRtrMplsPceInitGenSrteOperState is valid only if the
         value of vRtrMplsPceInitGenSrte is set to 'true'."
    ::= { vRtrMplsPceInitGenEntry 4 }

vRtrMplsPceInitGenSrteOperDnRsn  OBJECT-TYPE
    SYNTAX      INTEGER {
        notApplicable (0),
        adminDown     (1),
        mplsOperDown  (2)
    }
    MAX-ACCESS  read-only
    STATUS      current
    DESCRIPTION
        "The value of vRtrMplsPceInitGenSrteOperDnRsn indicates the reason due
         to which PCE Init SRTE LSP are operationally down."
    ::= { vRtrMplsPceInitGenEntry 5 }

vRtrMplsBindLblNHEgrStatsTable   OBJECT-TYPE
    SYNTAX      SEQUENCE OF VRtrMplsBindLblNHEgrStatsEntry
    MAX-ACCESS  not-accessible
    STATUS      current
    DESCRIPTION
        "The vRtrMplsBindLblNHEgrStatsTable has an entry for egress statistics
         for each next-hop in a next-hop group associated with a binding label
         path."
    ::= { tmnxMplsObjs 87 }

vRtrMplsBindLblNHEgrStatsEntry   OBJECT-TYPE
    SYNTAX      VRtrMplsBindLblNHEgrStatsEntry
    MAX-ACCESS  not-accessible
    STATUS      current
    DESCRIPTION
        "Each row entry represents a next-hop for a next-hop  group associated
         with a binding label path.

         Entries cannot be created and deleted via SNMP SET operations."
    AUGMENTS    { vRtrMplsBindLblPathNhgNHEntry }
    ::= { vRtrMplsBindLblNHEgrStatsTable 1 }

VRtrMplsBindLblNHEgrStatsEntry   ::= SEQUENCE
{
    vRtrMplsBindLblEgrStatsAggPkts   Counter64,
    vRtrMplsBindLblEgrStatsAggOctets Counter64
}

vRtrMplsBindLblEgrStatsAggPkts   OBJECT-TYPE
    SYNTAX      Counter64
    MAX-ACCESS  read-only
    STATUS      current
    DESCRIPTION
        "The total of number of egress packets for this binding label path
         next-hop group next-hop."
    ::= { vRtrMplsBindLblNHEgrStatsEntry 1 }

vRtrMplsBindLblEgrStatsAggOctets OBJECT-TYPE
    SYNTAX      Counter64
    MAX-ACCESS  read-only
    STATUS      current
    DESCRIPTION
        "The total of number of egress octets for this binding label path
         next-hop group next-hop"
    ::= { vRtrMplsBindLblNHEgrStatsEntry 2 }

vRtrMplsEndptNHEgrStatsTable     OBJECT-TYPE
    SYNTAX      SEQUENCE OF VRtrMplsEndptNHEgrStatsEntry
    MAX-ACCESS  not-accessible
    STATUS      current
    DESCRIPTION
        "The vRtrMplsEndptNHEgrStatsTable has an entry for egress statistics
         for each next-hop in a next-hop group associated with an endpoint
         path."
    ::= { tmnxMplsObjs 88 }

vRtrMplsEndptNHEgrStatsEntry     OBJECT-TYPE
    SYNTAX      VRtrMplsEndptNHEgrStatsEntry
    MAX-ACCESS  not-accessible
    STATUS      current
    DESCRIPTION
        "Each row entry represents a next-hop for a next-hop  group associated
         with an endpoint path.

         Entries cannot be created and deleted via SNMP SET operations."
    AUGMENTS    { vRtrMplsEndptPathNhgNHEntry }
    ::= { vRtrMplsEndptNHEgrStatsTable 1 }

VRtrMplsEndptNHEgrStatsEntry     ::= SEQUENCE
{
    vRtrMplsEndptEgrStatsAggPkts     Counter64,
    vRtrMplsEndptEgrStatsAggOctets   Counter64
}

vRtrMplsEndptEgrStatsAggPkts     OBJECT-TYPE
    SYNTAX      Counter64
    MAX-ACCESS  read-only
    STATUS      current
    DESCRIPTION
        "The total of number of egress packets for this endpoint path next-hop
         group next-hop."
    ::= { vRtrMplsEndptNHEgrStatsEntry 1 }

vRtrMplsEndptEgrStatsAggOctets   OBJECT-TYPE
    SYNTAX      Counter64
    MAX-ACCESS  read-only
    STATUS      current
    DESCRIPTION
        "The total of number of egress octets for this endpoint path next-hop
         group next-hop"
    ::= { vRtrMplsEndptNHEgrStatsEntry 2 }

vRtrMplsLspPathEgressStatsTable  OBJECT-TYPE
    SYNTAX      SEQUENCE OF VRtrMplsLspPathEgressStatsEntry
    MAX-ACCESS  not-accessible
    STATUS      current
    DESCRIPTION
        "The vRtrMplsLspPathEgressStatsTable has an entry for egress statistics
         associated with an LSP path."
    ::= { tmnxMplsObjs 89 }

vRtrMplsLspPathEgressStatsEntry  OBJECT-TYPE
    SYNTAX      VRtrMplsLspPathEgressStatsEntry
    MAX-ACCESS  not-accessible
    STATUS      current
    DESCRIPTION
        "Each row entry represents a collection of egress statistics for an LSP
         path.

         Entries cannot be created and deleted via SNMP SET operations. Entries
         in this table are created when egress statistics is  enabled for an
         LSP which supports per path egress statistics."
    INDEX       {
        vRtrID,
        vRtrMplsLspIndex,
        mplsTunnelIndex,
        mplsTunnelInstance,
        mplsTunnelIngressLSRId
    }
    ::= { vRtrMplsLspPathEgressStatsTable 1 }

VRtrMplsLspPathEgressStatsEntry  ::= SEQUENCE
{
    vRtrMplsLspPathEgrStatsOperState TmnxOperState,
    vRtrMplsLspEgressStatsAggrPkts   Counter64,
    vRtrMplsLspEgressStatsAggrOctets Counter64
}

vRtrMplsLspPathEgrStatsOperState OBJECT-TYPE
    SYNTAX      TmnxOperState
    MAX-ACCESS  read-only
    STATUS      current
    DESCRIPTION
        "The value of vRtrMplsLspPathEgrStatsOperState indicates the
         operational state of egress statistics for the LSP path."
    ::= { vRtrMplsLspPathEgressStatsEntry 1 }

vRtrMplsLspEgressStatsAggrPkts   OBJECT-TYPE
    SYNTAX      Counter64
    MAX-ACCESS  read-only
    STATUS      current
    DESCRIPTION
        "The value of vRtrMplsLspEgressStatsAggrPkts indicates the total number
         of egress packets for this LSP path"
    ::= { vRtrMplsLspPathEgressStatsEntry 2 }

vRtrMplsLspEgressStatsAggrOctets OBJECT-TYPE
    SYNTAX      Counter64
    MAX-ACCESS  read-only
    STATUS      current
    DESCRIPTION
        "The value of vRtrMplsLspEgressStatsAggrOctets indicates the total
         number of egress octets for this LSP path"
    ::= { vRtrMplsLspPathEgressStatsEntry 3 }

vRtrMplsPathHopTableLastChg      OBJECT-TYPE
    SYNTAX      TimeStamp
    MAX-ACCESS  read-only
    STATUS      current
    DESCRIPTION
        "The value of vRtrMplsPathHopTableLastChg indicates the sysUpTime at
         the time of the last modification of an entry in the
         vRtrMplsPathHopTable."
    ::= { tmnxMplsObjs 90 }

vRtrMplsPathHopTable             OBJECT-TYPE
    SYNTAX      SEQUENCE OF VRtrMplsPathHopEntry
    MAX-ACCESS  not-accessible
    STATUS      current
    DESCRIPTION
        "The vRtrMplsPathHopTable has an entry to indicate the hops, strict or
         loose, for an MPLS tunnel."
    ::= { tmnxMplsObjs 91 }

vRtrMplsPathHopEntry             OBJECT-TYPE
    SYNTAX      VRtrMplsPathHopEntry
    MAX-ACCESS  not-accessible
    STATUS      current
    DESCRIPTION
        "Each row entry represents a hop, strict or loose, for an MPLS tunnel
         configured for a virtual router in the system.

         Entries can be created and deleted via SNMP SET operations."
    INDEX       {
        vRtrID,
        vRtrMplsPathIndex,
        vRtrMplsPathHopIndex
    }
    ::= { vRtrMplsPathHopTable 1 }

VRtrMplsPathHopEntry             ::= SEQUENCE
{
    vRtrMplsPathIndex                Unsigned32,
    vRtrMplsPathHopIndex             Unsigned32,
    vRtrMplsPathHopRowStatus         RowStatus,
    vRtrMplsPathHopLastChange        TimeStamp,
    vRtrMplsPathHopAddrType          InetAddressType,
    vRtrMplsPathHopAddr              InetAddress,
    vRtrMplsPathHopStrictOrLoose     INTEGER,
    vRtrMplsPathHopSidLabel          Unsigned32
}

vRtrMplsPathIndex                OBJECT-TYPE
    SYNTAX      Unsigned32 (1..2147483647)
    MAX-ACCESS  not-accessible
    STATUS      current
    DESCRIPTION
        "The value of vRtrMplsPathIndex indicates the primary index  to
         identify a particular explicit route object."
    ::= { vRtrMplsPathHopEntry 1 }

vRtrMplsPathHopIndex             OBJECT-TYPE
    SYNTAX      Unsigned32 (1..2147483647)
    MAX-ACCESS  not-accessible
    STATUS      current
    DESCRIPTION
        "The value of vRtrMplsPathHopIndex indicates the secondary index to
         identify a particular hop."
    ::= { vRtrMplsPathHopEntry 2 }

vRtrMplsPathHopRowStatus         OBJECT-TYPE
    SYNTAX      RowStatus
    MAX-ACCESS  read-create
    STATUS      current
    DESCRIPTION
        "The row status used for creation, deletion, or control of
         vRtrMplsPathHopTable entries."
    ::= { vRtrMplsPathHopEntry 3 }

vRtrMplsPathHopLastChange        OBJECT-TYPE
    SYNTAX      TimeStamp
    MAX-ACCESS  read-only
    STATUS      current
    DESCRIPTION
        "The sysUpTime when this row was last modified."
    ::= { vRtrMplsPathHopEntry 4 }

vRtrMplsPathHopAddrType          OBJECT-TYPE
    SYNTAX      InetAddressType
    MAX-ACCESS  read-create
    STATUS      current
    DESCRIPTION
        "The value of vRtrMplsPathHopAddrType specifies the type of
         vRtrMplsPathHopAddr."
    DEFVAL      { unknown }
    ::= { vRtrMplsPathHopEntry 5 }

vRtrMplsPathHopAddr              OBJECT-TYPE
    SYNTAX      InetAddress (SIZE (0|4|16))
    MAX-ACCESS  read-create
    STATUS      current
    DESCRIPTION
        "The value of vRtrMplsPathHopAddr specifies the hop address."
    DEFVAL      { ''H }
    ::= { vRtrMplsPathHopEntry 6 }

vRtrMplsPathHopStrictOrLoose     OBJECT-TYPE
    SYNTAX      INTEGER {
        notApplicable (0),
        strict        (1),
        loose         (2)
    }
    MAX-ACCESS  read-create
    STATUS      current
    DESCRIPTION
        "The value of vRtrMplsPathHopStrictOrLoose indicates whether this
         tunnel hop is routed in a strict or loose fashion."
    DEFVAL      { notApplicable }
    ::= { vRtrMplsPathHopEntry 7 }

vRtrMplsPathHopSidLabel          OBJECT-TYPE
    SYNTAX      Unsigned32 (32..1048575 | 4294967295)
    MAX-ACCESS  read-create
    STATUS      current
    DESCRIPTION
        "The value of vRtrMplsPathHopSidLabel indicates the SID for this hop."
    DEFVAL      { 4294967295 }
    ::= { vRtrMplsPathHopEntry 8 }

tmnxMplsConformance              OBJECT IDENTIFIER ::= { tmnxSRConfs 6 }

tmnxMplsCompliances              OBJECT IDENTIFIER ::= { tmnxMplsConformance 1 }

tmnxMplsV3v0Compliance           MODULE-COMPLIANCE
    STATUS      obsolete
    DESCRIPTION
        "The compliance statement for management of extended MPLS on Nokia SROS
         series systems 3.0 Release."
    MODULE
        MANDATORY-GROUPS {
            tmnxMplsGlobalR2r1Group,
            tmnxMplsLspR2r1Group,
            tmnxMplsLspPathGroup,
            tmnxMplsXCGroup,
            tmnxMplsIfGroup,
            tmnxMplsTunnelARHopGroup,
            tmnxMplsTunnelCHopGroup,
            tmnxMplsAdminGroupGroup,
            tmnxMplsNotificationR2r1Group,
            tmnxMplsLabelRangeGroup
        }
    ::= { tmnxMplsCompliances 3 }

tmnxMplsV5v0Compliance           MODULE-COMPLIANCE
    STATUS      obsolete
    DESCRIPTION
        "The compliance statement for management of extended MPLS on Nokia SROS
         series systems 5.0 Release."
    MODULE
        MANDATORY-GROUPS {
            tmnxMplsGlobalV5v0Group,
            tmnxMplsLspV5v0Group,
            tmnxMplsLspPathGroup,
            tmnxMplsXCGroup,
            tmnxMplsIfGroup,
            tmnxMplsTunnelARHopGroup,
            tmnxMplsTunnelCHopGroup,
            tmnxMplsAdminGroupGroup,
            tmnxMplsNotificationR2r1Group,
            tmnxMplsLabelRangeGroup
        }
    ::= { tmnxMplsCompliances 4 }

tmnxMplsV6v0Compliance           MODULE-COMPLIANCE
    STATUS      obsolete
    DESCRIPTION
        "The compliance statement for management of extended MPLS on Nokia SROS
         series systems 6.0 Release."
    MODULE
        MANDATORY-GROUPS {
            tmnxMplsGlobalV6v0Group,
            tmnxMplsLspV5v0Group,
            tmnxMplsLspPathGroup,
            tmnxMplsXCGroup,
            tmnxMplsIfGroup,
            tmnxMplsTunnelARHopGroup,
            tmnxMplsTunnelCHopGroup,
            tmnxMplsAdminGroupGroup,
            tmnxMplsNotificationR2r1Group,
            tmnxMplsLabelRangeGroup,
            tmnxMplsSrlgV6v0Group,
            tmnxMplsLspPathV6v0Group,
            tmnxMplsIfV6v0Group,
            tmnxMplsLspV6v0Group
        }
    ::= { tmnxMplsCompliances 5 }

tmnxMplsV6v1Compliance           MODULE-COMPLIANCE
    STATUS      obsolete
    DESCRIPTION
        "The compliance statement for management of extended MPLS on Nokia SROS
         series systems 6.1 Release."
    MODULE
        MANDATORY-GROUPS {
            tmnxMplsGlobalV6v0Group,
            tmnxMplsLspV5v0Group,
            tmnxMplsLspPathV6v0Group,
            tmnxMplsXCGroup,
            tmnxMplsIfGroup,
            tmnxMplsTunnelARHopGroup,
            tmnxMplsTunnelCHopGroup,
            tmnxMplsAdminGroupGroup,
            tmnxMplsNotificationR2r1Group,
            tmnxMplsLabelRangeGroup,
            tmnxMplsSrlgV6v0Group,
            tmnxMplsLspPathV6v1Group,
            tmnxMplsIfV6v0Group,
            tmnxMplsLspV6v0Group
        }
    ::= { tmnxMplsCompliances 6 }

tmnxMplsV7v0Compliance           MODULE-COMPLIANCE
    STATUS      obsolete
    DESCRIPTION
        "The compliance statement for management of extended MPLS on Nokia SROS
         series systems 6.1 Release."
    MODULE
        MANDATORY-GROUPS {
            tmnxMplsGlobalV6v0Group,
            tmnxMplsLspV5v0Group,
            tmnxMplsLspPathV6v0Group,
            tmnxMplsXCGroup,
            tmnxMplsIfGroup,
            tmnxMplsTunnelARHopGroup,
            tmnxMplsTunnelCHopGroup,
            tmnxMplsAdminGroupGroup,
            tmnxMplsNotificationR2r1Group,
            tmnxMplsLabelRangeGroup,
            tmnxMplsSrlgV6v0Group,
            tmnxMplsLspPathV6v1Group,
            tmnxMplsIfV6v0Group,
            tmnxMplsLspV6v0Group,
            tmnxMplsLspV7v0Group,
            tmnxMplsGlobalV7v0Group,
            tmnxMplsP2mpInstanceGroup,
            tmnxMplsP2mpS2lGroup,
            tmnxMplsNotificationV7v0Group,
            tmnxMplsLspPathV7v0Group,
            tmnxMplsSrlgV7v0Group,
            tmnxMplsLspStatsV7v0Group
        }
    ::= { tmnxMplsCompliances 7 }

tmnxMplsV8v0Compliance           MODULE-COMPLIANCE
    STATUS      obsolete
    DESCRIPTION
        "The compliance statement for management of extended MPLS on Nokia SROS
         series systems 8.0 Release."
    MODULE
        MANDATORY-GROUPS {
            tmnxMplsGlobalV6v0Group,
            tmnxMplsLspV5v0Group,
            tmnxMplsLspPathV6v0Group,
            tmnxMplsXCGroup,
            tmnxMplsIfGroup,
            tmnxMplsTunnelARHopGroup,
            tmnxMplsTunnelCHopGroup,
            tmnxMplsAdminGroupGroup,
            tmnxMplsNotificationR2r1Group,
            tmnxMplsLabelRangeGroup,
            tmnxMplsSrlgV6v0Group,
            tmnxMplsLspPathV6v1Group,
            tmnxMplsIfV6v0Group,
            tmnxMplsLspV6v0Group,
            tmnxMplsLspV7v0Group,
            tmnxMplsGlobalV7v0Group,
            tmnxMplsP2mpInstanceGroup,
            tmnxMplsP2mpS2lGroup,
            tmnxMplsNotificationV7v0Group,
            tmnxMplsLspPathV7v0Group,
            tmnxMplsSrlgV7v0Group,
            tmnxMplsLspStatsV7v0Group,
            tmnxMplsLspV8v0Group,
            tmnxMplsLspPathV8v0Group,
            tmnxMplsNotifyObjsV8v0Group,
            tmnxMplsNotificationV8v0Group,
            tmnxMplsGlobalV8v0Group,
            tmnxMplsLspAutoBWV8v0Group,
            tmnxMplsLspTemplateV8v0Group
        }
    ::= { tmnxMplsCompliances 8 }

tmnxMplsV9v0Compliance           MODULE-COMPLIANCE
    STATUS      obsolete
    DESCRIPTION
        "The compliance statement for management of extended MPLS on Nokia SROS
         series systems 9.0 Release."
    MODULE
        MANDATORY-GROUPS {
            tmnxMplsGlobalV6v0Group,
            tmnxMplsLspV5v0Group,
            tmnxMplsLspPathV6v0Group,
            tmnxMplsXCGroup,
            tmnxMplsIfGroup,
            tmnxMplsTunnelARHopGroup,
            tmnxMplsTunnelCHopGroup,
            tmnxMplsAdminGroupGroup,
            tmnxMplsNotificationR2r1Group,
            tmnxMplsLabelRangeGroup,
            tmnxMplsSrlgV6v0Group,
            tmnxMplsLspPathV6v1Group,
            tmnxMplsIfV6v0Group,
            tmnxMplsLspV6v0Group,
            tmnxMplsLspV7v0Group,
            tmnxMplsGlobalV7v0Group,
            tmnxMplsP2mpInstanceGroup,
            tmnxMplsP2mpS2lGroup,
            tmnxMplsNotificationV7v0Group,
            tmnxMplsLspPathV7v0Group,
            tmnxMplsSrlgV7v0Group,
            tmnxMplsLspStatsV7v0Group,
            tmnxMplsLspV8v0Group,
            tmnxMplsLspPathV8v0Group,
            tmnxMplsNotifyObjsV8v0Group,
            tmnxMplsNotificationV8v0Group,
            tmnxMplsGlobalV8v0Group,
            tmnxMplsLspAutoBWV8v0Group,
            tmnxMplsLspTemplateV8v0Group,
            tmnxMplsGlobalV9v0Group,
            tmnxMplsLspV9v0Group,
            tmnxMplsLspV9v0R4Group,
            tmnxMplsNotifV9v0R4Group,
            tmnxMplsLspPathV9v0R4Group
        }
    ::= { tmnxMplsCompliances 9 }

tmnxMplsV10v0Compliance          MODULE-COMPLIANCE
    STATUS      obsolete
    DESCRIPTION
        "The compliance statement for management of extended MPLS on Nokia SROS
         series systems 10.0 Release."
    MODULE
        MANDATORY-GROUPS {
            tmnxMplsGlobalV6v0Group,
            tmnxMplsLspV5v0Group,
            tmnxMplsLspPathV6v0Group,
            tmnxMplsXCGroup,
            tmnxMplsIfGroup,
            tmnxMplsTunnelARHopGroup,
            tmnxMplsTunnelCHopGroup,
            tmnxMplsAdminGroupGroup,
            tmnxMplsNotificationR2r1Group,
            tmnxMplsLabelRangeGroup,
            tmnxMplsSrlgV6v0Group,
            tmnxMplsLspPathV6v1Group,
            tmnxMplsIfV6v0Group,
            tmnxMplsLspV6v0Group,
            tmnxMplsLspV7v0Group,
            tmnxMplsGlobalV7v0Group,
            tmnxMplsP2mpInstanceGroup,
            tmnxMplsP2mpS2lGroup,
            tmnxMplsNotificationV7v0Group,
            tmnxMplsLspPathV7v0Group,
            tmnxMplsSrlgV7v0Group,
            tmnxMplsLspStatsV7v0Group,
            tmnxMplsLspV8v0Group,
            tmnxMplsLspPathV8v0Group,
            tmnxMplsNotifyObjsV8v0Group,
            tmnxMplsNotificationV8v0Group,
            tmnxMplsGlobalV8v0Group,
            tmnxMplsLspAutoBWV8v0Group,
            tmnxMplsLspTemplateV8v0Group,
            tmnxMplsGlobalV9v0Group,
            tmnxMplsLspV9v0Group,
            tmnxMplsLspV9v0R4Group,
            tmnxMplsNotifV9v0R4Group,
            tmnxMplsLspPathV9v0R4Group,
            tmnxMplsGlobalV10v0Group
        }
    ::= { tmnxMplsCompliances 10 }

tmnxMplsV11v0Compliance          MODULE-COMPLIANCE
    STATUS      obsolete
    DESCRIPTION
        "The compliance statement for management of extended MPLS on Nokia SROS
         series systems 11.0 Release."
    MODULE
        MANDATORY-GROUPS {
            tmnxMplsLspPathV6v0Group,
            tmnxMplsXCGroup,
            tmnxMplsIfGroup,
            tmnxMplsTunnelARHopGroup,
            tmnxMplsTunnelCHopGroup,
            tmnxMplsAdminGroupGroup,
            tmnxMplsNotificationR2r1Group,
            tmnxMplsLabelRangeGroup,
            tmnxMplsSrlgV6v0Group,
            tmnxMplsIfV6v0Group,
            tmnxMplsLspV6v0Group,
            tmnxMplsLspV7v0Group,
            tmnxMplsGlobalV7v0Group,
            tmnxMplsP2mpInstanceGroup,
            tmnxMplsP2mpS2lGroup,
            tmnxMplsNotificationV7v0Group,
            tmnxMplsLspPathV7v0Group,
            tmnxMplsSrlgV7v0Group,
            tmnxMplsLspStatsV7v0Group,
            tmnxMplsLspV8v0Group,
            tmnxMplsLspPathV8v0Group,
            tmnxMplsNotifyObjsV8v0Group,
            tmnxMplsNotificationV8v0Group,
            tmnxMplsGlobalV8v0Group,
            tmnxMplsLspAutoBWV8v0Group,
            tmnxMplsLspTemplateV8v0Group,
            tmnxMplsGlobalV9v0Group,
            tmnxMplsLspV9v0R4Group,
            tmnxMplsNotifV9v0R4Group,
            tmnxMplsLspPathV9v0R4Group,
            tmnxMplsTpGroup,
            tmnxMplsNotifyObjsV10v0Group,
            tmnxMplsNotifyV10v0Group,
            tmnxMplsFRAdminGroup,
            tmnxMplsGlobalV11v0Group,
            tmnxMplsLspTemplateGroup,
            tmnxMplsNotifyV11v0Group,
            tmnxMplsLspAutoBWFcWtGroup,
            tmnxMplsGlobalV11v0R4Group,
            tmnxMplsNotifyObjsIgpOverload,
            tmnxMplsIgpOverloadNotify
        }
    ::= { tmnxMplsCompliances 11 }

tmnxMplsV12v0Compliance          MODULE-COMPLIANCE
    STATUS      obsolete
    DESCRIPTION
        "The compliance statement for management of extended MPLS on Nokia SROS
         series systems 12.0 Release."
    MODULE
        MANDATORY-GROUPS {
            tmnxMplsLspPathV6v0Group,
            tmnxMplsXCGroup,
            tmnxMplsIfGroup,
            tmnxMplsTunnelARHopGroup,
            tmnxMplsTunnelCHopGroup,
            tmnxMplsAdminGroupGroup,
            tmnxMplsNotificationR2r1Group,
            tmnxMplsLabelRangeGroup,
            tmnxMplsSrlgV6v0Group,
            tmnxMplsIfV6v0Group,
            tmnxMplsLspV6v0Group,
            tmnxMplsLspV7v0Group,
            tmnxMplsGlobalV7v0Group,
            tmnxMplsP2mpInstanceGroup,
            tmnxMplsP2mpS2lGroup,
            tmnxMplsNotificationV7v0Group,
            tmnxMplsLspPathV7v0Group,
            tmnxMplsSrlgV7v0Group,
            tmnxMplsLspStatsV7v0Group,
            tmnxMplsLspV8v0Group,
            tmnxMplsLspPathV8v0Group,
            tmnxMplsNotifyObjsV8v0Group,
            tmnxMplsNotificationV8v0Group,
            tmnxMplsGlobalV8v0Group,
            tmnxMplsLspAutoBWV8v0Group,
            tmnxMplsLspTemplateV8v0Group,
            tmnxMplsGlobalV9v0Group,
            tmnxMplsLspV9v0R4Group,
            tmnxMplsNotifV9v0R4Group,
            tmnxMplsLspPathV9v0R4Group,
            tmnxMplsTpGroup,
            tmnxMplsNotifyObjsV10v0Group,
            tmnxMplsNotifyV10v0Group,
            tmnxMplsFRAdminGroup,
            tmnxMplsLspTemplateGroup,
            tmnxMplsLspAutoBWFcWtGroup,
            tmnxMplsGlobalV11v0R4Group,
            tmnxMplsNotifyObjsIgpOverload,
            tmnxMplsIgpOverloadNotify,
            tmnxMplsLspTempInStatsGroup,
            tmnxMplsAutoBwUnderflowGroup,
            tmnxMplsBgpLabelRetentionGroup,
            tmnxMplsGlobalV12v0Group,
            tmnxMplsBypassOptGroup,
            tmnxMplsGlobalV12v0Group,
            tmnxMplsLSPPathV12v0Group,
            tmnxMplsGenV12v0Group,
            tmnxMplsLSPV12v0Group
        }
    ::= { tmnxMplsCompliances 12 }

tmnxMplsV13v0Compliance          MODULE-COMPLIANCE
    STATUS      obsolete
    DESCRIPTION
        "The compliance statement for management of extended MPLS on Nokia SROS
         series systems 12.0 Release."
    MODULE
        MANDATORY-GROUPS {
            tmnxMplsLspPathV6v0Group,
            tmnxMplsXCGroup,
            tmnxMplsIfGroup,
            tmnxMplsTunnelARHopGroup,
            tmnxMplsTunnelCHopGroup,
            tmnxMplsAdminGroupGroup,
            tmnxMplsNotificationR2r1Group,
            tmnxMplsLabelRangeGroup,
            tmnxMplsSrlgV6v0Group,
            tmnxMplsIfV6v0Group,
            tmnxMplsLspV6v0Group,
            tmnxMplsLspV7v0Group,
            tmnxMplsGlobalV7v0Group,
            tmnxMplsP2mpInstanceGroup,
            tmnxMplsP2mpS2lGroup,
            tmnxMplsNotificationV7v0Group,
            tmnxMplsLspPathV7v0Group,
            tmnxMplsSrlgV7v0Group,
            tmnxMplsLspStatsV7v0Group,
            tmnxMplsLspV8v0Group,
            tmnxMplsLspPathV8v0Group,
            tmnxMplsNotifyObjsV8v0Group,
            tmnxMplsNotificationV8v0Group,
            tmnxMplsGlobalV8v0Group,
            tmnxMplsLspAutoBWV8v0Group,
            tmnxMplsLspTemplateV8v0Group,
            tmnxMplsGlobalV9v0Group,
            tmnxMplsLspV9v0R4Group,
            tmnxMplsNotifV9v0R4Group,
            tmnxMplsLspPathV9v0R4Group,
            tmnxMplsTpGroup,
            tmnxMplsNotifyObjsV10v0Group,
            tmnxMplsNotifyV10v0Group,
            tmnxMplsFRAdminGroup,
            tmnxMplsLspTemplateGroup,
            tmnxMplsLspAutoBWFcWtGroup,
            tmnxMplsGlobalV11v0R4Group,
            tmnxMplsNotifyObjsIgpOverload,
            tmnxMplsIgpOverloadNotify,
            tmnxMplsLspTempInStatsGroup,
            tmnxMplsAutoBwUnderflowGroup,
            tmnxMplsBgpLabelRetentionGroup,
            tmnxMplsBypassOptGroup,
            tmnxMplsLSPPathV12v0Group,
            tmnxMplsGenV12v0Group,
            tmnxMplsLSPV12v0Group,
            tmnxMplsLoadBalanceWtV13v0Group,
            tmnxMplsLabelSegRouteV13v0Group,
            tmnxMplsLabelStaticRgeV13v0Group,
            tmnxMplsGlobalV13v0Group,
            tmnxMplsClassBasedFwdV13v0Group,
            tmnxMplsBfdOnLspV13v0Group
        }
    ::= { tmnxMplsCompliances 13 }

tmnxMplsV14v0Compliance          MODULE-COMPLIANCE
    STATUS      obsolete
    DESCRIPTION
        "The compliance statement for management of extended MPLS on Nokia SROS
         series systems 14.0 Release."
    MODULE
        MANDATORY-GROUPS {
            tmnxMplsLspPathV6v0Group,
            tmnxMplsXCGroup,
            tmnxMplsIfGroup,
            tmnxMplsTunnelARHopGroup,
            tmnxMplsTunnelCHopGroup,
            tmnxMplsNotificationR2r1Group,
            tmnxMplsLabelRangeGroup,
            tmnxMplsIfV6v0Group,
            tmnxMplsLspV6v0Group,
            tmnxMplsLspV7v0Group,
            tmnxMplsGlobalV7v0Group,
            tmnxMplsP2mpInstanceGroup,
            tmnxMplsP2mpS2lGroup,
            tmnxMplsNotificationV7v0Group,
            tmnxMplsLspPathV7v0Group,
            tmnxMplsSrlgV7v0Group,
            tmnxMplsLspStatsV7v0Group,
            tmnxMplsLspV8v0Group,
            tmnxMplsLspPathV8v0Group,
            tmnxMplsNotifyObjsV8v0Group,
            tmnxMplsNotificationV8v0Group,
            tmnxMplsGlobalV8v0Group,
            tmnxMplsLspAutoBWV8v0Group,
            tmnxMplsLspTemplateV8v0Group,
            tmnxMplsGlobalV9v0Group,
            tmnxMplsLspV9v0R4Group,
            tmnxMplsNotifV9v0R4Group,
            tmnxMplsLspPathV9v0R4Group,
            tmnxMplsTpGroup,
            tmnxMplsNotifyObjsV10v0Group,
            tmnxMplsNotifyV10v0Group,
            tmnxMplsFRAdminGroup,
            tmnxMplsLspTemplateGroup,
            tmnxMplsLspAutoBWFcWtGroup,
            tmnxMplsGlobalV11v0R4Group,
            tmnxMplsNotifyObjsIgpOverload,
            tmnxMplsIgpOverloadNotify,
            tmnxMplsLspTempInStatsGroup,
            tmnxMplsAutoBwUnderflowGroup,
            tmnxMplsBgpLabelRetentionGroup,
            tmnxMplsBypassOptGroup,
            tmnxMplsLSPPathV12v0Group,
            tmnxMplsGenV12v0Group,
            tmnxMplsLSPV12v0Group,
            tmnxMplsLoadBalanceWtV13v0Group,
            tmnxMplsLabelSegRouteV13v0Group,
            tmnxMplsLabelStaticRgeV13v0Group,
            tmnxMplsGlobalV13v0Group,
            tmnxMplsClassBasedFwdV13v0Group,
            tmnxMplsIfSrlgV14v0Group,
            tmnxMplsBfdOnLspV13v0Group,
            tmnxMplsSegRouting14v0Group,
            tmnxMplsEntropyLabel14v0Group,
            tmnxMplsLspTemplEL14v4Group,
            tmnxMplsSRLfaOvrhd14v4Group
        }
    ::= { tmnxMplsCompliances 14 }

tmnxMplsV15v0Compliance          MODULE-COMPLIANCE
    STATUS      obsolete
    DESCRIPTION
        "The compliance statement for management of extended MPLS on Nokia SROS
         series systems 15.0 Release."
    MODULE
        MANDATORY-GROUPS {
            tmnxMplsLspPathV6v0Group,
            tmnxMplsXCGroup,
            tmnxMplsIfGroup,
            tmnxMplsTunnelARHopGroup,
            tmnxMplsTunnelCHopGroup,
            tmnxMplsNotificationR2r1Group,
            tmnxMplsLabelRangeGroup,
            tmnxMplsIfV6v0Group,
            tmnxMplsLspV6v0Group,
            tmnxMplsLspV7v0Group,
            tmnxMplsGlobalV7v0Group,
            tmnxMplsP2mpInstanceGroup,
            tmnxMplsP2mpS2lGroup,
            tmnxMplsNotificationV7v0Group,
            tmnxMplsLspPathV7v0Group,
            tmnxMplsSrlgV7v0Group,
            tmnxMplsLspStatsV7v0Group,
            tmnxMplsLspV8v0Group,
            tmnxMplsLspPathV8v0Group,
            tmnxMplsNotifyObjsV8v0Group,
            tmnxMplsNotificationV8v0Group,
            tmnxMplsGlobalV8v0Group,
            tmnxMplsLspAutoBWV8v0Group,
            tmnxMplsLspTemplateV8v0Group,
            tmnxMplsGlobalV9v0Group,
            tmnxMplsLspV9v0R4Group,
            tmnxMplsNotifV9v0R4Group,
            tmnxMplsLspPathV9v0R4Group,
            tmnxMplsTpGroup,
            tmnxMplsNotifyObjsV10v0Group,
            tmnxMplsNotifyV10v0Group,
            tmnxMplsFRAdminGroup,
            tmnxMplsLspTemplateGroup,
            tmnxMplsLspAutoBWFcWtGroup,
            tmnxMplsGlobalV11v0R4Group,
            tmnxMplsNotifyObjsIgpOverload,
            tmnxMplsIgpOverloadNotify,
            tmnxMplsLspTempInStatsGroup,
            tmnxMplsAutoBwUnderflowGroup,
            tmnxMplsBgpLabelRetentionGroup,
            tmnxMplsBypassOptGroup,
            tmnxMplsLSPPathV12v0Group,
            tmnxMplsGenV12v0Group,
            tmnxMplsLoadBalanceWtV13v0Group,
            tmnxMplsLabelSegRouteV13v0Group,
            tmnxMplsLabelStaticRgeV13v0Group,
            tmnxMplsGlobalV13v0Group,
            tmnxMplsClassBasedFwdV13v0Group,
            tmnxMplsIfSrlgV14v0Group,
            tmnxMplsBfdOnLspV13v0Group,
            tmnxMplsSegRouting14v0Group,
            tmnxMplsEntropyLabel14v0Group,
            tmnxMplsLspTemplEL14v4Group,
            tmnxMplsSRLfaOvrhd14v4Group,
            tmnxMplsLspTempPceReportGroup,
            tmnxMplsLspTempSrLbl15v0Group,
            tmnxMplsBfdFailureActionGroup,
            tmnxMplsClassFwdPlcy15v0Group,
            tmnxMplsP2PSrTe15v0Group,
            tmnxMplsLspStatsGroup,
            tmnxMplsTunnelARHopSIDGroup,
            tmnxMplsLSPV15v0Group,
            tmnxMplsEntropyLabelSrteGroup
        }
    ::= { tmnxMplsCompliances 15 }

tmnxMplsV16v0Compliance          MODULE-COMPLIANCE
    STATUS      current
    DESCRIPTION
        "The compliance statement for management of extended MPLS on Nokia SROS
         series systems 16.0 Release."
    MODULE
        MANDATORY-GROUPS {
            tmnxMplsReservedLblBlkGroup,
            tmnxMplsIfAltStatsGroup,
            vRtrMplsLspAdminTagGroup,
            vRtrMplsFwdPlcyV16v0Group,
            vRtrMplsFwdPlcyNhgNHPushLblGroup,
            vRtrMplsPceInitSrteGroup,
            vRtrMplsAutoBwUseLastAdjBWGroup
        }
    ::= { tmnxMplsCompliances 16 }

tmnxMplsV19v0Compliance          MODULE-COMPLIANCE
    STATUS      current
    DESCRIPTION
        "The compliance statement for management of extended MPLS on Nokia SROS
         series systems 19.0 Release."
    MODULE
        MANDATORY-GROUPS {
            tmnxMplsGeneralSrTeLspGroup,
            tmnxMplsFwdPlcyEgressStatsGroup,
            tmnxMplsSrteSBfdGroup,
            tmnxMplsGenMaxBypassPlrGroup,
            tmnxMplsLspPathEgressStatsGroup,
            tmnxMplsLspSelfPingGroup,
            tmnxMplsLspNgAddrGroup,
            tmnxMplsLspSrTeIpv6Group,
            tmnxMplsPathHopGroup,
            tmnxMplsLspSelfPingOperGroup,
            tmnxMplsNotificationIPv6Group
        }
    ::= { tmnxMplsCompliances 17 }

tmnxMplsV20v0Compliance          MODULE-COMPLIANCE
    STATUS      current
    DESCRIPTION
        "The compliance statement for management of extended MPLS on Nokia SROS
         series systems 20.0 Release."
    MODULE
        MANDATORY-GROUPS {
            tmnxMplsLspPathV6v0Group,
            tmnxMplsXCGroup,
            tmnxMplsIfGroup,
            tmnxMplsTunnelCHopGroup,
            tmnxMplsNotificationR2r1Group,
            tmnxMplsLabelRangeGroup,
            tmnxMplsIfV6v0Group,
            tmnxMplsLspV7v0Group,
            tmnxMplsGlobalV7v0Group,
            tmnxMplsP2mpInstanceGroup,
            tmnxMplsP2mpS2lGroup,
            tmnxMplsNotificationV7v0Group,
            tmnxMplsLspPathV7v0Group,
            tmnxMplsSrlgV7v0Group,
            tmnxMplsLspStatsV7v0Group,
            tmnxMplsLspV8v0Group,
            tmnxMplsLspPathV8v0Group,
            tmnxMplsNotifyObjsV8v0Group,
            tmnxMplsNotificationV8v0Group,
            tmnxMplsGlobalV8v0Group,
            tmnxMplsLspAutoBWV8v0Group,
            tmnxMplsGlobalV9v0Group,
            tmnxMplsLspV9v0R4Group,
            tmnxMplsNotifV9v0R4Group,
            tmnxMplsLspPathV9v0R4Group,
            tmnxMplsTpGroup,
            tmnxMplsNotifyObjsV10v0Group,
            tmnxMplsNotifyV10v0Group,
            tmnxMplsFRAdminGroup,
            tmnxMplsLspTemplateGroup,
            tmnxMplsLspAutoBWFcWtGroup,
            tmnxMplsGlobalV11v0R4Group,
            tmnxMplsNotifyObjsIgpOverload,
            tmnxMplsIgpOverloadNotify,
            tmnxMplsLspTempInStatsGroup,
            tmnxMplsAutoBwUnderflowGroup,
            tmnxMplsBgpLabelRetentionGroup,
            tmnxMplsBypassOptGroup,
            tmnxMplsGenV12v0Group,
            tmnxMplsLoadBalanceWtV13v0Group,
            tmnxMplsLabelSegRouteV13v0Group,
            tmnxMplsLabelStaticRgeV13v0Group,
            tmnxMplsGlobalV13v0Group,
            tmnxMplsIfSrlgV14v0Group,
            tmnxMplsBfdOnLspV13v0Group,
            tmnxMplsEntropyLabel14v0Group,
            tmnxMplsLspTemplEL14v4Group,
            tmnxMplsSRLfaOvrhd14v4Group,
            tmnxMplsLspTempPceReportGroup,
            tmnxMplsLspTempSrLbl15v0Group,
            tmnxMplsBfdFailureActionGroup,
            tmnxMplsClassFwdPlcy15v0Group,
            tmnxMplsP2PSrTe15v0Group,
            tmnxMplsLspStatsGroup,
            tmnxMplsTunnelARHopSIDGroup,
            tmnxMplsEntropyLabelSrteGroup,
            tmnxMplsNotifyObjsLspResource,
            tmnxMplsNotifyV20v0Group,
            tmnxMplsV20v0Group,
            tmnxMplsTunnelARHopIdTypeGroup
        }
    ::= { tmnxMplsCompliances 18 }

tmnxMplsGroups                   OBJECT IDENTIFIER ::= { tmnxMplsConformance 2 }

tmnxMplsLspPathGroup             OBJECT-GROUP
    OBJECTS     {
        vRtrMplsLspPathTableSpinlock,
        vRtrMplsLspPathRowStatus,
        vRtrMplsLspPathLastChange,
        vRtrMplsLspPathType,
        vRtrMplsLspPathCos,
        vRtrMplsLspPathProperties,
        vRtrMplsLspPathBandwidth,
        vRtrMplsLspPathBwProtect,
        vRtrMplsLspPathState,
        vRtrMplsLspPathPreference,
        vRtrMplsLspPathCosSource,
        vRtrMplsLspPathClassOfService,
        vRtrMplsLspPathSetupPriority,
        vRtrMplsLspPathHoldPriority,
        vRtrMplsLspPathRecord,
        vRtrMplsLspPathHopLimit,
        vRtrMplsLspPathSharing,
        vRtrMplsLspPathAdminState,
        vRtrMplsLspPathOperState,
        vRtrMplsLspPathInheritance,
        vRtrMplsLspPathLspId,
        vRtrMplsLspPathRetryTimeRemaining,
        vRtrMplsLspPathTunnelARHopListIndex,
        vRtrMplsLspPathNegotiatedMTU,
        vRtrMplsLspPathFailCode,
        vRtrMplsLspPathFailNodeAddr,
        vRtrMplsLspPathAdminGroupInclude,
        vRtrMplsLspPathAdminGroupExclude,
        vRtrMplsLspPathAdaptive,
        vRtrMplsLspPathOptimizeTimer,
        vRtrMplsLspPathNextOptimize,
        vRtrMplsLspPathOperBandwidth,
        vRtrMplsLspPathMBBState,
        vRtrMplsLspPathResignal,
        vRtrMplsLspPathTunnelCRHopListIndex,
        vRtrMplsLspPathOperMTU,
        vRtrMplsLspPathRecordLabel,
        vRtrMplsLspPathTimeUp,
        vRtrMplsLspPathTimeDown,
        vRtrMplsLspPathRetryAttempts,
        vRtrMplsLspPathTransitionCount,
        vRtrMplsLspPathCspfQueries
    }
    STATUS      obsolete
    DESCRIPTION
        "The group of objects supporting management of extended MPLS LSP to
         path mapping on Nokia SROS series systems."
    ::= { tmnxMplsGroups 3 }

tmnxMplsXCGroup                  OBJECT-GROUP
    OBJECTS     {
        vRtrMplsXCIndex,
        vRtrMplsInSegmentIfIndex,
        vRtrMplsInSegmentLabel,
        vRtrMplsOutSegmentIndex,
        vRtrMplsERHopTunnelIndex,
        vRtrMplsARHopTunnelIndex,
        vRtrMplsRsvpSessionIndex,
        vRtrMplsXCFailCode,
        vRtrMplsXCCHopTableIndex
    }
    STATUS      current
    DESCRIPTION
        "The group of objects supporting management of extended MPLS LSP to
         cross-connection mapping on Nokia SROS series systems."
    ::= { tmnxMplsGroups 4 }

tmnxMplsIfGroup                  OBJECT-GROUP
    OBJECTS     {
        vRtrMplsIfAdminState,
        vRtrMplsIfOperState,
        vRtrMplsIfAdminGroup,
        vRtrMplsIfTxPktCount,
        vRtrMplsIfRxPktCount,
        vRtrMplsIfTxOctetCount,
        vRtrMplsIfRxOctetCount
    }
    STATUS      current
    DESCRIPTION
        "The group of objects supporting management of extended MPLS interfaces
         on Nokia SROS series systems."
    ::= { tmnxMplsGroups 5 }

tmnxMplsTunnelARHopGroup         OBJECT-GROUP
    OBJECTS     {
        vRtrMplsTunnelARHopProtection,
        vRtrMplsTunnelARHopRecordLabel,
        vRtrMplsTunnelARHopRouterId
    }
    STATUS      obsolete
    DESCRIPTION
        "The group of objects supporting management of extended MPLS Tunnel AR
         hops on Nokia SROS series systems."
    ::= { tmnxMplsGroups 6 }

tmnxMplsTunnelCHopGroup          OBJECT-GROUP
    OBJECTS     {
        vRtrMplsTunnelCHopAddrType,
        vRtrMplsTunnelCHopIpv4Addr,
        vRtrMplsTunnelCHopIpv4PrefixLen,
        vRtrMplsTunnelCHopIpv6Addr,
        vRtrMplsTunnelCHopIpv6PrefixLen,
        vRtrMplsTunnelCHopAsNumber,
        vRtrMplsTunnelCHopLspId,
        vRtrMplsTunnelCHopStrictOrLoose
    }
    STATUS      current
    DESCRIPTION
        "The group of objects supporting management of extended MPLS CSPF
         Tunnel hops on Nokia SROS series systems."
    ::= { tmnxMplsGroups 7 }

tmnxMplsAdminGroupGroup          OBJECT-GROUP
    OBJECTS     {
        vRtrMplsAdminGroupRowStatus,
        vRtrMplsAdminGroupValue
    }
    STATUS      obsolete
    DESCRIPTION
        "The group of objects supporting management of extended MPLS
         administrative groups on Nokia SROS series systems."
    ::= { tmnxMplsGroups 8 }

tmnxMplsFSGroupGroup             OBJECT-GROUP
    OBJECTS     {
        vRtrMplsFSGroupRowStatus,
        vRtrMplsFSGroupCost,
        vRtrMplsFSGroupParamsRowStatus
    }
    STATUS      obsolete
    DESCRIPTION
        "The group of objects supporting management of extended MPLS fate
         sharing groups on Nokia SROS series systems."
    ::= { tmnxMplsGroups 9 }

tmnxMplsNotifyObjsGroup          OBJECT-GROUP
    OBJECTS     {
        vRtrMplsLspNotificationReasonCode,
        vRtrMplsLspPathNotificationReasonCode,
        vRtrMplsNotifyRow,
        vRtrMplsLspIndex
    }
    STATUS      current
    DESCRIPTION
        "The group of objects supporting extended MPLS notifications on Nokia
         SROS series systems."
    ::= { tmnxMplsGroups 10 }

tmnxMplsGlobalR2r1Group          OBJECT-GROUP
    OBJECTS     {
        vRtrMplsGeneralLastChange,
        vRtrMplsGeneralAdminState,
        vRtrMplsGeneralOperState,
        vRtrMplsGeneralPropagateTtl,
        vRtrMplsGeneralTE,
        vRtrMplsGeneralNewLspIndex,
        vRtrMplsGeneralOptimizeTimer,
        vRtrMplsGeneralFRObject,
        vRtrMplsGeneralResignalTimer,
        vRtrMplsGeneralStaticLspOriginate,
        vRtrMplsGeneralStaticLspTransit,
        vRtrMplsGeneralStaticLspTerminate,
        vRtrMplsGeneralDynamicLspOriginate,
        vRtrMplsGeneralDynamicLspTransit,
        vRtrMplsGeneralDynamicLspTerminate,
        vRtrMplsGeneralDetourLspOriginate,
        vRtrMplsGeneralDetourLspTransit,
        vRtrMplsGeneralDetourLspTerminate
    }
    STATUS      obsolete
    DESCRIPTION
        "The group of objects supporting general management of extended MPLS on
         Nokia SROS series systems 2.1 Release."
    ::= { tmnxMplsGroups 12 }

tmnxMplsLspR2r1Group             OBJECT-GROUP
    OBJECTS     {
        vRtrMplsLspRowStatus,
        vRtrMplsLspLastChange,
        vRtrMplsLspName,
        vRtrMplsLspAdminState,
        vRtrMplsLspOperState,
        vRtrMplsLspFromAddr,
        vRtrMplsLspToAddr,
        vRtrMplsLspType,
        vRtrMplsLspOutSegIndx,
        vRtrMplsLspRetryTimer,
        vRtrMplsLspRetryLimit,
        vRtrMplsLspMetric,
        vRtrMplsLspDecrementTtl,
        vRtrMplsLspCspf,
        vRtrMplsLspFastReroute,
        vRtrMplsLspFRHopLimit,
        vRtrMplsLspFRBandwidth,
        vRtrMplsLspClassOfService,
        vRtrMplsLspSetupPriority,
        vRtrMplsLspHoldPriority,
        vRtrMplsLspRecord,
        vRtrMplsLspPreference,
        vRtrMplsLspBandwidth,
        vRtrMplsLspBwProtect,
        vRtrMplsLspHopLimit,
        vRtrMplsLspNegotiatedMTU,
        vRtrMplsLspRsvpResvStyle,
        vRtrMplsLspRsvpAdspec,
        vRtrMplsLspFRMethod,
        vRtrMplsLspFRNodeProtect,
        vRtrMplsLspAdminGroupInclude,
        vRtrMplsLspAdminGroupExclude,
        vRtrMplsLspAdaptive,
        vRtrMplsLspInheritance,
        vRtrMplsLspOptimizeTimer,
        vRtrMplsLspOperFastReroute,
        vRtrMplsLspFRObject,
        vRtrMplsLspOctets,
        vRtrMplsLspPackets,
        vRtrMplsLspAge,
        vRtrMplsLspTimeUp,
        vRtrMplsLspTimeDown,
        vRtrMplsLspPrimaryTimeUp,
        vRtrMplsLspTransitions,
        vRtrMplsLspLastTransition,
        vRtrMplsLspPathChanges,
        vRtrMplsLspLastPathChange,
        vRtrMplsLspConfiguredPaths,
        vRtrMplsLspStandbyPaths,
        vRtrMplsLspOperationalPaths
    }
    STATUS      obsolete
    DESCRIPTION
        "The group of objects supporting management of extended MPLS LSPs on
         Nokia SROS series systems 2.1 Release."
    ::= { tmnxMplsGroups 13 }

tmnxMplsNotificationR2r1Group    NOTIFICATION-GROUP
    NOTIFICATIONS {
        vRtrMplsStateChange,
        vRtrMplsIfStateChange,
        vRtrMplsLspUp,
        vRtrMplsLspDown,
        vRtrMplsLspPathUp,
        vRtrMplsLspPathDown,
        vRtrMplsLspPathRerouted,
        vRtrMplsLspPathResignaled
    }
    STATUS      current
    DESCRIPTION
        "The group of notifications supporting the extended MPLS feature on
         Nokia SROS series systems 2.1 Release."
    ::= { tmnxMplsGroups 14 }

tmnxMplsLabelRangeGroup          OBJECT-GROUP
    OBJECTS     {
        vRtrMplsLabelRangeMin,
        vRtrMplsLabelRangeMax,
        vRtrMplsLabelRangeAging,
        vRtrMplsLabelRangeAvailable,
        vRtrMplsStaticLSPLabelOwner,
        vRtrMplsStaticSvcLabelOwner
    }
    STATUS      current
    DESCRIPTION
        "The group of objects supporting management of extended MPLS label
         ranges on Nokia SROS series systems."
    ::= { tmnxMplsGroups 15 }

tmnxMplsGlobalV5v0Group          OBJECT-GROUP
    OBJECTS     {
        vRtrMplsGeneralLastChange,
        vRtrMplsGeneralAdminState,
        vRtrMplsGeneralOperState,
        vRtrMplsGeneralPropagateTtl,
        vRtrMplsGeneralTE,
        vRtrMplsGeneralNewLspIndex,
        vRtrMplsGeneralOptimizeTimer,
        vRtrMplsGeneralFRObject,
        vRtrMplsGeneralResignalTimer,
        vRtrMplsGeneralStaticLspOriginate,
        vRtrMplsGeneralStaticLspTransit,
        vRtrMplsGeneralStaticLspTerminate,
        vRtrMplsGeneralDynamicLspOriginate,
        vRtrMplsGeneralDynamicLspTransit,
        vRtrMplsGeneralDynamicLspTerminate,
        vRtrMplsGeneralDetourLspOriginate,
        vRtrMplsGeneralDetourLspTransit,
        vRtrMplsGeneralDetourLspTerminate,
        vRtrMplsGeneralHoldTimer,
        vRtrMplsGeneralDynamicBypass
    }
    STATUS      obsolete
    DESCRIPTION
        "The group of objects supporting general management of extended MPLS on
         Nokia SROS series systems 5.0 Release."
    ::= { tmnxMplsGroups 16 }

tmnxMplsLspV5v0Group             OBJECT-GROUP
    OBJECTS     {
        vRtrMplsLspRowStatus,
        vRtrMplsLspLastChange,
        vRtrMplsLspName,
        vRtrMplsLspAdminState,
        vRtrMplsLspOperState,
        vRtrMplsLspFromAddr,
        vRtrMplsLspToAddr,
        vRtrMplsLspType,
        vRtrMplsLspOutSegIndx,
        vRtrMplsLspRetryTimer,
        vRtrMplsLspRetryLimit,
        vRtrMplsLspMetric,
        vRtrMplsLspDecrementTtl,
        vRtrMplsLspCspf,
        vRtrMplsLspFastReroute,
        vRtrMplsLspFRHopLimit,
        vRtrMplsLspFRBandwidth,
        vRtrMplsLspClassOfService,
        vRtrMplsLspSetupPriority,
        vRtrMplsLspHoldPriority,
        vRtrMplsLspRecord,
        vRtrMplsLspPreference,
        vRtrMplsLspBandwidth,
        vRtrMplsLspBwProtect,
        vRtrMplsLspHopLimit,
        vRtrMplsLspNegotiatedMTU,
        vRtrMplsLspRsvpResvStyle,
        vRtrMplsLspRsvpAdspec,
        vRtrMplsLspFRMethod,
        vRtrMplsLspFRNodeProtect,
        vRtrMplsLspAdminGroupInclude,
        vRtrMplsLspAdminGroupExclude,
        vRtrMplsLspAdaptive,
        vRtrMplsLspInheritance,
        vRtrMplsLspOptimizeTimer,
        vRtrMplsLspOperFastReroute,
        vRtrMplsLspFRObject,
        vRtrMplsLspOctets,
        vRtrMplsLspPackets,
        vRtrMplsLspAge,
        vRtrMplsLspTimeUp,
        vRtrMplsLspTimeDown,
        vRtrMplsLspPrimaryTimeUp,
        vRtrMplsLspTransitions,
        vRtrMplsLspLastTransition,
        vRtrMplsLspPathChanges,
        vRtrMplsLspLastPathChange,
        vRtrMplsLspConfiguredPaths,
        vRtrMplsLspStandbyPaths,
        vRtrMplsLspOperationalPaths,
        vRtrMplsLspHoldTimer
    }
    STATUS      obsolete
    DESCRIPTION
        "The group of objects supporting management of extended MPLS LSPs on
         Nokia SROS series systems 5.0 Release."
    ::= { tmnxMplsGroups 17 }

tmnxMplsGlobalV6v0Group          OBJECT-GROUP
    OBJECTS     {
        vRtrMplsGeneralLastChange,
        vRtrMplsGeneralAdminState,
        vRtrMplsGeneralOperState,
        vRtrMplsGeneralPropagateTtl,
        vRtrMplsGeneralTE,
        vRtrMplsGeneralNewLspIndex,
        vRtrMplsGeneralOptimizeTimer,
        vRtrMplsGeneralFRObject,
        vRtrMplsGeneralResignalTimer,
        vRtrMplsGeneralStaticLspOriginate,
        vRtrMplsGeneralStaticLspTransit,
        vRtrMplsGeneralStaticLspTerminate,
        vRtrMplsGeneralDynamicLspOriginate,
        vRtrMplsGeneralDynamicLspTransit,
        vRtrMplsGeneralDynamicLspTerminate,
        vRtrMplsGeneralDetourLspOriginate,
        vRtrMplsGeneralDetourLspTransit,
        vRtrMplsGeneralDetourLspTerminate,
        vRtrMplsGeneralHoldTimer,
        vRtrMplsGeneralDynamicBypass,
        vRtrMplsGeneralNextResignal,
        vRtrMplsGeneralOperDownReason,
        vRtrMplsGeneralSrlgFrr,
        vRtrMplsGeneralSrlgFrrStrict
    }
    STATUS      obsolete
    DESCRIPTION
        "The group of objects supporting general management of extended MPLS on
         Nokia SROS series systems 6.0 Release."
    ::= { tmnxMplsGroups 18 }

tmnxMplsSrlgV6v0Group            OBJECT-GROUP
    OBJECTS     {
        vRtrMplsSrlgGrpTableLastChanged,
        vRtrMplsSrlgGrpRowStatus,
        vRtrMplsSrlgGrpLastChanged,
        vRtrMplsSrlgGrpValue,
        vRtrMplsIfSrlgGrpTblLastChanged,
        vRtrMplsIfSrlgGrpRowStatus,
        vRtrMplsIfSrlgGrpLastChanged
    }
    STATUS      obsolete
    DESCRIPTION
        "The group of objects supporting management of SRLG on Nokia 7xxx SR
         series systems release 6.0."
    ::= { tmnxMplsGroups 19 }

tmnxMplsLspPathV6v0Group         OBJECT-GROUP
    OBJECTS     {
        vRtrMplsLspPathSrlg,
        vRtrMplsLspPathSrlgDisjoint
    }
    STATUS      current
    DESCRIPTION
        "The group of objects supporting management of extended MPLS LSP to
         path mapping on Nokia SROS series systems."
    ::= { tmnxMplsGroups 20 }

tmnxMplsIfV6v0Group              OBJECT-GROUP
    OBJECTS     {
        vRtrMplsIfTeMetric
    }
    STATUS      current
    DESCRIPTION
        "The group of objects supporting management of Te metric feature on
         extended MPLS interfaces on 6.0 release Nokia SROS series systems."
    ::= { tmnxMplsGroups 21 }

tmnxMplsLspV6v0Group             OBJECT-GROUP
    OBJECTS     {
        vRtrMplsLspCspfTeMetricEnabled
    }
    STATUS      obsolete
    DESCRIPTION
        "The group of objects supporting management of Te metric feature
         extended MPLS LSPs on 6.0 release Nokia SROS series systems."
    ::= { tmnxMplsGroups 22 }

tmnxMplsLspPathV6v1Group         OBJECT-GROUP
    OBJECTS     {
        vRtrMplsLspPathTableSpinlock,
        vRtrMplsLspPathRowStatus,
        vRtrMplsLspPathLastChange,
        vRtrMplsLspPathType,
        vRtrMplsLspPathCos,
        vRtrMplsLspPathProperties,
        vRtrMplsLspPathBandwidth,
        vRtrMplsLspPathBwProtect,
        vRtrMplsLspPathState,
        vRtrMplsLspPathPreference,
        vRtrMplsLspPathCosSource,
        vRtrMplsLspPathClassOfService,
        vRtrMplsLspPathSetupPriority,
        vRtrMplsLspPathHoldPriority,
        vRtrMplsLspPathRecord,
        vRtrMplsLspPathHopLimit,
        vRtrMplsLspPathSharing,
        vRtrMplsLspPathAdminState,
        vRtrMplsLspPathOperState,
        vRtrMplsLspPathInheritance,
        vRtrMplsLspPathLspId,
        vRtrMplsLspPathRetryTimeRemaining,
        vRtrMplsLspPathTunnelARHopListIndex,
        vRtrMplsLspPathNegotiatedMTU,
        vRtrMplsLspPathFailCode,
        vRtrMplsLspPathFailNodeAddr,
        vRtrMplsLspPathAdminGroupInclude,
        vRtrMplsLspPathAdminGroupExclude,
        vRtrMplsLspPathAdaptive,
        vRtrMplsLspPathOptimizeTimer,
        vRtrMplsLspPathNextOptimize,
        vRtrMplsLspPathOperBandwidth,
        vRtrMplsLspPathResignal,
        vRtrMplsLspPathTunnelCRHopListIndex,
        vRtrMplsLspPathOperMTU,
        vRtrMplsLspPathRecordLabel,
        vRtrMplsLspPathTimeUp,
        vRtrMplsLspPathTimeDown,
        vRtrMplsLspPathRetryAttempts,
        vRtrMplsLspPathTransitionCount,
        vRtrMplsLspPathCspfQueries,
        vRtrMplsLspPathLastResigAttempt,
        vRtrMplsLspPathMetric,
        vRtrMplsLspPathLastMBBType,
        vRtrMplsLspPathLastMBBEnd,
        vRtrMplsLspPathLastMBBMetric,
        vRtrMplsLspPathLastMBBState,
        vRtrMplsLspPathMBBTypeInProg,
        vRtrMplsLspPathMBBStarted,
        vRtrMplsLspPathMBBNextRetry,
        vRtrMplsLspPathMBBRetryAttempts,
        vRtrMplsLspPathMBBFailCode,
        vRtrMplsLspPathMBBFailNodeArType,
        vRtrMplsLspPathMBBFailNodeAddr
    }
    STATUS      obsolete
    DESCRIPTION
        "The group of objects supporting management of extended MPLS LSP to
         path mapping on Nokia SROS series systems."
    ::= { tmnxMplsGroups 23 }

tmnxMplsObsoleteGroup            OBJECT-GROUP
    OBJECTS     {
        vRtrMplsLspPathMBBState,
        vRtrMplsFSGroupCost,
        vRtrMplsFSGroupParamsRowStatus,
        vRtrMplsFSGroupRowStatus
    }
    STATUS      current
    DESCRIPTION
        "The group of obsolete objects which are no longer supported in MPLS on
         6.0R4 release onwards on Nokia SROS series systems."
    ::= { tmnxMplsGroups 24 }

tmnxMplsLspV7v0Group             OBJECT-GROUP
    OBJECTS     {
        vRtrMplsLspP2mpId,
        vRtrMplsLspClassType,
        vRtrMplsLspOperMetric,
        vRtrMplsLspLdpOverRsvpInclude,
        vRtrMplsLspLeastFill,
        vRtrMplsLspVprnAutoBindInclude,
        vRtrMplsLspConfP2mpInstances
    }
    STATUS      current
    DESCRIPTION
        "The group of objects supporting management of extended LSP in MPLS on
         on Nokia SROS series systems 7.0 release."
    ::= { tmnxMplsGroups 25 }

tmnxMplsGlobalV7v0Group          OBJECT-GROUP
    OBJECTS     {
        vRtrMplsGeneralNewP2mpInstIndex,
        vRtrMplsGeneralS2lOriginate,
        vRtrMplsGeneralS2lTransit,
        vRtrMplsGeneralS2lTerminate,
        vRtrMplsGeneralLeastFillMinThd,
        vRtrMplsGenLeastFillReoptiThd,
        vRtrMplsGeneralUseSrlgDB,
        vRtrMplsInSegmentNumS2ls,
        vRtrMplsOutSegmentNumS2ls,
        vRtrMplsGeneralP2mpResigTimer,
        vRtrMplsGeneralP2mpNextResignal,
        vRtrMplsGeneralSecFastRetryTimer,
        vRtrMplsGeneralStaticLspFRTimer
    }
    STATUS      current
    DESCRIPTION
        "The group of all global objects in MPLS supporting management of MPLS
         features on Nokia SROS series systems 7.0 release."
    ::= { tmnxMplsGroups 26 }

tmnxMplsP2mpInstanceGroup        OBJECT-GROUP
    OBJECTS     {
        vRtrMplsP2mpInstTblLastChanged,
        vRtrMplsP2mpInstRowStatus,
        vRtrMplsP2mpInstLastChange,
        vRtrMplsP2mpInstName,
        vRtrMplsP2mpInstType,
        vRtrMplsP2mpInstProperties,
        vRtrMplsP2mpInstBandwidth,
        vRtrMplsP2mpInstState,
        vRtrMplsP2mpInstSetupPriority,
        vRtrMplsP2mpInstHoldPriority,
        vRtrMplsP2mpInstRecord,
        vRtrMplsP2mpInstHopLimit,
        vRtrMplsP2mpInstAdminState,
        vRtrMplsP2mpInstOperState,
        vRtrMplsP2mpInstInheritance,
        vRtrMplsP2mpInstLspId,
        vRtrMplsP2mpInstNegotiatedMTU,
        vRtrMplsP2mpInstFailCode,
        vRtrMplsP2mpInstFailNodeArType,
        vRtrMplsP2mpInstFailNodeAddr,
        vRtrMplsP2mpInstAdminGrpInclude,
        vRtrMplsP2mpInstAdminGrpExclude,
        vRtrMplsP2mpInstAdaptive,
        vRtrMplsP2mpInstOperBandwidth,
        vRtrMplsP2mpInstResignal,
        vRtrMplsP2mpInstOperMTU,
        vRtrMplsP2mpInstRecordLabel,
        vRtrMplsP2mpInstLastResigAttpt,
        vRtrMplsP2mpInstMetric,
        vRtrMplsP2mpInstLastMBBType,
        vRtrMplsP2mpInstLastMBBEnd,
        vRtrMplsP2mpInstLastMBBMetric,
        vRtrMplsP2mpInstLastMBBState,
        vRtrMplsP2mpInstMBBTypeInProg,
        vRtrMplsP2mpInstMBBStarted,
        vRtrMplsP2mpInstMBBNextRetry,
        vRtrMplsP2mpInstMBBRetryAttpts,
        vRtrMplsP2mpInstMBBFailCode,
        vRtrMplsP2mpInstMBBFailNodeType,
        vRtrMplsP2mpInstMBBFailNodeAddr,
        vRtrMplsP2mpInstStatS2lChanges,
        vRtrMplsP2mpInstStatLastS2lChange,
        vRtrMplsP2mpInstStatConfiguredS2ls,
        vRtrMplsP2mpInstStatOperationalS2ls,
        vRtrMplsP2mpInstStatLastS2lTimeUp,
        vRtrMplsP2mpInstStatLastS2lTimeDown,
        vRtrMplsP2mpInstStatTimeUp,
        vRtrMplsP2mpInstStatTimeDown,
        vRtrMplsP2mpInstStatTransitions,
        vRtrMplsP2mpInstStatLastTrans
    }
    STATUS      current
    DESCRIPTION
        "The group of all P2MP instance related objects supporting management
         of P2MP feature in MPLS on Nokia SROS series systems 7.0 release."
    ::= { tmnxMplsGroups 27 }

tmnxMplsP2mpS2lGroup             OBJECT-GROUP
    OBJECTS     {
        vRtrMplsS2lSubLspTblLastChanged,
        vRtrMplsS2lSubLspRowStatus,
        vRtrMplsS2lSubLspLastChange,
        vRtrMplsS2lSubLspType,
        vRtrMplsS2lSubLspProperties,
        vRtrMplsS2lSubLspState,
        vRtrMplsS2lSubLspAdminState,
        vRtrMplsS2lSubLspOperState,
        vRtrMplsS2lSubGroupId,
        vRtrMplsS2lSubLspId,
        vRtrMplsS2lSubLspRetryTimeRemain,
        vRtrMplsS2lSubLspNegotiatedMTU,
        vRtrMplsS2lSubLspFailCode,
        vRtrMplsS2lSubLspFailNodeArType,
        vRtrMplsS2lSubLspFailNodeAddr,
        vRtrMplsS2lSubLspOperBandwidth,
        vRtrMplsS2lSubLspOperMTU,
        vRtrMplsS2lSubLspLastResigAttpt,
        vRtrMplsS2lSubLspLastMBBType,
        vRtrMplsS2lSubLspLastMBBEnd,
        vRtrMplsS2lSubLspLastMBBMetric,
        vRtrMplsS2lSubLspLastMBBState,
        vRtrMplsS2lSubLspMBBTypeInProg,
        vRtrMplsS2lSubLspMBBStarted,
        vRtrMplsS2lSubLspMBBNextRetry,
        vRtrMplsS2lSubLspMBBRetryAttpts,
        vRtrMplsS2lSubLspMBBFailCode,
        vRtrMplsS2lSubLspMBBFailNodeType,
        vRtrMplsS2lSubLspMBBFailNodeAddr,
        vRtrMplsS2lSubLspUpTime,
        vRtrMplsS2lSubLspDownTime,
        vRtrMplsS2lSubLspTimeUp,
        vRtrMplsS2lSubLspTimeDown,
        vRtrMplsS2lSubLspRetryAttempts,
        vRtrMplsS2lSubLspTransitionCount,
        vRtrMplsS2lSubLspCspfQueries,
        vRtrMplsS2lSubLspTunARHopLtIndex,
        vRtrMplsS2lSubLspTunCRHopLtIndex
    }
    STATUS      current
    DESCRIPTION
        "The group of all S2L sub-LSP related objects supporting management of
         P2MP feature in MPLS on Nokia SROS series systems 7.0 release."
    ::= { tmnxMplsGroups 28 }

tmnxMplsNotifyObjsV7v0Group      OBJECT-GROUP
    OBJECTS     {
        vRtrMplsP2mpInstNotifIndex,
        vRtrMplsS2lSubLspNtDstAddrType,
        vRtrMplsS2lSubLspNtDstAddr,
        vRtrMplsP2mpInstNotifReasonCode,
        vRtrMplsLspPathCongChgPercent
    }
    STATUS      current
    DESCRIPTION
        "The group of notification objects supporting extended MPLS
         notifications on Nokia SROS series systems 7.0 release."
    ::= { tmnxMplsGroups 29 }

tmnxMplsNotificationV7v0Group    NOTIFICATION-GROUP
    NOTIFICATIONS {
        vRtrMplsP2mpInstanceUp,
        vRtrMplsP2mpInstanceDown,
        vRtrMplsS2lSubLspUp,
        vRtrMplsS2lSubLspDown,
        vRtrMplsS2lSubLspRerouted,
        vRtrMplsS2lSubLspResignaled,
        vRtrMplsLspPathSoftPreempted,
        vRtrMplsLspPathLstFillReoptElig,
        vRtrMplsP2mpInstanceResignaled,
        vRtrMplsResignalTimerExpired
    }
    STATUS      current
    DESCRIPTION
        "The group of notifications supporting the extended MPLS feature on
         Nokia SROS series systems 7.0 Release."
    ::= { tmnxMplsGroups 30 }

tmnxMplsLspPathV7v0Group         OBJECT-GROUP
    OBJECTS     {
        vRtrMplsLspPathClassType,
        vRtrMplsLspPathOperMetric,
        vRtrMplsLspPathResignalEligible,
        vRtrMplsLspPathIsFastRetry
    }
    STATUS      current
    DESCRIPTION
        "The group of objects supporting management of extended MPLS LSP to
         path mapping on Nokia SROS series systems."
    ::= { tmnxMplsGroups 31 }

tmnxMplsSrlgV7v0Group            OBJECT-GROUP
    OBJECTS     {
        vRtrMplsSrlgDBRtrIdRowStatus,
        vRtrMplsSrlgDBRtrIdAdminState,
        vRtrMplsSrlgDBRtrIdLastChanged,
        vRtrMplsSrlgDBRtrIdTblLastChg,
        vRtrMplsSrlgDBIfRowStatus,
        vRtrMplsSrlgDBIfLastChanged,
        vRtrMplsSrlgDBIfTblLastChanged
    }
    STATUS      current
    DESCRIPTION
        "The group of objects supporting management of SRLG on Nokia SROS
         series systems release 7.0."
    ::= { tmnxMplsGroups 32 }

tmnxMplsLspStatsV7v0Group        OBJECT-GROUP
    OBJECTS     {
        vRtrMplsLspStatsAccntingPolicy,
        vRtrMplsLspStatsCollectStats,
        vRtrMplsLspStatsLastChanged,
        vRtrMplsLspStatsRowStatus,
        vRtrMplsLspStatsTblLastChgd,
        vRtrMplsLspStatsAdminState,
        vRtrMplsInProfileOctetsFc0,
        vRtrMplsInProfileOctetsFc0High32,
        vRtrMplsInProfileOctetsFc0Low32,
        vRtrMplsInProfileOctetsFc1,
        vRtrMplsInProfileOctetsFc1High32,
        vRtrMplsInProfileOctetsFc1Low32,
        vRtrMplsInProfileOctetsFc2,
        vRtrMplsInProfileOctetsFc2High32,
        vRtrMplsInProfileOctetsFc2Low32,
        vRtrMplsInProfileOctetsFc3,
        vRtrMplsInProfileOctetsFc3High32,
        vRtrMplsInProfileOctetsFc3Low32,
        vRtrMplsInProfileOctetsFc4,
        vRtrMplsInProfileOctetsFc4High32,
        vRtrMplsInProfileOctetsFc4Low32,
        vRtrMplsInProfileOctetsFc5,
        vRtrMplsInProfileOctetsFc5High32,
        vRtrMplsInProfileOctetsFc5Low32,
        vRtrMplsInProfileOctetsFc6,
        vRtrMplsInProfileOctetsFc6High32,
        vRtrMplsInProfileOctetsFc6Low32,
        vRtrMplsInProfileOctetsFc7,
        vRtrMplsInProfileOctetsFc7High32,
        vRtrMplsInProfileOctetsFc7Low32,
        vRtrMplsInProfilePktsFc0,
        vRtrMplsInProfilePktsFc0High32,
        vRtrMplsInProfilePktsFc0Low32,
        vRtrMplsInProfilePktsFc1,
        vRtrMplsInProfilePktsFc1High32,
        vRtrMplsInProfilePktsFc1Low32,
        vRtrMplsInProfilePktsFc2,
        vRtrMplsInProfilePktsFc2High32,
        vRtrMplsInProfilePktsFc2Low32,
        vRtrMplsInProfilePktsFc3,
        vRtrMplsInProfilePktsFc3High32,
        vRtrMplsInProfilePktsFc3Low32,
        vRtrMplsInProfilePktsFc4,
        vRtrMplsInProfilePktsFc4High32,
        vRtrMplsInProfilePktsFc4Low32,
        vRtrMplsInProfilePktsFc5,
        vRtrMplsInProfilePktsFc5High32,
        vRtrMplsInProfilePktsFc5Low32,
        vRtrMplsInProfilePktsFc6,
        vRtrMplsInProfilePktsFc6High32,
        vRtrMplsInProfilePktsFc6Low32,
        vRtrMplsInProfilePktsFc7,
        vRtrMplsInProfilePktsFc7High32,
        vRtrMplsInProfilePktsFc7Low32,
        vRtrMplsOutOfProfOctetsFc0,
        vRtrMplsOutOfProfOctetsFc0High32,
        vRtrMplsOutOfProfOctetsFc0Low32,
        vRtrMplsOutOfProfOctetsFc1,
        vRtrMplsOutOfProfOctetsFc1High32,
        vRtrMplsOutOfProfOctetsFc1Low32,
        vRtrMplsOutOfProfOctetsFc2,
        vRtrMplsOutOfProfOctetsFc2High32,
        vRtrMplsOutOfProfOctetsFc2Low32,
        vRtrMplsOutOfProfOctetsFc3,
        vRtrMplsOutOfProfOctetsFc3High32,
        vRtrMplsOutOfProfOctetsFc3Low32,
        vRtrMplsOutOfProfOctetsFc4,
        vRtrMplsOutOfProfOctetsFc4High32,
        vRtrMplsOutOfProfOctetsFc4Low32,
        vRtrMplsOutOfProfOctetsFc5,
        vRtrMplsOutOfProfOctetsFc5High32,
        vRtrMplsOutOfProfOctetsFc5Low32,
        vRtrMplsOutOfProfOctetsFc6,
        vRtrMplsOutOfProfOctetsFc6High32,
        vRtrMplsOutOfProfOctetsFc6Low32,
        vRtrMplsOutOfProfOctetsFc7,
        vRtrMplsOutOfProfOctetsFc7High32,
        vRtrMplsOutOfProfOctetsFc7Low32,
        vRtrMplsOutOfProfPktsFc0,
        vRtrMplsOutOfProfPktsFc0High32,
        vRtrMplsOutOfProfPktsFc0Low32,
        vRtrMplsOutOfProfPktsFc1,
        vRtrMplsOutOfProfPktsFc1High32,
        vRtrMplsOutOfProfPktsFc1Low32,
        vRtrMplsOutOfProfPktsFc2,
        vRtrMplsOutOfProfPktsFc2High32,
        vRtrMplsOutOfProfPktsFc2Low32,
        vRtrMplsOutOfProfPktsFc3,
        vRtrMplsOutOfProfPktsFc3High32,
        vRtrMplsOutOfProfPktsFc3Low32,
        vRtrMplsOutOfProfPktsFc4,
        vRtrMplsOutOfProfPktsFc4High32,
        vRtrMplsOutOfProfPktsFc4Low32,
        vRtrMplsOutOfProfPktsFc5,
        vRtrMplsOutOfProfPktsFc5High32,
        vRtrMplsOutOfProfPktsFc5Low32,
        vRtrMplsOutOfProfPktsFc6,
        vRtrMplsOutOfProfPktsFc6High32,
        vRtrMplsOutOfProfPktsFc6Low32,
        vRtrMplsOutOfProfPktsFc7,
        vRtrMplsOutOfProfPktsFc7High32,
        vRtrMplsOutOfProfPktsFc7Low32,
        vRtrMplsLspStatsPSBMatch,
        vRtrMplsGeneralLspEgrStatCount,
        vRtrMplsGeneralLspIgrStatCount
    }
    STATUS      current
    DESCRIPTION
        "The group of objects supporting management of egress/ingress
         statistics on Nokia SROS series systems release 7.0."
    ::= { tmnxMplsGroups 33 }

tmnxMplsLspV8v0Group             OBJECT-GROUP
    OBJECTS     {
        vRtrMplsLspMainCTRetryLimit,
        vRtrMplsLspIgpShortcut
    }
    STATUS      current
    DESCRIPTION
        "The group of objects supporting management of extended LSP in MPLS on
         Nokia SROS series systems 8.0 release."
    ::= { tmnxMplsGroups 34 }

tmnxMplsLspPathV8v0Group         OBJECT-GROUP
    OBJECTS     {
        vRtrMplsLspPathBackupCT,
        vRtrMplsLspPathMainCTRetryRem,
        vRtrMplsLspPathOperCT,
        vRtrMplsLspPathNewPathIndex,
        vRtrMplsLspPathMBBMainCTRetryRem
    }
    STATUS      current
    DESCRIPTION
        "The group of objects supporting management of extended MPLS LSP to
         path mapping on Nokia SROS series systems 8.0 release."
    ::= { tmnxMplsGroups 35 }

tmnxMplsNotifyObjsV8v0Group      OBJECT-GROUP
    OBJECTS     {
        vRtrMplsLspPathMbbStatus,
        vRtrMplsLspPathMbbReasonCode
    }
    STATUS      current
    DESCRIPTION
        "The group of notification objects supporting extended MPLS
         notifications on Nokia SROS series systems 8.0 release."
    ::= { tmnxMplsGroups 36 }

tmnxMplsNotificationV8v0Group    NOTIFICATION-GROUP
    NOTIFICATIONS {
        vRtrMplsLspPathMbbStatusEvent
    }
    STATUS      current
    DESCRIPTION
        "The group of notifications supporting the extended MPLS feature on
         Nokia SROS series systems 8.0 Release."
    ::= { tmnxMplsGroups 37 }

tmnxMplsGlobalV8v0Group          OBJECT-GROUP
    OBJECTS     {
        vRtrMplsGeneralShortTTLPropLocal,
        vRtrMplsGeneralShortTTLPropTrans,
        vRtrMplsGeneralAutoBWDefSampMul,
        vRtrMplsGeneralAutoBWDefAdjMul,
        vRtrMplsGeneralExpBackoffRetry
    }
    STATUS      current
    DESCRIPTION
        "The group of all global objects in MPLS supporting management of MPLS
         features on Nokia SROS series systems 8.0 release."
    ::= { tmnxMplsGroups 38 }

tmnxMplsLspTemplateV8v0Group     OBJECT-GROUP
    OBJECTS     {
        vRtrMplsLspTemplateTblLastChgd,
        vRtrMplsLspTemplateRowStatus,
        vRtrMplsLspTemplateLastChanged,
        vRtrMplsLspTemplateAdminState,
        vRtrMplsLspTemplateType,
        vRtrMplsLspTemplateAdaptive,
        vRtrMplsLspTemplateBandwidth,
        vRtrMplsLspTemplateCspf,
        vRtrMplsLspTemplateDefaultPath,
        vRtrMplsLspTemplateAdmGrpIncl,
        vRtrMplsLspTemplateAdmGrpExcl,
        vRtrMplsLspTemplateFastReroute,
        vRtrMplsLspTemplateFRMethod,
        vRtrMplsLspTemplateFRHopLimit,
        vRtrMplsLspTemplateHopLimit,
        vRtrMplsLspTemplateRecord,
        vRtrMplsLspTemplateRecordLabel,
        vRtrMplsLspTemplateRetryLimit,
        vRtrMplsLspTemplateRetryTimer,
        vRtrMplsLspTemplateCspfTeMetric,
        vRtrMplsLspOriginTemplate,
        vRtrMplsLspTemplateLspCount,
        vRtrMplsLspTemplateMvpnRefCount
    }
    STATUS      obsolete
    DESCRIPTION
        "The group of objects supporting management of LSP Templates in MPLS on
         Nokia SROS series systems 8.0 release."
    ::= { tmnxMplsGroups 39 }

tmnxMplsLspAutoBWV8v0Group       OBJECT-GROUP
    OBJECTS     {
        vRtrMplsLspAutoBandwidth,
        vRtrMplsLspAutoBWTableLastChg,
        vRtrMplsLspAutoBWLastChange,
        vRtrMplsLspAutoBWAdjDNPercent,
        vRtrMplsLspAutoBWAdjDNMbps,
        vRtrMplsLspAutoBWAdjMultiplier,
        vRtrMplsLspAutoBWAdjUPPercent,
        vRtrMplsLspAutoBWAdjUPMbps,
        vRtrMplsLspAutoBWMaxBW,
        vRtrMplsLspAutoBWMinBW,
        vRtrMplsLspAutoBWMonitorBW,
        vRtrMplsLspAutoBWOverFlow,
        vRtrMplsLspAutoBWOvrFlwThreshold,
        vRtrMplsLspAutoBWOvrFlwBW,
        vRtrMplsLspAutoBWSampMultiplier,
        vRtrMplsLspAutoBWSampTime,
        vRtrMplsLspAutoBWLastAdj,
        vRtrMplsLspAutoBWLastAdjCause,
        vRtrMplsLspAutoBWNextAdj,
        vRtrMplsLspAutoBWMaxAvgRate,
        vRtrMplsLspAutoBWLastAvgRate,
        vRtrMplsLspAutoBWInheritance,
        vRtrMplsLspAutoBWCurrentBW,
        vRtrMplsLspAutoBWAdjTime,
        vRtrMplsLspAutoBWOvrFlwCount,
        vRtrMplsLspAutoBWSampCount,
        vRtrMplsLspAutoBWAdjCount,
        vRtrMplsLspAutoBWOperState,
        vRtrMplsLspAutoBWSampInterval,
        vRtrMplsLspPathSigBWMBBInProg,
        vRtrMplsLspPathSigBWLastMBB
    }
    STATUS      current
    DESCRIPTION
        "The group of all objects supporting management of Auto-Bandwidth in
         MPLS on Nokia SROS series systems 8.0 release."
    ::= { tmnxMplsGroups 40 }

tmnxMplsGlobalV9v0Group          OBJECT-GROUP
    OBJECTS     {
        vRtrMplsGeneralCspfOnLooseHop
    }
    STATUS      current
    DESCRIPTION
        "The group of all global objects in MPLS supporting management of MPLS
         features on Nokia SROS series systems 9.0 release."
    ::= { tmnxMplsGroups 41 }

tmnxMplsLspV9v0Group             OBJECT-GROUP
    OBJECTS     {
        vRtrMplsLspCspfToFirstLoose,
        vRtrMplsLspPropAdminGroup
    }
    STATUS      obsolete
    DESCRIPTION
        "The group of objects supporting management of extended LSP in MPLS on
         Nokia SROS series systems 9.0 release."
    ::= { tmnxMplsGroups 42 }

tmnxMplsLspV9v0R4Group           OBJECT-GROUP
    OBJECTS     {
        vRtrMplsLspBgpShortcut,
        vRtrMplsLspBgpTransportTunnel,
        vRtrMplsLspSwitchStbyPath,
        vRtrMplsLspSwitchStbyPathIndex,
        vRtrMplsLspSwitchStbyPathForce,
        vRtrMplsGeneralP2PMaxByPassAssoc,
        vRtrMplsLspExcludeNodeAddr,
        vRtrMplsLspExcludeNodeAddrType
    }
    STATUS      current
    DESCRIPTION
        "The group of objects supporting management of extended LSP in MPLS on
         Nokia SROS series systems 9.0R4 release."
    ::= { tmnxMplsGroups 43 }

tmnxMplsNotifyObjsV9v0R4Group    OBJECT-GROUP
    OBJECTS     {
        vRtrMplsLspSwitchStbyReasonCode,
        vRtrMplsLspOldTunnelIndex
    }
    STATUS      current
    DESCRIPTION
        "The group of notification objects supporting extended MPLS
         notifications on Nokia SROS series systems 9.0.R4 release."
    ::= { tmnxMplsGroups 44 }

tmnxMplsNotifV9v0R4Group         NOTIFICATION-GROUP
    NOTIFICATIONS {
        vRtrMplsLspSwitchStbyFailure,
        vRtrMplsLspActivePathChanged
    }
    STATUS      current
    DESCRIPTION
        "The group of notifications supporting the extended MPLS feature on
         Nokia SROS series systems 9.0.R4 Release."
    ::= { tmnxMplsGroups 45 }

tmnxMplsLspPathV9v0R4Group       OBJECT-GROUP
    OBJECTS     {
        vRtrMplsLspPathActiveByManual
    }
    STATUS      current
    DESCRIPTION
        "The group of objects supporting management of extended MPLS LSP to
         path mapping on Nokia SROS series systems 9.0.R4 release."
    ::= { tmnxMplsGroups 46 }

tmnxMplsGlobalV10v0Group         OBJECT-GROUP
    OBJECTS     {
        vRtrMplsGenP2pActPathFastRetry,
        vRtrMplsGenP2mpS2lFastRetry,
        vRtrMplsS2lSubLspIsFastRetry,
        vRtrMplsLspPathTimeoutIn,
        vRtrMplsLspPathMBBTimeoutIn,
        vRtrMplsS2lSubLspTimeoutIn,
        vRtrMplsS2lSubLspMBBTimeoutIn,
        vRtrMplsLspPathOperSetupPriority,
        vRtrMplsLspPathOperHoldPriority,
        vRtrMplsLspPathOperRecord,
        vRtrMplsLspPathOperRecordLabel,
        vRtrMplsLspPathOperHopLimit,
        vRtrMplsLspPathOperAdminGrpIncl,
        vRtrMplsLspPathOperAdminGrExcld,
        vRtrMplsLspPathOperCspf,
        vRtrMplsLspPathOperCspfToFrstLs,
        vRtrMplsLspPathOperLeastFill,
        vRtrMplsLspPathOperRsvpAdspec,
        vRtrMplsLspPathOperFRNodeProtect,
        vRtrMplsLspPathOperPropAdminGrp,
        vRtrMplsLspPathOperFRHopLimit,
        vRtrMplsGenLspInitRetryTimeout,
        vRtrMplsLspIgpShortcutLfaType,
        vRtrMplsLoggerEventBundling,
        vRtrMplsGenIssuMplsLockdown
    }
    STATUS      obsolete
    DESCRIPTION
        "The group of all global objects in MPLS supporting management of MPLS
         features on Nokia SROS series systems 10.0 release."
    ::= { tmnxMplsGroups 47 }

tmnxMplsTpGroup                  OBJECT-GROUP
    OBJECTS     {
        vRtrMplsLspToAddrType,
        vRtrMplsLspFromAddrType,
        vRtrMplsLspToNodeId,
        vRtrMplsLspFromNodeId,
        vRtrMplsLspDestGlobalId,
        vRtrMplsLspDestTunnelNum,
        vRtrMplsGenMplsTpLspOriginate,
        vRtrMplsGenMplsTpLspTransit,
        vRtrMplsGenMplsTpLspTerminate,
        vRtrMplsGenMplsTpOrigPathInst,
        vRtrMplsGenMplsTpTranPathInst,
        vRtrMplsGenMplsTpTermPathInst
    }
    STATUS      current
    DESCRIPTION
        "The group of objects supporting management of the MPLS-TP feature on
         Nokia SROS series systems."
    ::= { tmnxMplsGroups 48 }

tmnxMplsNotifyObjsV10v0Group     OBJECT-GROUP
    OBJECTS     {
        vRtrMplsXCNotifRednIndicesBitMap,
        vRtrMplsXCNotifyRednBundlingType,
        vRtrMplsXCNotifyRednNumOfBitsSet,
        vRtrMplsXCNotifyRednStartIndex,
        vRtrMplsXCNotifyRednEndIndex
    }
    STATUS      current
    DESCRIPTION
        "The group of notification objects supporting extended MPLS
         notifications on Nokia SROS series systems 10.0 release."
    ::= { tmnxMplsGroups 49 }

tmnxMplsNotifyV10v0Group         NOTIFICATION-GROUP
    NOTIFICATIONS {
        vRtrMplsXCBundleChange
    }
    STATUS      current
    DESCRIPTION
        "The group of notifications supporting the extended MPLS feature on
         Nokia SROS series systems 10.0 Release."
    ::= { tmnxMplsGroups 50 }

tmnxMplsFRAdminGroup             OBJECT-GROUP
    OBJECTS     {
        vRtrMplsGenFRAdminGroup,
        vRtrMplsLspTemplateFRPropAdmGrp,
        vRtrMplsLspFRPropAdminGroup,
        vRtrMplsTunnelCHopEgressAdmGrp,
        vRtrMplsLspPathOperFRPropAdmGrp
    }
    STATUS      current
    DESCRIPTION
        "The group of objects supporting administrative groups for Fast Reroute"
    ::= { tmnxMplsGroups 51 }

tmnxMplsGlobalV11v0Group         OBJECT-GROUP
    OBJECTS     {
        vRtrMplsLspPathOperInterArea,
        vRtrMplsTunnelCHopUnnumIfID,
        vRtrMplsTunnelCHopRtrID,
        vRtrMplsTunnelCHopIsABR,
        vRtrMplsTunnelARHopUnnumIfID,
        vRtrMplsLspRowStatus,
        vRtrMplsLspLastChange,
        vRtrMplsLspName,
        vRtrMplsLspAdminState,
        vRtrMplsLspOperState,
        vRtrMplsLspFromAddr,
        vRtrMplsLspToAddr,
        vRtrMplsLspType,
        vRtrMplsLspOutSegIndx,
        vRtrMplsLspRetryTimer,
        vRtrMplsLspRetryLimit,
        vRtrMplsLspMetric,
        vRtrMplsLspCspf,
        vRtrMplsLspFastReroute,
        vRtrMplsLspFRHopLimit,
        vRtrMplsLspFRBandwidth,
        vRtrMplsLspSetupPriority,
        vRtrMplsLspHoldPriority,
        vRtrMplsLspRecord,
        vRtrMplsLspBandwidth,
        vRtrMplsLspHopLimit,
        vRtrMplsLspNegotiatedMTU,
        vRtrMplsLspRsvpResvStyle,
        vRtrMplsLspRsvpAdspec,
        vRtrMplsLspFRMethod,
        vRtrMplsLspFRNodeProtect,
        vRtrMplsLspAdminGroupInclude,
        vRtrMplsLspAdminGroupExclude,
        vRtrMplsLspAdaptive,
        vRtrMplsLspInheritance,
        vRtrMplsLspOptimizeTimer,
        vRtrMplsLspOperFastReroute,
        vRtrMplsLspFRObject,
        vRtrMplsLspOctets,
        vRtrMplsLspPackets,
        vRtrMplsLspAge,
        vRtrMplsLspTimeUp,
        vRtrMplsLspTimeDown,
        vRtrMplsLspPrimaryTimeUp,
        vRtrMplsLspTransitions,
        vRtrMplsLspLastTransition,
        vRtrMplsLspPathChanges,
        vRtrMplsLspLastPathChange,
        vRtrMplsLspConfiguredPaths,
        vRtrMplsLspStandbyPaths,
        vRtrMplsLspOperationalPaths,
        vRtrMplsLspHoldTimer,
        vRtrMplsLspPathTableSpinlock,
        vRtrMplsLspPathRowStatus,
        vRtrMplsLspPathLastChange,
        vRtrMplsLspPathType,
        vRtrMplsLspPathProperties,
        vRtrMplsLspPathBandwidth,
        vRtrMplsLspPathState,
        vRtrMplsLspPathPreference,
        vRtrMplsLspPathSetupPriority,
        vRtrMplsLspPathHoldPriority,
        vRtrMplsLspPathRecord,
        vRtrMplsLspPathHopLimit,
        vRtrMplsLspPathAdminState,
        vRtrMplsLspPathOperState,
        vRtrMplsLspPathInheritance,
        vRtrMplsLspPathLspId,
        vRtrMplsLspPathRetryTimeRemaining,
        vRtrMplsLspPathTunnelARHopListIndex,
        vRtrMplsLspPathNegotiatedMTU,
        vRtrMplsLspPathFailCode,
        vRtrMplsLspPathFailNodeAddr,
        vRtrMplsLspPathAdminGroupInclude,
        vRtrMplsLspPathAdminGroupExclude,
        vRtrMplsLspPathAdaptive,
        vRtrMplsLspPathOptimizeTimer,
        vRtrMplsLspPathNextOptimize,
        vRtrMplsLspPathOperBandwidth,
        vRtrMplsLspPathResignal,
        vRtrMplsLspPathTunnelCRHopListIndex,
        vRtrMplsLspPathOperMTU,
        vRtrMplsLspPathRecordLabel,
        vRtrMplsLspPathTimeUp,
        vRtrMplsLspPathTimeDown,
        vRtrMplsLspPathRetryAttempts,
        vRtrMplsLspPathTransitionCount,
        vRtrMplsLspPathCspfQueries,
        vRtrMplsLspPathLastResigAttempt,
        vRtrMplsLspPathMetric,
        vRtrMplsLspPathLastMBBType,
        vRtrMplsLspPathLastMBBEnd,
        vRtrMplsLspPathLastMBBMetric,
        vRtrMplsLspPathLastMBBState,
        vRtrMplsLspPathMBBTypeInProg,
        vRtrMplsLspPathMBBStarted,
        vRtrMplsLspPathMBBNextRetry,
        vRtrMplsLspPathMBBRetryAttempts,
        vRtrMplsLspPathMBBFailCode,
        vRtrMplsLspPathMBBFailNodeArType,
        vRtrMplsLspPathMBBFailNodeAddr,
        vRtrMplsGeneralLastChange,
        vRtrMplsGeneralAdminState,
        vRtrMplsGeneralOperState,
        vRtrMplsGeneralNewLspIndex,
        vRtrMplsGeneralOptimizeTimer,
        vRtrMplsGeneralFRObject,
        vRtrMplsGeneralResignalTimer,
        vRtrMplsGeneralStaticLspOriginate,
        vRtrMplsGeneralStaticLspTransit,
        vRtrMplsGeneralStaticLspTerminate,
        vRtrMplsGeneralDynamicLspOriginate,
        vRtrMplsGeneralDynamicLspTransit,
        vRtrMplsGeneralDynamicLspTerminate,
        vRtrMplsGeneralDetourLspOriginate,
        vRtrMplsGeneralDetourLspTransit,
        vRtrMplsGeneralDetourLspTerminate,
        vRtrMplsGeneralHoldTimer,
        vRtrMplsGeneralDynamicBypass,
        vRtrMplsGeneralNextResignal,
        vRtrMplsGeneralOperDownReason,
        vRtrMplsGeneralSrlgFrr,
        vRtrMplsGeneralSrlgFrrStrict,
        vRtrMplsLspTemplatePropAdmGrp,
        vRtrMplsLabelMaxStaticLspLabels,
        vRtrMplsLabelMaxStaticSvcLabels,
        vRtrMplsS2lSubLspInterArea,
        vRtrMplsGenP2pActPathFastRetry,
        vRtrMplsGenP2mpS2lFastRetry,
        vRtrMplsS2lSubLspIsFastRetry,
        vRtrMplsLspPathTimeoutIn,
        vRtrMplsLspPathMBBTimeoutIn,
        vRtrMplsS2lSubLspTimeoutIn,
        vRtrMplsS2lSubLspMBBTimeoutIn,
        vRtrMplsLspPathOperSetupPriority,
        vRtrMplsLspPathOperHoldPriority,
        vRtrMplsLspPathOperRecord,
        vRtrMplsLspPathOperRecordLabel,
        vRtrMplsLspPathOperHopLimit,
        vRtrMplsLspPathOperAdminGrpIncl,
        vRtrMplsLspPathOperAdminGrExcld,
        vRtrMplsLspPathOperCspf,
        vRtrMplsLspPathOperLeastFill,
        vRtrMplsLspPathOperRsvpAdspec,
        vRtrMplsLspPathOperFRNodeProtect,
        vRtrMplsLspPathOperPropAdminGrp,
        vRtrMplsLspPathOperFRHopLimit,
        vRtrMplsGenLspInitRetryTimeout,
        vRtrMplsLspIgpShortcutLfaType,
        vRtrMplsLoggerEventBundling,
        vRtrMplsGenIssuMplsLockdown,
        vRtrMplsLspPropAdminGroup,
        vRtrMplsLspIgpShortcutRelOffset
    }
    STATUS      obsolete
    DESCRIPTION
        "The group of all global objects in MPLS supporting management of MPLS
         features on Nokia SROS series systems 11.0 release."
    ::= { tmnxMplsGroups 52 }

tmnxMplsV11v0ObsoleteGroup       OBJECT-GROUP
    OBJECTS     {
        vRtrMplsLspDecrementTtl,
        vRtrMplsLspClassOfService,
        vRtrMplsLspPathCos,
        vRtrMplsLspPathCosSource,
        vRtrMplsLspPathClassOfService,
        vRtrMplsLspBwProtect,
        vRtrMplsLspPathBwProtect,
        vRtrMplsLspPreference,
        vRtrMplsLspPathSharing,
        vRtrMplsGeneralPropagateTtl,
        vRtrMplsGeneralTE,
        vRtrMplsLspPathOperCspfToFrstLs,
        vRtrMplsLspCspfToFirstLoose
    }
    STATUS      current
    DESCRIPTION
        "The group of obsolete objects which are no longer supported in MPLS
         11.0R1 release onwards on Nokia SROS series systems."
    ::= { tmnxMplsGroups 53 }

tmnxMplsLspTemplateGroup         OBJECT-GROUP
    OBJECTS     {
        vRtrMplsLspTemplateBgpShortcut,
        vRtrMplsLspTemplateIgpShortcut,
        vRtrMplsLspTemplateLdpOverRsvp,
        vRtrMplsLspTemplateLeastFill,
        vRtrMplsLspTemplateMetric,
        vRtrMplsLspTemplateSetupPriority,
        vRtrMplsLspTemplateHoldPriority,
        vRtrMplsLspTemplateVprnAutoBind,
        vRtrMplsLspTempIgpSCutLfaType,
        vRtrMplsLspTempIgpSCutRelOffset,
        vRtrMplsLspTempAutoBandwidth,
        vRtrMplsLspTempFRNodeProtect,
        vRtrMplsLspTempAutoBWTblLastChg,
        vRtrMplsLspTempAutoBWLastChg,
        vRtrMplsLspTempAutoBWAdjDNPer,
        vRtrMplsLspTempAutoBWAdjDNMbps,
        vRtrMplsLspTempAutoBWAdjUPPer,
        vRtrMplsLspTempAutoBWAdjUPMbps,
        vRtrMplsLspTempAutoBWMaxBW,
        vRtrMplsLspTempAutoBWMinBW,
        vRtrMplsLspTempAutoBWMntrBW,
        vRtrMplsLspTempAutoBWAdjMult,
        vRtrMplsLspTempAutoBWOverFlow,
        vRtrMplsLspTempAutoBWOvrFlwThr,
        vRtrMplsLspTempAutoBWOvrFlwBW,
        vRtrMplsLspTempAutoBWSampMult,
        vRtrMplsLspTempAutoBWSampTime,
        vRtrMplsLspTempAutoBWInherit,
        vRtrMplsLspTemplateEgrStats,
        vRtrMplsLspTempCollectStats,
        vRtrMplsLspTempAccntingPolicy,
        vRtrMplsTemplPlcyBindTblLastChg,
        vRtrMplsLspTemplPlcyBindLastChg,
        vRtrMplsLspTemplPlcyBindRowStat,
        vRtrMplsLspTemplPlcyBind1,
        vRtrMplsLspTemplPlcyBind2,
        vRtrMplsLspTemplPlcyBind3,
        vRtrMplsLspTemplPlcyBind4,
        vRtrMplsLspTemplPlcyBind5,
        vRtrMplsLspTemplPlcyBindOneHop,
        vRtrMplsLspTempAutoBWBeWeight,
        vRtrMplsLspTempAutoBWL2Weight,
        vRtrMplsLspTempAutoBWAfWeight,
        vRtrMplsLspTempAutoBWL1Weight,
        vRtrMplsLspTempAutoBWH2Weight,
        vRtrMplsLspTempAutoBWEfWeight,
        vRtrMplsLspTempAutoBWH1Weight,
        vRtrMplsLspTempAutoBWNcWeight,
        vRtrMplsLspTemplateFromAddrType,
        vRtrMplsLspTemplateFromAddr,
        vRtrMplsLspTemplateClassType,
        vRtrMplsLspTempBkupClassType,
        vRtrMplsLspTempBgpTransportTunn,
        vRtrMplsLspTempMainCTRetryLimit,
        vRtrMplsLspTemplateRsvpAdspec
    }
    STATUS      current
    DESCRIPTION
        "The group of objects in MPLS supporting management of Lsp Template."
    ::= { tmnxMplsGroups 54 }

tmnxMplsNotifyV11v0Group         NOTIFICATION-GROUP
    NOTIFICATIONS {
        vRtrMplsLblRangeModify
    }
    STATUS      obsolete
    DESCRIPTION
        "The group of notifications supporting the extended MPLS feature on
         Nokia SROS series systems 11.0 Release."
    ::= { tmnxMplsGroups 55 }

tmnxMplsLspAutoBWFcWtGroup       OBJECT-GROUP
    OBJECTS     {
        vRtrMplsLspAutoBWBeWeight,
        vRtrMplsLspAutoBWL2Weight,
        vRtrMplsLspAutoBWAfWeight,
        vRtrMplsLspAutoBWL1Weight,
        vRtrMplsLspAutoBWH2Weight,
        vRtrMplsLspAutoBWEfWeight,
        vRtrMplsLspAutoBWH1Weight,
        vRtrMplsLspAutoBWNcWeight
    }
    STATUS      current
    DESCRIPTION
        "The group of objects in MPLS supporting management of Forwarding Class
         Weights for Lsp Auto Bandwidth on Nokia SROS series systems."
    ::= { tmnxMplsGroups 56 }

tmnxMplsGlobalV11v0R4Group       OBJECT-GROUP
    OBJECTS     {
        vRtrMplsLspStatsTpOnly,
        vRtrMplsGeneralMeshP2pOriginate,
        vRtrMplsGeneralOneHopP2pOrigin,
        vRtrMplsGenRetryOnIgpOverload
    }
    STATUS      current
    DESCRIPTION
        "The group of all global objects in MPLS supporting management of MPLS
         features on Nokia SROS series systems 11.0 R4 release."
    ::= { tmnxMplsGroups 57 }

tmnxMplsV12v0ObsoleteGroup       OBJECT-GROUP
    OBJECTS     {
        vRtrMplsLspBandwidth
    }
    STATUS      current
    DESCRIPTION
        "The group of obsolete objects which are no longer supported in MPLS
         12.0R1 release onwards on Nokia SROS series systems."
    ::= { tmnxMplsGroups 58 }

tmnxMplsNotifyObjsIgpOverload    OBJECT-GROUP
    OBJECTS     {
        vRtrMplsIgpOverloadRtrAddrType,
        vRtrMplsIgpOverloadRtrAddr,
        vRtrMplsIgpOverloadIgpType
    }
    STATUS      current
    DESCRIPTION
        "The group of notification objects supporting IGP shortcut notification
         feature on Nokia SROS series systems 11.0 Release."
    ::= { tmnxMplsGroups 59 }

tmnxMplsIgpOverloadNotify        NOTIFICATION-GROUP
    NOTIFICATIONS {
        vRtrMplsNodeInIgpOverload
    }
    STATUS      current
    DESCRIPTION
        "The group of notifications supporting IGP shortcut notification
         feature on Nokia SROS series systems 11.0 Release."
    ::= { tmnxMplsGroups 60 }

tmnxMplsLspTempInStatsGroup      OBJECT-GROUP
    OBJECTS     {
        vRtrMplsLspTempInStatTblLstChg,
        vRtrMplsLspTempInStatRowStatus,
        vRtrMplsLspTempInStatLastChanged,
        vRtrMplsLspTempInStatCollectStat,
        vRtrMplsLspTempInStatAccntPolicy,
        vRtrMplsLspTempInStatAdminState,
        vRtrMplsLspTempInStatMaxStats,
        vRtrMplsLspStatsLspType,
        vRtrMplsLspTempInStatTotlSession,
        vRtrMplsLspStatsEgrIndexUnAvail
    }
    STATUS      current
    DESCRIPTION
        "The group of notification supporting MPLS Ingress Statistics for
         Template Based Label Switched Path (LSP) on Nokia SROS series systems
         12.0 Release."
    ::= { tmnxMplsGroups 61 }

tmnxMplsAutoBwUnderflowGroup     OBJECT-GROUP
    OBJECTS     {
        vRtrMplsLspAutoBWUnderFlow,
        vRtrMplsLspAutoBWUndFlwThreshold,
        vRtrMplsLspAutoBWUndFlwBW,
        vRtrMplsLspAutoBWUndFlwCount,
        vRtrMplsLspAutoBWMaxUndFlwBw,
        vRtrMplsLspTempAutoBWUnderFlow,
        vRtrMplsLspTempAutoBWUndFlwThr,
        vRtrMplsLspTempAutoBWUndFlwBW
    }
    STATUS      current
    DESCRIPTION
        "The group of notification supporting MPLS Auto-Bandwidth underflow on
         Nokia SROS series systems 12.0 Release."
    ::= { tmnxMplsGroups 62 }

tmnxMplsBgpLabelRetentionGroup   OBJECT-GROUP
    OBJECTS     {
        vRtrMplsLabelBgpLabelsHoldTimer
    }
    STATUS      current
    DESCRIPTION
        "The group of notification supporting MPLS BGP Label Retention on Nokia
         SROS series systems 12.0 Release."
    ::= { tmnxMplsGroups 63 }

tmnxMplsGlobalV12v0Group         OBJECT-GROUP
    OBJECTS     {
        vRtrMplsTunnelCHopUnnumIfID,
        vRtrMplsTunnelCHopRtrID,
        vRtrMplsTunnelCHopIsABR,
        vRtrMplsTunnelARHopUnnumIfID,
        vRtrMplsLspTemplatePropAdmGrp,
        vRtrMplsLabelMaxStaticLspLabels,
        vRtrMplsLabelMaxStaticSvcLabels,
        vRtrMplsS2lSubLspInterArea,
        vRtrMplsS2lSubLspIsFastRetry,
        vRtrMplsS2lSubLspTimeoutIn,
        vRtrMplsS2lSubLspMBBTimeoutIn,
        vRtrMplsLoggerEventBundling,
        vRtrMplsLspIgpShortcutRelOffset
    }
    STATUS      obsolete
    DESCRIPTION
        "The group of all global objects in MPLS supporting management of MPLS
         features on Nokia SROS series systems 12.0 release."
    ::= { tmnxMplsGroups 64 }

tmnxMplsBypassOptGroup           OBJECT-GROUP
    OBJECTS     {
        vRtrMplsGeneralBypassResigTimer,
        vRtrMplsGenBypassNextResignal
    }
    STATUS      current
    DESCRIPTION
        "The group of objects supporting MPLS Bypass Optimization on Nokia SROS
         series systems 12.0 Release."
    ::= { tmnxMplsGroups 65 }

tmnxMplsGenV12v0Group            OBJECT-GROUP
    OBJECTS     {
        vRtrMplsGeneralLastChange,
        vRtrMplsGeneralAdminState,
        vRtrMplsGeneralOperState,
        vRtrMplsGeneralNewLspIndex,
        vRtrMplsGeneralOptimizeTimer,
        vRtrMplsGeneralFRObject,
        vRtrMplsGeneralResignalTimer,
        vRtrMplsGeneralStaticLspOriginate,
        vRtrMplsGeneralStaticLspTransit,
        vRtrMplsGeneralStaticLspTerminate,
        vRtrMplsGeneralDynamicLspOriginate,
        vRtrMplsGeneralDynamicLspTransit,
        vRtrMplsGeneralDynamicLspTerminate,
        vRtrMplsGeneralDetourLspOriginate,
        vRtrMplsGeneralDetourLspTransit,
        vRtrMplsGeneralDetourLspTerminate,
        vRtrMplsGeneralHoldTimer,
        vRtrMplsGeneralDynamicBypass,
        vRtrMplsGeneralNextResignal,
        vRtrMplsGeneralOperDownReason,
        vRtrMplsGeneralSrlgFrr,
        vRtrMplsGeneralSrlgFrrStrict,
        vRtrMplsGenMbbPrefCurrentHops,
        vRtrMplsGenP2pActPathFastRetry,
        vRtrMplsGenP2mpS2lFastRetry,
        vRtrMplsGenLspInitRetryTimeout,
        vRtrMplsGenIssuMplsLockdown
    }
    STATUS      current
    DESCRIPTION
        "The group of all general objects in MPLS supporting management of MPLS
         features on Nokia SROS series systems 12.0 release."
    ::= { tmnxMplsGroups 66 }

tmnxMplsLSPPathV12v0Group        OBJECT-GROUP
    OBJECTS     {
        vRtrMplsLspPathTableSpinlock,
        vRtrMplsLspPathRowStatus,
        vRtrMplsLspPathLastChange,
        vRtrMplsLspPathType,
        vRtrMplsLspPathProperties,
        vRtrMplsLspPathBandwidth,
        vRtrMplsLspPathState,
        vRtrMplsLspPathPreference,
        vRtrMplsLspPathSetupPriority,
        vRtrMplsLspPathHoldPriority,
        vRtrMplsLspPathRecord,
        vRtrMplsLspPathHopLimit,
        vRtrMplsLspPathAdminState,
        vRtrMplsLspPathOperState,
        vRtrMplsLspPathInheritance,
        vRtrMplsLspPathLspId,
        vRtrMplsLspPathRetryTimeRemaining,
        vRtrMplsLspPathTunnelARHopListIndex,
        vRtrMplsLspPathNegotiatedMTU,
        vRtrMplsLspPathFailCode,
        vRtrMplsLspPathFailNodeAddr,
        vRtrMplsLspPathAdminGroupInclude,
        vRtrMplsLspPathAdminGroupExclude,
        vRtrMplsLspPathAdaptive,
        vRtrMplsLspPathOptimizeTimer,
        vRtrMplsLspPathNextOptimize,
        vRtrMplsLspPathOperBandwidth,
        vRtrMplsLspPathResignal,
        vRtrMplsLspPathTunnelCRHopListIndex,
        vRtrMplsLspPathOperMTU,
        vRtrMplsLspPathRecordLabel,
        vRtrMplsLspPathTimeUp,
        vRtrMplsLspPathTimeDown,
        vRtrMplsLspPathRetryAttempts,
        vRtrMplsLspPathTransitionCount,
        vRtrMplsLspPathCspfQueries,
        vRtrMplsLspPathLastResigAttempt,
        vRtrMplsLspPathMetric,
        vRtrMplsLspPathLastMBBType,
        vRtrMplsLspPathLastMBBEnd,
        vRtrMplsLspPathLastMBBMetric,
        vRtrMplsLspPathLastMBBState,
        vRtrMplsLspPathMBBTypeInProg,
        vRtrMplsLspPathMBBStarted,
        vRtrMplsLspPathMBBNextRetry,
        vRtrMplsLspPathMBBRetryAttempts,
        vRtrMplsLspPathMBBFailCode,
        vRtrMplsLspPathMBBFailNodeArType,
        vRtrMplsLspPathMBBFailNodeAddr,
        vRtrMplsLspPathOperInterArea,
        vRtrMplsLspPathChanges,
        vRtrMplsLspPathTimeoutIn,
        vRtrMplsLspPathMBBTimeoutIn,
        vRtrMplsLspPathOperSetupPriority,
        vRtrMplsLspPathOperHoldPriority,
        vRtrMplsLspPathOperRecord,
        vRtrMplsLspPathOperRecordLabel,
        vRtrMplsLspPathOperHopLimit,
        vRtrMplsLspPathOperAdminGrpIncl,
        vRtrMplsLspPathOperAdminGrExcld,
        vRtrMplsLspPathOperCspf,
        vRtrMplsLspPathOperLeastFill,
        vRtrMplsLspPathOperRsvpAdspec,
        vRtrMplsLspPathOperFRNodeProtect,
        vRtrMplsLspPathOperPropAdminGrp,
        vRtrMplsLspPathOperFRHopLimit
    }
    STATUS      obsolete
    DESCRIPTION
        "The group of all LSP Path objects in MPLS supporting management of
         MPLS features on Nokia SROS series systems 12.0 release."
    ::= { tmnxMplsGroups 67 }

tmnxMplsLSPV12v0Group            OBJECT-GROUP
    OBJECTS     {
        vRtrMplsLspRowStatus,
        vRtrMplsLspLastChange,
        vRtrMplsLspName,
        vRtrMplsLspAdminState,
        vRtrMplsLspOperState,
        vRtrMplsLspFromAddr,
        vRtrMplsLspToAddr,
        vRtrMplsLspType,
        vRtrMplsLspOutSegIndx,
        vRtrMplsLspRetryTimer,
        vRtrMplsLspRetryLimit,
        vRtrMplsLspMetric,
        vRtrMplsLspCspf,
        vRtrMplsLspFastReroute,
        vRtrMplsLspFRHopLimit,
        vRtrMplsLspFRBandwidth,
        vRtrMplsLspSetupPriority,
        vRtrMplsLspHoldPriority,
        vRtrMplsLspRecord,
        vRtrMplsLspHopLimit,
        vRtrMplsLspNegotiatedMTU,
        vRtrMplsLspRsvpResvStyle,
        vRtrMplsLspRsvpAdspec,
        vRtrMplsLspFRMethod,
        vRtrMplsLspFRNodeProtect,
        vRtrMplsLspAdminGroupInclude,
        vRtrMplsLspAdminGroupExclude,
        vRtrMplsLspAdaptive,
        vRtrMplsLspInheritance,
        vRtrMplsLspOptimizeTimer,
        vRtrMplsLspOperFastReroute,
        vRtrMplsLspFRObject,
        vRtrMplsLspOctets,
        vRtrMplsLspPackets,
        vRtrMplsLspAge,
        vRtrMplsLspTimeUp,
        vRtrMplsLspTimeDown,
        vRtrMplsLspPrimaryTimeUp,
        vRtrMplsLspTransitions,
        vRtrMplsLspLastTransition,
        vRtrMplsLspLastPathChange,
        vRtrMplsLspConfiguredPaths,
        vRtrMplsLspStandbyPaths,
        vRtrMplsLspOperationalPaths,
        vRtrMplsLspHoldTimer,
        vRtrMplsLspIgpShortcutLfaType,
        vRtrMplsLspPropAdminGroup,
        vRtrMplsLspIgpShortcutRelOffset,
        vRtrMplsLspRevertTimer,
        vRtrMplsLspRevertTimeRemain
    }
    STATUS      obsolete
    DESCRIPTION
        "The group of all LSP objects in MPLS supporting management of MPLS
         features on Nokia SROS series systems 12.0 release."
    ::= { tmnxMplsGroups 68 }

tmnxMplsObsoleteNotifyV12Group   NOTIFICATION-GROUP
    NOTIFICATIONS {
        vRtrMplsLblRangeModify
    }
    STATUS      current
    DESCRIPTION
        "The group of obsolete notifications supporting management of the MPLS
         operations on Nokia 7xxx SR series systems."
    ::= { tmnxMplsGroups 69 }

tmnxMplsLoadBalanceWtV13v0Group  OBJECT-GROUP
    OBJECTS     {
        vRtrMplsLspLoadBalancingWeight,
        vRtrMplsLspTempLoadBalancingWt
    }
    STATUS      current
    DESCRIPTION
        "The group of all objects in MPLS supporting management of load
         balancing on Nokia SROS series systems 13.0 release."
    ::= { tmnxMplsGroups 70 }

tmnxMplsLabelSegRouteV13v0Group  OBJECT-GROUP
    OBJECTS     {
        vRtrMplsLabelSegRouteStartLabel,
        vRtrMplsLabelSegRouteEndLabel
    }
    STATUS      current
    DESCRIPTION
        "The group of all objects in MPLS supporting management of segment
         routing labels on Nokia SROS series systems 13.0 release."
    ::= { tmnxMplsGroups 71 }

tmnxMplsLabelStaticRgeV13v0Group OBJECT-GROUP
    OBJECTS     {
        vRtrMplsLabelStaticLabelRange
    }
    STATUS      current
    DESCRIPTION
        "The group of all objects in MPLS supporting management of static label
         range on Nokia SROS series systems 13.0 release."
    ::= { tmnxMplsGroups 72 }

tmnxMpls13v0ObsoleteGroup        OBJECT-GROUP
    OBJECTS     {
        vRtrMplsLabelMaxStaticLspLabels,
        vRtrMplsLabelMaxStaticSvcLabels
    }
    STATUS      current
    DESCRIPTION
        "The group of obsolete objects which are no longer supported in MPLS
         13.0R1 release onwards on Nokia SROS series systems."
    ::= { tmnxMplsGroups 73 }

tmnxMplsGlobalV13v0Group         OBJECT-GROUP
    OBJECTS     {
        vRtrMplsTunnelCHopUnnumIfID,
        vRtrMplsTunnelCHopRtrID,
        vRtrMplsTunnelCHopIsABR,
        vRtrMplsTunnelARHopUnnumIfID,
        vRtrMplsLspTemplatePropAdmGrp,
        vRtrMplsS2lSubLspInterArea,
        vRtrMplsS2lSubLspIsFastRetry,
        vRtrMplsS2lSubLspTimeoutIn,
        vRtrMplsS2lSubLspMBBTimeoutIn,
        vRtrMplsLoggerEventBundling,
        vRtrMplsLspIgpShortcutRelOffset
    }
    STATUS      current
    DESCRIPTION
        "The group of all global objects in MPLS supporting management of MPLS
         features on Nokia SROS series systems 12.0 release."
    ::= { tmnxMplsGroups 74 }

tmnxMplsClassBasedFwdV13v0Group  OBJECT-GROUP
    OBJECTS     {
        vRtrMplsLspClassFwdingEnabled,
        vRtrMplsLspFC,
        vRtrMplsLspTempClassFwdEnabled,
        vRtrMplsLspTempFC
    }
    STATUS      obsolete
    DESCRIPTION
        "The group of all objects in MPLS supporting class based forwarding on
         Nokia SROS series systems 13.0 release."
    ::= { tmnxMplsGroups 75 }

tmnxMplsBfdOnLspV13v0Group       OBJECT-GROUP
    OBJECTS     {
        vRtrMplsLspBfdTemplateName,
        vRtrMplsLspBfdEnable,
        vRtrMplsLspBfdPingIntvl,
        vRtrMplsLspPathBfdTemplateName,
        vRtrMplsLspPathBfdEnable,
        vRtrMplsLspPathBfdPingIntvl,
        vRtrMplsLspTempBfdTemplateName,
        vRtrMplsLspTempBfdEnable,
        vRtrMplsLspTempBfdPingIntvl
    }
    STATUS      current
    DESCRIPTION
        "The group of objects in MPLS supporting management of MPLS features on
         Nokia SROS series systems 13.0 release."
    ::= { tmnxMplsGroups 76 }

tmnxMplsAdminGroupObsoleteGroup  OBJECT-GROUP
    OBJECTS     {
        vRtrMplsAdminGroupRowStatus,
        vRtrMplsAdminGroupValue
    }
    STATUS      current
    DESCRIPTION
        "The group of obsolete objects which are no longer supported in MPLS
         14.0R1 release onwards on Nokia SROS series systems."
    ::= { tmnxMplsGroups 77 }

tmnxMplsIfSrlgV14v0Group         OBJECT-GROUP
    OBJECTS     {
        vRtrMplsIfSrlgGrpTblLastChanged,
        vRtrMplsIfSrlgGrpRowStatus,
        vRtrMplsIfSrlgGrpLastChanged
    }
    STATUS      current
    DESCRIPTION
        "The group of objects supporting management of SRLG on Nokia 7xxx SR
         series systems release 6.0."
    ::= { tmnxMplsGroups 78 }

tmnxMplsSrlgObsoleteGroup        OBJECT-GROUP
    OBJECTS     {
        vRtrMplsSrlgGrpTableLastChanged,
        vRtrMplsSrlgGrpRowStatus,
        vRtrMplsSrlgGrpLastChanged,
        vRtrMplsSrlgGrpValue
    }
    STATUS      current
    DESCRIPTION
        "The group of objects supporting management of SRLG on Nokia 7xxx SR
         series systems release 6.0."
    ::= { tmnxMplsGroups 79 }

tmnxMplsSegRouting14v0Group      OBJECT-GROUP
    OBJECTS     {
        vRtrMplsGeneralNewLspSRIndex,
        vRtrMplsGeneralSrTeLspOriginate,
        vRtrMplsGeneralPceReport,
        vRtrMplsLspExtPceCompute,
        vRtrMplsLspExtPceControl,
        vRtrMplsLspExtPceReport,
        vRtrMplsLspExtTtmTunnelId,
        vRtrMplsLspExtMaxSrLabels,
        vRtrMplsLspExtTunnelId,
        vRtrMplsLspPathProfTblLstChg,
        vRtrMplsLspPathProfRowStatus,
        vRtrMplsLspPathProfLastChange,
        vRtrMplsLspPathProfGroupId,
        vRtrMplsLspPathLastUpdateTime,
        vRtrMplsLspPathLastUpdateId,
        vRtrMplsLspPathLastUpdateState,
        vRtrMplsLspPathLastUpdFailCode
    }
    STATUS      obsolete
    DESCRIPTION
        "The group of objects in MPLS supporting Segment Routing TE of MPLS
         features on Nokia SROS series systems 14.0 release."
    ::= { tmnxMplsGroups 80 }

tmnxMplsEntropyLabel14v0Group    OBJECT-GROUP
    OBJECTS     {
        vRtrMplsGeneralEntropyLblRsvpTe,
        vRtrMplsLspExtEntropyLabel,
        vRtrMplsLspExtOperEntropyLabel,
        vRtrMplsLspExtNegEntropyLbl
    }
    STATUS      current
    DESCRIPTION
        "The group of objects in MPLS supporting entropy label of MPLS features
         on Nokia SROS series systems 14.0 release."
    ::= { tmnxMplsGroups 81 }

tmnxMplsLspTemplEL14v4Group      OBJECT-GROUP
    OBJECTS     {
        vRtrMplsLspTempEntropyLabel
    }
    STATUS      current
    DESCRIPTION
        "The group of objects in MPLS supporting entropy label of MPLS features
         on Nokia SROS series systems 14.0 release."
    ::= { tmnxMplsGroups 82 }

tmnxMplsSRLfaOvrhd14v4Group      OBJECT-GROUP
    OBJECTS     {
        vRtrMplsLspExtFrrOverheadLabel
    }
    STATUS      current
    DESCRIPTION
        "The group of objects in MPLS supporting segment routing MPLS features
         on Nokia SROS series systems 14.0 release."
    ::= { tmnxMplsGroups 83 }

tmnxMplsLspTempPceReportGroup    OBJECT-GROUP
    OBJECTS     {
        vRtrMplsLspTemplatePceReport
    }
    STATUS      current
    DESCRIPTION
        "The group of objects in MPLS supporting management of PCE Reporting
         features on Nokia SROS series systems 15.0 release."
    ::= { tmnxMplsGroups 84 }

tmnxMplsLspTempSrLbl15v0Group    OBJECT-GROUP
    OBJECTS     {
        vRtrMplsLspTempMaxSrLabels,
        vRtrMplsLspTempFrrOverheadLabel
    }
    STATUS      current
    DESCRIPTION
        "The group of objects in MPLS supporting segment routing labels of MPLS
         features on Nokia SROS series systems 15.0 release."
    ::= { tmnxMplsGroups 85 }

tmnxMplsBfdFailureActionGroup    OBJECT-GROUP
    OBJECTS     {
        vRtrMplsLspExtBfdFailureAction,
        vRtrMplsLspTempBfdFailureAction
    }
    STATUS      current
    DESCRIPTION
        "The group of objects in MPLS supporting management of BFD Failure
         Action features on Nokia SROS series systems 15.0 release."
    ::= { tmnxMplsGroups 86 }

tmnxMplsClassFwdPlcy15v0Group    OBJECT-GROUP
    OBJECTS     {
        vRtrMplsClassFwdPlcyTblLstChg,
        vRtrMplsClassFwdPlcyRowStatus,
        vRtrMplsClassFwdPlcyLastChanged,
        vRtrMplsClassFwdPlcyDefSetId,
        vRtrMplsClassFwdPlcyRefCount,
        vRtrMplsClassFwdPlcyFCTblLstChg,
        vRtrMplsClassFwdPlcyFCSetId,
        vRtrMplsLspExtCbfFwdingPlcy,
        vRtrMplsLspExtCbfFwdingSet,
        vRtrMplsLspTempCbfFwdingPlcy,
        vRtrMplsLspTempCbfFwdingSet
    }
    STATUS      current
    DESCRIPTION
        "The group of objects in MPLS supporting Class Based Forwarding Policy
         in LSP and LSP Template on Nokia SROS series systems 15.0 release."
    ::= { tmnxMplsGroups 87 }

tmnxMplsP2PSrTe15v0Group         OBJECT-GROUP
    OBJECTS     {
        vRtrMplsGenMeshP2PSrTeLspOrig,
        vRtrMplsGenOneHopP2PSrTeLspOrig
    }
    STATUS      current
    DESCRIPTION
        "The group of objects in MPLS supporting P2P Segment Routing TE of MPLS
         features on Nokia SROS series systems 15.0 release."
    ::= { tmnxMplsGroups 88 }

tmnxMplsLspStatsGroup            OBJECT-GROUP
    OBJECTS     {
        vRtrMplsLspAggregatePkts,
        vRtrMplsLspAggregateOctets
    }
    STATUS      current
    DESCRIPTION
        "The group of objects in MPLS supporting management of LSP Statistics
         on Nokia SROS series systems 15.0 release."
    ::= { tmnxMplsGroups 89 }

tmnxMplsTunnelARHopSIDGroup      OBJECT-GROUP
    OBJECTS     {
        vRtrMplsTunnelARHopSIDType
    }
    STATUS      current
    DESCRIPTION
        "The group of objects in MPLS supporting management of Tunnel AR Hop
         Statistics on Nokia SROS series systems 15.0 release."
    ::= { tmnxMplsGroups 90 }

tmnxMplsLSPV15v0Group            OBJECT-GROUP
    OBJECTS     {
        vRtrMplsLspRowStatus,
        vRtrMplsLspLastChange,
        vRtrMplsLspName,
        vRtrMplsLspAdminState,
        vRtrMplsLspOperState,
        vRtrMplsLspFromAddr,
        vRtrMplsLspToAddr,
        vRtrMplsLspType,
        vRtrMplsLspOutSegIndx,
        vRtrMplsLspRetryTimer,
        vRtrMplsLspRetryLimit,
        vRtrMplsLspMetric,
        vRtrMplsLspCspf,
        vRtrMplsLspFastReroute,
        vRtrMplsLspFRHopLimit,
        vRtrMplsLspFRBandwidth,
        vRtrMplsLspSetupPriority,
        vRtrMplsLspHoldPriority,
        vRtrMplsLspRecord,
        vRtrMplsLspHopLimit,
        vRtrMplsLspNegotiatedMTU,
        vRtrMplsLspRsvpResvStyle,
        vRtrMplsLspRsvpAdspec,
        vRtrMplsLspFRMethod,
        vRtrMplsLspFRNodeProtect,
        vRtrMplsLspAdminGroupInclude,
        vRtrMplsLspAdminGroupExclude,
        vRtrMplsLspAdaptive,
        vRtrMplsLspInheritance,
        vRtrMplsLspOptimizeTimer,
        vRtrMplsLspOperFastReroute,
        vRtrMplsLspFRObject,
        vRtrMplsLspAge,
        vRtrMplsLspTimeUp,
        vRtrMplsLspTimeDown,
        vRtrMplsLspPrimaryTimeUp,
        vRtrMplsLspTransitions,
        vRtrMplsLspLastTransition,
        vRtrMplsLspLastPathChange,
        vRtrMplsLspConfiguredPaths,
        vRtrMplsLspStandbyPaths,
        vRtrMplsLspOperationalPaths,
        vRtrMplsLspHoldTimer,
        vRtrMplsLspIgpShortcutLfaType,
        vRtrMplsLspPropAdminGroup,
        vRtrMplsLspIgpShortcutRelOffset,
        vRtrMplsLspRevertTimer,
        vRtrMplsLspRevertTimeRemain
    }
    STATUS      obsolete
    DESCRIPTION
        "The group of all LSP objects in MPLS supporting management of MPLS
         features on Nokia SROS series systems 15.0 release."
    ::= { tmnxMplsGroups 91 }

tmnxMplsLSPV15v0ObsoleteGroup    OBJECT-GROUP
    OBJECTS     {
        vRtrMplsLspOctets,
        vRtrMplsLspPackets
    }
    STATUS      current
    DESCRIPTION
        "The group of objects supporting management of SRLG on Nokia  SROS
         series systems obsoleted in release 15.0."
    ::= { tmnxMplsGroups 92 }

tmnxMplsEntropyLabelSrteGroup    OBJECT-GROUP
    OBJECTS     {
        vRtrMplsGeneralEntropyLblSrTe
    }
    STATUS      current
    DESCRIPTION
        "The group of objects in MPLS supporting management of Entropy Label on
         Nokia SROS series systems 15.0 release."
    ::= { tmnxMplsGroups 93 }

tmnxMplsReservedLblBlkGroup      OBJECT-GROUP
    OBJECTS     {
        vRtrMplsReservedLblBlkTblLastChg,
        vRtrMplsReservedLblBlkRowStatus,
        vRtrMplsReservedLblBlkLastChg,
        vRtrMplsReservedLblBlkStartLbl,
        vRtrMplsReservedLblBlkEndLbl
    }
    STATUS      current
    DESCRIPTION
        "The group of objects in MPLS supporting management of  reserved label
         blocks on Nokia SROS series systems 16.0 release."
    ::= { tmnxMplsGroups 94 }

tmnxMplsIfAltStatsGroup          OBJECT-GROUP
    OBJECTS     {
        vRtrMplsIfAltTxPktCount,
        vRtrMplsIfAltRxPktCount,
        vRtrMplsIfAltTxOctetCount,
        vRtrMplsIfAltRxOctetCount,
        vRtrMplsGeneralAuxStats
    }
    STATUS      current
    DESCRIPTION
        "The group of objects supporting management of extended MPLS
         capabilities on Nokia SROS series systems release 16.0."
    ::= { tmnxMplsGroups 95 }

vRtrMplsLspAdminTagGroup         OBJECT-GROUP
    OBJECTS     {
        vRtrMplsLspAdminTagTblLastChg,
        vRtrMplsLspAdminTagRowStatus,
        vRtrMplsLspAdminTagLastChanged,
        vRtrMplsLspTempAdminTagTblLstChg,
        vRtrMplsLspTempAdminTagRowStatus,
        vRtrMplsLspTempAdminTagLastChg
    }
    STATUS      current
    DESCRIPTION
        "The group of objects in MPLS supporting management of administrative
         tags in LSP on Nokia SROS series systems 16.0 release."
    ::= { tmnxMplsGroups 96 }

vRtrMplsFwdPlcyV16v0Group        OBJECT-GROUP
    OBJECTS     {
        vRtrMplsFwdPlcyTblLastChg,
        vRtrMplsFwdPlcyRowStatus,
        vRtrMplsFwdPlcyLastChanged,
        vRtrMplsFwdPlcyAdminState,
        vRtrMplsFwdPlcyOperState,
        vRtrMplsFwdPlcyBindingLabel,
        vRtrMplsFwdPlcyEndpointAddrType,
        vRtrMplsFwdPlcyEndpointAddr,
        vRtrMplsFwdPlcyRevertTimer,
        vRtrMplsFwdPlcyPreference,
        vRtrMplsFwdPlcyNHGrpTblLastChg,
        vRtrMplsFwdPlcyNHGrpRowStatus,
        vRtrMplsFwdPlcyNHGrpLastChanged,
        vRtrMplsFwdPlcyNHGrpAdminState,
        vRtrMplsFwdPlcyNHGrpOperState,
        vRtrMplsFwdPlcyNHGrpResType,
        vRtrMplsFwdPlcyNHGrpLoadBalWt,
        vRtrMplsFwdPlcyNhgNHTblLastChg,
        vRtrMplsFwdPlcyNhgNHRowStatus,
        vRtrMplsFwdPlcyNhgNHLastChanged,
        vRtrMplsFwdPlcyNhgNHOperState,
        vRtrMplsFwdPlcyNhgNHAddrType,
        vRtrMplsFwdPlcyNhgNHAddr,
        vRtrMplsFwdPlcyGenTblLastChg,
        vRtrMplsFwdPlcyGenRowStatus,
        vRtrMplsFwdPlcyGenLastChanged,
        vRtrMplsFwdPlcyGenAdminState,
        vRtrMplsFwdPlcyGenOperState,
        vRtrMplsFwdPlcyGenOperDownReason,
        vRtrMplsFwdPlcyGenReservedLblBlk,
        vRtrMplsFwdPlcyStatsTblLastChg,
        vRtrMplsFwdPlcyStatsRowStatus,
        vRtrMplsFwdPlcyStatsLastChanged,
        vRtrMplsFwdPlcyStatsAdminState,
        vRtrMplsBindLblPathName,
        vRtrMplsBindLblPathOperState,
        vRtrMplsBindLblPathLastOperChg,
        vRtrMplsBindLblOperDownReason,
        vRtrMplsBindLblPathNumNHGrpCnt,
        vRtrMplsBindLblPathRetryCount,
        vRtrMplsBindLblPathRetryTimeRem,
        vRtrMplsBindLblPathRevertTimer,
        vRtrMplsBindLblPathIngStatsEnabl,
        vRtrMplsBindLblPathPref,
        vRtrMplsBLPathIngStatOperState,
        vRtrMplsBindLblPathNhgOperState,
        vRtrMplsBindLblPathNHgResType,
        vRtrMplsBindLblPathNhgLoadBalWt,
        vRtrMplsBindLblPathNhgFailovrCnt,
        vRtrMplsBindLblPathNhgRevertCnt,
        vRtrMplsBindLblPathNhgRevTimeRem,
        vRtrMplsBindLblPathNhgNHAddrType,
        vRtrMplsBindLblPathNhgNHAddr,
        vRtrMplsBindLblPathNhgNHResolved,
        vRtrMplsBindLblPathNhgNHOutIf,
        vRtrMplsBindLblPathNhgDownReason,
        vRtrMplsBindLblPathNhgNHDownCode,
        vRtrMplsBindLblIngrAggPkts,
        vRtrMplsBindLblIngrAggOctets,
        vRtrMplsEndptPathName,
        vRtrMplsEndptPathOperState,
        vRtrMplsEndptPathLastOperChg,
        vRtrMplsEndptPathOperDownReason,
        vRtrMplsEndptPathNHGrpCnt,
        vRtrMplsEndptPathRetryCount,
        vRtrMplsEndptPathRetryTimeRem,
        vRtrMplsEndptPathRevertTimer,
        vRtrMplsEndptPathPref,
        vRtrMplsEndptPathTTMPref,
        vRtrMplsEndptPathNhgOperState,
        vRtrMplsEndptPathNhgResType,
        vRtrMplsEndptPathNhgLoadBalWt,
        vRtrMplsEndptPathNhgFailovrCnt,
        vRtrMplsEndptPathNhgRevertCnt,
        vRtrMplsEndptPathNhgRevTimeRem,
        vRtrMplsEndptPathNhgDownReason,
        vRtrMplsEndptPathNhgNHAddrType,
        vRtrMplsEndptPathNhgNHAddr,
        vRtrMplsEndptPathNhgNHResolved,
        vRtrMplsEndptPathNhgNHOutIf,
        vRtrMplsEndptPathNhgNHDownCode,
        vRtrMplsEndptPathMetric,
        vRtrMplsBindLblPathNHgNHPLabel,
        vRtrMplsEndptPathNhgNHPLabel,
        vRtrMplsBindLblPathNhgWeights,
        vRtrMplsEndptPathNhgWeights
    }
    STATUS      current
    DESCRIPTION
        "The group of objects in MPLS supporting management of Forwarding
         Policies on Nokia SROS series systems 16.0 release."
    ::= { tmnxMplsGroups 97 }

vRtrMplsFwdPlcyNhgNHPushLblGroup OBJECT-GROUP
    OBJECTS     {
        vRtrMplsFwdPlcyNhgNHPushLabel1,
        vRtrMplsFwdPlcyNhgNHPushLabel2,
        vRtrMplsFwdPlcyNhgNHPushLabel3,
        vRtrMplsFwdPlcyNhgNHPushLabel4,
        vRtrMplsFwdPlcyNhgNHPushLabel5,
        vRtrMplsFwdPlcyNhgNHPushLabel6,
        vRtrMplsFwdPlcyNhgNHPushLabel7,
        vRtrMplsFwdPlcyNhgNHPushLabel8,
        vRtrMplsFwdPlcyNhgNHPushLabel9,
        vRtrMplsFwdPlcyNhgNHPushLabel10,
        vRtrMplsFwdPlcyMetric,
        vRtrMplsFwdPlcyTtmPreference
    }
    STATUS      current
    DESCRIPTION
        "The group of objects in MPLS supporting management of
          Pushed-Labels on Nokia SROS series systems 16.0 release."
    ::= { tmnxMplsGroups 98 }

vRtrMplsPceInitSrteGroup         OBJECT-GROUP
    OBJECTS     {
        vRtrMplsLspTemplateId,
        vRtrMplsPceInitGenTblLastChg,
        vRtrMplsPceInitGenRowStatus,
        vRtrMplsPceInitGenSrte,
        vRtrMplsPceInitGenSrteAdminState,
        vRtrMplsPceInitGenSrteOperState,
        vRtrMplsGenPceInitP2PSrTeLspOrig,
        vRtrMplsPceInitGenSrteOperDnRsn
    }
    STATUS      current
    DESCRIPTION
        "The group of objects in MPLS supporting management of PCE INIT LSPs on
         Nokia SROS series systems 16.0 release."
    ::= { tmnxMplsGroups 99 }

vRtrMplsAutoBwUseLastAdjBWGroup  OBJECT-GROUP
    OBJECTS     {
        vRtrMplsLspAutoBWUseLastAdjBW,
        vRtrMplsLspAutoBWSecRetryLimit,
        vRtrMplsLspAutoBWLastAdjBW
    }
    STATUS      current
    DESCRIPTION
        "The group of notification supporting MPLS Auto-Bandwidth last
         adjusted use bandwidth on Nokia SROS series systems 16.0 Release."
    ::= { tmnxMplsGroups 100 }

tmnxMplsGeneralSrTeLspGroup      OBJECT-GROUP
    OBJECTS     {
        vRtrMplsGenSrTeResignalTimer,
        vRtrMplsLspExtPathCompMeth,
        vRtrMplsLspExtMetricType,
        vRtrMplsLspExtLocalSrProt,
        vRtrMplsLspExtLabelStackRed,
        vRtrMplsLspTempPathCompMeth,
        vRtrMplsLspTempMetricType,
        vRtrMplsLspTempLocalSrProt,
        vRtrMplsLspTempLabelStackRed,
        vRtrMplsLspPathOperCompMeth,
        vRtrMplsLspPathOperMetricType,
        vRtrMplsLspPathOperLocalSrProt,
        vRtrMplsLspPathOperLabelStackRed,
        vRtrMplsGenSrTeResigOnIgpEvent,
        vRtrMplsGenSrteNextResignal
    }
    STATUS      current
    DESCRIPTION
        "The group of objects in MPLS supporting management of SR-TE LSP
         resignal timers on Nokia SROS series systems 19.0 release."
    ::= { tmnxMplsGroups 101 }

tmnxMplsFwdPlcyEgressStatsGroup  OBJECT-GROUP
    OBJECTS     {
        vRtrMplsBindLblPathNhgNHEgrOper,
        vRtrMplsBindLblEgrStatsAggPkts,
        vRtrMplsBindLblEgrStatsAggOctets,
        vRtrMplsBindLblPathEgrStatsEnabl,
        vRtrMplsBLPathEgrStatOperState,
        vRtrMplsEndptPathNhgNHEgrOper,
        vRtrMplsEndptEgrStatsAggPkts,
        vRtrMplsEndptEgrStatsAggOctets,
        vRtrMplsEndptPathEgrStatsEnabl,
        vRtrMplsEndptPathEgrStatsOper
    }
    STATUS      current
    DESCRIPTION
        "The group of objects in MPLS supporting management of Forwarding
         Policy Egress Statistics on Nokia SROS  series systems 19.0 release."
    ::= { tmnxMplsGroups 102 }

tmnxMplsSrteSBfdGroup            OBJECT-GROUP
    OBJECTS     {
        vRtrMplsLspExtBfdUpWaitTimer,
        vRtrMplsLspPathBfdUpWaitTimer,
        vRtrMplsLspPathBfdUpWaitTmLeft,
        vRtrMplsLspPathBfdState,
        vRtrMplsLspPathBfdStartFailRsn,
        vRtrMplsLspTempBfdUpWaitTimer,
        vRtrMplsLspPathBfdOperUpWaitTmr
    }
    STATUS      current
    DESCRIPTION
        "The group of objects in MPLS supporting management of SR-TE SBFD on
         Nokia SROS series systems 19.0 release."
    ::= { tmnxMplsGroups 103 }

tmnxMplsGenMaxBypassPlrGroup     OBJECT-GROUP
    OBJECTS     {
        vRtrMplsGenMaxBypassPlrAssoc
    }
    STATUS      current
    DESCRIPTION
        "The group of objects in MPLS supporting management of Max Bypass PLR
         Associations on Nokia SROS series systems 19.0 release."
    ::= { tmnxMplsGroups 104 }

tmnxMplsLspPathEgressStatsGroup  OBJECT-GROUP
    OBJECTS     {
        vRtrMplsLspPathEgrStatsOperState,
        vRtrMplsLspEgressStatsAggrPkts,
        vRtrMplsLspEgressStatsAggrOctets
    }
    STATUS      current
    DESCRIPTION
        "The group of objects in MPLS supporting management of LSP egress
         statistics on Nokia SROS series  systems 19.0 release."
    ::= { tmnxMplsGroups 105 }

tmnxMplsLspSelfPingGroup         OBJECT-GROUP
    OBJECTS     {
        vRtrMplsGenLspSelfPingInterval,
        vRtrMplsGenLspSelfPingTimeout,
        vRtrMplsGenLspSelfPingRsvpTe,
        vRtrMplsLspTempSelfPing,
        vRtrMplsLspExtSelfPing
    }
    STATUS      current
    DESCRIPTION
        "The group of objects in MPLS supporting management of SR-TE SBFD on
         Nokia SROS series systems 19.0 release."
    ::= { tmnxMplsGroups 106 }

tmnxMplsLspSrTeIpv6Group         OBJECT-GROUP
    OBJECTS     {
        vRtrMplsGeneralV6OperState,
        vRtrMplsGeneralV6OperDownReason,
        vRtrMplsIfV6OperState
    }
    STATUS      current
    DESCRIPTION
        "The group of objects in MPLS supporting management of SR-TE IPV6
         address on Nokia SROS series systems 19.0 release."
    ::= { tmnxMplsGroups 107 }

tmnxMplsPathHopGroup             OBJECT-GROUP
    OBJECTS     {
        vRtrMplsPathHopTableLastChg,
        vRtrMplsPathHopRowStatus,
        vRtrMplsPathHopLastChange,
        vRtrMplsPathHopAddrType,
        vRtrMplsPathHopAddr,
        vRtrMplsPathHopStrictOrLoose,
        vRtrMplsPathHopSidLabel
    }
    STATUS      current
    DESCRIPTION
        "The group of objects in MPLS supporting management of MPLS hops on
         Nokia SROS series systems 19.0 release."
    ::= { tmnxMplsGroups 108 }

tmnxMplsLspNgAddrGroup           OBJECT-GROUP
    OBJECTS     {
        vRtrMplsLspNgFromAddr,
        vRtrMplsLspNgToAddr,
        vRtrMplsTunnelARHopNgRouterId,
        vRtrMplsLspPathNgFNAddrType,
        vRtrMplsLspPathNgFNAddr
    }
    STATUS      current
    DESCRIPTION
        "The group of objects in MPLS supporting management of Ng to/from
         address on Nokia SROS series systems 19.0 release."
    ::= { tmnxMplsGroups 109 }

tmnxMplsLspSelfPingOperGroup     OBJECT-GROUP
    OBJECTS     {
        vRtrMplsGenLspSelfPingTimeouts,
        vRtrMplsLspSelfPingTimeouts,
        vRtrMplsLspPathSelfPingOprState
    }
    STATUS      current
    DESCRIPTION
        "The group of operational objects in MPLS supporting management of
         SR-TE SBFD on Nokia SROS series systems 19.0 release."
    ::= { tmnxMplsGroups 110 }

tmnxMplsNotificationIPv6Group    NOTIFICATION-GROUP
    NOTIFICATIONS {
        vRtrMplsIPv6StateChange,
        vRtrMplsIfIPv6StateChange
    }
    STATUS      current
    DESCRIPTION
        "The group of notifications supporting the MPLS IPv6 on Nokia SROS
         series systems 19.10 Release."
    ::= { tmnxMplsGroups 111 }

tmnxMplsNotifyObjsLspResource    OBJECT-GROUP
    OBJECTS     {
        vRtrMplsResourceType
    }
    STATUS      current
    DESCRIPTION
        "The group of notification objects supporting IGP shortcut notification
         feature on Nokia SROS series systems 20.0 Release."
    ::= { tmnxMplsGroups 112 }

tmnxMplsNotifyV20v0Group         NOTIFICATION-GROUP
    NOTIFICATIONS {
        vRtrMplsLspResourceExhaustion
    }
    STATUS      current
    DESCRIPTION
        "The group of notifications supporting the MPLS  on Nokia SROS series
         systems 20.0 Release."
    ::= { tmnxMplsGroups 113 }

tmnxMplsV20v0Group               OBJECT-GROUP
    OBJECTS     {
        vRtrMplsTunnelARHopProtection,
        vRtrMplsTunnelARHopRecordLabel,
        vRtrMplsLspRowStatus,
        vRtrMplsLspLastChange,
        vRtrMplsLspName,
        vRtrMplsLspAdminState,
        vRtrMplsLspOperState,
        vRtrMplsLspType,
        vRtrMplsLspOutSegIndx,
        vRtrMplsLspRetryTimer,
        vRtrMplsLspRetryLimit,
        vRtrMplsLspMetric,
        vRtrMplsLspFastReroute,
        vRtrMplsLspFRHopLimit,
        vRtrMplsLspFRBandwidth,
        vRtrMplsLspSetupPriority,
        vRtrMplsLspHoldPriority,
        vRtrMplsLspRecord,
        vRtrMplsLspHopLimit,
        vRtrMplsLspNegotiatedMTU,
        vRtrMplsLspRsvpResvStyle,
        vRtrMplsLspRsvpAdspec,
        vRtrMplsLspFRMethod,
        vRtrMplsLspFRNodeProtect,
        vRtrMplsLspAdminGroupInclude,
        vRtrMplsLspAdminGroupExclude,
        vRtrMplsLspAdaptive,
        vRtrMplsLspInheritance,
        vRtrMplsLspOptimizeTimer,
        vRtrMplsLspOperFastReroute,
        vRtrMplsLspFRObject,
        vRtrMplsLspAge,
        vRtrMplsLspTimeUp,
        vRtrMplsLspTimeDown,
        vRtrMplsLspPrimaryTimeUp,
        vRtrMplsLspTransitions,
        vRtrMplsLspLastTransition,
        vRtrMplsLspLastPathChange,
        vRtrMplsLspConfiguredPaths,
        vRtrMplsLspStandbyPaths,
        vRtrMplsLspOperationalPaths,
        vRtrMplsLspHoldTimer,
        vRtrMplsLspIgpShortcutLfaType,
        vRtrMplsLspPropAdminGroup,
        vRtrMplsLspIgpShortcutRelOffset,
        vRtrMplsLspRevertTimer,
        vRtrMplsLspRevertTimeRemain,
        vRtrMplsLspTemplateTblLastChgd,
        vRtrMplsLspTemplateRowStatus,
        vRtrMplsLspTemplateLastChanged,
        vRtrMplsLspTemplateAdminState,
        vRtrMplsLspTemplateType,
        vRtrMplsLspTemplateAdaptive,
        vRtrMplsLspTemplateBandwidth,
        vRtrMplsLspTemplateCspf,
        vRtrMplsLspTemplateDefaultPath,
        vRtrMplsLspTemplateAdmGrpIncl,
        vRtrMplsLspTemplateAdmGrpExcl,
        vRtrMplsLspTemplateFastReroute,
        vRtrMplsLspTemplateFRMethod,
        vRtrMplsLspTemplateFRHopLimit,
        vRtrMplsLspTemplateHopLimit,
        vRtrMplsLspTemplateRecord,
        vRtrMplsLspTemplateRecordLabel,
        vRtrMplsLspTemplateRetryLimit,
        vRtrMplsLspTemplateRetryTimer,
        vRtrMplsLspTemplateCspfTeMetric,
        vRtrMplsLspOriginTemplate,
        vRtrMplsLspTemplateLspCount,
        vRtrMplsLspTemplateMvpnRefCount,
        vRtrMplsGeneralNewLspSRIndex,
        vRtrMplsGeneralSrTeLspOriginate,
        vRtrMplsGeneralPceReport,
        vRtrMplsLspExtPceControl,
        vRtrMplsLspExtPceReport,
        vRtrMplsLspExtTtmTunnelId,
        vRtrMplsLspExtMaxSrLabels,
        vRtrMplsLspExtTunnelId,
        vRtrMplsLspPathProfTblLstChg,
        vRtrMplsLspPathProfRowStatus,
        vRtrMplsLspPathProfLastChange,
        vRtrMplsLspPathProfGroupId,
        vRtrMplsLspPathLastUpdateTime,
        vRtrMplsLspPathLastUpdateId,
        vRtrMplsLspPathLastUpdateState,
        vRtrMplsLspPathLastUpdFailCode,
        vRtrMplsLspPathTableSpinlock,
        vRtrMplsLspPathRowStatus,
        vRtrMplsLspPathLastChange,
        vRtrMplsLspPathType,
        vRtrMplsLspPathProperties,
        vRtrMplsLspPathBandwidth,
        vRtrMplsLspPathState,
        vRtrMplsLspPathPreference,
        vRtrMplsLspPathSetupPriority,
        vRtrMplsLspPathHoldPriority,
        vRtrMplsLspPathRecord,
        vRtrMplsLspPathHopLimit,
        vRtrMplsLspPathAdminState,
        vRtrMplsLspPathOperState,
        vRtrMplsLspPathInheritance,
        vRtrMplsLspPathLspId,
        vRtrMplsLspPathRetryTimeRemaining,
        vRtrMplsLspPathTunnelARHopListIndex,
        vRtrMplsLspPathNegotiatedMTU,
        vRtrMplsLspPathFailCode,
        vRtrMplsLspPathFailNodeAddr,
        vRtrMplsLspPathAdminGroupInclude,
        vRtrMplsLspPathAdminGroupExclude,
        vRtrMplsLspPathAdaptive,
        vRtrMplsLspPathOptimizeTimer,
        vRtrMplsLspPathNextOptimize,
        vRtrMplsLspPathOperBandwidth,
        vRtrMplsLspPathResignal,
        vRtrMplsLspPathTunnelCRHopListIndex,
        vRtrMplsLspPathOperMTU,
        vRtrMplsLspPathRecordLabel,
        vRtrMplsLspPathTimeUp,
        vRtrMplsLspPathTimeDown,
        vRtrMplsLspPathRetryAttempts,
        vRtrMplsLspPathTransitionCount,
        vRtrMplsLspPathCspfQueries,
        vRtrMplsLspPathLastResigAttempt,
        vRtrMplsLspPathMetric,
        vRtrMplsLspPathLastMBBType,
        vRtrMplsLspPathLastMBBEnd,
        vRtrMplsLspPathLastMBBMetric,
        vRtrMplsLspPathLastMBBState,
        vRtrMplsLspPathMBBTypeInProg,
        vRtrMplsLspPathMBBStarted,
        vRtrMplsLspPathMBBNextRetry,
        vRtrMplsLspPathMBBRetryAttempts,
        vRtrMplsLspPathMBBFailCode,
        vRtrMplsLspPathMBBFailNodeArType,
        vRtrMplsLspPathMBBFailNodeAddr,
        vRtrMplsLspPathOperInterArea,
        vRtrMplsLspPathChanges,
        vRtrMplsLspPathTimeoutIn,
        vRtrMplsLspPathMBBTimeoutIn,
        vRtrMplsLspPathOperSetupPriority,
        vRtrMplsLspPathOperHoldPriority,
        vRtrMplsLspPathOperRecord,
        vRtrMplsLspPathOperRecordLabel,
        vRtrMplsLspPathOperHopLimit,
        vRtrMplsLspPathOperAdminGrpIncl,
        vRtrMplsLspPathOperAdminGrExcld,
        vRtrMplsLspPathOperLeastFill,
        vRtrMplsLspPathOperRsvpAdspec,
        vRtrMplsLspPathOperFRNodeProtect,
        vRtrMplsLspPathOperPropAdminGrp,
        vRtrMplsLspPathOperFRHopLimit,
        vRtrMplsLspClassFwdingEnabled,
        vRtrMplsLspTempClassFwdEnabled
    }
    STATUS      current
    DESCRIPTION
        "The group of objects supporting management of extended MPLS interfaces
         on Nokia SROS series systems 20.0 Release."
    ::= { tmnxMplsGroups 114 }

tmnxMplsObsoletedV20v0Group      OBJECT-GROUP
    OBJECTS     {
        vRtrMplsTunnelARHopRouterId,
        vRtrMplsLspFromAddr,
        vRtrMplsLspToAddr,
        vRtrMplsLspCspf,
        vRtrMplsLspTemplateCspf,
        vRtrMplsLspCspfTeMetricEnabled,
        vRtrMplsLspTemplateCspfTeMetric,
        vRtrMplsLspExtPceCompute,
        vRtrMplsLspPathOperCspf
    }
    STATUS      current
    DESCRIPTION
        "The group of obsolete objects for MPLS on a Nokia SROS series systems
         20.0 release."
    ::= { tmnxMplsGroups 115 }

tmnxMplsClassFwdObsoleteGroup    OBJECT-GROUP
    OBJECTS     {
        vRtrMplsLspFC,
        vRtrMplsLspTempFC
    }
    STATUS      current
    DESCRIPTION
        "The group of objects supporting management of class forwarding on
         Nokia SROS series systems obsoleted in release 20.0."
    ::= { tmnxMplsGroups 117 }

tmnxMplsTunnelARHopIdTypeGroup   OBJECT-GROUP
    OBJECTS     {
        vRtrMplsTunnelARHopNgRtrIdType
    }
    STATUS      current
    DESCRIPTION
        "The group of objects in MPLS supporting management of MPLS tunnel AR
         Hop table on Nokia SROS series systems."
    ::= { tmnxMplsGroups 119 }

tmnxMplsNotifyPrefix             OBJECT IDENTIFIER ::= { tmnxSRNotifyPrefix 6 }

tmnxMplsNotifications            OBJECT IDENTIFIER ::= { tmnxMplsNotifyPrefix 0 }

vRtrMplsStateChange              NOTIFICATION-TYPE
    OBJECTS     {
        vRtrID,
        vRtrMplsGeneralAdminState,
        vRtrMplsGeneralOperState
    }
    STATUS      current
    DESCRIPTION
        "This Notification is generated when the MPLS module changes state"
    ::= { tmnxMplsNotifications 1 }

vRtrMplsIfStateChange            NOTIFICATION-TYPE
    OBJECTS     {
        vRtrID,
        vRtrIfIndex,
        vRtrMplsIfAdminState,
        vRtrMplsIfOperState
    }
    STATUS      current
    DESCRIPTION
        "This Notification is generated when the MPLS interface changes state"
    ::= { tmnxMplsNotifications 2 }

vRtrMplsLspUp                    NOTIFICATION-TYPE
    OBJECTS     {
        vRtrID,
        vRtrMplsLspIndex,
        vRtrMplsLspAdminState,
        vRtrMplsLspOperState
    }
    STATUS      current
    DESCRIPTION
        "This Notification is generated when a LSP transitions to the
         'inService' state from any other state."
    ::= { tmnxMplsNotifications 3 }

vRtrMplsLspDown                  NOTIFICATION-TYPE
    OBJECTS     {
        vRtrID,
        vRtrMplsLspIndex,
        vRtrMplsLspAdminState,
        vRtrMplsLspOperState,
        vRtrMplsLspNotificationReasonCode
    }
    STATUS      current
    DESCRIPTION
        "This Notification is generated when an LSP transitions out of
         'inService' state to any other state."
    ::= { tmnxMplsNotifications 4 }

vRtrMplsLspPathUp                NOTIFICATION-TYPE
    OBJECTS     {
        vRtrID,
        vRtrMplsLspIndex,
        mplsTunnelIndex,
        mplsTunnelInstance,
        mplsTunnelIngressLSRId,
        vRtrMplsLspPathAdminState,
        vRtrMplsLspPathOperState
    }
    STATUS      current
    DESCRIPTION
        "This Notification is generated when a LSP Path transitions to the
         'inService' state from any other state."
    ::= { tmnxMplsNotifications 5 }

vRtrMplsLspPathDown              NOTIFICATION-TYPE
    OBJECTS     {
        vRtrID,
        vRtrMplsLspIndex,
        mplsTunnelIndex,
        mplsTunnelInstance,
        mplsTunnelIngressLSRId,
        vRtrMplsLspPathAdminState,
        vRtrMplsLspPathOperState,
        vRtrMplsLspPathNotificationReasonCode
    }
    STATUS      current
    DESCRIPTION
        "This Notification is generated when a LSP Path transitions out of
         'inService' state to any other state."
    ::= { tmnxMplsNotifications 6 }

vRtrMplsLspPathRerouted          NOTIFICATION-TYPE
    OBJECTS     {
        vRtrMplsLspPathAdminState,
        vRtrMplsLspPathOperState
    }
    STATUS      current
    DESCRIPTION
        "The vRtrMplsLspPathRerouted notification is generated when an LSP Path
         is rerouted."
    ::= { tmnxMplsNotifications 7 }

vRtrMplsLspPathResignaled        NOTIFICATION-TYPE
    OBJECTS     {
        vRtrMplsLspPathAdminState,
        vRtrMplsLspPathOperState,
        vRtrMplsLspPathLastMBBType
    }
    STATUS      current
    DESCRIPTION
        "The vRtrMplsLspPathResignaled notification is generated when an LSP
         Path is resignalled. The vRtrMplsLspPathLastMBBType indicates the
         reason why the LSP Path was resignalled."
    ::= { tmnxMplsNotifications 8 }

vRtrMplsP2mpInstanceUp           NOTIFICATION-TYPE
    OBJECTS     {
        vRtrID,
        vRtrMplsLspIndex,
        vRtrMplsP2mpInstNotifIndex,
        vRtrMplsP2mpInstAdminState,
        vRtrMplsP2mpInstOperState
    }
    STATUS      current
    DESCRIPTION
        "This Notification is generated when a P2MP instance transitions to the
         'inService' state from any other state."
    ::= { tmnxMplsNotifications 9 }

vRtrMplsP2mpInstanceDown         NOTIFICATION-TYPE
    OBJECTS     {
        vRtrID,
        vRtrMplsLspIndex,
        vRtrMplsP2mpInstNotifIndex,
        vRtrMplsP2mpInstAdminState,
        vRtrMplsP2mpInstOperState,
        vRtrMplsP2mpInstNotifReasonCode
    }
    STATUS      current
    DESCRIPTION
        "This Notification is generated when a P2MP instance transitions out of
         'inService' state to any other state."
    ::= { tmnxMplsNotifications 10 }

vRtrMplsS2lSubLspUp              NOTIFICATION-TYPE
    OBJECTS     {
        vRtrID,
        vRtrMplsLspIndex,
        vRtrMplsP2mpInstNotifIndex,
        mplsTunnelIndex,
        mplsTunnelInstance,
        mplsTunnelIngressLSRId,
        vRtrMplsS2lSubLspNtDstAddrType,
        vRtrMplsS2lSubLspNtDstAddr,
        vRtrMplsS2lSubLspAdminState,
        vRtrMplsS2lSubLspOperState
    }
    STATUS      current
    DESCRIPTION
        "This Notification is generated when a S2l sub LSP transitions to the
         'inService' state from any other state."
    ::= { tmnxMplsNotifications 11 }

vRtrMplsS2lSubLspDown            NOTIFICATION-TYPE
    OBJECTS     {
        vRtrID,
        vRtrMplsLspIndex,
        vRtrMplsP2mpInstNotifIndex,
        mplsTunnelIndex,
        mplsTunnelInstance,
        mplsTunnelIngressLSRId,
        vRtrMplsS2lSubLspNtDstAddrType,
        vRtrMplsS2lSubLspNtDstAddr,
        vRtrMplsS2lSubLspAdminState,
        vRtrMplsS2lSubLspOperState,
        vRtrMplsP2mpInstNotifReasonCode
    }
    STATUS      current
    DESCRIPTION
        "This Notification is generated when a S2l sub LSP transitions out of
         'inService' state to any other state."
    ::= { tmnxMplsNotifications 12 }

vRtrMplsS2lSubLspRerouted        NOTIFICATION-TYPE
    OBJECTS     {
        vRtrMplsS2lSubLspAdminState,
        vRtrMplsS2lSubLspOperState
    }
    STATUS      current
    DESCRIPTION
        "The vRtrMplsS2lSubLspRerouted notification is generated when an S2l
         sub LSP is rerouted."
    ::= { tmnxMplsNotifications 13 }

vRtrMplsS2lSubLspResignaled      NOTIFICATION-TYPE
    OBJECTS     {
        vRtrMplsS2lSubLspAdminState,
        vRtrMplsS2lSubLspOperState,
        vRtrMplsS2lSubLspLastMBBType
    }
    STATUS      current
    DESCRIPTION
        "The vRtrMplsS2lSubLspResignaled notification is generated when an S2l
         sub LSP is resignalled. The vRtrMplsS2lSubLspLastMBBType indicates the
         reason why the S2l sub LSP was resignalled."
    ::= { tmnxMplsNotifications 14 }

vRtrMplsLspPathSoftPreempted     NOTIFICATION-TYPE
    OBJECTS     {
        vRtrMplsLspPathAdminState,
        vRtrMplsLspPathOperState
    }
    STATUS      current
    DESCRIPTION
        "The vRtrMplsLspPathSoftPreempted notification is generated when an LSP
         Path is soft-preempted."
    ::= { tmnxMplsNotifications 15 }

vRtrMplsLspPathLstFillReoptElig  NOTIFICATION-TYPE
    OBJECTS     {
        vRtrMplsLspPathResignalEligible,
        vRtrMplsLspPathCongChgPercent
    }
    STATUS      current
    DESCRIPTION
        "The vRtrMplsLspPathLstFillReoptElig notification is set/reset based on
         when a timer based resignal found/did not find a path with the same
         cost but which has a better least-fill metric."
    ::= { tmnxMplsNotifications 16 }

vRtrMplsP2mpInstanceResignaled   NOTIFICATION-TYPE
    OBJECTS     {
        vRtrID,
        vRtrMplsLspIndex,
        vRtrMplsP2mpInstNotifIndex,
        vRtrMplsP2mpInstAdminState,
        vRtrMplsP2mpInstOperState,
        vRtrMplsP2mpInstLastMBBType
    }
    STATUS      current
    DESCRIPTION
        "This Notification is generated when a P2MP instance is resignalled.
         The vRtrMplsP2mpInstLastMBBType indicates the reason why the P2MP
         instance was resignalled."
    ::= { tmnxMplsNotifications 17 }

vRtrMplsResignalTimerExpired     NOTIFICATION-TYPE
    OBJECTS     {
        vRtrMplsGeneralResignalTimer
    }
    STATUS      current
    DESCRIPTION
        "The vRtrMplsResignalTimerExpired notification is generated when the
         resignal timer expires for a MPLS instance. Make before break (MBB)
         would be started only on those P2P LSP (Point to Point) paths that
         need to be resignalled. vRtrMplsGeneralResignalTimer would be reset
         once this notification is sent."
    ::= { tmnxMplsNotifications 18 }

vRtrMplsLspPathMbbStatusEvent    NOTIFICATION-TYPE
    OBJECTS     {
        vRtrMplsLspPathAdminState,
        vRtrMplsLspPathOperState,
        vRtrMplsLspPathLastMBBType,
        vRtrMplsLspPathMbbStatus,
        vRtrMplsLspPathMbbReasonCode
    }
    STATUS      current
    DESCRIPTION
        "The vRtrMplsLspPathMbbStatusEvent notification is generated to report
         the status of the make-before-break(MBB) operation for the LSP path."
    ::= { tmnxMplsNotifications 19 }

vRtrMplsLspSwitchStbyFailure     NOTIFICATION-TYPE
    OBJECTS     {
        vRtrID,
        vRtrMplsLspIndex,
        vRtrMplsLspAdminState,
        vRtrMplsLspOperState,
        vRtrMplsLspSwitchStbyPathForce,
        vRtrMplsLspSwitchStbyPathIndex,
        vRtrMplsLspSwitchStbyReasonCode
    }
    STATUS      current
    DESCRIPTION
        "[CAUSE] The vRtrMplsLspSwitchStbyFailure notification is generated to
         report an unsuccessful switchover from the current active secondary
         LSP path of an LSP to another secondary standby LSP path. The reason
         for the failure is specified by vRtrMplsLspSwitchStbyReasonCode.

         [EFFECT] The switchover to the new standby path failed for the LSP.

         [RECOVERY] The vRtrMplsLspSwitchStbyReasonCode will help the user
         troubleshoot the failure.  The user can attempt to switchover to
         another standby LSP path again."
    ::= { tmnxMplsNotifications 20 }

vRtrMplsLspActivePathChanged     NOTIFICATION-TYPE
    OBJECTS     {
        vRtrMplsLspPathState,
        vRtrMplsLspPathActiveByManual,
        vRtrMplsLspOldTunnelIndex
    }
    STATUS      current
    DESCRIPTION
        "[CAUSE] The vRtrMplsLspActivePathChanged notification is generated
         when the active path of an LSP successfully switches to an new path.

         This notification will also be sent when the active LSP path does not
         change but only the switch method changes on the path.

         The old LSP path index is specified by vRtrMplsLspOldTunnelIndex.

         The state and switch method of the current active LSP path are
         specified by vRtrMplsLspPathState and vRtrMplsLspPathActiveByManual
         respectively.

         [EFFECT]  The switchover to the new LSP path was successful
         and/or the switch method of the current active LSP path changed.

         [RECOVERY] There is no recovery required for this notification."
    ::= { tmnxMplsNotifications 21 }

vRtrMplsXCBundleChange           NOTIFICATION-TYPE
    OBJECTS     {
        vRtrID,
        vRtrMplsXCNotifRednIndicesBitMap,
        vRtrMplsXCNotifyRednBundlingType,
        vRtrMplsXCNotifyRednNumOfBitsSet,
        vRtrMplsXCNotifyRednStartIndex,
        vRtrMplsXCNotifyRednEndIndex
    }
    STATUS      current
    DESCRIPTION
        "[CAUSE] vRtrMplsXCBundleChange is generated when one or more RSVP
         sessions changed state and retained the changed state for an entire
         quiet interval of 2 minutes or the maximum interval of 10 minutes if
         the state of RSVP sessions kept on changing during this period of
         multiple quiet intervals.

         [EFFECT] RSVP sessions represented by bits in
         vRtrMplsXCNotifRednIndicesBitMap changed state on this router
         instance.

         [RECOVERY] There is no recovery required for this notification."
    ::= { tmnxMplsNotifications 22 }

vRtrMplsLblRangeModify           NOTIFICATION-TYPE
    OBJECTS     {
        vRtrMplsLabelMaxStaticLspLabels,
        vRtrMplsLabelMaxStaticSvcLabels
    }
    STATUS      obsolete
    DESCRIPTION
        "[CAUSE] vRtrMplsLblRangeModify is generated when the values of
         vRtrMplsLabelMaxStaticLspLabels or vRtrMplsLabelMaxStaticSvcLabels
         have been modified.

         [EFFECT] The maximum static labels are modified.

         [RECOVERY] There is no recovery required for this notification."
    ::= { tmnxMplsNotifications 23 }

vRtrMplsNodeInIgpOverload        NOTIFICATION-TYPE
    OBJECTS     {
        vRtrMplsGenRetryOnIgpOverload,
        vRtrMplsIgpOverloadRtrAddrType,
        vRtrMplsIgpOverloadRtrAddr,
        vRtrMplsIgpOverloadIgpType
    }
    STATUS      current
    DESCRIPTION
        "[CAUSE] The vRtrMplsNodeInIgpOverload notification is generated when
         MPLS gets a notification that a node is in IGP overload state.

         [EFFECT] The LSPs transiting through nodes that are in IGP overload
         state are teardown.

         [RECOVERY] There is no recovery required for this notification."
    ::= { tmnxMplsNotifications 24 }

vRtrMplsIPv6StateChange          NOTIFICATION-TYPE
    OBJECTS     {
        vRtrID,
        vRtrMplsGeneralAdminState,
        vRtrMplsGeneralV6OperState
    }
    STATUS      current
    DESCRIPTION
        "[CAUSE] The vRtrMplsIPv6StateChange notification is generated when
         MPLS protocol instance changes state.

         [EFFECT] The SR-TE LSPs with IPv6 addresses transition state.

         [RECOVERY] There is no recovery required for this notification."
    ::= { tmnxMplsNotifications 25 }

vRtrMplsIfIPv6StateChange        NOTIFICATION-TYPE
    OBJECTS     {
        vRtrID,
        vRtrIfIndex,
        vRtrMplsIfAdminState,
        vRtrMplsIfV6OperState
    }
    STATUS      current
    DESCRIPTION
        "[CAUSE] The vRtrMplsIPv6StateChange notification is generated when
         MPLS interface changes state.

         [EFFECT] The SR-TE LSPs with IPv6 addresses transition state.

         [RECOVERY] There is no recovery required for this notification."
    ::= { tmnxMplsNotifications 26 }

vRtrMplsLspResourceExhaustion    NOTIFICATION-TYPE
    OBJECTS     {
        vRtrID,
        vRtrMplsLspIndex,
        vRtrMplsLspType,
        vRtrMplsLspName,
        vRtrMplsResourceType
    }
    STATUS      current
    DESCRIPTION
        "[CAUSE] The vRtrMplsLspResourceExhaustion notification is generated
         when CPM or data path resource specified by vRtrMplsResourceType is
         exhausted.

         [EFFECT] If vRtrMplsResourceType is 'egressStatistics', LSP path
         egress statistics will not be collected.

         [RECOVERY] Appropriate config changes in the system may be required to
         free up the resources.

         Once the resources are available and vRtrMplsResourceType is
         'egressStatistics' and vRtrMplsLspType is 'srTe', lsp
         egress-statistics admin down and up will be needed to bring up lsp
         path egress-statistics."
    ::= { tmnxMplsNotifications 27 }

END

TIMETRA-TREE-SID-MIB DEFINITIONS ::= BEGIN

IMPORTS
    InetAddress, InetAddressType
                                                         FROM INET-ADDRESS-MIB
    MODULE-COMPLIANCE, NOTIFICATION-GROUP,
    OBJECT-GROUP
                                                         FROM SNMPv2-CONF
    Integer32, MODULE-IDENTITY,
    NOTIFICATION-TYPE, OBJECT-TYPE,
    Unsigned32
                                                         FROM SNMPv2-SMI
    RowStatus, TimeStamp, TruthValue
                                                         FROM SNMPv2-TC
    timetraSRMIBModules, tmnxSRConfs,
    tmnxSRNotifyPrefix, tmnxSRObjs
                                                         FROM TIMETRA-GLOBAL-MIB
    TLNamedItemOrEmpty, TNamedItem,
    TNamedItemOrEmpty, TmnxAdminState,
    TmnxOperState, TmnxTreeSidOrigin,
    TmnxTreeSidOwner, TmnxVRtrIDOrZero
                                                         FROM TIMETRA-TC-MIB
    vRtrID, vRtrIfIndex
                                                         FROM TIMETRA-VRTR-MIB
    ;

timetraTreeSidMIBModule          MODULE-IDENTITY
    LAST-UPDATED "201908070000Z"
    ORGANIZATION "Nokia"
    CONTACT-INFO
        "Nokia 7xxx Support
         Web: http://www.nokia.com"
    DESCRIPTION
        "This document is the SNMP MIB module for the Nokia SROS implementation
         of tree-sid.

         Copyright 2003-2019 Nokia. All rights reserved. Reproduction of this
         document is authorized on the condition that the foregoing copyright
         notice is included.

         This SNMP MIB module (Specification) embodies Nokia's proprietary
         intellectual property. Nokia retains all title and ownership in the
         Specification, including any revisions.

         Nokia grants all interested parties a non-exclusive license to use and
         distribute an unmodified copy of this Specification in connection with
         management of Nokia products, and without fee, provided this copyright
         notice and license appear on all copies.

         This Specification is supplied 'as is', and Nokia makes no warranty,
         either express or implied, as to the use, operation, condition, or
         performance of the Specification."

    REVISION    "201908070000Z"
    DESCRIPTION
        "Rev 19.0               7 Jul 2019 00:00
         19.0 release of the TIMETRA-TREE-SID-MIB."

    ::= { timetraSRMIBModules 126 }

tmnxTreeSid                      OBJECT IDENTIFIER ::= { tmnxSRObjs 126 }

tmnxTreeSidObjs                  OBJECT IDENTIFIER ::= { tmnxTreeSid 1 }

vRtrTreeSidPlcyTableLastChanged  OBJECT-TYPE
    SYNTAX      TimeStamp
    MAX-ACCESS  read-only
    STATUS      current
    DESCRIPTION
        "The value of vRtrTreeSidPlcyTableLastChanged indicates the sysUpTime
         at the time of the last modification of an entry in the
         vRtrTreeSidPolicyTable."
    ::= { tmnxTreeSidObjs 1 }

vRtrTreeSdPlcyLfAddrTblLastChgd  OBJECT-TYPE
    SYNTAX      TimeStamp
    MAX-ACCESS  read-only
    STATUS      current
    DESCRIPTION
        "The value of vRtrTreeSdPlcyLfAddrTblLastChgd indicates the sysUpTime
         at the time of the last modification of an entry in the
         vRtrTreeSidPolicyTable."
    ::= { tmnxTreeSidObjs 2 }

vRtrTreeSidReplPlcyTableLstChgd  OBJECT-TYPE
    SYNTAX      TimeStamp
    MAX-ACCESS  read-only
    STATUS      current
    DESCRIPTION
        "The value of vRtrTreeSidReplPlcyTableLstChgd indicates the sysUpTime
         at the time of the last modification of an entry in the
         vRtrTreeSidReplPlcyTable."
    ::= { tmnxTreeSidObjs 3 }

vRtrTrSdRpNHOGRplSdTblLstChgd    OBJECT-TYPE
    SYNTAX      TimeStamp
    MAX-ACCESS  read-only
    STATUS      current
    DESCRIPTION
        "The value of vRtrTrSdRpNHOGRplSdTblLstChgd indicates the sysUpTime at
         the time of the last modification of an entry in the
         vRtrTrSdRpNHOutGngReplSdTable."
    ::= { tmnxTreeSidObjs 4 }

vRtrTrSdRplPlcyCdtPthTblLstChgd  OBJECT-TYPE
    SYNTAX      TimeStamp
    MAX-ACCESS  read-only
    STATUS      current
    DESCRIPTION
        "The value of vRtrTrSdRplPlcyCdtPthTblLstChgd indicates the sysUpTime
         at the time of the last modification of an entry in the
         vRtrTreeSidPolicyCdtPathTable."
    ::= { tmnxTreeSidObjs 5 }

vRtrTreeSidGeneralTable          OBJECT-TYPE
    SYNTAX      SEQUENCE OF VRtrTreeSidGeneralEntry
    MAX-ACCESS  not-accessible
    STATUS      current
    DESCRIPTION
        "The vRtrTreeSidGeneralTable contain objects to configure a tree-sid
         general table."
    ::= { tmnxTreeSidObjs 6 }

vRtrTreeSidGeneralEntry          OBJECT-TYPE
    SYNTAX      VRtrTreeSidGeneralEntry
    MAX-ACCESS  not-accessible
    STATUS      current
    DESCRIPTION
        "The value of vRtrTreeSidGeneralEntry represents a tree-sid general
         entry configuration information.

         Entries are created and deleted by the user."
    INDEX       { vRtrID }
    ::= { vRtrTreeSidGeneralTable 1 }

VRtrTreeSidGeneralEntry          ::= SEQUENCE
{
    vRtrTreeSidGenAdminState         TmnxAdminState,
    vRtrTreeSidGenRsvdLblBlockName   TLNamedItemOrEmpty,
    vRtrTreeSidGenRowStatus          RowStatus,
    vRtrTreeSidGenLastChanged        TimeStamp,
    vRtrTreeSidGenBfdEnabled         BITS
}

vRtrTreeSidGenAdminState         OBJECT-TYPE
    SYNTAX      TmnxAdminState
    MAX-ACCESS  read-create
    STATUS      current
    DESCRIPTION
        "The value of vRtrTreeSidGenAdminState specifies the desired
         administrative state of the tree-sid."
    DEFVAL      { inService }
    ::= { vRtrTreeSidGeneralEntry 1 }

vRtrTreeSidGenRsvdLblBlockName   OBJECT-TYPE
    SYNTAX      TLNamedItemOrEmpty
    MAX-ACCESS  read-create
    STATUS      current
    DESCRIPTION
        "The value of vRtrTreeSidGenRsvdLblBlockName specifies the name of this
         tree-sid general table reserved label block."
    DEFVAL      { "" }
    ::= { vRtrTreeSidGeneralEntry 2 }

vRtrTreeSidGenRowStatus          OBJECT-TYPE
    SYNTAX      RowStatus
    MAX-ACCESS  read-create
    STATUS      current
    DESCRIPTION
        "The value of vRtrTreeSidGenRowStatus specifies the row status for this
         tree sid general table instance."
    ::= { vRtrTreeSidGeneralEntry 3 }

vRtrTreeSidGenLastChanged        OBJECT-TYPE
    SYNTAX      TimeStamp
    MAX-ACCESS  read-only
    STATUS      current
    DESCRIPTION
        "The value of vRtrTreeSidGenLastChanged indicates the sysUpTime at the
         time of the last modification of an entry for this tree sid general
         table instance."
    ::= { vRtrTreeSidGeneralEntry 4 }

vRtrTreeSidGenBfdEnabled         OBJECT-TYPE
    SYNTAX      BITS {
        ipv4 (0),
        ipv6 (1)
    }
    MAX-ACCESS  read-create
    STATUS      current
    DESCRIPTION
        "The value of vRtrTreeSidGenBfdEnabled specifies whether BFD tracking
         is enabled for p2mp-sr-tree.

         When this object has a value of 'ipv4', BFD tracking is enabled to
         each resolved ipv4 address. When this object has a value of 'ipv6',
         BFD tracking is enabled to each resolved ipv6 address. When this
         object has value of 0, BFD tracking is disabled."
    DEFVAL      { {} }
    ::= { vRtrTreeSidGeneralEntry 5 }

vRtrTreeSidPolicyTable           OBJECT-TYPE
    SYNTAX      SEQUENCE OF VRtrTreeSidPolicyEntry
    MAX-ACCESS  not-accessible
    STATUS      current
    DESCRIPTION
        "The vRtrTreeSidPolicyTable contains objects to configure a tree-sid
         policy table"
    ::= { tmnxTreeSidObjs 7 }

vRtrTreeSidPolicyEntry           OBJECT-TYPE
    SYNTAX      VRtrTreeSidPolicyEntry
    MAX-ACCESS  not-accessible
    STATUS      current
    DESCRIPTION
        "The value of vRtrTreeSidPolicyEntry represents a tree-sid policy
         configuration information.

         Entries are created and deleted by the user."
    INDEX       {
        vRtrID,
        vRtrTreeSidPolicyName
    }
    ::= { vRtrTreeSidPolicyTable 1 }

VRtrTreeSidPolicyEntry           ::= SEQUENCE
{
    vRtrTreeSidPolicyName            TNamedItem,
    vRtrTreeSidPolicyRowStatus       RowStatus,
    vRtrTreeSidPolicyRootAddr        InetAddress,
    vRtrTreeSidPolicyRootAddrType    InetAddressType,
    vRtrTreeSidPolicyTreeId          Unsigned32,
    vRtrTreeSidPolicyAdminState      TmnxAdminState,
    vRtrTreeSidPolicyOperStatus      TmnxOperState,
    vRtrTreeSidPolicyLastChanged     TimeStamp,
    vRtrTreeSidPolicyRtrId           TmnxVRtrIDOrZero,
    vRtrTreeSidPolicyActCdtPathName  TNamedItemOrEmpty
}

vRtrTreeSidPolicyName            OBJECT-TYPE
    SYNTAX      TNamedItem
    MAX-ACCESS  not-accessible
    STATUS      current
    DESCRIPTION
        "The value of vRtrTreeSidPolicyName specifies the name of this tree-sid
         policy entry."
    ::= { vRtrTreeSidPolicyEntry 1 }

vRtrTreeSidPolicyRowStatus       OBJECT-TYPE
    SYNTAX      RowStatus
    MAX-ACCESS  read-create
    STATUS      current
    DESCRIPTION
        "The value of vRtrTreeSidPolicyRowStatus specifies the row status for
         this tree sid policy instance."
    ::= { vRtrTreeSidPolicyEntry 2 }

vRtrTreeSidPolicyRootAddr        OBJECT-TYPE
    SYNTAX      InetAddress (SIZE (0|4))
    MAX-ACCESS  read-create
    STATUS      current
    DESCRIPTION
        "The value of vRtrTreeSidPolicyRootAddr specifies the root address of
         this tree-sid policy entry."
    DEFVAL      { '00000000'H }
    ::= { vRtrTreeSidPolicyEntry 3 }

vRtrTreeSidPolicyRootAddrType    OBJECT-TYPE
    SYNTAX      InetAddressType
    MAX-ACCESS  read-create
    STATUS      current
    DESCRIPTION
        "The value of vRtrTreeSidPolicyRootAddrType indicates the type of
         address for the tree-sid policy entry represented by
         vRtrTreeSidPolicyRootAddr."
    DEFVAL      { ipv4 }
    ::= { vRtrTreeSidPolicyEntry 4 }

vRtrTreeSidPolicyTreeId          OBJECT-TYPE
    SYNTAX      Unsigned32 (0 | 8193..16286)
    MAX-ACCESS  read-create
    STATUS      current
    DESCRIPTION
        "The value of vRtrTreeSidPolicyTreeId uniquely indentifies a tunnel in
         the root, this also represent a spefic constraint. Also known as color
         and/or p2mp-id"
    DEFVAL      { 0 }
    ::= { vRtrTreeSidPolicyEntry 5 }

vRtrTreeSidPolicyAdminState      OBJECT-TYPE
    SYNTAX      TmnxAdminState
    MAX-ACCESS  read-create
    STATUS      current
    DESCRIPTION
        "The value of vRtrTreeSidPolicyAdminState specifies the desired
         administrative state of tree-sid policy entry."
    DEFVAL      { outOfService }
    ::= { vRtrTreeSidPolicyEntry 6 }

vRtrTreeSidPolicyOperStatus      OBJECT-TYPE
    SYNTAX      TmnxOperState
    MAX-ACCESS  read-only
    STATUS      current
    DESCRIPTION
        "The value of vRtrTreeSidPolicyOperStatus indicates the operational
         status for a given tree-sid policy instance."
    DEFVAL      { outOfService }
    ::= { vRtrTreeSidPolicyEntry 7 }

vRtrTreeSidPolicyLastChanged     OBJECT-TYPE
    SYNTAX      TimeStamp
    MAX-ACCESS  read-only
    STATUS      current
    DESCRIPTION
        "The value vRtrTreeSidPolicyLastChanged indicates when an entry in
         vRtrTreeSidPolicyEntry was last changed."
    ::= { vRtrTreeSidPolicyEntry 8 }

vRtrTreeSidPolicyRtrId           OBJECT-TYPE
    SYNTAX      TmnxVRtrIDOrZero
    MAX-ACCESS  read-only
    STATUS      current
    DESCRIPTION
        "The value of vRtrTreeSidPolicyRtrId indicates if a service is
         configured with p2mp-policy."
    ::= { vRtrTreeSidPolicyEntry 9 }

vRtrTreeSidPolicyActCdtPathName  OBJECT-TYPE
    SYNTAX      TNamedItemOrEmpty
    MAX-ACCESS  read-only
    STATUS      current
    DESCRIPTION
        "The value of vRtrTreeSidPolicyActCdtPathName specifies a path name of
         a given instance within a tree-sid replication that is active for the
         given policy."
    DEFVAL      { "" }
    ::= { vRtrTreeSidPolicyEntry 10 }

vRtrTreeSidPolicyCdtPathTable    OBJECT-TYPE
    SYNTAX      SEQUENCE OF VRtrTreeSidPolicyCdtPathEntry
    MAX-ACCESS  not-accessible
    STATUS      current
    DESCRIPTION
        "The vRtrTreeSidPolicyCdtPathTable contains objects to configure
         candidate path entries for a given tree-sid policy table instance."
    ::= { tmnxTreeSidObjs 8 }

vRtrTreeSidPolicyCdtPathEntry    OBJECT-TYPE
    SYNTAX      VRtrTreeSidPolicyCdtPathEntry
    MAX-ACCESS  not-accessible
    STATUS      current
    DESCRIPTION
        "The value of vRtrTreeSidPolicyCdtPathEntry represents a unique path
         from root to a specific endpoint for the configuration information.

         Entries are created and deleted by the user."
    INDEX       {
        vRtrID,
        vRtrTreeSidPolicyName,
        vRtrTreeSidPolicyCdtPathName
    }
    ::= { vRtrTreeSidPolicyCdtPathTable 1 }

VRtrTreeSidPolicyCdtPathEntry    ::= SEQUENCE
{
    vRtrTreeSidPolicyCdtPathName     TNamedItem,
    vRtrTreeSidPolCdtPathRowStatus   RowStatus,
    vRtrTreeSidPolCdtPathAdminState  TmnxAdminState,
    vRtrTreeSidPolCdtPathOperState   TmnxOperState,
    vRtrTreeSidPolCdtPathOrigin      TmnxTreeSidOrigin,
    vRtrTreeSidPlcyCPOriginatorAsn   Unsigned32,
    vRtrTreeSidPlcyCPDescriminator   Unsigned32,
    vRtrTreeSidPlcyCdtPthPlspId      Unsigned32,
    vRtrTreeSidPlcyCdtPthPreference  Unsigned32,
    vRtrTreeSidPolCdtPathLastChanged TimeStamp,
    vRtrTreeSidPolCdtPathActiveInst  Unsigned32,
    vRtrTrSidPlcyCPOrigNodeAddrType  InetAddressType,
    vRtrTrSidPlcyCPOrigNodeAddr      InetAddress
}

vRtrTreeSidPolicyCdtPathName     OBJECT-TYPE
    SYNTAX      TNamedItem
    MAX-ACCESS  not-accessible
    STATUS      current
    DESCRIPTION
        "The value of vRtrTreeSidPolicyCdtPathName specifies a path name of a
         given candidate path table instance within a tree-sid replication
         policy table entry and it is equivalent to an LSP."
    ::= { vRtrTreeSidPolicyCdtPathEntry 1 }

vRtrTreeSidPolCdtPathRowStatus   OBJECT-TYPE
    SYNTAX      RowStatus
    MAX-ACCESS  read-create
    STATUS      current
    DESCRIPTION
        "The value of vRtrTreeSidPolCdtPathRowStatus specifies the row status
         of a given candidate path table instance within a tree-sid replication
         policy table entry."
    ::= { vRtrTreeSidPolicyCdtPathEntry 2 }

vRtrTreeSidPolCdtPathAdminState  OBJECT-TYPE
    SYNTAX      TmnxAdminState
    MAX-ACCESS  read-create
    STATUS      current
    DESCRIPTION
        "The value of vRtrTreeSidPolCdtPathAdminState specifies the desired
         administrative state of a vRtrTreeSidPolicyCdtPathEntry."
    DEFVAL      { outOfService }
    ::= { vRtrTreeSidPolicyCdtPathEntry 3 }

vRtrTreeSidPolCdtPathOperState   OBJECT-TYPE
    SYNTAX      TmnxOperState
    MAX-ACCESS  read-only
    STATUS      current
    DESCRIPTION
        "The value of vRtrTreeSidPolCdtPathOperState indicates the operational
         state of a vRtrTreeSidPolicyCdtPathEntry based on ilm programming."
    DEFVAL      { outOfService }
    ::= { vRtrTreeSidPolicyCdtPathEntry 4 }

vRtrTreeSidPolCdtPathOrigin      OBJECT-TYPE
    SYNTAX      TmnxTreeSidOrigin
    MAX-ACCESS  read-create
    STATUS      current
    DESCRIPTION
        "The value of vRtrTreeSidPolCdtPathOrigin specifies the value of
         protocol-origin of a candidate path which is an 8-bit value which
         identifies the component or protocol that originates or signals the
         candidate path."
    ::= { vRtrTreeSidPolicyCdtPathEntry 5 }

vRtrTreeSidPlcyCPOriginatorAsn   OBJECT-TYPE
    SYNTAX      Unsigned32
    MAX-ACCESS  read-create
    STATUS      current
    DESCRIPTION
        "The value of vRtrTreeSidPlcyCPOriginatorAsn specifies a 4 byte number
         to represent the originator asn value for a given candidate path entry
         inside a tree-sid replication policy instance."
    ::= { vRtrTreeSidPolicyCdtPathEntry 6 }

vRtrTreeSidPlcyCPDescriminator   OBJECT-TYPE
    SYNTAX      Unsigned32
    MAX-ACCESS  read-only
    STATUS      current
    DESCRIPTION
        "The value of vRtrTreeSidPlcyCPDescriminator indicates a 32 bit value
         associated with a vRtrTreeSidPolicyCdtPathEntry that uniquely
         identifies it within the context of an SR Policy from a specific
         Protocol-Origin."
    ::= { vRtrTreeSidPolicyCdtPathEntry 8 }

vRtrTreeSidPlcyCdtPthPlspId      OBJECT-TYPE
    SYNTAX      Unsigned32
    MAX-ACCESS  read-only
    STATUS      current
    DESCRIPTION
        "The value of vRtrTreeSidPlcyCdtPthPlspId specifies a unique identifier
         assigned by the controller and remain unchanged througout the life of
         a LSP (candidate path) for a given vRtrTreeSidPolicyCdtPathEntry."
    DEFVAL      { 0 }
    ::= { vRtrTreeSidPolicyCdtPathEntry 9 }

vRtrTreeSidPlcyCdtPthPreference  OBJECT-TYPE
    SYNTAX      Unsigned32 (0..1024)
    MAX-ACCESS  read-create
    STATUS      current
    DESCRIPTION
        "The value of vRtrTreeSidPlcyCdtPthPreference determines the best
         preferred candidate-path among the list of candiate paths towards a
         leaf, Higher preference is choosen."
    DEFVAL      { 100 }
    ::= { vRtrTreeSidPolicyCdtPathEntry 10 }

vRtrTreeSidPolCdtPathLastChanged OBJECT-TYPE
    SYNTAX      TimeStamp
    MAX-ACCESS  read-only
    STATUS      current
    DESCRIPTION
        "The value vRtrTreeSidPolCdtPathLastChanged indicates when an entry in
         vRtrTreeSidPolicyCdtPathTable was last changed."
    ::= { vRtrTreeSidPolicyCdtPathEntry 11 }

vRtrTreeSidPolCdtPathActiveInst  OBJECT-TYPE
    SYNTAX      Unsigned32 (0 | 1..2)
    MAX-ACCESS  read-create
    STATUS      current
    DESCRIPTION
        "The value of vRtrTreeSidPolCdtPathActiveInst specifies the active
         instance for the p2mp-policy candidate-path entry.

         Instances are defined in the vRtrTreeSidInstanceTable."
    DEFVAL      { 0 }
    ::= { vRtrTreeSidPolicyCdtPathEntry 12 }

vRtrTrSidPlcyCPOrigNodeAddrType  OBJECT-TYPE
    SYNTAX      InetAddressType
    MAX-ACCESS  read-create
    STATUS      current
    DESCRIPTION
        "The value of vRtrTrSidPlcyCPOrigNodeAddrType indicates the type of
         address for the tree-sid policy entry represented by
         vRtrTrSidPlcyCPOrigNodeAddr."
    DEFVAL      { unknown }
    ::= { vRtrTreeSidPolicyCdtPathEntry 13 }

vRtrTrSidPlcyCPOrigNodeAddr      OBJECT-TYPE
    SYNTAX      InetAddress (SIZE (0|4))
    MAX-ACCESS  read-create
    STATUS      current
    DESCRIPTION
        "The value of vRtrTrSidPlcyCPOrigNodeAddr specifies the originator
         address of this tree-sid candidate path entry."
    DEFVAL      { ''H }
    ::= { vRtrTreeSidPolicyCdtPathEntry 14 }

vRtrTreeSidReplPlcyTable         OBJECT-TYPE
    SYNTAX      SEQUENCE OF VRtrTreeSidReplPlcyEntry
    MAX-ACCESS  not-accessible
    STATUS      current
    DESCRIPTION
        "The vRtrTreeSidReplPlcyTable contains objects to configure a tree-sid
         replication policy table"
    ::= { tmnxTreeSidObjs 9 }

vRtrTreeSidReplPlcyEntry         OBJECT-TYPE
    SYNTAX      VRtrTreeSidReplPlcyEntry
    MAX-ACCESS  not-accessible
    STATUS      current
    DESCRIPTION
        "The value of vRtrTreeSidReplPlcyEntry represents a tree-sid
         replication policy configuration information.

         Entries are created and deleted by the user."
    INDEX       {
        vRtrID,
        vRtrTreeSidReplPlcyName
    }
    ::= { vRtrTreeSidReplPlcyTable 1 }

VRtrTreeSidReplPlcyEntry         ::= SEQUENCE
{
    vRtrTreeSidReplPlcyName          TNamedItem,
    vRtrTreeSidReplPlcyRowStatus     RowStatus,
    vRtrTreeSidReplPlcyRootAddr      InetAddress,
    vRtrTreeSidReplPlcyRootAddrType  InetAddressType,
    vRtrTreeSidReplPlcyTreeId        Unsigned32,
    vRtrTreeSidReplPlcyAdminState    TmnxAdminState,
    vRtrTreeSidReplPlcyOperStatus    TmnxOperState,
    vRtrTreeSidReplPlcyIncomingSid   Unsigned32,
    vRtrTreeSidReplPlcyOperation     INTEGER,
    vRtrTreeSidReplPlcyInstanceId    Unsigned32,
    vRtrTreeSdReplPlcyLastChanged    TimeStamp,
    vRtrTreeSidReplPlcyOrigin        TmnxTreeSidOrigin,
    vRtrTrSdReplPlcyRootAddrValid    TruthValue
}

vRtrTreeSidReplPlcyName          OBJECT-TYPE
    SYNTAX      TNamedItem
    MAX-ACCESS  not-accessible
    STATUS      current
    DESCRIPTION
        "The value of vRtrTreeSidReplPlcyName specifies the name of this
         tree-sid replication policy entry to be referenced by mvpn pmsi."
    ::= { vRtrTreeSidReplPlcyEntry 1 }

vRtrTreeSidReplPlcyRowStatus     OBJECT-TYPE
    SYNTAX      RowStatus
    MAX-ACCESS  read-create
    STATUS      current
    DESCRIPTION
        "The value of vRtrTreeSidReplPlcyRowStatus specifies the row status of
         a given tree-sid replication policy table instance."
    ::= { vRtrTreeSidReplPlcyEntry 2 }

vRtrTreeSidReplPlcyRootAddr      OBJECT-TYPE
    SYNTAX      InetAddress (SIZE (0|4))
    MAX-ACCESS  read-create
    STATUS      current
    DESCRIPTION
        "The value of vRtrTreeSidReplPlcyRootAddr specifies the root address of
         this tree-sid replication policy entry."
    DEFVAL      { ''H }
    ::= { vRtrTreeSidReplPlcyEntry 3 }

vRtrTreeSidReplPlcyRootAddrType  OBJECT-TYPE
    SYNTAX      InetAddressType
    MAX-ACCESS  read-create
    STATUS      current
    DESCRIPTION
        "The value of vRtrTreeSidReplPlcyRootAddrType indicates the type of
         address for the BGP peer represented by vRtrTreeSidReplPlcyRootAddr."
    DEFVAL      { unknown }
    ::= { vRtrTreeSidReplPlcyEntry 4 }

vRtrTreeSidReplPlcyTreeId        OBJECT-TYPE
    SYNTAX      Unsigned32 (0 | 8193..16286)
    MAX-ACCESS  read-create
    STATUS      current
    DESCRIPTION
        "The value of vRtrTreeSidReplPlcyTreeId uniquely indentifies a tunnel
         in the root, this also represent a spefic constraint. Also known as
         color and/or p2mp-id"
    DEFVAL      { 0 }
    ::= { vRtrTreeSidReplPlcyEntry 5 }

vRtrTreeSidReplPlcyAdminState    OBJECT-TYPE
    SYNTAX      TmnxAdminState
    MAX-ACCESS  read-create
    STATUS      current
    DESCRIPTION
        "The value of vRtrTreeSidReplPlcyAdminState specifies the desired
         administrative state of tree-sid replication policy entry."
    DEFVAL      { outOfService }
    ::= { vRtrTreeSidReplPlcyEntry 6 }

vRtrTreeSidReplPlcyOperStatus    OBJECT-TYPE
    SYNTAX      TmnxOperState
    MAX-ACCESS  read-only
    STATUS      current
    DESCRIPTION
        "The value of vRtrTreeSidReplPlcyOperStatus indicates the operational
         status for a given tree-sid replication policy instance."
    DEFVAL      { outOfService }
    ::= { vRtrTreeSidReplPlcyEntry 7 }

vRtrTreeSidReplPlcyIncomingSid   OBJECT-TYPE
    SYNTAX      Unsigned32
    MAX-ACCESS  read-create
    STATUS      current
    DESCRIPTION
        "The value of vRtrTreeSidReplPlcyIncomingSid represents the incoming
         label for the transit and leaf routers, root is 0."
    DEFVAL      { 0 }
    ::= { vRtrTreeSidReplPlcyEntry 8 }

vRtrTreeSidReplPlcyOperation     OBJECT-TYPE
    SYNTAX      INTEGER {
        none (0),
        push (1),
        pop  (2),
        swap (3)
    }
    MAX-ACCESS  read-create
    STATUS      current
    DESCRIPTION
        "The value of vRtrTreeSidReplPlcyOperation specifies the Label
         operation for the given tree-sid replication policy instance."
    DEFVAL      { none }
    ::= { vRtrTreeSidReplPlcyEntry 9 }

vRtrTreeSidReplPlcyInstanceId    OBJECT-TYPE
    SYNTAX      Unsigned32
    MAX-ACCESS  read-create
    STATUS      current
    DESCRIPTION
        "The value of the object vRtrTreeSidReplPlcyInstanceId indicates the
         instance identifier for the tree sid replication policy table.

         An instance value of 0 can be set by SNMP to unconfigure the instance
         id for the tree sid replication policy table"
    DEFVAL      { 0 }
    ::= { vRtrTreeSidReplPlcyEntry 10 }

vRtrTreeSdReplPlcyLastChanged    OBJECT-TYPE
    SYNTAX      TimeStamp
    MAX-ACCESS  read-only
    STATUS      current
    DESCRIPTION
        "The value vRtrTreeSdReplPlcyLastChanged indicates when an entry in
         vRtrTreeSidReplPlcyEntry was last changed."
    ::= { vRtrTreeSidReplPlcyEntry 11 }

vRtrTreeSidReplPlcyOrigin        OBJECT-TYPE
    SYNTAX      TmnxTreeSidOrigin
    MAX-ACCESS  read-create
    STATUS      current
    DESCRIPTION
        "The value of vRtrTreeSidReplPlcyOrigin specifies the value of
         protocol-origin of a replication policy which is an 8-bit value which
         identifies the component or protocol that originates or signals the
         replication policy."
    ::= { vRtrTreeSidReplPlcyEntry 12 }

vRtrTrSdReplPlcyRootAddrValid    OBJECT-TYPE
    SYNTAX      TruthValue
    MAX-ACCESS  read-create
    STATUS      current
    DESCRIPTION
        "The value of vRtrTrSdReplPlcyRootAddrValid specifies whether tree-sid
         replication policy has valid root address."
    DEFVAL      { false }
    ::= { vRtrTreeSidReplPlcyEntry 13 }

vRtrTreeSidReplPolNextHopTable   OBJECT-TYPE
    SYNTAX      SEQUENCE OF VRtrTreeSidReplPolNextHopEntry
    MAX-ACCESS  not-accessible
    STATUS      current
    DESCRIPTION
        "The vRtrTreeSidReplPolNextHopTable contains objects to configure next
         hop entries within a replication policy table entry."
    ::= { tmnxTreeSidObjs 10 }

vRtrTreeSidReplPolNextHopEntry   OBJECT-TYPE
    SYNTAX      VRtrTreeSidReplPolNextHopEntry
    MAX-ACCESS  not-accessible
    STATUS      current
    DESCRIPTION
        "The value of vRtrTreeSidReplPolNextHopEntry represents a unique path
         from root to a specific endpoint for the configuration information
         inside a vRtrTreeSidReplPolNextHopTable.

         Entries are created and deleted by the user."
    INDEX       {
        vRtrID,
        vRtrTreeSidReplPlcyName,
        vRtrTreeSidReplPolNextHopId
    }
    ::= { vRtrTreeSidReplPolNextHopTable 1 }

VRtrTreeSidReplPolNextHopEntry   ::= SEQUENCE
{
    vRtrTreeSidReplPolNextHopId      Unsigned32,
    vRtrTreeSidRplPolNHRowStatus     RowStatus,
    vRtrTreeSidReplPolNextHopAddr    InetAddress,
    vRtrTreeSidRplPlNextHopAddrType  InetAddressType,
    vRtrTreeSidReplPolNextHopIfName  TNamedItemOrEmpty,
    vRtrTreeSidRpNextHopProtectId    Unsigned32,
    vRtrTreeSidRpNextHopWeight       Unsigned32,
    vRtrTreeSidRpNextHopLastChanged  TimeStamp,
    vRtrTreeSidRpNextHopAdminState   TmnxAdminState,
    vRtrTreeSidRpNextHopOperState    TmnxOperState
}

vRtrTreeSidReplPolNextHopId      OBJECT-TYPE
    SYNTAX      Unsigned32 (1..4096)
    MAX-ACCESS  not-accessible
    STATUS      current
    DESCRIPTION
        "The value of vRtrTreeSidReplPolNextHopId represents the next-hop group
         index within a candidate path entry inside a tree-side replication
         policy instance."
    ::= { vRtrTreeSidReplPolNextHopEntry 1 }

vRtrTreeSidRplPolNHRowStatus     OBJECT-TYPE
    SYNTAX      RowStatus
    MAX-ACCESS  read-create
    STATUS      current
    DESCRIPTION
        "The value of vRtrTreeSidRplPolNHRowStatus specifies the row status for
         this next hop entry for a given candidate path entry inside a tree-sid
         replication policy instance. It is used to create and delete row
         entries in this table."
    ::= { vRtrTreeSidReplPolNextHopEntry 2 }

vRtrTreeSidReplPolNextHopAddr    OBJECT-TYPE
    SYNTAX      InetAddress (SIZE (0|4|16|20))
    MAX-ACCESS  read-create
    STATUS      current
    DESCRIPTION
        "The value of vRtrTreeSidReplPolNextHopAddr specifies the root address
         of this next-hop entry for a given candidate path entry inside a
         tree-sid replication policy instance."
    DEFVAL      { '00000000'H }
    ::= { vRtrTreeSidReplPolNextHopEntry 3 }

vRtrTreeSidRplPlNextHopAddrType  OBJECT-TYPE
    SYNTAX      InetAddressType
    MAX-ACCESS  read-create
    STATUS      current
    DESCRIPTION
        "The value of vRtrTreeSidRplPlNextHopAddrType indicates the type of
         address for the root address of this next-hop entry for a given
         candidate path entry inside a  tree-sid replication policy instance
         represented by vRtrTreeSidReplPolNextHopAddr."
    DEFVAL      { ipv4 }
    ::= { vRtrTreeSidReplPolNextHopEntry 4 }

vRtrTreeSidReplPolNextHopIfName  OBJECT-TYPE
    SYNTAX      TNamedItemOrEmpty
    MAX-ACCESS  read-create
    STATUS      current
    DESCRIPTION
        "The value of vRtrTreeSidReplPolNextHopIfName specifies the name of
         next hop out going interface for a given candidate path entry inside a
         tree-sid replication policy instance."
    DEFVAL      { "" }
    ::= { vRtrTreeSidReplPolNextHopEntry 5 }

vRtrTreeSidRpNextHopProtectId    OBJECT-TYPE
    SYNTAX      Unsigned32 (0 | 1..4096)
    MAX-ACCESS  read-create
    STATUS      current
    DESCRIPTION
        "The value of vRtrTreeSidRpNextHopProtectId specifies the protection id
         for a given candidate path entry inside a tree-sid replication policy
         instance."
    DEFVAL      { 0 }
    ::= { vRtrTreeSidReplPolNextHopEntry 6 }

vRtrTreeSidRpNextHopWeight       OBJECT-TYPE
    SYNTAX      Unsigned32
    MAX-ACCESS  read-only
    STATUS      current
    DESCRIPTION
        "The value of vRtrTreeSidRpNextHopWeight indicates the weighted load
         balancing value for a given candidate path entry inside a tree-sid
         replication policy instance."
    ::= { vRtrTreeSidReplPolNextHopEntry 7 }

vRtrTreeSidRpNextHopLastChanged  OBJECT-TYPE
    SYNTAX      TimeStamp
    MAX-ACCESS  read-only
    STATUS      current
    DESCRIPTION
        "The value vRtrTreeSidRpNextHopLastChanged indicates when an entry in
         vRtrTreeSidReplPolNextHopEntry was last changed."
    ::= { vRtrTreeSidReplPolNextHopEntry 8 }

vRtrTreeSidRpNextHopAdminState   OBJECT-TYPE
    SYNTAX      TmnxAdminState
    MAX-ACCESS  read-create
    STATUS      current
    DESCRIPTION
        "The value of vRtrTreeSidRpNextHopAdminState specifies the desired
         administrative state of tree-sid replication policy next-hop entry."
    DEFVAL      { outOfService }
    ::= { vRtrTreeSidReplPolNextHopEntry 9 }

vRtrTreeSidRpNextHopOperState    OBJECT-TYPE
    SYNTAX      TmnxOperState
    MAX-ACCESS  read-create
    STATUS      current
    DESCRIPTION
        "The value of vRtrTreeSidRpNextHopOperState indicates the desired
         operational state of tree-sid replication policy next-hop entry."
    ::= { vRtrTreeSidReplPolNextHopEntry 10 }

vRtrTrSdRpNHOutGngReplSdTable    OBJECT-TYPE
    SYNTAX      SEQUENCE OF VRtrTrSdRpNHOutGngReplSdEntry
    MAX-ACCESS  not-accessible
    STATUS      current
    DESCRIPTION
        "The vRtrTrSdRpNHOutGngReplSdTable represents the configuration objects
         to configure the labels of next-hop entries for a given candidate path
         entry within a replication policy table instance."
    ::= { tmnxTreeSidObjs 11 }

vRtrTrSdRpNHOutGngReplSdEntry    OBJECT-TYPE
    SYNTAX      VRtrTrSdRpNHOutGngReplSdEntry
    MAX-ACCESS  not-accessible
    STATUS      current
    DESCRIPTION
        "The vRtrTrSdRpNHOutGngReplSdEntry represents the replication label for
         this nexthop instance."
    INDEX       {
        vRtrID,
        vRtrTreeSidReplPlcyName,
        vRtrTreeSidReplPolNextHopId,
        vRtrTrSdRpNHOutGngReplSdIndex
    }
    ::= { vRtrTrSdRpNHOutGngReplSdTable 1 }

VRtrTrSdRpNHOutGngReplSdEntry    ::= SEQUENCE
{
    vRtrTrSdRpNHOutGngReplSdIndex    Unsigned32,
    vRtrTrSdRpNHOutGngReplSdLabel    Unsigned32,
    vRtrTrSdRpNHOGRplSdLstChanged    TimeStamp
}

vRtrTrSdRpNHOutGngReplSdIndex    OBJECT-TYPE
    SYNTAX      Unsigned32 (0 | 1..2)
    MAX-ACCESS  not-accessible
    STATUS      current
    DESCRIPTION
        "The value of vRtrTrSdRpNHOutGngReplSdIndex represents the Index for
         push-label."
    DEFVAL      { 0 }
    ::= { vRtrTrSdRpNHOutGngReplSdEntry 1 }

vRtrTrSdRpNHOutGngReplSdLabel    OBJECT-TYPE
    SYNTAX      Unsigned32 (3 | 16..1048576 | 4294967295)
    MAX-ACCESS  read-create
    STATUS      current
    DESCRIPTION
        "The value of vRtrTrSdRpNHOutGngReplSdLabel represents the value for
         push-label."
    DEFVAL      { 4294967295 }
    ::= { vRtrTrSdRpNHOutGngReplSdEntry 2 }

vRtrTrSdRpNHOGRplSdLstChanged    OBJECT-TYPE
    SYNTAX      TimeStamp
    MAX-ACCESS  read-only
    STATUS      current
    DESCRIPTION
        "The value vRtrTrSdRpNHOGRplSdLstChanged indicates when an entry in
         vRtrTrSdRpNHOutGngReplSdEntry was last changed."
    ::= { vRtrTrSdRpNHOutGngReplSdEntry 3 }

vRtrTreeSidInstanceTable         OBJECT-TYPE
    SYNTAX      SEQUENCE OF VRtrTreeSidInstanceEntry
    MAX-ACCESS  not-accessible
    STATUS      current
    DESCRIPTION
        "The vRtrTreeSidInstanceTable represents the configuration objects to
         configure the instances for the tree-sid application."
    ::= { tmnxTreeSidObjs 12 }

vRtrTreeSidInstanceEntry         OBJECT-TYPE
    SYNTAX      VRtrTreeSidInstanceEntry
    MAX-ACCESS  not-accessible
    STATUS      current
    DESCRIPTION
        "The vRtrTreeSidInstanceEntry represents the instances for the tree sid
         application."
    INDEX       {
        vRtrID,
        vRtrTreeSidPolicyName,
        vRtrTreeSidPolicyCdtPathName,
        vRtrTreeSidInstIndex
    }
    ::= { vRtrTreeSidInstanceTable 1 }

VRtrTreeSidInstanceEntry         ::= SEQUENCE
{
    vRtrTreeSidInstIndex             Unsigned32,
    vRtrTreeSidInstance              Unsigned32,
    vRtrTreeSidInstLastChanged       TimeStamp
}

vRtrTreeSidInstIndex             OBJECT-TYPE
    SYNTAX      Unsigned32 (1..2)
    MAX-ACCESS  not-accessible
    STATUS      current
    DESCRIPTION
        "The value of vRtrTreeSidInstIndex specifies the index of this tree-sid
         instance."
    ::= { vRtrTreeSidInstanceEntry 1 }

vRtrTreeSidInstance              OBJECT-TYPE
    SYNTAX      Unsigned32
    MAX-ACCESS  read-create
    STATUS      current
    DESCRIPTION
        "The value of vRtrTreeSidInstance specifies the instance value of a
         vRtrTreeSidInstance."
    DEFVAL      { 0 }
    ::= { vRtrTreeSidInstanceEntry 4 }

vRtrTreeSidInstLastChanged       OBJECT-TYPE
    SYNTAX      TimeStamp
    MAX-ACCESS  read-only
    STATUS      current
    DESCRIPTION
        "The value vRtrTreeSidInstLastChanged indicates when an entry in
         vRtrTreeSidInstanceTable was last changed."
    ::= { vRtrTreeSidInstanceEntry 5 }

vRtrTreeSidStatsTable            OBJECT-TYPE
    SYNTAX      SEQUENCE OF VRtrTreeSidStatsEntry
    MAX-ACCESS  not-accessible
    STATUS      current
    DESCRIPTION
        "The vRtrTreeSidStatsTable contain statisitics objects for tree-sid
         feature."
    ::= { tmnxTreeSidObjs 13 }

vRtrTreeSidStatsEntry            OBJECT-TYPE
    SYNTAX      VRtrTreeSidStatsEntry
    MAX-ACCESS  not-accessible
    STATUS      current
    DESCRIPTION
        "The value of vRtrTreeSidStatsEntry represents a tree-sid statistics
         entry information."
    INDEX       { vRtrID }
    ::= { vRtrTreeSidStatsTable 1 }

VRtrTreeSidStatsEntry            ::= SEQUENCE
{
    vRtrTreeSidNumP2mpStaticPolicies Unsigned32,
    vRtrTreeSidNumP2mpPcePolicies    Unsigned32,
    vRtrTreeSidNumP2mpSrPolicies     Unsigned32,
    vRtrTreeSidP2mpCdtPathStatic     Unsigned32,
    vRtrTreeSidP2mpCdtPathPce        Unsigned32,
    vRtrTreeSidP2mpCdtPathSrPolicy   Unsigned32,
    vRtrTreeSidReplSegStatic         Unsigned32,
    vRtrTreeSidReplSegPce            Unsigned32,
    vRtrTreeSidReplSegSrPolicy       Unsigned32,
    vRtrTreeSidNHStatic              Unsigned32,
    vRtrTreeSidNHPce                 Unsigned32,
    vRtrTreeSidNHSrPolicy            Unsigned32,
    vRtrTreeSidNumPush               Unsigned32,
    vRtrTreeSidNumSwap               Unsigned32,
    vRtrTreeSidNumPop                Unsigned32,
    vRtrTreeSidTnlsAlloc             Unsigned32,
    vRtrTreeSidNHIfInSvc             Unsigned32,
    vRtrTreeSidNHIfOutSvc            Unsigned32,
    vRtrTreeSidNHIfUnsup             Unsigned32,
    vRtrTreeSidNHIfMismatch          Unsigned32,
    vRtrTreeSidNHIfNoBfd             Unsigned32,
    vRtrTreeSidDPBackPressureActive  TruthValue,
    vRtrTreeSidDPBackPressureCount   Unsigned32,
    vRtrTreeSidErrorUnknOrigOwner    Unsigned32,
    vRtrTreeSidErrorDupTreeIds       Unsigned32,
    vRtrTreeSidErrorProgFailNHIdx    Unsigned32,
    vRtrTreeSidErrorProgFailLabels   Unsigned32,
    vRtrTreeSidErrorProgFailTunnels  Unsigned32,
    vRtrTreeSidErrorProgFailProtGrp  Unsigned32
}

vRtrTreeSidNumP2mpStaticPolicies OBJECT-TYPE
    SYNTAX      Unsigned32
    MAX-ACCESS  read-only
    STATUS      current
    DESCRIPTION
        "The vRtrTreeSidNumP2mpStaticPolicies indicates number of static P2MP
         policies."
    ::= { vRtrTreeSidStatsEntry 1 }

vRtrTreeSidNumP2mpPcePolicies    OBJECT-TYPE
    SYNTAX      Unsigned32
    MAX-ACCESS  read-only
    STATUS      current
    DESCRIPTION
        "The vRtrTreeSidNumP2mpPcePolicies indicates number of PCE P2MP
         policies."
    ::= { vRtrTreeSidStatsEntry 2 }

vRtrTreeSidNumP2mpSrPolicies     OBJECT-TYPE
    SYNTAX      Unsigned32
    MAX-ACCESS  read-only
    STATUS      current
    DESCRIPTION
        "The vRtrTreeSidNumP2mpSrPolicies indicates number of SR-Policy P2MP
         policies."
    ::= { vRtrTreeSidStatsEntry 3 }

vRtrTreeSidP2mpCdtPathStatic     OBJECT-TYPE
    SYNTAX      Unsigned32
    MAX-ACCESS  read-only
    STATUS      current
    DESCRIPTION
        "The vRtrTreeSidP2mpCdtPathStatic indicates number of static P2MP
         candidate-paths."
    ::= { vRtrTreeSidStatsEntry 4 }

vRtrTreeSidP2mpCdtPathPce        OBJECT-TYPE
    SYNTAX      Unsigned32
    MAX-ACCESS  read-only
    STATUS      current
    DESCRIPTION
        "The vRtrTreeSidP2mpCdtPathPce indicates number of PCE P2MP
         candidate-paths."
    ::= { vRtrTreeSidStatsEntry 5 }

vRtrTreeSidP2mpCdtPathSrPolicy   OBJECT-TYPE
    SYNTAX      Unsigned32
    MAX-ACCESS  read-only
    STATUS      current
    DESCRIPTION
        "The vRtrTreeSidP2mpCdtPathSrPolicy indicates number of SR-policy P2MP
         candidate-paths."
    ::= { vRtrTreeSidStatsEntry 6 }

vRtrTreeSidReplSegStatic         OBJECT-TYPE
    SYNTAX      Unsigned32
    MAX-ACCESS  read-only
    STATUS      current
    DESCRIPTION
        "The vRtrTreeSidReplSegStatic indicates number of static P2MP
         replication-segments."
    ::= { vRtrTreeSidStatsEntry 7 }

vRtrTreeSidReplSegPce            OBJECT-TYPE
    SYNTAX      Unsigned32
    MAX-ACCESS  read-only
    STATUS      current
    DESCRIPTION
        "The vRtrTreeSidReplSegPce indicates number of PCE P2MP
         replication-segments."
    ::= { vRtrTreeSidStatsEntry 8 }

vRtrTreeSidReplSegSrPolicy       OBJECT-TYPE
    SYNTAX      Unsigned32
    MAX-ACCESS  read-only
    STATUS      current
    DESCRIPTION
        "The vRtrTreeSidReplSegSrPolicy indicates number of SR-policy P2MP
         replication-segments."
    ::= { vRtrTreeSidStatsEntry 9 }

vRtrTreeSidNHStatic              OBJECT-TYPE
    SYNTAX      Unsigned32
    MAX-ACCESS  read-only
    STATUS      current
    DESCRIPTION
        "The vRtrTreeSidNHStatic indicates number of static next-hops."
    ::= { vRtrTreeSidStatsEntry 10 }

vRtrTreeSidNHPce                 OBJECT-TYPE
    SYNTAX      Unsigned32
    MAX-ACCESS  read-only
    STATUS      current
    DESCRIPTION
        "The vRtrTreeSidNHPce indicates number of PCE next-hops."
    ::= { vRtrTreeSidStatsEntry 11 }

vRtrTreeSidNHSrPolicy            OBJECT-TYPE
    SYNTAX      Unsigned32
    MAX-ACCESS  read-only
    STATUS      current
    DESCRIPTION
        "The vRtrTreeSidNHSrPolicy indicates number of PCE next-hops."
    ::= { vRtrTreeSidStatsEntry 12 }

vRtrTreeSidNumPush               OBJECT-TYPE
    SYNTAX      Unsigned32
    MAX-ACCESS  read-only
    STATUS      current
    DESCRIPTION
        "The vRtrTreeSidNumPush indicates number of pushes."
    ::= { vRtrTreeSidStatsEntry 13 }

vRtrTreeSidNumSwap               OBJECT-TYPE
    SYNTAX      Unsigned32
    MAX-ACCESS  read-only
    STATUS      current
    DESCRIPTION
        "The vRtrTreeSidNumSwap indicates number of swaps."
    ::= { vRtrTreeSidStatsEntry 14 }

vRtrTreeSidNumPop                OBJECT-TYPE
    SYNTAX      Unsigned32
    MAX-ACCESS  read-only
    STATUS      current
    DESCRIPTION
        "The vRtrTreeSidNumPop indicates number of pops."
    ::= { vRtrTreeSidStatsEntry 15 }

vRtrTreeSidTnlsAlloc             OBJECT-TYPE
    SYNTAX      Unsigned32
    MAX-ACCESS  read-only
    STATUS      current
    DESCRIPTION
        "The vRtrTreeSidTnlsAlloc indicates number of tunnels allocated."
    ::= { vRtrTreeSidStatsEntry 16 }

vRtrTreeSidNHIfInSvc             OBJECT-TYPE
    SYNTAX      Unsigned32
    MAX-ACCESS  read-only
    STATUS      current
    DESCRIPTION
        "The vRtrTreeSidNHIfInSvc indicates number of in-service next-hop
         interfaces."
    ::= { vRtrTreeSidStatsEntry 17 }

vRtrTreeSidNHIfOutSvc            OBJECT-TYPE
    SYNTAX      Unsigned32
    MAX-ACCESS  read-only
    STATUS      current
    DESCRIPTION
        "The vRtrTreeSidNHIfOutSvc indicates number of out-of-service next-hop
         interfaces."
    ::= { vRtrTreeSidStatsEntry 18 }

vRtrTreeSidNHIfUnsup             OBJECT-TYPE
    SYNTAX      Unsigned32
    MAX-ACCESS  read-only
    STATUS      current
    DESCRIPTION
        "The vRtrTreeSidNHIfUnsup indicates number of unsupported next-hop
         interfaces."
    ::= { vRtrTreeSidStatsEntry 19 }

vRtrTreeSidNHIfMismatch          OBJECT-TYPE
    SYNTAX      Unsigned32
    MAX-ACCESS  read-only
    STATUS      current
    DESCRIPTION
        "The vRtrTreeSidNHIfMismatch indicates number of mismatched next-hop
         interfaces."
    ::= { vRtrTreeSidStatsEntry 20 }

vRtrTreeSidNHIfNoBfd             OBJECT-TYPE
    SYNTAX      Unsigned32
    MAX-ACCESS  read-only
    STATUS      current
    DESCRIPTION
        "The vRtrTreeSidNHIfNoBfd indicates number of next-hop interfaces
         without BFD."
    ::= { vRtrTreeSidStatsEntry 21 }

vRtrTreeSidDPBackPressureActive  OBJECT-TYPE
    SYNTAX      TruthValue
    MAX-ACCESS  read-only
    STATUS      current
    DESCRIPTION
        "The vRtrTreeSidDPBackPressureActive indicates whether data-plane is
         experiencing back-pressure."
    ::= { vRtrTreeSidStatsEntry 22 }

vRtrTreeSidDPBackPressureCount   OBJECT-TYPE
    SYNTAX      Unsigned32
    MAX-ACCESS  read-only
    STATUS      current
    DESCRIPTION
        "The vRtrTreeSidDPBackPressureCount indicates number of active
         data-plane back-pressure."
    ::= { vRtrTreeSidStatsEntry 23 }

vRtrTreeSidErrorUnknOrigOwner    OBJECT-TYPE
    SYNTAX      Unsigned32
    MAX-ACCESS  read-only
    STATUS      current
    DESCRIPTION
        "The vRtrTreeSidErrorUnknOrigOwner indicates unknown originator owner
         errors."
    ::= { vRtrTreeSidStatsEntry 24 }

vRtrTreeSidErrorDupTreeIds       OBJECT-TYPE
    SYNTAX      Unsigned32
    MAX-ACCESS  read-only
    STATUS      current
    DESCRIPTION
        "The vRtrTreeSidErrorDupTreeIds indicates duplicate tree-identifier
         errors."
    ::= { vRtrTreeSidStatsEntry 25 }

vRtrTreeSidErrorProgFailNHIdx    OBJECT-TYPE
    SYNTAX      Unsigned32
    MAX-ACCESS  read-only
    STATUS      current
    DESCRIPTION
        "The vRtrTreeSidErrorProgFailNHIdx indicates programming failures due
         to next-hop index."
    ::= { vRtrTreeSidStatsEntry 26 }

vRtrTreeSidErrorProgFailLabels   OBJECT-TYPE
    SYNTAX      Unsigned32
    MAX-ACCESS  read-only
    STATUS      current
    DESCRIPTION
        "The vRtrTreeSidErrorProgFailLabels indicates programming failures due
         to labels."
    ::= { vRtrTreeSidStatsEntry 27 }

vRtrTreeSidErrorProgFailTunnels  OBJECT-TYPE
    SYNTAX      Unsigned32
    MAX-ACCESS  read-only
    STATUS      current
    DESCRIPTION
        "The vRtrTreeSidErrorProgFailTunnels indicates programming failures due
         to tunnels."
    ::= { vRtrTreeSidStatsEntry 28 }

vRtrTreeSidErrorProgFailProtGrp  OBJECT-TYPE
    SYNTAX      Unsigned32
    MAX-ACCESS  read-only
    STATUS      current
    DESCRIPTION
        "The vRtrTreeSidErrorProgFailProtGrp indicates programming failures due
         to protection-group."
    ::= { vRtrTreeSidStatsEntry 29 }

vRtrTreeSidLabelTable            OBJECT-TYPE
    SYNTAX      SEQUENCE OF VRtrTreeSidLabelEntry
    MAX-ACCESS  not-accessible
    STATUS      current
    DESCRIPTION
        "The vRtrTreeSidLabelTable contain information about labels for
         tree-sid feature."
    ::= { tmnxTreeSidObjs 14 }

vRtrTreeSidLabelEntry            OBJECT-TYPE
    SYNTAX      VRtrTreeSidLabelEntry
    MAX-ACCESS  not-accessible
    STATUS      current
    DESCRIPTION
        "The value of vRtrTreeSidLabelEntry represents tree-sid information
         about specific label."
    INDEX       {
        vRtrID,
        vRtrTreeSidLabel
    }
    ::= { vRtrTreeSidLabelTable 1 }

VRtrTreeSidLabelEntry            ::= SEQUENCE
{
    vRtrTreeSidLabel                 Integer32,
    vRtrTreeSidLabelInUse            TruthValue,
    vRtrTreeSidLabelOwner            TmnxTreeSidOwner
}

vRtrTreeSidLabel                 OBJECT-TYPE
    SYNTAX      Integer32
    MAX-ACCESS  not-accessible
    STATUS      current
    DESCRIPTION
        "The vRtrTreeSidLabel indicates the associated label."
    ::= { vRtrTreeSidLabelEntry 1 }

vRtrTreeSidLabelInUse            OBJECT-TYPE
    SYNTAX      TruthValue
    MAX-ACCESS  read-only
    STATUS      current
    DESCRIPTION
        "The vRtrTreeSidLabelInUse indicates whether label is in-use."
    ::= { vRtrTreeSidLabelEntry 2 }

vRtrTreeSidLabelOwner            OBJECT-TYPE
    SYNTAX      TmnxTreeSidOwner
    MAX-ACCESS  read-only
    STATUS      current
    DESCRIPTION
        "The vRtrTreeSidLabelOwner indicates the owner of this label."
    ::= { vRtrTreeSidLabelEntry 3 }

vRtrTreeSidLabelSummaryTable     OBJECT-TYPE
    SYNTAX      SEQUENCE OF VRtrTreeSidLabelSummaryEntry
    MAX-ACCESS  not-accessible
    STATUS      current
    DESCRIPTION
        "The vRtrTreeSidLabelSummaryTable contains information about the start
         label, end label, and the number of in-use labels."
    ::= { tmnxTreeSidObjs 15 }

vRtrTreeSidLabelSummaryEntry     OBJECT-TYPE
    SYNTAX      VRtrTreeSidLabelSummaryEntry
    MAX-ACCESS  not-accessible
    STATUS      current
    DESCRIPTION
        "The vRtrTreeSidLabelSummaryEntry represents tree-sid information about
         the start, end,  and number of in-use labels."
    INDEX       { vRtrID }
    ::= { vRtrTreeSidLabelSummaryTable 1 }

VRtrTreeSidLabelSummaryEntry     ::= SEQUENCE
{
    vRtrTreeSidLabelSummaryStart     Integer32,
    vRtrTreeSidLabelSummaryInUse     Integer32,
    vRtrTreeSidLabelSummaryEnd       Integer32
}

vRtrTreeSidLabelSummaryStart     OBJECT-TYPE
    SYNTAX      Integer32
    MAX-ACCESS  read-only
    STATUS      current
    DESCRIPTION
        "The vRtrTreeSidLabelSummaryStart indicates the beginnning label."
    ::= { vRtrTreeSidLabelSummaryEntry 1 }

vRtrTreeSidLabelSummaryInUse     OBJECT-TYPE
    SYNTAX      Integer32
    MAX-ACCESS  read-only
    STATUS      current
    DESCRIPTION
        "The vRtrTreeSidLabelSummaryInUse indicates the number of in-use
         labels."
    ::= { vRtrTreeSidLabelSummaryEntry 2 }

vRtrTreeSidLabelSummaryEnd       OBJECT-TYPE
    SYNTAX      Integer32
    MAX-ACCESS  read-only
    STATUS      current
    DESCRIPTION
        "The vRtrTreeSidLabelSummaryEnd indicates the the last label."
    ::= { vRtrTreeSidLabelSummaryEntry 3 }

vRtrTreeSidDBP2mpPlcyTable       OBJECT-TYPE
    SYNTAX      SEQUENCE OF VRtrTreeSidDBP2mpPlcyEntry
    MAX-ACCESS  not-accessible
    STATUS      current
    DESCRIPTION
        "The vRtrTreeSidDBP2mpPlcyTable contains objects for a tree-sid
         database p2mp-policy table"
    ::= { tmnxTreeSidObjs 16 }

vRtrTreeSidDBP2mpPlcyEntry       OBJECT-TYPE
    SYNTAX      VRtrTreeSidDBP2mpPlcyEntry
    MAX-ACCESS  not-accessible
    STATUS      current
    DESCRIPTION
        "The value of vRtrTreeSidDBP2mpPlcyEntry represents a tree-sid database
         p2mp-policy entry information."
    INDEX       {
        vRtrID,
        vRtrTreeSidDBP2mpPlcyRootAddr,
        vRtrTreeSidDBP2mpPlcyRtAddrType,
        vRtrTreeSidDBP2mpPlcyTreeId
    }
    ::= { vRtrTreeSidDBP2mpPlcyTable 1 }

VRtrTreeSidDBP2mpPlcyEntry       ::= SEQUENCE
{
    vRtrTreeSidDBP2mpPlcyRootAddr    InetAddress,
    vRtrTreeSidDBP2mpPlcyTreeId      Unsigned32,
    vRtrTreeSidDBP2mpPlcyNumPaths    Unsigned32,
    vRtrTreeSidDBP2mpPlcyOperState   TmnxOperState,
    vRtrTreeSidDBPolicyName          TNamedItem,
    vRtrTreeSidDBP2mpPlcyRtAddrType  InetAddressType,
    vRtrTreeSidDBP2mpPlcyTunnelIdx   Unsigned32,
    vRtrTrSdDBP2mpPlcyActCdtPthName  TNamedItemOrEmpty
}

vRtrTreeSidDBP2mpPlcyRootAddr    OBJECT-TYPE
    SYNTAX      InetAddress (SIZE (0|4))
    MAX-ACCESS  not-accessible
    STATUS      current
    DESCRIPTION
        "The value of vRtrTreeSidDBP2mpPlcyRootAddr indicates the root address
         of this tree-sid database p2mp-policy entry."
    DEFVAL      { '00000000'H }
    ::= { vRtrTreeSidDBP2mpPlcyEntry 1 }

vRtrTreeSidDBP2mpPlcyTreeId      OBJECT-TYPE
    SYNTAX      Unsigned32
    MAX-ACCESS  not-accessible
    STATUS      current
    DESCRIPTION
        "The value of vRtrTreeSidDBP2mpPlcyTreeId indicates a tunnel in the
         root, this also indicate a spefic constraint. Also known as color
         and/or p2mp-id"
    DEFVAL      { 0 }
    ::= { vRtrTreeSidDBP2mpPlcyEntry 2 }

vRtrTreeSidDBP2mpPlcyNumPaths    OBJECT-TYPE
    SYNTAX      Unsigned32
    MAX-ACCESS  read-only
    STATUS      current
    DESCRIPTION
        "The value of vRtrTreeSidDBP2mpPlcyNumPaths indicates the total number
         of candidate paths of the tree-sid database p2mp-policy entry."
    ::= { vRtrTreeSidDBP2mpPlcyEntry 3 }

vRtrTreeSidDBP2mpPlcyOperState   OBJECT-TYPE
    SYNTAX      TmnxOperState
    MAX-ACCESS  read-only
    STATUS      current
    DESCRIPTION
        "The value of vRtrTreeSidDBP2mpPlcyOperState indicates the operational
         state of tree-sid database p2mp-policy entry."
    DEFVAL      { outOfService }
    ::= { vRtrTreeSidDBP2mpPlcyEntry 4 }

vRtrTreeSidDBPolicyName          OBJECT-TYPE
    SYNTAX      TNamedItem
    MAX-ACCESS  read-only
    STATUS      current
    DESCRIPTION
        "The value of vRtrTreeSidDBPolicyName indicates the name of this
         tree-sid policy entry."
    ::= { vRtrTreeSidDBP2mpPlcyEntry 5 }

vRtrTreeSidDBP2mpPlcyRtAddrType  OBJECT-TYPE
    SYNTAX      InetAddressType
    MAX-ACCESS  not-accessible
    STATUS      current
    DESCRIPTION
        "The value of vRtrTreeSidDBP2mpPlcyRtAddrType indicates the type of
         address for the tree-sid database p2mp-policy entry represented by
         vRtrTreeSidDBP2mpPlcyRootAddr."
    DEFVAL      { ipv4 }
    ::= { vRtrTreeSidDBP2mpPlcyEntry 6 }

vRtrTreeSidDBP2mpPlcyTunnelIdx   OBJECT-TYPE
    SYNTAX      Unsigned32
    MAX-ACCESS  read-only
    STATUS      current
    DESCRIPTION
        "The value of vRtrTreeSidDBP2mpPlcyTunnelIdx indicates the tunnel index
         of the tree-sid database p2mp-policy entry."
    ::= { vRtrTreeSidDBP2mpPlcyEntry 7 }

vRtrTrSdDBP2mpPlcyActCdtPthName  OBJECT-TYPE
    SYNTAX      TNamedItemOrEmpty
    MAX-ACCESS  read-only
    STATUS      current
    DESCRIPTION
        "The value of vRtrTrSdDBP2mpPlcyActCdtPthName indicates a path name of
         a given instance within a tree-sid replication that is active for the
         given policy."
    DEFVAL      { "" }
    ::= { vRtrTreeSidDBP2mpPlcyEntry 8 }

vRtrTreeSidDBP2mpPlcyCPathTable  OBJECT-TYPE
    SYNTAX      SEQUENCE OF VRtrTreeSidDBP2mpPlcyCPathEntry
    MAX-ACCESS  not-accessible
    STATUS      current
    DESCRIPTION
        "The vRtrTreeSidDBP2mpPlcyCPathTable contains objects for a tree-sid
         database p2mp-policy candidate-path table"
    ::= { tmnxTreeSidObjs 17 }

vRtrTreeSidDBP2mpPlcyCPathEntry  OBJECT-TYPE
    SYNTAX      VRtrTreeSidDBP2mpPlcyCPathEntry
    MAX-ACCESS  not-accessible
    STATUS      current
    DESCRIPTION
        "The value of vRtrTreeSidDBP2mpPlcyCPathEntry represents a tree-sid
         database p2mp-policy candidate-path entry information."
    INDEX       {
        vRtrID,
        vRtrTreeSidDBP2mpPlcyRootAddr,
        vRtrTreeSidDBP2mpPlcyRtAddrType,
        vRtrTreeSidDBP2mpPlcyTreeId,
        vRtrTreeSidDBP2mpPlcyCPOrigin,
        vRtrTrSdDBPlcyCPOriginatorAsn,
        vRtrTrSidDBPlcyCPOrigNodeAddr,
        vRtrTrSdDBPlcyCPDescriminator,
        vRtrTSDBPlcyCPOrigNodeAddrType
    }
    ::= { vRtrTreeSidDBP2mpPlcyCPathTable 1 }

VRtrTreeSidDBP2mpPlcyCPathEntry  ::= SEQUENCE
{
    vRtrTreeSidDBP2mpPlcyCPOrigin    TmnxTreeSidOrigin,
    vRtrTrSdDBPlcyCPOriginatorAsn    Unsigned32,
    vRtrTrSidDBPlcyCPOrigNodeAddr    InetAddress,
    vRtrTSDBPlcyCPOrigNodeAddrType   InetAddressType,
    vRtrTrSdDBPlcyCPDescriminator    Unsigned32,
    vRtrTreeSidDBPlcyCdtPathName     TNamedItem,
    vRtrTreeSidDBPlcyCPOperState     TmnxOperState,
    vRtrTreeSidDBPlcyCPLastChgd      TimeStamp,
    vRtrTreeSidDBPlcyCdtPthPlspId    Unsigned32,
    vRtrTreeSidDBPlcyCPActiveInst    Unsigned32,
    vRtrTreeSidDBPlcyCPSByInst       Unsigned32,
    vRtrTreeSidDBPlcyCPPreference    Unsigned32
}

vRtrTreeSidDBP2mpPlcyCPOrigin    OBJECT-TYPE
    SYNTAX      TmnxTreeSidOrigin
    MAX-ACCESS  not-accessible
    STATUS      current
    DESCRIPTION
        "The value of vRtrTreeSidDBP2mpPlcyCPOrigin indicates the value of
         protocol-origin of a candidate path which is an 8-bit value which
         identifies the component or protocol that originates or signals the
         candidate path."
    ::= { vRtrTreeSidDBP2mpPlcyCPathEntry 1 }

vRtrTrSdDBPlcyCPOriginatorAsn    OBJECT-TYPE
    SYNTAX      Unsigned32
    MAX-ACCESS  not-accessible
    STATUS      current
    DESCRIPTION
        "The value of vRtrTrSdDBPlcyCPOriginatorAsn indicates a 4 byte number
         to represent the originator asn value for a given candidate path entry
         inside a tree-sid replication policy instance."
    ::= { vRtrTreeSidDBP2mpPlcyCPathEntry 2 }

vRtrTrSidDBPlcyCPOrigNodeAddr    OBJECT-TYPE
    SYNTAX      InetAddress (SIZE (0|4|16))
    MAX-ACCESS  not-accessible
    STATUS      current
    DESCRIPTION
        "The value of vRtrTrSidDBPlcyCPOrigNodeAddr indicates the originator
         address of this tree-sid candidate path entry."
    DEFVAL      { ''H }
    ::= { vRtrTreeSidDBP2mpPlcyCPathEntry 3 }

vRtrTSDBPlcyCPOrigNodeAddrType   OBJECT-TYPE
    SYNTAX      InetAddressType
    MAX-ACCESS  not-accessible
    STATUS      current
    DESCRIPTION
        "The value of vRtrTSDBPlcyCPOrigNodeAddrType indicates the type of
         address for the tree-sid database replication-segment entry
         represented by vRtrTrSidDBPlcyCPOrigNodeAddr."
    ::= { vRtrTreeSidDBP2mpPlcyCPathEntry 4 }

vRtrTrSdDBPlcyCPDescriminator    OBJECT-TYPE
    SYNTAX      Unsigned32
    MAX-ACCESS  not-accessible
    STATUS      current
    DESCRIPTION
        "The value of vRtrTrSdDBPlcyCPDescriminator indicates a 32 bit value
         associated with a vRtrTreeSidDBP2mpPlcyCPathTable that uniquely
         identifies it within the context of an SR Policy from a specific
         Protocol-Origin."
    ::= { vRtrTreeSidDBP2mpPlcyCPathEntry 5 }

vRtrTreeSidDBPlcyCdtPathName     OBJECT-TYPE
    SYNTAX      TNamedItem
    MAX-ACCESS  read-only
    STATUS      current
    DESCRIPTION
        "The value of vRtrTreeSidDBPlcyCdtPathName indicates a path name of a
         given candidate path table instance within a tree-sid replication
         policy table entry and it is equivalent to an LSP."
    ::= { vRtrTreeSidDBP2mpPlcyCPathEntry 6 }

vRtrTreeSidDBPlcyCPOperState     OBJECT-TYPE
    SYNTAX      TmnxOperState
    MAX-ACCESS  read-only
    STATUS      current
    DESCRIPTION
        "The value of vRtrTreeSidDBPlcyCPOperState indicates the operational
         state of a vRtrTreeSidDBP2mpPlcyCPathEntry based on ilm programming."
    DEFVAL      { outOfService }
    ::= { vRtrTreeSidDBP2mpPlcyCPathEntry 7 }

vRtrTreeSidDBPlcyCPLastChgd      OBJECT-TYPE
    SYNTAX      TimeStamp
    MAX-ACCESS  read-only
    STATUS      current
    DESCRIPTION
        "The value vRtrTreeSidDBPlcyCPLastChgd indicates when an entry in
         vRtrTreeSidDBP2mpPlcyCPathTable was last changed."
    ::= { vRtrTreeSidDBP2mpPlcyCPathEntry 8 }

vRtrTreeSidDBPlcyCdtPthPlspId    OBJECT-TYPE
    SYNTAX      Unsigned32
    MAX-ACCESS  read-only
    STATUS      current
    DESCRIPTION
        "The value of vRtrTreeSidDBPlcyCdtPthPlspId indicates a identifier
         assigned by the controller and remain unchanged througout the life of
         a LSP (candidate path) for a given vRtrTreeSidDBP2mpPlcyCPathEntry."
    DEFVAL      { 0 }
    ::= { vRtrTreeSidDBP2mpPlcyCPathEntry 9 }

vRtrTreeSidDBPlcyCPActiveInst    OBJECT-TYPE
    SYNTAX      Unsigned32
    MAX-ACCESS  read-only
    STATUS      current
    DESCRIPTION
        "The value of vRtrTreeSidDBPlcyCPActiveInst indicates the active
         instance value of a database p2mp policy candidate path instance."
    DEFVAL      { 0 }
    ::= { vRtrTreeSidDBP2mpPlcyCPathEntry 10 }

vRtrTreeSidDBPlcyCPSByInst       OBJECT-TYPE
    SYNTAX      Unsigned32
    MAX-ACCESS  read-only
    STATUS      current
    DESCRIPTION
        "The value of vRtrTreeSidDBPlcyCPSByInst indicates the standby instance
         value of a database p2mp policy candidate path instance."
    DEFVAL      { 0 }
    ::= { vRtrTreeSidDBP2mpPlcyCPathEntry 11 }

vRtrTreeSidDBPlcyCPPreference    OBJECT-TYPE
    SYNTAX      Unsigned32
    MAX-ACCESS  read-only
    STATUS      current
    DESCRIPTION
        "The value of vRtrTreeSidDBPlcyCPPreference indicates the best
         preferred candidate-path among the list of candiate paths towards a
         leaf, Higher preference is choosen."
    DEFVAL      { 100 }
    ::= { vRtrTreeSidDBP2mpPlcyCPathEntry 12 }

vRtrTreeSidDBReplPlcyTable       OBJECT-TYPE
    SYNTAX      SEQUENCE OF VRtrTreeSidDBReplPlcyEntry
    MAX-ACCESS  not-accessible
    STATUS      current
    DESCRIPTION
        "The vRtrTreeSidDBReplPlcyTable contains objects to configure a
         tree-sid database replication policy table."
    ::= { tmnxTreeSidObjs 18 }

vRtrTreeSidDBReplPlcyEntry       OBJECT-TYPE
    SYNTAX      VRtrTreeSidDBReplPlcyEntry
    MAX-ACCESS  not-accessible
    STATUS      current
    DESCRIPTION
        "The value of vRtrTreeSidDBReplPlcyEntry represents a tree-sid
         replication policy configuration information."
    INDEX       {
        vRtrID,
        vRtrTreeSidDBReplPlcyRootAddr,
        vRtrTreeSidDBReplPlcyRtAddrType,
        vRtrTreeSidDBReplPlcyTreeId,
        vRtrTreeSidDBReplPlcyInstanceId,
        vRtrTreeSidDBReplPlcyOrigin
    }
    ::= { vRtrTreeSidDBReplPlcyTable 1 }

VRtrTreeSidDBReplPlcyEntry       ::= SEQUENCE
{
    vRtrTreeSidDBReplPlcyRootAddr    InetAddress,
    vRtrTreeSidDBReplPlcyRtAddrType  InetAddressType,
    vRtrTreeSidDBReplPlcyTreeId      Unsigned32,
    vRtrTreeSidDBReplPlcyNumHops     Unsigned32,
    vRtrTreeSidDBReplPlcyInstanceId  Unsigned32,
    vRtrTreeSidDBReplPlcyOperStatus  TmnxOperState,
    vRtrTreeSidDBReplPlcyName        TNamedItem,
    vRtrTreeSidDBReplPlcyOrigin      TmnxTreeSidOrigin,
    vRtrTreeSidDBReplPlcyTunnelIdx   Unsigned32,
    vRtrTreeSidDBReplPlcyDownReason  INTEGER,
    vRtrTreeSidDBReplPlcyOperation   INTEGER,
    vRtrTreeSidDBRplPlcyIncomingSid  Unsigned32,
    vRtrTreeSidDBReplPlcyLtn         TruthValue,
    vRtrTreeSidDBReplPlcyIsLocal     TruthValue,
    vRtrTreeSidDBReplPlcyCCID        Unsigned32,
    vRtrTreeSidDBReplPlcyUpdateId    Unsigned32
}

vRtrTreeSidDBReplPlcyRootAddr    OBJECT-TYPE
    SYNTAX      InetAddress (SIZE (0|4))
    MAX-ACCESS  accessible-for-notify
    STATUS      current
    DESCRIPTION
        "The value of vRtrTreeSidDBReplPlcyRootAddr indicates the root address
         of this tree-sid replication policy entry."
    DEFVAL      { '00000000'H }
    ::= { vRtrTreeSidDBReplPlcyEntry 1 }

vRtrTreeSidDBReplPlcyRtAddrType  OBJECT-TYPE
    SYNTAX      InetAddressType
    MAX-ACCESS  accessible-for-notify
    STATUS      current
    DESCRIPTION
        "The value of vRtrTreeSidDBReplPlcyRtAddrType indicates the type of
         address for the tree-sid database replication-segment entry
         represented by vRtrTreeSidDBReplPlcyRootAddr."
    DEFVAL      { ipv4 }
    ::= { vRtrTreeSidDBReplPlcyEntry 2 }

vRtrTreeSidDBReplPlcyTreeId      OBJECT-TYPE
    SYNTAX      Unsigned32
    MAX-ACCESS  accessible-for-notify
    STATUS      current
    DESCRIPTION
        "The value of vRtrTreeSidDBReplPlcyTreeId indicates a tunnel in the
         root, this also represent a spefic constraint. Also known as color
         and/or p2mp-id"
    DEFVAL      { 0 }
    ::= { vRtrTreeSidDBReplPlcyEntry 3 }

vRtrTreeSidDBReplPlcyNumHops     OBJECT-TYPE
    SYNTAX      Unsigned32
    MAX-ACCESS  read-only
    STATUS      current
    DESCRIPTION
        "The value of vRtrTreeSidDBReplPlcyNumHops indicate the total number of
         next hops present inside the tree-sid database replication segment
         instance."
    DEFVAL      { 0 }
    ::= { vRtrTreeSidDBReplPlcyEntry 4 }

vRtrTreeSidDBReplPlcyInstanceId  OBJECT-TYPE
    SYNTAX      Unsigned32
    MAX-ACCESS  accessible-for-notify
    STATUS      current
    DESCRIPTION
        "The value of the object vRtrTreeSidDBReplPlcyInstanceId indicates the
         instance identifier for the tree sid db replication policy table."
    DEFVAL      { 0 }
    ::= { vRtrTreeSidDBReplPlcyEntry 5 }

vRtrTreeSidDBReplPlcyOperStatus  OBJECT-TYPE
    SYNTAX      TmnxOperState
    MAX-ACCESS  read-only
    STATUS      current
    DESCRIPTION
        "The value of vRtrTreeSidDBReplPlcyOperStatus indicates the operational
         status for a given tree-sid db replication policy instance."
    DEFVAL      { outOfService }
    ::= { vRtrTreeSidDBReplPlcyEntry 6 }

vRtrTreeSidDBReplPlcyName        OBJECT-TYPE
    SYNTAX      TNamedItem
    MAX-ACCESS  read-only
    STATUS      current
    DESCRIPTION
        "The value of vRtrTreeSidDBReplPlcyName indicates the name of this
         tree-sid database replication policy entry."
    ::= { vRtrTreeSidDBReplPlcyEntry 7 }

vRtrTreeSidDBReplPlcyOrigin      OBJECT-TYPE
    SYNTAX      TmnxTreeSidOrigin
    MAX-ACCESS  accessible-for-notify
    STATUS      current
    DESCRIPTION
        "The value of vRtrTreeSidDBReplPlcyOrigin indicates the value of
         protocol-origin of a candidate path which is an 8-bit value which
         identifies the component or protocol that originates or signals the
         candidate path."
    ::= { vRtrTreeSidDBReplPlcyEntry 8 }

vRtrTreeSidDBReplPlcyTunnelIdx   OBJECT-TYPE
    SYNTAX      Unsigned32
    MAX-ACCESS  read-only
    STATUS      current
    DESCRIPTION
        "The value of vRtrTreeSidDBReplPlcyTunnelIdx indicates the tunnel index
         of the tree-sid database replication policy entry."
    ::= { vRtrTreeSidDBReplPlcyEntry 9 }

vRtrTreeSidDBReplPlcyDownReason  OBJECT-TYPE
    SYNTAX      INTEGER {
        none           (0),
        idx-alloc-fail (1),
        all-nh-down    (2),
        label-reg-fail (3),
        iom-pgrm-fail  (4),
        iom-ack-pend   (5)
    }
    MAX-ACCESS  read-only
    STATUS      current
    DESCRIPTION
        "The value of vRtrTreeSidDBReplPlcyDownReason indicates the reason due
         to which the tree-sid database replication-policy instance is
         operationally down."
    ::= { vRtrTreeSidDBReplPlcyEntry 10 }

vRtrTreeSidDBReplPlcyOperation   OBJECT-TYPE
    SYNTAX      INTEGER {
        none (0),
        push (1),
        pop  (2),
        swap (3)
    }
    MAX-ACCESS  read-only
    STATUS      current
    DESCRIPTION
        "The value of vRtrTreeSidDBReplPlcyOperation indicates the Label
         operation for the given tree-sid replication policy instance."
    DEFVAL      { none }
    ::= { vRtrTreeSidDBReplPlcyEntry 11 }

vRtrTreeSidDBRplPlcyIncomingSid  OBJECT-TYPE
    SYNTAX      Unsigned32
    MAX-ACCESS  read-only
    STATUS      current
    DESCRIPTION
        "The value of vRtrTreeSidDBRplPlcyIncomingSid indicates the incoming
         label for the transit and leaf routers, root is 0."
    DEFVAL      { 0 }
    ::= { vRtrTreeSidDBReplPlcyEntry 12 }

vRtrTreeSidDBReplPlcyLtn         OBJECT-TYPE
    SYNTAX      TruthValue
    MAX-ACCESS  read-only
    STATUS      current
    DESCRIPTION
        "The value of vRtrTreeSidDBReplPlcyLtn indicates whether this
         replication policy is rooted in this node(ingress LSP)."
    DEFVAL      { false }
    ::= { vRtrTreeSidDBReplPlcyEntry 13 }

vRtrTreeSidDBReplPlcyIsLocal     OBJECT-TYPE
    SYNTAX      TruthValue
    MAX-ACCESS  read-only
    STATUS      current
    DESCRIPTION
        "The value of vRtrTreeSidDBReplPlcyIsLocal indicates whether this
         replication policy has any MVPN leaf(egress LSP)."
    DEFVAL      { false }
    ::= { vRtrTreeSidDBReplPlcyEntry 14 }

vRtrTreeSidDBReplPlcyCCID        OBJECT-TYPE
    SYNTAX      Unsigned32
    MAX-ACCESS  read-only
    STATUS      current
    DESCRIPTION
        "The value of vRtrTreeSidDBReplPlcyCCID indicates the referenced
         CCI(central controler instruction) object ID in PCC."
    ::= { vRtrTreeSidDBReplPlcyEntry 15 }

vRtrTreeSidDBReplPlcyUpdateId    OBJECT-TYPE
    SYNTAX      Unsigned32
    MAX-ACCESS  read-only
    STATUS      current
    DESCRIPTION
        "The value of vRtrTreeSidDBReplPlcyUpdateId indicates the referenced
         update id among the list of CCID objects in PCC. "
    ::= { vRtrTreeSidDBReplPlcyEntry 16 }

vRtrTreeSidDBRPlcyNextHopTable   OBJECT-TYPE
    SYNTAX      SEQUENCE OF VRtrTreeSidDBRPlcyNextHopEntry
    MAX-ACCESS  not-accessible
    STATUS      current
    DESCRIPTION
        "The vRtrTreeSidDBRPlcyNextHopTable contains objects to configure next
         hop entries within a tree-sid database replication policy table entry."
    ::= { tmnxTreeSidObjs 19 }

vRtrTreeSidDBRPlcyNextHopEntry   OBJECT-TYPE
    SYNTAX      VRtrTreeSidDBRPlcyNextHopEntry
    MAX-ACCESS  not-accessible
    STATUS      current
    DESCRIPTION
        "The value of vRtrTreeSidDBRPlcyNextHopEntry indicates a unique path
         from root to a specific endpoint for the configuration information
         inside a vRtrTreeSidDBRPlcyNextHopTable."
    INDEX       {
        vRtrID,
        vRtrTreeSidDBReplPlcyRootAddr,
        vRtrTreeSidDBReplPlcyRtAddrType,
        vRtrTreeSidDBReplPlcyTreeId,
        vRtrTreeSidDBReplPlcyInstanceId,
        vRtrTreeSidDBReplPlcyOrigin,
        vRtrTreeSidDBReplPlcyNextHopId
    }
    ::= { vRtrTreeSidDBRPlcyNextHopTable 1 }

VRtrTreeSidDBRPlcyNextHopEntry   ::= SEQUENCE
{
    vRtrTreeSidDBReplPlcyNextHopId   Unsigned32,
    vRtrTreeSidDBReplPolNextHopAddr  InetAddress,
    vRtrTreeSidDBRPNextHopAddrType   InetAddressType,
    vRtrTreeSidDBRpNextHopOperState  TmnxOperState,
    vRtrTreeSidDBRpNHDownReason      INTEGER,
    vRtrTreeSidDBRPProtectNHAddr     InetAddress,
    vRtrTrSdDBRPProtectNHAddrType    InetAddressType,
    vRtrTrSdDBReplPlcyNextHopIfName  TNamedItemOrEmpty,
    vRtrTSDBRPNHProtectOperState     TmnxOperState,
    vRtrTSDBNHRpProtectOperDwnRsn    INTEGER,
    vRtrTSDBNHRpProtectNextHopId     Unsigned32,
    vRtrTSDBRpProtectNextHopIfName   TNamedItemOrEmpty
}

vRtrTreeSidDBReplPlcyNextHopId   OBJECT-TYPE
    SYNTAX      Unsigned32 (1..4096)
    MAX-ACCESS  not-accessible
    STATUS      current
    DESCRIPTION
        "The value of vRtrTreeSidDBReplPlcyNextHopId indicates the next-hop
         group index within a candidate path entry inside a tree-side
         replication policy instance."
    ::= { vRtrTreeSidDBRPlcyNextHopEntry 1 }

vRtrTreeSidDBReplPolNextHopAddr  OBJECT-TYPE
    SYNTAX      InetAddress (SIZE (0|4|16|20))
    MAX-ACCESS  read-only
    STATUS      current
    DESCRIPTION
        "The value of vRtrTreeSidDBReplPolNextHopAddr indicates the root
         address of this next-hop entry for a given candidate path entry inside
         a tree-sid replication policy instance."
    DEFVAL      { '00000000'H }
    ::= { vRtrTreeSidDBRPlcyNextHopEntry 2 }

vRtrTreeSidDBRPNextHopAddrType   OBJECT-TYPE
    SYNTAX      InetAddressType
    MAX-ACCESS  read-only
    STATUS      current
    DESCRIPTION
        "The value of vRtrTreeSidDBRPNextHopAddrType indicates the type of
         address for the root address of this next-hop entry for a given
         candidate path entry inside a tree-sid replication policy instance
         represented by vRtrTreeSidDBReplPolNextHopAddr."
    DEFVAL      { ipv4 }
    ::= { vRtrTreeSidDBRPlcyNextHopEntry 3 }

vRtrTreeSidDBRpNextHopOperState  OBJECT-TYPE
    SYNTAX      TmnxOperState
    MAX-ACCESS  read-only
    STATUS      current
    DESCRIPTION
        "The value of vRtrTreeSidDBRpNextHopOperState indicates the operational
         state of tree-sid database replication policy next-hop entry."
    ::= { vRtrTreeSidDBRPlcyNextHopEntry 4 }

vRtrTreeSidDBRpNHDownReason      OBJECT-TYPE
    SYNTAX      INTEGER {
        none                   (0),
        invalid-nhop           (1),
        rtr-if-not-found       (2),
        rtr-if-down            (3),
        rtr-if-v6-down         (4),
        rtm-unresolved         (5),
        if-not-unnum           (6),
        if-not-ipv6-link-local (7),
        bfd-down               (8),
        idx-alloc-fail         (9),
        invalid-label-stack    (10)
    }
    MAX-ACCESS  read-only
    STATUS      current
    DESCRIPTION
        "The value of vRtrTreeSidDBRpNHDownReason indicates the down reason
         state of tree-sid database replication policy next-hop entry."
    ::= { vRtrTreeSidDBRPlcyNextHopEntry 5 }

vRtrTreeSidDBRPProtectNHAddr     OBJECT-TYPE
    SYNTAX      InetAddress (SIZE (0|4|16|20))
    MAX-ACCESS  read-only
    STATUS      current
    DESCRIPTION
        "The value of vRtrTreeSidDBRPProtectNHAddr indicates the next hop
         address of this protect next-hop entry for a given candidate path
         entry inside a tree-sid db replication policy instance."
    DEFVAL      { '00000000'H }
    ::= { vRtrTreeSidDBRPlcyNextHopEntry 6 }

vRtrTrSdDBRPProtectNHAddrType    OBJECT-TYPE
    SYNTAX      InetAddressType
    MAX-ACCESS  read-only
    STATUS      current
    DESCRIPTION
        "The value of vRtrTrSdDBRPProtectNHAddrType indicates the type of
         address for the protect next-hop address for a given candidate path
         entry inside a tree-sid db replication policy instance represented by
         vRtrTrSdDBRPProtectNHAddrType."
    DEFVAL      { ipv4 }
    ::= { vRtrTreeSidDBRPlcyNextHopEntry 7 }

vRtrTrSdDBReplPlcyNextHopIfName  OBJECT-TYPE
    SYNTAX      TNamedItemOrEmpty
    MAX-ACCESS  read-only
    STATUS      current
    DESCRIPTION
        "The value of vRtrTrSdDBReplPlcyNextHopIfName indicates the name of
         next hop out going interface for a given next-hop candidate path entry
         inside a tree-sid db replication policy instance."
    DEFVAL      { "" }
    ::= { vRtrTreeSidDBRPlcyNextHopEntry 8 }

vRtrTSDBRPNHProtectOperState     OBJECT-TYPE
    SYNTAX      TmnxOperState
    MAX-ACCESS  read-only
    STATUS      current
    DESCRIPTION
        "The value of vRtrTSDBRPNHProtectOperState indicates the operational
         state of tree-sid replication policy next-hop entry."
    ::= { vRtrTreeSidDBRPlcyNextHopEntry 9 }

vRtrTSDBNHRpProtectOperDwnRsn    OBJECT-TYPE
    SYNTAX      INTEGER {
        none                   (0),
        invalid-nhop           (1),
        rtr-if-not-found       (2),
        rtr-if-down            (3),
        rtr-if-v6-down         (4),
        rtm-unresolved         (5),
        if-not-unnum           (6),
        if-not-ipv6-link-local (7),
        bfd-down               (8),
        idx-alloc-fail         (9),
        invalid-label-stack    (10)
    }
    MAX-ACCESS  read-only
    STATUS      current
    DESCRIPTION
        "The value of vRtrTSDBNHRpProtectOperDwnRsn indicates the protect
         operational down reason state of tree-sid database replication policy
         next-hop entry."
    ::= { vRtrTreeSidDBRPlcyNextHopEntry 10 }

vRtrTSDBNHRpProtectNextHopId     OBJECT-TYPE
    SYNTAX      Unsigned32 (0 | 1..4096)
    MAX-ACCESS  read-only
    STATUS      current
    DESCRIPTION
        "The value of vRtrTSDBNHRpProtectNextHopId indicates the protect
         next-hop group index within a candidate path entry inside a tree-sid
         db replication policy instance."
    DEFVAL      { 0 }
    ::= { vRtrTreeSidDBRPlcyNextHopEntry 11 }

vRtrTSDBRpProtectNextHopIfName   OBJECT-TYPE
    SYNTAX      TNamedItemOrEmpty
    MAX-ACCESS  read-only
    STATUS      current
    DESCRIPTION
        "The value of vRtrTSDBRpProtectNextHopIfName indicates the name of next
         hop out going interface for a given protect next-hop candidate path
         entry inside a tree-sid db replication policy instance."
    DEFVAL      { "" }
    ::= { vRtrTreeSidDBRPlcyNextHopEntry 12 }

vRtrTrSdDBRpNHOutGngReplSdTable  OBJECT-TYPE
    SYNTAX      SEQUENCE OF VRtrTrSdDBRpNHOutGngReplSdEntry
    MAX-ACCESS  not-accessible
    STATUS      current
    DESCRIPTION
        "The vRtrTrSdDBRpNHOutGngReplSdTable represents the database objects to
         display the labels of next-hop entries for a given candidate path
         entry within a database replication policy table instance."
    ::= { tmnxTreeSidObjs 20 }

vRtrTrSdDBRpNHOutGngReplSdEntry  OBJECT-TYPE
    SYNTAX      VRtrTrSdDBRpNHOutGngReplSdEntry
    MAX-ACCESS  not-accessible
    STATUS      current
    DESCRIPTION
        "The vRtrTrSdDBRpNHOutGngReplSdEntry represents the replication label
         for this db nexthop instance."
    INDEX       {
        vRtrID,
        vRtrTreeSidDBReplPlcyRootAddr,
        vRtrTreeSidDBReplPlcyRtAddrType,
        vRtrTreeSidDBReplPlcyTreeId,
        vRtrTreeSidDBReplPlcyInstanceId,
        vRtrTreeSidDBReplPlcyOrigin,
        vRtrTreeSidDBReplPlcyNextHopId,
        vRtrTreeSidDBRplPlcyNHReplSid
    }
    ::= { vRtrTrSdDBRpNHOutGngReplSdTable 1 }

VRtrTrSdDBRpNHOutGngReplSdEntry  ::= SEQUENCE
{
    vRtrTreeSidDBRplPlcyNHReplSid    Unsigned32,
    vRtrTrSdDBRpNHOutGngReplSdLabel  Unsigned32
}

vRtrTreeSidDBRplPlcyNHReplSid    OBJECT-TYPE
    SYNTAX      Unsigned32 (0..9)
    MAX-ACCESS  not-accessible
    STATUS      current
    DESCRIPTION
        "The value of vRtrTreeSidDBRplPlcyNHReplSid represents the Index for
         push-label."
    ::= { vRtrTrSdDBRpNHOutGngReplSdEntry 1 }

vRtrTrSdDBRpNHOutGngReplSdLabel  OBJECT-TYPE
    SYNTAX      Unsigned32
    MAX-ACCESS  read-only
    STATUS      current
    DESCRIPTION
        "The value of vRtrTrSdDBRpNHOutGngReplSdLabel represents the value for
         push-label."
    DEFVAL      { 0 }
    ::= { vRtrTrSdDBRpNHOutGngReplSdEntry 2 }

vRtrTSDBRpNHOGProtectRplSdTable  OBJECT-TYPE
    SYNTAX      SEQUENCE OF VRtrTSDBRpNHOGProtectRplSdEntry
    MAX-ACCESS  not-accessible
    STATUS      current
    DESCRIPTION
        "The vRtrTSDBRpNHOGProtectRplSdTable represents the database objects to
         display the labels of next-hop entries for a given candidate path
         entry within a database replication policy table instance."
    ::= { tmnxTreeSidObjs 21 }

vRtrTSDBRpNHOGProtectRplSdEntry  OBJECT-TYPE
    SYNTAX      VRtrTSDBRpNHOGProtectRplSdEntry
    MAX-ACCESS  not-accessible
    STATUS      current
    DESCRIPTION
        "The vRtrTSDBRpNHOGProtectRplSdEntry represents the protecting
         replication label for this db nexthop instance."
    INDEX       {
        vRtrID,
        vRtrTreeSidDBReplPlcyRootAddr,
        vRtrTreeSidDBReplPlcyRtAddrType,
        vRtrTreeSidDBReplPlcyTreeId,
        vRtrTreeSidDBReplPlcyInstanceId,
        vRtrTreeSidDBReplPlcyOrigin,
        vRtrTreeSidDBReplPlcyNextHopId,
        vRtrTreeSidDBRPNHProtectReplSid
    }
    ::= { vRtrTSDBRpNHOGProtectRplSdTable 1 }

VRtrTSDBRpNHOGProtectRplSdEntry  ::= SEQUENCE
{
    vRtrTreeSidDBRPNHProtectReplSid  Unsigned32,
    vRtrTSDBRpNHOGProtectRplSdLabel  Unsigned32
}

vRtrTreeSidDBRPNHProtectReplSid  OBJECT-TYPE
    SYNTAX      Unsigned32 (0..9)
    MAX-ACCESS  not-accessible
    STATUS      current
    DESCRIPTION
        "The value of vRtrTreeSidDBRPNHProtectReplSid represents the Index for
         push-label."
    ::= { vRtrTSDBRpNHOGProtectRplSdEntry 1 }

vRtrTSDBRpNHOGProtectRplSdLabel  OBJECT-TYPE
    SYNTAX      Unsigned32
    MAX-ACCESS  read-only
    STATUS      current
    DESCRIPTION
        "The value of vRtrTSDBRpNHOGProtectRplSdLabel represents the value for
         push-label."
    DEFVAL      { 0 }
    ::= { vRtrTSDBRpNHOGProtectRplSdEntry 2 }

vRtrTreeSidTunnelTable           OBJECT-TYPE
    SYNTAX      SEQUENCE OF VRtrTreeSidTunnelEntry
    MAX-ACCESS  not-accessible
    STATUS      current
    DESCRIPTION
        "The vRtrTreeSidTunnelTable represents the table to display the tunnel
         table entries."
    ::= { tmnxTreeSidObjs 22 }

vRtrTreeSidTunnelEntry           OBJECT-TYPE
    SYNTAX      VRtrTreeSidTunnelEntry
    MAX-ACCESS  not-accessible
    STATUS      current
    DESCRIPTION
        "The vRtrTreeSidTunnelEntry represents the tunnel entry within a
         p2mp-sr-tree tunnel table."
    INDEX       {
        vRtrID,
        vRtrIfIndex
    }
    ::= { vRtrTreeSidTunnelTable 1 }

VRtrTreeSidTunnelEntry           ::= SEQUENCE
{
    vRtrTreeSidTunnelRootAddress     InetAddress,
    vRtrTreeSidTunnelRootAddrType    InetAddressType,
    vRtrTreeSidTunnelTreeId          Unsigned32,
    vRtrTreeSidTunnelType            INTEGER,
    vRtrTreeSidTunnelNumLeaves       Unsigned32,
    vRtrTreeSidTunnelOperState       TmnxOperState,
    vRtrTreeSidTunnelVRtrId          Unsigned32
}

vRtrTreeSidTunnelRootAddress     OBJECT-TYPE
    SYNTAX      InetAddress (SIZE (0|4))
    MAX-ACCESS  read-only
    STATUS      current
    DESCRIPTION
        "The value of vRtrTreeSidTunnelRootAddress indicates the root address
         of this tree-sid tunnel table entry."
    DEFVAL      { '00000000'H }
    ::= { vRtrTreeSidTunnelEntry 1 }

vRtrTreeSidTunnelRootAddrType    OBJECT-TYPE
    SYNTAX      InetAddressType
    MAX-ACCESS  read-only
    STATUS      current
    DESCRIPTION
        "The value of vRtrTreeSidTunnelRootAddrType indicates the type of
         address for the tree-sid database replication-segment entry
         represented by vRtrTreeSidTunnelRootAddress."
    DEFVAL      { ipv4 }
    ::= { vRtrTreeSidTunnelEntry 2 }

vRtrTreeSidTunnelTreeId          OBJECT-TYPE
    SYNTAX      Unsigned32
    MAX-ACCESS  read-only
    STATUS      current
    DESCRIPTION
        "The value of vRtrTreeSidTunnelTreeId indicates a tunnel in the root,
         this also represent a spefic constraint. Also known as color and/or
         p2mp-id"
    DEFVAL      { 0 }
    ::= { vRtrTreeSidTunnelEntry 3 }

vRtrTreeSidTunnelType            OBJECT-TYPE
    SYNTAX      INTEGER {
        tx (0),
        rx (1)
    }
    MAX-ACCESS  read-only
    STATUS      current
    DESCRIPTION
        "The value of vRtrTreeSidTunnelType indicates the type of the tunnel."
    ::= { vRtrTreeSidTunnelEntry 4 }

vRtrTreeSidTunnelNumLeaves       OBJECT-TYPE
    SYNTAX      Unsigned32
    MAX-ACCESS  read-only
    STATUS      current
    DESCRIPTION
        "The value of vRtrTreeSidTunnelNumLeaves indicate the number of leaves
         represnted by this tree sid tunnel entry."
    ::= { vRtrTreeSidTunnelEntry 5 }

vRtrTreeSidTunnelOperState       OBJECT-TYPE
    SYNTAX      TmnxOperState
    MAX-ACCESS  read-only
    STATUS      current
    DESCRIPTION
        "The value of vRtrTreeSidTunnelOperState indicates the desired
         operational state of tree-sid tunnel table entry."
    ::= { vRtrTreeSidTunnelEntry 6 }

vRtrTreeSidTunnelVRtrId          OBJECT-TYPE
    SYNTAX      Unsigned32
    MAX-ACCESS  read-only
    STATUS      current
    DESCRIPTION
        "The value of vRtrTreeSidTunnelVRtrId indicates the vrf index for the
         mvpn instance for this particular tunnel entry."
    ::= { vRtrTreeSidTunnelEntry 7 }

vRtrTreeSidTxTunnelLeafTable     OBJECT-TYPE
    SYNTAX      SEQUENCE OF VRtrTreeSidTxTunnelLeafEntry
    MAX-ACCESS  not-accessible
    STATUS      current
    DESCRIPTION
        "The vRtrTreeSidTxTunnelLeafTable represents the table to display
         tunnel tx leaf table entries."
    ::= { tmnxTreeSidObjs 23 }

vRtrTreeSidTxTunnelLeafEntry     OBJECT-TYPE
    SYNTAX      VRtrTreeSidTxTunnelLeafEntry
    MAX-ACCESS  not-accessible
    STATUS      current
    DESCRIPTION
        "The vRtrTreeSidTxTunnelLeafEntry represents the tunnel tx leaf entry
         within a p2mp-sr-tree tx tunnel leaf table."
    INDEX       {
        vRtrID,
        vRtrIfIndex,
        vRtrTreeSidTxTunnelLeafAddrType,
        vRtrTreeSidTxTunnelLeafAddress
    }
    ::= { vRtrTreeSidTxTunnelLeafTable 1 }

VRtrTreeSidTxTunnelLeafEntry     ::= SEQUENCE
{
    vRtrTreeSidTxTunnelLeafAddrType  InetAddressType,
    vRtrTreeSidTxTunnelLeafAddress   InetAddress,
    vRtrTreeSidTxTunnelRootAddrType  InetAddressType,
    vRtrTreeSidTxTunnelRootAddress   InetAddress,
    vRtrTreeSidTxTunnelTreeId        Unsigned32,
    vRtrTreeSidTxTunnelOperState     TmnxOperState,
    vRtrTreeSidTxTunnelVRtrId        Unsigned32
}

vRtrTreeSidTxTunnelLeafAddrType  OBJECT-TYPE
    SYNTAX      InetAddressType
    MAX-ACCESS  not-accessible
    STATUS      current
    DESCRIPTION
        "The value of vRtrTreeSidTxTunnelLeafAddrType indicates the type of
         address for the tree-sid tx tunnel leaf table entry."
    DEFVAL      { ipv4 }
    ::= { vRtrTreeSidTxTunnelLeafEntry 1 }

vRtrTreeSidTxTunnelLeafAddress   OBJECT-TYPE
    SYNTAX      InetAddress (SIZE (0|4))
    MAX-ACCESS  not-accessible
    STATUS      current
    DESCRIPTION
        "The value of vRtrTreeSidTxTunnelLeafAddress indicates the address of
         this tree-sid tx tunnel leaf table entry."
    DEFVAL      { '00000000'H }
    ::= { vRtrTreeSidTxTunnelLeafEntry 2 }

vRtrTreeSidTxTunnelRootAddrType  OBJECT-TYPE
    SYNTAX      InetAddressType
    MAX-ACCESS  read-only
    STATUS      current
    DESCRIPTION
        "The value of vRtrTreeSidTxTunnelRootAddrType indicates the type of
         address for the tree-sid tx tunnel leaf table entry."
    DEFVAL      { ipv4 }
    ::= { vRtrTreeSidTxTunnelLeafEntry 3 }

vRtrTreeSidTxTunnelRootAddress   OBJECT-TYPE
    SYNTAX      InetAddress (SIZE (0|4))
    MAX-ACCESS  read-only
    STATUS      current
    DESCRIPTION
        "The value of vRtrTreeSidTxTunnelRootAddress indicates the address of
         this tree-sid tx tunnel leaf table entry."
    DEFVAL      { '00000000'H }
    ::= { vRtrTreeSidTxTunnelLeafEntry 4 }

vRtrTreeSidTxTunnelTreeId        OBJECT-TYPE
    SYNTAX      Unsigned32
    MAX-ACCESS  read-only
    STATUS      current
    DESCRIPTION
        "The value of vRtrTreeSidTxTunnelTreeId indicates a tunnel in the root,
         this also represent a spefic constraint. Also known as color and/or
         p2mp-id"
    DEFVAL      { 0 }
    ::= { vRtrTreeSidTxTunnelLeafEntry 5 }

vRtrTreeSidTxTunnelOperState     OBJECT-TYPE
    SYNTAX      TmnxOperState
    MAX-ACCESS  read-only
    STATUS      current
    DESCRIPTION
        "The value of vRtrTreeSidTxTunnelOperState indicates the desired
         operational state of tree-sid tunnel table entry."
    ::= { vRtrTreeSidTxTunnelLeafEntry 6 }

vRtrTreeSidTxTunnelVRtrId        OBJECT-TYPE
    SYNTAX      Unsigned32
    MAX-ACCESS  read-only
    STATUS      current
    DESCRIPTION
        "The value of vRtrTreeSidTxTunnelVRtrId indicates the vrf index for the
         mvpn instance for this particular Tx tunnel."
    ::= { vRtrTreeSidTxTunnelLeafEntry 7 }

vRtrTreeSidNotificationObjs      OBJECT IDENTIFIER ::= { tmnxTreeSidObjs 24 }

vRtrTreeSidDBPlcyOldCdtPathName  OBJECT-TYPE
    SYNTAX      TNamedItem
    MAX-ACCESS  accessible-for-notify
    STATUS      current
    DESCRIPTION
        "The value of vRtrTreeSidDBPlcyOldCdtPathName indicates the configured
         tree-sid database old candidate-path value."
    ::= { vRtrTreeSidNotificationObjs 1 }

vRtrTreeSidDBPlcyCPOldActiveInst OBJECT-TYPE
    SYNTAX      Unsigned32
    MAX-ACCESS  accessible-for-notify
    STATUS      current
    DESCRIPTION
        "The value of vRtrTreeSidDBPlcyCPOldActiveInst indicates the configured
         tree-sid database old active candidate path instance value."
    DEFVAL      { 0 }
    ::= { vRtrTreeSidNotificationObjs 2 }

vRtrTreeSidResourceType          OBJECT-TYPE
    SYNTAX      INTEGER {
        nhlfe (1),
        ltn   (2),
        mcast (3)
    }
    MAX-ACCESS  accessible-for-notify
    STATUS      current
    DESCRIPTION
        "CPM or data path resource used by Tree-SID."
    ::= { vRtrTreeSidNotificationObjs 3 }

vRtrTreeSidConformance           OBJECT IDENTIFIER ::= { tmnxSRConfs 126 }

vRtrTreeSidCompliances           OBJECT IDENTIFIER ::= { vRtrTreeSidConformance 1 }

vRtrTreeSidComplianceV19v0       MODULE-COMPLIANCE
    STATUS      current
    DESCRIPTION
        "The compliance statement for management of Tree Sid features on Nokia
         SROS series systems release 19.0."
    MODULE
        MANDATORY-GROUPS {
            vRtrTreeSidConfigGroup,
            vRtrTreeSidProtectNextHopGroup
        }
    ::= { vRtrTreeSidCompliances 1 }

vRtrTreeSidComplianceV20v0       MODULE-COMPLIANCE
    STATUS      current
    DESCRIPTION
        "The compliance statement for management of Tree Sid features on Nokia
         SROS series systems release 20.0."
    MODULE
        MANDATORY-GROUPS {
            vRtrTreeSidConfigV20v0Group,
            vRtrTreeSidDatabaseV20v0Group,
            tmnxTSNotificationV20v0Group
        }
    ::= { vRtrTreeSidCompliances 2 }

vRtrTreeSidGroups                OBJECT IDENTIFIER ::= { vRtrTreeSidConformance 2 }

vRtrTreeSidV19v0Groups           OBJECT IDENTIFIER ::= { vRtrTreeSidGroups 1 }

vRtrTreeSidConfigGroup           OBJECT-GROUP
    OBJECTS     {
        vRtrTreeSidPlcyTableLastChanged,
        vRtrTreeSidReplPlcyTableLstChgd,
        vRtrTreeSdPlcyLfAddrTblLastChgd,
        vRtrTreeSidReplPlcyTableLstChgd,
        vRtrTrSdRpNHOGRplSdTblLstChgd,
        vRtrTrSdRplPlcyCdtPthTblLstChgd,
        vRtrTreeSidGenAdminState,
        vRtrTreeSidGenRsvdLblBlockName,
        vRtrTreeSidGenRowStatus,
        vRtrTreeSidGenLastChanged,
        vRtrTreeSidPolicyRowStatus,
        vRtrTreeSidPolicyRootAddr,
        vRtrTreeSidPolicyRootAddrType,
        vRtrTreeSidPolicyTreeId,
        vRtrTreeSidPolicyAdminState,
        vRtrTreeSidPolicyOperStatus,
        vRtrTreeSidPolicyLastChanged,
        vRtrTreeSidPolicyRtrId,
        vRtrTreeSidPolicyActCdtPathName,
        vRtrTreeSidPolCdtPathRowStatus,
        vRtrTreeSidPolCdtPathAdminState,
        vRtrTreeSidPolCdtPathOperState,
        vRtrTreeSidPolCdtPathOrigin,
        vRtrTreeSidPlcyCPOriginatorAsn,
        vRtrTrSidPlcyCPOrigNodeAddrType,
        vRtrTrSidPlcyCPOrigNodeAddr,
        vRtrTreeSidPlcyCPDescriminator,
        vRtrTreeSidPlcyCdtPthPlspId,
        vRtrTreeSidPlcyCdtPthPreference,
        vRtrTreeSidPolCdtPathLastChanged,
        vRtrTreeSidPolCdtPathActiveInst,
        vRtrTreeSidReplPlcyRowStatus,
        vRtrTreeSidReplPlcyRootAddr,
        vRtrTreeSidReplPlcyRootAddrType,
        vRtrTreeSidReplPlcyTreeId,
        vRtrTreeSidReplPlcyAdminState,
        vRtrTreeSidReplPlcyOperStatus,
        vRtrTreeSidReplPlcyIncomingSid,
        vRtrTreeSidReplPlcyOperation,
        vRtrTreeSidReplPlcyInstanceId,
        vRtrTreeSdReplPlcyLastChanged,
        vRtrTreeSidReplPlcyOrigin,
        vRtrTreeSidRplPolNHRowStatus,
        vRtrTreeSidReplPolNextHopAddr,
        vRtrTreeSidRplPlNextHopAddrType,
        vRtrTreeSidReplPolNextHopIfName,
        vRtrTreeSidRpNextHopProtectId,
        vRtrTreeSidRpNextHopWeight,
        vRtrTreeSidRpNextHopLastChanged,
        vRtrTreeSidRpNextHopAdminState,
        vRtrTreeSidRpNextHopOperState,
        vRtrTrSdRpNHOutGngReplSdLabel,
        vRtrTrSdRpNHOGRplSdLstChanged,
        vRtrTreeSidInstance,
        vRtrTreeSidInstLastChanged,
        vRtrTreeSidNumP2mpStaticPolicies,
        vRtrTreeSidNumP2mpPcePolicies,
        vRtrTreeSidNumP2mpSrPolicies,
        vRtrTreeSidP2mpCdtPathStatic,
        vRtrTreeSidP2mpCdtPathPce,
        vRtrTreeSidP2mpCdtPathSrPolicy,
        vRtrTreeSidReplSegStatic,
        vRtrTreeSidReplSegPce,
        vRtrTreeSidReplSegSrPolicy,
        vRtrTreeSidNHStatic,
        vRtrTreeSidNHPce,
        vRtrTreeSidNHSrPolicy,
        vRtrTreeSidNumPush,
        vRtrTreeSidNumSwap,
        vRtrTreeSidNumPop,
        vRtrTreeSidTnlsAlloc,
        vRtrTreeSidNHIfInSvc,
        vRtrTreeSidNHIfOutSvc,
        vRtrTreeSidNHIfUnsup,
        vRtrTreeSidNHIfMismatch,
        vRtrTreeSidNHIfNoBfd,
        vRtrTreeSidDPBackPressureActive,
        vRtrTreeSidDPBackPressureCount,
        vRtrTreeSidErrorUnknOrigOwner,
        vRtrTreeSidErrorDupTreeIds,
        vRtrTreeSidErrorProgFailNHIdx,
        vRtrTreeSidErrorProgFailLabels,
        vRtrTreeSidErrorProgFailTunnels,
        vRtrTreeSidErrorProgFailProtGrp,
        vRtrTreeSidLabelInUse,
        vRtrTreeSidLabelOwner,
        vRtrTreeSidLabelSummaryStart,
        vRtrTreeSidLabelSummaryEnd,
        vRtrTreeSidLabelSummaryInUse
    }
    STATUS      current
    DESCRIPTION
        "The group of objects supporting tree-sid configuration on Nokia SROS
         series systems release 19.0."
    ::= { vRtrTreeSidV19v0Groups 1 }

vRtrTreeSidProtectNextHopGroup   OBJECT-GROUP
    OBJECTS     {
        vRtrTreeSidRpNextHopProtectId
    }
    STATUS      current
    DESCRIPTION
        "The group of objects supporting tree-sid configuration to be disabled
         on Nokia SROS systems release 20.2."
    ::= { vRtrTreeSidV19v0Groups 2 }

vRtrTreeSidConfigV20v0Group      OBJECT-GROUP
    OBJECTS     {
        vRtrTreeSidGenBfdEnabled
    }
    STATUS      current
    DESCRIPTION
        "The group of objects supporting tree-sid configuration on Nokia SROS
         series systems release 20.0."
    ::= { vRtrTreeSidGroups 2 }

vRtrTreeSidDatabaseV20v0Group    OBJECT-GROUP
    OBJECTS     {
        vRtrTrSdDBP2mpPlcyActCdtPthName,
        vRtrTreeSidDBP2mpPlcyNumPaths,
        vRtrTreeSidDBP2mpPlcyOperState,
        vRtrTreeSidDBP2mpPlcyTunnelIdx,
        vRtrTreeSidDBPolicyName,
        vRtrTreeSidDBPlcyCdtPathName,
        vRtrTreeSidDBPlcyCPOperState,
        vRtrTreeSidDBPlcyCPLastChgd,
        vRtrTreeSidDBPlcyCdtPthPlspId,
        vRtrTreeSidDBPlcyCPActiveInst,
        vRtrTreeSidDBPlcyCPSByInst,
        vRtrTreeSidDBReplPlcyNumHops,
        vRtrTreeSidDBReplPlcyOperStatus,
        vRtrTreeSidDBReplPlcyName,
        vRtrTreeSidDBReplPlcyTunnelIdx,
        vRtrTreeSidDBReplPlcyDownReason,
        vRtrTreeSidDBReplPlcyOperation,
        vRtrTreeSidDBRplPlcyIncomingSid,
        vRtrTreeSidDBReplPlcyLtn,
        vRtrTreeSidDBReplPlcyIsLocal,
        vRtrTreeSidDBReplPlcyCCID,
        vRtrTreeSidDBReplPlcyUpdateId,
        vRtrTreeSidDBReplPolNextHopAddr,
        vRtrTreeSidDBRPNextHopAddrType,
        vRtrTrSdDBReplPlcyNextHopIfName,
        vRtrTreeSidDBRpNextHopOperState,
        vRtrTreeSidDBRpNHDownReason,
        vRtrTreeSidDBRPProtectNHAddr,
        vRtrTrSdDBRPProtectNHAddrType,
        vRtrTSDBRPNHProtectOperState,
        vRtrTSDBNHRpProtectOperDwnRsn,
        vRtrTSDBNHRpProtectNextHopId,
        vRtrTSDBRpProtectNextHopIfName,
        vRtrTrSdDBRpNHOutGngReplSdLabel,
        vRtrTSDBRpNHOGProtectRplSdLabel,
        vRtrTrSdReplPlcyRootAddrValid,
        vRtrTreeSidDBPlcyCPPreference,
        vRtrTreeSidTunnelRootAddress,
        vRtrTreeSidTunnelRootAddrType,
        vRtrTreeSidTunnelTreeId,
        vRtrTreeSidTunnelType,
        vRtrTreeSidTunnelNumLeaves,
        vRtrTreeSidTunnelOperState,
        vRtrTreeSidTunnelVRtrId,
        vRtrTreeSidTxTunnelTreeId,
        vRtrTreeSidTxTunnelOperState,
        vRtrTreeSidTxTunnelVRtrId,
        vRtrTreeSidTxTunnelRootAddrType,
        vRtrTreeSidTxTunnelRootAddress
    }
    STATUS      current
    DESCRIPTION
        "The group of objects supporting tree-sid database on Nokia SROS series
         systems release 20.0."
    ::= { vRtrTreeSidGroups 3 }

vRtrTreeSidNotifyObjsGroup       OBJECT-GROUP
    OBJECTS     {
        vRtrTreeSidDBPlcyOldCdtPathName,
        vRtrTreeSidDBPlcyCPOldActiveInst,
        vRtrTreeSidDBReplPlcyRootAddr,
        vRtrTreeSidDBReplPlcyRtAddrType,
        vRtrTreeSidDBReplPlcyTreeId,
        vRtrTreeSidDBReplPlcyInstanceId,
        vRtrTreeSidDBReplPlcyOrigin,
        vRtrTreeSidResourceType
    }
    STATUS      current
    DESCRIPTION
        "The group of objects supporting tree-sid notifications on Nokia SROS
         series systems."
    ::= { vRtrTreeSidGroups 4 }

tmnxTSNotificationV20v0Group     NOTIFICATION-GROUP
    NOTIFICATIONS {
        vRtrTreeSidCdtPathChanged,
        vRtrTreeSidCdtPathActInsChanged,
        vRtrTreeSidInSidRegFailure,
        vRtrTreeSidTreeIdAllocFailure,
        vRtrTreeSidRepSegResExhaustion,
        vRtrTreeSidRepSegResExhstCleared,
        vRtrTreeSidLabelRangeExhaustion,
        vRtrTreeSidLblRangeExhstCleared
    }
    STATUS      current
    DESCRIPTION
        "The group of notifications supporting TREE-SID protocol on Nokia SROS
         series systems."
    ::= { vRtrTreeSidGroups 5 }

vRtrTreeSidNotifyPrefix          OBJECT IDENTIFIER ::= { tmnxSRNotifyPrefix 126 }

vRtrTreeSidNotifications         OBJECT IDENTIFIER ::= { vRtrTreeSidNotifyPrefix 0 }

vRtrTreeSidCdtPathChanged        NOTIFICATION-TYPE
    OBJECTS     {
        vRtrTreeSidDBPlcyCdtPathName,
        vRtrTreeSidDBPlcyOldCdtPathName
    }
    STATUS      current
    DESCRIPTION
        "[CAUSE] Generated when the in-use candidate-path changes from
         vRtrTreeSidDBPlcyOldCdtPathName to vRtrTreeSidDBPlcyCdtPathName.

         [EFFECT] Switching to the new candidate-path was successful.

         [RECOVERY] None Required."
    ::= { vRtrTreeSidNotifications 1 }

vRtrTreeSidCdtPathActInsChanged  NOTIFICATION-TYPE
    OBJECTS     {
        vRtrTreeSidDBPlcyCdtPathName,
        vRtrTreeSidDBPlcyCPActiveInst,
        vRtrTreeSidDBPlcyCPOldActiveInst
    }
    STATUS      current
    DESCRIPTION
        "[CAUSE] Generated when the active instance for a candidate-path
         changes from vRtrTreeSidDBPlcyCPOldActiveInst to
         vRtrTreeSidDBPlcyCPActiveInst.

         [EFFECT] Switching to the new active-instance for the candidate-path
         was successful.

         [RECOVERY] None required."
    ::= { vRtrTreeSidNotifications 2 }

vRtrTreeSidInSidRegFailure       NOTIFICATION-TYPE
    OBJECTS     {
        vRtrTreeSidDBRplPlcyIncomingSid
    }
    STATUS      current
    DESCRIPTION
        "[CAUSE] Reports a failure while programming an incoming-sid specified
         by vRtrTreeSidDBRplPlcyIncomingSid.

         [EFFECT] Programming of the replication-segment failed.

         [RECOVERY] Configuration change, using a different incoming-sid."
    ::= { vRtrTreeSidNotifications 3 }

vRtrTreeSidTreeIdAllocFailure    NOTIFICATION-TYPE
    OBJECTS     {
        vRtrID
    }
    STATUS      current
    DESCRIPTION
        "[CAUSE] Generated when tree-id resource cannot be allocated.

         [EFFECT] System may not accept new replication-segment configuration

         [RECOVERY] Configuration change may be required. May also be cleared
         while retrying for the resource."
    ::= { vRtrTreeSidNotifications 4 }

vRtrTreeSidRepSegResExhaustion   NOTIFICATION-TYPE
    OBJECTS     {
        vRtrID,
        vRtrTreeSidDBReplPlcyRootAddr,
        vRtrTreeSidDBReplPlcyRtAddrType,
        vRtrTreeSidDBReplPlcyTreeId,
        vRtrTreeSidDBReplPlcyInstanceId,
        vRtrTreeSidDBReplPlcyOrigin,
        vRtrTreeSidResourceType
    }
    STATUS      current
    DESCRIPTION
        "[CAUSE] Generated when a CPM or data path resource specified by
         vRtrTreeSidResourceType cannot be allocated for the
         replication-segment.

         [EFFECT] The replication segment will be operationally down.

         [RECOVERY] Configuration change may be required. May be cleared while
         retrying for the exhausted resource."
    ::= { vRtrTreeSidNotifications 5 }

vRtrTreeSidRepSegResExhstCleared NOTIFICATION-TYPE
    OBJECTS     {
        vRtrID,
        vRtrTreeSidDBReplPlcyRootAddr,
        vRtrTreeSidDBReplPlcyRtAddrType,
        vRtrTreeSidDBReplPlcyTreeId,
        vRtrTreeSidDBReplPlcyInstanceId,
        vRtrTreeSidDBReplPlcyOrigin,
        vRtrTreeSidResourceType
    }
    STATUS      current
    DESCRIPTION
        "[CAUSE] Generated when an earlier resource exhaustion condition raised
         by vRtrTreeSidRepSegResExhaustion is cleared.

         [EFFECT] CPM or data path resource specified by
         vRtrTreeSidResourceType can be allocated now for the
         replication-segment.

         [RECOVERY] None required."
    ::= { vRtrTreeSidNotifications 6 }

vRtrTreeSidLabelRangeExhaustion  NOTIFICATION-TYPE
    OBJECTS     {
        vRtrID
    }
    STATUS      current
    DESCRIPTION
        "[CAUSE] Generated when the reserved-label range for p2mp-sr-tree is
         exhausted.

         [EFFECT] System may not accept new replication-segment configuration
         with pop and swap operation.

         [RECOVERY] Configuration change may be required."
    ::= { vRtrTreeSidNotifications 7 }

vRtrTreeSidLblRangeExhstCleared  NOTIFICATION-TYPE
    OBJECTS     {
        vRtrID
    }
    STATUS      current
    DESCRIPTION
        "[CAUSE] Generated when an earlier label range exhaustion condition
         raised by vRtrTreeSidLabelRangeExhaustion is cleared.

         [EFFECT] System can accept new replication-segment configuration with
         pop and swap operation.

         [RECOVERY] None required."
    ::= { vRtrTreeSidNotifications 8 }

END

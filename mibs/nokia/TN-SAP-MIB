TN-SAP-MIB DEFINITIONS ::= BEGIN

-- (c) Copyright 2021 Nokia Networks.  All rights reserved.
-- This software is the confidential and proprietary property of
-- Nokia and may only be used in accordance with the terms of the
-- license agreement provided with this software.

IMPORTS
    MODULE-IDENTITY, OBJECT-TYPE,
    NOTIFICATION-TYPE, Gauge32,
    Integer32, Unsigned32, IpAddress,
    Counter64, Counter32                        FROM SNMPv2-SMI

--  MODULE-COMPLIANCE, OBJECT-GROUP,
--  NOTIFICATION-GROUP                          FROM SNMPv2-CONF

    DisplayString,
    RowStatus, MacAddress, TimeStamp,
    TruthValue                                  FROM SNMPv2-TC

    InterfaceIndexOrZero                        FROM IF-MIB

    ServiceAdminStatus,
    TmnxPortID, TmnxEncapVal, TmnxServId, TmnxCustId,
    TNamedItemOrEmpty, TPortSchedulerPIR,
    TCpmProtPolicyID, TmnxEnabledDisabled,
    TPolicyStatementNameOrEmpty, TSapIngressPolicyID, TSapEgressPolicyID,
    TIngHsmdaPerPacketOffsetOvr,
    TEgrHsmdaPerPacketOffsetOvr,
    ServObjDesc, TFilterID, TFdbTableSizeProfileID, SapLoopbackMode
                                                FROM TN-TC-MIB

    tnSysSwitchId
                                                FROM TROPIC-SYSTEM-MIB

    tnServObjs, tnServNotifications,
    tnCustId, tnSvcId, tnSvcVpnId, tnTstpTraps,
    ServObjName, ServType, VpnId,
    TlsBpduTranslation, TlsLimitMacMoveLevel, TlsLimitMacMove, StpExceptionCondition,
    BridgeId, TStpPortState, StpPortRole,
    StpProtocol, MvplsPruneState,
    MstiInstanceIdOrZero,
    L2ptProtocols
                                                FROM TN-SERV-MIB

    tnSRMIBModules                              FROM TROPIC-GLOBAL-REG;

tnSvcSapMIBModule   MODULE-IDENTITY
    LAST-UPDATED    "202011130000Z"
    ORGANIZATION    "Nokia"
    CONTACT-INFO
        "Nokia 7x50 Support
         Web: http://www.nokia.com/comps/pages/carrier_support.jhtml"
    DESCRIPTION
        "This  document  is the SNMP MIB module to manage and provision
        the various services of the Nokia 7x50 SR system.

        This   SNMP   MIB  module  (Specification)  embodies  Nokia's
        proprietary  intellectual  property.  Nokia retains all title
        and ownership in the Specification, including any revisions.

        Nokia  grants  all interested parties a non-exclusive license
        to  use and distribute an unmodified copy of this Specification
        in  connection with management of Nokia products, and without
        fee,  provided  this copyright notice and license appear on all
        copies.

        This  Specification  is  supplied `as is', and Nokia makes no
        warranty,  either express or implied, as to the use, operation,
        condition, or performance of the Specification."

--
--  Revision History
--

    REVISION        "202011130000Z"
    DESCRIPTION     "Added the following in tnSapEthernetInfoTable:
                     tnSapEthernetLoopbackMode
                     tnSapEthernetLoopbackMacSwapStaticMac."

    REVISION        "202011060000Z"
    DESCRIPTION     "Added the following to tnSapOperFlags:
                     bpduGuardBlocked(41)."

    REVISION        "202009250000Z"
    DESCRIPTION     "Added the following to tnSapOperFlags:
                     portBouncing(33)
                     to
                     rstpBlock(40)         -- indicate RSTP port operatioal down."

    REVISION        "202008140000Z"
    DESCRIPTION     "Marked the following as deprecated:
                     tnSapTlsFdbTableSizeProfId."

    REVISION        "201909130000Z"
    DESCRIPTION     "Added the following to tnSapBaseInfoTable:
                     tnSapAlmProfName."

    REVISION        "201908160000Z"
    DESCRIPTION     "Added the following to tnSapTlsInfoTable:
                     tnSapTlsFdbTableSizeProfId."

    REVISION        "201707070000Z"
    DESCRIPTION     "Added the following to tnSapSubType:
                     etree-root (5)
                     etree-leaf (6)
                     etree-branch (7)
                     etree-trunk (8)."

    REVISION        "201602150000Z"
    DESCRIPTION     "Commented out tnSapTlsMrpTable Table."

    REVISION        "201212050000Z"
    DESCRIPTION     "Commented out unsupported MIB tables and
                     attributes for 1830."

    REVISION        "201209010000Z"
    DESCRIPTION     "Changed the following indexes from read-only to
                     not-accessible:
                     tnSapPortId
                     tnSapEncapValue
                     tnSapIngQosQueueId
                     tnSapEgrQosQueueId."

    REVISION        "200902280000Z"
    DESCRIPTION     "Rev 7.0                28 Feb 2009 00:00
                     7.0 release of the TIMETRA-SAP-MIB."

    REVISION        "200807010000Z"
    DESCRIPTION     "Rev 6.1                01 Jul 2008 00:00
                     6.1 release of the TIMETRA-SAP-MIB."

    REVISION        "200710010000Z"
    DESCRIPTION     "Rev 1.0                01 OCT 2007 00:00
                     1.0 release of the TIMETRA-SAP-MIB from TIMETRA-SERV-MIB."

    ::= { tnSRMIBModules 55 }

-- --------------------------------------------------------------------
--      TIMETRA-SAP-MIB organisation
-- --------------------------------------------------------------------
tnSapObjs             OBJECT IDENTIFIER ::= { tnServObjs 3 }
-- tnSapNotifyObjs       OBJECT IDENTIFIER ::= { tnSapObjs 100 }

-- tnSapConformance      OBJECT IDENTIFIER ::= { tnServConformance 3 }

tnSapTrapsPrefix          OBJECT IDENTIFIER ::= { tnServNotifications 3 }
    tnSapTraps                OBJECT IDENTIFIER ::= { tnSapTrapsPrefix 0 }

-- --------------------------------------------------------------------
-- tnSapObjs group
-- --------------------------------------------------------------------
-- tnSapNumEntries OBJECT-TYPE
--     SYNTAX          Integer32
--     MAX-ACCESS      read-only
--     STATUS          current
--     DESCRIPTION     "The current number of SAPs configured in this
--                      device."
--     ::= { tnSapObjs 1 }

-- ----------------------------------
-- Base SAP Table
-- ----------------------------------
tnSapBaseInfoTable OBJECT-TYPE
    SYNTAX          SEQUENCE OF TnSapBaseInfoEntry
    MAX-ACCESS      not-accessible
    STATUS          current
    DESCRIPTION     "A table that contains basic SAP information."
    ::= { tnSapObjs 2 }

tnSapBaseInfoEntry OBJECT-TYPE
    SYNTAX          TnSapBaseInfoEntry
    MAX-ACCESS      not-accessible
    STATUS          current
    DESCRIPTION     "Information about a specific SAP."
    INDEX           { tnSysSwitchId, tnSvcId, tnSapPortId, tnSapEncapValue }
    ::= { tnSapBaseInfoTable 1 }

TnSapBaseInfoEntry ::=
    SEQUENCE {
        tnSapPortId                       TmnxPortID,
        tnSapEncapValue                   TmnxEncapVal,
        tnSapRowStatus                    RowStatus,
        tnSapType                         ServType,
        tnSapDescription                  ServObjDesc,
        tnSapAdminStatus                  ServiceAdminStatus,
        tnSapOperStatus                   INTEGER,
        tnSapIngressQosPolicyId           TSapIngressPolicyID,
        tnSapIngressMacFilterId           TFilterID,
        tnSapIngressIpFilterId            TFilterID,
        tnSapEgressQosPolicyId            TSapEgressPolicyID,
        tnSapEgressMacFilterId            TFilterID,
        tnSapEgressIpFilterId             TFilterID,
        tnSapMirrorStatus                 INTEGER,
        tnSapIesIfIndex                   InterfaceIndexOrZero,
        tnSapLastMgmtChange               TimeStamp,
        tnSapCollectAcctStats             TruthValue,
        tnSapAccountingPolicyId           Unsigned32,
        tnSapVpnId                        VpnId,
        tnSapCustId                       TmnxCustId,
        tnSapCustMultSvcSite              ServObjName,
        tnSapIngressQosSchedulerPolicy    ServObjName,
        tnSapEgressQosSchedulerPolicy     ServObjName,
        tnSapSplitHorizonGrp              ServObjName,
        tnSapIngressSharedQueuePolicy     ServObjName,
        tnSapIngressMatchQinQDot1PBits    INTEGER,
        tnSapOperFlags                    BITS,
        tnSapLastStatusChange             TimeStamp,
        tnSapAntiSpoofing                 INTEGER,
        tnSapIngressIpv6FilterId          TFilterID,
        tnSapEgressIpv6FilterId           TFilterID,
        tnSapTodSuite                     TNamedItemOrEmpty,
        tnSapIngUseMultipointShared       TruthValue,
        tnSapEgressQinQMarkTopOnly        TruthValue,
        tnSapEgressAggRateLimit           TPortSchedulerPIR,
        tnSapEndPoint                     ServObjName,
        tnSapIngressVlanTranslation       INTEGER,
        tnSapIngressVlanTranslationId     Integer32,
        tnSapSubType                      INTEGER,
        tnSapCpmProtPolicyId              TCpmProtPolicyID,
        tnSapCpmProtMonitorMac            TruthValue,
        tnSapEgressFrameBasedAccounting   TruthValue,
        tnSapIngressAggRateLimit          TPortSchedulerPIR,
        tnSapEgressHsmdaShaperOverride    TNamedItemOrEmpty,
        tnSapIngressHsmdaPacketOffOvr     TIngHsmdaPerPacketOffsetOvr,
        tnSapEgressHsmdaPacketOffOverride TEgrHsmdaPerPacketOffsetOvr,
        tnSapCallingStationId             DisplayString,
        tnSapIsaAaApplicationProfile      ServObjName,
        tnSapEthRingIndex                 Unsigned32,
        tnSapAlmProfName                  OCTET STRING
    }

tnSapPortId OBJECT-TYPE
    SYNTAX          TmnxPortID
    MAX-ACCESS      not-accessible
    STATUS          current
    DESCRIPTION     "The ID of the access port where this SAP
                     is defined."
    ::= { tnSapBaseInfoEntry 1 }

tnSapEncapValue OBJECT-TYPE
    SYNTAX          TmnxEncapVal
    MAX-ACCESS      not-accessible
    STATUS          current
    DESCRIPTION     "The value of the label used to identify this
                     SAP on the access port specified by tnSapPortId."
    ::= { tnSapBaseInfoEntry 2 }

tnSapRowStatus OBJECT-TYPE
    SYNTAX          RowStatus
    MAX-ACCESS      read-create
    STATUS          current
    DESCRIPTION     "This object indicates the status of this row. The
                     only values supported during a set operation are
                     'createAndGo' and 'destroy'."
    ::= { tnSapBaseInfoEntry 3 }

tnSapType OBJECT-TYPE
    SYNTAX          ServType
    MAX-ACCESS      read-only
    STATUS          current
    DESCRIPTION     "This object indicates the type of service where
                     this SAP is defined."
    ::= { tnSapBaseInfoEntry 4 }

tnSapDescription OBJECT-TYPE
    SYNTAX          ServObjDesc
    MAX-ACCESS      read-create
    STATUS          current
    DESCRIPTION     "Generic information about this SAP."
    DEFVAL          { "" }
    ::= { tnSapBaseInfoEntry 5 }

tnSapAdminStatus OBJECT-TYPE
    SYNTAX          ServiceAdminStatus
    MAX-ACCESS      read-create
    STATUS          current
    DESCRIPTION     "The desired state of this SAP."
    DEFVAL          { up }
    ::= { tnSapBaseInfoEntry 6 }

tnSapOperStatus OBJECT-TYPE
    SYNTAX          INTEGER {
                        up                 (1),
                        down               (2),
                        ingressQosMismatch (3),
                        egressQosMismatch  (4),
                        portMtuTooSmall    (5),
                        svcAdminDown       (6),
                        iesIfAdminDown     (7)
                    }
    MAX-ACCESS      read-only
    STATUS          current
    DESCRIPTION     "The value of the object tnSapOperStatus indicates the
                     operating state of this SAP."
    ::= { tnSapBaseInfoEntry 7 }

tnSapIngressQosPolicyId OBJECT-TYPE
    SYNTAX          TSapIngressPolicyID
    MAX-ACCESS      read-create
    STATUS          current
    DESCRIPTION     "The value of the object tnSapIngressQosPolicyId specifies
                     the row index in the tSapIngressTable corresponding to this
                     ingress QoS policy, or one if no policy is specified.
                     The value 0 is needed for mirror SAPs that
                     cannot have a qos policy assigned."
    DEFVAL          { 1 }
    ::= { tnSapBaseInfoEntry 8 }

tnSapIngressMacFilterId OBJECT-TYPE
    SYNTAX          TFilterID
    MAX-ACCESS      read-create
    STATUS          current
    DESCRIPTION     "The value of the object tnSapIngressMacFilterId specifies
                     the row index in the tMacFilterTable corresponding to this
                     ingress filter, or zero if no filter is specified."
    DEFVAL          { 0 }
    ::= { tnSapBaseInfoEntry 9 }

tnSapIngressIpFilterId OBJECT-TYPE
    SYNTAX          TFilterID
    MAX-ACCESS      read-create
    STATUS          current
    DESCRIPTION     "The value of the object tnSapIngressIpFilterId specifies the
                     row index in the tIPFilterTable corresponding to this
                     ingress filter, or zero if no filter is specified."
    DEFVAL          { 0 }
    ::= { tnSapBaseInfoEntry 10 }

tnSapEgressQosPolicyId OBJECT-TYPE
    SYNTAX          TSapEgressPolicyID
    MAX-ACCESS      read-create
    STATUS          current
    DESCRIPTION     "The row index in the tSapEgressTable
                     corresponding to this egress QoS policy,
                     or one if no policy is specified."
    DEFVAL          { 1 }
    ::= { tnSapBaseInfoEntry 11 }

tnSapEgressMacFilterId OBJECT-TYPE
    SYNTAX          TFilterID
    MAX-ACCESS      read-create
    STATUS          current
    DESCRIPTION     "The row index in the tMacFilterTable
                     corresponding to this egress filter,
                     or zero if no filter is specified."
    DEFVAL          { 0 }
    ::= { tnSapBaseInfoEntry 12 }

tnSapEgressIpFilterId OBJECT-TYPE
    SYNTAX          TFilterID
    MAX-ACCESS      read-create
    STATUS          current
    DESCRIPTION     "The row index in the tIPFilterTable
                     corresponding to this egress filter,
                     or zero if no filter is specified."
    DEFVAL          { 0 }
    ::= { tnSapBaseInfoEntry 13 }

tnSapMirrorStatus OBJECT-TYPE
    SYNTAX          INTEGER {
                        ingress          (1),
                        egress           (2),
                        ingressAndEgress (3),
                        disabled         (4)
                    }
    MAX-ACCESS      read-only
    STATUS          current
    DESCRIPTION     "This object specifies whether traffic
                     mirroring has been enabled on this SAP."
    ::= { tnSapBaseInfoEntry 14 }

tnSapIesIfIndex OBJECT-TYPE
    SYNTAX          InterfaceIndexOrZero
    MAX-ACCESS      read-create
    STATUS          current
    DESCRIPTION     "When the value of tnSapType is 'ies' this
                     object specifies the index of the IES interface
                     where this SAP is defined. The value of this object
                     can be set only when the row is created and cannot
                     be changed while the row status is 'active'. This
                     object is otherwise not significant and should have
                     the value zero."
    ::= { tnSapBaseInfoEntry 15 }

tnSapLastMgmtChange OBJECT-TYPE
    SYNTAX          TimeStamp
    MAX-ACCESS      read-only
    STATUS          current
    DESCRIPTION     "The value of sysUpTime at the time of the
                     most recent management-initiated change to
                     this SAP."
    ::= { tnSapBaseInfoEntry 16 }

tnSapCollectAcctStats OBJECT-TYPE
    SYNTAX          TruthValue
    MAX-ACCESS      read-create
    STATUS          current
    DESCRIPTION     "When the value of this object is 'true' the agent
                     collects accounting statistics on this SAP."
    DEFVAL          { false }
    ::= { tnSapBaseInfoEntry 17 }

tnSapAccountingPolicyId OBJECT-TYPE
    SYNTAX          Unsigned32
    MAX-ACCESS      read-create
    STATUS          current
    DESCRIPTION     "This object specifies the policy to use to collect
                     accounting statistics on this SAP. The value zero
                     indicates that the agent should use the default
                     accounting policy, if one exists."
    DEFVAL          { 0 }
    ::= { tnSapBaseInfoEntry 18 }

tnSapVpnId OBJECT-TYPE
    SYNTAX          VpnId
    MAX-ACCESS      read-only
    STATUS          current
    DESCRIPTION     "The VPN ID of the associated service."
    ::= { tnSapBaseInfoEntry 19 }

tnSapCustId OBJECT-TYPE
    SYNTAX          TmnxCustId
    MAX-ACCESS      read-only
    STATUS          current
    DESCRIPTION     "The Customer ID of the associated service."
    ::= { tnSapBaseInfoEntry 20 }

tnSapCustMultSvcSite OBJECT-TYPE
    SYNTAX          ServObjName
    MAX-ACCESS      read-create
    STATUS          current
    DESCRIPTION     "The value of this object, when not null, indicates
                     the Multi-Service Site this SAP is a member of. This
                     information is used to configure the ingress and
                     egress QoS schedulers for this SAP."
    DEFVAL          { "" }
    ::= { tnSapBaseInfoEntry 21 }

tnSapIngressQosSchedulerPolicy OBJECT-TYPE
    SYNTAX          ServObjName
    MAX-ACCESS      read-create
    STATUS          current
    DESCRIPTION     "This object can be set only when tnSapCustMultSvcSite
                     is null. It indicates the ingress QoS scheduler for
                     this SAP."
    DEFVAL          { "" }
    ::= { tnSapBaseInfoEntry 22 }

tnSapEgressQosSchedulerPolicy OBJECT-TYPE
    SYNTAX          ServObjName
    MAX-ACCESS      read-create
    STATUS          current
    DESCRIPTION     "This object can be set only when tnSapCustMultSvcSite
                     is null. It indicates the egress QoS scheduler for
                     this SAP."
    DEFVAL          { "" }
    ::= { tnSapBaseInfoEntry 23 }

tnSapSplitHorizonGrp OBJECT-TYPE
    SYNTAX          ServObjName
    MAX-ACCESS      read-create
    STATUS          current
    DESCRIPTION     "This object specifies the name of the split-horizon
                     group where the SAP belongs to. This object can be
                     set only at the time the row is created. Per default
                     a SAP does not belong to any split-horizon group. The
                     name specified must correspond to an existing split-
                     horizon group in the TLS service where this SAP is
                     defined."
    DEFVAL          { "" }
    ::= { tnSapBaseInfoEntry 24 }

tnSapIngressSharedQueuePolicy OBJECT-TYPE
    SYNTAX          ServObjName
    MAX-ACCESS      read-create
    STATUS          current
    DESCRIPTION     "This object indicates the ingress shared queue policy
                     used by this SAP. When the value of this object is null
                     it means that the SAP will use individual ingress QoS
                     queues, instead of the shared ones."
    DEFVAL          { "" }
    ::= { tnSapBaseInfoEntry 25 }

tnSapIngressMatchQinQDot1PBits OBJECT-TYPE
    SYNTAX          INTEGER {
                        default (1),
                        top     (2),
                        bottom  (3)
                    }
    MAX-ACCESS      read-create
    STATUS          current
    DESCRIPTION     "This object applies only to SAP's defined on a port
                     configured for qinq service encapsulation. It indicates
                     which 802.1P bits will be used to match a QoS or a MAC
                     filter policy when a double-tagged frame is received on
                     this SAP."
    DEFVAL          { default }
    ::= { tnSapBaseInfoEntry 26 }

tnSapOperFlags OBJECT-TYPE
    SYNTAX          BITS {
                      sapAdminDown(0),           -- SAP is admin down
                      svcAdminDown(1),           -- Service is admin down
                      iesIfAdminDown(2),         -- IP interface is admin down
                                                 -- (IES and VPRN only)
                      portOperDown(3),           -- Access port is oper down
                      portMtuTooSmall(4),        -- Access port's MTU is less
                                                 -- than Service MTU
                      l2OperDown(5),             -- L2 PVC/PVP is oper down
                                                 -- (FR and ATM only)
                      ingressQosMismatch(6),     -- Mismatch between ingress
                                                 -- QoS and Scheduler policies
                      egressQosMismatch(7),      -- Mismatch between egress
                                                 -- QoS and Scheduler policies
                      relearnLimitExceeded(8),   -- MAC relearn limit was
                                                 -- exceeded (TLS only)
                      recProtSrcMac(9),          -- Received a packet with a
                                                 -- protected source MAC
                                                 -- (TLS only)
                      subIfAdminDown(10),        -- Subscriber interface is
                                                 -- admin down (group-interface
                                                 -- SAP only)
                      sapIpipeNoCeIpAddr(11),    -- CE IP Address not
                                                 -- configured for Ipipe SAP
                                                 -- (IPIPE SAP only)
                      sapTodResourceUnavail(12), -- SAP with ToD had
                                                 -- insufficient resources
                                                 -- at boot time and got
                                                 -- default policies.
                      sapTodMssResourceUnavail(13), -- MSS of this SAP uses
                                                 -- ToD and due to
                                                 -- insufficient resources
                                                 -- at boot time got
                                                 -- default scheduler
                                                 -- policies.
                      sapParamMismatch(14),      -- Service specific local
                                                 -- parameter mismatch
                      sapCemNoEcidOrMacAddr(15), -- ECID or MAC address not
                                                 -- configured (CEM SAP only)
                      sapStandbyForMcRing(16),   -- mc-ring keeps this SAP
                                                 -- standby for the
                                                 -- corresponding SAP on peer
                      sapSvcMtuTooSmall(17),     -- Service MTU is less
                                                 -- than the SAP payload
                      ingressNamedPoolMismatch(18), -- Invalid named-pool
                                                 -- on the ingress side
                      egressNamedPoolMismatch(19), -- Invalid named-pool
                                                 -- on the egress side
                      ipMirrorNoMacAddr(20),     -- No MAC Address configured
                                                 -- for the ip-mirror
                      sapEpipeNoRingNode(21),    -- No TN-MC-REDUNDANCY-MIB
                                                 -- ::tnMcEpipeSapEntry object
                                                 -- configured for Epipe SAP
                                                 -- (EPIPE SAP only)
                      mcStandby(22),             -- indicates the SAP is standby
                                                 -- because of a mutli-chassis
                                                 -- protocol
                      mhStandby(23),             -- indicates the SAP is standby
                                                 -- because of a BGP multi-home
                                                 -- protocol
                      oamDownMepFault(24),       -- ETH-CFM down MEP fault
                                                 -- detected
                      oamUpMepFault(25),         -- ETH-CFM up MEP fault detected
                      ethTunTagMisconfig(26),    -- missing tag(s) for Eth-Tunnel
                                                 -- SAP
                      ingressPolicerMismatch(27), -- indicate ingress policer
                                                 -- is parented to non-existent
                                                 -- arbiter
                      egressPolicerMismatch(28), -- indicate egress policer is
                                                 -- parented to non-existent arbiter
                      sapTlsNoRingNode(29),      -- No TN-MC-REDUNDANCY-MIB
                                                 -- ::tnMcTlsSapEntry object
                                                 -- configured for TLS SAP
                                                 -- (VPLS SAP only)
                      ethRingPathBlocked(30),    -- indicates eth-ring path is
                                                 -- blocked.
                      oamTunnelMepFault(31),     -- indicates eth-cfm Tunnel
                                                 -- MEP fault detected.
                      operGrpDown(32),           -- indicates operational-group
                                                 -- is down
                      portBouncing(33),
                      sapEgressHQosMgmtMismatch(34),
                      evpnP2mpConflict(35),
                      l2tpv3TunnelDown(36),
                      labelStackLimitExceeded(37),
                      sapIngQGrpRedirMismatch(38),
                      sapEgrQGrpRedirMismatch(39),
                      rstpBlocked(40),           -- indicate RSTP port operatioal down
                      bpduGuardBlocked(41)
                    }
    MAX-ACCESS      read-only
    STATUS          current
    DESCRIPTION     "This object specifies all the conditions that
                     affect the operating status of this SAP."
    ::= { tnSapBaseInfoEntry 27 }

tnSapLastStatusChange OBJECT-TYPE
    SYNTAX          TimeStamp
    MAX-ACCESS      read-only
    STATUS          current
    DESCRIPTION     "The value of sysUpTime at the time of the
                     most recent operating status change to this
                     SAP."
    ::= { tnSapBaseInfoEntry 28 }

tnSapAntiSpoofing OBJECT-TYPE
    SYNTAX          INTEGER {
                        disabled            (0),
                        sourceIpAddr        (1),
                        sourceMacAddr       (2),
                        sourceIpAndMacAddr  (3),
                        nextHopIpAndMacAddr (4)
                    }
    MAX-ACCESS      read-create
    STATUS          current
    DESCRIPTION     "The value of the object tnSapAntiSpoofing specifies
                     the type of anti-spoof filtering applicable on this SAP.

                     'nextHopIpAndMacAddr (4)' is not supported on SR-1, where
                     the value of TIMETRA-CHASSIS-MIB::tmnxChassisType is '5'."
    DEFVAL { disabled }
    ::= { tnSapBaseInfoEntry 29 }

tnSapIngressIpv6FilterId OBJECT-TYPE
    SYNTAX          TFilterID
    MAX-ACCESS      read-create
    STATUS          current
    DESCRIPTION     "The value of the object tnSapIngressIpv6FilterId specifies
                     the row index in the tIPv6FilterTable corresponding to
                     this ingress ipv6 filter, or zero if no ipv6 filter is
                     specified."
    DEFVAL          { 0 }
    ::= { tnSapBaseInfoEntry 30 }

tnSapEgressIpv6FilterId OBJECT-TYPE
    SYNTAX          TFilterID
    MAX-ACCESS      read-create
    STATUS          current
    DESCRIPTION     "The value of the object tnSapEgressIpv6FilterId specifies
                     the row index in the tIPv6FilterTable corresponding to
                     this egress ipv6 filter, or zero if no ipv6 filter is
                     specified."
    DEFVAL          { 0 }
    ::= { tnSapBaseInfoEntry 31 }

tnSapTodSuite OBJECT-TYPE
    SYNTAX          TNamedItemOrEmpty
    MAX-ACCESS      read-create
    STATUS          current
    DESCRIPTION     "The value of the object tnSapTodSuite specifies the Time of
                     Day (ToD) suite to be applied on this SAP.
                     An empty string indicates that no ToD suite is applied
                     on this SAP.
                     A set request will only be allowed, if the indicated suite
                     is defined in TIMETRA-SCHEDULER-MIB::tmnxTodSuiteTable."
    DEFVAL          { ''H }
    ::= { tnSapBaseInfoEntry 32 }

tnSapIngUseMultipointShared       OBJECT-TYPE
    SYNTAX          TruthValue
    MAX-ACCESS      read-create
    STATUS          current
    DESCRIPTION     "When the value of tnSapIngressSharedQueuePolicy is not null,
                     the value of the object tnSapIngUseMultipointShared
                     specifies whether this SAP uses the multipoint-shared
                     queues of the shared policy."
    DEFVAL          { false }
    ::= { tnSapBaseInfoEntry 33 }

tnSapEgressQinQMarkTopOnly OBJECT-TYPE
    SYNTAX          TruthValue
    MAX-ACCESS      read-create
    STATUS          current
    DESCRIPTION     "When the encapsulation type of the access port where
                     this SAP is defined is qinq, the value of the object
                     tnSapEgressQinQMarkTopOnly specifies which P-bits to mark
                     during packet egress. When the value is false both set
                     of P-bits are marked. When the value is true, only the
                     P-bits in the top Q-tag are marked."
    DEFVAL          { false }
    ::= { tnSapBaseInfoEntry 34 }

tnSapEgressAggRateLimit   OBJECT-TYPE
    SYNTAX          TPortSchedulerPIR
    UNITS           "kbps"
    MAX-ACCESS      read-create
    STATUS          current
    DESCRIPTION     "The value of the object tnSapEgressAggRateLimit
                     specifies the maximum total rate of all egress queues for
                     this SAP. The value '-1' means that there
                     is no limit."
    DEFVAL          { -1 }
    ::= { tnSapBaseInfoEntry 35 }

tnSapEndPoint         OBJECT-TYPE
    SYNTAX          ServObjName
    MAX-ACCESS      read-create
    STATUS          current
    DESCRIPTION     "The value of the object tnSapEndPoint specifies the service
                     endpoint to which this SAP is attached. The tnSvcId of the
                     SAP MUST match the tnSvcId of the service endpoint."
    DEFVAL          { "" }
    ::= { tnSapBaseInfoEntry 36 }

tnSapIngressVlanTranslation OBJECT-TYPE
    SYNTAX          INTEGER {
                        none        (1),
                        vlanId      (2),
                        copyOuter   (3)
                        }
    MAX-ACCESS      read-create
    STATUS          current
    DESCRIPTION     "The value of tnSapIngressVlanTranslation specifies the
                     desired Ingress Vlan Translation.

                     A value of 'vlanId' specifies that the value of
                     tnSapIngressVlanTranslationId is to be used to overwrite
                     the preserved VLAN id in the packet.

                     A value of 'copyOuter' specifies that the outer VLAN
                     id should be used to overwrite the preserved VLAN id in
                     the packet.

                     An 'inconsistentValue' error is returned when an attempt
                     is made to set the value of tnSapIngressVlanTranslation
                     to 'vlanId' and tnSapIngressVlanTranslationId is
                     set to '-1'."
    DEFVAL          { none }
    ::= { tnSapBaseInfoEntry 37 }

tnSapIngressVlanTranslationId OBJECT-TYPE
    SYNTAX          Integer32  (-1|0..4094)
    MAX-ACCESS      read-create
    STATUS          current
    DESCRIPTION     "The value of tnSapIngressVlanTranslationId specifies the
                     VLAN id to be used to overwrite the preserved VLAN id
                     in the packet.

                     An 'inconsistentValue' error is returned when an
                     attempt is made to set the value of
                     tnSapIngressVlanTranslationId to other than '-1' and
                     tnSapIngressVlanTranslation is not set to 'vlanId'."
    DEFVAL          { -1 }
    ::= { tnSapBaseInfoEntry 38 }

tnSapSubType          OBJECT-TYPE
    SYNTAX          INTEGER {
                        regular      (0),
                        capture      (1),
                        managed      (2),
                        video        (3),
                        etree-root   (5),
                        etree-leaf   (6),
                        etree-branch (7),
                        etree-trunk  (8)
                    }
    MAX-ACCESS      read-create
    STATUS          current
    DESCRIPTION     "The value of the object tnSapSubType indicates the
                     sub-type for this SAP.

                     A value of 'regular' indicates a standard SAP.

                     A value of 'capture' specifies a capturing SAP
                     in which triggering packets will be sent to the CPM.
                     Non-triggering packets captured by the 'capture' SAP
                     will be dropped.

                     A value of 'managed' indicates a managed SAP which
                     was created dynamically after receiving triggering
                     packets on a SAP with a tnSapSubType value of
                     'capture'. Entries with a value of 'managed'
                     are not user editable and are not maintained
                     in the configuration file.

                     A value of 'video' indicates a video SAP which
                     terminates on a video SAP. Entries with a value of
                     'video' are not user editable and are not maintained
                     in the configuration file.

                     Whereas any of the four values may be returned in
                     in response to an SNMP GET request, only two values
                     may be specified in an SNMP SET request: 'regular'
                     and 'capture'. An attempt to specify a value
                     of 'managed' or 'video' in an SNMP SET request will fail
                     with an error of 'inconsistentValue'.

                     The value of this object cannot be changed after creation."
    DEFVAL          { regular }
    ::= { tnSapBaseInfoEntry 39 }

tnSapCpmProtPolicyId  OBJECT-TYPE
    SYNTAX          TCpmProtPolicyID
    MAX-ACCESS      read-create
    STATUS          current
    DESCRIPTION
        "The value of tnSapCpmProtPolicyId associates a CPM Protection policy
         with a SAP.

         A value of zero (0) specifies that no CPM Protection policy is
         associated with this SAP.

         A value of one (1) specifies that the default CPM Protection policy is
         associated with this SAP.

         If no value for tnSapCpmProtPolicyId is specified when the
         tnSapBaseInfoEntry is created, the system assigns a default value
         as follows: if the system creates a corresponding entry
         in the tnSapSubMgmtInfoTable, the default value is 'one'; otherwise,
         the default value is 'zero'. This means that all SAP's that
         support Enhanced Subscriber Management get a default value of 'one'.

         If a SAP would get a default value of 'one', it is not
         allowed to set the value of tnSapCpmProtPolicyId to 'zero'.

         If a SAP would get a default value of 'zero', it is not
         allowed to modify the value of tnSapCpmProtPolicyId.

         This object is not supported on SR-1 and ESS-1, where the
         value of TIMETRA-CHASSIS-MIB::tmnxChassisType is '5',
         and 7710, where the value of TIMETRA-CHASSIS-MIB::tmnxChassisType is
         '7' or '9'."
    ::= { tnSapBaseInfoEntry 40 }

tnSapCpmProtMonitorMac OBJECT-TYPE
    SYNTAX          TruthValue
    MAX-ACCESS      read-create
    STATUS          current
    DESCRIPTION
         "The value of tnSapCpmProtMonitorMac specifies whether the
         tmnxCpmProtPolPerSrcRateLimit of the CPM Protection policy must be applied.

         If the value of tnSapCpmProtMonitorMac is 'true', the per-source rate limit
         must be applied.

         If the value of tnSapCpmProtPolicyId is equal to zero (0), the value of
         tnSapCpmProtMonitorMac is irrelevant and will be ignored.

         This object is not supported on SR-1 and ESS-1, where the
         value of TIMETRA-CHASSIS-MIB::tmnxChassisType is '5',
         and 7710, where the value of TIMETRA-CHASSIS-MIB::tmnxChassisType is
         '7' or '9'."
    DEFVAL          { false }
    ::= { tnSapBaseInfoEntry 41 }

tnSapEgressFrameBasedAccounting OBJECT-TYPE
    SYNTAX       TruthValue
    MAX-ACCESS   read-create
    STATUS       current
    DESCRIPTION
        "The value of tnSapEgressFrameBasedAccounting specifies whether
         to use frame-based accounting when evaluating
         tnSapEgressAggRateLimit for all egress queues for this SAP.

         If the value is 'false', the default packet-based accounting
         method will be used."
    DEFVAL { false }
    ::= { tnSapBaseInfoEntry 42 }

tnSapIngressAggRateLimit   OBJECT-TYPE
    SYNTAX          TPortSchedulerPIR
    UNITS           "kbps"
    MAX-ACCESS      read-create
    STATUS          current
    DESCRIPTION     "The value of the object tnSapIngressAggRateLimit
                     specifies the maximum total rate of all ingress queues for
                     this SAP. The value '-1' means that there
                     is no limit."
    DEFVAL          { -1 }
    ::= { tnSapBaseInfoEntry 43 }

tnSapEgressHsmdaShaperOverride   OBJECT-TYPE
    SYNTAX          TNamedItemOrEmpty
    MAX-ACCESS      read-create
    STATUS          current
    DESCRIPTION     "The value of the object tnSapEgressHsmdaShaperOverride
                     specifies the name of the secondary shaper for this SAP.
                     The value must correspond to an entry in the tmnxPortEgrShaperTable.
                     If the empty string is specified, the default secondary shaper will
                     be used."
    DEFVAL          { "" }
    ::= { tnSapBaseInfoEntry 44 }

tnSapIngressHsmdaPacketOffOvr        OBJECT-TYPE
    SYNTAX      TIngHsmdaPerPacketOffsetOvr
    UNITS       "bytes"
    MAX-ACCESS  read-create
    STATUS      current
    DESCRIPTION
        "The value of tnSapIngressHsmdaPacketOffOvr specifies the value,
         in bytes, of the adjustment to make to the size of each
         packet for HSMDA queue accounting on ingress."
    DEFVAL { -128 }
    ::= { tnSapBaseInfoEntry 45 }

tnSapEgressHsmdaPacketOffOverride        OBJECT-TYPE
    SYNTAX      TEgrHsmdaPerPacketOffsetOvr
    UNITS       "bytes"
    MAX-ACCESS  read-create
    STATUS      current
    DESCRIPTION
        "The value of tnSapEgressHsmdaPacketOffOverride specifies the value,
         in bytes, of the adjustment to make to the size of each
         packet for HSMDA queue accounting on ingress."
    DEFVAL { -128 }
    ::= { tnSapBaseInfoEntry 46 }

tnSapCallingStationId OBJECT-TYPE
    SYNTAX          DisplayString (SIZE (0..64))
    MAX-ACCESS      read-create
    STATUS          current
    DESCRIPTION     "The value of tnSapCallingStationId specifies the
                     calling-station-id to be included in all RADIUS
                     authentication and accounting requests if configured
                     to be included in the corresponding RADIUS authentication
                     or accounting policy.

                     If the empty string is specified, no calling-station-id
                     will be included."
    DEFVAL { "" }
    ::= { tnSapBaseInfoEntry 47 }

tnSapIsaAaApplicationProfile OBJECT-TYPE
    SYNTAX          ServObjName
    MAX-ACCESS      read-create
    STATUS          current
    DESCRIPTION     "The value of tnSapIsaAaApplicationProfile specifies
                     the ISA-AA application profile for this tnSap. The
                     specified application profile needs to exist in the
                     TIMETRA-BSX-NG-MIB::tmnxBsxAppProfTable."
    DEFVAL          { "" }
    ::= { tnSapBaseInfoEntry  48 }

tnSapEthRingIndex  OBJECT-TYPE
    SYNTAX          Unsigned32
    MAX-ACCESS      read-create
    STATUS          current
    DESCRIPTION     "The value of tnSapEthRingIndex specifies the Ethernet Ring
                     associated with this SAP.

                     This object, if required, MUST be configured during the
                     row creation of the tnSapBaseInfoTable row, and MUST
                     reference an existing row in
                     TIMETRA-ETH-RING-MIB::tmnxEthRingConfigTable.

                     The value zero, the default value, specifies there is no
                     Ethernet Ring associated with this SAP.

                     This object can not be changed once set; the SAP MUST be
                     destroyed and re-created to change the tnSapEthRingIndex
                     object."
    DEFVAL           { 0 }
    ::= { tnSapBaseInfoEntry 52 }

tnSapAlmProfName OBJECT-TYPE
    SYNTAX         OCTET STRING (SIZE(1..40))
    MAX-ACCESS     read-create
    STATUS         current
    DESCRIPTION    "."
    ::= { tnSapBaseInfoEntry 53 }

-- -------------------------------------
-- TLS SAP Table
-- -------------------------------------
tnSapTlsInfoTable OBJECT-TYPE
    SYNTAX          SEQUENCE OF SapTlsInfoEntry
    MAX-ACCESS      not-accessible
    STATUS          current
    DESCRIPTION     "A table that contains TLS SAP information."
    ::= { tnSapObjs 3 }

tnSapTlsInfoEntry OBJECT-TYPE
    SYNTAX          SapTlsInfoEntry
    MAX-ACCESS      not-accessible
    STATUS          current
    DESCRIPTION     "TLS specific information about a SAP."
    INDEX           { tnSysSwitchId, tnSvcId, tnSapPortId, tnSapEncapValue }
    ::= { tnSapTlsInfoTable 1 }

SapTlsInfoEntry ::=
    SEQUENCE {
        tnSapTlsStpAdminStatus            TmnxEnabledDisabled,
        tnSapTlsStpPriority               INTEGER,
        tnSapTlsStpPortNum                INTEGER,
        tnSapTlsStpPathCost               INTEGER,
        tnSapTlsStpRapidStart             TmnxEnabledDisabled,
        tnSapTlsStpBpduEncap              INTEGER,
        tnSapTlsStpPortState              TStpPortState,
        tnSapTlsStpDesignatedBridge       BridgeId,
        tnSapTlsStpDesignatedPort         Integer32,
        tnSapTlsStpForwardTransitions     Gauge32,
        tnSapTlsStpInConfigBpdus          Gauge32,
        tnSapTlsStpInTcnBpdus             Gauge32,
        tnSapTlsStpInBadBpdus             Gauge32,
        tnSapTlsStpOutConfigBpdus         Gauge32,
        tnSapTlsStpOutTcnBpdus            Gauge32,
        tnSapTlsStpOperBpduEncap          INTEGER,
        tnSapTlsVpnId                     VpnId,
        tnSapTlsCustId                    TmnxCustId,
        tnSapTlsMacAddressLimit           Integer32,
        tnSapTlsNumMacAddresses           Integer32,
        tnSapTlsNumStaticMacAddresses     Integer32,
        tnSapTlsMacLearning               TmnxEnabledDisabled,
        tnSapTlsMacAgeing                 TmnxEnabledDisabled,
        tnSapTlsStpOperEdge               TruthValue,
        tnSapTlsStpAdminPointToPoint      INTEGER,
        tnSapTlsStpPortRole               StpPortRole,
        tnSapTlsStpAutoEdge               TmnxEnabledDisabled,
        tnSapTlsStpOperProtocol           StpProtocol,
        tnSapTlsStpInRstBpdus             Gauge32,
        tnSapTlsStpOutRstBpdus            Gauge32,
        tnSapTlsLimitMacMove              TlsLimitMacMove,
--        tnSapTlsDhcpSnooping              TmnxEnabledDisabled,
        tnSapTlsMacPinning                TmnxEnabledDisabled,
        tnSapTlsDiscardUnknownSource      TmnxEnabledDisabled,
        tnSapTlsMvplsPruneState           MvplsPruneState,
        tnSapTlsMvplsMgmtService          TmnxServId,
        tnSapTlsMvplsMgmtPortId           TmnxPortID,
        tnSapTlsMvplsMgmtEncapValue       TmnxEncapVal,
        tnSapTlsArpReplyAgent             INTEGER,
        tnSapTlsStpException              StpExceptionCondition,
        tnSapTlsAuthenticationPolicy      TPolicyStatementNameOrEmpty,
        tnSapTlsL2ptTermination           TmnxEnabledDisabled,
        tnSapTlsBpduTranslation           TlsBpduTranslation,
        tnSapTlsStpRootGuard              TruthValue,
        tnSapTlsStpInsideRegion           TruthValue,
        tnSapTlsEgressMcastGroup          TNamedItemOrEmpty,
        tnSapTlsStpInMstBpdus             Gauge32,
        tnSapTlsStpOutMstBpdus            Gauge32,
        tnSapTlsRestProtSrcMac            TruthValue,
        tnSapTlsRestUnprotDstMac          TruthValue,
        tnSapTlsStpRxdDesigBridge         BridgeId,
        tnSapTlsStpRootGuardViolation     TruthValue,
        tnSapTlsShcvAction                INTEGER,
        tnSapTlsShcvSrcIp                 IpAddress,
        tnSapTlsShcvSrcMac                MacAddress,
        tnSapTlsShcvInterval              Unsigned32,
        tnSapTlsMvplsMgmtMsti             MstiInstanceIdOrZero,
        tnSapTlsMacMoveNextUpTime         Unsigned32,
        tnSapTlsMacMoveRateExcdLeft       Unsigned32,
        tnSapTlsRestProtSrcMacAction      INTEGER,
        tnSapTlsL2ptForceBoundary         TruthValue,
        tnSapTlsLimitMacMoveLevel         TlsLimitMacMoveLevel,
        tnSapTlsBpduTransOper             INTEGER,
        tnSapTlsDefMtnSapPolicy             TPolicyStatementNameOrEmpty,
        tnSapTlsL2ptProtocols             L2ptProtocols,
        tnSapTlsL2ptForceProtocols        L2ptProtocols,
        tnSapTlsPppoeMtnSapTrigger          TruthValue,
        tnSapTlsDhcpMtnSapTrigger           TruthValue,
        tnSapTlsMrpJoinTime               Unsigned32,
        tnSapTlsMrpLeaveTime              Unsigned32,
        tnSapTlsMrpLeaveAllTime           Unsigned32,
        tnSapTlsMrpPeriodicTime           Unsigned32,
        tnSapTlsMrpPeriodicEnabled        TruthValue,
        tnSapTlsPppoePolicy               TNamedItemOrEmpty,
        tnSapTlsArpMsapTrigger            TruthValue,
        tnSapTlsInTcBitBpdus              Counter32,
        tnSapTlsOutTcBitBpdus             Counter32,
        tnSapTlsShcvRetryTimeout          Unsigned32,
        tnSapTlsShcvRetryCount            Unsigned32,
        tnSapTlsFdbTableSizeProfId        TFdbTableSizeProfileID  -- deprecated
    }

tnSapTlsStpAdminStatus OBJECT-TYPE
    SYNTAX          TmnxEnabledDisabled
    MAX-ACCESS      read-write
    STATUS          current
    DESCRIPTION     "The value of the object tnSapTlsStpAdminStatus specifies
                     whether this SAP participates in the TLS's Spanning Tree
                     Protocol."
    DEFVAL          { enabled }
    ::= { tnSapTlsInfoEntry 1 }

tnSapTlsStpPriority OBJECT-TYPE
    SYNTAX          Integer32 (0..255)
    MAX-ACCESS      read-write
    STATUS          current
    DESCRIPTION     "The value of the object tnSapTlsStpPriority specifies
                     the value of the port priority field which is contained in
                     the most significant 4 bits of the 16-bit Port ID
                     associated with this SAP. As only the most significant 4
                     bits of the value are used, the actual value of this object
                     is limited to multiples of 16: e.g. the agent rounds down
                     the value to one of: 0, 16, 32, .. , 224, 240."
    DEFVAL          { 128 }
    ::= { tnSapTlsInfoEntry 2 }

tnSapTlsStpPortNum OBJECT-TYPE
    SYNTAX          Integer32 (0..4094)
    MAX-ACCESS      read-write
    STATUS          current
    DESCRIPTION     "The value of the object tnSapTlsStpPortNum specifies the
                     value of the port number field which is contained in the
                     least significant 12 bits of the 16-bit Port ID associated
                     with this SAP. Values in the range 2048..4094 are
                     automatically assigned by the agent when the SAP is
                     created or when the value of this object is set to zero
                     via management. Values in the range 1..2047 can be set
                     via management, to allow this object to have a
                     deterministic value across system reboots."
    ::= { tnSapTlsInfoEntry 3 }

tnSapTlsStpPathCost OBJECT-TYPE
    SYNTAX          Integer32 (1..200000000)
    MAX-ACCESS      read-write
    STATUS          current
    DESCRIPTION     "The value of the object  tnSapTlsStpPathCost specifies the
                     contribution of this port to the path cost of paths
                     towards the spanning tree root which include this port."
    DEFVAL          { 10 }
    ::= { tnSapTlsInfoEntry 4 }

tnSapTlsStpRapidStart OBJECT-TYPE
    SYNTAX          TmnxEnabledDisabled
    MAX-ACCESS      read-write
    STATUS          current
    DESCRIPTION     "The value of the object tnSapTlsStpRapidStart specifies
                     whether Rapid Start is enabled on this SAP. When the value
                     is 'enabled' the Spanning Tree Protocol state transitions
                     on this SAP are driven by the value of the 'HelloTime'
                     instead of the value of 'ForwardDelay', thus allowing a
                     faster transition into the forwarding state. This
                     parameter is also referred to as 'adminEdge'. "
    DEFVAL          { disabled }
    ::= { tnSapTlsInfoEntry 5 }

tnSapTlsStpBpduEncap OBJECT-TYPE
    SYNTAX          INTEGER {
                        dynamic (1),
                        dot1d   (2),
                        pvst    (3)
                    }
    MAX-ACCESS      read-write
    STATUS          current
    DESCRIPTION     "The value of the object tnSapTlsStpBpduEncap specifies the
                     type of encapsulation used on BPDUs sent out and received
                     on this SAP."
    DEFVAL          { dynamic }
    ::= { tnSapTlsInfoEntry 6 }

tnSapTlsStpPortState OBJECT-TYPE
    SYNTAX          TStpPortState
    MAX-ACCESS      read-only
    STATUS          current
    DESCRIPTION     "The value of the object tnSapTlsStpPortState indicates the
                     port's current state as defined by application of the
                     Spanning Tree Protocol. This state controls what action a
                     port takes on reception of a frame. If the bridge has
                     detected a port that is malfunctioning it will
                     place that port into the 'broken' state."
    ::= { tnSapTlsInfoEntry 7 }

tnSapTlsStpDesignatedBridge OBJECT-TYPE
    SYNTAX          BridgeId
    MAX-ACCESS      read-only
    STATUS          current
    DESCRIPTION     "The value of the object tnSapTlsStpDesignatedBridge
                     indicates  the Bridge Identifier of the bridge which this
                     port considers to be the Designated Bridge for this port's
                     segment."
    ::= { tnSapTlsInfoEntry 8 }

tnSapTlsStpDesignatedPort OBJECT-TYPE
    SYNTAX          Integer32
    MAX-ACCESS      read-only
    STATUS          current
    DESCRIPTION     "The value of the object tnSapTlsStpDesignatedPort indicates
                     the Port Identifier of the port on the Designated Bridge
                     for this port's segment."
    ::= { tnSapTlsInfoEntry 9 }

tnSapTlsStpForwardTransitions OBJECT-TYPE
    SYNTAX          Gauge32
    MAX-ACCESS      read-only
    STATUS          current
    DESCRIPTION     "The value of the object tnSapTlsStpForwardTransitions
                     indicates the number of times this port has transitioned
                     from the Learning state to the Forwarding state."
    ::= { tnSapTlsInfoEntry 10 }

tnSapTlsStpInConfigBpdus OBJECT-TYPE
    SYNTAX          Gauge32
    MAX-ACCESS      read-only
    STATUS          current
    DESCRIPTION     "The value of the object tnSapTlsStpInConfigBpdus indicates
                     the number of Configuration BPDUs received on this SAP."
    ::= { tnSapTlsInfoEntry 11 }

tnSapTlsStpInTcnBpdus OBJECT-TYPE
    SYNTAX          Gauge32
    MAX-ACCESS      read-only
    STATUS          current
    DESCRIPTION     "The value of the object  tnSapTlsStpInTcnBpdus indicates the
                     number of Topology Change Notification BPDUs received on
                     this SAP."
    ::= { tnSapTlsInfoEntry 12 }

tnSapTlsStpInBadBpdus OBJECT-TYPE
    SYNTAX          Gauge32
    MAX-ACCESS      read-only
    STATUS          current
    DESCRIPTION     "This object specifies the number of bad
                     BPDUs received on this SAP."
    ::= { tnSapTlsInfoEntry 13 }

tnSapTlsStpOutConfigBpdus OBJECT-TYPE
    SYNTAX          Gauge32
    MAX-ACCESS      read-only
    STATUS          current
    DESCRIPTION     "The value of the object tnSapTlsStpOutConfigBpdus indicates
                     the number of Configuration BPDUs sent out this SAP."
    ::= { tnSapTlsInfoEntry 14 }

tnSapTlsStpOutTcnBpdus OBJECT-TYPE
    SYNTAX          Gauge32
    MAX-ACCESS      read-only
    STATUS          current
    DESCRIPTION     "This object specifies the number of Topology
                     Change Notification BPDUs sent out this SAP."
    ::= { tnSapTlsInfoEntry 15 }

tnSapTlsStpOperBpduEncap OBJECT-TYPE
    SYNTAX          INTEGER {
                        dynamic (1),
                        dot1d   (2),
                        pvst    (3)
                    }
    MAX-ACCESS      read-only
    STATUS          current
    DESCRIPTION     "The value of the object tnSapTlsStpOperBpduEncap indicates
                     the operating encapsulation  type used on BPDUs sent out
                     and received on this SAP."
    ::= { tnSapTlsInfoEntry 16 }

tnSapTlsVpnId OBJECT-TYPE
    SYNTAX          VpnId
    MAX-ACCESS      read-only
    STATUS          current
    DESCRIPTION     "The value of the object tnSapTlsVpnId indicates the VPN ID
                     of the associated service."
    ::= { tnSapTlsInfoEntry 17 }

tnSapTlsCustId OBJECT-TYPE
    SYNTAX          TmnxCustId
    MAX-ACCESS      read-only
    STATUS          current
    DESCRIPTION     "The Customer ID of the associated service."
    ::= { tnSapTlsInfoEntry 18 }

tnSapTlsMacAddressLimit OBJECT-TYPE
    SYNTAX          Integer32(0..511999)
    MAX-ACCESS      read-write
    STATUS          current
    DESCRIPTION     "The value of the object tnSapTlsMacAddressLimit specifies
                     the maximum number of learned and static entries allowed
                     in the FDB of this SAP. The value 0 means: no limit for
                     this SAP.

                     The maximum value of tnSapTlsMacAddressLimit is '511999',
                     when the the value of
                     TIMETRA-CHASSIS-MIB::tmnxChassisOperMode is 'd'.

                     The maximum value of tnSapTlsMacAddressLimit is '196607',
                     when the the value of
                     TIMETRA-CHASSIS-MIB::tmnxChassisOperMode is 'c'.

                     In other cases, the maximum value of
                     tnSapTlsMacAddressLimit is '131071'."
    DEFVAL          { 0 }
    ::= { tnSapTlsInfoEntry 19 }

tnSapTlsNumMacAddresses OBJECT-TYPE
    SYNTAX          Integer32
    MAX-ACCESS      read-only
    STATUS          current
    DESCRIPTION     "The value of the object tnSapTlsNumMacAddresses indicates
                     the number of MAC addresses  currently present in the FDB
                     that belong to this  SAP  (Both  learned and static MAC
                     addresses are counted)."
    ::= { tnSapTlsInfoEntry 20 }

tnSapTlsNumStaticMacAddresses OBJECT-TYPE
    SYNTAX          Integer32
    MAX-ACCESS      read-only
    STATUS          current
    DESCRIPTION     "The value of the object tnSapTlsNumStaticMacAddresses
                     indicates the number of static MAC addresses currently
                     present in the FDB that belong to this SAP."
    ::= { tnSapTlsInfoEntry 21 }

tnSapTlsMacLearning OBJECT-TYPE
    SYNTAX          TmnxEnabledDisabled
    MAX-ACCESS      read-write
    STATUS          current
    DESCRIPTION     "The value of the object tnSapTlsMacLearning specifies
                     whether the MAC learning process  is enabled for this SAP.
                     The value is ignored if MAC learning is disabled on
                     service level."
    DEFVAL          { enabled }
    ::= { tnSapTlsInfoEntry 22 }

tnSapTlsMacAgeing OBJECT-TYPE
    SYNTAX          TmnxEnabledDisabled
    MAX-ACCESS      read-write
    STATUS          current
    DESCRIPTION     "The value of the object tnSapTlsMacAgeing specifies whether
                     the MAC aging process  is enabled for this SAP. the value
                     is ignored if MAC aging is disabled on service level."
    DEFVAL          { enabled }
    ::= { tnSapTlsInfoEntry 23 }

tnSapTlsStpOperEdge OBJECT-TYPE
    SYNTAX          TruthValue
    MAX-ACCESS      read-only
    STATUS          current
    DESCRIPTION     "The value of the object tnSapTlsStpOperEdge indicates the
                     operational value of the Edge Port parameter. The object
                     is initialized to the value of tnSapTlsStpRapidStart and is
                     set FALSE on reception of a BPDU."
    REFERENCE
                    "IEEE 802.1t clause 14.8.2, 18.3.4"
    ::= { tnSapTlsInfoEntry 24 }

tnSapTlsStpAdminPointToPoint OBJECT-TYPE
    SYNTAX          INTEGER {
                        forceTrue  (0),
                        forceFalse (1)
                    }
    MAX-ACCESS      read-write
    STATUS          current
    DESCRIPTION     "The value of the object tnSapTlsStpAdminPointToPoint
                     specifies the administrative point-to-point  status  of
                     the LAN segment attached to this  tnSap. The value
                     'forceTrue' means that this port should  always  be
                     treated as if it is connected to a point-to-point link.
                     The value of 'forceFalse' means that this port should
                     be treated as having a shared media connection."
    REFERENCE
                    "IEEE 802.1w clause 6.4.3, 6.5, 14.8.2"
    DEFVAL          { forceTrue }
    ::= { tnSapTlsInfoEntry 25 }

tnSapTlsStpPortRole OBJECT-TYPE
    SYNTAX          StpPortRole
    MAX-ACCESS      read-only
    STATUS          current
    DESCRIPTION     "tnSapTlsStpPortRole indicates the current role of the
                     tnSap as defined by the Rapid Spanning Tree Protocol."
    ::= { tnSapTlsInfoEntry 26 }

tnSapTlsStpAutoEdge OBJECT-TYPE
    SYNTAX          TmnxEnabledDisabled
    MAX-ACCESS      read-write
    STATUS          current
    DESCRIPTION     "tnSapTlsStpAutoEdge specifies whether this SAP
                     is enabled for auto-edge detection as defined by Rapid
                     Spanning Tree Protocol."
    DEFVAL          { enabled }
    ::= { tnSapTlsInfoEntry 27 }

tnSapTlsStpOperProtocol OBJECT-TYPE
    SYNTAX          StpProtocol
    MAX-ACCESS      read-only
    STATUS          current
    DESCRIPTION     "tnSapTlsStpOperProtocol indicates whether stp, rstp or
                     mstp is  running  on this SAP. If the protocol is not
                     enabled  on  this  SAP,  the  value  notApplicable  is
                     returned."
    ::= { tnSapTlsInfoEntry 28 }

tnSapTlsStpInRstBpdus OBJECT-TYPE
    SYNTAX          Gauge32
    MAX-ACCESS      read-only
    STATUS          current
    DESCRIPTION     "The value of the object  tnSapTlsStpInRstBpdus indicates
                     the number of Rapid Spanning Tree (RST) BPDUs received on
                     this SAP."
    ::= { tnSapTlsInfoEntry 29 }

tnSapTlsStpOutRstBpdus OBJECT-TYPE
    SYNTAX          Gauge32
    MAX-ACCESS      read-only
    STATUS          current
    DESCRIPTION     "The value of the  object tnSapTlsStpOutRstBpdus indicates
                     the number of Rapid Spanning Tree (RST) BPDUs sent out on
                     this SAP."
    ::= { tnSapTlsInfoEntry 30 }

tnSapTlsLimitMacMove OBJECT-TYPE
    SYNTAX          TlsLimitMacMove
    MAX-ACCESS      read-write
    STATUS          current
    DESCRIPTION     "When tnSapTlsLimitMacMove value is set  to  'blockable'
                     the  agent will monitor the MAC relearn rate on this
                     SAP,  and it will  block  it  when the re-learn rate
                     specified  by  tnSvcTlsMacMoveMaxRate  is exceeded. When
                     the  value is  'nonBlockable'  this  SAP will not be
                     blocked,  and  another  blockable  SAP will be blocked
                     instead."
    DEFVAL          { blockable }
    ::= { tnSapTlsInfoEntry 31 }

-- tnSapTlsDhcpSnooping OBJECT-TYPE
--     SYNTAX          TmnxEnabledDisabled
--     MAX-ACCESS      read-write
--     STATUS          obsolete
--     DESCRIPTION     "The value of the object tnSapTlsDhcpSnooping specifies
--                      whether or not DHCP packets received on this SAP will be
--                      snooped. This object was made obsolete in the 3.0 release."
--     DEFVAL          { disabled }
--     ::= { tnSapTlsInfoEntry 32 }

tnSapTlsMacPinning OBJECT-TYPE
    SYNTAX          TmnxEnabledDisabled
    MAX-ACCESS      read-write
    STATUS          current
    DESCRIPTION     "The value of the object tnSapTlsMacPinning specifies whether
                     or not MAC address pinning is active on this SAP. The
                     value will be set by default to disabled. However for a
                     SAP that belongs to a residential SHG, the value is set to
                     enabled by the system, and cannot be altered by the
                     operator. Setting the value to enable disables
                     re-learning of MAC addresses on other SAPs or
                     spoke-SDPs within the same VPLS; the MAC address will
                     hence remain attached to the SAP for the duration of
                     its age-timer. This object has effect only for MAC
                     addresses learned via the normal MAC learning
                     process, and not for entries learned via DHCP."
    ::= { tnSapTlsInfoEntry 33 }

tnSapTlsDiscardUnknownSource OBJECT-TYPE
    SYNTAX          TmnxEnabledDisabled
    MAX-ACCESS      read-write
    STATUS          current
    DESCRIPTION     "with   the object tnSapTlsMacAddressLimit a limit can be
                     configured  for  the  max number of MAC addresses that
                     will  be learned on this  SAP.  When  this limit is
                     reached, packets with unknown source MAC address are
                     forwarded by default. By setting
                     tnSapTlsDiscardUnknownSource  to enabled, packets with
                     unknown source MAC will be dropped in stead."
    DEFVAL          { disabled }
    ::= { tnSapTlsInfoEntry 34 }

tnSapTlsMvplsPruneState OBJECT-TYPE
    SYNTAX          MvplsPruneState
    MAX-ACCESS      read-only
    STATUS          current
    DESCRIPTION     "The value of tnSapTlsMvplsPruneState indicates the mVPLS
                     prune state of the SAP. The object will be set to
                     notApplicable if the SAP is not managed by a mVPLS. If
                     the SAP is managed the state reflects whether or not
                     the SAP is pruned by the STP instance running in the
                     mVPLS instance."
    ::= { tnSapTlsInfoEntry 35 }

tnSapTlsMvplsMgmtService OBJECT-TYPE
    SYNTAX          TmnxServId
    MAX-ACCESS      read-only
    STATUS          current
    DESCRIPTION     "The value of tnSapTlsMvplsMgmtService indicates the
                     service Id of the service where the STP instance is
                     running that is managing this SAP. This object is
                     only valid if tnSapTlsMvplsPruneState is different from
                     notApplicable."
    ::= { tnSapTlsInfoEntry 36 }

tnSapTlsMvplsMgmtPortId OBJECT-TYPE
    SYNTAX          TmnxPortID
    MAX-ACCESS      read-only
    STATUS          current
    DESCRIPTION     "The value of tnSapTlsMvplsMgmtPortId indicates the SAP
                     port Id of the SAP in the mVPLS instance specified in
                     tnSapTlsMvplsMgmtService that is controlling this SAP.
                     This object is only valid if tnSapTlsMvplsPruneState is
                     different from notApplicable."
    ::= { tnSapTlsInfoEntry 37 }

tnSapTlsMvplsMgmtEncapValue OBJECT-TYPE
    SYNTAX          TmnxEncapVal
    MAX-ACCESS      read-only
    STATUS          current
    DESCRIPTION     "The value of tnSapTlsMvplsMgmtEncapValue indicates the
                     SAP Encap value of the SAP in the mVPLS instance
                     specified in tnSapTlsMvplsMgmtService that is
                     controlling this SAP. This object is only valid if
                     tnSapTlsMvplsPruneState is different from notApplicable."
    ::= { tnSapTlsInfoEntry 38 }

tnSapTlsArpReplyAgent OBJECT-TYPE
    SYNTAX          INTEGER {
                        disabled               (1),
                        enabled                (2),
                        enabledWithSubscrIdent (3)
                    }
    MAX-ACCESS      read-write
    STATUS          current
    DESCRIPTION     "The value of the object tnSapTlsArpReplyAgent specifies
                     the status of the special ARP response mechanism in the
                     system for ARP requests destined to static or dynamic hosts
                     associated with this SAP.
                     disabled: the ARP reply function is not operational
                     enabled: the ARP reply function is enabled without
                              subscriber identification.
                     enabledWithSubscrIdent: the ARP reply function is enabled
                                             with subscriber identification."
    DEFVAL          { disabled }
    ::= { tnSapTlsInfoEntry 39 }

tnSapTlsStpException OBJECT-TYPE
    SYNTAX          StpExceptionCondition
    MAX-ACCESS      read-only
    STATUS          current
    DESCRIPTION     "The value of the object tnSapTlsStpException indicates
                     whether an STP exception condition is present on this
                     Sap.
                     - none : no exception condition found.
                     - oneWayCommuniation : The neighbor RSTP peer on this link
                                            is not able to detect our presence.
                     - downstreamLoopDetected :A loop is detected on this link."
    ::= { tnSapTlsInfoEntry 40 }

tnSapTlsAuthenticationPolicy OBJECT-TYPE
    SYNTAX          TPolicyStatementNameOrEmpty
    MAX-ACCESS      read-write
    STATUS          current
    DESCRIPTION     "The value of the object tnSapTlsAuthenticationPolicy specifies
                     which subscriber authentication policy  must  be applied when
                     a DHCP msg is received on the interface.  The  authentication
                     policies  must be defined  in  tmnxSubAuthPlcyTable. The policy
                     will only be applied when tnSapTlsDhcpSnoop is enabled."
    DEFVAL          { ''H }
    ::= { tnSapTlsInfoEntry 41 }

tnSapTlsL2ptTermination OBJECT-TYPE
    SYNTAX          TmnxEnabledDisabled
    MAX-ACCESS      read-write
    STATUS          current
    DESCRIPTION     "The value of the object tnSapTlsL2ptTermination specifies
                     whether received Layer 2 Protocol Tunnel (L2PT) pdu's
                     are terminated on this port or tnSap."
    DEFVAL          { disabled }
    ::= { tnSapTlsInfoEntry 42 }

tnSapTlsBpduTranslation OBJECT-TYPE
    SYNTAX          TlsBpduTranslation
    MAX-ACCESS      read-write
    STATUS          current
    DESCRIPTION     "The value of the object tnSapTlsBpduTranslation specifies
                     whether received L2 Protocol Tunnel pdu's are
                     translated before being sent out on this port or tnSap."
    DEFVAL          { disabled }
    ::= { tnSapTlsInfoEntry 43 }

tnSapTlsStpRootGuard OBJECT-TYPE
    SYNTAX          TruthValue
    MAX-ACCESS      read-write
    STATUS          current
    DESCRIPTION     "The value of the object tnSapTlsStpRootGuard specifies
                     whether this port is allowed to become STP root port.
                     It corresponds to the parameter 'restrictedRole' in 802.1Q.
                     If set, it can cause lack of spanning tree connectivity."
    DEFVAL          { false }
    ::= { tnSapTlsInfoEntry 44 }

tnSapTlsStpInsideRegion OBJECT-TYPE
    SYNTAX          TruthValue
    MAX-ACCESS      read-only
    STATUS          current
    DESCRIPTION     "The value of the object tnSapTlsStpInsideRegion indicates
                     whether the network connected to the SAP is in the same
                     MST region. It corresponds to the parameter 'infoInternal'
                     in 802.1Q."
    ::= { tnSapTlsInfoEntry 45 }

tnSapTlsEgressMcastGroup OBJECT-TYPE
    SYNTAX          TNamedItemOrEmpty
    MAX-ACCESS      read-write
    STATUS          current
    DESCRIPTION     "The value of the object tnSapTlsEgressMcastGroup specifies
                     the Egress Multicast Group this SAP belongs to."
    DEFVAL          { "" }
    ::= { tnSapTlsInfoEntry 46 }

tnSapTlsStpInMstBpdus OBJECT-TYPE
    SYNTAX          Gauge32
    MAX-ACCESS      read-only
    STATUS          current
    DESCRIPTION     "The value of the object tnSapTlsStpInMstBpdus indicates
                     the number of Multiple Spanning Tree (MST) BPDUs received
                     on this SAP."
    ::= { tnSapTlsInfoEntry 47 }

tnSapTlsStpOutMstBpdus OBJECT-TYPE
    SYNTAX          Gauge32
    MAX-ACCESS      read-only
    STATUS          current
    DESCRIPTION     "The value of the object tnSapTlsStpOutMstBpdus indicates
                     the number of Multiple Spanning Tree (MST) BPDUs sent out
                     on this SAP."
    ::= { tnSapTlsInfoEntry 48 }

tnSapTlsRestProtSrcMac OBJECT-TYPE
    SYNTAX          TruthValue
    MAX-ACCESS      read-write
    STATUS          current
    DESCRIPTION     "The value of the object tnSapTlsRestProtSrcMac specifies
                     how the agent will handle relearn requests for protected
                     MAC addresses. When the value of this object is 'true'
                     requests to relearn a protected MAC address will be
                     ignored.
                     In addition, if the value of tnSapTlsRestProtSrcMacAction
                     is 'disable', then the SAP where the protected source
                     MAC was seen will be brought operationally down."
    DEFVAL          { false }
    ::= { tnSapTlsInfoEntry 49 }

tnSapTlsRestUnprotDstMac OBJECT-TYPE
    SYNTAX          TruthValue
    MAX-ACCESS      read-write
    STATUS          current
    DESCRIPTION     "The value of the object tnSapTlsRestUnprotDstMac specifies
                     how the system will forward packets destined to an
                     unprotected MAC address. When the value of this object is
                     'true' packets destined to an unprotected MAC address
                     will be dropped."
    DEFVAL          { false }
    ::= { tnSapTlsInfoEntry 50 }

tnSapTlsStpRxdDesigBridge OBJECT-TYPE
    SYNTAX          BridgeId
    MAX-ACCESS      read-only
    STATUS          current
    DESCRIPTION     "The value of the object tnSapTlsStpRxdDesigBridge
                     indicates  the designated Bridge Identifier in the last
                     BPDU which was received on this SAP. It identifies
                     which bridge is connected to the SAP."
    ::= { tnSapTlsInfoEntry 51 }

tnSapTlsStpRootGuardViolation OBJECT-TYPE
    SYNTAX          TruthValue
    MAX-ACCESS      read-only
    STATUS          current
    DESCRIPTION     "The value of the object tnSapTlsStpRootGuardViolation
                     indicates whether there is a root-guard violation at the
                     present time. This can only happen when tnSapTlsStpRootGuard
                     is set to true."
    ::= { tnSapTlsInfoEntry 52 }


tnSapTlsShcvAction OBJECT-TYPE
    SYNTAX          INTEGER {
                         alarm  (1),
                         remove (2)
                    }
    MAX-ACCESS      read-write
    STATUS          current
    DESCRIPTION     "The value of the object tnSapTlsShcvAction
                     indicates whether any action should be triggered when
                     the connectivity check fails."
    DEFVAL          { alarm }
    ::= { tnSapTlsInfoEntry 53 }


tnSapTlsShcvSrcIp OBJECT-TYPE
    SYNTAX          IpAddress
    MAX-ACCESS      read-write
    STATUS          current
    DESCRIPTION     "The value of the object tnSapTlsShcvSrcIp
                     specifies the source IP address used when doing the
                     connectivity check. The value 0.0.0.0 indicates that
                     no host IP address is specified."
    ::= { tnSapTlsInfoEntry 54 }

tnSapTlsShcvSrcMac OBJECT-TYPE
    SYNTAX          MacAddress
    MAX-ACCESS      read-write
    STATUS          current
    DESCRIPTION     "The value of the object tnSapTlsShcvSrcMac
                     specifies the MAC address used when doing the connectivity
                     check. The value 0:0:0:0:0:0 indicates that no host MAC
                     address is specified."
    ::= { tnSapTlsInfoEntry 55 }

tnSapTlsShcvInterval OBJECT-TYPE
    SYNTAX          Unsigned32 (0..6000)
    UNITS           "minutes"
    MAX-ACCESS      read-write
    STATUS          current
    DESCRIPTION     "The value of the object tnSapTlsShcvInterval specifies
                     the interval in minutes between connectivity checks.
                     Zero means no connectivity checking."
    DEFVAL          { 0 }
    ::= { tnSapTlsInfoEntry 56 }

tnSapTlsMvplsMgmtMsti OBJECT-TYPE
    SYNTAX          MstiInstanceIdOrZero
    MAX-ACCESS      read-only
    STATUS          current
    DESCRIPTION     "The value of the object tnSapTlsMvplsMgmtMsti indicates the
                     MST-instance in the mVPLS instance specified in
                     tnSapTlsMvplsMgmtService that is controlling this SAP. A
                     value of 0 indicates the CIST.
                     This object is only valid if tnSapTlsMvplsPruneState is
                     different from notApplicable."
    ::= { tnSapTlsInfoEntry 57 }

tnSapTlsMacMoveNextUpTime OBJECT-TYPE
    SYNTAX          Unsigned32
    UNITS           "seconds"
    MAX-ACCESS      read-only
    STATUS          current
    DESCRIPTION     "The value of the object tnSapTlsMacMoveNextUpTime counts down
                     the time in seconds until a SAP that has been brought down
                     due to exceeding the TLS tnSvcTlsMacMoveMaxRate, tnSapOperFlags
                     'relearnLimitExceeded', is automatically brought up again.

                     When this value is 0xffff, the SAP will never be
                     automatically brought up.

                     When tnSapOperStatus is 'up', this object counts down the
                     time in seconds until the value of
                     tnSapTlsMacMoveRateExcdLeft is reset."
    ::= { tnSapTlsInfoEntry 58 }

tnSapTlsMacMoveRateExcdLeft   OBJECT-TYPE
    SYNTAX          Unsigned32
    MAX-ACCESS      read-only
    STATUS          current
    DESCRIPTION     "The value of the object tnSapTlsMacMoveRateExcdLeft
                     counts down the number of times this SAP can exceed the
                     TLS tnSvcTlsMacMoveMaxRate and still be automatically
                     brought up."
    ::= { tnSapTlsInfoEntry 59 }

tnSapTlsRestProtSrcMacAction OBJECT-TYPE
    SYNTAX          INTEGER {
                        disable    (1),
                        alarm-only (2)
                    }
    MAX-ACCESS      read-write
    STATUS          current
    DESCRIPTION     "The value of the object tnSapTlsRestProtSrcMacAction
                     indicates the action to take whenever a relearn request
                     for a protected MAC is received on a restricted SAP.
                     When the value of this object is 'disable' the SAP
                     will be placed in the operational down state, with the
                     operating flag 'recProtSrcMac' set. When the value of
                     this object is 'alarm-only', the SAP will be left up
                     and only a notification, tnSapReceivedProtSrcMac,  will be
                     generated."
    DEFVAL          { disable }
    ::= { tnSapTlsInfoEntry 60 }

tnSapTlsL2ptForceBoundary OBJECT-TYPE
    SYNTAX          TruthValue
    MAX-ACCESS      read-write
    STATUS          current
    DESCRIPTION     "The value of tnSapTlsL2ptForceBoundary specifies if
                     tnSapTlsL2ptTermination is enforced for its managed SAP's.
                     Setting the value of the object tnSapTlsL2ptForceBoundary of
                     a SAP in a Management VPLS to `true' forces all its
                     managed SAP's to have tnSapTlsL2ptTermination enabled. This
                     value can only be `true' if the SAP belongs to a
                     management VPLS.
                     If this SAP has managed SAP's already with
                     tnSapTlsL2ptTermination disabled, it is not allowed
                     to set tnSapTlsL2ptForceBoundary to `true'."
    DEFVAL          { false }
    ::= { tnSapTlsInfoEntry 61 }

tnSapTlsLimitMacMoveLevel OBJECT-TYPE
    SYNTAX          TlsLimitMacMoveLevel
    MAX-ACCESS      read-write
    STATUS          current
    DESCRIPTION     "The value of the object tnSapTlsLimitMacMoveLevel
                     specifies the hierarchy in which SAPs are
                     blocked when a MAC-move limit is exceeded. When a MAC is
                     moving among multiple SAPs or spoke-SDPs, the SAP bind
                     or spoke-SDP bind with the lower level is blocked first.
                     (tertiary is the lowest)"
    DEFVAL          { tertiary }
    ::= { tnSapTlsInfoEntry 62 }

tnSapTlsBpduTransOper OBJECT-TYPE
    SYNTAX          INTEGER {
                        undefined (1),
                        disabled  (2),
                        pvst      (3),
                        stp       (4),
                        pvst-rw   (5)
                    }
    MAX-ACCESS      read-only
    STATUS          current
    DESCRIPTION     "The value of the object tnSapTlsBpduTransOper indicates
                     the operational bpdu encapsulation used for BPDU
                     translated frames."
    ::= { tnSapTlsInfoEntry 63 }

tnSapTlsDefMtnSapPolicy OBJECT-TYPE
    SYNTAX          TPolicyStatementNameOrEmpty
    MAX-ACCESS      read-write
    STATUS          current
    DESCRIPTION     "The value of tnSapTlsDefMtnSapPolicy specifies the
                     default Managed SAP policy to use to create
                     Managed SAPs when the response from the Radius
                     server does not specify a Managed SAP policy.

                     The value of tnSapTlsDefMtnSapPolicy is only valid for
                     a SAP with a tnSapSubType value of 'capture'.
                     If the value is set to a non-empty string for a
                     SAP with a tnSapSubType value other than 'capture',
                     an 'inconsistentValue' error will be returned.

                     The Managed SAP policy must be defined in
                     tnMtnSapPlcyTable, otherwise an 'inconsistentValue'
                     error will be returned."
    DEFVAL         { "" }
    ::= { tnSapTlsInfoEntry 64 }

tnSapTlsL2ptProtocols OBJECT-TYPE
    SYNTAX          L2ptProtocols
    MAX-ACCESS      read-write
    STATUS          current
    DESCRIPTION     "The value of the object tnSapTlsL2ptTermination specifies
                     which L2 Protocol Tunnel pdu's are terminated
                     on this port or tnSap."
    DEFVAL          { { stp } }
    ::= { tnSapTlsInfoEntry 65 }

tnSapTlsL2ptForceProtocols OBJECT-TYPE
    SYNTAX          L2ptProtocols
    MAX-ACCESS      read-write
    STATUS          current
    DESCRIPTION     "The value of the object tnSapTlsL2ptForceProtocols specifies
                     which L2 Protocol Tunnel pdu's must be terminated by
                     SAP's managed by this SAP.
                     This object is only relevant if the value of the object
                     tnSapTlsL2ptForceBoundary is 'true'.
                     For every SAP managed by this SAP, each L2 protocol
                     specified by tnSapTlsL2ptForceProtocols must be terminated,
                     while other L2 protocols may or may not be terminated,
                     depending on the value of tnSapTlsL2ptProtocols of that
                     managed SAP."
    DEFVAL          { { stp } }
    ::= { tnSapTlsInfoEntry 66 }

tnSapTlsPppoeMtnSapTrigger OBJECT-TYPE
    SYNTAX          TruthValue
    MAX-ACCESS      read-write
    STATUS          current
    DESCRIPTION     "The value of tnSapTlsPppoeMtnSapTrigger specifies whether
                     the receipt of PPPoE trigger packets on a VPLS SAP
                     with a tnSapSubType value of 'capture' will result in
                     a Radius authentication that will provide a service
                     context and the creation of a SAP with a tnSapSubType
                     value of 'managed'.

                     An attempt to set the value tnSapTlsPppoeMtnSapTrigger to
                     'true' on a SAP with tnSapSubType other than 'capture'
                     will return an 'inconsistentValue' error."
    DEFVAL         { false }
    ::= { tnSapTlsInfoEntry 67 }

tnSapTlsDhcpMtnSapTrigger OBJECT-TYPE
    SYNTAX          TruthValue
    MAX-ACCESS      read-write
    STATUS          current
    DESCRIPTION     "The value of tnSapTlsDhcpMtnSapTrigger specifies whether
                     the receipt of DHCP trigger packets on this VPLS SAP
                     with a tnSapSubType value of 'capture' will result in
                     a Radius authentication that will provide a service
                     context and the creation of a SAP with a tnSapSubType
                     value of 'managed'.

                     An attempt to set the value tnSapTlsDhcpMtnSapTrigger to
                     'true' on a SAP with tnSapSubType other than 'capture'
                     will return an 'inconsistentValue' error."
    DEFVAL         { false }
    ::= { tnSapTlsInfoEntry 68 }

tnSapTlsMrpJoinTime OBJECT-TYPE
    SYNTAX          Unsigned32 (1..10)
    UNITS           "deci-seconds"
    MAX-ACCESS      read-write
    STATUS          current
    DESCRIPTION     "The value of tnSapTlsMrpJoinTime specifies a timer value in
                    10ths of seconds which determines the maximum rate at
                    which attribute join messages can be sent on the SAP."
    DEFVAL         { 2 }
    ::= { tnSapTlsInfoEntry 69 }

tnSapTlsMrpLeaveTime OBJECT-TYPE
    SYNTAX          Unsigned32 (30..60)
    UNITS           "deci-seconds"
    MAX-ACCESS      read-write
    STATUS          current
    DESCRIPTION     "The value of tnSapTlsMrpLeaveTime specifies a timer value in
                    10ths of seconds which determines the amount of time a
                    registered attribute is held in leave state before the
                    registration is removed."
    DEFVAL         { 30 }
    ::= { tnSapTlsInfoEntry 70 }

tnSapTlsMrpLeaveAllTime OBJECT-TYPE
    SYNTAX          Unsigned32 (60..300)
    UNITS           "deci-seconds"
    MAX-ACCESS      read-write
    STATUS          current
    DESCRIPTION     "The value of tnSapTlsMrpLeaveAllTime specifies the a timer
                    value in 10ths of seconds which determines the frequency
                    where all attribute declarations on the SAP are all
                    refreshed."
    DEFVAL         { 100 }
    ::= { tnSapTlsInfoEntry 71 }

tnSapTlsMrpPeriodicTime OBJECT-TYPE
    SYNTAX          Unsigned32 (10..100)
    UNITS           "deci-seconds"
    MAX-ACCESS      read-write
    STATUS          current
    DESCRIPTION     "The value of tnSapTlsMrpPeriodicTime specifies a timer value
                    in 10ths of seconds which determines the frequency of
                    re-transmission of attribute declarations."
    DEFVAL         { 10 }
    ::= { tnSapTlsInfoEntry 72 }

tnSapTlsMrpPeriodicEnabled OBJECT-TYPE
    SYNTAX          TruthValue
    MAX-ACCESS      read-write
    STATUS          current
    DESCRIPTION     "The value of tnSapTlsMrpPeriodicEnabled specifies whether
                    re-transmission of attribute declarations is enabled."
    DEFVAL         { false }
    ::= { tnSapTlsInfoEntry 73 }

tnSapTlsPppoePolicy OBJECT-TYPE
    SYNTAX          TNamedItemOrEmpty
    MAX-ACCESS      read-write
    STATUS          current
    DESCRIPTION     "The value of tnSapTlsPppoePolicy specifies the PPPoE
                     policy (defined in TIMETRA-PPPOE-MIB::tmnxPppoePlcyTable)
                     to use to create Managed SAPs via PPPoE with PAP/CHAP
                     authentication.

                     The value of tnSapTlsPppoePolicy is only valid for a SAP
                     with a tnSapSubType value of 'capture'. If the value is set
                     to a  non-empty string for a SAP with a tnSapSubType value
                     other than 'capture', an 'inconsistentValue' error will
                     be returned."
    DEFVAL         { "" }
    ::= { tnSapTlsInfoEntry 74 }

tnSapTlsArpMsapTrigger OBJECT-TYPE
    SYNTAX          TruthValue
    MAX-ACCESS      read-write
    STATUS          current
    DESCRIPTION     "The value of tnSapTlsArpMsapTrigger specifies whether
                     the receipt of ARP trigger packets on this VPLS SAP
                     with a tnSapSubType value of 'capture' will result in
                     a Radius authentication that will provide a service
                     context and the creation of a SAP with a tnSapSubType
                     value of 'managed'.

                     An attempt to set the value tnSapTlsArpMsapTrigger to
                     'true' on a SAP with tnSapSubType other than 'capture'
                     will return an 'inconsistentValue' error."
    DEFVAL         { false }
    ::= { tnSapTlsInfoEntry 75 }

tnSapTlsInTcBitBpdus OBJECT-TYPE
    SYNTAX          Counter32
    MAX-ACCESS      read-only
    STATUS          current
    DESCRIPTION     "The value of the object  sapTlsInTcBitBpdus indicates the
                     number of BPDUs received on this SAP
                     with the Topology Change bit set."
    ::= { tnSapTlsInfoEntry 76 }

tnSapTlsOutTcBitBpdus OBJECT-TYPE
    SYNTAX          Counter32
    MAX-ACCESS      read-only
    STATUS          current
    DESCRIPTION     "The value of the object  sapTlsOutTcBitBpdus indicates the
                     number of BPDUs sent out this SAP
                     with the Topology Change bit set."
    ::= { tnSapTlsInfoEntry 77 }

tnSapTlsShcvRetryTimeout OBJECT-TYPE
    SYNTAX          Unsigned32 (10..60)
    UNITS           "seconds"
    MAX-ACCESS      read-write
    STATUS          current
    DESCRIPTION     "The value of the object sapTlsShcvRetryTimeout specifies
                     the timeout in seconds before a connectivity check
                     retransmission."
    DEFVAL          { 10 }
    ::= { tnSapTlsInfoEntry 81 }

tnSapTlsShcvRetryCount OBJECT-TYPE
    SYNTAX          Unsigned32 (2..29)
    MAX-ACCESS      read-write
    STATUS          current
    DESCRIPTION     "The value of the object sapTlsShcvRetryCount specifies
                     the number of connectivity check retransmissions.

                     Setting the value to n specifies that, for any given host,
                     at most (n+1) probes are done each interval,
                     and (n+1) missed replies are considered as a connectivity
                     failure."
    DEFVAL          { 2 }
    ::= { tnSapTlsInfoEntry 82 }

tnSapTlsFdbTableSizeProfId OBJECT-TYPE
    SYNTAX          TFdbTableSizeProfileID
    MAX-ACCESS      read-write
    STATUS          deprecated
    DESCRIPTION     "The value of the object tnSapTlsFdbTableSizeProfId specifies
                     the row index in the tnPacketSwitchFdbTableSizeProfileTable
                     corresponding to this Fdb Table Size Profile, or one if no
                     profile is specified."
    DEFVAL          { 1 }
    ::= { tnSapTlsInfoEntry 83 }

-- ---------------------------------------------------------------------
-- ATM SAP Table
--
--
--  Sparse Dependent Extention of the tnSapBaseInfoTable.
--
--  The same indexes are used for both the base table, tnSapBaseInfoTable,
--  and the sparse dependent table, tnSapAtmInfoTable.
--
--  This in effect extends the tnSapBaseInfoTable with additional columns.
--  Rows are created in the tnSapAtmInfoTable only for those entries
--  in the tnSapBaseInfoTable that are created on a port that 'atmEncap' set
--- for port encapsulation.
--
--  Deletion of a row in the tnSapBaseInfoTable results in the
--  same fate for the row in the tnSapAtmInfoTable.
-- ---------------------------------------------------------------------
-- tnSapAtmInfoTable OBJECT-TYPE
--     SYNTAX          SEQUENCE OF SapAtmInfoEntry
--     MAX-ACCESS      not-accessible
--     STATUS          current
--     DESCRIPTION     "A table that contains ATM SAP information."
--     ::= { tnSapObjs 4 }
--
-- tnSapAtmInfoEntry OBJECT-TYPE
--     SYNTAX          SapAtmInfoEntry
--     MAX-ACCESS      not-accessible
--     STATUS          current
--     DESCRIPTION     "Information about a specific ATM SAP."
--     INDEX           { tnSysSwitchId,  tnSvcId, tnSapPortId, tnSapEncapValue }
--     ::= { tnSapAtmInfoTable 1 }
--
-- SapAtmInfoEntry ::=
--     SEQUENCE {
--         tnSapAtmEncapsulation             INTEGER,
-- ==         tnSapAtmIngressTrafficDescIndex   AtmTrafficDescrParamIndex,
-- ==         tnSapAtmEgressTrafficDescIndex    AtmTrafficDescrParamIndex,
--         tnSapAtmOamAlarmCellHandling      ServiceAdminStatus,
--         tnSapAtmOamTerminate              ServiceAdminStatus,
--         tnSapAtmOamPeriodicLoopback       ServiceAdminStatus,
--         tnSapAtmLLFAdminStatus            ServiceAdminStatus,
--         tnSapAtmLLFOperStatus             INTEGER
--   }
--
-- tnSapAtmEncapsulation OBJECT-TYPE
--     SYNTAX          INTEGER {
--                          vcMultiplexRoutedProtocol      (1),
--                          vcMultiplexBridgedProtocol8023 (2),
--                          llcSnapRoutedProtocol          (7),
--                          multiprotocolFrameRelaySscs    (8),
--                          unknown                        (10),
--                          llcSnapBridgedProtocol8023     (11)
--                      }
--     MAX-ACCESS       read-write
--     STATUS           current
--     DESCRIPTION      "This object specifies the data encapsulation used
--                       over the AAL5 SSCS layer.  The definition references
--                       RFC 2684 Multiprotocol Encapsulation over ATM AAL5
--                       and to the ATM Forum LAN Emulation specification."
--     DEFVAL           { llcSnapRoutedProtocol }
--     ::= { tnSapAtmInfoEntry 1 }
--
-- == tnSapAtmIngressTrafficDescIndex OBJECT-TYPE
-- ==     SYNTAX           AtmTrafficDescrParamIndex(1..1000)
-- ==     MAX-ACCESS       read-write
-- ==     STATUS           current
-- ==     DESCRIPTION      "This object specifies the index of the ATM traffic
-- ==                       descriptor in the ATM traffic data encapsulation used
-- ==                       in for the ingress direction over the AAL5 SSCS layer.
-- ==                       The definition references RFC 2684 Multiprotocol
-- ==                       Encapsulation over ATM AAL5 and to the ATM Forum LAN
-- ==                       Emulation specification."
-- ==     DEFVAL           { 1 }
-- ==     ::= { tnSapAtmInfoEntry 2 }
--
-- == tnSapAtmEgressTrafficDescIndex OBJECT-TYPE
-- ==     SYNTAX           AtmTrafficDescrParamIndex(1..1000)
-- ==     MAX-ACCESS       read-write
-- ==     STATUS           current
-- ==     DESCRIPTION      "This object specifies the index of the ATM traffic
-- ==                       descriptor in the ATM traffic data encapsulation used
-- ==                       in for the egress direction over the AAL5 SSCS layer.
-- ==                       The definition references RFC 2684 Multiprotocol
-- ==                       Encapsulation over ATM AAL5 and to the ATM Forum LAN
-- ==                       Emulation specification."
-- ==     DEFVAL           { 1 }
-- ==     ::= { tnSapAtmInfoEntry 3 }
--
-- tnSapAtmOamAlarmCellHandling OBJECT-TYPE
--     SYNTAX           ServiceAdminStatus
--     MAX-ACCESS       read-write
--     STATUS           current
--     DESCRIPTION      "A value of up specifies that the OAM status of a pvc
--                       affects  the  tnSap  operational  status and OAM AIS/RDI
--                       cell generation upon a tnSap operational status of down.
--                       A value of down specifies that the OAM status of a pvc
--                       will   not   affect  the  operational  status  of  the
--                       associated   tnSap   and   no   OAM  AIS/RDI  cells  are
--                       generated."
--     DEFVAL          { up }
--     ::= { tnSapAtmInfoEntry 4 }
--
-- tnSapAtmOamTerminate OBJECT-TYPE
--     SYNTAX           ServiceAdminStatus
--     MAX-ACCESS       read-write
--     STATUS           current
--     DESCRIPTION      "The tnSapAtmOamTerminate object specifies whether this
--                       SAP will act as an OAM termination point.
--                       If enabled, OAM cells will be sunk by the SAP and can
--                       affect the SAP's operational status (if
--                       tnSapAtmOamAlarmCellHandling is also enabled). Otherwise
--                       the OAM cells will be passed into the APIPE service.
--                       This object is only configurable for ATM SAPs that are
--                       part of an APIPE service SDU or VCC mode. If the
--                       tnSapPortId belongs to an Multi-Chassis APS port, the
--                       default value is up."
--     DEFVAL           { down }
--     ::= { tnSapAtmInfoEntry 5 }
--
-- tnSapAtmOamPeriodicLoopback OBJECT-TYPE
--     SYNTAX           ServiceAdminStatus
--     MAX-ACCESS       read-write
--     STATUS           current
--     DESCRIPTION      "The tnSapAtmOamPeriodicLoopback object specifies whether
--                       this SAP will run periodic OAM loopbacks or not.  If
--                       enabled, an ATM OAM loopback cell will be transmitted
--                       every period as configured in tAtmSysOamLoopbackPeriod.
--                       If a response is not received and tAtmSysOamRetryDown
--                       consecutive retries also result in failure, the endpoint
--                       will transition to the eteAisLoc state.  Once in the
--                       eteAisLoc state, an ATM OAM loopback cell will be
--                       transmitted every period as configured in
--                       tAtmSysOamLoopbackPeriod. If a response is received for
--                       the periodic loopback and tAtmSysOamRetryUp consecutive
--                       retries also each receive a response, the endpoint will
--                       transition back to the up state.  This object is only
--                       configurable on IES or VPRN service endpoints."
--     DEFVAL           { down }
--     ::= { tnSapAtmInfoEntry 6 }
--
-- tnSapAtmLLFAdminStatus OBJECT-TYPE
--     SYNTAX          ServiceAdminStatus
--     MAX-ACCESS      read-write
--     STATUS          current
--     DESCRIPTION     "tnSapAtmLLFAdminStatus specifies whether or not Link-
--                     Loss Forwarding is enabled ('up'). When this object is set
--                     to 'up' the underlying port will be forced into the
--                     operationally 'down' state if the service is operationally
--                     'down', or any of the 'sdpBindPwPeerStatusBits' are set,
--                     and will set the underlying port's
--                     tmnxPortReasonDownFlags 'linklossFwd' bit. Setting
--                     this object to 'down' will clear the 'linklossFwd' reason.
--                     tnSapAtmLLFAdminStatus can only be enabled on tnSaps
--                     configured for an APIPE service using an
--                     port with the tmnxPortEncapType set to 'atmEncap' and
--                     tnSapEncapValue set for ATM ports."
--     DEFVAL          { down }
--     ::= { tnSapAtmInfoEntry 7 }
--
-- tnSapAtmLLFOperStatus OBJECT-TYPE
--     SYNTAX          INTEGER {
--                         fault (1),   == service is down or fault detected.
--                         clear (2)    == service is up and no fault detected.
--                     }
--     MAX-ACCESS      read-only
--     STATUS          current
--     DESCRIPTION     "tnSapAtmLLFOperStatus indicates whether or not the
--                     underlying port is forced operationally 'down' due to the
--                     service being operationally 'down' or an
--                     sdpBindPwPeerStatusBits bit is set.
--                     tnSapAtmLLFOperStatus is set to 'fault' when the
--                     tnSapAtmLLFAdminStatus is set to 'up,' and either a
--                     fault has occurred on the pseudo-wire, or the service is
--                     down, otherwise tnSapAtmLLFOperStatus is set to 'clear.'"
--     ::= { tnSapAtmInfoEntry 8 }

--
-- Dummy Scalar
--
tnSapScalar1 OBJECT-TYPE
    SYNTAX          Unsigned32
    MAX-ACCESS      read-only
    STATUS          current
    DESCRIPTION     "A dummy scalar that satisfies a SNMP get request
                     quickly when there is no 11QPE24 card provisioned.
                     Otherwise, it has to traverse the remaining 11QPE24
                     MIB to get to the next applicable item."
    ::= { tnSapObjs 5 }

-- ---------------------------------
-- Base SAP Statistics Table
-- ---------------------------------
tnSapBaseStatsTable OBJECT-TYPE
    SYNTAX          SEQUENCE OF TnSapBaseStatsEntry
    MAX-ACCESS      not-accessible
    STATUS          current
    DESCRIPTION     "A table that contains basic SAP statistics.
                     In the descriptions below 'Pchip' refers
                     to the Nokia 7x50 SR series Packet Processing
                     chip, while 'Qchip' refers to the Nokia 7x50
                     SR series QoS Queueing Engine chip."
    ::= { tnSapObjs 6 }

tnSapBaseStatsEntry OBJECT-TYPE
    SYNTAX          TnSapBaseStatsEntry
    MAX-ACCESS      not-accessible
    STATUS          current
    DESCRIPTION     "Basic statistics about a specific SAP."
    INDEX           { tnSysSwitchId, tnSvcId, tnSapPortId, tnSapEncapValue }
    ::= { tnSapBaseStatsTable 1 }

TnSapBaseStatsEntry ::=
    SEQUENCE {
        tnSapBaseStatsIngressPchipDroppedPackets          Counter64,
        tnSapBaseStatsIngressPchipDroppedOctets           Counter64,
        tnSapBaseStatsIngressPchipOfferedHiPrioPackets    Counter64,
        tnSapBaseStatsIngressPchipOfferedHiPrioOctets     Counter64,
        tnSapBaseStatsIngressPchipOfferedLoPrioPackets    Counter64,
        tnSapBaseStatsIngressPchipOfferedLoPrioOctets     Counter64,
        tnSapBaseStatsIngressQchipDroppedHiPrioPackets    Counter64,
        tnSapBaseStatsIngressQchipDroppedHiPrioOctets     Counter64,
        tnSapBaseStatsIngressQchipDroppedLoPrioPackets    Counter64,
        tnSapBaseStatsIngressQchipDroppedLoPrioOctets     Counter64,
        tnSapBaseStatsIngressQchipForwardedInProfPackets  Counter64,
        tnSapBaseStatsIngressQchipForwardedInProfOctets   Counter64,
        tnSapBaseStatsIngressQchipForwardedOutProfPackets Counter64,
        tnSapBaseStatsIngressQchipForwardedOutProfOctets  Counter64,
        tnSapBaseStatsEgressQchipDroppedInProfPackets     Counter64,
        tnSapBaseStatsEgressQchipDroppedInProfOctets      Counter64,
        tnSapBaseStatsEgressQchipDroppedOutProfPackets    Counter64,
        tnSapBaseStatsEgressQchipDroppedOutProfOctets     Counter64,
        tnSapBaseStatsEgressQchipForwardedInProfPackets   Counter64,
        tnSapBaseStatsEgressQchipForwardedInProfOctets    Counter64,
        tnSapBaseStatsEgressQchipForwardedOutProfPackets  Counter64,
        tnSapBaseStatsEgressQchipForwardedOutProfOctets   Counter64,
        tnSapBaseStatsCustId                              TmnxCustId,
        tnSapBaseStatsIngressPchipOfferedUncoloredPackets Counter64,
        tnSapBaseStatsIngressPchipOfferedUncoloredOctets  Counter64,
        tnSapBaseStatsAuthenticationPktsDiscarded         Counter32,
        tnSapBaseStatsAuthenticationPktsSuccess           Counter32,
        tnSapBaseStatsLastClearedTime                     TimeStamp
    }

tnSapBaseStatsIngressPchipDroppedPackets OBJECT-TYPE
    SYNTAX          Counter64
    MAX-ACCESS      read-only
    STATUS          current
    DESCRIPTION     "The number of packets dropped by the
                     ingress Pchip due to: SAP state,
                     ingress MAC, IP or IPv6 filter, same segment
                     discard, bad checksum, etc."
    ::= { tnSapBaseStatsEntry 1 }

tnSapBaseStatsIngressPchipDroppedOctets OBJECT-TYPE
    SYNTAX          Counter64
    MAX-ACCESS      read-only
    STATUS          current
    DESCRIPTION     "The number of octets dropped by the
                     ingress Pchip due to: SAP state,
                     ingress MAC, IP or IPv6 filter, same segment
                     discard, bad checksum, etc."
    ::= { tnSapBaseStatsEntry 2 }

tnSapBaseStatsIngressPchipOfferedHiPrioPackets OBJECT-TYPE
    SYNTAX          Counter64
    MAX-ACCESS      read-only
    STATUS          current
    DESCRIPTION     "The number of high priority packets,
                     as determined by the SAP ingress QoS
                     policy, offered by the Pchip to the
                     Qchip."
    ::= { tnSapBaseStatsEntry 3 }

tnSapBaseStatsIngressPchipOfferedHiPrioOctets OBJECT-TYPE
    SYNTAX          Counter64
    MAX-ACCESS      read-only
    STATUS          current
    DESCRIPTION     "The number of high priority octets,
                     as determined by the SAP ingress QoS
                     policy, offered by the Pchip to the
                     Qchip."
    ::= { tnSapBaseStatsEntry 4 }

tnSapBaseStatsIngressPchipOfferedLoPrioPackets OBJECT-TYPE
    SYNTAX          Counter64
    MAX-ACCESS      read-only
    STATUS          current
    DESCRIPTION     "The number of low priority packets,
                     as determined by the SAP ingress QoS
                     policy, offered by the Pchip to the
                     Qchip."
    ::= { tnSapBaseStatsEntry 5 }

tnSapBaseStatsIngressPchipOfferedLoPrioOctets OBJECT-TYPE
    SYNTAX          Counter64
    MAX-ACCESS      read-only
    STATUS          current
    DESCRIPTION     "The number of low priority octets,
                     as determined by the SAP ingress QoS
                     policy, offered by the Pchip to the
                     Qchip."
    ::= { tnSapBaseStatsEntry 6 }

tnSapBaseStatsIngressQchipDroppedHiPrioPackets OBJECT-TYPE
    SYNTAX          Counter64
    MAX-ACCESS      read-only
    STATUS          current
    DESCRIPTION     "The number of high priority packets,
                     as determined by the SAP ingress QoS
                     policy, dropped by the Qchip due to:
                     MBS exceeded, buffer pool limit
                     exceeded, etc."
    ::= { tnSapBaseStatsEntry 7 }

tnSapBaseStatsIngressQchipDroppedHiPrioOctets OBJECT-TYPE
    SYNTAX          Counter64
    MAX-ACCESS      read-only
    STATUS          current
    DESCRIPTION     "The number of high priority octets,
                     as determined by the SAP ingress QoS
                     policy, dropped by the Qchip due to:
                     MBS exceeded, buffer pool limit
                     exceeded, etc."
    ::= { tnSapBaseStatsEntry 8 }

tnSapBaseStatsIngressQchipDroppedLoPrioPackets OBJECT-TYPE
    SYNTAX          Counter64
    MAX-ACCESS      read-only
    STATUS          current
    DESCRIPTION     "The number of low priority packets,
                     as determined by the SAP ingress QoS
                     policy, dropped by the Qchip due to:
                     MBS exceeded, buffer pool limit
                     exceeded, etc."
    ::= { tnSapBaseStatsEntry 9 }

tnSapBaseStatsIngressQchipDroppedLoPrioOctets OBJECT-TYPE
    SYNTAX          Counter64
    MAX-ACCESS      read-only
    STATUS          current
    DESCRIPTION     "The number of low priority octets,
                     as determined by the SAP ingress QoS
                     policy, dropped by the Qchip due to:
                     MBS exceeded, buffer pool limit
                     exceeded, etc."
    ::= { tnSapBaseStatsEntry 10 }

tnSapBaseStatsIngressQchipForwardedInProfPackets OBJECT-TYPE
    SYNTAX          Counter64
    MAX-ACCESS      read-only
    STATUS          current
    DESCRIPTION     "The number of in-profile packets
                     (rate below CIR) forwarded by the
                     ingress Qchip."
    ::= { tnSapBaseStatsEntry 11 }

tnSapBaseStatsIngressQchipForwardedInProfOctets OBJECT-TYPE
    SYNTAX          Counter64
    MAX-ACCESS      read-only
    STATUS          current
    DESCRIPTION     "The number of in-profile octets
                     (rate below CIR) forwarded by the
                     ingress Qchip."
    ::= { tnSapBaseStatsEntry 12 }

tnSapBaseStatsIngressQchipForwardedOutProfPackets OBJECT-TYPE
    SYNTAX          Counter64
    MAX-ACCESS      read-only
    STATUS          current
    DESCRIPTION     "The number of out-of-profile packets
                     (rate above CIR) forwarded by the
                     ingress Qchip."
    ::= { tnSapBaseStatsEntry 13 }

tnSapBaseStatsIngressQchipForwardedOutProfOctets OBJECT-TYPE
    SYNTAX          Counter64
    MAX-ACCESS      read-only
    STATUS          current
    DESCRIPTION     "The number of out-of-profile octets
                     (rate above CIR) forwarded by the
                     ingress Qchip."
    ::= { tnSapBaseStatsEntry 14 }

tnSapBaseStatsEgressQchipDroppedInProfPackets OBJECT-TYPE
    SYNTAX          Counter64
    MAX-ACCESS      read-only
    STATUS          current
    DESCRIPTION     "The number of in-profile packets
                     discarded by the egress Qchip due
                     to: MBS exceeded, buffer pool limit
                     exceeded, etc."
    ::= { tnSapBaseStatsEntry 15 }

tnSapBaseStatsEgressQchipDroppedInProfOctets OBJECT-TYPE
    SYNTAX          Counter64
    MAX-ACCESS      read-only
    STATUS          current
    DESCRIPTION     "The number of in-profile octets
                     discarded by the egress Qchip due
                     to: MBS exceeded, buffer pool limit
                     exceeded, etc."
    ::= { tnSapBaseStatsEntry 16 }

tnSapBaseStatsEgressQchipDroppedOutProfPackets OBJECT-TYPE
    SYNTAX          Counter64
    MAX-ACCESS      read-only
    STATUS          current
    DESCRIPTION     "The number of out-of-profile packets
                     discarded by the egress Qchip due
                     to: MBS exceeded, buffer pool limit
                     exceeded, etc."
    ::= { tnSapBaseStatsEntry 17 }

tnSapBaseStatsEgressQchipDroppedOutProfOctets OBJECT-TYPE
    SYNTAX          Counter64
    MAX-ACCESS      read-only
    STATUS          current
    DESCRIPTION     "The number of out-of-profile packets
                     discarded by the egress Qchip due
                     to: MBS exceeded, buffer pool limit
                     exceeded, etc."
    ::= { tnSapBaseStatsEntry 18 }

tnSapBaseStatsEgressQchipForwardedInProfPackets OBJECT-TYPE
    SYNTAX          Counter64
    MAX-ACCESS      read-only
    STATUS          current
    DESCRIPTION     "The number of in-profile packets
                     (rate below CIR) forwarded by the
                     egress Qchip."
    ::= { tnSapBaseStatsEntry 19 }

tnSapBaseStatsEgressQchipForwardedInProfOctets OBJECT-TYPE
    SYNTAX          Counter64
    MAX-ACCESS      read-only
    STATUS          current
    DESCRIPTION     "The number of in-profile octets
                     (rate below CIR) forwarded by the
                     egress Qchip."
    ::= { tnSapBaseStatsEntry 20 }

tnSapBaseStatsEgressQchipForwardedOutProfPackets OBJECT-TYPE
    SYNTAX          Counter64
    MAX-ACCESS      read-only
    STATUS          current
    DESCRIPTION     "The number of out-of-profile packets
                     (rate above CIR) forwarded by the
                     egress Qchip."
    ::= { tnSapBaseStatsEntry 21 }

tnSapBaseStatsEgressQchipForwardedOutProfOctets OBJECT-TYPE
    SYNTAX          Counter64
    MAX-ACCESS      read-only
    STATUS          current
    DESCRIPTION     "The number of out-of-profile octets
                     (rate above CIR) forwarded by the
                     egress Qchip."
    ::= { tnSapBaseStatsEntry 22 }

tnSapBaseStatsCustId OBJECT-TYPE
    SYNTAX          TmnxCustId
    MAX-ACCESS      read-only
    STATUS          current
    DESCRIPTION     "The Customer ID for the associated service."
    ::= { tnSapBaseStatsEntry 23 }

tnSapBaseStatsIngressPchipOfferedUncoloredPackets OBJECT-TYPE
    SYNTAX          Counter64
    MAX-ACCESS      read-only
    STATUS          current
    DESCRIPTION     "The number of uncolored packets,
                     as determined by the SAP ingress QoS
                     policy, offered by the Pchip to the
                     Qchip."
    ::= { tnSapBaseStatsEntry 24 }

tnSapBaseStatsIngressPchipOfferedUncoloredOctets OBJECT-TYPE
    SYNTAX          Counter64
    MAX-ACCESS      read-only
    STATUS          current
    DESCRIPTION     "The number of uncolored octets,
                     as determined by the SAP ingress QoS
                     policy, offered by the Pchip to the
                     Qchip."
    ::= { tnSapBaseStatsEntry 25 }

tnSapBaseStatsAuthenticationPktsDiscarded OBJECT-TYPE
    SYNTAX          Counter32
    MAX-ACCESS      read-only
    STATUS          current
    DESCRIPTION     "The number of DHCP packets discarded
                     as result of authentication."
    ::= { tnSapBaseStatsEntry 26 }

tnSapBaseStatsAuthenticationPktsSuccess OBJECT-TYPE
    SYNTAX          Counter32
    MAX-ACCESS      read-only
    STATUS          current
    DESCRIPTION     "The number of DHCP packets successfully authenticated."
    ::= { tnSapBaseStatsEntry 27 }

tnSapBaseStatsLastClearedTime OBJECT-TYPE
    SYNTAX          TimeStamp
    MAX-ACCESS      read-only
    STATUS          current
    DESCRIPTION     "The value of tnSapBaseStatsLastClearedTime indicates
                     the sysUpTime when the counters in this table were
                     last cleared."
    ::= { tnSapBaseStatsEntry 28 }

-- ----------------------------------------
-- Ingress QoS Queue SAP Statistics Table
-- ----------------------------------------
-- tnSapIngQosQueueStatsTable OBJECT-TYPE
--     SYNTAX          SEQUENCE OF SapIngQosQueueStatsEntry
--     MAX-ACCESS      not-accessible
--     STATUS          current
--     DESCRIPTION     "A table that contains ingress QoS queue SAP
--                      statistics."
--     ::= { tnSapObjs 7 }
--
-- tnSapIngQosQueueStatsEntry OBJECT-TYPE
--     SYNTAX          SapIngQosQueueStatsEntry
--     MAX-ACCESS      not-accessible
--     STATUS          current
--     DESCRIPTION     "Ingress statistics about a specific SAP's
--                      QoS queue."
--     INDEX           { tnSysSwitchId,  tnSvcId, tnSapPortId, tnSapEncapValue, tnSapIngQosQueueId }
--     ::= { tnSapIngQosQueueStatsTable 1 }
--
-- SapIngQosQueueStatsEntry ::=
--     SEQUENCE {
--         tnSapIngQosQueueId                           TSapIngQueueId,
--         tnSapIngQosQueueStatsOfferedHiPrioPackets    Counter64,
--         tnSapIngQosQueueStatsDroppedHiPrioPackets    Counter64,
--         tnSapIngQosQueueStatsOfferedLoPrioPackets    Counter64,
--         tnSapIngQosQueueStatsDroppedLoPrioPackets    Counter64,
--         tnSapIngQosQueueStatsOfferedHiPrioOctets     Counter64,
--         tnSapIngQosQueueStatsDroppedHiPrioOctets     Counter64,
--         tnSapIngQosQueueStatsOfferedLoPrioOctets     Counter64,
--         tnSapIngQosQueueStatsDroppedLoPrioOctets     Counter64,
--         tnSapIngQosQueueStatsForwardedInProfPackets  Counter64,
--         tnSapIngQosQueueStatsForwardedOutProfPackets Counter64,
--         tnSapIngQosQueueStatsForwardedInProfOctets   Counter64,
--         tnSapIngQosQueueStatsForwardedOutProfOctets  Counter64,
--         tnSapIngQosCustId                            TmnxCustId,
--         tnSapIngQosQueueStatsUncoloredPacketsOffered Counter64,
--         tnSapIngQosQueueStatsUncoloredOctetsOffered  Counter64
--     }
--
-- tnSapIngQosQueueId OBJECT-TYPE
--     SYNTAX          TSapIngQueueId
--     MAX-ACCESS      not-accessible
--     STATUS          current
--     DESCRIPTION     "The index of the ingress QoS queue of
--                      this SAP."
--     ::= { tnSapIngQosQueueStatsEntry 1 }
--
-- tnSapIngQosQueueStatsOfferedHiPrioPackets OBJECT-TYPE
--     SYNTAX          Counter64
--     MAX-ACCESS      read-only
--     STATUS          current
--     DESCRIPTION     "The number of high priority packets,
--                      as determined by the SAP ingress QoS
--                      policy, offered by the Pchip to the
--                      Qchip."
--     ::= { tnSapIngQosQueueStatsEntry 2 }
--
-- tnSapIngQosQueueStatsDroppedHiPrioPackets OBJECT-TYPE
--     SYNTAX          Counter64
--     MAX-ACCESS      read-only
--     STATUS          current
--     DESCRIPTION     "The number of high priority packets,
--                      as determined by the SAP ingress QoS
--                      policy, dropped by the Qchip due to:
--                      MBS exceeded, buffer pool limit
--                      exceeded, etc."
--     ::= { tnSapIngQosQueueStatsEntry 3 }
--
-- tnSapIngQosQueueStatsOfferedLoPrioPackets OBJECT-TYPE
--     SYNTAX          Counter64
--     MAX-ACCESS      read-only
--     STATUS          current
--     DESCRIPTION     "The number of low priority packets,
--                      as determined by the SAP ingress QoS
--                      policy, offered by the Pchip to the
--                      Qchip."
--     ::= { tnSapIngQosQueueStatsEntry 4 }
--
-- tnSapIngQosQueueStatsDroppedLoPrioPackets OBJECT-TYPE
--     SYNTAX          Counter64
--     MAX-ACCESS      read-only
--     STATUS          current
--     DESCRIPTION     "The number of low priority packets,
--                      as determined by the SAP ingress QoS
--                      policy, dropped by the Qchip due to:
--                      MBS exceeded, buffer pool limit
--                      exceeded, etc."
--     ::= { tnSapIngQosQueueStatsEntry 5 }
--
-- tnSapIngQosQueueStatsOfferedHiPrioOctets OBJECT-TYPE
--     SYNTAX          Counter64
--     MAX-ACCESS      read-only
--     STATUS          current
--     DESCRIPTION     "The number of high priority octets,
--                      as determined by the SAP ingress QoS
--                      policy, offered by the Pchip to the
--                      Qchip."
--     ::= { tnSapIngQosQueueStatsEntry 6 }
--
-- tnSapIngQosQueueStatsDroppedHiPrioOctets OBJECT-TYPE
--     SYNTAX          Counter64
--     MAX-ACCESS      read-only
--     STATUS          current
--     DESCRIPTION     "The number of high priority octets,
--                      as determined by the SAP ingress QoS
--                      policy, dropped by the Qchip due to:
--                      MBS exceeded, buffer pool limit
--                      exceeded, etc."
--     ::= { tnSapIngQosQueueStatsEntry 7 }
--
-- tnSapIngQosQueueStatsOfferedLoPrioOctets OBJECT-TYPE
--     SYNTAX          Counter64
--     MAX-ACCESS      read-only
--     STATUS          current
--     DESCRIPTION     "The number of low priority octets,
--                      as determined by the SAP ingress QoS
--                      policy, offered by the Pchip to the
--                      Qchip."
--     ::= { tnSapIngQosQueueStatsEntry 8 }
--
-- tnSapIngQosQueueStatsDroppedLoPrioOctets OBJECT-TYPE
--     SYNTAX          Counter64
--     MAX-ACCESS      read-only
--     STATUS          current
--     DESCRIPTION     "The number of low priority octets,
--                      as determined by the SAP ingress QoS
--                      policy, dropped by the Qchip due to:
--                      MBS exceeded, buffer pool limit
--                      exceeded, etc."
--     ::= { tnSapIngQosQueueStatsEntry 9 }
--
-- tnSapIngQosQueueStatsForwardedInProfPackets OBJECT-TYPE
--     SYNTAX          Counter64
--     MAX-ACCESS      read-only
--     STATUS          current
--     DESCRIPTION     "The number of in-profile packets
--                      (rate below CIR) forwarded by the
--                      ingress Qchip."
--     ::= { tnSapIngQosQueueStatsEntry 10 }
--
-- tnSapIngQosQueueStatsForwardedOutProfPackets OBJECT-TYPE
--     SYNTAX          Counter64
--     MAX-ACCESS      read-only
--     STATUS          current
--     DESCRIPTION     "The number of out-of-profile packets
--                      (rate above CIR) forwarded by the
--                      ingress Qchip."
--     ::= { tnSapIngQosQueueStatsEntry 11 }
--
-- tnSapIngQosQueueStatsForwardedInProfOctets OBJECT-TYPE
--     SYNTAX          Counter64
--     MAX-ACCESS      read-only
--     STATUS          current
--     DESCRIPTION     "The number of in-profile octets
--                      (rate below CIR) forwarded by the
--                      ingress Qchip."
--     ::= { tnSapIngQosQueueStatsEntry 12 }
--
-- tnSapIngQosQueueStatsForwardedOutProfOctets OBJECT-TYPE
--     SYNTAX          Counter64
--     MAX-ACCESS      read-only
--     STATUS          current
--     DESCRIPTION     "The number of out-of-profile octets
--                      (rate above CIR) forwarded by the
--                      ingress Qchip."
--     ::= { tnSapIngQosQueueStatsEntry 13 }
--
-- tnSapIngQosCustId OBJECT-TYPE
--     SYNTAX          TmnxCustId
--     MAX-ACCESS      read-only
--     STATUS          current
--     DESCRIPTION     "The Customer ID for the associated service."
--     ::= { tnSapIngQosQueueStatsEntry 14 }
--
-- tnSapIngQosQueueStatsUncoloredPacketsOffered OBJECT-TYPE
--     SYNTAX          Counter64
--     MAX-ACCESS      read-only
--     STATUS          current
--     DESCRIPTION     "The number of uncolored packets offered to
--                      the ingress Qchip."
--     ::= { tnSapIngQosQueueStatsEntry 15 }
--
-- tnSapIngQosQueueStatsUncoloredOctetsOffered OBJECT-TYPE
--     SYNTAX          Counter64
--     MAX-ACCESS      read-only
--     STATUS          current
--     DESCRIPTION     "The number of uncolored octets offered to
--                      the ingress Qchip."
--     ::= { tnSapIngQosQueueStatsEntry 16 }

-- ----------------------------------------
-- Egress QoS Queue SAP Statistics Table
-- ----------------------------------------
-- tnSapEgrQosQueueStatsTable OBJECT-TYPE
--     SYNTAX          SEQUENCE OF SapEgrQosQueueStatsEntry
--     MAX-ACCESS      not-accessible
--     STATUS          current
--     DESCRIPTION     "A table that contains egress QoS queue SAP
--                      statistics."
--     ::= { tnSapObjs 8 }
--
-- tnSapEgrQosQueueStatsEntry OBJECT-TYPE
--     SYNTAX          SapEgrQosQueueStatsEntry
--     MAX-ACCESS      not-accessible
--     STATUS          current
--     DESCRIPTION     "Egress statistics about a specific SAP's
--                      QoS queue."
--     INDEX           { tnSysSwitchId,  tnSvcId, tnSapPortId, tnSapEncapValue, tnSapEgrQosQueueId }
--     ::= { tnSapEgrQosQueueStatsTable 1 }
--
-- SapEgrQosQueueStatsEntry ::=
--     SEQUENCE {
--         tnSapEgrQosQueueId                           TSapEgrQueueId,
--         tnSapEgrQosQueueStatsForwardedInProfPackets  Counter64,
--         tnSapEgrQosQueueStatsDroppedInProfPackets    Counter64,
--         tnSapEgrQosQueueStatsForwardedOutProfPackets Counter64,
--         tnSapEgrQosQueueStatsDroppedOutProfPackets   Counter64,
--         tnSapEgrQosQueueStatsForwardedInProfOctets   Counter64,
--         tnSapEgrQosQueueStatsDroppedInProfOctets     Counter64,
--         tnSapEgrQosQueueStatsForwardedOutProfOctets  Counter64,
--         tnSapEgrQosQueueStatsDroppedOutProfOctets    Counter64,
--         tnSapEgrQosCustId                            TmnxCustId
--     }
--
-- tnSapEgrQosQueueId OBJECT-TYPE
--     SYNTAX          TSapEgrQueueId
--     MAX-ACCESS      not-accessible
--     STATUS          current
--     DESCRIPTION     "The index of the egress QoS queue of
--                      this SAP."
--     ::= { tnSapEgrQosQueueStatsEntry 1 }
--
-- tnSapEgrQosQueueStatsForwardedInProfPackets OBJECT-TYPE
--     SYNTAX          Counter64
--     MAX-ACCESS      read-only
--     STATUS          current
--     DESCRIPTION     "The number of in-profile packets
--                      (rate below CIR) forwarded by the
--                      egress Qchip."
--     ::= { tnSapEgrQosQueueStatsEntry 2 }
--
-- tnSapEgrQosQueueStatsDroppedInProfPackets OBJECT-TYPE
--     SYNTAX          Counter64
--     MAX-ACCESS      read-only
--     STATUS          current
--     DESCRIPTION     "The number of in-profile packets
--                      discarded by the egress Qchip due
--                      to: MBS exceeded, buffer pool limit
--                      exceeded, etc."
--     ::= { tnSapEgrQosQueueStatsEntry 3 }
--
-- tnSapEgrQosQueueStatsForwardedOutProfPackets OBJECT-TYPE
--     SYNTAX          Counter64
--     MAX-ACCESS      read-only
--     STATUS          current
--     DESCRIPTION     "The number of out-of-profile packets
--                      (rate above CIR) forwarded by the
--                      egress Qchip."
--     ::= { tnSapEgrQosQueueStatsEntry 4 }
--
-- tnSapEgrQosQueueStatsDroppedOutProfPackets OBJECT-TYPE
--     SYNTAX          Counter64
--     MAX-ACCESS      read-only
--     STATUS          current
--     DESCRIPTION     "The number of out-of-profile packets
--                      discarded by the egress Qchip due
--                      to: MBS exceeded, buffer pool limit
--                      exceeded, etc."
--     ::= { tnSapEgrQosQueueStatsEntry 5 }
--
-- tnSapEgrQosQueueStatsForwardedInProfOctets OBJECT-TYPE
--     SYNTAX          Counter64
--     MAX-ACCESS      read-only
--     STATUS          current
--     DESCRIPTION     "The number of in-profile octets
--                      (rate below CIR) forwarded by the
--                      egress Qchip."
--     ::= { tnSapEgrQosQueueStatsEntry 6 }
--
-- tnSapEgrQosQueueStatsDroppedInProfOctets OBJECT-TYPE
--     SYNTAX          Counter64
--     MAX-ACCESS      read-only
--     STATUS          current
--     DESCRIPTION     "The number of in-profile octets
--                      discarded by the egress Qchip due
--                      to: MBS exceeded, buffer pool limit
--                      exceeded, etc."
--     ::= { tnSapEgrQosQueueStatsEntry 7 }
--
-- tnSapEgrQosQueueStatsForwardedOutProfOctets OBJECT-TYPE
--     SYNTAX          Counter64
--     MAX-ACCESS      read-only
--     STATUS          current
--     DESCRIPTION     "The number of out-of-profile octets
--                      (rate above CIR) forwarded by the
--                      egress Qchip."
--     ::= { tnSapEgrQosQueueStatsEntry 8 }
--
-- tnSapEgrQosQueueStatsDroppedOutProfOctets OBJECT-TYPE
--     SYNTAX          Counter64
--     MAX-ACCESS      read-only
--     STATUS          current
--     DESCRIPTION     "The number of out-of-profile octets
--                      discarded by the egress Qchip due
--                      to: MBS exceeded, buffer pool limit
--                      exceeded, etc."
--     ::= { tnSapEgrQosQueueStatsEntry 9 }
--
-- tnSapEgrQosCustId OBJECT-TYPE
--     SYNTAX          TmnxCustId
--     MAX-ACCESS      read-only
--     STATUS          current
--     DESCRIPTION     "The Customer ID for the associated service."
--     ::= { tnSapEgrQosQueueStatsEntry 10 }

-- -------------------------------------------------
-- Ingress QoS Scheduler SAP Statistics Table
-- -------------------------------------------------
-- tnSapIngQosSchedStatsTable OBJECT-TYPE
--     SYNTAX          SEQUENCE OF SapIngQosSchedStatsEntry
--     MAX-ACCESS      not-accessible
--     STATUS          current
--     DESCRIPTION     "A table that contains ingress QoS queue SAP
--                      statistics."
--     ::= { tnSapObjs 9 }
--
-- tnSapIngQosSchedStatsEntry OBJECT-TYPE
--     SYNTAX          SapIngQosSchedStatsEntry
--     MAX-ACCESS      not-accessible
--     STATUS          current
--     DESCRIPTION     "Ingress statistics about a specific SAP's
--                      QoS queue."
--     INDEX           { tnSysSwitchId,  tnSvcId, tnSapPortId, tnSapEncapValue,
--                       IMPLIED tnSapIngQosSchedName }
--     ::= { tnSapIngQosSchedStatsTable 1 }
--
-- SapIngQosSchedStatsEntry ::=
--     SEQUENCE {
--         tnSapIngQosSchedName                     TNamedItem,
--         tnSapIngQosSchedStatsForwardedPackets    Counter64,
--         tnSapIngQosSchedStatsForwardedOctets     Counter64,
--         tnSapIngQosSchedCustId                   TmnxCustId
--     }
--
-- tnSapIngQosSchedName OBJECT-TYPE
--     SYNTAX          TNamedItem
--     MAX-ACCESS      not-accessible
--     STATUS          current
--     DESCRIPTION     "The index of the ingress QoS scheduler of
--                      this SAP."
--     ::= { tnSapIngQosSchedStatsEntry 1 }
--
-- tnSapIngQosSchedStatsForwardedPackets OBJECT-TYPE
--     SYNTAX          Counter64
--     MAX-ACCESS      read-only
--     STATUS          current
--     DESCRIPTION     "The number of forwarded packets, as
--                      determined by the SAP ingress scheduler
--                      policy, offered by the Pchip to the
--                      Qchip."
--     ::= { tnSapIngQosSchedStatsEntry 2 }
--
-- tnSapIngQosSchedStatsForwardedOctets OBJECT-TYPE
--     SYNTAX          Counter64
--     MAX-ACCESS      read-only
--     STATUS          current
--     DESCRIPTION     "The number of forwarded octets, as
--                      determined by the SAP ingress scheduler
--                      policy, offered by the Pchip to the
--                      Qchip."
--     ::= { tnSapIngQosSchedStatsEntry 3 }
--
-- tnSapIngQosSchedCustId OBJECT-TYPE
--     SYNTAX          TmnxCustId
--     MAX-ACCESS      read-only
--     STATUS          current
--     DESCRIPTION     "The Customer ID for the associated service."
--     ::= { tnSapIngQosSchedStatsEntry 4 }

-- ---------------------------------------------
-- Egress QoS Scheduler SAP Statistics Table
-- ---------------------------------------------
-- tnSapEgrQosSchedStatsTable OBJECT-TYPE
--     SYNTAX          SEQUENCE OF SapEgrQosSchedStatsEntry
--     MAX-ACCESS      not-accessible
--     STATUS          current
--     DESCRIPTION     "A table that contains ingress QoS queue SAP
--                      statistics."
--     ::= { tnSapObjs 10 }
--
-- tnSapEgrQosSchedStatsEntry OBJECT-TYPE
--     SYNTAX          SapEgrQosSchedStatsEntry
--     MAX-ACCESS      not-accessible
--     STATUS          current
--     DESCRIPTION     "Egress statistics about a specific SAP's
--                      QoS queue."
--     INDEX           { tnSysSwitchId,  tnSvcId, tnSapPortId, tnSapEncapValue,
--                       IMPLIED tnSapEgrQosSchedName }
--     ::= { tnSapEgrQosSchedStatsTable 1 }
--
-- SapEgrQosSchedStatsEntry ::=
--     SEQUENCE {
--         tnSapEgrQosSchedName                     TNamedItem,
--         tnSapEgrQosSchedStatsForwardedPackets    Counter64,
--         tnSapEgrQosSchedStatsForwardedOctets     Counter64,
--         tnSapEgrQosSchedCustId                   TmnxCustId
--     }
--
-- tnSapEgrQosSchedName OBJECT-TYPE
--     SYNTAX          TNamedItem
--     MAX-ACCESS      not-accessible
--     STATUS          current
--     DESCRIPTION     "The index of the egress QoS scheduler of
--                      this SAP."
--     ::= { tnSapEgrQosSchedStatsEntry 1 }
--
-- tnSapEgrQosSchedStatsForwardedPackets OBJECT-TYPE
--     SYNTAX          Counter64
--     MAX-ACCESS      read-only
--     STATUS          current
--     DESCRIPTION     "The number of forwarded packets by the
--                      egress Qchip, as determined by the SAP
--                      egress scheduler policy."
--     ::= { tnSapEgrQosSchedStatsEntry 2 }
--
-- tnSapEgrQosSchedStatsForwardedOctets OBJECT-TYPE
--     SYNTAX          Counter64
--     MAX-ACCESS      read-only
--     STATUS          current
--     DESCRIPTION     "The number of forwarded octets by the
--                      egress Qchip, as determined by the SAP
--                      egress scheduler policy."
--     ::= { tnSapEgrQosSchedStatsEntry 3 }
--
-- tnSapEgrQosSchedCustId OBJECT-TYPE
--     SYNTAX          TmnxCustId
--     MAX-ACCESS      read-only
--     STATUS          current
--     DESCRIPTION     "The Customer ID for the associated service."
--     ::= { tnSapEgrQosSchedStatsEntry 4 }

-- -----------------------------------------
-- TLS SAP Managed VLAN List Table
-- -----------------------------------------
-- tnSapTlsManagedVlanListTable OBJECT-TYPE
--     SYNTAX          SEQUENCE OF SapTlsManagedVlanListEntry
--     MAX-ACCESS      not-accessible
--     STATUS          current
--     DESCRIPTION     "This table is used only for SAPs that are part
--                      of a management VPLS. It indicates for each SAP the
--                      ranges of associated VLANs that will be affected when
--                      the SAP changes state."
--     ::= { tnSapObjs 11 }
--
-- tnSapTlsManagedVlanListEntry OBJECT-TYPE
--     SYNTAX          SapTlsManagedVlanListEntry
--     MAX-ACCESS      not-accessible
--     STATUS          current
--     DESCRIPTION     "Each row specifies a range of VLANS associated
--                      with a SAP of a MVPLS. Ranges may contains overlapping
--                      sections only for Mvpls SAPs that belong to the same
--                      service."
--     INDEX           { tnSysSwitchId,  tnSvcId,
--                       tnSapPortId,
--                       tnSapEncapValue,
--                       tnSapTlsMvplsMinVlanTag,
--                       tnSapTlsMvplsMaxVlanTag }
--     ::= { tnSapTlsManagedVlanListTable 1 }
--
-- SapTlsManagedVlanListEntry ::=
--     SEQUENCE {
--         tnSapTlsMvplsMinVlanTag     Unsigned32,
--         tnSapTlsMvplsMaxVlanTag     Unsigned32,
--         tnSapTlsMvplsRowStatus      RowStatus
--     }
--
-- tnSapTlsMvplsMinVlanTag OBJECT-TYPE
--     SYNTAX          Unsigned32(0 .. 4095)
--     MAX-ACCESS      not-accessible
--     STATUS          current
--     DESCRIPTION     "The value of tnSapTlsMvplsMinVlanTag specifies
--                      the left bound (i.e. min. value) of a range of VLANs
--                      that are associated with the Mvpls SAP.
--                      tnSapTlsMvplsMinVlanTag must be smaller than (or equal
--                      to) tnSapTlsMvplsMaxVlanTag.
--                      Special values are:
--                      0: this value is reserved for the null tag.
--                      4095: this value denotes the default SAP."
--     ::= { tnSapTlsManagedVlanListEntry 1 }
--
-- tnSapTlsMvplsMaxVlanTag OBJECT-TYPE
--     SYNTAX          Unsigned32(0 .. 4095)
--     MAX-ACCESS      not-accessible
--     STATUS          current
--     DESCRIPTION     "The value of tnSapTlsMvplsMaxVlanTag specifies the
--                      right bound (i.e. max. value) of a range of VLANs that
--                      are associated with the Mvpls SAP.
--                      Special values are:
--                      0: this value is reserved for the null tag.
--                      4095: this value denotes the default SAP."
--     ::= { tnSapTlsManagedVlanListEntry 2 }
--
-- tnSapTlsMvplsRowStatus OBJECT-TYPE
--     SYNTAX           RowStatus
--     MAX-ACCESS       read-create
--     STATUS           current
--     DESCRIPTION      "The value of tnSapTlsMvplsRowStatus specifies
--                       the status of this row. The only values supported
--                       during a set operation are 'createAndGo' and
--                       'destroy'. A row (i.e. a range of VLAN tags) can be
--                       destroyed only if there are no SAPs defined in
--                       regular VPLSses in this range."
--     ::= { tnSapTlsManagedVlanListEntry 3 }

-- ----------------------------------------------------
-- SAP Anti-spoof Table
-- ----------------------------------------------------
-- tnSapAntiSpoofTable OBJECT-TYPE
--     SYNTAX          SEQUENCE OF SapAntiSpoofEntry
--     MAX-ACCESS      not-accessible
--     STATUS          obsolete
--     DESCRIPTION     "The tnSapAntiSpoofTable contains information about
--                      anti-spoofing filters on a SAP."
--     ::= { tnSapObjs 12 }
--
-- tnSapAntiSpoofEntry OBJECT-TYPE
--     SYNTAX          SapAntiSpoofEntry
--     MAX-ACCESS      not-accessible
--     STATUS          obsolete
--     DESCRIPTION     "An entry in the tnSapAntiSpoofTable."
--     INDEX           { tnSysSwitchId,  tnSapPortId,
--                       tnSapEncapValue,
--                       tnSapAntiSpoofIpAddress,
--                       tnSapAntiSpoofMacAddress }
--     ::= { tnSapAntiSpoofTable 1 }
--
-- SapAntiSpoofEntry ::=
--     SEQUENCE {
--         tnSapAntiSpoofIpAddress  IpAddress,
--         tnSapAntiSpoofMacAddress MacAddress
--     }
--
-- tnSapAntiSpoofIpAddress OBJECT-TYPE
--     SYNTAX          IpAddress
--     MAX-ACCESS      read-only
--     STATUS          obsolete
--     DESCRIPTION     "The value of tnSapAntiSpoofIpAddress indicates the IP
--                      address for which this table entry contains information."
--     ::= { tnSapAntiSpoofEntry 1 }
--
-- tnSapAntiSpoofMacAddress OBJECT-TYPE
--     SYNTAX          MacAddress
--     MAX-ACCESS      read-only
--     STATUS          obsolete
--     DESCRIPTION     "The value of tnSapAntiSpoofMacAddress indicates the MAC
--                      address for which this table entry contains information."
--     ::= { tnSapAntiSpoofEntry 2 }

-- -----------------------------------------
-- SAP Static Host Table
-- -----------------------------------------
-- tnSapStaticHostTable OBJECT-TYPE
--     SYNTAX          SEQUENCE OF SapStaticHostEntry
--     MAX-ACCESS      not-accessible
--     STATUS          current
--     DESCRIPTION     "The tnSapStaticHostTable is used to configure static hosts
--                      on a SAP."
--     ::= { tnSapObjs 13 }
--
-- tnSapStaticHostEntry OBJECT-TYPE
--     SYNTAX          SapStaticHostEntry
--     MAX-ACCESS      not-accessible
--     STATUS          current
--     DESCRIPTION     "Each row entry represents information on a statically
--                      configured host. Entries can be created and deleted via
--                      SNMP SET operations."
--     INDEX           { tnSysSwitchId,  tnSvcId,
--                       tnSapPortId,
--                       tnSapEncapValue,
--                       tnSapStaticHostIpAddress,
--                       tnSapStaticHostMacAddress }
--     ::= { tnSapStaticHostTable 1 }
--
-- SapStaticHostEntry ::=
--     SEQUENCE {
--         tnSapStaticHostRowStatus          RowStatus,
--         tnSapStaticHostIpAddress          IpAddress,
--         tnSapStaticHostMacAddress         MacAddress,
--         tnSapStaticHostSubscrIdent        DisplayString,
--         tnSapStaticHostSubProfile         ServObjName,
--         tnSapStaticHostSlaProfile         ServObjName,
--         tnSapStaticHostShcvOperState      INTEGER,
--         tnSapStaticHostShcvChecks         Unsigned32,
--         tnSapStaticHostShcvReplies        Unsigned32,
--         tnSapStaticHostShcvReplyTime      TimeStamp,
--         tnSapStaticHostDynMacAddress      MacAddress,
--         tnSapStaticHostRetailerSvcId      TmnxServId,
--         tnSapStaticHostRetailerIf         InterfaceIndexOrZero,
--         tnSapStaticHostFwdingState        TmnxOperState,
--         tnSapStaticHostAncpString         DisplayString,
--         tnSapStaticHostSubIdIsSapId       TruthValue,
--         tnSapStaticHostAppProfile         ServObjName,
--         tnSapStaticHostIntermediateDestId DisplayString,
--         tnSapStaticHostAdminStatus        ServiceAdminStatus
--     }
--
-- tnSapStaticHostRowStatus OBJECT-TYPE
--     SYNTAX          RowStatus
--     MAX-ACCESS      read-create
--     STATUS          current
--     DESCRIPTION     "The value of the object tnSapStaticHostRowStatus controls
--                      the creation and deletion of rows in this table."
--     ::= { tnSapStaticHostEntry 1 }
--
-- tnSapStaticHostIpAddress OBJECT-TYPE
--     SYNTAX          IpAddress
--     MAX-ACCESS      not-accessible
--     STATUS          current
--     DESCRIPTION     "The value of the object tnSapStaticHostIpAddress specifies
--                      the IP address associated with this static host. The value
--                      0.0.0.0 indicates that no host IP address is specified."
--     ::= { tnSapStaticHostEntry 2 }
--
-- tnSapStaticHostMacAddress OBJECT-TYPE
--     SYNTAX          MacAddress
--     MAX-ACCESS      not-accessible
--     STATUS          current
--     DESCRIPTION     "The value of the object tnSapStaticHostMacAddress specifies
--                      the MAC address associated with this static host. The
--                      value 0:0:0:0:0:0 indicates that no host MAC address is
--                      specified."
--     ::= { tnSapStaticHostEntry 3 }
--
-- tnSapStaticHostSubscrIdent OBJECT-TYPE
--     SYNTAX          DisplayString (SIZE (0..32))
--     MAX-ACCESS      read-create
--     STATUS          current
--     DESCRIPTION     "The value of the object tnSapStaticHostSubscrIdent specifies
--                      the subscriber identification for this static host."
--     DEFVAL          { "" }
--     ::= { tnSapStaticHostEntry 4 }
--
-- tnSapStaticHostSubProfile OBJECT-TYPE
--     SYNTAX          ServObjName
--     MAX-ACCESS      read-create
--     STATUS          current
--     DESCRIPTION     "The value of the object tnSapStaticHostSubProfile specifies
--                      the subscriber profile for this static host. The specified
--                      subscriber profile needs to exists in the
--                      TIMETRA-SUBSCRIBER-MGMT-MIB::tmnxSubProfileTable."
--     DEFVAL          { "" }
--     ::= { tnSapStaticHostEntry 5 }
--
-- tnSapStaticHostSlaProfile OBJECT-TYPE
--     SYNTAX          ServObjName
--     MAX-ACCESS      read-create
--     STATUS          current
--     DESCRIPTION     "The value of the object tnSapStaticHostSlaProfile specifies
--                      the SLA profile for this static host. The specified
--                      SLA profile needs to exists in the
--                      TIMETRA-SUBSCRIBER-MGMT-MIB::tmnxSLAProfileTable."
--     DEFVAL          { "" }
--     ::= { tnSapStaticHostEntry 6 }
--
-- tnSapStaticHostShcvOperState OBJECT-TYPE
--     SYNTAX          INTEGER {
--                         disabled  (1),
--                         undefined (2),
--                         down      (3),
--                         up        (4)
--                     }
--     MAX-ACCESS      read-only
--     STATUS          current
--     DESCRIPTION     "The value of the object tnSapStaticHostShcvOperState
--                      gives the state of the subscriber host connectivity
--                      check for this static host."
--     ::= { tnSapStaticHostEntry 7 }
--
-- tnSapStaticHostShcvChecks OBJECT-TYPE
--     SYNTAX          Unsigned32
--     MAX-ACCESS      read-only
--     STATUS          current
--     DESCRIPTION     "The value of the object tnSapStaticHostShcvChecks specifies
--                      the number of connectivity checks for this static host."
--     ::= { tnSapStaticHostEntry 8 }
--
-- tnSapStaticHostShcvReplies OBJECT-TYPE
--     SYNTAX          Unsigned32
--     MAX-ACCESS      read-only
--     STATUS          current
--     DESCRIPTION     "The value of the object tnSapStaticHostShcvReplies specifies
--                      the number of host replies for this static host."
--     ::= { tnSapStaticHostEntry 9 }
--
-- tnSapStaticHostShcvReplyTime OBJECT-TYPE
--     SYNTAX          TimeStamp
--     MAX-ACCESS      read-only
--     STATUS          current
--     DESCRIPTION     "The value of the object tnSapStaticHostShcvReplyTime
--                      gives the timestamp of the last successful connectivity
--                      check for this static host."
--     ::= { tnSapStaticHostEntry 10 }
--
-- tnSapStaticHostDynMacAddress OBJECT-TYPE
--     SYNTAX          MacAddress
--     MAX-ACCESS      read-only
--     STATUS          current
--     DESCRIPTION     "The value of the object tnSapStaticHostDynMacAddress gives
--                      the MAC address learned via ARP in case this is an IP-only
--                      static host (tnSapStaticHostMacAddress is set to
--                      0:0:0:0:0:0).
--                      The value 0:0:0:0:0:0 indicates that no MAC address is
--                      learned yet."
--     ::= { tnSapStaticHostEntry 11 }
--
-- tnSapStaticHostRetailerSvcId OBJECT-TYPE
--     SYNTAX          TmnxServId
--     MAX-ACCESS      read-only
--     STATUS          current
--     DESCRIPTION     "The value of the object tnSapStaticHostRetailerSvcId
--                      indicates the service ID of the retailer VPRN service
--                      to which this static host belongs. When this object is
--                      non zero, the static host belongs to a retailer VPRN."
--     ::= { tnSapStaticHostEntry 12 }
--
-- tnSapStaticHostRetailerIf OBJECT-TYPE
--     SYNTAX          InterfaceIndexOrZero
--     MAX-ACCESS      read-only
--     STATUS          current
--     DESCRIPTION     "The value of the object tnSapStaticHostRetailerIf indicates
--                      the interface index of the retailer VPRN interface to which
--                      this static host belongs. When this object is non zero,
--                      the static host belongs to a retailer VPRN."
--     ::= { tnSapStaticHostEntry 13 }
--
-- tnSapStaticHostFwdingState OBJECT-TYPE
--     SYNTAX          TmnxOperState
--     MAX-ACCESS      read-only
--     STATUS          current
--     DESCRIPTION     "The value of tnSapStaticHostFwdingState indicates the
--                      forwarding state of this static host. When the value
--                      is 'outOfService', host traffic is not forwarded.
--                      When it is 'inService', host traffic is forwarded."
--     ::= { tnSapStaticHostEntry 14 }
--
-- tnSapStaticHostAncpString OBJECT-TYPE
--     SYNTAX          DisplayString (SIZE (0..63))
--     MAX-ACCESS      read-create
--     STATUS          current
--     DESCRIPTION     "The value of tnSapStaticHostAncpString specifies
--                      the ancp-string associated to this SAP host."
--     DEFVAL          { "" }
--     ::= { tnSapStaticHostEntry 15 }
--
-- tnSapStaticHostSubIdIsSapId OBJECT-TYPE
--     SYNTAX          TruthValue
--     MAX-ACCESS      read-create
--     STATUS          current
--     DESCRIPTION     "The value of the object tnSapStaticHostSubIdIsSapId
--                      specifies whether the SAP-id is taken as subscriber
--                      identification for this static host."
--     DEFVAL          { false }
--     ::= { tnSapStaticHostEntry 16 }
--
-- tnSapStaticHostAppProfile OBJECT-TYPE
--     SYNTAX          ServObjName
--     MAX-ACCESS      read-create
--     STATUS          current
--     DESCRIPTION     "The value of tnSapStaticHostAppProfile specifies
--                      the application profile for this static host. The
--                      specified application profile needs to exist in the
--                      TIMETRA-BSX-NG-MIB::tmnxBsxAppProfTable."
--     DEFVAL          { "" }
--     ::= { tnSapStaticHostEntry 17 }
--
-- tnSapStaticHostIntermediateDestId OBJECT-TYPE
--     SYNTAX          DisplayString (SIZE (0..32))
--     MAX-ACCESS      read-create
--     STATUS          current
--     DESCRIPTION     "The value of tnSapStaticHostIntermediateDestId specifies
--                      to which intermediate destination (for example a DSLAM)
--                      this host belongs."
--     DEFVAL          { "" }
--     ::= { tnSapStaticHostEntry 18 }
--
-- tnSapStaticHostAdminStatus OBJECT-TYPE
--     SYNTAX          ServiceAdminStatus
--     MAX-ACCESS      read-create
--     STATUS          current
--     DESCRIPTION     "The value of tnSapStaticHostAdminStatus specifies
--                      the administrative status of this host."
--     DEFVAL          { down }
--     ::= { tnSapStaticHostEntry 19 }

-- ----------------------------------------
-- SAP Tls DHCP Information Table
-- ----------------------------------------
-- tnSapTlsDhcpInfoTable OBJECT-TYPE
--     SYNTAX          SEQUENCE OF SapTlsDhcpInfoEntry
--     MAX-ACCESS      not-accessible
--     STATUS          current
--     DESCRIPTION     "tnSapTlsDhcpInfoTable  contains  DHCP information related
--                      to a TLS  SAP.  This table complements tnSapTlsInfoTable,
--                      and contains an entry for each Tls SAP. Rows in this
--                      table are created and deleted automatically by the system."
--     ::= { tnSapObjs 14 }
--
-- tnSapTlsDhcpInfoEntry OBJECT-TYPE
--     SYNTAX          SapTlsDhcpInfoEntry
--     MAX-ACCESS      not-accessible
--     STATUS          current
--     DESCRIPTION     " DHCP specific information for a TLS SAP."
--     INDEX           { tnSysSwitchId,  tnSvcId, tnSapPortId, tnSapEncapValue }
--     ::= { tnSapTlsDhcpInfoTable 1 }
--
-- SapTlsDhcpInfoEntry ::=
--     SEQUENCE {
--         tnSapTlsDhcpAdminState            TmnxEnabledDisabled,
--         tnSapTlsDhcpDescription           ServObjDesc,
--         tnSapTlsDhcpSnoop                 TmnxEnabledDisabled,
--         tnSapTlsDhcpLeasePopulate         Unsigned32,
--         tnSapTlsDhcpOperLeasePopulate     Unsigned32,
--         tnSapTlsDhcpInfoAction            INTEGER,
--         tnSapTlsDhcpCircuitId             INTEGER,
--         tnSapTlsDhcpRemoteId              INTEGER,
--         tnSapTlsDhcpRemoteIdString        DisplayString,
--         tnSapTlsDhcpProxyAdminState       TmnxEnabledDisabled,
--         tnSapTlsDhcpProxyServerAddr       IpAddress,
--         tnSapTlsDhcpProxyLeaseTime        Unsigned32,
--         tnSapTlsDhcpProxyLTRadiusOverride TruthValue,
--         tnSapTlsDhcpVendorIncludeOptions  BITS,
--         tnSapTlsDhcpVendorOptionString    DisplayString
--         }
--
-- tnSapTlsDhcpAdminState OBJECT-TYPE
--     SYNTAX          TmnxEnabledDisabled
--     MAX-ACCESS      read-write
--     STATUS          current
--     DESCRIPTION     "The value of the object tnSapTlsDhcpAdminState specifies
--                      the overall enable/disable state of all DHCP related
--                      actions  on  this  Sap. The value 'disabled' allows
--                      the user to configure  individual DHCP commands but
--                      administratively disable them."
--     DEFVAL          { disabled }
--     ::= { tnSapTlsDhcpInfoEntry 1 }
--
-- tnSapTlsDhcpDescription OBJECT-TYPE
--     SYNTAX          ServObjDesc
--     MAX-ACCESS      read-write
--     STATUS          current
--     DESCRIPTION     "The value of the object tnSapTlsDhcpDescription specifies
--                      a user provided description for DHCP on this Sap.
--                      It consists of any printable, seven-bit ASCII characters
--                      up to 80 characters in length."
--     DEFVAL          { ''H }
--     ::= { tnSapTlsDhcpInfoEntry 2 }
--
-- tnSapTlsDhcpSnoop OBJECT-TYPE
--     SYNTAX          TmnxEnabledDisabled
--     MAX-ACCESS      read-write
--     STATUS          current
--     DESCRIPTION     "The value of the object tnSapTlsDhcpSnoop specifies
--                      the enable/disable state for DHCP snooping on this Sap.
--                      Note that in order for snooping to be enabled
--                      the object tnSapTlsDhcpAdminState must also have the
--                      value enabled."
--     DEFVAL          { disabled }
--     ::= { tnSapTlsDhcpInfoEntry 3 }
--
-- tnSapTlsDhcpLeasePopulate OBJECT-TYPE
--     SYNTAX          Unsigned32 (0..32767)
--     MAX-ACCESS      read-write
--     STATUS          current
--     DESCRIPTION     "The value of the object tnSapTlsDhcpLeasePopulate specifies
--                      the maximum number of DHCP lease states allowed on this
--                      SAP."
--     DEFVAL { 0 }
--     ::= { tnSapTlsDhcpInfoEntry 4 }
--
-- tnSapTlsDhcpOperLeasePopulate OBJECT-TYPE
--     SYNTAX          Unsigned32 (0..32767)
--     MAX-ACCESS      read-only
--     STATUS          current
--     DESCRIPTION     "The value of the object tnSapTlsDhcpOperLeasePopulate
--                      indicates the number of DHCP lease states currently
--                      allocated on this SAP."
--     ::= { tnSapTlsDhcpInfoEntry 5 }
--
-- tnSapTlsDhcpInfoAction OBJECT-TYPE
--     SYNTAX          INTEGER {
--                         replace (1),
--                         drop    (2),
--                         keep    (3)
--                     }
--     MAX-ACCESS      read-write
--     STATUS          current
--     DESCRIPTION     "The value of the object tnSapTlsDhcpInfoAction specifies
--                      the DHCP option reforwarding policy:
--                      'replace' - replace existing information with
--                                  configured information
--                      'drop'    - discard messages with existing relay
--                                  information if the option-82 information
--                                  is also present.
--                      'keep'    - retain the existing relay information."
--     DEFVAL { keep }
--     ::= { tnSapTlsDhcpInfoEntry 6 }
--
-- tnSapTlsDhcpCircuitId OBJECT-TYPE
--     SYNTAX          INTEGER {
--                         none           (0),
--                         asciiTuple     (1),
--                         vlanAsciiTuple (2)
--                     }
--     MAX-ACCESS      read-write
--     STATUS          current
--     DESCRIPTION     "The value of the object tnSapTlsDhcpCircuitId specifies
--                      whether or not the circuit-id suboption is present, and if
--                      it is present what information goes in it:
--                      - 'none'          the circuit-id suboption will not be part
--                                        of the information option (Option 82).
--                      - 'asciiTuple'    the ASCII-encoded  concatenated tuple
--                                        consisting of the
--                                           - access-node-identifier
--                                           - service-id
--                                           - interface-name
--                                        is used.
--                     - 'vlanAsciiTuple' the format will include VLAN-id and dot1p
--                                        bits in addition to what is included in
--                                        ascii-tuple already.  The format is
--                                        supported on dot1q and qinq encapsulated
--                                        ports only.  Thus, when the option 82
--                                        bits are stripped, dot1p bits will be
--                                        copied to the Ethernet header of an
--                                        outgoing packet."
--     DEFVAL { asciiTuple }
--     ::= { tnSapTlsDhcpInfoEntry 7 }
--
-- tnSapTlsDhcpRemoteId OBJECT-TYPE
--     SYNTAX          INTEGER {
--                         none      (1),
--                         mac       (2),
--                         remote-id (3)
--                     }
--     MAX-ACCESS      read-write
--     STATUS          current
--     DESCRIPTION     "The value of the object tnSapTlsDhcpRemoteId specifies
--                      what information goes into the remote-id suboption in
--                      the DHCP Relay packet.
--                      If the value of this object is set to 'none',
--                      the remote-id suboption will not be part of the
--                      information option (Option 82).
--                      If the value of this object is set to 'mac',
--                      the MAC address of the remote end is encoded in the
--                      suboption.
--                      If the value of this object is set to 'remote-id',
--                      tnSapTlsDhcpRemoteIdString will represent the remote-id.
--                      By default, the remote-id value is none."
--     DEFVAL { none }
--     ::= { tnSapTlsDhcpInfoEntry 8 }
--
-- tnSapTlsDhcpRemoteIdString OBJECT-TYPE
--     SYNTAX          DisplayString (SIZE (0..32))
--     MAX-ACCESS      read-write
--     STATUS          current
--     DESCRIPTION     "The value of the object tnSapTlsDhcpRemoteIdString specifies
--                      the remote-id.  This object exists only if
--                      tnSapTlsDhcpRemoteId has a value of 'remote-id'."
--     DEFVAL { "" }
--     ::= { tnSapTlsDhcpInfoEntry 9 }
--
-- tnSapTlsDhcpProxyAdminState   OBJECT-TYPE
--     SYNTAX          TmnxEnabledDisabled
--     MAX-ACCESS      read-write
--     STATUS          current
--     DESCRIPTION     "The value of tnSapTlsDhcpProxyAdminState specifies the
--                      desired administrative state of the proxy server on this
--                      interface.
--
--                      Note that in order for the proxy server to be enabled,
--                      the value of tnSapTlsDhcpAdminState must also be 'enabled'."
--     DEFVAL { disabled }
--     ::= { tnSapTlsDhcpInfoEntry 10 }
--
-- tnSapTlsDhcpProxyServerAddr   OBJECT-TYPE
--     SYNTAX          IpAddress
--     MAX-ACCESS      read-write
--     STATUS          current
--     DESCRIPTION     "The value of tnSapTlsDhcpProxyServerAddr specifies
--                      the IP address which will be used as the source address
--                      of the emulated DHCP server in the context of
--                      this VPLS SAP.
--
--                      This address is mandatory for the proxy server capability
--                      and it should be in the context of the subnet represented
--                      by this VPLS."
--     DEFVAL { '00000000'H }
--     ::= { tnSapTlsDhcpInfoEntry 11 }
--
-- tnSapTlsDhcpProxyLeaseTime    OBJECT-TYPE
--     SYNTAX          Unsigned32 (0|300..315446399)
--     UNITS           "seconds"
--     MAX-ACCESS      read-write
--     STATUS          current
--     DESCRIPTION     "The value of tnSapTlsDhcpProxyLeaseTime specifies in seconds
--                      how long a DHCP client is allowed to use the offered IP
--                      address.
--
--                      Value 0 means the lease time provided by a RADIUS or
--                      an upstream DHCP server will not be overridden. A lease
--                      time of 7 days is used when RADIUS does not provide
--                      a lease time."
--     DEFVAL { 0 }
--     ::= { tnSapTlsDhcpInfoEntry 12 }
--
-- tnSapTlsDhcpProxyLTRadiusOverride OBJECT-TYPE
--     SYNTAX          TruthValue
--     MAX-ACCESS      read-write
--     STATUS          current
--     DESCRIPTION     "The value of tnSapTlsDhcpProxyLTRadiusOverride specifies
--                      whether or not the lease time provided by the RADIUS
--                      server is presented to the DHCP client.
--
--                      By default the proxy-server will always make use of
--                      tnSapTlsDhcpProxyLeaseTime, regardless of what lease time
--                      information is provided from the RADIUS server.
--                      When tnSapTlsDhcpProxyLTRadiusOverride is set to 'true', the
--                      proxy-server will use the lease time information provided
--                      by the RADIUS server, regardless of the configured one."
--     DEFVAL { false }
--     ::= { tnSapTlsDhcpInfoEntry 13 }
--
-- tnSapTlsDhcpVendorIncludeOptions OBJECT-TYPE
--     SYNTAX          BITS {
--                         systemId  (0),
--                         clientMac (1),
--                         serviceId (2),
--                         tnSapId     (3)
--                     }
--     MAX-ACCESS      read-write
--     STATUS          current
--     DESCRIPTION     "The value of tnSapTlsDhcpVendorIncludeOptions specifies
--                      what is encoded in the Nokia vendor specific
--                      sub-option of option 82.
--
--                      The value of this object is only used when
--                      tnSapTlsDhcpInfoAction is 'replace'."
--     DEFVAL { '0'H }
--     ::= { tnSapTlsDhcpInfoEntry 14 }
--
-- tnSapTlsDhcpVendorOptionString OBJECT-TYPE
--     SYNTAX          DisplayString (SIZE (0..32))
--     MAX-ACCESS      read-write
--     STATUS          current
--     DESCRIPTION     "The value of tnSapTlsDhcpVendorOptionString specifies the
--                      string that goes into the Nokia vendor specific
--                      sub-option of option 82.
--
--                      This string is only used when tnSapTlsDhcpInfoAction is set
--                      to 'replace'."
--     DEFVAL { "" }
--     ::= { tnSapTlsDhcpInfoEntry 15 }

-- --------------------------------------
-- SAP Tls Dhcp Stats Table
-- --------------------------------------
-- tnSapTlsDhcpStatsTable OBJECT-TYPE
--     SYNTAX          SEQUENCE OF SapTlsDhcpStatsEntry
--     MAX-ACCESS      not-accessible
--     STATUS          current
--     DESCRIPTION     "tnSapTlsDhcpStatsTable contains DHCP statistics related
--                      to  a TLS SAP. This table complements tnSapTlsInfoTable,
--                      and  contains  an entry for each Tls SAP. Rows in this
--                      table  are  created  and  deleted automatically by the
--                      system."
--     ::= { tnSapObjs 15 }
--
-- tnSapTlsDhcpStatsEntry OBJECT-TYPE
--     SYNTAX          SapTlsDhcpStatsEntry
--     MAX-ACCESS      not-accessible
--     STATUS          current
--     DESCRIPTION     " DHCP statistics for a TLS SAP."
--     INDEX           { tnSysSwitchId,  tnSvcId, tnSapPortId, tnSapEncapValue }
--     ::= { tnSapTlsDhcpStatsTable 1 }
--
-- SapTlsDhcpStatsEntry ::=
--     SEQUENCE {
--         tnSapTlsDhcpStatsClntSnoopdPckts      Counter32,
--         tnSapTlsDhcpStatsSrvrSnoopdPckts      Counter32,
--         tnSapTlsDhcpStatsClntForwdPckts       Counter32,
--         tnSapTlsDhcpStatsSrvrForwdPckts       Counter32,
--         tnSapTlsDhcpStatsClntDropdPckts       Counter32,
--         tnSapTlsDhcpStatsSrvrDropdPckts       Counter32,
--         tnSapTlsDhcpStatsClntProxRadPckts     Counter32,
--         tnSapTlsDhcpStatsClntProxLSPckts      Counter32,
--         tnSapTlsDhcpStatsGenReleasePckts      Counter32,
--         tnSapTlsDhcpStatsGenForceRenPckts     Counter32
--     }
--
-- tnSapTlsDhcpStatsClntSnoopdPckts OBJECT-TYPE
--     SYNTAX          Counter32
--     MAX-ACCESS      read-only
--     STATUS          current
--     DESCRIPTION     "The value of the object tnSapTlsDhcpStatsClntSnoopdPckts
--                      indicates the number of  DHCP client packets that have
--                      been snooped on this SAP."
--     ::= { tnSapTlsDhcpStatsEntry 1 }
--
-- tnSapTlsDhcpStatsSrvrSnoopdPckts OBJECT-TYPE
--     SYNTAX          Counter32
--     MAX-ACCESS      read-only
--     STATUS          current
--     DESCRIPTION     "The value of the object tnSapTlsDhcpStatsSrvrSnoopdPckts
--                      indicates the number of  DHCP server packets that have
--                      been snooped on this SAP."
--     ::= { tnSapTlsDhcpStatsEntry 2 }
--
-- tnSapTlsDhcpStatsClntForwdPckts OBJECT-TYPE
--     SYNTAX          Counter32
--     MAX-ACCESS      read-only
--     STATUS          current
--     DESCRIPTION     "The value of the object tnSapTlsDhcpStatsClntForwdPckts
--                      indicates the number  of  DHCP  client  packets  that
--                      have been forwarded on this SAP."
--     ::= { tnSapTlsDhcpStatsEntry 3 }
--
-- tnSapTlsDhcpStatsSrvrForwdPckts OBJECT-TYPE
--     SYNTAX          Counter32
--     MAX-ACCESS      read-only
--     STATUS          current
--     DESCRIPTION     "The value of the object tnSapTlsDhcpStatsSrvrForwdPckts
--                      indicates the number of  DHCP  server  packets  that have
--                      been forwarded on this SAP."
--     ::= { tnSapTlsDhcpStatsEntry 4 }
--
-- tnSapTlsDhcpStatsClntDropdPckts OBJECT-TYPE
--     SYNTAX          Counter32
--     MAX-ACCESS      read-only
--     STATUS          current
--     DESCRIPTION     "The value of the object tnSapTlsDhcpStatsClntDropdPckts
--                      indicates the number of  DHCP client packets that have
--                      been dropped on this SAP."
--     ::= { tnSapTlsDhcpStatsEntry 5 }
--
-- tnSapTlsDhcpStatsSrvrDropdPckts OBJECT-TYPE
--     SYNTAX          Counter32
--     MAX-ACCESS      read-only
--     STATUS          current
--     DESCRIPTION     "The value of the object tnSapTlsDhcpStatsSrvrDropdPckts
--                      indicates the number of  DHCP server packets that have
--                      been dropped on this SAP."
--     ::= { tnSapTlsDhcpStatsEntry 6 }
--
-- tnSapTlsDhcpStatsClntProxRadPckts OBJECT-TYPE
--     SYNTAX          Counter32
--     MAX-ACCESS      read-only
--     STATUS          current
--     DESCRIPTION     "The value of the object tnSapTlsDhcpStatsClntProxRadPckts
--                      indicates the number of DHCP client packets that have
--                      been proxied on this SAP based on data received from a
--                      RADIUS server."
--     ::= { tnSapTlsDhcpStatsEntry 7 }
--
-- tnSapTlsDhcpStatsClntProxLSPckts OBJECT-TYPE
--     SYNTAX          Counter32
--     MAX-ACCESS      read-only
--     STATUS          current
--     DESCRIPTION     "The value of the object tnSapTlsDhcpStatsClntProxLSPckts
--                      indicates the number of DHCP client packets that have
--                      been proxied on this SAP based on a lease state. The
--                      lease itself can have been obtained from a DHCP or RADIUS
--                      server. This is the so called lease split functionality."
--     ::= { tnSapTlsDhcpStatsEntry 8 }
--
-- tnSapTlsDhcpStatsGenReleasePckts OBJECT-TYPE
--     SYNTAX          Counter32
--     MAX-ACCESS      read-only
--     STATUS          current
--     DESCRIPTION     "The value of the object tnSapTlsDhcpStatsGenReleasePckts
--                      indicates the number of DHCP RELEASE messages spoofed on
--                      this SAP to the DHCP server."
--     ::= { tnSapTlsDhcpStatsEntry 9 }
--
-- tnSapTlsDhcpStatsGenForceRenPckts OBJECT-TYPE
--     SYNTAX          Counter32
--     MAX-ACCESS      read-only
--     STATUS          current
--     DESCRIPTION     "The value of the object tnSapTlsDhcpStatsGenForceRenPckts
--                      indicates the number of DHCP FORCERENEW messages spoofed
--                      on this SAP to the DHCP clients."
--     ::= { tnSapTlsDhcpStatsEntry 10 }

-- ----------------------------------------
-- SAP Tls Dhcp Lease State Table
-- ----------------------------------------
-- tnSapTlsDhcpLeaseStateTable OBJECT-TYPE
--     SYNTAX          SEQUENCE OF SapTlsDhcpLeaseStateEntry
--     MAX-ACCESS      not-accessible
--     STATUS          obsolete
--     DESCRIPTION     "tnSapTlsDhcpLeaseStateTable contains DHCP lease state info
--                      for a TLS SAP. This table complements tnSapTlsInfoTable,
--                      and contains an entry for each Tls SAP. Rows in this table
--                      are created and deleted automatically by the system.
--                      The content of this table is moved to the
--                      svcDhcpLeaseStateTable."
--     ::= { tnSapObjs 16 }
--
-- tnSapTlsDhcpLeaseStateEntry OBJECT-TYPE
--     SYNTAX          SapTlsDhcpLeaseStateEntry
--     MAX-ACCESS      not-accessible
--     STATUS          obsolete
--     DESCRIPTION     "DHCP Lease State information on a TLS SAP."
--     INDEX           { tnSysSwitchId,  tnSvcId,
--                       tnSapPortId,
--                       tnSapEncapValue,
--                       tnSapTlsDhcpLseStateCiAddr,
--                       tnSapTlsDhcpLseStateChAddr }
--     ::= { tnSapTlsDhcpLeaseStateTable 1 }
--
-- SapTlsDhcpLeaseStateEntry ::=
--     SEQUENCE {
--         tnSapTlsDhcpLseStateCiAddr        IpAddress,
--         tnSapTlsDhcpLseStateChAddr        MacAddress,
--         tnSapTlsDhcpLseStateRemainLseTime Unsigned32,
--         tnSapTlsDhcpLseStateOption82      OCTET STRING,
--         tnSapTlsDhcpLseStatePersistKey    Unsigned32
--     }
--
-- tnSapTlsDhcpLseStateCiAddr OBJECT-TYPE
--     SYNTAX          IpAddress
--     MAX-ACCESS      not-accessible
--     STATUS          obsolete
--     DESCRIPTION     "The value of the object tnSapTlsDhcpLseStateCiAddr indicates
--                      the IP address of the DHCP lease state."
--     ::= { tnSapTlsDhcpLeaseStateEntry 1 }
--
-- tnSapTlsDhcpLseStateChAddr OBJECT-TYPE
--     SYNTAX          MacAddress
--     MAX-ACCESS      not-accessible
--     STATUS          obsolete
--     DESCRIPTION     "The value of the object tnSapTlsDhcpLseStateChAddr indicates
--                      the MAC address of the DHCP lease state."
--     ::= { tnSapTlsDhcpLeaseStateEntry 2 }
--
-- tnSapTlsDhcpLseStateRemainLseTime OBJECT-TYPE
--     SYNTAX          Unsigned32
--     MAX-ACCESS      read-only
--     STATUS          obsolete
--     DESCRIPTION     "The value of the object tnSapTlsDhcpLseStateRemainLseTime
--                      indicates the remaining lease time of the Ip address of
--                      the DHCP lease state.
--                      This object was made obsolete in the 4.0 release."
--     ::= { tnSapTlsDhcpLeaseStateEntry 3 }
--
-- tnSapTlsDhcpLseStateOption82 OBJECT-TYPE
--     SYNTAX          OCTET STRING
--     MAX-ACCESS      read-only
--     STATUS          obsolete
--     DESCRIPTION     "The value of the object tnSapTlsDhcpLseStateOption82
--                      indicates the content of the Option82 for this DHCP
--                      lease state.
--                      This object was made obsolete in the 4.0 release."
--     ::= { tnSapTlsDhcpLeaseStateEntry 4 }
--
-- tnSapTlsDhcpLseStatePersistKey OBJECT-TYPE
--     SYNTAX          Unsigned32
--     MAX-ACCESS      read-only
--     STATUS          obsolete
--     DESCRIPTION     "The value of the object tnSapTlsDhcpLseStatePersistKey
--                      indicates a key value that can be used to track this lease
--                      state in the persistence file.
--                      This object was made obsolete in the 4.0 release."
--     ::= { tnSapTlsDhcpLeaseStateEntry 5 }

-- --------------------------------------------
-- Ingress QoS Scheduler SAP Statistics Table
-- --------------------------------------------
-- tnSapPortIdIngQosSchedStatsTable OBJECT-TYPE
--     SYNTAX          SEQUENCE OF SapPortIdIngQosSchedStatsEntry
--     MAX-ACCESS      not-accessible
--     STATUS          current
--     DESCRIPTION
--         "The tnSapPortIdIngQosSchedStatsTable contains ingress QoS
--          queue SAP statistics. This table is used when the SAP
--          is  a CCAG or LAG in 'link' mode, or an APS."
--     ::= { tnSapObjs 17 }
--
-- tnSapPortIdIngQosSchedStatsEntry OBJECT-TYPE
--     SYNTAX          SapPortIdIngQosSchedStatsEntry
--     MAX-ACCESS      not-accessible
--     STATUS          current
--     DESCRIPTION     "Each entry represents the ingress statistics about a
--                      specific SAP's QoS queue. Entries are created when
--                      a scheduler policy is applied to a SAP."
--     INDEX           { tnSysSwitchId,  tnSvcId, tnSapPortId, tnSapEncapValue,
--                       tnSapPortIdIngQosSchedName, tnSapPortIdIngPortId }
--     ::= { tnSapPortIdIngQosSchedStatsTable 1 }
--
-- SapPortIdIngQosSchedStatsEntry ::=
--     SEQUENCE {
--         tnSapPortIdIngQosSchedName      TNamedItem,
--         tnSapPortIdIngPortId            TmnxPortID,
--         tnSapPortIdIngQosSchedFwdPkts   Counter64,
--         tnSapPortIdIngQosSchedFwdOctets Counter64,
--         tnSapPortIdIngQosSchedCustId    TmnxCustId
--     }
--
-- tnSapPortIdIngQosSchedName OBJECT-TYPE
--     SYNTAX          TNamedItem
--     MAX-ACCESS      not-accessible
--     STATUS          current
--     DESCRIPTION     "The value of tnSapPortIdIngQosSchedName is used as an index
--                      of the ingress QoS scheduler of this SAP."
--     ::= { tnSapPortIdIngQosSchedStatsEntry 1 }
--
-- tnSapPortIdIngPortId OBJECT-TYPE
--     SYNTAX          TmnxPortID
--     MAX-ACCESS      not-accessible
--     STATUS          current
--     DESCRIPTION     "The value of tnSapPortIdIngPortId is used
--                      as an index of the ingress QoS scheduler of this SAP. When
--                      the SAP is an aps/ccag/lag in 'link' mode, this object is
--                      the TmnxPortID of the member-port on which the scheduler is
--                      applied."
--     ::= {tnSapPortIdIngQosSchedStatsEntry 2 }
--
-- tnSapPortIdIngQosSchedFwdPkts OBJECT-TYPE
--     SYNTAX          Counter64
--     MAX-ACCESS      read-only
--     STATUS          current
--     DESCRIPTION     "The value of tnSapPortIdIngQosSchedFwdPkts indicates
--                      the number of forwarded packets, as determined by the SAP
--                      ingress scheduler policy, offered by the Pchip to the
--                      Qchip."
--     ::= { tnSapPortIdIngQosSchedStatsEntry 3 }
--
-- tnSapPortIdIngQosSchedFwdOctets OBJECT-TYPE
--     SYNTAX          Counter64
--     MAX-ACCESS      read-only
--     STATUS          current
--     DESCRIPTION     "The value of tnSapPortIdIngQosSchedFwdOctets indicates
--                      the number of forwarded octets,as determined by the SAP
--                      ingress scheduler policy, offered by the Pchip to the
--                      Qchip."
--     ::= { tnSapPortIdIngQosSchedStatsEntry 4 }
--
-- tnSapPortIdIngQosSchedCustId OBJECT-TYPE
--     SYNTAX          TmnxCustId
--     MAX-ACCESS      read-only
--     STATUS          current
--     DESCRIPTION     "The value of tnSapPortIdIngQosSchedCustId indicates the
--                      Customer ID for the associated service."
--     ::= { tnSapPortIdIngQosSchedStatsEntry 5 }

-- ------------------------------------------------------------
-- Egress QoS Scheduler SAP Statistics Table for Link mode SAPs
-- ------------------------------------------------------------
-- tnSapPortIdEgrQosSchedStatsTable OBJECT-TYPE
--     SYNTAX          SEQUENCE OF SapPortIdEgrQosSchedStatsEntry
--     MAX-ACCESS      not-accessible
--     STATUS          current
--     DESCRIPTION     "The tnSapPortIdEgrQosSchedStatsTable contains egress QoS
--                      queue SAP statistics. This table is used when the SAP
--                      is  a CCAG or LAG in 'link' mode, or an APS."
--     ::= { tnSapObjs 18 }
--
-- tnSapPortIdEgrQosSchedStatsEntry OBJECT-TYPE
--     SYNTAX          SapPortIdEgrQosSchedStatsEntry
--     MAX-ACCESS      not-accessible
--     STATUS          current
--     DESCRIPTION     "Each entry represents the egress statistics about a
--                      specific SAP's QoS queue. Entries are created when
--                      a scheduler policy is applied to a SAP."
--     INDEX           { tnSysSwitchId,  tnSvcId, tnSapPortId, tnSapEncapValue,
--                       tnSapPortIdEgrQosSchedName, tnSapPortIdEgrPortId }
--     ::= { tnSapPortIdEgrQosSchedStatsTable 1 }
--
-- SapPortIdEgrQosSchedStatsEntry ::=
--     SEQUENCE {
--         tnSapPortIdEgrQosSchedName        TNamedItem,
--         tnSapPortIdEgrPortId              TmnxPortID,
--         tnSapPortIdEgrQosSchedFwdPkts     Counter64,
--         tnSapPortIdEgrQosSchedFwdOctets   Counter64,
--         tnSapPortIdEgrQosSchedCustId      TmnxCustId
--     }
--
-- tnSapPortIdEgrQosSchedName OBJECT-TYPE
--     SYNTAX          TNamedItem
--     MAX-ACCESS      not-accessible
--     STATUS          current
--     DESCRIPTION     "The value of tnSapPortIdEgrQosSchedName is used as an index
--                      of the egress QoS scheduler of this SAP."
--     ::= { tnSapPortIdEgrQosSchedStatsEntry 1 }
--
-- tnSapPortIdEgrPortId OBJECT-TYPE
--     SYNTAX          TmnxPortID
--     MAX-ACCESS      not-accessible
--     STATUS          current
--     DESCRIPTION     "The value of tnSapPortIdEgrPortId is used
--                      as an index of the egress QoS scheduler of this SAP. When
--                      the SAP is an aps/ccag/lag in 'link' mode, this object is
--                      the TmnxPortID of the member-port on which the scheduler is
--                      applied."
--     ::= {tnSapPortIdEgrQosSchedStatsEntry 2 }
--
-- tnSapPortIdEgrQosSchedFwdPkts OBJECT-TYPE
--     SYNTAX          Counter64
--     MAX-ACCESS      read-only
--     STATUS          current
--     DESCRIPTION     "The value of tnSapPortIdEgrQosSchedFwdPkts indicates
--                      the number of forwarded packets, as determined by the SAP
--                      egress scheduler policy, offered by the Pchip to the
--                      Qchip."
--     ::= { tnSapPortIdEgrQosSchedStatsEntry 3 }
--
-- tnSapPortIdEgrQosSchedFwdOctets OBJECT-TYPE
--     SYNTAX          Counter64
--     MAX-ACCESS      read-only
--     STATUS          current
--     DESCRIPTION     "The value of tnSapPortIdEgrQosSchedFwdOctets indicates
--                      the number of forwarded octets,as determined by the SAP
--                      egress scheduler policy, offered by the Pchip to the
--                      Qchip."
--     ::= { tnSapPortIdEgrQosSchedStatsEntry 4 }
--
-- tnSapPortIdEgrQosSchedCustId OBJECT-TYPE
--     SYNTAX          TmnxCustId
--     MAX-ACCESS      read-only
--     STATUS          current
--     DESCRIPTION     "The value of tnSapPortIdEgrQosSchedCustId indicates the
--                      Customer ID for the associated service."
--     ::= { tnSapPortIdEgrQosSchedStatsEntry 5 }

-- ------------------------------------------
-- SAP Ingress QoS Queue Table
-- ------------------------------------------
-- tnSapIngQosQueueInfoTable OBJECT-TYPE
--     SYNTAX          SEQUENCE OF SapIngQosQueueInfoEntry
--     MAX-ACCESS      not-accessible
--     STATUS          current
--     DESCRIPTION     "This table is used to override the base parameters
--                      of a queue, as defined in the associated SAP
--                      ingress QoS policy."
--     ::= { tnSapObjs 19 }
--
-- tnSapIngQosQueueInfoEntry OBJECT-TYPE
--     SYNTAX          SapIngQosQueueInfoEntry
--     MAX-ACCESS      not-accessible
--     STATUS          current
--     DESCRIPTION     "Override values for the specified SAP ingress QoS
--                      queue. These values override the corresponding ones
--                      specified in the associated SAP ingress QoS policy."
--     INDEX           { tnSysSwitchId,  tnSvcId,
--                       tnSapPortId,
--                       tnSapEncapValue,
--                       tnSapIngQosQId }
--     ::= { tnSapIngQosQueueInfoTable 1 }
--
-- SapIngQosQueueInfoEntry ::=
--     SEQUENCE {
--         tnSapIngQosQId                TIngressQueueId,
--         tnSapIngQosQRowStatus         RowStatus,
--         tnSapIngQosQLastMgmtChange    TimeStamp,
--         tnSapIngQosQOverrideFlags     TQosQueueAttribute,
--         tnSapIngQosQCBS               TBurstSize,
--         tnSapIngQosQMBS               TBurstSize,
--         tnSapIngQosQHiPrioOnly        TBurstPercentOrDefault,
--         tnSapIngQosQCIRAdaptation     TAdaptationRule,
--         tnSapIngQosQPIRAdaptation     TAdaptationRule,
--         tnSapIngQosQAdminPIR          TPIRRate,
--         tnSapIngQosQAdminCIR          TCIRRate
--     }
--
-- tnSapIngQosQId OBJECT-TYPE
--     SYNTAX          TIngressQueueId
--     MAX-ACCESS      not-accessible
--     STATUS          current
--     DESCRIPTION     "The value of tnSapIngQosQId indicates the ID of the
--                      queue whose parameters are to be overridden."
--     ::= { tnSapIngQosQueueInfoEntry 1 }
--
-- tnSapIngQosQRowStatus OBJECT-TYPE
--     SYNTAX          RowStatus
--     MAX-ACCESS      read-create
--     STATUS          current
--     DESCRIPTION     "The value of tnSapIngQosQRowStatus controls the creation
--                      and deletion of rows in this table."
--     ::= { tnSapIngQosQueueInfoEntry 2 }
--
-- tnSapIngQosQLastMgmtChange OBJECT-TYPE
--     SYNTAX          TimeStamp
--     MAX-ACCESS      read-only
--     STATUS          current
--     DESCRIPTION     "The value of tnSapIngQosQLastMgmtChange indicates the
--                      value of sysUpTime at the time of the last management
--                      change of any writable object of this row."
--     ::= { tnSapIngQosQueueInfoEntry 3 }
--
-- tnSapIngQosQOverrideFlags OBJECT-TYPE
--     SYNTAX          TQosQueueAttribute
--     MAX-ACCESS      read-create
--     STATUS          current
--     DESCRIPTION     "The value of tnSapIngQosQOverrideFlags specifies the
--                      set of attributes whose values have been overridden
--                      via management on this queue. Clearing a given flag
--                      will return the corresponding overridden attribute
--                      to the value defined on the SAP's ingress QoS policy."
--     ::= { tnSapIngQosQueueInfoEntry 4 }
--
-- tnSapIngQosQCBS OBJECT-TYPE
--     SYNTAX          TBurstSize
--     UNITS           "kilo bytes"
--     MAX-ACCESS      read-create
--     STATUS          current
--     DESCRIPTION     "The value of tnSapIngQosQCBS specifies the amount of
--                      reserved buffer space (in kilo bytes) for this queue."
--     DEFVAL { -1 }
--     ::= { tnSapIngQosQueueInfoEntry 5 }
--
-- tnSapIngQosQMBS OBJECT-TYPE
--     SYNTAX          TBurstSize
--     UNITS           "kilo bytes"
--     MAX-ACCESS      read-create
--     STATUS          current
--     DESCRIPTION     "The value of tnSapIngQosQMBS specifies the maximum
--                      amount of buffer space (in kilo bytes) allowed for
--                      this queue."
--     DEFVAL { -1 }
--     ::= { tnSapIngQosQueueInfoEntry 6 }
--
-- tnSapIngQosQHiPrioOnly OBJECT-TYPE
--     SYNTAX          TBurstPercentOrDefault
--     UNITS           "percent"
--     MAX-ACCESS      read-create
--     STATUS          current
--     DESCRIPTION     "The value of tnSapIngQosQHiPrioOnly specifies the
--                      percentage of buffer space for this queue, used
--                      exclusively by high priority packets."
--     DEFVAL { -1 }
--     ::= { tnSapIngQosQueueInfoEntry 7 }
--
-- tnSapIngQosQCIRAdaptation OBJECT-TYPE
--     SYNTAX          TAdaptationRule
--     MAX-ACCESS      read-create
--     STATUS          current
--     DESCRIPTION     "The value of tnSapIngQosQCIRAdaptation specifies the
--                      criteria to use to compute the operational CIR value
--                      for this queue, while maintaining a minimum offset."
--     DEFVAL { closest }
--     ::= { tnSapIngQosQueueInfoEntry 8 }
--
-- tnSapIngQosQPIRAdaptation OBJECT-TYPE
--     SYNTAX          TAdaptationRule
--     MAX-ACCESS      read-create
--     STATUS          current
--     DESCRIPTION     "The value of tnSapIngQosQPIRAdaptation specifies the
--                      criteria to use to compute the operational PIR value
--                      for this queue, while maintaining a minimum offset."
--     DEFVAL { closest }
--     ::= { tnSapIngQosQueueInfoEntry 9 }
--
-- tnSapIngQosQAdminPIR OBJECT-TYPE
--     SYNTAX          TPIRRate
--     UNITS           "kilo bits per second"
--     MAX-ACCESS      read-create
--     STATUS          current
--     DESCRIPTION     "The value of tnSapIngQosQAdminPIR specifies the desired
--                      PIR value for this queue."
--     DEFVAL { -1 }
--     ::= { tnSapIngQosQueueInfoEntry 10 }
--
-- tnSapIngQosQAdminCIR OBJECT-TYPE
--     SYNTAX          TCIRRate
--     UNITS           "kilo bits per second"
--     MAX-ACCESS      read-create
--     STATUS          current
--     DESCRIPTION     "The value of tnSapIngQosQAdminCIR specifies the desired
--                      CIR value for this queue."
--     DEFVAL { -1 }
--     ::= { tnSapIngQosQueueInfoEntry 11 }

-- ----------------------------
-- SAP Egress QoS Queue Table
-- ----------------------------
-- tnSapEgrQosQueueInfoTable OBJECT-TYPE
--     SYNTAX          SEQUENCE OF SapEgrQosQueueInfoEntry
--     MAX-ACCESS      not-accessible
--     STATUS          current
--     DESCRIPTION     "This table is used to override the base parameters
--                      of a queue, as defined in the associated SAP
--                      egress QoS policy."
--     ::= { tnSapObjs 20 }
--
-- tnSapEgrQosQueueInfoEntry OBJECT-TYPE
--     SYNTAX          SapEgrQosQueueInfoEntry
--     MAX-ACCESS      not-accessible
--     STATUS          current
--     DESCRIPTION     "Override values for the specified SAP egress QoS
--                      queue. These values override the corresponding ones
--                      specified in the associated SAP egress QoS policy."
--     INDEX           { tnSysSwitchId,  tnSvcId,
--                       tnSapPortId,
--                       tnSapEncapValue,
--                       tnSapEgrQosQId }
--     ::= { tnSapEgrQosQueueInfoTable 1 }
--
-- SapEgrQosQueueInfoEntry ::=
--     SEQUENCE {
--         tnSapEgrQosQId                TEgressQueueId,
--         tnSapEgrQosQRowStatus         RowStatus,
--         tnSapEgrQosQLastMgmtChange    TimeStamp,
--         tnSapEgrQosQOverrideFlags     TQosQueueAttribute,
--         tnSapEgrQosQCBS               TBurstSize,
--         tnSapEgrQosQMBS               TBurstSize,
--         tnSapEgrQosQHiPrioOnly        TBurstPercentOrDefault,
--         tnSapEgrQosQCIRAdaptation     TAdaptationRule,
--         tnSapEgrQosQPIRAdaptation     TAdaptationRule,
--         tnSapEgrQosQAdminPIR          TPIRRate,
--         tnSapEgrQosQAdminCIR          TCIRRate,
--         tnSapEgrQosQAvgOverhead       Unsigned32
--     }
--
-- tnSapEgrQosQId OBJECT-TYPE
--     SYNTAX          TEgressQueueId
--     MAX-ACCESS      not-accessible
--     STATUS          current
--     DESCRIPTION     "The value of tnSapEgrQosQId indicates the ID of the
--                      queue whose parameters are to be overridden."
--     ::= { tnSapEgrQosQueueInfoEntry 1 }
--
-- tnSapEgrQosQRowStatus OBJECT-TYPE
--     SYNTAX          RowStatus
--     MAX-ACCESS      read-create
--     STATUS          current
--     DESCRIPTION     "The value of tnSapEgrQosQRowStatus controls the creation
--                      and deletion of rows in this table."
--     ::= { tnSapEgrQosQueueInfoEntry 2 }
--
-- tnSapEgrQosQLastMgmtChange OBJECT-TYPE
--     SYNTAX          TimeStamp
--     MAX-ACCESS      read-only
--     STATUS          current
--     DESCRIPTION     "The value of tnSapEgrQosQLastMgmtChange indicates the
--                      value of sysUpTime at the time of the last management
--                      change of any writable object of this row."
--     ::= { tnSapEgrQosQueueInfoEntry 3 }
--
-- tnSapEgrQosQOverrideFlags OBJECT-TYPE
--     SYNTAX          TQosQueueAttribute
--     MAX-ACCESS      read-create
--     STATUS          current
--     DESCRIPTION     "The value of tnSapEgrQosQOverrideFlags specifies the
--                      set of attributes whose values have been overridden
--                      via management on this queue. Clearing a given flag
--                      will return the corresponding overridden attribute
--                      to the value defined on the SAP's ingress QoS policy."
--     ::= { tnSapEgrQosQueueInfoEntry 4 }
--
-- tnSapEgrQosQCBS OBJECT-TYPE
--     SYNTAX          TBurstSize
--     UNITS           "kilo bytes"
--     MAX-ACCESS      read-create
--     STATUS          current
--     DESCRIPTION     "The value of tnSapEgrQosQCBS specifies the amount of
--                      reserved buffer space (in kilo bytes) for this queue."
--     DEFVAL { -1 }
--     ::= { tnSapEgrQosQueueInfoEntry 5 }
--
-- tnSapEgrQosQMBS OBJECT-TYPE
--     SYNTAX          TBurstSize
--     UNITS           "kilo bytes"
--     MAX-ACCESS      read-create
--     STATUS          current
--     DESCRIPTION     "The value of tnSapEgrQosQMBS specifies the maximum
--                      amount of buffer space (in kilo bytes) allowed for
--                      this queue."
--     DEFVAL { -1 }
--     ::= { tnSapEgrQosQueueInfoEntry 6 }
--
-- tnSapEgrQosQHiPrioOnly OBJECT-TYPE
--     SYNTAX          TBurstPercentOrDefault
--     UNITS           "percent"
--     MAX-ACCESS      read-create
--     STATUS          current
--     DESCRIPTION     "The value of tnSapEgrQosQHiPrioOnly specifies the
--                      percentage of buffer space for this queue, used
--                      exclusively by high priority packets."
--     DEFVAL { -1 }
--     ::= { tnSapEgrQosQueueInfoEntry 7 }
--
-- tnSapEgrQosQCIRAdaptation OBJECT-TYPE
--     SYNTAX          TAdaptationRule
--     MAX-ACCESS      read-create
--     STATUS          current
--     DESCRIPTION     "The value of tnSapEgrQosQCIRAdaptation specifies the
--                      criteria to use to compute the operational CIR value
--                      for this queue, while maintaining a minimum offset."
--     DEFVAL { closest }
--     ::= { tnSapEgrQosQueueInfoEntry 8 }
--
-- tnSapEgrQosQPIRAdaptation OBJECT-TYPE
--     SYNTAX          TAdaptationRule
--     MAX-ACCESS      read-create
--     STATUS          current
--     DESCRIPTION     "The value of tnSapEgrQosQPIRAdaptation specifies the
--                      criteria to use to compute the operational PIR value
--                      for this queue, while maintaining a minimum offset."
--     DEFVAL { closest }
--     ::= { tnSapEgrQosQueueInfoEntry 9 }
--
-- tnSapEgrQosQAdminPIR OBJECT-TYPE
--     SYNTAX          TPIRRate
--     UNITS           "kilo bits per second"
--     MAX-ACCESS      read-create
--     STATUS          current
--     DESCRIPTION     "The value of tnSapEgrQosQAdminPIR specifies the desired
--                      PIR value for this queue."
--     DEFVAL { -1 }
--     ::= { tnSapEgrQosQueueInfoEntry 10 }
--
-- tnSapEgrQosQAdminCIR OBJECT-TYPE
--     SYNTAX          TCIRRate
--     UNITS           "kilo bits per second"
--     MAX-ACCESS      read-create
--     STATUS          current
--     DESCRIPTION     "The value of tnSapEgrQosQAdminCIR specifies the desired
--                      CIR value for this queue."
--     DEFVAL { -1 }
--     ::= { tnSapEgrQosQueueInfoEntry 11 }
--
-- tnSapEgrQosQAvgOverhead   OBJECT-TYPE
--     SYNTAX          Unsigned32 (0..10000)
--     MAX-ACCESS      read-create
--     STATUS          current
--     DESCRIPTION     "The value of tnSapEgrQosQAvgOverhead specifies the
--                      encapsulation overhead, in hundredths of a percent,
--                      used to translate packet-based rate to frame-based
--                      rate and vice versa."
--     DEFVAL      { 0 }
--     ::= { tnSapEgrQosQueueInfoEntry 12 }

-- ------------------------------------
-- SAP Ingress QoS Scheduler Table
-- ------------------------------------
-- tnSapIngQosSchedInfoTable OBJECT-TYPE
--     SYNTAX          SEQUENCE OF SapIngQosSchedInfoEntry
--     MAX-ACCESS      not-accessible
--     STATUS          current
--     DESCRIPTION     "This table is used to override the base parameters
--                      of a virtual scheduler, as defined in the associated
--                      SAP ingress scheduler policy."
--     ::= { tnSapObjs 21 }
--
-- tnSapIngQosSchedInfoEntry OBJECT-TYPE
--     SYNTAX          SapIngQosSchedInfoEntry
--     MAX-ACCESS      not-accessible
--     STATUS          current
--     DESCRIPTION     "Override values for the specified SAP ingress virtual
--                      scheduler. These values override the corresponding
--                      ones specified in the associated SAP ingress scheduler
--                      policy."
--     INDEX           { tnSysSwitchId,  tnSvcId,
--                       tnSapPortId,
--                       tnSapEncapValue,
--                       IMPLIED tnSapIngQosSName }
--     ::= { tnSapIngQosSchedInfoTable 1 }
--
-- SapIngQosSchedInfoEntry ::=
--     SEQUENCE {
--         tnSapIngQosSName              TNamedItem,
--         tnSapIngQosSRowStatus         RowStatus,
--         tnSapIngQosSLastMgmtChange    TimeStamp,
--         tnSapIngQosSOverrideFlags     TVirtSchedAttribute,
--         tnSapIngQosSPIR               TPIRRate,
--         tnSapIngQosSCIR               TCIRRate,
--         tnSapIngQosSSummedCIR         TruthValue
--     }
--
-- tnSapIngQosSName OBJECT-TYPE
--     SYNTAX          TNamedItem
--     MAX-ACCESS      not-accessible
--     STATUS          current
--     DESCRIPTION     "The value of tnSapIngQosSName indicates the name of
--                      the virtual scheduler whose parameters are to be
--                      overridden."
--     ::= { tnSapIngQosSchedInfoEntry 1 }
--
-- tnSapIngQosSRowStatus OBJECT-TYPE
--     SYNTAX          RowStatus
--     MAX-ACCESS      read-create
--     STATUS          current
--     DESCRIPTION     "The value of tnSapIngQosSRowStatus controls the creation
--                      and deletion of rows in this table."
--     ::= { tnSapIngQosSchedInfoEntry 2 }
--
-- tnSapIngQosSLastMgmtChange OBJECT-TYPE
--     SYNTAX          TimeStamp
--     MAX-ACCESS      read-only
--     STATUS          current
--     DESCRIPTION     "The value of tnSapIngQosSLastMgmtChange indicates the
--                      value of sysUpTime at the time of the last management
--                      change of any writable object of this row."
--     ::= { tnSapIngQosSchedInfoEntry 3 }
--
-- tnSapIngQosSOverrideFlags OBJECT-TYPE
--     SYNTAX          TVirtSchedAttribute
--     MAX-ACCESS      read-create
--     STATUS          current
--     DESCRIPTION     "The value of tnSapIngQosSOverrideFlags specifies the
--                      set of attributes whose values have been overridden
--                      via management on this virtual scheduler. Clearing a
--                      given flag will return the corresponding overridden
--                      attribute to the value defined on the SAP's ingress
--                      scheduler policy."
--     ::= { tnSapIngQosSchedInfoEntry 4 }
--
-- tnSapIngQosSPIR OBJECT-TYPE
--     SYNTAX          TPIRRate
--     UNITS           "kilo bits per second"
--     MAX-ACCESS      read-create
--     STATUS          current
--     DESCRIPTION     "The value of tnSapIngQosSPIR specifies the desired
--                      PIR value for this virtual scheduler."
--     DEFVAL { -1 }
--     ::= { tnSapIngQosSchedInfoEntry 5 }
--
-- tnSapIngQosSCIR OBJECT-TYPE
--     SYNTAX          TCIRRate
--     UNITS           "kilo bits per second"
--     MAX-ACCESS      read-create
--     STATUS          current
--     DESCRIPTION     "The value of tnSapIngQosSCIR specifies the desired
--                      CIR value for this virtual scheduler."
--     DEFVAL { -1 }
--     ::= { tnSapIngQosSchedInfoEntry 6 }
--
-- tnSapIngQosSSummedCIR     OBJECT-TYPE
--     SYNTAX          TruthValue
--     MAX-ACCESS      read-create
--     STATUS          current
--     DESCRIPTION     "The value of tnSapIngQosSSummedCIR specifies if the CIR
--                      should be used as the summed CIR values of the children
--                      schedulers or queues. If set to 'true', the applicable
--                      scheduler CIR (tnSapIngQosSCIR) loses its meaning."
--     DEFVAL { true }
--     ::= { tnSapIngQosSchedInfoEntry 7 }

-- ------------------------------------
-- SAP Egress QoS Scheduler Table
-- ------------------------------------
-- tnSapEgrQosSchedInfoTable OBJECT-TYPE
--     SYNTAX          SEQUENCE OF SapEgrQosSchedInfoEntry
--     MAX-ACCESS      not-accessible
--     STATUS          current
--     DESCRIPTION     "This table is used to override the base parameters
--                      of a virtual scheduler, as defined in the associated
--                      SAP egress scheduler policy."
--     ::= { tnSapObjs 22 }
--
-- tnSapEgrQosSchedInfoEntry OBJECT-TYPE
--     SYNTAX          SapEgrQosSchedInfoEntry
--     MAX-ACCESS      not-accessible
--     STATUS          current
--     DESCRIPTION     "Override values for the specified SAP egress virtual
--                      scheduler. These values override the corresponding
--                      ones specified in the associated SAP egress scheduler
--                      policy."
--     INDEX           { tnSysSwitchId,  tnSvcId,
--                       tnSapPortId,
--                       tnSapEncapValue,
--                       IMPLIED tnSapEgrQosSName }
--     ::= { tnSapEgrQosSchedInfoTable 1 }
--
-- SapEgrQosSchedInfoEntry ::=
--     SEQUENCE {
--         tnSapEgrQosSName              TNamedItem,
--         tnSapEgrQosSRowStatus         RowStatus,
--         tnSapEgrQosSLastMgmtChange    TimeStamp,
--         tnSapEgrQosSOverrideFlags     TVirtSchedAttribute,
--         tnSapEgrQosSPIR               TPIRRate,
--         tnSapEgrQosSCIR               TCIRRate,
--         tnSapEgrQosSSummedCIR         TruthValue
--     }
--
-- tnSapEgrQosSName OBJECT-TYPE
--     SYNTAX          TNamedItem
--     MAX-ACCESS      not-accessible
--     STATUS          current
--     DESCRIPTION     "The value of tnSapEgrQosSName indicates the name of
--                      the virtual scheduler whose parameters are to be
--                      overridden."
--     ::= { tnSapEgrQosSchedInfoEntry 1 }
--
-- tnSapEgrQosSRowStatus OBJECT-TYPE
--     SYNTAX          RowStatus
--     MAX-ACCESS      read-create
--     STATUS          current
--     DESCRIPTION     "The value of tnSapEgrQosSRowStatus controls the creation
--                      and deletion of rows in this table."
--     ::= { tnSapEgrQosSchedInfoEntry 2 }
--
-- tnSapEgrQosSLastMgmtChange OBJECT-TYPE
--     SYNTAX          TimeStamp
--     MAX-ACCESS      read-only
--     STATUS          current
--     DESCRIPTION     "The value of tnSapEgrQosSLastMgmtChange indicates the
--                      value of sysUpTime at the time of the last management
--                      change of any writable object of this row."
--     ::= { tnSapEgrQosSchedInfoEntry 3 }
--
-- tnSapEgrQosSOverrideFlags OBJECT-TYPE
--     SYNTAX          TVirtSchedAttribute
--     MAX-ACCESS      read-create
--     STATUS          current
--     DESCRIPTION     "The value of tnSapEgrQosSOverrideFlags specifies the
--                      set of attributes whose values have been overridden
--                      via management on this virtual scheduler. Clearing a
--                      given flag will return the corresponding overridden
--                      attribute to the value defined on the SAP's egress
--                      scheduler policy."
--     ::= { tnSapEgrQosSchedInfoEntry 4 }
--
-- tnSapEgrQosSPIR OBJECT-TYPE
--     SYNTAX          TPIRRate
--     UNITS           "kilo bits per second"
--     MAX-ACCESS      read-create
--     STATUS          current
--     DESCRIPTION     "The value of tnSapEgrQosSPIR specifies the desired
--                      PIR value for this virtual scheduler."
--     DEFVAL { -1 }
--     ::= { tnSapEgrQosSchedInfoEntry 5 }
--
-- tnSapEgrQosSCIR OBJECT-TYPE
--     SYNTAX          TCIRRate
--     UNITS           "kilo bits per second"
--     MAX-ACCESS      read-create
--     STATUS          current
--     DESCRIPTION     "The value of tnSapEgrQosSCIR specifies the desired
--                      CIR value for this virtual scheduler."
--     DEFVAL { -1 }
--     ::= { tnSapEgrQosSchedInfoEntry 6 }
--
-- tnSapEgrQosSSummedCIR     OBJECT-TYPE
--     SYNTAX          TruthValue
--     MAX-ACCESS      read-create
--     STATUS          current
--     DESCRIPTION     "The value of tnSapEgrQosSSummedCIR specifies if the CIR
--                      should be used as the summed CIR values of the children
--                      schedulers or queues. If set to 'true', the applicable
--                      scheduler CIR (tnSapEgrQosSCIR) loses its meaning."
--     DEFVAL { true }
--     ::= { tnSapEgrQosSchedInfoEntry 7 }

-- --------------------------------------
-- SAP Subscriber Management Table
-- --------------------------------------
-- tnSapSubMgmtInfoTable OBJECT-TYPE
--     SYNTAX          SEQUENCE OF SapSubMgmtInfoEntry
--     MAX-ACCESS      not-accessible
--     STATUS          current
--     DESCRIPTION     "A table that contains SAP subscriber management
--                      information."
--     ::= { tnSapObjs 23 }
--
-- tnSapSubMgmtInfoEntry OBJECT-TYPE
--     SYNTAX          SapSubMgmtInfoEntry
--     MAX-ACCESS      not-accessible
--     STATUS          current
--     DESCRIPTION     "Subscriber management specific information about a SAP."
--     INDEX           { tnSysSwitchId,  tnSvcId, tnSapPortId, tnSapEncapValue }
--     ::= { tnSapSubMgmtInfoTable 1 }
--
-- SapSubMgmtInfoEntry ::=
--     SEQUENCE {
--         tnSapSubMgmtAdminStatus           TmnxEnabledDisabled,
--         tnSapSubMgmtDefSubProfile         ServObjName,
--         tnSapSubMgmtDefSlaProfile         ServObjName,
--         tnSapSubMgmtSubIdentPolicy        ServObjName,
--         tnSapSubMgmtSubscriberLimit       Unsigned32,
--         tnSapSubMgmtProfiledTrafficOnly   TruthValue,
--         tnSapSubMgmtNonSubTrafficSubIdent DisplayString,
--         tnSapSubMgmtNonSubTrafficSubProf  ServObjName,
--         tnSapSubMgmtNonSubTrafficSlaProf  ServObjName,
--         tnSapSubMgmtMacDaHashing          TruthValue,
--         tnSapSubMgmtDefSubIdent           INTEGER,
--         tnSapSubMgmtDefSubIdentString     DisplayString,
--         tnSapSubMgmtDefAppProfile         ServObjName,
--         tnSapSubMgmtNonSubTrafficAppProf  ServObjName
--     }
--
-- tnSapSubMgmtAdminStatus OBJECT-TYPE
--     SYNTAX          TmnxEnabledDisabled
--     MAX-ACCESS      read-create
--     STATUS          current
--     DESCRIPTION     "The value of tnSapSubMgmtAdminStatus specifies whether
--                      enhanced subscriber management is enabled on this SAP."
--     DEFVAL { disabled }
--     ::= { tnSapSubMgmtInfoEntry 1 }
--
-- tnSapSubMgmtDefSubProfile OBJECT-TYPE
--     SYNTAX          ServObjName
--     MAX-ACCESS      read-create
--     STATUS          current
--     DESCRIPTION     "The value of tnSapSubMgmtDefSubProfile specifies the default
--                      subscriber profile applicable on this SAP. The
--                      corresponding profile is defined in
--                      TIMETRA-SUBSCRIBER-MGMT-MIB::tmnxSubProfileTable.
--
--                      A value of 'default' is not allowed for this object."
--     DEFVAL { "" }
--     ::= { tnSapSubMgmtInfoEntry 2 }
--
-- tnSapSubMgmtDefSlaProfile OBJECT-TYPE
--     SYNTAX          ServObjName
--     MAX-ACCESS      read-create
--     STATUS          current
--     DESCRIPTION     "The value of tnSapSubMgmtDefSlaProfile specifies the default
--                      SLA profile applicable on this SAP. The corresponding
--                      profile is defined in
--                      TIMETRA-SUBSCRIBER-MGMT-MIB::tmnxSLAProfileTable."
--     DEFVAL { "" }
--     ::= { tnSapSubMgmtInfoEntry 3 }
--
-- tnSapSubMgmtSubIdentPolicy OBJECT-TYPE
--     SYNTAX          ServObjName
--     MAX-ACCESS      read-create
--     STATUS          current
--     DESCRIPTION     "The value of tnSapSubMgmtSubIdentPolicy specifies the
--                      subscriber identification policy applicable on this SAP.
--                      The corresponding policy is defined in
--                      TIMETRA-SUBSCRIBER-MGMT-MIB::tmnxSubIdentPolicyTable."
--     DEFVAL { "" }
--     ::= { tnSapSubMgmtInfoEntry 4 }
--
-- tnSapSubMgmtSubscriberLimit OBJECT-TYPE
--     SYNTAX          Unsigned32 (0..20000)
--     MAX-ACCESS      read-create
--     STATUS          current
--     DESCRIPTION     "The value of tnSapSubMgmtSubscriberLimit specifies the
--                      maximum number of subscribers allowed for this SAP.
--
--                      If the value is 0, there is no limit. Only if the value is
--                      1, the 'single-sub-parameters' defined with objects
--                      tnSapSubMgmtProfiledTrafficOnly,
--                      tnSapSubMgmtNonSubTrafficSubProf and
--                      tnSapSubMgmtNonSubTrafficSlaProf are meaningful."
--     DEFVAL { 1 }
--     ::= { tnSapSubMgmtInfoEntry 5 }
--
-- tnSapSubMgmtProfiledTrafficOnly OBJECT-TYPE
--     SYNTAX          TruthValue
--     MAX-ACCESS      read-create
--     STATUS          current
--     DESCRIPTION     "The value of tnSapSubMgmtProfiledTrafficOnly specifies
--                      whether only profiled traffic is applicable for this SAP.
--                      If set to 'true', all SAP queues will be deleted.
--
--                      The value of this object is only meaningful if
--                      tnSapSubMgmtSubscriberLimit is set to 1."
--     DEFVAL { false }
--     ::= { tnSapSubMgmtInfoEntry 6 }
--
-- tnSapSubMgmtNonSubTrafficSubIdent OBJECT-TYPE
--     SYNTAX          DisplayString (SIZE (0..32))
--     MAX-ACCESS      read-create
--     STATUS          current
--     DESCRIPTION     "The value of tnSapSubMgmtNonSubTrafficSubIdent specifies the
--                      subscriber identification applicable on this SAP for all
--                      non-subscriber traffic.
--
--                      The value of this object is only meaningful if
--                      tnSapSubMgmtSubscriberLimit is set to 1."
--     DEFVAL { "" }
--     ::= { tnSapSubMgmtInfoEntry 7 }
--
-- tnSapSubMgmtNonSubTrafficSubProf OBJECT-TYPE
--     SYNTAX          ServObjName
--     MAX-ACCESS      read-create
--     STATUS          current
--     DESCRIPTION     "The value of tnSapSubMgmtNonSubTrafficSubProf specifies the
--                      subscriber profile applicable on this SAP for all
--                      non-subscriber traffic.
--
--                      The value of this object is only meaningful if
--                      tnSapSubMgmtSubscriberLimit is set to 1."
--     DEFVAL { "" }
--     ::= { tnSapSubMgmtInfoEntry 8 }
--
-- tnSapSubMgmtNonSubTrafficSlaProf OBJECT-TYPE
--     SYNTAX          ServObjName
--     MAX-ACCESS      read-create
--     STATUS          current
--     DESCRIPTION     "The value of tnSapSubMgmtNonSubTrafficSlaProf specifies the
--                      SLA profile applicable on this SAP for all non-subscriber
--                      traffic.
--
--                      The value of this object is only meaningful if
--                      tnSapSubMgmtSubscriberLimit is set to 1."
--     DEFVAL { "" }
--     ::= { tnSapSubMgmtInfoEntry 9 }
--
-- tnSapSubMgmtMacDaHashing OBJECT-TYPE
--     SYNTAX          TruthValue
--     MAX-ACCESS      read-create
--     STATUS          current
--     DESCRIPTION     "The value of tnSapSubMgmtMacDaHashing specifies whether
--                      subscriber traffic egressing a LAG SAP has its egress LAG
--                      link selected by a function of the MAC destination address
--                      instead of subscriber id.
--
--                      The value of this object is only meaningful if
--                      tnSapSubMgmtAdminStatus is set to 'enabled' and can only
--                      be configured for TLS services."
--     DEFVAL { false }
--     ::= { tnSapSubMgmtInfoEntry 10 }
--
-- tnSapSubMgmtDefSubIdent OBJECT-TYPE
--     SYNTAX          INTEGER {
--                         useSapId  (1),
--                         useString (2)
--                     }
--     MAX-ACCESS      read-create
--     STATUS          current
--     DESCRIPTION     "The value of tnSapSubMgmtDefSubIdent specifies what is
--                      used as the default subscriber identification applicable
--                      on this SAP.
--
--                      This value is used in case no other source (like Radius)
--                      provides a subscriber identification string.
--
--                      If the value of this objects is set to 'useSapId',
--                      the SAP-id is used as the default subscriber identification
--                      string. In this case, tnSapSubMgmtDefSubIdentString must
--                      contain the empty string.
--                      If the value of this object is set to 'useString',
--                      the value of tnSapSubMgmtDefSubIdentString is used as the
--                      default subscriber identification string. In this case,
--                      an empty tnSapSubMgmtDefSubIdentString means that there is no
--                      default subscriber identification configured."
--     DEFVAL { useString }
--     ::= { tnSapSubMgmtInfoEntry 11 }
--
-- tnSapSubMgmtDefSubIdentString OBJECT-TYPE
--     SYNTAX          DisplayString (SIZE (0..32))
--     MAX-ACCESS      read-create
--     STATUS          current
--     DESCRIPTION     "The value of tnSapSubMgmtDefSubIdentString specifies the
--                      default subscriber identification string applicable on
--                      this SAP."
--     DEFVAL { "" }
--     ::= { tnSapSubMgmtInfoEntry 12 }
--
-- tnSapSubMgmtDefAppProfile OBJECT-TYPE
--     SYNTAX          ServObjName
--     MAX-ACCESS      read-create
--     STATUS          current
--     DESCRIPTION     "The value of tnSapSubMgmtDefAppProfile specifies the default
--                      application profile applicable on this SAP. The
--                      corresponding profile is defined in
--                      TIMETRA-BSX-NG-MIB::tmnxBsxAppProfTable."
--     DEFVAL { "" }
--     ::= { tnSapSubMgmtInfoEntry 13 }
--
-- tnSapSubMgmtNonSubTrafficAppProf OBJECT-TYPE
--     SYNTAX          ServObjName
--     MAX-ACCESS      read-create
--     STATUS          current
--     DESCRIPTION     "The value of tnSapSubMgmtNonSubTrafficAppProf specifies the
--                      application profile applicable on this SAP for all
--                      non-subscriber traffic.
--
--                      The value of this object is only meaningful if
--                      tnSapSubMgmtSubscriberLimit is set to 1."
--     DEFVAL { "" }
--     ::= { tnSapSubMgmtInfoEntry 14 }

-- -----------------------------------------
-- SAP TLS MSTI Table
-- -----------------------------------------
-- tnSapTlsMstiTable OBJECT-TYPE
--     SYNTAX          SEQUENCE OF SapTlsMstiEntry
--     MAX-ACCESS      not-accessible
--     STATUS          current
--     DESCRIPTION     "This table contains Multiple Spanning Tree Instance
--                      information for the SAP. Each management VPLS running
--                      MSTP can have upto 15 MSTI. An entry in this table is
--                      automatically created when a tlsMstiEntry is created."
--     ::= { tnSapObjs 24 }
--
-- tnSapTlsMstiEntry OBJECT-TYPE
--     SYNTAX          SapTlsMstiEntry
--     MAX-ACCESS      not-accessible
--     STATUS          current
--     DESCRIPTION     "Information about a specific MSTI for a SAP."
--     INDEX           { tnSysSwitchId,  tnSvcId, tnSapPortId, tnSapEncapValue, tnTlsMstiInstanceId}
--     ::= { tnSapTlsMstiTable 1 }
--
-- SapTlsMstiEntry ::=
--     SEQUENCE {
--         tnSapTlsMstiPriority          Integer32,
--         tnSapTlsMstiPathCost          INTEGER,
--         tnSapTlsMstiLastMgmtChange    TimeStamp,
--         tnSapTlsMstiPortRole          StpPortRole,
--         tnSapTlsMstiPortState         TStpPortState,
--         tnSapTlsMstiDesignatedBridge  BridgeId,
--         tnSapTlsMstiDesignatedPort    Integer32
--     }
--
-- tnSapTlsMstiPriority OBJECT-TYPE
--     SYNTAX          Integer32 (0..255)
--     MAX-ACCESS      read-write
--     STATUS          current
--     DESCRIPTION     "The value of the object tnSapTlsMstiPriority specifies
--                      the value of the port priority field which is contained in
--                      the most significant 4 bits of the 16-bit Port ID
--                      associated with this SAP and MSTI. As only the most
--                      significant 4 bits of the value are used, the actual value
--                      of this object is limited to multiples of 16: e.g. the
--                      agent rounds down the value to one of: 0, 16, 32, .. ,
--                      224, 240."
--     DEFVAL          { 128 }
--     ::= { tnSapTlsMstiEntry 1 }
--
-- tnSapTlsMstiPathCost OBJECT-TYPE
--     SYNTAX          INTEGER (1..200000000)
--     MAX-ACCESS      read-write
--     STATUS          current
--     DESCRIPTION     "The value of the object tnSapTlsMstiPathCost specifies the
--                      contribution of this port to the MSTI path cost of paths
--                      towards the spanning tree regional root which include this
--                      port."
--     DEFVAL          { 10 }
--     ::= { tnSapTlsMstiEntry 2 }
--
-- tnSapTlsMstiLastMgmtChange OBJECT-TYPE
--     SYNTAX          TimeStamp
--     MAX-ACCESS      read-only
--     STATUS          current
--     DESCRIPTION     "The value of the object tnSapTlsMstiLastMgmtChange indicates
--                      the value of sysUpTime at the time of the most recent
--                      management-initiated change to this SAP MSTI information."
--     ::= { tnSapTlsMstiEntry 3 }
--
-- tnSapTlsMstiPortRole OBJECT-TYPE
--     SYNTAX          StpPortRole
--     MAX-ACCESS      read-only
--     STATUS          current
--     DESCRIPTION     "tnSapTlsMstiPortRole indicates the current role of the
--                      tnSap in the MSTI as defined by the Spanning Tree Protocol."
--     ::= { tnSapTlsMstiEntry 4 }
--
-- tnSapTlsMstiPortState OBJECT-TYPE
--     SYNTAX          TStpPortState
--     MAX-ACCESS      read-only
--     STATUS          current
--     DESCRIPTION     "The value of the object tnSapTlsMstiPortState indicates the
--                      port's current state as defined by application of the
--                      Spanning Tree Protocol. This state controls what action a
--                      port takes on reception of a frame. If the bridge has
--                      detected a port that is malfunctioning it will
--                      place that port into the 'broken' state."
--     ::= { tnSapTlsMstiEntry 5 }
--
-- tnSapTlsMstiDesignatedBridge OBJECT-TYPE
--     SYNTAX          BridgeId
--     MAX-ACCESS      read-only
--     STATUS          current
--     DESCRIPTION     "The value of the object tnSapTlsMstiDesignatedBridge
--                      indicates  the Bridge Identifier of the bridge which this
--                      port considers to be the Designated Bridge for this port's
--                      segment for this MSTI."
--     ::= { tnSapTlsMstiEntry 6 }
--
-- tnSapTlsMstiDesignatedPort OBJECT-TYPE
--     SYNTAX          Integer32
--     MAX-ACCESS      read-only
--     STATUS          current
--     DESCRIPTION     "The value of the object tnSapTlsMstiDesignatedPort indicates
--                      the Port Identifier of the port on the Designated Bridge
--                      for this port's segment for this MSTI."
--     ::= { tnSapTlsMstiEntry 7 }

-- -------------------------------------
-- IPIPE SAP Table
-- -------------------------------------
-- tnSapIpipeInfoTable OBJECT-TYPE
--     SYNTAX          SEQUENCE OF SapIpipeInfoEntry
--     MAX-ACCESS      not-accessible
--     STATUS          current
--     DESCRIPTION     "A table that contains IPIPE specific SAP information."
--     ::= { tnSapObjs 25 }
--
-- tnSapIpipeInfoEntry OBJECT-TYPE
--     SYNTAX          SapIpipeInfoEntry
--     MAX-ACCESS      not-accessible
--     STATUS          current
--     DESCRIPTION     "IPIPE specific information about a SAP."
--     INDEX           { tnSysSwitchId,  tnSvcId, tnSapPortId, tnSapEncapValue }
--     ::= { tnSapIpipeInfoTable 1 }
--
-- SapIpipeInfoEntry ::=
--     SEQUENCE {
--         tnSapIpipeCeInetAddressType           InetAddressType,
--         tnSapIpipeCeInetAddress               InetAddress,
--         tnSapIpipeMacRefreshInterval          Unsigned32,
--         tnSapIpipeMacAddress                  MacAddress,
--         tnSapIpipeArpedMacAddress             MacAddress,
--         tnSapIpipeArpedMacAddressTimeout      Unsigned32,
--         tnSapIpipeDiscoveredCeInetAddrType    InetAddressType,
--         tnSapIpipeDiscoveredCeInetAddr        InetAddress,
--         tnSapIpipeUseBroadcastMac             TruthValue,
--         tnSapIpipeUsingBroadcastMac           TruthValue
--     }
--
-- tnSapIpipeCeInetAddressType OBJECT-TYPE
--     SYNTAX          InetAddressType
--     MAX-ACCESS      read-write
--     STATUS          current
--     DESCRIPTION     "The value of the object tnSapIpipeCeInetAddressType
--                      specifies the addresstype of the local end host IP
--                      of an IPIPE.
--
--                      This object is only configurable if the value of
--                      'svcIpipeCeAddressDiscovery' is 'disabled."
--     ::= { tnSapIpipeInfoEntry 1}
--
-- tnSapIpipeCeInetAddress OBJECT-TYPE
--     SYNTAX          InetAddress (SIZE(0|4))
--     MAX-ACCESS      read-write
--     STATUS          current
--     DESCRIPTION     "The type of this address is determined by the value of
--                      the tnSapIpipeCeInetAddressType object.
--
--                      This object specifies the IPv4 address of the
--                      local end host of an IPIPE.
--
--                      This object is only configurable if the value of
--                      'svcIpipeCeAddressDiscovery' is 'disabled."
--     ::= { tnSapIpipeInfoEntry 2 }
--
-- tnSapIpipeMacRefreshInterval OBJECT-TYPE
--     SYNTAX      Unsigned32 (0..65535)
--     UNITS       "seconds"
--     MAX-ACCESS  read-write
--     STATUS      current
--     DESCRIPTION
--         "The value of tnSapIpipeMacRefreshInterval specifies the interval
--          between successive attempts to refresh the MAC address of the CE
--          device associated with an Ethernet ipipe SAP. If no other event
--          (such as reception of an ARP request from the CE) occurs that
--          would refresh the MAC address before the end of the interval,
--          an ARP request will be originated from the IPIPE SAP."
--     DEFVAL { 14400 }
--     ::= { tnSapIpipeInfoEntry 3 }
--
-- tnSapIpipeMacAddress  OBJECT-TYPE
--     SYNTAX         MacAddress
--     MAX-ACCESS     read-write
--     STATUS         current
--     DESCRIPTION    "The value of the object tnSapIpipeMacAddress specifies
--                     the MAC address of an IPIPE Ethernet SAP."
--     ::= { tnSapIpipeInfoEntry 4 }
--
-- tnSapIpipeArpedMacAddress  OBJECT-TYPE
--     SYNTAX         MacAddress
--     MAX-ACCESS     read-only
--     STATUS         current
--     DESCRIPTION    "The value of the object tnSapIpipeArpedMacAddress indicates
--                     the MAC address of the local end host."
--     ::= { tnSapIpipeInfoEntry 5 }
--
-- tnSapIpipeArpedMacAddressTimeout  OBJECT-TYPE
--     SYNTAX      Unsigned32 (0..65535)
--     MAX-ACCESS     read-only
--     STATUS         current
--     DESCRIPTION    "The value of the object tnSapIpipeArpedMacAddressTimeout
--                     indicates the number of seconds to wait for the
--                     tnSapIpipeArpedMacAddress to be re-refreshed."
--     ::= { tnSapIpipeInfoEntry 6 }
--
-- tnSapIpipeDiscoveredCeInetAddrType OBJECT-TYPE
--     SYNTAX          InetAddressType
--     MAX-ACCESS      read-only
--     STATUS          current
--     DESCRIPTION     "The value of the object tnSapIpipeDiscoveredCeInetAddrType
--                      indicates the addresstype of the local end discovered
--                      host IP of an IPIPE SAP."
--     ::= { tnSapIpipeInfoEntry 7}
--
-- tnSapIpipeDiscoveredCeInetAddr OBJECT-TYPE
--     SYNTAX          InetAddress (SIZE(0|4))
--     MAX-ACCESS      read-only
--     STATUS          current
--     DESCRIPTION     "The type of this address is determined by the value of
--                      the tnSapIpipeDiscoveredCeInetAddrType object.
--
--                      This object indicates the IPv4 address of the discovered
--                      local end host of an IPIPE SAP."
--     ::= { tnSapIpipeInfoEntry 8 }
--
-- tnSapIpipeUseBroadcastMac OBJECT-TYPE
--     SYNTAX          TruthValue
--     MAX-ACCESS      read-write
--     STATUS          current
--     DESCRIPTION     "The value of tnSapIpipeUseBroadcastMac specifies whether
--                      to use a broadcast MAC address to forward traffic from
--                      the Ethernet Ipipe SAP when tnSapIpipeArpedMacAddress is
--                      not a valid MAC address (no ARPed MAC address).
--
--                      If svcIpipeCeAddressDiscovery is set to 'disabled (2)',
--                      this value cannot be changed from the default value.
--
--                      For non-Ethernet SAPs this value cannot be changed
--                      from the default value."
--     DEFVAL { false }
--     ::= { tnSapIpipeInfoEntry 9 }
--
-- tnSapIpipeUsingBroadcastMac OBJECT-TYPE
--     SYNTAX          TruthValue
--     MAX-ACCESS      read-only
--     STATUS          current
--     DESCRIPTION     "The value of tnSapIpipeUsingBroadcastMac indicates whether
--                      a broadcast MAC address is currently being used to
--                      forward traffic from the Ethernet Ipipe SAP."
--     ::= { tnSapIpipeInfoEntry 10 }

-- -----------------------------------------
-- SAP Base ToD Monitoring Table
-- -----------------------------------------
-- tnSapTodMonitorTable OBJECT-TYPE
--     SYNTAX          SEQUENCE OF SapTodMonitorEntry
--     MAX-ACCESS      not-accessible
--     STATUS          current
--     DESCRIPTION     "This table contains information on configurable objects
--                      on SAP level, that can be modified by a scheduled policy."
--     ::= { tnSapObjs 26 }
--
-- tnSapTodMonitorEntry OBJECT-TYPE
--     SYNTAX          SapTodMonitorEntry
--     MAX-ACCESS      not-accessible
--     STATUS          current
--     DESCRIPTION     "Information about ToD policy modifiable config data
--                      for a SAP."
--     INDEX           { tnSysSwitchId,  tnSvcId, tnSapPortId, tnSapEncapValue }
--     ::= { tnSapTodMonitorTable 1 }
--
-- SapTodMonitorEntry ::=
--     SEQUENCE {
--         tnSapCurrentIngressIpFilterId      TFilterID,
--         tnSapCurrentIngressIpv6FilterId    TFilterID,
--         tnSapCurrentIngressMacFilterId     TFilterID,
--         tnSapCurrentIngressQosPolicyId     TSapIngressPolicyID,
--         tnSapCurrentIngressQosSchedPlcy    ServObjName,
--         tnSapCurrentEgressIpFilterId       TFilterID,
--         tnSapCurrentEgressIpv6FilterId     TFilterID,
--         tnSapCurrentEgressMacFilterId      TFilterID,
--         tnSapCurrentEgressQosPolicyId      TSapEgressPolicyID,
--         tnSapCurrentEgressQosSchedPlcy     ServObjName,
--         tnSapIntendedIngressIpFilterId     TFilterID,
--         tnSapIntendedIngressIpv6FilterId   TFilterID,
--         tnSapIntendedIngressMacFilterId    TFilterID,
--         tnSapIntendedIngressQosPolicyId    TSapIngressPolicyID,
--         tnSapIntendedIngressQosSchedPlcy   ServObjName,
--         tnSapIntendedEgressIpFilterId      TFilterID,
--         tnSapIntendedEgressIpv6FilterId    TFilterID,
--         tnSapIntendedEgressMacFilterId     TFilterID,
--         tnSapIntendedEgressQosPolicyId     TSapEgressPolicyID,
--         tnSapIntendedEgressQosSchedPlcy    ServObjName
--     }
--
-- tnSapCurrentIngressIpFilterId OBJECT-TYPE
--     SYNTAX          TFilterID
--     MAX-ACCESS      read-only
--     STATUS          current
--     DESCRIPTION     "The value of the object tnSapCurrentIngressIpFilterId
--                      indicates the index in the tIPFilterTable corresponding to
--                      the ingress filter applied on this SAP, or zero if no
--                      filter is currently active.
--                      The active filter may deviate from tnSapIngressIpFilterId in
--                      case it is overruled by a ToD Suite policy."
--     ::= { tnSapTodMonitorEntry 1 }
--
-- tnSapCurrentIngressIpv6FilterId OBJECT-TYPE
--     SYNTAX          TFilterID
--     MAX-ACCESS      read-only
--     STATUS          current
--     DESCRIPTION     "The value of the object tnSapCurrentIngressIpv6FilterId
--                      indicates the index in the tIPv6FilterTable corresponding
--                      to the ingress Ipv6 filter applied on this SAP, or zero if
--                      no filter is currently active.
--                      The active filter may deviate from tnSapIngressIpv6FilterId
--                      in case it is overruled by a ToD Suite policy."
--     ::= { tnSapTodMonitorEntry 2 }
--
-- tnSapCurrentIngressMacFilterId OBJECT-TYPE
--     SYNTAX          TFilterID
--     MAX-ACCESS      read-only
--     STATUS          current
--     DESCRIPTION     "The value of the object tnSapCurrentIngressMacFilterId
--                      indicates the index in the tMacFilterTable corresponding
--                      to the ingress Mac filter applied on this SAP, or zero if
--                      no filter is currently active.
--                      The active filter may deviate from tnSapIngressMacFilterId
--                      in case it is overruled by a ToD Suite policy."
--     ::= { tnSapTodMonitorEntry 3 }
--
-- tnSapCurrentIngressQosPolicyId OBJECT-TYPE
--     SYNTAX          TSapIngressPolicyID
--     MAX-ACCESS      read-only
--     STATUS          current
--     DESCRIPTION     "The value of the object tnSapCurrentIngressQosPolicyId
--                      indicates the index in the tSapIngressTable corresponding
--                      to the ingress Qos Policy applied on this SAP, or zero if
--                      no filter is currently active.
--                      The active filter may deviate from tnSapIngressQosPolicyId
--                      in case it is overruled by a ToD Suite policy."
--     ::= { tnSapTodMonitorEntry 4 }
--
-- tnSapCurrentIngressQosSchedPlcy OBJECT-TYPE
--     SYNTAX          ServObjName
--     MAX-ACCESS      read-only
--     STATUS          current
--     DESCRIPTION     "The value of the object tnSapCurrentIngressQosSchedPlcy
--                      indicates the ingress QoS scheduler on this SAP, or zero
--                      if none is currently active.
--                      The active policy may deviate from
--                      tnSapIngressQosSchedulerPolicy in case it is overruled by a
--                      ToD Suite policy defined on this SAP, or on the
--                      multi-service this SAP belongs to. "
--     ::= { tnSapTodMonitorEntry 5 }
--
-- tnSapCurrentEgressIpFilterId OBJECT-TYPE
--     SYNTAX          TFilterID
--     MAX-ACCESS      read-only
--     STATUS          current
--     DESCRIPTION     "The value of the object tnSapCurrentEgressIpFilterId
--                      indicates the index in the tIPFilterTable corresponding to
--                      the Egress filter applied on this SAP, or zero if no
--                      filter is currently active.
--                      The active filter may deviate from tnSapEgressIpFilterId in
--                      case it is overruled by a ToD Suite policy."
--     ::= { tnSapTodMonitorEntry 6 }
--
-- tnSapCurrentEgressIpv6FilterId OBJECT-TYPE
--     SYNTAX          TFilterID
--     MAX-ACCESS      read-only
--     STATUS          current
--     DESCRIPTION     "The value of the object tnSapCurrentEgressIpv6FilterId
--                      indicates the index in the tIPv6FilterTable corresponding
--                      to the Egress Ipv6 filter applied on this SAP, or zero if
--                      no filter is currently active.
--                      The active filter may deviate from tnSapEgressIpv6FilterId
--                      in case it is overruled by a ToD Suite policy."
--     ::= { tnSapTodMonitorEntry 7 }
--
-- tnSapCurrentEgressMacFilterId OBJECT-TYPE
--     SYNTAX          TFilterID
--     MAX-ACCESS      read-only
--     STATUS          current
--     DESCRIPTION     "The value of the object tnSapCurrentEgressMacFilterId
--                      indicates the index in the tMacFilterTable corresponding
--                      to the Egress Mac filter applied on this SAP, or zero if
--                      no filter is currently active.
--                      The active filter may deviate from tnSapEgressMacFilterId in
--                      case it is overruled by a ToD Suite policy."
--     ::= { tnSapTodMonitorEntry 8 }
--
-- tnSapCurrentEgressQosPolicyId OBJECT-TYPE
--     SYNTAX          TSapEgressPolicyID
--     MAX-ACCESS      read-only
--     STATUS          current
--     DESCRIPTION     "The value of the object tnSapCurrentEgressQosPolicyId
--                      indicates the index in the tSapEgressTable corresponding
--                      to the Egress Qos Policy applied on this SAP, or zero if
--                      no filter is currently active.
--                      The active filter may deviate from tnSapEgressQosPolicyId in
--                      case it is overruled by a ToD Suite policy."
--     ::= { tnSapTodMonitorEntry 9 }
--
-- tnSapCurrentEgressQosSchedPlcy OBJECT-TYPE
--     SYNTAX          ServObjName
--     MAX-ACCESS      read-only
--     STATUS          current
--     DESCRIPTION     "The value of the object tnSapCurrentEgressQosSchedPlcy
--                      indicates the Egress QoS scheduler on this SAP, or zero if
--                      none is currently active.
--                      The active policy may deviate from
--                      tnSapEgressQosSchedulerPolicy in case it is overruled by a
--                      ToD Suite policy defined on this SAP, or on the
--                      multi-customer this SAP belongs to."
--     ::= { tnSapTodMonitorEntry 10 }
--
-- tnSapIntendedIngressIpFilterId OBJECT-TYPE
--     SYNTAX          TFilterID
--     MAX-ACCESS      read-only
--     STATUS          current
--     DESCRIPTION     "The value of the object tnSapIntendedIngressIpFilterId
--                      indicates the index in the tIPFilterTable corresponding
--                      to the ingress IP filter that should be applied on
--                      this SAP.
--                      If it deviates from tnSapCurrentIngressIpFilterId, this
--                      means that there was a problem when trying to activate
--                      this filter. It can only deviate when using ToD Suites
--                      for the SAP. When the ToD Suites decides that a new
--                      filter must be applied, it will try to do this. If it
--                      fails, the current and intended field are not equal."
--     ::= { tnSapTodMonitorEntry 11 }
--
-- tnSapIntendedIngressIpv6FilterId OBJECT-TYPE
--     SYNTAX          TFilterID
--     MAX-ACCESS      read-only
--     STATUS          current
--     DESCRIPTION     "The value of the object tnSapIntendedIngressIpv6FilterId
--                      indicates the index in the tIPv6FilterTable corresponding
--                      to the ingress Ipv6 filter that should be applied on this
--                      SAP.
--                      If it deviates from tnSapCurrentIngressIpv6FilterId, this
--                      means that there was a problem when trying to activate
--                      this filter. It can only deviate when using ToD Suites
--                      for the SAP. When the ToD Suites decides that a new
--                      filter must be applied, it will try to do this. If it
--                      fails, the current and intended field are not equal."
--     ::= { tnSapTodMonitorEntry 12 }
--
-- tnSapIntendedIngressMacFilterId OBJECT-TYPE
--     SYNTAX          TFilterID
--     MAX-ACCESS      read-only
--     STATUS          current
--     DESCRIPTION     "The value of the object tnSapIntendedIngressMacFilterId
--                      indicates the index in the tMacFilterTable corresponding
--                      to the ingress Mac filter that should be applied
--                      on this SAP.
--                      If it deviates from tnSapCurrentIngressMacFilterId, this
--                      means that there was a problem when trying to activate
--                      this filter. It can only deviate when using ToD Suites for
--                      the SAP. When the ToD Suites decides that a new filter
--                      must be applied, it will try to do this. If it fails,
--                      the current and intended field are not equal."
--     ::= { tnSapTodMonitorEntry 13 }
--
-- tnSapIntendedIngressQosPolicyId OBJECT-TYPE
--     SYNTAX          TSapIngressPolicyID
--     MAX-ACCESS      read-only
--     STATUS          current
--     DESCRIPTION     "The value of the object tnSapIntendedIngressQosPolicyId
--                      indicates the index in the tSapIngressTable corresponding
--                      to the ingress Qos policy that should be applied
--                      on this SAP.
--                      If it deviates from tnSapCurrentIngressQosPolicyId, this
--                      means that there was a problem when trying to activate
--                      this filter. It can only deviate when using ToD Suites for
--                      the SAP. When the ToD Suites decides that a new filter
--                      must be applied, it will try to do this. If it fails, the
--                      current and intended field are not equal."
--     ::= { tnSapTodMonitorEntry 14 }
--
-- tnSapIntendedIngressQosSchedPlcy OBJECT-TYPE
--     SYNTAX          ServObjName
--     MAX-ACCESS      read-only
--     STATUS          current
--     DESCRIPTION     "The value of the object tnSapIntendedIngressQosSchedPlcy
--                      indicates the ingress QoS scheduler that should be applied
--                      on this SAP.
--                      If it deviates from tnSapCurrentIngressQosSchedPlcy, this
--                      means that there was a problem when trying to activate
--                      this filter. It can only deviate when using ToD Suites for
--                      the SAP. When the ToD Suites decides that a new filter
--                      must be applied, it will try to do this. If it fails,
--                      the current and intended field are not equal."
--     ::= { tnSapTodMonitorEntry 15 }
--
-- tnSapIntendedEgressIpFilterId OBJECT-TYPE
--     SYNTAX          TFilterID
--     MAX-ACCESS      read-only
--     STATUS          current
--     DESCRIPTION     "The value of the object tnSapIntendedEgressIpFilterId
--                      indicates the index in the tIPFilterTable corresponding to
--                      the Egress IP filter scheduler that should be applied on
--                      this SAP.
--                      If it deviates from tnSapCurrentEgressIpFilterId, this
--                      means that there was a problem when trying to activate
--                      this filter. It can only deviate when using ToD Suites for
--                      the SAP. When the ToD Suites decides that a new filter
--                      must be applied, it will try to do this. If it fails,
--                      the current and intended field are not equal."
--     ::= { tnSapTodMonitorEntry 16 }
--
-- tnSapIntendedEgressIpv6FilterId OBJECT-TYPE
--     SYNTAX          TFilterID
--     MAX-ACCESS      read-only
--     STATUS          current
--     DESCRIPTION     "The value of the object tnSapIntendedEgressIpv6FilterId
--                      indicates the index in the tIPv6FilterTable corresponding
--                      to the Egress IPv6 filter scheduler that should be applied
--                      on this SAP.
--                      If it deviates from tnSapCurrentEgressIpv6FilterId, this
--                      means that there was a problem when trying to activate
--                      this filter. It can only deviate when using ToD Suites for
--                      the SAP. When the ToD Suites decides that a new filter
--                      must be applied, it will try to do this. If it fails,
--                      the current and intended field are not equal."
--     ::= { tnSapTodMonitorEntry 17 }
--
-- tnSapIntendedEgressMacFilterId OBJECT-TYPE
--     SYNTAX          TFilterID
--     MAX-ACCESS      read-only
--     STATUS          current
--     DESCRIPTION     "The value of the object tnSapIntendedEgressMacFilterId
--                      indicates the index in the tMacFilterTable corresponding
--                      to the Egress mac filter scheduler that should be applied
--                      on this SAP.
--                      If it deviates from tnSapCurrentEgressMacFilterId, this
--                      means that there was a problem when trying to activate
--                      this filter. It can only deviate when using ToD Suites for
--                      the SAP. When the ToD Suites decides that a new filter
--                      must be applied, it will try to do this. If it fails,
--                      the current and intended field are not equal."
--     ::= { tnSapTodMonitorEntry 18 }
--
-- tnSapIntendedEgressQosPolicyId OBJECT-TYPE
--     SYNTAX          TSapEgressPolicyID
--     MAX-ACCESS      read-only
--     STATUS          current
--     DESCRIPTION     "The value of the object tnSapIntendedEgressQosPolicyId
--                      indicates the index in the tSapEgressTable corresponding
--                      to the Egress Qos Policy that should be applied
--                      on this SAP.
--                      If it deviates from tnSapCurrentEgressQosPolicyId, this
--                      means that there was a problem when trying to activate
--                      this filter. It can only deviate when using ToD Suites for
--                      the SAP. When the ToD Suites decides that a new filter
--                      must be applied, it will try to do this. If it fails,
--                      the current and intended field are not equal."
--     ::= { tnSapTodMonitorEntry 19 }
--
-- tnSapIntendedEgressQosSchedPlcy OBJECT-TYPE
--     SYNTAX          ServObjName
--     MAX-ACCESS      read-only
--     STATUS          current
--     DESCRIPTION     "The value of the object tnSapIntendedEgressQosSchedPlcy
--                      indicates the index in the tSapEgressTable corresponding
--                      to the Egress Qos Scheduler policy that should be applied
--                      on this SAP.
--                      If it deviates from tnSapCurrentEgressQosSchedPlcy, this
--                      means that there was a problem when trying to activate
--                      this filter. It can only deviate when using ToD Suites for
--                      the SAP. When the ToD Suites decides that a new filter
--                      must be applied, it will try to do this. If it fails,
--                      the current and intended field are not equal."
--     ::= { tnSapTodMonitorEntry 20 }

-- -------------------------------------------------
-- SAP Ingress Qos queue stats per Qos policy
-- -------------------------------------------------
-- tnSapIngrQosPlcyStatsTable OBJECT-TYPE
--     SYNTAX          SEQUENCE OF SapIngrQosPlcyStatsEntry
--     MAX-ACCESS      not-accessible
--     STATUS          current
--     DESCRIPTION     "A table that contains Ingress Qos policy related
--                      statistics for a SAP."
--     ::= { tnSapObjs 27 }
--
-- tnSapIngrQosPlcyStatsEntry OBJECT-TYPE
--     SYNTAX          SapIngrQosPlcyStatsEntry
--     MAX-ACCESS      not-accessible
--     STATUS          current
--     DESCRIPTION     "Statistics about a specific Ingress Qos Policy applied
--                      on a specific SAP."
--     INDEX           { tnSysSwitchId,  tnSvcId, tnSapPortId, tnSapEncapValue, tnSapIgQosPlcyId }
--     ::= { tnSapIngrQosPlcyStatsTable 1 }
--
-- SapIngrQosPlcyStatsEntry ::=
--     SEQUENCE {
--         tnSapIgQosPlcyId                      TSapIngressPolicyID,
--         tnSapIgQosPlcyDroppedHiPrioPackets    Counter64,
--         tnSapIgQosPlcyDroppedHiPrioOctets     Counter64,
--         tnSapIgQosPlcyDroppedLoPrioPackets    Counter64,
--         tnSapIgQosPlcyDroppedLoPrioOctets     Counter64,
--         tnSapIgQosPlcyForwardedInProfPackets  Counter64,
--         tnSapIgQosPlcyForwardedInProfOctets   Counter64,
--         tnSapIgQosPlcyForwardedOutProfPackets Counter64,
--         tnSapIgQosPlcyForwardedOutProfOctets  Counter64
--     }
--
-- tnSapIgQosPlcyId OBJECT-TYPE
--     SYNTAX          TSapIngressPolicyID
--     MAX-ACCESS      not-accessible
--     STATUS          current
--     DESCRIPTION     "The value of the object tnSapIgQosPlcyId indicates
--                      the row index in the tSapIngressTable corresponding to this
--                      ingress QoS policy, or one if no policy is specified."
--     ::= { tnSapIngrQosPlcyStatsEntry 1 }
--
-- tnSapIgQosPlcyDroppedHiPrioPackets OBJECT-TYPE
--     SYNTAX          Counter64
--     MAX-ACCESS      read-only
--     STATUS          current
--     DESCRIPTION     "The value of the object tnSapIgQosPlcyDroppedHiPrioPackets
--                      indicates the number of high priority packets,
--                      as determined by the SAP ingress QoS
--                      policy, dropped by the Qchip due to:
--                      MBS exceeded, buffer pool limit exceeded, etc."
--     ::= { tnSapIngrQosPlcyStatsEntry 2 }
--
-- tnSapIgQosPlcyDroppedHiPrioOctets OBJECT-TYPE
--     SYNTAX          Counter64
--     MAX-ACCESS      read-only
--     STATUS          current
--     DESCRIPTION     "The value of the object tnSapIgQosPlcyDroppedHiPrioOctets
--                      indicates the number of high priority octets,
--                      as determined by the SAP ingress QoS
--                      policy, dropped by the Qchip due to:
--                      MBS exceeded, buffer pool limit exceeded, etc."
--     ::= { tnSapIngrQosPlcyStatsEntry 3 }
--
-- tnSapIgQosPlcyDroppedLoPrioPackets OBJECT-TYPE
--     SYNTAX          Counter64
--     MAX-ACCESS      read-only
--     STATUS          current
--     DESCRIPTION     "The value of the object tnSapIgQosPlcyDroppedLoPrioPackets
--                      indicates the number of low priority packets,
--                      as determined by the SAP ingress QoS
--                      policy, dropped by the Qchip due to:
--                      MBS exceeded, buffer pool limit exceeded, etc."
--     ::= { tnSapIngrQosPlcyStatsEntry 4 }
--
-- tnSapIgQosPlcyDroppedLoPrioOctets OBJECT-TYPE
--     SYNTAX          Counter64
--     MAX-ACCESS      read-only
--     STATUS          current
--     DESCRIPTION     "The value of the object tnSapIgQosPlcyDroppedLoPrioOctets
--                      indicates the number of low priority octets,
--                      as determined by the SAP ingress QoS
--                      policy, dropped by the Qchip due to:
--                      MBS exceeded, buffer pool limit exceeded, etc."
--     ::= { tnSapIngrQosPlcyStatsEntry 5 }
--
-- tnSapIgQosPlcyForwardedInProfPackets OBJECT-TYPE
--     SYNTAX          Counter64
--     MAX-ACCESS      read-only
--     STATUS          current
--     DESCRIPTION     "The value of the object tnSapIgQosPlcyForwardedInProfPackets
--                      indicates the number of in-profile packets
--                      (rate below CIR) forwarded by the ingress Qchip."
--     ::= { tnSapIngrQosPlcyStatsEntry 6 }
--
-- tnSapIgQosPlcyForwardedInProfOctets OBJECT-TYPE
--     SYNTAX          Counter64
--     MAX-ACCESS      read-only
--     STATUS          current
--     DESCRIPTION     "The value of the object tnSapIgQosPlcyForwardedInProfOctets
--                      indicates the number of in-profile octets
--                      (rate below CIR) forwarded by the ingress Qchip."
--     ::= { tnSapIngrQosPlcyStatsEntry 7 }
--
-- tnSapIgQosPlcyForwardedOutProfPackets OBJECT-TYPE
--     SYNTAX          Counter64
--     MAX-ACCESS      read-only
--     STATUS          current
--     DESCRIPTION     "The value of the object tnSapIgQosPlcyForwardedOutProfPackets
--                      indicates the number of out-of-profile packets
--                      (rate above CIR) forwarded by the ingress Qchip."
--     ::= { tnSapIngrQosPlcyStatsEntry 8 }
--
-- tnSapIgQosPlcyForwardedOutProfOctets OBJECT-TYPE
--     SYNTAX          Counter64
--     MAX-ACCESS      read-only
--     STATUS          current
--     DESCRIPTION     "The value of the object tnSapIgQosPlcyForwardedOutProfOctets
--                      indicates the number of out-of-profile octets
--                      (rate above CIR) forwarded by the ingress Qchip."
--     ::= { tnSapIngrQosPlcyStatsEntry 9 }

-- -------------------------------------------------
-- SAP Egress Qos queue stats per Qos policy
-- -------------------------------------------------
-- tnSapEgrQosPlcyStatsTable OBJECT-TYPE
--     SYNTAX          SEQUENCE OF SapEgrQosPlcyStatsEntry
--     MAX-ACCESS      not-accessible
--     STATUS          current
--     DESCRIPTION     "A table that contains Egress Qos policy related
--                      statistics for a SAP."
--     ::= { tnSapObjs 28 }
--
-- tnSapEgrQosPlcyStatsEntry OBJECT-TYPE
--     SYNTAX          SapEgrQosPlcyStatsEntry
--     MAX-ACCESS      not-accessible
--     STATUS          current
--     DESCRIPTION     "Statistics about a specific Egress Qos Policy applied
--                      on a specific SAP."
--     INDEX           { tnSysSwitchId,  tnSvcId, tnSapPortId, tnSapEncapValue, tnSapEgQosPlcyId }
--     ::= { tnSapEgrQosPlcyStatsTable 1 }
--
-- SapEgrQosPlcyStatsEntry ::=
--     SEQUENCE {
--         tnSapEgQosPlcyId                      TSapEgressPolicyID,
--         tnSapEgQosPlcyDroppedInProfPackets    Counter64,
--         tnSapEgQosPlcyDroppedInProfOctets     Counter64,
--         tnSapEgQosPlcyDroppedOutProfPackets   Counter64,
--         tnSapEgQosPlcyDroppedOutProfOctets    Counter64,
--         tnSapEgQosPlcyForwardedInProfPackets  Counter64,
--         tnSapEgQosPlcyForwardedInProfOctets   Counter64,
--         tnSapEgQosPlcyForwardedOutProfPackets Counter64,
--         tnSapEgQosPlcyForwardedOutProfOctets  Counter64
--     }
--
-- tnSapEgQosPlcyId OBJECT-TYPE
--     SYNTAX          TSapEgressPolicyID
--     MAX-ACCESS      not-accessible
--     STATUS          current
--     DESCRIPTION     "The value of the object tnSapEgQosPlcyId indicates
--                      the row index in the tSapEgressTable corresponding to this
--                      egress QoS policy, or one if no policy is specified."
--     ::= { tnSapEgrQosPlcyStatsEntry 1 }
--
-- tnSapEgQosPlcyDroppedInProfPackets OBJECT-TYPE
--     SYNTAX          Counter64
--     MAX-ACCESS      read-only
--     STATUS          current
--     DESCRIPTION     "The value of the object tnSapEgQosPlcyDroppedInProfPackets
--                      indicates the number of in-profile packets,
--                      as determined by the SAP egress QoS
--                      policy, dropped by the Qchip due to:
--                      MBS exceeded, buffer pool limit exceeded, etc."
--     ::= { tnSapEgrQosPlcyStatsEntry 2 }
--
-- tnSapEgQosPlcyDroppedInProfOctets OBJECT-TYPE
--     SYNTAX          Counter64
--     MAX-ACCESS      read-only
--     STATUS          current
--     DESCRIPTION     "The value of the object tnSapEgQosPlcyDroppedInProfOctets
--                      indicates the number of in-profile octets,
--                      as determined by the SAP egress QoS
--                      policy, dropped by the Qchip due to:
--                      MBS exceeded, buffer pool limit exceeded, etc."
--     ::= { tnSapEgrQosPlcyStatsEntry 3 }
--
-- tnSapEgQosPlcyDroppedOutProfPackets OBJECT-TYPE
--     SYNTAX          Counter64
--     MAX-ACCESS      read-only
--     STATUS          current
--     DESCRIPTION     "The value of the object tnSapEgQosPlcyDroppedOutProfPackets
--                      indicates the number of out-profile packets,
--                      as determined by the SAP egress QoS
--                      policy, dropped by the Qchip due to:
--                      MBS exceeded, buffer pool limit exceeded, etc."
--     ::= { tnSapEgrQosPlcyStatsEntry 4 }
--
-- tnSapEgQosPlcyDroppedOutProfOctets OBJECT-TYPE
--     SYNTAX          Counter64
--     MAX-ACCESS      read-only
--     STATUS          current
--     DESCRIPTION     "The value of the object tnSapEgQosPlcyDroppedOutProfOctets
--                      indicates the number of out-profile octets,
--                      as determined by the SAP egress QoS
--                      policy, dropped by the Qchip due to:
--                      MBS exceeded, buffer pool limit exceeded, etc."
--     ::= { tnSapEgrQosPlcyStatsEntry 5 }
--
-- tnSapEgQosPlcyForwardedInProfPackets OBJECT-TYPE
--     SYNTAX          Counter64
--     MAX-ACCESS      read-only
--     STATUS          current
--     DESCRIPTION     "The value of the object tnSapEgQosPlcyForwardedInProfPackets
--                      indicates the number of in-profile packets
--                      (rate below CIR) forwarded by the egress Qchip."
--     ::= { tnSapEgrQosPlcyStatsEntry 6 }
--
-- tnSapEgQosPlcyForwardedInProfOctets OBJECT-TYPE
--     SYNTAX          Counter64
--     MAX-ACCESS      read-only
--     STATUS          current
--     DESCRIPTION     "The value of the object tnSapEgQosPlcyForwardedInProfOctets
--                      indicates the number of in-profile octets
--                      (rate below CIR) forwarded by the egress Qchip."
--     ::= { tnSapEgrQosPlcyStatsEntry 7 }
--
-- tnSapEgQosPlcyForwardedOutProfPackets OBJECT-TYPE
--     SYNTAX          Counter64
--     MAX-ACCESS      read-only
--     STATUS          current
--     DESCRIPTION     "The value of the object tnSapEgQosPlcyForwardedOutProfPackets
--                      indicates the number of out-of-profile packets
--                      (rate above CIR) forwarded by the egress Qchip."
--     ::= { tnSapEgrQosPlcyStatsEntry 8 }
--
-- tnSapEgQosPlcyForwardedOutProfOctets OBJECT-TYPE
--     SYNTAX          Counter64
--     MAX-ACCESS      read-only
--     STATUS          current
--     DESCRIPTION     "The value of the object tnSapEgQosPlcyForwardedOutProfOctets
--                      indicates the number of out-of-profile octets
--                      (rate above CIR) forwarded by the egress Qchip."
--     ::= { tnSapEgrQosPlcyStatsEntry 9 }

-- ------------------------------------------
-- Ingress QoS Plcy Queue SAP Statistics Table
-- ------------------------------------------
-- tnSapIngQosPlcyQueueStatsTable OBJECT-TYPE
--     SYNTAX          SEQUENCE OF SapIngQosPlcyQueueStatsEntry
--     MAX-ACCESS      not-accessible
--     STATUS          current
--     DESCRIPTION     "A table that contains ingress QoS queue SAP
--                      statistics, per Ingress QoS Policy the queue
--                      was used by."
--     ::= { tnSapObjs 29 }
--
-- tnSapIngQosPlcyQueueStatsEntry OBJECT-TYPE
--     SYNTAX          SapIngQosPlcyQueueStatsEntry
--     MAX-ACCESS      not-accessible
--     STATUS          current
--     DESCRIPTION     "Ingress statistics about a specific SAP's
--                      QoS queue for a given Qos policy."
--     INDEX           { tnSysSwitchId,  tnSvcId,
--                       tnSapPortId,
--                       tnSapEncapValue,
--                       tnSapIgQosPlcyQueuePlcyId,
--                       tnSapIgQosPlcyQueueId }
--     ::= { tnSapIngQosPlcyQueueStatsTable 1 }
--
-- SapIngQosPlcyQueueStatsEntry ::=
--     SEQUENCE {
--         tnSapIgQosPlcyQueuePlcyId                       TSapIngressPolicyID,
--         tnSapIgQosPlcyQueueId                           TSapIngQueueId,
--         tnSapIgQosPlcyQueueStatsOfferedHiPrioPackets    Counter64,
--         tnSapIgQosPlcyQueueStatsDroppedHiPrioPackets    Counter64,
--         tnSapIgQosPlcyQueueStatsOfferedLoPrioPackets    Counter64,
--         tnSapIgQosPlcyQueueStatsDroppedLoPrioPackets    Counter64,
--         tnSapIgQosPlcyQueueStatsOfferedHiPrioOctets     Counter64,
--         tnSapIgQosPlcyQueueStatsDroppedHiPrioOctets     Counter64,
--         tnSapIgQosPlcyQueueStatsOfferedLoPrioOctets     Counter64,
--         tnSapIgQosPlcyQueueStatsDroppedLoPrioOctets     Counter64,
--         tnSapIgQosPlcyQueueStatsForwardedInProfPackets  Counter64,
--         tnSapIgQosPlcyQueueStatsForwardedOutProfPackets Counter64,
--         tnSapIgQosPlcyQueueStatsForwardedInProfOctets   Counter64,
--         tnSapIgQosPlcyQueueStatsForwardedOutProfOctets  Counter64,
--         tnSapIgQosPlcyQueueCustId                       TmnxCustId,
--         tnSapIgQosPlcyQueueStatsUncoloredPacketsOffered Counter64,
--         tnSapIgQosPlcyQueueStatsUncoloredOctetsOffered  Counter64
--     }
--
-- tnSapIgQosPlcyQueuePlcyId OBJECT-TYPE
--     SYNTAX          TSapIngressPolicyID
--     MAX-ACCESS      not-accessible
--     STATUS          current
--     DESCRIPTION     "The value of the object tnSapIgQosPlcyQueuePlcyId indicates
--                      the row index in the tSapIngressTable corresponding to
--                      this ingress QoS policy."
--     ::= { tnSapIngQosPlcyQueueStatsEntry 1 }
--
-- tnSapIgQosPlcyQueueId OBJECT-TYPE
--     SYNTAX          TSapIngQueueId
--     MAX-ACCESS      not-accessible
--     STATUS          current
--     DESCRIPTION     "The index of the ingress QoS queue of this SAP used by the
--                      policy indicated by tnSapIgQosPlcyQueuePlcyId."
--     ::= { tnSapIngQosPlcyQueueStatsEntry 2 }
--
-- tnSapIgQosPlcyQueueStatsOfferedHiPrioPackets OBJECT-TYPE
--     SYNTAX          Counter64
--     MAX-ACCESS      read-only
--     STATUS          current
--     DESCRIPTION     "The value of tnSapIgQosPlcyQueueStatsOfferedHiPrioPackets
--                      indicates the number of high priority packets,
--                      as determined by the SAP ingress QoS policy, offered by
--                      the Pchip to the Qchip."
--     ::= { tnSapIngQosPlcyQueueStatsEntry 3 }
--
-- tnSapIgQosPlcyQueueStatsDroppedHiPrioPackets OBJECT-TYPE
--     SYNTAX          Counter64
--     MAX-ACCESS      read-only
--     STATUS          current
--     DESCRIPTION     "The value of tnSapIgQosPlcyQueueStatsDroppedHiPrioPackets
--                      indicates the number of high priority packets,
--                      as determined by the SAP ingress QoS policy, dropped by
--                      the Qchip due to: MBS exceeded, buffer pool limit
--                      exceeded, etc."
--     ::= { tnSapIngQosPlcyQueueStatsEntry 4 }
--
-- tnSapIgQosPlcyQueueStatsOfferedLoPrioPackets OBJECT-TYPE
--     SYNTAX          Counter64
--     MAX-ACCESS      read-only
--     STATUS          current
--     DESCRIPTION     "The value of tnSapIgQosPlcyQueueStatsOfferedLoPrioPackets
--                      indicates the number of  low priority packets,
--                      as determined by the SAP ingress QoS policy, offered by
--                      the Pchip to the Qchip."
--     ::= { tnSapIngQosPlcyQueueStatsEntry 5 }
--
-- tnSapIgQosPlcyQueueStatsDroppedLoPrioPackets OBJECT-TYPE
--     SYNTAX          Counter64
--     MAX-ACCESS      read-only
--     STATUS          current
--     DESCRIPTION     "The value of tnSapIgQosPlcyQueueStatsDroppedLoPrioPackets
--                      indicates the number of low priority packets,
--                      as determined by the SAP ingress QoS policy, dropped by
--                      the Qchip due to: MBS exceeded, buffer pool limit
--                      exceeded, etc."
--     ::= { tnSapIngQosPlcyQueueStatsEntry 6 }
--
-- tnSapIgQosPlcyQueueStatsOfferedHiPrioOctets OBJECT-TYPE
--     SYNTAX          Counter64
--     MAX-ACCESS      read-only
--     STATUS          current
--     DESCRIPTION     "The value of tnSapIgQosPlcyQueueStatsOfferedHiPrioOctets
--                      indicates the number of high priority octets,
--                      as determined by the SAP ingress QoS policy, offered by
--                      the Pchip to the Qchip."
--     ::= { tnSapIngQosPlcyQueueStatsEntry 7 }
--
-- tnSapIgQosPlcyQueueStatsDroppedHiPrioOctets OBJECT-TYPE
--     SYNTAX          Counter64
--     MAX-ACCESS      read-only
--     STATUS          current
--     DESCRIPTION     "The value of tnSapIgQosPlcyQueueStatsDroppedHiPrioOctets
--                      indicates the number ofhigh priority octets,
--                      as determined by the SAP ingress QoS policy, dropped by
--                      the Qchip due to: MBS exceeded, buffer pool limit
--                      exceeded, etc."
--     ::= { tnSapIngQosPlcyQueueStatsEntry 8 }
--
-- tnSapIgQosPlcyQueueStatsOfferedLoPrioOctets OBJECT-TYPE
--     SYNTAX          Counter64
--     MAX-ACCESS      read-only
--     STATUS          current
--     DESCRIPTION     "The value of tnSapIgQosPlcyQueueStatsOfferedLoPrioOctets
--                      indicates the number of low priority octets,
--                      as determined by the SAP ingress QoS policy, offered by
--                      the Pchip to the Qchip."
--     ::= { tnSapIngQosPlcyQueueStatsEntry 9 }
--
-- tnSapIgQosPlcyQueueStatsDroppedLoPrioOctets OBJECT-TYPE
--     SYNTAX          Counter64
--     MAX-ACCESS      read-only
--     STATUS          current
--     DESCRIPTION     "The value of tnSapIgQosPlcyQueueStatsDroppedLoPrioOctets
--                      indicates the number of low priority octets,
--                      as determined by the SAP ingress QoS policy, dropped by
--                      the Qchip due to: MBS exceeded, buffer pool limit
--                      exceeded, etc."
--     ::= { tnSapIngQosPlcyQueueStatsEntry 10 }
--
-- tnSapIgQosPlcyQueueStatsForwardedInProfPackets OBJECT-TYPE
--     SYNTAX          Counter64
--     MAX-ACCESS      read-only
--     STATUS          current
--     DESCRIPTION     "The value of tnSapIgQosPlcyQueueStatsForwardedInProfPackets
--                      indicates the number of in-profile packets
--                      (rate below CIR) forwarded by the ingress Qchip."
--     ::= { tnSapIngQosPlcyQueueStatsEntry 11 }
--
-- tnSapIgQosPlcyQueueStatsForwardedOutProfPackets OBJECT-TYPE
--     SYNTAX          Counter64
--     MAX-ACCESS      read-only
--     STATUS          current
--     DESCRIPTION     "The value of tnSapIgQosPlcyQueueStatsForwardedOutProfPackets
--                      indicates the number of out-of-profile packets
--                      (rate above CIR) forwarded by the ingress Qchip."
--     ::= { tnSapIngQosPlcyQueueStatsEntry 12 }
--
-- tnSapIgQosPlcyQueueStatsForwardedInProfOctets OBJECT-TYPE
--     SYNTAX          Counter64
--     MAX-ACCESS      read-only
--     STATUS          current
--     DESCRIPTION     "The value of tnSapIgQosPlcyQueueStatsForwardedInProfOctets
--                      indicates the number of in-profile octets
--                      (rate below CIR) forwarded by the ingress Qchip."
--     ::= { tnSapIngQosPlcyQueueStatsEntry 13 }
--
-- tnSapIgQosPlcyQueueStatsForwardedOutProfOctets OBJECT-TYPE
--     SYNTAX          Counter64
--     MAX-ACCESS      read-only
--     STATUS          current
--     DESCRIPTION     "The value of tnSapIgQosPlcyQueueStatsForwardedOutProfOctets
--                      indicates the number of  out-of-profile octets
--                      (rate above CIR) forwarded by the ingress Qchip."
--     ::= { tnSapIngQosPlcyQueueStatsEntry 14 }
--
-- tnSapIgQosPlcyQueueCustId OBJECT-TYPE
--     SYNTAX          TmnxCustId
--     MAX-ACCESS      read-only
--     STATUS          current
--     DESCRIPTION     "The value of the object tnSapIgQosPlcyQueueCustId
--                      indicates the Customer ID for the associated service."
--     ::= { tnSapIngQosPlcyQueueStatsEntry 15 }
--
-- tnSapIgQosPlcyQueueStatsUncoloredPacketsOffered OBJECT-TYPE
--     SYNTAX          Counter64
--     MAX-ACCESS      read-only
--     STATUS          current
--     DESCRIPTION     "The value of tnSapIgQosPlcyQueueStatsUncoloredPacketsOffered
--                      indicates the number of uncolored packets offered to
--                      the ingress Qchip."
--     ::= { tnSapIngQosPlcyQueueStatsEntry 16 }
--
-- tnSapIgQosPlcyQueueStatsUncoloredOctetsOffered OBJECT-TYPE
--     SYNTAX          Counter64
--     MAX-ACCESS      read-only
--     STATUS          current
--     DESCRIPTION     "The value of tnSapIgQosPlcyQueueStatsUncoloredOctetsOffered
--                      indicates the number of uncolored octets offered to
--                      the ingress Qchip."
--     ::= { tnSapIngQosPlcyQueueStatsEntry 17 }

-- ------------------------------------------
-- Egress QoS Plcy Queue SAP Statistics Table
-- ------------------------------------------
-- tnSapEgrQosPlcyQueueStatsTable OBJECT-TYPE
--     SYNTAX          SEQUENCE OF SapEgrQosPlcyQueueStatsEntry
--     MAX-ACCESS      not-accessible
--     STATUS          current
--     DESCRIPTION     "A table that contains egress QoS queue SAP
--                      statistics per Egress QoS Policy the queue
--                      was used by."
--     ::= { tnSapObjs 30 }
--
-- tnSapEgrQosPlcyQueueStatsEntry OBJECT-TYPE
--     SYNTAX          SapEgrQosPlcyQueueStatsEntry
--     MAX-ACCESS      not-accessible
--     STATUS          current
--     DESCRIPTION     "Egress statistics about a specific SAP's
--                      QoS queue for a given Qos policy."
--     INDEX           { tnSysSwitchId,  tnSvcId,
--                       tnSapPortId,
--                       tnSapEncapValue,
--                       tnSapEgQosPlcyQueuePlcyId,
--                       tnSapEgQosPlcyQueueId }
--     ::= { tnSapEgrQosPlcyQueueStatsTable 1 }
--
-- SapEgrQosPlcyQueueStatsEntry ::=
--     SEQUENCE {
--         tnSapEgQosPlcyQueuePlcyId                       TSapEgressPolicyID,
--         tnSapEgQosPlcyQueueId                           TSapEgrQueueId,
--         tnSapEgQosPlcyQueueStatsForwardedInProfPackets  Counter64,
--         tnSapEgQosPlcyQueueStatsDroppedInProfPackets    Counter64,
--         tnSapEgQosPlcyQueueStatsForwardedOutProfPackets Counter64,
--         tnSapEgQosPlcyQueueStatsDroppedOutProfPackets   Counter64,
--         tnSapEgQosPlcyQueueStatsForwardedInProfOctets   Counter64,
--         tnSapEgQosPlcyQueueStatsDroppedInProfOctets     Counter64,
--         tnSapEgQosPlcyQueueStatsForwardedOutProfOctets  Counter64,
--         tnSapEgQosPlcyQueueStatsDroppedOutProfOctets    Counter64,
--         tnSapEgQosPlcyQueueCustId                       TmnxCustId
--     }
--
-- tnSapEgQosPlcyQueuePlcyId OBJECT-TYPE
--     SYNTAX          TSapEgressPolicyID
--     MAX-ACCESS      not-accessible
--     STATUS          current
--     DESCRIPTION     "The row index in the tSapEgressTable
--                      corresponding to this egress QoS policy."
--     ::= { tnSapEgrQosPlcyQueueStatsEntry 1 }
--
-- tnSapEgQosPlcyQueueId OBJECT-TYPE
--     SYNTAX          TSapEgrQueueId
--     MAX-ACCESS      not-accessible
--     STATUS          current
--     DESCRIPTION     "The value of tnSapEgQosPlcyQueueId indicates
--                      index of the egress QoS queue of this SAP."
--     ::= { tnSapEgrQosPlcyQueueStatsEntry 2 }
--
-- tnSapEgQosPlcyQueueStatsForwardedInProfPackets OBJECT-TYPE
--     SYNTAX          Counter64
--     MAX-ACCESS      read-only
--     STATUS          current
--     DESCRIPTION     "The value of tnSapEgQosPlcyQueueStatsForwardedInProfPackets
--                      indicates the number of in-profile packets (rate below
--                      CIR) forwarded by the egress Qchip."
--     ::= { tnSapEgrQosPlcyQueueStatsEntry 3 }
--
-- tnSapEgQosPlcyQueueStatsDroppedInProfPackets OBJECT-TYPE
--     SYNTAX          Counter64
--     MAX-ACCESS      read-only
--     STATUS          current
--     DESCRIPTION     "The value of tnSapEgQosPlcyQueueStatsDroppedInProfPackets
--                      indicates the number of in-profile packets discarded by
--                      the egress Qchip due to: MBS exceeded, buffer pool limit
--                      exceeded, etc."
--     ::= { tnSapEgrQosPlcyQueueStatsEntry 4 }
--
-- tnSapEgQosPlcyQueueStatsForwardedOutProfPackets OBJECT-TYPE
--     SYNTAX          Counter64
--     MAX-ACCESS      read-only
--     STATUS          current
--     DESCRIPTION     "The value of tnSapEgQosPlcyQueueStatsForwardedOutProfPackets
--                      indicates the number of out-of-profile packets (rate
--                      above CIR) forwarded by the egress Qchip."
--     ::= { tnSapEgrQosPlcyQueueStatsEntry 5 }
--
-- tnSapEgQosPlcyQueueStatsDroppedOutProfPackets OBJECT-TYPE
--     SYNTAX          Counter64
--     MAX-ACCESS      read-only
--     STATUS          current
--     DESCRIPTION     "The value of tnSapEgQosPlcyQueueStatsDroppedOutProfPackets
--                      indicates the number out-of-profile packets discarded by
--                      the egress Qchip due to: MBS exceeded, buffer pool limit
--                      exceeded, etc."
--     ::= { tnSapEgrQosPlcyQueueStatsEntry 6 }
--
-- tnSapEgQosPlcyQueueStatsForwardedInProfOctets OBJECT-TYPE
--     SYNTAX          Counter64
--     MAX-ACCESS      read-only
--     STATUS          current
--     DESCRIPTION     "The value of tnSapEgQosPlcyQueueStatsForwardedInProfOctets
--                      indicates the number ofin-profile octets (rate below CIR)
--                      forwarded by the egress Qchip."
--     ::= { tnSapEgrQosPlcyQueueStatsEntry 7 }
--
-- tnSapEgQosPlcyQueueStatsDroppedInProfOctets OBJECT-TYPE
--     SYNTAX          Counter64
--     MAX-ACCESS      read-only
--     STATUS          current
--     DESCRIPTION     "The value of tnSapEgQosPlcyQueueStatsDroppedInProfOctets
--                      indicates the number in-profile octets discarded by the
--                      egress Qchip due to: MBS exceeded, buffer pool limit
--                      exceeded, etc."
--     ::= { tnSapEgrQosPlcyQueueStatsEntry 8 }
--
-- tnSapEgQosPlcyQueueStatsForwardedOutProfOctets OBJECT-TYPE
--     SYNTAX          Counter64
--     MAX-ACCESS      read-only
--     STATUS          current
--     DESCRIPTION     "The value of tnSapEgQosPlcyQueueStatsForwardedOutProfOctets
--                      indicates the number of out-of-profile octets (rate
--                      above CIR) forwarded by the egress Qchip."
--     ::= { tnSapEgrQosPlcyQueueStatsEntry 9 }
--
-- tnSapEgQosPlcyQueueStatsDroppedOutProfOctets OBJECT-TYPE
--     SYNTAX          Counter64
--     MAX-ACCESS      read-only
--     STATUS          current
--     DESCRIPTION     "The value of tnSapEgQosPlcyQueueStatsDroppedOutProfOctets
--                      indicates the number out-of-profile octets discarded by
--                      the egress Qchip due to: MBS exceeded, buffer pool limit
--                      exceeded, etc."
--     ::= { tnSapEgrQosPlcyQueueStatsEntry 10 }
--
-- tnSapEgQosPlcyQueueCustId OBJECT-TYPE
--     SYNTAX          TmnxCustId
--     MAX-ACCESS      read-only
--     STATUS          current
--     DESCRIPTION     "The value of the object tnSapEgQosPlcyQueueCustId indicates
--                      the Customer ID for the associated service."
--     ::= { tnSapEgrQosPlcyQueueStatsEntry 11 }

-- ----------------------------------------
-- SAP DHCP Information Table
-- ----------------------------------------
-- tnSapDhcpInfoTable OBJECT-TYPE
--     SYNTAX          SEQUENCE OF SapDhcpInfoEntry
--     MAX-ACCESS      not-accessible
--     STATUS          current
--     DESCRIPTION     "tnSapDhcpInfoTable contains DHCP information related to a
--                      routed CO subscriber SAP.  This table complements
--                      tnSapBaseInfoTable, and contains an entry for each
--                      routed CO subscriber SAP. Rows in this table
--                      are created and deleted automatically by the system."
--     ::= { tnSapObjs 31 }
--
-- tnSapDhcpInfoEntry OBJECT-TYPE
--     SYNTAX          SapDhcpInfoEntry
--     MAX-ACCESS      not-accessible
--     STATUS          current
--     DESCRIPTION     "DHCP specific information for a routed CO subscriber SAP."
--     INDEX           { tnSysSwitchId,  tnSvcId, tnSapPortId, tnSapEncapValue }
--     ::= { tnSapDhcpInfoTable 1 }
--
-- SapDhcpInfoEntry ::=
--     SEQUENCE {
--         tnSapDhcpOperLeasePopulate  Unsigned32
--     }
--
-- tnSapDhcpOperLeasePopulate OBJECT-TYPE
--     SYNTAX          Unsigned32
--     MAX-ACCESS      read-only
--     STATUS          current
--     DESCRIPTION     "The value of the object tnSapDhcpOperLeasePopulate
--                      indicates the number of DHCP lease states currently
--                      allocated on this SAP."
--     ::= { tnSapDhcpInfoEntry 1 }

-- -------------------------------------------------
-- SAP Ingress QoS Scheduler Per-Policy Statistics Table
-- -------------------------------------------------
-- tnSapIngSchedPlcyStatsTable OBJECT-TYPE
--     SYNTAX          SEQUENCE OF SapIngSchedPlcyStatsEntry
--     MAX-ACCESS      not-accessible
--     STATUS          current
--     DESCRIPTION     "A table that contains ingress QoS queue
--                      statistics for the SAP's, organized by
--                      scheduler policy."
--     ::= { tnSapObjs 32 }
--
-- tnSapIngSchedPlcyStatsEntry OBJECT-TYPE
--     SYNTAX          SapIngSchedPlcyStatsEntry
--     MAX-ACCESS      not-accessible
--     STATUS          current
--     DESCRIPTION     "Statistics about a specific SAP's ingress Qos Scheduler.
--                      Entries are created when a scheduler policy of a SAP
--                      is replaced with another one due to Time-Of-Day policies."
--     INDEX           { tnSysSwitchId,  tnSvcId, tnSapPortId, tnSapEncapValue, tnSchedulerPolicyName,
--                       IMPLIED tnSapIngQosSchedName }
--     ::= { tnSapIngSchedPlcyStatsTable 1 }
--
-- SapIngSchedPlcyStatsEntry ::=
--     SEQUENCE {
--         tnSapIngSchedPlcyStatsFwdPkt    Counter64,
--         tnSapIngSchedPlcyStatsFwdOct    Counter64
--     }
--
-- tnSapIngSchedPlcyStatsFwdPkt OBJECT-TYPE
--     SYNTAX          Counter64
--     MAX-ACCESS      read-only
--     STATUS          current
--     DESCRIPTION     "The number of forwarded packets, as
--                      determined by the SAP ingress scheduler
--                      policy, offered by the Pchip to the
--                      Qchip."
--     ::= { tnSapIngSchedPlcyStatsEntry 1 }
--
-- tnSapIngSchedPlcyStatsFwdOct OBJECT-TYPE
--     SYNTAX          Counter64
--     MAX-ACCESS      read-only
--     STATUS          current
--     DESCRIPTION     "The number of forwarded octets, as
--                      determined by the SAP ingress scheduler
--                      policy, offered by the Pchip to the
--                      Qchip."
--     ::= { tnSapIngSchedPlcyStatsEntry 2 }

-- ---------------------------------------------
-- SAP Egress QoS Scheduler Per-Policy Statistics Table
-- ---------------------------------------------
-- tnSapEgrSchedPlcyStatsTable OBJECT-TYPE
--     SYNTAX          SEQUENCE OF SapEgrSchedPlcyStatsEntry
--     MAX-ACCESS      not-accessible
--     STATUS          current
--     DESCRIPTION     "A table that contains egress QoS scheduler
--                      statistics for the SAP's, organized by
--                      scheduler policy."
--     ::= { tnSapObjs 33 }
--
-- tnSapEgrSchedPlcyStatsEntry OBJECT-TYPE
--     SYNTAX          SapEgrSchedPlcyStatsEntry
--     MAX-ACCESS      not-accessible
--     STATUS          current
--     DESCRIPTION     "Statistics about a specific SAP's egress QoS scheduler.
--                      Entries are created when a scheduler policy of a SAP
--                      is replaced with another one due to Time-Of-Day policies."
--     INDEX           { tnSysSwitchId,  tnSvcId, tnSapPortId, tnSapEncapValue, tnSchedulerPolicyName,
--                       IMPLIED tnSapEgrQosSchedName }
--     ::= { tnSapEgrSchedPlcyStatsTable 1 }
--
-- SapEgrSchedPlcyStatsEntry ::=
--     SEQUENCE {
--         tnSapEgrSchedPlcyStatsFwdPkt    Counter64,
--         tnSapEgrSchedPlcyStatsFwdOct    Counter64
--     }
--
-- tnSapEgrSchedPlcyStatsFwdPkt OBJECT-TYPE
--     SYNTAX          Counter64
--     MAX-ACCESS      read-only
--     STATUS          current
--     DESCRIPTION     "The number of packets forwarded by the
--                      egress Qchip, as determined by the SAP
--                      egress scheduler policy."
--     ::= { tnSapEgrSchedPlcyStatsEntry 1 }
--
-- tnSapEgrSchedPlcyStatsFwdOct OBJECT-TYPE
--     SYNTAX          Counter64
--     MAX-ACCESS      read-only
--     STATUS          current
--     DESCRIPTION     "The number of octets forwarded by the
--                      egress Qchip, as determined by the SAP
--                      egress scheduler policy."
--     ::= { tnSapEgrSchedPlcyStatsEntry 2 }

-- --------------------------------------------
-- SAP Ingress QoS Scheduler Per-Policy Statistics Table
-- with specific Port ID
-- --------------------------------------------
-- tnSapIngSchedPlcyPortStatsTable OBJECT-TYPE
--     SYNTAX          SEQUENCE OF SapIngSchedPlcyPortStatsEntry
--     MAX-ACCESS      not-accessible
--     STATUS          current
--     DESCRIPTION
--         "The tnSapIngSchedPlcyPortStatsTable contains
--          ingress QoS scheduler statistics for the SAP's, organized per
--          scheduler policy and per port. This table is used when the SAP
--          is  a CCAG or LAG in 'link' mode, or an APS.
--          Entries are created when a scheduler policy of a SAP
--          is replaced with another one due to Time-Of-Day policies."
--     ::= { tnSapObjs 34 }
--
-- tnSapIngSchedPlcyPortStatsEntry OBJECT-TYPE
--     SYNTAX          SapIngSchedPlcyPortStatsEntry
--     MAX-ACCESS      not-accessible
--     STATUS          current
--     DESCRIPTION     "Statistics about a specific SAP's ingress Qos Scheduler.
--                      Entries are created when a scheduler policy of a SAP
--                      is replaced with another one due to Time-Of-Day policies."
--     INDEX           { tnSysSwitchId,  tnSvcId, tnSapPortId, tnSapEncapValue, tnSchedulerPolicyName,
--                       tnVirtualSchedulerName, tnSapPortIdIngPortId }
--     ::= { tnSapIngSchedPlcyPortStatsTable 1 }
--
-- SapIngSchedPlcyPortStatsEntry ::=
--     SEQUENCE {
--         tnSapIngSchedPlcyPortStatsPort   TmnxPortID,
--         tnSapIngSchedPlcyPortStatsFwdPkt Counter64,
--         tnSapIngSchedPlcyPortStatsFwdOct Counter64
--     }
--
-- tnSapIngSchedPlcyPortStatsPort OBJECT-TYPE
--     SYNTAX          TmnxPortID
--     MAX-ACCESS      not-accessible
--     STATUS          current
--     DESCRIPTION     "The value of tnSapIngSchedPlcyPortStatsPort is used
--                      as an index of the ingress QoS scheduler of this SAP. When
--                      the SAP is an aps/ccag/lag in 'link' mode, this object is
--                      the TmnxPortID of the member-port on which the scheduler is
--                      applied."
--     ::= {tnSapIngSchedPlcyPortStatsEntry 1 }
--
-- tnSapIngSchedPlcyPortStatsFwdPkt OBJECT-TYPE
--     SYNTAX          Counter64
--     MAX-ACCESS      read-only
--     STATUS          current
--     DESCRIPTION     "The value of tnSapIngSchedPlcyPortStatsFwdPkt indicates
--                      the number of forwarded packets, as determined by the SAP
--                      ingress scheduler policy, offered by the Pchip to the
--                      Qchip."
--     ::= { tnSapIngSchedPlcyPortStatsEntry 2 }
--
-- tnSapIngSchedPlcyPortStatsFwdOct OBJECT-TYPE
--     SYNTAX          Counter64
--     MAX-ACCESS      read-only
--     STATUS          current
--     DESCRIPTION     "The value of tnSapIngSchedPlcyPortStatsFwdOct indicates
--                      the number of forwarded octets,as determined by the SAP
--                      ingress scheduler policy, offered by the Pchip to the
--                      Qchip."
--     ::= { tnSapIngSchedPlcyPortStatsEntry 3 }

-- ------------------------------------------------------------
-- SAP Egress QoS Scheduler Per-Policy Statistics Table
-- with specific Port ID
-- ------------------------------------------------------------
-- tnSapEgrSchedPlcyPortStatsTable OBJECT-TYPE
--     SYNTAX          SEQUENCE OF SapEgrSchedPlcyPortStatsEntry
--     MAX-ACCESS      not-accessible
--     STATUS          current
--     DESCRIPTION
--         "The tnSapEgrSchedPlcyPortStatsTable contains
--          egress QoS scheduler statistics for the SAP's, organized per
--          scheduler policy and per port. This table is used when the SAP
--          is  a CCAG or LAG in 'link' mode, or an APS.
--          Entries are created when a scheduler policy of a SAP
--          is replaced with another one due to Time-Of-Day policies."
--     ::= { tnSapObjs 35 }
--
-- tnSapEgrSchedPlcyPortStatsEntry OBJECT-TYPE
--     SYNTAX          SapEgrSchedPlcyPortStatsEntry
--     MAX-ACCESS      not-accessible
--     STATUS          current
--     DESCRIPTION     "Statistics about a specific SAP's egress Qos Scheduler.
--                      Entries are created when a scheduler policy of a SAP
--                      is replaced with another one due to Time-Of-Day policies."
--     INDEX           { tnSysSwitchId,  tnSvcId, tnSapPortId, tnSapEncapValue, tnSchedulerPolicyName,
--                       tnVirtualSchedulerName, tnSapPortIdEgrPortId }
--     ::= { tnSapEgrSchedPlcyPortStatsTable 1 }
--
-- SapEgrSchedPlcyPortStatsEntry ::=
--     SEQUENCE {
--         tnSapEgrSchedPlcyPortStatsPort   TmnxPortID,
--         tnSapEgrSchedPlcyPortStatsFwdPkt Counter64,
--         tnSapEgrSchedPlcyPortStatsFwdOct Counter64
--     }
--
-- tnSapEgrSchedPlcyPortStatsPort OBJECT-TYPE
--     SYNTAX          TmnxPortID
--     MAX-ACCESS      not-accessible
--     STATUS          current
--     DESCRIPTION     "The value of tnSapEgrSchedPlcyPortStatsPort is used
--                      as an index of the egress QoS scheduler of this SAP. When
--                      the SAP is an aps/ccag/lag in 'link' mode, this object is
--                      the TmnxPortID of the member-port on which the scheduler is
--                      applied."
--     ::= {tnSapEgrSchedPlcyPortStatsEntry 1 }
--
-- tnSapEgrSchedPlcyPortStatsFwdPkt OBJECT-TYPE
--     SYNTAX          Counter64
--     MAX-ACCESS      read-only
--     STATUS          current
--     DESCRIPTION     "The value of tnSapEgrSchedPlcyPortStatsFwdPkt indicates
--                      the number of forwarded packets, as determined by the SAP
--                      egress scheduler policy, offered by the Pchip to the
--                      Qchip."
--     ::= { tnSapEgrSchedPlcyPortStatsEntry 2 }
--
-- tnSapEgrSchedPlcyPortStatsFwdOct OBJECT-TYPE
--     SYNTAX          Counter64
--     MAX-ACCESS      read-only
--     STATUS          current
--     DESCRIPTION     "The value of tnSapEgrSchedPlcyPortStatsFwdOct indicates
--                      the number of forwarded octets,as determined by the SAP
--                      egress scheduler policy, offered by the Pchip to the
--                      Qchip."
--     ::= { tnSapEgrSchedPlcyPortStatsEntry 3 }

-- ---------------------------------------------------------------------
--  CEM SAP Information Table
--
--  Sparse Dependent Extention of the tnSapBaseInfoTable.
--
--  The same indexes are used for both the base table, tnSapBaseInfoTable,
--  and the sparse dependent table, tnSapCemInfoTable.
--
--  This in effect extends the tnSapBaseInfoTable with additional columns.
--  Rows are created in the tnSapCemInfoTable only for those entries
--  in the tnSapBaseInfoTable that are created on a port with 'cemEncap'
--  encapsulation.
--
--  Deletion of a row in the tnSapBaseInfoTable results in the
--  same fate for the row in the tnSapCemInfoTable.
-- ---------------------------------------------------------------------
-- tnSapCemInfoTable OBJECT-TYPE
--     SYNTAX          SEQUENCE OF SapCemInfoEntry
--     MAX-ACCESS      not-accessible
--     STATUS          current
--     DESCRIPTION     "A table that contains CEM SAP information."
--     ::= { tnSapObjs 40 }
--
-- tnSapCemInfoEntry OBJECT-TYPE
--     SYNTAX          SapCemInfoEntry
--     MAX-ACCESS      not-accessible
--     STATUS          current
--     DESCRIPTION     "Information about a specific CEM SAP."
--     INDEX           { tnSysSwitchId,  tnSvcId, tnSapPortId, tnSapEncapValue }
--     ::= { tnSapCemInfoTable 1 }
--
-- SapCemInfoEntry ::=
--     SEQUENCE {
--         tnSapCemLastMgmtChange              TimeStamp,
--         tnSapCemEndpointType                INTEGER,
--         tnSapCemBitrate                     Unsigned32,
--         tnSapCemCasTrunkFraming             TdmOptionsCasTrunkFraming,
--         tnSapCemPayloadSize                 Unsigned32,
--         tnSapCemJitterBuffer                Unsigned32,
--         tnSapCemUseRtpHeader                TruthValue,
--         tnSapCemDifferential                TruthValue,
--         tnSapCemTimestampFreq               Unsigned32,
--         tnSapCemReportAlarm                 CemSapReportAlarm,
--         tnSapCemReportAlarmStatus           CemSapReportAlarm,
--         tnSapCemLocalEcid                   CemSapEcid,
--         tnSapCemRemoteMacAddr               MacAddress,
--         tnSapCemRemoteEcid                  CemSapEcid,
--         tnSapCemJitterBufPackets            Unsigned32,
--         tnSapCemPlayoutBufPacketsThreshold  Unsigned32
--   }
--
-- tnSapCemLastMgmtChange OBJECT-TYPE
--     SYNTAX          TimeStamp
--     MAX-ACCESS      read-only
--     STATUS          current
--     DESCRIPTION     "The value of the object tnSapCemLastMgmtChange indicates
--                      the value of sysUpTime at the time of the most recent
--                      management-initiated change to this CEM SAP information."
--     ::= { tnSapCemInfoEntry 1 }
--
-- tnSapCemEndpointType   OBJECT-TYPE
--     SYNTAX           INTEGER {
--                          unstructuredE1 (1),
--                          unstructuredT1 (2),
--                          unstructuredE3 (3),
--                          unstructuredT3 (4),
--                          nxDS0          (5),
--                          nxDS0WithCas   (6)
--                      }
--     MAX-ACCESS       read-only
--     STATUS           current
--     DESCRIPTION      "This object indicates the CEM SAP endpoint type."
--     ::= { tnSapCemInfoEntry 2 }
--
-- tnSapCemBitrate        OBJECT-TYPE
--     SYNTAX           Unsigned32 (0..699)
--     UNITS            "64 Kbits/s"
--     MAX-ACCESS       read-only
--     STATUS           current
--     DESCRIPTION      "This object indicates the bit-rate in multiples of
--                       64 Kbit/s of the CEM SAP."
--     ::= { tnSapCemInfoEntry 3 }
--
-- tnSapCemCasTrunkFraming  OBJECT-TYPE
--     SYNTAX           TdmOptionsCasTrunkFraming
--     MAX-ACCESS       read-only
--     STATUS           current
--     DESCRIPTION      "This object indicates the CAS trunk framing mode of
--                       the CEM SAP."
--     ::= { tnSapCemInfoEntry 4 }
--
-- tnSapCemPayloadSize   OBJECT-TYPE
--     SYNTAX           Unsigned32 (0|16..2048)
--     UNITS            "bytes"
--     MAX-ACCESS       read-write
--     STATUS           current
--     DESCRIPTION      "This object specifies the payload size (in bytes) of
--                       packets transmitted to the Packet Service Network (PSN)
--                       by the CEM SAP.  This determines the size of the data
--                       that will be transmitted over the service.  As well,
--                       if the size of the data received is not consistent with
--                       the payload size then the packet is considered malformed.
--
--                       The default value depends on the CEM SAP endpoint type
--                       (tnSapCemEndpointType), and if applicable, the number of
--                       timeslots (tnSapCemBitrate):
--                       =========================================================
--                       | Endpoint Type      | Timeslots | Default payload size |
--                       =========================================================
--                       | 'unstructuredE1'   | n/a       |    256 bytes         |
--                       =========================================================
--                       | 'unstructuredT1'   | n/a       |    192 bytes         |
--                       =========================================================
--                       | 'unstructuredE3'   | n/a       |   1024 bytes         |
--                       =========================================================
--                       | 'unstructuredT3'   | n/a       |   1024 bytes         |
--                       =========================================================
--                       | 'nxDS0' (E1/T1)    | N = 1     |     64 bytes         |
--                       |                    ====================================
--                       |                    | N = 2..4  | N x 32 bytes         |
--                       |                    ====================================
--                       |                    | N = 5..15 | N x 16 bytes         |
--                       |                    ====================================
--                       |                    | N >= 16   | N x  8 bytes         |
--                       =========================================================
--                       | 'nxDS0WithCas' (E1)| N         | N x 16 bytes         |
--                       =========================================================
--                       | 'nxDS0WithCas' (T1)| N         | N x 24 bytes         |
--                       =========================================================
--
--                       For 'nxDS0WithCas', the tnSapCemPayloadSize cannot
--                       be changed away from the default value.
--
--                       For '1xDS0', tnSapCemPayloadSize must be a multiple of 2.
--
--                       For 'NxDS0', where N > 1, tnSapCemPayloadSize must be a
--                       multiple of the number of timeslots (tnSapCemBitrate).
--
--                       For 'unstructuredE1', 'unstructuredT1', 'unstructuredE3'
--                       and 'unstructuredT3', tnSapCemPayloadSize must be a
--                       multiple of 32 bytes.
--
--                       Configuring tnSapCemPayloadSize and tnSapCemJitterBuffer to
--                       values that result in less than 2 packet buffers or
--                       greater than 32 packet buffers is not allowed.
--
--                       For all endpoint types except for 'nxDS0WithCas', the
--                       minimum payload size is given below:
--                       =========================================================
--                       | Endpoint Type      | Timeslots | Minimum payload size |
--                       =========================================================
--                       | 'unstructuredE1'   | n/a       |    256 bytes         |
--                       =========================================================
--                       | 'unstructuredT1'   | n/a       |    192 bytes         |
--                       =========================================================
--                       | 'unstructuredE3'   | n/a       |   1024 bytes         |
--                       =========================================================
--                       | 'unstructuredT3'   | n/a       |   1024 bytes         |
--                       =========================================================
--                       | 'nxDS0' (E1)       | N = 1..4  | N x 16 bytes         |
--                       =========================================================
--                       | 'nxDS0' (T1)       | N = 1..4  | N x 24 bytes         |
--                       =========================================================
--                       | 'nxDS0' (E1/T1)    | N = 5..15 | N x 16 bytes         |
--                       |                    ====================================
--                       |                    | N >= 16   | N x  8 bytes         |
--                       =========================================================
--
--                       For all endpoints types except for 'nxDS0WithCas', the
--                       maximum payload size is 2048 bytes.
--
--                       Setting this object to 0 sets it back to the default
--                       value."
--     ::= { tnSapCemInfoEntry 5 }
--
-- tnSapCemJitterBuffer   OBJECT-TYPE
--     SYNTAX           Unsigned32 (0|1..250)
--     UNITS            "milliseconds"
--     MAX-ACCESS       read-write
--     STATUS           current
--     DESCRIPTION      "This object specifies the jitter buffer size in
--                       milliseconds (ms).
--
--                       Default value depends on the CEM SAP endpoint type
--                       (tnSapCemEndpointType), and if applicable, the number of
--                       timeslots (tnSapCemBitrate):
--                       =========================================================
--                       | Endpoint Type      | Timeslots | Default jitter buf.  |
--                       =========================================================
--                       | 'unstructuredE1'   | n/a       |    5 ms              |
--                       =========================================================
--                       | 'unstructuredT1'   | n/a       |    5 ms              |
--                       =========================================================
--                       | 'unstructuredE3'   | n/a       |    5 ms              |
--                       =========================================================
--                       | 'unstructuredT3'   | n/a       |    5 ms              |
--                       =========================================================
--                       | 'nxDS0' (E1/T1)    | N = 1     |   32 ms              |
--                       |                    ====================================
--                       |                    | N = 2..4  |   16 ms              |
--                       |                    ====================================
--                       |                    | N = 5..15 |    8 ms              |
--                       |                    ====================================
--                       |                    | N >= 16   |    5 ms              |
--                       =========================================================
--                       | 'nxDS0WithCas' (E1)| N         |    8 ms              |
--                       =========================================================
--                       | 'nxDS0WithCas' (T1)| N         |   12 ms              |
--                       =========================================================
--
--                       Configuring tnSapCemPayloadSize and tnSapCemJitterBuffer to
--                       values that result in less than 2 packet buffers or
--                       greater than 32 packet buffers is not allowed.
--
--                       The valid range is 1 to 250 ms.  Setting this object
--                       to 0 sets it back to the default value."
--     ::= { tnSapCemInfoEntry 6 }
--
-- tnSapCemUseRtpHeader  OBJECT-TYPE
--     SYNTAX          TruthValue
--     MAX-ACCESS      read-write
--     STATUS          current
--     DESCRIPTION     "This object specifies whether a RTP header is used when
--                      packets are transmitted to the Packet Service Network
--                      (PSN) by the CEM SAP."
--     DEFVAL          { false }
--     ::= { tnSapCemInfoEntry 7 }
--
-- tnSapCemDifferential  OBJECT-TYPE
--     SYNTAX          TruthValue
--     MAX-ACCESS      read-only
--     STATUS          current
--     DESCRIPTION     "This object specifies whether this CEM SAP is in
--                      differential mode."
--     ::= { tnSapCemInfoEntry 8 }
--
-- tnSapCemTimestampFreq OBJECT-TYPE
--     SYNTAX          Unsigned32
--     UNITS           "8 KHz"
--     MAX-ACCESS      read-only
--     STATUS          current
--     DESCRIPTION     "This object specifies whether the value of the timestamp
--                      frequency in multiples of 8 KHz for this CEM SAP."
--     ::= { tnSapCemInfoEntry 9 }
--
-- tnSapCemReportAlarm OBJECT-TYPE
--     SYNTAX          CemSapReportAlarm
--     MAX-ACCESS      read-write
--     STATUS          current
--     DESCRIPTION
--                     "The value of tnSapCemReportAlarm determines when and if to
--                     generate notifications for the CEM SAP."
--     DEFVAL      { {strayPkts, malformedPkts, pktLoss, bfrOverrun, bfrUnderrun} }
--     ::= { tnSapCemInfoEntry 10 }
--
-- tnSapCemReportAlarmStatus  OBJECT-TYPE
--     SYNTAX          CemSapReportAlarm
--     MAX-ACCESS      read-only
--     STATUS          current
--     DESCRIPTION
--                     "The value of tnSapCemReportAlarmStatus indicates the current
--                      alarms on this CEM SAP."
--     ::= { tnSapCemInfoEntry 11 }
--
-- tnSapCemLocalEcid OBJECT-TYPE
--     SYNTAX          CemSapEcid
--     MAX-ACCESS      read-write
--     STATUS          current
--     DESCRIPTION     "The value of the object tnSapCemLocalEcid specifies
--                      the local ECID.
--
--                      Only valid if CEM SAP belongs to an EPIPE service."
--     DEFVAL { 0 }
--     ::= { tnSapCemInfoEntry 12 }
--
-- tnSapCemRemoteMacAddr OBJECT-TYPE
--     SYNTAX          MacAddress
--     MAX-ACCESS      read-write
--     STATUS          current
--     DESCRIPTION     "The value of the object tnSapCemRemoteMacAddr specifies
--                      the remote MAC address.
--
--                      Only valid if CEM SAP belongs to an EPIPE service."
--     DEFVAL { '000000000000'h }
--     ::= { tnSapCemInfoEntry 13 }
--
-- tnSapCemRemoteEcid OBJECT-TYPE
--     SYNTAX          CemSapEcid
--     MAX-ACCESS      read-write
--     STATUS          current
--     DESCRIPTION     "The value of the object tnSapCemRemoteEcid specifies
--                      the remote ECID.
--
--                      Only valid if CEM SAP belongs to an EPIPE service."
--     DEFVAL { 0 }
--     ::= { tnSapCemInfoEntry 14 }
--
-- tnSapCemJitterBufPackets OBJECT-TYPE
--     SYNTAX           Unsigned32
--     UNITS            "packets"
--     MAX-ACCESS       read-only
--     STATUS           current
--     DESCRIPTION      "This value indicates the jitter buffer length in
--                       number of packet buffers."
--     ::= { tnSapCemInfoEntry 15 }
--
-- tnSapCemPlayoutBufPacketsThreshold OBJECT-TYPE
--     SYNTAX           Unsigned32
--     UNITS            "packets"
--     MAX-ACCESS       read-only
--     STATUS           current
--     DESCRIPTION      "This value indicates the playout buffer packets threshold
--                       in number of packet buffers."
--     ::= { tnSapCemInfoEntry 16 }

-- ---------------------------------------------------------------------
-- CEM SAP Statistics Table
--
--
--  Sparse Dependent Extention of the tnSapBaseInfoTable.
--
--  The same indexes are used for both the base table, tnSapBaseInfoTable,
--  and the sparse dependent table, tnSapCemStatsTable.
--
--  This in effect extends the tnSapBaseInfoTable with additional columns.
--  Rows are created in the tnSapCemStatsTable only for those entries
--  in the tnSapBaseInfoTable that are created on a port that 'cemEncap' set
--  for port encapsulation.
--
--  Deletion of a row in the tnSapBaseInfoTable results in the
--  same fate for the row in the tnSapCemStatsTable.
-- ---------------------------------------------------------------------
-- tnSapCemStatsTable OBJECT-TYPE
--     SYNTAX          SEQUENCE OF SapCemStatsEntry
--     MAX-ACCESS      not-accessible
--     STATUS          current
--     DESCRIPTION     "A table that contains CEM SAP statistics."
--     ::= { tnSapObjs 41 }
--
-- tnSapCemStatsEntry OBJECT-TYPE
--     SYNTAX          SapCemStatsEntry
--     MAX-ACCESS      not-accessible
--     STATUS          current
--     DESCRIPTION     "Statistics for a specific CEM SAP."
--     INDEX           { tnSysSwitchId,  tnSvcId, tnSapPortId, tnSapEncapValue }
--     ::= { tnSapCemStatsTable 1 }
--
-- SapCemStatsEntry ::=
--     SEQUENCE {
--         tnSapCemStatsIngressForwardedPkts   Counter32,
--         tnSapCemStatsIngressDroppedPkts     Counter32,
--         tnSapCemStatsEgressForwardedPkts    Counter32,
--         tnSapCemStatsEgressDroppedPkts      Counter32,
--         tnSapCemStatsEgressMissingPkts      Counter32,
--         tnSapCemStatsEgressPktsReOrder      Counter32,
--         tnSapCemStatsEgressJtrBfrUnderruns  Counter32,
--         tnSapCemStatsEgressJtrBfrOverruns   Counter32,
--         tnSapCemStatsEgressMisOrderDropped  Counter32,
--         tnSapCemStatsEgressMalformedPkts    Counter32,
--         tnSapCemStatsEgressLBitDropped      Counter32,
--         tnSapCemStatsEgressMultipleDropped  Counter32,
--         tnSapCemStatsEgressESs              Counter32,
--         tnSapCemStatsEgressSESs             Counter32,
--         tnSapCemStatsEgressUASs             Counter32,
--         tnSapCemStatsEgressFailureCounts    Counter32,
--         tnSapCemStatsEgressUnderrunCounts   Counter32,
--         tnSapCemStatsEgressOverrunCounts    Counter32,
--         tnSapCemStatsEgressJtrBfrDepth      Gauge32
--     }
--
-- tnSapCemStatsIngressForwardedPkts OBJECT-TYPE
--     SYNTAX          Counter32
--     MAX-ACCESS      read-only
--     STATUS          current
--     DESCRIPTION     "The value of tnSapCemStatsIngressForwardedPkts indicates
--                      the number of packets that were successfully forwarded."
--     ::= { tnSapCemStatsEntry 1 }
--
-- tnSapCemStatsIngressDroppedPkts OBJECT-TYPE
--     SYNTAX          Counter32
--     MAX-ACCESS      read-only
--     STATUS          current
--     DESCRIPTION     "The value of tnSapCemStatsIngressDroppedPkts indicates
--                      the total number of packets that were dropped due to
--                      errors."
--     ::= { tnSapCemStatsEntry 2 }
--
-- tnSapCemStatsEgressForwardedPkts OBJECT-TYPE
--     SYNTAX          Counter32
--     MAX-ACCESS      read-only
--     STATUS          current
--     DESCRIPTION     "The value of tnSapCemStatsEgressForwardedPkts indicates the
--                      number of packets that were successfully forwarded."
--     ::= { tnSapCemStatsEntry 3 }
--
-- tnSapCemStatsEgressDroppedPkts OBJECT-TYPE
--     SYNTAX          Counter32
--     MAX-ACCESS      read-only
--     STATUS          current
--     DESCRIPTION     "The value of tnSapCemStatsEgressDroppedPkts indicates
--                      the total number of packets that were dropped due to
--                      errors."
--     ::= { tnSapCemStatsEntry 4 }
--
-- tnSapCemStatsEgressMissingPkts   OBJECT-TYPE
--     SYNTAX          Counter32
--     MAX-ACCESS      read-only
--     STATUS          current
--     DESCRIPTION     "The value of tnSapCemStatsEgressMissingPkts indicates the
--                      number of missing packets (as detected via control word
--                      sequence number gaps)."
--     ::= { tnSapCemStatsEntry 5 }
--
-- tnSapCemStatsEgressPktsReOrder   OBJECT-TYPE
--     SYNTAX          Counter32
--     MAX-ACCESS      read-only
--     STATUS          current
--     DESCRIPTION     "The value of tnSapCemStatsEgressPktsReOrder indicates the
--                      number of packets detected out of sequence (via control
--                      word sequence number), but successfully re-ordered."
--     ::= { tnSapCemStatsEntry 6 }
--
-- tnSapCemStatsEgressJtrBfrUnderruns  OBJECT-TYPE
--     SYNTAX          Counter32
--     MAX-ACCESS      read-only
--     STATUS          current
--     DESCRIPTION     "The value of tnSapCemStatsEgressJtrBfrUnderruns indicates
--                      the number of times a packet needed to be played out and
--                      the jitter buffer was empty."
--     ::= { tnSapCemStatsEntry 7 }
--
-- tnSapCemStatsEgressJtrBfrOverruns  OBJECT-TYPE
--     SYNTAX          Counter32
--     MAX-ACCESS      read-only
--     STATUS          current
--     DESCRIPTION     "The value of tnSapCemStatsEgressJtrBfrOverruns indicates
--                      the number of times a packet was dropped because it could
--                      not fit in the jitter buffer."
--     ::= { tnSapCemStatsEntry 8 }
--
-- tnSapCemStatsEgressMisOrderDropped  OBJECT-TYPE
--     SYNTAX          Counter32
--     MAX-ACCESS      read-only
--     STATUS          current
--     DESCRIPTION     "The value of tnSapCemStatsEgressMisOrderDropped indicates
--                      the number of packets detected out of order (via control
--                      word sequence numbers), and could not be re-ordered, or
--                      could not be placed in the jitter buffer because it was
--                      out of the current window."
--     ::= { tnSapCemStatsEntry 9 }
--
-- tnSapCemStatsEgressMalformedPkts  OBJECT-TYPE
--     SYNTAX          Counter32
--     MAX-ACCESS      read-only
--     STATUS          current
--     DESCRIPTION     "The value of tnSapCemStatsEgressMalformedPkts indicates the
--                      number of packets detected with unexpected size, or bad
--                      headers' stack."
--     ::= { tnSapCemStatsEntry 10 }
--
-- tnSapCemStatsEgressLBitDropped  OBJECT-TYPE
--     SYNTAX          Counter32
--     MAX-ACCESS      read-only
--     STATUS          current
--     DESCRIPTION     "The value of tnSapCemStatsEgressLBitDropped indicates the
--                      number of packets dropped due to the L bit set by the far
--                      end."
--     ::= { tnSapCemStatsEntry 11 }
--
-- tnSapCemStatsEgressMultipleDropped  OBJECT-TYPE
--     SYNTAX          Counter32
--     MAX-ACCESS      read-only
--     STATUS          current
--     DESCRIPTION     "The value of tnSapCemStatsEgressMultipleDropped indicates
--                      the number of packets dropped due to multiple sequence
--                      numbers."
--     ::= { tnSapCemStatsEntry 12 }
--
-- tnSapCemStatsEgressESs  OBJECT-TYPE
--     SYNTAX          Counter32
--     MAX-ACCESS      read-only
--     STATUS          current
--     DESCRIPTION     "The value of tnSapCemStatsEgressESs indicates the number of
--                      Error Seconds (ESs) encountered. Any malformed packet,
--                      seq.  error, LOPS and similar are considered as error
--                      seconds."
--     ::= { tnSapCemStatsEntry 13 }
--
-- tnSapCemStatsEgressSESs  OBJECT-TYPE
--     SYNTAX          Counter32
--     MAX-ACCESS      read-only
--     STATUS          current
--     DESCRIPTION     "The value of tnSapCemStatsEgressSESs indicates the number
--                      of Severely Error Seconds (SESs) encountered.  This is
--                      when more than 30 percent of the packets within a one
--                      second window are missing."
--     ::= { tnSapCemStatsEntry 14 }
--
-- tnSapCemStatsEgressUASs  OBJECT-TYPE
--     SYNTAX          Counter32
--     MAX-ACCESS      read-only
--     STATUS          current
--     DESCRIPTION     "The value of tnSapCemStatsEgressUASs indicates the number of
--                      Unavailable Seconds (UASs) encountered. Any consecutive
--                      ten seconds of SESs are counted as one UAS."
--     ::= { tnSapCemStatsEntry 15 }
--
-- tnSapCemStatsEgressFailureCounts  OBJECT-TYPE
--     SYNTAX          Counter32
--     MAX-ACCESS      read-only
--     STATUS          current
--     DESCRIPTION     "The value of tnSapCemStatsEgressFailureCounts indicates
--                      the number failure events.  A failure event begins when
--                      the LOPS failure is declared, and ends when the failure
--                      is cleared."
--     ::= { tnSapCemStatsEntry 16 }
--
-- tnSapCemStatsEgressUnderrunCounts  OBJECT-TYPE
--     SYNTAX          Counter32
--     MAX-ACCESS      read-only
--     STATUS          current
--     DESCRIPTION     "The value of tnSapCemStatsEgressUnderrunCounts indicates
--                      the number of times the jitter buffer went into an
--                      underrun state."
--     ::= { tnSapCemStatsEntry 17 }
--
-- tnSapCemStatsEgressOverrunCounts  OBJECT-TYPE
--     SYNTAX          Counter32
--     MAX-ACCESS      read-only
--     STATUS          current
--     DESCRIPTION     "The value of tnSapCemStatsEgressOverrunCounts indicates
--                      the number of times the jitter buffer went into an
--                      overrun state."
--     ::= { tnSapCemStatsEntry 18 }
--
-- tnSapCemStatsEgressJtrBfrDepth  OBJECT-TYPE
--     SYNTAX          Gauge32
--     MAX-ACCESS      read-only
--     STATUS          current
--     DESCRIPTION     "The value of tnSapCemStatsEgressJtrBfrDepth indicates
--                      the current packet depth of the jitter buffer."
--     ::= { tnSapCemStatsEntry 19 }

-- ------------------------------------------------------------
-- SAP TLS L2PT Statistics Table
-- ------------------------------------------------------------
-- tnSapTlsL2ptStatsTable OBJECT-TYPE
--     SYNTAX          SEQUENCE OF SapTlsL2ptStatsEntry
--     MAX-ACCESS      not-accessible
--     STATUS          current
--     DESCRIPTION     "A table that contains SAP Layer 2 Protocol Tunneling
--                      Statistics.
--                      This table complements tnSapTlsInfoTable. Rows in this
--                      table are created and deleted automatically by the
--                      system."
--     ::= { tnSapObjs 42 }
--
-- tnSapTlsL2ptStatsEntry OBJECT-TYPE
--     SYNTAX          SapTlsL2ptStatsEntry
--     MAX-ACCESS      not-accessible
--     STATUS          current
--     DESCRIPTION     "Layer 2 Protocol Tunneling Statistics for a specific SAP.
--                      The statistics are provided for each combination of
--                      Destination Address and LLC SNAP type."
--     INDEX           { tnSysSwitchId,  tnSvcId, tnSapPortId, tnSapEncapValue }
--     ::= { tnSapTlsL2ptStatsTable 1 }
--
-- SapTlsL2ptStatsEntry ::=
--     SEQUENCE {
--         tnSapTlsL2ptStatsLastClearedTime              TimeStamp,
--         tnSapTlsL2ptStatsL2ptEncapStpConfigBpdusRx    Counter32,
--         tnSapTlsL2ptStatsL2ptEncapStpConfigBpdusTx    Counter32,
--         tnSapTlsL2ptStatsL2ptEncapStpRstBpdusRx       Counter32,
--         tnSapTlsL2ptStatsL2ptEncapStpRstBpdusTx       Counter32,
--         tnSapTlsL2ptStatsL2ptEncapStpTcnBpdusRx       Counter32,
--         tnSapTlsL2ptStatsL2ptEncapStpTcnBpdusTx       Counter32,
--         tnSapTlsL2ptStatsL2ptEncapPvstConfigBpdusRx   Counter32,
--         tnSapTlsL2ptStatsL2ptEncapPvstConfigBpdusTx   Counter32,
--         tnSapTlsL2ptStatsL2ptEncapPvstRstBpdusRx      Counter32,
--         tnSapTlsL2ptStatsL2ptEncapPvstRstBpdusTx      Counter32,
--         tnSapTlsL2ptStatsL2ptEncapPvstTcnBpdusRx      Counter32,
--         tnSapTlsL2ptStatsL2ptEncapPvstTcnBpdusTx      Counter32,
--         tnSapTlsL2ptStatsStpConfigBpdusRx             Counter32,
--         tnSapTlsL2ptStatsStpConfigBpdusTx             Counter32,
--         tnSapTlsL2ptStatsStpRstBpdusRx                Counter32,
--         tnSapTlsL2ptStatsStpRstBpdusTx                Counter32,
--         tnSapTlsL2ptStatsStpTcnBpdusRx                Counter32,
--         tnSapTlsL2ptStatsStpTcnBpdusTx                Counter32,
--         tnSapTlsL2ptStatsPvstConfigBpdusRx            Counter32,
--         tnSapTlsL2ptStatsPvstConfigBpdusTx            Counter32,
--         tnSapTlsL2ptStatsPvstRstBpdusRx               Counter32,
--         tnSapTlsL2ptStatsPvstRstBpdusTx               Counter32,
--         tnSapTlsL2ptStatsPvstTcnBpdusRx               Counter32,
--         tnSapTlsL2ptStatsPvstTcnBpdusTx               Counter32,
--         tnSapTlsL2ptStatsOtherBpdusRx                 Counter32,
--         tnSapTlsL2ptStatsOtherBpdusTx                 Counter32,
--         tnSapTlsL2ptStatsOtherL2ptBpdusRx             Counter32,
--         tnSapTlsL2ptStatsOtherL2ptBpdusTx             Counter32,
--         tnSapTlsL2ptStatsOtherInvalidBpdusRx          Counter32,
--         tnSapTlsL2ptStatsOtherInvalidBpdusTx          Counter32,
--         tnSapTlsL2ptStatsL2ptEncapCdpBpdusRx          Counter32,
--         tnSapTlsL2ptStatsL2ptEncapCdpBpdusTx          Counter32,
--         tnSapTlsL2ptStatsL2ptEncapVtpBpdusRx          Counter32,
--         tnSapTlsL2ptStatsL2ptEncapVtpBpdusTx          Counter32,
--         tnSapTlsL2ptStatsL2ptEncapDtpBpdusRx          Counter32,
--         tnSapTlsL2ptStatsL2ptEncapDtpBpdusTx          Counter32,
--         tnSapTlsL2ptStatsL2ptEncapPagpBpdusRx         Counter32,
--         tnSapTlsL2ptStatsL2ptEncapPagpBpdusTx         Counter32,
--         tnSapTlsL2ptStatsL2ptEncapUdldBpdusRx         Counter32,
--         tnSapTlsL2ptStatsL2ptEncapUdldBpdusTx         Counter32,
--         tnSapTlsL2ptStatsCdpBpdusRx                   Counter32,
--         tnSapTlsL2ptStatsCdpBpdusTx                   Counter32,
--         tnSapTlsL2ptStatsVtpBpdusRx                   Counter32,
--         tnSapTlsL2ptStatsVtpBpdusTx                   Counter32,
--         tnSapTlsL2ptStatsDtpBpdusRx                   Counter32,
--         tnSapTlsL2ptStatsDtpBpdusTx                   Counter32,
--         tnSapTlsL2ptStatsPagpBpdusRx                  Counter32,
--         tnSapTlsL2ptStatsPagpBpdusTx                  Counter32,
--         tnSapTlsL2ptStatsUdldBpdusRx                  Counter32,
--         tnSapTlsL2ptStatsUdldBpdusTx                  Counter32
--     }
--
-- tnSapTlsL2ptStatsLastClearedTime OBJECT-TYPE
--     SYNTAX          TimeStamp
--     MAX-ACCESS      read-only
--     STATUS          current
--     DESCRIPTION     "The value of tnSapTlsL2ptStatsLastClearedTime indicates
--                      the last time that these stats were cleared. The value
--                      zero indicates that they have not been cleared yet."
--     ::= { tnSapTlsL2ptStatsEntry 1 }
--
-- tnSapTlsL2ptStatsL2ptEncapStpConfigBpdusRx OBJECT-TYPE
--     SYNTAX          Counter32
--     MAX-ACCESS      read-only
--     STATUS          current
--     DESCRIPTION     "The value of tnSapTlsL2ptStatsL2ptEncapStpConfigBpdusRx indicates the
--                      number of L2PT encapsulated STP config bpdus received on this SAP."
--     ::= { tnSapTlsL2ptStatsEntry 2 }
--
-- tnSapTlsL2ptStatsL2ptEncapStpConfigBpdusTx OBJECT-TYPE
--     SYNTAX          Counter32
--     MAX-ACCESS      read-only
--     STATUS          current
--     DESCRIPTION     "The value of tnSapTlsL2ptStatsL2ptEncapStpConfigBpdusTx indicates the
--                      number of L2PT encapsulated STP config bpdus transmitted on this SAP."
--     ::= { tnSapTlsL2ptStatsEntry 3 }
--
-- tnSapTlsL2ptStatsL2ptEncapStpRstBpdusRx OBJECT-TYPE
--     SYNTAX          Counter32
--     MAX-ACCESS      read-only
--     STATUS          current
--     DESCRIPTION     "The value of tnSapTlsL2ptStatsL2ptEncapStpRstBpdusRx indicates the
--                      number of L2PT encapsulated STP rst bpdus received on this SAP."
--     ::= { tnSapTlsL2ptStatsEntry 4 }
--
-- tnSapTlsL2ptStatsL2ptEncapStpRstBpdusTx OBJECT-TYPE
--     SYNTAX          Counter32
--     MAX-ACCESS      read-only
--     STATUS          current
--     DESCRIPTION     "The value of tnSapTlsL2ptStatsL2ptEncapStpRstBpdusTx indicates the
--                      number of L2PT encapsulated STP rst bpdus transmitted on this SAP."
--     ::= { tnSapTlsL2ptStatsEntry 5 }
--
-- tnSapTlsL2ptStatsL2ptEncapStpTcnBpdusRx OBJECT-TYPE
--     SYNTAX          Counter32
--     MAX-ACCESS      read-only
--     STATUS          current
--     DESCRIPTION     "The value of tnSapTlsL2ptStatsL2ptEncapStpTcnBpdusRx indicates the
--                      number of L2PT encapsulated STP tcn bpdus received on this SAP."
--     ::= { tnSapTlsL2ptStatsEntry 6 }
--
-- tnSapTlsL2ptStatsL2ptEncapStpTcnBpdusTx OBJECT-TYPE
--     SYNTAX          Counter32
--     MAX-ACCESS      read-only
--     STATUS          current
--     DESCRIPTION     "The value of tnSapTlsL2ptStatsL2ptEncapStpTcnBpdusTx indicates the
--                      number of L2PT encapsulated STP tcn bpdus transmitted on this SAP."
--     ::= { tnSapTlsL2ptStatsEntry 7 }
--
-- tnSapTlsL2ptStatsL2ptEncapPvstConfigBpdusRx OBJECT-TYPE
--     SYNTAX          Counter32
--     MAX-ACCESS      read-only
--     STATUS          current
--     DESCRIPTION     "The value of tnSapTlsL2ptStatsL2ptEncapPvstConfigBpdusRx indicates the
--                      number of L2PT encapsulated PVST config bpdus received on this SAP."
--     ::= { tnSapTlsL2ptStatsEntry 8 }
--
-- tnSapTlsL2ptStatsL2ptEncapPvstConfigBpdusTx OBJECT-TYPE
--     SYNTAX          Counter32
--     MAX-ACCESS      read-only
--     STATUS          current
--     DESCRIPTION     "The value of tnSapTlsL2ptStatsL2ptEncapPvstConfigBpdusTx indicates the
--                      number of L2PT encapsulated PVST config bpdus transmitted on this SAP."
--     ::= { tnSapTlsL2ptStatsEntry 9 }
--
-- tnSapTlsL2ptStatsL2ptEncapPvstRstBpdusRx OBJECT-TYPE
--     SYNTAX          Counter32
--     MAX-ACCESS      read-only
--     STATUS          current
--     DESCRIPTION     "The value of tnSapTlsL2ptStatsL2ptEncapPvstRstBpdusRx indicates the
--                      number of L2PT encapsulated PVST rst bpdus received on this SAP."
--     ::= { tnSapTlsL2ptStatsEntry 10 }
--
-- tnSapTlsL2ptStatsL2ptEncapPvstRstBpdusTx OBJECT-TYPE
--     SYNTAX          Counter32
--     MAX-ACCESS      read-only
--     STATUS          current
--     DESCRIPTION     "The value of tnSapTlsL2ptStatsL2ptEncapPvstRstBpdusTx indicates the
--                      number of L2PT encapsulated PVST rst bpdus transmitted on this SAP."
--     ::= { tnSapTlsL2ptStatsEntry 11 }
--
-- tnSapTlsL2ptStatsL2ptEncapPvstTcnBpdusRx OBJECT-TYPE
--     SYNTAX          Counter32
--     MAX-ACCESS      read-only
--     STATUS          current
--     DESCRIPTION     "The value of tnSapTlsL2ptStatsL2ptEncapPvstTcnBpdusRx indicates the
--                      number of L2PT encapsulated PVST tcn bpdus received on this SAP."
--     ::= { tnSapTlsL2ptStatsEntry 12 }
--
-- tnSapTlsL2ptStatsL2ptEncapPvstTcnBpdusTx OBJECT-TYPE
--     SYNTAX          Counter32
--     MAX-ACCESS      read-only
--     STATUS          current
--     DESCRIPTION     "The value of tnSapTlsL2ptStatsL2ptEncapPvstTcnBpdusTx indicates the
--                      number of L2PT encapsulated PVST tcn bpdus transmitted on this SAP."
--     ::= { tnSapTlsL2ptStatsEntry 13 }
--
-- tnSapTlsL2ptStatsStpConfigBpdusRx OBJECT-TYPE
--     SYNTAX          Counter32
--     MAX-ACCESS      read-only
--     STATUS          current
--     DESCRIPTION     "The value of tnSapTlsL2ptStatsStpConfigBpdusRx indicates the
--                      number of STP config bpdus received on this SAP."
--     ::= { tnSapTlsL2ptStatsEntry 14 }
--
-- tnSapTlsL2ptStatsStpConfigBpdusTx OBJECT-TYPE
--     SYNTAX          Counter32
--     MAX-ACCESS      read-only
--     STATUS          current
--     DESCRIPTION     "The value of tnSapTlsL2ptStatsStpConfigBpdusTx indicates the
--                      number of STP config bpdus transmitted on this SAP."
--     ::= { tnSapTlsL2ptStatsEntry 15 }
--
-- tnSapTlsL2ptStatsStpRstBpdusRx OBJECT-TYPE
--     SYNTAX          Counter32
--     MAX-ACCESS      read-only
--     STATUS          current
--     DESCRIPTION     "The value of tnSapTlsL2ptStatsStpRstBpdusRx indicates the
--                      number of STP rst bpdus received on this SAP."
--     ::= { tnSapTlsL2ptStatsEntry 16 }
--
-- tnSapTlsL2ptStatsStpRstBpdusTx OBJECT-TYPE
--     SYNTAX          Counter32
--     MAX-ACCESS      read-only
--     STATUS          current
--     DESCRIPTION     "The value of tnSapTlsL2ptStatsStpRstBpdusTx indicates the
--                      number of STP rst bpdus transmitted on this SAP."
--     ::= { tnSapTlsL2ptStatsEntry 17 }
--
-- tnSapTlsL2ptStatsStpTcnBpdusRx OBJECT-TYPE
--     SYNTAX          Counter32
--     MAX-ACCESS      read-only
--     STATUS          current
--     DESCRIPTION     "The value of tnSapTlsL2ptStatsStpTcnBpdusRx indicates the
--                      number of STP tcn bpdus received on this SAP."
--     ::= { tnSapTlsL2ptStatsEntry 18 }
--
-- tnSapTlsL2ptStatsStpTcnBpdusTx OBJECT-TYPE
--     SYNTAX          Counter32
--     MAX-ACCESS      read-only
--     STATUS          current
--     DESCRIPTION     "The value of tnSapTlsL2ptStatsStpTcnBpdusTx indicates the
--                      number of STP tcn bpdus transmitted on this SAP."
--     ::= { tnSapTlsL2ptStatsEntry 19 }
--
-- tnSapTlsL2ptStatsPvstConfigBpdusRx OBJECT-TYPE
--     SYNTAX          Counter32
--     MAX-ACCESS      read-only
--     STATUS          current
--     DESCRIPTION     "The value of tnSapTlsL2ptStatsPvstConfigBpdusRx indicates the
--                      number of PVST config bpdus received on this SAP."
--     ::= { tnSapTlsL2ptStatsEntry 20 }
--
-- tnSapTlsL2ptStatsPvstConfigBpdusTx OBJECT-TYPE
--     SYNTAX          Counter32
--     MAX-ACCESS      read-only
--     STATUS          current
--     DESCRIPTION     "The value of tnSapTlsL2ptStatsPvstConfigBpdusTx indicates the
--                      number of PVST config bpdus transmitted on this SAP."
--     ::= { tnSapTlsL2ptStatsEntry 21 }
--
-- tnSapTlsL2ptStatsPvstRstBpdusRx OBJECT-TYPE
--     SYNTAX          Counter32
--     MAX-ACCESS      read-only
--     STATUS          current
--     DESCRIPTION     "The value of tnSapTlsL2ptStatsPvstRstBpdusRx indicates the
--                      number of PVST rst bpdus received on this SAP."
--     ::= { tnSapTlsL2ptStatsEntry 22 }
--
-- tnSapTlsL2ptStatsPvstRstBpdusTx OBJECT-TYPE
--     SYNTAX          Counter32
--     MAX-ACCESS      read-only
--     STATUS          current
--     DESCRIPTION     "The value of tnSapTlsL2ptStatsPvstRstBpdusTx indicates the
--                      number of PVST rst bpdus transmitted on this SAP."
--     ::= { tnSapTlsL2ptStatsEntry 23 }
--
-- tnSapTlsL2ptStatsPvstTcnBpdusRx OBJECT-TYPE
--     SYNTAX          Counter32
--     MAX-ACCESS      read-only
--     STATUS          current
--     DESCRIPTION     "The value of tnSapTlsL2ptStatsPvstTcnBpdusRx indicates the
--                      number of PVST tcn bpdus received on this SAP."
--     ::= { tnSapTlsL2ptStatsEntry 24 }
--
-- tnSapTlsL2ptStatsPvstTcnBpdusTx OBJECT-TYPE
--     SYNTAX          Counter32
--     MAX-ACCESS      read-only
--     STATUS          current
--     DESCRIPTION     "The value of tnSapTlsL2ptStatsPvstTcnBpdusTx indicates the
--                      number of PVST tcn bpdus transmitted on this SAP."
--     ::= { tnSapTlsL2ptStatsEntry 25 }
--
-- tnSapTlsL2ptStatsOtherBpdusRx OBJECT-TYPE
--     SYNTAX          Counter32
--     MAX-ACCESS      read-only
--     STATUS          current
--     DESCRIPTION     "The value of tnSapTlsL2ptStatsOtherBpdusRx indicates the
--                      number of other bpdus received on this SAP."
--     ::= { tnSapTlsL2ptStatsEntry 26 }
--
-- tnSapTlsL2ptStatsOtherBpdusTx OBJECT-TYPE
--     SYNTAX          Counter32
--     MAX-ACCESS      read-only
--     STATUS          current
--     DESCRIPTION     "The value of tnSapTlsL2ptStatsOtherBpdusTx indicates the
--                      number of other bpdus transmitted on this SAP."
--     ::= { tnSapTlsL2ptStatsEntry 27 }
--
-- tnSapTlsL2ptStatsOtherL2ptBpdusRx OBJECT-TYPE
--     SYNTAX          Counter32
--     MAX-ACCESS      read-only
--     STATUS          current
--     DESCRIPTION     "The value of tnSapTlsL2ptStatsOtherL2ptBpdusRx indicates the
--                      number of other L2PT bpdus received on this SAP."
--     ::= { tnSapTlsL2ptStatsEntry 28 }
--
-- tnSapTlsL2ptStatsOtherL2ptBpdusTx OBJECT-TYPE
--     SYNTAX          Counter32
--     MAX-ACCESS      read-only
--     STATUS          current
--     DESCRIPTION     "The value of tnSapTlsL2ptStatsOtherL2ptBpdusTx indicates the
--                      number of other L2PT bpdus transmitted on this SAP."
--     ::= { tnSapTlsL2ptStatsEntry 29 }
--
-- tnSapTlsL2ptStatsOtherInvalidBpdusRx OBJECT-TYPE
--     SYNTAX          Counter32
--     MAX-ACCESS      read-only
--     STATUS          current
--     DESCRIPTION     "The value of tnSapTlsL2ptStatsOtherInvalidBpdusRx indicates the
--                      number of other invalid bpdus received on this SAP."
--     ::= { tnSapTlsL2ptStatsEntry 30 }
--
-- tnSapTlsL2ptStatsOtherInvalidBpdusTx OBJECT-TYPE
--     SYNTAX          Counter32
--     MAX-ACCESS      read-only
--     STATUS          current
--     DESCRIPTION     "The value of tnSapTlsL2ptStatsOtherInvalidBpdusTx indicates the
--                      number of other invalid bpdus transmitted on this SAP."
--     ::= { tnSapTlsL2ptStatsEntry 31 }
--
-- tnSapTlsL2ptStatsL2ptEncapCdpBpdusRx OBJECT-TYPE
--     SYNTAX          Counter32
--     MAX-ACCESS      read-only
--     STATUS          current
--     DESCRIPTION     "The value of tnSapTlsL2ptStatsL2ptEncapCdpBpdusRx indicates the
--                      number of L2PT encapsulated CDP bpdus received on this SAP."
--     ::= { tnSapTlsL2ptStatsEntry 32 }
--
-- tnSapTlsL2ptStatsL2ptEncapCdpBpdusTx OBJECT-TYPE
--     SYNTAX          Counter32
--     MAX-ACCESS      read-only
--     STATUS          current
--     DESCRIPTION     "The value of tnSapTlsL2ptStatsL2ptEncapCdpBpdusTx indicates the
--                      number of L2PT encapsulated CDP bpdus transmitted on this SAP."
--     ::= { tnSapTlsL2ptStatsEntry 33 }
--
-- tnSapTlsL2ptStatsL2ptEncapVtpBpdusRx OBJECT-TYPE
--     SYNTAX          Counter32
--     MAX-ACCESS      read-only
--     STATUS          current
--     DESCRIPTION     "The value of tnSapTlsL2ptStatsL2ptEncapVtpBpdusRx indicates the
--                      number of L2PT encapsulated VTP bpdus received on this SAP."
--     ::= { tnSapTlsL2ptStatsEntry 34 }
--
-- tnSapTlsL2ptStatsL2ptEncapVtpBpdusTx OBJECT-TYPE
--     SYNTAX          Counter32
--     MAX-ACCESS      read-only
--     STATUS          current
--     DESCRIPTION     "The value of tnSapTlsL2ptStatsL2ptEncapVtpBpdusTx indicates the
--                      number of L2PT encapsulated VTP bpdus transmitted on this SAP."
--     ::= { tnSapTlsL2ptStatsEntry 35 }
--
-- tnSapTlsL2ptStatsL2ptEncapDtpBpdusRx OBJECT-TYPE
--     SYNTAX          Counter32
--     MAX-ACCESS      read-only
--     STATUS          current
--     DESCRIPTION     "The value of tnSapTlsL2ptStatsL2ptEncapDtpBpdusRx indicates the
--                      number of L2PT encapsulated DTP bpdus received on this SAP."
--     ::= { tnSapTlsL2ptStatsEntry 36 }
--
-- tnSapTlsL2ptStatsL2ptEncapDtpBpdusTx OBJECT-TYPE
--     SYNTAX          Counter32
--     MAX-ACCESS      read-only
--     STATUS          current
--     DESCRIPTION     "The value of tnSapTlsL2ptStatsL2ptEncapDtpBpdusTx indicates the
--                      number of L2PT encapsulated DTP bpdus transmitted on this SAP."
--     ::= { tnSapTlsL2ptStatsEntry 37 }
--
-- tnSapTlsL2ptStatsL2ptEncapPagpBpdusRx OBJECT-TYPE
--     SYNTAX          Counter32
--     MAX-ACCESS      read-only
--     STATUS          current
--     DESCRIPTION     "The value of tnSapTlsL2ptStatsL2ptEncapPagpBpdusRx indicates the
--                      number of L2PT encapsulated PAGP bpdus received on this SAP."
--     ::= { tnSapTlsL2ptStatsEntry 38 }
--
-- tnSapTlsL2ptStatsL2ptEncapPagpBpdusTx OBJECT-TYPE
--     SYNTAX          Counter32
--     MAX-ACCESS      read-only
--     STATUS          current
--     DESCRIPTION     "The value of tnSapTlsL2ptStatsL2ptEncapPagpBpdusTx indicates the
--                      number of L2PT encapsulated PAGP bpdus transmitted on this SAP."
--     ::= { tnSapTlsL2ptStatsEntry 39 }
--
--
-- tnSapTlsL2ptStatsL2ptEncapUdldBpdusRx OBJECT-TYPE
--     SYNTAX          Counter32
--     MAX-ACCESS      read-only
--     STATUS          current
--     DESCRIPTION     "The value of tnSapTlsL2ptStatsL2ptEncapUdldBpdusRx indicates the
--                      number of L2PT encapsulated UDLD bpdus received on this SAP."
--     ::= { tnSapTlsL2ptStatsEntry 40 }
--
-- tnSapTlsL2ptStatsL2ptEncapUdldBpdusTx OBJECT-TYPE
--     SYNTAX          Counter32
--     MAX-ACCESS      read-only
--     STATUS          current
--     DESCRIPTION     "The value of tnSapTlsL2ptStatsL2ptEncapUdldBpdusTx indicates the
--                      number of L2PT encapsulated UDLD bpdus transmitted on this SAP."
--     ::= { tnSapTlsL2ptStatsEntry 41 }
--
-- tnSapTlsL2ptStatsCdpBpdusRx OBJECT-TYPE
--     SYNTAX          Counter32
--     MAX-ACCESS      read-only
--     STATUS          current
--     DESCRIPTION     "The value of tnSapTlsL2ptStatsCdpBpdusRx indicates the
--                      number of CDP bpdus received on this SAP."
--     ::= { tnSapTlsL2ptStatsEntry 42 }
--
-- tnSapTlsL2ptStatsCdpBpdusTx OBJECT-TYPE
--     SYNTAX          Counter32
--     MAX-ACCESS      read-only
--     STATUS          current
--     DESCRIPTION     "The value of tnSapTlsL2ptStatsCdpBpdusTx indicates the
--                      number of CDP bpdus transmitted on this SAP."
--     ::= { tnSapTlsL2ptStatsEntry 43 }
--
-- tnSapTlsL2ptStatsVtpBpdusRx OBJECT-TYPE
--     SYNTAX          Counter32
--     MAX-ACCESS      read-only
--     STATUS          current
--     DESCRIPTION     "The value of tnSapTlsL2ptStatsVtpBpdusRx indicates the
--                      number of VTP bpdus received on this SAP."
--     ::= { tnSapTlsL2ptStatsEntry 44 }
--
-- tnSapTlsL2ptStatsVtpBpdusTx OBJECT-TYPE
--     SYNTAX          Counter32
--     MAX-ACCESS      read-only
--     STATUS          current
--     DESCRIPTION     "The value of tnSapTlsL2ptStatsVtpBpdusTx indicates the
--                      number of VTP bpdus transmitted on this SAP."
--     ::= { tnSapTlsL2ptStatsEntry 45 }
--
--
-- tnSapTlsL2ptStatsDtpBpdusRx OBJECT-TYPE
--     SYNTAX          Counter32
--     MAX-ACCESS      read-only
--     STATUS          current
--     DESCRIPTION     "The value of tnSapTlsL2ptStatsDtpBpdusRx indicates the
--                      number of DTP bpdus received on this SAP."
--     ::= { tnSapTlsL2ptStatsEntry 46 }
--
-- tnSapTlsL2ptStatsDtpBpdusTx OBJECT-TYPE
--     SYNTAX          Counter32
--     MAX-ACCESS      read-only
--     STATUS          current
--     DESCRIPTION     "The value of tnSapTlsL2ptStatsDtpBpdusTx indicates the
--                      number of DTP bpdus transmitted on this SAP."
--     ::= { tnSapTlsL2ptStatsEntry 47 }
--
-- tnSapTlsL2ptStatsPagpBpdusRx OBJECT-TYPE
--     SYNTAX          Counter32
--     MAX-ACCESS      read-only
--     STATUS          current
--     DESCRIPTION     "The value of tnSapTlsL2ptStatsPagpBpdusRx indicates the
--                      number of PAGP bpdus received on this SAP."
--     ::= { tnSapTlsL2ptStatsEntry 48 }
--
-- tnSapTlsL2ptStatsPagpBpdusTx OBJECT-TYPE
--     SYNTAX          Counter32
--     MAX-ACCESS      read-only
--     STATUS          current
--     DESCRIPTION     "The value of tnSapTlsL2ptStatsPagpBpdusTx indicates the
--                      number of PAGP bpdus transmitted on this SAP."
--     ::= { tnSapTlsL2ptStatsEntry 49 }
--
--
-- tnSapTlsL2ptStatsUdldBpdusRx OBJECT-TYPE
--     SYNTAX          Counter32
--     MAX-ACCESS      read-only
--     STATUS          current
--     DESCRIPTION     "The value of tnSapTlsL2ptStatsUdldBpdusRx indicates the
--                      number of UDLD bpdus received on this SAP."
--     ::= { tnSapTlsL2ptStatsEntry 50 }
--
-- tnSapTlsL2ptStatsUdldBpdusTx OBJECT-TYPE
--     SYNTAX          Counter32
--     MAX-ACCESS      read-only
--     STATUS          current
--     DESCRIPTION     "The value of tnSapTlsL2ptStatsUdldBpdusTx indicates the
--                      number of UDLD bpdus transmitted on this SAP."
--     ::= { tnSapTlsL2ptStatsEntry 51 }

-- ---------------------------------------------------------------------
-- Ethernet SAP Table
--
--
--  Sparse Dependent Extension of the tnSapBaseInfoTable.
--
--  The same indexes are used for both the base table, tnSapBaseInfoTable,
--  and the sparse dependent table, tnSapEthernetInfoTable.
--
--  This in effect extends the tnSapBaseInfoTable with additional columns.
--  Rows are created in the tnSapEthernetInfoTable only for those entries
--  in the tnSapBaseInfoTable that are created on a port with a
--  tmnxPortEncapType of 'EthernetEncap.'
--
--  Deletion of a row in the tnSapBaseInfoTable results in the
--  same fate for the row in the tnSapEthernetInfoTable.
-- ---------------------------------------------------------------------
tnSapEthernetInfoTable OBJECT-TYPE
    SYNTAX          SEQUENCE OF SapEthernetInfoEntry
    MAX-ACCESS      not-accessible
    STATUS          current
    DESCRIPTION     "A table that contains Ethernet SAP information."
    ::= { tnSapObjs 43 }

tnSapEthernetInfoEntry OBJECT-TYPE
    SYNTAX          SapEthernetInfoEntry
    MAX-ACCESS      not-accessible
    STATUS          current
    DESCRIPTION     "Information about a specific Ethernet SAP."
    INDEX           { tnSysSwitchId, tnSvcId, tnSapPortId, tnSapEncapValue }
    ::= { tnSapEthernetInfoTable 1 }

SapEthernetInfoEntry ::=
    SEQUENCE {
        tnSapEthernetLLFAdminStatus             ServiceAdminStatus,
        tnSapEthernetLLFOperStatus              INTEGER,
        tnSapEthernetLLFId                      Unsigned32,
        tnSapEthernetLoopbackMode               SapLoopbackMode,
        tnSapEthernetLoopbackMacSwapStaticMac   TruthValue
    }

tnSapEthernetLLFAdminStatus OBJECT-TYPE
    SYNTAX          ServiceAdminStatus
    MAX-ACCESS      read-create
    STATUS          current
    DESCRIPTION     "tnSapEthernetLLFAdminStatus specifies whether or not Link-
                    Loss Forwarding is enabled ('up'). When this object is set
                    to 'up' the underlying port will be forced into the
                    operationally 'down' state if the service is operationally
                    'down', or any of the remote LPT indicators for the port
                    are received, and will set the underlying port's
                    tmnxPortEtherReasonDownFlags 'linklossFwd' bit. Setting
                    this object to 'down' will clear the 'linklossFwd' reason.
                    tnSapEthernetLLFAdminStatus can only be enabled on saps
                    configured for an EPIPE or a VPLSS service using an Ethernet
                    port with the tnPortEncapType set to 'nullEncap.' A VPLS
                    service must use ERP and the LLFId must be nonzero."
    DEFVAL          { down }
    ::= { tnSapEthernetInfoEntry 1 }

tnSapEthernetLLFOperStatus OBJECT-TYPE
    SYNTAX          INTEGER {
                        fault (1),   -- service is down or fault detected.
                        clear (2)    -- service is up and no fault detected.
                    }
    MAX-ACCESS      read-only
    STATUS          current
    DESCRIPTION     "tnSapEthernetLLFOperStatus indicates whether or not the
                    underlying port is forced operationally 'down' due to the
                    service being operationally 'down' or an
                    sdpBindPwPeerStatusBits bit is set.
                    tnSapEthernetLLFOperStatus is set to 'fault' when the
                    tnSapEthernetLLFAdminStatus is set to 'up,' and either a
                    fault has occurred on the pseudo-wire, or the service is
                    down, otherwise tnSapEthernetLLFOperStatus is set to 'clear.'"
    ::= { tnSapEthernetInfoEntry 2 }

tnSapEthernetLLFId OBJECT-TYPE
    SYNTAX          Unsigned32 (0..5)
    MAX-ACCESS      read-create
    STATUS          current
    DESCRIPTION     "sapEthernetLLFId specifies an identifier between sending
                    and receiving objects that are LLF enabled. Only the object with
                    the same sapEthernetLLFId will receive the LLF status.
                    There can be up to five pairs of LLF-enabled SAPs per Ethernet Ring.
                    0 means no index is specified. The value can only be changed if
                    sapEthernetLLFAdminStatus is 'down'. This Id is used only in VPLS and
                    ignored in EPIPE"
    DEFVAL          { 0 }
    ::= { tnSapEthernetInfoEntry 3 }

tnSapEthernetLoopbackMode OBJECT-TYPE
    SYNTAX          SapLoopbackMode
    MAX-ACCESS      read-create
    STATUS          current
    DESCRIPTION     "tnSapEthernetLoopbackMode specifies the loopback mode of a sap.
                    When mode 'terminal' is set, SAP terminal loopback is enabled
                      with MAC swap.
                    When mode 'facility' is set, SAP facility loopback is enabled.
                      No MAC swap is performed."
    DEFVAL          { disabled }
    ::= { tnSapEthernetInfoEntry 4 }

tnSapEthernetLoopbackMacSwapStaticMac OBJECT-TYPE
    SYNTAX          TruthValue
    MAX-ACCESS      read-create
    STATUS          current
    DESCRIPTION     "tnSapEthernetLoopbackMacSwapStaticMac indicates whether or
                     not a unicast MAC is used in MAC swap when SAP terminal
                     loopback is enabled.  tnCardSapLoopbackMacAddr or
                     tnPacketSwitchSapLoopbackMacAddr need to be provisioned
                     before this attribute can be set to true."
    DEFVAL          { false }
    ::= { tnSapEthernetInfoEntry 5 }

-- --------------------------------------------------------
-- tnMtnSapPlcyTable
-- --------------------------------------------------------
-- tnMtnSapPlcyTable OBJECT-TYPE
--     SYNTAX      SEQUENCE OF MtnSapPlcyEntry
--     MAX-ACCESS  not-accessible
--     STATUS      current
--     DESCRIPTION
--         "The tnMtnSapPlcyTable has an entry for each managed SAP(MSAP) policy
--          configured in the system."
--     ::= { tnSapObjs 44 }
--
-- tnMtnSapPlcyEntry    OBJECT-TYPE
--     SYNTAX      MtnSapPlcyEntry
--     MAX-ACCESS  not-accessible
--     STATUS      current
--     DESCRIPTION
--         "Each entry represents the configuration for a managed SAP(MSAP) policy.
--
--          The values for each entry will be used to populate the following
--          tables when the MSAP policy is applied to a MSAP:
--
--          TIMETRA-SAP-MIB::tnSapBaseInfoTable
--          TIMETRA-SAP-MIB::tnSapSubMgmtInfoTable
--         "
--     INDEX { tnSysSwitchId, tnMtnSapPlcyName }
--     ::= { tnMtnSapPlcyTable 1}
--
-- MtnSapPlcyEntry ::= SEQUENCE
--     {
--         tnMtnSapPlcyName                     TNamedItem,
--         tnMtnSapPlcyRowStatus                RowStatus,
--         tnMtnSapPlcyLastChanged              TimeStamp,
--         tnMtnSapPlcyDescription              TItemDescription,
--         tnMtnSapPlcyCpmProtPolicyId          TCpmProtPolicyID,
--         tnMtnSapPlcyCpmProtMonitorMac        TruthValue,
--         tnMtnSapPlcySubMgmtDefSubId          INTEGER,
--         tnMtnSapPlcySubMgmtDefSubIdStr       TNamedItemOrEmpty,
--         tnMtnSapPlcySubMgmtDefSubProfile     TNamedItemOrEmpty,
--         tnMtnSapPlcySubMgmtDefSlaProfile     TNamedItemOrEmpty,
--         tnMtnSapPlcySubMgmtDefAppProfile     TNamedItemOrEmpty,
--         tnMtnSapPlcySubMgmtSubIdPlcy         TPolicyStatementNameOrEmpty,
--         tnMtnSapPlcySubMgmtSubscriberLimit   Unsigned32,
--         tnMtnSapPlcySubMgmtProfiledTrafOnly  TruthValue,
--         tnMtnSapPlcySubMgmtNonSubTrafSubId   TNamedItemOrEmpty,
--         tnMtnSapPlcySubMgmtNonSubTrafSubProf TNamedItemOrEmpty,
--         tnMtnSapPlcySubMgmtNonSubTrafSlaProf TNamedItemOrEmpty,
--         tnMtnSapPlcySubMgmtNonSubTrafAppProf TNamedItemOrEmpty,
--         tnMtnSapPlcyAssociatedMtnSaps          Counter32
--     }
--
-- tnMtnSapPlcyName        OBJECT-TYPE
--     SYNTAX      TNamedItem
--     MAX-ACCESS  not-accessible
--     STATUS      current
--     DESCRIPTION
--         "The value of tnMtnSapPlcyName specifies the name of the MSAP policy."
--     ::= { tnMtnSapPlcyEntry 1 }
--
-- tnMtnSapPlcyRowStatus        OBJECT-TYPE
--     SYNTAX      RowStatus
--     MAX-ACCESS  read-create
--     STATUS      current
--     DESCRIPTION
--         "The value of tnMtnSapPlcyRowStatus is used for the creation
--          and deletion of MSAP policies."
--     ::= { tnMtnSapPlcyEntry 2 }
--
-- tnMtnSapPlcyLastChanged        OBJECT-TYPE
--     SYNTAX      TimeStamp
--     MAX-ACCESS  read-only
--     STATUS      current
--     DESCRIPTION
--         "The value of tnMtnSapPlcyLastChanged indicates the sysUpTime
--          at the time of the last modification of this entry.
--
--          If no changes were made to the entry since the last
--          re-initialization of the local network management subsystem,
--          then this object contains a zero value."
--     ::= { tnMtnSapPlcyEntry 3 }
--
-- tnMtnSapPlcyDescription        OBJECT-TYPE
--     SYNTAX      TItemDescription
--     MAX-ACCESS  read-create
--     STATUS      current
--     DESCRIPTION
--         "The value of tnMtnSapPlcyDescription specifies the description
--          of the MSAP policy."
--     DEFVAL { "" }
--     ::= { tnMtnSapPlcyEntry 4 }
--
-- tnMtnSapPlcyCpmProtPolicyId  OBJECT-TYPE
--     SYNTAX          TCpmProtPolicyID
--     MAX-ACCESS      read-create
--     STATUS          current
--     DESCRIPTION
--         "The value of tnMtnSapPlcyCpmProtPolicyId specifies a CPM Protection
--          policy for the MSAP policy.
--
--          If a corresponding policy is not defined in
--          TIMETRA-SECURITY-MIB::tmnxCpmProtPolTable, an 'inconsistentValue'
--          error will be returned.
--
--          A value of one specifies that the default CPM Protection
--          policy is associated with the Managed SAP.
--
--          This object is not supported on SR-1 and ESS-1, where the
--          value of TIMETRA-CHASSIS-MIB::tmnxChassisType is '5',
--          and 7710, where the value of TIMETRA-CHASSIS-MIB::tmnxChassisType is
--          '7' or '9'. An attempt  to set tnMtnSapPlcyCpmProtPolicyId to a non-zero
--          value on one of these unsupported chassis types will return
--          an 'inconsistentValue' error."
--     DEFVAL { 1 }
--     ::= { tnMtnSapPlcyEntry 5 }
--
-- tnMtnSapPlcyCpmProtMonitorMac OBJECT-TYPE
--     SYNTAX          TruthValue
--     MAX-ACCESS      read-create
--     STATUS          current
--     DESCRIPTION
--          "The value of tnMtnSapPlcyCpmProtMonitorMac specifies whether the
--           tmnxCpmProtPolPerSrcRateLimit of the CPM Protection policy,
--           as specified by tnMtnSapPlcyCpmProtPolicyId, must be applied.
--
--          If the value of tnMtnSapPlcyCpmProtMonitorMac is 'true', the
--          per-source rate limit must be applied.
--
--          If the value of tnMtnSapPlcyCpmProtPolicyId is equal to zero,
--          the value of tnMtnSapPlcyCpmProtMonitorMac is irrelevant and
--          will be ignored.
--
--          This object is not supported on SR-1 and ESS-1, where the
--          value of TIMETRA-CHASSIS-MIB::tmnxChassisType is '5',
--          and 7710, where the value of TIMETRA-CHASSIS-MIB::tmnxChassisType is
--          '7' or '9'. An attempt  to set tnMtnSapPlcyCpmProtMonitorMac to 'true'
--          on one of these unsupported chassis types will return an
--          'inconsistentValue' error."
--     DEFVAL { false }
--     ::= { tnMtnSapPlcyEntry 6 }
--
-- tnMtnSapPlcySubMgmtDefSubId        OBJECT-TYPE
--     SYNTAX      INTEGER {
--                     useSapId  (1),
--                     useString (2)
--                 }
--     MAX-ACCESS  read-create
--     STATUS      current
--     DESCRIPTION
--         "The value of tnMtnSapPlcySubMgmtDefSubId specifies what will be used as
--          the default subscriber identification applicable on the MSAP.
--
--          This value is used in case no other source (like Radius) provides a
--          subscriber identification string.
--
--          If the value of this object is set to 'useSapId', the SAP-id will
--          be used as the default subscriber identification string. In this case,
--          tnMtnSapPlcySubMgmtDefSubIdStr must contain the empty string, so any
--          non-empty string in tnMtnSapPlcySubMgmtDefSubIdStr will be set to an empty
--          string.
--
--          If the value of this object is set to 'useString', the value of
--          tnMtnSapPlcySubMgmtDefSubIdStr will be used as the default subscriber
--          identification string. In this case, an empty tnMtnSapPlcySubMgmtDefSubIdStr
--          means that there is no default subscriber identification configured."
--     DEFVAL { useString }
--     ::= { tnMtnSapPlcyEntry 7 }
--
-- tnMtnSapPlcySubMgmtDefSubIdStr        OBJECT-TYPE
--     SYNTAX      TNamedItemOrEmpty
--     MAX-ACCESS  read-create
--     STATUS      current
--     DESCRIPTION
--         "The value of tnMtnSapPlcySubMgmtDefSubIdStr specifies the default
--          subscriber identification string applicable on this MSAP."
--     DEFVAL { "" }
--     ::= { tnMtnSapPlcyEntry 8 }
--
-- tnMtnSapPlcySubMgmtDefSubProfile        OBJECT-TYPE
--     SYNTAX      TNamedItemOrEmpty
--     MAX-ACCESS  read-create
--     STATUS      current
--     DESCRIPTION
--         "The value of tnMtnSapPlcySubMgmtDefSubProfile specifies the default
--          subscriber profile applicable on the MSAP.
--
--          If a corresponding profile is not defined in tmnxSubProfileTable, an
--          'inconsistentValue' error will be returned.
--
--          A value of 'default' is not allowed for this object."
--     DEFVAL { "" }
--     ::= { tnMtnSapPlcyEntry 9 }
--
-- tnMtnSapPlcySubMgmtDefSlaProfile        OBJECT-TYPE
--     SYNTAX      TNamedItemOrEmpty
--     MAX-ACCESS  read-create
--     STATUS      current
--     DESCRIPTION
--         "The value of tnMtnSapPlcySubMgmtDefSlaProfile specifies the default SLA
--          profile applicable on the MSAP.
--
--          If a corresponding profile is not defined in tmnxSLAProfileTable, an
--          'inconsistentValue' error will be returned."
--     DEFVAL { "" }
--     ::= { tnMtnSapPlcyEntry 10 }
--
-- tnMtnSapPlcySubMgmtDefAppProfile        OBJECT-TYPE
--     SYNTAX      TNamedItemOrEmpty
--     MAX-ACCESS  read-create
--     STATUS      current
--     DESCRIPTION
--         "The value of tnMtnSapPlcySubMgmtDefAppProfile specifies the default
--          application profile applicable on the MSAP.
--
--          If a corresponding profile is not defined in
--          TIMETRA-BSX-NG-MIB::tmnxBsxAppProfTable, an 'inconsistentValue'
--          error will be returned."
--     DEFVAL { "" }
--     ::= { tnMtnSapPlcyEntry 11 }
--
-- tnMtnSapPlcySubMgmtSubIdPlcy        OBJECT-TYPE
--     SYNTAX      TPolicyStatementNameOrEmpty
--     MAX-ACCESS  read-create
--     STATUS      current
--     DESCRIPTION
--         "The value of tnMtnSapPlcySubMgmtSubIdPlcy specifies the subscriber
--          identification policy applicable on the MSAP.
--
--          If a corresponding profile is not defined in tmnxSubIdentPolicyTable,
--          an 'inconsistentValue' error will be returned."
--     DEFVAL { "" }
--     ::= { tnMtnSapPlcyEntry 12 }
--
-- tnMtnSapPlcySubMgmtSubscriberLimit OBJECT-TYPE
--     SYNTAX          Unsigned32 (0..20000)
--     MAX-ACCESS      read-create
--     STATUS          current
--     DESCRIPTION
--         "The value of tnMtnSapPlcySubMgmtSubscriberLimit specifies the
--          maximum number of subscribers allowed for the MSAP.
--
--          A value is 0 means there is no limit.
--
--          The values for the objects tnMtnSapPlcySubMgmtProfiledTrafOnly,
--          tnMtnSapPlcySubMgmtNonSubTrafSubProf, and
--          tnMtnSapPlcySubMgmtNonSubTrafSlaProf are only meaningful when
--          the value of tnMtnSapPlcySubMgmtSubscriberLimit is 1 and will not
--          be used when the value of tnMtnSapPlcySubMgmtSubscriberLimit is
--          not 1."
--     DEFVAL { 1 }
--     ::= { tnMtnSapPlcyEntry 13 }
--
-- tnMtnSapPlcySubMgmtProfiledTrafOnly OBJECT-TYPE
--     SYNTAX          TruthValue
--     MAX-ACCESS      read-create
--     STATUS          current
--     DESCRIPTION
--         "The value of tnMtnSapPlcySubMgmtProfiledTrafOnly specifies
--          whether only profiled traffic is applicable for the MSAP.
--          If set to 'true', the MSAP queues will be deleted.
--
--          The value of this object is only meaningful if
--          tnMtnSapPlcySubMgmtSubscriberLimit is set to 1."
--     DEFVAL { false }
--     ::= { tnMtnSapPlcyEntry 14 }
--
-- tnMtnSapPlcySubMgmtNonSubTrafSubId OBJECT-TYPE
--     SYNTAX          TNamedItemOrEmpty
--     MAX-ACCESS      read-create
--     STATUS          current
--     DESCRIPTION
--         "The value of tnMtnSapPlcySubMgmtNonSubTrafSubId specifies the
--          subscriber identification applicable on the MSAP for all
--          non-subscriber traffic.
--
--          The value of this object is only meaningful if
--          tnMtnSapPlcySubMgmtSubscriberLimit is set to 1."
--     DEFVAL { "" }
--     ::= { tnMtnSapPlcyEntry 15 }
--
-- tnMtnSapPlcySubMgmtNonSubTrafSubProf OBJECT-TYPE
--     SYNTAX          TNamedItemOrEmpty
--     MAX-ACCESS      read-create
--     STATUS          current
--     DESCRIPTION
--         "The value of tnMtnSapPlcySubMgmtNonSubTrafSubProf specifies the
--          subscriber profile applicable on the MSAP for all
--          non-subscriber traffic.
--
--          The value of this object is only meaningful if
--          tnMtnSapPlcySubMgmtSubscriberLimit is set to 1."
--     DEFVAL { "" }
--     ::= { tnMtnSapPlcyEntry 16 }
--
-- tnMtnSapPlcySubMgmtNonSubTrafSlaProf OBJECT-TYPE
--     SYNTAX          TNamedItemOrEmpty
--     MAX-ACCESS      read-create
--     STATUS          current
--     DESCRIPTION
--         "The value of tnMtnSapPlcySubMgmtNonSubTrafSlaProf specifies the
--          SLA profile applicable on the MSAP for all non-subscriber
--          traffic.
--
--          The value of this object is only meaningful if
--          tnMtnSapPlcySubMgmtSubscriberLimit is set to 1."
--     DEFVAL { "" }
--     ::= { tnMtnSapPlcyEntry 17 }
--
-- tnMtnSapPlcySubMgmtNonSubTrafAppProf OBJECT-TYPE
--     SYNTAX          TNamedItemOrEmpty
--     MAX-ACCESS      read-create
--     STATUS          current
--     DESCRIPTION
--         "The value of tnMtnSapPlcySubMgmtNonSubTrafAppProf specifies the
--          Application profile applicable on the MSAP for all
--          non-subscriber traffic.
--
--          The value of this object is only meaningful if
--          tnMtnSapPlcySubMgmtSubscriberLimit is set to 1."
--     DEFVAL { "" }
--     ::= { tnMtnSapPlcyEntry 18 }
--
-- tnMtnSapPlcyAssociatedMtnSaps OBJECT-TYPE
--     SYNTAX          Counter32
--     MAX-ACCESS      read-only
--     STATUS          current
--     DESCRIPTION
--         "The value of tnMtnSapPlcyAssociatedMtnSaps indicates the
--          number of MSAPs associated with this MSAP policy."
--     ::= { tnMtnSapPlcyEntry 19 }

-- --------------------------------------------------------
-- tnMtnSapTlsPlcyTable
-- --------------------------------------------------------
-- tnMtnSapTlsPlcyTable OBJECT-TYPE
--     SYNTAX      SEQUENCE OF MtnSapTlsPlcyEntry
--     MAX-ACCESS  not-accessible
--     STATUS      current
--     DESCRIPTION
--         "The tnMtnSapTlsPlcyTable has an entry for each managed SAP (MSAP)
--          policy configured in the system."
--     ::= { tnSapObjs 45 }
--
-- tnMtnSapTlsPlcyEntry    OBJECT-TYPE
--     SYNTAX      MtnSapTlsPlcyEntry
--     MAX-ACCESS  not-accessible
--     STATUS      current
--     DESCRIPTION
--         "Each entry represents the VPLS-related configuration for a managed
--          SAP (MSAP) policy.
--
--          The values for each entry will be used to populate the following
--          VPLS-related tables when the MSAP policy is applied to a MSAP:
--
--          TIMETRA-SAP-MIB::tnSapTlsInfoTable
--          TIMETRA-SAP-MIB::tnSapTlsDhcpInfoTable
--          NOKIA-IGMP-SNOOPING-MIB::tlsIgmpSnpgConfigTable
--         "
--     AUGMENTS { tnMtnSapPlcyEntry }
--     ::= { tnMtnSapTlsPlcyTable 1}
--
-- MtnSapTlsPlcyEntry ::= SEQUENCE
--     {
--         tnMtnSapTlsPlcyLastChanged               TimeStamp,
--         tnMtnSapTlsPlcySplitHorizonGrp           TNamedItemOrEmpty,
--         tnMtnSapTlsPlcyArpReplyAgent             INTEGER,
--         tnMtnSapTlsPlcySubMgmtMacDaHashing       TruthValue,
--         tnMtnSapTlsPlcyDhcpLeasePopulate         Unsigned32,
--         tnMtnSapTlsPlcyDhcpPrxyAdminState        TmnxEnabledDisabled,
--         tnMtnSapTlsPlcyDhcpPrxyServAddrType      InetAddressType,
--         tnMtnSapTlsPlcyDhcpPrxyServAddr          InetAddress,
--         tnMtnSapTlsPlcyDhcpPrxyLeaseTime         Unsigned32,
--         tnMtnSapTlsPlcyDhcpPrxyLTRadOverride     TruthValue,
--         tnMtnSapTlsPlcyDhcpInfoAction            INTEGER,
--         tnMtnSapTlsPlcyDhcpCircuitId             INTEGER,
--         tnMtnSapTlsPlcyDhcpRemoteId              INTEGER,
--         tnMtnSapTlsPlcyDhcpRemoteIdString        TNamedItemOrEmpty,
--         tnMtnSapTlsPlcyDhcpVendorInclOpts        BITS,
--         tnMtnSapTlsPlcyDhcpVendorOptStr          TNamedItemOrEmpty,
--         tnMtnSapTlsPlcyEgressMcastGroup          TNamedItemOrEmpty,
--         tnMtnSapTlsPlcyIgmpSnpgImportPlcy        TPolicyStatementNameOrEmpty,
--         tnMtnSapTlsPlcyIgmpSnpgFastLeave         TmnxEnabledDisabled,
--         tnMtnSapTlsPlcyIgmpSnpgSendQueries       TmnxEnabledDisabled,
--         tnMtnSapTlsPlcyIgmpSnpgGenQueryIntv      Unsigned32,
--         tnMtnSapTlsPlcyIgmpSnpgQueryRespIntv     Unsigned32,
--         tnMtnSapTlsPlcyIgmpSnpgRobustCount       Unsigned32,
--         tnMtnSapTlsPlcyIgmpSnpgLastMembIntvl     Unsigned32,
--         tnMtnSapTlsPlcyIgmpSnpgMaxNbrGrps        Unsigned32,
--         tnMtnSapTlsPlcyIgmpSnpgMvrFromVplsId     TmnxServId,
--         tnMtnSapTlsPlcyIgmpSnpgVersion           TmnxIgmpVersion,
--         tnMtnSapTlsPlcyIgmpSnpgMcacPlcyName      TPolicyStatementNameOrEmpty,
--         tnMtnSapTlsPlcyIgmpSnpgMcacUncnstBW      Integer32,
--         tnMtnSapTlsPlcyIgmpSnpgMcacPrRsvMnBW     Integer32,
--         tnMtnSapTlsPlcyArpHostMaxNumHosts        Unsigned32,
--         tnMtnSapTlsPlcyArpHostMinAuthIntvl       Unsigned32
--
--     }
--
-- tnMtnSapTlsPlcyLastChanged        OBJECT-TYPE
--     SYNTAX      TimeStamp
--     MAX-ACCESS  read-only
--     STATUS      current
--     DESCRIPTION
--         "The value of tnMtnSapTlsPlcyLastChanged indicates the sysUpTime
--          at the time of the last modification of this entry.
--
--          If no changes were made to the entry since the last
--          re-initialization of the local network management subsystem,
--          then this object contains a zero value."
--     ::= { tnMtnSapTlsPlcyEntry 1 }
--
-- tnMtnSapTlsPlcySplitHorizonGrp        OBJECT-TYPE
--     SYNTAX      TNamedItemOrEmpty
--     MAX-ACCESS  read-create
--     STATUS      current
--     DESCRIPTION
--         "The value of tnMtnSapTlsPlcySplitHorizonGrp specifies the name of the
--          split-horizon group for the MSAP.
--
--          If the name specified does not correspond to a tlsShgInfoEntry
--          for the VPLS service, the creation of the MSAP will fail.
--          Additionally, if tnMtnSapTlsPlcySplitHorizonGrp is set to a new value,
--          the tnSapSplitHorizonGrp object for any existing MSAPs created by
--          this policy will not be updated."
--     DEFVAL { "" }
--     ::= { tnMtnSapTlsPlcyEntry 2 }
--
-- tnMtnSapTlsPlcyArpReplyAgent        OBJECT-TYPE
--     SYNTAX      INTEGER {
--                     disabled               (1),
--                     enabled                (2),
--                     enabledWithSubscrIdent (3)
--                 }
--     MAX-ACCESS  read-create
--     STATUS      current
--     DESCRIPTION
--         "The value of tnMtnSapTlsPlcyArpReplyAgent specifies the status of the special
--          ARP response mechanism in the system for ARP requests destined to
--          static or dynamic hosts associated with the MSAP.
--
--          'disabled'               - the ARP reply function is not operational
--          'enabled'                - the ARP reply function is enabled without
--                                       subscriber identification.
--          'enabledWithSubscrIdent' - the ARP reply function is enabled
--                                       with subscriber identification."
--     DEFVAL { disabled }
--     ::= { tnMtnSapTlsPlcyEntry 3 }
--
-- tnMtnSapTlsPlcySubMgmtMacDaHashing OBJECT-TYPE
--     SYNTAX          TruthValue
--     MAX-ACCESS      read-create
--     STATUS          current
--     DESCRIPTION
--         "The value of tnMtnSapTlsPlcySubMgmtMacDaHashing specifies whether
--          subscriber traffic egressing a LAG MSAP has its egress LAG
--          link selected by a function of the MAC destination address
--          instead of subscriber id."
--     DEFVAL { false }
--     ::= { tnMtnSapTlsPlcyEntry 4 }
--
-- tnMtnSapTlsPlcyDhcpLeasePopulate        OBJECT-TYPE
--     SYNTAX      Unsigned32 (0..32767)
--     MAX-ACCESS  read-create
--     STATUS      current
--     DESCRIPTION
--         "The value of tnMtnSapTlsPlcyDhcpLeasePopulate specifies the maximum number of
--          DHCP lease states allowed on the MSAP."
--     DEFVAL { 1 }
--     ::= { tnMtnSapTlsPlcyEntry 5 }
--
-- tnMtnSapTlsPlcyDhcpPrxyAdminState        OBJECT-TYPE
--     SYNTAX      TmnxEnabledDisabled
--     MAX-ACCESS  read-create
--     STATUS      current
--     DESCRIPTION
--         "The value of tnMtnSapTlsPlcyDhcpPrxyAdminState specifies the desired
--          administrative state of the proxy server on the interface."
--     DEFVAL { disabled }
--     ::= { tnMtnSapTlsPlcyEntry 6 }
--
-- tnMtnSapTlsPlcyDhcpPrxyServAddrType        OBJECT-TYPE
--     SYNTAX      InetAddressType
--     MAX-ACCESS  read-create
--     STATUS      current
--     DESCRIPTION
--         "The value of tnMtnSapTlsPlcyDhcpPrxyServAddrType specifies the address type
--         of tnMtnSapTlsPlcyDhcpPrxyServAddr."
--     DEFVAL { unknown }
--     ::= { tnMtnSapTlsPlcyEntry 7 }
--
-- tnMtnSapTlsPlcyDhcpPrxyServAddr        OBJECT-TYPE
--     SYNTAX      InetAddress (SIZE(0|4|16|20))
--     MAX-ACCESS  read-create
--     STATUS      current
--     DESCRIPTION
--         "The value of tnMtnSapTlsPlcyDhcpPrxyServAddr specifies the IP address of the
--          which will be used as the source address of the emulated DHCP server
--          in the context of the VPLS MSAP.
--
--          This address is mandatory for the proxy server capability and it
--          should be in the context of the subnet represented by the VPLS."
--     DEFVAL { ''H }
--     ::= { tnMtnSapTlsPlcyEntry 8 }
--
-- tnMtnSapTlsPlcyDhcpPrxyLeaseTime        OBJECT-TYPE
--     SYNTAX      Unsigned32 (0|300..315446399)
--     UNITS       "seconds"
--     MAX-ACCESS  read-create
--     STATUS      current
--     DESCRIPTION
--         "The value of tnMtnSapTlsPlcyDhcpPrxyLeaseTime specifies, in seconds, how long
--          a DHCP client is allowed to use the offered IP address.
--
--          A value of 0 means the lease time provided by a RADIUS or an upstream
--          DHCP server will not be overridden. A value of
--          7 days (315446399 seconds) is used when RADIUS does not provide a
--          lease time."
--     DEFVAL { 0 }
--     ::= { tnMtnSapTlsPlcyEntry 9 }
--
-- tnMtnSapTlsPlcyDhcpPrxyLTRadOverride        OBJECT-TYPE
--     SYNTAX      TruthValue
--     MAX-ACCESS  read-create
--     STATUS      current
--     DESCRIPTION
--         "The value of tnMtnSapTlsPlcyDhcpPrxyLTRadOverride specifies whether or not the
--          lease time provided by the RADIUS server is presented to the DHCP
--          client.
--
--          By default the proxy-server will always make use of
--          tnMtnSapTlsPlcyDhcpPrxyLeaseTime, regardless of what lease time information is
--          provided from the RADIUS server. When tnMtnSapTlsPlcyDhcpPrxyLTRadOverride is
--          set to 'true', the proxy-server will use the lease time
--          information provided by the RADIUS server, regardless of the
--          configured lease time."
--     DEFVAL { false }
--     ::= { tnMtnSapTlsPlcyEntry 10 }
--
-- tnMtnSapTlsPlcyDhcpInfoAction        OBJECT-TYPE
--     SYNTAX      INTEGER {
--                     replace (1),
--                     drop    (2),
--                     keep    (3)
--                 }
--     MAX-ACCESS  read-create
--     STATUS      current
--     DESCRIPTION
--         "The value of tnMtnSapTlsPlcyDhcpInfoAction specifies the DHCP option
--          reforwarding policy:
--
--          'replace' - replace existing information with configured
--                        information
--          'drop'    - discard messages with existing relay information if the
--                        option-82 information is also present
--          'keep'    - retain the existing relay information"
--     DEFVAL { keep }
--     ::= { tnMtnSapTlsPlcyEntry 11 }
--
-- tnMtnSapTlsPlcyDhcpCircuitId        OBJECT-TYPE
--     SYNTAX      INTEGER {
--                     none           (0),
--                     asciiTuple     (1),
--                     vlanAsciiTuple (2)
--                 }
--     MAX-ACCESS  read-create
--     STATUS      current
--     DESCRIPTION
--         "The value of tnMtnSapTlsPlcyDhcpCircuitId specifies whether or not the
--          circuit-id suboption is present, and if it is present what
--          information goes in it:
--
--          none           - the circuit-id suboption will not be part of
--                           the information option (Option 82).
--          asciiTuple     - the ASCII-encoded concatenated tuple consisting
--                           of the
--                               - access-node-identifier
--                               - service-id
--                               - interface-name
--                           is used.
--          vlanAsciiTuple - the format will include VLAN-id and dot1p bits
--                           in addition to what is included in ascii-tuple
--                           already.  The format is supported on dot1q and
--                           qinq encapsulated ports only.  Thus, when the
--                           option 82 bits are stripped, dot1p bits will be
--                           copied to the Ethernet header of an outgoing
--                           packet."
--     DEFVAL { asciiTuple }
--     ::= { tnMtnSapTlsPlcyEntry 12 }
--
-- tnMtnSapTlsPlcyDhcpRemoteId        OBJECT-TYPE
--     SYNTAX      INTEGER {
--                     none      (1),
--                     mac       (2),
--                     remote-id (3)
--                 }
--     MAX-ACCESS  read-create
--     STATUS      current
--     DESCRIPTION
--         "The value of tnMtnSapTlsPlcyDhcpRemoteId specifies what information goes into
--          the remote-id suboption in the DHCP Relay packet.
--
--          If the value of this object is set to 'none', the remote-id suboption
--          will not be part of the information option (Option 82).
--
--          If the value of this object is set to 'mac', the MAC address of the
--          remote end is encoded in the suboption.
--
--          If the value of this object is set to 'remote-id',
--          tnMtnSapTlsPlcyDhcpRemoteIdString will represent the remote-id.
--
--          By default, the remote-id value is none."
--     DEFVAL { none }
--     ::= { tnMtnSapTlsPlcyEntry 13 }
--
-- tnMtnSapTlsPlcyDhcpRemoteIdString        OBJECT-TYPE
--     SYNTAX      TNamedItemOrEmpty
--     MAX-ACCESS  read-create
--     STATUS      current
--     DESCRIPTION
--         "The value of tnMtnSapTlsPlcyDhcpRemoteIdString specifies the remote-id. The
--          value of this object is ignored if tnMtnSapTlsPlcyDhcpRemoteId does not have
--          the value of 'remote-id'."
--     DEFVAL { "" }
--     ::= { tnMtnSapTlsPlcyEntry 14 }
--
-- tnMtnSapTlsPlcyDhcpVendorInclOpts        OBJECT-TYPE
--     SYNTAX      BITS {
--                     systemId  (0),
--                     clientMac (1),
--                     serviceId (2),
--                     tnSapId     (3)
--                 }
--     MAX-ACCESS  read-create
--     STATUS      current
--     DESCRIPTION
--         "The value of tnMtnSapTlsPlcyDhcpVendorInclOpts specifies what is encoded in the
--          Nokia vendor specific sub-option of option 82.
--
--          The value of this object is only used when tnMtnSapTlsPlcyDhcpInfoAction is
--          'replace'."
--     DEFVAL { '0'H }
--     ::= { tnMtnSapTlsPlcyEntry 15 }
--
-- tnMtnSapTlsPlcyDhcpVendorOptStr        OBJECT-TYPE
--     SYNTAX      TNamedItemOrEmpty
--     MAX-ACCESS  read-create
--     STATUS      current
--     DESCRIPTION
--         "The value of tnMtnSapTlsPlcyDhcpVendorOptStr specifies the string that goes
--          into the Nokia vendor specific sub-option of option 82.
--
--          This string is only used when tnMtnSapTlsPlcyDhcpInfoAction is set to
--          'replace'."
--     DEFVAL { "" }
--     ::= { tnMtnSapTlsPlcyEntry 16 }
--
-- tnMtnSapTlsPlcyEgressMcastGroup OBJECT-TYPE
--     SYNTAX          TNamedItemOrEmpty
--     MAX-ACCESS      read-create
--     STATUS          current
--     DESCRIPTION
--         "The value of tnMtnSapTlsPlcyEgressMcastGroup specifies the Egress Multicast
--          Group for the MSAP."
--     DEFVAL { "" }
--     ::= { tnMtnSapTlsPlcyEntry 17 }
--
-- tnMtnSapTlsPlcyIgmpSnpgImportPlcy OBJECT-TYPE
--     SYNTAX      TPolicyStatementNameOrEmpty
--     MAX-ACCESS  read-create
--     STATUS      current
--     DESCRIPTION
--         "The value of tnMtnSapTlsPlcyIgmpSnpgImportPlcy specifies the policy statement
--          that is be applied to all incoming IGMP messages on the MSAP."
--     DEFVAL { "" }
--     ::= { tnMtnSapTlsPlcyEntry 18 }
--
-- tnMtnSapTlsPlcyIgmpSnpgFastLeave OBJECT-TYPE
--     SYNTAX      TmnxEnabledDisabled
--     MAX-ACCESS  read-create
--     STATUS      current
--     DESCRIPTION
--         "The value of tnMtnSapTlsPlcyIgmpSnpgFastLeave specifies
--          whether fast leave is allowed on this MSAP.
--
--          If set to 'enabled', the system prunes the port on which an IGMP
--          'leave' message has been received without waiting for the Group
--          Specific Query to timeout."
--     DEFVAL { disabled }
--     ::= { tnMtnSapTlsPlcyEntry 19 }
--
-- tnMtnSapTlsPlcyIgmpSnpgSendQueries OBJECT-TYPE
--     SYNTAX      TmnxEnabledDisabled
--     MAX-ACCESS  read-create
--     STATUS      current
--     DESCRIPTION
--         "The value of tnMtnSapTlsPlcyIgmpSnpgSendQueries specifies
--          whether the system generates General Queries by itself on
--          the MSAP."
--     DEFVAL { disabled }
--     ::= { tnMtnSapTlsPlcyEntry 20 }
--
-- tnMtnSapTlsPlcyIgmpSnpgGenQueryIntv OBJECT-TYPE
--     SYNTAX      Unsigned32 (2..1024)
--     UNITS       "seconds"
--     MAX-ACCESS  read-create
--     STATUS      current
--     DESCRIPTION
--         "The value of tnMtnSapTlsPlcyIgmpSnpgGenQueryIntv specifies
--          the interval (in seconds) between two consecutive general queries sent
--          by the system on the MSAP.
--
--          The value of this object is only meaningful when the value of
--          tnMtnSapTlsPlcyIgmpSnpgSendQueries is 'enabled'."
--     DEFVAL { 125 }
--     ::= { tnMtnSapTlsPlcyEntry 21 }
--
-- tnMtnSapTlsPlcyIgmpSnpgQueryRespIntv OBJECT-TYPE
--     SYNTAX      Unsigned32 (1..1023)
--     UNITS       "seconds"
--     MAX-ACCESS  read-create
--     STATUS      current
--     DESCRIPTION
--         "The value of tnMtnSapTlsPlcyIgmpSnpgQueryRespIntv specifies
--          the maximum response time (in seconds) advertised in IGMPv2/v3
--          queries.
--
--          The value of this object is only meaningful when the value of
--          tnMtnSapTlsPlcyIgmpSnpgSendQueries is 'enabled'."
--     DEFVAL { 10 }
--     ::= { tnMtnSapTlsPlcyEntry 22 }
--
-- tnMtnSapTlsPlcyIgmpSnpgRobustCount OBJECT-TYPE
--     SYNTAX      Unsigned32 (2..7)
--     MAX-ACCESS  read-create
--     STATUS      current
--     DESCRIPTION
--         "The value of tnMtnSapTlsPlcyIgmpSnpgRobustCount specifies
--          the robustness variable on the MSAP.
--
--          This object allows tuning for the expected packet loss on the MSAP.
--          If a MSAP is expected to be lossy, the Robustness Variable may be
--          increased. IGMP snooping is robust to (Robustness Variable-1) packet
--          losses.
--
--          The value of this object is only meaningful when the value of
--          tnMtnSapTlsPlcyIgmpSnpgSendQueries is 'enabled'."
--     DEFVAL { 2 }
--     ::= { tnMtnSapTlsPlcyEntry 23 }
--
-- tnMtnSapTlsPlcyIgmpSnpgLastMembIntvl OBJECT-TYPE
--     SYNTAX      Unsigned32 (1..50)
--     UNITS       "deci-seconds"
--     MAX-ACCESS  read-create
--     STATUS      current
--     DESCRIPTION
--         "The value of tnMtnSapTlsPlcyIgmpSnpgLastMembIntvl specifies the
--          Max Response Time (in tenths of a second) used in
--          Group-Specific and Group-Source-Specific Queries sent in response
--          to 'leave' messages. This is also the amount of time between
--          Group-Specific Query messages.
--
--          This value may be tuned to modify the leave latency of the network.
--          A reduced value results in reduced time to detect the loss of the last
--          member of a group."
--     DEFVAL { 10 }
--     ::= { tnMtnSapTlsPlcyEntry 24 }
--
-- tnMtnSapTlsPlcyIgmpSnpgMaxNbrGrps OBJECT-TYPE
--     SYNTAX      Unsigned32 (0..1000)
--     MAX-ACCESS  read-create
--     STATUS      current
--     DESCRIPTION
--         "The value of tnMtnSapTlsPlcyIgmpSnpgMaxNbrGrps specifies how many group
--          addresses are allowed for the MSAP.
--
--          The value 0 means that no limit is imposed."
--     DEFVAL { 0 }
--     ::= { tnMtnSapTlsPlcyEntry 25 }
--
-- tnMtnSapTlsPlcyIgmpSnpgMvrFromVplsId OBJECT-TYPE
--     SYNTAX      TmnxServId
--     MAX-ACCESS  read-create
--     STATUS      current
--     DESCRIPTION
--         "The value of tnMtnSapTlsPlcyIgmpSnpgMvrFromVplsId specifies from which
--          VPLS the multicast streams corresponding to the groups learned
--          via the MSAP are copied.
--
--          Groups which cannot be joined to the corresponding MVR VPLS
--          (because MVR is not up or the configured MVR policy rejects the group)
--          copy the multicast streams from the local VPLS if IGMP snooping is up
--          (i.e. tlsIgmpSnpgCfgAdminState is 'enabled')."
--     DEFVAL { 0 }
--     ::= { tnMtnSapTlsPlcyEntry 26 }
--
-- tnMtnSapTlsPlcyIgmpSnpgVersion OBJECT-TYPE
--     SYNTAX      TmnxIgmpVersion
--     MAX-ACCESS  read-create
--     STATUS      current
--     DESCRIPTION
--         "The value of tnMtnSapTlsPlcyIgmpSnpgVersion specifies the version
--          of IGMP running on the MSAP."
--     DEFVAL { version3 }
--     ::= { tnMtnSapTlsPlcyEntry 27 }
--
-- tnMtnSapTlsPlcyIgmpSnpgMcacPlcyName OBJECT-TYPE
--     SYNTAX     TPolicyStatementNameOrEmpty
--     MAX-ACCESS read-create
--     STATUS     current
--     DESCRIPTION
--         "The value of tnMtnSapTlsPlcyIgmpSnpgMcacPlcyName specifies the name
--          of the multicast CAC (Connection Admission Control) policy."
--     DEFVAL { "" }
--     ::= { tnMtnSapTlsPlcyEntry 28 }
--
-- tnMtnSapTlsPlcyIgmpSnpgMcacUncnstBW OBJECT-TYPE
--     SYNTAX      Integer32 (-1|0..2147483647)
--     UNITS       "kbps"
--     MAX-ACCESS  read-create
--     STATUS      current
--     DESCRIPTION
--         "The value of tnMtnSapTlsPlcyIgmpSnpgMcacUncnstBW specifies the bandwidth
--          assigned for interface's multicast CAC policy traffic in kilo-bits per
--          second(kbps).
--
--          If the default value of '-1' is set, there is no constraint on
--          bandwidth allocated at the interface.
--
--          If the value of tnMtnSapTlsPlcyIgmpSnpgMcacUncnstBW is set to '0' and if
--          a multicast CAC policy is assigned on the interface, then
--          no group (channel) from that policy is allowed on that interface."
--     DEFVAL { -1 }
--     ::= { tnMtnSapTlsPlcyEntry 29 }
--
-- tnMtnSapTlsPlcyIgmpSnpgMcacPrRsvMnBW OBJECT-TYPE
--     SYNTAX      Integer32 (-1|0..2147483647)
--     UNITS       "kbps"
--     MAX-ACCESS  read-create
--     STATUS      current
--     DESCRIPTION
--         "The value of tnMtnSapTlsPlcyIgmpSnpgMcacPrRsvMnBW specifies the bandwidth
--          pre-reserved for all the mandatory channels on a given interface
--          in kilo-bits per second(kbps).
--
--          If the value of tnMtnSapTlsPlcyIgmpSnpgMcacUncnstBW is '0', no mandatory
--          channels are allowed. If the value of tnMtnSapTlsPlcyIgmpSnpgMcacPrRsvMnBW
--          is '-1', then all mandatory and optional channels are allowed.
--
--          If the value of tnMtnSapTlsPlcyIgmpSnpgMcacPrRsvMnBW is equal to the
--          value of tnMtnSapTlsPlcyIgmpSnpgMcacUncnstBW, then all the unconstrained
--          bandwidth on a given interface is allocated to mandatory channels
--          configured through multicast CAC policy on that interface and no
--          optional groups (channels) are allowed.
--
--          The value of tnMtnSapTlsPlcyIgmpSnpgMcacPrRsvMnBW should always be less
--          than or equal to that of tnMtnSapTlsPlcyIgmpSnpgMcacUncnstBW. An attempt
--          to set the value of tnMtnSapTlsPlcyIgmpSnpgMcacPrRsvMnBW greater than
--          that of tnMtnSapTlsPlcyIgmpSnpgMcacUncnstBW will result in
--          'inconsistentValue' error."
--     DEFVAL { -1 }
--     ::= { tnMtnSapTlsPlcyEntry 30 }
--
-- tnMtnSapTlsPlcyArpHostMaxNumHosts OBJECT-TYPE
--     SYNTAX      Unsigned32 (1..32767)
--     MAX-ACCESS  read-create
--     STATUS      current
--     DESCRIPTION
--         "The value of tnMtnSapTlsPlcyArpHostMaxNumHosts specifies the maximum
--          number of ARP hosts allowed on the TLS MSAP."
--     DEFVAL { 1 }
--     ::= { tnMtnSapTlsPlcyEntry 31 }
--
-- tnMtnSapTlsPlcyArpHostMinAuthIntvl OBJECT-TYPE
--     SYNTAX      Unsigned32 (1..6000)
--     UNITS       "minutes"
--     MAX-ACCESS  read-create
--     STATUS      current
--     DESCRIPTION
--         "The value of tnMtnSapTlsPlcyArpHostMinAuthIntvl specifies the minimum
--          interval between two consecutive authentication attempts for the
--          same ARP host."
--     DEFVAL { 15 }
--     ::= { tnMtnSapTlsPlcyEntry 32 }

-- --------------------------------------------------------
--
--  tnMtnSapIgmpSnpgMcacLevelTable
--
-- --------------------------------------------------------

-- tnMtnSapIgmpSnpgMcacLevelTable OBJECT-TYPE
--     SYNTAX      SEQUENCE OF MSapIgmpSnpgMcacLevelEntry
--     MAX-ACCESS  not-accessible
--     STATUS      current
--     DESCRIPTION "The tnMtnSapIgmpSnpgMcacLevelTable has an entry for each
--                  multicast CAC policy constraint level configured for
--                  a Managed SAP policy."
--     ::= { tnSapObjs 46 }
--
-- tnMtnSapIgmpSnpgMcacLevelEntry OBJECT-TYPE
--     SYNTAX      MSapIgmpSnpgMcacLevelEntry
--     MAX-ACCESS  not-accessible
--     STATUS      current
--     DESCRIPTION "Each row entry represents a multicast CAC policy
--                  bundle level constraints for a particular Managed
--                  SAP policy. Entries are created and deleted by
--                  the user."
--     INDEX { tnSysSwitchId, tnMtnSapPlcyName, tnMtnSapIgmpSnpgMcacLevelId }
--     ::= { tnMtnSapIgmpSnpgMcacLevelTable 1}
--
-- MSapIgmpSnpgMcacLevelEntry ::= SEQUENCE {
--    tnMtnSapIgmpSnpgMcacLevelId          Unsigned32,
--    tnMtnSapIgmpSnpgMcacLevelRowStatus   RowStatus,
--    tnMtnSapIgmpSnpgMcacLevelLastChanged TimeStamp,
--    tnMtnSapIgmpSnpgMcacLevelBW          Unsigned32
-- }
--
-- tnMtnSapIgmpSnpgMcacLevelId OBJECT-TYPE
--     SYNTAX      Unsigned32 (1..8)
--     MAX-ACCESS  not-accessible
--     STATUS      current
--     DESCRIPTION "The value of tnMtnSapIgmpSnpgMcacLevelId indicates
--                  the level id of the multicast CAC policy bundle
--                  constraint.
--
--                  The value of level 1 has the highest priority and
--                  level 8 the lowest."
--     ::= { tnMtnSapIgmpSnpgMcacLevelEntry 1 }
--
-- tnMtnSapIgmpSnpgMcacLevelRowStatus OBJECT-TYPE
--     SYNTAX      RowStatus
--     MAX-ACCESS  read-create
--     STATUS      current
--     DESCRIPTION "The value of tnMtnSapIgmpSnpgMcacLevelRowStatus is
--                  used for creation and deletion of level constraint
--                  in a CAC for a Managed SAP policy."
--     ::= { tnMtnSapIgmpSnpgMcacLevelEntry 2 }
--
-- tnMtnSapIgmpSnpgMcacLevelLastChanged OBJECT-TYPE
--     SYNTAX      TimeStamp
--     MAX-ACCESS  read-only
--     STATUS      current
--     DESCRIPTION "The value of tnMtnSapIgmpSnpgMcacLevelLastChanged indicates
--                  the sysUpTime at the time of the last modification
--                  of this entry.
--
--                  If no changes were made to the entry since the last
--                  re-initialization of the local network management
--                  subsystem, then this object contains a zero value."
--     ::= { tnMtnSapIgmpSnpgMcacLevelEntry 3 }
--
-- tnMtnSapIgmpSnpgMcacLevelBW OBJECT-TYPE
--     SYNTAX      Unsigned32
--     UNITS       "kbps"
--     MAX-ACCESS  read-create
--     STATUS      current
--     DESCRIPTION "The value of tnMtnSapIgmpSnpgMcacLevelBW specifies
--                  the bandwidth in kilo-bits per second (kbps) for
--                  the level."
--     DEFVAL { 1 }
--     ::= { tnMtnSapIgmpSnpgMcacLevelEntry 4 }

-- --------------------------------------------------------
--
--  tnMtnSapIgmpSnpgMcacLagTable
--
-- --------------------------------------------------------

-- tnMtnSapIgmpSnpgMcacLagTable OBJECT-TYPE
--     SYNTAX      SEQUENCE OF MSapIgmpSnpgMcacLagEntry
--     MAX-ACCESS  not-accessible
--     STATUS      current
--     DESCRIPTION "The tnMtnSapIgmpSnpgMcacLagTable has an entry for each lag
--                  port configured for a multicast CAC policy bundle configured
--                  for a Managed SAP policy."
--     ::= { tnSapObjs 47 }
--
-- tnMtnSapIgmpSnpgMcacLagEntry OBJECT-TYPE
--     SYNTAX      MSapIgmpSnpgMcacLagEntry
--     MAX-ACCESS  not-accessible
--     STATUS      current
--     DESCRIPTION "Each row entry represents a particular multicast CAC lag port
--                  constraints for a Managed SAP policy.. Entries are
--                  created and deleted by the user."
--     INDEX { tnSysSwitchId, tnMtnSapPlcyName, tnMtnSapIgmpSnpgMcacLagPortsDown }
--     ::= { tnMtnSapIgmpSnpgMcacLagTable 1}
--
-- MSapIgmpSnpgMcacLagEntry ::= SEQUENCE {
--    tnMtnSapIgmpSnpgMcacLagPortsDown    Unsigned32,
--    tnMtnSapIgmpSnpgMcacLagRowStatus    RowStatus,
--    tnMtnSapIgmpSnpgMcacLagLastChanged  TimeStamp,
--    tnMtnSapIgmpSnpgMcacLagLevel        Unsigned32
-- }
--
-- tnMtnSapIgmpSnpgMcacLagPortsDown OBJECT-TYPE
--     SYNTAX      Unsigned32 (1..8)
--     MAX-ACCESS  not-accessible
--     STATUS      current
--     DESCRIPTION "The value of tnMtnSapIgmpSnpgMcacLagPortsDown indicates
--                  the configured number of ports in a lag group that are down.
--
--                  If the number of ports available in the lag is reduced by the
--                  number of ports configured for tnMtnSapIgmpSnpgMcacLagPortsDown
--                  object then bandwidth allowed for bundle will be updated to
--                  the value of tnMtnSapIgmpSnpgMcacLevelBW indexed by
--                  tnMtnSapIgmpSnpgMcacLagLevel value."
--     ::= { tnMtnSapIgmpSnpgMcacLagEntry 1 }
--
-- tnMtnSapIgmpSnpgMcacLagRowStatus OBJECT-TYPE
--     SYNTAX      RowStatus
--     MAX-ACCESS  read-create
--     STATUS      current
--     DESCRIPTION "The value of tnMtnSapIgmpSnpgMcacLagRowStatus is used for
--                  creation and deletion of lag constraint in a CAC policy."
--     ::= { tnMtnSapIgmpSnpgMcacLagEntry 2 }
--
-- tnMtnSapIgmpSnpgMcacLagLastChanged OBJECT-TYPE
--     SYNTAX      TimeStamp
--     MAX-ACCESS  read-only
--     STATUS      current
--     DESCRIPTION "The value of tnMtnSapIgmpSnpgMcacLagLastChanged indicates the
--                  sysUpTime at the time of the last modification of this entry.
--
--                  If no changes were made to the entry since the last
--                  re-initialization of the local network management subsystem,
--                  then this object contains a zero value."
--     ::= { tnMtnSapIgmpSnpgMcacLagEntry 3 }
--
-- tnMtnSapIgmpSnpgMcacLagLevel OBJECT-TYPE
--     SYNTAX      Unsigned32 (1..8)
--     MAX-ACCESS  read-create
--     STATUS      current
--     DESCRIPTION "The value of tnMtnSapIgmpSnpgMcacLagLevel specifies the level
--                  id to use when the value of tnMtnSapIgmpSnpgMcacLagPortsDown
--                  matches the actual number of ports down in a lag.
--
--                  Using the value of tnMtnSapIgmpSnpgMcacLagLevel as an index,
--                  the operational MSAP unconstrained bandwidth will be set
--                  to tnMtnSapIgmpSnpgMcacLevelBW.
--
--                  By default, for all lag constraints the link level will
--                  be set to 1 at row creation."
--     DEFVAL { 1 }
--     ::= { tnMtnSapIgmpSnpgMcacLagEntry 4 }

-- ---------------------------------------------------------------------
--  Managed SAP Information Table
--
--  Sparse Dependent Extension of the tnSapBaseInfoTable.
--
--  The same indexes are used for both the base table, tnSapBaseInfoTable,
--  and the sparse dependent table, tnMtnSapInfoTable.
--
--  This in effect extends the tnSapBaseInfoTable with additional columns.
--  Rows are created in the tnMtnSapInfoTable only for those entries
--  in the tnSapBaseInfoTable that are created on a port with a
--  tnSapSubType of 'managed'.
--
--  Deletion of a row in the tnSapBaseInfoTable results in the
--  same fate for the row in the tnMtnSapInfoTable.
-- ---------------------------------------------------------------------

-- tnMtnSapInfoTable OBJECT-TYPE
--     SYNTAX          SEQUENCE OF MSapInfoEntry
--     MAX-ACCESS      not-accessible
--     STATUS          current
--     DESCRIPTION     "A table that contains Managed SAP information."
--     ::= { tnSapObjs 48 }
--
-- tnMtnSapInfoEntry OBJECT-TYPE
--     SYNTAX          MSapInfoEntry
--     MAX-ACCESS      not-accessible
--     STATUS          current
--     DESCRIPTION     "Information about a specific Managed SAP."
--     INDEX           { tnSysSwitchId,  tnSvcId, tnSapPortId, tnSapEncapValue }
--     ::= { tnMtnSapInfoTable 1 }
--
-- MSapInfoEntry ::=
--     SEQUENCE {
--         tnMtnSapInfoCreationSapPortEncapVal      TmnxEncapVal,
--         tnMtnSapInfoCreationPlcyName             TNamedItem,
--         tnMtnSapInfoReEvalPolicy                 TmnxActionType,
--         tnMtnSapInfoLastChanged                  TimeStamp
--     }
--
-- tnMtnSapInfoCreationSapPortEncapVal OBJECT-TYPE
--     SYNTAX            TmnxEncapVal
--     MAX-ACCESS        read-only
--     STATUS            current
--     DESCRIPTION       "The value of tnMtnSapInfoCreationSapPortEncapVal indicates
--                        the port encapsulation value of the SAP with a tnSapSubType
--                        value of 'capture' that created this MSAP."
--     ::= { tnMtnSapInfoEntry 1 }
--
-- tnMtnSapInfoCreationPlcyName OBJECT-TYPE
--     SYNTAX           TNamedItem
--     MAX-ACCESS       read-only
--     STATUS           current
--     DESCRIPTION      "The value of tnMtnSapInfoCreationPlcyName indicates
--                       the value of the tnMtnSapPlcyName object for MSAP policy
--                       used to create this MSAP."
--     ::= { tnMtnSapInfoEntry 2 }
--
-- tnMtnSapInfoReEvalPolicy OBJECT-TYPE
--     SYNTAX           TmnxActionType
--     MAX-ACCESS       read-write
--     STATUS           current
--     DESCRIPTION      "The value of tnMtnSapInfoReEvalPolicy specifies whether
--                       to re-apply the Managed SAP policy associated with
--                       this MSAP.
--
--                       When a SET of this object is done with a value of
--                       'doAction', the system will attempt to re-apply the
--                       MSAP policy indicated by tnMtnSapInfoCreationPlcyName.
--                       If this action is successful, 'noError' will be returned.
--                       If this action is unsuccessful, an 'inconsistentValue'
--                       error will be returned. Attempting to SET this object with
--                       a value of 'notApplicable' will have no effect and will
--                       return 'noError'.
--
--                       SNMP GET and GETNEXT requests on this object will
--                       return 'notApplicable'."
--     DEFVAL { notApplicable }
--     ::= { tnMtnSapInfoEntry 3 }
--
-- tnMtnSapInfoLastChanged OBJECT-TYPE
--     SYNTAX      TimeStamp
--     MAX-ACCESS  read-only
--     STATUS      current
--     DESCRIPTION "The value of tnMtnSapInfoLastChanged indicates the
--                  sysUpTime at the time of the last modification of this entry.
--
--                  If no changes were made to the entry since the last
--                  re-initialization of the local network management subsystem,
--                  then this object contains a zero value."
--     ::= { tnMtnSapInfoEntry 4 }

-- ---------------------------------------------------------------------
-- Capture SAP Stats Table
--
--
--  Sparse Dependent Extension of the tnSapBaseInfoTable.
--
--  The same indexes are used for both the base table, tnSapBaseInfoTable,
--  and the sparse dependent table, tnMtnSapCaptureSapStatsTable.
--
--  This in effect extends the tnSapBaseInfoTable with additional columns.
--  Rows are created in the tnMtnSapTriggerPktStatsTable only for those entries
--  in the tnSapBaseInfoTable that have a tnSapSubType of 'capture'.
--
--  Deletion of a row in the tnSapBaseInfoTable results in the
--  same fate for the row in the tnMtnSapTriggerPktStatsTable.
-- ---------------------------------------------------------------------
-- tnMtnSapCaptureSapStatsTable OBJECT-TYPE
--     SYNTAX          SEQUENCE OF MSapCaptureSapStatsEntry
--     MAX-ACCESS      not-accessible
--     STATUS          current
--     DESCRIPTION     "A table that contains statistics for SAPs
--                      with a tnSapSubType value of 'capture'."
--     ::= { tnSapObjs 49 }
--
-- tnMtnSapCaptureSapStatsEntry OBJECT-TYPE
--     SYNTAX          MSapCaptureSapStatsEntry
--     MAX-ACCESS      not-accessible
--     STATUS          current
--     DESCRIPTION     "Statistics for a specific 'capture' SAP."
--     INDEX           { tnSysSwitchId,  tnSvcId,
--                       tnSapPortId,
--                       tnSapEncapValue,
--                       tnMtnSapCaptureSapStatsTriggerType }
--     ::= { tnMtnSapCaptureSapStatsTable 1 }
--
-- MSapCaptureSapStatsEntry ::=
--     SEQUENCE {
--         tnMtnSapCaptureSapStatsTriggerType   INTEGER,
--         tnMtnSapCaptureSapStatsPktsRecvd     Counter32,
--         tnMtnSapCaptureSapStatsPktsRedirect  Counter32,
--         tnMtnSapCaptureSapStatsPktsDropped   Counter32
--     }
--
-- tnMtnSapCaptureSapStatsTriggerType OBJECT-TYPE
--     SYNTAX            INTEGER {
--                           dhcp  (1),
--                           pppoe (2),
--                           arp   (3)
--                       }
--     MAX-ACCESS        not-accessible
--     STATUS            current
--     DESCRIPTION       "The value of tnMtnSapCaptureSapStatsTriggerType indicates the
--                        type of trigger packets this entry is for."
--     ::= { tnMtnSapCaptureSapStatsEntry 1 }
--
-- tnMtnSapCaptureSapStatsPktsRecvd OBJECT-TYPE
--     SYNTAX           Counter32
--     MAX-ACCESS       read-only
--     STATUS           current
--     DESCRIPTION      "The value of tnMtnSapCaptureSapStatsPktsRecvd indicates the
--                       number of packets received on this 'capture' SAP."
--     ::= { tnMtnSapCaptureSapStatsEntry 2 }
--
-- tnMtnSapCaptureSapStatsPktsRedirect OBJECT-TYPE
--     SYNTAX           Counter32
--     MAX-ACCESS       read-only
--     STATUS           current
--     DESCRIPTION      "The value of tnMtnSapCaptureSapStatsPktsRedirect indicates the
--                       number of packets redirected on this 'capture' SAP."
--     ::= { tnMtnSapCaptureSapStatsEntry 3 }
--
-- tnMtnSapCaptureSapStatsPktsDropped OBJECT-TYPE
--     SYNTAX           Counter32
--     MAX-ACCESS       read-only
--     STATUS           current
--     DESCRIPTION      "The value of tnMtnSapCaptureSapStatsPktsDropped indicates the
--                       number of packets dropped on this 'capture' SAP."
--     ::= { tnMtnSapCaptureSapStatsEntry 4 }

-- -------------------------------------
-- TLS SAP MRP Table
-- -------------------------------------
-- tnSapTlsMrpTable OBJECT-TYPE
--     SYNTAX          SEQUENCE OF SapTlsMrpEntry
--     MAX-ACCESS      not-accessible
--     STATUS          current
--     DESCRIPTION     "The tnSapTlsMrpTable augments tnSapTlsInfoTable with
--                      attributes of the Multiple Registration Protocol (MRP)
--                      feature for the TLS SAP."
--     ::= { tnSapObjs 50 }
--
-- tnSapTlsMrpEntry OBJECT-TYPE
--     SYNTAX          SapTlsMrpEntry
--     MAX-ACCESS      not-accessible
--     STATUS          current
--     DESCRIPTION     "MRP specific information about a SAP in a TLS."
--     AUGMENTS        { tnSapTlsInfoEntry }
--     ::= { tnSapTlsMrpTable 1 }
--
-- SapTlsMrpEntry ::=
--     SEQUENCE {
--         tnSapTlsMrpRxPdus               Counter32,
--         tnSapTlsMrpDroppedPdus          Counter32,
--         tnSapTlsMrpTxPdus               Counter32,
--         tnSapTlsMrpRxNewEvent           Counter32,
--         tnSapTlsMrpRxJoinInEvent        Counter32,
--         tnSapTlsMrpRxInEvent            Counter32,
--         tnSapTlsMrpRxJoinEmptyEvent     Counter32,
--         tnSapTlsMrpRxEmptyEvent         Counter32,
--         tnSapTlsMrpRxLeaveEvent         Counter32,
--         tnSapTlsMrpTxNewEvent           Counter32,
--         tnSapTlsMrpTxJoinInEvent        Counter32,
--         tnSapTlsMrpTxInEvent            Counter32,
--         tnSapTlsMrpTxJoinEmptyEvent     Counter32,
--         tnSapTlsMrpTxEmptyEvent         Counter32,
--         tnSapTlsMrpTxLeaveEvent         Counter32
--     }
--
-- tnSapTlsMrpRxPdus OBJECT-TYPE
--     SYNTAX           Counter32
--     MAX-ACCESS       read-only
--     STATUS           current
--     DESCRIPTION
--         "The value of tnSapTlsMrpRxPdus indicates the number of MRP packets
--         received on this SAP."
--     ::= { tnSapTlsMrpEntry 1 }
--
-- tnSapTlsMrpDroppedPdus OBJECT-TYPE
--     SYNTAX           Counter32
--     MAX-ACCESS       read-only
--     STATUS           current
--     DESCRIPTION
--         "The value of tnSapTlsMrpDroppedPdus indicates the number of dropped MRP
--          packets on this SAP."
--     ::= { tnSapTlsMrpEntry 2 }
--
-- tnSapTlsMrpTxPdus OBJECT-TYPE
--     SYNTAX           Counter32
--     MAX-ACCESS       read-only
--     STATUS           current
--     DESCRIPTION
--         "The value of tnSapTlsMrpTxPdus indicates the number of MRP packets
--          transmitted on this SAP."
--     ::= { tnSapTlsMrpEntry 3 }
--
-- tnSapTlsMrpRxNewEvent OBJECT-TYPE
--     SYNTAX           Counter32
--     MAX-ACCESS       read-only
--     STATUS           current
--     DESCRIPTION
--         "The value of tnSapTlsMrpRxNewEvent indicates the number of 'New' MRP
--          events received on this SAP."
--     ::= { tnSapTlsMrpEntry 4 }
--
-- tnSapTlsMrpRxJoinInEvent OBJECT-TYPE
--     SYNTAX           Counter32
--     MAX-ACCESS       read-only
--     STATUS           current
--     DESCRIPTION
--         "The value of tnSapTlsMrpRxJoinInEvent indicates the number of 'Join-In'
--          MRP events received on this SAP."
--     ::= { tnSapTlsMrpEntry 5 }
--
-- tnSapTlsMrpRxInEvent OBJECT-TYPE
--     SYNTAX           Counter32
--     MAX-ACCESS       read-only
--     STATUS           current
--     DESCRIPTION
--         "The value of tnSapTlsMrpRxInEvent indicates the number of 'In' MRP
--          events received on this SAP."
--     ::= { tnSapTlsMrpEntry 6 }
--
-- tnSapTlsMrpRxJoinEmptyEvent OBJECT-TYPE
--     SYNTAX           Counter32
--     MAX-ACCESS       read-only
--     STATUS           current
--     DESCRIPTION
--         "The value of tnSapTlsMrpRxJoinEmptyEvent indicates the number of
--         'Join Empty' MRP events received on this SAP."
--     ::= { tnSapTlsMrpEntry 7 }
--
-- tnSapTlsMrpRxEmptyEvent OBJECT-TYPE
--     SYNTAX           Counter32
--     MAX-ACCESS       read-only
--     STATUS           current
--     DESCRIPTION
--         "The value of tnSapTlsMrpRxEmptyEvent indicates the number of 'Empty'
--          MRP events received on this SAP."
--     ::= { tnSapTlsMrpEntry 8 }
--
-- tnSapTlsMrpRxLeaveEvent OBJECT-TYPE
--     SYNTAX           Counter32
--     MAX-ACCESS       read-only
--     STATUS           current
--     DESCRIPTION
--        "The value of tnSapTlsMrpRxLeaveEvent indicates the number of 'Leave'
--         MRP events received on this SAP."
--     ::= { tnSapTlsMrpEntry 9 }
--
-- tnSapTlsMrpTxNewEvent OBJECT-TYPE
--     SYNTAX           Counter32
--     MAX-ACCESS       read-only
--     STATUS           current
--     DESCRIPTION
--         "The value of tnSapTlsMrpTxNewEvent indicates the number of 'New' MRP
--          events transmitted on this SAP."
--     ::= { tnSapTlsMrpEntry 10 }
--
-- tnSapTlsMrpTxJoinInEvent OBJECT-TYPE
--     SYNTAX           Counter32
--     MAX-ACCESS       read-only
--     STATUS           current
--     DESCRIPTION
--         "The value of tnSapTlsMrpTxJoinInEvent indicates the number of 'Join-In'
--          MRP events transmitted on this SAP."
--     ::= { tnSapTlsMrpEntry 11 }
--
-- tnSapTlsMrpTxInEvent OBJECT-TYPE
--     SYNTAX           Counter32
--     MAX-ACCESS       read-only
--     STATUS           current
--     DESCRIPTION
--         "The value of tnSapTlsMrpTxInEvent indicates the number of 'In' MRP
--          events transmitted on this SAP."
--     ::= { tnSapTlsMrpEntry 12 }
--
-- tnSapTlsMrpTxJoinEmptyEvent OBJECT-TYPE
--     SYNTAX           Counter32
--     MAX-ACCESS       read-only
--     STATUS           current
--     DESCRIPTION
--         "The value of tnSapTlsMrpTxJoinEmptyEvent indicates the number of
--         'Join Empty' MRP events transmitted on this SAP."
--     ::= { tnSapTlsMrpEntry 13 }
--
-- tnSapTlsMrpTxEmptyEvent OBJECT-TYPE
--     SYNTAX           Counter32
--     MAX-ACCESS       read-only
--     STATUS           current
--     DESCRIPTION
--         "The value of tnSapTlsMrpTxEmptyEvent indicates the number of 'Empty'
--         MRP events transmitted on this SAP."
--     ::= { tnSapTlsMrpEntry 14 }
--
-- tnSapTlsMrpTxLeaveEvent OBJECT-TYPE
--     SYNTAX           Counter32
--     MAX-ACCESS       read-only
--     STATUS           current
--    DESCRIPTION
--         "The value of tnSapTlsMrpTxLeaveEvent indicates the number of 'Leave'
--         MRP events transmitted on this SAP."
--     ::= { tnSapTlsMrpEntry 15 }
--
-- -------------------------------------
-- TLS SAP MMRP Table
-- -------------------------------------
-- tnSapTlsMmrpTable OBJECT-TYPE
--     SYNTAX          SEQUENCE OF SapTlsMmrpEntry
--     MAX-ACCESS      not-accessible
--     STATUS          current
--     DESCRIPTION     "This table contains an entry for each MAC address managed
--                     by Multiple MAC Registration Protocol (MMRP) on the SAP
--                     for the TLS.  Entries are dynamically created and
--                     destroyed by the system as the MAC Addresses are registered
--                     or declared in MMRP."
--     ::= { tnSapObjs 51 }
--
-- tnSapTlsMmrpEntry OBJECT-TYPE
--     SYNTAX          SapTlsMmrpEntry
--     MAX-ACCESS      not-accessible
--     STATUS          current
--     DESCRIPTION     "MMRP specific information about a MAC address managed by
--                     MMRP on a SAP in a TLS."
--     INDEX           { tnSysSwitchId,  tnSvcId, tnSapPortId, tnSapEncapValue, tnSapTlsMmrpMacAddr }
--     ::= { tnSapTlsMmrpTable 1 }
--
-- SapTlsMmrpEntry ::=
--     SEQUENCE {
--         tnSapTlsMmrpMacAddr              MacAddress,
--         tnSapTlsMmrpDeclared             TruthValue,
--         tnSapTlsMmrpRegistered           TruthValue
--     }
--
-- tnSapTlsMmrpMacAddr OBJECT-TYPE
--     SYNTAX        MacAddress
--     MAX-ACCESS    not-accessible
--     STATUS        current
--     DESCRIPTION
--         "The value of tnSapTlsMmrpMacAddr indicates an ethernet MAC address which
--         is being managed by MMRP on this SAP."
--     ::= { tnSapTlsMmrpEntry 1 }
--
-- tnSapTlsMmrpDeclared OBJECT-TYPE
--     SYNTAX        TruthValue
--     MAX-ACCESS    read-only
--     STATUS        current
--     DESCRIPTION
--         "The value of tnSapTlsMmrpDeclared indicates whether the MRP applicant
--         on this SAP is declaring this MAC address on behalf of MMRP."
--     ::= { tnSapTlsMmrpEntry 2 }
--
-- tnSapTlsMmrpRegistered OBJECT-TYPE
--     SYNTAX        TruthValue
--     MAX-ACCESS    read-only
--     STATUS        current
--     DESCRIPTION
--         "The value of tnSapTlsMmrpRegistered indicates whether the MRP registrant
--         on this SAP has notified MMRP of a registration of this MAC address."
--     ::= { tnSapTlsMmrpEntry 3 }

-- --------------------------------------------
-- SAP HSMDA QOS Ingress Queue Overrides Table
-- --------------------------------------------
-- tnSapIngQosHsmdaQueueTable OBJECT-TYPE
--     SYNTAX      SEQUENCE OF SapIngQosHsmdaQueueEntry
--     MAX-ACCESS  not-accessible
--     STATUS      current
--     DESCRIPTION
--         "The tmnxSubHsmdaIngQueueOvrTable has an entry for each Hsmda
--          SAP-level ingress queue override configured on the system."
--     ::= { tnSapObjs 52 }
--
-- tnSapIngQosHsmdaQueueEntry     OBJECT-TYPE
--     SYNTAX      SapIngQosHsmdaQueueEntry
--     MAX-ACCESS  not-accessible
--     STATUS      current
--     DESCRIPTION
--         "Each row entry represents a Hsmda SAP-level ingress queue
--          override record.
--
--          Entries are created and deleted via SNMP SET operations on
--          tmnxSubHsmdaIngQueueOvrRowStat."
--     INDEX { tnSysSwitchId, tnSvcId, tnSapPortId, tnSapEncapValue, tnSapIngQosHsmdaQueueId }
--     ::= { tnSapIngQosHsmdaQueueTable 1}
--
-- SapIngQosHsmdaQueueEntry  ::= SEQUENCE
--     {
--         tnSapIngQosHsmdaQueueId           TIngressHsmdaQueueId,
--         tnSapIngQosHsmdaQueueRowStatus    RowStatus,
--         tnSapIngQosHsmdaQueueLastChanged  TimeStamp,
--         tnSapIngQosHsmdaQueueAdminPIR     THsmdaPIRKRateOverride,
--         tnSapIngQosHsmdaQueueAdminCIR     THsmdaCIRKRateOverride,
--         tnSapIngQosHsmdaQueueSlopePolicy  TNamedItemOrEmpty
--     }
--
-- tnSapIngQosHsmdaQueueId        OBJECT-TYPE
--     SYNTAX      TIngressHsmdaQueueId
--     MAX-ACCESS  not-accessible
--     STATUS      current
--     DESCRIPTION
--         "The value of tnSapIngQosHsmdaQueueId index specifies the Hsmda
--          egress queue which this override record will affect."
--     ::= { tnSapIngQosHsmdaQueueEntry 1 }
--
-- tnSapIngQosHsmdaQueueRowStatus        OBJECT-TYPE
--     SYNTAX      RowStatus
--     MAX-ACCESS  read-create
--     STATUS      current
--     DESCRIPTION
--         "The value of tnSapIngQosHsmdaQueueRowStatus specifies..."
--     ::= { tnSapIngQosHsmdaQueueEntry 2 }
--
-- tnSapIngQosHsmdaQueueLastChanged        OBJECT-TYPE
--     SYNTAX      TimeStamp
--     MAX-ACCESS  read-only
--     STATUS      current
--     DESCRIPTION
--         "The value of tnSapIngQosHsmdaQueueLastChanged indicates the sysUpTime
--          at the time of the most recent management-initiated change to this
--          table row."
--     ::= { tnSapIngQosHsmdaQueueEntry 3 }
--
-- tnSapIngQosHsmdaQueueAdminPIR        OBJECT-TYPE
--     SYNTAX      THsmdaPIRKRateOverride
--     UNITS       "kbps"
--     MAX-ACCESS  read-create
--     STATUS      current
--     DESCRIPTION
--         "The value of tnSapIngQosHsmdaQueueAdminPIR specifies the PIR rate in kbps
--          allowed for this Hsmda ingress queue."
--     DEFVAL { -2 }
--     ::= { tnSapIngQosHsmdaQueueEntry 4 }
--
-- tnSapIngQosHsmdaQueueAdminCIR        OBJECT-TYPE
--     SYNTAX      THsmdaCIRKRateOverride
--     UNITS       "kbps"
--     MAX-ACCESS  read-create
--     STATUS      current
--     DESCRIPTION
--         "The value of tnSapIngQosHsmdaQueueAdminCIR specifies the CIR rate in kbps
--          allowed for this Hsmda ingress queue."
--     DEFVAL { -2 }
--     ::= { tnSapIngQosHsmdaQueueEntry 5 }
--
-- tnSapIngQosHsmdaQueueSlopePolicy        OBJECT-TYPE
--     SYNTAX      TNamedItemOrEmpty
--     MAX-ACCESS  read-create
--     STATUS      current
--     DESCRIPTION
--         "The value of tnSapIngQosHsmdaQueueSlopePolicy specifies the slope
--          policy that defines the RED slopes for this Hsmda ingress queue."
--     DEFVAL { "" }
--     ::= { tnSapIngQosHsmdaQueueEntry 6 }

------------------------------------------------
-- Ingress QoS HSMDA Queue SAP Statistics Table
------------------------------------------------
-- tnSapIngQosHsmdaQueueStatsTable OBJECT-TYPE
--     SYNTAX          SEQUENCE OF SapIngQosHsmdaQueueStatsEntry
--     MAX-ACCESS      not-accessible
--     STATUS          current
--     DESCRIPTION
--         "A table that contains ingress QoS HSMDA queue SAP statistics."
--     ::= { tnSapObjs 53 }
--
-- tnSapIngQosHsmdaQueueStatsEntry OBJECT-TYPE
--     SYNTAX          SapIngQosHsmdaQueueStatsEntry
--     MAX-ACCESS      not-accessible
--     STATUS          current
--     DESCRIPTION
--         "Ingress statistics about a specific SAP's QoS HSMDA queue."
--     INDEX           { tnSysSwitchId,  tnSvcId, tnSapPortId, tnSapEncapValue, tnSapIngQosHsmdaQueueId }
--     ::= { tnSapIngQosHsmdaQueueStatsTable 1 }
--
-- SapIngQosHsmdaQueueStatsEntry ::= SEQUENCE {
--         tnSapIngHsmdaQStatCustId             TmnxCustId,
--         tnSapIngHsmdaQStatHiPktsDropped      Counter64,
--         tnSapIngHsmdaQStatLoPktsDropped      Counter64,
--         tnSapIngHsmdaQStatHiOctsDropped      Counter64,
--         tnSapIngHsmdaQStatLoOctsDropped      Counter64,
--         tnSapIngHsmdaQStatInProfPktsFwd      Counter64,
--         tnSapIngHsmdaQStatOutProfPktsFwd     Counter64,
--         tnSapIngHsmdaQStatInProfOctsFwd      Counter64,
--         tnSapIngHsmdaQStatOutProfOctsFwd     Counter64,
--         tnSapIngHsmdaQStatAllPktsOffered     Counter64,
--         tnSapIngHsmdaQStatAllOctsOffered     Counter64
--     }
--
-- tnSapIngHsmdaQStatCustId  OBJECT-TYPE
--     SYNTAX          TmnxCustId
--     MAX-ACCESS      read-only
--     STATUS          current
--     DESCRIPTION
--         "The value of tnSapIngHsmdaQStatCustId indicates the customer ID
--          for the statistics."
--     ::= { tnSapIngQosHsmdaQueueStatsEntry 1 }
--
-- tnSapIngHsmdaQStatHiPktsDropped        OBJECT-TYPE
--     SYNTAX      Counter64
--     MAX-ACCESS  read-only
--     STATUS      current
--     DESCRIPTION
--         "The value of tnSapIngHsmdaQStatHiPktsDropped indicates the
--          number of high-priority packets dropped on ingress on
--          this SAP."
--     ::= { tnSapIngQosHsmdaQueueStatsEntry 2 }
--
-- tnSapIngHsmdaQStatLoPktsDropped        OBJECT-TYPE
--     SYNTAX      Counter64
--     MAX-ACCESS  read-only
--     STATUS      current
--     DESCRIPTION
--         "The value of tnSapIngHsmdaQStatLoPktsDropped indicates the
--          number of low-priority packets dropped on ingress on
--          this SAP."
--     ::= { tnSapIngQosHsmdaQueueStatsEntry 3 }
--
-- tnSapIngHsmdaQStatHiOctsDropped        OBJECT-TYPE
--     SYNTAX      Counter64
--     MAX-ACCESS  read-only
--     STATUS      current
--     DESCRIPTION
--         "The value of tnSapIngHsmdaQStatHiOctsDropped indicates the
--          number of high-priority octets dropped on ingress on
--          this SAP."
--     ::= { tnSapIngQosHsmdaQueueStatsEntry 4 }
--
-- tnSapIngHsmdaQStatLoOctsDropped        OBJECT-TYPE
--     SYNTAX      Counter64
--     MAX-ACCESS  read-only
--     STATUS      current
--     DESCRIPTION
--         "The value of tnSapIngHsmdaQStatLoOctsDropped indicates the
--          number of low-priority octets dropped on ingress on
--          this SAP."
--     ::= { tnSapIngQosHsmdaQueueStatsEntry 5 }
--
-- tnSapIngHsmdaQStatInProfPktsFwd        OBJECT-TYPE
--     SYNTAX      Counter64
--     MAX-ACCESS  read-only
--     STATUS      current
--     DESCRIPTION
--         "The value of tnSapIngHsmdaQStatInProfPktsFwd indicates the
--          number of in-profile packets forwarded on ingress on
--          this SAP."
--     ::= { tnSapIngQosHsmdaQueueStatsEntry 6 }
--
-- tnSapIngHsmdaQStatOutProfPktsFwd        OBJECT-TYPE
--     SYNTAX      Counter64
--     MAX-ACCESS  read-only
--     STATUS      current
--     DESCRIPTION
--         "The value of tnSapIngHsmdaQStatOutProfPktsFwd indicates the
--          number of out-of-profile packets forwarded on ingress on
--          this SAP."
--     ::= { tnSapIngQosHsmdaQueueStatsEntry 7 }
--
-- tnSapIngHsmdaQStatInProfOctsFwd        OBJECT-TYPE
--     SYNTAX      Counter64
--     MAX-ACCESS  read-only
--     STATUS      current
--     DESCRIPTION
--         "The value of tnSapIngHsmdaQStatInProfOctsFwd indicates the
--          number of out-of-profile packets forwarded on ingress on
--          this SAP."
--     ::= { tnSapIngQosHsmdaQueueStatsEntry 8 }
--
-- tnSapIngHsmdaQStatOutProfOctsFwd        OBJECT-TYPE
--     SYNTAX      Counter64
--     MAX-ACCESS  read-only
--     STATUS      current
--     DESCRIPTION
--         "The value of tnSapIngHsmdaQStatOutProfOctsFwd indicates the
--          number of out-of-profile packets forwarded on ingress on
--          this SAP."
--     ::= { tnSapIngQosHsmdaQueueStatsEntry 9 }
--
-- tnSapIngHsmdaQStatAllPktsOffered        OBJECT-TYPE
--     SYNTAX      Counter64
--     MAX-ACCESS  read-only
--     STATUS      current
--     DESCRIPTION
--         "The value of tnSapIngHsmdaQStatAllPktsOffered indicates the
--          total number of packets offered on ingress on this SAP."
--     ::= { tnSapIngQosHsmdaQueueStatsEntry 10 }
--
-- tnSapIngHsmdaQStatAllOctsOffered        OBJECT-TYPE
--     SYNTAX      Counter64
--     MAX-ACCESS  read-only
--     STATUS      current
--     DESCRIPTION
--         "The value of tnSapIngHsmdaQStatAllOctsOffered indicates the
--          total number of octets offered on ingress on this SAP."
--     ::= { tnSapIngQosHsmdaQueueStatsEntry 11 }

------------------------------------------------------
-- Ingress QoS HSMDA Queue Counter SAP Statistics Table
------------------------------------------------------
-- tnSapIngQosHsmdaCntrStatsTable OBJECT-TYPE
--     SYNTAX          SEQUENCE OF SapIngQosHsmdaCntrStatsEntry
--     MAX-ACCESS      not-accessible
--     STATUS          current
--     DESCRIPTION
--         "A table that contains ingress QoS HSMDA counter SAP statistics."
--     ::= { tnSapObjs 54 }
--
-- tnSapIngQosHsmdaCntrStatsEntry OBJECT-TYPE
--     SYNTAX          SapIngQosHsmdaCntrStatsEntry
--     MAX-ACCESS      not-accessible
--     STATUS          current
--     DESCRIPTION
--         "Ingress statistics about a specific SAP's QoS HSMDA counter."
--     INDEX           { tnSysSwitchId,  tnSvcId, tnSapPortId, tnSapEncapValue, tnSapIngHsmdaCntrStCntrId }
--     ::= { tnSapIngQosHsmdaCntrStatsTable 1 }
--
-- SapIngQosHsmdaCntrStatsEntry ::= SEQUENCE {
--         tnSapIngHsmdaCntrStCntrId             TIngressHsmdaCounterId,
--         tnSapIngHsmdaCntrStCustId             TmnxCustId,
--         tnSapIngHsmdaCntrStHiPktDrop      Counter64,
--         tnSapIngHsmdaCntrStLoPktDrop      Counter64,
--         tnSapIngHsmdaCntrStHiOctDrop      Counter64,
--         tnSapIngHsmdaCntrStLoOctDrop      Counter64,
--         tnSapIngHsmdaCntrStInProfPktFwd      Counter64,
--         tnSapIngHsmdaCntrStOutProfPktFwd     Counter64,
--         tnSapIngHsmdaCntrStInProfOctFwd      Counter64,
--         tnSapIngHsmdaCntrStOutProfOctFwd     Counter64,
--         tnSapIngHsmdaCntrStAllPktOffered     Counter64,
--         tnSapIngHsmdaCntrStAllOctOffered     Counter64
--     }
--
-- tnSapIngHsmdaCntrStCntrId  OBJECT-TYPE
--     SYNTAX          TIngressHsmdaCounterId
--     MAX-ACCESS      not-accessible
--     STATUS          current
--     DESCRIPTION
--         "The value of tnSapIngHsmdaCntrStCntrId indicates the counter ID
--          for the statistics."
--     ::= { tnSapIngQosHsmdaCntrStatsEntry 1 }
--
-- tnSapIngHsmdaCntrStCustId  OBJECT-TYPE
--     SYNTAX          TmnxCustId
--     MAX-ACCESS      read-only
--     STATUS          current
--     DESCRIPTION
--         "The value of tnSapIngHsmdaCntrStCustId indicates the customer ID
--          for the statistics."
--     ::= { tnSapIngQosHsmdaCntrStatsEntry 2 }
--
-- tnSapIngHsmdaCntrStHiPktDrop        OBJECT-TYPE
--     SYNTAX      Counter64
--     MAX-ACCESS  read-only
--     STATUS      current
--     DESCRIPTION
--         "The value of tnSapIngHsmdaCntrStHiPktDrop indicates the
--          number of high-priority packets dropped for the ingress
--          counter, specified by the index tnSapIngHsmdaCntrStCntrId,
--          on this SAP."
--     ::= { tnSapIngQosHsmdaCntrStatsEntry 3 }
--
-- tnSapIngHsmdaCntrStLoPktDrop        OBJECT-TYPE
--     SYNTAX      Counter64
--     MAX-ACCESS  read-only
--     STATUS      current
--     DESCRIPTION
--         "The value of tnSapIngHsmdaCntrStLoPktDrop indicates the
--          number of low-priority packets dropped for the ingress
--          counter, specified by the index tnSapIngHsmdaCntrStCntrId,
--          on this SAP."
--     ::= { tnSapIngQosHsmdaCntrStatsEntry 4 }
--
-- tnSapIngHsmdaCntrStHiOctDrop        OBJECT-TYPE
--     SYNTAX      Counter64
--     MAX-ACCESS  read-only
--     STATUS      current
--     DESCRIPTION
--         "The value of tnSapIngHsmdaCntrStHiOctDrop indicates the
--          number of high-priority octets dropped for the ingress
--          counter, specified by the index tnSapIngHsmdaCntrStCntrId,
--          on this SAP."
--     ::= { tnSapIngQosHsmdaCntrStatsEntry 5 }
--
-- tnSapIngHsmdaCntrStLoOctDrop        OBJECT-TYPE
--     SYNTAX      Counter64
--     MAX-ACCESS  read-only
--     STATUS      current
--     DESCRIPTION
--         "The value of tnSapIngHsmdaCntrStLoOctDrop indicates the
--          number of low-priority octets dropped for the ingress
--          counter, specified by the index tnSapIngHsmdaCntrStCntrId,
--          on this SAP."
--     ::= { tnSapIngQosHsmdaCntrStatsEntry 6 }
--
-- tnSapIngHsmdaCntrStInProfPktFwd        OBJECT-TYPE
--     SYNTAX      Counter64
--     MAX-ACCESS  read-only
--     STATUS      current
--     DESCRIPTION
--         "The value of tnSapIngHsmdaCntrStInProfPktFwd indicates the
--          number of in-profile packets forwarded for the ingress
--          counter, specified by the index tnSapIngHsmdaCntrStCntrId,
--          on this SAP."
--     ::= { tnSapIngQosHsmdaCntrStatsEntry 7 }
--
-- tnSapIngHsmdaCntrStOutProfPktFwd        OBJECT-TYPE
--     SYNTAX      Counter64
--     MAX-ACCESS  read-only
--     STATUS      current
--     DESCRIPTION
--         "The value of tnSapIngHsmdaCntrStOutProfPktFwd indicates the
--          number of out-of-profile packets forwarded for the ingress
--          counter, specified by the index tnSapIngHsmdaCntrStCntrId,
--          on this SAP."
--     ::= { tnSapIngQosHsmdaCntrStatsEntry 8 }
--
-- tnSapIngHsmdaCntrStInProfOctFwd        OBJECT-TYPE
--     SYNTAX      Counter64
--     MAX-ACCESS  read-only
--     STATUS      current
--     DESCRIPTION
--         "The value of tnSapIngHsmdaCntrStInProfOctFwd indicates the
--          number of out-of-profile packets forwarded for the ingress
--          counter, specified by the index tnSapIngHsmdaCntrStCntrId,
--          on this SAP."
--     ::= { tnSapIngQosHsmdaCntrStatsEntry 9 }
--
-- tnSapIngHsmdaCntrStOutProfOctFwd        OBJECT-TYPE
--     SYNTAX      Counter64
--     MAX-ACCESS  read-only
--     STATUS      current
--     DESCRIPTION
--         "The value of tnSapIngHsmdaCntrStOutProfOctFwd indicates the
--          number of out-of-profile packets forwarded for the ingress
--          counter, specified by the index tnSapIngHsmdaCntrStCntrId,
--          on this SAP."
--     ::= { tnSapIngQosHsmdaCntrStatsEntry 10 }
--
-- tnSapIngHsmdaCntrStAllPktOffered        OBJECT-TYPE
--     SYNTAX      Counter64
--     MAX-ACCESS  read-only
--     STATUS      current
--     DESCRIPTION
--         "The value of tnSapIngHsmdaCntrStAllPktOffered indicates the
--          total number of packets offered on ingress on this SAP."
--     ::= { tnSapIngQosHsmdaCntrStatsEntry 11 }
--
-- tnSapIngHsmdaCntrStAllOctOffered        OBJECT-TYPE
--     SYNTAX      Counter64
--     MAX-ACCESS  read-only
--     STATUS      current
--     DESCRIPTION
--         "The value of tnSapIngHsmdaCntrStAllOctOffered indicates the
--          total number of octets offered on ingress on this SAP."
--     ::= { tnSapIngQosHsmdaCntrStatsEntry 12 }

-- --------------------------------------------
-- SAP HSMDA QOS Egress Queue Overrides Table
-- --------------------------------------------

-- tnSapEgrQosHsmdaQueueTable OBJECT-TYPE
--     SYNTAX      SEQUENCE OF SapEgrQosHsmdaQueueEntry
--     MAX-ACCESS  not-accessible
--     STATUS      current
--     DESCRIPTION
--         "The tnSapEgrQosHsmdaQueueTable has an entry for each Hsmda
--          SAP-level egress queue override configured on the system."
--     ::= { tnSapObjs 55 }
--
-- tnSapEgrQosHsmdaQueueEntry     OBJECT-TYPE
--     SYNTAX      SapEgrQosHsmdaQueueEntry
--     MAX-ACCESS  not-accessible
--     STATUS      current
--     DESCRIPTION
--         "Each row entry represents a Hsmda SAP-level egress queue
--          override record.
--
--          Entries are created and deleted via SNMP SET operations on
--          tmnxSubHsmdaIngQueueOvrRowStat."
--     INDEX { tnSysSwitchId, tnSvcId, tnSapPortId, tnSapEncapValue, tnSapEgrQosHsmdaQueueId }
--     ::= { tnSapEgrQosHsmdaQueueTable 1}
--
-- SapEgrQosHsmdaQueueEntry  ::= SEQUENCE
--     {
--         tnSapEgrQosHsmdaQueueId           TEgressHsmdaQueueId,
--         tnSapEgrQosHsmdaQueueRowStatus    RowStatus,
--         tnSapEgrQosHsmdaQueueLastChanged  TimeStamp,
--         tnSapEgrQosHsmdaQueueAdminPIR     THsmdaPIRKRateOverride,
--         tnSapEgrQosHsmdaQueueAdminCIR     THsmdaCIRKRateOverride,
--         tnSapEgrQosHsmdaQueueSlopePolicy  TNamedItemOrEmpty
--     }
--
-- tnSapEgrQosHsmdaQueueId        OBJECT-TYPE
--     SYNTAX      TEgressHsmdaQueueId
--     MAX-ACCESS  not-accessible
--     STATUS      current
--     DESCRIPTION
--          "The value of tnSapEgrQosHsmdaQueueId index specifies the Hsmda
--           egress queue which this override record will affect."
--     ::= { tnSapEgrQosHsmdaQueueEntry 1 }
--
-- tnSapEgrQosHsmdaQueueRowStatus        OBJECT-TYPE
--     SYNTAX      RowStatus
--     MAX-ACCESS  read-create
--     STATUS      current
--     DESCRIPTION
--         "The value of tnSapEgrQosHsmdaQueueRowStatus controls the creation
--          and deletion of rows in this table."
--     ::= { tnSapEgrQosHsmdaQueueEntry 2 }
--
-- tnSapEgrQosHsmdaQueueLastChanged        OBJECT-TYPE
--     SYNTAX      TimeStamp
--     MAX-ACCESS  read-only
--     STATUS      current
--     DESCRIPTION
--         "The value of tnSapEgrQosHsmdaQueueLastChanged indicates the sysUpTime
--          at the time of the most recent management-initiated change to this
--          table row."
--     ::= { tnSapEgrQosHsmdaQueueEntry 3 }
--
-- tnSapEgrQosHsmdaQueueAdminPIR        OBJECT-TYPE
--     SYNTAX      THsmdaPIRKRateOverride
--     UNITS       "kbps"
--     MAX-ACCESS  read-create
--     STATUS      current
--     DESCRIPTION
--         "The value of tnSapEgrQosHsmdaQueueAdminPIR specifies the PIR rate in kbps
--          allowed for this Hsmda ingress queue."
--     DEFVAL { -2 }
--     ::= { tnSapEgrQosHsmdaQueueEntry 4 }
--
-- tnSapEgrQosHsmdaQueueAdminCIR        OBJECT-TYPE
--     SYNTAX      THsmdaCIRKRateOverride
--     UNITS       "kbps"
--     MAX-ACCESS  read-create
--     STATUS      current
--     DESCRIPTION
--         "The value of tnSapEgrQosHsmdaQueueAdminCIR specifies the CIR rate in kbps
--          allowed for this Hsmda ingress queue."
--     DEFVAL { -2 }
--     ::= { tnSapEgrQosHsmdaQueueEntry 5 }
--
-- tnSapEgrQosHsmdaQueueSlopePolicy        OBJECT-TYPE
--     SYNTAX      TNamedItemOrEmpty
--     MAX-ACCESS  read-create
--     STATUS      current
--     DESCRIPTION
--         "The value of tnSapEgrQosHsmdaQueueSlopePolicy specifies the slope
--          policy that defines the RED slopes for this Hsmda ingress queue."
--     DEFVAL { "" }
--     ::= { tnSapEgrQosHsmdaQueueEntry 6 }

------------------------------------------------
-- Egress QoS HSMDA Queue SAP Statistics Table
------------------------------------------------
-- tnSapEgrQosHsmdaQueueStatsTable OBJECT-TYPE
--     SYNTAX          SEQUENCE OF SapEgrQosHsmdaQueueStatsEntry
--     MAX-ACCESS      not-accessible
--     STATUS          current
--     DESCRIPTION
--         "A table that contains egress QoS HSMDA queue SAP statistics."
--     ::= { tnSapObjs 56 }
--
-- tnSapEgrQosHsmdaQueueStatsEntry OBJECT-TYPE
--     SYNTAX          SapEgrQosHsmdaQueueStatsEntry
--     MAX-ACCESS      not-accessible
--     STATUS          current
--     DESCRIPTION
--         "Egress statistics about a specific SAP's QoS HSMDA queue."
--     INDEX           { tnSysSwitchId,  tnSvcId, tnSapPortId, tnSapEncapValue, tnSapEgrQosHsmdaQueueId }
--     ::= { tnSapEgrQosHsmdaQueueStatsTable 1 }
--
-- SapEgrQosHsmdaQueueStatsEntry ::= SEQUENCE {
--         tnSapEgrHsmdaQStatCustId             TmnxCustId,
--         tnSapEgrHsmdaQStatInProfPktFwd      Counter64,
--         tnSapEgrHsmdaQStatInProfPktDropd    Counter64,
--         tnSapEgrHsmdaQStatOutProfPktFwd     Counter64,
--         tnSapEgrHsmdaQStatOutProfPktDropd   Counter64,
--         tnSapEgrHsmdaQStatInProfOctFwd      Counter64,
--         tnSapEgrHsmdaQStatInProfOctDropd    Counter64,
--         tnSapEgrHsmdaQStatOutProfOctFwd     Counter64,
--         tnSapEgrHsmdaQStatOutProfOctDropd   Counter64
--     }
--
-- tnSapEgrHsmdaQStatCustId  OBJECT-TYPE
--     SYNTAX          TmnxCustId
--     MAX-ACCESS      read-only
--     STATUS          current
--     DESCRIPTION
--         "The value of tnSapEgrHsmdaQStatCustId indicates the
--         customer ID for the statistics."
--     ::= { tnSapEgrQosHsmdaQueueStatsEntry 1 }
--
-- tnSapEgrHsmdaQStatInProfPktFwd        OBJECT-TYPE
--     SYNTAX      Counter64
--     MAX-ACCESS  read-only
--     STATUS      current
--     DESCRIPTION
--         "The value of tnSapEgrHsmdaQStatInProfPktFwd indicates the
--          number of in-profile packets forwarded on egress on
--          this SAP."
--     ::= { tnSapEgrQosHsmdaQueueStatsEntry 2 }
--
-- tnSapEgrHsmdaQStatInProfPktDropd        OBJECT-TYPE
--     SYNTAX      Counter64
--     MAX-ACCESS  read-only
--     STATUS      current
--     DESCRIPTION
--         "The value of tnSapEgrHsmdaQStatInProfPktDropd indicates the
--          number of in-profile packets dropped on egress on
--          this SAP."
--     ::= { tnSapEgrQosHsmdaQueueStatsEntry 3 }
--
-- tnSapEgrHsmdaQStatOutProfPktFwd        OBJECT-TYPE
--     SYNTAX      Counter64
--     MAX-ACCESS  read-only
--     STATUS      current
--     DESCRIPTION
--         "The value of tnSapEgrHsmdaQStatOutProfPktFwd indicates the
--          number of out-of-profile packets forwarded on egress on
--          this SAP."
--     ::= { tnSapEgrQosHsmdaQueueStatsEntry 4 }
--
-- tnSapEgrHsmdaQStatOutProfPktDropd        OBJECT-TYPE
--     SYNTAX      Counter64
--     MAX-ACCESS  read-only
--     STATUS      current
--     DESCRIPTION
--         "The value of tnSapEgrHsmdaQStatOutProfPktDropd indicates the
--          number of out-of-profile packets dropped on egress on
--          this SAP."
--     ::= { tnSapEgrQosHsmdaQueueStatsEntry 5 }
--
-- tnSapEgrHsmdaQStatInProfOctFwd        OBJECT-TYPE
--     SYNTAX      Counter64
--     MAX-ACCESS  read-only
--     STATUS      current
--     DESCRIPTION
--         "The value of tnSapEgrHsmdaQStatInProfOctFwd indicates the
--          number of out-of-profile packets forwarded on egress on
--          this SAP."
--     ::= { tnSapEgrQosHsmdaQueueStatsEntry 6 }
--
-- tnSapEgrHsmdaQStatInProfOctDropd        OBJECT-TYPE
--     SYNTAX      Counter64
--     MAX-ACCESS  read-only
--     STATUS      current
--     DESCRIPTION
--         "The value of tnSapEgrHsmdaQStatInProfOctDropd indicates the
--          number of out-of-profile packets dropped on egress on
--          this SAP."
--     ::= { tnSapEgrQosHsmdaQueueStatsEntry 7 }
--
-- tnSapEgrHsmdaQStatOutProfOctFwd        OBJECT-TYPE
--     SYNTAX      Counter64
--     MAX-ACCESS  read-only
--     STATUS      current
--     DESCRIPTION
--         "The value of tnSapEgrHsmdaQStatOutProfOctFwd indicates the
--          number of out-of-profile packets forwarded on egress on
--          this SAP."
--     ::= { tnSapEgrQosHsmdaQueueStatsEntry 8 }
--
-- tnSapEgrHsmdaQStatOutProfOctDropd        OBJECT-TYPE
--     SYNTAX      Counter64
--     MAX-ACCESS  read-only
--     STATUS      current
--     DESCRIPTION
--         "The value of tnSapEgrHsmdaQStatOutProfOctDropd indicates the
--          number of out-of-profile packets dropped on egress on
--          this SAP."
--     ::= { tnSapEgrQosHsmdaQueueStatsEntry 9 }

------------------------------------------------------
-- Egress QoS HSMDA Queue Counter SAP Statistics Table
------------------------------------------------------
-- tnSapEgrQosHsmdaCntrStatsTable OBJECT-TYPE
--     SYNTAX          SEQUENCE OF SapEgrQosHsmdaCntrStatsEntry
--     MAX-ACCESS      not-accessible
--     STATUS          current
--     DESCRIPTION
--         "A table that contains egress QoS HSMDA counter SAP statistics."
--     ::= { tnSapObjs 57 }
--
-- tnSapEgrQosHsmdaCntrStatsEntry OBJECT-TYPE
--     SYNTAX          SapEgrQosHsmdaCntrStatsEntry
--     MAX-ACCESS      not-accessible
--     STATUS          current
--     DESCRIPTION
--         "Egress statistics about a specific SAP's QoS HSMDA counter."
--     INDEX           { tnSysSwitchId,  tnSvcId, tnSapPortId, tnSapEncapValue, tnSapEgrHsmdaCntrStCntrId }
--     ::= { tnSapEgrQosHsmdaCntrStatsTable 1 }
--
-- SapEgrQosHsmdaCntrStatsEntry ::= SEQUENCE {
--         tnSapEgrHsmdaCntrStCntrId             TEgressHsmdaCounterId,
--         tnSapEgrHsmdaCntrStCustId             TmnxCustId,
--         tnSapEgrHsmdaCntrStInProfPktFwd      Counter64,
--         tnSapEgrHsmdaCntrStInProfPktDrop    Counter64,
--         tnSapEgrHsmdaCntrStOutProfPktFwd     Counter64,
--         tnSapEgrHsmdaCntrStOutProfPktDrop   Counter64,
--         tnSapEgrHsmdaCntrStInProfOctFwd      Counter64,
--         tnSapEgrHsmdaCntrStInProfOctDrop    Counter64,
--         tnSapEgrHsmdaCntrStOutProfOctFwd     Counter64,
--         tnSapEgrHsmdaCntrStOutProfOctDrop   Counter64
--     }
--
-- tnSapEgrHsmdaCntrStCntrId  OBJECT-TYPE
--     SYNTAX          TEgressHsmdaCounterId
--     MAX-ACCESS      not-accessible
--     STATUS          current
--     DESCRIPTION
--         "The value of tnSapEgrHsmdaCntrStCntrId indicates the counter ID
--          for the statistics."
--     ::= { tnSapEgrQosHsmdaCntrStatsEntry 1 }
--
-- tnSapEgrHsmdaCntrStCustId  OBJECT-TYPE
--     SYNTAX          TmnxCustId
--     MAX-ACCESS      read-only
--     STATUS          current
--     DESCRIPTION
--         "The value of tnSapEgrHsmdaCntrStCustId indicates the customer ID
--          for the statistics."
--     ::= { tnSapEgrQosHsmdaCntrStatsEntry 2 }
--
-- tnSapEgrHsmdaCntrStInProfPktFwd        OBJECT-TYPE
--     SYNTAX      Counter64
--     MAX-ACCESS  read-only
--     STATUS      current
--     DESCRIPTION
--         "The value of tnSapEgrHsmdaCntrStInProfPktFwd indicates the
--          number of in-profile packets forwarded for the egress
--          counter, specified by the index tnSapIngHsmdaCntrStCntrId,
--          on this SAP."
--     ::= { tnSapEgrQosHsmdaCntrStatsEntry 3 }
--
-- tnSapEgrHsmdaCntrStInProfPktDrop        OBJECT-TYPE
--     SYNTAX      Counter64
--     MAX-ACCESS  read-only
--     STATUS      current
--     DESCRIPTION
--         "The value of tnSapEgrHsmdaCntrStInProfPktDrop indicates the
--          number of in-profile packets dropped for the egress
--          counter, specified by the index tnSapIngHsmdaCntrStCntrId,
--          on this SAP."
--     ::= { tnSapEgrQosHsmdaCntrStatsEntry 4 }
--
-- tnSapEgrHsmdaCntrStOutProfPktFwd        OBJECT-TYPE
--     SYNTAX      Counter64
--     MAX-ACCESS  read-only
--     STATUS      current
--     DESCRIPTION
--         "The value of tnSapEgrHsmdaCntrStOutProfPktFwd indicates the
--          number of out-of-profile packets forwarded for the egress
--          counter, specified by the index tnSapIngHsmdaCntrStCntrId,
--          on this SAP."
--     ::= { tnSapEgrQosHsmdaCntrStatsEntry 5 }
--
-- tnSapEgrHsmdaCntrStOutProfPktDrop        OBJECT-TYPE
--     SYNTAX      Counter64
--     MAX-ACCESS  read-only
--     STATUS      current
--     DESCRIPTION
--         "The value of tnSapEgrHsmdaCntrStOutProfPktDrop indicates the
--          number of out-of-profile packets dropped for the egress
--          counter, specified by the index tnSapIngHsmdaCntrStCntrId,
--          on this SAP."
--     ::= { tnSapEgrQosHsmdaCntrStatsEntry 6 }
--
-- tnSapEgrHsmdaCntrStInProfOctFwd        OBJECT-TYPE
--     SYNTAX      Counter64
--     MAX-ACCESS  read-only
--     STATUS      current
--     DESCRIPTION
--         "The value of tnSapEgrHsmdaCntrStInProfOctFwd indicates the
--          number of out-of-profile packets forwarded for the egress
--          counter, specified by the index tnSapIngHsmdaCntrStCntrId,
--          on this SAP."
--     ::= { tnSapEgrQosHsmdaCntrStatsEntry 7 }
--
-- tnSapEgrHsmdaCntrStInProfOctDrop        OBJECT-TYPE
--     SYNTAX      Counter64
--     MAX-ACCESS  read-only
--     STATUS      current
--     DESCRIPTION
--         "The value of tnSapEgrHsmdaCntrStInProfOctDrop indicates the
--          number of out-of-profile packets dropped for the egress
--          counter, specified by the index tnSapIngHsmdaCntrStCntrId,
--          on this SAP."
--     ::= { tnSapEgrQosHsmdaCntrStatsEntry 8 }
--
-- tnSapEgrHsmdaCntrStOutProfOctFwd        OBJECT-TYPE
--     SYNTAX      Counter64
--     MAX-ACCESS  read-only
--     STATUS      current
--     DESCRIPTION
--         "The value of tnSapEgrHsmdaCntrStOutProfOctFwd indicates the
--          number of out-of-profile packets forwarded for the egress
--          counter, specified by the index tnSapIngHsmdaCntrStCntrId,
--          on this SAP."
--     ::= { tnSapEgrQosHsmdaCntrStatsEntry 9 }
--
-- tnSapEgrHsmdaCntrStOutProfOctDrop        OBJECT-TYPE
--     SYNTAX      Counter64
--     MAX-ACCESS  read-only
--     STATUS      current
--     DESCRIPTION
--         "The value of tnSapEgrHsmdaCntrStOutProfOctDrop indicates the
--          number of out-of-profile packets dropped for the egress
--          counter, specified by the index tnSapIngHsmdaCntrStCntrId,
--          on this SAP."
--     ::= { tnSapEgrQosHsmdaCntrStatsEntry 10 }

-- --------------------------------------------------------
-- tnMtnSapL3PlcyTable
-- --------------------------------------------------------
-- tnMtnSapL3PlcyTable OBJECT-TYPE
--     SYNTAX      SEQUENCE OF MtnSapL3PlcyEntry
--     MAX-ACCESS  not-accessible
--     STATUS      current
--     DESCRIPTION
--         "The tnMtnSapL3PlcyTable has an entry for each managed SAP (MSAP)
--          policy configured in the system."
--     ::= { tnSapObjs 58 }
--
-- tnMtnSapL3PlcyEntry    OBJECT-TYPE
--     SYNTAX      MtnSapL3PlcyEntry
--     MAX-ACCESS  not-accessible
--     STATUS      current
--     DESCRIPTION
--         "Each entry represents the L3-related configuration for a managed
--          SAP (MSAP) policy."
--     AUGMENTS { tnMtnSapPlcyEntry }
--     ::= { tnMtnSapL3PlcyTable 1}
--
-- MtnSapL3PlcyEntry ::= SEQUENCE
--     {
--         tnMtnSapL3PlcyLastChanged         TimeStamp,
--         tnMtnSapL3PlcyAntiSpoof           INTEGER
--     }
--
-- tnMtnSapL3PlcyLastChanged        OBJECT-TYPE
--     SYNTAX      TimeStamp
--     MAX-ACCESS  read-only
--     STATUS      current
--     DESCRIPTION
--         "The value of tnMtnSapL3PlcyLastChanged indicates the sysUpTime
--          at the time of the last modification of this entry.
--
--          If no changes were made to the entry since the last
--          re-initialization of the local network management subsystem,
--          then this object contains a zero value."
--     ::= { tnMtnSapL3PlcyEntry 1 }
--
-- tnMtnSapL3PlcyAntiSpoof        OBJECT-TYPE
--     SYNTAX          INTEGER {
--                         sourceIpAndMacAddr  (3),
--                         nextHopIpAndMacAddr (4)
--                     }
--     MAX-ACCESS      read-create
--     STATUS          current
--     DESCRIPTION     "The value of the object tnMtnSapL3PlcyAntiSpoof specifies
--                      the type of anti-spoof filtering applicable on this MSAP.
--
--                      'nextHopIpAndMacAddr (4)' is not supported on SR-1, where
--                      the value of TIMETRA-CHASSIS-MIB::tmnxChassisType is '5'."
--     DEFVAL { sourceIpAndMacAddr }
--     ::= { tnMtnSapL3PlcyEntry 2 }

-- --------------------------------------
-- TblLastChgd objects for tnMtnSap tables
-- --------------------------------------

-- tnMtnSapPlcyTblLastChgd  OBJECT-TYPE
--     SYNTAX          TimeStamp
--     MAX-ACCESS      read-only
--     STATUS          current
--     DESCRIPTION     "The value of tnMtnSapPlcyTblLastChgd indicates the
--                      sysUpTime at the time of the last modification of
--                      tnMtnSapPlcyTable.
--
--                      If no changes were made to the entry since the last
--                      re-initialization of the local network management subsystem,
--                      then this object contains a zero value."
--     ::= { tnSapObjs 59 }
--
-- tnMtnSapTlsPlcyTblLastChgd  OBJECT-TYPE
--     SYNTAX          TimeStamp
--     MAX-ACCESS      read-only
--     STATUS          current
--     DESCRIPTION     "The value of tnMtnSapTlsPlcyTblLastChgd indicates the
--                      sysUpTime at the time of the last modification of
--                      tnMtnSapTlsPlcyTable.
--
--                      If no changes were made to the entry since the last
--                      re-initialization of the local network management subsystem,
--                      then this object contains a zero value."
--     ::= { tnSapObjs 60 }
--
-- tnMtnSapIgmpSnpgMcacLvlTblLastChgd  OBJECT-TYPE
--     SYNTAX          TimeStamp
--     MAX-ACCESS      read-only
--     STATUS          current
--     DESCRIPTION     "The value of tnMtnSapIgmpSnpgMcacLvlTblLastChgd indicates the
--                      sysUpTime at the time of the last modification of
--                      tnMtnSapIgmpSnpgMcacLevelTable.
--
--                      If no changes were made to the entry since the last
--                      re-initialization of the local network management subsystem,
--                      then this object contains a zero value."
--     ::= { tnSapObjs 61 }
--
-- tnMtnSapIgmpSnpgMcacLagTblLastChgd  OBJECT-TYPE
--     SYNTAX          TimeStamp
--     MAX-ACCESS      read-only
--     STATUS          current
--     DESCRIPTION     "The value of tnMtnSapIgmpSnpgMcacLagTblLastChgd indicates the
--                      sysUpTime at the time of the last modification of
--                      tnMtnSapIgmpSnpgMcacLagTable.
--
--                      If no changes were made to the entry since the last
--                      re-initialization of the local network management subsystem,
--                      then this object contains a zero value."
--     ::= { tnSapObjs 62 }
--
-- tnMtnSapInfoTblLastChgd  OBJECT-TYPE
--     SYNTAX          TimeStamp
--     MAX-ACCESS      read-only
--     STATUS          current
--     DESCRIPTION     "The value of tnMtnSapInfoTblLastChgd indicates the
--                      sysUpTime at the time of the last modification of
--                      tnMtnSapInfoTable.
--
--                      If no changes were made to the entry since the last
--                      re-initialization of the local network management subsystem,
--                      then this object contains a zero value."
--     ::= { tnSapObjs 63 }
--
-- tnMtnSapL3PlcyTblLastChgd  OBJECT-TYPE
--     SYNTAX          TimeStamp
--     MAX-ACCESS      read-only
--     STATUS          current
--     DESCRIPTION     "The value of tnMtnSapL3PlcyTblLastChgd indicates the
--                      sysUpTime at the time of the last modification of
--                      tnMtnSapL3PlcyTable.
--
--                      If no changes were made to the entry since the last
--                      re-initialization of the local network management subsystem,
--                      then this object contains a zero value."
--     ::= { tnSapObjs 64 }

-- -----------------------------------------
-- SAP Static Host Managed Route Table
-- -----------------------------------------

-- tnSapStaticHostMRtTblLastChgd OBJECT-TYPE
--     SYNTAX          TimeStamp
--     MAX-ACCESS      read-only
--     STATUS          current
--     DESCRIPTION     "The value of tnSapStaticHostMRtTblLastChgd indicates the
--                      sysUpTime at the time of the last modification of
--                      tnSapStaticHostMRtTable.
--
--                      If no changes were made to the entry since the last
--                      re-initialization of the local network management
--                      subsystem, this object contains a zero value."
--     ::= { tnSapObjs 65 }
--
-- tnSapStaticHostMRtTable OBJECT-TYPE
--     SYNTAX          SEQUENCE OF SapStaticHostMRtEntry
--     MAX-ACCESS      not-accessible
--     STATUS          current
--     DESCRIPTION     "The tnSapStaticHostMRtTable contains managed routes of
--                      SAP static hosts.
--
--                      Entries can be created and deleted via SNMP SET
--                      operations."
--     ::= { tnSapObjs 66 }
--
-- tnSapStaticHostMRtEntry OBJECT-TYPE
--     SYNTAX          SapStaticHostMRtEntry
--     MAX-ACCESS      not-accessible
--     STATUS          current
--     DESCRIPTION     "Each row entry represents information on a specific
--                      managed route."
--     INDEX           { tnSysSwitchId,  tnSvcId,
--                       tnSapPortId,
--                       tnSapEncapValue,
--                       tnSapStaticHostIpAddress,
--                       tnSapStaticHostMacAddress,
--                       tnSapStaticHostMRtAddrType,
--                       tnSapStaticHostMRtAddr,
--                       tnSapStaticHostMRtPrefixLen }
--     ::= { tnSapStaticHostMRtTable 1 }
--
-- SapStaticHostMRtEntry ::=
--     SEQUENCE {
--         tnSapStaticHostMRtAddrType         InetAddressType,
--         tnSapStaticHostMRtAddr             InetAddress,
--         tnSapStaticHostMRtPrefixLen        InetAddressPrefixLength,
--         tnSapStaticHostMRtRowStatus        RowStatus,
--         tnSapStaticHostMRtLastMgmtChange   TimeStamp,
--         tnSapStaticHostMRtStatus           TmnxManagedRouteStatus
--     }
--
-- tnSapStaticHostMRtAddrType OBJECT-TYPE
--     SYNTAX          InetAddressType
--     MAX-ACCESS      not-accessible
--     STATUS          current
--     DESCRIPTION     "The value of tnSapStaticHostMRtAddrType indicates
--                      the address type of tnSapStaticHostMRtAddr."
--     ::= { tnSapStaticHostMRtEntry 1 }
--
-- tnSapStaticHostMRtAddr OBJECT-TYPE
--     SYNTAX          InetAddress (SIZE(4|16))
--     MAX-ACCESS      not-accessible
--     STATUS          current
--     DESCRIPTION     "The value of tnSapStaticHostMRtAddr indicates
--                      the IP address of the managed route."
--     ::= { tnSapStaticHostMRtEntry 2 }
--
-- tnSapStaticHostMRtPrefixLen OBJECT-TYPE
--     SYNTAX          InetAddressPrefixLength (0..32)
--     MAX-ACCESS      not-accessible
--     STATUS          current
--     DESCRIPTION     "The value of tnSapStaticHostMRtPrefixLen indicates
--                      the prefix length of the subnet associated with
--                      tnSapStaticHostMRtAddr."
--     ::= { tnSapStaticHostMRtEntry 3 }
--
-- tnSapStaticHostMRtRowStatus OBJECT-TYPE
--     SYNTAX          RowStatus
--     MAX-ACCESS      read-create
--     STATUS          current
--     DESCRIPTION     "The value of tnSapStaticHostMRtRowStatus controls the
--                      creation and deletion of rows in this table."
--     ::= { tnSapStaticHostMRtEntry 4 }
--
-- tnSapStaticHostMRtLastMgmtChange OBJECT-TYPE
--     SYNTAX          TimeStamp
--     MAX-ACCESS      read-only
--     STATUS          current
--     DESCRIPTION     "The value of tnSapStaticHostMRtLastMgmtChange indicates the
--                      value of sysUpTime at the time of the last management
--                      change of any writable object of this row."
--     ::= { tnSapStaticHostMRtEntry 5 }
--
-- tnSapStaticHostMRtStatus OBJECT-TYPE
--     SYNTAX          TmnxManagedRouteStatus
--     MAX-ACCESS      read-only
--     STATUS          current
--     DESCRIPTION     "The value of svcDhcpManagedRouteStatus indicates
--                      the state of this managed route."
--     ::= { tnSapStaticHostMRtEntry 6 }

-- ---------------------------------------------------------------------
--  tnSapTlsArpHostTable
--
--
--  Sparse Dependent Extension of the tnSapTlsInfoTable.
--
--  The same indexes are used for both the base table, tnSapTlsInfoTable,
--  and the sparse dependent table, tnSapTlsArpHostTable.
--
--  This in effect extends the tnSapTlsInfoTable with additional columns.
--  A row is automatically created in the tnSapTlsArpHostTable for each row
--  in the tnSapTlsInfoTable .
--
--  Deletion of a row in the tnSapTlsInfoTable results in the
--  same fate for the row in the tnSapTlsArpHostTable.
-- ---------------------------------------------------------------------

-- tnSapTlsArpHostTableLastMgmtChange OBJECT-TYPE
--     SYNTAX      TimeStamp
--     MAX-ACCESS  read-only
--     STATUS      current
--     DESCRIPTION
--         "The value of tnSapTlsArpHostTableLastMgmtChange indicates the sysUpTime
--          at the time of the most recent management-initiated change to the
--          tnSapTlsArpHostTable."
--     ::= { tnSapObjs 67 }
--
-- tnSapTlsArpHostTable OBJECT-TYPE
--     SYNTAX      SEQUENCE OF SapTlsArpHostEntry
--     MAX-ACCESS  not-accessible
--     STATUS      current
--     DESCRIPTION
--         "A table that contains ARP host configuration
--          information about a SAP in a TLS."
--     ::= { tnSapObjs 68 }
--
-- tnSapTlsArpHostEntry OBJECT-TYPE
--     SYNTAX      SapTlsArpHostEntry
--     MAX-ACCESS  not-accessible
--     STATUS      current
--     DESCRIPTION
--         "ARP host specific information about a SAP in a TLS."
--     INDEX           { tnSysSwitchId,  tnSvcId, tnSapPortId, tnSapEncapValue }
--     ::= { tnSapTlsArpHostTable 1 }
--
-- SapTlsArpHostEntry ::=
--     SEQUENCE {
--         tnSapTlsArpHostLastMgmtChange       TimeStamp,
--         tnSapTlsArpHostAdminState           TmnxAdminState,
--         tnSapTlsArpHostMaxNumHosts          Unsigned32,
--         tnSapTlsArpHostMinAuthIntvl         Unsigned32
--     }
--
-- tnSapTlsArpHostLastMgmtChange OBJECT-TYPE
--     SYNTAX      TimeStamp
--     MAX-ACCESS  read-only
--     STATUS      current
--     DESCRIPTION
--         "The value of tnSapTlsArpHostLastMgmtChange indicates the sysUpTime at
--          the time of the most recent management-initiated change to this
--          table row."
--     ::= { tnSapTlsArpHostEntry 1 }
--
-- tnSapTlsArpHostAdminState OBJECT-TYPE
--     SYNTAX      TmnxAdminState
--     MAX-ACCESS  read-write
--     STATUS      current
--     DESCRIPTION
--         "The value of the object tnSapTlsArpHostAdminState specifies the
--          administrative state of the ARP host functionality on this TLS SAP."
--     DEFVAL { outOfService }
--     ::= { tnSapTlsArpHostEntry 2 }
--
-- tnSapTlsArpHostMaxNumHosts OBJECT-TYPE
--     SYNTAX      Unsigned32 (1..32767)
--     MAX-ACCESS  read-write
--     STATUS      current
--     DESCRIPTION
--         "The value of tnSapTlsArpHostMaxNumHosts specifies the maximum
--          number of ARP hosts allowed on this TLS SAP."
--     DEFVAL { 1 }
--     ::= { tnSapTlsArpHostEntry 3 }
--
-- tnSapTlsArpHostMinAuthIntvl OBJECT-TYPE
--     SYNTAX      Unsigned32 (1..6000)
--     UNITS       "minutes"
--     MAX-ACCESS  read-write
--     STATUS      current
--     DESCRIPTION
--         "The value of tnSapTlsArpHostMinAuthIntvl specifies the minimum
--          interval between two consecutive authentication attempts for the
--          same ARP host."
--     DEFVAL { 15 }
--     ::= { tnSapTlsArpHostEntry 4 }

-- ---------------------------------------------------------------------
--  tnSapIgmpTrkTable
--
--
--  Sparse Dependent Extension of the tnSapBaseInfoTable.
--
--  The same indexes are used for both the base table, tnSapBaseInfoTable,
--  and the sparse dependent table, tnSapIgmpTrkTable.
--
--  This in effect extends the tnSapBaseInfoTable with additional columns.
--  A row is automatically created in the tnSapIgmpTrkTable for each applicable
--  row in the tnSapBaseInfoTable .
--
--  Deletion of a row in the tnSapBaseInfoTable results in the
--  same fate for the row in the tnSapIgmpTrkTable.
-- ---------------------------------------------------------------------

-- tnSapIgmpTrkTableLastMgmtChange OBJECT-TYPE
--     SYNTAX      TimeStamp
--     MAX-ACCESS  read-only
--     STATUS      current
--     DESCRIPTION
--         "The value of tnSapIgmpTrkTableLastMgmtChange indicates the sysUpTime
--          at the time of the most recent management-initiated change to the
--          tnSapIgmpTrkTable."
--     ::= { tnSapObjs 69 }
--
-- tnSapIgmpTrkTable OBJECT-TYPE
--     SYNTAX      SEQUENCE OF SapIgmpTrkEntry
--     MAX-ACCESS  not-accessible
--     STATUS      current
--     DESCRIPTION
--         "A table that contains IGMP host tracking configuration
--          information about SAP's.
--
--          The system automatically creates an entry in this table
--          for each SAP where it creates a corresponding entry in the
--          tnSapSubMgmtInfoTable.
--
--          This means that all SAP's that support Enhanced Subscriber Management
--          have en entry in this table."
--     ::= { tnSapObjs 70 }
--
-- tnSapIgmpTrkEntry OBJECT-TYPE
--     SYNTAX      SapIgmpTrkEntry
--     MAX-ACCESS  not-accessible
--     STATUS      current
--     DESCRIPTION
--         "IGMP host tracking specific information about a SAP."
--     INDEX           { tnSysSwitchId,  tnSvcId, tnSapPortId, tnSapEncapValue }
--     ::= { tnSapIgmpTrkTable 1 }
--
-- SapIgmpTrkEntry ::=
--     SEQUENCE {
--         tnSapIgmpTrkLastMgmtChange          TimeStamp,
--         tnSapIgmpTrkExpiryTime              Unsigned32,
--         tnSapIgmpTrkImportPlcy              TPolicyStatementNameOrEmpty,
--         tnSapIgmpTrkMaxNbrGrps              Unsigned32,
--         tnSapIgmpTrkNbrGrps                 Gauge32,
--         tnSapIgmpTrkMaxNbrSrcs              Unsigned32
--     }
--
-- tnSapIgmpTrkLastMgmtChange OBJECT-TYPE
--     SYNTAX      TimeStamp
--     MAX-ACCESS  read-only
--     STATUS      current
--     DESCRIPTION
--         "The value of tnSapIgmpTrkLastMgmtChange indicates the sysUpTime at
--          the time of the most recent management-initiated change to this
--          table row."
--     ::= { tnSapIgmpTrkEntry 1 }
--
-- tnSapIgmpTrkExpiryTime OBJECT-TYPE
--     SYNTAX      Unsigned32 (0|1..65535)
--     UNITS       "seconds"
--     MAX-ACCESS  read-write
--     STATUS      current
--     DESCRIPTION
--         "The value of tnSapIgmpTrkExpiryTime specifies
--          the time in seconds that this system continues to track an inactive
--          host.
--
--          The value zero specifies that the value must be set to the actual
--          value of the object svcIgmpTrkExpiryTime of the service this SAP
--          belongs to."
--     DEFVAL { 0 }
--     ::= { tnSapIgmpTrkEntry 2 }
--
-- tnSapIgmpTrkImportPlcy OBJECT-TYPE
--     SYNTAX      TPolicyStatementNameOrEmpty
--     MAX-ACCESS  read-write
--     STATUS      current
--     DESCRIPTION
--         "The value of the object tnSapIgmpTrkImportPlcy specifies
--          the policy statement that must be applied to all
--          incoming IGMP messages on this SAP."
--     DEFVAL { "" }
--     ::= { tnSapIgmpTrkEntry 3 }
--
-- tnSapIgmpTrkMaxNbrGrps OBJECT-TYPE
--     SYNTAX      Unsigned32 (0..1000)
--     MAX-ACCESS  read-write
--     STATUS      current
--     DESCRIPTION
--         "The value of the object tnSapIgmpTrkMaxNbrGrps specifies
--          how many group addresses are allowed for this SAP.
--
--          The value 0 means that no limit is imposed."
--     DEFVAL { 0 }
--     ::= { tnSapIgmpTrkEntry 4 }
--
-- tnSapIgmpTrkNbrGrps OBJECT-TYPE
--     SYNTAX      Gauge32
--     MAX-ACCESS  read-only
--     STATUS      current
--     DESCRIPTION
--         "The value of the object tnSapIgmpTrkNbrGrps indicates
--          how many group addresses are tracked for this SAP."
--     ::= { tnSapIgmpTrkEntry 5 }
--
-- tnSapIgmpTrkMaxNbrSrcs OBJECT-TYPE
--     SYNTAX      Unsigned32 (0..1000)
--     MAX-ACCESS  read-write
--     STATUS      current
--     DESCRIPTION
--         "The value of the object tnSapIgmpTrkMaxNbrSrcs specifies
--          how many source addresses are allowed per group address for this SAP.
--
--          The value 0 means that no limit is imposed."
--     DEFVAL { 0 }
--     ::= { tnSapIgmpTrkEntry 6 }

-- ---------------------------------------------------------------------
-- FR SAP Table
--
--
--  Sparse Dependent Extention of the tnSapBaseInfoTable.
--
--  The same indexes are used for both the base table, tnSapBaseInfoTable,
--  and the sparse dependent table, tnSapFrInfoTable.
--
--  This in effect extends the tnSapBaseInfoTable with additional columns.
--  Rows are created in the tnSapFrInfoTable only for those entries
--  in the tnSapBaseInfoTable that are created on a port that has
--  'frEncap' set for port encapsulation.
--
--  Deletion of a row in the tnSapBaseInfoTable results in the
--  same fate for the row in the tnSapFrInfoTable.
-- ---------------------------------------------------------------------
-- tnSapFrInfoTable OBJECT-TYPE
--     SYNTAX          SEQUENCE OF SapFrInfoEntry
--     MAX-ACCESS      not-accessible
--     STATUS          current
--     DESCRIPTION     "A table that contains FR SAP information."
--     ::= { tnSapObjs 71 }
--
-- tnSapFrInfoEntry OBJECT-TYPE
--     SYNTAX          SapFrInfoEntry
--     MAX-ACCESS      not-accessible
--     STATUS          current
--     DESCRIPTION     "Information about a specific FR SAP."
--     INDEX           { tnSysSwitchId,  tnSvcId, tnSapPortId, tnSapEncapValue }
--     ::= { tnSapFrInfoTable 1 }
--
-- SapFrInfoEntry ::=
--     SEQUENCE {
--         tnSapFrInfoFrf12Mode        TmnxEnabledDisabled,
--         tnSapFrInfoSchedulingClass  TmnxMcFrClassIndex,
--         tnSapFrInfoLastChanged      TimeStamp
--     }
--
-- tnSapFrInfoFrf12Mode OBJECT-TYPE
--     SYNTAX      TmnxEnabledDisabled
--     MAX-ACCESS  read-create
--     STATUS      current
--     DESCRIPTION
--         "The value of tnSapFrInfoFrf12Mode enables or disables the
--          use of FRF12 headers. This must be set to disabled for this
--          entry to be added to a mlfr bundle."
--     DEFVAL { disabled }
--     ::= { tnSapFrInfoEntry 1 }
--
-- tnSapFrInfoSchedulingClass    OBJECT-TYPE
--     SYNTAX      TmnxMcFrClassIndex
--     MAX-ACCESS  read-create
--     STATUS      current
--     DESCRIPTION
--         "The value of tnSapFrInfoSchedulingClass specifies the scheduling class
--          to use for this tnSap. This object is only applicable for a tnSapPortId that
--          has tmnxBundleType set to 'mlfr', tnSapFrInfoFrf12Mode SAPs set to 'enabled'
--          or tmnxFrIntfFrf12Mode set to 'enabled'."
--     DEFVAL      { 3 }
--     ::= { tnSapFrInfoEntry 2 }
--
-- tnSapFrInfoLastChanged OBJECT-TYPE
--     SYNTAX      TimeStamp
--     MAX-ACCESS  read-only
--     STATUS      current
--     DESCRIPTION
--         "The value of tnSapFrInfoLastChanged indicates the sysUpTime
--          at the time of the last modification of this entry."
--     ::= { tnSapFrInfoEntry 3 }

-- ---------------------------------------------------------------------
-- FRF12 SAP Table
--
--
--  Sparse Dependent Extention of the tnSapFrInfoTable.
--
--  The same indexes are used for both the tnSapFrInfoTable,
--  and the sparse dependent table, tnSapFrf12InfoTable.
--
--  This in effect extends the tnSapFrInfoTable with additional columns.
--  Rows are created in the tnSapFrf12InfoTable only for those entries
--  in the tnSapFrInfoTable that are created with tnSapFrInfoFrf12Mode set
--- to 'enable'.
--
--  Setting tnSapFrInfoFrf12Mode to 'disable' results in the removal
--  for the row in the tnSapFrf12InfoTable.
-- ---------------------------------------------------------------------
-- tnSapFrf12InfoTable OBJECT-TYPE
--     SYNTAX          SEQUENCE OF SapFrf12InfoEntry
--     MAX-ACCESS      not-accessible
--     STATUS          current
--     DESCRIPTION     "A table that contains FRF12 SAP information."
--     ::= { tnSapObjs 74 }
--
-- tnSapFrf12InfoEntry OBJECT-TYPE
--     SYNTAX          SapFrf12InfoEntry
--     MAX-ACCESS      not-accessible
--     STATUS          current
--     DESCRIPTION     "Information about a specific FR SAP."
--     INDEX           { tnSysSwitchId,  tnSvcId, tnSapPortId, tnSapEncapValue }
--     ::= { tnSapFrf12InfoTable 1 }
--
-- SapFrf12InfoEntry ::=
--     SEQUENCE {
--         tnSapFrf12InfoFragmentThreshold     Unsigned32,
--         tnSapFrf12InfoLastChanged           TimeStamp
--     }
--
-- tnSapFrf12InfoFragmentThreshold    OBJECT-TYPE
--     SYNTAX      Unsigned32(128..512)
--     MAX-ACCESS  read-create
--     STATUS      current
--     DESCRIPTION
--         "The value of tnSapFrf12InfoFragmentThreshold specifies the maximum length
--          of a fragment to be transmitted."
--     DEFVAL      { 128 }
--     ::= { tnSapFrf12InfoEntry 1 }
--
-- tnSapFrf12InfoLastChanged OBJECT-TYPE
--     SYNTAX      TimeStamp
--     MAX-ACCESS  read-only
--     STATUS      current
--     DESCRIPTION
--         "The value of tnSapFrf12InfoLastChanged indicates the sysUpTime
--          at the time of the last modification of this entry.."
--     ::= { tnSapFrf12InfoEntry 2 }

-- ---------------------------------------------------------------------
--  tnSapArpHostStatTable
--
--
--  Sparse Dependent Extension of the tnSapBaseInfoTable.
--
--  The same indexes are used for both the base table, tnSapBaseInfoTable,
--  and the sparse dependent table, tnSapArpHostStatTable.
--
--  This in effect extends the tnSapBaseInfoTable with additional columns.
--  A row is automatically created in the tnSapArpHostStatTable for each applicable
--  row in the tnSapBaseInfoTable .
--
--  Deletion of a row in the tnSapBaseInfoTable results in the
--  same fate for the row in the tnSapArpHostStatTable.
-- ---------------------------------------------------------------------

-- tnSapArpHostStatTable OBJECT-TYPE
--     SYNTAX      SEQUENCE OF SapArpHostStatEntry
--     MAX-ACCESS  not-accessible
--     STATUS      current
--     DESCRIPTION
--         "A table that contains ARP host status and statistics
--          information about SAP's."
--     ::= { tnSapObjs 75 }
--
-- tnSapArpHostStatEntry OBJECT-TYPE
--     SYNTAX      SapArpHostStatEntry
--     MAX-ACCESS  not-accessible
--     STATUS      current
--     DESCRIPTION
--         "ARP host specific status and statistics information about a SAP."
--     INDEX           { tnSysSwitchId,  tnSvcId, tnSapPortId, tnSapEncapValue }
--     ::= { tnSapArpHostStatTable 1 }
--
-- SapArpHostStatEntry ::=
--     SEQUENCE {
--         tnSapArpHostStatLastClearedTime    TimeStamp,
--         tnSapArpHostStatNumHosts           Gauge32,
--         tnSapArpHostStatTriggersRx         Counter32,
--         tnSapArpHostStatTriggersIgnored    Counter32,
--         tnSapArpHostStatTrigIgnQFull       Counter32,
--         tnSapArpHostStatNumForcedVerif     Counter32,
--         tnSapArpHostStatNumCreated         Counter32,
--         tnSapArpHostStatNumDeleted         Counter32,
--         tnSapArpHostStatNumUpdated         Counter32,
--         tnSapArpHostStatNumAuthReq         Counter32
--     }
--
-- tnSapArpHostStatLastClearedTime OBJECT-TYPE
--     SYNTAX      TimeStamp
--     MAX-ACCESS  read-only
--     STATUS      current
--     DESCRIPTION
--         "The value of tnSapArpHostStatLastClearedTime indicates
--          the last time that these stats were cleared.
--
--          The value zero indicates that they have not been cleared yet."
--     ::= { tnSapArpHostStatEntry 1 }
--
-- tnSapArpHostStatNumHosts OBJECT-TYPE
--     SYNTAX      Gauge32
--     MAX-ACCESS  read-only
--     STATUS      current
--     DESCRIPTION
--         "The value of tnSapArpHostStatNumHosts indicates
--          the actual number of ARP hosts on this SAP."
--     ::= { tnSapArpHostStatEntry 2 }
--
-- tnSapArpHostStatTriggersRx OBJECT-TYPE
--     SYNTAX      Counter32
--     MAX-ACCESS  read-only
--     STATUS      current
--     DESCRIPTION
--         "The value of tnSapArpHostStatTriggersRx indicates
--          the number of ARP triggers received on this SAP
--          since the last re-initialization of the local network
--          management subsystem, or the last time the system statistics were
--          cleared."
--     ::= { tnSapArpHostStatEntry 3 }
--
-- tnSapArpHostStatTriggersIgnored OBJECT-TYPE
--     SYNTAX      Counter32
--     MAX-ACCESS  read-only
--     STATUS      current
--     DESCRIPTION
--         "The value of tnSapArpHostStatTriggersIgnored indicates
--          the number of ARP triggers received on this SAP
--          that did not result in the creation of a new ARP host
--          since the last re-initialization of the local network
--          management subsystem, or the last time the system statistics were
--          cleared.
--
--          This number does not include the number indicated by
--          tnSapArpHostStatTrigIgnQFull."
--     ::= { tnSapArpHostStatEntry 4 }
--
-- tnSapArpHostStatTrigIgnQFull OBJECT-TYPE
--     SYNTAX      Counter32
--     MAX-ACCESS  read-only
--     STATUS      current
--     DESCRIPTION
--         "The value of tnSapArpHostStatTrigIgnQFull indicates
--          the number of ARP triggers received on this SAP
--          that did not result in the creation of a new ARP host because
--          the internal ARP trigger event queue of the system was full,
--          since the last re-initialization of the local network
--          management subsystem, or the last time the system statistics were
--          cleared."
--     ::= { tnSapArpHostStatEntry 5 }
--
-- tnSapArpHostStatNumForcedVerif OBJECT-TYPE
--     SYNTAX      Counter32
--     MAX-ACCESS  read-only
--     STATUS      current
--     DESCRIPTION
--         "The value of tnSapArpHostStatNumForcedVerif indicates
--          the number of times that the system started a forced subscriber
--          host connectivity verification for an ARP host on this SAP
--          since the last re-initialization of the local network
--          management subsystem, or the last time the system statistics were
--          cleared."
--     ::= { tnSapArpHostStatEntry 6 }
--
-- tnSapArpHostStatNumCreated OBJECT-TYPE
--     SYNTAX      Counter32
--     MAX-ACCESS  read-only
--     STATUS      current
--     DESCRIPTION
--         "The value of tnSapArpHostStatNumCreated indicates
--          the number of times that an ARP host was created on this SAP
--          since the last re-initialization of the local network
--          management subsystem, or the last time the system statistics were
--          cleared."
--     ::= { tnSapArpHostStatEntry 7 }
--
-- tnSapArpHostStatNumDeleted OBJECT-TYPE
--     SYNTAX      Counter32
--     MAX-ACCESS  read-only
--     STATUS      current
--     DESCRIPTION
--         "The value of tnSapArpHostStatNumDeleted indicates
--          the number of times that an ARP host was deleted on this SAP
--          since the last re-initialization of the local network
--          management subsystem, or the last time the system statistics were
--          cleared."
--     ::= { tnSapArpHostStatEntry 8 }
--
-- tnSapArpHostStatNumUpdated OBJECT-TYPE
--     SYNTAX      Counter32
--     MAX-ACCESS  read-only
--     STATUS      current
--     DESCRIPTION
--         "The value of tnSapArpHostStatNumUpdated indicates
--          the number of times that an ARP host was updated on this SAP
--          since the last re-initialization of the local network
--          management subsystem, or the last time the system statistics were
--          cleared."
--     ::= { tnSapArpHostStatEntry 9 }
--
-- tnSapArpHostStatNumAuthReq OBJECT-TYPE
--     SYNTAX      Counter32
--     MAX-ACCESS  read-only
--     STATUS      current
--     DESCRIPTION
--         "The value of tnSapArpHostStatNumAuthReq indicates
--          the number of times that the system initiated
--          an authentication request for an ARP host on this SAP
--          since the last re-initialization of the local network
--          management subsystem, or the last time the system statistics were
--          cleared."
--     ::= { tnSapArpHostStatEntry 10 }

-- ----------------------------------
-- PBB SAP Table
-- ----------------------------------
-- tnSapPbbTable OBJECT-TYPE
--     SYNTAX          SEQUENCE OF SapPbbEntry
--     MAX-ACCESS      not-accessible
--     STATUS          current
--     DESCRIPTION     "A table that contains
--                      Provider Backbone Bridging (PBB/IEEE 802.1ah) SAP
--                      information."
--     ::= { tnSapObjs 76 }
--
-- tnSapPbbEntry OBJECT-TYPE
--     SYNTAX          SapPbbEntry
--     MAX-ACCESS      not-accessible
--     STATUS          current
--     DESCRIPTION     "PBB I-Component instance-specific information about a
--                      specific SAP in the B-Component instance.
--
--                      Entries in this table can be created or deleted
--                      via SNMP operations."
--     INDEX           { tnSysSwitchId,  tnSapPbbSvcIdIVpls,
--                       tnSapPbbSvcIdBVpls,
--                       tnSapPbbPortId,
--                       tnSapPbbEncapValue }
--     ::= { tnSapPbbTable 1 }
--
-- SapPbbEntry ::=
--     SEQUENCE {
--         tnSapPbbSvcIdIVpls                 TmnxServId,
--         tnSapPbbSvcIdBVpls                 TmnxServId,
--         tnSapPbbPortId                     TmnxPortID,
--         tnSapPbbEncapValue                 TmnxEncapVal,
--         tnSapPbbRowStatus                  RowStatus,
--         tnSapPbbLastMgmtChange             TimeStamp,
--         tnSapPbbIgmpSnpgMRouter            TruthValue
--     }
--
-- tnSapPbbSvcIdIVpls OBJECT-TYPE
--     SYNTAX          TmnxServId
--     MAX-ACCESS      not-accessible
--     STATUS          current
--     DESCRIPTION     "The value of the object tnSapPbbSvcIdIVpls specifies the
--                      Service identifier of the I-Component instance."
--     ::= { tnSapPbbEntry 1 }
--
-- tnSapPbbSvcIdBVpls OBJECT-TYPE
--     SYNTAX          TmnxServId
--     MAX-ACCESS      not-accessible
--     STATUS          current
--     DESCRIPTION     "The value of the object tnSapPbbSvcIdBVpls specifies the
--                      Service identifier of the B-Component instance."
--     ::= { tnSapPbbEntry 2 }
--
-- tnSapPbbPortId OBJECT-TYPE
--     SYNTAX          TmnxPortID
--     MAX-ACCESS      not-accessible
--     STATUS          current
--     DESCRIPTION     "The value of the object tnSapPbbPortId specifies
--                      the ID of the access port in the B-Component instance
--                      where this SAP is defined."
--     ::= { tnSapPbbEntry 3 }
--
-- tnSapPbbEncapValue OBJECT-TYPE
--     SYNTAX          TmnxEncapVal
--     MAX-ACCESS      not-accessible
--     STATUS          current
--     DESCRIPTION     "The value of the object tnSapPbbEncapValue specifies
--                      the value of the label used to identify this SAP in the
--                      B-Component instance on the access port specified by
--                      tnSapPortId."
--     ::= { tnSapPbbEntry 4 }
--
-- tnSapPbbRowStatus OBJECT-TYPE
--     SYNTAX          RowStatus
--     MAX-ACCESS      read-create
--     STATUS          current
--     DESCRIPTION     "The value of tnSapPbbRowStatus specifies
--                      the row status of this row.
--
--                      The only values supported during a set operation are
--                      'createAndGo' and 'destroy'."
--     ::= { tnSapPbbEntry 5 }
--
-- tnSapPbbLastMgmtChange OBJECT-TYPE
--     SYNTAX          TimeStamp
--     MAX-ACCESS      read-only
--     STATUS          current
--     DESCRIPTION
--                     "The value of tnSapPbbLastMgmtChange indicates
--                      the sysUpTime at the time of the most recent
--                      management-initiated change to this table row."
--     ::= { tnSapPbbEntry 6 }
--
-- tnSapPbbIgmpSnpgMRouter OBJECT-TYPE
--     SYNTAX          TruthValue
--     MAX-ACCESS      read-create
--     STATUS          current
--     DESCRIPTION
--                     "The value of the object tnSapPbbIgmpSnpgMRouter specifies
--                      if a multicast router is attached behind this SAP."
--     DEFVAL { false }
--     ::= { tnSapPbbEntry 7 }

-- --------------------------------------
-- SAP Notification Objects
-- --------------------------------------
-- tnSapNotifyObjs       OBJECT IDENTIFIER ::= { tnSapObjs 100 }
--
-- tnSapNotifyPortId OBJECT-TYPE
--     SYNTAX          TmnxPortID
--     MAX-ACCESS      accessible-for-notify
--     STATUS          current
--     DESCRIPTION     "The ID of the access port where a SAP is defined.
--                      This object is used by the tnSapPortStateChangeProcessed
--                      notification to indicate the port ID that changed
--                      state and that resulted in having the associated
--                      tnSapStatusChanged events suppressed for all SAPs on
--                      that port."
--     ::= { tnSapNotifyObjs 1 }
--
-- tnMtnSapStatus OBJECT-TYPE
--     SYNTAX          ConfigStatus
--     MAX-ACCESS      accessible-for-notify
--     STATUS          current
--     DESCRIPTION     "The status of the Managed SAP which is used
--                      by the tnMtnSapStateChanged notification to indicate
--                      what state the Managed SAP has entered: 'created',
--                      'modified', or 'deleted'."
--     ::= { tnSapNotifyObjs 2 }
--
-- svcManagedSapCreationError OBJECT-TYPE
--    SYNTAX         DisplayString
--    MAX-ACCESS     accessible-for-notify
--    STATUS         current
--    DESCRIPTION    "The value of the object svcManagedSapCreationError
--                    indicates the reason why the system was unable to create
--                    the managed SAP."
--    ::= { tnSapNotifyObjs 3 }
--
-- tnSapTlsNotifyMacAddr OBJECT-TYPE
--     SYNTAX         MacAddress
--     MAX-ACCESS     accessible-for-notify
--     STATUS         current
--     DESCRIPTION    "The value of the object tnSapTlsNotifyMacAddr
--                     indicates the MAC address associated with
--                     a VPLS SAP."
--     ::= { tnSapNotifyObjs 4 }
--
-- tnSapBGPPeeringHostIpAddrType OBJECT-TYPE
--     SYNTAX          InetAddressType
--     MAX-ACCESS      accessible-for-notify
--     STATUS          current
--     DESCRIPTION     "The value of tnSapBGPPeeringHostIpAddrType indicates the
--                      address type of tnSapBGPPeeringHostIpAddr."
--     ::= { tnSapNotifyObjs 5 }
--
-- tnSapBGPPeeringHostIpAddr OBJECT-TYPE
--     SYNTAX          InetAddress (SIZE(0|4))
--     MAX-ACCESS      accessible-for-notify
--     STATUS          current
--     DESCRIPTION     "The value of tnSapBGPPeeringHostIpAddr indicates the IP
--                      address of the host."
--     ::= { tnSapNotifyObjs 6 }
--
-- tnSapBGPPeeringNotifDescription OBJECT-TYPE
--     SYNTAX      DisplayString
--     MAX-ACCESS  accessible-for-notify
--     STATUS      current
--     DESCRIPTION
--         "The object tnSapBGPPeeringNotifDescription is a printable character
--         string."
--     ::= { tnSapNotifyObjs 7 }
--
-- tnSapBGPPeeringAttrDiscarded OBJECT-TYPE
--     SYNTAX      TruthValue
--     MAX-ACCESS  accessible-for-notify
--     STATUS      current
--     DESCRIPTION
--         "The value of the object tnSapBGPPeeringAttrDiscarded is equal to 'true'
--          if the BGP Peering attributes have been discarded."
--     ::= { tnSapNotifyObjs 8 }
--
-- tnSapBGPPeeringVRtrID  OBJECT-TYPE
--     SYNTAX      TmnxVRtrID
--     MAX-ACCESS  accessible-for-notify
--     STATUS      current
--     DESCRIPTION
--         "The  unique value that identifies a virtual router."
--     ::= { tnSapNotifyObjs 9 }

-- --------------------------------------
-- SAP Notifications
-- --------------------------------------
-- tnSapCreated NOTIFICATION-TYPE
--     OBJECTS {
--         tnCustId,
--         tnSvcId,
--         tnSvcVpnId,
--         tnSapPortId,
--         tnSapEncapValue
--     }
--     STATUS          obsolete
--     DESCRIPTION     "This trap is sent when a new row is created
--                      in the tnSapBaseInfoTable."
--     ::= { tnSapTraps 1 }
--
-- tnSapDeleted NOTIFICATION-TYPE
--     OBJECTS {
--         tnCustId,
--         tnSvcId,
--         tnSvcVpnId,
--         tnSapPortId,
--         tnSapEncapValue
--     }
--     STATUS          obsolete
--     DESCRIPTION     "This trap is sent when an existing row is
--                      deleted from the tnSapBaseInfoTable."
--     ::= { tnSapTraps 2 }

tnSapStatusChanged NOTIFICATION-TYPE
    OBJECTS {
        tnCustId,
        tnSvcId,
        tnSvcVpnId,
        tnSapPortId,
        tnSapEncapValue,
        tnSapAdminStatus,
        tnSapOperStatus,
        tnSapOperFlags
    }
    STATUS          current
    DESCRIPTION     "The tnSapStatusChanged notification is generated
                     when there is a change in the administrative or
                     operating status of an SAP.

                     Notice that this trap is not generated whenever
                     the SAP operating status change is caused by an
                     operating status change on the associated access
                     port."
    ::= { tnSapTraps 3 }

tnSapTlsMacAddrLimitAlarmRaised  NOTIFICATION-TYPE
    OBJECTS {
        tnCustId,
        tnSvcId,
        tnSvcVpnId,
        tnSapPortId,
        tnSapEncapValue
    }
    STATUS          current
    DESCRIPTION     "The trap tnSapTlsMacAddrLimitAlarmRaised is sent whenever
                     the number of MAC addresses stored in the FDB for this SAP
                     increases to reach the watermark specified by the object
                     svcTlsFdbTableFullHighWatermark."
    ::= { tnSapTraps 4 }

tnSapTlsMacAddrLimitAlarmCleared  NOTIFICATION-TYPE
    OBJECTS {
        tnCustId,
        tnSvcId,
        tnSvcVpnId,
        tnSapPortId,
        tnSapEncapValue
    }
    STATUS          current
    DESCRIPTION     "The trap tnSapTlsMacAddrLimitAlarmCleared is sent whenever
                     the number of MAC addresses stored in the FDB for this SAP
                     drops to the watermark specified by the object
                     svcTlsFdbTableFullLowWatermark."
    ::= { tnSapTraps 5 }

-- tnSapTlsDHCPLseStEntriesExceeded   NOTIFICATION-TYPE
--     OBJECTS {
--         tnCustId,
--         tnSvcId,
--         tnSvcVpnId,
--         tnSapPortId,
--         tnSapEncapValue,
--         tnTlsDhcpLseStateNewCiAddr,
--         tnTlsDhcpLseStateNewChAddr,
--         tnTlsDHCPClientLease
--     }
--     STATUS          obsolete
--     DESCRIPTION     "The tnSapTlsDHCPLseStEntriesExceeded notification is
--                      generated when the number  of  DHCP  lease states
--                      entries on a given SAP reaches a user configurable
--                      upper limit given by tnSapTlsDhcpLeasePopulate."
--     ::= { tnSapTraps 6 }
--
-- tnSapTlsDHCPLeaseStateOverride NOTIFICATION-TYPE
--     OBJECTS {
--         tnCustId,
--         tnSvcId,
--         tnSvcVpnId,
--         tnSapPortId,
--         tnSapEncapValue,
--         tnTlsDhcpLseStateNewCiAddr,
--         tnTlsDhcpLseStateNewChAddr,
--         tnTlsDhcpLseStateOldCiAddr,
--         tnTlsDhcpLseStateOldChAddr
--     }
--     STATUS          obsolete
--     DESCRIPTION     "The tnSapTlsDHCPLeaseStateOverride notification is
--                      generated when an existing DHCP lease state is
--                      overridden by a new lease state which has the same
--                      IP address but a different MAC address."
--     ::= { tnSapTraps 7 }
--
-- tnSapTlsDHCPSuspiciousPcktRcvd NOTIFICATION-TYPE
--     OBJECTS {
--         tnCustId,
--         tnSvcId,
--         tnSvcVpnId,
--         tnSapPortId,
--         tnSapEncapValue,
--         tnTlsDhcpPacketProblem
--     }
--     STATUS          obsolete
--     DESCRIPTION     "The tnSapTlsDHCPSuspiciousPcktRcvd notification is
--                      generated when a DHCP packet is received with suspicious
--                      content."
--     ::= { tnSapTraps 8 }
--
-- tnSapDHCPLeaseEntriesExceeded NOTIFICATION-TYPE
--     OBJECTS {
--         tnCustId,
--         tnSvcId,
--         tnSvcVpnId,
--         tnSapPortId,
--         tnSapEncapValue,
--         tnSvcDhcpLseStateNewCiAddr,
--         tnSvcDhcpLseStateNewChAddr,
--         tnSvcDhcpClientLease
--     }
--     STATUS          current
--     DESCRIPTION     "The tnSapDHCPLeaseEntriesExceeded notification is generated
--                      when the number of DHCP lease state entries on a given SAP
--                      reaches a user configurable upper limit. This limit is
--                      given by tnSapTlsDhcpLeasePopulate for a TLS service and by
--                      TIMETRA-VRTR-MIB::vRtrIfDHCPLeasePopulate for an IES or
--                      VPRN service."
--     ::= { tnSapTraps 9 }
--
-- tnSapDHCPLseStateOverride NOTIFICATION-TYPE
--     OBJECTS {
--         tnCustId,
--         tnSvcId,
--         tnSvcVpnId,
--         tnSapPortId,
--         tnSapEncapValue,
--         tnSvcDhcpLseStateNewCiAddr,
--         tnSvcDhcpLseStateNewChAddr,
--         tnSvcDhcpLseStateOldCiAddr,
--         tnSvcDhcpLseStateOldChAddr
--     }
--     STATUS          current
--     DESCRIPTION     "The tnSapDHCPLseStateOverride notification is generated when
--                      an existing DHCP lease state is overridden by a new lease
--                      state which has the same IP address but a different MAC
--                      address."
--     ::= { tnSapTraps 10 }
--
-- tnSapDHCPSuspiciousPcktRcvd NOTIFICATION-TYPE
--     OBJECTS {
--         tnCustId,
--         tnSvcId,
--         tnSvcVpnId,
--         tnSapPortId,
--         tnSapEncapValue,
--         tnSvcDhcpPacketProblem
--     }
--     STATUS          current
--     DESCRIPTION     "The tnSapDHCPSuspiciousPcktRcvd notification is generated
--                      when a DHCP packet is received with suspicious content."
--     ::= { tnSapTraps 11 }
--
-- tnSapDHCPLseStatePopulateErr NOTIFICATION-TYPE
--     OBJECTS {
--         tnCustId,
--         tnSvcId,
--         tnSvcVpnId,
--         tnSapPortId,
--         tnSapEncapValue,
--         tnSvcDhcpLseStatePopulateError
--     }
--     STATUS          current
--     DESCRIPTION     "The tnSapDHCPLseStatePopulateErr notification indicates that
--                      the system was unable to update the DHCP Lease State table
--                      with the information contained in the DHCP ACK message.
--                      The DHCP ACK message has been discarded."
--     ::= { tnSapTraps 12 }
--
-- tnHostConnectivityLost NOTIFICATION-TYPE
--     OBJECTS {
--         tnCustId,
--         tnSvcId,
--         tnSvcVpnId,
--         tnSapPortId,
--         tnSapEncapValue,
--         tnHostConnectivityCiAddrType,
--         tnHostConnectivityCiAddr,
--         tnHostConnectivityChAddr
--     }
--     STATUS          current
--     DESCRIPTION     "The tnHostConnectivityLost notification indicates that
--                      the system lost the connectivity with the indicated host."
--     ::= { tnSapTraps 13 }
--
-- tnHostConnectivityRestored NOTIFICATION-TYPE
--     OBJECTS {
--         tnCustId,
--         tnSvcId,
--         tnSvcVpnId,
--         tnSapPortId,
--         tnSapEncapValue,
--         tnHostConnectivityCiAddrType,
--         tnHostConnectivityCiAddr,
--         tnHostConnectivityChAddr
--     }
--     STATUS          current
--     DESCRIPTION     "The tnHostConnectivityRestored notification indicates that
--                      the system has restored the connectivity with the
--                      indicated host."
--     ::= { tnSapTraps 14 }
--
-- tnSapReceivedProtSrcMac NOTIFICATION-TYPE
--     OBJECTS {
--         tnSvcId,
--         tnSapPortId,
--         tnSapEncapValue,
--         tnProtectedMacForNotify,
--         tnSapTlsRestProtSrcMacAction
--     }
--     STATUS          current
--     DESCRIPTION     "The tnSapReceivedProtSrcMac notification is generated when a
--                      protected source MAC is received on a TLS SAP with
--                      tnSapTlsRestProtSrcMac 'true', or if the TLS
--                      SAP belongs to an SHG with tlsShgRestProtSrcMac 'true'."
--     ::= { tnSapTraps 15 }
--
-- tnSapStaticHostDynMacConflict NOTIFICATION-TYPE
--     OBJECTS {
--         tnSvcId,
--         tnSapPortId,
--         tnSapEncapValue,
--         tnStaticHostDynamicMacIpAddress,
--         tnStaticHostDynamicMacConflict
--     }
--     STATUS          current
--     DESCRIPTION     "The tnSapStaticHostDynMacConflict notification indicates
--                      that the system is trying to learn a conflicting IP-only
--                      static host dynamic MAC address
--                      (tnSapStaticHostDynMacAddress)."
--     ::= { tnSapTraps 16 }
--
-- tnSapTlsMacMoveExceeded NOTIFICATION-TYPE
--     OBJECTS {
--         tnCustId,
--         tnSvcId,
--         tnSvcVpnId,
--         tnSapPortId,
--         tnSapEncapValue,
--         tnSapAdminStatus,
--         tnSapOperStatus,
--         tnSapTlsMacMoveRateExcdLeft,
--         tnSapTlsMacMoveNextUpTime,
--         tnSvcTlsMacMoveMaxRate,
--         tnSapTlsNotifyMacAddr
--     }
--     STATUS          current
--     DESCRIPTION     "The tnSapTlsMacMoveExceeded notification is generated
--                      when the SAP exceeds the TLS tnSvcTlsMacMoveMaxRate."
--     ::= { tnSapTraps 17 }
--
-- tnSapDHCPProxyServerError NOTIFICATION-TYPE
--     OBJECTS {
--         tnCustId,
--         tnSvcId,
--         tnSvcVpnId,
--         tnSapPortId,
--         tnSapEncapValue,
--         tnSvcDhcpProxyError
--     }
--     STATUS          current
--     DESCRIPTION     "The tnSapDHCPProxyServerError notification indicates that
--                      the system was unable to proxy DHCP requests."
--     ::= { tnSapTraps 18 }
--
-- tnSapDHCPCoAError NOTIFICATION-TYPE
--     OBJECTS {
--         tnCustId,
--         tnSvcId,
--         tnSvcVpnId,
--         tnSapPortId,
--         tnSapEncapValue,
--         tnSvcDhcpCoAError
--     }
--     STATUS          obsolete
--     DESCRIPTION     "The tnSapDHCPCoAError notification indicates that
--                      the system was unable to process a Change of Authorization
--                      (CoA) request from a Radius server."
--     ::= { tnSapTraps 19 }
--
-- tnSapDHCPSubAuthError NOTIFICATION-TYPE
--     OBJECTS {
--         tnCustId,
--         tnSvcId,
--         tnSvcVpnId,
--         tnSapPortId,
--         tnSapEncapValue,
--         tnSvcDhcpSubAuthError
--     }
--     STATUS          obsolete
--     DESCRIPTION     "The tnSapDHCPSubAuthError notification indicates that
--                      the system encountered a problem while trying to
--                      authenticate a subscriber."
--     ::= { tnSapTraps 20 }

-- tnSapPortStateChangeProcessed NOTIFICATION-TYPE
--     OBJECTS {
--         tnSapNotifyPortId
--     }
--     STATUS          current
--     DESCRIPTION     "The tnSapPortStateChangeProcessed notification indicates
--                      that the agent has finished processing an access port
--                      state change event, and that the operating status of
--                      all the affected SAP's has been updated accordingly.
--                      The value of the tnSapNotifyPortId object indicates the
--                      ID of the port that experienced the state change."
--     ::= { tnSapTraps 21 }

tnSapDHCPLseStateMobilityError NOTIFICATION-TYPE
    OBJECTS {
        tnCustId,
        tnSvcId,
        tnSvcVpnId,
        tnSapPortId,
        tnSapEncapValue
    }
    STATUS          current
    DESCRIPTION     "The tnSapDHCPLseStateMobilityError notification indicates
                     that the system was unable to perform a mobility check
                     for this lease state."
    ::= { tnSapTraps 22 }

-- tnSapCemPacketDefectAlarm NOTIFICATION-TYPE
--    OBJECTS {
--         tnCustId,
--         tnSvcVpnId,
--         tnSapCemReportAlarmStatus
--    }
--    STATUS            current
--    DESCRIPTION       "Generated when a CEM SAP alarm condition is detected.
--                       It is generated only when the packet error indicated
--                       by 'tnSapCemReportAlarmStatus' persists over a 3 second
--                       window."
--     ::= { tnSapTraps 23 }

-- tnSapCemPacketDefectAlarmClear NOTIFICATION-TYPE
--    OBJECTS {
--         tnCustId,
--         tnSvcVpnId,
--         tnSapCemReportAlarmStatus
--    }
--    STATUS            current
--    DESCRIPTION       "Generated when a CEM SAP alarm condition is cleared.
--                       It is generated only when the packet error indicated
--                       by 'tnSapCemReportAlarmStatus' no longer persists over
--                       a 10 second window."
--     ::= { tnSapTraps 24 }

-- tnMtnSapStateChanged NOTIFICATION-TYPE
--    OBJECTS {
--        tnSvcId,
--        tnSapPortId,
--        tnSapEncapValue,
--        tnMtnSapStatus
--    }
--    STATUS          current
--    DESCRIPTION     "The tnMtnSapStateChanged notification is generated when a
--                     Managed SAP is 'created', 'modified', or 'deleted', with the
--                     value of tnMtnSapStatus indicated which state it has entered."
--    ::= { tnSapTraps 25 }

-- tnMtnSapCreationFailure  NOTIFICATION-TYPE
--    OBJECTS {
--        tnCustId,
--        tnSvcId,
--        tnSvcVpnId,
--        tnSapPortId,
--        tnSapEncapValue,
--        svcManagedSapCreationError
--    }
--    STATUS          current
--    DESCRIPTION     "The trap tnMtnSapCreationFailure is sent whenever
--                     the system fails to create a managed SAP.
--                     The tnSvcId, tnSvcVpnId, tnSapPortId and tnSapEncapValue are
--                     those of the capturing SAP."
--    ::= { tnSapTraps 26 }

-- tnSapHostBGPPeeringSetupFailed NOTIFICATION-TYPE
--     OBJECTS {
--         tnCustId,
--         tnSvcId,
--         tnSvcVpnId,
--         tnSapPortId,
--         tnSapEncapValue,
--         tnSapBGPPeeringHostIpAddr,
--         tnSapBGPPeeringHostIpAddrType,
--         tnSapBGPPeeringVRtrID,
--         tnSapBGPPeeringAttrDiscarded,
--         tnSapBGPPeeringNotifDescription
--     }
--     STATUS          current
--     DESCRIPTION     "The tnSapHostBGPPeeringSetupFailed notification indicates
--                      that the system was unable to create a BGP neighbor
--                      and set up BGP peering for the given host."
--     ::= { tnSapTraps 27 }

-- ------------------------------------
-- TLS STP traps
-- ------------------------------------
tnTopologyChangeSapMajorState NOTIFICATION-TYPE
    OBJECTS {
        tnCustId,
        tnSvcId,
        tnSapPortId,
        tnSapEncapValue
    }
    STATUS         current
    DESCRIPTION    "The    tnTopologyChangeSapMajorState   notification    is
                    generated  when  a  SAP has transitioned its state from
                    learning  to  forwarding or from forwarding to blocking
                    or broken. The spanning tree topology has been modified
                    and   it   may   denote  loss  of  customer  access  or
                    redundancy.   Check   the   new  topology  against  the
                    provisioned  topology  to  determine  the  severity  of
                    connectivity loss."
    ::= { tnTstpTraps 1 }

tnNewRootSap NOTIFICATION-TYPE
    OBJECTS {
        tnCustId,
        tnSvcId,
        tnSapPortId,
        tnSapEncapValue
    }
    STATUS          current
    DESCRIPTION     "The  tnNewRootSap  notification is  generated  when  the
                     previous  root bridge has been aged out and a new root
                     bridge  has  been elected. A new root bridge creates a
                     new  spanning  tree topology and it may denote loss of
                     customer  access or redundancy. Check the new topology
                     against  the  provisioned  topology  to  determine the
                     severity of connectivity loss."
    ::= { tnTstpTraps 2 }

tnTopologyChangeSapState NOTIFICATION-TYPE
    OBJECTS {
        tnCustId,
        tnSvcId,
        tnSapPortId,
        tnSapEncapValue
    }
    STATUS          current
    DESCRIPTION     "The tnTopologyChangeSapState notification is   generated
                     when  a  SAP  has  transitioned  state  to blocking or
                     broken  from a state other than forwarding. This event
                     complements     what     is     not     covered     by
                     tnTopologyChangeSapMajorState.    The    spanning   tree
                     topology  has  been modified and it may denote loss of
                     customer  access or redundancy. Check the new topology
                     against the provisioned topology to determine severity
                     of connectivity loss."
    ::= { tnTstpTraps 5 }

tnReceivedTCN NOTIFICATION-TYPE
    OBJECTS {
        tnCustId,
        tnSvcId,
        tnSapPortId,
        tnSapEncapValue
    }
    STATUS          current
    DESCRIPTION     "The tnReceivedTCN notification is generated  when  a SAP
                     has received TCN from another bridge. This bridge will
                     either  have  its  configured  BPDU  with the topology
                     change  flag  set  if  it is a root bridge, or it will
                     pass  TCN  to  its root bridge. Eventually the address
                     aging  timer  for the forwarding database will be made
                     shorter  for  a  short  period of time. No recovery is
                     needed."
    ::= { tnTstpTraps 6 }

-- tnHigherPriorityBridge NOTIFICATION-TYPE
--     OBJECTS {
--         tnCustId,
--         tnSvcId,
--         tnSapPortId,
--         tnSapEncapValue,
--         tnCustomerBridgeId,
--         tnCustomerRootBridgeId
--     }
--     STATUS          current
--     DESCRIPTION     "The tnHigherPriorityBridge notification is generated when
--                      a  customer's device has been configured with a bridge
--                      priority  equal  to  zero. The SAP that the customer's
--                      device  is  connected  through will be blocked. Remove
--                      the  customer's  device  or reconfigure the customer's
--                      bridge priority with a value greater than zero."
--     ::= { tnTstpTraps 9 }
--
-- tnBridgedTLS NOTIFICATION-TYPE
--     OBJECTS {
--         tnCustId,
--         tnSvcId,
--         tnSapPortId,
--         tnSapEncapValue
--     }
--     STATUS          obsolete
--     DESCRIPTION     "The  tnBridgedTLS  notification  is  generated  when   a
--                      configuration  BPDU  has been received that identifies
--                      that  another TLS with a different VPNID is attempting
--                      to   bridge   with   this   TLS.   At  least  one  ESR
--                      participating  within  one  of the TLS that is locally
--                      connected must have an active VCP for this to be seen.
--                      The  SAP  that  the  configuration BPDU is received on
--                      will  be  blocked  to prevent the TLS to TLS bridging.
--                      Reconfigure  the  bridged  TLS  into  a  single TLS or
--                      remove the connectivity."
--     ::= { tnTstpTraps 10 }
--
-- tnSapEncapPVST NOTIFICATION-TYPE
--     OBJECTS {
--         tnCustId,
--         tnSvcId,
--         tnSapPortId,
--         tnSapEncapValue,
--         tnOtherBridgeId
--     }
--     STATUS          current
--     DESCRIPTION     "The tnSapEncapPVST  notification  is  generated when the
--                      SAP  receives  a BPDU that is PVST encapsulated, after
--                      having  received  BPDUs  that were 802.d encapsulated.
--                      The  SAP  BPDUs  will  also  be  PVST encapsulated. No
--                      recovery is needed."
--     ::= { tnTstpTraps 11 }
--
-- tnSapEncapDot1d NOTIFICATION-TYPE
--     OBJECTS {
--         tnCustId,
--         tnSvcId,
--         tnSapPortId,
--         tnSapEncapValue,
--         tnOtherBridgeId
--     }
--     STATUS          current
--     DESCRIPTION     "The  tnSapEncapDot1d  notification is generated when the
--                      SAP  receives a BPDU that is 802.1d encapsulated after
--                      having received BPDUs that were PVST encapsulated. The
--                      SAP   BPDUs  will  also  be  802.1d  encapsulated.  No
--                      recovery is needed."
--     ::= { tnTstpTraps 12 }
--
-- tnSapReceiveOwnBpdu NOTIFICATION-TYPE
--     OBJECTS {
--         tnCustId,
--         tnSvcId,
--         tnSapPortId,
--         tnSapEncapValue,
--         tnOtherBridgeId
--     }
--     STATUS          obsolete
--     DESCRIPTION     "The tnSapReceiveOwnBpdu notification is generated when the
--                      SAP STP received it's own BPDU."
--     ::= { tnTstpTraps 13 }

tnSapActiveProtocolChange NOTIFICATION-TYPE
    OBJECTS {
        tnCustId,
        tnSvcId,
        tnSapPortId,
        tnSapEncapValue,
        tnSapTlsStpOperProtocol
    }
    STATUS          current
    DESCRIPTION     "The tnSapActiveProtocolChange notification is generated
                     when  the  spanning  tree protocol on this SAP changes
                     from  rstp  to  stp  or  vise  versa.  No  recovery is
                     needed."
    ::= { tnTstpTraps 30 }

tnStpRootGuardViolation NOTIFICATION-TYPE
    OBJECTS {
        tnSvcId,
        tnSapPortId,
        tnSapEncapValue,
        tnSapTlsStpRootGuardViolation
    }
    STATUS          current
    DESCRIPTION     "The tnStpRootGuardViolation notification is
                     generated when a SAP which has root-guard configured is
                     trying to become root (has a better STP priority vector).
                     The SAP will become alternate and traffic will be blocked."
    ::= { tnTstpTraps 35 }

tnSapStpExcepCondStateChng NOTIFICATION-TYPE
    OBJECTS {
        tnCustId,
        tnSvcId,
        tnSapPortId,
        tnSapEncapValue,
        tnSapTlsStpException
    }
    STATUS          current
    DESCRIPTION     "The tnSapStpExcepCondStateChng notification is
                     generated when the value of the object tnSapTlsStpException
                     has changed, i.e. when the exception condition
                     changes on the indicated SAP."
    ::= { tnTstpTraps 37 }

-- ----------------------------------------------------------------------------
-- Conformance Information
-- ----------------------------------------------------------------------------
-- tnSapCompliances  OBJECT IDENTIFIER ::= { tnSapConformance 1 }
-- tnSapGroups       OBJECT IDENTIFIER ::= { tnSapConformance 2 }

-- ----------------------------------------------
-- Compliance Statements
-- ----------------------------------------------
-- tnSap7450V6v0Compliance MODULE-COMPLIANCE
--    STATUS  obsolete
--    DESCRIPTION
--        "The compliance statement for management of services SAPs
--         on Nokia 7450 ESS series systems."
--    MODULE  this module
--        MANDATORY-GROUPS
--        {
--           tnSapV6v0Group,
--           tnSapTlsV6v0Group,
--           tnSapBaseV6v0Group,
--           tnSapAtmV6v0Group,
--           tnSapQosV6v0Group,
--           tnSapStaticHostV6v0Group,
--           tnSapPortIdV6v0Group,
--           tnSapSubMgmtV6v0Group,
--           tnSapMstiV6v0Group,
--           tnSapIppipeV6v0Group,
--           tnSapPolicyV6v0Group,
--           tnSapL2ptV6v0Group,
--           tnSapMtnSapV6v0Group,
--           tnSapHsmdaV6v0Group,
--           tnSapNotifyGroup,
--           tnSapNotificationObjV6v0Group,
--           tnSapCemNotificationV6v0Group,
--           tmnxTlsMtnSapPppoeV6v0Group,
--           tnSapCemV6v0Group
--           tnSapIpV6FilterV6v0Group
--           tnSapDhcpV6v0Group,
--           tnSapMrpV6v0Group,
--           tnSapBsxV6v0Group
--       }
--    ::= { tnSapCompliances 100 }

-- tnSap7750V6v0Compliance MODULE-COMPLIANCE
--    STATUS  obsolete
--    DESCRIPTION
--        "The compliance statement for management of services SAPs
--         on Nokia 7750 SR series systems."
--    MODULE  this module
--        MANDATORY-GROUPS
--        {
--           tnSapV6v0Group,
--           tnSapTlsV6v0Group,
--           tnSapBaseV6v0Group,
--           tnSapAtmV6v0Group,
--           tnSapQosV6v0Group,
--           tnSapStaticHostV6v0Group,
--           tnSapPortIdV6v0Group,
--           tnSapSubMgmtV6v0Group,
--           tnSapMstiV6v0Group,
--           tnSapIppipeV6v0Group,
--           tnSapPolicyV6v0Group,
--           tnSapL2ptV6v0Group,
--           tnSapMtnSapV6v0Group,
--           tnSapHsmdaV6v0Group,
--           tnSapNotifyGroup,
--           tnSapNotificationObjV6v0Group,
--           tnSapCemNotificationV6v0Group,
--           tmnxTlsMtnSapPppoeV6v0Group,
--           tnSapCemV6v0Group,
--           tnSapIpV6FilterV6v0Group,
--           tnSapDhcpV6v0Group,
--           tnSapMrpV6v0Group,
--           tnSapBsxV6v0Group
--       }
--    ::= { tnSapCompliances 101 }

-- tnSap7710V6v0Compliance MODULE-COMPLIANCE
--    STATUS  obsolete
--    DESCRIPTION
--        "The compliance statement for management of services SAPs
--         on Nokia 7710 SR series systems."
--    MODULE  this module
--        MANDATORY-GROUPS
--        {
--           tnSapV6v0Group,
--           tnSapTlsV6v0Group,
--           tnSapBaseV6v0Group,
--           tnSapAtmV6v0Group,
--           tnSapQosV6v0Group,
--           tnSapStaticHostV6v0Group,
--           tnSapPortIdV6v0Group,
--           tnSapSubMgmtV6v0Group,
--           tnSapMstiV6v0Group,
--           tnSapIppipeV6v0Group,
--           tnSapPolicyV6v0Group,
--           tnSapL2ptV6v0Group,
--           tnSapMtnSapV6v0Group,
--           tnSapHsmdaV6v0Group,
--           tnSapNotifyGroup,
--           tnSapNotificationObjV6v0Group,
--           tnSapCemNotificationV6v0Group,
--           tmnxTlsMtnSapPppoeV6v0Group,
--           tnSapCemV6v0Group,
--           tnSapIpV6FilterV6v0Group,
--           tnSapDhcpV6v0Group,
--           tnSapMrpV6v0Group
--       }
--    ::= { tnSapCompliances 102 }

-- tnSap7450V6v1Compliance MODULE-COMPLIANCE
--    STATUS  obsolete
--    DESCRIPTION
--        "The compliance statement for management of services SAPs
--         on Nokia 7450 ESS series systems."
--    MODULE  this module
--        MANDATORY-GROUPS
--        {
--           tnSapV6v0Group,
--           tnSapTlsV6v1Group,
--           tnSapBaseV6v0Group,
--           tnSapAtmV6v0Group,
--           tnSapQosV6v0Group,
--           tnSapStaticHostV6v1Group,
--           tnSapPortIdV6v0Group,
--           tnSapSubMgmtV6v0Group,
--           tnSapMstiV6v0Group,
--           tnSapIppipeV6v0Group,
--           tnSapPolicyV6v0Group,
--           tnSapL2ptV6v0Group,
--           tnSapMtnSapV6v0Group,
--           tnSapMtnSapV6v1Group,
--           tnSapHsmdaV6v0Group,
--           tnSapNotifyGroup,
--           tnSapNotificationObjV6v0Group,
--           tnSapCemNotificationV6v0Group,
--           tmnxTlsMtnSapPppoeV6v0Group,
--           tnSapCemV6v0Group
--           tnSapIpV6FilterV6v0Group
--           tnSapDhcpV6v0Group,
--           tnSapMrpV6v0Group,
--           tnSapBsxV6v0Group
--       }
--    ::= { tnSapCompliances 103 }

-- tnSap7750V6v1Compliance MODULE-COMPLIANCE
--    STATUS  obsolete
--    DESCRIPTION
--        "The compliance statement for management of services SAPs
--         on Nokia 7750 SR series systems."
--    MODULE  this module
--        MANDATORY-GROUPS
--        {
--           tnSapV6v0Group,
--           tnSapTlsV6v1Group,
--           tnSapBaseV6v0Group,
--           tnSapAtmV6v0Group,
--           tnSapQosV6v0Group,
--           tnSapStaticHostV6v1Group,
--           tnSapPortIdV6v0Group,
--           tnSapSubMgmtV6v0Group,
--           tnSapMstiV6v0Group,
--           tnSapIppipeV6v0Group,
--           tnSapPolicyV6v0Group,
--           tnSapL2ptV6v0Group,
--           tnSapMtnSapV6v0Group,
--           tnSapMtnSapV6v1Group,
--           tnSapHsmdaV6v0Group,
--           tnSapNotifyGroup,
--           tnSapNotificationObjV6v0Group,
--           tnSapCemNotificationV6v0Group,
--           tmnxTlsMtnSapPppoeV6v0Group,
--           tnSapCemV6v0Group,
--           tnSapIpV6FilterV6v0Group,
--           tnSapDhcpV6v0Group,
--           tnSapMrpV6v0Group,
--           tnSapBsxV6v0Group
--       }
--    ::= { tnSapCompliances 104 }

-- tnSap7710V6v1Compliance MODULE-COMPLIANCE
--    STATUS  obsolete
--    DESCRIPTION
--        "The compliance statement for management of services SAPs
--         on Nokia 7710 SR series systems."
--    MODULE  this module
--        MANDATORY-GROUPS
--        {
--           tnSapV6v0Group,
--           tnSapTlsV6v1Group,
--           tnSapBaseV6v0Group,
--           tnSapAtmV6v0Group,
--           tnSapQosV6v0Group,
--           tnSapStaticHostV6v1Group,
--           tnSapPortIdV6v0Group,
--           tnSapSubMgmtV6v0Group,
--           tnSapMstiV6v0Group,
--           tnSapIppipeV6v0Group,
--           tnSapPolicyV6v0Group,
--           tnSapL2ptV6v0Group,
--           tnSapMtnSapV6v0Group,
--           tnSapMtnSapV6v1Group,
--           tnSapHsmdaV6v0Group,
--           tnSapNotifyGroup,
--           tnSapNotificationObjV6v0Group,
--           tnSapCemNotificationV6v0Group,
--           tmnxTlsMtnSapPppoeV6v0Group,
--           tnSapCemV6v0Group,
--           tnSapIpV6FilterV6v0Group,
--           tnSapDhcpV6v0Group,
--           tnSapMrpV6v0Group
--           tnSapBsxV6v0Group           no Application Assurance on 7710
--       }
--    ::= { tnSapCompliances 105 }

-- tnSap7450V7v0Compliance MODULE-COMPLIANCE
--    STATUS  current
--    DESCRIPTION
--        "The compliance statement for management of services SAPs
--         on Nokia 7450 ESS series systems."
--    MODULE  this module
--        MANDATORY-GROUPS
--        {
--           tnSapV7v0Group,
--           tnSapTlsV6v1Group,
--           tnSapBaseV6v0Group,
--           tnSapQosV6v0Group,
--           tnSapStaticHostV6v1Group,
--           tnSapPortIdV6v0Group,
--           tnSapSubMgmtV6v0Group,
--           tnSapMstiV6v0Group,
--           tnSapPolicyV6v0Group,
--           tnSapL2ptV6v0Group,
--           tnSapMtnSapV6v0Group,
--           tnSapMtnSapV6v1Group,
--           tnSapHsmdaV6v0Group,
--           tnSapNotifyGroup,
--           tnSapCemNotificationV6v0Group,
--           tmnxTlsMtnSapPppoeV6v0Group,
--           tnSapCemV6v0Group
--           tnSapIpV6FilterV6v0Group
--           tnSapDhcpV6v0Group,
--           tnSapMrpV6v0Group,
--           tnSapBsxV7v0Group,
--           tnSapArpHostGroup,
--           tnSapIgmpTrkGroup,
--           tnSapAtmV7v0Group,
--           tnSapIpipeV7v0Group,
--           tnSapPbbGroup,
--           tmnxSapTlsV7v0Group
--       }
--    ::= { tnSapCompliances 106 }

-- tnSap7750V7v0Compliance MODULE-COMPLIANCE
--    STATUS  current
--    DESCRIPTION
--        "The compliance statement for management of services SAPs
--         on Nokia 7750 SR series systems."
--    MODULE  this module
--        MANDATORY-GROUPS
--        {
--           tnSapV7v0Group,
--           tnSapTlsV6v1Group,
--           tnSapBaseV6v0Group,
--           tnSapAtmV6v0Group,
--           tnSapQosV6v0Group,
--           tnSapStaticHostV6v1Group,
--           tnSapPortIdV6v0Group,
--           tnSapSubMgmtV6v0Group,
--           tnSapMstiV6v0Group,
--           tnSapPolicyV6v0Group,
--           tnSapL2ptV6v0Group,
--           tnSapMtnSapV6v0Group,
--           tnSapMtnSapV6v1Group,
--           tnSapHsmdaV6v0Group,
--           tnSapNotifyGroup,
--           tnSapCemNotificationV6v0Group,
--           tmnxTlsMtnSapPppoeV6v0Group,
--           tnSapCemV6v0Group,
--           tnSapIpV6FilterV6v0Group,
--           tnSapDhcpV6v0Group,
--           tnSapMrpV6v0Group,
--           tnSapBsxV7v0Group,
--           tnSapArpHostGroup,
--           tnSapIgmpTrkGroup,
--           tnSapFrGroup,
--           tnSapIpipeV7v0Group,
--           tnSapPbbGroup,
--           tmnxSapTlsV7v0Group
--       }
--    ::= { tnSapCompliances 107 }

-- tnSap7710V7v0Compliance MODULE-COMPLIANCE
--    STATUS  current
--    DESCRIPTION
--        "The compliance statement for management of services SAPs
--         on Nokia 7710 SR series systems."
--    MODULE  this module
--        MANDATORY-GROUPS
--        {
--           tnSapV7v0Group,
--           tnSapTlsV6v1Group,
--           tnSapBaseV6v0Group,
--           tmnxSapAtmV6v0Group,
--           tnSapQosV6v0Group,
--           tnSapStaticHostV6v1Group,
--           tnSapPortIdV6v0Group,
--           tnSapSubMgmtV6v0Group,
--           tnSapMstiV6v0Group,
--           tnSapPolicyV6v0Group,
--           tnSapL2ptV6v0Group,
--           tnSapMtnSapV6v0Group,
--           tnSapMtnSapV6v1Group,
--           tnSapHsmdaV6v0Group,
--           tnSapNotifyGroup,
--           tnSapCemNotificationV6v0Group,
--           tmnxTlsMtnSapPppoeV6v0Group,
--           tnSapCemV6v0Group,
--           tnSapIpV6FilterV6v0Group,
--           tnSapDhcpV6v0Group,
--           tnSapMrpV6v0Group,
--           tnSapBsxV7v0Group           no Application Assurance on 7710
--           tnSapArpHostGroup,
--           tnSapIgmpTrkGroup,
--           tnSapFrGroup,
--           tnSapIpipeV7v0Group,
--           tnSapPbbGroup,
--           tmnxSapTlsV7v0Group
--       }
--    ::= { tnSapCompliances 108 }

-- ----------------------
-- SAP Group
-- ----------------------

-- tnSapV6v0Group OBJECT-GROUP
--    OBJECTS {
--      tnSapNumEntries,
--      tnSapPortId,
--      tnSapEncapValue,
--      tnSapRowStatus,
--      tnSapType,
--      tnSapDescription,
--      tnSapAdminStatus,
--      tnSapOperStatus,
--      tnSapIngressQosPolicyId,
--      tnSapIngressMacFilterId,
--      tnSapIngressIpFilterId,
--      tnSapIngressVlanTranslationId,
--      tnSapEgressQosPolicyId,
--      tnSapEgressMacFilterId,
--      tnSapEgressIpFilterId,
--      tnSapMirrorStatus,
--      tnSapIesIfIndex,
--      tnSapLastMgmtChange,
--      tnSapCollectAcctStats,
--      tnSapAccountingPolicyId,
--      tnSapVpnId,
--      tnSapCustId,
--      tnSapCustMultSvcSite,
--      tnSapIngressQosSchedulerPolicy,
--      tnSapEgressQosSchedulerPolicy,
--      tnSapSplitHorizonGrp,
--      tnSapIngressSharedQueuePolicy,
--      tnSapIngressMatchQinQDot1PBits,
--      tnSapOperFlags,
--      tnSapLastStatusChange,
--      tnSapAntiSpoofing,
--      tnSapTodSuite,
--      tnSapIngUseMultipointShared,
--      tnSapEgressQinQMarkTopOnly,
--      tnSapEgressAggRateLimit,
--      tnSapEndPoint,
--      tnSapIngressVlanTranslation,
--      tnSapSubType,
--      tnSapCpmProtPolicyId,
--      tnSapCpmProtMonitorMac,
--      tnSapEgressFrameBasedAccounting,
--      tnSapEthernetLLFAdminStatus,
--      tnSapEthernetLLFOperStatus,
--      tnSapTlsMvplsRowStatus,
--      tnSapAntiSpoofIpAddress,
--      tnSapAntiSpoofMacAddress,
--      tnSapEgressFrameBasedAccounting
--    }
--    STATUS      obsolete
--    DESCRIPTION
--        "The group of objects supporting management of Sap
--         general capabilities on Nokia 7x50 SR series systems."
--    ::= { tnSapGroups 100 }


-- tnSapTlsV6v0Group OBJECT-GROUP
--    OBJECTS {
--      tnSapTlsStpAdminStatus,
--      tnSapTlsStpPriority,
--      tnSapTlsStpPortNum,
--      tnSapTlsStpPathCost,
--      tnSapTlsStpRapidStart,
--      tnSapTlsStpBpduEncap,
--      tnSapTlsStpPortState,
--      tnSapTlsStpDesignatedBridge,
--      tnSapTlsStpDesignatedPort,
--      tnSapTlsStpForwardTransitions,
--      tnSapTlsStpInConfigBpdus,
--      tnSapTlsStpInTcnBpdus,
--      tnSapTlsStpInBadBpdus,
--      tnSapTlsStpOutConfigBpdus,
--      tnSapTlsStpOutTcnBpdus,
--      tnSapTlsStpOperBpduEncap,
--      tnSapTlsVpnId,
--      tnSapTlsCustId,
--      tnSapTlsMacAddressLimit,
--      tnSapTlsNumMacAddresses,
--      tnSapTlsNumStaticMacAddresses,
--      tnSapTlsMacLearning,
--      tnSapTlsMacAgeing,
--      tnSapTlsStpOperEdge,
--      tnSapTlsStpAdminPointToPoint,
--      tnSapTlsStpPortRole,
--      tnSapTlsStpAutoEdge,
--      tnSapTlsStpOperProtocol,
--      tnSapTlsStpInRstBpdus,
--      tnSapTlsStpOutRstBpdus,
--      tnSapTlsLimitMacMove,
--      tnSapTlsMacPinning,
--      tnSapTlsDiscardUnknownSource,
--      tnSapTlsMvplsPruneState,
--      tnSapTlsMvplsMgmtService,
--      tnSapTlsMvplsMgmtPortId,
--      tnSapTlsMvplsMgmtEncapValue,
--      tnSapTlsArpReplyAgent,
--      tnSapTlsStpException,
--      tnSapTlsAuthenticationPolicy,
--      tnSapTlsL2ptTermination,
--      tnSapTlsBpduTranslation,
--      tnSapTlsStpRootGuard,
--      tnSapTlsStpInsideRegion,
--      tnSapTlsEgressMcastGroup,
--      tnSapTlsStpInMstBpdus,
--      tnSapTlsStpOutMstBpdus,
--      tnSapTlsRestProtSrcMac,
--      tnSapTlsRestProtSrcMacAction,
--      tnSapTlsRestUnprotDstMac,
--      tnSapTlsStpRxdDesigBridge,
--      tnSapTlsStpRootGuardViolation,
--      tnSapTlsShcvAction,
--      tnSapTlsShcvSrcIp,
--      tnSapTlsShcvSrcMac,
--      tnSapTlsShcvInterval,
--      tnSapTlsMvplsMgmtMsti,
--      tnSapTlsMacMoveNextUpTime,
--      tnSapTlsMacMoveRateExcdLeft,
--      tnSapTlsL2ptForceBoundary,
--      tnSapTlsLimitMacMoveLevel,
--      tnSapTlsBpduTransOper,
--      tnSapTlsDefMtnSapPolicy,
--      tnSapTlsL2ptProtocols,
--      tnSapTlsL2ptForceProtocols,
--      tnSapTlsDhcpMtnSapTrigger,
--      tnSapTlsDhcpProxyLeaseTime,
--      tnSapTlsDhcpRemoteId,
--      tnSapTlsMrpJoinTime,
--      tnSapTlsMrpLeaveTime,
--      tnSapTlsMrpLeaveAllTime,
--      tnSapTlsMrpPeriodicTime,
--      tnSapTlsMrpPeriodicEnabled
--      }
--    STATUS      obsolete
--    DESCRIPTION
--        "The group of objects supporting management of Sap
--         TLS capabilities on Nokia 7x50 SR series systems."
--    ::= { tnSapGroups 101 }

-- tnSapAtmV6v0Group OBJECT-GROUP
--    OBJECTS {
--      tnSapAtmEncapsulation,
--      tnSapAtmIngressTrafficDescIndex,
--      tnSapAtmEgressTrafficDescIndex,
--      tnSapAtmOamAlarmCellHandling,
--      tnSapAtmOamTerminate,
--      tnSapAtmOamPeriodicLoopback,
--      tnSapAtmLLFAdminStatus,
--      tnSapAtmLLFOperStatus
--      }
--    STATUS      current
--    DESCRIPTION
--        "The group of objects supporting management of Sap
--         ATM capabilities on Nokia 7x50 SR series systems."
--    ::= { tnSapGroups 102 }

-- tnSapBaseV6v0Group OBJECT-GROUP
--    OBJECTS {
--      tnSapBaseStatsIngressPchipDroppedPackets,
--      tnSapBaseStatsIngressPchipDroppedOctets,
--      tnSapBaseStatsIngressPchipOfferedHiPrioPackets,
--      tnSapBaseStatsIngressPchipOfferedHiPrioOctets,
--      tnSapBaseStatsIngressPchipOfferedLoPrioPackets,
--      tnSapBaseStatsIngressPchipOfferedLoPrioOctets,
--      tnSapBaseStatsIngressQchipDroppedHiPrioPackets,
--      tnSapBaseStatsIngressQchipDroppedHiPrioOctets,
--      tnSapBaseStatsIngressQchipDroppedLoPrioPackets,
--      tnSapBaseStatsIngressQchipDroppedLoPrioOctets,
--      tnSapBaseStatsIngressQchipForwardedInProfPackets,
--      tnSapBaseStatsIngressQchipForwardedInProfOctets,
--      tnSapBaseStatsIngressQchipForwardedOutProfPackets,
--      tnSapBaseStatsIngressQchipForwardedOutProfOctets,
--      tnSapBaseStatsEgressQchipDroppedInProfPackets,
--      tnSapBaseStatsEgressQchipDroppedInProfOctets,
--      tnSapBaseStatsEgressQchipDroppedOutProfPackets,
--      tnSapBaseStatsEgressQchipDroppedOutProfOctets,
--      tnSapBaseStatsEgressQchipForwardedInProfPackets,
--      tnSapBaseStatsEgressQchipForwardedInProfOctets,
--      tnSapBaseStatsEgressQchipForwardedOutProfPackets,
--      tnSapBaseStatsEgressQchipForwardedOutProfOctets,
--      tnSapBaseStatsCustId,
--      tnSapBaseStatsIngressPchipOfferedUncoloredPackets,
--      tnSapBaseStatsIngressPchipOfferedUncoloredOctets,
--      tnSapBaseStatsAuthenticationPktsDiscarded,
--      tnSapBaseStatsAuthenticationPktsSuccess,
--      tnSapBaseStatsLastClearedTime
--      }
--    STATUS      current
--    DESCRIPTION
--        "The group of objects supporting management of Sap
--         Base capabilities on Nokia 7x50 SR series systems."
--    ::= { tnSapGroups 103 }

-- tnSapQosV6v0Group OBJECT-GROUP
--    OBJECTS {
--      tnSapIngQosQueueId,
--      tnSapIngQosQueueStatsOfferedHiPrioPackets,
--      tnSapIngQosQueueStatsDroppedHiPrioPackets,
--      tnSapIngQosQueueStatsOfferedLoPrioPackets,
--      tnSapIngQosQueueStatsDroppedLoPrioPackets,
--      tnSapIngQosQueueStatsOfferedHiPrioOctets,
--      tnSapIngQosQueueStatsDroppedHiPrioOctets,
--      tnSapIngQosQueueStatsOfferedLoPrioOctets,
--      tnSapIngQosQueueStatsDroppedLoPrioOctets,
--      tnSapIngQosQueueStatsForwardedInProfPackets,
--      tnSapIngQosQueueStatsForwardedOutProfPackets,
--      tnSapIngQosQueueStatsForwardedInProfOctets,
--      tnSapIngQosQueueStatsForwardedOutProfOctets,
--      tnSapIngQosCustId,
--      tnSapIngQosQueueStatsUncoloredPacketsOffered,
--      tnSapIngQosQueueStatsUncoloredOctetsOffered,
--      tnSapEgrQosQueueId,
--      tnSapEgrQosQueueStatsForwardedInProfPackets,
--      tnSapEgrQosQueueStatsDroppedInProfPackets,
--      tnSapEgrQosQueueStatsForwardedOutProfPackets,
--      tnSapEgrQosQueueStatsDroppedOutProfPackets,
--      tnSapEgrQosQueueStatsForwardedInProfOctets,
--      tnSapEgrQosQueueStatsDroppedInProfOctets,
--      tnSapEgrQosQueueStatsForwardedOutProfOctets,
--      tnSapEgrQosQueueStatsDroppedOutProfOctets,
--      tnSapEgrQosCustId,
--      tnSapIngQosSchedStatsForwardedPackets,
--      tnSapIngQosSchedStatsForwardedOctets,
--      tnSapIngQosSchedCustId,
--      tnSapEgrQosSchedStatsForwardedPackets,
--      tnSapEgrQosSchedStatsForwardedOctets,
--      tnSapEgrQosSchedCustId,

--      tnSapIngQosQRowStatus,
--      tnSapIngQosQLastMgmtChange,
--      tnSapIngQosQOverrideFlags,
--      tnSapIngQosQCBS,
--      tnSapIngQosQMBS,
--      tnSapIngQosQHiPrioOnly,
--      tnSapIngQosQCIRAdaptation,
--      tnSapIngQosQPIRAdaptation,
--      tnSapIngQosQAdminPIR,
--      tnSapIngQosQAdminCIR,
--      tnSapEgrQosQRowStatus,
--      tnSapEgrQosQLastMgmtChange,
--      tnSapEgrQosQOverrideFlags,
--      tnSapEgrQosQCBS,
--      tnSapEgrQosQMBS,
--      tnSapEgrQosQHiPrioOnly,
--      tnSapEgrQosQCIRAdaptation,
--      tnSapEgrQosQPIRAdaptation,
--      tnSapEgrQosQAdminPIR,
--      tnSapEgrQosQAdminCIR,
--      tnSapEgrQosQAvgOverhead,
--      tnSapIngQosSRowStatus,
--      tnSapIngQosSLastMgmtChange,
--      tnSapIngQosSOverrideFlags,
--      tnSapIngQosSPIR,
--      tnSapIngQosSCIR,
--      tnSapIngQosSSummedCIR,
--      tnSapEgrQosSRowStatus,
--      tnSapEgrQosSLastMgmtChange,
--      tnSapEgrQosSOverrideFlags,
--      tnSapEgrQosSPIR,
--      tnSapEgrQosSCIR,
--      tnSapEgrQosSSummedCIR
--      }
--    STATUS      current
--    DESCRIPTION
--        "The group of objects supporting management of Sap
--         Ingress/Egress QoS capabilities on Nokia 7x50 SR series systems."
--    ::= { tnSapGroups 104 }

-- tnSapStaticHostV6v0Group OBJECT-GROUP
--    OBJECTS {
--      tnSapStaticHostRowStatus,
--      tnSapStaticHostSubscrIdent,
--      tnSapStaticHostSubProfile,
--      tnSapStaticHostSlaProfile,
--      tnSapStaticHostShcvOperState,
--      tnSapStaticHostShcvChecks,
--      tnSapStaticHostShcvReplies,
--      tnSapStaticHostShcvReplyTime,
--      tnSapStaticHostDynMacAddress,
--      tnSapStaticHostRetailerSvcId,
--      tnSapStaticHostRetailerIf,
--      tnSapStaticHostFwdingState,
--      tnSapStaticHostAncpString,
--      tnSapStaticHostSubIdIsSapId,
--      tnSapStaticHostIntermediateDestId
--      }
--    STATUS      obsolete
--    DESCRIPTION
--        "The group of objects supporting management of Sap
--         static host capabilities on Nokia 7x50 SR series systems."
--    ::= { tnSapGroups 105 }

-- tnSapStaticHostV6v1Group OBJECT-GROUP
--    OBJECTS {
--      tnSapStaticHostRowStatus,
--      tnSapStaticHostSubscrIdent,
--      tnSapStaticHostSubProfile,
--      tnSapStaticHostSlaProfile,
--      tnSapStaticHostShcvOperState,
--      tnSapStaticHostShcvChecks,
--      tnSapStaticHostShcvReplies,
--      tnSapStaticHostShcvReplyTime,
--      tnSapStaticHostDynMacAddress,
--      tnSapStaticHostRetailerSvcId,
--      tnSapStaticHostRetailerIf,
--      tnSapStaticHostFwdingState,
--      tnSapStaticHostAncpString,
--      tnSapStaticHostSubIdIsSapId,
--      tnSapStaticHostIntermediateDestId,
--      tnSapStaticHostAdminStatus,
--      tnSapStaticHostMRtTblLastChgd,
--      tnSapStaticHostMRtRowStatus,
--      tnSapStaticHostMRtLastMgmtChange,
--      tnSapStaticHostMRtStatus
--      }
--    STATUS      current
--    DESCRIPTION
--        "The group of objects supporting management of Sap
--         static host capabilities on Nokia 7x50 SR series systems."
--    ::= { tnSapGroups 121 }


-- tnSapDhcpV6v0Group OBJECT-GROUP
--    OBJECTS {
--      tnSapTlsDhcpAdminState,
--      tnSapTlsDhcpDescription,
--      tnSapTlsDhcpSnoop,
--      tnSapTlsDhcpLeasePopulate,
--      tnSapTlsDhcpOperLeasePopulate,
--      tnSapTlsDhcpInfoAction,
--      tnSapTlsDhcpCircuitId,
--      tnSapTlsDhcpRemoteIdString,
--      tnSapTlsDhcpProxyAdminState,
--      tnSapTlsDhcpProxyServerAddr,
--      tnSapTlsDhcpProxyLTRadiusOverride,
--      tnSapTlsDhcpVendorIncludeOptions,
--      tnSapTlsDhcpVendorOptionString,
--      tnSapTlsDhcpStatsClntSnoopdPckts,
--      tnSapTlsDhcpStatsSrvrSnoopdPckts,
--      tnSapTlsDhcpStatsClntForwdPckts,
--      tnSapTlsDhcpStatsSrvrForwdPckts,
--      tnSapTlsDhcpStatsClntDropdPckts,
--      tnSapTlsDhcpStatsSrvrDropdPckts,
--      tnSapTlsDhcpStatsClntProxRadPckts,
--      tnSapTlsDhcpStatsClntProxLSPckts,
--      tnSapTlsDhcpStatsGenReleasePckts,
--      tnSapTlsDhcpStatsGenForceRenPckts,
--      tnSapDhcpOperLeasePopulate
--      }
--    STATUS      current
--    DESCRIPTION
--        "The group of objects supporting management of Sap
--         TLS DHCP capabilities on Nokia 7x50 SR series systems."
--    ::= { tnSapGroups 106 }


-- tnSapPortIdV6v0Group OBJECT-GROUP
--    OBJECTS {
--      tnSapPortIdIngQosSchedFwdPkts,
--      tnSapPortIdIngQosSchedFwdOctets,
--      tnSapPortIdIngQosSchedCustId,
--      tnSapPortIdEgrQosSchedFwdPkts,
--      tnSapPortIdEgrQosSchedFwdOctets,
--      tnSapPortIdEgrQosSchedCustId
--      }
--    STATUS      current
--    DESCRIPTION
--        "The group of objects supporting management of Sap
--         Port ID capabilities on Nokia 7x50 SR series systems."
--    ::= { tnSapGroups 107 }


-- tnSapSubMgmtV6v0Group OBJECT-GROUP
--    OBJECTS {
--      tnSapSubMgmtAdminStatus,
--      tnSapSubMgmtDefSubProfile,
--      tnSapSubMgmtDefSlaProfile,
--      tnSapSubMgmtSubIdentPolicy,
--      tnSapSubMgmtSubscriberLimit,
--      tnSapSubMgmtProfiledTrafficOnly,
--      tnSapSubMgmtNonSubTrafficSubIdent,
--      tnSapSubMgmtNonSubTrafficSubProf,
--      tnSapSubMgmtNonSubTrafficSlaProf,
--      tnSapSubMgmtMacDaHashing,
--      tnSapSubMgmtDefSubIdent,
--      tnSapSubMgmtDefSubIdentString
--      }
--    STATUS      current
--    DESCRIPTION
--        "The group of objects supporting management of Sap
--         Sub-management capabilities on Nokia 7x50 SR series systems."
--    ::= { tnSapGroups 108 }


-- tnSapMstiV6v0Group OBJECT-GROUP
--    OBJECTS {
--      tnSapTlsMstiPriority,
--      tnSapTlsMstiPathCost,
--      tnSapTlsMstiLastMgmtChange,
--      tnSapTlsMstiPortRole,
--      tnSapTlsMstiPortState,
--      tnSapTlsMstiDesignatedBridge,
--      tnSapTlsMstiDesignatedPort
--      }
--    STATUS      current
--    DESCRIPTION
--        "The group of objects supporting management of Sap
--         TLS MSTI capabilities on Nokia 7x50 SR series systems."
--    ::= { tnSapGroups 109 }


-- tnSapIppipeV6v0Group OBJECT-GROUP
--    OBJECTS {
--      tnSapIpipeCeInetAddress,
--      tnSapIpipeCeInetAddressType,
--      tnSapIpipeMacRefreshInterval,
--      tnSapIpipeMacAddress,
--      tnSapIpipeArpedMacAddress,
--      tnSapIpipeArpedMacAddressTimeout
--      }
--    STATUS      obsolete
--    DESCRIPTION
--        "The group of objects supporting management of Sap
--         I-Pipe capabilities on Nokia 7x50 SR series systems."
--    ::= { tnSapGroups 110 }

-- tnSapPolicyV6v0Group OBJECT-GROUP
--    OBJECTS {
--      tnSapCurrentIngressIpFilterId,
--      tnSapCurrentIngressMacFilterId,
--      tnSapCurrentIngressQosPolicyId,
--      tnSapCurrentIngressQosSchedPlcy,
--      tnSapCurrentEgressIpFilterId,
--      tnSapCurrentEgressMacFilterId,
--      tnSapCurrentEgressQosPolicyId,
--      tnSapCurrentEgressQosSchedPlcy,
--      tnSapIntendedIngressIpFilterId,
--      tnSapIntendedIngressMacFilterId,
--      tnSapIntendedIngressQosPolicyId,
--      tnSapIntendedIngressQosSchedPlcy,
--      tnSapIntendedEgressIpFilterId,
--      tnSapIntendedEgressMacFilterId,
--      tnSapIntendedEgressQosPolicyId,
--      tnSapIntendedEgressQosSchedPlcy,

--      tnSapIgQosPlcyDroppedHiPrioPackets,
--      tnSapIgQosPlcyDroppedHiPrioOctets,
--      tnSapIgQosPlcyDroppedLoPrioPackets,
--      tnSapIgQosPlcyDroppedLoPrioOctets,
--      tnSapIgQosPlcyForwardedInProfPackets,
--      tnSapIgQosPlcyForwardedInProfOctets,
--      tnSapIgQosPlcyForwardedOutProfPackets,
--      tnSapIgQosPlcyForwardedOutProfOctets,
--      tnSapEgQosPlcyDroppedInProfPackets,
--      tnSapEgQosPlcyDroppedInProfOctets,
--      tnSapEgQosPlcyDroppedOutProfPackets,
--      tnSapEgQosPlcyDroppedOutProfOctets,
--      tnSapEgQosPlcyForwardedInProfPackets,
--      tnSapEgQosPlcyForwardedInProfOctets,
--      tnSapEgQosPlcyForwardedOutProfPackets,
--      tnSapEgQosPlcyForwardedOutProfOctets,
--      tnSapIgQosPlcyQueueStatsOfferedHiPrioPackets,
--      tnSapIgQosPlcyQueueStatsDroppedHiPrioPackets,
--      tnSapIgQosPlcyQueueStatsOfferedLoPrioPackets,
--      tnSapIgQosPlcyQueueStatsDroppedLoPrioPackets,
--      tnSapIgQosPlcyQueueStatsOfferedHiPrioOctets,
--      tnSapIgQosPlcyQueueStatsDroppedHiPrioOctets,
--      tnSapIgQosPlcyQueueStatsOfferedLoPrioOctets,
--      tnSapIgQosPlcyQueueStatsDroppedLoPrioOctets,
--      tnSapIgQosPlcyQueueStatsForwardedInProfPackets,
--      tnSapIgQosPlcyQueueStatsForwardedOutProfPackets,
--      tnSapIgQosPlcyQueueStatsForwardedInProfOctets,
--      tnSapIgQosPlcyQueueStatsForwardedOutProfOctets,
--      tnSapIgQosPlcyQueueCustId,
--      tnSapIgQosPlcyQueueStatsUncoloredPacketsOffered,
--      tnSapIgQosPlcyQueueStatsUncoloredOctetsOffered,
--      tnSapEgQosPlcyQueueStatsForwardedInProfPackets,
--      tnSapEgQosPlcyQueueStatsDroppedInProfPackets,
--      tnSapEgQosPlcyQueueStatsForwardedOutProfPackets,
--      tnSapEgQosPlcyQueueStatsDroppedOutProfPackets,
--      tnSapEgQosPlcyQueueStatsForwardedInProfOctets,
--      tnSapEgQosPlcyQueueStatsDroppedInProfOctets,
--      tnSapEgQosPlcyQueueStatsForwardedOutProfOctets,
--      tnSapEgQosPlcyQueueStatsDroppedOutProfOctets,
--      tnSapEgQosPlcyQueueCustId,

--      tnSapIngSchedPlcyStatsFwdPkt,
--      tnSapIngSchedPlcyStatsFwdOct,
--      tnSapEgrSchedPlcyStatsFwdPkt,
--      tnSapEgrSchedPlcyStatsFwdOct,
--      tnSapIngSchedPlcyPortStatsFwdPkt,
--      tnSapIngSchedPlcyPortStatsFwdOct,
--      tnSapEgrSchedPlcyPortStatsFwdPkt,
--      tnSapEgrSchedPlcyPortStatsFwdOct
--      }
--    STATUS      current
--    DESCRIPTION
--        "The group of objects supporting management of Sap
--         ingress/egress capabilities on Nokia 7x50 SR series systems."
--    ::= { tnSapGroups 111 }


-- tnSapCemV6v0Group OBJECT-GROUP
--    OBJECTS {
--      tnSapCemLastMgmtChange,
--      tnSapCemEndpointType,
--      tnSapCemBitrate,
--      tnSapCemCasTrunkFraming,
--      tnSapCemPayloadSize,
--      tnSapCemJitterBuffer,
--      tnSapCemUseRtpHeader,
--      tnSapCemDifferential,
--      tnSapCemTimestampFreq,
--      tnSapCemReportAlarm,
--      tnSapCemReportAlarmStatus,
--      tnSapCemLocalEcid,
--      tnSapCemRemoteMacAddr,
--      tnSapCemRemoteEcid,
--      tnSapCemJitterBufPackets,
--      tnSapCemPlayoutBufPacketsThreshold,
--      tnSapCemStatsIngressForwardedPkts,
--      tnSapCemStatsIngressDroppedPkts,
--      tnSapCemStatsEgressForwardedPkts,
--      tnSapCemStatsEgressDroppedPkts,
--      tnSapCemStatsEgressMissingPkts,
--      tnSapCemStatsEgressPktsReOrder,
--      tnSapCemStatsEgressJtrBfrUnderruns,
--      tnSapCemStatsEgressJtrBfrOverruns,
--      tnSapCemStatsEgressMisOrderDropped,
--      tnSapCemStatsEgressMalformedPkts,
--      tnSapCemStatsEgressLBitDropped,
--      tnSapCemStatsEgressMultipleDropped,
--      tnSapCemStatsEgressESs,
--      tnSapCemStatsEgressSESs,
--      tnSapCemStatsEgressUASs,
--      tnSapCemStatsEgressFailureCounts,
--      tnSapCemStatsEgressUnderrunCounts,
--      tnSapCemStatsEgressOverrunCounts,
--      tnSapCemStatsEgressJtrBfrDepth
--      }
--    STATUS      current
--    DESCRIPTION
--        "The group of objects supporting management of Sap
--         Cem capabilities on Nokia 7x50 SR series systems."
--    ::= { tnSapGroups 112 }


-- tnSapL2ptV6v0Group OBJECT-GROUP
--    OBJECTS {
--      tnSapTlsL2ptStatsLastClearedTime,
--      tnSapTlsL2ptStatsL2ptEncapStpConfigBpdusRx,
--      tnSapTlsL2ptStatsL2ptEncapStpConfigBpdusTx,
--      tnSapTlsL2ptStatsL2ptEncapStpRstBpdusRx,
--      tnSapTlsL2ptStatsL2ptEncapStpRstBpdusTx,
--      tnSapTlsL2ptStatsL2ptEncapStpTcnBpdusRx,
--      tnSapTlsL2ptStatsL2ptEncapStpTcnBpdusTx,
--      tnSapTlsL2ptStatsL2ptEncapPvstConfigBpdusRx,
--      tnSapTlsL2ptStatsL2ptEncapPvstConfigBpdusTx,
--      tnSapTlsL2ptStatsL2ptEncapPvstRstBpdusRx,
--      tnSapTlsL2ptStatsL2ptEncapPvstRstBpdusTx,
--      tnSapTlsL2ptStatsL2ptEncapPvstTcnBpdusRx,
--      tnSapTlsL2ptStatsL2ptEncapPvstTcnBpdusTx,
--      tnSapTlsL2ptStatsStpConfigBpdusRx,
--      tnSapTlsL2ptStatsStpConfigBpdusTx,
--      tnSapTlsL2ptStatsStpRstBpdusRx,
--      tnSapTlsL2ptStatsStpRstBpdusTx,
--      tnSapTlsL2ptStatsStpTcnBpdusRx,
--      tnSapTlsL2ptStatsStpTcnBpdusTx,
--      tnSapTlsL2ptStatsPvstConfigBpdusRx,
--      tnSapTlsL2ptStatsPvstConfigBpdusTx,
--      tnSapTlsL2ptStatsPvstRstBpdusRx,
--      tnSapTlsL2ptStatsPvstRstBpdusTx,
--      tnSapTlsL2ptStatsPvstTcnBpdusRx,
--      tnSapTlsL2ptStatsPvstTcnBpdusTx,
--      tnSapTlsL2ptStatsOtherBpdusRx,
--      tnSapTlsL2ptStatsOtherBpdusTx,
--      tnSapTlsL2ptStatsOtherL2ptBpdusRx,
--      tnSapTlsL2ptStatsOtherL2ptBpdusTx,
--      tnSapTlsL2ptStatsOtherInvalidBpdusRx,
--      tnSapTlsL2ptStatsOtherInvalidBpdusTx,
--      tnSapTlsL2ptStatsL2ptEncapCdpBpdusRx,
--      tnSapTlsL2ptStatsL2ptEncapCdpBpdusTx,
--      tnSapTlsL2ptStatsL2ptEncapVtpBpdusRx,
--      tnSapTlsL2ptStatsL2ptEncapVtpBpdusTx,
--      tnSapTlsL2ptStatsL2ptEncapDtpBpdusRx,
--      tnSapTlsL2ptStatsL2ptEncapDtpBpdusTx,
--      tnSapTlsL2ptStatsL2ptEncapPagpBpdusRx,
--      tnSapTlsL2ptStatsL2ptEncapPagpBpdusTx,
--      tnSapTlsL2ptStatsL2ptEncapUdldBpdusRx,
--      tnSapTlsL2ptStatsL2ptEncapUdldBpdusTx,
--      tnSapTlsL2ptStatsCdpBpdusRx,
--      tnSapTlsL2ptStatsCdpBpdusTx,
--      tnSapTlsL2ptStatsVtpBpdusRx,
--      tnSapTlsL2ptStatsVtpBpdusTx,
--      tnSapTlsL2ptStatsDtpBpdusRx,
--      tnSapTlsL2ptStatsDtpBpdusTx,
--      tnSapTlsL2ptStatsPagpBpdusRx,
--      tnSapTlsL2ptStatsPagpBpdusTx,
--      tnSapTlsL2ptStatsUdldBpdusRx,
--      tnSapTlsL2ptStatsUdldBpdusTx
--      }
--    STATUS      current
--    DESCRIPTION
--        "The group of objects supporting management of Sap
--         TLS L2pt capabilities on Nokia 7x50 SR series systems."
--    ::= { tnSapGroups 113 }


-- tnSapMtnSapV6v0Group OBJECT-GROUP
--    OBJECTS {
--      tnMtnSapPlcyRowStatus,
--      tnMtnSapPlcyLastChanged,
--      tnMtnSapPlcyDescription,
--      tnMtnSapPlcyCpmProtPolicyId,
--      tnMtnSapPlcyCpmProtMonitorMac,
--      tnMtnSapPlcySubMgmtDefSubId,
--      tnMtnSapPlcySubMgmtDefSubIdStr,
--      tnMtnSapPlcySubMgmtDefSubProfile,
--      tnMtnSapPlcySubMgmtDefSlaProfile,
--      tnMtnSapPlcySubMgmtSubIdPlcy,
--      tnMtnSapPlcySubMgmtSubscriberLimit,
--      tnMtnSapPlcySubMgmtProfiledTrafOnly,
--      tnMtnSapPlcySubMgmtNonSubTrafSubId,
--      tnMtnSapPlcySubMgmtNonSubTrafSubProf,
--      tnMtnSapPlcySubMgmtNonSubTrafSlaProf,
--      tnMtnSapPlcyAssociatedMtnSaps,
--      tnMtnSapTlsPlcyLastChanged,
--      tnMtnSapTlsPlcySplitHorizonGrp,
--      tnMtnSapTlsPlcyArpReplyAgent,
--      tnMtnSapTlsPlcySubMgmtMacDaHashing,
--      tnMtnSapTlsPlcyDhcpLeasePopulate,
--      tnMtnSapTlsPlcyDhcpPrxyAdminState,
--      tnMtnSapTlsPlcyDhcpPrxyServAddr,
--      tnMtnSapTlsPlcyDhcpPrxyServAddrType,
--      tnMtnSapTlsPlcyDhcpPrxyLTRadOverride,
--      tnMtnSapTlsPlcyDhcpInfoAction,
--      tnMtnSapTlsPlcyDhcpCircuitId,
--      tnMtnSapTlsPlcyDhcpRemoteId,
--      tnMtnSapTlsPlcyDhcpRemoteIdString,
--      tnMtnSapTlsPlcyDhcpVendorInclOpts,
--      tnMtnSapTlsPlcyDhcpVendorOptStr,
--      tnMtnSapTlsPlcyDhcpPrxyLeaseTime,
--      tnMtnSapTlsPlcyEgressMcastGroup,
--      tnMtnSapTlsPlcyIgmpSnpgImportPlcy,
--      tnMtnSapTlsPlcyIgmpSnpgFastLeave,
--      tnMtnSapTlsPlcyIgmpSnpgSendQueries,
--      tnMtnSapTlsPlcyIgmpSnpgGenQueryIntv,
--      tnMtnSapTlsPlcyIgmpSnpgQueryRespIntv,
--      tnMtnSapTlsPlcyIgmpSnpgRobustCount,
--      tnMtnSapTlsPlcyIgmpSnpgLastMembIntvl,
--      tnMtnSapTlsPlcyIgmpSnpgMaxNbrGrps,
--      tnMtnSapTlsPlcyIgmpSnpgMvrFromVplsId,
--      tnMtnSapTlsPlcyIgmpSnpgVersion,
--      tnMtnSapTlsPlcyIgmpSnpgMcacPlcyName,
--      tnMtnSapTlsPlcyIgmpSnpgMcacPrRsvMnBW,
--      tnMtnSapTlsPlcyIgmpSnpgMcacUncnstBW,
--
--      tnMtnSapIgmpSnpgMcacLevelRowStatus,
--      tnMtnSapIgmpSnpgMcacLevelLastChanged,
--      tnMtnSapIgmpSnpgMcacLevelBW,
--      tnMtnSapIgmpSnpgMcacLagRowStatus,
--      tnMtnSapIgmpSnpgMcacLagLastChanged,
--      tnMtnSapIgmpSnpgMcacLagLevel,
--      tnMtnSapInfoCreationSapPortEncapVal,
--      tnMtnSapInfoCreationPlcyName,
--      tnMtnSapInfoReEvalPolicy,
--      tnMtnSapInfoLastChanged,

--      tnMtnSapCaptureSapStatsPktsRecvd,
--      tnMtnSapCaptureSapStatsPktsRedirect,
--      tnMtnSapCaptureSapStatsPktsDropped,
--      tnMtnSapPlcyTblLastChgd,
--      tnMtnSapTlsPlcyTblLastChgd,
--      tnMtnSapIgmpSnpgMcacLvlTblLastChgd,
--      tnMtnSapIgmpSnpgMcacLagTblLastChgd,
--      tnMtnSapInfoTblLastChgd
--      }
--    STATUS      current
--    DESCRIPTION
--        "The group of objects supporting management of
--         managed SAP capabilities on Nokia 7x50 SR series systems."
--    ::= { tnSapGroups 114 }


-- tnSapMrpV6v0Group OBJECT-GROUP
--    OBJECTS {
--      tnSapTlsMrpRxPdus,
--      tnSapTlsMrpDroppedPdus,
--      tnSapTlsMrpTxPdus,
--      tnSapTlsMrpRxNewEvent,
--      tnSapTlsMrpRxJoinInEvent,
--      tnSapTlsMrpRxInEvent,
--      tnSapTlsMrpRxJoinEmptyEvent,
--      tnSapTlsMrpRxEmptyEvent,
--      tnSapTlsMrpRxLeaveEvent,
--      tnSapTlsMrpTxNewEvent,
--      tnSapTlsMrpTxJoinInEvent,
--      tnSapTlsMrpTxInEvent,
--      tnSapTlsMrpTxJoinEmptyEvent,
--      tnSapTlsMrpTxEmptyEvent,
--      tnSapTlsMrpTxLeaveEvent,
--      tnSapTlsMmrpDeclared,
--      tnSapTlsMmrpRegistered
--      }
--    STATUS      current
--    DESCRIPTION
--        "The group of objects supporting management of Sap
--         MRP capabilities on Nokia 7x50 SR series systems."
--    ::= { tnSapGroups 115 }

-- tnSapHsmdaV6v0Group OBJECT-GROUP
--    OBJECTS {
--      tnSapIngressAggRateLimit,
--      tnSapEgressHsmdaShaperOverride,
--      tnSapIngressHsmdaPacketOffOvr,
--      tnSapEgressHsmdaPacketOffOverride,
--      tnSapIngQosHsmdaQueueRowStatus,
--      tnSapIngQosHsmdaQueueLastChanged,
--      tnSapIngQosHsmdaQueueAdminPIR,
--      tnSapIngQosHsmdaQueueAdminCIR,
--      tnSapIngQosHsmdaQueueSlopePolicy,
--      tnSapEgrQosHsmdaQueueRowStatus,
--      tnSapEgrQosHsmdaQueueLastChanged,
--      tnSapEgrQosHsmdaQueueAdminPIR,
--      tnSapEgrQosHsmdaQueueAdminCIR,
--      tnSapEgrQosHsmdaQueueSlopePolicy,
--      tnSapIngHsmdaQStatCustId,
--      tnSapIngHsmdaQStatHiPktsDropped,
--      tnSapIngHsmdaQStatLoPktsDropped,
--      tnSapIngHsmdaQStatHiOctsDropped,
--      tnSapIngHsmdaQStatLoOctsDropped,
--      tnSapIngHsmdaQStatInProfPktsFwd,
--      tnSapIngHsmdaQStatOutProfPktsFwd,
--      tnSapIngHsmdaQStatInProfOctsFwd,
--      tnSapIngHsmdaQStatOutProfOctsFwd,
--      tnSapIngHsmdaQStatAllPktsOffered,
--      tnSapIngHsmdaQStatAllOctsOffered,
--      tnSapIngHsmdaCntrStCustId,
--      tnSapIngHsmdaCntrStHiPktDrop,
--      tnSapIngHsmdaCntrStLoPktDrop,
--      tnSapIngHsmdaCntrStHiOctDrop,
--      tnSapIngHsmdaCntrStLoOctDrop,
--      tnSapIngHsmdaCntrStInProfPktFwd,
--      tnSapIngHsmdaCntrStOutProfPktFwd,
--      tnSapIngHsmdaCntrStInProfOctFwd,
--      tnSapIngHsmdaCntrStOutProfOctFwd,
--      tnSapIngHsmdaCntrStAllPktOffered,
--      tnSapIngHsmdaCntrStAllOctOffered,
--      tnSapEgrHsmdaQStatCustId,
--      tnSapEgrHsmdaQStatInProfPktFwd,
--      tnSapEgrHsmdaQStatInProfPktDropd,
--      tnSapEgrHsmdaQStatOutProfPktFwd,
--      tnSapEgrHsmdaQStatOutProfPktDropd,
--      tnSapEgrHsmdaQStatInProfOctFwd,
--      tnSapEgrHsmdaQStatInProfOctDropd,
--      tnSapEgrHsmdaQStatOutProfOctFwd,
--      tnSapEgrHsmdaQStatOutProfOctDropd,
--      tnSapEgrHsmdaCntrStCustId,
--      tnSapEgrHsmdaCntrStInProfPktFwd,
--      tnSapEgrHsmdaCntrStInProfPktDrop,
--      tnSapEgrHsmdaCntrStOutProfPktFwd,
--      tnSapEgrHsmdaCntrStOutProfPktDrop,
--      tnSapEgrHsmdaCntrStInProfOctFwd,
--      tnSapEgrHsmdaCntrStInProfOctDrop,
--      tnSapEgrHsmdaCntrStOutProfOctFwd,
--      tnSapEgrHsmdaCntrStOutProfOctDrop
--      }
--    STATUS      current
--    DESCRIPTION
--        "The group of objects supporting management of Sap Ingress/Egress
--         QoS Hsmda capabilities on Nokia 7x50 SR series systems."
--    ::= { tnSapGroups 116 }

-- tmnxTlsMtnSapPppoeV6v0Group OBJECT-GROUP
--    OBJECTS {
--        tnSapTlsPppoeMtnSapTrigger
--    }
--    STATUS      current
--    DESCRIPTION
--        "The group of objects supporting PPPOE on Managed SAPs
--         feature on the Nokia 7x50 SR series systems."
--    ::= { tnSapGroups 117 }

-- tnSapIpV6FilterV6v0Group OBJECT-GROUP
--    OBJECTS {
--      tnSapIngressIpv6FilterId,
--      tnSapEgressIpv6FilterId,
--      tnSapCurrentIngressIpv6FilterId,
--      tnSapCurrentEgressIpv6FilterId,
--      tnSapIntendedIngressIpv6FilterId,
--      tnSapIntendedEgressIpv6FilterId
--    }
--    STATUS      current
--    DESCRIPTION
--        "The group of objects supporting management of Sap Ingress Policy
--         capabilities on Nokia 7x50 SR series systems."
--    ::= { tnSapGroups 118 }

-- tnSapBsxV6v0Group OBJECT-GROUP
--    OBJECTS {
--      tnSapStaticHostAppProfile,
--      tnSapSubMgmtDefAppProfile,
--      tnSapSubMgmtNonSubTrafficAppProf,
--      tnMtnSapPlcySubMgmtDefAppProfile,
--      tnMtnSapPlcySubMgmtNonSubTrafAppProf
--      }
--    STATUS      obsolete
--    DESCRIPTION
--        "The group of objects supporting management of BSX (Application
--         Assurance) capabilities on Nokia 7x50 SR series systems."
--    ::= { tnSapGroups 119 }

-- tnSapMtnSapV6v1Group OBJECT-GROUP
--    OBJECTS {
--       tnMtnSapL3PlcyTblLastChgd,
--       tnMtnSapL3PlcyLastChanged,
--       tnMtnSapL3PlcyAntiSpoof
--      }
--    STATUS      current
--    DESCRIPTION
--        "The group of objects supporting management of
--         managed SAP L3 capabilities on Nokia 7x50 SR series systems."
--    ::= { tnSapGroups 120 }

-- tnSapTlsV6v1Group OBJECT-GROUP
--    OBJECTS {
--      tnSapTlsStpAdminStatus,
--      tnSapTlsStpPriority,
--      tnSapTlsStpPortNum,
--      tnSapTlsStpPathCost,
--      tnSapTlsStpRapidStart,
--      tnSapTlsStpBpduEncap,
--      tnSapTlsStpPortState,
--      tnSapTlsStpDesignatedBridge,
--      tnSapTlsStpDesignatedPort,
--      tnSapTlsStpForwardTransitions,
--      tnSapTlsStpInConfigBpdus,
--      tnSapTlsStpInTcnBpdus,
--      tnSapTlsStpInBadBpdus,
--      tnSapTlsStpOutConfigBpdus,
--      tnSapTlsStpOutTcnBpdus,
--      tnSapTlsStpOperBpduEncap,
--      tnSapTlsVpnId,
--      tnSapTlsCustId,
--      tnSapTlsMacAddressLimit,
--      tnSapTlsNumMacAddresses,
--      tnSapTlsNumStaticMacAddresses,
--      tnSapTlsMacLearning,
--      tnSapTlsMacAgeing,
--      tnSapTlsStpOperEdge,
--      tnSapTlsStpAdminPointToPoint,
--      tnSapTlsStpPortRole,
--      tnSapTlsStpAutoEdge,
--      tnSapTlsStpOperProtocol,
--      tnSapTlsStpInRstBpdus,
--      tnSapTlsStpOutRstBpdus,
--      tnSapTlsLimitMacMove,
--      tnSapTlsMacPinning,
--      tnSapTlsDiscardUnknownSource,
--      tnSapTlsMvplsPruneState,
--      tnSapTlsMvplsMgmtService,
--      tnSapTlsMvplsMgmtPortId,
--      tnSapTlsMvplsMgmtEncapValue,
--      tnSapTlsArpReplyAgent,
--      tnSapTlsStpException,
--      tnSapTlsAuthenticationPolicy,
--      tnSapTlsL2ptTermination,
--      tnSapTlsBpduTranslation,
--      tnSapTlsStpRootGuard,
--      tnSapTlsStpInsideRegion,
--      tnSapTlsEgressMcastGroup,
--      tnSapTlsStpInMstBpdus,
--      tnSapTlsStpOutMstBpdus,
--      tnSapTlsRestProtSrcMac,
--      tnSapTlsRestProtSrcMacAction,
--      tnSapTlsRestUnprotDstMac,
--      tnSapTlsStpRxdDesigBridge,
--      tnSapTlsStpRootGuardViolation,
--      tnSapTlsShcvAction,
--      tnSapTlsShcvSrcIp,
--      tnSapTlsShcvSrcMac,
--      tnSapTlsShcvInterval,
--      tnSapTlsMvplsMgmtMsti,
--      tnSapTlsMacMoveNextUpTime,
--      tnSapTlsMacMoveRateExcdLeft,
--      tnSapTlsL2ptForceBoundary,
--      tnSapTlsLimitMacMoveLevel,
--      tnSapTlsBpduTransOper,
--      tnSapTlsDefMtnSapPolicy,
--      tnSapTlsL2ptProtocols,
--      tnSapTlsL2ptForceProtocols,
--      tnSapTlsDhcpMtnSapTrigger,
--      tnSapTlsDhcpProxyLeaseTime,
--      tnSapTlsDhcpRemoteId,
--      tnSapTlsMrpJoinTime,
--      tnSapTlsMrpLeaveTime,
--      tnSapTlsMrpLeaveAllTime,
--      tnSapTlsMrpPeriodicTime,
--      tnSapTlsMrpPeriodicEnabled,
--      tnSapTlsPppoePolicy,
--      sapTlsPppoePolicy,
--      sapTlsInTcBitBpdus,
--      sapTlsOutTcBitBpdus
--      }
--    STATUS      current
--    DESCRIPTION
--        "The group of objects supporting management of Sap
--         TLS capabilities on Nokia 7x50 SR series systems."
--    ::= { tnSapGroups 122 }

-- tnSapArpHostGroup OBJECT-GROUP
--    OBJECTS {
--       tnSapTlsArpHostTableLastMgmtChange,
--       tnSapTlsArpHostLastMgmtChange,
--       tnSapTlsArpHostAdminState,
--       tnSapTlsArpHostMaxNumHosts,
--       tnSapTlsArpHostMinAuthIntvl,
--       tnSapTlsArpMtnSapTrigger,
--       tnMtnSapTlsPlcyArpHostMaxNumHosts,
--       tnMtnSapTlsPlcyArpHostMinAuthIntvl,
--       tnSapArpHostStatLastClearedTime,
--       tnSapArpHostStatNumHosts,
--       tnSapArpHostStatTriggersRx,
--       tnSapArpHostStatTriggersIgnored,
--       tnSapArpHostStatTrigIgnQFull,
--       tnSapArpHostStatNumForcedVerif,
--       tnSapArpHostStatNumCreated,
--       tnSapArpHostStatNumDeleted,
--       tnSapArpHostStatNumUpdated,
--       tnSapArpHostStatNumAuthReq
--      }
--    STATUS      current
--    DESCRIPTION
--        "The group of objects supporting management of
--         ARP hosts' capabilities for SAP's on Nokia 7xxx series systems."
--    ::= { tnSapGroups 123 }

-- tnSapV7v0Group OBJECT-GROUP
--    OBJECTS {
--      tnSapNumEntries,
--      tnSapPortId,
--      tnSapEncapValue,
--      tnSapRowStatus,
--      tnSapType,
--      tnSapDescription,
--      tnSapAdminStatus,
--      tnSapOperStatus,
--      tnSapIngressQosPolicyId,
--      tnSapIngressMacFilterId,
--      tnSapIngressIpFilterId,
--      tnSapIngressVlanTranslationId,
--      tnSapEgressQosPolicyId,
--      tnSapEgressMacFilterId,
--      tnSapEgressIpFilterId,
--      tnSapMirrorStatus,
--      tnSapIesIfIndex,
--      tnSapLastMgmtChange,
--      tnSapCollectAcctStats,
--      tnSapAccountingPolicyId,
--      tnSapVpnId,
--      tnSapCustId,
--      tnSapCustMultSvcSite,
--      tnSapIngressQosSchedulerPolicy,
--      tnSapEgressQosSchedulerPolicy,
--      tnSapSplitHorizonGrp,
--      tnSapIngressSharedQueuePolicy,
--      tnSapIngressMatchQinQDot1PBits,
--      tnSapOperFlags,
--      tnSapLastStatusChange,
--      tnSapAntiSpoofing,
--      tnSapTodSuite,
--      tnSapIngUseMultipointShared,
--      tnSapEgressQinQMarkTopOnly,
--      tnSapEgressAggRateLimit,
--      tnSapEndPoint,
--      tnSapIngressVlanTranslation,
--      tnSapSubType,
--      tnSapCpmProtPolicyId,
--      tnSapCpmProtMonitorMac,
--      tnSapEgressFrameBasedAccounting,
--      tnSapEthernetLLFAdminStatus,
--      tnSapEthernetLLFOperStatus,
--      tnSapTlsMvplsRowStatus,
--      tnSapEgressFrameBasedAccounting,
--      tnSapCallingStationId
--    }
--    STATUS      current
--    DESCRIPTION
--        "The group of objects supporting management of Sap
--         general capabilities on Nokia 7x50 SR series systems."
--    ::= { tnSapGroups 124 }

-- tnSapIgmpTrkGroup OBJECT-GROUP
--    OBJECTS {
--       tnSapIgmpTrkTableLastMgmtChange,
--       tnSapIgmpTrkLastMgmtChange,
--       tnSapIgmpTrkExpiryTime,
--       tnSapIgmpTrkImportPlcy,
--       tnSapIgmpTrkMaxNbrGrps,
--       tnSapIgmpTrkNbrGrps,
--       tnSapIgmpTrkMaxNbrSrcs
--      }
--    STATUS      current
--    DESCRIPTION
--        "The group of objects supporting management of
--         IGMP host tracking capabilities for SAP's on Nokia 7xxx series
--         systems."
--    ::= { tnSapGroups 125 }

-- tnSapFrGroup OBJECT-GROUP
--    OBJECTS {
--      tnSapFrInfoFrf12Mode,
--      tnSapFrInfoSchedulingClass,
--      tnSapFrInfoLastChanged,
--      tnSapFrf12InfoFragmentThreshold,
--      tnSapFrf12InfoLastChanged
--      }
--    STATUS      current
--    DESCRIPTION
--        "The group of objects supporting management of Sap
--         FR capabilities on Nokia 7x50 SR series systems."
--    ::= { tnSapGroups 126 }

-- tnSapIpipeV7v0Group OBJECT-GROUP
--    OBJECTS {
--      tnSapIpipeCeInetAddress,
--      tnSapIpipeCeInetAddressType,
--      tnSapIpipeMacRefreshInterval,
--      tnSapIpipeMacAddress,
--      tnSapIpipeArpedMacAddress,
--      tnSapIpipeArpedMacAddressTimeout,
--      tnSapIpipeDiscoveredCeInetAddrType,
--      tnSapIpipeDiscoveredCeInetAddr,
--      tnSapIpipeUseBroadcastMac,
--      tnSapIpipeUsingBroadcastMac
--      }
--    STATUS      current
--    DESCRIPTION
--        "The group of objects supporting management of Sap
--         IPIPE capabilities on Nokia 7x50 SR series systems."
--    ::= { tnSapGroups 127 }

-- tnSapBsxV7v0Group OBJECT-GROUP
--    OBJECTS {
--      tnSapStaticHostAppProfile,
--      tnSapSubMgmtDefAppProfile,
--      tnSapSubMgmtNonSubTrafficAppProf,
--      tnMtnSapPlcySubMgmtDefAppProfile,
--      tnMtnSapPlcySubMgmtNonSubTrafAppProf,
--      tnSapIsaAaApplicationProfile
--      }
--    STATUS      current
--    DESCRIPTION
--        "The group of objects supporting management of BSX (Application
--         Assurance) capabilities on Nokia 7x50 SR series systems
--         in release R7.0"
--    ::= { tnSapGroups 128 }

--tmnxSapTlsV7v0Group OBJECT-GROUP
--    OBJECTS {
--      sapTlsShcvRetryTimeout,
--      sapTlsShcvRetryCount
--      }
--    STATUS      current
--    DESCRIPTION
--        "The group of objects supporting management of SAP
--         TLS capabilities on Nokia 7x50 SR series systems
--         added in release 7.0."
--    ::= { tmnxSapGroups 137 }

-- tnSapPbbGroup OBJECT-GROUP
--    OBJECTS {
--       tnSapPbbRowStatus,
--       tnSapPbbLastMgmtChange,
--       tnSapPbbIgmpSnpgMRouter
--      }
--    STATUS      current
--    DESCRIPTION
--        "The group of objects supporting management of
--         Provider Backbone Bridging (PBB/IEEE 802.1ah) capabilities for SAP's
--         on Nokia 7xxx series systems."
--    ::= { tnSapGroups 130 }

-- Notification objects

-- tnSapNotificationObjV6v0Group OBJECT-GROUP
--    OBJECTS {
--      tnSapNotifyPortId,
--      svcManagedSapCreationError,
--      tnMtnSapStatus
--    }
--    STATUS      obsolete
--    DESCRIPTION
--        "The group of objects supporting management of notifications
--         on Nokia 7x50 SR series systems."
--    ::= { tnSapGroups 200 }
--
-- tnSapNotificationObjV7v0Group OBJECT-GROUP
--    OBJECTS {
--      tnSapNotifyPortId,
--      svcManagedSapCreationError,
--      tnMtnSapStatus,
--      tnSapTlsNotifyMacAddr,
--      tnSapBGPPeeringHostIpAddr,
--      tnSapBGPPeeringHostIpAddrType,
--      tnSapBGPPeeringAttrDiscarded,
--      tnSapBGPPeeringNotifDescription,
--      tnSapBGPPeeringVRtrID
--    }
--    STATUS      current
--    DESCRIPTION
--        "The group of objects supporting management of notifications
--         on Nokia 7x50 SR series systems."
--    ::= { tnSapGroups 201 }

-- Obsoleted Group
-- tnSapObsoletedV6v0Group OBJECT-GROUP
--    OBJECTS {
--      tnSapTlsDhcpSnooping,
--      tnSapTlsDhcpLseStateRemainLseTime,
--      tnSapTlsDhcpLseStateOption82,
--      tnSapTlsDhcpLseStatePersistKey
--    }
--    STATUS      obsolete
--    DESCRIPTION
--        "The group of obsolete objects for the services feature
--         on Nokia 7x50 SR series systems."
--    ::= { tnSapGroups 300 }

-- tnSapObsoletedV7v0Group OBJECT-GROUP
--    OBJECTS {
--      tnSapTlsDhcpSnooping,
--      tnSapTlsDhcpLseStateRemainLseTime,
--      tnSapTlsDhcpLseStateOption82,
--      tnSapTlsDhcpLseStatePersistKey,
--      tnSapAntiSpoofIpAddress,
--      tnSapAntiSpoofMacAddress
--    }
--    STATUS      current
--    DESCRIPTION
--        "The group of obsolete objects on Nokia 7x50 SR series
--         systems."
--    ::= { tnSapGroups 301 }

-- NOTIFICATION Group
-- tnSapNotifyGroup NOTIFICATION-GROUP
--    NOTIFICATIONS   {
--      tnSapStatusChanged,
--      tnSapTlsMacAddrLimitAlarmRaised,
--      tnSapTlsMacAddrLimitAlarmCleared,
--      tnSapDHCPLeaseEntriesExceeded,
--      tnSapDHCPLseStateOverride,
--      tnSapDHCPSuspiciousPcktRcvd,
--      tnSapDHCPLseStatePopulateErr,
--      tnHostConnectivityLost,
--      tnHostConnectivityRestored,
--      tnSapReceivedProtSrcMac,
--      tnSapStaticHostDynMacConflict,
--      tnSapTlsMacMoveExceeded,
--      tnSapDHCPProxyServerError,
--      tnSapPortStateChangeProcessed,
--      tnSapDHCPLseStateMobilityError,
--      tnMtnSapStateChanged,
--      tnMtnSapCreationFailure,
--      tnTopologyChangeSapMajorState,
--      tnNewRootSap,
--      tnTopologyChangeSapState,
--      tnReceivedTCN,
--      tnHigherPriorityBridge,
--      tnSapEncapPVST,
--      tnSapEncapDot1d,
--      tnSapActiveProtocolChange,
--      tnStpRootGuardViolation,
--      tnSapStpExcepCondStateChng,
--      tnSapHostBGPPeeringSetupFailed
--    }
--    STATUS      current
--    DESCRIPTION
--        "The group of notifications for the Sap feature
--         on Nokia 7x50 SR series systems."
--    ::= { tnSapGroups 400 }

-- tnSapCemNotificationV6v0Group NOTIFICATION-GROUP
--    NOTIFICATIONS   {
--        tnSapCemPacketDefectAlarm,
--        tnSapCemPacketDefectAlarmClear
--    }
--    STATUS      current
--    DESCRIPTION
--        "The group of notifications supporting the CEM Sap feature
--         on Nokia 7710 SR series systems."
--    ::= { tnSapGroups 401 }

-- tnSapObsoletedNotifyGroup NOTIFICATION-GROUP
--    NOTIFICATIONS   {
--      tnSapCreated,
--      tnSapDeleted,
--      tnSapTlsDHCPLseStEntriesExceeded,
--      tnSapTlsDHCPLeaseStateOverride,
--      tnSapTlsDHCPSuspiciousPcktRcvd,
--      tnSapDHCPCoAError,
--      tnSapDHCPSubAuthError,
--      tnBridgedTLS,
--      tnSapReceiveOwnBpdu
--    }
--    STATUS      current
--    DESCRIPTION
--        "The group of obsolete notifications for the Sap feature
--         on Nokia 7x50 SR series systems."
--    ::= { tnSapGroups 402 }

END

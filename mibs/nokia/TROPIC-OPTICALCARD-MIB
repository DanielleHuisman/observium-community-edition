TROPIC-OPTICALCARD-MIB DEFINITIONS ::= BEGIN

-- (c) Copyright 2021 Nokia Networks.  All rights reserved.
-- This software is the confidential and proprietary property of
-- Nokia and may only be used in accordance with the terms of the
-- license agreement provided with this software.

IMPORTS
      OBJECT-TYPE, MODULE-IDENTITY,
      Unsigned32, Integer32                   FROM SNMPv2-SMI
      MODULE-COMPLIANCE, OBJECT-GROUP         FROM SNMPv2-CONF
      TEXTUAL-CONVENTION,
      TruthValue, RowStatus                   FROM SNMPv2-TC
      TropicLEDColorType,
      TropicLEDStateType,
      TnCommand,
      AluWdmFcruProtectionRoleType            FROM TROPIC-TC
      tnShelfIndex                            FROM TROPIC-SHELF-MIB
      tnSlotIndex                             FROM TROPIC-SLOT-MIB
      tnCardModules, tnOpticalCardMIB         FROM TROPIC-GLOBAL-REG
      SnmpAdminString                         FROM SNMP-FRAMEWORK-MIB;

  tnOpticalCardMibModule MODULE-IDENTITY
      LAST-UPDATED    "202104021200Z"
      ORGANIZATION    "Nokia"
      CONTACT-INFO    "Nokia
                       Attn: Jeff Donnelly
                       600 Mountain Avenue
                       New Providence, NJ 07974

                       Phone: +1 732 221 6408
                       Email: jeff.donnelly@nokia.com"

      DESCRIPTION "The card-specific attributes for Nokia
                   WDM network elements."

      REVISION    "202104021200Z"
      DESCRIPTION "Marked the following as obsolete:
                   tnCpcCardAttributeTotal
                   tnCpcCardTable."

      REVISION    "202010231200Z"
      DESCRIPTION "1) Changed SYNTAX of the following textual conventions:
                      TropicSfdInvPortLoss
                      TropicSfdInvFiberLength
                      TropicDcmInvFiberType
                      TropicDcmInvDcmSize
                      TropicDcmInvInsertionLoss
                      TropicDcmInvInsertionLossSlope
                      TropicDcmInvDispersionFit
                      TropicDcmInvFiberLength
                      TropicDcmInvPmd
                      TropicDcmInvLatencyMismatch
                      TropicDcmInvLatency.
                   2) Updated DESCRIPTION of the following:
                      tnSfd5CardTable
                      tnSfd10CardTable
                      tnDcmxCardTable.
                   3) Changed SYNTAX of the following:
                      tnSfd5CardPortLossCh5
                      tnSfd10CardDMuxPortLossCh3
                      tnSfd10CardMuxPortLossCh8."

      REVISION    "202009041200Z"
      DESCRIPTION "Marked the following as deprecated:
                   tnCpcCardAttributeTotal
                   tnCpcCardTable."

      REVISION    "202006261200Z"
      DESCRIPTION "Added the following to tnCardFunctionMode:
                   demo(29)."

      REVISION    "202006051200Z"
      DESCRIPTION "1) Added the following textual conventions:
                      TropicSfdInvPortLoss
                      TropicSfdInvFiberLength
                      TropicDcmInvFiberType
                      TropicDcmInvDcmSize
                      TropicDcmInvInsertionLoss
                      TropicDcmInvInsertionLossSlope
                      TropicDcmInvDispersionFit
                      TropicDcmInvFiberLength
                      TropicDcmInvPmd
                      TropicDcmInvLatencyMismatch
                      TropicDcmInvLatency.
                   2) Added the following tables:
                      tnSfd5CardTable
                      tnSfd10CardTable
                      tnDcmxCardTable."

      REVISION    "202003131200Z"
      DESCRIPTION "Added the following to tnCardFunctionMode:
                   none(25)
                   to
                   aes256Gcm(28)."

      REVISION    "201905241200Z"
      DESCRIPTION "Marked the following as obsolete:
                   tn4dpa4CardTable
                   tnOpsaCardTable
                   tn43sca1CardTable."

      REVISION    "201903151200Z"
      DESCRIPTION "Added the following to tnCardFunctionMode:
                   clientLine(22),
                   to
                   otn100GbeEncrypt(24)."

      REVISION    "201902011200Z"
      DESCRIPTION "Added the following to tnCpcCardTable:
                   tnCpcCardLEDColor
                   tnCpcCardLEDState."

      REVISION    "201811091200Z"
      DESCRIPTION "Added the following table:
                   tnCpcCardTable."

      REVISION    "201810101200Z"
      DESCRIPTION "Added the following to tnCardFunctionMode:
                   threeX100Gbe2xOtu4(19),
                   threeX100Gbe2x100GbeBjFec(20),
                   threeX100GbeBjFec2xOtu4(21)."

      REVISION    "201808171200Z"
      DESCRIPTION "Added the following to tnCardFunctionMode:
                   otn100Gbe200Gbe."

      REVISION    "201806221200Z"
      DESCRIPTION "Added the following to tnWssCardTable:
                   tnWssCardEnableFilterlessDge."

      REVISION    "201802231200Z"
      DESCRIPTION "Updated the contact info."

      REVISION    "201711031200Z"
      DESCRIPTION "Added the following table:
                   tnAutomationConfigTable."

      REVISION    "201707281200Z"
      DESCRIPTION "Added the following to tnCardFunctionMode:
                   otl410(14),
                   to
                   otn100gbe(17)."

      REVISION    "201707071200Z"
      DESCRIPTION "Fixed MIB compile issues."

      REVISION    "201705311200Z"
      DESCRIPTION "Added the following table:
                   tnCardEtherTypeProfileTable."

      REVISION    "201701201200Z"
      DESCRIPTION "Added the following to tnCruCardTable:
                   tnFCruProtectionRole."

      REVISION    "201611181200Z"
      DESCRIPTION "Added the following to tnCardFunctionMode:
                   hundredGBEBkp400(12),
                   hundredGBEBjFec(13)."

      REVISION    "201611161200Z"
      DESCRIPTION "Updated the contact info."

      REVISION    "201610261200Z"
      DESCRIPTION "Updated the description of tnDcmCardProgrammedCompensationDistance."

      REVISION    "201610211200Z"
      DESCRIPTION "Added the following value to
                   tnDcmCardProvisionedFiberType:
                   smfp(6)."

      REVISION    "201609211200Z"
      DESCRIPTION "Added the following to tnCardFunctionMode:
                   hundredGBEInterwork(11)."

      REVISION    "201605311200Z"
      DESCRIPTION "Added the following to tnCardFunctionMode:
                   pTPIOCTLLocalClock(7),
                   pTPIOCTLCentralizedClock(8),
                   pTPIOCTLRelay(9),
                   pTPIOCTLLambdaConversion(10)"

      REVISION    "201605091200Z"
      DESCRIPTION "Renamed the following on tnWssCardTable:
                   From tnWssCardWssIsFlexgrid and tnWssCardiWssGranularityMHz
                   To tnWssCardIsFlexgrid and tnWssCardGranularityMHz."

      REVISION    "201604081200Z"
      DESCRIPTION "1) Added the following to tnWssCardTable:
                      tnWssCardWssIsFlexgrid,
                      tnWssCardWssGranularityMHz.
                   2) Added the following to tnIroadmCardInfoTable:
                      tnIroadmCardInfoWssIsFlexgrid,
                      tnIroadmCardInfoWssGranularityMHz."

      REVISION    "201501081200Z"
      DESCRIPTION "Added the following table:
                   tnIsonCardModeTable."

      REVISION    "201411191200Z"
      DESCRIPTION "Added the following tables:
                   tnIroadmCardConfigTable
                   tnIroadmCardInfoTable."

      REVISION    "201408131200Z"
      DESCRIPTION "Added the following table:
                   tnCruCardTable."

      REVISION    "201402261200Z"
      DESCRIPTION "Added DEFVAL to attributes."

      REVISION    "201310211200Z"
      DESCRIPTION "Added WR20-TF to the DESCRIPTION of the following:
                   tnWssCardAdBlockLevelAdd
                   tnWssCardAdBlockLevelDrop."

      REVISION    "201305211200Z"
      DESCRIPTION "Marked the following as obsolete:
                   tnOpticalCardEvents
                   tnBandFilterCardTable
                   tnChannelFilterCardTable
                   tnChannelAddDropCardTable
                   tnExternalDcuCardTable
                   tnBroadbandCardTable."

      REVISION    "201304261200Z"
      DESCRIPTION "Added the following to tnWtocmaCardOsnrScanStatus:
                   waiting(3)."

      REVISION    "201304091200Z"
      DESCRIPTION "Added the following to tnWtocmaCardTable:
                   tnWtocmaCardDspState."

      REVISION    "201303141200Z"
      DESCRIPTION "Added the following table:
                   tnWtocmaCardTable."

      REVISION    "201301071200Z"
      DESCRIPTION "Added the following table:
                   tnPtpctlCardTable."

      REVISION    "201210241200Z"
      DESCRIPTION "Added the following to tn11dpe12aCardTable:
                   tn11dpe12aCardCrossPackServiceSupported."

      REVISION    "201210221200Z"
      DESCRIPTION "Added the following table:
                   tn112pdm11CardTable."

      REVISION    "201209061200Z"
      DESCRIPTION "Added a range in SYNTAX for the following:
                   tn11dpe12aCardLBRTimeout."

      REVISION    "201209011200Z"
      DESCRIPTION "Added the following to tn11dpe12aCardTable:
                   tn11dpe12aCardSLRTimeout."

      REVISION    "201206131200Z"
      DESCRIPTION "Updated UNITS, DESCRIPTION, and DEFVAL of the following:
                   tn11dpe12aCardLBMInterval."

      REVISION    "201204271200Z"
      DESCRIPTION "1) Marked the following as deprecated:
                      tn4dpa4CardTable
                      tn43sca1CardTable.
                   2) Added the following table:
                      tnCardFunctionModeTable."

      REVISION    "201203291200Z"
      DESCRIPTION "1) Added the following table:
                      tn11dpe12aCardTable.
                   2) Renamed tnOpsProtectionMode to tnOpsCardProtectionMode.
                   3) Updated tnWssCardReservedDegree with the following:
                      WR2:     1 to 2  -- pre-R5.1
                      WR2-88:  1 to 2  -- R5.1."

      REVISION    "201203181200Z"
      DESCRIPTION "1) Added the following to tnOpsaProtectionMode:
                      otup(4).
                   2) Marked the following table and its attribute as
                      deprecated:
                      tnOpsaCardTable.
                   3) Added the following table to replace tnOpsaCardTable:
                      tnOpsCardTable."

      REVISION    "201109301200Z"
      DESCRIPTION "Added the following to tn1dpp24mCardTable:
                   tn1dpp24mCardImpedance."

      REVISION    "201108121200Z"
      DESCRIPTION "Added the following table:
                   tn43sca1CardTable."

      REVISION    "201107221200Z"
      DESCRIPTION "1) Marked the following as obsolete:
                      tnWssCardIsAdBlockAdd
                      tnWssCardIsAdBlockDrop.
                   2) Added the following to tnWssCardTable:
                      tnWssCardAdBlockLevelAdd
                      tnWssCardAdBlockLevelDrop."

      REVISION    "201107191200Z"
      DESCRIPTION "Added the following table:
                   tn1dpp24mCardTable."

      REVISION    "201105231200Z"
      DESCRIPTION "1) Added DEFVAL for the following attributes:
                      tnWssCardAddPathTargetPower, 130
                      tnWssCardAddPathEgressPower, -900
                      tnWssCardAddPathTotalChannel, 12
                      tnWssCardReservedDegree, 2.
                   2) Updated tnWssCardReservedDegree as follows:
                      Current configurable range: 1 to 8
                      to
                      Current configurable range:
                      CWR8:    1 to 8
                      CWR8-88: 1 to 8
                      WR2:     1 to 2
                      WR8-88A: 1 to 8."

      REVISION    "201103251200Z"
      DESCRIPTION "Added the following to tnWssCardTable:
                   tnWssCardIsAdBlockAdd
                   tnWssCardIsAdBlockDrop."

      REVISION    "201011081200Z"
      DESCRIPTION "Added the following to tn11dpe12eCardTable:
                   tn11dpe12eQINQModeFlowCm."

      REVISION    "201011011200Z"
      DESCRIPTION "1) Changed configurable range of
                      tnDcmCardProgrammedCompensationDistance for 1830
                      from (10, 140) to (10, 240) and added 160, 180,
                      200, 220, and 240 as possible values.
                   2) Added the following values to
                      tnDcmCardProvisionedFiberType:
                      ssmfb(4),
                      eleafb(5)."

      REVISION    "201010241200Z"
      DESCRIPTION "Added the following to tnWssCardTable:
                   tnWssCardLnsEnable
                   tnWssCardLnsPower."

      REVISION    "201009281200Z"
      DESCRIPTION "Added the following table:
                   tn11dpe12eCardTable."

      REVISION    "201007291200Z"
      DESCRIPTION "Added the following table:
                   tnOpsaCardTable."

      REVISION    "201005101200Z"
      DESCRIPTION "1) Added the following to tn11dpge12CardRateMode:
                      qinqRate(3).
                   2) Added the following to tn11dpge12CardTable:
                      tn11dpge12QINQModeTPID."

      REVISION    "201001271200Z"
      DESCRIPTION "Added the following to tnDcmCardTable:
                   tnDcmCardProvisionedFiberType."

      REVISION    "201001251200Z"
      DESCRIPTION "Added values of 130 and 140 to
                   tnDcmCardProgrammedCompensationDistance."

      REVISION    "201001081200Z"
      DESCRIPTION "Updated description of tn4dpa4CardFunctionMode."

      REVISION    "200909261200Z"
      DESCRIPTION "Added the following table:
                   tn4dpa4CardTable."

      REVISION    "200908051200Z"
      DESCRIPTION "Removed tnItlbCardTable."

      REVISION    "200906221200Z"
      DESCRIPTION "Updated range of tnWssCardAddPathTotalChannel
                   for CWR8 and CWR8-88."

      REVISION    "200905311200Z"
      DESCRIPTION "Renamed tnSfcCardOneFiberMode to tnSfcCardFiberMode
                   and added default value."

      REVISION    "200905191200Z"
      DESCRIPTION "Added the following to tnSfcCardTable:
                   tnSfcCardOneFiberMode."

      REVISION    "200904301200Z"
      DESCRIPTION "Updated description of tnWssCardAddPathTotalChannel
                   for 88 channels."

      REVISION    "200904231200Z"
      DESCRIPTION "Added the following table:
                   tn11dpge12CardTable."

      REVISION    "200904071200Z"
      DESCRIPTION "Added the following table:
                   tnItlbCardTable."

      REVISION    "200903251200Z"
      DESCRIPTION "Added values of 90 to 120 to
                   tnDcmCardProgrammedCompensationDistance."

      REVISION    "200807251200Z"
      DESCRIPTION "Added the resource allocation management tables."

      REVISION    "200806091200Z"
      DESCRIPTION "Updated the descriptions of the following:
                   tnDcmCardProgrammedCompensationDistance
                   and tnDcmCardPresentCompensationDistance."

      REVISION    "200805291200Z"
      DESCRIPTION "1) Renamed tnDcmCardCompensationDistance to tnDcmCardSize.
                   2) Added the following to tnDcmCardTable:
                      tnDcmCardTotalDispTilt
                      tnDcmCardDispFiberLength
                      tnDcmCardPMD."

      REVISION    "200804111200Z"
      DESCRIPTION "Added remote inventory for the DCM and SFD cards."

      REVISION    "200802161200Z"
      DESCRIPTION "1) Updated the optical card MIB description.
                   2) Added the add path total channel and reserved
                      degree attributes to tnWssCardTable."

      ::= { tnCardModules 5 }

  tnOpticalCardConf        OBJECT IDENTIFIER ::= { tnOpticalCardMIB 1 }
  tnOpticalCardGroups      OBJECT IDENTIFIER ::= { tnOpticalCardConf 1 }
  tnOpticalCardCompliances OBJECT IDENTIFIER ::= { tnOpticalCardConf 2 }
  tnOpticalCardObjs        OBJECT IDENTIFIER ::= { tnOpticalCardMIB 2 }
--  obsolete
--  tnOpticalCardEvents      OBJECT IDENTIFIER ::= { tnOpticalCardMIB 3 }

-------------------------------------------------------------------------------
-- Optical Card Textual Conventions
-------------------------------------------------------------------------------
    AluWdmSonetSdhPpSectionIfType ::= TEXTUAL-CONVENTION
        STATUS         current
        DESCRIPTION    "VTS source."
        SYNTAX         INTEGER {
                         none(1),
                         oc3(2),
                         oc12(3),
                         oc48(4),
                         stm1(5),
                         stm4(6),
                         stm16(7)
                       }

    AluWdmPcsSectionIfType ::= TEXTUAL-CONVENTION
        STATUS         current
        DESCRIPTION    "VTS source."
        SYNTAX         INTEGER {
                         none(1),
                         gige(2),
                         fc100(3),
                         fc200(4),
                         fc400(5)
                       }

    TropicSfdInvPortLoss  ::= TEXTUAL-CONVENTION
        DISPLAY-HINT   "4a"
        STATUS         current
        DESCRIPTION    "Readable SFD Port Loss Type string."
        SYNTAX         OCTET STRING (SIZE(0..5))

    TropicSfdInvFiberLength ::= TEXTUAL-CONVENTION
        DISPLAY-HINT   "2a.1a"
        STATUS         current
        DESCRIPTION    "Fiber Length, in centimetres (0.01m)."
        SYNTAX         OCTET STRING (SIZE(0..6))

    TropicDcmInvFiberType  ::= TEXTUAL-CONVENTION
        DISPLAY-HINT   "4a"
        STATUS         current
        DESCRIPTION    "Readable DCM Fiber Type string."
        SYNTAX         OCTET STRING (SIZE(0..5))

    TropicDcmInvDcmSize ::= TEXTUAL-CONVENTION
        DISPLAY-HINT   "3a.1a"
        STATUS         current
        DESCRIPTION    "Readable DCM transmission fiber length string (unit: km)."
        SYNTAX         OCTET STRING (SIZE(0..5))

    TropicDcmInvInsertionLoss ::= TEXTUAL-CONVENTION
        DISPLAY-HINT   "2a.1a"
        STATUS         current
        DESCRIPTION    "Readable insertion loss string (unit: dB)."
        SYNTAX         OCTET STRING (SIZE(0..5))

    TropicDcmInvInsertionLossSlope ::= TEXTUAL-CONVENTION
        DISPLAY-HINT   "2a.1a"
        STATUS         current
        DESCRIPTION    "Readable insertion loss slope string (unit: dB).
                        The format is [+-]x.x"
        SYNTAX         OCTET STRING (SIZE(0..5))

    TropicDcmInvDispersionFit ::= TEXTUAL-CONVENTION
        DISPLAY-HINT   "40a"
        STATUS         current
        DESCRIPTION    "Readable DCM dispersion fit string. The format is
                        [+-]x.xxxE[+-]xx[+-]x.xxxE[+-]xx[+-]x.xxxE[+-]xx[+-]x.xxxE[+-]xx"
        SYNTAX         OCTET STRING (SIZE(0..41))

    TropicDcmInvFiberLength ::= TEXTUAL-CONVENTION
        DISPLAY-HINT   "2a.1a"
        STATUS         current
        DESCRIPTION    "Readable string for dispersion fiber length inside DCM
                        module (unit: km)."
        SYNTAX         OCTET STRING (SIZE(0..5))

    TropicDcmInvPmd ::= TEXTUAL-CONVENTION
        DISPLAY-HINT   "2a.1a"
        STATUS         current
        DESCRIPTION    "Readable DCM Polarization Mode Dispersion Type string
                        (unit: ps)."
        SYNTAX         OCTET STRING (SIZE(0..5))

    TropicDcmInvLatencyMismatch ::= TEXTUAL-CONVENTION
        DISPLAY-HINT   "2a.1a"
        STATUS         current
        DESCRIPTION    "Readable DCM Latency Mismatch string.
                        The format is [+-]x.x"
        SYNTAX         OCTET STRING (SIZE(0..5))

    TropicDcmInvLatency ::= TEXTUAL-CONVENTION
        DISPLAY-HINT   "2a.1a"
        STATUS         current
        DESCRIPTION    "Readable DCM Latency.
                        The format is [+-]x.x"
        SYNTAX         OCTET STRING (SIZE(0..5))

--------------------------------------------------------------------------------
-- Optical Card Scalars
--------------------------------------------------------------------------------
    tnOpticalCardTotal OBJECT-TYPE
        SYNTAX         Integer32
        MAX-ACCESS     read-only
        STATUS         current
        DESCRIPTION    "The total number of optical card records
                        allocated on a 1696ROADM/1830 NE."
        ::= { tnOpticalCardObjs 1 }

--    obsolete
--    tnBandFilterCardTable    OBJECT-TYPE ::= { tnOpticalCardObjs 2 }
--    tnChannelFilterCardTable OBJECT-TYPE ::= { tnOpticalCardObjs 3 }

--------------------------------------------------------------------------------
-- DCM Card Table
--------------------------------------------------------------------------------
    tnDcmCardTable OBJECT-TYPE
        SYNTAX         SEQUENCE OF TnDcmCardEntry
        MAX-ACCESS     not-accessible
        STATUS         current
        DESCRIPTION    "A table of DCM card specific attributes."
        ::= { tnOpticalCardObjs 4 }

    tnDcmCardEntry OBJECT-TYPE
        SYNTAX         TnDcmCardEntry
        MAX-ACCESS     not-accessible
        STATUS         current
        DESCRIPTION    "."
        INDEX { tnShelfIndex,
                tnSlotIndex }
        ::= { tnDcmCardTable 1 }

    TnDcmCardEntry ::= SEQUENCE {
        tnDcmCardProgrammedCompensationDistance Unsigned32,
        tnDcmCardPresentCompensationDistance Unsigned32,
        tnDcmCardSize                        SnmpAdminString,
        tnDcmCardFiberType                   SnmpAdminString,
        tnDcmCardAverageInsertionLoss        SnmpAdminString,
        tnDcmCardInsertionLossSlope          SnmpAdminString,
        tnDcmCardAverageInsertionLossPad     SnmpAdminString,
        tnDcmCardInsertionLossSlopePad       SnmpAdminString,
        tnDcmCardTotalDispTilt               SnmpAdminString,
        tnDcmCardDispFiberLength             SnmpAdminString,
        tnDcmCardPMD                         SnmpAdminString,
        tnDcmCardProvisionedFiberType        INTEGER
    }

    tnDcmCardProgrammedCompensationDistance OBJECT-TYPE
        SYNTAX         Unsigned32
        UNITS          "km"
        MAX-ACCESS     read-create
        STATUS         current
        DESCRIPTION    "The programmed compensation distance
                        associated with this DCM card.

                        Current configurable range 1696R: 15 to 100.
                        Possible programmed values are 15, 40, 60, 80
                        and 100.  A value of 0 indicates that the
                        distance is not defined.

                        Current configurable range 1830: 10 to 240.
                        Possible programmed values are 5, 10, 15, 20, 25, 30, 35, 40,
                        50, 60, 70, 80, 90, 100, 110, 120, 130, and 140,
                        160, 180, 200, 220, and 240.  A value of 0
                        indicates that the distance is not defined."
        DEFVAL         { 0 }
        ::= { tnDcmCardEntry 1 }

    tnDcmCardPresentCompensationDistance OBJECT-TYPE
        SYNTAX         Unsigned32
        UNITS          "km"
        MAX-ACCESS     read-only
        STATUS         current
        DESCRIPTION    "The present compensation distance associated
                        with this DCM card.  Not applicable to the 1830
                        PSS-32."
        ::= { tnDcmCardEntry 2 }

    tnDcmCardSize OBJECT-TYPE
        SYNTAX         SnmpAdminString (SIZE(0..255))
        MAX-ACCESS     read-only
        STATUS         current
        DESCRIPTION    "The length of TRANSMISSION fiber that the DCM is
                        designed to compensate (unit:km)."
        DEFVAL         { "" }
        ::= { tnDcmCardEntry 3 }

    tnDcmCardFiberType OBJECT-TYPE
        SYNTAX         SnmpAdminString (SIZE(0..255))
        MAX-ACCESS     read-only
        STATUS         current
        DESCRIPTION    "The type of fiber that the DCM is designed to
                        dispersion-compensate."
        DEFVAL         { "" }
        ::= { tnDcmCardEntry 4 }

    tnDcmCardAverageInsertionLoss OBJECT-TYPE
        SYNTAX         SnmpAdminString (SIZE(0..255))
        MAX-ACCESS     read-only
        STATUS         current
        DESCRIPTION    "The measured insertion loss averaged over
                        wavelength with no external attenuation added to
                        the DCM (unit:dB)."
        DEFVAL         { "" }
        ::= { tnDcmCardEntry 5 }

    tnDcmCardInsertionLossSlope OBJECT-TYPE
        SYNTAX         SnmpAdminString (SIZE(0..255))
        MAX-ACCESS     read-only
        STATUS         current
        DESCRIPTION    "A linear least-squares fitted slope of the
                        measured attenuation (positive or negative) over
                        the wavelength range with no external attenuation
                        added to the DCM (unit: dB). The slope is defined
                        over the full wavelength range with a negative
                        slope signifying a higher insertion loss at the
                        lower wavelength."
        DEFVAL         { "" }
        ::= { tnDcmCardEntry 6 }

    tnDcmCardAverageInsertionLossPad OBJECT-TYPE
        SYNTAX         SnmpAdminString (SIZE(0..255))
        MAX-ACCESS     read-only
        STATUS         current
        DESCRIPTION    "The measured insertion loss averaged over
                        wavelength with external attenuation added to
                        the DCM (unit: dB)."
        DEFVAL         { "" }
        ::= { tnDcmCardEntry 7 }

    tnDcmCardInsertionLossSlopePad OBJECT-TYPE
        SYNTAX         SnmpAdminString (SIZE(0..255))
        MAX-ACCESS     read-only
        STATUS         current
        DESCRIPTION    "A linear least-squares fitted slope of the
                        measured attenuation (positive or negative) over
                        the wavelength range with external attenuation
                        added to the DCM (unit: dB).  The slope is defined
                        over the full wavelength range with a negative
                        slope signifying a higher insertion loss at the
                        lower wavelength."
        DEFVAL         { "" }
        ::= { tnDcmCardEntry 8 }

    tnDcmCardTotalDispTilt OBJECT-TYPE
        SYNTAX         SnmpAdminString (SIZE(0..255))
        MAX-ACCESS     read-only
        STATUS         current
        DESCRIPTION    "Coefficients A, B, C and D of a 3rd order
                        polynomial fit of Chromatic dispersion vs.
                        wavelength from 1528 to 1565nm in 0.4-2.0nm steps
                        such that TotalDispersion =
                        A*(l-1546)3 + B*(l-1546)2 + C*(l-1546) + D."
        DEFVAL         { "" }
        ::= { tnDcmCardEntry 9 }

    tnDcmCardDispFiberLength OBJECT-TYPE
        SYNTAX         SnmpAdminString (SIZE(0..255))
        MAX-ACCESS     read-only
        STATUS         current
        DESCRIPTION    "The total length of dispersion fiber inside the
                        DCM module, to the closest km."
        DEFVAL         { "" }
        ::= { tnDcmCardEntry 10 }

    tnDcmCardPMD OBJECT-TYPE
        SYNTAX         SnmpAdminString (SIZE(0..255))
        MAX-ACCESS     read-only
        STATUS         current
        DESCRIPTION    "The value for Polarization mode dispersion
                        (unit: ps)."
        DEFVAL         { "" }
        ::= { tnDcmCardEntry 11 }

    tnDcmCardProvisionedFiberType OBJECT-TYPE
        SYNTAX         INTEGER {
                         ssmf(1),
                         eleaf(2),
                         twrs(3),
                         ssmfb(4),
                         eleafb(5),
                         smfp(6)
                       }
        MAX-ACCESS     read-create
        STATUS         current
        DESCRIPTION    "The type of fiber that the DCM is provisioned to
                        dispersion-compensate."
        DEFVAL         { ssmf }
        ::= { tnDcmCardEntry 12 }

--    obsolete
--    tnChannelAddDropCardTable OBJECT-TYPE ::= { tnOpticalCardObjs 5 }
--    tnExternalDcuCardTable    OBJECT-TYPE ::= { tnOpticalCardObjs 6 }
--    tnBroadbandCardTable      OBJECT-TYPE ::= { tnOpticalCardObjs 7 }

--------------------------------------------------------------------------------
-- Power Control Card Table
--------------------------------------------------------------------------------
    tnPowerControlCardTable OBJECT-TYPE
        SYNTAX         SEQUENCE OF TnPowerControlCardEntry
        MAX-ACCESS     not-accessible
        STATUS         current
        DESCRIPTION    "A table of Power Control card specific attributes."
        ::= { tnOpticalCardObjs 8 }

    tnPowerControlCardEntry OBJECT-TYPE
        SYNTAX         TnPowerControlCardEntry
        MAX-ACCESS     not-accessible
        STATUS         current
        DESCRIPTION    "."
        INDEX { tnShelfIndex,
                tnSlotIndex }
        ::= { tnPowerControlCardTable 1 }

    TnPowerControlCardEntry ::= SEQUENCE {
        tnPowerControlCardCapabilityProgrammed TruthValue,
        tnPowerControlCardCapabilityPresent    TruthValue,
        tnPowerControlCardCapabilityInUse      TruthValue
    }

    tnPowerControlCardCapabilityProgrammed OBJECT-TYPE
        SYNTAX         TruthValue
        MAX-ACCESS     read-create
        STATUS         current
        DESCRIPTION    "The Power Control card programmed capability."
        DEFVAL         { true }
        ::= { tnPowerControlCardEntry 1 }

    tnPowerControlCardCapabilityPresent OBJECT-TYPE
        SYNTAX         TruthValue
        MAX-ACCESS     read-only
        STATUS         current
        DESCRIPTION    "The Power Control card capability present."
        DEFVAL         { true }
        ::= { tnPowerControlCardEntry 2 }

    tnPowerControlCardCapabilityInUse OBJECT-TYPE
        SYNTAX         TruthValue
        MAX-ACCESS     read-only
        STATUS         current
        DESCRIPTION    "Indicates if the Power Control card capability
                        is in use by the system for services."
        ::= { tnPowerControlCardEntry 3 }

--------------------------------------------------------------------------------
-- WSS Card Table
--------------------------------------------------------------------------------
    tnWssCardTable OBJECT-TYPE
        SYNTAX         SEQUENCE OF TnWssCardEntry
        MAX-ACCESS     not-accessible
        STATUS         current
        DESCRIPTION    "A table of WSS card specific attributes."
        ::= { tnOpticalCardObjs 9 }

    tnWssCardEntry OBJECT-TYPE
        SYNTAX         TnWssCardEntry
        MAX-ACCESS     not-accessible
        STATUS         current
        DESCRIPTION    "."
        INDEX { tnShelfIndex,
                tnSlotIndex }
        ::= { tnWssCardTable 1 }

    TnWssCardEntry ::= SEQUENCE {
        tnWssCardAddPathTargetPower  Integer32,
        tnWssCardAddPathEgressPower  Integer32,
        tnWssCardAddPathTotalChannel Unsigned32,
        tnWssCardReservedDegree      Unsigned32,
        tnWssCardLnsEnable           INTEGER,
        tnWssCardLnsPower            Integer32,
--        obsolete
--        tnWssCardIsAdBlockAdd        TruthValue,
--        tnWssCardIsAdBlockDrop       TruthValue,
        tnWssCardAdBlockLevelAdd     Unsigned32,
        tnWssCardAdBlockLevelDrop    Unsigned32,
        tnWssCardIsFlexgrid       Unsigned32,
        tnWssCardGranularityMHz   Integer32,
        tnWssCardEnableFilterlessDge TruthValue
    }

    tnWssCardAddPathTargetPower OBJECT-TYPE
        SYNTAX         Integer32
        UNITS          "mBm"
        MAX-ACCESS     read-create
        STATUS         current
        DESCRIPTION    "The desired power at the output of the amplet
                        inside the WSS.

                        Current configurable range: -1000 to 1000."
        DEFVAL         { 130 }
        ::= { tnWssCardEntry 1 }

    tnWssCardAddPathEgressPower OBJECT-TYPE
        SYNTAX         Integer32
        UNITS          "mBm"
        MAX-ACCESS     read-create
        STATUS         current
        DESCRIPTION    "The desired output power for add services as
                        they come out the WDM port.

                        Current configurable range: -3500 to 1100."
        DEFVAL         { -900 }
        ::= { tnWssCardEntry 2 }

    tnWssCardAddPathTotalChannel OBJECT-TYPE
        SYNTAX         Unsigned32
        MAX-ACCESS     read-create
        STATUS         current
        DESCRIPTION    "The maximum number of channels supported on the
                        add path.

                        Current configurable ranges:

                        CWR8:    8 to 44
                        CWR8-88: 8 to 88."
        DEFVAL         { 12 }
        ::= { tnWssCardEntry 3 }

    tnWssCardReservedDegree OBJECT-TYPE
        SYNTAX         Unsigned32
        MAX-ACCESS     read-create
        STATUS         current
        DESCRIPTION    "The reserved degree.

                        Current configurable ranges:

                        CWR8:    1 to 8
                        CWR8-88: 1 to 8
                        WR2:     1 to 2  -- pre-R5.1
                        WR2-88:  1 to 2  -- R5.1
                        WR8-88A: 1 to 8."
        DEFVAL         { 2 }
        ::= { tnWssCardEntry 4 }

    tnWssCardLnsEnable OBJECT-TYPE
        SYNTAX         INTEGER {
                         on(1),
                         off(2)
                       }
        MAX-ACCESS     read-create
        STATUS         current
        DESCRIPTION    "The flag to turn on/off the LNS laser."
        DEFVAL         { off }
        ::= { tnWssCardEntry 5 }

    tnWssCardLnsPower OBJECT-TYPE
        SYNTAX         Integer32
        UNITS          "mBm"
        MAX-ACCESS     read-only
        STATUS         current
        DESCRIPTION    "The output power of the LNS laser.

                        Current range: -9900 to 1000."
        ::= { tnWssCardEntry 6 }

--    obsolete
--    tnWssCardIsAdBlockAdd  OBJECT-TYPE ::= { tnWssCardEntry 7 }
--    tnWssCardIsAdBlockDrop OBJECT-TYPE ::= { tnWssCardEntry 8 }

    tnWssCardAdBlockLevelAdd OBJECT-TYPE
        SYNTAX         Unsigned32 (0..3)
        MAX-ACCESS     read-create
        STATUS         current
        DESCRIPTION    "Current configurable values:
                        CWR8-88: 0, 3.
                        WR8-88A: 0, 1, 2.
                        WR20-TF: 0."
        DEFVAL         { 0 }
        ::= { tnWssCardEntry 9 }

    tnWssCardAdBlockLevelDrop OBJECT-TYPE
        SYNTAX         Unsigned32 (0..3)
        MAX-ACCESS     read-create
        STATUS         current
        DESCRIPTION    "Current configurable values:
                        CWR8-88: 0, 3.
                        WR8-88A: 0, 1, 2.
                        WR20-TF: 0."
        DEFVAL         { 0 }
        ::= { tnWssCardEntry 10 }

    tnWssCardIsFlexgrid OBJECT-TYPE
        SYNTAX         Unsigned32 (0..1)
        UNITS          "MHz"
        MAX-ACCESS     read-only
        STATUS         current
        DESCRIPTION    "Indicates if the card Wavelength Selective Switch(es)
                        supports flexible frequency slices.

                        Defval:
                        1 for WR8-88AF, WR20-TF, WR20-TFM, WR20TFML.
                        0 for all others."
        ::= { tnWssCardEntry 11 }

    tnWssCardGranularityMHz OBJECT-TYPE
        SYNTAX         Integer32
        UNITS          "MHz"
        MAX-ACCESS     read-only
        STATUS         current
        DESCRIPTION    "Indicates the granularity (minimum slice size multiple)
                        of the card Wavelength Selective Switch(es).

                        If tnFlexgridOtsInfoLineWssIsFlexgrid is true, the
                        upper frequency edge of a slice aligns with reference
                        193.1 THz for n=0 (ITU G.694.1).

                        If tnFlexgridOtsInfoLineWssIsFlexgrid is false, the
                        granularity is the channel slot width centered on the
                        regular ITU grid implied by the granularity.

                        Values in MHz. Should be displayed in user interfaces in GHz.

                        Defval:
                        CWR8 = 100000
                        CWR8-88 = 50000
                        WR2-88 = 50000
                        WR8-88A = 50000
                        WR8-88AF = 12500
                        WR20-TF = 6250
                        WR20-TFM = 6250
                        WR20TFML = 6250
                        IROADM = 50000"
        ::= { tnWssCardEntry 12 }

    tnWssCardEnableFilterlessDge OBJECT-TYPE
        SYNTAX         TruthValue
        MAX-ACCESS     read-create
        STATUS         current
        DESCRIPTION    "Sets the Dynamic Gain Equalizer functionality
                        to regular or filterless mode.Supported for
                        WR20-TF, WR20-TFM, WR20TFML cards. Changing
                        value in-service is service affecting."
        DEFVAL         { false }
        ::= { tnWssCardEntry 13 }

--------------------------------------------------------------------------------
-- SFD Card Table
--------------------------------------------------------------------------------
    tnSfdCardTable OBJECT-TYPE
        SYNTAX         SEQUENCE OF TnSfdCardEntry
        MAX-ACCESS     not-accessible
        STATUS         current
        DESCRIPTION    "A table of SFD card specific attributes."
        ::= { tnOpticalCardObjs 10 }

    tnSfdCardEntry OBJECT-TYPE
        SYNTAX         TnSfdCardEntry
        MAX-ACCESS     not-accessible
        STATUS         current
        DESCRIPTION    "."
        INDEX { tnShelfIndex,
                tnSlotIndex }
        ::= { tnSfdCardTable 1 }

    TnSfdCardEntry ::= SEQUENCE {
        tnSfdCardAverageMuxInsertionLoss   SnmpAdminString,
        tnSfdCardAverageDemuxInsertionLoss SnmpAdminString
    }

    tnSfdCardAverageMuxInsertionLoss OBJECT-TYPE
        SYNTAX         SnmpAdminString (SIZE(0..255))
        MAX-ACCESS     read-only
        STATUS         current
        DESCRIPTION    "."
        DEFVAL         { "" }
        ::= { tnSfdCardEntry 1 }

    tnSfdCardAverageDemuxInsertionLoss OBJECT-TYPE
        SYNTAX         SnmpAdminString (SIZE(0..255))
        MAX-ACCESS     read-only
        STATUS         current
        DESCRIPTION    "."
        DEFVAL         { "" }
        ::= { tnSfdCardEntry 2 }

--------------------------------------------------------------------------------
-- SONET/SDH PP Section Card Table
--------------------------------------------------------------------------------
    tnSonetSdhPpSectionCardTable OBJECT-TYPE
        SYNTAX         SEQUENCE OF TnSonetSdhPpSectionCardEntry
        MAX-ACCESS     not-accessible
        STATUS         current
        DESCRIPTION    "SONET/SDH PP Section resource allocation."
        ::= { tnOpticalCardObjs 11 }

    tnSonetSdhPpSectionCardEntry OBJECT-TYPE
        SYNTAX         TnSonetSdhPpSectionCardEntry
        MAX-ACCESS     not-accessible
        STATUS         current
        DESCRIPTION    "."
        INDEX { tnShelfIndex,
                tnSlotIndex }
        ::= { tnSonetSdhPpSectionCardTable 1 }

    TnSonetSdhPpSectionCardEntry ::= SEQUENCE {
        tnSonetSdhPpSection1Port   Unsigned32,
        tnSonetSdhPpSection2Port   Unsigned32,
        tnSonetSdhPpSection3Port   Unsigned32,
        tnSonetSdhPpSection4Port   Unsigned32,
        tnSonetSdhPpSection5Port   Unsigned32,
        tnSonetSdhPpSection6Port   Unsigned32,
        tnSonetSdhPpSection7Port   Unsigned32,
        tnSonetSdhPpSection8Port   Unsigned32,
        tnSonetSdhPpSection1IfType AluWdmSonetSdhPpSectionIfType,
        tnSonetSdhPpSection2IfType AluWdmSonetSdhPpSectionIfType,
        tnSonetSdhPpSection3IfType AluWdmSonetSdhPpSectionIfType,
        tnSonetSdhPpSection4IfType AluWdmSonetSdhPpSectionIfType,
        tnSonetSdhPpSection5IfType AluWdmSonetSdhPpSectionIfType,
        tnSonetSdhPpSection6IfType AluWdmSonetSdhPpSectionIfType,
        tnSonetSdhPpSection7IfType AluWdmSonetSdhPpSectionIfType,
        tnSonetSdhPpSection8IfType AluWdmSonetSdhPpSectionIfType
    }

    tnSonetSdhPpSection1Port OBJECT-TYPE
        SYNTAX         Unsigned32
        MAX-ACCESS     read-only
        STATUS         current
        DESCRIPTION    "."
        ::= { tnSonetSdhPpSectionCardEntry 1 }

    tnSonetSdhPpSection2Port OBJECT-TYPE
        SYNTAX         Unsigned32
        MAX-ACCESS     read-only
        STATUS         current
        DESCRIPTION    "."
        ::= { tnSonetSdhPpSectionCardEntry 2 }

    tnSonetSdhPpSection3Port OBJECT-TYPE
        SYNTAX         Unsigned32
        MAX-ACCESS     read-only
        STATUS         current
        DESCRIPTION    "."
        ::= { tnSonetSdhPpSectionCardEntry 3 }

    tnSonetSdhPpSection4Port OBJECT-TYPE
        SYNTAX         Unsigned32
        MAX-ACCESS     read-only
        STATUS         current
        DESCRIPTION    "."
        ::= { tnSonetSdhPpSectionCardEntry 4 }

    tnSonetSdhPpSection5Port OBJECT-TYPE
        SYNTAX         Unsigned32
        MAX-ACCESS     read-only
        STATUS         current
        DESCRIPTION    "."
        ::= { tnSonetSdhPpSectionCardEntry 5 }

    tnSonetSdhPpSection6Port OBJECT-TYPE
        SYNTAX         Unsigned32
        MAX-ACCESS     read-only
        STATUS         current
        DESCRIPTION    "."
        ::= { tnSonetSdhPpSectionCardEntry 6 }

    tnSonetSdhPpSection7Port OBJECT-TYPE
        SYNTAX         Unsigned32
        MAX-ACCESS     read-only
        STATUS         current
        DESCRIPTION    "."
        ::= { tnSonetSdhPpSectionCardEntry 7 }

    tnSonetSdhPpSection8Port OBJECT-TYPE
        SYNTAX         Unsigned32
        MAX-ACCESS     read-only
        STATUS         current
        DESCRIPTION    "."
        ::= { tnSonetSdhPpSectionCardEntry 8 }

    tnSonetSdhPpSection1IfType OBJECT-TYPE
        SYNTAX         AluWdmSonetSdhPpSectionIfType
        MAX-ACCESS     read-only
        STATUS         current
        DESCRIPTION    "."
        ::= { tnSonetSdhPpSectionCardEntry 9 }

    tnSonetSdhPpSection2IfType OBJECT-TYPE
        SYNTAX         AluWdmSonetSdhPpSectionIfType
        MAX-ACCESS     read-only
        STATUS         current
        DESCRIPTION    "."
        ::= { tnSonetSdhPpSectionCardEntry 10 }

    tnSonetSdhPpSection3IfType OBJECT-TYPE
        SYNTAX         AluWdmSonetSdhPpSectionIfType
        MAX-ACCESS     read-only
        STATUS         current
        DESCRIPTION    "."
        ::= { tnSonetSdhPpSectionCardEntry 11 }

    tnSonetSdhPpSection4IfType OBJECT-TYPE
        SYNTAX         AluWdmSonetSdhPpSectionIfType
        MAX-ACCESS     read-only
        STATUS         current
        DESCRIPTION    "."
        ::= { tnSonetSdhPpSectionCardEntry 12 }

    tnSonetSdhPpSection5IfType OBJECT-TYPE
        SYNTAX         AluWdmSonetSdhPpSectionIfType
        MAX-ACCESS     read-only
        STATUS         current
        DESCRIPTION    "."
        ::= { tnSonetSdhPpSectionCardEntry 13 }

    tnSonetSdhPpSection6IfType OBJECT-TYPE
        SYNTAX         AluWdmSonetSdhPpSectionIfType
        MAX-ACCESS     read-only
        STATUS         current
        DESCRIPTION    "."
        ::= { tnSonetSdhPpSectionCardEntry 14 }

    tnSonetSdhPpSection7IfType OBJECT-TYPE
        SYNTAX         AluWdmSonetSdhPpSectionIfType
        MAX-ACCESS     read-only
        STATUS         current
        DESCRIPTION    "."
        ::= { tnSonetSdhPpSectionCardEntry 15 }

    tnSonetSdhPpSection8IfType OBJECT-TYPE
        SYNTAX         AluWdmSonetSdhPpSectionIfType
        MAX-ACCESS     read-only
        STATUS         current
        DESCRIPTION    "."
        ::= { tnSonetSdhPpSectionCardEntry 16 }

--------------------------------------------------------------------------------
-- PCS Section Card Table
--------------------------------------------------------------------------------
    tnPcsSectionCardTable OBJECT-TYPE
        SYNTAX         SEQUENCE OF TnPcsSectionCardEntry
        MAX-ACCESS     not-accessible
        STATUS         current
        DESCRIPTION    "PCS Section resource allocation."
        ::= { tnOpticalCardObjs 12 }

    tnPcsSectionCardEntry OBJECT-TYPE
        SYNTAX         TnPcsSectionCardEntry
        MAX-ACCESS     not-accessible
        STATUS         current
        DESCRIPTION    "."
        INDEX { tnShelfIndex,
                tnSlotIndex }
        ::= { tnPcsSectionCardTable 1 }

    TnPcsSectionCardEntry ::= SEQUENCE {
        tnPcsSection1Port    Unsigned32,
        tnPcsSection2Port    Unsigned32,
        tnPcsSection3Port    Unsigned32,
        tnPcsSection4Port    Unsigned32,
        tnPcsSection5Port    Unsigned32,
        tnPcsSection6Port    Unsigned32,
        tnPcsSection7Port    Unsigned32,
        tnPcsSection8Port    Unsigned32,
        tnPcsSection9Port    Unsigned32,
        tnPcsSection10Port   Unsigned32,
        tnPcsSection1IfType  AluWdmPcsSectionIfType,
        tnPcsSection2IfType  AluWdmPcsSectionIfType,
        tnPcsSection3IfType  AluWdmPcsSectionIfType,
        tnPcsSection4IfType  AluWdmPcsSectionIfType,
        tnPcsSection5IfType  AluWdmPcsSectionIfType,
        tnPcsSection6IfType  AluWdmPcsSectionIfType,
        tnPcsSection7IfType  AluWdmPcsSectionIfType,
        tnPcsSection8IfType  AluWdmPcsSectionIfType,
        tnPcsSection9IfType  AluWdmPcsSectionIfType,
        tnPcsSection10IfType AluWdmPcsSectionIfType
    }

    tnPcsSection1Port OBJECT-TYPE
        SYNTAX         Unsigned32
        MAX-ACCESS     read-only
        STATUS         current
        DESCRIPTION    "."
        ::= { tnPcsSectionCardEntry 1 }

    tnPcsSection2Port OBJECT-TYPE
        SYNTAX         Unsigned32
        MAX-ACCESS     read-only
        STATUS         current
        DESCRIPTION    "."
        ::= { tnPcsSectionCardEntry 2 }

    tnPcsSection3Port OBJECT-TYPE
        SYNTAX         Unsigned32
        MAX-ACCESS     read-only
        STATUS         current
        DESCRIPTION    "."
        ::= { tnPcsSectionCardEntry 3 }

    tnPcsSection4Port OBJECT-TYPE
        SYNTAX         Unsigned32
        MAX-ACCESS     read-only
        STATUS         current
        DESCRIPTION    "."
        ::= { tnPcsSectionCardEntry 4 }

    tnPcsSection5Port OBJECT-TYPE
        SYNTAX         Unsigned32
        MAX-ACCESS     read-only
        STATUS         current
        DESCRIPTION    "."
        ::= { tnPcsSectionCardEntry 5 }

    tnPcsSection6Port OBJECT-TYPE
        SYNTAX         Unsigned32
        MAX-ACCESS     read-only
        STATUS         current
        DESCRIPTION    "."
        ::= { tnPcsSectionCardEntry 6 }

    tnPcsSection7Port OBJECT-TYPE
        SYNTAX         Unsigned32
        MAX-ACCESS     read-only
        STATUS         current
        DESCRIPTION    "."
        ::= { tnPcsSectionCardEntry 7 }

    tnPcsSection8Port OBJECT-TYPE
        SYNTAX         Unsigned32
        MAX-ACCESS     read-only
        STATUS         current
        DESCRIPTION    "."
        ::= { tnPcsSectionCardEntry 8 }

    tnPcsSection9Port OBJECT-TYPE
        SYNTAX         Unsigned32
        MAX-ACCESS     read-only
        STATUS         current
        DESCRIPTION    "."
        ::= { tnPcsSectionCardEntry 9 }

    tnPcsSection10Port OBJECT-TYPE
        SYNTAX         Unsigned32
        MAX-ACCESS     read-only
        STATUS         current
        DESCRIPTION    "."
        ::= { tnPcsSectionCardEntry 10 }

    tnPcsSection1IfType OBJECT-TYPE
        SYNTAX         AluWdmPcsSectionIfType
        MAX-ACCESS     read-only
        STATUS         current
        DESCRIPTION    "."
        ::= { tnPcsSectionCardEntry 11 }

    tnPcsSection2IfType OBJECT-TYPE
        SYNTAX         AluWdmPcsSectionIfType
        MAX-ACCESS     read-only
        STATUS         current
        DESCRIPTION    "."
        ::= { tnPcsSectionCardEntry 12 }

    tnPcsSection3IfType OBJECT-TYPE
        SYNTAX         AluWdmPcsSectionIfType
        MAX-ACCESS     read-only
        STATUS         current
        DESCRIPTION    "."
        ::= { tnPcsSectionCardEntry 13 }

    tnPcsSection4IfType OBJECT-TYPE
        SYNTAX         AluWdmPcsSectionIfType
        MAX-ACCESS     read-only
        STATUS         current
        DESCRIPTION    "."
        ::= { tnPcsSectionCardEntry 14 }

    tnPcsSection5IfType OBJECT-TYPE
        SYNTAX         AluWdmPcsSectionIfType
        MAX-ACCESS     read-only
        STATUS         current
        DESCRIPTION    "."
        ::= { tnPcsSectionCardEntry 15 }

    tnPcsSection6IfType OBJECT-TYPE
        SYNTAX         AluWdmPcsSectionIfType
        MAX-ACCESS     read-only
        STATUS         current
        DESCRIPTION    "."
        ::= { tnPcsSectionCardEntry 16 }

    tnPcsSection7IfType OBJECT-TYPE
        SYNTAX         AluWdmPcsSectionIfType
        MAX-ACCESS     read-only
        STATUS         current
        DESCRIPTION    "."
        ::= { tnPcsSectionCardEntry 17 }

    tnPcsSection8IfType OBJECT-TYPE
        SYNTAX         AluWdmPcsSectionIfType
        MAX-ACCESS     read-only
        STATUS         current
        DESCRIPTION    "."
        ::= { tnPcsSectionCardEntry 18 }

    tnPcsSection9IfType OBJECT-TYPE
        SYNTAX         AluWdmPcsSectionIfType
        MAX-ACCESS     read-only
        STATUS         current
        DESCRIPTION    "."
        ::= { tnPcsSectionCardEntry 19 }

    tnPcsSection10IfType OBJECT-TYPE
        SYNTAX         AluWdmPcsSectionIfType
        MAX-ACCESS     read-only
        STATUS         current
        DESCRIPTION    "."
        ::= { tnPcsSectionCardEntry 20 }

--------------------------------------------------------------------------------
-- 11dpge12 Card Table
--------------------------------------------------------------------------------
    tn11dpge12CardTable OBJECT-TYPE
        SYNTAX         SEQUENCE OF Tn11dpge12CardEntry
        MAX-ACCESS     not-accessible
        STATUS         current
        DESCRIPTION    "A table of 11dpge12 card specific attributes."
        ::= { tnOpticalCardObjs 14 }

    tn11dpge12CardEntry OBJECT-TYPE
        SYNTAX         Tn11dpge12CardEntry
        MAX-ACCESS     not-accessible
        STATUS         current
        DESCRIPTION    "."
        INDEX { tnShelfIndex,
                tnSlotIndex }
        ::= { tn11dpge12CardTable 1 }

    Tn11dpge12CardEntry ::= SEQUENCE {
        tn11dpge12CardRateMode   INTEGER,
        tn11dpge12QINQModeTPID   Unsigned32
    }

    tn11dpge12CardRateMode OBJECT-TYPE
        SYNTAX         INTEGER {
                         fullRate(1),
                         subRate(2),
                         qinqRate(3)
                       }
        MAX-ACCESS     read-create
        STATUS         current
        DESCRIPTION    "The card rate mode for 11DPGE12."
        DEFVAL         { fullRate }
        ::= { tn11dpge12CardEntry 1 }

    tn11dpge12QINQModeTPID OBJECT-TYPE
        SYNTAX         Unsigned32
        MAX-ACCESS     read-create
        STATUS         current
        DESCRIPTION    "The Q in Q Mode TPID for 11DPGE12.

                        Current configurable range: 0x00 to 0xFFFF."
        DEFVAL         { "0x88a8" }
        ::= { tn11dpge12CardEntry 2 }

--------------------------------------------------------------------------------
-- SFC Card Table
--------------------------------------------------------------------------------
    tnSfcCardTable OBJECT-TYPE
        SYNTAX         SEQUENCE OF TnSfcCardEntry
        MAX-ACCESS     not-accessible
        STATUS         current
        DESCRIPTION    "A table of SFC card specific attributes."
        ::= { tnOpticalCardObjs 15 }

    tnSfcCardEntry OBJECT-TYPE
        SYNTAX         TnSfcCardEntry
        MAX-ACCESS     not-accessible
        STATUS         current
        DESCRIPTION    "."
        INDEX { tnShelfIndex,
                tnSlotIndex }
        ::= { tnSfcCardTable 1 }

    TnSfcCardEntry ::= SEQUENCE {
        tnSfcCardFiberMode            INTEGER
    }

    tnSfcCardFiberMode OBJECT-TYPE
        SYNTAX         INTEGER {
                         twoFiber(1),
                         oneFiberMux(2)
                       }
        MAX-ACCESS     read-create
        STATUS         current
        DESCRIPTION    "Fiber Mode for SFC cards."
        DEFVAL         { twoFiber }
        ::= { tnSfcCardEntry 1 }

--    obsolete
--    tn4dpa4CardTable OBJECT-TYPE ::= { tnOpticalCardObjs 16 }
--    tnOpsaCardTable  OBJECT-TYPE ::= { tnOpticalCardObjs 17 }

--------------------------------------------------------------------------------
-- 11DPE12E Card Table
--------------------------------------------------------------------------------
    tn11dpe12eCardTable OBJECT-TYPE
        SYNTAX         SEQUENCE OF Tn11dpe12eCardEntry
        MAX-ACCESS     not-accessible
        STATUS         current
        DESCRIPTION    "A table of 11DPE12E card specific attributes."
        ::= { tnOpticalCardObjs 18 }

    tn11dpe12eCardEntry OBJECT-TYPE
        SYNTAX         Tn11dpe12eCardEntry
        MAX-ACCESS     not-accessible
        STATUS         current
        DESCRIPTION    "."
        INDEX { tnShelfIndex,
                tnSlotIndex }
        ::= { tn11dpe12eCardTable 1 }

    Tn11dpe12eCardEntry ::= SEQUENCE {
        tn11dpe12eCardRateMode      INTEGER,
        tn11dpe12eQINQModeTPID1     Unsigned32,
        tn11dpe12eQINQModeTPID2     Unsigned32,
        tn11dpe12eQINQModeTPID3     Unsigned32,
        tn11dpe12eQINQModeTPID4     Unsigned32,
        tn11dpe12eQINQModeFlowCm    INTEGER
    }

    tn11dpe12eCardRateMode OBJECT-TYPE
        SYNTAX         INTEGER {
                         fullRate(1),
                         subRate(2),
                         qinqRate(3)
                       }
        MAX-ACCESS     read-create
        STATUS         current
        DESCRIPTION    "The card rate mode for 11DPE12E."
        DEFVAL         { fullRate }
        ::= { tn11dpe12eCardEntry 1 }

    tn11dpe12eQINQModeTPID1 OBJECT-TYPE
        SYNTAX         Unsigned32
        MAX-ACCESS     read-create
        STATUS         current
        DESCRIPTION    "The Q in Q Mode TPID1 for 11DPE12E.

                        Current configurable range: 0x00 to 0xFFFF."
        DEFVAL         { "0x88a8" }
        ::= { tn11dpe12eCardEntry 2 }

    tn11dpe12eQINQModeTPID2 OBJECT-TYPE
        SYNTAX         Unsigned32
        MAX-ACCESS     read-create
        STATUS         current
        DESCRIPTION    "The Q in Q Mode TPID2 for 11DPE12E.

                        Current configurable range: 0x00 to 0xFFFF."
        DEFVAL         { "0x8100" }
        ::= { tn11dpe12eCardEntry 3 }

    tn11dpe12eQINQModeTPID3 OBJECT-TYPE
        SYNTAX         Unsigned32
        MAX-ACCESS     read-create
        STATUS         current
        DESCRIPTION    "The Q in Q Mode TPID3 for 11DPE12E.

                        Current configurable range: 0x00 to 0xFFFF."
        DEFVAL         { "0x9100" }
        ::= { tn11dpe12eCardEntry 4 }

    tn11dpe12eQINQModeTPID4 OBJECT-TYPE
        SYNTAX         Unsigned32
        MAX-ACCESS     read-create
        STATUS         current
        DESCRIPTION    "The Q in Q Mode TPID4 for 11DPE12E.

                        Current configurable range: 0x00 to 0xFFFF."
        DEFVAL         { "0x9200" }
        ::= { tn11dpe12eCardEntry 5 }

    tn11dpe12eQINQModeFlowCm OBJECT-TYPE
        SYNTAX         INTEGER {
                         apspcc(1),
                         ccm(2)
                       }
        MAX-ACCESS     read-create
        STATUS         current
        DESCRIPTION    "The flow control mode for 11DPE12E."
        DEFVAL         { apspcc }
        ::= { tn11dpe12eCardEntry 6 }

--------------------------------------------------------------------------------
-- 1DPP24M Card Table
--------------------------------------------------------------------------------
    tn1dpp24mCardTable OBJECT-TYPE
        SYNTAX         SEQUENCE OF Tn1dpp24mCardEntry
        MAX-ACCESS     not-accessible
        STATUS         current
        DESCRIPTION    "A table of 1DPP24M card specific attributes."
        ::= { tnOpticalCardObjs 19 }

    tn1dpp24mCardEntry OBJECT-TYPE
        SYNTAX         Tn1dpp24mCardEntry
        MAX-ACCESS     not-accessible
        STATUS         current
        DESCRIPTION    "."
        INDEX { tnShelfIndex,
                tnSlotIndex }
        ::= { tn1dpp24mCardTable 1 }

    Tn1dpp24mCardEntry ::= SEQUENCE {
        tn1dpp24mCardFunctionMode  INTEGER,
        tn1dpp24mCardImpedance     INTEGER
    }

    tn1dpp24mCardFunctionMode OBJECT-TYPE
        SYNTAX         INTEGER {
                         master(1),
                         slave(2)
                       }
        MAX-ACCESS     read-create
        STATUS         current
        DESCRIPTION    "1DPP24M with master mode provides 21 E1 client
                          access and one line port (STM-1/OC-3).
                        The master card line port maps up to a maximum
                          of 42 E1 (21 E1 from slave card and 21 E1
                          from master card) into one STM-1/OC-3.  Clock
                          recovered from master pack's line port will
                          be used as the clock source and it will also
                          be distributed to the slave pack through the
                          back plane.
                        1DPP24M with slave mode provides only 21 E1
                          client access (line port is not in use),
                          connecting with the master card in the ESSI
                          serial bus through the backplane.  Timing
                          recovery is from the master card's L1 port."
        DEFVAL         { master }
        ::= { tn1dpp24mCardEntry 1 }

    tn1dpp24mCardImpedance OBJECT-TYPE
        SYNTAX         INTEGER {
                         imp75ohm(1),
                         imp120ohm(2)
                       }
        MAX-ACCESS     read-create
        STATUS         current
        DESCRIPTION    "Nominal impedance of E1 interfaces.  Valid values
                        are:
                        -75ohm
                        -120ohm."
        DEFVAL         { imp75ohm }
        ::= { tn1dpp24mCardEntry 2 }

--    obsolete
--    tn43sca1CardTable OBJECT-TYPE ::= { tnOpticalCardObjs 20 }

--------------------------------------------------------------------------------
-- OPS Card Table
--------------------------------------------------------------------------------
    tnOpsCardTable OBJECT-TYPE
        SYNTAX         SEQUENCE OF TnOpsCardEntry
        MAX-ACCESS     not-accessible
        STATUS         current
        DESCRIPTION    "A table of OPS optical card specific attributes."
        ::= { tnOpticalCardObjs 21 }

    tnOpsCardEntry OBJECT-TYPE
        SYNTAX         TnOpsCardEntry
        MAX-ACCESS     not-accessible
        STATUS         current
        DESCRIPTION    "."
        INDEX { tnShelfIndex,
                tnSlotIndex }
        ::= { tnOpsCardTable 1 }

    TnOpsCardEntry ::= SEQUENCE {
        tnOpsCardProtectionMode  INTEGER
    }

    tnOpsCardProtectionMode OBJECT-TYPE
        SYNTAX         INTEGER {
                         ochp(1),
                         olp(2),
                         omsp(3),
                         otup(4)
                       }
        MAX-ACCESS     read-create
        STATUS         current
        DESCRIPTION    "This attribute determines the protection mode.

                        Defaults:
                        OPSA:  ochp
                        OPSB:  otup."
        ::= { tnOpsCardEntry 1 }

--------------------------------------------------------------------------------
-- 11DPE12A Card Table
--------------------------------------------------------------------------------
    tn11dpe12aCardTable OBJECT-TYPE
        SYNTAX         SEQUENCE OF Tn11dpe12aCardEntry
        MAX-ACCESS     not-accessible
        STATUS         current
        DESCRIPTION    "A table of 11DPE12A card specific attributes."
        ::= { tnOpticalCardObjs 22 }

    tn11dpe12aCardEntry OBJECT-TYPE
        SYNTAX         Tn11dpe12aCardEntry
        MAX-ACCESS     not-accessible
        STATUS         current
        DESCRIPTION    "."
        INDEX { tnShelfIndex,
                tnSlotIndex }
        ::= { tn11dpe12aCardTable 1 }

    Tn11dpe12aCardEntry ::= SEQUENCE {
        tn11dpe12aCardRateMode                       INTEGER,
        tn11dpe12aCardQINQModeTPID1                  Unsigned32,
        tn11dpe12aCardQINQModeTPID2                  Unsigned32,
        tn11dpe12aCardQINQModeTPID3                  Unsigned32,
        tn11dpe12aCardQINQModeTPID4                  Unsigned32,
        tn11dpe12aCardLBMInterval                    Unsigned32,
        tn11dpe12aCardLBRTimeout                     Unsigned32,
        tn11dpe12aCardFlowCm                         INTEGER,
        tn11dpe12aCardSLRTimeout                     Unsigned32,
        tn11dpe12aCardCrossPackServiceSupported      INTEGER
    }

    tn11dpe12aCardRateMode OBJECT-TYPE
        SYNTAX         INTEGER {
                         fullRate(1),
                         subRate(2),
                         qinqRate(3)
                       }
        MAX-ACCESS     read-create
        STATUS         current
        DESCRIPTION    "The card rate mode for 11dpe12a."
        DEFVAL         { fullRate }
        ::= { tn11dpe12aCardEntry 1 }

    tn11dpe12aCardQINQModeTPID1 OBJECT-TYPE
        SYNTAX         Unsigned32
        MAX-ACCESS     read-create
        STATUS         current
        DESCRIPTION    "The Q in Q Mode TPID1 for 11dpe12a.

                        Current configurable range: 0x00 to 0xFFFF."
        DEFVAL         { "0x88a8" }
        ::= { tn11dpe12aCardEntry 2 }

    tn11dpe12aCardQINQModeTPID2 OBJECT-TYPE
        SYNTAX         Unsigned32
        MAX-ACCESS     read-create
        STATUS         current
        DESCRIPTION    "The Q in Q Mode TPID2 for 11dpe12a.

                        Current configurable range: 0x00 to 0xFFFF."
        DEFVAL         { "0x8100" }
        ::= { tn11dpe12aCardEntry 3 }

    tn11dpe12aCardQINQModeTPID3 OBJECT-TYPE
        SYNTAX         Unsigned32
        MAX-ACCESS     read-create
        STATUS         current
        DESCRIPTION    "The Q in Q Mode TPID3 for 11dpe12a.

                        Current configurable range: 0x00 to 0xFFFF."
        DEFVAL         { "0x9100" }
        ::= { tn11dpe12aCardEntry 4 }

    tn11dpe12aCardQINQModeTPID4 OBJECT-TYPE
        SYNTAX         Unsigned32
        MAX-ACCESS     read-create
        STATUS         current
        DESCRIPTION    "The Q in Q Mode TPID4 for 11dpe12a.

                        Current configurable range: 0x00 to 0xFFFF."
        DEFVAL         { "0x9200" }
        ::= { tn11dpe12aCardEntry 5 }

    tn11dpe12aCardLBMInterval OBJECT-TYPE
        SYNTAX         Unsigned32
        UNITS          "ms"
        MAX-ACCESS     read-create
        STATUS         current
        DESCRIPTION    "The interval between consequent LBM messages.

                        Current configurable range: 0 and [1000, 1100,
                        ..., 10000] in increment of 100."
        DEFVAL         { 1000 }
        ::= { tn11dpe12aCardEntry 6 }

    tn11dpe12aCardLBRTimeout OBJECT-TYPE
        SYNTAX         Unsigned32 (1..30)
        UNITS          "seconds"
        MAX-ACCESS     read-create
        STATUS         current
        DESCRIPTION    "LBR timeout.

                        Current configurable range: 1 to 30."
        DEFVAL         { 5 }
        ::= { tn11dpe12aCardEntry 7 }

    tn11dpe12aCardFlowCm OBJECT-TYPE
        SYNTAX         INTEGER {
                         apspcc(1),
                         ccm(2),
                         csf(3)
                       }
        MAX-ACCESS     read-create
        STATUS         current
        DESCRIPTION    "The flow control mode for 11DPE12A."
        DEFVAL         { apspcc }
        ::= { tn11dpe12aCardEntry 8 }

    tn11dpe12aCardSLRTimeout OBJECT-TYPE
        SYNTAX         Unsigned32 (1..10)
        UNITS          "seconds"
        MAX-ACCESS     read-create
        STATUS         current
        DESCRIPTION    "SLR timeout.

                        Current configurable range: 1 to 10."
        DEFVAL         { 5 }
        ::= { tn11dpe12aCardEntry 9 }

    tn11dpe12aCardCrossPackServiceSupported OBJECT-TYPE
        SYNTAX         INTEGER {
                         enable(1),
                         disable(2)
                       }
        MAX-ACCESS     read-create
        STATUS         current
        DESCRIPTION    "The cross pack service supported value for 11DPE12A."
        DEFVAL         { disable }
        ::= { tn11dpe12aCardEntry 10 }

--------------------------------------------------------------------------------
-- Card Function Mode Table
--------------------------------------------------------------------------------
    tnCardFunctionModeTable OBJECT-TYPE
        SYNTAX         SEQUENCE OF TnCardFunctionModeEntry
        MAX-ACCESS     not-accessible
        STATUS         current
        DESCRIPTION    "A table of card function mode."
        ::= { tnOpticalCardObjs 23 }

    tnCardFunctionModeEntry OBJECT-TYPE
        SYNTAX         TnCardFunctionModeEntry
        MAX-ACCESS     not-accessible
        STATUS         current
        DESCRIPTION    "."
        INDEX { tnShelfIndex,
                tnSlotIndex }
        ::= { tnCardFunctionModeTable 1 }

    TnCardFunctionModeEntry ::= SEQUENCE {
        tnCardFunctionMode  INTEGER
    }

    tnCardFunctionMode OBJECT-TYPE
        SYNTAX         INTEGER {
                         flexMux(1),
                         dualTran(2),
                         sonetSdh(3),
                         otu3(4),
                         hundredGbe(5),
                         otu4(6),
                         pTPIOCTLLocalClock(7),
                         pTPIOCTLCentralizedClock(8),
                         pTPIOCTLRelay(9),
                         pTPIOCTLLambdaConversion(10),
                         hundredGBEInterwork(11),
                         hundredGBEBkp400(12),
                         hundredGBEBjFec(13),
                         otl410(14),
                         caui(15),
                         eth100g(16),
                         otn100gbe(17),
                         otn100Gbe200Gbe(18),
                         threeX100Gbe2xOtu4(19),
                         threeX100Gbe2x100GbeBjFec(20),
                         threeX100GbeBjFec2xOtu4(21),
                         clientLine(22),
                         clientHairPin(23),
                         otn100GbeEncrypt(24),
                         none(25),
                         fst(26),
                         aes256Ctr(27),
                         aes256Gcm(28),
                         demo(29)
                       }
        MAX-ACCESS     read-create
        STATUS         current
        DESCRIPTION    "This attribute determines the card's firmware image type,
                        and therefore affects many aspects of card and port
                        behavior.  When this attribute is changed, the card will
                        be cold reset to update the firmware image.  The
                        following values are applicable to the cards specified:
                          4DPA4   - flexMux, dualTran.  Default is flexMux.
                          43SCA1  - sonetSdh, otu3.  Default is sonetSdh.
                          112SCA1 - hundredGbe, otu4.  Default is hundredGbe.
                          112SNA1 - hundredGbe, otu4.  Default is hundredGbe.
                          PTPIOC  - PTPIOCTLLocalClock, PTPIOCTLCentralizedClock,
                                    PTPIOCTLRelay, PTPIOCTLLambdaConversion.
                                    Default is PTPIOCTLLocalClock.
                          LCI2000 - eth100g , otn100gbe.  Default is eth100g.
                          6PX800  - otn100gbe , otn100Gbe200Gbe."
        ::= { tnCardFunctionModeEntry 1 }

--------------------------------------------------------------------------------
-- 112PDM11 Card Table
--------------------------------------------------------------------------------
    tn112pdm11CardTable OBJECT-TYPE
        SYNTAX         SEQUENCE OF Tn112pdm11CardEntry
        MAX-ACCESS     not-accessible
        STATUS         current
        DESCRIPTION    "A table of 112PDM11 card specific attributes."
        ::= { tnOpticalCardObjs 24 }

    tn112pdm11CardEntry OBJECT-TYPE
        SYNTAX         Tn112pdm11CardEntry
        MAX-ACCESS     not-accessible
        STATUS         current
        DESCRIPTION    "."
        INDEX { tnShelfIndex,
                tnSlotIndex }
        ::= { tn112pdm11CardTable 1 }

    Tn112pdm11CardEntry ::= SEQUENCE {
        tn112pdm11CardMaxDMNumbers      Unsigned32,
        tn112pdm11CardUsedDMNumbers     Unsigned32
    }

    tn112pdm11CardMaxDMNumbers OBJECT-TYPE
        SYNTAX         Unsigned32
        MAX-ACCESS     read-only
        STATUS         current
        DESCRIPTION    "The maximum source delay measurement (DM) number
                        that can be supported."
        DEFVAL         { 1 }
        ::= { tn112pdm11CardEntry 1 }

    tn112pdm11CardUsedDMNumbers OBJECT-TYPE
        SYNTAX         Unsigned32
        MAX-ACCESS     read-only
        STATUS         current
        DESCRIPTION    "The used source delay measurement (DM) number."
        DEFVAL         { 0 }
        ::= { tn112pdm11CardEntry 2 }

--------------------------------------------------------------------------------
-- PTPCTL Card Scalar
--------------------------------------------------------------------------------
    tnPtpctlCardAttributeTotal OBJECT-TYPE
        SYNTAX         Integer32
        MAX-ACCESS     read-only
        STATUS         current
        DESCRIPTION    "."
        ::= { tnOpticalCardObjs 25 }

--------------------------------------------------------------------------------
-- PTPCTL Card Table
--------------------------------------------------------------------------------
    tnPtpctlCardTable OBJECT-TYPE
        SYNTAX         SEQUENCE OF TnPtpctlCardEntry
        MAX-ACCESS     not-accessible
        STATUS         current
        DESCRIPTION    "A table of PTPCTL card specific attributes."
        ::= { tnOpticalCardObjs 26 }

    tnPtpctlCardEntry OBJECT-TYPE
        SYNTAX         TnPtpctlCardEntry
        MAX-ACCESS     not-accessible
        STATUS         current
        DESCRIPTION    "."
        INDEX { tnShelfIndex,
                tnSlotIndex }
        ::= { tnPtpctlCardTable 1 }

    TnPtpctlCardEntry ::= SEQUENCE {
        tnPtpctlCardEqpsLEDColor     TropicLEDColorType,
        tnPtpctlCardEqpsLEDState     TropicLEDStateType,
        tnPtpctlCardPtpLEDColor      TropicLEDColorType,
        tnPtpctlCardPtpLEDState      TropicLEDStateType
    }

    tnPtpctlCardEqpsLEDColor OBJECT-TYPE
        SYNTAX         TropicLEDColorType
        MAX-ACCESS     read-only
        STATUS         current
        DESCRIPTION    "The color of the EQPS status LED."
        ::= { tnPtpctlCardEntry 1 }

    tnPtpctlCardEqpsLEDState OBJECT-TYPE
        SYNTAX         TropicLEDStateType
        MAX-ACCESS     read-only
        STATUS         current
        DESCRIPTION    "The state of the EQPS status LED."
        ::= { tnPtpctlCardEntry 2 }

    tnPtpctlCardPtpLEDColor OBJECT-TYPE
        SYNTAX         TropicLEDColorType
        MAX-ACCESS     read-only
        STATUS         current
        DESCRIPTION    "The color of the PTP time synchronous status LED."
        ::= { tnPtpctlCardEntry 3 }

    tnPtpctlCardPtpLEDState OBJECT-TYPE
        SYNTAX         TropicLEDStateType
        MAX-ACCESS     read-only
        STATUS         current
        DESCRIPTION    "The state of the PTP time synchronous status LED."
        ::= { tnPtpctlCardEntry 4 }

--------------------------------------------------------------------------------
-- WTOCMA Card Scalar
--------------------------------------------------------------------------------
    tnWtocmaCardAttributeTotal OBJECT-TYPE
        SYNTAX         Integer32
        MAX-ACCESS     read-only
        STATUS         current
        DESCRIPTION    "."
        ::= { tnOpticalCardObjs 27 }

--------------------------------------------------------------------------------
-- WTOCMA Card Table
--------------------------------------------------------------------------------
    tnWtocmaCardTable OBJECT-TYPE
        SYNTAX         SEQUENCE OF TnWtocmaCardEntry
        MAX-ACCESS     not-accessible
        STATUS         current
        DESCRIPTION    "A table of WTOCMA card specific attributes."
        ::= { tnOpticalCardObjs 28 }

    tnWtocmaCardEntry OBJECT-TYPE
        SYNTAX         TnWtocmaCardEntry
        MAX-ACCESS     not-accessible
        STATUS         current
        DESCRIPTION    "."
        INDEX { tnShelfIndex,
                tnSlotIndex }
        ::= { tnWtocmaCardTable 1 }

    TnWtocmaCardEntry ::= SEQUENCE {
        tnWtocmaCardOsnrScan           TnCommand,
        tnWtocmaCardOsnrScanAbort      TnCommand,
        tnWtocmaCardOsnrScanStatus     INTEGER,
        tnWtocmaCardDspState           INTEGER
    }

    tnWtocmaCardOsnrScan OBJECT-TYPE
        SYNTAX         TnCommand
        MAX-ACCESS     read-create
        STATUS         current
        DESCRIPTION    "Start on-demand OSNR scan.  When read back, the
                        value of this attribute is noCmd."
        DEFVAL         { noCmd }
        ::= { tnWtocmaCardEntry 1 }

    tnWtocmaCardOsnrScanAbort OBJECT-TYPE
        SYNTAX         TnCommand
        MAX-ACCESS     read-create
        STATUS         current
        DESCRIPTION    "Abort on-demand OSNR scan.  When read back, the
                        value of this attribute is noCmd."
        DEFVAL         { noCmd }
        ::= { tnWtocmaCardEntry 2 }

    tnWtocmaCardOsnrScanStatus OBJECT-TYPE
        SYNTAX         INTEGER {
                         notInProgress(1),
                         inProgress(2),
                         waiting(3)
                       }
        MAX-ACCESS     read-only
        STATUS         current
        DESCRIPTION    "On-demand OSNR scan status."
        DEFVAL         { notInProgress }
        ::= { tnWtocmaCardEntry 3 }

    tnWtocmaCardDspState OBJECT-TYPE
        SYNTAX         INTEGER {
                         newChan(1),
                         osnr(2),
                         osnrOnDemand(3),
                         misKeyedChan(4),
                         idle(5)
                       }
        MAX-ACCESS     read-only
        STATUS         current
        DESCRIPTION    "DSP current state."
        DEFVAL         { newChan }
        ::= { tnWtocmaCardEntry 4 }


--------------------------------------------------------------------------------
-- CRU Card Scalar
--------------------------------------------------------------------------------
    tnCruCardAttributeTotal OBJECT-TYPE
        SYNTAX         Integer32
        MAX-ACCESS     read-only
        STATUS         current
        DESCRIPTION    "."
        ::= { tnOpticalCardObjs 29 }

--------------------------------------------------------------------------------
-- CRU Card Table
--------------------------------------------------------------------------------
    tnCruCardTable OBJECT-TYPE
        SYNTAX         SEQUENCE OF TnCruCardEntry
        MAX-ACCESS     not-accessible
        STATUS         current
        DESCRIPTION    "A table of CRU card specific attributes."
        ::= { tnOpticalCardObjs 30 }

    tnCruCardEntry OBJECT-TYPE
        SYNTAX         TnCruCardEntry
        MAX-ACCESS     not-accessible
        STATUS         current
        DESCRIPTION    "."
        INDEX { tnShelfIndex,
                tnSlotIndex }
        ::= { tnCruCardTable 1 }

    TnCruCardEntry ::= SEQUENCE {
        tnCruCardActivityState         INTEGER,
        tnCruCardEqpsLEDColor          TropicLEDColorType,
        tnCruCardEqpsLEDState          TropicLEDStateType,
        tnFCruProtectionRole           AluWdmFcruProtectionRoleType
    }

    tnCruCardActivityState OBJECT-TYPE
        SYNTAX         INTEGER {
                         unknown(1),
                         unequipped(2),
                         active(3),
                         standbyTrackingToActive(4),
                         standbyNotTrackingToActive(5)
                       }
        MAX-ACCESS     read-only
        STATUS         current
        DESCRIPTION    "CRU card activity states."
        DEFVAL         { unknown }
        ::= { tnCruCardEntry 1 }

    tnCruCardEqpsLEDColor OBJECT-TYPE
        SYNTAX         TropicLEDColorType
        MAX-ACCESS     read-only
        STATUS         current
        DESCRIPTION    "The color of the CRU EQPS status LED."
        ::= { tnCruCardEntry 2 }

    tnCruCardEqpsLEDState OBJECT-TYPE
        SYNTAX         TropicLEDStateType
        MAX-ACCESS     read-only
        STATUS         current
        DESCRIPTION    "The state of the CRU EQPS status LED."
        ::= { tnCruCardEntry 3 }

    tnFCruProtectionRole OBJECT-TYPE
        SYNTAX         AluWdmFcruProtectionRoleType
        MAX-ACCESS     read-create
        STATUS         current
        DESCRIPTION    "FCRU card protection role."
        DEFVAL         { unknown }
        ::= { tnCruCardEntry 4 }

--------------------------------------------------------------------------------
-- IROADM Card Config Scalar
--------------------------------------------------------------------------------
    tnIroadmCardConfigAttributeTotal OBJECT-TYPE
        SYNTAX         Integer32
        MAX-ACCESS     read-only
        STATUS         current
        DESCRIPTION    "Total number of attributes in
                        tnIroadmCardConfigTable."
        ::= { tnOpticalCardObjs 31 }

--------------------------------------------------------------------------------
-- IROADM Card Config Table
--------------------------------------------------------------------------------
    tnIroadmCardConfigTable OBJECT-TYPE
        SYNTAX         SEQUENCE OF TnIroadmCardConfigEntry
        MAX-ACCESS     not-accessible
        STATUS         current
        DESCRIPTION    "."
        ::= { tnOpticalCardObjs 32 }

    tnIroadmCardConfigEntry OBJECT-TYPE
        SYNTAX         TnIroadmCardConfigEntry
        MAX-ACCESS     not-accessible
        STATUS         current
        DESCRIPTION    "."
        INDEX { tnShelfIndex,
                tnSlotIndex }
        ::= { tnIroadmCardConfigTable 1 }

    TnIroadmCardConfigEntry ::= SEQUENCE {
        tnIroadmCardConfigOptIntDetection      INTEGER,
        tnIroadmCardConfigOptIntBaseline       Integer32,
        tnIroadmCardConfigOptIntLossThreshold  Unsigned32,
        tnIroadmCardConfigOptIntPollPeriod     Unsigned32,
        tnIroadmCardConfigOptIntClearAlarm     TnCommand
        }

    tnIroadmCardConfigOptIntDetection OBJECT-TYPE
        SYNTAX         INTEGER {
                       on(1),
                       off(2)
                       }
        MAX-ACCESS     read-create
        STATUS         current
        DESCRIPTION    "."
        DEFVAL         { off }
        ::= { tnIroadmCardConfigEntry 1 }

    tnIroadmCardConfigOptIntBaseline OBJECT-TYPE
        SYNTAX         Integer32
        UNITS          "mB"
        MAX-ACCESS     read-create
        STATUS         current
        DESCRIPTION    "Current configurable range:

                        -100, 100 to 5000."
        DEFVAL         { -100 }
        ::= { tnIroadmCardConfigEntry 2 }

    tnIroadmCardConfigOptIntLossThreshold OBJECT-TYPE
        SYNTAX         Unsigned32
        UNITS          "mB"
        MAX-ACCESS     read-create
        STATUS         current
        DESCRIPTION    "Current configurable  range:

                        100 to 500."
        DEFVAL         { 150 }
        ::= { tnIroadmCardConfigEntry 3 }

    tnIroadmCardConfigOptIntPollPeriod OBJECT-TYPE
        SYNTAX         Unsigned32
        UNITS          "seconds"
        MAX-ACCESS     read-create
        STATUS         current
        DESCRIPTION    "Current configurable range:

                        20 to 120."
        DEFVAL         { 30 }
        ::= { tnIroadmCardConfigEntry 4 }

    tnIroadmCardConfigOptIntClearAlarm OBJECT-TYPE
        SYNTAX         TnCommand
        MAX-ACCESS     read-create
        STATUS         current
        DESCRIPTION    "."
        DEFVAL         { noCmd }
        ::= { tnIroadmCardConfigEntry 5 }

--------------------------------------------------------------------------------
-- IROADM Card Info Scalar
--------------------------------------------------------------------------------
    tnIroadmCardInfoAttributeTotal OBJECT-TYPE
        SYNTAX         Integer32
        MAX-ACCESS     read-only
        STATUS         current
        DESCRIPTION    "Total no of attributes in
                        tnIroadmCardInfoTable."
        ::= { tnOpticalCardObjs 33 }

--------------------------------------------------------------------------------
-- IROADM Card Info Table
--------------------------------------------------------------------------------
    tnIroadmCardInfoTable OBJECT-TYPE
        SYNTAX         SEQUENCE OF TnIroadmCardInfoEntry
        MAX-ACCESS     not-accessible
        STATUS         current
        DESCRIPTION    "."
        ::= { tnOpticalCardObjs 34 }

    tnIroadmCardInfoEntry OBJECT-TYPE
        SYNTAX         TnIroadmCardInfoEntry
        MAX-ACCESS     not-accessible
        STATUS         current
        DESCRIPTION    "."
        INDEX { tnShelfIndex,
                tnSlotIndex }
        ::= { tnIroadmCardInfoTable 1 }

    TnIroadmCardInfoEntry ::= SEQUENCE {
        tnIroadmCardInfoIngressOAMPumpTemperature Integer32,
        tnIroadmCardInfoIngressOAMPumpBias        Integer32,
        tnIroadmCardInfoEgressOAMPumpTemperature  Integer32,
        tnIroadmCardInfoEgressOAMPumpBias         Integer32,
        tnIroadmCardInfoOptIntSpanLoss            Unsigned32,
        tnIroadmCardInfoWssIsFlexgrid             Unsigned32,
        tnIroadmCardInfoWssGranularityMHz         Integer32
        }

    tnIroadmCardInfoIngressOAMPumpTemperature OBJECT-TYPE
        SYNTAX         Integer32
        UNITS          "Celsius"
        MAX-ACCESS     read-only
        STATUS         current
        DESCRIPTION    "."
        DEFVAL         { off }
        ::= { tnIroadmCardInfoEntry 1 }

    tnIroadmCardInfoIngressOAMPumpBias OBJECT-TYPE
        SYNTAX         Integer32
        UNITS          "mA"
        MAX-ACCESS     read-only
        STATUS         current
        DESCRIPTION    "Current range:

                        -100, 100 to 5000."
        DEFVAL         { -100 }
        ::= { tnIroadmCardInfoEntry 2 }

    tnIroadmCardInfoEgressOAMPumpTemperature OBJECT-TYPE
        SYNTAX         Integer32
        UNITS          "Celsius"
        MAX-ACCESS     read-only
        STATUS         current
        DESCRIPTION    "Current range:

                        100 to 500."
        DEFVAL         { 150 }
        ::= { tnIroadmCardInfoEntry 3 }

    tnIroadmCardInfoEgressOAMPumpBias OBJECT-TYPE
        SYNTAX         Integer32
        UNITS          "mA"
        MAX-ACCESS     read-only
        STATUS         current
        DESCRIPTION    "Current range:

                        20 to 120."
        DEFVAL         { 30 }
        ::= { tnIroadmCardInfoEntry 4 }

    tnIroadmCardInfoOptIntSpanLoss OBJECT-TYPE
        SYNTAX         Unsigned32
        UNITS          "mB"
        MAX-ACCESS     read-only
        STATUS         current
        DESCRIPTION    "Current range:

                        0 to 9900."
        DEFVAL         { 9900 }
        ::= { tnIroadmCardInfoEntry 5 }

    tnIroadmCardInfoWssIsFlexgrid OBJECT-TYPE
        SYNTAX         Unsigned32 (0..1)
        UNITS          "MHz"
        MAX-ACCESS     read-only
        STATUS         current
        DESCRIPTION    "Indicates if the card Wavelength Selective Switch(es)
                        supports flexible frequency slices.

                       Defval:
                       1 for WR8-88AF, WR20-TF, WR20-TFM, WR20TFML.
                       0 for all others."
        ::= { tnIroadmCardInfoEntry 6 }

    tnIroadmCardInfoWssGranularityMHz OBJECT-TYPE
        SYNTAX         Integer32
        UNITS          "MHz"
        MAX-ACCESS     read-only
        STATUS         current
        DESCRIPTION    "Indicates the granularity (minimum slice size multiple)
                        of the card Wavelength Selective Switch(es).

                        If tnFlexgridOtsInfoLineWssIsFlexgrid is true, the
                        upper frequency edge of a slice aligns with reference
                        193.1 THz for n=0 (ITU G.694.1).

                        If tnFlexgridOtsInfoLineWssIsFlexgrid is false, the
                        granularity is the channel slot width centered on the
                        regular ITU grid implied by the granularity.

                        Values in MHz. Should be displayed in user interfaces in GHz.

                        Defval:
                        CWR8 = 100000
                        CWR8-88 = 50000
                        WR2-88 = 50000
                        WR8-88A = 50000
                        WR8-88AF = 12500
                        WR20-TF = 6250
                        WR20-TFM = 6250
                        WR20TFML = 6250
                        IROADM = 50000"
        ::= { tnIroadmCardInfoEntry 7 }

--------------------------------------------------------------------------------
-- ISON Card Info Scalar
--------------------------------------------------------------------------------
    tnIsonCardModeAttributeTotal OBJECT-TYPE
        SYNTAX         Integer32
        MAX-ACCESS     read-only
        STATUS         current
        DESCRIPTION    "Total no of attributes in
                        tnIsonCardInfoTable."
        ::= { tnOpticalCardObjs 35 }

--------------------------------------------------------------------------------
-- ISON Card Mode Table
--------------------------------------------------------------------------------
    tnIsonCardModeTable OBJECT-TYPE
        SYNTAX         SEQUENCE OF TnIsonCardModeEntry
        MAX-ACCESS     not-accessible
        STATUS         current
        DESCRIPTION    "A table of ISON card mode specific attributes."
        ::= { tnOpticalCardObjs 36 }

    tnIsonCardModeEntry OBJECT-TYPE
        SYNTAX         TnIsonCardModeEntry
        MAX-ACCESS     not-accessible
        STATUS         current
        DESCRIPTION    "."
        INDEX { tnShelfIndex,
                tnSlotIndex }
        ::= { tnIsonCardModeTable 1 }

    TnIsonCardModeEntry ::= SEQUENCE {
        tnIsonCardModeSelection         INTEGER
    }

    tnIsonCardModeSelection OBJECT-TYPE
        SYNTAX         INTEGER {
                         straight(1),
                         cross(2)
                       }
        MAX-ACCESS     read-create
        STATUS         current
        DESCRIPTION    "ISON Card selection mode."
        DEFVAL         { straight }
        ::= { tnIsonCardModeEntry 1 }

--------------------------------------------------------------------------------
-- EtherType Configuration Profile Table Scalar
--------------------------------------------------------------------------------
    tnCardEtherTypeProfileAttributeTotal OBJECT-TYPE
        SYNTAX         Integer32
        MAX-ACCESS     read-only
        STATUS         current
        DESCRIPTION    "Total no of attributes in
                        tnCardEtherTypeProfileTable."
        ::= { tnOpticalCardObjs 38 }

--------------------------------------------------------------------------------
--  EtherType Configuration Profile Table in QinQ mode
--------------------------------------------------------------------------------
    tnCardEtherTypeProfileTable OBJECT-TYPE
        SYNTAX         SEQUENCE OF TnCardEtherTypeProfileEntry
        MAX-ACCESS     not-accessible
        STATUS         current
        DESCRIPTION    "The TnEtherTypeProfileTable has an entry for each Ethernet
                        IOM card in each chassis in the TMNX system."
        ::= { tnOpticalCardObjs 39 }

    tnCardEtherTypeProfileEntry OBJECT-TYPE
        SYNTAX         TnCardEtherTypeProfileEntry
        MAX-ACCESS     not-accessible
        STATUS         current
        DESCRIPTION    "Each row entry represents an ethertype configuration profile
                        which can be associated with each ethernet port."
        INDEX { tnShelfIndex,
                tnSlotIndex,
                tnCardEthertypeQinQID }
        ::= { tnCardEtherTypeProfileTable 1 }

    TnCardEtherTypeProfileEntry ::= SEQUENCE {
        tnCardEthertypeQinQID                Integer32,
        tnCardEthertypeQinQDesc              SnmpAdminString,
        tnCardEthertypeQinQEtype             Integer32,
        tnCardEthertypeQinQRowStatus         RowStatus
    }

    tnCardEthertypeQinQID OBJECT-TYPE
        SYNTAX         Integer32 (1..128)
        MAX-ACCESS     not-accessible
        STATUS         current
        DESCRIPTION    "Ethertype profile ID in QinQ mode.  ID 1 is the default profile."
        ::= { tnCardEtherTypeProfileEntry 1 }

    tnCardEthertypeQinQDesc OBJECT-TYPE
        SYNTAX         SnmpAdminString
        MAX-ACCESS     read-create
        STATUS         current
        DESCRIPTION    "This object specifies the description of ethertype profile."
        ::= { tnCardEtherTypeProfileEntry 2 }

    tnCardEthertypeQinQEtype OBJECT-TYPE
        SYNTAX         Integer32 ('600'H..'ffff'H)
        MAX-ACCESS     read-create
        STATUS         current
        DESCRIPTION    "This object specifies the ethertype used by ethernet port."
        DEFVAL         { '8100'H }
        ::= { tnCardEtherTypeProfileEntry 3 }

    tnCardEthertypeQinQRowStatus OBJECT-TYPE
        SYNTAX         RowStatus
        MAX-ACCESS     read-create
        STATUS         current
        DESCRIPTION    "The value of tnCardEthertypeQinQRowStatus defines the status
                        of the row."
        ::= { tnCardEtherTypeProfileEntry 4 }

--------------------------------------------------------------------------------
-- AUTOMATION Config Scalar
--------------------------------------------------------------------------------
    tnAutomationConfigAttributeTotal OBJECT-TYPE
        SYNTAX         Integer32
        MAX-ACCESS     read-only
        STATUS         current
        DESCRIPTION    "Total number of attributes in tnAutomationConfigTable."
        ::= { tnOpticalCardObjs 40 }

--------------------------------------------------------------------------------
-- AUTOMATION Config Table
--------------------------------------------------------------------------------
    tnAutomationConfigTable OBJECT-TYPE
        SYNTAX         SEQUENCE OF TnAutomationConfigEntry
        MAX-ACCESS     not-accessible
        STATUS         current
        DESCRIPTION    "."
        ::= { tnOpticalCardObjs 41 }

    tnAutomationConfigEntry OBJECT-TYPE
        SYNTAX         TnAutomationConfigEntry
        MAX-ACCESS     not-accessible
        STATUS         current
        DESCRIPTION    "."
        INDEX { tnShelfIndex,
                tnSlotIndex }
        ::= { tnAutomationConfigTable 1 }

    TnAutomationConfigEntry ::= SEQUENCE {
        tnAutomationConfigAutoTopoDegreeNumber    Unsigned32
    }

    tnAutomationConfigAutoTopoDegreeNumber OBJECT-TYPE
        SYNTAX         Unsigned32
        MAX-ACCESS     read-create
        STATUS         current
        DESCRIPTION    "Current configurable range:

                        0 to 1000."
        DEFVAL         { 0 }
        ::= { tnAutomationConfigEntry 1 }

--    obsolete
--    tnCpcCardAttributeTotal OBJECT-TYPE ::= { tnOpticalCardObjs 42 }
--    tnCpcCardTable          OBJECT-TYPE ::= { tnOpticalCardObjs 43 }

--------------------------------------------------------------------------------
-- SFD5 Card Scalar
--------------------------------------------------------------------------------
    tnSfd5CardAttributeTotal OBJECT-TYPE
        SYNTAX         Integer32
        MAX-ACCESS     read-only
        STATUS         current
        DESCRIPTION    "."
        ::= { tnOpticalCardObjs 44 }

--------------------------------------------------------------------------------
-- SFD5 Card Table
--------------------------------------------------------------------------------
    tnSfd5CardTable OBJECT-TYPE
        SYNTAX         SEQUENCE OF TnSfd5CardEntry
        MAX-ACCESS     not-accessible
        STATUS         current
        DESCRIPTION    "A table of SFD5 card specific attributes."
        ::= { tnOpticalCardObjs 45 }

    tnSfd5CardEntry OBJECT-TYPE
        SYNTAX         TnSfd5CardEntry
        MAX-ACCESS     not-accessible
        STATUS         current
        DESCRIPTION    "."
        INDEX { tnShelfIndex,
                tnSlotIndex }
        ::= { tnSfd5CardTable 1 }

    TnSfd5CardEntry ::= SEQUENCE {
        tnSfd5CardPortLossCh1      TropicSfdInvPortLoss,
        tnSfd5CardPortLossCh2      TropicSfdInvPortLoss,
        tnSfd5CardPortLossCh3      TropicSfdInvPortLoss,
        tnSfd5CardPortLossCh4      TropicSfdInvPortLoss,
        tnSfd5CardPortLossCh5      TropicSfdInvPortLoss,
        tnSfd5CardPortLossCh6      TropicSfdInvPortLoss,
        tnSfd5CardPortLossCh7      TropicSfdInvPortLoss,
        tnSfd5CardPortLossCh8      TropicSfdInvPortLoss,
        tnSfd5CardPortLossCh9      TropicSfdInvPortLoss,
        tnSfd5CardPortLossCh10     TropicSfdInvPortLoss,
        tnSfd5CardPortLossEXP      TropicSfdInvPortLoss,
        tnSfd5CardAveBIUFibLen     TropicSfdInvFiberLength,
        tnSfd5CardAveBIDFibLen     TropicSfdInvFiberLength
    }

    tnSfd5CardPortLossCh1 OBJECT-TYPE
        SYNTAX         TropicSfdInvPortLoss
        MAX-ACCESS     read-only
        STATUS         current
        DESCRIPTION    "Port loss measurement in channel 1"
        DEFVAL         { "" }
        ::= { tnSfd5CardEntry 1 }

    tnSfd5CardPortLossCh2 OBJECT-TYPE
        SYNTAX         TropicSfdInvPortLoss
        MAX-ACCESS     read-only
        STATUS         current
        DESCRIPTION    "Port loss measurement in channel 2"
        DEFVAL         { "" }
        ::= { tnSfd5CardEntry 2 }

    tnSfd5CardPortLossCh3 OBJECT-TYPE
        SYNTAX         TropicSfdInvPortLoss
        MAX-ACCESS     read-only
        STATUS         current
        DESCRIPTION    "Port loss measurement in channel 3"
        DEFVAL         { "" }
        ::= { tnSfd5CardEntry 3 }

    tnSfd5CardPortLossCh4 OBJECT-TYPE
        SYNTAX         TropicSfdInvPortLoss
        MAX-ACCESS     read-only
        STATUS         current
        DESCRIPTION    "Port loss measurement in channel 4"
        DEFVAL         { "" }
        ::= { tnSfd5CardEntry 4 }

    tnSfd5CardPortLossCh5 OBJECT-TYPE
        SYNTAX         TropicSfdInvPortLoss
        MAX-ACCESS     read-only
        STATUS         current
        DESCRIPTION    "Port loss measurement in channel 5"
        DEFVAL         { "" }
        ::= { tnSfd5CardEntry 5 }

    tnSfd5CardPortLossCh6 OBJECT-TYPE
        SYNTAX         TropicSfdInvPortLoss
        MAX-ACCESS     read-only
        STATUS         current
        DESCRIPTION    "Port loss measurement in channel 6"
        DEFVAL         { "" }
        ::= { tnSfd5CardEntry 6 }

    tnSfd5CardPortLossCh7 OBJECT-TYPE
        SYNTAX         TropicSfdInvPortLoss
        MAX-ACCESS     read-only
        STATUS         current
        DESCRIPTION    "Port loss measurement in channel 7"
        DEFVAL         { "" }
        ::= { tnSfd5CardEntry 7 }

    tnSfd5CardPortLossCh8 OBJECT-TYPE
        SYNTAX         TropicSfdInvPortLoss
        MAX-ACCESS     read-only
        STATUS         current
        DESCRIPTION    "Port loss measurement in channel 8"
        DEFVAL         { "" }
        ::= { tnSfd5CardEntry 8 }

    tnSfd5CardPortLossCh9 OBJECT-TYPE
        SYNTAX         TropicSfdInvPortLoss
        MAX-ACCESS     read-only
        STATUS         current
        DESCRIPTION    "Port loss measurement in channel 9"
        DEFVAL         { "" }
        ::= { tnSfd5CardEntry 9 }

    tnSfd5CardPortLossCh10 OBJECT-TYPE
        SYNTAX         TropicSfdInvPortLoss
        MAX-ACCESS     read-only
        STATUS         current
        DESCRIPTION    "Port loss measurement in channel 10"
        DEFVAL         { "" }
        ::= { tnSfd5CardEntry 10 }

    tnSfd5CardPortLossEXP OBJECT-TYPE
        SYNTAX         TropicSfdInvPortLoss
        MAX-ACCESS     read-only
        STATUS         current
        DESCRIPTION    "Port loss measurement"
        DEFVAL         { "" }
        ::= { tnSfd5CardEntry 11 }

    tnSfd5CardAveBIUFibLen OBJECT-TYPE
        SYNTAX         TropicSfdInvFiberLength
        MAX-ACCESS     read-only
        STATUS         current
        DESCRIPTION    "Average BIU fiber length"
        DEFVAL         { "" }
        ::= { tnSfd5CardEntry 12 }

    tnSfd5CardAveBIDFibLen OBJECT-TYPE
        SYNTAX         TropicSfdInvFiberLength
        MAX-ACCESS     read-only
        STATUS         current
        DESCRIPTION    "Average BID fiber length"
        DEFVAL         { "" }
        ::= { tnSfd5CardEntry 13 }

--------------------------------------------------------------------------------
-- SFD10 Card Scalar
--------------------------------------------------------------------------------
    tnSfd10CardAttributeTotal OBJECT-TYPE
        SYNTAX         Integer32
        MAX-ACCESS     read-only
        STATUS         current
        DESCRIPTION    "."
        ::= { tnOpticalCardObjs 46 }

--------------------------------------------------------------------------------
-- SFD10 Card Table
--------------------------------------------------------------------------------
    tnSfd10CardTable OBJECT-TYPE
        SYNTAX         SEQUENCE OF TnSfd10CardEntry
        MAX-ACCESS     not-accessible
        STATUS         current
        DESCRIPTION    "A table of SFD10 card specific attributes."
        ::= { tnOpticalCardObjs 47 }

    tnSfd10CardEntry OBJECT-TYPE
        SYNTAX         TnSfd10CardEntry
        MAX-ACCESS     not-accessible
        STATUS         current
        DESCRIPTION    "."
        INDEX { tnShelfIndex,
                tnSlotIndex }
        ::= { tnSfd10CardTable 1 }

    TnSfd10CardEntry ::= SEQUENCE {
        tnSfd10CardDMuxPortLossCh1      TropicSfdInvPortLoss,
        tnSfd10CardDMuxPortLossCh2      TropicSfdInvPortLoss,
        tnSfd10CardDMuxPortLossCh3      TropicSfdInvPortLoss,
        tnSfd10CardDMuxPortLossCh4      TropicSfdInvPortLoss,
        tnSfd10CardDMuxPortLossCh5      TropicSfdInvPortLoss,
        tnSfd10CardDMuxPortLossCh6      TropicSfdInvPortLoss,
        tnSfd10CardDMuxPortLossCh7      TropicSfdInvPortLoss,
        tnSfd10CardDMuxPortLossCh8      TropicSfdInvPortLoss,
        tnSfd10CardDMuxPortLossCh9      TropicSfdInvPortLoss,
        tnSfd10CardDMuxPortLossCh10     TropicSfdInvPortLoss,
        tnSfd10CardDMuxPortLossEXP      TropicSfdInvPortLoss,
        tnSfd10CardMuxPortLossCh1       TropicSfdInvPortLoss,
        tnSfd10CardMuxPortLossCh2       TropicSfdInvPortLoss,
        tnSfd10CardMuxPortLossCh3       TropicSfdInvPortLoss,
        tnSfd10CardMuxPortLossCh4       TropicSfdInvPortLoss,
        tnSfd10CardMuxPortLossCh5       TropicSfdInvPortLoss,
        tnSfd10CardMuxPortLossCh6       TropicSfdInvPortLoss,
        tnSfd10CardMuxPortLossCh7       TropicSfdInvPortLoss,
        tnSfd10CardMuxPortLossCh8       TropicSfdInvPortLoss,
        tnSfd10CardMuxPortLossCh9       TropicSfdInvPortLoss,
        tnSfd10CardMuxPortLossCh10      TropicSfdInvPortLoss,
        tnSfd10CardMuxPortLossEXP       TropicSfdInvPortLoss,
        tnSfd10CardAveMuxFibLen         TropicSfdInvFiberLength,
        tnSfd10CardAveDMUXFibLen        TropicSfdInvFiberLength
    }

    tnSfd10CardDMuxPortLossCh1 OBJECT-TYPE
        SYNTAX         TropicSfdInvPortLoss
        MAX-ACCESS     read-only
        STATUS         current
        DESCRIPTION    "DMUX port loss measurement in channel 1"
        DEFVAL         { "" }
        ::= { tnSfd10CardEntry 1 }

    tnSfd10CardDMuxPortLossCh2 OBJECT-TYPE
        SYNTAX         TropicSfdInvPortLoss
        MAX-ACCESS     read-only
        STATUS         current
        DESCRIPTION    "DMUX port loss measurement in channel 2"
        DEFVAL         { "" }
        ::= { tnSfd10CardEntry 2 }

    tnSfd10CardDMuxPortLossCh3 OBJECT-TYPE
        SYNTAX         TropicSfdInvPortLoss
        MAX-ACCESS     read-only
        STATUS         current
        DESCRIPTION    "DMUX port loss measurement in channel 3"
        DEFVAL         { "" }
        ::= { tnSfd10CardEntry 3 }

    tnSfd10CardDMuxPortLossCh4 OBJECT-TYPE
        SYNTAX         TropicSfdInvPortLoss
        MAX-ACCESS     read-only
        STATUS         current
        DESCRIPTION    "DMUX port loss measurement in channel 4"
        DEFVAL         { "" }
        ::= { tnSfd10CardEntry 4 }

    tnSfd10CardDMuxPortLossCh5 OBJECT-TYPE
        SYNTAX         TropicSfdInvPortLoss
        MAX-ACCESS     read-only
        STATUS         current
        DESCRIPTION    "DMUX port loss measurement in channel 5"
        DEFVAL         { "" }
        ::= { tnSfd10CardEntry 5 }

    tnSfd10CardDMuxPortLossCh6 OBJECT-TYPE
        SYNTAX         TropicSfdInvPortLoss
        MAX-ACCESS     read-only
        STATUS         current
        DESCRIPTION    "DMUX port loss measurement in channel 6"
        DEFVAL         { "" }
        ::= { tnSfd10CardEntry 6 }

    tnSfd10CardDMuxPortLossCh7 OBJECT-TYPE
        SYNTAX         TropicSfdInvPortLoss
        MAX-ACCESS     read-only
        STATUS         current
        DESCRIPTION    "DMUX port loss measurement in channel 7"
        DEFVAL         { "" }
        ::= { tnSfd10CardEntry 7 }

    tnSfd10CardDMuxPortLossCh8 OBJECT-TYPE
        SYNTAX         TropicSfdInvPortLoss
        MAX-ACCESS     read-only
        STATUS         current
        DESCRIPTION    "DMUX port loss measurement in channel 8"
        DEFVAL         { "" }
        ::= { tnSfd10CardEntry 8 }

    tnSfd10CardDMuxPortLossCh9 OBJECT-TYPE
        SYNTAX         TropicSfdInvPortLoss
        MAX-ACCESS     read-only
        STATUS         current
        DESCRIPTION    "DMUX port loss measurement in channel 9"
        DEFVAL         { "" }
        ::= { tnSfd10CardEntry 9 }

    tnSfd10CardDMuxPortLossCh10 OBJECT-TYPE
        SYNTAX         TropicSfdInvPortLoss
        MAX-ACCESS     read-only
        STATUS         current
        DESCRIPTION    "DMUX port loss measurement in channel 10"
        DEFVAL         { "" }
        ::= { tnSfd10CardEntry 10 }

    tnSfd10CardDMuxPortLossEXP OBJECT-TYPE
        SYNTAX         TropicSfdInvPortLoss
        MAX-ACCESS     read-only
        STATUS         current
        DESCRIPTION    "DMUX port loss measurement"
        DEFVAL         { "" }
        ::= { tnSfd10CardEntry 11 }

    tnSfd10CardMuxPortLossCh1 OBJECT-TYPE
        SYNTAX         TropicSfdInvPortLoss
        MAX-ACCESS     read-only
        STATUS         current
        DESCRIPTION    "MUX port loss measurement in channel 1"
        DEFVAL         { "" }
        ::= { tnSfd10CardEntry 12 }

    tnSfd10CardMuxPortLossCh2 OBJECT-TYPE
        SYNTAX         TropicSfdInvPortLoss
        MAX-ACCESS     read-only
        STATUS         current
        DESCRIPTION    "MUX port loss measurement in channel 2"
        DEFVAL         { "" }
        ::= { tnSfd10CardEntry 13 }

    tnSfd10CardMuxPortLossCh3 OBJECT-TYPE
        SYNTAX         TropicSfdInvPortLoss
        MAX-ACCESS     read-only
        STATUS         current
        DESCRIPTION    "MUX port loss measurement in channel 3"
        DEFVAL         { "" }
        ::= { tnSfd10CardEntry 14 }

    tnSfd10CardMuxPortLossCh4 OBJECT-TYPE
        SYNTAX         TropicSfdInvPortLoss
        MAX-ACCESS     read-only
        STATUS         current
        DESCRIPTION    "MUX port loss measurement in channel 4"
        DEFVAL         { "" }
        ::= { tnSfd10CardEntry 15 }

    tnSfd10CardMuxPortLossCh5 OBJECT-TYPE
        SYNTAX         TropicSfdInvPortLoss
        MAX-ACCESS     read-only
        STATUS         current
        DESCRIPTION    "MUX port loss measurement in channel 5"
        DEFVAL         { "" }
        ::= { tnSfd10CardEntry 16 }

    tnSfd10CardMuxPortLossCh6 OBJECT-TYPE
        SYNTAX         TropicSfdInvPortLoss
        MAX-ACCESS     read-only
        STATUS         current
        DESCRIPTION    "MUX port loss measurement in channel 6"
        DEFVAL         { "" }
        ::= { tnSfd10CardEntry 17 }

    tnSfd10CardMuxPortLossCh7 OBJECT-TYPE
        SYNTAX         TropicSfdInvPortLoss
        MAX-ACCESS     read-only
        STATUS         current
        DESCRIPTION    "MUX port loss measurement in channel 7"
        DEFVAL         { "" }
        ::= { tnSfd10CardEntry 18 }

    tnSfd10CardMuxPortLossCh8 OBJECT-TYPE
        SYNTAX         TropicSfdInvPortLoss
        MAX-ACCESS     read-only
        STATUS         current
        DESCRIPTION    "MUX port loss measurement in channel 8"
        DEFVAL         { "" }
        ::= { tnSfd10CardEntry 19 }

    tnSfd10CardMuxPortLossCh9 OBJECT-TYPE
        SYNTAX         TropicSfdInvPortLoss
        MAX-ACCESS     read-only
        STATUS         current
        DESCRIPTION    "MUX port loss measurement in channel 9"
        DEFVAL         { "" }
        ::= { tnSfd10CardEntry 20 }

    tnSfd10CardMuxPortLossCh10 OBJECT-TYPE
        SYNTAX         TropicSfdInvPortLoss
        MAX-ACCESS     read-only
        STATUS         current
        DESCRIPTION    "MUX port loss measurement in channel 10"
        DEFVAL         { "" }
        ::= { tnSfd10CardEntry 21 }

    tnSfd10CardMuxPortLossEXP OBJECT-TYPE
        SYNTAX         TropicSfdInvPortLoss
        MAX-ACCESS     read-only
        STATUS         current
        DESCRIPTION    "MUX port loss measurement"
        DEFVAL         { "" }
        ::= { tnSfd10CardEntry 22 }

    tnSfd10CardAveMuxFibLen OBJECT-TYPE
        SYNTAX         TropicSfdInvFiberLength
        MAX-ACCESS     read-only
        STATUS         current
        DESCRIPTION    "Average MUX fiber length"
        DEFVAL         { "" }
        ::= { tnSfd10CardEntry 23 }

    tnSfd10CardAveDMUXFibLen OBJECT-TYPE
        SYNTAX         TropicSfdInvFiberLength
        MAX-ACCESS     read-only
        STATUS         current
        DESCRIPTION    "Average DMUX fiber length"
        DEFVAL         { "" }
        ::= { tnSfd10CardEntry 24 }

--------------------------------------------------------------------------------
-- DCM Card Scalar (Dcm70341 and Bidi Dcm)
--------------------------------------------------------------------------------
    tnDcmxCardAttributeTotal OBJECT-TYPE
        SYNTAX         Integer32
        MAX-ACCESS     read-only
        STATUS         current
        DESCRIPTION    "."
        ::= { tnOpticalCardObjs 48 }

--------------------------------------------------------------------------------
-- DCM Card Table (Dcm70341 and Bidi Dcm)
--------------------------------------------------------------------------------
    tnDcmxCardTable OBJECT-TYPE
        SYNTAX         SEQUENCE OF TnDcmxCardEntry
        MAX-ACCESS     not-accessible
        STATUS         current
        DESCRIPTION    "A table of DCM card specific attributes."
        ::= { tnOpticalCardObjs 49 }

    tnDcmxCardEntry OBJECT-TYPE
        SYNTAX         TnDcmxCardEntry
        MAX-ACCESS     not-accessible
        STATUS         current
        DESCRIPTION    "."
        INDEX { tnShelfIndex,
                tnSlotIndex }
        ::= { tnDcmxCardTable 1 }

    TnDcmxCardEntry ::= SEQUENCE {
        tnDcmxCardFiberType                    TropicDcmInvFiberType,
        tnDcmxCardDcmSize                      TropicDcmInvDcmSize,
        tnDcmxCardAverageInsertionLossDCF1     TropicDcmInvInsertionLoss,
        tnDcmxCardInsertionLossSlopeDCF1       TropicDcmInvInsertionLossSlope,
        tnDcmxCardTotalDispFitDCF1             TropicDcmInvDispersionFit,
        tnDcmxCardDispFiberLengthDCF1          TropicDcmInvFiberLength,
        tnDcmxCardPMDDCF1                      TropicDcmInvPmd,
        tnDcmxCardAverageInsertionLossDCF2     TropicDcmInvInsertionLoss,
        tnDcmxCardInsertionLossSlopeDCF2       TropicDcmInvInsertionLossSlope,
        tnDcmxCardTotalDispFitDCF2             TropicDcmInvDispersionFit,
        tnDcmxCardDispFiberLengthDCF2          TropicDcmInvFiberLength,
        tnDcmxCardPMDDCF2                      TropicDcmInvPmd,
        tnDcmxCardLatencyMismatch              TropicDcmInvLatencyMismatch,
        tnDcmxCardLatency                      TropicDcmInvLatency
    }

    tnDcmxCardFiberType OBJECT-TYPE
        SYNTAX         TropicDcmInvFiberType
        MAX-ACCESS     read-only
        STATUS         current
        DESCRIPTION    "The type of fiber that the DCM is designed to
                        dispersion-compensate."
        DEFVAL         { "" }
        ::= { tnDcmxCardEntry 1 }

    tnDcmxCardDcmSize OBJECT-TYPE
        SYNTAX         TropicDcmInvDcmSize
        MAX-ACCESS     read-only
        STATUS         current
        DESCRIPTION    "The length of TRANSMISSION fiber that the DCM is
                        designed to compensate (unit: km)."
        DEFVAL         { "" }
        ::= { tnDcmxCardEntry 2 }

    tnDcmxCardAverageInsertionLossDCF1 OBJECT-TYPE
        SYNTAX         TropicDcmInvInsertionLoss
        MAX-ACCESS     read-only
        STATUS         current
        DESCRIPTION    "The measured insertion loss averaged over wavelength
                        with no external attenuation added
                        to the DCM (unit:dB) for DCF."
        DEFVAL         { "" }
        ::= { tnDcmxCardEntry 3 }

    tnDcmxCardInsertionLossSlopeDCF1 OBJECT-TYPE
        SYNTAX         TropicDcmInvInsertionLossSlope
        MAX-ACCESS     read-only
        STATUS         current
        DESCRIPTION    "A linear least-squares fitted slope of the measured
                        attenuation (positive or negative) over the wavelength
                        range with no external attenuation added to the DCM
                        (unit: dB) for DCF. The slope is defined over the full
                        wavelength range with a negative slope signifying a
                        higher insertion loss at the lower wavelength."
        DEFVAL         { "" }
        ::= { tnDcmxCardEntry 4 }

    tnDcmxCardTotalDispFitDCF1 OBJECT-TYPE
        SYNTAX         TropicDcmInvDispersionFit
        MAX-ACCESS     read-only
        STATUS         current
        DESCRIPTION    "Coefficients A, B, C and D of a 3rd Order polynomial
                        fit of chromatic dispersion vs. wavelength from 1528
                        to 1565nm in 0.4-2.0nm steps for DCF such that
                        TotalDispersion = A*(-1546)3 + B*(-1546)2 + C*(-1546) + D."
        DEFVAL         { "" }
        ::= { tnDcmxCardEntry 5 }

    tnDcmxCardDispFiberLengthDCF1 OBJECT-TYPE
        SYNTAX         TropicDcmInvFiberLength
        MAX-ACCESS     read-only
        STATUS         current
        DESCRIPTION    "The total length of dispersion fibre of DCF inside the
                        DCM module, to the closest km (unit: km)."
        DEFVAL         { "" }
        ::= { tnDcmxCardEntry 6 }

    tnDcmxCardPMDDCF1 OBJECT-TYPE
        SYNTAX         TropicDcmInvPmd
        MAX-ACCESS     read-only
        STATUS         current
        DESCRIPTION    "The value for Polarization mode dispersion (unit:ps) for DCF."
        DEFVAL         { "" }
        ::= { tnDcmxCardEntry 7 }

    tnDcmxCardAverageInsertionLossDCF2 OBJECT-TYPE
        SYNTAX         TropicDcmInvInsertionLoss
        MAX-ACCESS     read-only
        STATUS         current
        DESCRIPTION    "The measured insertion loss averaged over wavelength
                        with no external attenuation added to the DCM (unit: dB)
                        for DCF2.  LM DCM only."
        DEFVAL         { "" }
        ::= { tnDcmxCardEntry 8 }

    tnDcmxCardInsertionLossSlopeDCF2 OBJECT-TYPE
        SYNTAX         TropicDcmInvInsertionLossSlope
        MAX-ACCESS     read-only
        STATUS         current
        DESCRIPTION    "A linear least-squares fitted slope of the measured
                        attenuation (positive or negative) over the wavelength
                        range with no external attenuation added to the DCM
                        (unit: dB) for DCF2. The slope is defined over the full
                        wavelength range with a negative slope signifying a
                        higher insertion loss at the lower wavelength.  LM DCM
                        only."
        DEFVAL         { "" }
        ::= { tnDcmxCardEntry 9 }

    tnDcmxCardTotalDispFitDCF2 OBJECT-TYPE
        SYNTAX         TropicDcmInvDispersionFit
        MAX-ACCESS     read-only
        STATUS         current
        DESCRIPTION    "Coefficients A, B, C and D of a 3rd Order polynomial
                        fit of chromatic dispersion vs. wavelength from 1528
                        to 1565nm in 0.4-2.0nm steps for DCF2 such that
                        TotalDispersion = A*(-1546)3 + B*(-1546)2 + C*(-1546) + D.
                        LM DCM only."
        DEFVAL         { "" }
        ::= { tnDcmxCardEntry 10 }

    tnDcmxCardDispFiberLengthDCF2 OBJECT-TYPE
        SYNTAX         TropicDcmInvFiberLength
        MAX-ACCESS     read-only
        STATUS         current
        DESCRIPTION    "The total length of dispersion fiber of DCF2 inside the
                        DCM module, to the closest km (unit:km).  LM DCM only."
        DEFVAL         { "" }
        ::= { tnDcmxCardEntry 11 }

    tnDcmxCardPMDDCF2 OBJECT-TYPE
        SYNTAX         TropicDcmInvPmd
        MAX-ACCESS     read-only
        STATUS         current
        DESCRIPTION    "The value for Polarization mode dispersion (unit:ps) for
                        DCF2.  LM DCM only."
        DEFVAL         { "" }
        ::= { tnDcmxCardEntry 12 }

    tnDcmxCardLatencyMismatch OBJECT-TYPE
        SYNTAX         TropicDcmInvLatencyMismatch
        MAX-ACCESS     read-only
        STATUS         current
        DESCRIPTION    "The latency mismatches value of the DCF1 and DCF2 in the
                        module. Latency mismatch value = DCF1- DCF2.  LM DCM only."
        DEFVAL         { "" }
        ::= { tnDcmxCardEntry 13 }

    tnDcmxCardLatency OBJECT-TYPE
        SYNTAX         TropicDcmInvLatency
        MAX-ACCESS     read-only
        STATUS         current
        DESCRIPTION    "The latency value of the DCF in the module.  Bidi DCM only."
        DEFVAL         { "" }
        ::= { tnDcmxCardEntry 14 }
--------------------------------------------------------------------------------
-- Conformance Group Definitions
--------------------------------------------------------------------------------
    tnOpticalCardScalarsGroup OBJECT-GROUP
        OBJECTS {
            tnOpticalCardTotal
        }
        STATUS         current
        DESCRIPTION    "."
        ::= { tnOpticalCardGroups 1 }

--    obsolete
--    tnBandFilterCardGroup    OBJECT-GROUP ::= { tnOpticalCardGroups 2 }
--    tnChannelFilterCardGroup OBJECT-GROUP ::= { tnOpticalCardGroups 3 }

    tnDcmCardGroup OBJECT-GROUP
        OBJECTS {
            tnDcmCardProgrammedCompensationDistance,
            tnDcmCardPresentCompensationDistance,
            tnDcmCardSize,
            tnDcmCardFiberType,
            tnDcmCardAverageInsertionLoss,
            tnDcmCardInsertionLossSlope,
            tnDcmCardAverageInsertionLossPad,
            tnDcmCardInsertionLossSlopePad,
            tnDcmCardTotalDispTilt,
            tnDcmCardDispFiberLength,
            tnDcmCardPMD,
            tnDcmCardProvisionedFiberType
        }
        STATUS         current
        DESCRIPTION    "."
        ::= { tnOpticalCardGroups 4 }

--    obsolete
--    tnChannelAddDropCardGroup OBJECT-GROUP ::= { tnOpticalCardGroups 5 }
--    tnExternalDcuCardGroup    OBJECT-GROUP ::= { tnOpticalCardGroups 6 }
--    tnBroadbandCardGroup      OBJECT-GROUP ::= { tnOpticalCardGroups 7 }

    tnPowerControlCardGroup OBJECT-GROUP
        OBJECTS {
            tnPowerControlCardCapabilityProgrammed,
            tnPowerControlCardCapabilityPresent,
            tnPowerControlCardCapabilityInUse
        }
        STATUS         current
        DESCRIPTION    "."
        ::= { tnOpticalCardGroups 8 }

    tnWssCardGroup OBJECT-GROUP
        OBJECTS {
            tnWssCardAddPathTargetPower,
            tnWssCardAddPathEgressPower,
            tnWssCardAddPathTotalChannel,
            tnWssCardReservedDegree,
            tnWssCardLnsEnable,
            tnWssCardLnsPower,
--            obsolete
--            tnWssCardIsAdBlockAdd,
--            tnWssCardIsAdBlockDrop,
            tnWssCardAdBlockLevelAdd,
            tnWssCardAdBlockLevelDrop,
            tnWssCardIsFlexgrid,
            tnWssCardGranularityMHz,
            tnWssCardEnableFilterlessDge
        }
        STATUS         current
        DESCRIPTION    "."
        ::= { tnOpticalCardGroups 9 }

    tnSfdCardGroup OBJECT-GROUP
        OBJECTS {
            tnSfdCardAverageMuxInsertionLoss,
            tnSfdCardAverageDemuxInsertionLoss
        }
        STATUS         current
        DESCRIPTION    "."
        ::= { tnOpticalCardGroups 10 }

    tnSonetSdhPpSectionCardGroup OBJECT-GROUP
        OBJECTS {
            tnSonetSdhPpSection1Port,
            tnSonetSdhPpSection2Port,
            tnSonetSdhPpSection3Port,
            tnSonetSdhPpSection4Port,
            tnSonetSdhPpSection5Port,
            tnSonetSdhPpSection6Port,
            tnSonetSdhPpSection7Port,
            tnSonetSdhPpSection8Port,
            tnSonetSdhPpSection1IfType,
            tnSonetSdhPpSection2IfType,
            tnSonetSdhPpSection3IfType,
            tnSonetSdhPpSection4IfType,
            tnSonetSdhPpSection5IfType,
            tnSonetSdhPpSection6IfType,
            tnSonetSdhPpSection7IfType,
            tnSonetSdhPpSection8IfType
        }
        STATUS         current
        DESCRIPTION    "."
        ::= { tnOpticalCardGroups 11 }

    tnPcsSectionCardGroup OBJECT-GROUP
        OBJECTS {
            tnPcsSection1Port,
            tnPcsSection2Port,
            tnPcsSection3Port,
            tnPcsSection4Port,
            tnPcsSection5Port,
            tnPcsSection6Port,
            tnPcsSection7Port,
            tnPcsSection8Port,
            tnPcsSection9Port,
            tnPcsSection10Port,
            tnPcsSection1IfType,
            tnPcsSection2IfType,
            tnPcsSection3IfType,
            tnPcsSection4IfType,
            tnPcsSection5IfType,
            tnPcsSection6IfType,
            tnPcsSection7IfType,
            tnPcsSection8IfType,
            tnPcsSection9IfType,
            tnPcsSection10IfType
        }
        STATUS         current
        DESCRIPTION    "."
        ::= { tnOpticalCardGroups 12 }

    tn11dpge12CardGroup OBJECT-GROUP
        OBJECTS {
            tn11dpge12CardRateMode,
            tn11dpge12QINQModeTPID
        }
        STATUS         current
        DESCRIPTION    "."
        ::= { tnOpticalCardGroups 14 }

    tnSfcCardGroup OBJECT-GROUP
        OBJECTS {
            tnSfcCardFiberMode
        }
        STATUS         current
        DESCRIPTION    "."
        ::= { tnOpticalCardGroups 15 }

--    obsolete
--    tn4dpa4CardGroup OBJECT-GROUP ::= { tnOpticalCardGroups 16 }
--    tnOpsaCardGroup  OBJECT-GROUP ::= { tnOpticalCardGroups 17 }

    tn11dpe12eCardGroup OBJECT-GROUP
        OBJECTS {
            tn11dpe12eCardRateMode,
            tn11dpe12eQINQModeTPID1,
            tn11dpe12eQINQModeTPID2,
            tn11dpe12eQINQModeTPID3,
            tn11dpe12eQINQModeTPID4,
            tn11dpe12eQINQModeFlowCm
        }
        STATUS         current
        DESCRIPTION    "."
        ::= { tnOpticalCardGroups 18 }

    tn1dpp24mCardGroup OBJECT-GROUP
        OBJECTS {
            tn1dpp24mCardFunctionMode,
            tn1dpp24mCardImpedance
        }
        STATUS         current
        DESCRIPTION    "."
        ::= { tnOpticalCardGroups 19 }

--    obsolete
--    tn43sca1CardGroup OBJECT-GROUP ::= { tnOpticalCardGroups 20 }

    tnOpsCardGroup OBJECT-GROUP
        OBJECTS {
            tnOpsCardProtectionMode
        }
        STATUS         current
        DESCRIPTION    "."
        ::= { tnOpticalCardGroups 21 }

    tn11dpe12aCardGroup OBJECT-GROUP
        OBJECTS {
            tn11dpe12aCardRateMode,
            tn11dpe12aCardQINQModeTPID1,
            tn11dpe12aCardQINQModeTPID2,
            tn11dpe12aCardQINQModeTPID3,
            tn11dpe12aCardQINQModeTPID4,
            tn11dpe12aCardLBMInterval,
            tn11dpe12aCardLBRTimeout,
            tn11dpe12aCardFlowCm,
            tn11dpe12aCardSLRTimeout,
            tn11dpe12aCardCrossPackServiceSupported
        }
        STATUS         current
        DESCRIPTION    "."
        ::= { tnOpticalCardGroups 22 }

    tnCardFunctionModeGroup OBJECT-GROUP
        OBJECTS {
            tnCardFunctionMode
        }
        STATUS         current
        DESCRIPTION    "."
        ::= { tnOpticalCardGroups 23 }

    tn112pdm11CardGroup OBJECT-GROUP
        OBJECTS {
            tn112pdm11CardMaxDMNumbers,
            tn112pdm11CardUsedDMNumbers
        }
        STATUS         current
        DESCRIPTION    "."
        ::= { tnOpticalCardGroups 24 }

    tnPtpctlCardScalarsGroup OBJECT-GROUP
        OBJECTS {
            tnPtpctlCardAttributeTotal
        }
        STATUS         current
        DESCRIPTION    "."
        ::= { tnOpticalCardGroups 25 }

    tnPtpctlCardGroup OBJECT-GROUP
        OBJECTS {
            tnPtpctlCardEqpsLEDColor,
            tnPtpctlCardEqpsLEDState,
            tnPtpctlCardPtpLEDColor,
            tnPtpctlCardPtpLEDState
        }
        STATUS         current
        DESCRIPTION    "."
        ::= { tnOpticalCardGroups 26 }

    tnWtocmaCardScalarsGroup OBJECT-GROUP
        OBJECTS {
            tnWtocmaCardAttributeTotal
        }
        STATUS         current
        DESCRIPTION    "."
        ::= { tnOpticalCardGroups 27 }

    tnWtocmaCardGroup OBJECT-GROUP
        OBJECTS {
            tnWtocmaCardOsnrScan,
            tnWtocmaCardOsnrScanAbort,
            tnWtocmaCardOsnrScanStatus,
            tnWtocmaCardDspState
        }
        STATUS         current
        DESCRIPTION    "."
        ::= { tnOpticalCardGroups 28 }

    tnCruCardScalarsGroup OBJECT-GROUP
        OBJECTS {
            tnCruCardAttributeTotal
        }
        STATUS         current
        DESCRIPTION    "."
        ::= { tnOpticalCardGroups 29 }

    tnCruCardGroup OBJECT-GROUP
        OBJECTS {
            tnCruCardActivityState,
            tnCruCardEqpsLEDColor,
            tnCruCardEqpsLEDState,
            tnFCruProtectionRole
        }
        STATUS         current
        DESCRIPTION    "."
        ::= { tnOpticalCardGroups 30 }

    tnIroadmCardConfigScalarsGroup OBJECT-GROUP
        OBJECTS {
            tnIroadmCardConfigAttributeTotal
        }
        STATUS         current
        DESCRIPTION    "."
        ::= { tnOpticalCardGroups 31 }

    tnIroadmCardConfigGroup OBJECT-GROUP
        OBJECTS {
            tnIroadmCardConfigOptIntDetection,
            tnIroadmCardConfigOptIntBaseline,
            tnIroadmCardConfigOptIntLossThreshold,
            tnIroadmCardConfigOptIntPollPeriod,
            tnIroadmCardConfigOptIntClearAlarm
        }
        STATUS         current
        DESCRIPTION    "."
        ::= { tnOpticalCardGroups 32 }

    tnIroadmCardInfoScalarsGroup OBJECT-GROUP
        OBJECTS {
            tnIroadmCardInfoAttributeTotal
        }
        STATUS         current
        DESCRIPTION    "."
        ::= { tnOpticalCardGroups 33 }

    tnIroadmCardInfoGroup OBJECT-GROUP
        OBJECTS {
           tnIroadmCardInfoIngressOAMPumpTemperature,
           tnIroadmCardInfoIngressOAMPumpBias,
           tnIroadmCardInfoEgressOAMPumpTemperature,
           tnIroadmCardInfoEgressOAMPumpBias,
           tnIroadmCardInfoOptIntSpanLoss,
           tnIroadmCardInfoWssIsFlexgrid,
           tnIroadmCardInfoWssGranularityMHz
        }
        STATUS         current
        DESCRIPTION    "."
        ::= { tnOpticalCardGroups 34 }

    tnIsonCardModeScalarsGroup OBJECT-GROUP
        OBJECTS {
            tnIsonCardModeAttributeTotal
        }
        STATUS         current
        DESCRIPTION    "."
        ::= { tnOpticalCardGroups 35 }

    tnIsonCardModeGroup OBJECT-GROUP
        OBJECTS {
           tnIsonCardModeSelection
        }
        STATUS         current
        DESCRIPTION    "."
        ::= { tnOpticalCardGroups 36 }

    tnCardEtherTypeProfileScalarsGroup OBJECT-GROUP
        OBJECTS {
            tnCardEtherTypeProfileAttributeTotal
        }
        STATUS         current
        DESCRIPTION    "."
        ::= { tnOpticalCardGroups 38 }

    tnCardEtherTypeProfileGroup OBJECT-GROUP
        OBJECTS {
           tnCardEthertypeQinQDesc,
           tnCardEthertypeQinQEtype,
           tnCardEthertypeQinQRowStatus
        }
        STATUS         current
        DESCRIPTION    "."
        ::= { tnOpticalCardGroups 39 }

    tnAutomationConfigScalarsGroup OBJECT-GROUP
        OBJECTS {
            tnAutomationConfigAttributeTotal
        }
        STATUS         current
        DESCRIPTION    "."
        ::= { tnOpticalCardGroups 40 }

    tnAutomationConfigGroup OBJECT-GROUP
        OBJECTS {
           tnAutomationConfigAutoTopoDegreeNumber
        }
        STATUS         current
        DESCRIPTION    "."
        ::= { tnOpticalCardGroups 41 }

--    obsolete
--    tnCpcCardScalarsGroup OBJECT-GROUP ::= { tnOpticalCardGroups 42 }
--    tnCpcCardGroup        OBJECT-GROUP ::= { tnOpticalCardGroups 43 }

    tnSfd5CardScalarsGroup OBJECT-GROUP
        OBJECTS {
            tnSfd5CardAttributeTotal
        }
        STATUS         current
        DESCRIPTION    "."
        ::= { tnOpticalCardGroups 44 }

    tnSfd5CardGroup OBJECT-GROUP
        OBJECTS {
            tnSfd5CardPortLossCh1,
            tnSfd5CardPortLossCh2,
            tnSfd5CardPortLossCh3,
            tnSfd5CardPortLossCh4,
            tnSfd5CardPortLossCh5,
            tnSfd5CardPortLossCh6,
            tnSfd5CardPortLossCh7,
            tnSfd5CardPortLossCh8,
            tnSfd5CardPortLossCh9,
            tnSfd5CardPortLossCh10,
            tnSfd5CardPortLossEXP,
            tnSfd5CardAveBIUFibLen,
            tnSfd5CardAveBIDFibLen
        }
        STATUS         current
        DESCRIPTION    "."
        ::= { tnOpticalCardGroups 45 }

    tnSfd10CardScalarsGroup OBJECT-GROUP
        OBJECTS {
            tnSfd10CardAttributeTotal
        }
        STATUS         current
        DESCRIPTION    "."
        ::= { tnOpticalCardGroups 46 }

    tnSfd10CardGroup OBJECT-GROUP
        OBJECTS {
            tnSfd10CardDMuxPortLossCh1,
            tnSfd10CardDMuxPortLossCh2,
            tnSfd10CardDMuxPortLossCh3,
            tnSfd10CardDMuxPortLossCh4,
            tnSfd10CardDMuxPortLossCh5,
            tnSfd10CardDMuxPortLossCh6,
            tnSfd10CardDMuxPortLossCh7,
            tnSfd10CardDMuxPortLossCh8,
            tnSfd10CardDMuxPortLossCh9,
            tnSfd10CardDMuxPortLossCh10,
            tnSfd10CardDMuxPortLossEXP,
            tnSfd10CardMuxPortLossCh1,
            tnSfd10CardMuxPortLossCh2,
            tnSfd10CardMuxPortLossCh3,
            tnSfd10CardMuxPortLossCh4,
            tnSfd10CardMuxPortLossCh5,
            tnSfd10CardMuxPortLossCh6,
            tnSfd10CardMuxPortLossCh7,
            tnSfd10CardMuxPortLossCh8,
            tnSfd10CardMuxPortLossCh9,
            tnSfd10CardMuxPortLossCh10,
            tnSfd10CardMuxPortLossEXP,
            tnSfd10CardAveMuxFibLen,
            tnSfd10CardAveDMUXFibLen
        }
        STATUS         current
        DESCRIPTION    "."
        ::= { tnOpticalCardGroups 47 }

    tnDcmxCardScalarsGroup OBJECT-GROUP
        OBJECTS {
            tnDcmxCardAttributeTotal
        }
        STATUS         current
        DESCRIPTION    "."
        ::= { tnOpticalCardGroups 48 }

    tnDcmxCardGroup OBJECT-GROUP
        OBJECTS {
            tnDcmxCardFiberType,
            tnDcmxCardDcmSize,
            tnDcmxCardAverageInsertionLossDCF1,
            tnDcmxCardInsertionLossSlopeDCF1,
            tnDcmxCardTotalDispFitDCF1,
            tnDcmxCardDispFiberLengthDCF1,
            tnDcmxCardPMDDCF1,
            tnDcmxCardAverageInsertionLossDCF2,
            tnDcmxCardInsertionLossSlopeDCF2,
            tnDcmxCardTotalDispFitDCF2,
            tnDcmxCardDispFiberLengthDCF2,
            tnDcmxCardPMDDCF2,
            tnDcmxCardLatencyMismatch,
            tnDcmxCardLatency
        }
        STATUS         current
        DESCRIPTION    "."
        ::= { tnOpticalCardGroups 49 }

--------------------------------------------------------------------------------
-- Compliance Statements (mandatory)
--------------------------------------------------------------------------------
    tnOpticalCardCompliance MODULE-COMPLIANCE
        STATUS         current
        DESCRIPTION    "."
        MODULE
        MANDATORY-GROUPS {
            tnOpticalCardScalarsGroup,
--            obsolete
--            tnBandFilterCardGroup,
--            tnChannelFilterCardGroup,
            tnDcmCardGroup,
--            obsolete
--            tnChannelAddDropCardGroup,
--            tnExternalDcuCardGroup,
--            tnBroadbandCardGroup,
            tnPowerControlCardGroup,
            tnWssCardGroup,
            tnSfdCardGroup,
            tnSonetSdhPpSectionCardGroup,
            tnPcsSectionCardGroup,
            tn11dpge12CardGroup,
            tnSfcCardGroup,
--            obsolete
--            tn4dpa4CardGroup,
--            tnOpsaCardGroup,
            tn11dpe12eCardGroup,
            tn1dpp24mCardGroup,
--            obsolete
--            tn43sca1CardGroup,
            tnOpsCardGroup,
            tn11dpe12aCardGroup,
            tnCardFunctionModeGroup,
            tn112pdm11CardGroup,
            tnPtpctlCardScalarsGroup,
            tnPtpctlCardGroup,
            tnWtocmaCardScalarsGroup,
            tnWtocmaCardGroup,
            tnCruCardScalarsGroup,
            tnCruCardGroup,
            tnIroadmCardConfigScalarsGroup,
            tnIroadmCardConfigGroup,
            tnIroadmCardInfoScalarsGroup,
            tnIroadmCardInfoGroup,
            tnIsonCardModeScalarsGroup,
            tnIsonCardModeGroup,
            tnCardEtherTypeProfileScalarsGroup,
            tnCardEtherTypeProfileGroup,
            tnAutomationConfigScalarsGroup,
            tnAutomationConfigGroup,
--            obsolete
--            tnCpcCardScalarsGroup,
--            tnCpcCardGroup,
            tnSfd5CardScalarsGroup,
            tnSfd5CardGroup,
            tnSfd10CardScalarsGroup,
            tnSfd10CardGroup,
            tnDcmxCardScalarsGroup,
            tnDcmxCardGroup
        }
        ::= { tnOpticalCardCompliances 1 }

END -- DEFINITION OF TROPIC-OPTICALCARD-MIB

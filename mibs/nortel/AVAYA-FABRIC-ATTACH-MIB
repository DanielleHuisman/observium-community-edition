AVAYA-FABRIC-ATTACH-MIB DEFINITIONS ::= BEGIN

IMPORTS
    MODULE-IDENTITY, NOTIFICATION-TYPE, OBJECT-TYPE, 
    Unsigned32, Integer32, Counter32
            FROM SNMPv2-SMI
    MODULE-COMPLIANCE, OBJECT-GROUP
            FROM SNMPv2-CONF
    SnmpAdminString
            FROM SNMP-FRAMEWORK-MIB
    bayStackMibs
            FROM SYNOPTICS-ROOT-MIB
    RowStatus, TruthValue
            FROM SNMPv2-TC
   DisplayString
            FROM RFC1213-MIB;


avayaFabricAttachMib MODULE-IDENTITY
    LAST-UPDATED "202009040000Z"     -- August 3, 2020
    ORGANIZATION "Avaya Networks, Inc."
    CONTACT-INFO "avaya.com"
    DESCRIPTION
        "This MIB module contains objects related to the Fabric Attach support."


    REVISION    "202009040000Z" -- Sept 04, 2020
    DESCRIPTION "Ver 31: Added avFabricAttachPortOrigin. Request by A Rebega(Oana)"



    REVISION    "202008030000Z" -- August 3, 2020
    DESCRIPTION "Ver 30: Defined avFabricAttachIsidVlanAsgnsIsidName and
                             avFabricAttachZeroTouchClientAttachIsidName to show the
                             Isid Name on the server if it exists.  This isid is not part of
                             the FA TLVs, rather it is manually configured on the server."


    REVISION    "201801250000Z" -- January 25, 2018
    DESCRIPTION "Ver 29: Defined avFabricAttachZeroTouchMgmtVlanDist attribute. 
                         Added autoMgmtVlanFaClient enumeration support for
                         the avFabricAttachZeroTouchOptionFlags and the    
                         avFabricAttachZeroTouchClientOptionFlags attributes."

    REVISION    "201611210000Z" -- November 21, 2016
    DESCRIPTION "Ver 28: Defined avFabricAttachDiscoveredElement and 
                         avFabricAttachExpiredElement notifications."

    REVISION    "201610260000Z" -- October 26, 2016
    DESCRIPTION "Ver 27: Updated avFabricAttachZeroTouchClientDetectTable index
                         to support multiple detection data items per client type.
                         A logic operation can also be specified to control data
                         combinations (avFabricAttachZeroTouchClientDetectLogicOper)." 

    REVISION    "201607120000Z" -- July 12, 2016
    DESCRIPTION "Ver 26: Added avFabricAttachZeroTouchClientAttachExcludeStatic
                         attribute to ZTC Attach table. Added new FA global
                         statistics to export current binding counts in database. 
                         Introduced FA Client detection support through the  
                         avFabricAttachZeroTouchClientDetectTable."

    REVISION    "201605090000Z" -- May 9, 2016
    DESCRIPTION "Ver 25: Defined avFabricAttachZeroTouchClientAttachTable
                         and the associated autoClientAttach Zero Touch 
                         option flag. NSV support is deprecated with this 
                         update. Updated avFabricAttachZeroTouchClientTable
                         with avFabricAttachZeroTouchClientName and client
                         origin (avFabricAttachZeroTouchClientOrigin) objects.
                         Updated avFabricAttachIsidVlanAsgnsOrigin to support
                         binding data originated through Zero Touch Client
                         processing."

    REVISION    "201604040000Z" -- April 4, 2016
    DESCRIPTION "Ver 24: Added avFabricAttachZeroTouchNsvIsid attribute
                         to the avFabricAttachZeroTouchNsvTable definition."

    REVISION    "201602120000Z" -- February 12, 2016
    DESCRIPTION "Ver 23: Added avFabricAttachStatsClearPortErrorCounters 
                         attribute. Updated description text for Fabric
                         Attach statistics counters."

    REVISION    "201601260000Z" -- January 26, 2016
    DESCRIPTION "Ver 22: Added avFabricAttachPortMsgAuthKeymode attribute."

    REVISION    "201511120000Z" -- November 12, 2015
    DESCRIPTION "Ver 21: Added avFabricAttachDiscElemsAsgnsAuth.
			 Added enum value none(4) for
			 avFabricAttachDiscElemsElementAuth
			 Changes requested by Zuyan Wang (VSP) - Prem"

    REVISION    "201510300000Z" -- October 30, 2015
    DESCRIPTION "Ver 20: Reverted back the enum value invalid(1) to the original name
			 other(1) for avFabricAttachDiscElemsElementType.
			 Changes requested by Zuyan Wang (VSP) - Prem"

    REVISION    "201510300000Z" -- October 30, 2015
    DESCRIPTION "Ver 19: Added avFabricAttachStats,
                         avFabricAttachStatsClearErrorCounters,
			 avFabricAttachStatsClearGlobalErrorCounters, 
			 avFabricAttachDiscElemsElementOperAuthStatus,
			 avFabricAttachDiscElemsElementAsgnsOperAuthStatus,
			 avFabricAttachStatsAsgnAuthFailed and
			 avFabricAttachGlobalStatsAsgnAuthFailed.
			 Renamed enum value other(1) to invalid(1) for
			 avFabricAttachDiscElemsElementType.
			 Renamed avFabricAttachStatsAuthFailed to
			 avFabricAttachStatsDiscAuthFailed.
			 Renamed avFabricAttachGlobalStatsAuthFailed to
			 avFabricAttachGlobalStatsDiscAuthFailed
			 Changes requested by Zuyan Wang (VSP) - Prem"

    REVISION    "201509010000Z" -- September 1, 2015
    DESCRIPTION "Ver 18: Added avFabricAttachZeroTouchClientTable to support
                 Zero Touch FA Client configuration."

    REVISION    "201504270000Z" -- April 27, 2015
    DESCRIPTION "Ver 17: Added avFabricAttachDiscElemsElementTrunkId attribute
                 to export discovered element trunk associations."

    REVISION    "201504200000Z" -- April 20, 2015
    DESCRIPTION "Ver 16: Added autoPvidModeFaClient enumeration support
                 for the avFabricAttachZeroTouchOptionFlags attribute."

    REVISION    "201504080000Z" -- April 08, 2015
    DESCRIPTION "Ver 15: Added avFabricAttachStatsDiscElemExpired,
		 avFabricAttachStatsDiscElemDeleted and
		 avFabricAttachStatsAsgnDeleted under AvFabricAttachStatsEntry.
		 Also added avFabricAttachGlobalStatsDiscElemExpired,
		 avFabricAttachGlobalStatsDiscElemDeleted and 
		 avFabricAttachGlobalStatsAsgnDeleted
		 Changes requested by Zuyan Wang (VSP) - Prem"

    REVISION    "201503110000Z" -- March 11, 2015
    DESCRIPTION "Ver 14: Added values faClientOnaSdn(16) and faClientOnaSpbOIp(17) to 
		 avFabricAttachElementType and avFabricAttachDiscElemsElementType.
		 Added values provisionModeDisabled(2), provisionModeSpbm(3) and
		 provisionModeVlan(4) to avFabricAttachDiscElemsElementState.
		 Changed avFabricAttachTimeout to avFabricAttachAsgnTimeout.
		 Added mib objects avFabricAttachDiscTimeout, avFabricAttachPortMgmtIsid
		 and avFabricAttachPortMgmtCvid.
		 Changes requested by Zuyan Wang (VSP) - Prem"

    REVISION    "201412180000Z" -- December 18, 2014
    DESCRIPTION "Ver 13: Added avFabricAttachExtendedLogging attribute to
                 control extended logging capabilities. Added binding source
                 attribute to the avFabricAttachIsidVlanAsgnsTable."

    REVISION    "201412050000Z" -- December 5, 2014
    DESCRIPTION "Ver 12: Updated the avFabricAttachPortTable with per-port
                 authentication attributes (avFabricAttachPortMsgAuthStatus,
                 avFabricAttachPortMsgAuthKey). Updated discovered element
                 authentication status enumerations. Updated statistics
                 table object names by removing 'Sdk' to avoid confusion."

    REVISION    "201411100000Z" -- November 10, 2014
    DESCRIPTION "Ver 11: Added avFabricAttachTimeout, avFabricAttachSdkStatsTable, 
                 avFabricAttachGlobalSdkStats mib objects.
		 Requested by Zuyan Wang for Fabric Attach on VSP8K (prempa)."

    REVISION    "201410280000Z" -- October 28, 2014
    DESCRIPTION "Ver 10: Added standalone proxy attributes."

    REVISION    "201410060000Z" -- October 6, 2014
    DESCRIPTION "Ver 9:  Added Zero Touch attribute definitions.
                         Updated FA Discovered Elements table."

    REVISION    "201409100000Z" -- September 10, 2014
    DESCRIPTION "Ver 8:  Updated attribute enumerations and naming.
                         Updated FA Discovered Elements table."

    REVISION    "201407160000Z" -- July 16, 2014
    DESCRIPTION "Ver 7:  Added Auto Provision support."

    REVISION    "201404240000Z" -- April 24, 2014
    DESCRIPTION "Ver 6:  Updated FA element names in enumerations and 
                         object descriptions."

    REVISION    "201403030000Z" -- March 3, 2014
    DESCRIPTION "Ver 5:  Added FA Discovered Elements table."

    REVISION    "201401300000Z" -- January 30, 2014
    DESCRIPTION "Ver 4:  Added the ability to control host proxy operation.
                         Expanded and clarified FA element types."

    REVISION    "201311220000Z" -- November 22, 2013
    DESCRIPTION "Ver 3:  Added support for message authentication."

    REVISION    "201310110000Z" -- October 11, 2013
    DESCRIPTION "Ver 2:  Added avFabricAttachPortTable and avFabricAttachAutoAttachService.
                         Added RowStatus to IMPORTS."

    REVISION    "201308120000Z" -- August 12, 2013
    DESCRIPTION "Ver 1:  Initial version."

    ::= { bayStackMibs 46 }

avFabricAttachNotifications OBJECT IDENTIFIER ::= { avayaFabricAttachMib 0 }
avFabricAttachObjects       OBJECT IDENTIFIER ::= { avayaFabricAttachMib 1 }
avFabricAttachNotifyObjects OBJECT IDENTIFIER ::= { avayaFabricAttachMib 2 }

--
-- Fabric Attach scalar attributes
--

avFabricAttachService OBJECT-TYPE
    SYNTAX         INTEGER {
                       enabled(1),
                       disabled(2)
                   }
    MAX-ACCESS     read-write
    STATUS         current
    DESCRIPTION
        "Exports the status of the Fabric 
        Attach service."

    ::= { avFabricAttachObjects 1 }

avFabricAttachElementType OBJECT-TYPE
    SYNTAX         INTEGER {
                       other(1),
                       faServer(2),
                       faProxy(3),
                       faServerNoAuth(4),
                       faProxyNoAuth(5),
                       faClientWapType1(6),
                       faClientWapType2(7),
                       faClientSwitch(8),
                       faClientRouter(9),
                       faClientIpPhone(10),
                       faClientIpCamera(11),
                       faClientIpVideo(12),
                       faClientSecurityDev(13),
                       faClientVirtSwitch(14),
                       faClientSrvrEndpt(15),
                       faClientOnaSdn(16),
                       faClientOnaSpbOIp(17)
                   }
    MAX-ACCESS     read-write
    STATUS         current
    DESCRIPTION
        "Exports the Fabric Attach element type 
        indicating the services supported by 
        the system. May be read-only on platforms
        that only support a single element type."

    ::= { avFabricAttachObjects 2 }

avFabricAttachPrimaryServerId OBJECT-TYPE
    SYNTAX         OCTET STRING (SIZE (0..32))
    MAX-ACCESS     read-only
    STATUS         current
    DESCRIPTION
        "Exports primary server ID data on a FA
        Proxy if a primary server has been selected.
        A zero length string indicates that a
        primary server does not currently exist."

    ::= { avFabricAttachObjects 3 }

avFabricAttachPrimaryServerDescr OBJECT-TYPE
    SYNTAX         SnmpAdminString (SIZE (0..128))
    MAX-ACCESS     read-only
    STATUS         current
    DESCRIPTION
        "Exports a primary server description on a 
        FA Proxy if a primary server has been selected."

    ::= { avFabricAttachObjects 4 }

--
-- Fabric Attach I-SID/VLAN Assignment Table support        
--

avFabricAttachIsidVlanAsgnsTable OBJECT-TYPE
    SYNTAX      SEQUENCE OF AvFabricAttachIsidVlanAsgnsEntry
    MAX-ACCESS  not-accessible
    STATUS      current
    DESCRIPTION
        "This table contains the I-SID <--> VLAN assignments
        for the Fabric Attach application."

    ::= { avFabricAttachObjects 5 }

avFabricAttachIsidVlanAsgnsEntry OBJECT-TYPE
    SYNTAX      AvFabricAttachIsidVlanAsgnsEntry
    MAX-ACCESS  not-accessible
    STATUS      current
    DESCRIPTION
        "Information about the I-SID <--> VLAN assignments
        for the Fabric Attach application."

    INDEX { avFabricAttachIsidVlanAsgnsIfIndex, 
            avFabricAttachIsidVlanAsgnsIsid, 
            avFabricAttachIsidVlanAsgnsVlan }

    ::= { avFabricAttachIsidVlanAsgnsTable 1 }

AvFabricAttachIsidVlanAsgnsEntry ::= SEQUENCE {
    avFabricAttachIsidVlanAsgnsIfIndex    Integer32,
    avFabricAttachIsidVlanAsgnsIsid       Integer32,
    avFabricAttachIsidVlanAsgnsVlan       Integer32,
    avFabricAttachIsidVlanAsgnsState      INTEGER,
    avFabricAttachIsidVlanAsgnsRowStatus  RowStatus,
    avFabricAttachIsidVlanAsgnsOrigin     INTEGER,
    avFabricAttachIsidVlanAsgnsIsidName  DisplayString 
}

avFabricAttachIsidVlanAsgnsIfIndex OBJECT-TYPE
    SYNTAX         Integer32 (0..65535)
    MAX-ACCESS     not-accessible
    STATUS         current
    DESCRIPTION
        "Interface identifier component of the I-SID <-> 
        VLAN assignment."

    ::= { avFabricAttachIsidVlanAsgnsEntry 1 }

avFabricAttachIsidVlanAsgnsIsid OBJECT-TYPE
    SYNTAX         Integer32 (0..16777215)
    MAX-ACCESS     not-accessible
    STATUS         current
    DESCRIPTION
        "I-SID component of the I-SID <-> VLAN 
        assignment."

    ::= { avFabricAttachIsidVlanAsgnsEntry 2 }

avFabricAttachIsidVlanAsgnsVlan OBJECT-TYPE
    SYNTAX         Integer32 (1..4094)
    MAX-ACCESS     not-accessible
    STATUS         current
    DESCRIPTION
        "VLAN ID component of the I-SID <-> VLAN 
        assignment."

    ::= { avFabricAttachIsidVlanAsgnsEntry 3 }

avFabricAttachIsidVlanAsgnsState OBJECT-TYPE
    SYNTAX         INTEGER {
                       other(1),
                       pending(2),
                       active(3),
                       rejected(4)
                   }
    MAX-ACCESS     read-only
    STATUS         current
    DESCRIPTION
        "The current state of the Fabric Attach
        I-SID <-> VLAN assignment."

    ::= { avFabricAttachIsidVlanAsgnsEntry 4 }

avFabricAttachIsidVlanAsgnsRowStatus OBJECT-TYPE
    SYNTAX         RowStatus
    MAX-ACCESS     read-create
    STATUS         current
    DESCRIPTION
        "This object allows entries to be created and deleted
        in the avFabricAttachIsidVlanAsgnsTable."

    ::= { avFabricAttachIsidVlanAsgnsEntry 5 }

avFabricAttachIsidVlanAsgnsOrigin OBJECT-TYPE
    SYNTAX         INTEGER {
                       other(1),
                       faProxy(2),
                       faClient(3),
                       faRadiusClient(4),
                       faZeroTouchClient(5)
                   }
    MAX-ACCESS     read-only
    STATUS         current
    DESCRIPTION
        "Origin information for the Fabric Attach
        I-SID <-> VLAN assignment."

    ::= { avFabricAttachIsidVlanAsgnsEntry 6 }

avFabricAttachIsidVlanAsgnsIsidName OBJECT-TYPE
    SYNTAX             DisplayString (SIZE (0..64))
    MAX-ACCESS    read-only
    STATUS             current
    DESCRIPTION   "The administratively-assigned name for the I-SID.
                               This name is configured on the device and is not
                               learned via the FA TLVs."
     ::= { avFabricAttachIsidVlanAsgnsEntry 7 } 


--
-- Fabric Attach Port Table support
--

avFabricAttachPortTable OBJECT-TYPE
    SYNTAX      SEQUENCE OF AvFabricAttachPortEntry
    MAX-ACCESS  not-accessible
    STATUS      current
    DESCRIPTION
        "This table contains port-specific data
        for the Fabric Attach application."

    ::= { avFabricAttachObjects 6 }

avFabricAttachPortEntry OBJECT-TYPE
    SYNTAX      AvFabricAttachPortEntry
    MAX-ACCESS  not-accessible
    STATUS      current
    DESCRIPTION
        "Port-specific data related to the
        Fabric Attach application."

    INDEX { avFabricAttachPortIfIndex }

    ::= { avFabricAttachPortTable 1 }

AvFabricAttachPortEntry ::= SEQUENCE {
    avFabricAttachPortIfIndex        Integer32,
    avFabricAttachPortState          INTEGER,
    avFabricAttachPortRowStatus      RowStatus,
    avFabricAttachPortMsgAuthStatus  INTEGER,
    avFabricAttachPortMsgAuthKey     OCTET STRING,
    avFabricAttachPortMgmtIsid       Integer32,
    avFabricAttachPortMgmtCvid       Integer32,
    avFabricAttachPortMsgAuthKeymode INTEGER,
    avFabricAttachPortOrigin         INTEGER
}

avFabricAttachPortIfIndex OBJECT-TYPE
    SYNTAX         Integer32 (0..65535)
    MAX-ACCESS     not-accessible
    STATUS         current
    DESCRIPTION
        "Port (ifIndex) identifier attribute."

    ::= { avFabricAttachPortEntry 1 }

avFabricAttachPortState OBJECT-TYPE
    SYNTAX         INTEGER {
                       enabled(1),
                       disabled(2)
                   }
    MAX-ACCESS     read-create
    STATUS         current
    DESCRIPTION
        "The current port state from a Fabric Attach
        perspective. Indicates whether FA TLVs will
        be included in LLDPDUs generated on the port
        (enabled) or not (disabled)."

    ::= { avFabricAttachPortEntry 2 }

avFabricAttachPortRowStatus OBJECT-TYPE
    SYNTAX         RowStatus
    MAX-ACCESS     read-create
    STATUS         current
    DESCRIPTION
        "This object allows entries to be created, deleted
        and modified in the avFabricAttachPortTable, if the
        operation is supported by the agent."

    ::= { avFabricAttachPortEntry 3 }

avFabricAttachPortMsgAuthStatus OBJECT-TYPE
    SYNTAX         INTEGER {
                       enabled(1),
                       disabled(2)
                   }
    MAX-ACCESS     read-create
    STATUS         current
    DESCRIPTION
        "Controls the current Fabric Attach 
        message authentication status for the
        associated interface."

    ::= { avFabricAttachPortEntry 4 }

avFabricAttachPortMsgAuthKey OBJECT-TYPE
    SYNTAX         OCTET STRING (SIZE(0..32))
    MAX-ACCESS     read-create
    STATUS         current
    DESCRIPTION
        "Provides access to the Fabric Attach 
        message authentication key for the associated
        interface. Can be used to establish a new
        key of length 1..32 octets. Always returns 
        a zero-length string when queried."

    ::= { avFabricAttachPortEntry 5 }

avFabricAttachPortMgmtIsid OBJECT-TYPE
    SYNTAX         Integer32(0..16777215)
    MAX-ACCESS     read-create
    STATUS         current
    DESCRIPTION
        "Fabric Attach management i-sid for the associated
        interface. Zero means the management i-sid feature is 
        not enabled"
    DEFVAL         { 0 }

    ::= { avFabricAttachPortEntry 6 }

avFabricAttachPortMgmtCvid OBJECT-TYPE
    SYNTAX         Integer32(0..4096)
    MAX-ACCESS     read-create
    STATUS         current
    DESCRIPTION
        "Fabric Attach management customer vid for 
        the associated interface. Zero means the 
        management i-sid feature is not enabled. 
        4096 means it is untagged"
    DEFVAL         { 0 }

    ::= { avFabricAttachPortEntry 7 }

avFabricAttachPortMsgAuthKeymode OBJECT-TYPE
    SYNTAX         INTEGER {
                       strict(1),
                       standard(2)
                   }
    MAX-ACCESS     read-create
    STATUS         current
    DESCRIPTION
        "Controls the current Fabric Attach 
        message authentication key-mode for the
        associated interface.

        A value of 'strict(1)' indicates that
        authentication using only the user-defined
        authentication key should be performed.

        A value of 'standard(2)' indicates that
        authentication using the user-defined
        authentication key as well as the default
        authentication key should be performed."

    ::= { avFabricAttachPortEntry 8 }



avFabricAttachPortOrigin OBJECT-TYPE
    SYNTAX         INTEGER {
                        config(1),
                        autoSense(2)
                   }
    MAX-ACCESS     read-only
    STATUS         current
    DESCRIPTION
        "Fabric Attach Origin indicates how the FA 
        interface was created: manual (CLI/SNMP), 
        ZTF (Auto-Sense) or other."
    DEFVAL         { 1 }

    ::= { avFabricAttachPortEntry 9 }


avFabricAttachZeroTouchService OBJECT-TYPE
    SYNTAX         INTEGER {
                       enabled(1),
                       disabled(2)
                   }
    MAX-ACCESS     read-write
    STATUS         current
    DESCRIPTION
        "Controls the status of the Fabric 
        Attach Zero Touch service."

    ::= { avFabricAttachObjects 7 }

avFabricAttachMsgAuthStatus OBJECT-TYPE
    SYNTAX         INTEGER {
                       enabled(1),
                       disabled(2)
                   }
    MAX-ACCESS     read-write
    STATUS         current
    DESCRIPTION
        "Controls the current Fabric Attach 
        message authentication status."

    ::= { avFabricAttachObjects 8 }

avFabricAttachMsgAuthKey OBJECT-TYPE
    SYNTAX         OCTET STRING (SIZE(0..32))
    MAX-ACCESS     read-write
    STATUS         current
    DESCRIPTION
        "Provides access to the Fabric Attach 
        message authentication key. Can be used
        to establish a new key of length 1..32
        octets. Always returns a zero-length 
        string when queried."

    ::= { avFabricAttachObjects 9 }

avFabricAttachClientProxyStatus OBJECT-TYPE
    SYNTAX         INTEGER {
                       enabled(1),
                       disabled(2)
                   }
    MAX-ACCESS     read-write
    STATUS         current
    DESCRIPTION
        "Controls the current Fabric Attach 
        client proxy status. A FA Proxy provides
        proxy services to FA Clients only when
        client proxy support is enabled."

    ::= { avFabricAttachObjects 10 }

--
-- Fabric Attach Discovered Elements Table support
--

avFabricAttachDiscElemsTable OBJECT-TYPE
    SYNTAX      SEQUENCE OF AvFabricAttachDiscElemsEntry
    MAX-ACCESS  not-accessible
    STATUS      current
    DESCRIPTION
        "This table contains details about locally
        connected Fabric Attach elements that have
        been discovered."

    ::= { avFabricAttachObjects 11 }

avFabricAttachDiscElemsEntry OBJECT-TYPE
    SYNTAX      AvFabricAttachDiscElemsEntry
    MAX-ACCESS  not-accessible
    STATUS      current
    DESCRIPTION
        "Contains details about a locally connected
        Fabric Attach element."

    INDEX { avFabricAttachDiscElemsIfIndex }

    ::= { avFabricAttachDiscElemsTable 1 }

AvFabricAttachDiscElemsEntry ::= SEQUENCE {
    avFabricAttachDiscElemsIfIndex                    Integer32,
    avFabricAttachDiscElemsElementType                INTEGER,
    avFabricAttachDiscElemsElementVlan                Integer32,
    avFabricAttachDiscElemsElementId                  OCTET STRING,
    avFabricAttachDiscElemsElementState               BITS,
    avFabricAttachDiscElemsElementAuth                INTEGER,
    avFabricAttachDiscElemsElementTrunkId             Integer32,
    avFabricAttachDiscElemsElementOperAuthStatus      INTEGER,
    avFabricAttachDiscElemsElementAsgnsOperAuthStatus INTEGER,
    avFabricAttachDiscElemsAsgnsAuth                  INTEGER
}

avFabricAttachDiscElemsIfIndex OBJECT-TYPE
    SYNTAX         Integer32 (0..65535)
    MAX-ACCESS     not-accessible
    STATUS         current
    DESCRIPTION
        "Identifies the interface through which the
        Fabric Attach element represented by this entry
        was discovered."

    ::= { avFabricAttachDiscElemsEntry 1 }

avFabricAttachDiscElemsElementType OBJECT-TYPE
    SYNTAX         INTEGER {
                       other(1),
                       faServer(2),
                       faProxy(3),
                       faServerNoAuth(4),
                       faProxyNoAuth(5),
                       faClientWapType1(6),
                       faClientWapType2(7),
                       faClientSwitch(8),
                       faClientRouter(9),
                       faClientIpPhone(10),
                       faClientIpCamera(11),
                       faClientIpVideo(12),
                       faClientSecurityDev(13),
                       faClientVirtSwitch(14),
                       faClientSrvrEndpt(15),
                       faClientOnaSdn(16),
                       faClientOnaSpbOIp(17)
                   }
    MAX-ACCESS     read-only
    STATUS         current
    DESCRIPTION
        "Identifies the Fabric Attach element type
        as advertised through LLDP." 

    ::= { avFabricAttachDiscElemsEntry 2 }

avFabricAttachDiscElemsElementVlan OBJECT-TYPE
    SYNTAX         Integer32 (0..4095)
    MAX-ACCESS     read-only
    STATUS         current
    DESCRIPTION
        "Identifies the Fabric Attach element VLAN
        as advertised through LLDP." 

    ::= { avFabricAttachDiscElemsEntry 3 }

avFabricAttachDiscElemsElementId OBJECT-TYPE
    SYNTAX         OCTET STRING (SIZE (0..32))
    MAX-ACCESS     read-only
    STATUS         current
    DESCRIPTION
        "Exports the Chassis ID associated with the
        discovered Fabric Attach element as advertised
        through LLDP."

    ::= { avFabricAttachDiscElemsEntry 4 }

avFabricAttachDiscElemsElementState OBJECT-TYPE
    SYNTAX         BITS {
                       trafficTagged(0),
                       trafficTaggedAndUntagged(1),
                       provisionModeDisabled(2),
                       provisionModeSpbm(3),
                       provisionModeVlan(4)
                   }
    MAX-ACCESS     read-only
    STATUS         current
    DESCRIPTION
        "Exports the state flag data associated with the
        discovered Fabric Attach element as advertised
        through LLDP."

    ::= { avFabricAttachDiscElemsEntry 5 }

avFabricAttachDiscElemsElementAuth OBJECT-TYPE
    SYNTAX         INTEGER {
                       authenticationPass(1),
                       authenticationFail(2),
                       notAuthenticated(3),
		       none(4)
                   }
    MAX-ACCESS     read-only
    STATUS         current
    DESCRIPTION
        "Discovered element authentication status."

    ::= { avFabricAttachDiscElemsEntry 6 }

avFabricAttachDiscElemsElementTrunkId OBJECT-TYPE
    SYNTAX         Integer32 (0..65535)
    MAX-ACCESS     read-only
    STATUS         current
    DESCRIPTION
        "Identifies the trunk ID through which the
        Fabric Attach element represented by this entry
        was discovered."

    ::= { avFabricAttachDiscElemsEntry 7 }

avFabricAttachDiscElemsElementOperAuthStatus OBJECT-TYPE
    SYNTAX	   INTEGER {
    			none(1), -- no packets received yet 
			successNoAuth(2), -- success with no-auth on either local or remote
			successAuth(3), -- success with auth on both local and remote
			failMismatchedKeys(4), -- failure due to key mismatch
			failLocalAuthRemoteNoAuth(5), -- failure due to local auth and remote no-auth
			failLocalNoAuthRemoteAuth(6) -- failure due to local no-auth and remote auth
		   }
    MAX-ACCESS     read-only
    STATUS         current
    DESCRIPTION    "the current operational Fabric Attach elements 
		    authentication status for the associated interface."
    ::= { avFabricAttachDiscElemsEntry 8 }

avFabricAttachDiscElemsElementAsgnsOperAuthStatus OBJECT-TYPE
    SYNTAX	   INTEGER {
    			none(1), -- no packets received yet
			successNoAuth(2), -- success with no-auth on either local or remote
			successAuth(3), -- success with auth on both local and remote
			failMismatchedKeys(4), -- failure due to key mismatch
			failLocalAuthRemoteNoAuth(5), -- failure due to local auth and remote no-auth
			failLocalNoAuthRemoteAuth(6) -- failure due to local no-auth and remote auth
		   } 
    MAX-ACCESS	   read-only
    STATUS	   current
    DESCRIPTION    "the current operational Fabric Attach assignment 
		    authentication status for the associated interface."

    ::= { avFabricAttachDiscElemsEntry 9 }

avFabricAttachDiscElemsAsgnsAuth OBJECT-TYPE
    SYNTAX	   INTEGER {
    			authenticationPass(1),
			authenticationFail(2),
			notAuthenticated(3),
			none(4)
		   } 
    MAX-ACCESS	   read-only
    STATUS	   current
    DESCRIPTION    "The assignment authentication status"

    ::= { avFabricAttachDiscElemsEntry 10 }

avFabricAttachAutoProvision OBJECT-TYPE
    SYNTAX         INTEGER {
                       disabled(1),
                       faServer(2),
                       faProxy(3)
                   }
    MAX-ACCESS     read-write
    STATUS         current
    DESCRIPTION
        "Exports the Fabric Attach Auto Provision 
        setting indicating the services supported by 
        the system. May be read-only on platforms
        that don't support this functionality."

    ::= { avFabricAttachObjects 12 }

avFabricAttachProvisionMode OBJECT-TYPE
    SYNTAX         INTEGER {
                       disabled(1),
                       spbm(2),
                       vlan(3)
                   }
    MAX-ACCESS     read-only
    STATUS         current
    DESCRIPTION
        "Exports the Fabric Attach provision mode."

    ::= { avFabricAttachObjects 13 }

avFabricAttachZeroTouchOptionFlags OBJECT-TYPE
    SYNTAX         BITS {
                       ipAddrDhcp(0),
                       autoPortModeFaClient(1),
                       autoPortModeMhmv(2),
                       radiusServer(3),
                       nsv(4),
                       autoTrustedModeFaClient(5),
                       autoPvidModeFaClient(6),
                       autoClientAttach(7),
                       autoMgmtVlanFaClient(8)
                   }
    MAX-ACCESS     read-write
    STATUS         current
    DESCRIPTION
        "Exports the Zero Touch option data."

    ::= { avFabricAttachObjects 14 }

--
-- Fabric Attach Zero Touch NSV Table support        
--

avFabricAttachZeroTouchNsvTable OBJECT-TYPE
    SYNTAX      SEQUENCE OF AvFabricAttachZeroTouchNsvEntry
    MAX-ACCESS  not-accessible
    STATUS      current
    DESCRIPTION
        "This table contains the Zero Touch NSV specifications
        for the Fabric Attach application."

    ::= { avFabricAttachObjects 15 }

avFabricAttachZeroTouchNsvEntry OBJECT-TYPE
    SYNTAX      AvFabricAttachZeroTouchNsvEntry
    MAX-ACCESS  not-accessible
    STATUS      current
    DESCRIPTION
        "Information about the Zero Touch NSV specifications
        for the Fabric Attach application."

    INDEX { avFabricAttachZeroTouchNsvType }

    ::= { avFabricAttachZeroTouchNsvTable 1 }

AvFabricAttachZeroTouchNsvEntry ::= SEQUENCE {
    avFabricAttachZeroTouchNsvType          Integer32,
    avFabricAttachZeroTouchNsvVlan          Integer32,
    avFabricAttachZeroTouchNsvPortPriority  Integer32,
    avFabricAttachZeroTouchNsvStateFlags    BITS,
    avFabricAttachZeroTouchNsvRowStatus     RowStatus,
    avFabricAttachZeroTouchNsvIsid          Integer32
}

avFabricAttachZeroTouchNsvType OBJECT-TYPE
    SYNTAX         Integer32 (0..63)
    MAX-ACCESS     not-accessible
    STATUS         current
    DESCRIPTION
        "Element type identifier component of the NSV
        specification."

    ::= { avFabricAttachZeroTouchNsvEntry 1 }

avFabricAttachZeroTouchNsvVlan OBJECT-TYPE
    SYNTAX         Integer32 (1..4094)
    MAX-ACCESS     read-create
    STATUS         current
    DESCRIPTION
        "VLAN ID component of the NSV specification."

    ::= { avFabricAttachZeroTouchNsvEntry 2 }

avFabricAttachZeroTouchNsvPortPriority OBJECT-TYPE
    SYNTAX         Integer32 (0..7)
    MAX-ACCESS     read-create
    STATUS         current
    DESCRIPTION
        "Port priority component of the NSV specification."
    DEFVAL	   { 0 }

    ::= { avFabricAttachZeroTouchNsvEntry 3 }

avFabricAttachZeroTouchNsvStateFlags OBJECT-TYPE
    SYNTAX         BITS {
                       updatePvid(0),
                       updatePortPriority(1)
                   }
    MAX-ACCESS     read-create
    STATUS         current
    DESCRIPTION
        "State flags associated with the NSV specification."

    ::= { avFabricAttachZeroTouchNsvEntry 4 }

avFabricAttachZeroTouchNsvRowStatus OBJECT-TYPE
    SYNTAX         RowStatus
    MAX-ACCESS     read-create
    STATUS         current
    DESCRIPTION
        "This object allows entries to be created and deleted
        in the avFabricAttachZeroTouchNsvTable."

    ::= { avFabricAttachZeroTouchNsvEntry 5 }

avFabricAttachZeroTouchNsvIsid OBJECT-TYPE
    SYNTAX         Integer32 (0..16777214)
    MAX-ACCESS     read-create
    STATUS         current
    DESCRIPTION
        "I-SID component of the NSV specification. A value of
        0 indicates that an I-SID has not been specified."
    DEFVAL	   { 0 }

    ::= { avFabricAttachZeroTouchNsvEntry 6 }

avFabricAttachZeroTouchRadiusPriSrvrIpv4Addr OBJECT-TYPE
    SYNTAX         OCTET STRING (SIZE (4))
    MAX-ACCESS     read-only
    STATUS         current
    DESCRIPTION
        "This object represents the Zero Touch RADIUS
        primary server IPv4 address information currently
        maintained by the FA agent."

    ::= { avFabricAttachObjects 16 }

avFabricAttachZeroTouchRadiusSecSrvrIpv4Addr OBJECT-TYPE
    SYNTAX         OCTET STRING (SIZE (4))
    MAX-ACCESS     read-only
    STATUS         current
    DESCRIPTION
        "This object represents the Zero Touch RADIUS
        secondary server IPv4 address information currently
        maintained by the FA agent."

    ::= { avFabricAttachObjects 17 }

avFabricAttachZeroTouchRadiusTimeout OBJECT-TYPE
    SYNTAX         Integer32 (1..60)
    MAX-ACCESS     read-only
    STATUS         current
    DESCRIPTION
        "This object represents the Zero Touch RADIUS
        timeout information currently maintained by 
        the FA agent."

    ::= { avFabricAttachObjects 18 }

avFabricAttachStandaloneProxy OBJECT-TYPE
    SYNTAX         INTEGER {
                       enabled(1),
                       disabled(2)
                   }
    MAX-ACCESS     read-write
    STATUS         current
    DESCRIPTION
        "Controls the standalone FA Proxy mode."

    ::= { avFabricAttachObjects 19 }

avFabricAttachStaticUplinkIfIndex OBJECT-TYPE
    SYNTAX         Integer32 (0..65535)
    MAX-ACCESS     read-write
    STATUS         current
    DESCRIPTION
        "Static uplink (ifIndex) identifier attribute."

    ::= { avFabricAttachObjects 20 }

avFabricAttachStaticUplinkTrunk OBJECT-TYPE
    SYNTAX         Integer32 (0..1023)
    MAX-ACCESS     read-write
    STATUS         current
    DESCRIPTION
        "Static uplink (trunk ID) identifier attribute."

    ::= { avFabricAttachObjects 21 }

avFabricAttachAsgnTimeout  OBJECT-TYPE
    SYNTAX        Integer32 (30..480)
    MAX-ACCESS    read-write
    STATUS        current
    DESCRIPTION   "Exports the Fabric Attach assignment timeout."
    DEFVAL        { 240 }
    ::= { avFabricAttachObjects 22 }

avFabricAttachStatsTable  OBJECT-TYPE
    SYNTAX        SEQUENCE OF AvFabricAttachStatsEntry
    MAX-ACCESS    not-accessible
    STATUS        current
    DESCRIPTION   "This table contains Fabric Attach port 
                   statistics data."
    ::= { avFabricAttachObjects 23 }

avFabricAttachStatsEntry OBJECT-TYPE
    SYNTAX        AvFabricAttachStatsEntry
    MAX-ACCESS    not-accessible
    STATUS        current
    DESCRIPTION   "Each entry contains Fabric Attach operational 
                   statistics for a specific device port. Ports 
                   are identified by their MIB II ifIndex value."
    INDEX         { avFabricAttachStatsPortIndex }
    ::= { avFabricAttachStatsTable 1 }

AvFabricAttachStatsEntry ::= SEQUENCE {
             avFabricAttachStatsPortIndex        	Integer32,
             avFabricAttachStatsDiscElemReceived   	Counter32,
             avFabricAttachStatsAsgnReceived		Counter32,
             avFabricAttachStatsAsgnAccepted		Counter32,
             avFabricAttachStatsAsgnRejected		Counter32,
             avFabricAttachStatsAsgnExpired		Counter32,
             avFabricAttachStatsDiscAuthFailed		Counter32,
             avFabricAttachStatsDiscElemExpired         Counter32,
             avFabricAttachStatsDiscElemDeleted         Counter32, 
             avFabricAttachStatsAsgnDeleted             Counter32,
	     avFabricAttachStatsAsgnAuthFailed		Counter32
    }

avFabricAttachStatsPortIndex OBJECT-TYPE
    SYNTAX        Integer32 (0..65535)
    MAX-ACCESS    not-accessible
    STATUS        current
    DESCRIPTION   "An index value that uniquely identifies a port.
                   This value corresponds to a MIB II ifIndex."
    ::= { avFabricAttachStatsEntry 1 }

avFabricAttachStatsDiscElemReceived  OBJECT-TYPE
    SYNTAX        Counter32
    MAX-ACCESS    read-only
    STATUS        current
    DESCRIPTION   "Indicates the number of FA Element TLVs 
                   received on the identified port."
    ::= { avFabricAttachStatsEntry 2 }

avFabricAttachStatsAsgnReceived   OBJECT-TYPE
    SYNTAX        Counter32
    MAX-ACCESS    read-only
    STATUS        current
    DESCRIPTION   "Indicates the number of I-SID/VLAN bindings
                   received in FA I-SID/VLAN Assignment TLVs on
                   the identified port."
    ::= { avFabricAttachStatsEntry 3 }

avFabricAttachStatsAsgnAccepted  OBJECT-TYPE
    SYNTAX        Counter32
    MAX-ACCESS    read-only
    STATUS        current
    DESCRIPTION   "Indicates the number of I-SID/VLAN bindings
                   from received FA I-SID/VLAN Assignment TLVs
                   that are accepted (activated) on the identified
                   port. Counter is incremented when the binding
                   transitions from a non-accepted state (e.g.,
                   'pending', 'rejected') to the accepted state."
    ::= { avFabricAttachStatsEntry 4 }

avFabricAttachStatsAsgnRejected OBJECT-TYPE
    SYNTAX        Counter32
    MAX-ACCESS    read-only
    STATUS        current
    DESCRIPTION   "Indicates the number of I-SID/VLAN bindings
                   from received FA I-SID/VLAN Assignment TLVs
                   that are rejected on the identified port. 
                   Counter is incremented when the binding
                   transitions from a non-rejected state (e.g.,
                   'pending', 'accepted') to the rejected state."
    ::= { avFabricAttachStatsEntry 5 }

avFabricAttachStatsAsgnExpired OBJECT-TYPE
    SYNTAX        Counter32
    MAX-ACCESS    read-only
    STATUS        current
    DESCRIPTION   "Indicates the number of I-SID/VLAN bindings
                   from received FA I-SID/VLAN Assignment TLVs
                   that have expired on the identified port. 
                   Counter is not incremented when bindings
                   are deleted for reasons other than expiration." 
    ::= { avFabricAttachStatsEntry 6 }

avFabricAttachStatsDiscAuthFailed OBJECT-TYPE
    SYNTAX        Counter32
    MAX-ACCESS    read-only
    STATUS        current
    DESCRIPTION   "Indicates the number of received FA Element 
                   TLVs for which authentication was attempted 
                   and failed on the identified port."
    ::= { avFabricAttachStatsEntry 7 }

avFabricAttachStatsDiscElemExpired  OBJECT-TYPE
    SYNTAX        Counter32
    MAX-ACCESS    read-only
    STATUS        current
    DESCRIPTION   "Indicates the number of discovered FA elements
                   from received FA Element TLVs that have expired 
                   on the identified port. Counter is not incremented 
                   when elements are deleted for reasons other than 
                   expiration." 
    ::= { avFabricAttachStatsEntry 8 }

avFabricAttachStatsDiscElemDeleted  OBJECT-TYPE
    SYNTAX        Counter32
    MAX-ACCESS    read-only
    STATUS        current
    DESCRIPTION   "Indicates the number of discovered FA elements
                   from received FA Element TLVs that have been
                   deleted on the identified port. Counter is only 
                   incremented when elements are deleted for 
                   reasons other than expiration." 
    ::= { avFabricAttachStatsEntry 9 }

avFabricAttachStatsAsgnDeleted OBJECT-TYPE
    SYNTAX        Counter32
    MAX-ACCESS    read-only
    STATUS        current
    DESCRIPTION   "Indicates the number of I-SID/VLAN bindings
                   from received FA I-SID/VLAN Assignment TLVs
                   that have been deleted on the identified port.
                   Counter is only incremented when bindings
                   are deleted for reasons other than expiration." 
    ::= { avFabricAttachStatsEntry 10 }

avFabricAttachStatsAsgnAuthFailed OBJECT-TYPE
    SYNTAX	  Counter32
    MAX-ACCESS	  read-only
    STATUS	  current
    DESCRIPTION   "Indicates the number of received FA I-SID/VLAN 
                   Assignment TLVs for which authentication was 
                   attempted and failed on the identified port."
    ::= { avFabricAttachStatsEntry 11 }

avFabricAttachGlobalStats    OBJECT IDENTIFIER ::= { avFabricAttachObjects 24 }

avFabricAttachGlobalStatsDiscElemReceived  OBJECT-TYPE
    SYNTAX        Counter32
    MAX-ACCESS    read-only
    STATUS        current
    DESCRIPTION   "Indicates the number of FA Element TLVs 
                   received on all device ports since the
                   most recent epoch (e.g., device reset,
                   global statistics reset)."
    ::= { avFabricAttachGlobalStats 1 }

avFabricAttachGlobalStatsAsgnReceived   OBJECT-TYPE
    SYNTAX        Counter32
    MAX-ACCESS    read-only
    STATUS        current
    DESCRIPTION   "Indicates the number of I-SID/VLAN bindings
                   received in FA I-SID/VLAN Assignment TLVs on
                   all device ports since the most recent epoch 
                   (e.g., device reset, global statistics reset)."
    ::= { avFabricAttachGlobalStats 2 }

avFabricAttachGlobalStatsAsgnAccepted  OBJECT-TYPE
    SYNTAX        Counter32
    MAX-ACCESS    read-only
    STATUS        current
    DESCRIPTION   "Indicates the number of I-SID/VLAN bindings
                   from received FA I-SID/VLAN Assignment TLVs
                   that are accepted (activated) on all device
                   ports since the most recent epoch (e.g., 
                   device reset, global statistics reset). 
                   Counter is incremented when the binding 
                   transitions from a non-accepted state (e.g., 
                   'pending', 'rejected') to the accepted state."
    ::= { avFabricAttachGlobalStats 3 }

avFabricAttachGlobalStatsAsgnRejected OBJECT-TYPE
    SYNTAX        Counter32
    MAX-ACCESS    read-only
    STATUS        current
    DESCRIPTION   "Indicates the number of I-SID/VLAN bindings
                   from received FA I-SID/VLAN Assignment TLVs
                   that are rejected on all device ports since 
                   the most recent epoch (e.g., device reset, 
                   global statistics reset). Counter is 
                   incremented when the binding transitions from 
                   a non-rejected state (e.g., 'pending', 
                   'accepted') to the rejected state."
    ::= { avFabricAttachGlobalStats 4 }

avFabricAttachGlobalStatsAsgnExpired OBJECT-TYPE
    SYNTAX        Counter32
    MAX-ACCESS    read-only
    STATUS        current
    DESCRIPTION   "Indicates the number of I-SID/VLAN bindings
                   from received FA I-SID/VLAN Assignment TLVs
                   that have expired on all device ports since 
                   the most recent epoch (e.g., device reset, 
                   global statistics reset). Counter is not 
                   incremented when bindings are deleted for 
                   reasons other than expiration." 
    ::= { avFabricAttachGlobalStats 5 }

avFabricAttachGlobalStatsDiscAuthFailed OBJECT-TYPE
    SYNTAX        Counter32
    MAX-ACCESS    read-only
    STATUS        current
    DESCRIPTION   "Indicates the number of received FA Element 
                   TLVs for which authentication was attempted 
                   and failed on all device ports since the 
                   most recent epoch (e.g., device reset, global 
                   statistics reset)."
    ::= { avFabricAttachGlobalStats 6 }

avFabricAttachGlobalStatsDiscElemExpired  OBJECT-TYPE
    SYNTAX        Counter32
    MAX-ACCESS    read-only
    STATUS        current
    DESCRIPTION   "Indicates the number of discovered FA elements
                   from received FA Element TLVs that have been
                   deleted on all device ports since the most 
                   recent epoch (e.g., device reset, global 
                   statistics reset). Counter is only incremented 
                   when elements are deleted for reasons other 
                   than expiration." 
    ::= { avFabricAttachGlobalStats 7 }

avFabricAttachGlobalStatsDiscElemDeleted  OBJECT-TYPE
    SYNTAX        Counter32
    MAX-ACCESS    read-only
    STATUS        current
    DESCRIPTION   "Indicates the number of discovered FA elements
                   from received FA Element TLVs that have been
                   deleted on all device ports since the most 
                   recent epoch (e.g., device reset, global 
                   statistics reset). Counter is only incremented 
                   when elements are deleted for reasons other 
                   than expiration." 
    ::= { avFabricAttachGlobalStats 8 }

avFabricAttachGlobalStatsAsgnDeleted OBJECT-TYPE
    SYNTAX        Counter32
    MAX-ACCESS    read-only
    STATUS        current
    DESCRIPTION   "Indicates the number of I-SID/VLAN bindings
                   from received FA I-SID/VLAN Assignment TLVs
                   that have been deleted on all device ports
                   since the most recent epoch (e.g., device 
                   reset, global statistics reset). Counter is 
                   only incremented when bindings are deleted 
                   for reasons other than expiration." 
    ::= { avFabricAttachGlobalStats 9 }

avFabricAttachGlobalStatsAsgnAuthFailed OBJECT-TYPE
    SYNTAX	  Counter32
    MAX-ACCESS    read-only
    STATUS        current
    DESCRIPTION   "Indicates the number of received FA I-SID/VLAN 
                   Assignment TLVs for which authentication was 
                   attempted and failed on all device ports
                   since the most recent epoch (e.g., device 
                   reset, global statistics reset)."
    ::= { avFabricAttachGlobalStats 10 }

avFabricAttachGlobalStatsCurReceivedBindings OBJECT-TYPE
    SYNTAX	  Counter32
    MAX-ACCESS    read-only
    STATUS        current
    DESCRIPTION   "Indicates the number of received FA I-SID/VLAN 
                   bindings currently maintained in the database."
    ::= { avFabricAttachGlobalStats 11 }

avFabricAttachGlobalStatsCurAdvertisedBindings OBJECT-TYPE
    SYNTAX	  Counter32
    MAX-ACCESS    read-only
    STATUS        current
    DESCRIPTION   "Indicates the number of FA I-SID/VLAN bindings 
                   that are currently being advertised (service
                   requests)."
    ::= { avFabricAttachGlobalStats 12 }

avFabricAttachExtendedLogging OBJECT-TYPE
    SYNTAX         INTEGER {
                       enabled(1),
                       disabled(2)
                   }
    MAX-ACCESS     read-write
    STATUS         current
    DESCRIPTION
        "Controls the Fabric Attach extended 
        logging capabilities."

    ::= { avFabricAttachObjects 25 }
 
avFabricAttachDiscTimeout  OBJECT-TYPE
    SYNTAX        Integer32 (30..480)
    MAX-ACCESS    read-write
    STATUS        current
    DESCRIPTION   "Exports the Fabric Attach discovery timeout."
    DEFVAL        { 240 }
    ::= { avFabricAttachObjects 26 }

--
-- Fabric Attach Zero Touch Client Table support        
--

avFabricAttachZeroTouchClientTable OBJECT-TYPE
    SYNTAX      SEQUENCE OF AvFabricAttachZeroTouchClientEntry
    MAX-ACCESS  not-accessible
    STATUS      current
    DESCRIPTION
        "This table contains the Zero Touch Client specifications
        for the Fabric Attach application."

    ::= { avFabricAttachObjects 27 }

avFabricAttachZeroTouchClientEntry OBJECT-TYPE
    SYNTAX      AvFabricAttachZeroTouchClientEntry
    MAX-ACCESS  not-accessible
    STATUS      current
    DESCRIPTION
        "Information about the Zero Touch Client specifications
        for the Fabric Attach application."

    INDEX { avFabricAttachZeroTouchClientType }

    ::= { avFabricAttachZeroTouchClientTable 1 }

AvFabricAttachZeroTouchClientEntry ::= SEQUENCE {
    avFabricAttachZeroTouchClientType          Integer32,
    avFabricAttachZeroTouchClientDescr         SnmpAdminString,
    avFabricAttachZeroTouchClientOptionFlags   BITS,
    avFabricAttachZeroTouchClientRowStatus     RowStatus,
    avFabricAttachZeroTouchClientName          SnmpAdminString,
    avFabricAttachZeroTouchClientOrigin        INTEGER
}

avFabricAttachZeroTouchClientType OBJECT-TYPE
    SYNTAX         Integer32 (0..255)
    MAX-ACCESS     not-accessible
    STATUS         current
    DESCRIPTION
        "FA Element type identifier component of the Client
        specification."

    ::= { avFabricAttachZeroTouchClientEntry 1 }

avFabricAttachZeroTouchClientDescr OBJECT-TYPE
    SYNTAX         SnmpAdminString (SIZE (0..80))
    MAX-ACCESS     read-create
    STATUS         current
    DESCRIPTION
        "Client description for the Client specification."

    ::= { avFabricAttachZeroTouchClientEntry 2 }

avFabricAttachZeroTouchClientOptionFlags OBJECT-TYPE
    SYNTAX         BITS {
                       ipAddrDhcp(0),
                       autoPortModeFaClient(1),
                       autoPortModeMhmv(2),
                       radiusServer(3),
                       nsv(4),
                       autoTrustedModeFaClient(5),
                       autoPvidModeFaClient(6),
                       autoClientAttach(7),
                       autoMgmtVlanFaClient(8)
                   }
    MAX-ACCESS     read-create
    STATUS         current
    DESCRIPTION
        "Zero Touch options associated with the Client 
        specification. Supported values are synchronized
        with the Zero Touch options available through the
        avFabricAttachZeroTouchOptionFlags attribute." 

    ::= { avFabricAttachZeroTouchClientEntry 3 }

avFabricAttachZeroTouchClientRowStatus OBJECT-TYPE
    SYNTAX         RowStatus
    MAX-ACCESS     read-create
    STATUS         current
    DESCRIPTION
        "This object allows entries to be created, deleted
        and modified in the avFabricAttachZeroTouchClientTable."

    ::= { avFabricAttachZeroTouchClientEntry 4 }

avFabricAttachZeroTouchClientName OBJECT-TYPE
    SYNTAX         SnmpAdminString (SIZE (0..32))
    MAX-ACCESS     read-create
    STATUS         current
    DESCRIPTION
        "Client name for the Client specification."

    ::= { avFabricAttachZeroTouchClientEntry 5 }

avFabricAttachZeroTouchClientOrigin OBJECT-TYPE
    SYNTAX         INTEGER {
                       standard(1),
                       custom(2)
                   }
    MAX-ACCESS     read-only
    STATUS         current
    DESCRIPTION
        "Client origin information. Clients may be well-known
        ('standard(1)') devices that utilize FA signaling. If
        supported, clients may also be user-defined ('custom(2)')
        devices that are typically identified by means other
        than FA signaling. Standard clients are pre-populated
        in the table and support limited modifications."

    ::= { avFabricAttachZeroTouchClientEntry 6 }

avFabricAttachStats OBJECT IDENTIFIER ::= { avFabricAttachObjects 28 }

avFabricAttachStatsClearErrorCounters OBJECT-TYPE
    SYNTAX	   TruthValue
    MAX-ACCESS	   read-write
    STATUS	   current
    DESCRIPTION
        "Clears Fabric Attach statistic and error counters
        on all device interfaces. Setting this attribute
        to 'true(1)' clears all counters. The value 'false(2)'
        is returned when the attribute is queried."
    DEFVAL	   { false }
    ::= { avFabricAttachStats 1 }

avFabricAttachStatsClearGlobalErrorCounters OBJECT-TYPE
    SYNTAX	   TruthValue
    MAX-ACCESS	   read-write
    STATUS	   current
    DESCRIPTION    
        "Clears Fabric Attach statistic and error global
        (summary) counters. Setting this attribute to 
        'true(1)' clears all summary counters. The value 
        'false(2)' is returned when the attribute is 
        queried."
    DEFVAL	   { false }
    ::= { avFabricAttachStats 2 }

avFabricAttachStatsClearPortErrorCounters OBJECT-TYPE
    SYNTAX         Integer32 (0..65535)
    MAX-ACCESS	   read-write
    STATUS	   current
    DESCRIPTION
        "Clears Fabric Attach statistic and error counters
        for a specific interface. Setting this attribute to 
        an ifIndex value identifying a device interface
        clears the counters associated with the interface.
        The value 0 is returned when the attribute is queried."
    DEFVAL	   { 0 }
    ::= { avFabricAttachStats 3 }

--
-- Fabric Attach Zero Touch Client Attach Table support        
--

avFabricAttachZeroTouchClientAttachTable OBJECT-TYPE
    SYNTAX      SEQUENCE OF AvFabricAttachZeroTouchClientAttachEntry
    MAX-ACCESS  not-accessible
    STATUS      current
    DESCRIPTION
        "This table contains the Zero Touch Client auto-attach
        specifications for the Fabric Attach application."

    ::= { avFabricAttachObjects 29 }

avFabricAttachZeroTouchClientAttachEntry OBJECT-TYPE
    SYNTAX      AvFabricAttachZeroTouchClientAttachEntry
    MAX-ACCESS  not-accessible
    STATUS      current
    DESCRIPTION
        "Information about the Zero Touch Client auto-attach
        specifications for the Fabric Attach application."

    INDEX { avFabricAttachZeroTouchClientAttachType }

    ::= { avFabricAttachZeroTouchClientAttachTable 1 }

AvFabricAttachZeroTouchClientAttachEntry ::= SEQUENCE {
    avFabricAttachZeroTouchClientAttachType           Integer32,
    avFabricAttachZeroTouchClientAttachVlan           Integer32,
    avFabricAttachZeroTouchClientAttachPortPriority   Integer32,
    avFabricAttachZeroTouchClientAttachIsid           Integer32,
    avFabricAttachZeroTouchClientAttachRowStatus      RowStatus,
    avFabricAttachZeroTouchClientAttachExcludeStatic  INTEGER,
	avFabricAttachZeroTouchClientAttachIsidName  DisplayString 
}

avFabricAttachZeroTouchClientAttachType OBJECT-TYPE
    SYNTAX         Integer32 (0..255)
    MAX-ACCESS     not-accessible
    STATUS         current
    DESCRIPTION
        "Element type identifier component of the Zero 
        Touch Client auto-attach specification."

    ::= { avFabricAttachZeroTouchClientAttachEntry 1 }

avFabricAttachZeroTouchClientAttachVlan OBJECT-TYPE
    SYNTAX         Integer32 (1..4096)
    MAX-ACCESS     read-create
    STATUS         current
    DESCRIPTION
        "VLAN ID component of the Zero Touch Client
        auto-attach specification. A value of 4096
        indicates that a VLAN has not been specified
        (e.g., an untagged traffic environment)."
    DEFVAL	   { 4096 }

    ::= { avFabricAttachZeroTouchClientAttachEntry 2 }

avFabricAttachZeroTouchClientAttachPortPriority OBJECT-TYPE
    SYNTAX         Integer32 (0..8)
    MAX-ACCESS     read-create
    STATUS         current
    DESCRIPTION
        "Port priority component of the Zero Touch Client
        auto-attach specification. A value of 8 indicates
        that a port priority has not been specified."
    DEFVAL	   { 8 }

    ::= { avFabricAttachZeroTouchClientAttachEntry 3 }

avFabricAttachZeroTouchClientAttachIsid OBJECT-TYPE
    SYNTAX         Integer32 (0..16777214)
    MAX-ACCESS     read-create
    STATUS         current
    DESCRIPTION
        "I-SID component of the Zero Touch Client auto-attach
        specification. A value of 0 indicates that an I-SID 
        has not been specified."
    DEFVAL	   { 0 }

    ::= { avFabricAttachZeroTouchClientAttachEntry 4 }

avFabricAttachZeroTouchClientAttachRowStatus OBJECT-TYPE
    SYNTAX         RowStatus
    MAX-ACCESS     read-create
    STATUS         current
    DESCRIPTION
        "This object allows entries to be created and deleted
        in the avFabricAttachZeroTouchClientAttachTable."

    ::= { avFabricAttachZeroTouchClientAttachEntry 5 }

avFabricAttachZeroTouchClientAttachExcludeStatic OBJECT-TYPE
    SYNTAX         INTEGER {
                       keepStaticVlans(1),
                       removeStaticVlans(2)
                   }
    MAX-ACCESS     read-create
    STATUS         current
    DESCRIPTION
        "Indicates if static VLANs associated with the client
        interface should be removed while the client is
        connected to the device."
    DEFVAL	   { removeStaticVlans }

    ::= { avFabricAttachZeroTouchClientAttachEntry 6 }

avFabricAttachZeroTouchClientAttachIsidName OBJECT-TYPE
    SYNTAX             DisplayString (SIZE (0..64))
    MAX-ACCESS    read-only
    STATUS             current
    DESCRIPTION   "The administratively-assigned name for the I-SID.
                               This name is configured on the device."
   ::= { avFabricAttachZeroTouchClientAttachEntry 7 }


--
-- Fabric Attach Zero Touch Client Detect Table support        
--

avFabricAttachZeroTouchClientDetectTable OBJECT-TYPE
    SYNTAX      SEQUENCE OF AvFabricAttachZeroTouchClientDetectEntry
    MAX-ACCESS  not-accessible
    STATUS      current
    DESCRIPTION
        "This table contains the Zero Touch Client detection
        specifications for the Fabric Attach application."

    ::= { avFabricAttachObjects 30 }

avFabricAttachZeroTouchClientDetectEntry OBJECT-TYPE
    SYNTAX      AvFabricAttachZeroTouchClientDetectEntry
    MAX-ACCESS  not-accessible
    STATUS      current
    DESCRIPTION
        "Information about the Zero Touch Client detection
        specifications for the Fabric Attach application."

    INDEX { avFabricAttachZeroTouchClientDetectType, 
            avFabricAttachZeroTouchClientDetectMethod }

    ::= { avFabricAttachZeroTouchClientDetectTable 1 }

AvFabricAttachZeroTouchClientDetectEntry ::= SEQUENCE {
    avFabricAttachZeroTouchClientDetectType         Integer32,
    avFabricAttachZeroTouchClientDetectMethod       INTEGER,
    avFabricAttachZeroTouchClientDetectData         OCTET STRING,
    avFabricAttachZeroTouchClientDetectElementType  Integer32,
    avFabricAttachZeroTouchClientDetectLogicOper    INTEGER,
    avFabricAttachZeroTouchClientDetectRowStatus    RowStatus
}

avFabricAttachZeroTouchClientDetectType OBJECT-TYPE
    SYNTAX         Integer32 (0..255)
    MAX-ACCESS     not-accessible
    STATUS         current
    DESCRIPTION
        "Element type identifier component of the Zero 
        Touch Client detection specification."

    ::= { avFabricAttachZeroTouchClientDetectEntry 1 }

avFabricAttachZeroTouchClientDetectMethod OBJECT-TYPE
    SYNTAX         INTEGER {
                       lldpChassisIdMac(1),
                       lldpChassisIdString(2),
                       lldpSystemDescrString(3),
                       lldpMgmtAddrIPv4(4)
                   }
    MAX-ACCESS     not-accessible
    STATUS         current
    DESCRIPTION
        "Specifies the detection method used to identify
        custom Zero Touch Clients."

    ::= { avFabricAttachZeroTouchClientDetectEntry 2 }

avFabricAttachZeroTouchClientDetectData OBJECT-TYPE
    SYNTAX         OCTET STRING (SIZE (0..32))
    MAX-ACCESS     read-create
    STATUS         current
    DESCRIPTION
        "Specifies the data that is used to identify
        custom Zero Touch Clients. Data application
        depends on the associated detection method."

    ::= { avFabricAttachZeroTouchClientDetectEntry 3 }

avFabricAttachZeroTouchClientDetectElementType OBJECT-TYPE
    SYNTAX         Integer32 (0..63)
    MAX-ACCESS     read-create
    STATUS         current
    DESCRIPTION
        "Identifies a standard FA element type that can
        be used together with the associated detection
        method/data to identify custom clients. A value
        equal to 0 indicates that the element type check
        is not required."
    DEFVAL         { 0 }

    ::= { avFabricAttachZeroTouchClientDetectEntry 4 }

avFabricAttachZeroTouchClientDetectLogicOper OBJECT-TYPE
    SYNTAX         INTEGER {
                       and(1),
                       or(2)
                   }
    MAX-ACCESS     read-create
    STATUS         current
    DESCRIPTION
        "Specifies the logic operation used to identify
        custom Zero Touch Clients when multiple detection
        methods and data sets are defined for the same
        custom client type."
    DEFVAL         { or }

    ::= { avFabricAttachZeroTouchClientDetectEntry 5 }

avFabricAttachZeroTouchClientDetectRowStatus OBJECT-TYPE
    SYNTAX         RowStatus
    MAX-ACCESS     read-create
    STATUS         current
    DESCRIPTION
        "This object allows entries to be created and deleted
        in the avFabricAttachZeroTouchClientDetectTable."

    ::= { avFabricAttachZeroTouchClientDetectEntry 6 }

avFabricAttachZeroTouchMgmtVlanDist OBJECT-TYPE
    SYNTAX         INTEGER {
                       enabled(1),
                       disabled(2)
                   }
    MAX-ACCESS     read-write
    STATUS         current
    DESCRIPTION
        "Controls the inclusion of management VLAN data
        in the Fabric Attach LLDP frames."

    ::= { avFabricAttachObjects 31 }

--
-- Fabric Attach notification objects
--

avFabricAttachDiscElemsSysDescr OBJECT-TYPE
    SYNTAX      SnmpAdminString (SIZE(0..255))
    MAX-ACCESS  accessible-for-notify
    STATUS      current
    DESCRIPTION
        "The string value used to identify the system description
        of the remote system distributed through LLDP." 
    REFERENCE
        "IEEE 802.1AB-2004 9.5.7.2"

    ::= { avFabricAttachNotifyObjects 1 }

avFabricAttachDiscElemsMgmtOid OBJECT-TYPE
    SYNTAX      OBJECT IDENTIFIER
    MAX-ACCESS  accessible-for-notify
    STATUS      current
    DESCRIPTION
        "The OID value used to identify the type of hardware component 
        or protocol entity associated with the management address 
        advertised by the remote system agent distributed through LLDP."
    REFERENCE
        "IEEE 802.1AB-2004 9.5.9.8"

    ::= { avFabricAttachNotifyObjects 2 }

--
-- Fabric Attach notifications
--

avFabricAttachDiscoveredElement NOTIFICATION-TYPE
    OBJECTS        {
                       avFabricAttachDiscElemsElementType,
                       avFabricAttachDiscElemsElementId,
                       avFabricAttachDiscElemsElementAuth,
                       avFabricAttachDiscElemsSysDescr,  
                       avFabricAttachDiscElemsMgmtOid 
                   }
    STATUS         current
    DESCRIPTION
        "This notification is generated when a FA element is discovered."

    ::= { avFabricAttachNotifications  1 }

avFabricAttachExpiredElement NOTIFICATION-TYPE
    OBJECTS        {
                       avFabricAttachDiscElemsElementType,
                       avFabricAttachDiscElemsElementId
                   }
    STATUS         current
    DESCRIPTION
        "This notification is generated when a FA element expires."

    ::= { avFabricAttachNotifications  2 }

END

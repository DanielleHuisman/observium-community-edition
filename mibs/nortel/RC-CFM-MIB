RC-CFM-MIB DEFINITIONS ::= BEGIN

IMPORTS
    MODULE-IDENTITY, OBJECT-TYPE, Integer32, Counter64, Counter32, Gauge32
        FROM SNMPv2-SMI
    TEXTUAL-CONVENTION, DisplayString, MacAddress, TruthValue, RowStatus,
    DateAndTime
        FROM SNMPv2-TC
    InterfaceIndex, InterfaceIndexOrZero
        FROM IF-MIB
    VlanIdOrNone
        FROM Q-BRIDGE-MIB
    rcCfm, EnableValue, CfmNameString
        FROM RAPID-CITY
    InetAddressType, InetAddress
        FROM INET-ADDRESS-MIB;

rcCfmMib MODULE-IDENTITY
       LAST-UPDATED     "201312030000Z"
       ORGANIZATION     "Nortel Networks"
       CONTACT-INFO     "
                                        Mike Nguyen
                         Postal:        Nortel Networks, Inc. 
                                        600 Technology Park
                                        Billerica, MA 01821 
                         E-mail:        minguyen@nortel.com"
       DESCRIPTION       "OE MIB for Connectivity Fault Management"

       REVISION "201312030000Z" -- 03 Dec 2013
       DESCRIPTION "Version 27: Added rcCfmGlobalsBmac and
	                        rcCfmGlobalsCmac By VSP4K 3.1 stream"

       REVISION "201310100000Z" -- 10 October 2013
       DESCRIPTION "Version 26: Corrected syntax definitions.
                    Added InetAddressType and InetAddress to IMPORTS."

       REVISION "201206250000Z" -- 25 June 2012
       DESCRIPTION "Version 25: Added rcCfmL2McastTraceReplyBMac and
	   			rcCfmL2McastTraceReplyIsid to rcCfmL2McastTraceReplyTable."

       REVISION "201205020000Z" -- 02 May 2012
       DESCRIPTION "Version 24: Changed the description of 
	   			rcCfmTransmitL2McastTraceVrfName 
	   			and added rcCfmL2McastTraceReplyVrfName
				to rcCfmL2McastTraceReplyTable in the 
				middle of the table (this mib table has
				not been part of any customer released 
				stream, hence made this change) and adjusted
				the OIDs of the objects that are defined 
				after this mib object."

       REVISION "201203210000Z" -- 21 Mar. 2012
       DESCRIPTION "Version 23: Changed the enum value of 
	   			rcCfmTransmitL2McastTraceServiceType
				from cvlan to vlan and updated its 
				description and rcCfmTransmitL2McastTraceServiceId.
                                Changed the enum value of 
	   			rcCfmL2McastTraceReplyServiceType
				from cvlan to vlan and updated its 
				description and rcCfmL2McastTraceReplyServiceId." 

       REVISION "201109230000Z" -- 23 Sept. 2011
       DESCRIPTION "Version 22: Added rcCfmTransmitL2McastTraceTable,
                                rcCfmL2McastTraceReplyTable" 

       REVISION "201105130000Z" -- 13 May 2011
       DESCRIPTION "Version 21: Added rcCfmGlobalsSpbmAdminState,
                                rcCfmGlobalsSpbmLevel,
                                rcCfmGlobalsSpbmMepId,
                                rcCfmGlobalsCmacAdminState,
                                rcCfmGlobalsCmacLevel,
                                rcCfmGlobalsCmacMepId,
                                Changed description for
                                   rcCfmTransmitLbmFrameSize,
                                Updated rcCfmTransmitLbmSourceMode,
                                   rcCfmTransmitLtmSourceMode,
                                   rcCfmTransmitL2PingSourceMode,
                                   rcCfmTransmitL2TraceSourceMode"

       REVISION "201101140000Z" -- 14 January 2011
       DESCRIPTION "Version 20: Added rcCfmTransmitLbmSourceMode,
	                        rcCfmTransmitLtmSourceMode,
				rcCfmLtrReplyTable,
				rcCfmTransmitL2PingTable,
				rcCfmTransmitL2TraceTable,
				rcCfmL2TraceReplyTable,
				rcCfmTransmitL2IpPingTable,
				rcCfmL2IpPingReplyTable,
				rcCfmTransmitL2IpTraceTable,
				rcCfmL2IpTraceReplyTable.
                                Modified the enumeration definition
				for rcCfmTransmitLbmTestPattern.
				Added ltmLeafNode(12) under the enum
				definition for rcCfmTransmitLtmFlag"

       REVISION "200904100000Z" -- 10 Apr 2009
       DESCRIPTION "Version 19: Added rcCfmMaintenanceEndPointLabel,
                                      rcCfmStatsAccessDrops,
                                      rcCfmStatsAggregateUplinkDrops.
                                Modified rcCfmMaintenanceEndPointIfIndex,
                                         rcCfmMaintenanceEndPointCcmVlanId,
                                         rcCfmStatsIfTlvTx,
                                         rcCfmRemoteMepStatsIfTlvRx."

       REVISION "200903250000Z" -- 25 Mar 2009
       DESCRIPTION "Version 18: Added enum value nodal(7) under
                                rcCfmMaintenanceDomainType."

       REVISION "200903160000Z" -- 16 Mar 2009
       DESCRIPTION "Version 17: Added rcCfmTransmitLbmFrameSize
                                under RcCfmTransmitLbmEntry.
                                Modified: syntax for rcCfmTransmitLbmStatus,
                                                     rcCfmTransmitLbmResult."
 

       REVISION "200902270000Z" -- 27 Feb 2009
       DESCRIPTION "Version 16: rcCfmTransmitLbmInterFrameInt default changed
                                to 500"

       REVISION "200902100000Z" -- 10 Feb 2009
       DESCRIPTION "Version 15: Added lowerLayerDown to
                                   rcCfmRemoteMepStatsIfTlvRx."

       REVISION "200902090000Z" -- 09 Feb 2009
       DESCRIPTION "Version 14: SMIv2 cleanup.
                                Added rcCfmMaintenanceEndPointIfIndex,
                                      rcCfmMaintenanceEndPointCcmVlanId"

       REVISION "200811100000Z" -- 10 Nov 2008
       DESCRIPTION "Version 13: Added  rcCfmGlobalsCcmTrapDisplayEnable."

       REVISION "200810030000Z" -- 03 Oct 2008
       DESCRIPTION "Version 12: Added rcCfmDhuId as Attribute 32 under
                                rcCfmTrap Group "

       REVISION "200809260000Z" -- 26 Sept 2008
       DESCRIPTION "Version 11: Modified rcCfmMaintenanceEndPointMepDirection,
                                         rcCfmTrunkOperStatus,
                                         rcCfmTransmitLtmTtl,
                                         rcCfmLtrTtl. "

       REVISION "200807140000Z" -- 14 July 2008
       DESCRIPTION "Version 10: Modified rcCfmTransmitLbmVlanDropEnable,
	                                 CfmRelayActionFieldValue,
					 rcCfmMaintenanceEndPointAisTxEnable,
					 rcCfmMaintenanceEndPointAisInterval,
					 rcCfmTransmitLtmStatus,
					 rcCfmTransmitLbmMessages,
					 RcCfmLtrEntry,
					 rcCfmTransmitLtmFlag
	                        Added rcCfmMaintenanceDomainClearAisStats,
				      rcCfmMaintenanceAssociationClearAisStats,
				      rcCfmMaintenanceEndPointClearAisStats"

       REVISION "200805090000Z" -- 09 May 2008
       DESCRIPTION "Version 9: Fixed smilint errors."

       REVISION "200803140000Z" -- 14 March 2008
       DESCRIPTION "Version 8: Modified rcCfmGlobalsPortVid,
	                                RcCfmMaintenanceIntermediatePointEntry,
					rcCfmGlobalsEtherType,
					rcCfmGlobalsPortVid,
					rcCfmGlobalsPbtDropTrapTimer,
					rcCfmTransmitLtmResult,
			       Added    rcCfmMaintenanceEndPointAisTxEnable,
			                rcCfmMaintenanceEndPointAisInterval,
					rcCfmMaintenanceEndPointIfTlv,
					rcCfmStatsIfTlvTx,
					rcCfmRemoteMepStatsIfTlvRx,
					rcCfmMaintenanceEndPointMepDirection,
					rcCfmTransmitLtmFlag,
					rcCfmLtrTable"	   

       REVISION "200712040000Z" -- 04 Dec 2007
       DESCRIPTION "Version 7: Added rcCfmMaintenanceEndPointMepStatus,
	                             rcCfmTrunkRemote,
	                             missing EnableValue to rcCfmMaintenanceDomainPmEnable,
	                             missing quote at CONTACT-INFO,
				     rcCfmTrunkDualHomePartner,
	                       Modified rcCfmTransmitLbmSeqNumber,
                                        rcCfmTransmitLtmSeqNumber,
			       Removed rcCfmMaintenanceEndPointUserLabel1,
			               rcCfmMaintenanceEndPointUserLabel2,
				       rcCfmTrunkRemote"

       REVISION "200708160000Z" -- 16 Aug 2007
       DESCRIPTION "Version 6: Modified rcCfmFdPerformanceTarget, 
	                                rcCfmFdFdvPerformanceTarget,
					rcCfmFdStatsCurrTarget,
					rcCfmFdStatsCurrAverage,
					rcCfmFdStatsCurrMinimum,
					rcCfmFdStatsCurrMaximum,
					rcCfmFdStatsCurrFdvTarget,
					rcCfmFdStatsCurrFdvAverage,
					rcCfmFdStatsCurrFdvMinimum,
					rcCfmFdStatsCurrFdvMaximum,
					rcCfmFdStatsHistTarget,
					rcCfmFdStatsHistAverage,
					rcCfmFdStatsHistMinimum,
					rcCfmFdStatsHistMaximum,
					rcCfmFdStatsHistFdvTarget,
					rcCfmFdStatsHistFdvAverage,
					rcCfmFdStatsHistFdvMinimum,
					rcCfmFdStatsHistFdvMaximum"
					
	
       REVISION "200705150000Z" -- 15 May 2007
       DESCRIPTION "Version 5: Correct the INDEX rcCfmPbtTrunkStatsName to not-accessible" 

       REVISION "200705140000Z" -- 14 May 2007
       DESCRIPTION "Version 4: Correct the INDEX rcCfmPortStatsIndex to not-accessible
				Added  rcCfmFdvTarget and rcCfmFdvAverage" 

       REVISION "200704180000Z" -- 22 Apr 2007
       DESCRIPTION "Version 3: Added rcCfmMaintenanceDomainType,rcCfmMaintenanceDomainEventTrapEnable,
				     rcCfmMaintenanceDomainPmEnable,rcCfmMaintenanceAssociationNumOfRemoteMep,
   	        		     rcCfmMaintenanceAssociationRemoveAutoRmep,
				     rcCfmMaintenanceAssociationCcmRdiEnable,
                		     rcCfmMaintenanceAssociationCcmMulticast,
				     rcCfmMaintenanceAssociationEventTrapEnable,
                                     rcCfmMaintenanceAssociationPmEnable, 
				     rcCfmMaintenanceEndPointServiceDescription,
   	        		     rcCfmMaintenanceEndPointRemoveAutoRmep,
				     rcCfmMaintenanceEndPointUserLabel1,
				     rcCfmMaintenanceEndPointUserLabel2,
				     rcCfmTrunkGroupLoopBackVlanId,rcCfmTrunkGroupUserLabel1,rcCfmTrunkGroupUserLabel2,
				     rcCfmPbtMsti,rcCfmTrunkClearStats,rcCfmTrunkUserLabel1,rcCfmTrunkUserLabel2,
				     rcCfmTrunkSubportQueueSet,rcCfmStatsDefect,
			       Added Atrributes 12-28 for rcCfmTrap Group,
			       Added cCfmGlobalsPortVid,rcCfmGlobalsPbtDropTrapTimer and rcCfmGlobalsPmEnable
			       Removed rcCfmMaintenanceEndPointServiceId,rcCfmMaintenanceEndPointServiceName (Not used)"



       REVISION "200606210000Z" -- 21 June 2006
       DESCRIPTION "Version 2: Added rcCfmTrunkGroupIndication, rcCfmTrunkGroupProtected,
				rcCfmRemoteMepId, rcCfmLocalMepId,rcCfmMepCcmIndication,
				rcCfmCvid, rcCfmRemoteMacAddr,rcCfmIsidId to rcCfmTrap.
			       Added rcCfmMaintenanceDomainLevel, rcCfmMaintenanceDomainNumOfMip,
                		to rcCfmMaintenanceDomainTable
			       Corrected/Updated the rcCfmMaintenanceAssociationTable.
			       Corrected/updated rcCfmMaintenanceEndPointTable.
                               Added rcCfmTrunkSourceMac to rcCfmTrunkTable
			       Added rcCfmRemoteMaintenanceEndPointTable
			       Added rcCfmMepLearnStatsTable
			       Added rcCfmGlobalsPbtMac to rcCfmGlobals
			       Added rcCfmMaintenanceIntermediatePointTable"

       REVISION "200602030000Z" -- 03 February 2006
       DESCRIPTION "Version 1: Initial version"
       ::= { rcCfm 0 }

-- Maintenance Domain Table

rcCfmMaintenanceDomainTable OBJECT-TYPE
	SYNTAX		SEQUENCE OF RcCfmMaintenanceDomainEntry
	MAX-ACCESS	not-accessible
	STATUS		current
	DESCRIPTION	"Connectivity Fault Management Maintenance Domain table"
	::= { rcCfm 1}

rcCfmMaintenanceDomainEntry OBJECT-TYPE
	SYNTAX		RcCfmMaintenanceDomainEntry
	MAX-ACCESS	not-accessible
	STATUS		current
	DESCRIPTION	"Connectivity Fault Management Maintenance Domain entry."
	INDEX		{rcCfmMaintenanceDomainIndex }
	::= { rcCfmMaintenanceDomainTable 1}

RcCfmMaintenanceDomainEntry ::=
	SEQUENCE {
		rcCfmMaintenanceDomainIndex		Integer32,
		rcCfmMaintenanceDomainName		DisplayString,
		rcCfmMaintenanceDomainRowStatus		RowStatus,
                rcCfmMaintenanceDomainNumOfMa		Integer32,
                rcCfmMaintenanceDomainClearStats	TruthValue,
                rcCfmMaintenanceDomainLevel		Integer32,
	        rcCfmMaintenanceDomainNumOfMip		Integer32,
		rcCfmMaintenanceDomainType              INTEGER, 
                rcCfmMaintenanceDomainEventTrapEnable   EnableValue,
                rcCfmMaintenanceDomainPmEnable          EnableValue,
		rcCfmMaintenanceDomainClearAisStats	TruthValue
		}

rcCfmMaintenanceDomainIndex OBJECT-TYPE
	SYNTAX		Integer32 (1..2147483647)
	MAX-ACCESS	not-accessible
	STATUS		current
	DESCRIPTION	"Maintenance Domain index"
	::= { rcCfmMaintenanceDomainEntry 1}

rcCfmMaintenanceDomainName OBJECT-TYPE	
	SYNTAX	        DisplayString(SIZE (1..255))
	MAX-ACCESS	read-create
	STATUS		current
	DESCRIPTION	"Maintenance Domain Name"
	::= { rcCfmMaintenanceDomainEntry 2}

rcCfmMaintenanceDomainRowStatus OBJECT-TYPE
	SYNTAX		RowStatus
	MAX-ACCESS	read-create
	STATUS		current
	DESCRIPTION	"Used to create/delete entries"
	::= { rcCfmMaintenanceDomainEntry 3}

rcCfmMaintenanceDomainNumOfMa OBJECT-TYPE
        SYNTAX        	Integer32
        MAX-ACCESS      read-only
        STATUS        	current
        DESCRIPTION   	"Used to indicate the number of MAs belong
                      	to this maintenance domain"
        ::= { rcCfmMaintenanceDomainEntry 4 }

rcCfmMaintenanceDomainClearStats   OBJECT-TYPE
        SYNTAX          TruthValue
        MAX-ACCESS      read-create
        STATUS          current
        DESCRIPTION     "To clear the MEPS CCM sending/receiving 
			 message counter un der this domain"
        DEFVAL          { false }
        ::= { rcCfmMaintenanceDomainEntry 5 }

rcCfmMaintenanceDomainLevel OBJECT-TYPE
	SYNTAX		Integer32 (0..7)
        MAX-ACCESS      read-write
        STATUS          current
        DESCRIPTION     "To set the maintenance level in this domain"
	DEFVAL		{4}
        ::= { rcCfmMaintenanceDomainEntry 6 }

rcCfmMaintenanceDomainNumOfMip OBJECT-TYPE
        SYNTAX        	Integer32
        MAX-ACCESS      read-only
        STATUS        	current
        DESCRIPTION   	"Used to indicate the number of Mips belong
                      	to this maintenance domain"
        ::= { rcCfmMaintenanceDomainEntry 7 }

rcCfmMaintenanceDomainType OBJECT-TYPE
        SYNTAX          INTEGER {
                            none(0),
                            trunk(1),
                            sg(2),
                            endpt(3),
                            vlan(4),
                            port(5),
                            mimencapvlan(6),
                            nodal(7)
                         }
        MAX-ACCESS      read-only
        STATUS          current
        DESCRIPTION     "To indicate the type of domain" 
        ::= { rcCfmMaintenanceDomainEntry 8 }

rcCfmMaintenanceDomainEventTrapEnable OBJECT-TYPE
        SYNTAX          EnableValue
        MAX-ACCESS      read-create
        STATUS          current
        DESCRIPTION     "Event Trap enable"
        REFERENCE       "MERS v4.2 PRD - R15"
        DEFVAL {enable}
        ::= { rcCfmMaintenanceDomainEntry 9 }

rcCfmMaintenanceDomainPmEnable OBJECT-TYPE
        SYNTAX          EnableValue
        MAX-ACCESS      read-create
        STATUS          current
        DESCRIPTION     "Performance monitor enable"
        REFERENCE       "MERS v4.2 PRD"
        DEFVAL {disable}
        ::= { rcCfmMaintenanceDomainEntry 10 }

rcCfmMaintenanceDomainClearAisStats   OBJECT-TYPE
        SYNTAX          TruthValue
        MAX-ACCESS      read-write
        STATUS          current
        DESCRIPTION     "To clear the AIS CCM sending/receiving 
			 message counter un der this domain"
        DEFVAL          { false }
        ::= { rcCfmMaintenanceDomainEntry 11 }


-- Maintenance Association Table

rcCfmMaintenanceAssociationTable OBJECT-TYPE
	SYNTAX		SEQUENCE OF RcCfmMaintenanceAssociationEntry
	MAX-ACCESS	not-accessible
	STATUS		current
	DESCRIPTION	"Connectivity Fault Management Maintenance Association table"
	::= { rcCfm 2}

rcCfmMaintenanceAssociationEntry OBJECT-TYPE
	SYNTAX		RcCfmMaintenanceAssociationEntry
	MAX-ACCESS	not-accessible
	STATUS		current
	DESCRIPTION	"Connectivity Fault Management Maintenance Association entry."
	INDEX		{rcCfmMaintenanceAssociationDomainIndex, rcCfmMaintenanceAssociationAssociationIndex }
	::= { rcCfmMaintenanceAssociationTable 1}

RcCfmMaintenanceAssociationEntry ::=
	SEQUENCE {
		rcCfmMaintenanceAssociationDomainIndex		Integer32,
                rcCfmMaintenanceAssociationAssociationIndex    	Integer32,
		rcCfmMaintenanceAssociationDomainName		DisplayString,
                rcCfmMaintenanceAssociationAssociationName	DisplayString,
                rcCfmMaintenanceAssociationAdminState		EnableValue,
		rcCfmMaintenanceAssociationRowStatus		RowStatus,
                rcCfmMaintenanceAssociationCcmInterval		Integer32,
                rcCfmMaintenanceAssociationCcmLifetime		Integer32,
                rcCfmMaintenanceAssociationCcmPriority		Integer32,
                rcCfmMaintenanceAssociationCcmTxEnable		EnableValue,
                rcCfmMaintenanceAssociationCcmRxEnable		EnableValue,
                rcCfmMaintenanceAssociationNumOfMep     	Integer32,
                rcCfmMaintenanceAssociationClearStats		TruthValue,
                rcCfmMaintenanceAssociationAutoDetect		EnableValue,
                rcCfmMaintenanceAssociationNumOfRemoteMep	Integer32,
		rcCfmMaintenanceAssociationRemoveAutoRmep	Integer32,
                rcCfmMaintenanceAssociationCcmRdiEnable         EnableValue,
                rcCfmMaintenanceAssociationCcmMulticast		EnableValue,
                rcCfmMaintenanceAssociationEventTrapEnable      EnableValue,
                rcCfmMaintenanceAssociationPmEnable             EnableValue,
		rcCfmMaintenanceAssociationClearAisStats	TruthValue
	
		}

rcCfmMaintenanceAssociationDomainIndex OBJECT-TYPE
	SYNTAX		Integer32 (1..2147483647)
	MAX-ACCESS	not-accessible
	STATUS		current
	DESCRIPTION	"Maintenance Association Domain Index"
	::= { rcCfmMaintenanceAssociationEntry 1}

rcCfmMaintenanceAssociationAssociationIndex OBJECT-TYPE
	SYNTAX		Integer32 (1..2147483647)
	MAX-ACCESS	not-accessible
	STATUS		current
	DESCRIPTION	"Maintenance Association Index"
	::= { rcCfmMaintenanceAssociationEntry 2}

rcCfmMaintenanceAssociationDomainName OBJECT-TYPE
	SYNTAX		DisplayString(SIZE (1..255))
	MAX-ACCESS	read-only
	STATUS		current
	DESCRIPTION	"Maintenance Association Domain Name"
	::= { rcCfmMaintenanceAssociationEntry 3}

rcCfmMaintenanceAssociationAssociationName OBJECT-TYPE
	SYNTAX		DisplayString(SIZE (1..255))
	MAX-ACCESS	read-create
	STATUS		current
	DESCRIPTION	"Maintenance Association Name"
	::= { rcCfmMaintenanceAssociationEntry 4}

rcCfmMaintenanceAssociationAdminState OBJECT-TYPE
        SYNTAX        EnableValue
        MAX-ACCESS    read-create
        STATUS        current
        DESCRIPTION   "Administratively enable or disable a maintenance association."
	DEFVAL        { disable }
        ::= { rcCfmMaintenanceAssociationEntry 5}

rcCfmMaintenanceAssociationRowStatus OBJECT-TYPE
	SYNTAX		RowStatus
	MAX-ACCESS	read-create
	STATUS		current
	DESCRIPTION	"Used to create/delete entries"
	::= { rcCfmMaintenanceAssociationEntry 6}

rcCfmMaintenanceAssociationCcmInterval OBJECT-TYPE
	SYNTAX		Integer32 (0..65535000)
        UNITS		"milliseconds"
	MAX-ACCESS	read-create
	STATUS		current
	DESCRIPTION	"Interval of periodic Continuity Check Message to be transmitted"
        DEFVAL { 5000 }
	::= { rcCfmMaintenanceAssociationEntry 7}

rcCfmMaintenanceAssociationCcmLifetime OBJECT-TYPE
	SYNTAX		Integer32 (0..655350)
	MAX-ACCESS	read-create
	STATUS		current
	DESCRIPTION	"Lifetime of periodic Continuity Check Message"
        DEFVAL { 15000 }
	::= { rcCfmMaintenanceAssociationEntry 8}

rcCfmMaintenanceAssociationCcmPriority OBJECT-TYPE
	SYNTAX		Integer32 (0..7)
	MAX-ACCESS	read-create
	STATUS		current
	DESCRIPTION	"Priority of Continuity Check Message to be transmitted"
        DEFVAL { 7 }
	::= { rcCfmMaintenanceAssociationEntry 9}

rcCfmMaintenanceAssociationCcmTxEnable OBJECT-TYPE
	SYNTAX		EnableValue
	MAX-ACCESS	read-create
	STATUS		current
	DESCRIPTION	"Continuity Check Message transmit enable"
        DEFVAL { disable }
	::= { rcCfmMaintenanceAssociationEntry 10}

rcCfmMaintenanceAssociationCcmRxEnable OBJECT-TYPE
	SYNTAX		EnableValue
	MAX-ACCESS	read-create
	STATUS		current
	DESCRIPTION	"Continuity Check Message receive enable"
        DEFVAL { disable }
	::= { rcCfmMaintenanceAssociationEntry 11}

rcCfmMaintenanceAssociationNumOfMep OBJECT-TYPE
        SYNTAX        	Integer32
        MAX-ACCESS      read-only
        STATUS        	current
        DESCRIPTION   	"Used to indicate the number of MEPs belong
                      	to this maintenance association"
        ::= { rcCfmMaintenanceAssociationEntry 12 }

rcCfmMaintenanceAssociationClearStats   OBJECT-TYPE
        SYNTAX          TruthValue
        MAX-ACCESS      read-create
        STATUS          current
        DESCRIPTION     "To clear the MEPs CCM sending/receiving 
			 message counter under this MA"
        DEFVAL          { false }
        ::= { rcCfmMaintenanceAssociationEntry 13 }

rcCfmMaintenanceAssociationAutoDetect   OBJECT-TYPE
        SYNTAX          EnableValue
        MAX-ACCESS      read-create
        STATUS          current
        DESCRIPTION     "Indicates whether MA allows auto-detect of remote MEPs"
        DEFVAL          { disable }
        ::= { rcCfmMaintenanceAssociationEntry 14 }

rcCfmMaintenanceAssociationNumOfRemoteMep OBJECT-TYPE
        SYNTAX        	Integer32
        MAX-ACCESS      read-only
        STATUS        	current
        DESCRIPTION   	"Used to indicate the number of remote MEPs belong
                      	to this maintenance association"
        ::= { rcCfmMaintenanceAssociationEntry 15 }

rcCfmMaintenanceAssociationRemoveAutoRmep OBJECT-TYPE
        SYNTAX        Integer32 (0..8191)
        MAX-ACCESS    read-create
        STATUS        current
        DESCRIPTION   "Remove auto learned Remote Maintenance 
                       Endpoint ID, or 0 for unspecified"
	::= { rcCfmMaintenanceAssociationEntry 16 }

rcCfmMaintenanceAssociationCcmRdiEnable OBJECT-TYPE
        SYNTAX          EnableValue
        MAX-ACCESS      read-create
        STATUS          current
        DESCRIPTION     "Continuity Check Message RDI enable"
        REFERENCE       "MERS v4.2 PRD - R21,R24,R29,R33,R61,R73"
        DEFVAL          {enable}
	::= { rcCfmMaintenanceAssociationEntry 17 }

rcCfmMaintenanceAssociationCcmMulticast   OBJECT-TYPE
        SYNTAX          EnableValue
        MAX-ACCESS      read-create
        STATUS          current
        DESCRIPTION     "Indicates whether MA sends Multicast or Unicast CCMs"
        DEFVAL          { enable }
        ::= { rcCfmMaintenanceAssociationEntry 18 }

rcCfmMaintenanceAssociationEventTrapEnable OBJECT-TYPE
        SYNTAX          EnableValue
        MAX-ACCESS      read-create
        STATUS          current
        DESCRIPTION     "Event Trap enable
                         This MA level setting overrides MD level setting."
        REFERENCE       "MERS v4.2 PRD - R15"
        DEFVAL {enable}
        ::= { rcCfmMaintenanceAssociationEntry 19 }

rcCfmMaintenanceAssociationPmEnable OBJECT-TYPE
        SYNTAX          EnableValue
        MAX-ACCESS      read-create
        STATUS          current
        DESCRIPTION     "Performance monitor enable
                         This MA level setting overrides MD level setting."
        REFERENCE       "MERS v4.2 PRD"
        DEFVAL {disable}
        ::= { rcCfmMaintenanceAssociationEntry 20 }

rcCfmMaintenanceAssociationClearAisStats   OBJECT-TYPE
        SYNTAX          TruthValue
        MAX-ACCESS      read-write
        STATUS          current
        DESCRIPTION     "To clear the Ais CCM sending/receiving 
			 message counter under this MA"
        DEFVAL          { false }
        ::= { rcCfmMaintenanceAssociationEntry 21 }


-- Maintenance EndPoint Table

rcCfmMaintenanceEndPointTable OBJECT-TYPE
	SYNTAX		SEQUENCE OF RcCfmMaintenanceEndPointEntry
	MAX-ACCESS	not-accessible
	STATUS		current
	DESCRIPTION	"Connectivity Fault Management Maintenance Association table"
	::= { rcCfm 3}

rcCfmMaintenanceEndPointEntry OBJECT-TYPE
	SYNTAX		RcCfmMaintenanceEndPointEntry
	MAX-ACCESS	not-accessible
	STATUS		current
	DESCRIPTION	"Connectivity Fault Management Maintenance EndPoint entry."
	INDEX		{rcCfmMaintenanceEndPointDomainIndex, rcCfmMaintenanceEndPointAssociationIndex, rcCfmMaintenanceEndPointId }
	::= { rcCfmMaintenanceEndPointTable 1}

RcCfmMaintenanceEndPointEntry ::=
        SEQUENCE {
                rcCfmMaintenanceEndPointDomainIndex        Integer32,
                rcCfmMaintenanceEndPointAssociationIndex   Integer32,
                rcCfmMaintenanceEndPointId                 Integer32,
                rcCfmMaintenanceEndPointDomainName         DisplayString,
                rcCfmMaintenanceEndPointAssociationName    DisplayString,
                rcCfmMaintenanceEndPointAdminState         EnableValue,
                rcCfmMaintenanceEndPointRowStatus          RowStatus,
                rcCfmMaintenanceEndPointCcmPriority        Integer32,
                rcCfmMaintenanceEndPointCcmTxEnable        EnableValue,
                rcCfmMaintenanceEndPointCcmRxEnable        EnableValue,
                rcCfmMaintenanceEndPointMepType            INTEGER,
                rcCfmMaintenanceEndPointClearStats         TruthValue,
                rcCfmMaintenanceEndPointServiceDescription DisplayString,  
                rcCfmMaintenanceEndPointRemoveAutoRmep     Integer32,
                rcCfmMaintenanceEndPointMepStatus          INTEGER,
                rcCfmMaintenanceEndPointAisTxEnable        EnableValue,
                rcCfmMaintenanceEndPointAisInterval        INTEGER,
                rcCfmMaintenanceEndPointIfTlv              EnableValue,
                rcCfmMaintenanceEndPointMepDirection       INTEGER,
                rcCfmMaintenanceEndPointClearAisStats      TruthValue,
                rcCfmMaintenanceEndPointIfIndex            InterfaceIndexOrZero,
                rcCfmMaintenanceEndPointCcmVlanId          VlanIdOrNone,
                rcCfmMaintenanceEndPointLabel              DisplayString
        }

rcCfmMaintenanceEndPointDomainIndex OBJECT-TYPE
	SYNTAX		Integer32 (1..2147483647)
	MAX-ACCESS	not-accessible
	STATUS		current
	DESCRIPTION	"Maintenance Domain Name"
	::= { rcCfmMaintenanceEndPointEntry 1}

rcCfmMaintenanceEndPointAssociationIndex OBJECT-TYPE
	SYNTAX		Integer32 (1..2147483647)
	MAX-ACCESS	not-accessible
	STATUS		current
	DESCRIPTION	"Maintenance Association Name"
	::= { rcCfmMaintenanceEndPointEntry 2}

rcCfmMaintenanceEndPointId OBJECT-TYPE
	SYNTAX		Integer32 (1..8191)
	MAX-ACCESS	not-accessible
	STATUS		current
	DESCRIPTION	"Maintenance EndPoint ID"
	::= { rcCfmMaintenanceEndPointEntry 3}

rcCfmMaintenanceEndPointDomainName OBJECT-TYPE
	SYNTAX		DisplayString
	MAX-ACCESS	read-only
	STATUS		current
	DESCRIPTION	"Maintenance Domain Name"
	::= { rcCfmMaintenanceEndPointEntry 4}

rcCfmMaintenanceEndPointAssociationName OBJECT-TYPE
	SYNTAX		DisplayString
	MAX-ACCESS	read-only
	STATUS		current
	DESCRIPTION	"Maintenance Association Name"
	::= { rcCfmMaintenanceEndPointEntry 5}

rcCfmMaintenanceEndPointAdminState OBJECT-TYPE
        SYNTAX        EnableValue
        MAX-ACCESS    read-create
        STATUS        current
        DESCRIPTION   "Administratively enable or disable a maintenance EndPoint."
	DEFVAL        { disable }
        ::= { rcCfmMaintenanceEndPointEntry 6}

rcCfmMaintenanceEndPointRowStatus OBJECT-TYPE
	SYNTAX		RowStatus
	MAX-ACCESS	read-create
	STATUS		current
	DESCRIPTION	"Used to create/delete entries"
	::= { rcCfmMaintenanceEndPointEntry 7}

rcCfmMaintenanceEndPointCcmPriority OBJECT-TYPE
	SYNTAX		Integer32 (0..7)
	MAX-ACCESS	read-create
	STATUS		current
	DESCRIPTION	"Priority of Continuity Check Message to be transmitted"
        DEFVAL { 7 }
	::= { rcCfmMaintenanceEndPointEntry 8}

rcCfmMaintenanceEndPointCcmTxEnable OBJECT-TYPE
	SYNTAX		EnableValue
	MAX-ACCESS	read-create
	STATUS		current
	DESCRIPTION	"Continuity Check Message transmit enable"
        DEFVAL { disable }
	::= { rcCfmMaintenanceEndPointEntry 9}

rcCfmMaintenanceEndPointCcmRxEnable OBJECT-TYPE
	SYNTAX		EnableValue
	MAX-ACCESS	read-create
	STATUS		current
	DESCRIPTION	"Continuity Check Message receive enable"
        DEFVAL { disable }
	::= { rcCfmMaintenanceEndPointEntry 10}

rcCfmMaintenanceEndPointMepType OBJECT-TYPE
        SYNTAX        INTEGER { 
                          trunk(1),
                          sg(2),
                          endpt(4),
                          unused(8),
                          vlan(16),
	                  port(32),
                          endptClient(64),
                          remotetrunk(32769),
                          remotesg(32770),
                          remoteendpt(32772),
	                  remoteVlan(32784),
	                  remotePort(32800),
	                  remoteEndptClient(32832),
                          nodal(3145728)
                       }
        MAX-ACCESS    read-only
        STATUS        current
        DESCRIPTION   "Mep Type"
        ::= { rcCfmMaintenanceEndPointEntry 11 }

rcCfmMaintenanceEndPointClearStats   OBJECT-TYPE
        SYNTAX          TruthValue
        MAX-ACCESS      read-create
        STATUS          current
        DESCRIPTION     "To clear the MEP CCM sending/receiving 
			 message counter"
        DEFVAL          { false }
        ::= { rcCfmMaintenanceEndPointEntry 12 }

rcCfmMaintenanceEndPointServiceDescription OBJECT-TYPE
        SYNTAX          DisplayString(SIZE (0..48))
        MAX-ACCESS      read-only
        STATUS          current
        DESCRIPTION     "Used to specify what service this mep assigned to"
        ::= { rcCfmMaintenanceEndPointEntry 13}

rcCfmMaintenanceEndPointRemoveAutoRmep OBJECT-TYPE
        SYNTAX        Integer32 (0..8191)
        MAX-ACCESS    read-create
        STATUS        current
        DESCRIPTION   "Remove auto learned Remote Maintenance 
                       Endpoint ID, or 0 for unspecified"
	::= { rcCfmMaintenanceEndPointEntry 14 }

rcCfmMaintenanceEndPointMepStatus OBJECT-TYPE
        SYNTAX        INTEGER { 
                          active(1),
                          inactive(2) 
                      }
        MAX-ACCESS    read-only
        STATUS        current
        DESCRIPTION   "Indicating if the mep status is active or inactive. 
                       Only Dual-Home Ring endpoint client meps can have       
                       active/inactive status. All other mep types have
                       active status." 
	::= { rcCfmMaintenanceEndPointEntry 15 }

rcCfmMaintenanceEndPointAisTxEnable OBJECT-TYPE
	SYNTAX		EnableValue
	MAX-ACCESS	read-create
	STATUS		current
	DESCRIPTION	"Alarm Indication Signal Message transmit enable"
        DEFVAL { disable }
	::= { rcCfmMaintenanceEndPointEntry 16}

rcCfmMaintenanceEndPointAisInterval OBJECT-TYPE
	SYNTAX		INTEGER{
			   intv1000(1000),
			   intv60000(60000)
			}	
        UNITS		"milliseconds"
	MAX-ACCESS	read-create
	STATUS		current
	DESCRIPTION	"Interval of periodic Alarm Indication Signal Message to be transmitted. Unit in milliseconds."
        DEFVAL { intv60000 }
        ::= { rcCfmMaintenanceEndPointEntry 17}

rcCfmMaintenanceEndPointIfTlv OBJECT-TYPE
        SYNTAX        EnableValue
        MAX-ACCESS    read-create
        STATUS        current
        DESCRIPTION   "Admin control of the Interface-Status-Tlv in
                       maintenanceEndpoint."
        DEFVAL        { disable }
        ::= { rcCfmMaintenanceEndPointEntry 18 }

rcCfmMaintenanceEndPointMepDirection OBJECT-TYPE
        SYNTAX        INTEGER { 
                                   up(1),
                                   down(2),
                                   unknown(3) 
                                }
        MAX-ACCESS    read-only
        STATUS        current
        DESCRIPTION   "Indicates the direction in which the Maintenance association faces on the bridge port." 
        DEFVAL        { unknown } 
        ::= { rcCfmMaintenanceEndPointEntry 19 }

rcCfmMaintenanceEndPointClearAisStats   OBJECT-TYPE
        SYNTAX          TruthValue
        MAX-ACCESS      read-create
        STATUS          current
        DESCRIPTION     "To clear the AIS sending/receiving 
			 message counter"
        DEFVAL          { false }
        ::= { rcCfmMaintenanceEndPointEntry 20 }

rcCfmMaintenanceEndPointIfIndex OBJECT-TYPE
        SYNTAX          InterfaceIndexOrZero
        MAX-ACCESS      read-create
        STATUS          current
        DESCRIPTION
            "This object is the interface index of the interface either a
            bridge port, or an aggregated IEEE 802.1 link within a bridge port,
            to which the MEP is attached."
        DEFVAL { 0 }
        ::= { rcCfmMaintenanceEndPointEntry 21 }

rcCfmMaintenanceEndPointCcmVlanId OBJECT-TYPE
        SYNTAX		   VlanIdOrNone
        MAX-ACCESS	   read-create
        STATUS		   current
        DESCRIPTION
	   "Customer CCM VLAN ID"
        DEFVAL { 0 }
        ::= { rcCfmMaintenanceEndPointEntry 22 }

rcCfmMaintenanceEndPointLabel OBJECT-TYPE
	SYNTAX		DisplayString (SIZE(0..48))
	MAX-ACCESS	read-create
	STATUS		current
        DESCRIPTION
            "User provided field. Used to give extra management
            information/data."
        ::= { rcCfmMaintenanceEndPointEntry 23 }


-- Trunk Group Table

rcCfmTrunkGroupTable OBJECT-TYPE
	SYNTAX		SEQUENCE OF RcCfmTrunkGroupEntry
	MAX-ACCESS	not-accessible
	STATUS		current
	DESCRIPTION	"Connectivity Fault TrunkGroup table"
	::= { rcCfm 4}

rcCfmTrunkGroupEntry OBJECT-TYPE
	SYNTAX		RcCfmTrunkGroupEntry
	MAX-ACCESS	not-accessible
	STATUS		current
	DESCRIPTION	"Connectivity Fault Management TrunkGroup entry."
	INDEX		{rcCfmTrunkGroupName}
	::= { rcCfmTrunkGroupTable 1}

RcCfmTrunkGroupEntry ::=
	SEQUENCE {
                rcCfmTrunkGroupName		CfmNameString,
		rcCfmTrunkGroupRowStatus	RowStatus,
                rcCfmTrunkGroupPrimaryTrunk	DisplayString,
		rcCfmTrunkGroupSecondaryTrunk	DisplayString,
		rcCfmTrunkGroupActiveTrunk	DisplayString,
		rcCfmTrunkGroupRevertive	EnableValue,
		rcCfmTrunkGroupLoopBackVlanId   Integer32,
		rcCfmTrunkGroupUserLabel1  OCTET STRING,
		rcCfmTrunkGroupUserLabel2  OCTET STRING
		
		}

rcCfmTrunkGroupName OBJECT-TYPE
	SYNTAX		CfmNameString
	MAX-ACCESS	not-accessible
	STATUS		current
	DESCRIPTION	"Trunk Group Name"
	::= { rcCfmTrunkGroupEntry 1}

rcCfmTrunkGroupRowStatus OBJECT-TYPE
	SYNTAX		RowStatus
	MAX-ACCESS	read-create
	STATUS		current
	DESCRIPTION	"Used to create/delete entries"
	::= { rcCfmTrunkGroupEntry 2}

rcCfmTrunkGroupPrimaryTrunk OBJECT-TYPE
	SYNTAX		DisplayString(SIZE(32))
	MAX-ACCESS	read-create
	STATUS		current
	DESCRIPTION	"Trunk Group PBT Primary Trunk Name"
	::= { rcCfmTrunkGroupEntry 3}

rcCfmTrunkGroupSecondaryTrunk OBJECT-TYPE
	SYNTAX		DisplayString(SIZE(32))
	MAX-ACCESS	read-create
	STATUS		current
	DESCRIPTION	"Trunk Group PBT Secondary Trunk Name"
	::= { rcCfmTrunkGroupEntry 4}

rcCfmTrunkGroupActiveTrunk OBJECT-TYPE
	SYNTAX		DisplayString(SIZE(32))
	MAX-ACCESS	read-create
	STATUS		current
	DESCRIPTION	"Trunk Group PBT Active Trunk Name"
	::= { rcCfmTrunkGroupEntry 5}

rcCfmTrunkGroupRevertive OBJECT-TYPE
        SYNTAX        EnableValue
        MAX-ACCESS    read-create
        STATUS        current
        DESCRIPTION   "Revertive enable or disable"
	DEFVAL        { disable }
        ::= { rcCfmTrunkGroupEntry 6}

rcCfmTrunkGroupLoopBackVlanId  OBJECT-TYPE
	SYNTAX		  Integer32 (0..4094)
	MAX-ACCESS	  read-create
	STATUS		  current
	DESCRIPTION	  "Loopback VLAN ID for local pbt switching"
	::= { rcCfmTrunkGroupEntry 7}

rcCfmTrunkGroupUserLabel1  OBJECT-TYPE 
	SYNTAX          OCTET STRING (SIZE(0..89))
        MAX-ACCESS      read-write
        STATUS          current
        DESCRIPTION     "User provided field. Used to give extra management information/data "
        ::= { rcCfmTrunkGroupEntry 8 }

rcCfmTrunkGroupUserLabel2  OBJECT-TYPE 
	SYNTAX          OCTET STRING (SIZE(0..89))
        MAX-ACCESS      read-write
        STATUS          current
        DESCRIPTION     "User provided additional field. Used to give extra management information/data "
        ::= { rcCfmTrunkGroupEntry 9}


--  Trunk Table

rcCfmTrunkTable OBJECT-TYPE
	SYNTAX		SEQUENCE OF RcCfmTrunkEntry
	MAX-ACCESS	not-accessible
	STATUS		current
	DESCRIPTION	"Connectivity Fault Trunk table"
	::= { rcCfm 5}

rcCfmTrunkEntry OBJECT-TYPE
	SYNTAX		RcCfmTrunkEntry
	MAX-ACCESS	not-accessible
	STATUS		current
	DESCRIPTION	"Connectivity Fault Management Trunk entry."
	INDEX		{rcCfmTrunkName}
	::= { rcCfmTrunkTable 1}

RcCfmTrunkEntry ::=
	SEQUENCE {
                rcCfmTrunkName		CfmNameString,
                rcCfmTrunkPort		InterfaceIndex,
                rcCfmTrunkAdminState	EnableValue,
		rcCfmTrunkRowStatus	RowStatus,
                rcCfmTrunkMac		MacAddress,
		rcCfmTrunkMdName	DisplayString,
                rcCfmTrunkMaName	DisplayString,
		rcCfmTrunkVlanId	Integer32,
                rcCfmTrunkReverseVlanId	Integer32,
                rcCfmTrunkMepId	        Integer32,
                rcCfmTrunkHoldTimer     Integer32,
                rcCfmTrunkOperStatus    INTEGER,
		rcCfmTrunkSourceMac	MacAddress,
		rcCfmTrunkClearStats    TruthValue,
		rcCfmTrunkUserLabel1  OCTET STRING ,
		rcCfmTrunkUserLabel2  OCTET STRING ,
		rcCfmTrunkSubportQueueSet Integer32,
		rcCfmTrunkDualHomePartner EnableValue
		}


rcCfmTrunkName OBJECT-TYPE
	SYNTAX		CfmNameString
	MAX-ACCESS	not-accessible
	STATUS		current
	DESCRIPTION	"PBT Trunk Name"
	::= { rcCfmTrunkEntry 1}

rcCfmTrunkPort OBJECT-TYPE
	SYNTAX		InterfaceIndex
	MAX-ACCESS	read-create
	STATUS		current
	DESCRIPTION	"PBT Trunk Port"
	::= { rcCfmTrunkEntry 2}

rcCfmTrunkAdminState OBJECT-TYPE
        SYNTAX        EnableValue
        MAX-ACCESS    read-create
        STATUS        current
        DESCRIPTION   "Administratively enable or disable a PBT trunk."
	DEFVAL        { disable }
        ::= { rcCfmTrunkEntry 3}

rcCfmTrunkRowStatus OBJECT-TYPE
	SYNTAX		RowStatus
	MAX-ACCESS	read-create
	STATUS		current
	DESCRIPTION	"Used to create/delete entries"
	::= { rcCfmTrunkEntry 4}

rcCfmTrunkMac OBJECT-TYPE
	SYNTAX		MacAddress
	MAX-ACCESS	read-create
	STATUS		current
	DESCRIPTION	"Trunk Mac (remote CP mac)"
	::= { rcCfmTrunkEntry 5}

rcCfmTrunkMdName OBJECT-TYPE
	SYNTAX		DisplayString(SIZE(255))
	MAX-ACCESS	read-create
	STATUS		current
	DESCRIPTION	"PBT Trunk Maintenance Domain Name"
	::= { rcCfmTrunkEntry 6}

rcCfmTrunkMaName OBJECT-TYPE
	SYNTAX		DisplayString(SIZE(255))
	MAX-ACCESS	read-create
	STATUS		current
	DESCRIPTION	"PBT Trunk Maintenance Association Name"
	::= { rcCfmTrunkEntry 7}

rcCfmTrunkVlanId OBJECT-TYPE
	SYNTAX		Integer32 (0..4095)
	MAX-ACCESS	read-create
	STATUS		current
	DESCRIPTION	"PBT trunk VLAN ID"
	::= { rcCfmTrunkEntry 8}

rcCfmTrunkReverseVlanId OBJECT-TYPE
	SYNTAX		Integer32 (0..4095)
	MAX-ACCESS	read-create
	STATUS		current
	DESCRIPTION	"PBT trunk reverse VLAN ID"
	::= { rcCfmTrunkEntry 9}

rcCfmTrunkMepId OBJECT-TYPE
	SYNTAX		Integer32 (0..8191)
	MAX-ACCESS	read-create
	STATUS		current
	DESCRIPTION	"PBT trunk MEP ID. Range 1-8191 is a valid Mep ID to
			be assigned to the CFM Trunk. '0' means unassign the 
			Med ID from the CFM Trunk"
	::= { rcCfmTrunkEntry 10}

rcCfmTrunkHoldTimer OBJECT-TYPE
        SYNTAX        Integer32
        MAX-ACCESS    read-create
        STATUS        current
        DESCRIPTION   "Trunk hold timer value."
        ::= { rcCfmTrunkEntry 11 }

rcCfmTrunkOperStatus OBJECT-TYPE
        SYNTAX        INTEGER { 
                          up(1), 
                          down(2),
                          waiting(3)
                       }
        MAX-ACCESS    read-only
        STATUS        current
        DESCRIPTION   "The current operational status of this trunk."
        DEFVAL        { down }
        ::= { rcCfmTrunkEntry 12 }

rcCfmTrunkSourceMac OBJECT-TYPE
	SYNTAX		MacAddress
	MAX-ACCESS	read-create
	STATUS		current
	DESCRIPTION	"Trunk Source Mac (local switch PBT mac)"
	::= { rcCfmTrunkEntry 13}
rcCfmTrunkClearStats OBJECT-TYPE
        SYNTAX        TruthValue
        MAX-ACCESS    read-create
        STATUS        current
        DESCRIPTION   "Action to clear the stats for all trunks"
        DEFVAL        { false }
        ::= { rcCfmTrunkEntry 14}


rcCfmTrunkUserLabel1 OBJECT-TYPE
	SYNTAX          OCTET STRING (SIZE(0..89))
        MAX-ACCESS      read-write
        STATUS          current
        DESCRIPTION     "User provided field. Used to give extra management information/data "
        ::= { rcCfmTrunkEntry 15 }

rcCfmTrunkUserLabel2 OBJECT-TYPE
	SYNTAX          OCTET STRING (SIZE(0..89))
        MAX-ACCESS      read-write
        STATUS          current
        DESCRIPTION     "User provided additional field. Used to give extra management information/data "
        ::= { rcCfmTrunkEntry 16 }

rcCfmTrunkSubportQueueSet OBJECT-TYPE
	SYNTAX		Integer32 (1..80)
	MAX-ACCESS	read-create
	STATUS		current
	DESCRIPTION	"Subport Queue Set Index Number"
	DEFVAL		{ 1 }
	::= { rcCfmTrunkEntry 17}

rcCfmTrunkDualHomePartner OBJECT-TYPE
        SYNTAX        EnableValue
        MAX-ACCESS    read-create
        STATUS        current
        DESCRIPTION   "Enable PBT trunk as Dual Home Partner"
  	DEFVAL        { disable }
        ::= { rcCfmTrunkEntry 18}

-- Service Group Table

rcCfmServiceGroupTable OBJECT-TYPE
	SYNTAX		SEQUENCE OF RcCfmServiceGroupEntry
	MAX-ACCESS	not-accessible
	STATUS		current
	DESCRIPTION	"Connectivity Fault Service Group table"
	::= { rcCfm 6}

rcCfmServiceGroupEntry OBJECT-TYPE
	SYNTAX		RcCfmServiceGroupEntry
	MAX-ACCESS	not-accessible
	STATUS		current
	DESCRIPTION	"Connectivity Fault Management ServiceGroup entry."
	INDEX		{rcCfmServiceGroupName}
	::= { rcCfmServiceGroupTable 1}

RcCfmServiceGroupEntry ::=
	SEQUENCE {
                rcCfmServiceGroupName		CfmNameString,
                rcCfmServiceGroupPort		InterfaceIndex,
                rcCfmServiceGroupAdminState	EnableValue,
		rcCfmServiceGroupRowStatus	RowStatus,
                rcCfmServiceGroupMac		MacAddress,
                rcCfmServiceGroupMdName		DisplayString,
		rcCfmServiceGroupMaName		DisplayString,
                rcCfmServiceGroupTgName		DisplayString,
                rcCfmServiceGroupMepId	        Integer32,
                rcCfmServiceGroupRingId         Integer32,
                rcCfmServiceGroupCcmOperStatus  INTEGER
		}

rcCfmServiceGroupName OBJECT-TYPE
	SYNTAX		CfmNameString
	MAX-ACCESS	not-accessible
	STATUS		current
	DESCRIPTION	"PBT ServiceGroup Name"
	::= { rcCfmServiceGroupEntry 1}

rcCfmServiceGroupPort OBJECT-TYPE
	SYNTAX		InterfaceIndex
	MAX-ACCESS	read-create
	STATUS		current
	DESCRIPTION	"PBT ServiceGroup Port"
	::= { rcCfmServiceGroupEntry 2}

rcCfmServiceGroupAdminState OBJECT-TYPE
        SYNTAX        EnableValue
        MAX-ACCESS    read-create
        STATUS        current
        DESCRIPTION   "Administratively enable or disable a PBT Service Group."
	DEFVAL        { disable }
        ::= { rcCfmServiceGroupEntry 3}

rcCfmServiceGroupRowStatus OBJECT-TYPE
	SYNTAX		RowStatus
	MAX-ACCESS	read-create
	STATUS		current
	DESCRIPTION	"Used to create/delete entries"
	::= { rcCfmServiceGroupEntry 4}

rcCfmServiceGroupMac OBJECT-TYPE
	SYNTAX		MacAddress
	MAX-ACCESS	read-create
	STATUS		current
	DESCRIPTION	"ServiceGroup Mac (remote mac of NPU)"
	::= { rcCfmServiceGroupEntry 5}

rcCfmServiceGroupMdName OBJECT-TYPE
	SYNTAX		DisplayString(SIZE(255))
	MAX-ACCESS	read-create
	STATUS		current
	DESCRIPTION	"PBT ServiceGroup Maintenance Domain Name"
	::= { rcCfmServiceGroupEntry 6}

rcCfmServiceGroupMaName OBJECT-TYPE
	SYNTAX		DisplayString(SIZE(255))
	MAX-ACCESS	read-create
	STATUS		current
	DESCRIPTION	"PBT ServiceGroup Maintenance Association Name"
	::= { rcCfmServiceGroupEntry 7}

rcCfmServiceGroupTgName OBJECT-TYPE
	SYNTAX		DisplayString(SIZE(32))
	MAX-ACCESS	read-create
	STATUS		current
	DESCRIPTION	"PBT ServiceGroup Trunk Group Name"
	::= { rcCfmServiceGroupEntry 8}

rcCfmServiceGroupMepId OBJECT-TYPE
	SYNTAX		Integer32 (0..8191)
	MAX-ACCESS	read-create
	STATUS		current
	DESCRIPTION	"PBT ServiceGroup MEP ID. Range 1-8191 is a valid Mep
			 ID to be assigned to the CFM Service group. '0' means
			 unassign the Med ID from the CFM service group"
	::= { rcCfmServiceGroupEntry 9}

rcCfmServiceGroupRingId OBJECT-TYPE
        SYNTAX        Integer32 (0..254)
        MAX-ACCESS    read-create
        STATUS        current
        DESCRIPTION   "Ring ID associated with Service Group"
	DEFVAL       { 0 }	
        ::= { rcCfmServiceGroupEntry 10}

rcCfmServiceGroupCcmOperStatus OBJECT-TYPE
        SYNTAX        INTEGER { 
                          up(1), 
                          down(2)
                       }
        MAX-ACCESS    read-only
        STATUS        current
        DESCRIPTION   "The current CCM operational status of this service group."
        ::= { rcCfmServiceGroupEntry 11 }

-- PBT Vlans Table

rcCfmPbt  OBJECT IDENTIFIER ::= {rcCfm 7}

rcCfmPbtVlans OBJECT-TYPE
	SYNTAX		OCTET STRING(SIZE(512))
 	MAX-ACCESS	read-write
 	STATUS		current
 	DESCRIPTION	"Connectivity Fault Management PBT vlan entry."
 	::= { rcCfmPbt 1}

rcCfmPbtMsti OBJECT-TYPE
        SYNTAX        Integer32 (0..63)
        MAX-ACCESS    read-write
        STATUS        current
        DESCRIPTION   "MSTI instance ID for PBT VLANS"
	DEFVAL       { 0 }	
        ::= { rcCfmPbt 2}

--- CFM Stats Table

rcCfmStatsTable OBJECT-TYPE
        SYNTAX        SEQUENCE OF RcCfmStatsEntry
        MAX-ACCESS    not-accessible
        STATUS        current
        DESCRIPTION   "CFM stats table"
        ::= { rcCfm 8 }
 
rcCfmStatsEntry OBJECT-TYPE
        SYNTAX        RcCfmStatsEntry
        MAX-ACCESS    not-accessible
        STATUS        current
        DESCRIPTION   "CFM Stats table entry. Contain CFM Message
                      sending/receiving and missing counter"
        INDEX         { rcCfmStatsDomainIndex, rcCfmStatsAssociationIndex, rcCfmStatsMepId}
        ::= { rcCfmStatsTable 1 }
 
RcCfmStatsEntry ::= 
        SEQUENCE {
                rcCfmStatsDomainIndex		Integer32,
                rcCfmStatsAssociationIndex	Integer32,
                rcCfmStatsDomainName		DisplayString,
                rcCfmStatsAssociationName	DisplayString,
		rcCfmStatsMepId			Integer32,
                rcCfmStatsTxCnt			Counter64,
                rcCfmStatsRxCnt			Counter64,
                rcCfmStatsRxZeroCnt		Counter64,
                rcCfmStatsMissedCnt		Counter64,
                rcCfmStatsUpTimeCnt		Counter64,
		rcCfmStatsDefect	        Integer32,
		rcCfmStatsAisTxCnt              Counter64,
                rcCfmStatsAisRxCnt              Counter64,
                rcCfmStatsAisOperState          INTEGER,
                rcCfmStatsAisMipLevel           Integer32,
                rcCfmStatsIfTlvTx               INTEGER,
		rcCfmStatsAccessDrops		Counter64,
		rcCfmStatsAggregateUplinkDrops  Counter64
       }

rcCfmStatsDomainIndex OBJECT-TYPE
	SYNTAX		Integer32 (1..2147483647)
	MAX-ACCESS	not-accessible
	STATUS		current
	DESCRIPTION	"Maintenance Domain Name"
	::= { rcCfmStatsEntry 1}

rcCfmStatsAssociationIndex OBJECT-TYPE
	SYNTAX		Integer32 (1..2147483647)
	MAX-ACCESS	not-accessible
	STATUS		current
	DESCRIPTION	"Maintenance Association Name"
	::= { rcCfmStatsEntry 2}

rcCfmStatsDomainName OBJECT-TYPE
	SYNTAX		DisplayString
	MAX-ACCESS	read-only
	STATUS		current
	DESCRIPTION	"Maintenance Domain Name"
	::= { rcCfmStatsEntry 3}

rcCfmStatsAssociationName OBJECT-TYPE
	SYNTAX		DisplayString
	MAX-ACCESS	read-only
	STATUS		current
	DESCRIPTION	"Maintenance Association Name"
	::= { rcCfmStatsEntry 4}

rcCfmStatsMepId OBJECT-TYPE
	SYNTAX		Integer32 (1..8191)
	MAX-ACCESS	not-accessible
	STATUS		current
	DESCRIPTION	"Maintenance EndPoint ID"
	::= { rcCfmStatsEntry 5}

rcCfmStatsTxCnt  OBJECT-TYPE
        SYNTAX         Counter64
        MAX-ACCESS     read-only
        STATUS         current
        DESCRIPTION    "The total Number of CFM messages are 
                       transmitted by trunk or ESM port"
        ::= { rcCfmStatsEntry 6}

rcCfmStatsRxCnt  OBJECT-TYPE
        SYNTAX         Counter64
        MAX-ACCESS     read-only
        STATUS         current
        DESCRIPTION    "The total Number of CFM messages are 
                       received by trunk or ESM port"
        ::= { rcCfmStatsEntry 7 }

rcCfmStatsRxZeroCnt  OBJECT-TYPE
        SYNTAX         Counter64
        MAX-ACCESS     read-only
        STATUS         current
        DESCRIPTION    "The total Number of CFM messages are 
                       received by trunk or ESM port"
        ::= { rcCfmStatsEntry 8 }

rcCfmStatsMissedCnt  OBJECT-TYPE
        SYNTAX         Counter64
        MAX-ACCESS     read-only
        STATUS         current
        DESCRIPTION    "The total Number of CFM messages are 
                       missing on trunk or ESM port"
        ::= { rcCfmStatsEntry 9 }

rcCfmStatsUpTimeCnt  OBJECT-TYPE
        SYNTAX         Counter64
        MAX-ACCESS     read-only
        STATUS         current
        DESCRIPTION    "The total Time of CFM messages are 
                        UP on trunk or ESM port in milliseconds"
        ::= { rcCfmStatsEntry 10 }

rcCfmStatsDefect  OBJECT-TYPE
        SYNTAX         Integer32 (0..5)
        MAX-ACCESS     read-only
        STATUS         current 
        DESCRIPTION    "An enumerated value indicating the highest-priority
                        defect that has been present since the MEP Fault Notification
                        Generate State Machine was last in the FNG_RESET state, either:
                        1) DefRDICCM: The last CCM received by this MEP from some
                           remote MEP contained the RDI bit.
                        2) DefMACstats: The last CCM received by this MEP from 
                           some remote MEP indicated that the transmitting MEP's 
                           associated MAC is reporting an error status.
                        3) DefRemoteCCM: This MEP is not receiving CCMs from some
                           other MEP in its configured list.
                        4) DefErrorCCM: This MEP is receiving invalid CCMs.
                        5) DefXconCCM: This MEP is receiving CCMs that could be from some other MA. 
                       "
        ::= { rcCfmStatsEntry 11 }

rcCfmStatsAisTxCnt  OBJECT-TYPE
        SYNTAX         Counter64
        MAX-ACCESS     read-only
        STATUS         current
        DESCRIPTION    "The total Number of AIS messages 
                       transmitted by Client Mep on Port/MLT"
        ::= { rcCfmStatsEntry 12}

rcCfmStatsAisRxCnt  OBJECT-TYPE
        SYNTAX         Counter64
        MAX-ACCESS     read-only
        STATUS         current
        DESCRIPTION    "The total Number of AIS messages 
                        received by Client Mep on Port/MLT"
        ::= { rcCfmStatsEntry 13}

rcCfmStatsAisOperState  OBJECT-TYPE
        SYNTAX         INTEGER {
                     true(1),
                     false(2)
                 }
        MAX-ACCESS     read-only
        STATUS         current
        DESCRIPTION    "To indicate the operational status of AIS. It is set 
                        to true when AIS is transmitted. It is set to false
                        when AIS is cleared."
        ::= { rcCfmStatsEntry 14}

rcCfmStatsAisMipLevel  OBJECT-TYPE
        SYNTAX         Integer32(0..7)
        MAX-ACCESS     read-only
        STATUS         current
        DESCRIPTION    "This is Maintenance Domain Level of the MIP on which
                        the AIS is transmitted."
        ::= { rcCfmStatsEntry 15}

rcCfmStatsIfTlvTx      OBJECT-TYPE
        SYNTAX         INTEGER {
                           none(1),
                           up(2), 
                           down(3),
                           lowerLayerDown(4),
                           testing(5),
                           unknown(6),
                           dormant(7),
                           notpresent(8)
                       }
        MAX-ACCESS     read-only
        STATUS         current
        DESCRIPTION    "To indicate the operational state of Interface
                        Status TLV transmitted on MaintenanceEndpoint.
                        This status indicates that the state of the local
                        UNI Port."
        ::= { rcCfmStatsEntry 16 }

rcCfmStatsAccessDrops  OBJECT-TYPE
        SYNTAX         Counter64
        MAX-ACCESS     read-only
        STATUS         current
        DESCRIPTION    "The total number of packets dropped on ingress to 
                       access port, for this MEP, due to same or lower MD level"
        ::= { rcCfmStatsEntry 17 }

rcCfmStatsAggregateUplinkDrops  OBJECT-TYPE
        SYNTAX         Counter64
        MAX-ACCESS     read-only
        STATUS         current
        DESCRIPTION    "The total number of packets dropped on ingress to
                       uplink port, for all MEPS, due to lower MD level"
        ::= { rcCfmStatsEntry 18 }

-- CCM operational indication
rcCfmTrap OBJECT IDENTIFIER ::= { rcCfm 9 } 

rcCfmTrunkCcmIndication	OBJECT-TYPE
        SYNTAX        	INTEGER { 
       			up(1),
			down(2)
       	   	      }	
        MAX-ACCESS    read-only
        STATUS        current 
        DESCRIPTION  " A Trunk CCM indication signifies that the trunk CCM operational status
                       has changed state to UP or DOWN"
                      
        ::= { rcCfmTrap 1 }
rcCfmServiceGroupCcmIndication	OBJECT-TYPE
        SYNTAX        	INTEGER { 
       			up(1),
			down(2)
       	   	      }	
        MAX-ACCESS    read-only
        STATUS        current 
        DESCRIPTION  " A Service Group CCM indication signifies that the service group CCM 
                       operational status has changed state to UP or DOWN"
                      
        ::= { rcCfmTrap 2 }

rcCfmEndPointCcmIndication	OBJECT-TYPE
        SYNTAX        	INTEGER { 
       			up(1),
			down(2)
       	   	      }	
        MAX-ACCESS    read-only
        STATUS        current 
        DESCRIPTION  " A Endpoint CCM indication signifies that the endpoint CCM 
                       operational status has changed state to UP or DOWN"
                      
        ::= { rcCfmTrap 3 }

rcCfmTrunkGroupIndication	OBJECT-TYPE
         SYNTAX        	INTEGER { 
        		majorFailure(1),
                        primaryFailed(2),
                        secondaryFailed(3),
                        manualSwitched(4),
                        reversion(5)
        	       }	
         MAX-ACCESS    read-only
         STATUS        current 
         DESCRIPTION  " A Trunk group CCM indication signifies what kind of protection failure
                        within the trunk group"
                       
         ::= { rcCfmTrap 4 }

rcCfmTrunkGroupProtected	OBJECT-TYPE
         SYNTAX        	INTEGER { 
        		wasprotected(1),
                        wasnotprotected(2)
        	       }	
         MAX-ACCESS    read-only
         STATUS        current 
         DESCRIPTION  " signifies trunk group was protected or was not protected"
                       
         ::= { rcCfmTrap 5 }

rcCfmRemoteMepId OBJECT-TYPE
        SYNTAX		Integer32 (1..8191)
	MAX-ACCESS	read-only
	STATUS		current
        DESCRIPTION     "Remote Maintenance Endpoint ID"
	::= {rcCfmTrap 6}

rcCfmLocalMepId OBJECT-TYPE
        SYNTAX		Integer32 (1..8191)
	MAX-ACCESS      read-only
	STATUS		current
        DESCRIPTION     "Local Maintenance Endpoint ID"
	::= {rcCfmTrap 7}

rcCfmMepCcmIndication OBJECT-TYPE
	SYNTAX		INTEGER {
			   down(1), 
	                   up(2),
			   learned(3),
			   update(4)
			}	
	MAX-ACCESS	read-only
	STATUS		current
	DESCRIPTION	"CCM indication signifies that the MEP CCM 
                        operational status"
	::= {rcCfmTrap 8}

rcCfmCvid OBJECT-TYPE
        SYNTAX        Integer32 (1..4094)
        MAX-ACCESS    read-only
        STATUS        current
        DESCRIPTION   "A value that uniquely identifies the Customer
			Vlan Id in i-sid endpt."
        ::= { rcCfmTrap 9 }

rcCfmRemoteMacAddr OBJECT-TYPE
        SYNTAX        MacAddress
        MAX-ACCESS    read-only
        STATUS        current
        DESCRIPTION   "remote MAC address"
        ::= { rcCfmTrap 10}

rcCfmIsidId OBJECT-TYPE
        SYNTAX        Integer32 (1..16777215)
        MAX-ACCESS    read-only
        STATUS        current
        DESCRIPTION   "Service Instance ID of the I component"
        ::= { rcCfmTrap 11 }
rcCfmTrapTrunkName OBJECT-TYPE
	SYNTAX		DisplayString(SIZE(0..32))
	MAX-ACCESS	read-only
	STATUS		current
	DESCRIPTION	"PBT Trunk Name"
	::= { rcCfmTrap 12}

rcCfmPbitNum OBJECT-TYPE
        SYNTAX        Integer32 (0..7)
        MAX-ACCESS    read-only
        STATUS        current
        DESCRIPTION   " p-bit value used to queue packets"
        ::= { rcCfmTrap 13 }


rcCfmUserLabel1 OBJECT-TYPE
	SYNTAX		DisplayString(SIZE(0..80))
	MAX-ACCESS	read-only
	STATUS		current
	DESCRIPTION	"Memo field <Data OSS port ID>"
        REFERENCE       "MERS v4.2 PRD" 
	::= { rcCfmTrap 14}

rcCfmUserLabel2 OBJECT-TYPE
	SYNTAX		DisplayString(SIZE(0..80))
	MAX-ACCESS	read-only
	STATUS		current
	DESCRIPTION	"Memo field <Sonet OSS circuit ID>"
        REFERENCE       "MERS v4.2 PRD" 
	::= { rcCfmTrap 15}

rcCfmMonitorCosPriority OBJECT-TYPE
        SYNTAX		Integer32 (0..7)
	MAX-ACCESS      read-only
	STATUS		current
        DESCRIPTION     "Monitor customer traffic on COS priority"
	::= {rcCfmTrap 16}

rcCfmThresholdIndication OBJECT-TYPE
        SYNTAX        	INTEGER { 
       			exceeded(1),
			recovered(2)
       	   	      }	
        MAX-ACCESS    read-only
        STATUS        current 
        DESCRIPTION  " A threshold indication is:
                          alarm -  when the set-threshold has been exceeded 
                          clear -  when the clear-threshold level has been 
                                   reached after an alarm condition
                     "
        ::= { rcCfmTrap 17 }

rcCfmActualPercentage  OBJECT-TYPE
        SYNTAX         Integer32 (0..99)
        MAX-ACCESS     read-only
        STATUS         current
        DESCRIPTION    "Measured Percentage in 1 percent increments"
        ::= { rcCfmTrap 18}

rcCfmActualSubPercentage  OBJECT-TYPE
        SYNTAX         Integer32 (0..99)
        MAX-ACCESS     read-only
        STATUS         current
        DESCRIPTION    "Measured Sub percentage in 1/100 percent increments"
        ::= { rcCfmTrap 19}

rcCfmAlarmThreshold  OBJECT-TYPE
        SYNTAX         Integer32 (0..99)
        MAX-ACCESS     read-only
        STATUS         current
        DESCRIPTION    "Configured alarm percentage threshold"
        ::= { rcCfmTrap 20}

rcCfmAlarmSubThreshold  OBJECT-TYPE
        SYNTAX         Integer32 (0..99)
        MAX-ACCESS     read-only
        STATUS         current
        DESCRIPTION    "Configured alarm sub percentage threshold"
        ::= { rcCfmTrap 21}

rcCfmClearThreshold  OBJECT-TYPE
        SYNTAX         Integer32 (0..99)
        MAX-ACCESS     read-only
        STATUS         current
        DESCRIPTION    "Configured clear percentage threshold"
        ::= { rcCfmTrap 22}

rcCfmClearSubThreshold  OBJECT-TYPE
        SYNTAX         Integer32 (0..99)
        MAX-ACCESS     read-only
        STATUS         current
        DESCRIPTION    "Configured clear sub percentage threshold"
        ::= { rcCfmTrap 23}

rcCfmFdTarget  OBJECT-TYPE
        SYNTAX         Counter32
        MAX-ACCESS     read-only
        STATUS         current
        DESCRIPTION    "frame delay target"
        ::= { rcCfmTrap 24}

rcCfmFdAverage  OBJECT-TYPE
        SYNTAX         Counter32
        MAX-ACCESS     read-only
        STATUS         current
        DESCRIPTION    "frame delay average"
        ::= { rcCfmTrap 25}

rcCfmTime  OBJECT-TYPE
        SYNTAX          DateAndTime
        MAX-ACCESS      read-only
        STATUS          current
        DESCRIPTION     "The date and time stamp."
	::= { rcCfmTrap 26}

rcCfmTrapTrunkGroupName OBJECT-TYPE 
        SYNTAX          DisplayString (SIZE (0..32))    
        MAX-ACCESS      read-only
        STATUS          current
        DESCRIPTION     "trunk group name."
	::= { rcCfmTrap 27}

rcCfmVid OBJECT-TYPE
        SYNTAX        Integer32 (0..4096)
        MAX-ACCESS    read-only
        STATUS        current
        DESCRIPTION   "A value that uniquely identifies the Customer
			Vlan Id in i-sid endpt."
        ::= { rcCfmTrap 28 }

rcCfmFdvTarget  OBJECT-TYPE
        SYNTAX         Counter32
        MAX-ACCESS     read-only
        STATUS         current
        DESCRIPTION    "frame delay variation target"
        ::= { rcCfmTrap 29}

rcCfmFdvAverage  OBJECT-TYPE
        SYNTAX         Counter32
        MAX-ACCESS     read-only
        STATUS         current
        DESCRIPTION    "frame delay variation average"
        ::= { rcCfmTrap 30}

rcCfmDirection OBJECT-TYPE
        SYNTAX        	INTEGER { 
       			up(1),
			down(2)
       	   	      }	
        MAX-ACCESS    read-only
        STATUS        current 
        DESCRIPTION  " MEP direction"
        ::= { rcCfmTrap 31 }

rcCfmDhuId OBJECT-TYPE
        SYNTAX        Integer32 (1..254)
        MAX-ACCESS    read-only
        STATUS        current
        DESCRIPTION   "A value that uniquely identifies the
                       DH Uni Id in i-sid endpt."
        ::= { rcCfmTrap 32 }

rcCfmIftlvIndication	OBJECT-TYPE
        SYNTAX        	INTEGER { 
       			down(1),
			up(2)
       	   	      }	
        MAX-ACCESS    read-only
        STATUS        current 
        DESCRIPTION  " A Iftlv indication signifies that the operational status of CCM that is 
		       sent or received with iftlv has changed state to UP or DOWN"
                      
        ::= { rcCfmTrap 33 }

rcCfmGlobals OBJECT IDENTIFIER ::= { rcCfm 10 } 

rcCfmGlobalsEtherType OBJECT-TYPE
        SYNTAX        Integer32 (1..'FFFF'h)
        MAX-ACCESS    read-write
        STATUS        current
        DESCRIPTION   "CFM Ether Type"
        DEFVAL        { '8902'h }
        ::= { rcCfmGlobals 1 }

rcCfmGlobalsPbtMac OBJECT-TYPE
        SYNTAX	      MacAddress
        MAX-ACCESS    read-write
        STATUS        current
        DESCRIPTION   "PBT base MAC address"
        ::= { rcCfmGlobals 2 }

rcCfmGlobalsPortVid OBJECT-TYPE
        SYNTAX        Integer32 (0..4095)
        MAX-ACCESS    read-write
        STATUS        current
        DESCRIPTION   "CFM default port vid, 4095 is used for untagged."
        ::= { rcCfmGlobals 3 }

rcCfmGlobalsPbtDropTrapTimer OBJECT-TYPE
        SYNTAX        Integer32 (1..1440)
        MAX-ACCESS    read-write
        STATUS        current
        DESCRIPTION   "The timer settings for traps being sent 
		       on discard of packets with unknown 
		       destination MAC in minutes"
        DEFVAL        { 900 }
        ::= { rcCfmGlobals 4 }

rcCfmGlobalsPmEnable OBJECT-TYPE
        SYNTAX          EnableValue
        MAX-ACCESS      read-write
        STATUS          current
        DESCRIPTION     "Performance monitor enable"
        REFERENCE       "MERS v4.2 PRD"
        DEFVAL {enable}
        ::= { rcCfmGlobals 5 }

rcCfmGlobalsCcmTrapDisplayEnable OBJECT-TYPE
        SYNTAX          EnableValue
        MAX-ACCESS      read-write
        STATUS          current
        DESCRIPTION     "CCM trap display enable"
        DEFVAL {enable}
        ::= { rcCfmGlobals 6 }

rcCfmGlobalsPmLogEnable OBJECT-TYPE
        SYNTAX          EnableValue
        MAX-ACCESS      read-write
        STATUS          current
        DESCRIPTION     "Enable PM Auto Logging"
        DEFVAL {disable}
        ::= { rcCfmGlobals 7 }

rcCfmGlobalsSpbmAdminState OBJECT-TYPE
        SYNTAX        EnableValue
        MAX-ACCESS    read-write
        STATUS        current
        DESCRIPTION   "Enable/Disable global cfm support for SPBM VLANs"
        DEFVAL        { disable }
        ::= { rcCfmGlobals 8 }

rcCfmGlobalsSpbmLevel OBJECT-TYPE
        SYNTAX        Integer32 (0..7)
        MAX-ACCESS    read-write
        STATUS        current
        DESCRIPTION   "Used to set the global cfm maintenance level for SPBM VLANs"
        DEFVAL        { 4 }
        ::= { rcCfmGlobals 9 }

rcCfmGlobalsSpbmMepId OBJECT-TYPE
        SYNTAX        Integer32 (1..8191)
        MAX-ACCESS    read-write
        STATUS        current
        DESCRIPTION   "Set the global cfm Maintenance End Point ID value for SPBM VLANs"
        DEFVAL        { 1 }
        ::= { rcCfmGlobals 10 }

rcCfmGlobalsCmacAdminState OBJECT-TYPE
        SYNTAX        EnableValue
        MAX-ACCESS    read-write
        STATUS        current
        DESCRIPTION   "Enable/Disable global cfm support for C-VLANs"
        DEFVAL        { disable }
        ::= { rcCfmGlobals 11 }

 
rcCfmGlobalsCmacLevel OBJECT-TYPE
        SYNTAX        Integer32 (0..7)
        MAX-ACCESS    read-write
        STATUS        current
        DESCRIPTION   "Used to set the global cfm maintenance level for C-VLANs"
        DEFVAL        { 4 }
        ::= { rcCfmGlobals 12 }

 
rcCfmGlobalsCmacMepId OBJECT-TYPE
        SYNTAX        Integer32 (1..8191)
        MAX-ACCESS    read-write
        STATUS        current
        DESCRIPTION   "Set the global cfm Maintenance End Point ID value for C-VLANs"
        DEFVAL        { 1 }
        ::= { rcCfmGlobals 13 }
    
rcCfmGlobalsBmac     OBJECT-TYPE
        SYNTAX          MacAddress
        MAX-ACCESS      read-only
        STATUS          current
        DESCRIPTION     "The Bmac address of the node"
        ::= { rcCfmGlobals 14 }
        
rcCfmGlobalsCmac     OBJECT-TYPE
        SYNTAX          MacAddress
        MAX-ACCESS      read-only
        STATUS          current
        DESCRIPTION     "The Cmac address of the node "
        ::= { rcCfmGlobals 15 }

    
-- Remote Maintenance EndPoint Table

rcCfmRemoteMepConfigTable OBJECT-TYPE
	SYNTAX		SEQUENCE OF RcCfmRemoteMepConfigEntry
	MAX-ACCESS	not-accessible
	STATUS		current
	DESCRIPTION	"Connectivity Fault Management Remote Maintenance Association table"
	::= { rcCfm 11}

rcCfmRemoteMepConfigEntry OBJECT-TYPE
	SYNTAX		RcCfmRemoteMepConfigEntry
	MAX-ACCESS	not-accessible
	STATUS		current
	DESCRIPTION	"Connectivity Fault Management Remote Maintenance EndPoint entry."
	INDEX		{rcCfmRemoteMepConfigDomainIndex, rcCfmRemoteMepConfigAssociationIndex, rcCfmRemoteMepConfigId }
	::= { rcCfmRemoteMepConfigTable 1}

RcCfmRemoteMepConfigEntry ::=
	SEQUENCE {
		rcCfmRemoteMepConfigDomainIndex		Integer32,
                rcCfmRemoteMepConfigAssociationIndex	Integer32,
		rcCfmRemoteMepConfigId			Integer32,
                rcCfmRemoteMepConfigDomainName		DisplayString,
                rcCfmRemoteMepConfigAssociationName	DisplayString,
		rcCfmRemoteMepConfigMacAddr		MacAddress,
                rcCfmRemoteMepConfigRowStatus		RowStatus
		}

rcCfmRemoteMepConfigDomainIndex OBJECT-TYPE
	SYNTAX		Integer32 (1..2147483647)
	MAX-ACCESS	not-accessible
	STATUS		current
	DESCRIPTION	"Remote Maintenance Domain Name"
	::= { rcCfmRemoteMepConfigEntry 1}

rcCfmRemoteMepConfigAssociationIndex OBJECT-TYPE
	SYNTAX		Integer32 (1..2147483647)
	MAX-ACCESS	not-accessible
	STATUS		current
	DESCRIPTION	"Remote Maintenance Association Name"
	::= { rcCfmRemoteMepConfigEntry 2}

rcCfmRemoteMepConfigId OBJECT-TYPE
	SYNTAX		Integer32 (1..8191)
	MAX-ACCESS	not-accessible
	STATUS		current
	DESCRIPTION	"Remote Maintenance EndPoint ID"
	::= { rcCfmRemoteMepConfigEntry 3}

rcCfmRemoteMepConfigDomainName OBJECT-TYPE
	SYNTAX		DisplayString
	MAX-ACCESS	read-only
	STATUS		current
	DESCRIPTION	"Remote Maintenance Domain Name"
	::= { rcCfmRemoteMepConfigEntry 4}

rcCfmRemoteMepConfigAssociationName OBJECT-TYPE
	SYNTAX		DisplayString
	MAX-ACCESS	read-only
	STATUS		current
	DESCRIPTION	"Remote Maintenance Association Name"
	::= { rcCfmRemoteMepConfigEntry 5}

rcCfmRemoteMepConfigMacAddr OBJECT-TYPE
	SYNTAX		MacAddress
	MAX-ACCESS	read-create
	STATUS		current
	DESCRIPTION	"Mac address of remote maintenance endpoint"
	::= { rcCfmRemoteMepConfigEntry 6}

rcCfmRemoteMepConfigRowStatus OBJECT-TYPE
	SYNTAX		RowStatus
	MAX-ACCESS	read-create
	STATUS		current
	DESCRIPTION	"Used to create/delete entries"
	::= { rcCfmRemoteMepConfigEntry 7}

-- Remote Mep Learn Stats
 
RcCfmRemoteMepState ::= TEXTUAL-CONVENTION
   STATUS current
   DESCRIPTION
      "Operational state of the remote MEP state machine"
   REFERENCE
      "802.1ag clauses 12.14.7.6.3 b), 20.16 and 20.17"
   SYNTAX INTEGER {
      rMepIdle (1),
      rMepStart (2),
      rMepFailed (3),
      rMepOk (4)
   }

RcCfmPmOperState ::= TEXTUAL-CONVENTION
   STATUS current
   DESCRIPTION
      "Operational state of the Performance Montitor form mep-rmep pair"

   SYNTAX INTEGER {
      rPmUp (1),
      rPmDown (2),
      rPmError (3),
      rPmSync (4)
   }

rcCfmRemoteMepStatsTable OBJECT-TYPE
        SYNTAX        SEQUENCE OF RcCfmRemoteMepStatsEntry
        MAX-ACCESS    not-accessible
        STATUS        current
        DESCRIPTION   "CFM Mep Learn stats table contains the 
		       local and remote mep Tx and Rx statistics"
        ::= { rcCfm 12 }
 
rcCfmRemoteMepStatsEntry OBJECT-TYPE
        SYNTAX        RcCfmRemoteMepStatsEntry
        MAX-ACCESS    not-accessible
        STATUS        current
        DESCRIPTION   "CFM Stats table entry. Contain CFM Message
                      sending/receiving and missing counter. 
		      Entry indicate the CCM message still alive"
        INDEX         { rcCfmRemoteMepStatsDomainIndex, rcCfmRemoteMepStatsAssociationIndex, rcCfmRemoteMepStatsMepId, rcCfmRemoteMepStatsRemoteMepId}
        ::= { rcCfmRemoteMepStatsTable 1 }
 
RcCfmRemoteMepStatsEntry ::= 
        SEQUENCE {
                rcCfmRemoteMepStatsDomainIndex		Integer32,
                rcCfmRemoteMepStatsAssociationIndex	Integer32,
		rcCfmRemoteMepStatsMepId		Integer32,
		rcCfmRemoteMepStatsRemoteMepId          Integer32,
                rcCfmRemoteMepStatsDomainName           DisplayString,
                rcCfmRemoteMepStatsAssociationName	DisplayString,
                rcCfmRemoteMepStatsLearnType            INTEGER,
                rcCfmRemoteMepStatsRemoteMacAddr        MacAddress,
                rcCfmRemoteMepStatsRxCnt		Counter64,
                rcCfmRemoteMepStatsSeqErrCnt		Counter64,
                rcCfmRemoteMepStatsOperState            INTEGER,
                rcCfmRemoteMepStatsClearStats           TruthValue,
                rcCfmRemoteMepStatsDbRdi                TruthValue,
		rcCfmRemoteMepStatsIfTlvRx              INTEGER 
                }
      
rcCfmRemoteMepStatsDomainIndex OBJECT-TYPE
	SYNTAX		Integer32 (1..2147483647)
	MAX-ACCESS	not-accessible
	STATUS		current
	DESCRIPTION	"Maintenance Domain Name index"
	::= { rcCfmRemoteMepStatsEntry 1}

rcCfmRemoteMepStatsAssociationIndex OBJECT-TYPE
	SYNTAX		Integer32 (1..2147483647)
	MAX-ACCESS	not-accessible
	STATUS		current
	DESCRIPTION	"Maintenance Association Name index"
	::= { rcCfmRemoteMepStatsEntry 2}

rcCfmRemoteMepStatsMepId OBJECT-TYPE
	SYNTAX		Integer32 (1..8191)
	MAX-ACCESS	not-accessible
	STATUS		current
	DESCRIPTION	"Local MEP (Maintenance EndPoint) ID"
	::= { rcCfmRemoteMepStatsEntry 3}

rcCfmRemoteMepStatsRemoteMepId OBJECT-TYPE
	SYNTAX		Integer32 (1..8191)
	MAX-ACCESS	not-accessible
	STATUS		current
	DESCRIPTION	"Remote Mep Id which the local mep rx
			CCM message from"
	::= { rcCfmRemoteMepStatsEntry 4}

rcCfmRemoteMepStatsDomainName OBJECT-TYPE
	SYNTAX		DisplayString(SIZE(1..22))
	MAX-ACCESS	read-only
	STATUS		current
	DESCRIPTION	"Maintenance Domain Name"
	::= { rcCfmRemoteMepStatsEntry 5}

rcCfmRemoteMepStatsAssociationName OBJECT-TYPE
	SYNTAX		DisplayString(SIZE(1..22))
	MAX-ACCESS	read-only
	STATUS		current
	DESCRIPTION	"Maintenance Association Name"
	::= { rcCfmRemoteMepStatsEntry 6}
	
rcCfmRemoteMepStatsLearnType OBJECT-TYPE
	SYNTAX		INTEGER {
			  static(1),
			  dynamic(2)
			}
	MAX-ACCESS	read-only	
	STATUS		current
	DESCRIPTION	"Indicate the learning remote Mep is static 
			 created or dynamic learn"
	::= { rcCfmRemoteMepStatsEntry 7}

rcCfmRemoteMepStatsRemoteMacAddr OBJECT-TYPE
        SYNTAX        MacAddress
        MAX-ACCESS    read-only
        STATUS        current
        DESCRIPTION   "A remote MAC address"
        ::= { rcCfmRemoteMepStatsEntry 8 }

rcCfmRemoteMepStatsRxCnt  OBJECT-TYPE
        SYNTAX         Counter64
        MAX-ACCESS     read-only
        STATUS         current
        DESCRIPTION    "The total Number of CFM messages are 
                       received by trunk or ESM port"
        ::= { rcCfmRemoteMepStatsEntry 9 }

rcCfmRemoteMepStatsSeqErrCnt  OBJECT-TYPE
        SYNTAX         Counter64
        MAX-ACCESS     read-only
        STATUS         current
        DESCRIPTION    "The total Number of Sequence errors" 
        ::= { rcCfmRemoteMepStatsEntry 10}

rcCfmRemoteMepStatsOperState  OBJECT-TYPE
        SYNTAX         INTEGER {
                           start(1),
                           up(2),
                           down(3)
                        }
        MAX-ACCESS     read-only
        STATUS         current
        DESCRIPTION    "To indicate the operational state of remote 
		        maintenance endpoint"
        ::= { rcCfmRemoteMepStatsEntry 11 }

rcCfmRemoteMepStatsClearStats   OBJECT-TYPE
        SYNTAX          TruthValue
        MAX-ACCESS      read-write
        STATUS          current
        DESCRIPTION     "To clear the CCM messages counter"
        DEFVAL          { false }
        ::= { rcCfmRemoteMepStatsEntry 12 }

rcCfmRemoteMepStatsDbRdi OBJECT-TYPE
   SYNTAX TruthValue
   MAX-ACCESS read-only
   STATUS current
   DESCRIPTION
      "State of the RDI bit in the last received CCM (true for
      RDI=1), or false if none has been received."
   REFERENCE
      "802.1ag clauses 12.14.7.6.3 and 20.15.2"
   ::= { rcCfmRemoteMepStatsEntry 13 }

rcCfmRemoteMepStatsIfTlvRx OBJECT-TYPE
   SYNTAX     INTEGER { 
            none(1),
            up(2), 
            down(3),
            lowerLayerDown(4),
            testing(5),
            unknown(6),
            dormant(7),
            notpresent(8)
          }
   MAX-ACCESS read-only
   STATUS current
   DESCRIPTION
      "To indicate the operational state of Interface Status TLV received 
       on MaintenanceEndpoint. This status indicates that the state of the
       remote UNI Port"
   ::= { rcCfmRemoteMepStatsEntry 14 }

-- Maintenance Intermediate Point Table

-- Maintenance Intermediate Point Table

rcCfmMaintenanceIntermediatePointTable OBJECT-TYPE
	SYNTAX		SEQUENCE OF RcCfmMaintenanceIntermediatePointEntry
	MAX-ACCESS	not-accessible
	STATUS		current
	DESCRIPTION	"Connectivity Fault Management Maintenance Intermediate Point table"
	::= { rcCfm 13}

rcCfmMaintenanceIntermediatePointEntry OBJECT-TYPE
	SYNTAX		RcCfmMaintenanceIntermediatePointEntry
	MAX-ACCESS	not-accessible
	STATUS		current
	DESCRIPTION	"Connectivity Fault Management Maintenance Intermediate Point entry."
	INDEX		{rcCfmMaintenanceIntermediatePointDomainIndex, rcCfmMaintenanceIntermediatePointId }
	::= { rcCfmMaintenanceIntermediatePointTable 1}

RcCfmMaintenanceIntermediatePointEntry ::=
	SEQUENCE {
		rcCfmMaintenanceIntermediatePointDomainIndex		Integer32,
		rcCfmMaintenanceIntermediatePointId			Integer32,
                rcCfmMaintenanceIntermediatePointDomainName		DisplayString,
		rcCfmMaintenanceIntermediatePointRowStatus		RowStatus,
                rcCfmMaintenanceIntermediatePointMipType         	INTEGER,
		rcCfmMaintenanceIntermediatePointClearStats		TruthValue,
                rcCfmMaintenanceIntermediatePointServiceDescription     DisplayString  
		}

rcCfmMaintenanceIntermediatePointDomainIndex OBJECT-TYPE
	SYNTAX		Integer32 (1..2147483647)
	MAX-ACCESS	not-accessible
	STATUS		current
	DESCRIPTION	"Maintenance Domain Name"
	::= { rcCfmMaintenanceIntermediatePointEntry 1}

rcCfmMaintenanceIntermediatePointId OBJECT-TYPE
	SYNTAX		Integer32 (1..8191)
	MAX-ACCESS	not-accessible
	STATUS		current
	DESCRIPTION	"Maintenance IntermediatePoint ID"
	::= { rcCfmMaintenanceIntermediatePointEntry 2}

rcCfmMaintenanceIntermediatePointDomainName OBJECT-TYPE
	SYNTAX		DisplayString
	MAX-ACCESS	read-only
	STATUS		current
	DESCRIPTION	"Maintenance Domain Name"
	::= { rcCfmMaintenanceIntermediatePointEntry 3}

rcCfmMaintenanceIntermediatePointRowStatus OBJECT-TYPE
	SYNTAX		RowStatus
	MAX-ACCESS	read-create
	STATUS		current
	DESCRIPTION	"Used to create/delete entries"
	::= { rcCfmMaintenanceIntermediatePointEntry 4}

rcCfmMaintenanceIntermediatePointMipType OBJECT-TYPE
        SYNTAX        INTEGER { 
                          vlan(1),
  	                  unused(2),
			  endptClient(4)
                        }
        MAX-ACCESS    read-only
        STATUS        current
        DESCRIPTION   "Mip Type"
        ::= { rcCfmMaintenanceIntermediatePointEntry 5 }

rcCfmMaintenanceIntermediatePointClearStats   OBJECT-TYPE
        SYNTAX          TruthValue
        MAX-ACCESS      read-create
        STATUS          current
        DESCRIPTION     "To clear the MIP CCM sending/receiving 
			 message counter"
        DEFVAL          { false }
        ::= { rcCfmMaintenanceIntermediatePointEntry 6 }

rcCfmMaintenanceIntermediatePointServiceDescription OBJECT-TYPE
        SYNTAX          DisplayString(SIZE (0..48))
        MAX-ACCESS      read-only
        STATUS          current
        DESCRIPTION     "Used to specify what service this mip assigned to"
        ::= { rcCfmMaintenanceIntermediatePointEntry 7}


--- CFM NNI Table

rcCfmNniTable OBJECT-TYPE
        SYNTAX        SEQUENCE OF RcCfmNniEntry
        MAX-ACCESS    not-accessible
        STATUS        current
        DESCRIPTION   "CFM NNI table"
        ::= { rcCfm 14 }
 
rcCfmNniEntry OBJECT-TYPE
        SYNTAX        RcCfmNniEntry
        MAX-ACCESS    not-accessible
        STATUS        current
        DESCRIPTION   "CFM NNI table entry"
        INDEX         { rcCfmNniPort, rcCfmNniServiceId, rcCfmNniPwIndex, rcCfmNniTlsIndex}
        ::= { rcCfmNniTable 1 }
 
RcCfmNniEntry ::= 
        SEQUENCE {
                rcCfmNniPort		InterfaceIndex,
                rcCfmNniServiceId	Integer32,
   		rcCfmNniPwIndex		Integer32,
                rcCfmNniTlsIndex	Integer32,
                rcCfmNniTgName		DisplayString

       }

rcCfmNniPort OBJECT-TYPE
	SYNTAX		InterfaceIndex
	MAX-ACCESS	not-accessible
	STATUS		current
	DESCRIPTION	"PBT Trunk Port"
	::= { rcCfmNniEntry 1}

rcCfmNniServiceId OBJECT-TYPE
	SYNTAX		Integer32 (0..16777215) 
	MAX-ACCESS	not-accessible
	STATUS		current
	DESCRIPTION	"TDI or MIM"
	::= { rcCfmNniEntry 2}

rcCfmNniPwIndex OBJECT-TYPE
	SYNTAX		Integer32 (0..16777215)
	MAX-ACCESS	not-accessible
	STATUS		current
	DESCRIPTION	"PW index"
	::= { rcCfmNniEntry 3}

rcCfmNniTlsIndex OBJECT-TYPE
	SYNTAX		Integer32 (1..2147483647)
	MAX-ACCESS	not-accessible
	STATUS		current
	DESCRIPTION	"Access Port"
	::= { rcCfmNniEntry 4}

rcCfmNniTgName OBJECT-TYPE
	SYNTAX		DisplayString(SIZE(32))
	MAX-ACCESS	read-only
	STATUS		current
	DESCRIPTION	"PBT Trunk Group Name"
	::= { rcCfmNniEntry 5}

--- PBT NNI Stats Table

rcCfmNniStatsTable OBJECT-TYPE
        SYNTAX        SEQUENCE OF RcCfmNniStatsEntry
        MAX-ACCESS    not-accessible
        STATUS        current
        DESCRIPTION   "CFM NNI stats table"
        ::= { rcCfm 15 }

rcCfmNniStatsEntry OBJECT-TYPE
        SYNTAX        RcCfmNniStatsEntry
        MAX-ACCESS    not-accessible
        STATUS        current
        DESCRIPTION   "CFM NNI Stats table entry. Contain bytes processed and dropped
                       due to lookup failure in the SDT table"
        INDEX         { rcCfmNniStatsPort}
        ::= { rcCfmNniStatsTable 1 }
 
RcCfmNniStatsEntry ::= 
        SEQUENCE {
                rcCfmNniStatsPort			InterfaceIndex,
		rcCfmNniStatsOel2RxOctets		Counter64,
		rcCfmNniStatsOel2RxDroppedOctets	Counter64,
		rcCfmNniStatsMimRxOctets		Counter64,
		rcCfmNniStatsMimRxDroppedOctets		Counter64,
		rcCfmNniStatsPweRxOctets		Counter64,
		rcCfmNniStatsPweRxDroppedOctets		Counter64
       }

rcCfmNniStatsPort OBJECT-TYPE
	SYNTAX		InterfaceIndex
	MAX-ACCESS	not-accessible
	STATUS		current
	DESCRIPTION	"PBT Trunk Port"
	::= { rcCfmNniStatsEntry 1}

rcCfmNniStatsOel2RxOctets  OBJECT-TYPE
        SYNTAX         Counter64
        MAX-ACCESS     read-only
        STATUS         current
        DESCRIPTION    "The total Number of bytes (OEL2 encapsulation) processed on ingress NNI port"
        ::= { rcCfmNniStatsEntry 2}

rcCfmNniStatsOel2RxDroppedOctets  OBJECT-TYPE
        SYNTAX         Counter64
        MAX-ACCESS     read-only
        STATUS         current
        DESCRIPTION    "The total Number of bytes (OEL2 encapsulation) dropped on ingress NNI port"
        ::= { rcCfmNniStatsEntry 3}

rcCfmNniStatsMimRxOctets  OBJECT-TYPE
        SYNTAX         Counter64
        MAX-ACCESS     read-only
        STATUS         current
        DESCRIPTION    "The total Number of bytes (MIM encapsulation) processed on ingress NNI port"
        ::= { rcCfmNniStatsEntry 4}

rcCfmNniStatsMimRxDroppedOctets  OBJECT-TYPE
        SYNTAX         Counter64
        MAX-ACCESS     read-only
        STATUS         current
        DESCRIPTION    "The total Number of bytes (MIM encapsulation) dropped on ingress NNI port"
        ::= { rcCfmNniStatsEntry 5}

rcCfmNniStatsPweRxOctets  OBJECT-TYPE
        SYNTAX         Counter64
        MAX-ACCESS     read-only
        STATUS         current
        DESCRIPTION    "The total Number of bytes (PWE encapsulation) processed on ingress NNI port"
        ::= { rcCfmNniStatsEntry 6}

rcCfmNniStatsPweRxDroppedOctets  OBJECT-TYPE
        SYNTAX         Counter64
        MAX-ACCESS     read-only
        STATUS         current
        DESCRIPTION    "The total Number of bytes (PWE encapsulation) dropped on ingress NNI port"
        ::= { rcCfmNniStatsEntry 7}



rcCfmMipStatsTable OBJECT-TYPE
        SYNTAX        SEQUENCE OF RcCfmMipStatsEntry
        MAX-ACCESS    not-accessible
        STATUS        current
        DESCRIPTION   "CFM Mip stats table"
        ::= { rcCfm 16 }
 
rcCfmMipStatsEntry OBJECT-TYPE
        SYNTAX        RcCfmMipStatsEntry
        MAX-ACCESS    not-accessible
        STATUS        current
        DESCRIPTION   "CFM Mip Stats table entry. Contain CFM Mip message number of
                      receiving/replying loopback & linktrace."
        INDEX         { rcCfmMipStatsDomainIndex, rcCfmMipStatsMipId}
        ::= { rcCfmMipStatsTable 1 }
 
RcCfmMipStatsEntry ::= 
        SEQUENCE {
                rcCfmMipStatsDomainIndex		Integer32,
        	rcCfmMipStatsDomainName	  	        DisplayString,
		rcCfmMipStatsMipId			Integer32,
                rcCfmMipStatsLoopbackReceived		Counter64,
                rcCfmMipStatsLoopbackReplied		Counter64,
                rcCfmMipStatsLinktraceReceived		Counter64,
                rcCfmMipStatsLinktraceReplied		Counter64
       }

rcCfmMipStatsDomainIndex OBJECT-TYPE
	SYNTAX		Integer32 (1..2147483647)
	MAX-ACCESS	not-accessible
	STATUS		current
	DESCRIPTION	"Maintenance Domain Name"
	::= { rcCfmMipStatsEntry 1}

rcCfmMipStatsDomainName OBJECT-TYPE
	SYNTAX		DisplayString(SIZE (22))
	MAX-ACCESS	read-only
	STATUS		current
	DESCRIPTION	"Maintenance Domain Name"
	::= { rcCfmMipStatsEntry 2}

rcCfmMipStatsMipId OBJECT-TYPE
	SYNTAX		Integer32 (1..8191)
	MAX-ACCESS	not-accessible
	STATUS		current
	DESCRIPTION	"Maintenance Intermediate Point ID"
	::= { rcCfmMipStatsEntry 3}

rcCfmMipStatsLoopbackReceived  OBJECT-TYPE
        SYNTAX         Counter64
        MAX-ACCESS     read-only
        STATUS         current
        DESCRIPTION    "The total Number of CFM loopback messages received."
        ::= { rcCfmMipStatsEntry 4 }

rcCfmMipStatsLoopbackReplied  OBJECT-TYPE
        SYNTAX         Counter64
        MAX-ACCESS     read-only
        STATUS         current
        DESCRIPTION    "The total Number of CFM loopback messages replied."
        ::= { rcCfmMipStatsEntry 5 }

rcCfmMipStatsLinktraceReceived  OBJECT-TYPE
        SYNTAX         Counter64
        MAX-ACCESS     read-only
        STATUS         current
        DESCRIPTION    "The total Number of CFM linktrace messages received."
        ::= { rcCfmMipStatsEntry 6 }

rcCfmMipStatsLinktraceReplied  OBJECT-TYPE
        SYNTAX         Counter64
        MAX-ACCESS     read-only
        STATUS         current
        DESCRIPTION    "The total Number of CFM linktrace messages replied."
        ::= { rcCfmMipStatsEntry 7 }
-- The Transmit Loopback Table

rcCfmTransmitLbmTable OBJECT-TYPE
	SYNTAX		SEQUENCE OF RcCfmTransmitLbmEntry
	MAX-ACCESS	not-accessible
	STATUS		current
	DESCRIPTION	"Connectivity Fault Management transmit LBM table"
	::= { rcCfm 17}

rcCfmTransmitLbmEntry OBJECT-TYPE
	SYNTAX		RcCfmTransmitLbmEntry
	MAX-ACCESS	not-accessible
	STATUS		current
	DESCRIPTION	"Connectivity Fault Management Maintenance EndPoint LBM entry."
	INDEX		{rcCfmTransmitLbmDomainIndex, rcCfmTransmitLbmAssociationIndex, rcCfmTransmitLbmIndex }
	::= { rcCfmTransmitLbmTable 1}

RcCfmTransmitLbmEntry ::=
	SEQUENCE {
		rcCfmTransmitLbmDomainIndex		Integer32,
                rcCfmTransmitLbmAssociationIndex	Integer32,
		rcCfmTransmitLbmIndex			Integer32,
                rcCfmTransmitLbmDomainName		DisplayString,
                rcCfmTransmitLbmAssociationName		DisplayString,
		rcCfmTransmitLbmDestMacAddress		MacAddress,
		rcCfmTransmitLbmDestMepId		Integer32,
		rcCfmTransmitLbmDestIsMepId		TruthValue,
		rcCfmTransmitLbmMessages		Integer32,
		rcCfmTransmitLbmVlanPriority		Integer32,
		rcCfmTransmitLbmVlanDropEnable		TruthValue,
		rcCfmTransmitLbmSeqNumber		Integer32,
		rcCfmTransmitLbmResultOk		TruthValue,
		rcCfmTransmitLbmStatus			INTEGER,
		rcCfmTransmitLbmResult                  OCTET STRING,
                rcCfmTransmitLbmMode                    INTEGER,
                rcCfmTransmitLbmTimeoutInt              Integer32,
                rcCfmTransmitLbmInterFrameInt           Integer32,
                rcCfmTransmitLbmTestPattern             INTEGER,
		rcCfmTransmitLbmDataSize	        Integer32,
		rcCfmTransmitLbmFrameSize           	Integer32,
	        rcCfmTransmitLbmSourceMode              INTEGER
	}

rcCfmTransmitLbmDomainIndex OBJECT-TYPE
	SYNTAX		Integer32 (1..2147483647)
	MAX-ACCESS	not-accessible
	STATUS		current
	DESCRIPTION	"Maintenance Domain Name"
	::= { rcCfmTransmitLbmEntry 1}

rcCfmTransmitLbmAssociationIndex OBJECT-TYPE
	SYNTAX		Integer32 (1..2147483647)
	MAX-ACCESS	not-accessible
	STATUS		current
	DESCRIPTION	"Maintenance Association Name"
	::= { rcCfmTransmitLbmEntry 2}

rcCfmTransmitLbmIndex OBJECT-TYPE
	SYNTAX		Integer32 (1..8191)
	MAX-ACCESS	not-accessible
	STATUS		current
	DESCRIPTION	"Maintenance EndPoint Index"
	::= { rcCfmTransmitLbmEntry 3}

rcCfmTransmitLbmDomainName OBJECT-TYPE
	SYNTAX		DisplayString(SIZE (1..22))
	MAX-ACCESS	read-only
	STATUS		current
	DESCRIPTION	"Maintenance Domain Name"
	::= { rcCfmTransmitLbmEntry 4}

rcCfmTransmitLbmAssociationName OBJECT-TYPE
	SYNTAX		DisplayString(SIZE (1..22))
	MAX-ACCESS	read-only
	STATUS		current
	DESCRIPTION	"Maintenance Association Name"
	::= { rcCfmTransmitLbmEntry 5}

rcCfmTransmitLbmDestMacAddress OBJECT-TYPE
	SYNTAX 		MacAddress
	MAX-ACCESS	read-write
	STATUS		current
	DESCRIPTION	"An indication of the target MAC Address Field to 
			be transmitted, either:
			A unicast destination MAC address."
	::= { rcCfmTransmitLbmEntry 6}

rcCfmTransmitLbmDestMepId OBJECT-TYPE
	SYNTAX 		Integer32 (0..8191)
	MAX-ACCESS	read-write
	STATUS		current
	DESCRIPTION	"An indication of the target MAC Address Field to 
			be transmitted, either:
			The Maintenance Assiciation End Point identifier of 
			another MEP in the same Maintenance Association"
	::= { rcCfmTransmitLbmEntry 7}

rcCfmTransmitLbmDestIsMepId OBJECT-TYPE
	SYNTAX 		TruthValue
	MAX-ACCESS	read-write
	STATUS		current
	DESCRIPTION	"True indicates that MepId of the target MEP is used
			for Loopback transmission.
			False indicates that unicast destination MAC address 
			of the target MEP is used for Loopback transmission."
	::= { rcCfmTransmitLbmEntry 8}

rcCfmTransmitLbmMessages  OBJECT-TYPE
	SYNTAX  	Integer32(1..10000)
	MAX-ACCESS	read-write
	STATUS		current
	DESCRIPTION	"The number of loopback messages to be transmitted."
	DEFVAL {1}
	::= { rcCfmTransmitLbmEntry 9}

rcCfmTransmitLbmVlanPriority OBJECT-TYPE
	SYNTAX  	Integer32(0..7)
	MAX-ACCESS	read-write
	STATUS		current
	DESCRIPTION	"Priority. 3 bit value to be used in the VLAN tsg, if present in 
			the transmitted frame."
	DEFVAL {7}
	::= { rcCfmTransmitLbmEntry 11}

rcCfmTransmitLbmVlanDropEnable OBJECT-TYPE
	SYNTAX  	TruthValue
	MAX-ACCESS	read-write
	STATUS		current
	DESCRIPTION	"Drop Enable bit value to be used in the VLAN tag, if present in 
			the transmitted frame."
	DEFVAL {false}
	::= { rcCfmTransmitLbmEntry 12}

rcCfmTransmitLbmSeqNumber OBJECT-TYPE
	SYNTAX 		Integer32
	MAX-ACCESS	read-only
	STATUS		current
	DESCRIPTION	"The transaction identifier/sequence number of the first loopback 
			message (to be) sent."
	DEFVAL {0}
	::= { rcCfmTransmitLbmEntry 13}		

rcCfmTransmitLbmResultOk OBJECT-TYPE
	SYNTAX 		TruthValue
	MAX-ACCESS	read-only
	STATUS		current
	DESCRIPTION	"Indicates the result of the operation:
			-true.      The Loopback Message(s) will be (or have been) sent.
			-false.   The Loopback Message(s) will not be sent."
	DEFVAL {true}
	::= { rcCfmTransmitLbmEntry 14}
	 
rcCfmTransmitLbmStatus 	OBJECT-TYPE
	SYNTAX 		INTEGER {
				ready(1),
				transmit(2),
                                                                                abort(3)
			}
	MAX-ACCESS	read-write
	STATUS		current
	DESCRIPTION	"Status of the transmit loopback service:
			-ready.      The service is available.


			-transmit.   The service is transmitting, or about to transmit, 
				     the Loopback messages.
                                                            
                                                            -abort       The service is aborted or about to abort the Loopback messages.                   
			This column will also be used to avoid concurrency or race condition 
			problems that could occur if two or more management entities try to 
			use the service at the sane time. "
	REFERENCE       "Delete notReady status due to CR Q01482201"
	DEFVAL {ready}
	::= { rcCfmTransmitLbmEntry 15}

rcCfmTransmitLbmResult  OBJECT-TYPE
	SYNTAX 		OCTET STRING (SIZE (1..799))
	MAX-ACCESS	read-only
	STATUS		current
	DESCRIPTION	"Display the LBM result."
	::= { rcCfmTransmitLbmEntry 16}
	 
rcCfmTransmitLbmMode  OBJECT-TYPE
        SYNTAX        INTEGER {
                              throughput(1),
                              roundTripTime(2)
                      }
        MAX-ACCESS      read-write
        STATUS          current
        DESCRIPTION     "Modes of the transmit loopback service:

                        throughput:  The throughput mode of operation. 
                        LBM Frame will be sent out at the configured transmit 
                        interval rate for the burst-count number.

                        roundTripTime: The RoundTripTime mode of operation. 
                        LBM Frame will be sent out one at a time and the 
                        transmit time will be recorded locally. "
        DEFVAL {throughput}
        ::= { rcCfmTransmitLbmEntry 17}

rcCfmTransmitLbmTimeoutInt  OBJECT-TYPE
        SYNTAX          Integer32(1..10)
        MAX-ACCESS      read-write
        STATUS          current
        DESCRIPTION    "The interval to wait for an LBM time-out with a 
                       range of (1..10)  seconds with a default value of 3 
                       seconds."
        DEFVAL {3}
        ::= { rcCfmTransmitLbmEntry 18}

rcCfmTransmitLbmInterFrameInt  OBJECT-TYPE
        SYNTAX          Integer32(0..1000)
        MAX-ACCESS      read-write
        STATUS          current
        DESCRIPTION     "The interval between LBM frames with a range of 
                        (0..1000) msecs with a default value of 500 msecs.
                        The value of 0 msecs indicates to send the frames as 
                        fast as possible."
        DEFVAL {500}
        ::= { rcCfmTransmitLbmEntry 19}

rcCfmTransmitLbmTestPattern OBJECT-TYPE
        SYNTAX          INTEGER {
                               allZero(1),
                               allZeroCrc(2),
                               pseudoRandomBitSequence(3),
                               pseudoRandomBitSequenceCrc(4)
                        }
        MAX-ACCESS      read-write
        STATUS          current
        DESCRIPTION     "The test pattern to use in the LBM PDU with range of 
                        values namely allZero, allZeroCrc, 
                        pseudoRandomBitSequence and pseudoRandomBitSequenceCrc 
                        and with a default value of allZero.
                        value                  meaning
                        --------               -------
                        allZero(0)             Null signal without CRC-32
                        allZeroCrc(1)          Null signal with CRC-32    
                        pseudoRandomBitSequence(2) PRBS 1/2^31-1 without CRC-32
                        pseudoRandomBitSequenceCrc(3) PBRS 1/2^31-1 with CRC-32"
        DEFVAL {allZero}
        ::= { rcCfmTransmitLbmEntry 20}

rcCfmTransmitLbmDataSize  OBJECT-TYPE
	SYNTAX  	Integer32(0..400)
	MAX-ACCESS	read-write
	STATUS		current
	DESCRIPTION	"An arbitrary amount of data to be included in the data TLV, if the
			Data Size is selected to be sent."
	DEFVAL {0}
	::= { rcCfmTransmitLbmEntry 21}

rcCfmTransmitLbmFrameSize  OBJECT-TYPE
	SYNTAX  	Integer32(0..9600)
	MAX-ACCESS	read-write
	STATUS		current
	DESCRIPTION	"If the frame size is specified then the data size
                         shall be internally calculated and the calculated
                         data size shall be included in the data TLV."
	DEFVAL {0}
	::= { rcCfmTransmitLbmEntry 22}

rcCfmTransmitLbmSourceMode  OBJECT-TYPE
        SYNTAX        INTEGER {
			      nodal(1),
			      smltVirtual(2),
                              noVlanMac(3)             
                      }
        MAX-ACCESS      read-write
        STATUS          current
        DESCRIPTION     "Source modes of the transmit loopback service. "
        DEFVAL {nodal}
        ::= { rcCfmTransmitLbmEntry 23}

-- The Transmit Linktrace Table

rcCfmTransmitLtmTable OBJECT-TYPE
	SYNTAX		SEQUENCE OF RcCfmTransmitLtmEntry
	MAX-ACCESS	not-accessible
	STATUS		current
	DESCRIPTION	"Connectivity Fault Management transmit LBM table"
	::= { rcCfm 18}

rcCfmTransmitLtmEntry OBJECT-TYPE
	SYNTAX		RcCfmTransmitLtmEntry
	MAX-ACCESS	not-accessible
	STATUS		current
	DESCRIPTION	"Connectivity Fault Management Maintenance EndPoint LTM entry."
	INDEX		{rcCfmTransmitLtmDomainIndex, rcCfmTransmitLtmAssociationIndex, rcCfmTransmitLtmIndex }
	::= { rcCfmTransmitLtmTable 1}

RcCfmTransmitLtmEntry ::=
	SEQUENCE {
		rcCfmTransmitLtmDomainIndex		Integer32,
                rcCfmTransmitLtmAssociationIndex	Integer32,
		rcCfmTransmitLtmIndex			Integer32,
                rcCfmTransmitLtmDomainName		DisplayString,
                rcCfmTransmitLtmAssociationName		DisplayString,
		rcCfmTransmitLtmVlanPriority		Integer32,
		rcCfmTransmitLtmDestMacAddress		MacAddress,
		rcCfmTransmitLtmDestMepId		Integer32,
		rcCfmTransmitLtmDestIsMepId		TruthValue,
		rcCfmTransmitLtmTtl 			Integer32,
		rcCfmTransmitLtmSeqNumber		Integer32,
		rcCfmTransmitLtmResultOk		TruthValue,
		rcCfmTransmitLtmStatus			INTEGER,
		rcCfmTransmitLtmResult                  OCTET STRING,
		rcCfmTransmitLtmFlag                    INTEGER,
		rcCfmTransmitLtmSourceMode              INTEGER
	}

rcCfmTransmitLtmDomainIndex OBJECT-TYPE
	SYNTAX		Integer32 (1..2147483647)
	MAX-ACCESS	not-accessible
	STATUS		current
	DESCRIPTION	"Maintenance Domain Name"
	::= { rcCfmTransmitLtmEntry 1}

rcCfmTransmitLtmAssociationIndex OBJECT-TYPE
	SYNTAX		Integer32 (1..2147483647)
	MAX-ACCESS	not-accessible
	STATUS		current
	DESCRIPTION	"Maintenance Association Name"
	::= { rcCfmTransmitLtmEntry 2}

rcCfmTransmitLtmIndex OBJECT-TYPE
	SYNTAX		Integer32 (1..8191)
	MAX-ACCESS	not-accessible
	STATUS		current
	DESCRIPTION	"Maintenance EndPoint Index"
	::= { rcCfmTransmitLtmEntry 3}

rcCfmTransmitLtmDomainName OBJECT-TYPE
	SYNTAX		DisplayString(SIZE (1..22))
	MAX-ACCESS	read-only
	STATUS		current
	DESCRIPTION	"Maintenance Domain Name"
	::= { rcCfmTransmitLtmEntry 4}

rcCfmTransmitLtmAssociationName OBJECT-TYPE
	SYNTAX		DisplayString(SIZE (1..22))
	MAX-ACCESS	read-only
	STATUS		current
	DESCRIPTION	"Maintenance Association Name"
	::= { rcCfmTransmitLtmEntry 5}

rcCfmTransmitLtmVlanPriority OBJECT-TYPE
        SYNTAX          Integer32(0..7)
        MAX-ACCESS      read-write
        STATUS          current
        DESCRIPTION     "Priority. 3 bit value to be used in the VLAN tag, if present in
                        the transmitted frame."
        DEFVAL {7}
	::= { rcCfmTransmitLtmEntry 6}

rcCfmTransmitLtmDestMacAddress OBJECT-TYPE
	SYNTAX 		MacAddress
	MAX-ACCESS	read-write
	STATUS		current
	DESCRIPTION	"An indication of the target MAC Address Field to 
			be transmitted, either:
			A unicast destination MAC address."
	::= { rcCfmTransmitLtmEntry 7}

rcCfmTransmitLtmDestMepId OBJECT-TYPE
	SYNTAX 		Integer32 (0..8191)
	MAX-ACCESS	read-write
	STATUS		current
	DESCRIPTION	"An indication of the target MAC Address Field to 
			be transmitted, either:
			The Maintenance Assiciation End Point identifier of 
			another MEP in the same Maintenance Association"
	::= { rcCfmTransmitLtmEntry 8}

rcCfmTransmitLtmDestIsMepId OBJECT-TYPE
	SYNTAX 		TruthValue
	MAX-ACCESS	read-write
	STATUS		current
	DESCRIPTION	"True indicates that MepId of the target MEP is used
			for Loopback transmission.
			False indicates that unicast destination MAC address 
			of the target MEP is used for Loopback transmission."
	::= { rcCfmTransmitLtmEntry 9}

rcCfmTransmitLtmTtl     OBJECT-TYPE
	SYNTAX  	Integer32(0..255)
	MAX-ACCESS	read-write
	STATUS		current
	DESCRIPTION	"The number of hops remaining to this LTM. 
			 Decremented by 1 by each Bridge that handles the LTM. 
			 The decremented value is returned in the LTR. If 0 
                         on output, the LTM is not transmitted to the next 
                         hop. The value of the TTL Field in the LTM 
                         transmitted by the originating MEP is controlled by a 
                         Managed Object; The default value if none is 
                         specified is 64."
	DEFVAL {64}
	::= { rcCfmTransmitLtmEntry 10}

rcCfmTransmitLtmSeqNumber OBJECT-TYPE
	SYNTAX 		Integer32
	MAX-ACCESS	read-only
	STATUS		current
	DESCRIPTION	"The transaction identifier/sequence number of the first loopback 
			message (to be) sent."
	DEFVAL {0}
	::= { rcCfmTransmitLtmEntry 11}		

rcCfmTransmitLtmResultOk OBJECT-TYPE
	SYNTAX 		TruthValue
	MAX-ACCESS	read-only
	STATUS		current
	DESCRIPTION	"Indicates the result of the operation:
			-true.      The Loopback Message(s) will be (or have been) sent.
			-false.   The Loopback Message(s) will not be sent."
	DEFVAL {true}
	::= { rcCfmTransmitLtmEntry 12}
	 
rcCfmTransmitLtmStatus 	OBJECT-TYPE
	SYNTAX 		INTEGER {
				ready(1),
				transmit(2),
				abort(3)

			}
	MAX-ACCESS	read-write
	STATUS		current
	DESCRIPTION	"Status of the transmit loopback service:
			-ready.      The service is available.


			-transmit.   The service is transmitting, or about to transmit, 
				     the Loopback messages.
				     
			-abort.      The service is aborted, or about to abort the LTM message
	     
			This column will also be used to avoid concurrency or race condition 
			problems that could occur if two or more management entities try to 
			use the service at the sane time. "
	REFERENCE       "Delete notReady status due to CR Q01482201"
	DEFVAL {ready}
	::= { rcCfmTransmitLtmEntry 13}

rcCfmTransmitLtmResult  OBJECT-TYPE
	SYNTAX 		OCTET STRING(SIZE (1..1023))
	MAX-ACCESS	read-only
	STATUS		obsolete
	DESCRIPTION	"Display the LTM result."
	::= { rcCfmTransmitLtmEntry 14}

rcCfmTransmitLtmFlag    OBJECT-TYPE
	SYNTAX 		INTEGER {
	                        none(1),
				internalError(2),
                                noRemoteMep(3),
                                invalidRemoteMepMac(4),
                                noRemoteMepMacLearned(5),
                                mepDisabled(6), 
                                noLtrResponse(7),
                                ltmToOwnMepMac(8),
                                epDisabled(9),
                                trunkDisabled(10),
                                ltmComplete(11),
				ltmLeafNode(12) 
			}
	MAX-ACCESS	read-only
	STATUS	        current 	
	DESCRIPTION	"LTM result flag indicating LTM status or error code. 
                         Each enum value represents a status or error case.  
                         1 - No error  
                         2 - Ltm Internal Error
                         3 - Unknown Remote Maintenance End Point
                         4 - Invalid Remote Maintenance End Point Mac Address
                         5 - Unset Remote Maintenance End Point Mac Address
                         6 - Mep must be enabled in order to perform LTM
                         7 - No Ltr response received
                         8 - Linktrace to own Mep MAC is not sent
                         9 - Endpoint must be enabled in order to perform LTM
                         10 - Pbt-trunk must be enabled in order to perform LTM
                         11 - LTM completed
			 12 - LTM leaf node"
	::= { rcCfmTransmitLtmEntry 15}

rcCfmTransmitLtmSourceMode  OBJECT-TYPE
        SYNTAX        INTEGER {
			      nodal(1),
			      smltVirtual(2),
                              noVlanMac(3)             
                      }
        MAX-ACCESS      read-write
        STATUS          current
        DESCRIPTION     "Source modes of the transmit linktrace service. "
        DEFVAL {nodal}
        ::= {rcCfmTransmitLtmEntry 16 }

 rcCfmPbtTrunkStatsTable OBJECT-TYPE
	SYNTAX        SEQUENCE OF RcCfmPbtTrunkStatsEntry
	MAX-ACCESS    not-accessible
	STATUS        current
	DESCRIPTION   "Table of PBT trunk statistics."
	::= { rcCfm 19 }

rcCfmPbtTrunkStatsEntry OBJECT-TYPE
	SYNTAX        RcCfmPbtTrunkStatsEntry
	MAX-ACCESS    not-accessible
	STATUS        current
	DESCRIPTION   "A PBT Trunk Statistics table entry."
	INDEX         {  rcCfmPbtTrunkStatsName }
	::= { rcCfmPbtTrunkStatsTable 1 }
 
RcCfmPbtTrunkStatsEntry ::=
	SEQUENCE {

		rcCfmPbtTrunkStatsName		CfmNameString,
                rcCfmPbtTrunkStatsPort		InterfaceIndex,
                rcCfmPbtTrunkStatsDA		MacAddress,
		rcCfmPbtTrunkStatsVlanId	Integer32,
                rcCfmPbtTrunkStatsRevVlanId	Integer32,
                rcCfmPbtTrunkStatsSA	        MacAddress,
		rcCfmPbtTrunkStatsRxOctets	Counter64,
		rcCfmPbtTrunkStatsRxFrames	Counter64,  	
		rcCfmPbtTrunkStatsTxOctets      Counter64, 
		rcCfmPbtTrunkStatsTxFrames      Counter64, 
		rcCfmPbtTrunkStatsRxPbit0Octets Counter64,
		rcCfmPbtTrunkStatsRxPbit0Frames Counter64,
		rcCfmPbtTrunkStatsRxPbit1Octets Counter64,
		rcCfmPbtTrunkStatsRxPbit1Frames Counter64,
		rcCfmPbtTrunkStatsRxPbit2Octets Counter64,
		rcCfmPbtTrunkStatsRxPbit2Frames Counter64,
		rcCfmPbtTrunkStatsRxPbit3Octets Counter64,
		rcCfmPbtTrunkStatsRxPbit3Frames Counter64,
		rcCfmPbtTrunkStatsRxPbit4Octets Counter64,
		rcCfmPbtTrunkStatsRxPbit4Frames Counter64,
		rcCfmPbtTrunkStatsRxPbit5Octets Counter64,
		rcCfmPbtTrunkStatsRxPbit5Frames Counter64,
		rcCfmPbtTrunkStatsRxPbit6Octets Counter64,
		rcCfmPbtTrunkStatsRxPbit6Frames Counter64,
		rcCfmPbtTrunkStatsRxPbit7Octets Counter64,
		rcCfmPbtTrunkStatsRxPbit7Frames Counter64,
		rcCfmPbtTrunkStatsTxPbit0Octets Counter64,
		rcCfmPbtTrunkStatsTxPbit0Frames Counter64,
		rcCfmPbtTrunkStatsTxPbit1Octets Counter64,
		rcCfmPbtTrunkStatsTxPbit1Frames Counter64,
		rcCfmPbtTrunkStatsTxPbit2Octets Counter64,
		rcCfmPbtTrunkStatsTxPbit2Frames Counter64,
		rcCfmPbtTrunkStatsTxPbit3Octets Counter64,
		rcCfmPbtTrunkStatsTxPbit3Frames Counter64,
		rcCfmPbtTrunkStatsTxPbit4Octets Counter64,
		rcCfmPbtTrunkStatsTxPbit4Frames Counter64,
		rcCfmPbtTrunkStatsTxPbit5Octets Counter64,
		rcCfmPbtTrunkStatsTxPbit5Frames Counter64,
		rcCfmPbtTrunkStatsTxPbit6Octets Counter64,
		rcCfmPbtTrunkStatsTxPbit6Frames Counter64,
		rcCfmPbtTrunkStatsTxPbit7Octets Counter64,
		rcCfmPbtTrunkStatsTxPbit7Frames Counter64
		}
rcCfmPbtTrunkStatsName OBJECT-TYPE
	SYNTAX		CfmNameString
	MAX-ACCESS	not-accessible
	STATUS		current
	DESCRIPTION	"PBT Trunk Name."
	::= { rcCfmPbtTrunkStatsEntry 1 }
 
rcCfmPbtTrunkStatsPort OBJECT-TYPE
	SYNTAX		InterfaceIndex
	MAX-ACCESS	read-only
	STATUS		current
	DESCRIPTION	"PBT Trunk Port"
	::= { rcCfmPbtTrunkStatsEntry 2}

rcCfmPbtTrunkStatsDA OBJECT-TYPE
	SYNTAX		MacAddress
	MAX-ACCESS	read-only
	STATUS		current
	DESCRIPTION	"Trunk Mac (remote CP mac)"
	::= { rcCfmPbtTrunkStatsEntry 3}


rcCfmPbtTrunkStatsVlanId OBJECT-TYPE
	SYNTAX		Integer32 (0..4095)
	MAX-ACCESS	read-only
	STATUS		current
	DESCRIPTION	"PBT trunk VLAN ID"
	::= { rcCfmPbtTrunkStatsEntry 4}

rcCfmPbtTrunkStatsRevVlanId OBJECT-TYPE
	SYNTAX		Integer32 (0..4095)
	MAX-ACCESS	read-only
	STATUS		current
	DESCRIPTION	"PBT trunk reverse VLAN ID"
	::= { rcCfmPbtTrunkStatsEntry 5}


rcCfmPbtTrunkStatsSA OBJECT-TYPE
	SYNTAX		MacAddress
	MAX-ACCESS	read-only
	STATUS		current
	DESCRIPTION	"Trunk Source Mac (local switch PBT mac)"
	::= { rcCfmPbtTrunkStatsEntry 6}

 
rcCfmPbtTrunkStatsRxOctets	OBJECT-TYPE
	SYNTAX		Counter64
	MAX-ACCESS	read-only
	STATUS		current
	DESCRIPTION	" Number of Octets received by the trunk.This does not include
			  trunk CCM messag (control) packets."
	::= { rcCfmPbtTrunkStatsEntry 7 }

rcCfmPbtTrunkStatsRxFrames	OBJECT-TYPE
	SYNTAX		Counter64
	MAX-ACCESS	read-only
	STATUS		current
	DESCRIPTION	" Number of Packets received by the trunk.This does not include
			  trunk CCM messag (control) packets."
	::= { rcCfmPbtTrunkStatsEntry 8 }

rcCfmPbtTrunkStatsTxOctets	OBJECT-TYPE
	SYNTAX		Counter64
	MAX-ACCESS	read-only
	STATUS		current
	DESCRIPTION	" Number of Octets transmitted by the trunk.This does not include
			  trunk CCM messag (control) packets."
	::= { rcCfmPbtTrunkStatsEntry 9 }

rcCfmPbtTrunkStatsTxFrames	OBJECT-TYPE
	SYNTAX		Counter64
	MAX-ACCESS	read-only
	STATUS		current
	DESCRIPTION	" Number of Packets transmitted  by the trunk.This does not include
			  trunk CCM messag (control) packets."
	::= { rcCfmPbtTrunkStatsEntry 10 }
	
rcCfmPbtTrunkStatsRxPbit0Octets 	OBJECT-TYPE
	SYNTAX		Counter64
	MAX-ACCESS	read-only
	STATUS		current
	DESCRIPTION	" Number of Pbit 0  Octets received by the trunk."
	::= { rcCfmPbtTrunkStatsEntry 11 }

rcCfmPbtTrunkStatsRxPbit0Frames 	OBJECT-TYPE
	SYNTAX		Counter64
	MAX-ACCESS	read-only
	STATUS		current
	DESCRIPTION	" Number of P-Bit 0 Packets received by the trunk."
	::= { rcCfmPbtTrunkStatsEntry 12 }

rcCfmPbtTrunkStatsRxPbit1Octets 	OBJECT-TYPE
	SYNTAX		Counter64
	MAX-ACCESS	read-only
	STATUS		current
	DESCRIPTION	" Number of Pbit 1  Octets received by the trunk."
	::= { rcCfmPbtTrunkStatsEntry 13 }

rcCfmPbtTrunkStatsRxPbit1Frames 	OBJECT-TYPE
	SYNTAX		Counter64
	MAX-ACCESS	read-only
	STATUS		current
	DESCRIPTION	" Number of P-Bit 1 Packets received by the trunk."
	::= { rcCfmPbtTrunkStatsEntry 14 }

rcCfmPbtTrunkStatsRxPbit2Octets 	OBJECT-TYPE
	SYNTAX		Counter64
	MAX-ACCESS	read-only
	STATUS		current
	DESCRIPTION	" Number of Pbit 2  Octets received by the trunk."
	::= { rcCfmPbtTrunkStatsEntry 15 }

rcCfmPbtTrunkStatsRxPbit2Frames 	OBJECT-TYPE
	SYNTAX		Counter64
	MAX-ACCESS	read-only
	STATUS		current
	DESCRIPTION	" Number of P-Bit 2 Packets received by the trunk."
	::= { rcCfmPbtTrunkStatsEntry  16 }

rcCfmPbtTrunkStatsRxPbit3Octets 	OBJECT-TYPE
	SYNTAX		Counter64
	MAX-ACCESS	read-only
	STATUS		current
	DESCRIPTION	" Number of Pbit 3  Octets received by the trunk."
	::= { rcCfmPbtTrunkStatsEntry 17 }

rcCfmPbtTrunkStatsRxPbit3Frames 	OBJECT-TYPE
	SYNTAX		Counter64
	MAX-ACCESS	read-only
	STATUS		current
	DESCRIPTION	" Number of P-Bit 3 Packets received by the trunk."
	::= { rcCfmPbtTrunkStatsEntry 18 }

rcCfmPbtTrunkStatsRxPbit4Octets 	OBJECT-TYPE
	SYNTAX		Counter64
	MAX-ACCESS	read-only
	STATUS		current
	DESCRIPTION	" Number of Pbit 4  Octets received by the trunk."
	::= { rcCfmPbtTrunkStatsEntry 19 }

rcCfmPbtTrunkStatsRxPbit4Frames		OBJECT-TYPE
	SYNTAX		Counter64
	MAX-ACCESS	read-only
	STATUS		current
	DESCRIPTION	" Number of P-Bit 4 Packets received by the trunk."
	::= { rcCfmPbtTrunkStatsEntry 20 }

rcCfmPbtTrunkStatsRxPbit5Octets 	OBJECT-TYPE
	SYNTAX		Counter64
	MAX-ACCESS	read-only
	STATUS		current
	DESCRIPTION	" Number of Pbit 5  Octets received by the trunk."
	::= { rcCfmPbtTrunkStatsEntry 21 }

rcCfmPbtTrunkStatsRxPbit5Frames 	OBJECT-TYPE
	SYNTAX		Counter64
	MAX-ACCESS	read-only
	STATUS		current
	DESCRIPTION	" Number of P-Bit 5 Packets received by the trunk."
	::= { rcCfmPbtTrunkStatsEntry 22 }

rcCfmPbtTrunkStatsRxPbit6Octets 	OBJECT-TYPE
	SYNTAX		Counter64
	MAX-ACCESS	read-only
	STATUS		current
	DESCRIPTION	" Number of Pbit64  Octets received by the trunk."
	::= { rcCfmPbtTrunkStatsEntry 23 }

rcCfmPbtTrunkStatsRxPbit6Frames 	OBJECT-TYPE
	SYNTAX		Counter64
	MAX-ACCESS	read-only
	STATUS		current
	DESCRIPTION	" Number of P-Bit 6 Packets received by the trunk."
	::= { rcCfmPbtTrunkStatsEntry 24 }

rcCfmPbtTrunkStatsRxPbit7Octets 	OBJECT-TYPE
	SYNTAX		Counter64
	MAX-ACCESS	read-only
	STATUS		current
	DESCRIPTION	" Number of Pbit64  Octets received by the trunk."
	::= { rcCfmPbtTrunkStatsEntry 25 }

rcCfmPbtTrunkStatsRxPbit7Frames 	OBJECT-TYPE
	SYNTAX		Counter64
	MAX-ACCESS	read-only
	STATUS		current
	DESCRIPTION	" Number of P-Bit 6 Packets received by the trunk."
	::= { rcCfmPbtTrunkStatsEntry 26 }

	
rcCfmPbtTrunkStatsTxPbit0Octets 	OBJECT-TYPE
	SYNTAX		Counter64
	MAX-ACCESS	read-only
	STATUS		current
	DESCRIPTION	" Number of Pbit 0  Octets transmitted by the trunk."
	::= { rcCfmPbtTrunkStatsEntry 27 }

rcCfmPbtTrunkStatsTxPbit0Frames 	OBJECT-TYPE
	SYNTAX		Counter64
	MAX-ACCESS	read-only
	STATUS		current
	DESCRIPTION	" Number of P-Bit 0 Packets transmitted by the trunk."
	::= { rcCfmPbtTrunkStatsEntry 28 }

rcCfmPbtTrunkStatsTxPbit1Octets 	OBJECT-TYPE
	SYNTAX		Counter64
	MAX-ACCESS	read-only
	STATUS		current
	DESCRIPTION	" Number of Pbit 1  Octets transmitted by the trunk."
	::= { rcCfmPbtTrunkStatsEntry 29 }

rcCfmPbtTrunkStatsTxPbit1Frames 	OBJECT-TYPE
	SYNTAX		Counter64
	MAX-ACCESS	read-only
	STATUS		current
	DESCRIPTION	" Number of P-Bit 1 Packets transmitted by the trunk."
	::= { rcCfmPbtTrunkStatsEntry 30 }

rcCfmPbtTrunkStatsTxPbit2Octets 	OBJECT-TYPE
	SYNTAX		Counter64
	MAX-ACCESS	read-only
	STATUS		current
	DESCRIPTION	" Number of Pbit 2  Octets transmitted by the trunk."
	::= { rcCfmPbtTrunkStatsEntry 31 }

rcCfmPbtTrunkStatsTxPbit2Frames 	OBJECT-TYPE
	SYNTAX		Counter64
	MAX-ACCESS	read-only
	STATUS		current
	DESCRIPTION	" Number of P-Bit 2 Packets transmitted by the trunk."
	::= { rcCfmPbtTrunkStatsEntry 32 }

rcCfmPbtTrunkStatsTxPbit3Octets 	OBJECT-TYPE
	SYNTAX		Counter64
	MAX-ACCESS	read-only
	STATUS		current
	DESCRIPTION	" Number of Pbit 3  Octets transmitted by the trunk."
	::= { rcCfmPbtTrunkStatsEntry 33 }

rcCfmPbtTrunkStatsTxPbit3Frames 	OBJECT-TYPE
	SYNTAX		Counter64
	MAX-ACCESS	read-only
	STATUS		current
	DESCRIPTION	" Number of P-Bit 3 Packets transmitted by the trunk."
	::= { rcCfmPbtTrunkStatsEntry 34 }

rcCfmPbtTrunkStatsTxPbit4Octets 	OBJECT-TYPE
	SYNTAX		Counter64
	MAX-ACCESS	read-only
	STATUS		current
	DESCRIPTION	" Number of Pbit 4  Octets transmitted by the trunk."
	::= { rcCfmPbtTrunkStatsEntry 35 }

rcCfmPbtTrunkStatsTxPbit4Frames 	OBJECT-TYPE
	SYNTAX		Counter64
	MAX-ACCESS	read-only
	STATUS		current
	DESCRIPTION	" Number of P-Bit 4 Packets transmitted by the trunk."
	::= { rcCfmPbtTrunkStatsEntry 36 }

rcCfmPbtTrunkStatsTxPbit5Octets 	OBJECT-TYPE
	SYNTAX		Counter64
	MAX-ACCESS	read-only
	STATUS		current
	DESCRIPTION	" Number of Pbit 5  Octets transmitted by the trunk."
	::= { rcCfmPbtTrunkStatsEntry 37 }

rcCfmPbtTrunkStatsTxPbit5Frames 	OBJECT-TYPE
	SYNTAX		Counter64
	MAX-ACCESS	read-only
	STATUS		current
	DESCRIPTION	" Number of P-Bit 5 Packets transmitted by the trunk."
	::= { rcCfmPbtTrunkStatsEntry 38 }

rcCfmPbtTrunkStatsTxPbit6Octets 	OBJECT-TYPE
	SYNTAX		Counter64
	MAX-ACCESS	read-only
	STATUS		current
	DESCRIPTION	" Number of Pbit64  Octets transmitted by the trunk."
	::= { rcCfmPbtTrunkStatsEntry 39 }

rcCfmPbtTrunkStatsTxPbit6Frames 	OBJECT-TYPE
	SYNTAX		Counter64
	MAX-ACCESS	read-only
	STATUS		current
	DESCRIPTION	" Number of P-Bit 6 Packets transmitted by the trunk."
	::= { rcCfmPbtTrunkStatsEntry 40 }

rcCfmPbtTrunkStatsTxPbit7Octets 	OBJECT-TYPE
	SYNTAX		Counter64
	MAX-ACCESS	read-only
	STATUS		current
	DESCRIPTION	" Number of Pbit64  Octets transmitted by the trunk."
	::= { rcCfmPbtTrunkStatsEntry 41 }

rcCfmPbtTrunkStatsTxPbit7Frames 	OBJECT-TYPE
	SYNTAX		Counter64
	MAX-ACCESS	read-only
	STATUS		current
	DESCRIPTION	" Number of P-Bit 6 Packets transmitted by the trunk."
	::= { rcCfmPbtTrunkStatsEntry 42 }

-- CFM Port stats table
rcCfmPortStatsTable OBJECT-TYPE
        SYNTAX        SEQUENCE OF RcCfmPortStatsEntry
        MAX-ACCESS    not-accessible
        STATUS        current
        DESCRIPTION   "CFM Port stats table contains the 
		       port Tx and Rx CFM statistics"
	::= { rcCfm 20 }

rcCfmPortStatsEntry OBJECT-TYPE
        SYNTAX        RcCfmPortStatsEntry
        MAX-ACCESS    not-accessible
        STATUS        current
        DESCRIPTION   "CFM Port Stats table entry. Contain port's CFM Message
                      sending/receiving counter."
        INDEX         { rcCfmPortStatsIndex }
        ::= { rcCfmPortStatsTable 1 }
 
RcCfmPortStatsEntry ::= 
        SEQUENCE {
                rcCfmPortStatsIndex	        InterfaceIndex,
		rcCfmPortStatsTxCnt             Counter64,
                rcCfmPortStatsRxCnt		Counter64
                }
      
rcCfmPortStatsIndex OBJECT-TYPE
	SYNTAX		InterfaceIndex
	MAX-ACCESS	not-accessible
	STATUS		current
	DESCRIPTION	"Slot/Port index"
	::= { rcCfmPortStatsEntry 1}

rcCfmPortStatsTxCnt  OBJECT-TYPE
        SYNTAX         Counter64
        MAX-ACCESS     read-only
        STATUS         current
        DESCRIPTION    "The total Number of CFM messages that are 
                       sent by port"
        ::= { rcCfmPortStatsEntry 2 }

rcCfmPortStatsRxCnt  OBJECT-TYPE
        SYNTAX         Counter64
        MAX-ACCESS     read-only
        STATUS         current
        DESCRIPTION    "The total Number of CFM messages are 
                       received by port"
        ::= { rcCfmPortStatsEntry 3 }

-- Frame Loss Ratio Profile Table

rcCfmFlrTable OBJECT-TYPE
        SYNTAX          SEQUENCE OF RcCfmFlrEntry
        MAX-ACCESS      not-accessible
        STATUS          current
        DESCRIPTION     "Frame Loss Ratio Profile table"
        ::= { rcCfm 21 }

rcCfmFlrEntry OBJECT-TYPE
        SYNTAX          RcCfmFlrEntry
        MAX-ACCESS      not-accessible
        STATUS          current
        DESCRIPTION     "Frame Loss Ratio entry."
        INDEX           {rcCfmFlrIndex}
        ::= { rcCfmFlrTable 1}

RcCfmFlrEntry ::=
        SEQUENCE {
                rcCfmFlrIndex                       Integer32,
                rcCfmFlrProfileName                 DisplayString,
                rcCfmFlrRowStatus                   RowStatus,
                rcCfmFlrPriority                    Integer32,
                rcCfmFlrAlarmThresholdPercent       Integer32,
                rcCfmFlrAlarmThresholdSubPercent    Integer32,
                rcCfmFlrClearThresholdPercent       Integer32,
                rcCfmFlrClearThresholdSubPercent    Integer32,
                rcCfmFlrThresholdState              EnableValue,
                rcCfmFlrNumberOfRefs                Gauge32 
                }

rcCfmFlrIndex OBJECT-TYPE
        SYNTAX          Integer32 (1..1000)
        MAX-ACCESS      not-accessible
        STATUS          current
        DESCRIPTION     "Frame-Loss-Ratio profile index"
        ::= { rcCfmFlrEntry 1}

rcCfmFlrProfileName OBJECT-TYPE
        SYNTAX          DisplayString(SIZE (1..22))
        MAX-ACCESS      read-create
        STATUS          current
        DESCRIPTION     "Frame-Loss-Ratio Profile Name"
        ::= { rcCfmFlrEntry 2}

rcCfmFlrRowStatus OBJECT-TYPE
        SYNTAX          RowStatus
        MAX-ACCESS      read-create
        STATUS          current
        DESCRIPTION     "Used to create/delete entries"
        ::= { rcCfmFlrEntry 3}

rcCfmFlrPriority OBJECT-TYPE
        SYNTAX          Integer32 (0..7)
        MAX-ACCESS      read-create 
        STATUS          current
        DESCRIPTION     "Frame Loss Ratio messaging runs on COS priority"
        DEFVAL { 7 }
        ::= { rcCfmFlrEntry 4}

rcCfmFlrAlarmThresholdPercent OBJECT-TYPE
        SYNTAX          Integer32 (0..99)
        MAX-ACCESS      read-create 
        STATUS          current
        DESCRIPTION     "FLR set alarm threshold percentage"
        DEFVAL { 85 }
        ::= { rcCfmFlrEntry 5}

rcCfmFlrAlarmThresholdSubPercent OBJECT-TYPE
        SYNTAX          Integer32 (0..99)
        MAX-ACCESS      read-create 
        STATUS          current
        DESCRIPTION     "FLR set alarm threshold percentage in 1/100 percent increments"
        DEFVAL { 0 }
        ::= { rcCfmFlrEntry 6}

rcCfmFlrClearThresholdPercent OBJECT-TYPE
        SYNTAX          Integer32 (0..99)
        MAX-ACCESS      read-create 
        STATUS          current
        DESCRIPTION     "FLR clear alarm threshold percentage"
        DEFVAL { 0 }
        ::= { rcCfmFlrEntry 7}

rcCfmFlrClearThresholdSubPercent OBJECT-TYPE
        SYNTAX          Integer32 (0..99)
        MAX-ACCESS      read-create 
        STATUS          current
        DESCRIPTION     "FLR clear alarm threshold percentage in 1/100 percent increments"
        DEFVAL { 0 }
        ::= { rcCfmFlrEntry 8}

rcCfmFlrThresholdState OBJECT-TYPE
        SYNTAX        EnableValue
        MAX-ACCESS    read-create
        STATUS        current
        DESCRIPTION   "FLR threshold State"
        DEFVAL { disable }
        ::= { rcCfmFlrEntry 9}

rcCfmFlrNumberOfRefs OBJECT-TYPE
        SYNTAX          Gauge32 
        MAX-ACCESS      read-only 
        STATUS          current
        DESCRIPTION     "Number of PMs that reference this flr-profile"
        DEFVAL { 0 }
        ::= { rcCfmFlrEntry 10}

-- Frame Delay and Frame Delay Variation Profile Table

rcCfmFdTable OBJECT-TYPE
        SYNTAX          SEQUENCE OF RcCfmFdEntry
        MAX-ACCESS      not-accessible
        STATUS          current
        DESCRIPTION     "CFM Frame Delay and Frame Delay Variation Profile table
"
        ::= { rcCfm 22 }

rcCfmFdEntry OBJECT-TYPE
        SYNTAX          RcCfmFdEntry
        MAX-ACCESS      not-accessible
        STATUS          current
        DESCRIPTION     "Frame Delay and Frame Delay Variation entry."
        INDEX           {rcCfmFdIndex}
        ::= { rcCfmFdTable 1}

RcCfmFdEntry ::=
        SEQUENCE {
                rcCfmFdIndex                       Integer32,
                rcCfmFdProfileName                 DisplayString,
                rcCfmFdRowStatus                   RowStatus,
                rcCfmFdPriority                    Integer32,
                rcCfmFdPerformanceTarget           Integer32,
                rcCfmFdAlarmThresholdPercent       Integer32,
                rcCfmFdAlarmThresholdSubPercent    Integer32,
                rcCfmFdClearThresholdPercent       Integer32,
                rcCfmFdClearThresholdSubPercent    Integer32,
                rcCfmFdFdvPerformanceTarget        Integer32,
                rcCfmFdFdvAlarmThresholdPercent    Integer32,
                rcCfmFdFdvAlarmThresholdSubPercent Integer32,
                rcCfmFdFdvClearThresholdPercent    Integer32,
                rcCfmFdFdvClearThresholdSubPercent Integer32,
                rcCfmFdThresholdState              EnableValue,
                rcCfmFdNumberOfRefs                Gauge32 
                }

rcCfmFdIndex OBJECT-TYPE
        SYNTAX          Integer32 (1..1000)
        MAX-ACCESS      not-accessible
        STATUS          current
        DESCRIPTION     "Frame-Delay profile index"
        ::= { rcCfmFdEntry 1}

rcCfmFdProfileName OBJECT-TYPE
        SYNTAX          DisplayString(SIZE (1..22))
        MAX-ACCESS      read-create
        STATUS          current
        DESCRIPTION     "Frame-Delay Profile Name"
        ::= { rcCfmFdEntry 2}

rcCfmFdRowStatus OBJECT-TYPE
        SYNTAX          RowStatus
        MAX-ACCESS      read-create
        STATUS          current
        DESCRIPTION     "Used to create/delete entries"
        ::= { rcCfmFdEntry 3}

rcCfmFdPriority OBJECT-TYPE
        SYNTAX          Integer32 (0..7)
        MAX-ACCESS      read-create 
        STATUS          current
        DESCRIPTION     "Frame Delay messaging runs on COS priority"
        DEFVAL { 7 }
        ::= { rcCfmFdEntry 4}

rcCfmFdPerformanceTarget OBJECT-TYPE
        SYNTAX          Integer32 (1..10000000)
        MAX-ACCESS      read-create 
        STATUS          current
        DESCRIPTION     "Frame delay performance objective in microseconds"
        DEFVAL { 10000000 }
        ::= { rcCfmFdEntry 5}

rcCfmFdAlarmThresholdPercent OBJECT-TYPE
        SYNTAX          Integer32 (0..99)
        MAX-ACCESS      read-create 
        STATUS          current
        DESCRIPTION     "FD set alarm threshold percentage"
        DEFVAL { 85 }
        ::= { rcCfmFdEntry 6}

rcCfmFdAlarmThresholdSubPercent OBJECT-TYPE
        SYNTAX          Integer32 (0..99)
        MAX-ACCESS      read-create 
        STATUS          current
        DESCRIPTION     "FD set alarm threshold percentage in 1/100 percent incr
ements"
        DEFVAL { 0 }
        ::= { rcCfmFdEntry 7}

rcCfmFdClearThresholdPercent OBJECT-TYPE
        SYNTAX          Integer32 (0..99)
        MAX-ACCESS      read-create 
        STATUS          current
        DESCRIPTION     "FD clear alarm threshold percentage"
        DEFVAL { 0 }
        ::= { rcCfmFdEntry 8}

rcCfmFdClearThresholdSubPercent OBJECT-TYPE
        SYNTAX          Integer32 (0..99)
        MAX-ACCESS      read-create 
        STATUS          current
        DESCRIPTION     "FD clear alarm threshold percentage in 1/100 percent in
crements"
        DEFVAL { 0 }
        ::= { rcCfmFdEntry 9}

rcCfmFdFdvPerformanceTarget OBJECT-TYPE
        SYNTAX          Integer32 (1..10000000)
        MAX-ACCESS      read-create 
        STATUS          current
        DESCRIPTION     "Frame delay variation performance objective in microseconds"
        DEFVAL { 10000000 }
        ::= { rcCfmFdEntry 10}

rcCfmFdFdvAlarmThresholdPercent OBJECT-TYPE
        SYNTAX          Integer32 (0..99)
        MAX-ACCESS      read-create 
        STATUS          current
        DESCRIPTION     "FDV set alarm threshold percentage"
        DEFVAL { 85 }
        ::= { rcCfmFdEntry 11}

rcCfmFdFdvAlarmThresholdSubPercent OBJECT-TYPE
        SYNTAX          Integer32 (0..99)
        MAX-ACCESS      read-create 
        STATUS          current
        DESCRIPTION     "FDV set alarm threshold percentage in 1/100 percent inc
rements"
        DEFVAL { 0 }
        ::= { rcCfmFdEntry 12}

rcCfmFdFdvClearThresholdPercent OBJECT-TYPE
        SYNTAX          Integer32 (0..99)
        MAX-ACCESS      read-create 
        STATUS          current
        DESCRIPTION     "FDV clear alarm threshold percentage"
        DEFVAL { 0 }
        ::= { rcCfmFdEntry 13}

rcCfmFdFdvClearThresholdSubPercent OBJECT-TYPE
        SYNTAX          Integer32 (0..99)
        MAX-ACCESS      read-create 
        STATUS          current
        DESCRIPTION     "FDV clear alarm threshold percentage in 1/100 percent i
ncrements"
        DEFVAL { 0 }
        ::= { rcCfmFdEntry 14}

rcCfmFdThresholdState OBJECT-TYPE
        SYNTAX        EnableValue
        MAX-ACCESS    read-create
        STATUS        current
        DESCRIPTION   "FD / FDV threshold State"
        DEFVAL { disable }
        ::= { rcCfmFdEntry 15}

rcCfmFdNumberOfRefs OBJECT-TYPE
        SYNTAX          Gauge32 
        MAX-ACCESS      read-only 
        STATUS          current
        DESCRIPTION     "Number of PM's that referencen this fd-profile"
        DEFVAL { 0 }
        ::= { rcCfmFdEntry 16}

-- Frame Loss Ratio Stats Info Table

rcCfmFlrStatsInfoTable OBJECT-TYPE
        SYNTAX          SEQUENCE OF RcCfmFlrStatsInfoEntry
        MAX-ACCESS      not-accessible
        STATUS          current
        DESCRIPTION     "CFM Frame Loss Ratio Stats Info"
        ::= { rcCfm 23}

rcCfmFlrStatsInfoEntry OBJECT-TYPE
        SYNTAX          RcCfmFlrStatsInfoEntry
        MAX-ACCESS      not-accessible
        STATUS          current
        DESCRIPTION     "Frame Loss Ratio Stats Info entry."
        INDEX           { rcCfmFlrStatsInfoMdIndex,
                          rcCfmFlrStatsInfoMaIndex,
                          rcCfmFlrStatsInfoMepId,
                          rcCfmFlrStatsInfoRmepId,
                          rcCfmFlrStatsInfoPriorityIndex }
        ::= { rcCfmFlrStatsInfoTable 1}

RcCfmFlrStatsInfoEntry ::=
        SEQUENCE {
                rcCfmFlrStatsInfoMdIndex                Integer32,
                rcCfmFlrStatsInfoMaIndex                Integer32,
                rcCfmFlrStatsInfoMepId                  Integer32,
                rcCfmFlrStatsInfoRmepId                 Integer32,
		rcCfmFlrStatsInfoPriorityIndex		Integer32,
                rcCfmFlrStatsInfoMdName                 DisplayString,
                rcCfmFlrStatsInfoMaName                 DisplayString,
                rcCfmFlrStatsInfoPriority               Integer32,
                rcCfmFlrStatsInfoNearEndPercent         Integer32,
                rcCfmFlrStatsInfoNearEndSubPercent      Integer32,
                rcCfmFlrStatsInfoFarEndPercent          Integer32,
                rcCfmFlrStatsInfoFarEndSubPercent       Integer32,
                rcCfmFlrStatsInfoPmOperState            RcCfmPmOperState
                }

rcCfmFlrStatsInfoMdIndex OBJECT-TYPE
        SYNTAX          Integer32 (1..2147483647)
        MAX-ACCESS      not-accessible
        STATUS          current
        DESCRIPTION     "Maintenance Domain Name"
        ::= { rcCfmFlrStatsInfoEntry 1}

rcCfmFlrStatsInfoMaIndex OBJECT-TYPE
        SYNTAX          Integer32 (1..2147483647)
        MAX-ACCESS      not-accessible
        STATUS          current
        DESCRIPTION     "Maintenance Association Name"
        ::= { rcCfmFlrStatsInfoEntry 2}

rcCfmFlrStatsInfoMepId OBJECT-TYPE
        SYNTAX          Integer32 (1..8191)
        MAX-ACCESS      not-accessible
        STATUS          current
        DESCRIPTION     "Maintenance EndPoint ID"
        ::= { rcCfmFlrStatsInfoEntry 3}

rcCfmFlrStatsInfoRmepId OBJECT-TYPE
        SYNTAX          Integer32 (1..8191)
        MAX-ACCESS      not-accessible
        STATUS          current
        DESCRIPTION     "Peer Identifier which matches a RemoteMepId.
                         The performance monitoring pair is MepId-RmepId"
        ::= { rcCfmFlrStatsInfoEntry 4}

rcCfmFlrStatsInfoPriorityIndex OBJECT-TYPE
        SYNTAX          Integer32 (1..8)
        MAX-ACCESS      not-accessible
        STATUS          current
        DESCRIPTION     "priorityIndex equals priority plus 1 - priority can't be
			used as an index since it starts from 0"
        ::= { rcCfmFlrStatsInfoEntry 5}

rcCfmFlrStatsInfoMdName OBJECT-TYPE
        SYNTAX          DisplayString(SIZE(1..22))
        MAX-ACCESS      read-only
        STATUS          current
        DESCRIPTION     "Maintenance Domain Name"
        ::= { rcCfmFlrStatsInfoEntry 6}

rcCfmFlrStatsInfoMaName OBJECT-TYPE
        SYNTAX          DisplayString(SIZE(1..22))
        MAX-ACCESS      read-only
        STATUS          current
        DESCRIPTION     "Maintenance Association Name"
        ::= { rcCfmFlrStatsInfoEntry 7}

rcCfmFlrStatsInfoPriority OBJECT-TYPE
        SYNTAX          Integer32 (0..7)
        MAX-ACCESS      read-only
        STATUS          current
        DESCRIPTION     "Frame Loss Ratio messaging runs on COS priority"
        DEFVAL { 7 }
        ::= { rcCfmFlrStatsInfoEntry 8}

rcCfmFlrStatsInfoNearEndPercent OBJECT-TYPE
        SYNTAX          Integer32 (0..99)
        MAX-ACCESS      read-only
        STATUS          current
        DESCRIPTION     "Measured near-end FLR percentage"
        ::= { rcCfmFlrStatsInfoEntry 9}

rcCfmFlrStatsInfoNearEndSubPercent OBJECT-TYPE
        SYNTAX          Integer32 (0..99)
        MAX-ACCESS      read-only
        STATUS          current
        DESCRIPTION     "Measured near-end FLR sub percentage"
        ::= { rcCfmFlrStatsInfoEntry 10}

rcCfmFlrStatsInfoFarEndPercent OBJECT-TYPE
        SYNTAX          Integer32 (0..99)
        MAX-ACCESS      read-only
        STATUS          current
        DESCRIPTION     "Measured far-end FLR percentage"
        ::= { rcCfmFlrStatsInfoEntry 11}

rcCfmFlrStatsInfoFarEndSubPercent OBJECT-TYPE
        SYNTAX          Integer32 (0..99)
        MAX-ACCESS      read-only
        STATUS          current
        DESCRIPTION     "Measured far-end FLR sub percentage"
        ::= { rcCfmFlrStatsInfoEntry 12}

rcCfmFlrStatsInfoPmOperState OBJECT-TYPE
        SYNTAX          RcCfmPmOperState
        MAX-ACCESS      read-only
        STATUS          current
        DESCRIPTION
           "The operational state of the PM."
        ::= {rcCfmFlrStatsInfoEntry 13}

-- Frame Loss Ratio Stats Current Table

rcCfmFlrStatsCurrTable OBJECT-TYPE
        SYNTAX          SEQUENCE OF RcCfmFlrStatsCurrEntry
        MAX-ACCESS      not-accessible
        STATUS          current
        DESCRIPTION     "CFM Frame Loss Ratio Stats Current"
        ::= { rcCfm 24}

rcCfmFlrStatsCurrEntry OBJECT-TYPE
        SYNTAX          RcCfmFlrStatsCurrEntry
        MAX-ACCESS      not-accessible
        STATUS          current
        DESCRIPTION     "CFM Frame Loss Ratio Stats Current entry."
        INDEX           { rcCfmFlrStatsCurrMdIndex,
                          rcCfmFlrStatsCurrMaIndex,
                          rcCfmFlrStatsCurrMepId,
                          rcCfmFlrStatsCurrRmepId,
                          rcCfmFlrStatsCurrPriorityIndex }
        ::= { rcCfmFlrStatsCurrTable 1}

RcCfmFlrStatsCurrEntry ::=
        SEQUENCE {
                rcCfmFlrStatsCurrMdIndex                       Integer32,
                rcCfmFlrStatsCurrMaIndex                       Integer32,
                rcCfmFlrStatsCurrMepId                         Integer32,
                rcCfmFlrStatsCurrRmepId                        Integer32,
		rcCfmFlrStatsCurrPriorityIndex		       Integer32,
                rcCfmFlrStatsCurrMdName                        DisplayString,
                rcCfmFlrStatsCurrMaName                        DisplayString,
                rcCfmFlrStatsCurrPriority                      Integer32,
                rcCfmFlrStatsCurrPmOperState                   RcCfmPmOperState,
                rcCfmFlrStatsCurrStartTime                     OCTET STRING ,
                rcCfmFlrStatsCurrEndTime                       OCTET STRING ,
		rcCfmFlrStatsCurrHistInterval                  Gauge32,
                rcCfmFlrStatsCurrSampleRate                    Gauge32,
                rcCfmFlrStatsCurrNearEndPercent                Integer32,
                rcCfmFlrStatsCurrNearEndSubPercent             Integer32,
                rcCfmFlrStatsCurrFarEndPercent                 Integer32,
                rcCfmFlrStatsCurrFarEndSubPercent              Integer32,
                rcCfmFlrStatsCurrMinNearEndPercent             Integer32,
                rcCfmFlrStatsCurrMinNearEndSubPercent          Integer32,
                rcCfmFlrStatsCurrMinFarEndPercent              Integer32,
                rcCfmFlrStatsCurrMinFarEndSubPercent           Integer32,
                rcCfmFlrStatsCurrMaxNearEndPercent             Integer32,
                rcCfmFlrStatsCurrMaxNearEndSubPercent          Integer32,
                rcCfmFlrStatsCurrMaxFarEndPercent              Integer32,
                rcCfmFlrStatsCurrMaxFarEndSubPercent           Integer32,
                rcCfmFlrStatsCurrTxFrames                      Counter64,
                rcCfmFlrStatsCurrRxFrames                      Counter64,
                rcCfmFlrStatsCurrFlFrames                      Counter64,
                rcCfmFlrStatsCurrTxFarEndFrames                Counter64,
                rcCfmFlrStatsCurrRxFarEndFrames                Counter64,
                rcCfmFlrStatsCurrFlFarEndFrames                Counter64,
                rcCfmFlrStatsCurrSamplesPerInterval            Gauge32,
                rcCfmFlrStatsCurrSamplesTransmitted            Gauge32,
                rcCfmFlrStatsCurrMinFlFrames                   Counter32,
		rcCfmFlrStatsCurrSamplesNotSent                Gauge32,
		rcCfmFlrStatsCurrSamplesReceived               Gauge32,
                rcCfmFlrStatsCurrMinFlFarEndFrames             Counter32,
                rcCfmFlrStatsCurrMaxFlFrames                   Counter32,
                rcCfmFlrStatsCurrMaxFlFarEndFrames             Counter32
                }

rcCfmFlrStatsCurrMdIndex OBJECT-TYPE
        SYNTAX          Integer32 (1..2147483647)
        MAX-ACCESS      not-accessible
        STATUS          current
        DESCRIPTION     "Maintenance Domain Name"
        ::= { rcCfmFlrStatsCurrEntry 1}

rcCfmFlrStatsCurrMaIndex OBJECT-TYPE
        SYNTAX          Integer32 (1..2147483647)
        MAX-ACCESS      not-accessible
        STATUS          current
        DESCRIPTION     "Maintenance Association Name"
        ::= { rcCfmFlrStatsCurrEntry 2}

rcCfmFlrStatsCurrMepId OBJECT-TYPE
        SYNTAX          Integer32 (1..8191)
        MAX-ACCESS      not-accessible
        STATUS          current
        DESCRIPTION     "Maintenance EndPoint ID"
        ::= { rcCfmFlrStatsCurrEntry 3}

rcCfmFlrStatsCurrRmepId OBJECT-TYPE
        SYNTAX          Integer32 (1..8191)
        MAX-ACCESS      not-accessible
        STATUS          current
        DESCRIPTION     "Peer Identifier which matches a RemoteMepId.
                         The performance monitoring pair is MepId-RmepId"
        ::= { rcCfmFlrStatsCurrEntry 4}

rcCfmFlrStatsCurrPriorityIndex OBJECT-TYPE
        SYNTAX          Integer32 (1..8)
        MAX-ACCESS      not-accessible
        STATUS          current
        DESCRIPTION     "priorityIndex equals priority plus 1 - priority can't be
			used as an index since it starts from 0"
        ::= { rcCfmFlrStatsCurrEntry 5}

rcCfmFlrStatsCurrMdName OBJECT-TYPE
        SYNTAX          DisplayString(SIZE(1..22))
        MAX-ACCESS      read-only
        STATUS          current
        DESCRIPTION     "Maintenance Domain Name"
        ::= { rcCfmFlrStatsCurrEntry 6}

rcCfmFlrStatsCurrMaName OBJECT-TYPE
        SYNTAX          DisplayString(SIZE(1..22))
        MAX-ACCESS      read-only
        STATUS          current
        DESCRIPTION     "Maintenance Association Name"
        ::= { rcCfmFlrStatsCurrEntry 7}

rcCfmFlrStatsCurrPriority OBJECT-TYPE
        SYNTAX          Integer32 (0..7)
        MAX-ACCESS      read-only
        STATUS          current
        DESCRIPTION     "Frame Loss Ratio messaging runs on COS priority"
        DEFVAL { 7 }
        ::= { rcCfmFlrStatsCurrEntry 8}

rcCfmFlrStatsCurrPmOperState OBJECT-TYPE
        SYNTAX          RcCfmPmOperState
        MAX-ACCESS      read-only
        STATUS          current
        DESCRIPTION     "The operational state of the PM."
        ::= {rcCfmFlrStatsCurrEntry 9}

rcCfmFlrStatsCurrStartTime  OBJECT-TYPE
	SYNTAX          OCTET STRING (SIZE(11))
        MAX-ACCESS      read-only
        STATUS          current
        DESCRIPTION     "The date and time stamp."
        ::= { rcCfmFlrStatsCurrEntry 10}

rcCfmFlrStatsCurrEndTime  OBJECT-TYPE
	SYNTAX          OCTET STRING (SIZE(11))
        MAX-ACCESS      read-only
        STATUS          current
        DESCRIPTION     "The date and time stamp."
        ::= { rcCfmFlrStatsCurrEntry 11}

rcCfmFlrStatsCurrHistInterval  OBJECT-TYPE
        SYNTAX          Gauge32
        MAX-ACCESS      read-only
        STATUS          current
        DESCRIPTION     "History Interval"
        ::= { rcCfmFlrStatsCurrEntry 12}

rcCfmFlrStatsCurrSampleRate  OBJECT-TYPE
        SYNTAX          Gauge32
        MAX-ACCESS      read-only
        STATUS          current
        DESCRIPTION     "Sample rate in seconds"
        ::= { rcCfmFlrStatsCurrEntry 13}

rcCfmFlrStatsCurrNearEndPercent OBJECT-TYPE
        SYNTAX          Integer32 (0..99)
        MAX-ACCESS      read-only
        STATUS          current
        DESCRIPTION     "Measured near-end FLR percentage"
        ::= { rcCfmFlrStatsCurrEntry 14}

rcCfmFlrStatsCurrNearEndSubPercent OBJECT-TYPE
        SYNTAX          Integer32 (0..99)
        MAX-ACCESS      read-only
        STATUS          current
        DESCRIPTION     "Measured near-end FLR sub percentage"
        ::= { rcCfmFlrStatsCurrEntry 15}

rcCfmFlrStatsCurrFarEndPercent OBJECT-TYPE
        SYNTAX          Integer32 (0..99)
        MAX-ACCESS      read-only
        STATUS          current
        DESCRIPTION     "Measured far-end FLR percentage"
        ::= { rcCfmFlrStatsCurrEntry 16}

rcCfmFlrStatsCurrFarEndSubPercent OBJECT-TYPE
        SYNTAX          Integer32 (0..99)
        MAX-ACCESS      read-only
        STATUS          current
        DESCRIPTION     "Measured far-end FLR sub percentage"
        ::= { rcCfmFlrStatsCurrEntry 17}

rcCfmFlrStatsCurrMinNearEndPercent OBJECT-TYPE
        SYNTAX          Integer32 (0..99)
        MAX-ACCESS      read-only
        STATUS          current
        DESCRIPTION     "Measured near-end FLR percentage"
        ::= { rcCfmFlrStatsCurrEntry 18}

rcCfmFlrStatsCurrMinNearEndSubPercent OBJECT-TYPE
        SYNTAX          Integer32 (0..99)
        MAX-ACCESS      read-only
        STATUS          current
        DESCRIPTION     "Measured near-end FLR sub percentage"
        ::= { rcCfmFlrStatsCurrEntry 19}

rcCfmFlrStatsCurrMinFarEndPercent OBJECT-TYPE
        SYNTAX          Integer32 (0..99)
        MAX-ACCESS      read-only
        STATUS          current
        DESCRIPTION     "Measured near-end FLR percentage"
        ::= { rcCfmFlrStatsCurrEntry 20}

rcCfmFlrStatsCurrMinFarEndSubPercent OBJECT-TYPE
        SYNTAX          Integer32 (0..99)
        MAX-ACCESS      read-only
        STATUS          current
        DESCRIPTION     "Measured near-end FLR sub percentage"
        ::= { rcCfmFlrStatsCurrEntry 21}

rcCfmFlrStatsCurrMaxNearEndPercent OBJECT-TYPE
        SYNTAX          Integer32 (0..99)
        MAX-ACCESS      read-only
        STATUS          current
        DESCRIPTION     "Measured near-end FLR percentage"
        ::= { rcCfmFlrStatsCurrEntry 22}

rcCfmFlrStatsCurrMaxNearEndSubPercent OBJECT-TYPE
        SYNTAX          Integer32 (0..99)
        MAX-ACCESS      read-only
        STATUS          current
        DESCRIPTION     "Measured near-end FLR sub percentage"
        ::= { rcCfmFlrStatsCurrEntry 23}

rcCfmFlrStatsCurrMaxFarEndPercent OBJECT-TYPE
        SYNTAX          Integer32 (0..99)
        MAX-ACCESS      read-only
        STATUS          current
        DESCRIPTION     "Measured near-end FLR percentage"
        ::= { rcCfmFlrStatsCurrEntry 24}

rcCfmFlrStatsCurrMaxFarEndSubPercent OBJECT-TYPE
        SYNTAX          Integer32 (0..99)
        MAX-ACCESS      read-only
        STATUS          current
        DESCRIPTION     "Measured near-end FLR sub percentage"
        ::= { rcCfmFlrStatsCurrEntry 25}

rcCfmFlrStatsCurrTxFrames OBJECT-TYPE
        SYNTAX          Counter64
        MAX-ACCESS      read-only
        STATUS          current
        DESCRIPTION     "Tx frames"
        ::= { rcCfmFlrStatsCurrEntry 26}

rcCfmFlrStatsCurrRxFrames OBJECT-TYPE
        SYNTAX          Counter64
        MAX-ACCESS      read-only
        STATUS          current
        DESCRIPTION     "Rx frames"
        ::= { rcCfmFlrStatsCurrEntry 27}

rcCfmFlrStatsCurrFlFrames OBJECT-TYPE
        SYNTAX          Counter64
        MAX-ACCESS      read-only
        STATUS          current
        DESCRIPTION     "Frame Loss frames"
        ::= { rcCfmFlrStatsCurrEntry 28}

rcCfmFlrStatsCurrTxFarEndFrames OBJECT-TYPE
        SYNTAX          Counter64
        MAX-ACCESS      read-only
        STATUS          current
        DESCRIPTION     "Far-end Tx frames"
        ::= { rcCfmFlrStatsCurrEntry 29}

rcCfmFlrStatsCurrRxFarEndFrames OBJECT-TYPE
        SYNTAX          Counter64
        MAX-ACCESS      read-only
        STATUS          current
        DESCRIPTION     "Far-end Rx frames"
        ::= { rcCfmFlrStatsCurrEntry 30}

rcCfmFlrStatsCurrFlFarEndFrames OBJECT-TYPE
        SYNTAX          Counter64
        MAX-ACCESS      read-only
        STATUS          current
        DESCRIPTION     "Far-end Frame Loss frames"
        ::= { rcCfmFlrStatsCurrEntry 31}

rcCfmFlrStatsCurrSamplesPerInterval  OBJECT-TYPE
        SYNTAX          Gauge32
        MAX-ACCESS      read-only
        STATUS          current
        DESCRIPTION     "Samples per interval"
        ::= { rcCfmFlrStatsCurrEntry 32}

rcCfmFlrStatsCurrSamplesTransmitted  OBJECT-TYPE
        SYNTAX          Gauge32
        MAX-ACCESS      read-only
        STATUS          current
        DESCRIPTION     "Samples transmitted"
        ::= { rcCfmFlrStatsCurrEntry 33}

rcCfmFlrStatsCurrMinFlFrames OBJECT-TYPE
        SYNTAX          Counter32
        MAX-ACCESS      read-only
        STATUS          current
        DESCRIPTION     "Minimum sample Frame Loss frames"
        ::= { rcCfmFlrStatsCurrEntry 34}

rcCfmFlrStatsCurrSamplesNotSent  OBJECT-TYPE
        SYNTAX          Gauge32
        MAX-ACCESS      read-only
        STATUS          current
        DESCRIPTION     "Samples not sent"
        ::= { rcCfmFlrStatsCurrEntry 35}

rcCfmFlrStatsCurrSamplesReceived  OBJECT-TYPE
        SYNTAX          Gauge32
        MAX-ACCESS      read-only
        STATUS          current
        DESCRIPTION     "Samples received"
        ::= { rcCfmFlrStatsCurrEntry 36}

rcCfmFlrStatsCurrMinFlFarEndFrames OBJECT-TYPE
        SYNTAX          Counter32
        MAX-ACCESS      read-only
        STATUS          current
        DESCRIPTION     "Minimum sample Far-end Frame Loss frames"
        ::= { rcCfmFlrStatsCurrEntry 37}

rcCfmFlrStatsCurrMaxFlFrames OBJECT-TYPE
        SYNTAX          Counter32
        MAX-ACCESS      read-only
        STATUS          current
        DESCRIPTION     "Maximum sample Frame Loss frames"
        ::= { rcCfmFlrStatsCurrEntry 38}

rcCfmFlrStatsCurrMaxFlFarEndFrames OBJECT-TYPE
        SYNTAX          Counter32
        MAX-ACCESS      read-only
        STATUS          current
        DESCRIPTION     "Maximum sample Far-end Frame Loss frames"
        ::= { rcCfmFlrStatsCurrEntry 39}

-- Frame Loss Ratio Stats History Table

rcCfmFlrStatsHistTable OBJECT-TYPE
        SYNTAX          SEQUENCE OF RcCfmFlrStatsHistEntry
        MAX-ACCESS      not-accessible
        STATUS          current
        DESCRIPTION     "CFM Frame Loss Ratio Stats History"
        ::= { rcCfm 25}

rcCfmFlrStatsHistEntry OBJECT-TYPE
        SYNTAX          RcCfmFlrStatsHistEntry
        MAX-ACCESS      not-accessible
        STATUS          current
        DESCRIPTION     "CFM Frame Loss Ratio Stats History entry."
        INDEX           { rcCfmFlrStatsHistMdIndex,
                          rcCfmFlrStatsHistMaIndex,
                          rcCfmFlrStatsHistMepId,
                          rcCfmFlrStatsHistRmepId,
                          rcCfmFlrStatsHistPriorityIndex,
			  rcCfmFlrStatsHistIndex }
        ::= { rcCfmFlrStatsHistTable 1}

RcCfmFlrStatsHistEntry ::=
        SEQUENCE {
                rcCfmFlrStatsHistMdIndex                    Integer32,
                rcCfmFlrStatsHistMaIndex                    Integer32,
                rcCfmFlrStatsHistMepId                      Integer32,
                rcCfmFlrStatsHistRmepId                     Integer32,
		rcCfmFlrStatsHistPriorityIndex		    Integer32,
                rcCfmFlrStatsHistIndex                      Integer32,
                rcCfmFlrStatsHistMdName                     DisplayString,
                rcCfmFlrStatsHistMaName                     DisplayString,
                rcCfmFlrStatsHistPriority                   Integer32,
                rcCfmFlrStatsHistStatus                     INTEGER,
                rcCfmFlrStatsHistStartTime                  OCTET STRING ,
                rcCfmFlrStatsHistEndTime                    OCTET STRING ,
                rcCfmFlrStatsHistHistInterval               Gauge32,
                rcCfmFlrStatsHistSampleRate                 Gauge32,
                rcCfmFlrStatsHistNearEndPercent             Integer32,
                rcCfmFlrStatsHistNearEndSubPercent          Integer32,
                rcCfmFlrStatsHistFarEndPercent              Integer32,
                rcCfmFlrStatsHistFarEndSubPercent           Integer32,
                rcCfmFlrStatsHistMinNearEndPercent          Integer32,
                rcCfmFlrStatsHistMinNearEndSubPercent       Integer32,
                rcCfmFlrStatsHistMinFarEndPercent           Integer32,
                rcCfmFlrStatsHistMinFarEndSubPercent        Integer32,
                rcCfmFlrStatsHistMaxNearEndPercent          Integer32,
                rcCfmFlrStatsHistMaxNearEndSubPercent       Integer32,
                rcCfmFlrStatsHistMaxFarEndPercent           Integer32,
                rcCfmFlrStatsHistMaxFarEndSubPercent        Integer32,
                rcCfmFlrStatsHistTxFrames                   Counter64,
                rcCfmFlrStatsHistRxFrames                   Counter64,
                rcCfmFlrStatsHistFlFrames                   Counter64,
                rcCfmFlrStatsHistTxFarEndFrames             Counter64,
                rcCfmFlrStatsHistRxFarEndFrames             Counter64,
                rcCfmFlrStatsHistFlFarEndFrames             Counter64,
                rcCfmFlrStatsHistSamplesPerInterval         Gauge32,
                rcCfmFlrStatsHistSamplesTransmitted         Gauge32,
                rcCfmFlrStatsHistMinFlFrames                Counter32,
                rcCfmFlrStatsHistSamplesNotSent             Gauge32,
                rcCfmFlrStatsHistSamplesReceived            Gauge32,
                rcCfmFlrStatsHistMinFlFarEndFrames          Counter32,
                rcCfmFlrStatsHistMaxFlFrames                Counter32,
                rcCfmFlrStatsHistMaxFlFarEndFrames          Counter32
                }

rcCfmFlrStatsHistMdIndex OBJECT-TYPE
        SYNTAX          Integer32 (1..2147483647)
        MAX-ACCESS      not-accessible
        STATUS          current
        DESCRIPTION     "Maintenance Domain Name"
        ::= { rcCfmFlrStatsHistEntry 1}

rcCfmFlrStatsHistMaIndex OBJECT-TYPE
        SYNTAX          Integer32 (1..2147483647)
        MAX-ACCESS      not-accessible
        STATUS          current
        DESCRIPTION     "Maintenance Association Name"
        ::= { rcCfmFlrStatsHistEntry 2}

rcCfmFlrStatsHistMepId OBJECT-TYPE
        SYNTAX          Integer32 (1..8191)
        MAX-ACCESS      not-accessible
        STATUS          current
        DESCRIPTION     "Maintenance EndPoint ID"
        ::= { rcCfmFlrStatsHistEntry 3}

rcCfmFlrStatsHistRmepId OBJECT-TYPE
        SYNTAX          Integer32 (1..8191)
        MAX-ACCESS      not-accessible
        STATUS          current
        DESCRIPTION     "Peer Identifier which matches a RemoteMepId.
                         The performance monitoring pair is MepId-RmepId"
        ::= { rcCfmFlrStatsHistEntry 4}

rcCfmFlrStatsHistPriorityIndex OBJECT-TYPE
        SYNTAX          Integer32 (1..8)
        MAX-ACCESS      not-accessible
        STATUS          current
        DESCRIPTION     "priorityIndex equals priority plus 1 - priority can't be
			used as an index since it starts from 0"
        ::= { rcCfmFlrStatsHistEntry 5}

rcCfmFlrStatsHistIndex OBJECT-TYPE
        SYNTAX          Integer32 (1..1000)
        MAX-ACCESS      not-accessible 
        STATUS          current
        DESCRIPTION     "History Index"
        ::= { rcCfmFlrStatsHistEntry 6}

rcCfmFlrStatsHistMdName OBJECT-TYPE
        SYNTAX          DisplayString(SIZE(1..22))
        MAX-ACCESS      read-only
        STATUS          current
        DESCRIPTION     "Maintenance Domain Name"
        ::= { rcCfmFlrStatsHistEntry 7}

rcCfmFlrStatsHistMaName OBJECT-TYPE
        SYNTAX          DisplayString(SIZE(1..22))
        MAX-ACCESS      read-only
        STATUS          current
        DESCRIPTION     "Maintenance Association Name"
        ::= { rcCfmFlrStatsHistEntry 8}

rcCfmFlrStatsHistPriority OBJECT-TYPE
        SYNTAX          Integer32 (0..7)
        MAX-ACCESS      read-only
        STATUS          current
        DESCRIPTION     "Frame Loss Ratio messaging runs on COS priority"
        DEFVAL { 7 }
        ::= { rcCfmFlrStatsHistEntry 9}

rcCfmFlrStatsHistStatus OBJECT-TYPE
        SYNTAX          INTEGER {
	                   complete(1),
			   incomplete(2)
	                }
        MAX-ACCESS      read-only
        STATUS          current
        DESCRIPTION
           "The status of this history interval."
        ::= {rcCfmFlrStatsHistEntry 10}

rcCfmFlrStatsHistStartTime  OBJECT-TYPE
	SYNTAX          OCTET STRING (SIZE(11))
        MAX-ACCESS      read-only
        STATUS          current
        DESCRIPTION     "The date and time stamp."
        ::= { rcCfmFlrStatsHistEntry 11}

rcCfmFlrStatsHistEndTime  OBJECT-TYPE
	SYNTAX          OCTET STRING (SIZE(11))
        MAX-ACCESS      read-only
        STATUS          current
        DESCRIPTION     "The date and time stamp."
        ::= { rcCfmFlrStatsHistEntry 12}

rcCfmFlrStatsHistHistInterval  OBJECT-TYPE
        SYNTAX          Gauge32
        MAX-ACCESS      read-only
        STATUS          current
        DESCRIPTION     "History Interval"
        ::= { rcCfmFlrStatsHistEntry 13}

rcCfmFlrStatsHistSampleRate  OBJECT-TYPE
        SYNTAX          Gauge32
        MAX-ACCESS      read-only
        STATUS          current
        DESCRIPTION     "Sample rate in seconds"
        ::= { rcCfmFlrStatsHistEntry 14}

rcCfmFlrStatsHistNearEndPercent OBJECT-TYPE
        SYNTAX          Integer32 (0..99)
        MAX-ACCESS      read-only
        STATUS          current
        DESCRIPTION     "Measured near-end FLR percentage"
        ::= { rcCfmFlrStatsHistEntry 15}

rcCfmFlrStatsHistNearEndSubPercent OBJECT-TYPE
        SYNTAX          Integer32 (0..99)
        MAX-ACCESS      read-only
        STATUS          current
        DESCRIPTION     "Measured near-end FLR sub percentage"
        ::= { rcCfmFlrStatsHistEntry 16} 

rcCfmFlrStatsHistFarEndPercent OBJECT-TYPE
        SYNTAX          Integer32 (0..99)
        MAX-ACCESS      read-only
        STATUS          current
        DESCRIPTION     "Measured far-end FLR percentage"
        ::= { rcCfmFlrStatsHistEntry 17}

rcCfmFlrStatsHistFarEndSubPercent OBJECT-TYPE
        SYNTAX          Integer32 (0..99)
        MAX-ACCESS      read-only
        STATUS          current 
        DESCRIPTION     "Measured far-end FLR sub percentage"
        ::= { rcCfmFlrStatsHistEntry 18}

rcCfmFlrStatsHistMinNearEndPercent OBJECT-TYPE
        SYNTAX          Integer32 (0..99) 
        MAX-ACCESS      read-only
        STATUS          current
        DESCRIPTION     "Measured near-end FLR percentage"
        ::= { rcCfmFlrStatsHistEntry 19}

rcCfmFlrStatsHistMinNearEndSubPercent OBJECT-TYPE
        SYNTAX          Integer32 (0..99)
        MAX-ACCESS      read-only
        STATUS          current
        DESCRIPTION     "Measured near-end FLR sub percentage"
        ::= { rcCfmFlrStatsHistEntry 20}

rcCfmFlrStatsHistMinFarEndPercent OBJECT-TYPE
        SYNTAX          Integer32 (0..99)
        MAX-ACCESS      read-only
        STATUS          current
        DESCRIPTION     "Measured near-end FLR percentage"
        ::= { rcCfmFlrStatsHistEntry 21}

rcCfmFlrStatsHistMinFarEndSubPercent OBJECT-TYPE
        SYNTAX          Integer32 (0..99)
        MAX-ACCESS      read-only
        STATUS          current
        DESCRIPTION     "Measured near-end FLR sub percentage"
        ::= { rcCfmFlrStatsHistEntry 22}

rcCfmFlrStatsHistMaxNearEndPercent OBJECT-TYPE
        SYNTAX          Integer32 (0..99)
        MAX-ACCESS      read-only
        STATUS          current
        DESCRIPTION     "Measured near-end FLR percentage"
        ::= { rcCfmFlrStatsHistEntry 23}

rcCfmFlrStatsHistMaxNearEndSubPercent OBJECT-TYPE
        SYNTAX          Integer32 (0..99)
        MAX-ACCESS      read-only
        STATUS          current
        DESCRIPTION     "Measured near-end FLR sub percentage"
        ::= { rcCfmFlrStatsHistEntry 24}

rcCfmFlrStatsHistMaxFarEndPercent OBJECT-TYPE
        SYNTAX          Integer32 (0..99)
        MAX-ACCESS      read-only
        STATUS          current
        DESCRIPTION     "Measured near-end FLR percentage"
        ::= { rcCfmFlrStatsHistEntry 25}

rcCfmFlrStatsHistMaxFarEndSubPercent OBJECT-TYPE
        SYNTAX          Integer32 (0..99)
        MAX-ACCESS      read-only
        STATUS          current
        DESCRIPTION     "Measured near-end FLR sub percentage"
        ::= { rcCfmFlrStatsHistEntry 26}

rcCfmFlrStatsHistTxFrames OBJECT-TYPE
        SYNTAX          Counter64
        MAX-ACCESS      read-only
        STATUS          current
        DESCRIPTION     "Tx frames"
        ::= { rcCfmFlrStatsHistEntry 27}

rcCfmFlrStatsHistRxFrames OBJECT-TYPE
        SYNTAX          Counter64
        MAX-ACCESS      read-only
        STATUS          current
        DESCRIPTION     "Rx frames"
        ::= { rcCfmFlrStatsHistEntry 28}

rcCfmFlrStatsHistFlFrames OBJECT-TYPE
        SYNTAX          Counter64
        MAX-ACCESS      read-only
        STATUS          current
        DESCRIPTION     "Frame Loss frames"
        ::= { rcCfmFlrStatsHistEntry 29}

rcCfmFlrStatsHistTxFarEndFrames OBJECT-TYPE
        SYNTAX          Counter64
        MAX-ACCESS      read-only
        STATUS          current
        DESCRIPTION     "Far-end Tx frames"
        ::= { rcCfmFlrStatsHistEntry 30}

rcCfmFlrStatsHistRxFarEndFrames OBJECT-TYPE
        SYNTAX          Counter64
        MAX-ACCESS      read-only
        STATUS          current
        DESCRIPTION     "Far-end Rx frames"
        ::= { rcCfmFlrStatsHistEntry 31}

rcCfmFlrStatsHistFlFarEndFrames OBJECT-TYPE
        SYNTAX          Counter64
        MAX-ACCESS      read-only
        STATUS          current
        DESCRIPTION     "Far-end Frame Loss frames"
        ::= { rcCfmFlrStatsHistEntry 32}

rcCfmFlrStatsHistSamplesPerInterval  OBJECT-TYPE
        SYNTAX          Gauge32
        MAX-ACCESS      read-only
        STATUS          current
        DESCRIPTION     "Samples per interval"
        ::= { rcCfmFlrStatsHistEntry 33}

rcCfmFlrStatsHistSamplesTransmitted  OBJECT-TYPE
        SYNTAX          Gauge32
        MAX-ACCESS      read-only
        STATUS          current
        DESCRIPTION     "Samples transmitted"
        ::= { rcCfmFlrStatsHistEntry 34}

rcCfmFlrStatsHistMinFlFrames OBJECT-TYPE
        SYNTAX          Counter32
        MAX-ACCESS      read-only
        STATUS          current
        DESCRIPTION     "Minimum sample Frame Loss frames"
        ::= { rcCfmFlrStatsHistEntry 35}

rcCfmFlrStatsHistSamplesNotSent  OBJECT-TYPE
        SYNTAX          Gauge32
        MAX-ACCESS      read-only
        STATUS          current
        DESCRIPTION     "Samples not sent"
        ::= { rcCfmFlrStatsHistEntry 36}

rcCfmFlrStatsHistSamplesReceived  OBJECT-TYPE
        SYNTAX          Gauge32
        MAX-ACCESS      read-only
        STATUS          current
        DESCRIPTION     "Samples received"
        ::= { rcCfmFlrStatsHistEntry 37}

rcCfmFlrStatsHistMinFlFarEndFrames OBJECT-TYPE
        SYNTAX          Counter32
        MAX-ACCESS      read-only
        STATUS          current
        DESCRIPTION     "Minimum sample Far-end Frame Loss frames"
        ::= { rcCfmFlrStatsHistEntry 38}

rcCfmFlrStatsHistMaxFlFrames OBJECT-TYPE
        SYNTAX          Counter32
        MAX-ACCESS      read-only
        STATUS          current
        DESCRIPTION     "Maximum sample Frame Loss frames"
        ::= { rcCfmFlrStatsHistEntry 39}

rcCfmFlrStatsHistMaxFlFarEndFrames OBJECT-TYPE
        SYNTAX          Counter32
        MAX-ACCESS      read-only
        STATUS          current
        DESCRIPTION     "Maximum sample Far-end Frame Loss frames"
        ::= { rcCfmFlrStatsHistEntry 40}

-- Frame Delay Stats Info Table

rcCfmFdStatsInfoTable OBJECT-TYPE
        SYNTAX          SEQUENCE OF RcCfmFdStatsInfoEntry
        MAX-ACCESS      not-accessible
        STATUS          current
        DESCRIPTION     "CFM Frame Delay Stats Info"
        ::= { rcCfm 26}

rcCfmFdStatsInfoEntry OBJECT-TYPE
        SYNTAX          RcCfmFdStatsInfoEntry
        MAX-ACCESS      not-accessible
        STATUS          current
        DESCRIPTION     "Frame Delay Stats Info entry."
        INDEX           { rcCfmFdStatsInfoMdIndex,
                          rcCfmFdStatsInfoMaIndex,
                          rcCfmFdStatsInfoMepId,
                          rcCfmFdStatsInfoRmepId,
                          rcCfmFdStatsInfoPriorityIndex  }
        ::= { rcCfmFdStatsInfoTable 1}

RcCfmFdStatsInfoEntry ::=
        SEQUENCE {
                rcCfmFdStatsInfoMdIndex                Integer32,
                rcCfmFdStatsInfoMaIndex                Integer32,
                rcCfmFdStatsInfoMepId                  Integer32,
                rcCfmFdStatsInfoRmepId                 Integer32,
		rcCfmFdStatsInfoPriorityIndex	       Integer32,
                rcCfmFdStatsInfoMdName                 DisplayString,
                rcCfmFdStatsInfoMaName                 DisplayString,
                rcCfmFdStatsInfoPriority               Integer32,
                rcCfmFdStatsInfoFdPercent              Integer32,
                rcCfmFdStatsInfoFdSubPercent           Integer32,
                rcCfmFdStatsInfoFdvPercent             Integer32,
                rcCfmFdStatsInfoFdvSubPercent          Integer32,
                rcCfmFdStatsInfoPmOperState            RcCfmPmOperState
                }

rcCfmFdStatsInfoMdIndex OBJECT-TYPE
        SYNTAX          Integer32 (1..2147483647)
        MAX-ACCESS      not-accessible
        STATUS          current
        DESCRIPTION     "Maintenance Domain Name"
        ::= { rcCfmFdStatsInfoEntry 1}

rcCfmFdStatsInfoMaIndex OBJECT-TYPE
        SYNTAX          Integer32 (1..2147483647)
        MAX-ACCESS      not-accessible
        STATUS          current
        DESCRIPTION     "Maintenance Association Name"
        ::= { rcCfmFdStatsInfoEntry 2}

rcCfmFdStatsInfoMepId OBJECT-TYPE
        SYNTAX          Integer32 (1..8191)
        MAX-ACCESS      not-accessible
        STATUS          current
        DESCRIPTION     "Maintenance EndPoint ID"
        ::= { rcCfmFdStatsInfoEntry 3}

rcCfmFdStatsInfoRmepId OBJECT-TYPE
        SYNTAX          Integer32 (1..8191)
        MAX-ACCESS      not-accessible
        STATUS          current
        DESCRIPTION     "Peer Identifier which matches a RemoteMepId.
                         The performance monitoring pair is MepId-RmepId"
        ::= { rcCfmFdStatsInfoEntry 4}

rcCfmFdStatsInfoPriorityIndex OBJECT-TYPE
        SYNTAX          Integer32 (1..8)
        MAX-ACCESS      not-accessible 
        STATUS          current
        DESCRIPTION     "priorityIndex equals priority plus 1 - priority can't be
			used as an index since it starts from 0"
        ::= { rcCfmFdStatsInfoEntry 5}

rcCfmFdStatsInfoMdName OBJECT-TYPE
        SYNTAX          DisplayString(SIZE(1..22))
        MAX-ACCESS      read-only
        STATUS          current
        DESCRIPTION     "Maintenance Domain Name"
        ::= { rcCfmFdStatsInfoEntry 6}

rcCfmFdStatsInfoMaName OBJECT-TYPE
        SYNTAX          DisplayString(SIZE(1..22))
        MAX-ACCESS      read-only
        STATUS          current
        DESCRIPTION     "Maintenance Association Name"
        ::= { rcCfmFdStatsInfoEntry 7}

rcCfmFdStatsInfoPriority OBJECT-TYPE
        SYNTAX          Integer32 (0..7)
        MAX-ACCESS      read-only 
        STATUS          current
        DESCRIPTION     "Frame Delay messaging runs on COS priority"
	DEFVAL { 7 }
        ::= { rcCfmFdStatsInfoEntry 8}

rcCfmFdStatsInfoFdPercent OBJECT-TYPE
        SYNTAX          Integer32 (0..99)
        MAX-ACCESS      read-only
        STATUS          current
        DESCRIPTION     "Measured FD percentage"
        ::= { rcCfmFdStatsInfoEntry 9}

rcCfmFdStatsInfoFdSubPercent OBJECT-TYPE
        SYNTAX          Integer32 (0..99)
        MAX-ACCESS      read-only
        STATUS          current
        DESCRIPTION     "Measured FD sub percentage"
        ::= { rcCfmFdStatsInfoEntry 10}

rcCfmFdStatsInfoFdvPercent OBJECT-TYPE
        SYNTAX          Integer32 (0..99)
        MAX-ACCESS      read-only
        STATUS          current
        DESCRIPTION     "Measured FDV percentage"
        ::= { rcCfmFdStatsInfoEntry 11}

rcCfmFdStatsInfoFdvSubPercent OBJECT-TYPE
        SYNTAX          Integer32 (0..99)
        MAX-ACCESS      read-only
        STATUS          current
        DESCRIPTION     "Measured FDV sub percentage"
        ::= { rcCfmFdStatsInfoEntry 12}

rcCfmFdStatsInfoPmOperState OBJECT-TYPE
        SYNTAX          RcCfmPmOperState
        MAX-ACCESS      read-only
        STATUS          current
        DESCRIPTION
           "The operational state of the PM."
        ::= {rcCfmFdStatsInfoEntry 13}

-- Frame Delay Stats Current Table

rcCfmFdStatsCurrTable OBJECT-TYPE
        SYNTAX          SEQUENCE OF RcCfmFdStatsCurrEntry
        MAX-ACCESS      not-accessible
        STATUS          current
        DESCRIPTION     "CFM Frame Delay Stats Current"
        ::= { rcCfm 27}

rcCfmFdStatsCurrEntry OBJECT-TYPE
        SYNTAX          RcCfmFdStatsCurrEntry
        MAX-ACCESS      not-accessible
        STATUS          current
        DESCRIPTION     "CFM Frame Delay Stats Current entry."
        INDEX           { rcCfmFdStatsCurrMdIndex,
                          rcCfmFdStatsCurrMaIndex,
                          rcCfmFdStatsCurrMepId,
                          rcCfmFdStatsCurrRmepId,
                          rcCfmFdStatsCurrPriorityIndex }
        ::= { rcCfmFdStatsCurrTable 1}

RcCfmFdStatsCurrEntry ::=
        SEQUENCE {
                rcCfmFdStatsCurrMdIndex                Integer32,
                rcCfmFdStatsCurrMaIndex                Integer32,
                rcCfmFdStatsCurrMepId                  Integer32,
                rcCfmFdStatsCurrRmepId                 Integer32,
		rcCfmFdStatsCurrPriorityIndex	       Integer32,
                rcCfmFdStatsCurrMdName                 DisplayString,
                rcCfmFdStatsCurrMaName                 DisplayString,
                rcCfmFdStatsCurrPriority               Integer32,
                rcCfmFdStatsCurrFdPercent              Integer32,
                rcCfmFdStatsCurrFdSubPercent           Integer32,
                rcCfmFdStatsCurrFdvPercent             Integer32,
                rcCfmFdStatsCurrFdvSubPercent          Integer32,
                rcCfmFdStatsCurrPmOperState            RcCfmPmOperState,
                rcCfmFdStatsCurrStartTime              OCTET STRING ,
                rcCfmFdStatsCurrEndTime                OCTET STRING ,
		rcCfmFdStatsCurrHistInterval           Gauge32,
                rcCfmFdStatsCurrSampleRate             Gauge32,
                rcCfmFdStatsCurrTarget                 Counter32,
                rcCfmFdStatsCurrAverage                Counter32,
                rcCfmFdStatsCurrMinimum                Counter32,
                rcCfmFdStatsCurrMaximum                Counter32,
                rcCfmFdStatsCurrFdvTarget              Counter32,
                rcCfmFdStatsCurrFdvAverage             Counter32,
                rcCfmFdStatsCurrFdvMinimum             Counter32,
                rcCfmFdStatsCurrFdvMaximum             Counter32,
                rcCfmFdStatsCurrSamplesPerInterval     Gauge32,
                rcCfmFdStatsCurrSamplesTransmitted     Gauge32,
		rcCfmFdStatsCurrSamplesNotSent         Gauge32,
		rcCfmFdStatsCurrSamplesReceived        Gauge32
                }

rcCfmFdStatsCurrMdIndex OBJECT-TYPE
        SYNTAX          Integer32 (1..2147483647)
        MAX-ACCESS      not-accessible
        STATUS          current
        DESCRIPTION     "Maintenance Domain Name"
        ::= { rcCfmFdStatsCurrEntry 1}

rcCfmFdStatsCurrMaIndex OBJECT-TYPE
        SYNTAX          Integer32 (1..2147483647)
        MAX-ACCESS      not-accessible
        STATUS          current
        DESCRIPTION     "Maintenance Association Name"
        ::= { rcCfmFdStatsCurrEntry 2}

rcCfmFdStatsCurrMepId OBJECT-TYPE
        SYNTAX          Integer32 (1..8191)
        MAX-ACCESS      not-accessible
        STATUS          current
        DESCRIPTION     "Maintenance EndPoint ID"
        ::= { rcCfmFdStatsCurrEntry 3}

rcCfmFdStatsCurrRmepId OBJECT-TYPE
        SYNTAX          Integer32 (1..8191)
        MAX-ACCESS      not-accessible
        STATUS          current
        DESCRIPTION     "Peer Identifier which matches a RemoteMepId.
                         The performance monitoring pair is MepId-RmepId"
        ::= { rcCfmFdStatsCurrEntry 4}

rcCfmFdStatsCurrPriorityIndex OBJECT-TYPE
        SYNTAX          Integer32 (1..8)
        MAX-ACCESS      not-accessible 
        STATUS          current
        DESCRIPTION     "priorityIndex equals priority plus 1 - priority can't be
			used as an index since it starts from 0"
        ::= { rcCfmFdStatsCurrEntry 5}

rcCfmFdStatsCurrMdName OBJECT-TYPE
        SYNTAX          DisplayString(SIZE(1..22))
        MAX-ACCESS      read-only
        STATUS          current
        DESCRIPTION     "Maintenance Domain Name"
        ::= { rcCfmFdStatsCurrEntry 6}

rcCfmFdStatsCurrMaName OBJECT-TYPE
        SYNTAX          DisplayString(SIZE(1..22))
        MAX-ACCESS      read-only
        STATUS          current
        DESCRIPTION     "Maintenance Association Name"
        ::= { rcCfmFdStatsCurrEntry 7}

rcCfmFdStatsCurrPriority OBJECT-TYPE
        SYNTAX          Integer32 (0..7)
        MAX-ACCESS      read-only 
        STATUS          current
        DESCRIPTION     "Frame Delay messaaging runs on COS priority"
	DEFVAL { 7 }
        ::= { rcCfmFdStatsCurrEntry 8}

rcCfmFdStatsCurrFdPercent OBJECT-TYPE
        SYNTAX          Integer32 (0..99)
        MAX-ACCESS      read-only
        STATUS          current
        DESCRIPTION     "Measured FD percentage"
        ::= { rcCfmFdStatsCurrEntry 9}

rcCfmFdStatsCurrFdSubPercent OBJECT-TYPE
        SYNTAX          Integer32 (0..99)
        MAX-ACCESS      read-only
        STATUS          current
        DESCRIPTION     "Measured FD sub percentage"
        ::= { rcCfmFdStatsCurrEntry 10}

rcCfmFdStatsCurrFdvPercent OBJECT-TYPE
        SYNTAX          Integer32 (0..99)
        MAX-ACCESS      read-only
        STATUS          current
        DESCRIPTION     "Measured FDV percentage"
        ::= { rcCfmFdStatsCurrEntry 11}

rcCfmFdStatsCurrFdvSubPercent OBJECT-TYPE
        SYNTAX          Integer32 (0..99)
        MAX-ACCESS      read-only
        STATUS          current
        DESCRIPTION     "Measured FDV sub percentage"
        ::= { rcCfmFdStatsCurrEntry 12}

rcCfmFdStatsCurrPmOperState OBJECT-TYPE
        SYNTAX          RcCfmPmOperState
        MAX-ACCESS      read-only
        STATUS          current
        DESCRIPTION     "The operational state of the PM."
        ::= {rcCfmFdStatsCurrEntry 13}

rcCfmFdStatsCurrStartTime  OBJECT-TYPE
	SYNTAX          OCTET STRING (SIZE(11))
        MAX-ACCESS      read-only
        STATUS          current
        DESCRIPTION     "The date and time stamp."
        ::= { rcCfmFdStatsCurrEntry 14}

rcCfmFdStatsCurrEndTime  OBJECT-TYPE
	SYNTAX          OCTET STRING (SIZE(11))
        MAX-ACCESS      read-only
        STATUS          current
        DESCRIPTION     "The date and time stamp."
        ::= { rcCfmFdStatsCurrEntry 15}

rcCfmFdStatsCurrHistInterval  OBJECT-TYPE
        SYNTAX          Gauge32
        MAX-ACCESS      read-only
        STATUS          current
        DESCRIPTION     "History Interval"
        ::= { rcCfmFdStatsCurrEntry 16}

rcCfmFdStatsCurrSampleRate  OBJECT-TYPE
        SYNTAX          Gauge32
        MAX-ACCESS      read-only
        STATUS          current
        DESCRIPTION     "Sample rate in seconds"
        ::= { rcCfmFdStatsCurrEntry 17}

rcCfmFdStatsCurrTarget OBJECT-TYPE
        SYNTAX          Counter32
        MAX-ACCESS      read-only
        STATUS          current
        DESCRIPTION     "FD target in microseconds"
        ::= { rcCfmFdStatsCurrEntry 18}

rcCfmFdStatsCurrAverage OBJECT-TYPE
        SYNTAX          Counter32
        MAX-ACCESS      read-only
        STATUS          current
        DESCRIPTION     "FD average in microseconds"
        ::= { rcCfmFdStatsCurrEntry 19}

rcCfmFdStatsCurrMinimum OBJECT-TYPE
        SYNTAX          Counter32
        MAX-ACCESS      read-only
        STATUS          current
        DESCRIPTION     "FD minimum in microseconds"
        ::= { rcCfmFdStatsCurrEntry 20}

rcCfmFdStatsCurrMaximum OBJECT-TYPE
        SYNTAX          Counter32
        MAX-ACCESS      read-only
        STATUS          current
        DESCRIPTION     "FD maximum in microseconds"
        ::= { rcCfmFdStatsCurrEntry 21}

rcCfmFdStatsCurrFdvTarget OBJECT-TYPE
        SYNTAX          Counter32
        MAX-ACCESS      read-only
        STATUS          current
        DESCRIPTION     "FDV target in microseconds"
        ::= { rcCfmFdStatsCurrEntry 22}

rcCfmFdStatsCurrFdvAverage OBJECT-TYPE
        SYNTAX          Counter32
        MAX-ACCESS      read-only
        STATUS          current
        DESCRIPTION     "FDV average in microseconds"
        ::= { rcCfmFdStatsCurrEntry 23}

rcCfmFdStatsCurrFdvMinimum OBJECT-TYPE
        SYNTAX          Counter32
        MAX-ACCESS      read-only
        STATUS          current
        DESCRIPTION     "FDV minimum in microseconds"
        ::= { rcCfmFdStatsCurrEntry 24}

rcCfmFdStatsCurrFdvMaximum OBJECT-TYPE
        SYNTAX          Counter32
        MAX-ACCESS      read-only
        STATUS          current
        DESCRIPTION     "FDV maximum in microseconds"
        ::= { rcCfmFdStatsCurrEntry 25}

rcCfmFdStatsCurrSamplesPerInterval  OBJECT-TYPE
        SYNTAX          Gauge32
        MAX-ACCESS      read-only
        STATUS          current
        DESCRIPTION     "Samples per interval"
        ::= { rcCfmFdStatsCurrEntry 26}

rcCfmFdStatsCurrSamplesTransmitted  OBJECT-TYPE
        SYNTAX          Gauge32
        MAX-ACCESS      read-only
        STATUS          current
        DESCRIPTION     "Samples transmitted"
        ::= { rcCfmFdStatsCurrEntry 27}

rcCfmFdStatsCurrSamplesNotSent  OBJECT-TYPE
        SYNTAX          Gauge32
        MAX-ACCESS      read-only
        STATUS          current
        DESCRIPTION     "Samples not sent"
        ::= { rcCfmFdStatsCurrEntry 28}

rcCfmFdStatsCurrSamplesReceived  OBJECT-TYPE
        SYNTAX          Gauge32
        MAX-ACCESS      read-only
        STATUS          current
        DESCRIPTION     "Samples received"
        ::= { rcCfmFdStatsCurrEntry 29}


-- Frame Delay Stats History Table

rcCfmFdStatsHistTable OBJECT-TYPE
        SYNTAX          SEQUENCE OF RcCfmFdStatsHistEntry
        MAX-ACCESS      not-accessible
        STATUS          current
        DESCRIPTION     "CFM Frame Delay Stats History"
        ::= { rcCfm 28}

rcCfmFdStatsHistEntry OBJECT-TYPE
        SYNTAX          RcCfmFdStatsHistEntry
        MAX-ACCESS      not-accessible
        STATUS          current
        DESCRIPTION     "CFM Frame Delay Stats History entry."
        INDEX           { rcCfmFdStatsHistMdIndex,
                          rcCfmFdStatsHistMaIndex,
                          rcCfmFdStatsHistMepId,
                          rcCfmFdStatsHistRmepId,
                          rcCfmFdStatsHistPriorityIndex}
        ::= { rcCfmFdStatsHistTable 1}

RcCfmFdStatsHistEntry ::=
        SEQUENCE {
                rcCfmFdStatsHistMdIndex                Integer32,
                rcCfmFdStatsHistMaIndex                Integer32,
                rcCfmFdStatsHistMepId                  Integer32,
                rcCfmFdStatsHistRmepId                 Integer32,
		rcCfmFdStatsHistPriorityIndex	       Integer32,
                rcCfmFdStatsHistIndex                  Integer32,
                rcCfmFdStatsHistMdName                 DisplayString,
                rcCfmFdStatsHistMaName                 DisplayString,
                rcCfmFdStatsHistPriority               Integer32,
                rcCfmFdStatsHistFdPercent              Integer32,
                rcCfmFdStatsHistFdSubPercent           Integer32,
                rcCfmFdStatsHistFdvPercent             Integer32,
                rcCfmFdStatsHistFdvSubPercent          Integer32,
                rcCfmFdStatsHistStatus                 INTEGER,
                rcCfmFdStatsHistStartTime              OCTET STRING ,
                rcCfmFdStatsHistEndTime                OCTET STRING ,
                rcCfmFdStatsHistHistInterval           Gauge32,
                rcCfmFdStatsHistSampleRate             Gauge32,
                rcCfmFdStatsHistTarget                 Counter32,
                rcCfmFdStatsHistAverage                Counter32,
                rcCfmFdStatsHistMinimum                Counter32,
                rcCfmFdStatsHistMaximum                Counter32,
                rcCfmFdStatsHistFdvTarget              Counter32,
                rcCfmFdStatsHistFdvAverage             Counter32,
                rcCfmFdStatsHistFdvMinimum             Counter32,
                rcCfmFdStatsHistFdvMaximum             Counter32,
		rcCfmFdStatsHistSamplesPerInterval     Gauge32,
                rcCfmFdStatsHistSamplesTransmitted     Gauge32,
		rcCfmFdStatsHistSamplesNotSent         Gauge32,
                rcCfmFdStatsHistSamplesReceived        Gauge32
                }

rcCfmFdStatsHistMdIndex OBJECT-TYPE
        SYNTAX          Integer32 (1..2147483647)
        MAX-ACCESS      not-accessible
        STATUS          current
        DESCRIPTION     "Maintenance Domain Name"
        ::= { rcCfmFdStatsHistEntry 1}

rcCfmFdStatsHistMaIndex OBJECT-TYPE
        SYNTAX          Integer32 (1..2147483647)
        MAX-ACCESS      not-accessible
        STATUS          current
        DESCRIPTION     "Maintenance Association Name"
        ::= { rcCfmFdStatsHistEntry 2}

rcCfmFdStatsHistMepId OBJECT-TYPE
        SYNTAX          Integer32 (1..8191)
        MAX-ACCESS      not-accessible
        STATUS          current
        DESCRIPTION     "Maintenance EndPoint ID"
        ::= { rcCfmFdStatsHistEntry 3}

rcCfmFdStatsHistRmepId OBJECT-TYPE
        SYNTAX          Integer32 (1..8191)
        MAX-ACCESS      not-accessible
        STATUS          current
        DESCRIPTION     "Peer Identifier which matches a RemoteMepId.
                         The performance monitoring pair is MepId-RmepId"
        ::= { rcCfmFdStatsHistEntry 4}

rcCfmFdStatsHistPriorityIndex OBJECT-TYPE
        SYNTAX          Integer32 (1..8)
        MAX-ACCESS      not-accessible 
        STATUS          current
        DESCRIPTION     "priorityIndex equals priority plus 1 - priority can't be
			used as an index since it starts from 0"
        ::= { rcCfmFdStatsHistEntry 5}

rcCfmFdStatsHistIndex OBJECT-TYPE
        SYNTAX          Integer32 (1..1000)
        MAX-ACCESS      not-accessible 
        STATUS          current
        DESCRIPTION     "History Index"
        ::= { rcCfmFdStatsHistEntry 6}

rcCfmFdStatsHistMdName OBJECT-TYPE
        SYNTAX          DisplayString(SIZE(1..22))
        MAX-ACCESS      read-only
        STATUS          current
        DESCRIPTION     "Maintenance Domain Name"
        ::= { rcCfmFdStatsHistEntry 7}

rcCfmFdStatsHistMaName OBJECT-TYPE
        SYNTAX          DisplayString(SIZE(1..22))
        MAX-ACCESS      read-only
        STATUS          current
        DESCRIPTION     "Maintenance Association Name"
        ::= { rcCfmFdStatsHistEntry 8}

rcCfmFdStatsHistPriority OBJECT-TYPE
        SYNTAX          Integer32 (0..7)
        MAX-ACCESS      read-only 
        STATUS          current
        DESCRIPTION     "Frame Delay messaging runs on COS priority"
	DEFVAL { 7 }
        ::= { rcCfmFdStatsHistEntry 9}

rcCfmFdStatsHistFdPercent OBJECT-TYPE
        SYNTAX          Integer32 (0..99)
        MAX-ACCESS      read-only
        STATUS          current
        DESCRIPTION     "Measured FD percentage"
        ::= { rcCfmFdStatsHistEntry 10}

rcCfmFdStatsHistFdSubPercent OBJECT-TYPE
        SYNTAX          Integer32 (0..99)
        MAX-ACCESS      read-only
        STATUS          current
        DESCRIPTION     "Measured FD sub percentage"
        ::= { rcCfmFdStatsHistEntry 11}

rcCfmFdStatsHistFdvPercent OBJECT-TYPE
        SYNTAX          Integer32 (0..99)
        MAX-ACCESS      read-only
        STATUS          current
        DESCRIPTION     "Measured FDV percentage"
        ::= { rcCfmFdStatsHistEntry 12}

rcCfmFdStatsHistFdvSubPercent OBJECT-TYPE
        SYNTAX          Integer32 (0..99)
        MAX-ACCESS      read-only
        STATUS          current
        DESCRIPTION     "Measured FDV sub percentage"
        ::= { rcCfmFdStatsHistEntry 13}

rcCfmFdStatsHistStatus OBJECT-TYPE
        SYNTAX          INTEGER {
	                   complete(1),
			   incomplete(2)
	                }
        MAX-ACCESS      read-only
        STATUS          current
        DESCRIPTION
           "The status of this history interval."
        ::= {rcCfmFdStatsHistEntry 14}

rcCfmFdStatsHistStartTime  OBJECT-TYPE
	SYNTAX          OCTET STRING (SIZE(11))
        MAX-ACCESS      read-only
        STATUS          current
        DESCRIPTION     "The date and time stamp."
        ::= { rcCfmFdStatsHistEntry 15}

rcCfmFdStatsHistEndTime  OBJECT-TYPE
	SYNTAX          OCTET STRING (SIZE(11))
        MAX-ACCESS      read-only
        STATUS          current
        DESCRIPTION     "The date and time stamp."
        ::= { rcCfmFdStatsHistEntry 16}

rcCfmFdStatsHistHistInterval  OBJECT-TYPE
        SYNTAX          Gauge32
        MAX-ACCESS      read-only
        STATUS          current
        DESCRIPTION     "History Interval"
        ::= { rcCfmFdStatsHistEntry 17}

rcCfmFdStatsHistSampleRate  OBJECT-TYPE
        SYNTAX          Gauge32
        MAX-ACCESS      read-only
        STATUS          current
        DESCRIPTION     "Sample rate in seconds"
        ::= { rcCfmFdStatsHistEntry 18}

rcCfmFdStatsHistTarget OBJECT-TYPE
        SYNTAX          Counter32
        MAX-ACCESS      read-only
        STATUS          current
        DESCRIPTION     "FD target in microseconds"
        ::= { rcCfmFdStatsHistEntry 19}

rcCfmFdStatsHistAverage OBJECT-TYPE
        SYNTAX          Counter32
        MAX-ACCESS      read-only
        STATUS          current
        DESCRIPTION     "FD average in microseconds"
        ::= { rcCfmFdStatsHistEntry 20}

rcCfmFdStatsHistMinimum OBJECT-TYPE
        SYNTAX          Counter32
        MAX-ACCESS      read-only
        STATUS          current
        DESCRIPTION     "FD minimum in microseconds"
        ::= { rcCfmFdStatsHistEntry 21}

rcCfmFdStatsHistMaximum OBJECT-TYPE
        SYNTAX          Counter32
        MAX-ACCESS      read-only
        STATUS          current
        DESCRIPTION     "FD maximum in microseconds"
        ::= { rcCfmFdStatsHistEntry 22}

rcCfmFdStatsHistFdvTarget OBJECT-TYPE
        SYNTAX          Counter32
        MAX-ACCESS      read-only
        STATUS          current
        DESCRIPTION     "FDV target in microseconds"
        ::= { rcCfmFdStatsHistEntry 23}

rcCfmFdStatsHistFdvAverage OBJECT-TYPE
        SYNTAX          Counter32
        MAX-ACCESS      read-only
        STATUS          current
        DESCRIPTION     "FDV average in microseconds"
        ::= { rcCfmFdStatsHistEntry 24}

rcCfmFdStatsHistFdvMinimum OBJECT-TYPE
        SYNTAX          Counter32
        MAX-ACCESS      read-only
        STATUS          current
        DESCRIPTION     "FDV minimum in microseconds"
        ::= { rcCfmFdStatsHistEntry 25}

rcCfmFdStatsHistFdvMaximum OBJECT-TYPE
        SYNTAX          Counter32
        MAX-ACCESS      read-only
        STATUS          current
        DESCRIPTION     "FDV maximum in microseconds"
        ::= { rcCfmFdStatsHistEntry 26}

rcCfmFdStatsHistSamplesPerInterval  OBJECT-TYPE
        SYNTAX          Gauge32
        MAX-ACCESS      read-only
        STATUS          current
        DESCRIPTION     "Samples per interval"
        ::= { rcCfmFdStatsHistEntry 27}

rcCfmFdStatsHistSamplesTransmitted  OBJECT-TYPE
        SYNTAX          Gauge32
        MAX-ACCESS      read-only
        STATUS          current
        DESCRIPTION     "Samples transmitted"
        ::= { rcCfmFdStatsHistEntry 28}

rcCfmFdStatsHistSamplesNotSent  OBJECT-TYPE
        SYNTAX          Gauge32
        MAX-ACCESS      read-only
        STATUS          current
        DESCRIPTION     "Samples not sent"
        ::= { rcCfmFdStatsHistEntry 29}

rcCfmFdStatsHistSamplesReceived  OBJECT-TYPE
        SYNTAX          Gauge32
        MAX-ACCESS      read-only
        STATUS          current
        DESCRIPTION     "Samples received"
        ::= { rcCfmFdStatsHistEntry 30}


-- Performance Monitoring Configuration Table

rcCfmPmTable OBJECT-TYPE
	SYNTAX		SEQUENCE OF RcCfmPmEntry
	MAX-ACCESS	not-accessible
	STATUS		current
	DESCRIPTION	"CFM Performance Monitoring Configuration"
	::= { rcCfm 29}

rcCfmPmEntry OBJECT-TYPE
	SYNTAX		RcCfmPmEntry
	MAX-ACCESS	not-accessible
	STATUS		current
	DESCRIPTION	"Connectivity Fault Management Performance Monitoring entry."
	INDEX		{rcCfmPmMdIndex, rcCfmPmMaIndex, rcCfmPmMepId, rcCfmPmRmepId }
	::= { rcCfmPmTable 1}

RcCfmPmEntry ::=
	SEQUENCE {
                rcCfmPmMdIndex                Integer32,
                rcCfmPmMaIndex                Integer32,
                rcCfmPmMepId                  Integer32,
                rcCfmPmRmepId                 Integer32,
                rcCfmPmMdName                 DisplayString,
                rcCfmPmMaName                 DisplayString,
                rcCfmPmRowStatus              RowStatus,
                rcCfmPmState                  EnableValue,
                rcCfmPmFdList                 DisplayString,
                rcCfmPmFdSize                 Integer32,
                rcCfmPmFlrList                DisplayString,
                rcCfmPmFlrSize                Integer32,
                rcCfmPmHistoryInterval        INTEGER,
		rcCfmPmSampleRate             INTEGER
		}

rcCfmPmMdIndex OBJECT-TYPE
	SYNTAX		Integer32 (1..2147483647)
	MAX-ACCESS	not-accessible
	STATUS		current
	DESCRIPTION	"Maintenance Domain Name"
	::= { rcCfmPmEntry 1}

rcCfmPmMaIndex OBJECT-TYPE
	SYNTAX		Integer32 (1..2147483647)
	MAX-ACCESS	not-accessible
	STATUS		current
	DESCRIPTION	"Maintenance Association Name"
	::= { rcCfmPmEntry 2}

rcCfmPmMepId OBJECT-TYPE
	SYNTAX		Integer32 (1..8191)
	MAX-ACCESS	not-accessible
	STATUS		current
	DESCRIPTION	"Maintenance EndPoint ID"
	::= { rcCfmPmEntry 3}

rcCfmPmRmepId OBJECT-TYPE
	SYNTAX		Integer32 (1..8191)
	MAX-ACCESS	not-accessible
	STATUS		current
	DESCRIPTION	"Remote Maintenance Endpoint ID.  
                         The performance monitoring pair is MepId-RmepId"
	::= { rcCfmPmEntry 4}

rcCfmPmMdName OBJECT-TYPE
	SYNTAX		DisplayString(SIZE(1..22))
	MAX-ACCESS	read-only
	STATUS		current
	DESCRIPTION	"Maintenance Domain Name"
	::= { rcCfmPmEntry 5}

rcCfmPmMaName OBJECT-TYPE
	SYNTAX		DisplayString(SIZE(1..22))
	MAX-ACCESS	read-only
	STATUS		current
	DESCRIPTION	"Maintenance Association Name"
	::= { rcCfmPmEntry 6}

rcCfmPmRowStatus OBJECT-TYPE
	SYNTAX		RowStatus
	MAX-ACCESS	read-create
	STATUS		current
	DESCRIPTION	"Used to create/delete entries"
	::= { rcCfmPmEntry 7 }

rcCfmPmState OBJECT-TYPE
        SYNTAX          EnableValue
        MAX-ACCESS      read-create
        STATUS          current
        DESCRIPTION     "Performance Monitoring State"
        DEFVAL { disable }
	::= { rcCfmPmEntry 8 }

rcCfmPmFdList OBJECT-TYPE
        SYNTAX          DisplayString (SIZE(0..200))
        MAX-ACCESS      read-create
        STATUS          current
        DESCRIPTION
          "Comma separated list of Frame-Delay profile names.
           Valid profile names must first be created using rcCfmFdProfileName.
           Number of entries in the list is indicated by rcCfmPmFdSize."
	::= { rcCfmPmEntry 9 }

rcCfmPmFdSize OBJECT-TYPE
        SYNTAX          Integer32 (0..8)
        MAX-ACCESS      read-only
        STATUS          current
        DESCRIPTION     "Number of Frame-Delay profiles names"
        ::= { rcCfmPmEntry 10 }

rcCfmPmFlrList OBJECT-TYPE
        SYNTAX          DisplayString (SIZE(0..200))
        MAX-ACCESS      read-create
        STATUS          current
        DESCRIPTION     
          "Comma separated list of Frame-Loss-Ratio profile names.
           Valid profile names must first be created using rcCfmFlrProfileName.
           Number of entries in the list is indicated by rcCfmPmFlrSize."
	::= { rcCfmPmEntry 11 }

rcCfmPmFlrSize OBJECT-TYPE
        SYNTAX          Integer32 (0..8)
        MAX-ACCESS      read-only
        STATUS          current
        DESCRIPTION     "Number of FLR profile names in FLR list"
        ::= { rcCfmPmEntry 12 }

rcCfmPmHistoryInterval OBJECT-TYPE
	SYNTAX		INTEGER {
                           hi5(5),
                           hi15(15),
                           hi30(30),
                           hi60(60),
                           hi120(120),
                           hi360(360),
                           hi720(720),
                           hi1440(1440)
	                }
	UNITS           "minutes"
	MAX-ACCESS	read-create
	STATUS		current
	DESCRIPTION	"History summary interval in minutes"
        DEFVAL { hi15 }
	::= { rcCfmPmEntry 13}

rcCfmPmSampleRate OBJECT-TYPE
        SYNTAX          INTEGER {
	                   si1(1),
			   si10(10),
			   si30(30),
			   si60(60),
			   si900(900),
			   si1800(1800),
			   si3600(3600)
	                }
	UNITS           "seconds"
        MAX-ACCESS      read-create 
        STATUS          current
        DESCRIPTION     "Sample rate once per sample interval specified in seconds"
        DEFVAL { si30 }
	::= { rcCfmPmEntry 14}

-- Linktrace Reply Table

CfmRelayActionFieldValue ::= TEXTUAL-CONVENTION
    STATUS current
    DESCRIPTION
            "Possible values the Relay action field can take."
    REFERENCE
            "802.1ag clauses 12.14.7.5.3:g, 20.36.2.5, 21.9.5, and
             Table 21-27"
    SYNTAX INTEGER {
             rlyHit (1),
             rlyFdb (2),
             rlyMpdb (3),
	     unknown (4)
    }

CfmIngressActionFieldValue ::= TEXTUAL-CONVENTION
    STATUS current
    DESCRIPTION
            "Possible values returned in the ingress action field."
    REFERENCE
            "802.1ag clauses 12.14.7.5.3:g, 20.36.2.6, 21.9.8.1, and
            Table 21-30"
    SYNTAX INTEGER {
             ingOk (1),
             ingDown (2),
             ingBlocked (3),
             ingVid (4),
             ingNoTlv (5)
    }

CfmEgressActionFieldValue ::= TEXTUAL-CONVENTION
    STATUS current
    DESCRIPTION
            "Possible values returned in the egress action field"
    REFERENCE
            "802.1ag clauses 12.14.7.5.3:o, 20.36.2.10, 21.9.9.1, and
             Table 21-32"
    SYNTAX INTEGER {
             egrOk (1),
             egrDown (2),
             egrBlocked (3),
             egrVid (4),
             egrNoTlv (5)
    }

LldpPortIdSubtype ::= TEXTUAL-CONVENTION
    STATUS      current
    DESCRIPTION
            "This TC describes the source of a particular type of Port 
             identifier used in the LLDP MIB. The enumeration 'interfaceAlias(1)'
             represents a port identifier based on the ifAlias MIB object, 
             defined in IETF RFC 2863. The enumeration 'portComponent(2)'
             represents a port identifier based on the value of 
             entPhysicalAlias (defined in IETF RFC 2737) for a port component 
             (i.e., entPhysicalClass value of 'port(10)'), within the 
             containing chassis. The enumeration 'macAddress(3)' represents a 
             port identifier based on a unicast source address (encoded in 
             network byte order and IEEE 802.3 canonical bit order), which has
             been detected by the agent and associated with a particular port 
             (IEEE Std 802-2001). The enumeration 'networkAddress(4)' represents
             a port identifier based on a network address, detected by the 
             agent and associated with a particular port. The enumeration 
             'interfaceName(5)' represents a port identifier based on the 
             ifName MIB object, defined in IETF RFC 2863. The enumeration
             'agentCircuitId(6)' represents a port identifier based on the 
             agent-local identifier of the circuit (defined in RFC 3046), 
             detected by the agent and associated with a particular port. The 
             enumeration 'local(7)' represents a port identifier based on a 
             value locally assigned."
    SYNTAX   INTEGER {
             interfaceAlias(1),
             portComponent(2),
             macAddress(3),
             networkAddress(4),
             interfaceName(5),
             agentCircuitId(6),
             local(7)
    }

LldpPortId ::= TEXTUAL-CONVENTION
    DISPLAY-HINT "1a"
    STATUS      current
    DESCRIPTION
            "This TC describes the format of a port identifier string. 
            Objects of this type are always used with an associated 
            LldpPortIdSubtype object, which identifies the format of the 
            particular LldpPortId object instance. If the associated 
            LldpPortIdSubtype object has a value of 
            '342/200/230interfaceAlias(1)', then the octet string identifies 
            a particular instance of the ifAlias object (defined in IETF RFC 
            2863). If the particular ifAlias object does not contain any
            values, another port identifier type should be used. If the 
            associated LldpPortIdSubtype object has a value of 
            'portComponent(2)', then the octet string identifies a particular 
            instance of the entPhysicalAlias object (defined in IETF RFC 2737)
            for a port or backplane component. If the associated 
            LldpPortIdSubtype object has a value of 'macAddress(3)', then 
            this string identifies a Particular unicast source address 
            (encoded in network byte order and IEEE 802.3 canonical bit order)
            associated with the port (IEEE Std 802-2001). If the associated 
            LldpPortIdSubtype object has a value of 'networkAddress(4)', then 
            this string identifies a Network address associated with the port. 
            The first octet contains the IANA AddressFamilyNumbers enumeration 
            value for the specific address type, and octets 2 through N 
            contain the networkAddress address value in network byte order. If 
            the associated LldpPortIdSubtype object has a value of 
            'interfaceName(5)', then the octet string identifies A particular 
            instance of the ifName object (defined in IETF RFC 2863). If the 
            particular ifName object does not contain any values, another port 
            identifier type should be used. If the associated ldpPortIdSubtype 
            object has a value of 'agentCircuitId(6)', then this string 
            identifies a agent-local identifier of the circuit (defined in RFC
            3046). If the associated LldpPortIdSubtype object has a value of 
            '342/200/230local(7)', then this string identifies a locally 
            assigned port ID."
    SYNTAX      OCTET STRING (SIZE (1..255))

-- The Linktrace Reply Table


rcCfmLtrTable OBJECT-TYPE
        SYNTAX          SEQUENCE OF RcCfmLtrEntry
        MAX-ACCESS      not-accessible
        STATUS          current 
        DESCRIPTION     
                "This table contains a list of Linktrace replies received 
                by a specific MEP in response to a linktrace message."
        ::= { rcCfm 32}

rcCfmLtrEntry OBJECT-TYPE
        SYNTAX          RcCfmLtrEntry
        MAX-ACCESS      not-accessible
        STATUS          current
        DESCRIPTION     "The Linktrace Reply table entry."
        INDEX           {rcCfmLtrDomainIndex, rcCfmLtrAssociationIndex,
                         rcCfmLtrMepId, rcCfmLtrSeqNumber, rcCfmLtrTtl,
                         rcCfmLtrReceiveOrder}
        ::= { rcCfmLtrTable 1}
    
RcCfmLtrEntry ::=
        SEQUENCE {
                rcCfmLtrDomainIndex          Integer32,
                rcCfmLtrAssociationIndex     Integer32,
                rcCfmLtrMepId                Integer32,
		rcCfmLtrSeqNumber            Integer32,
	        rcCfmLtrTtl                  Integer32,
                rcCfmLtrReceiveOrder         Integer32,
		rcCfmLtrDomainName           DisplayString,
                rcCfmLtrAssociationName      DisplayString,
		rcCfmLtrForwarded            TruthValue,
                rcCfmLtrTerminalMep          TruthValue,
                rcCfmLtrLastEgressIdentifier OCTET STRING,
                rcCfmLtrNextEgressIdentifier OCTET STRING,
                rcCfmLtrRelayAction          CfmRelayActionFieldValue,
                rcCfmLtrSrcMac               MacAddress,
                rcCfmLtrIngressAction        CfmIngressActionFieldValue,
                rcCfmLtrIngressMac           MacAddress,
                rcCfmLtrIngressPortIdSubtype LldpPortIdSubtype,
                rcCfmLtrIngressPortId        LldpPortId,
                rcCfmLtrEgressAction         CfmEgressActionFieldValue,
                rcCfmLtrEgressMac            MacAddress, 
                rcCfmLtrEgressPortIdSubtype  LldpPortIdSubtype,
                rcCfmLtrEgressPortId         LldpPortId
             }
rcCfmLtrDomainIndex OBJECT-TYPE
        SYNTAX          Integer32 (1..2147483647)
        MAX-ACCESS      not-accessible
        STATUS          current
        DESCRIPTION     "Maintenance Domain Index"
        ::= { rcCfmLtrEntry 1}

rcCfmLtrAssociationIndex OBJECT-TYPE
        SYNTAX          Integer32 (1..2147483647) 
        MAX-ACCESS      not-accessible
        STATUS          current
        DESCRIPTION     "Maintenance Association Index"
        ::= { rcCfmLtrEntry 2}
    
rcCfmLtrMepId OBJECT-TYPE
        SYNTAX          Integer32 (1..8191)
        MAX-ACCESS      not-accessible
        STATUS          current
        DESCRIPTION     "Maintenance EndPoint ID"
        ::= { rcCfmLtrEntry 3}

rcCfmLtrSeqNumber OBJECT-TYPE
        SYNTAX          Integer32 (0..2147483647)  
        MAX-ACCESS      not-accessible
        STATUS          current
        DESCRIPTION     
                "The transaction identifier/sequence number returned by a 
                previous transmit linkrace message command, indicating which 
                LTM's response is going to be returned."
        ::= { rcCfmLtrEntry 4}

rcCfmLtrTtl     OBJECT-TYPE
        SYNTAX          Integer32 (0..255)
        MAX-ACCESS      not-accessible
        STATUS          current
        DESCRIPTION     "Ttl field value for a returned LTR."
        ::= { rcCfmLtrEntry 5}

rcCfmLtrReceiveOrder OBJECT-TYPE
        SYNTAX          Integer32 (1..2147483647)
        MAX-ACCESS      not-accessible
        STATUS          current
        DESCRIPTION     
                "An index to distinguish among multiple LTRs with the same 
                LTR Transaction Identifier field  value. This value is 
                assigned sequentially from 1, in the order that the Linktrace 
                Initiator received the LTRs."
        ::= { rcCfmLtrEntry 6}

rcCfmLtrDomainName OBJECT-TYPE
        SYNTAX          DisplayString(SIZE(1..22))
        MAX-ACCESS      read-only
        STATUS          current
        DESCRIPTION     "Maintenance Domain Name"
        ::= { rcCfmLtrEntry 7}

rcCfmLtrAssociationName OBJECT-TYPE
        SYNTAX          DisplayString(SIZE(1..22))
        MAX-ACCESS      read-only
        STATUS          current
        DESCRIPTION     "Maintenance Association Name"
        ::= { rcCfmLtrEntry 8}

rcCfmLtrForwarded OBJECT-TYPE
        SYNTAX          TruthValue
        MAX-ACCESS      read-only
        STATUS          current
        DESCRIPTION     
                "Indicates if a LTM was forwarded by the responding MP, as 
                returned in the 'FwdYes' flag of the flags field."
        ::= { rcCfmLtrEntry 9}

rcCfmLtrTerminalMep OBJECT-TYPE
        SYNTAX          TruthValue
        MAX-ACCESS      read-only
        STATUS          current
        DESCRIPTION     
                "A boolean value stating whether the forwarded LTM reached 
                a MEP enclosing its MA, as returned in the Terminal MEP flag 
                of the Flags field."
        ::= { rcCfmLtrEntry 10}

rcCfmLtrLastEgressIdentifier OBJECT-TYPE
        SYNTAX          OCTET STRING (SIZE(8))
        MAX-ACCESS      read-only 
        STATUS          current
        DESCRIPTION     
                "An octet field holding the Last Egress Identifier returned 
                in the LTR Egress   Identifier TLV of the LTR. The Last Egress 
                Identifier identifies the MEP Linktrace Indicator that 
                originated, or the Linktrace Responder that forwarded, the LTM 
                to which this LTR is the response. This is the same value as 
                the Egress Identifier TLV of that LTM."
        ::= { rcCfmLtrEntry 11}


rcCfmLtrNextEgressIdentifier OBJECT-TYPE
        SYNTAX          OCTET STRING (SIZE(8))
        MAX-ACCESS      read-only 
        STATUS          current
        DESCRIPTION     
                "An octet field holding the Next Egress Identifier returned in 
                the LTR Egress Identifier TLV of the LTR. The Next Egress 
                Identifier Identifies the Linktrace Responder that transmitted 
                this LTR, and can forward the LTM to the next hop. This is the 
                same value as the Egress Identifier TLV of the forwarded LTM, 
                if any. If the FwdYes bit of the Flags field is false, the 
                contents of this field are undefined, and the field is ignored 
                by the receiver."
        ::= { rcCfmLtrEntry 12}

rcCfmLtrRelayAction OBJECT-TYPE
        SYNTAX          CfmRelayActionFieldValue
        MAX-ACCESS      read-only 
        STATUS           current
        DESCRIPTION     "Value returned in the Relay Action field."
	DEFVAL          { unknown }     
        ::= { rcCfmLtrEntry 13}


rcCfmLtrSrcMac OBJECT-TYPE
        SYNTAX          MacAddress
        MAX-ACCESS      read-only
        STATUS          current
        DESCRIPTION     
                "Mac address of the MP that respond to the LTM request for 
                this LTR"  
        ::= { rcCfmLtrEntry 14}

rcCfmLtrIngressAction OBJECT-TYPE 
        SYNTAX          CfmIngressActionFieldValue
        MAX-ACCESS      read-only
        STATUS          current
        DESCRIPTION     
                "The value returned in the Ingress Action Field of the LTM. 
                The value ingNoTlv(5) indicates that no Reply Ingress TLV 
                was returned in the LTM."
        ::= { rcCfmLtrEntry 15} 

rcCfmLtrIngressMac OBJECT-TYPE
        SYNTAX          MacAddress
        MAX-ACCESS      read-only
        STATUS          current
        DESCRIPTION     
                "Mac address returned in the ingress MAC address field. If the 
                rcCfmLtrIngress object contains the value ingNoTlv(5), then 
                the contents of this object are meaningless."
        ::= { rcCfmLtrEntry 16}

rcCfmLtrIngressPortIdSubtype OBJECT-TYPE
        SYNTAX          LldpPortIdSubtype
        MAX-ACCESS      read-only
        STATUS          current
        DESCRIPTION     
                "Format of the Ingress Port ID. If the rcCfmLtrIngress object 
                contains the value ingNoTlv(5), then the contents of this 
                object are meaningless."
        ::= { rcCfmLtrEntry 17}

rcCfmLtrIngressPortId OBJECT-TYPE
        SYNTAX          LldpPortId
        MAX-ACCESS      read-only
        STATUS          current
        DESCRIPTION     
                "Ingress Port ID. The format of this object is determined by 
                the value of the rcCfmLtrIngressPortIdSubtype object. If the 
                rcCfmLtrIngress object contains the value ingNoTlv(5), then 
                the contents of this object are meaningless."
        ::= { rcCfmLtrEntry 18}

rcCfmLtrEgressAction OBJECT-TYPE
        SYNTAX          CfmEgressActionFieldValue
        MAX-ACCESS      read-only
        STATUS          current
        DESCRIPTION     
                "The value returned in the Egress Action Field of the LTM. The 
                value egrNoTlv(5) indicates that no Reply Egress TLV was 
                returned in the LTM."
        ::= { rcCfmLtrEntry 19}

rcCfmLtrEgressMac OBJECT-TYPE
        SYNTAX          MacAddress
        MAX-ACCESS      read-only
        STATUS          current
        DESCRIPTION     
                "Mac address returned in the egress MAC address field. If the 
                rcCfmLtrEgress object contains the value egrNoTlv(5), then the 
                contents of this object are meaningless."
        ::= { rcCfmLtrEntry 20}

rcCfmLtrEgressPortIdSubtype OBJECT-TYPE
        SYNTAX          LldpPortIdSubtype
        MAX-ACCESS      read-only
        STATUS          current
        DESCRIPTION     
                "Format of the Egress Port ID. If the rcCfmLtrEgress object 
                contains the value egrNoTlv(5), then the contents of this 
                object are meaningless."
        ::= { rcCfmLtrEntry 21}

rcCfmLtrEgressPortId OBJECT-TYPE
        SYNTAX          LldpPortId
        MAX-ACCESS      read-only
        STATUS          current
        DESCRIPTION     
                "Egress Port ID. The format of this object is determined by 
                the value of the rcCfmLtrEgressPortIdSubtype object. If the 
                rcCfmLtrEgress object contains the value egrNoTlv(5), then 
                the contents of this object are meaningless."
        ::= { rcCfmLtrEntry 22}

rcCfmLtrReplyTable OBJECT-TYPE
        SYNTAX          SEQUENCE OF RcCfmLtrReplyEntry
        MAX-ACCESS      not-accessible
        STATUS          current 
        DESCRIPTION     
                "This table contains a list of Linktrace replies received 
                by a specific MEP in response to a linktrace message."
        ::= { rcCfm 33}

rcCfmLtrReplyEntry OBJECT-TYPE
        SYNTAX          RcCfmLtrReplyEntry
        MAX-ACCESS      not-accessible
        STATUS          current
        DESCRIPTION     "The Linktrace Reply table entry."
        INDEX           {rcCfmLtrReplyDomainIndex, 
                         rcCfmLtrReplyAssociationIndex,
                         rcCfmLtrReplyMepId, 
                         rcCfmLtrReplySeqNumber, 
                         rcCfmLtrReplyHop,
                         rcCfmLtrReplyReceiveOrder}
        ::= { rcCfmLtrReplyTable 1}
    
RcCfmLtrReplyEntry ::=
        SEQUENCE {
                rcCfmLtrReplyDomainIndex          Integer32,
                rcCfmLtrReplyAssociationIndex     Integer32,
                rcCfmLtrReplyMepId                Integer32,
                rcCfmLtrReplySeqNumber            Integer32,
                rcCfmLtrReplyHop                  Integer32,
                rcCfmLtrReplyReceiveOrder         Integer32,
                rcCfmLtrReplyTtl                  Integer32,
                rcCfmLtrReplyDomainName           DisplayString,
                rcCfmLtrReplyAssociationName      DisplayString,
                rcCfmLtrReplyForwarded            TruthValue,
                rcCfmLtrReplyTerminalMep          TruthValue,
                rcCfmLtrReplyLastEgressIdentifier OCTET STRING,
                rcCfmLtrReplyNextEgressIdentifier OCTET STRING,
                rcCfmLtrReplyRelayAction          CfmRelayActionFieldValue,
                rcCfmLtrReplySrcMac               MacAddress,
                rcCfmLtrReplyIngressAction        CfmIngressActionFieldValue,
                rcCfmLtrReplyIngressMac           MacAddress,
                rcCfmLtrReplyIngressPortIdSubtype LldpPortIdSubtype,
                rcCfmLtrReplyIngressPortId        LldpPortId,
                rcCfmLtrReplyEgressAction         CfmEgressActionFieldValue,
                rcCfmLtrReplyEgressMac            MacAddress, 
                rcCfmLtrReplyEgressPortIdSubtype  LldpPortIdSubtype,
                rcCfmLtrReplyEgressPortId         LldpPortId
             }
rcCfmLtrReplyDomainIndex OBJECT-TYPE
        SYNTAX          Integer32 (1..2147483647)
        MAX-ACCESS      not-accessible
        STATUS          current
        DESCRIPTION     "Maintenance Domain Index"
        ::= { rcCfmLtrReplyEntry 1}

rcCfmLtrReplyAssociationIndex OBJECT-TYPE
        SYNTAX          Integer32 (1..2147483647) 
        MAX-ACCESS      not-accessible
        STATUS          current
        DESCRIPTION     "Maintenance Association Index"
        ::= { rcCfmLtrReplyEntry 2}
    
rcCfmLtrReplyMepId OBJECT-TYPE
        SYNTAX          Integer32 (1..8191)
        MAX-ACCESS      not-accessible
        STATUS          current
        DESCRIPTION     "Maintenance EndPoint ID"
        ::= { rcCfmLtrReplyEntry 3}

rcCfmLtrReplySeqNumber OBJECT-TYPE
        SYNTAX          Integer32 (0..2147483647)  
        MAX-ACCESS      not-accessible
        STATUS          current
        DESCRIPTION     
                "The transaction identifier/sequence number returned by a 
                previous transmit linktrace message command, indicating which 
                LTM's response is going to be returned."
        DEFVAL {0}
        ::= { rcCfmLtrReplyEntry 4}

rcCfmLtrReplyHop     OBJECT-TYPE
        SYNTAX          Integer32 (0..255)
        MAX-ACCESS      not-accessible
        STATUS          current
        DESCRIPTION     "The number of hops away from LTM initiator"
        ::= { rcCfmLtrReplyEntry 5}

rcCfmLtrReplyReceiveOrder OBJECT-TYPE
        SYNTAX          Integer32 (1..2147483647)
        MAX-ACCESS      not-accessible
        STATUS          current
        DESCRIPTION     
                "An index to distinguish among multiple LTRs with the same 
                LTR Transaction Identifier field  value. This value is 
                assigned sequentially from 1, in the order that the Linktrace 
                Initiator received the LTRs."
        ::= { rcCfmLtrReplyEntry 6}

rcCfmLtrReplyTtl     OBJECT-TYPE
        SYNTAX          Integer32 (0..255)
        MAX-ACCESS      read-only
        STATUS          current
        DESCRIPTION     "Ttl field value for a returned LTR."
        ::= { rcCfmLtrReplyEntry 7}

rcCfmLtrReplyDomainName OBJECT-TYPE
        SYNTAX          DisplayString(SIZE(1..22))
        MAX-ACCESS      read-only
        STATUS          current
        DESCRIPTION     "Maintenance Domain Name"
        ::= { rcCfmLtrReplyEntry 8}

rcCfmLtrReplyAssociationName OBJECT-TYPE
        SYNTAX          DisplayString(SIZE(1..22))
        MAX-ACCESS      read-only
        STATUS          current
        DESCRIPTION     "Maintenance Association Name"
        ::= { rcCfmLtrReplyEntry 9}

rcCfmLtrReplyForwarded OBJECT-TYPE
        SYNTAX          TruthValue
        MAX-ACCESS      read-only
        STATUS          current
        DESCRIPTION     
                "Indicates if a LTM was forwarded by the responding MP, as 
                returned in the 'FwdYes' flag of the flags field."
        ::= { rcCfmLtrReplyEntry 10}

rcCfmLtrReplyTerminalMep OBJECT-TYPE
        SYNTAX          TruthValue
        MAX-ACCESS      read-only
        STATUS          current
        DESCRIPTION     
                "A boolean value stating whether the forwarded LTM reached 
                a MEP enclosing its MA, as returned in the Terminal MEP flag 
                of the Flags field."
        ::= { rcCfmLtrReplyEntry 11}

rcCfmLtrReplyLastEgressIdentifier OBJECT-TYPE
        SYNTAX          OCTET STRING (SIZE(8))
        MAX-ACCESS      read-only 
        STATUS          current
        DESCRIPTION     
                "An octet field holding the Last Egress Identifier returned 
                in the LTR Egress   Identifier TLV of the LTR. The Last Egress 
                Identifier identifies the MEP Linktrace Indicator that 
                originated, or the Linktrace Responder that forwarded, the LTM 
                to which this LTR is the response. This is the same value as 
                the Egress Identifier TLV of that LTM."
        ::= { rcCfmLtrReplyEntry 12}


rcCfmLtrReplyNextEgressIdentifier OBJECT-TYPE
        SYNTAX          OCTET STRING (SIZE(8))
        MAX-ACCESS      read-only 
        STATUS          current
        DESCRIPTION     
                "An octet field holding the Next Egress Identifier returned in 
                the LTR Egress Identifier TLV of the LTR. The Next Egress 
                Identifier Identifies the Linktrace Responder that transmitted 
                this LTR, and can forward the LTM to the next hop. This is the 
                same value as the Egress Identifier TLV of the forwarded LTM, 
                if any. If the FwdYes bit of the Flags field is false, the 
                contents of this field are undefined, and the field is ignored 
                by the receiver."
        ::= { rcCfmLtrReplyEntry 13}

rcCfmLtrReplyRelayAction OBJECT-TYPE
        SYNTAX          CfmRelayActionFieldValue
        MAX-ACCESS      read-only 
        STATUS           current
        DESCRIPTION     "Value returned in the Relay Action field."
        DEFVAL          { unknown } 
        ::= { rcCfmLtrReplyEntry 14}


rcCfmLtrReplySrcMac OBJECT-TYPE
        SYNTAX          MacAddress
        MAX-ACCESS      read-only
        STATUS          current
        DESCRIPTION     
                "Mac address of the MP that respond to the LTM request for 
                this LTR"  
        ::= { rcCfmLtrReplyEntry 15}

rcCfmLtrReplyIngressAction OBJECT-TYPE 
        SYNTAX          CfmIngressActionFieldValue
        MAX-ACCESS      read-only
        STATUS          current
        DESCRIPTION     
                "The value returned in the Ingress Action Field of the LTM. 
                The value ingNoTlv(5) indicates that no Reply Ingress TLV 
                was returned in the LTM."
        ::= { rcCfmLtrReplyEntry 16} 

rcCfmLtrReplyIngressMac OBJECT-TYPE
        SYNTAX          MacAddress
        MAX-ACCESS      read-only
        STATUS          current
        DESCRIPTION     
                "Mac address returned in the ingress MAC address field. If the 
                rcCfmLtrReplyIngress object contains the value ingNoTlv(5), then 
                the contents of this object are meaningless."
        ::= { rcCfmLtrReplyEntry 17}

rcCfmLtrReplyIngressPortIdSubtype OBJECT-TYPE
        SYNTAX          LldpPortIdSubtype
        MAX-ACCESS      read-only
        STATUS          current
        DESCRIPTION     
                "Format of the Ingress Port ID. If the rcCfmLtrReplyIngress 
                object contains the value ingNoTlv(5), then the contents of 
                this object are meaningless."
        ::= { rcCfmLtrReplyEntry 18}

rcCfmLtrReplyIngressPortId OBJECT-TYPE
        SYNTAX          LldpPortId
        MAX-ACCESS      read-only
        STATUS          current
        DESCRIPTION     
                "Ingress Port ID. The format of this object is determined by 
                the value of the rcCfmLtrReplyIngressPortIdSubtype object. 
                If the rcCfmLtrReplyIngress object contains the value 
                ingNoTlv(5), then 
                the contents of this object are meaningless."
        ::= { rcCfmLtrReplyEntry 19}

rcCfmLtrReplyEgressAction OBJECT-TYPE
        SYNTAX          CfmEgressActionFieldValue
        MAX-ACCESS      read-only
        STATUS          current
        DESCRIPTION     
                "The value returned in the Egress Action Field of the LTM. The 
                value egrNoTlv(5) indicates that no Reply Egress TLV was 
                returned in the LTM."
        ::= { rcCfmLtrReplyEntry 20}

rcCfmLtrReplyEgressMac OBJECT-TYPE
        SYNTAX          MacAddress
        MAX-ACCESS      read-only
        STATUS          current
        DESCRIPTION     
                "Mac address returned in the egress MAC address field. If the 
                rcCfmLtrReplyEgress object contains the value egrNoTlv(5), 
                then the contents of this object are meaningless."
        ::= { rcCfmLtrReplyEntry 21}

rcCfmLtrReplyEgressPortIdSubtype OBJECT-TYPE
        SYNTAX          LldpPortIdSubtype
        MAX-ACCESS      read-only
        STATUS          current
        DESCRIPTION     
                "Format of the Egress Port ID. If the rcCfmLtrReplyEgress 
                 object contains the value egrNoTlv(5), then the contents 
                 of this object are meaningless."
        ::= { rcCfmLtrReplyEntry 22}

rcCfmLtrReplyEgressPortId OBJECT-TYPE
        SYNTAX          LldpPortId
        MAX-ACCESS      read-only
        STATUS          current
        DESCRIPTION     
                "Egress Port ID. The format of this object is determined by 
                the value of the rcCfmLtrReplyEgressPortIdSubtype object. 
                If the rcCfmLtrReplyEgress object contains the value 
                egrNoTlv(5), then the contents of this object are meaningless."
        ::= { rcCfmLtrReplyEntry 23}

-- The Transmit L2Ping Table

rcCfmTransmitL2PingTable OBJECT-TYPE
	SYNTAX		SEQUENCE OF RcCfmTransmitL2PingEntry
	MAX-ACCESS	not-accessible
	STATUS		current
	DESCRIPTION	"Connectivity Fault Management transmit L2Ping table"
	::= { rcCfm 34}

rcCfmTransmitL2PingEntry OBJECT-TYPE
	SYNTAX		RcCfmTransmitL2PingEntry
	MAX-ACCESS	not-accessible
	STATUS		current
	DESCRIPTION	"Connectivity Fault Management Maintenance EndPoint L2Ping entry."
	INDEX		{rcCfmTransmitL2PingVlanId }
	::= { rcCfmTransmitL2PingTable 1}

RcCfmTransmitL2PingEntry ::=
	SEQUENCE {
		rcCfmTransmitL2PingVlanId	        Integer32,
		rcCfmTransmitL2PingDestMacAddress       MacAddress,
		rcCfmTransmitL2PingHostName             OCTET STRING,	
		rcCfmTransmitL2PingDestIsHostName       TruthValue,
		rcCfmTransmitL2PingMessages		Integer32,
		rcCfmTransmitL2PingPriority		Integer32,
	        rcCfmTransmitL2PingTimeoutInt           Integer32,
	        rcCfmTransmitL2PingTestPattern          INTEGER,
	        rcCfmTransmitL2PingDataSize	        Integer32,
	        rcCfmTransmitL2PingFrameSize	        Integer32,
	        rcCfmTransmitL2PingSourceMode           INTEGER,
		rcCfmTransmitL2PingSeqNumber		Integer32,
		rcCfmTransmitL2PingResultOk		TruthValue,
		rcCfmTransmitL2PingStatus		INTEGER,
		rcCfmTransmitL2PingResult       OCTET STRING
 	}

rcCfmTransmitL2PingVlanId OBJECT-TYPE
	SYNTAX		Integer32 (1..4094)
	MAX-ACCESS	not-accessible
	STATUS		current
	DESCRIPTION	"A value that uniquely identifies the Customer Vlan"
	::= { rcCfmTransmitL2PingEntry 1}

rcCfmTransmitL2PingDestMacAddress OBJECT-TYPE
	SYNTAX		MacAddress
	MAX-ACCESS	read-write
	STATUS		current
	DESCRIPTION	"An indication of the target MAC Address field to be transmitted"
	::= { rcCfmTransmitL2PingEntry 2}

rcCfmTransmitL2PingHostName OBJECT-TYPE
	SYNTAX		OCTET STRING (SIZE (0..255))
	MAX-ACCESS	read-write
	STATUS		current
	DESCRIPTION	"The target host name"
	::= { rcCfmTransmitL2PingEntry 3}

rcCfmTransmitL2PingDestIsHostName OBJECT-TYPE
	SYNTAX 		TruthValue
	MAX-ACCESS	read-write
	STATUS		current
	DESCRIPTION	"True indicates that the host name is used for L2Ping transmission"
	::= { rcCfmTransmitL2PingEntry 4}

rcCfmTransmitL2PingMessages  OBJECT-TYPE
	SYNTAX  	Integer32(1..200)
	MAX-ACCESS	read-write
	STATUS		current
	DESCRIPTION	"The number of L2Ping messages to be transmitted."
               
	DEFVAL {1}
	::= { rcCfmTransmitL2PingEntry 5}

rcCfmTransmitL2PingPriority OBJECT-TYPE
	SYNTAX  	Integer32(0..7)
	MAX-ACCESS	read-write
	STATUS		current
	DESCRIPTION	"Priority. 3 bit value to be used in the VLAN hdr,  
			if present in the transmitted frame."
	DEFVAL {7}
	::= { rcCfmTransmitL2PingEntry 6}

rcCfmTransmitL2PingTimeoutInt  OBJECT-TYPE
        SYNTAX          Integer32(1..10)
        MAX-ACCESS      read-write
        STATUS          current
        DESCRIPTION    "The interval to wait for an L2Ping time-out with a 
                       range of (1..10)  seconds with a default value of 3 
                       seconds."
        DEFVAL {3}
        ::= { rcCfmTransmitL2PingEntry 7}

rcCfmTransmitL2PingTestPattern OBJECT-TYPE
        SYNTAX          INTEGER {
                               allZero(1),
                               allZeroCrc(2),
                               pseudoRandomBitSequence(3),
                               pseudoRandomBitSequenceCrc(4)
                        }
        MAX-ACCESS      read-write
        STATUS          current
        DESCRIPTION     "The test pattern to use in the L2Ping PDU with range of 
                        values namely allZero, allZeroCrc, 
                        pseudoRandomBitSequence and pseudoRandomBitSequenceCrc 
                        and with a default value of allZero.
                        value                  meaning
                        --------               -------
                        allZero(0)             Null signal without CRC-32
                        allZeroCrc(1)          Null signal with CRC-32    
                        pseudoRandomBitSequence(2) PRBS 1/2^31-1 without CRC-32
                        pseudoRandomBitSequenceCrc(3) PBRS 1/2^31-1 with CRC-32"
        DEFVAL {allZero}
        ::= { rcCfmTransmitL2PingEntry 8}

rcCfmTransmitL2PingDataSize  OBJECT-TYPE
	SYNTAX  	Integer32(0..400)
	MAX-ACCESS	read-write
	STATUS		current
	DESCRIPTION	"An arbitrary amount of data to be included in the data TLV, if the
			Data Size is selected to be sent."
	DEFVAL {0}
	::= { rcCfmTransmitL2PingEntry 9}

rcCfmTransmitL2PingFrameSize  OBJECT-TYPE
	SYNTAX  	Integer32(0..9600)
	MAX-ACCESS	read-write
	STATUS		current
	DESCRIPTION	"If the frame size is specified then the data size 
                        shall be internally calculated and the calculated data
                        size shall be included in the data TLV."
	DEFVAL {0}
	::= { rcCfmTransmitL2PingEntry 10}

rcCfmTransmitL2PingSourceMode  OBJECT-TYPE
        SYNTAX        INTEGER {
			      nodal(1),
			      smltVirtual(2),
                              noVlanMac(3)             
                      }
        MAX-ACCESS      read-write
        STATUS          current
        DESCRIPTION     "Source modes of the transmit loopback service. "
        DEFVAL {nodal}
        ::= { rcCfmTransmitL2PingEntry 11}


rcCfmTransmitL2PingSeqNumber OBJECT-TYPE
	SYNTAX 		Integer32
	MAX-ACCESS	read-only
	STATUS		current
	DESCRIPTION	"The transaction identifier/sequence number of the first loopback 
			message (to be) sent."
	DEFVAL {0}
	::= { rcCfmTransmitL2PingEntry 12}		

rcCfmTransmitL2PingResultOk OBJECT-TYPE
	SYNTAX 		TruthValue
	MAX-ACCESS	read-only
	STATUS		current
	DESCRIPTION	"Indicates the result of the operation:
			-true.    The L2Ping Message(s) will be (or have been) sent.
			-false.   The L2Ping Message(s) will not be sent."
	DEFVAL {true}
	::= { rcCfmTransmitL2PingEntry 13}
	 
rcCfmTransmitL2PingStatus 	OBJECT-TYPE
	SYNTAX 		INTEGER {
				ready(1),
				transmit(2),
                                abort(3)
			}
	MAX-ACCESS	read-write
	STATUS		current
	DESCRIPTION	"Status of the transmit loopback service:
			-ready.      The service is available.
			-transmit.   The service is transmitting, or about to 
                                     transmit, the L2Ping messages.
                        -abort       The service is aborted or about to abort 
                                     the L2Ping messages.

			This column will also be used to avoid concurrency or 
                        race condition problems that could occur if two or 
                        more management entities try to 
			use the service at the same time. "
	REFERENCE       "Delete notReady status due to CR Q01482201"
	DEFVAL {ready}
	::= { rcCfmTransmitL2PingEntry 14}

rcCfmTransmitL2PingResult  OBJECT-TYPE
	SYNTAX 		OCTET STRING (SIZE (1..799))
	MAX-ACCESS	read-only
	STATUS		current
	DESCRIPTION	"Display the L2Ping result."
	::= { rcCfmTransmitL2PingEntry 15}
	 

-- The Transmit L2Trace Table

rcCfmTransmitL2TraceTable OBJECT-TYPE
	SYNTAX		SEQUENCE OF RcCfmTransmitL2TraceEntry
	MAX-ACCESS	not-accessible
	STATUS		current
	DESCRIPTION	"Connectivity Fault Management transmit L2Trace table"
	::= { rcCfm 35}

rcCfmTransmitL2TraceEntry OBJECT-TYPE
	SYNTAX		RcCfmTransmitL2TraceEntry
	MAX-ACCESS	not-accessible
	STATUS		current
	DESCRIPTION	"Connectivity Fault Management Maintenance EndPoint L2Trace entry."
	INDEX		{rcCfmTransmitL2TraceVlanId }
	::= { rcCfmTransmitL2TraceTable 1}

RcCfmTransmitL2TraceEntry ::=
	SEQUENCE {
		rcCfmTransmitL2TraceVlanId	        	Integer32,
	        rcCfmTransmitL2TracePriority			Integer32,
		rcCfmTransmitL2TraceDestMacAddress      	MacAddress,
		rcCfmTransmitL2TraceHostName            	OCTET STRING,
	        rcCfmTransmitL2TraceIsid                        Integer32,
	        rcCfmTransmitL2TraceNickName                    DisplayString,	
		rcCfmTransmitL2TraceDestIsHostName      	TruthValue,
		rcCfmTransmitL2TraceIsidTree			TruthValue,
		rcCfmTransmitL2TraceTtl 			Integer32,
	        rcCfmTransmitL2TraceSourceMode            	INTEGER,
		rcCfmTransmitL2TraceSeqNumber			Integer32,
		rcCfmTransmitL2TraceResultOk			TruthValue,
		rcCfmTransmitL2TraceStatus		        INTEGER,
       		rcCfmTransmitL2TraceFlag		        INTEGER
	}

rcCfmTransmitL2TraceVlanId OBJECT-TYPE
	SYNTAX		Integer32 (1..4094)
	MAX-ACCESS	not-accessible
	STATUS		current
	DESCRIPTION	"A value that uniquely identifies the Customer Vlan"
	::= { rcCfmTransmitL2TraceEntry 1}

rcCfmTransmitL2TracePriority OBJECT-TYPE
	SYNTAX  	Integer32(0..7)
	MAX-ACCESS	read-write
	STATUS		current
	DESCRIPTION	"Priority. 3 bit value to be used in the VLAN hdr, 
                        if present in the transmitted frame."
	DEFVAL {7}
	::= { rcCfmTransmitL2TraceEntry 2}

rcCfmTransmitL2TraceDestMacAddress OBJECT-TYPE
	SYNTAX		MacAddress
	MAX-ACCESS	read-write
	STATUS		current
	DESCRIPTION	"An indication of the target MAC Address field to be transmitted"
	::= { rcCfmTransmitL2TraceEntry 3}

rcCfmTransmitL2TraceHostName OBJECT-TYPE
	SYNTAX		OCTET STRING (SIZE (0..255))
	MAX-ACCESS	read-write
	STATUS		current
	DESCRIPTION	"The target host name"
	::= { rcCfmTransmitL2TraceEntry 4}

rcCfmTransmitL2TraceIsid  OBJECT-TYPE
	SYNTAX        Integer32 (1..16777215)
        MAX-ACCESS    read-write
        STATUS        current
        DESCRIPTION   "Isid Id"
	::= { rcCfmTransmitL2TraceEntry 5}

rcCfmTransmitL2TraceNickName OBJECT-TYPE
	SYNTAX        DisplayString (SIZE (7))
 	MAX-ACCESS    read-only
	STATUS        current
        DESCRIPTION   "Local Node nick name"
	::= { rcCfmTransmitL2TraceEntry 6}

rcCfmTransmitL2TraceDestIsHostName OBJECT-TYPE
	SYNTAX 		TruthValue
	MAX-ACCESS	read-write
	STATUS		current
	DESCRIPTION	"True indicates that the host name is used for L2Trace transmission"
	::= { rcCfmTransmitL2TraceEntry 7}

rcCfmTransmitL2TraceIsidTree  OBJECT-TYPE
	SYNTAX 		TruthValue
	MAX-ACCESS	read-write
	STATUS		current
	DESCRIPTION	"True indicates that the multicast tree will be traced.
		         False indicates that the unicast path will be traced"
	::= { rcCfmTransmitL2TraceEntry 8}

rcCfmTransmitL2TraceTtl     OBJECT-TYPE
	SYNTAX  	Integer32(0..255)
	MAX-ACCESS	read-write
	STATUS		current
	DESCRIPTION	"The number of hops remaining to this L2Trace. 
			 Decremented by 1 by each Bridge that handles the L2Trace. 
			 The decremented value is returned in the L2Trace. If 0 
                         on output, the L2Trace is not transmitted to the next 
                         hop. The value of the TTL Field in the L2Trace
                         transmitted by the originating MEP is controlled by a 
                         Managed Object; The default value if none is 
                         specified is 64."
	DEFVAL {64}
	::= { rcCfmTransmitL2TraceEntry 9}


rcCfmTransmitL2TraceSourceMode  OBJECT-TYPE
        SYNTAX        INTEGER {
			      nodal(1),
			      smltVirtual(2),
                              noVlanMac(3)             
                      }
        MAX-ACCESS      read-write
        STATUS          current
        DESCRIPTION     "Source modes of the transmit loopback service. "
        DEFVAL {nodal}
        ::= { rcCfmTransmitL2TraceEntry 10}

rcCfmTransmitL2TraceSeqNumber OBJECT-TYPE
	SYNTAX 		Integer32
	MAX-ACCESS	read-only
	STATUS		current
	DESCRIPTION	"The transaction identifier/sequence number of the first loopback 
			message (to be) sent."
	DEFVAL {0}
	::= { rcCfmTransmitL2TraceEntry 11}		

rcCfmTransmitL2TraceResultOk OBJECT-TYPE
	SYNTAX 		TruthValue
	MAX-ACCESS	read-only
	STATUS		current
	DESCRIPTION	"Indicates the result of the operation:
			-true.    The L2Trace Message(s) will be (or have been) sent.
			-false.   The L2Trace Message(s) will not be sent."
	DEFVAL {true}
	::= { rcCfmTransmitL2TraceEntry 12}
	 
rcCfmTransmitL2TraceStatus 	OBJECT-TYPE
	SYNTAX 		INTEGER {
				ready(1),
				transmit(2),
                                abort(3)
			}
	MAX-ACCESS	read-write
	STATUS		current
	DESCRIPTION	"Status of the transmit loopback service:
			-ready.      The service is available.
			-transmit.   The service is transmitting, or about to 
                                     transmit, the L2Trace messages.
                        -abort       The service is aborted or about to abort 
                                     the L2Trace messages.

			This column will also be used to avoid concurrency or 
                        race condition problems that could occur if two or 
                        more management entities try to 
			use the service at the same time. "
	REFERENCE       "Delete notReady status due to CR Q01482201"
	DEFVAL {ready}
	::= { rcCfmTransmitL2TraceEntry 13}

rcCfmTransmitL2TraceFlag    OBJECT-TYPE
	SYNTAX 		INTEGER {
				none(1),
				internalError(2),
                                invalidMac(3),
                                mepDisabled(4), 
                                noL2TraceResponse(5),
                                l2TraceToOwnMepMac(6),
                                l2TraceComplete(7),
			        l2TraceLookupFailure(8),
				l2TraceLeafNode(9),
				l2TraceNotInTree(10),
				l2TraceSmltNotPrimary(11)
			}
	MAX-ACCESS	read-only
	STATUS	        current 	
	DESCRIPTION	"L2Trace result flag indicating L2Trace status or error code. 
                         Each enum value represents a status or error case.  
                         1 - No error  
                         2 - L2Trace Internal Error
                         3 - Invalid Mac Address
                         4 - Mep must be enabled in order to perform L2Trace
                         5 - No L2Trace response received
                         6 - L2Trace to own Mep MAC is not sent
                         7 - L2Trace completed
			 8 - Lookup failure for L2Trace
			 9 - On a leaf node in the i-sid tree
			10 - Not in the i-sid tree
			11 - Requested SMLT Source from Non-Primary Node"
	
		 
	::= { rcCfmTransmitL2TraceEntry 14}	 

-- L2Trace Reply Table

rcCfmL2TraceReplyTable OBJECT-TYPE
        SYNTAX          SEQUENCE OF RcCfmL2TraceReplyEntry
        MAX-ACCESS      not-accessible
        STATUS          current 
        DESCRIPTION     
                "This table contains a list of l2trace replies received 
                by a specific MEP in response to a linktrace message."
        ::= { rcCfm 36}

rcCfmL2TraceReplyEntry OBJECT-TYPE
        SYNTAX          RcCfmL2TraceReplyEntry
        MAX-ACCESS      not-accessible
        STATUS          current
        DESCRIPTION     "The Linktrace Reply table entry."
        INDEX           {rcCfmL2TraceReplyVlanId,rcCfmL2TraceReplySeqNumber,
                         rcCfmL2TraceReplyHop,rcCfmL2TraceReplyReceiveOrder}
        ::= { rcCfmL2TraceReplyTable 1}
    
RcCfmL2TraceReplyEntry ::=
        SEQUENCE {
		rcCfmL2TraceReplyVlanId	              Integer32,
		rcCfmL2TraceReplySeqNumber	      Integer32,
		rcCfmL2TraceReplyHop                  Integer32,	
                rcCfmL2TraceReplyReceiveOrder         Integer32,
		rcCfmL2TraceReplyTtl                  Integer32,	
                rcCfmL2TraceReplySrcMac               MacAddress,
		rcCfmL2TraceReplyHostName             OCTET STRING,
		rcCfmL2TraceReplyLastSrcMac            MacAddress,
		rcCfmL2TraceReplyLastHostName          OCTET STRING
             }

rcCfmL2TraceReplyVlanId OBJECT-TYPE
	SYNTAX		Integer32 (1..4094)
	MAX-ACCESS	not-accessible
	STATUS		current
	DESCRIPTION	"A value that uniquely identifies the Customer Vlan"
	::= {rcCfmL2TraceReplyEntry 1}

rcCfmL2TraceReplySeqNumber OBJECT-TYPE
        SYNTAX          Integer32 (0..2147483647)  
        MAX-ACCESS      not-accessible
        STATUS          current
        DESCRIPTION     
                "The transaction identifier/sequence number returned by a 
                previous transmit linktrace message command, indicating which 
                L2Trace's response is going to be returned."
        DEFVAL {0}
        ::= { rcCfmL2TraceReplyEntry 2}

rcCfmL2TraceReplyHop     OBJECT-TYPE
        SYNTAX          Integer32 (0..255)
        MAX-ACCESS      not-accessible
        STATUS          current
        DESCRIPTION     "The number of hops away from L2Trace initiator."
        ::= { rcCfmL2TraceReplyEntry 3}

rcCfmL2TraceReplyReceiveOrder OBJECT-TYPE
        SYNTAX          Integer32 (1..2147483647)
        MAX-ACCESS      not-accessible
        STATUS          current
        DESCRIPTION     
                "An index to distinguish among multiple L2Trace responses 
                with the same Transaction Identifier field  value. This value 
                is assigned sequentially from 1, in the order that the 
                Linktrace Initiator received the responses."
        ::= { rcCfmL2TraceReplyEntry 4}

rcCfmL2TraceReplyTtl     OBJECT-TYPE
        SYNTAX          Integer32 (0..255)
        MAX-ACCESS      read-only
        STATUS          current
        DESCRIPTION     "Ttl field value for a returned L2Trace response."
        ::= { rcCfmL2TraceReplyEntry 5}

rcCfmL2TraceReplySrcMac OBJECT-TYPE
        SYNTAX          MacAddress
        MAX-ACCESS      read-only
        STATUS          current
        DESCRIPTION     
                "Mac address of the MP that respond to the L2Trace request for 
                this L2traceReply"  
        ::= { rcCfmL2TraceReplyEntry 6}

rcCfmL2TraceReplyHostName OBJECT-TYPE
	SYNTAX    OCTET STRING (SIZE (0..255))
	MAX-ACCESS      read-only
        STATUS          current
        DESCRIPTION     
                "The host name of the replying node"
	::= { rcCfmL2TraceReplyEntry 7}

rcCfmL2TraceReplyLastSrcMac OBJECT-TYPE
	SYNTAX          MacAddress
        MAX-ACCESS      read-only
        STATUS          current
        DESCRIPTION     
                "The MAC address of the node that forwarded the L2Trace to the responding node"
	::= { rcCfmL2TraceReplyEntry 8}
	
rcCfmL2TraceReplyLastHostName OBJECT-TYPE
	SYNTAX    OCTET STRING (SIZE (0..255))
	MAX-ACCESS      read-only
        STATUS          current
        DESCRIPTION     
                "The host name of the node that forwarded the L2Trace to the responding node"
	::= { rcCfmL2TraceReplyEntry 9}

-- The Transmit L2 Ip Ping Table

rcCfmTransmitL2IpPingTable OBJECT-TYPE
	SYNTAX		SEQUENCE OF RcCfmTransmitL2IpPingEntry
	MAX-ACCESS	not-accessible
	STATUS		current
	DESCRIPTION	"Connectivity Fault Management transmit L2IpPing table"
	::= { rcCfm 37}

rcCfmTransmitL2IpPingEntry OBJECT-TYPE
	SYNTAX		RcCfmTransmitL2IpPingEntry
	MAX-ACCESS	not-accessible
	STATUS		current
	DESCRIPTION	"L2IpPing entry."
	INDEX		{rcCfmTransmitL2IpPingIpAddrType,
                         rcCfmTransmitL2IpPingIpAddr}
	::= { rcCfmTransmitL2IpPingTable 1}

RcCfmTransmitL2IpPingEntry ::=
	SEQUENCE {
                rcCfmTransmitL2IpPingIpAddrType         InetAddressType,
                rcCfmTransmitL2IpPingIpAddr             InetAddress,
                rcCfmTransmitL2IpPingVrfId              Integer32,
                rcCfmTransmitL2IpPingVrfName            DisplayString,  
		rcCfmTransmitL2IpPingMessages		Integer32,
	        rcCfmTransmitL2IpPingTimeoutInt         Integer32,
	        rcCfmTransmitL2IpPingTestPattern        INTEGER,
	        rcCfmTransmitL2IpPingDataSize	        Integer32,
		rcCfmTransmitL2IpPingStatus		INTEGER,
		rcCfmTransmitL2IpPingResultOk		TruthValue,
                rcCfmTransmitL2IpPingPathsFound         Integer32,
                rcCfmTransmitL2IpPingRowStatus          RowStatus
 	}

rcCfmTransmitL2IpPingIpAddrType OBJECT-TYPE
        SYNTAX        InetAddressType
        MAX-ACCESS    not-accessible
        STATUS        current
        DESCRIPTION   "The address type of destination IP Address "
        ::= { rcCfmTransmitL2IpPingEntry 1 }

rcCfmTransmitL2IpPingIpAddr OBJECT-TYPE
        SYNTAX        InetAddress
        MAX-ACCESS    not-accessible
        STATUS        current
        DESCRIPTION   "Destination IP Address. Support ipv4 at this time"
        ::= { rcCfmTransmitL2IpPingEntry 2 }

rcCfmTransmitL2IpPingVrfId OBJECT-TYPE
        SYNTAX        Integer32
        MAX-ACCESS    read-only
        STATUS        current
        DESCRIPTION   "VRF ID "
        ::= { rcCfmTransmitL2IpPingEntry 3 }

rcCfmTransmitL2IpPingVrfName   OBJECT-TYPE
     SYNTAX         DisplayString (SIZE (0..64))
     MAX-ACCESS     read-only
     STATUS         current
     DESCRIPTION    "The Name of the Virtual Router"
        ::= {rcCfmTransmitL2IpPingEntry 4 }

rcCfmTransmitL2IpPingMessages  OBJECT-TYPE
	SYNTAX  	Integer32(1..200)
	MAX-ACCESS	read-create
	STATUS		current
	DESCRIPTION	"The number of L2IpPing messages to be transmitted 
                         per mac/vlan pair."               
	DEFVAL {1}
	::= { rcCfmTransmitL2IpPingEntry 5}

rcCfmTransmitL2IpPingTimeoutInt  OBJECT-TYPE
        SYNTAX          Integer32(1..10)
        MAX-ACCESS      read-create
        STATUS          current
        DESCRIPTION    "The interval to wait for an L2IpPing time-out with a 
                       range of (1..10)  seconds with a default value of 3 
                       seconds."
        DEFVAL {3}
        ::= { rcCfmTransmitL2IpPingEntry 6}

rcCfmTransmitL2IpPingTestPattern OBJECT-TYPE
        SYNTAX          INTEGER {
                               allZero(1),
                               allZeroCrc(2),
                               pseudoRandomBitSequence(3),
                               pseudoRandomBitSequenceCrc(4)
                        }
        MAX-ACCESS      read-create
        STATUS          current
        DESCRIPTION     "The test pattern to use in the L2IpPing PDUs 
                        with range of values namely allZero, allZeroCrc, 
                        pseudoRandomBitSequence and pseudoRandomBitSequenceCrc 
                        and with a default value of allZero.
                        value                  meaning
                        --------               -------
                        allZero(0)             Null signal without CRC-32
                        allZeroCrc(1)          Null signal with CRC-32    
                        pseudoRandomBitSequence(2) PRBS 1/2^31-1 without CRC-32
                        pseudoRandomBitSequenceCrc(3) PBRS 1/2^31-1 with CRC-32"
        DEFVAL {allZero}
        ::= { rcCfmTransmitL2IpPingEntry 7}

rcCfmTransmitL2IpPingDataSize  OBJECT-TYPE
	SYNTAX  	Integer32(0..400)
	MAX-ACCESS	read-create
	STATUS		current
	DESCRIPTION	"An arbitrary amount of data to be included in the 
                        data TLV, if the Data Size is selected to be sent."
	DEFVAL {0}
	::= { rcCfmTransmitL2IpPingEntry 8}

rcCfmTransmitL2IpPingStatus 	OBJECT-TYPE
	SYNTAX 		INTEGER {
				ready(1),
				transmit(2),
                                abort(3)
			}
	MAX-ACCESS	read-create
	STATUS		current
	DESCRIPTION	"Status of the transmit loopback service:
			-ready.      The service is available.
			-transmit.   The service is transmitting, or about to 
                                     transmit, the L2IpPing messages.
                        -abort       The service is aborted or about to abort 
                                     the L2IpPing messages.

			This column will also be used to avoid concurrency or 
                        race condition problems that could occur if two or 
                        more management entities try to 
			use the service at the same time. "
	REFERENCE       "Delete notReady status due to CR Q01482201"
	DEFVAL {ready}
	::= { rcCfmTransmitL2IpPingEntry 9}

rcCfmTransmitL2IpPingResultOk OBJECT-TYPE
	SYNTAX 		TruthValue
	MAX-ACCESS	read-only
	STATUS		current
	DESCRIPTION	"Indicates the result of the operation:
			-true.    L2IpPing Message(s) will be/have been sent.
			-false.   L2IpPing Message(s) will not be sent."
	DEFVAL {true}
	::= { rcCfmTransmitL2IpPingEntry 10}
	 
rcCfmTransmitL2IpPingPathsFound   OBJECT-TYPE
	SYNTAX  	Integer32
	MAX-ACCESS	read-only
	STATUS	        current 	
	DESCRIPTION	"The number of paths found to execute l2ping command"
        DEFVAL          { 0 }
	::= { rcCfmTransmitL2IpPingEntry 11}	

rcCfmTransmitL2IpPingRowStatus OBJECT-TYPE
        SYNTAX        RowStatus
        MAX-ACCESS    read-create
        STATUS        current
        DESCRIPTION   "Used to create/delete entries in the 
                       rcCfmTransmitL2IpPingTable. Deletion of an entry
                       in this table results in corresponding
                       rcCfmL2IpPingReplyTable entries being deleted."
        ::= { rcCfmTransmitL2IpPingEntry 12 }

-- L2 Ip Ping Reply Table

rcCfmL2IpPingReplyTable OBJECT-TYPE
        SYNTAX          SEQUENCE OF RcCfmL2IpPingReplyEntry
        MAX-ACCESS      not-accessible
        STATUS          current 
        DESCRIPTION     
                "This table contains a list of l2 ip ping replies received "
        ::= { rcCfm 38}

rcCfmL2IpPingReplyEntry OBJECT-TYPE
        SYNTAX          RcCfmL2IpPingReplyEntry
        MAX-ACCESS      not-accessible
        STATUS          current
        DESCRIPTION     "The L2 Ip Ping Reply table entry."
        INDEX           {rcCfmL2IpPingReplyIpAddrType,
                         rcCfmL2IpPingReplyIpAddr,
                         rcCfmL2IpPingReplySendOrder}
        ::= { rcCfmL2IpPingReplyTable 1}
    
RcCfmL2IpPingReplyEntry ::=
        SEQUENCE {
                rcCfmL2IpPingReplyIpAddrType            InetAddressType,
                rcCfmL2IpPingReplyIpAddr                InetAddress,
                rcCfmL2IpPingReplySendOrder             Integer32,
                rcCfmL2IpPingReplyVrfId                 Integer32,
		rcCfmL2IpPingReplyVlanId                Integer32,
                rcCfmL2IpPingReplyDestMacAddress        MacAddress,
                rcCfmL2IpPingReplyPortNum               InterfaceIndex,
		rcCfmL2IpPingReplyDestHostName          OCTET STRING,
		rcCfmL2IpPingReplySize                  Integer32,
		rcCfmL2IpPingReplyPktsTx                Integer32,
		rcCfmL2IpPingReplyPktsRx                Integer32,
		rcCfmL2IpPingReplyPercentLossWhole      Integer32,	
		rcCfmL2IpPingReplyPercentLossFract      Integer32,	
                rcCfmL2IpPingReplyMinRoundTrip          Integer32,
                rcCfmL2IpPingReplyMaxRoundTrip          Integer32,
                rcCfmL2IpPingReplyRttAvgWhole           Integer32,
                rcCfmL2IpPingReplyRttAvgFract           Integer32,
                rcCfmL2IpPingReplyFlag                  INTEGER
             }

rcCfmL2IpPingReplyIpAddrType OBJECT-TYPE
        SYNTAX        InetAddressType
        MAX-ACCESS    not-accessible
        STATUS        current
        DESCRIPTION   "The address type of destination IP Address "
        ::= { rcCfmL2IpPingReplyEntry 1 }

rcCfmL2IpPingReplyIpAddr OBJECT-TYPE
        SYNTAX        InetAddress
        MAX-ACCESS    not-accessible
        STATUS        current
        DESCRIPTION   "Destination IP Address. Support ipv4 at this time"
        ::= { rcCfmL2IpPingReplyEntry 2 }

rcCfmL2IpPingReplySendOrder OBJECT-TYPE
        SYNTAX          Integer32 (0..2147483647)
        MAX-ACCESS      not-accessible
        STATUS          current
        DESCRIPTION     
                "An index to distinguish among multiple L2Ping sessions 
                This value is assigned sequentially from 1. It denotes
                order that sessions were sent. It correlates to the number
                of paths found and stored in the rcCfmTransmitL2IpPingEntry."
        ::= { rcCfmL2IpPingReplyEntry 3}

rcCfmL2IpPingReplyVrfId OBJECT-TYPE
        SYNTAX        Integer32
        MAX-ACCESS    read-only
        STATUS        current
        DESCRIPTION   "VRF ID "
        ::= { rcCfmL2IpPingReplyEntry 4 }

rcCfmL2IpPingReplyVlanId OBJECT-TYPE
	SYNTAX		Integer32 (1..4094)
	MAX-ACCESS	read-only
	STATUS		current
	DESCRIPTION	"Vlan found from L3 lookup and used for transmission"
	::= {rcCfmL2IpPingReplyEntry 5}

rcCfmL2IpPingReplyDestMacAddress OBJECT-TYPE
	SYNTAX		MacAddress
	MAX-ACCESS	read-only
	STATUS		current
	DESCRIPTION	"An indication of the target MAC Address transmitted"
	::= { rcCfmL2IpPingReplyEntry 6}

rcCfmL2IpPingReplyPortNum OBJECT-TYPE
        SYNTAX          InterfaceIndex
        MAX-ACCESS      read-only
        STATUS          current
        DESCRIPTION     "Either the value '0', or the port number of the
                        port used for the l2ping.  "
        ::= { rcCfmL2IpPingReplyEntry 7 }

rcCfmL2IpPingReplyDestHostName OBJECT-TYPE
	SYNTAX    OCTET STRING (SIZE (0..255))
	MAX-ACCESS      read-only
        STATUS          current
        DESCRIPTION     
                "The host name of the responding node"
	::= { rcCfmL2IpPingReplyEntry 8}

rcCfmL2IpPingReplySize OBJECT-TYPE
        SYNTAX          Integer32 (0..9600)  
        MAX-ACCESS      read-only
        STATUS          current
        DESCRIPTION     
                "The number of bytes of data sent"
        DEFVAL {0}
        ::= { rcCfmL2IpPingReplyEntry 9}

rcCfmL2IpPingReplyPktsTx     OBJECT-TYPE
        SYNTAX          Integer32 
        MAX-ACCESS      read-only
        STATUS          current
        DESCRIPTION     "Number of Packets transmitted for this vlan/mac"
        ::= { rcCfmL2IpPingReplyEntry 10}

rcCfmL2IpPingReplyPktsRx     OBJECT-TYPE
        SYNTAX          Integer32 
        MAX-ACCESS      read-only
        STATUS          current
        DESCRIPTION     "Number of Packets received for this vlan/mac"
        ::= { rcCfmL2IpPingReplyEntry 11}

rcCfmL2IpPingReplyPercentLossWhole     OBJECT-TYPE
        SYNTAX          Integer32 (0..100) 
        MAX-ACCESS      read-only
        STATUS          current
        DESCRIPTION     "Percentage of packet loss for this vlan/mac"
        ::= { rcCfmL2IpPingReplyEntry 12}

rcCfmL2IpPingReplyPercentLossFract     OBJECT-TYPE
        SYNTAX          Integer32 (0..100) 
        MAX-ACCESS      read-only
        STATUS          current
        DESCRIPTION     "Percentage of packet loss for this vlan/mac"
        ::= { rcCfmL2IpPingReplyEntry 13}

rcCfmL2IpPingReplyMinRoundTrip    OBJECT-TYPE
        SYNTAX          Integer32  
        MAX-ACCESS      read-only
        STATUS          current
        DESCRIPTION     "Min time for round-trip for this vlan/mac in us"
        ::= { rcCfmL2IpPingReplyEntry 14}

rcCfmL2IpPingReplyMaxRoundTrip    OBJECT-TYPE
        SYNTAX          Integer32  
        MAX-ACCESS      read-only
        STATUS          current
        DESCRIPTION     "Max time for round-trip for this vlan/mac in us"
        ::= { rcCfmL2IpPingReplyEntry 15}

rcCfmL2IpPingReplyRttAvgWhole    OBJECT-TYPE
        SYNTAX          Integer32  
        MAX-ACCESS      read-only
        STATUS          current
        DESCRIPTION     "Average time for round-trip for this vlan/mac in us"
        ::= { rcCfmL2IpPingReplyEntry 16}

rcCfmL2IpPingReplyRttAvgFract    OBJECT-TYPE
        SYNTAX          Integer32  
        MAX-ACCESS      read-only
        STATUS          current
        DESCRIPTION     "Fractional portion of Average time for round-trip"
        ::= { rcCfmL2IpPingReplyEntry 17}

rcCfmL2IpPingReplyFlag     OBJECT-TYPE
	SYNTAX 		INTEGER {
				none(1),
				internalError(2),
                                invalidMac(3),
                                mepDisabled(4), 
                                invalidMD(5),
                                invalidMA(6),
			        noMepFound(7),
                                unknownServiceInstance(8),
                                l2PingToOwnMepMac(9),
                                l2PingComplete(10)
			}
	MAX-ACCESS	read-only
	STATUS	        current 	
	DESCRIPTION	"Result flag indicating status or error code. 
                         Each enum value represents a status or error case.  
                         1 - No error  
                         2 - Internal Error
                         3 - Invalid Ip
                         4 - L2Trace completed
			 5 - Lookup failure for IP (no vlan/mac entries)"
        ::= { rcCfmL2IpPingReplyEntry 18}

-- The Transmit L2 Ip Trace Table
rcCfmTransmitL2IpTraceTable OBJECT-TYPE
	SYNTAX		SEQUENCE OF RcCfmTransmitL2IpTraceEntry
	MAX-ACCESS	not-accessible
	STATUS		current
	DESCRIPTION	"Connectivity Fault Management transmit L2IpTrace table"
	::= { rcCfm 39}

rcCfmTransmitL2IpTraceEntry OBJECT-TYPE
	SYNTAX		RcCfmTransmitL2IpTraceEntry
	MAX-ACCESS	not-accessible
	STATUS		current
	DESCRIPTION	"L2IpTrace entry."
	INDEX		{rcCfmTransmitL2IpTraceIpAddrType,
                         rcCfmTransmitL2IpTraceIpAddr }
	::= { rcCfmTransmitL2IpTraceTable 1}

RcCfmTransmitL2IpTraceEntry ::=
	SEQUENCE {
                rcCfmTransmitL2IpTraceIpAddrType        InetAddressType,
                rcCfmTransmitL2IpTraceIpAddr            InetAddress,
                rcCfmTransmitL2IpTraceVrfId             Integer32,
                rcCfmTransmitL2IpTraceVrfName           DisplayString,  
		rcCfmTransmitL2IpTraceTtl 	        Integer32,
		rcCfmTransmitL2IpTraceStatus		INTEGER,
		rcCfmTransmitL2IpTraceResultOk		TruthValue,
                rcCfmTransmitL2IpTracePathsFound        Integer32,
                rcCfmTransmitL2IpTraceRowStatus         RowStatus
	}

rcCfmTransmitL2IpTraceIpAddrType OBJECT-TYPE
        SYNTAX        InetAddressType
        MAX-ACCESS    not-accessible
        STATUS        current
        DESCRIPTION   "The address type of destination IP Address "
        ::= { rcCfmTransmitL2IpTraceEntry 1 }

rcCfmTransmitL2IpTraceIpAddr OBJECT-TYPE
        SYNTAX        InetAddress 
        MAX-ACCESS    not-accessible
        STATUS        current
        DESCRIPTION   "Destination IP Address. Support ipv4 at this time"
        ::= { rcCfmTransmitL2IpTraceEntry 2 }

rcCfmTransmitL2IpTraceVrfId OBJECT-TYPE
        SYNTAX        Integer32
        MAX-ACCESS    read-only
        STATUS        current
        DESCRIPTION   "VRF ID "
        ::= { rcCfmTransmitL2IpTraceEntry 3 }

rcCfmTransmitL2IpTraceVrfName   OBJECT-TYPE
     SYNTAX         DisplayString (SIZE (0..64))
     MAX-ACCESS     read-only
     STATUS         current
     DESCRIPTION    "The Name of the Virtual Router"
        ::= {rcCfmTransmitL2IpTraceEntry 4 }

rcCfmTransmitL2IpTraceTtl     OBJECT-TYPE
	SYNTAX  	Integer32(0..255)
	MAX-ACCESS	read-create
	STATUS		current
	DESCRIPTION	"The number of hops remaining to this L2Trace. 
			 Decremented by 1 by each Bridge that handles the L2Trace. 
			 The decremented value is returned in the L2Trace. If 0 
                         on output, the L2Trace is not transmitted to the next 
                         hop. The value of the TTL Field in the L2Trace
                         transmitted by the originating MEP is controlled by a 
                         Managed Object; The default value if none is 
                         specified is 64."
	DEFVAL {64}
	::= { rcCfmTransmitL2IpTraceEntry 5}

rcCfmTransmitL2IpTraceStatus 	OBJECT-TYPE
	SYNTAX 		INTEGER {
				ready(1),
				transmit(2),
                                abort(3)
			}
	MAX-ACCESS	read-create
	STATUS		current
	DESCRIPTION	"Status of the transmit loopback service:
			-ready.      The service is available.
			-transmit.   The service is transmitting, or about to 
                                     transmit, the L2Trace messages.
                        -abort       The service is aborted or about to abort 
                                     the L2Trace messages.

			This column will also be used to avoid concurrency or 
                        race condition problems that could occur if two or 
                        more management entities try to 
			use the service at the same time. "
	REFERENCE       "Delete notReady status due to CR Q01482201"
	DEFVAL {ready}
	::= { rcCfmTransmitL2IpTraceEntry 6}

rcCfmTransmitL2IpTraceResultOk OBJECT-TYPE
	SYNTAX 		TruthValue
	MAX-ACCESS	read-only
	STATUS		current
	DESCRIPTION	"Indicates the result of the operation:
			-true.    The Trace Message(s) will be/have been sent.
			-false.   The Trace Message(s) will not be sent."
	DEFVAL {true}
	::= { rcCfmTransmitL2IpTraceEntry 7}
	
rcCfmTransmitL2IpTracePathsFound   OBJECT-TYPE
	SYNTAX  	Integer32
	MAX-ACCESS	read-only
	STATUS	        current 	
	DESCRIPTION	"The number of paths found to execute l2trace command"
        DEFVAL          { 0 }
	::= { rcCfmTransmitL2IpTraceEntry 8}	

rcCfmTransmitL2IpTraceRowStatus OBJECT-TYPE
        SYNTAX        RowStatus
        MAX-ACCESS    read-create
        STATUS        current
        DESCRIPTION   "Used to create/delete entries in the 
                       rcCfmTransmitL2IpTraceTable. Deletion of an entry
                       in this table results in corresponding
                       rcCfmL2IpTraceReplyTable entries being deleted."
        ::= { rcCfmTransmitL2IpTraceEntry 9 }

 
-- L2IpTrace Reply Table

rcCfmL2IpTraceReplyTable OBJECT-TYPE
        SYNTAX          SEQUENCE OF RcCfmL2IpTraceReplyEntry
        MAX-ACCESS      not-accessible
        STATUS          current 
        DESCRIPTION     
                "This table contains a list of l2 ip trace replies received 
                by a specific MEP in response to a linktrace message."
        ::= { rcCfm 40}

rcCfmL2IpTraceReplyEntry OBJECT-TYPE
        SYNTAX          RcCfmL2IpTraceReplyEntry
        MAX-ACCESS      not-accessible
        STATUS          current
        DESCRIPTION     "The L2 Ip Trace Reply table entry."
        INDEX           {rcCfmL2IpTraceReplyIpAddrType,
                         rcCfmL2IpTraceReplyIpAddr,
                         rcCfmL2IpTraceReplySendOrder,
                         rcCfmL2IpTraceReplyHop,
                         rcCfmL2IpTraceReplyReceiveOrder}
        ::= { rcCfmL2IpTraceReplyTable 1}
    
RcCfmL2IpTraceReplyEntry ::=
        SEQUENCE {
                rcCfmL2IpTraceReplyIpAddrType          InetAddressType,
                rcCfmL2IpTraceReplyIpAddr              InetAddress,
                rcCfmL2IpTraceReplySendOrder           Integer32,
		rcCfmL2IpTraceReplyHop                 Integer32,	
                rcCfmL2IpTraceReplyReceiveOrder        Integer32,
		rcCfmL2IpTraceReplyTtl                 Integer32,	
                rcCfmL2IpTraceReplyVrfId               Integer32,
		rcCfmL2IpTraceReplyVlanId	       Integer32,
                rcCfmL2IpTraceReplyDestMacAddress      MacAddress,
                rcCfmL2IpTraceReplyPortNum             InterfaceIndex,
		rcCfmL2IpTraceReplySeqNumber	       Integer32,
                rcCfmL2IpTraceReplySrcMac              MacAddress,
		rcCfmL2IpTraceReplyHostName            OCTET STRING,
		rcCfmL2IpTraceReplyLastSrcMac          MacAddress,
		rcCfmL2IpTraceReplyLastHostName        OCTET STRING,
                rcCfmL2IpTraceReplyFlag                INTEGER
             }

rcCfmL2IpTraceReplyIpAddrType OBJECT-TYPE
        SYNTAX        InetAddressType
        MAX-ACCESS    not-accessible
        STATUS        current
        DESCRIPTION   "The address type of destination IP Address "
        ::= { rcCfmL2IpTraceReplyEntry 1 }

rcCfmL2IpTraceReplyIpAddr OBJECT-TYPE
        SYNTAX        InetAddress 
        MAX-ACCESS    not-accessible
        STATUS        current
        DESCRIPTION   "Destination IP Address. Support ipv4 at this time"
        ::= { rcCfmL2IpTraceReplyEntry 2 }

rcCfmL2IpTraceReplySendOrder OBJECT-TYPE
        SYNTAX          Integer32 (0..2147483647)
        MAX-ACCESS      not-accessible
        STATUS          current
        DESCRIPTION     
                "An index to distinguish among multiple L2Trace sessions 
                This value is assigned sequentially from 1. It denotes
                order that sessions were sent. It correlates to the number
                of paths found and stored in the rcCfmTransmitL2IpTraceEntry."
        ::= { rcCfmL2IpTraceReplyEntry 3}

rcCfmL2IpTraceReplyHop     OBJECT-TYPE
        SYNTAX          Integer32 (0..255)
        MAX-ACCESS      not-accessible
        STATUS          current
        DESCRIPTION     "The number of L2 hops away from L2Trace initiator."
        ::= { rcCfmL2IpTraceReplyEntry 4}

rcCfmL2IpTraceReplyReceiveOrder OBJECT-TYPE
        SYNTAX          Integer32 (0..2147483647)
        MAX-ACCESS      not-accessible
        STATUS          current
        DESCRIPTION     
                "An index to distinguish among multiple L2Trace responses 
                with the same Send Transaction Identifier field  value. 
                This value is assigned sequentially from 1, in the order 
                that the Linktrace Initiator received the responses. A
                zero value may be seen in error conditions"
        ::= { rcCfmL2IpTraceReplyEntry 5}

rcCfmL2IpTraceReplyTtl     OBJECT-TYPE
        SYNTAX          Integer32 (0..255)
        MAX-ACCESS      read-only
        STATUS          current
        DESCRIPTION     "Ttl field value for a returned L2Trace response."
        ::= { rcCfmL2IpTraceReplyEntry 6}

rcCfmL2IpTraceReplyVrfId OBJECT-TYPE
        SYNTAX        Integer32
        MAX-ACCESS    read-only
        STATUS        current
        DESCRIPTION   "VRF ID "
        ::= { rcCfmL2IpTraceReplyEntry 7}

rcCfmL2IpTraceReplyVlanId OBJECT-TYPE
	SYNTAX		Integer32 (1..4094)
	MAX-ACCESS	read-only
	STATUS		current
	DESCRIPTION	"Vlan found from L3 lookup and used for transmission"
	::= {rcCfmL2IpTraceReplyEntry 8}

rcCfmL2IpTraceReplyDestMacAddress OBJECT-TYPE
	SYNTAX		MacAddress
	MAX-ACCESS	read-only
	STATUS		current
	DESCRIPTION	"An indication of the target MAC Address transmitted"
	::= { rcCfmL2IpTraceReplyEntry 9}

rcCfmL2IpTraceReplySeqNumber OBJECT-TYPE
        SYNTAX          Integer32 (0..2147483647)  
        MAX-ACCESS      read-only
        STATUS          current
        DESCRIPTION     
                "The transaction identifier/sequence number used in  
                linktrace message packet"
        DEFVAL {0}
        ::= { rcCfmL2IpTraceReplyEntry 10}

rcCfmL2IpTraceReplyPortNum OBJECT-TYPE
        SYNTAX          InterfaceIndex
        MAX-ACCESS      read-only
        STATUS          current
        DESCRIPTION     "Either the value '0', or the port number of the
                        port used for the l2trace.  "
        ::= { rcCfmL2IpTraceReplyEntry 11 }

rcCfmL2IpTraceReplySrcMac OBJECT-TYPE
        SYNTAX          MacAddress
        MAX-ACCESS      read-only
        STATUS          current
        DESCRIPTION     
                "Mac address of the MP that responded to L2Trace request for 
                this L2traceReply"  
        ::= { rcCfmL2IpTraceReplyEntry 12}

rcCfmL2IpTraceReplyHostName OBJECT-TYPE
	SYNTAX    OCTET STRING (SIZE (0..255))
	MAX-ACCESS      read-only
        STATUS          current
        DESCRIPTION     
                "The host name of the replying node"
	::= { rcCfmL2IpTraceReplyEntry 13}

rcCfmL2IpTraceReplyLastSrcMac OBJECT-TYPE
	SYNTAX          MacAddress
        MAX-ACCESS      read-only
        STATUS          current
        DESCRIPTION     
                "The MAC address of the node that forwarded the 
                L2Trace to the responding node"
	::= { rcCfmL2IpTraceReplyEntry 14}
	
rcCfmL2IpTraceReplyLastHostName OBJECT-TYPE
	SYNTAX    OCTET STRING (SIZE (0..255))
	MAX-ACCESS      read-only
        STATUS          current
        DESCRIPTION     
                "The host name of the node that forwarded the L2Trace 
                to the responding node"
	::= { rcCfmL2IpTraceReplyEntry 15}

rcCfmL2IpTraceReplyFlag    OBJECT-TYPE
	SYNTAX 		INTEGER {
				none(1),
				internalError(2),
                                invalidMac(3),
                                mepDisabled(4), 
                                noL2TraceResponse(5),
                                l2TraceToOwnMepMac(6),
                                l2TraceComplete(7),
			        l2TraceLookupFailure(8)
			}
	MAX-ACCESS	read-only
	STATUS	        current 	
	DESCRIPTION	"L2Trace result flag indicating status or error code. 
                         Each enum value represents a status or error case.  
                         1 - No error  
                         2 - L2Trace Internal Error
                         3 - Invalid Mac Address
                         4 - Mep must be enabled in order to perform L2Trace
                         5 - No L2Trace response received
                         6 - L2Trace to own Mep MAC is not sent
                         7 - L2Trace completed
			 8 - Lookup failure for L2Trace"

	::= { rcCfmL2IpTraceReplyEntry 16}

-- The Transmit L2 Multicast Trace Table

rcCfmTransmitL2McastTraceTable OBJECT-TYPE
        SYNTAX          SEQUENCE OF RcCfmTransmitL2McastTraceEntry
        MAX-ACCESS      not-accessible
        STATUS          current 
        DESCRIPTION     
                "This table contains a list of l2 multicast route trace
                requests."
        ::= { rcCfm 41}

rcCfmTransmitL2McastTraceEntry OBJECT-TYPE
        SYNTAX          RcCfmTransmitL2McastTraceEntry
        MAX-ACCESS      not-accessible
        STATUS          current 
        DESCRIPTION     "CFM Transmit L2 Multicast Trace Entry."
        INDEX           { rcCfmTransmitL2McastTraceSrcIpAddrType,
                          rcCfmTransmitL2McastTraceSrcIpAddr,
                          rcCfmTransmitL2McastTraceGroupIpAddrType,
                          rcCfmTransmitL2McastTraceGroupIpAddr,
                          rcCfmTransmitL2McastTraceServiceType,
                          rcCfmTransmitL2McastTraceServiceId
                        }
        ::= { rcCfmTransmitL2McastTraceTable 1 }


RcCfmTransmitL2McastTraceEntry ::= SEQUENCE {

        rcCfmTransmitL2McastTraceSrcIpAddrType          InetAddressType,
        rcCfmTransmitL2McastTraceSrcIpAddr              InetAddress,
        rcCfmTransmitL2McastTraceGroupIpAddrType        InetAddressType,
        rcCfmTransmitL2McastTraceGroupIpAddr            InetAddress,
        rcCfmTransmitL2McastTraceServiceType            INTEGER,
        rcCfmTransmitL2McastTraceServiceId              Integer32,
        rcCfmTransmitL2McastTraceVrfName                DisplayString,
        rcCfmTransmitL2McastTraceRowStatus              RowStatus,
        rcCfmTransmitL2McastTracePriority               Integer32,
        rcCfmTransmitL2McastTraceTtl                    Integer32,
        rcCfmTransmitL2McastTraceSeqNumber              Integer32,
        rcCfmTransmitL2McastTraceStatus                 INTEGER,
        rcCfmTransmitL2McastTraceResultOk               TruthValue,
        rcCfmTransmitL2McastTraceFlag                   INTEGER
        }

rcCfmTransmitL2McastTraceSrcIpAddrType OBJECT-TYPE
	SYNTAX          InetAddressType
	MAX-ACCESS      not-accessible
        STATUS          current
        DESCRIPTION     
                "The address type of Source IP Address"
	::= { rcCfmTransmitL2McastTraceEntry 1 }

rcCfmTransmitL2McastTraceSrcIpAddr OBJECT-TYPE
	SYNTAX          InetAddress
	MAX-ACCESS      not-accessible
        STATUS          current
        DESCRIPTION     
                "Source IP Address. Support ipv4 at this time"
	::= { rcCfmTransmitL2McastTraceEntry 2 }

rcCfmTransmitL2McastTraceGroupIpAddrType OBJECT-TYPE
	SYNTAX          InetAddressType
	MAX-ACCESS      not-accessible
        STATUS          current
        DESCRIPTION     
                "The address type of Multicast Group IP Address"
	::= { rcCfmTransmitL2McastTraceEntry 3 }

rcCfmTransmitL2McastTraceGroupIpAddr OBJECT-TYPE
	SYNTAX          InetAddress
	MAX-ACCESS      not-accessible
        STATUS          current
        DESCRIPTION     
                "Multicast Group IP Address. Support ipv4 at this time"
	::= { rcCfmTransmitL2McastTraceEntry 4 }

rcCfmTransmitL2McastTraceServiceType OBJECT-TYPE
	SYNTAX          INTEGER {
                        vlan(1),
                        vrfid(2)
                        }
	MAX-ACCESS      not-accessible
        STATUS          current
        DESCRIPTION     
                "Service type indicates what value of service id means.
                 vlan - indicates value maps to VLAN
                 vrfid - indicates value maps to a VRF Id"
	::= { rcCfmTransmitL2McastTraceEntry 5 }

rcCfmTransmitL2McastTraceServiceId OBJECT-TYPE
	SYNTAX          Integer32
	MAX-ACCESS      not-accessible
        STATUS          current
        DESCRIPTION     
                "Value of VLAN or VRF-Id.  Meaning controlled by
                rcCfmTransmitL2McastTraceServiceType.  Value must be
                valid for type (e.g. VLAN range 1..4094)"
	::= { rcCfmTransmitL2McastTraceEntry 6 }

rcCfmTransmitL2McastTraceVrfName OBJECT-TYPE
	SYNTAX          DisplayString (SIZE (0..64))
	MAX-ACCESS      read-only
        STATUS          current
        DESCRIPTION     "The name of the Virtual Router of the originator"
	::= { rcCfmTransmitL2McastTraceEntry 7 }

rcCfmTransmitL2McastTraceRowStatus OBJECT-TYPE
	SYNTAX          RowStatus
	MAX-ACCESS      read-create
        STATUS          current
        DESCRIPTION     "Used to create/delete entries in the 
                        rcCfmTransmitL2McastTraceTable.  Deletion
                        of an entry in this table results in a corresponding
                        rcCfmL2McastTraceReplyTable entries being deleted"
	::= { rcCfmTransmitL2McastTraceEntry 8 }

rcCfmTransmitL2McastTracePriority OBJECT-TYPE
	SYNTAX          Integer32(0..7)
	MAX-ACCESS      read-create
        STATUS          current
        DESCRIPTION     "Priority. 3 bit value to be used in the VLAN hdr, 
                        if present in the transmitted frame."
	DEFVAL {7}
	::= { rcCfmTransmitL2McastTraceEntry 9 }

rcCfmTransmitL2McastTraceTtl OBJECT-TYPE
	SYNTAX          Integer32(0..255)
	MAX-ACCESS      read-create
        STATUS          current
        DESCRIPTION     "The number of hops remaining to this trace.
                        Decremented by 1 by each Bridge that handles trace.
                        If 0 on output, the trace is not transmitted to
                        the next hop.  The value of the TTL Field in the 
                        trace trasnmitted by originating MEP is controlled
                        by a Managed Object; the default value if none is 
                        specified is 64."
	DEFVAL {64}
	::= { rcCfmTransmitL2McastTraceEntry 10 }

rcCfmTransmitL2McastTraceSeqNumber OBJECT-TYPE
	SYNTAX 		Integer32
	MAX-ACCESS	read-only
	STATUS		current
	DESCRIPTION	"The transaction identifier/sequence number of the 
                        first message (to be) sent."
	::= { rcCfmTransmitL2McastTraceEntry 11}	
	
rcCfmTransmitL2McastTraceStatus OBJECT-TYPE
	SYNTAX 		INTEGER {
				ready(1),
				transmit(2),
                                abort(3)
			}
	MAX-ACCESS	read-create
	STATUS		current
	DESCRIPTION	"Status of the transmit loopback service:
			-ready.      The service is available.
			-transmit.   The service is transmitting, or about to 
                                     transmit the trace messages.
                        -abort       The service is aborted or about to abort
                                     the trace messages.

			This column will also be used to avoid concurrency or 
                        race condition problems that could occur if two or 
                        more management entities try to 
			use the service at the same time. "
	DEFVAL {ready}
	::= { rcCfmTransmitL2McastTraceEntry 12}	

rcCfmTransmitL2McastTraceResultOk OBJECT-TYPE
	SYNTAX 		TruthValue
	MAX-ACCESS	read-only
	STATUS		current
	DESCRIPTION	"Indicates the result of the operation:
			-true.    The Trace Message(s) will/have been sent.
			-false.   The Trace Message(s) will not be sent."
	DEFVAL {true}
	::= { rcCfmTransmitL2McastTraceEntry 13 }

rcCfmTransmitL2McastTraceFlag    OBJECT-TYPE
	SYNTAX 		INTEGER {
				none(1),
				internalError(2),
                                mepDisabled(3), 
                                noResponse(4),
                                traceComplete(5),
				leafNode(6),
				noDataIsidFound(7)
			}
	MAX-ACCESS	read-only
	STATUS	        current 	
	DESCRIPTION	"Result flag indicating L2Trace status or error code. 
                         Each enum value represents a status or error case.  
                         1 - No error  
                         2 - Internal Error
                         3 - Mep must be enabled in order to perform trace
                         4 - No response received
                         5 - Trace completed
			 6 - On a leaf node in the i-sid tree
			 7 - No Data Isid was found for S,G"
	::= {  rcCfmTransmitL2McastTraceEntry 14}


-- The L2 Multicast Trace Reply Table

rcCfmL2McastTraceReplyTable OBJECT-TYPE
        SYNTAX          SEQUENCE OF RcCfmL2McastTraceReplyEntry
        MAX-ACCESS      not-accessible
        STATUS          current 
        DESCRIPTION     
                "This table contains a list of multicast route trace
                replies received by a specific MEP in response to a
                trace message."
        ::= { rcCfm 42}

rcCfmL2McastTraceReplyEntry OBJECT-TYPE
        SYNTAX          RcCfmL2McastTraceReplyEntry
        MAX-ACCESS      not-accessible
        STATUS          current 
        DESCRIPTION     "The L2 Multicast Trace Reply Table Entry"
        INDEX           { rcCfmL2McastTraceReplySrcIpAddrType,
                          rcCfmL2McastTraceReplySrcIpAddr,
                          rcCfmL2McastTraceReplyGroupIpAddrType,
                          rcCfmL2McastTraceReplyGroupIpAddr,
                          rcCfmL2McastTraceReplyServiceType,
                          rcCfmL2McastTraceReplyServiceId,
                          rcCfmL2McastTraceReplyHop,
                          rcCfmL2McastTraceReplyReceiveOrder
                        }
        ::= { rcCfmL2McastTraceReplyTable 1 }


RcCfmL2McastTraceReplyEntry ::= SEQUENCE {

        rcCfmL2McastTraceReplySrcIpAddrType          InetAddressType,
        rcCfmL2McastTraceReplySrcIpAddr              InetAddress,
        rcCfmL2McastTraceReplyGroupIpAddrType        InetAddressType,
        rcCfmL2McastTraceReplyGroupIpAddr            InetAddress,
        rcCfmL2McastTraceReplyServiceType            INTEGER,
        rcCfmL2McastTraceReplyServiceId              Integer32,
        rcCfmL2McastTraceReplyHop                    Integer32,
        rcCfmL2McastTraceReplyReceiveOrder           Integer32,
        rcCfmL2McastTraceReplyTtl                    Integer32,
        rcCfmL2McastTraceReplyVrfName                DisplayString,
        rcCfmL2McastTraceReplySrcMac                 MacAddress,
        rcCfmL2McastTraceReplyHostName               OCTET STRING,
        rcCfmL2McastTraceReplyLastSrcMac             MacAddress,
        rcCfmL2McastTraceReplyLastHostName           OCTET STRING,
        rcCfmL2McastTraceReplySpbmVlanId             Integer32,
	rcCfmL2McastTraceReplyBMac		     MacAddress,
	rcCfmL2McastTraceReplyIsid		     Integer32
        }

rcCfmL2McastTraceReplySrcIpAddrType OBJECT-TYPE
	SYNTAX          InetAddressType
	MAX-ACCESS      not-accessible
        STATUS          current
        DESCRIPTION     
                "The address type of Source IP Address"
	::= { rcCfmL2McastTraceReplyEntry 1 }

rcCfmL2McastTraceReplySrcIpAddr OBJECT-TYPE
	SYNTAX          InetAddress
	MAX-ACCESS      not-accessible
        STATUS          current
        DESCRIPTION     
                "Source IP Address. Support ipv4 at this time"
	::= { rcCfmL2McastTraceReplyEntry 2 }

rcCfmL2McastTraceReplyGroupIpAddrType OBJECT-TYPE
	SYNTAX          InetAddressType
	MAX-ACCESS      not-accessible
        STATUS          current
        DESCRIPTION     
                "The address type of Multicast Group IP Address"
	::= { rcCfmL2McastTraceReplyEntry 3 }

rcCfmL2McastTraceReplyGroupIpAddr OBJECT-TYPE
	SYNTAX          InetAddress
	MAX-ACCESS      not-accessible
        STATUS          current
        DESCRIPTION     
                "Multicast Group IP Address. Support ipv4 at this time"
	::= { rcCfmL2McastTraceReplyEntry 4 }

rcCfmL2McastTraceReplyServiceType OBJECT-TYPE
	SYNTAX          INTEGER {
                        vlan(1),
                        vrfid(2)
                        }
	MAX-ACCESS      not-accessible
        STATUS          current
        DESCRIPTION     
                "Service type indicates what value of service id means.
                 vlan - indicates value maps to VLAN
                 vrfid - indicates value maps to a VRF Id"
	::= { rcCfmL2McastTraceReplyEntry 5 }

rcCfmL2McastTraceReplyServiceId OBJECT-TYPE
	SYNTAX          Integer32
	MAX-ACCESS      not-accessible
        STATUS          current
        DESCRIPTION     
                "Value of VLAN or VRF-Id.  Meaning controlled by
                rcCfmL2McastTraceReplyServiceType.  Value must be
                valid for type (e.g. VLAN range 1..4094)"
	::= { rcCfmL2McastTraceReplyEntry 6 }

rcCfmL2McastTraceReplyHop OBJECT-TYPE
	SYNTAX          Integer32 (0..255)
	MAX-ACCESS      not-accessible
        STATUS          current
        DESCRIPTION     "The number of hops away from trace initiator"
	::= { rcCfmL2McastTraceReplyEntry 7 }

rcCfmL2McastTraceReplyReceiveOrder OBJECT-TYPE
	SYNTAX          Integer32 (1..2147483647)
	MAX-ACCESS      not-accessible
        STATUS          current
        DESCRIPTION     
                "An index to distinguish among multiple responses
                 with the same Transaction Identifier field  value. This value
                 is assigned sequentially from 1, in the order that the 
                Linktrace Initiator received the responses."
        ::= { rcCfmL2McastTraceReplyEntry 8 }

rcCfmL2McastTraceReplyTtl OBJECT-TYPE
	SYNTAX          Integer32(0..255)
	MAX-ACCESS      read-only
        STATUS          current
        DESCRIPTION     "Ttl field value for a returned trace response."
	::= { rcCfmL2McastTraceReplyEntry 9 }

rcCfmL2McastTraceReplyVrfName OBJECT-TYPE
	SYNTAX          DisplayString (SIZE (0..64))
	MAX-ACCESS      read-only
        STATUS          current
        DESCRIPTION     "The name of the Virtual Router of the originator"
        ::= { rcCfmL2McastTraceReplyEntry 10}

rcCfmL2McastTraceReplySrcMac OBJECT-TYPE
	SYNTAX          MacAddress
	MAX-ACCESS      read-only
        STATUS          current
        DESCRIPTION     "Mac address of the MP that respond to the trace
                        request"
	::= { rcCfmL2McastTraceReplyEntry 11 }

rcCfmL2McastTraceReplyHostName OBJECT-TYPE
	SYNTAX          OCTET STRING (SIZE (0..255))
	MAX-ACCESS      read-only
        STATUS          current
        DESCRIPTION     "The host name of the replying node"
	::= { rcCfmL2McastTraceReplyEntry 12 }

rcCfmL2McastTraceReplyLastSrcMac OBJECT-TYPE
	SYNTAX          MacAddress
	MAX-ACCESS      read-only
        STATUS          current
        DESCRIPTION     "The MAC address of the node that forwarded the trace
                        to the responding node"
	::= { rcCfmL2McastTraceReplyEntry 13 }

rcCfmL2McastTraceReplyLastHostName OBJECT-TYPE
	SYNTAX          OCTET STRING (SIZE (0..255))
	MAX-ACCESS      read-only
        STATUS          current
        DESCRIPTION     "The host name of the node that forwarded the trace
                        to the responding node"
	::= { rcCfmL2McastTraceReplyEntry 14 }

rcCfmL2McastTraceReplySpbmVlanId OBJECT-TYPE
	SYNTAX          Integer32
	MAX-ACCESS      read-only
        STATUS          current
        DESCRIPTION     "The SPBM VLAN id used for the trace"
	::= { rcCfmL2McastTraceReplyEntry 15 }


rcCfmL2McastTraceReplyBMac OBJECT-TYPE
	SYNTAX          MacAddress
	MAX-ACCESS      read-only
        STATUS          current
        DESCRIPTION     "The multicast MAC address for the group"
	::= { rcCfmL2McastTraceReplyEntry 16 }

rcCfmL2McastTraceReplyIsid OBJECT-TYPE
        SYNTAX        Integer32 (1..16777215)
        MAX-ACCESS    read-only
        STATUS        current
        DESCRIPTION   "Isid id for the group"
	::= { rcCfmL2McastTraceReplyEntry 17 }


END

RC-IP-MIB DEFINITIONS ::= BEGIN

IMPORTS
    MODULE-IDENTITY, OBJECT-TYPE, Integer32, Unsigned32, Counter32, IpAddress, TimeTicks
        FROM SNMPv2-SMI
    DisplayString, TruthValue, MacAddress, RowStatus, TimeStamp, PhysAddress
        FROM SNMPv2-TC
    SnmpAdminString
        FROM SNMP-FRAMEWORK-MIB
    InterfaceIndex, InterfaceIndexOrZero
        FROM IF-MIB
    rcIp, EnableValue, IdList
        FROM RAPID-CITY
    VrfIdentifier
        FROM RC-VRF-MIB
    InetAddressType, InetAddress
        FROM INET-ADDRESS-MIB
    ipMRouteEntry, ipMRouteNextHopEntry, ipMRouteInterfaceEntry
        FROM IPMROUTE-STD-MIB;


rcIpMib MODULE-IDENTITY
       LAST-UPDATED     "202005060000Z"
       ORGANIZATION     "Bay Networks, Rapid-City Group"
       CONTACT-INFO     "Yu-Ten Lee
                         Postal:        Nortel Networks, Inc.
                                        4655 Great America Parkway
                                        Santa Clara, CA 95052-8185

                         Tel:           408-495-2560
                         Fax:           408-495-6680
                         E-mail:        ylee@baynetworks.com"

       DESCRIPTION      "Enterprise MIB for the Accelar product family."

       REVISION "202005060000Z" -- 6 May 2019
       DESCRIPTION "Version 82: Add rcIpAdEntName
	   			Requested by Deb Fitzgerald (Prem)"

       REVISION "201906190000Z" -- 19 Jun 2019
       DESCRIPTION "Version 81: Add rcIpConfBfdVrfId and rcIpConfBfdVrfName
	                        to rcIpConfBfdTable.
	   			Requested by Vinay (commit 4a2f8e58) (Prem)"

       REVISION "201906060000Z" -- 06 Jun 2019
       DESCRIPTION "Version 80: Add mgmtOob, mgmtClip and mgmtVlan under
	   			rcIpAdEntIfType.
	   			Requested by Andrew Chillar (NLS) (Prem)"

       REVISION "201904040000Z" -- 04 Apr 2019
       DESCRIPTION "Version 79: Corrected the OID of rcIpSpbPimGwNeighborEntry
	   			(from 2 to 1) (Prem)"

       REVISION "201703150000Z" -- 15 March 2017	 
       DESCRIPTION "Version 79: Added rcMRouteExtNextHopPortTable
	   			Originally requested by Osamu (submit 32617)
				and then Dorin Ionut interchanged the indices
				(submit 33322) - prempa."

       REVISION "201702010000Z" -- 01 February 2017	 
       DESCRIPTION "Version 78: Corrected MIB compiler errors."

       REVISION "201610040000Z" -- 04 Oct 2016	 
       DESCRIPTION "Version 77  Changed the enum values of rcIpSpbPimGwControllerForeignSrcType
	   			to match the enum values of rcIpSpbPimGwGatewayForeignSrcOwnerType.
				Requested by Ada Mladin (prempa)"

       REVISION "201610030000Z" -- 03 Oct 2016	 
       DESCRIPTION "Version 76  Added rcIpSpbPimGwNodeTable"
	   
       REVISION "201609150000Z" -- 15 September 2016	 
       DESCRIPTION "Version 75: Changed the order of named-number values of 
	   			rcIpSpbPimGwGatewayForeignSrcOwnerType
				Requested by Saru, Nadia Cristina (prempa)"

       REVISION "201609120000Z" -- 12 September 2016	 
       DESCRIPTION "Version 74: Replaced rcIpSpbPimGwGatewayForeignSrcOwner
	   			with rcIpSpbPimGwGatewayForeignSrcOwnerType in
				rcIpSpbPimGwGatewayForeignSrcTable.
				Requested by Saru, Nadia Cristina (prempa)"

       REVISION "201606280000Z" -- 28 June 2016	 
       DESCRIPTION "Version 73: Update rcIpSpbPimGwControllerForeignSrcTable by removing
	                        rcIpSpbPimGwControllerForeignSrcToSourceAddress.
				And corrected the OID.
				Added rcIpSpbPimGwGatewayForeignSrcOwner to
				      rcIpSpbPimGwGatewayForeignSrcTable"
	   
       REVISION "201606200000Z" -- 20 June 2016	 
       DESCRIPTION "Version 72: Changed the range of the following objects
	                        from 5..65535 to 0..18724 
				rcIpSpbPimGwGlobalHelloInterval,
				rcIpSpbPimGwInterfaceHelloInterval.

				Changed the range of the following objects
				from 5..65535 to 1..18724
				rcIpSpbPimGwGlobalJoinPruneInterval,
				rcIpSpbPimGwInterfaceJoinPruneInterval."

       REVISION "201606160000Z" -- 16 June 2016	 
       DESCRIPTION "Version 72: Added rcIpConfIpsecEnable to
	                        rcIpConfTable"

       REVISION "201606020000Z" -- 02 June 2016
       DESCRIPTION "Version 71: Added rcMRouteExtNextHopL2Isid to
                                rcMRouteExtNextHopTable"	   

       REVISION "201605060000Z" -- 06 May 2016
       DESCRIPTION "Version 70: Changed the range of the following objects
	   			from 1..64 to 0..64 -
				rcIpIsisInFilterNickNamePolicyName,
				rcIpIsisInFilterIsidPolicyName,
				rcIpIsisInFilterNickNameIsidPolicyName,
				rcIpIsisInFilterIsidListPolicyName,
				rcIpIsisInFilterNickNameIsidListPolicyName,
				rcIpIsisInFilterDefaultPolicyName

				Added the following objects - 
				rcIpIsisInFilterNickNameBackBonePolicyName,
				rcIpIsisInFilterIsidBackbonePolicyName,
				rcIpIsisInFilterNickNameIsidBackBonePolicyName,
				rcIpIsisInFilterIsidListBackBonePolicyName,
				rcIpIsisInFilterNickNameIsidListBackBonePolicyName,
				rcIpIsisInFilterDefaultBackbonePolicyName.
				Requested by Hemadri Mhaskar (submit 28198) (prempa)"

       REVISION "201604280000Z" -- 28 April 2016
       DESCRIPTION "Version 69: Added rcMRouteExt, rcMRouteExtTable,
	                        rcMRouteExtNextHopTable,
				rcMRouteExtInterfaceTable"

       REVISION "201604210000Z" -- 21 April 2016
       DESCRIPTION "Version 68:	 Changed rcIpSpbPimGwGatewayForeignSrcInPort
	   			 from INTEGER to InterfaceIndex. (prempa)"
	   
       REVISION "201604200000Z" -- 20 April 2016
       DESCRIPTION "Version 67:	 Changed rcIpSpbPimGwGlobalHelloInterval and 
				 rcIpSpbPimGwGlobalJoinPruneInterval from 
				 read-write to read-only.
				 Requested by Veda/Osamu (prempa)"
	   
       REVISION "201604190000Z" -- 19 April 2016
       DESCRIPTION "Version 66:	 Added rcIpSpbPimGw, rcIpSpbPimGwGlobal,
	   			 rcIpSpbPimGwGlobalHelloInterval, 
				 rcIpSpbPimGwGlobalJoinPruneInterval,
				 rcIpSpbPimGwInterfaceTable,
				 rcIpSpbPimGwNeighborTable,
				 rcIpSpbPimGwControllerForeignSrcTable,
				 rcIpSpbPimGwControllerSpbmcSrcTable,
				 rcIpSpbPimGwGatewayForeignSrcTable.
				 Removed rcIpMcastPimGwControllerForeignSrcTable and
				 rcIpMcastPimGwAgentForeignSrcTable.
				 Requested by Veda (prempa)"
	   
       REVISION "201601120000Z" -- 12 Jan 2016
       DESCRIPTION "Version 65:	 Added rcIpConfVrrpChkSumComputation (Request By Doru)"
	   
       REVISION "201511060000Z" -- 6 November 2015
       DESCRIPTION "Version 64: Renamed rcIpMulticastForeignSourceTable
	   			to rcIpMcastPimGwControllerForeignSrcTable
				and redesigned the table (based on design
				requirements) and also created a new table
				- rcIpMcastPimGwAgentForeignSrcTable.
	   			Requested by Veda, submit 26004 (Prem)"

       REVISION "201509020000Z" -- 2 September 2015
       DESCRIPTION "Version 63: Added rcIpMulticastPimGateway and
	   			rcIpMulticastForeignSourceTable.
	   			Requested by Veda, submit 25389 (Prem)"
	   
       REVISION "201509010000Z" -- 01 Sept. 2015
       DESCRIPTION "Version 62: Added rcIpConfGlobalSourceRouteEnable and
	                              rcIpConfGlobalIcmpEchoBroadcastRequestEnable
				      (malok) "

       REVISION "201506240000Z" -- 24 June 2015
       DESCRIPTION "Version 61: Changed rcIpConfPimGateway to 
	   			rcIpConfPimGatewayEnable and also
				changed the SYNTAX to TruthValue. (Prem)"

       REVISION "201506240000Z" -- 24 June 2015
       DESCRIPTION "Version 60: Added rcIpConfPimGateway
	   			Requested by Julie Carleton (VOSS) (Prem)"

       REVISION "201505290000Z" -- 29 May 2015
       DESCRIPTION "Version 59:  Corrected MIB compiling error."
	   
       REVISION "201505060000Z" -- 06 May 2015
       DESCRIPTION "Version 58: Added rcIpConfVrrpVersion.
                                Requested by Doru/Cristina. Submit 23688 (Prem)"
	   
       REVISION "201504030000Z" -- 3 April 2015
       DESCRIPTION "Version 57: Added rcIpNetToMediaDestCvid."
		
       REVISION "201502030000Z" -- 3 February 2015
       DESCRIPTION "Version 56: Expand range for rcIpConfDhcpIfIndex.
                    Corrected syntax of rcIpDhcpOp82StatsCircuitId."
       
       REVISION "201411140000Z" -- 14 Nov 2014
       DESCRIPTION "Version 55:	Design changes resulted in removing -
	   		rcIpIsisInFilterNickNameTableApply,
			rcIpIsisInFilterIsidTableApply,
			rcIpIsisInFilterNickNameIsidTableApply,
			rcIpIsisInFilterIsidListTableApply,
			rcIpIsisInFilterNickNameIsidListTableApply,
			rcIpIsisInFilterApplyAll,
			rcIpIsisInFilterNickNameApply,
			rcIpIsisInFilterIsidApply,
			rcIpIsisInFilterNickNameIsidApply,
			rcIpIsisInFilterIsidListApply,
			rcIpIsisInFilterNickNameIsidListApply,
			rcIpIsisInFilterDefaultApply
		    and added - rcIpIsisInFilterApply.
		    Requested by Deborah Fitzgerald.
		    Changes originally made in VSP9K 4.0 (Prem)"

       REVISION "201410220000Z" -- 22 Oct 2014
       DESCRIPTION "Version 54:	Added rcIpIpmcPimStaleSessionDelete"
	   
       REVISION "201404040000Z" -- 04 April 2014
       DESCRIPTION "Version 53: Correct and update
	                      rcIpIsisInFilterNickNameIsidApply
	                       rcIpIsisInFilterNickNameTableApply
			       rcIpIsisInFilterIsidTableApply
	                       rcIpIsisInFilterNickNameIsidTableApply
	                       rcIpIsisInFilterIsidListTableApply
	                       rcIpIsisInFilterNickNameIsidListTableApply
	                       added rcIpIsisInFilterApplyAll"
	   
       REVISION "201403180000Z" -- 18 March 2014
       DESCRIPTION "Version 52: 
                    added mib objects -
                         rcIpIsisInFilterNickNameApply,
                         rcIpIsisInFilterIsidApply,
                         rcIpIsisInFilterNickNameIsidApply,
                         rcIpIsisInFilterIsidListApply,
                         rcIpIsisInFilterNickNameIsidListApply.
                    Removed rcIpIsisInFilterEnable.
                    Changed the following mib objects - 
                         rcIpIsisIsidListValue to rcIpIsisIsidListIsid,
                         rcIpIsisInFilterApply to rcIpIsisInFilterDefaultApply,
                         rcIpIsisInFilterPolicyName to rcIpIsisInFilterDefaultPolicyName,
                    Added range to -
                         rcIpIsisInFilterNickNamePolicyName,
                         rcIpIsisInFilterIsid,
                         rcIpIsisInFilterIsidPolicyName,
                         rcIpIsisInFilterNickNameIsid,
                         rcIpIsisInFilterNickNameIsidPolicyName,
                         rcIpIsisInFilterIsidListPolicyName,
                         rcIpIsisInFilterNickNameIsidListPolicyName"

       REVISION "201311080000Z"  -- Nov 13, 2013
       DESCRIPTION "Version 51: added rcIpIsis, rcIpIsisGenInFiler, 
                   rcIpIsisInFilterNickNameTableSize,
                   rcIpIsisInFilterNickNameApply, rcIpIsisInFilterIsidTableSize,
                   rcIpIsisInFilterIsidApply, rcIpIsisInFilterNickNameIsidTableSize,
                   rcIpIsisInFilterNickNameIsidApply, rcIpIsisInFilterIsidListTableSize,
                   rcIpIsisInFilterIsidListApply, rcIpIsisInFilterNickNameIsidListTableSize,
                   rcIpIsisInFilterNickNameIsidListApply, rcIpIsisInFilter,
                   rcIpIsisInFilterNickNameTable, rcIpIsisInFilterIsidTable,
                   rcIpIsisInFilterNickNameIsidTable, rcIpIsisIsidListTable,
                   rcIpIsisInFilterIsidListTable, rcIpIsisInFilterNickNameIsidListTable,
                   rcIpIsisInFilterDefault, rcIpIsisInFilterApply,
                   rcIpIsisInFilterEnable,rcIpIsisInFilterPolicyName"

       REVISION "201208160000Z"  -- August 16, 2012
       DESCRIPTION "Version 50: added rcIpNetToMediaBMac"
	   
       REVISION "201208020000Z"  -- August 02, 2012
       DESCRIPTION "Version 49: added rcIpMvpnTable"

       REVISION "201203120000Z"  -- March 12, 2012
       DESCRIPTION "Version 48: added rcIpNetToMediaTable in VSP 3.3"

       REVISION "201201090000Z"  -- Jan 09, 2012
       DESCRIPTION "Version 47: added rcIpConfDhcpAgentAddr and
	                              rcIpDhcpOp82StatsAgentAddr"

       REVISION "201110280000Z"  -- October 28, 2011
       DESCRIPTION "Version 46: added rcIpConfSpbMulticastEnable and 
	            rcIpConfSpbMulticastQuerierAddr"

       REVISION "201103020000Z"  -- March 2, 2011
       DESCRIPTION "Version 45: added rcIpConfGlobalArpMcastMacFlooding rcIpConfGlobalGarpEnable"
	   
       REVISION "201102070000Z"  -- February 7, 2011
       DESCRIPTION "Version 44:  Fixed typo in rcIpDhcpOp82StatsCircuitId." 

       REVISION "201101130000Z"  -- January 13, 2011
       DESCRIPTION "Version 43:  Changed MAX-ACCESS of rcIpDhcpOp82StatsIfIndex
                    to not-accessible.  Increased range of 
                    rcIpDhcpOp82StatsIfIndex from (0..6142).
                    Removed rcIpDhcpOp82StatsRowStatus." 

       REVISION "201101060000Z"  -- January 06, 2011
       DESCRIPTION "Version 42:  Added rcIpConfBfdStaticFlag and increased the 
	            size from 32 to 64 for rcIpRsmltOperVrfName, 
		    rcIpRsmltPeerVrfName and rcIpRsmltEdgePeerVrfName."
  
       REVISION "201012140000Z"  -- December 14, 2010
       DESCRIPTION "Version 41:  Added rcIpConfDhcpCircuitId, 
                                   rcIpConfDhcpRemoteId, rcIpConfDhcpTrusted
                                   to rcIpConfDhcpTable.
                                 Added rcIpDhcpOp82StatsTable."                     

       REVISION "201009290000Z"  -- September 29, 2010
       DESCRIPTION "Version 40:  Removed rcIpDhcpNewForwardTable. Originally the table was added
	                         in VSP 9000 3.0 stream to fix an issue, but before the stream 
				 was released, it was decided to back out this MIB. So removing
				 it from the MRT."
  
       REVISION "201009160000Z"  -- September 16, 2010
       DESCRIPTION "Version 39:  Added rcIpDhcpNewForwardTable"
  
       REVISION "201009140000Z"  -- September 14, 2010
       DESCRIPTION "Version 38:  Added rcIpConfGlobalEcmp5PathList,
                                       rcIpConfGlobalEcmp6PathList,
                                       rcIpConfGlobalEcmp7PathList,
                                       rcIpConfGlobalEcmp8PathList "

       REVISION "201008260000Z"  -- August 26, 2010
       DESCRIPTION "Version 37:  Added support for DHCP option 82 remote-id"

       REVISION "200909150000Z" -- 15 September 2009
       DESCRIPTION "Version 36: Added rcIpMulticastSquareSmlt and rcIpMulticastSquareSmltEnable."

       REVISION "200907090000Z" -- 09 July 2009
       DESCRIPTION "Version 35: Added IP ARP and IP MC record delete tables."

       REVISION "200904080000Z" -- 08 April 2009
       DESCRIPTION "Version 34: Added DHCP max-frame length object."

       REVISION "200903260000Z" -- 26 March 2009
       DESCRIPTION "Version 33: Added DHCP forwarding scalar objects."

       REVISION "200903100000Z" -- 10 March 2009
       DESCRIPTION "Version 32: Added rcIpEcmp."

       REVISION "200812080000Z" -- 08 December 2008
       DESCRIPTION "Version 31: Expand range of rcIpConfIfIndex."

       REVISION "200809240000Z" -- 24 September 2008
       DESCRIPTION "Version 30: Added rcIpConfBfdHoldOffInterval to rcIpConfBfdTable"

       REVISION "200809170000Z" -- 17 September 2008
       DESCRIPTION "Version 29: Added rcIpStaticMRoute"

       REVISION "200806260000Z" -- 26 June 2008
       DESCRIPTION "Version 28: Change rcIpDhcpForwardMode in sequence RcIpDhcpForwardEntry
                                SYNTAX from Integer32 to INTEGER.
                                Change rcIpConfIcmpRdiscPreferenceLevel in sequence RcIpConfIcmpRdiscEntry
                                SYNTAX from INTEGER to Integer32.
                                Add rcIpRsmltOperVrfId, rcIpRsmltOperVrfName in rcIpRsmltOperTable.
                                Add rcIpRsmltPeerVrfId, rcIpRsmltPeerVrfName in rcIpRsmltPeerTable.
                                Add rcIpRsmltEdgePeerVrfId, rcIpRsmltEdgePeerVrfName in rcIpRsmltEdgePeerTable.
                                Add SnmpAdminString in IMPORTS clause."
                                
       REVISION "200805080000Z" -- 08 May 2008
       DESCRIPTION "Version 27: Added objects to clear dhcp counters.
                                Fixed several SMIv2 compliance errors."

       REVISION "200804300000Z" -- 30 April 2008
       DESCRIPTION "Version 26: Added rcIpBfdTrapEnabled and rcIpBfdHoldOffTimerInterval"

       REVISION "200803140000Z" -- 14 March 2008
       DESCRIPTION "Version 25: Modified rcIpConfBfdEnable"

       REVISION "200803130000Z" -- 13 March 2008
       DESCRIPTION "Version 24: Changed module name to 'RC-VRF-MIB'
from 'RC-VIRTUAL-ROUTING-MIB'."

       REVISION "200803040000Z" -- 04 Mar 2008
       DESCRIPTION "Version 23: Deleted all objects under rcIpBfd"    

       REVISION "200802070000Z" -- 07 Feb 2008
       DESCRIPTION "Version 22: Added rcIpConfIpVpnLiteEnable to rcIpConfTable"    

       REVISION "200801100000Z" -- 10 Jan 2008
       DESCRIPTION "Version 21: Added rcIpConfBfdEnable in RcIpConfEntry, rcIpConfBfdTable, rcIpBfd"    
			
       REVISION "200705260000Z" -- 26 May 2007
       DESCRIPTION "Version 20: Revert the change made in Version 19.
			Added rcIpInterVrfStaticRoute."     

       REVISION "200705220000Z" -- 22 May 2007
       DESCRIPTION "Version 19: Exclude rcIpStaticRoute table."

       REVISION "200705170000Z" -- 17 May 2007
       DESCRIPTION "Version 18: Removed rcIpConfGlobalRoutingEnable, rcIpConfGlobalDefaultTTL, 
			rcIpConfGlobalArpLifeTime. Modified rcIpConfGlobalSuperNetEnable."

       REVISION "200704030000Z" -- 3 Apr 2007
       DESCRIPTION "Version 17: Added rcIpRsmltEdgeSupportEnable & rcIpRsmltEdgePeerTable"

       REVISION "200702200000Z" -- 20 Feb 2007
       DESCRIPTION "Version 16: Fixed a MIB compilation error"

       REVISION "200701310000Z" -- 31 Jan 2007
       DESCRIPTION "Version 15: Added 4 objects under rcIpConfGlobal"

       REVISION "200612290000Z" -- 29 December 2006
       DESCRIPTION "Version 14: Added rcIpAdEntVrfId"

       REVISION "200612130000Z" -- 13 December 2006
       DESCRIPTION "Version 13: Added rcIpVpn"

       REVISION "200607140000Z" -- 14 July 2006
       DESCRIPTION "Version 13: Added rcIpAdEntSecondaryIf"

       REVISION "200606150000Z" -- 15 June 2006
       DESCRIPTION "Version 12: Increased the range for rcIpConfDhcpIfIndex"

       REVISION "200602090000Z" -- 09 February 2006
       DESCRIPTION "Version 11: Added rcIpConfIsisEnable"

       REVISION "200511220000Z" -- 22 Nov 2005
       DESCRIPTION "Version 10: Added rcIpConfReversePathCheckEnable &
                                rcIpConfReversePathCheckMode"

       REVISION "200509260000Z" -- 26 Sep 2005
       DESCRIPTION "Version 9: Updated rcIpConfGlobalEcmpMaxPath to 8"

       REVISION "200505180000Z" -- 18 May 2005
       DESCRIPTION "Version 8: Removed rcIpConfOspfIfMtuIgnore from rcIpConfTable
                               and changes in rcIpConfOspfIfType"

       REVISION "200502160000Z" -- 16 Feb 2005
       DESCRIPTION "Version 7: Changed range for rcIpAdEntVlanId"

       REVISION "200502040000Z" -- 04 Feb 2005
       DESCRIPTION "Version 6 : Added rcIpConfOspfIfMtuIgnore in rcIpConfTable"

       REVISION "200407210000Z" -- 21 July 2004
       DESCRIPTION  "Version 5 : Fixed typo"

       REVISION "200407190000Z" -- 19 July 2004
       DESCRIPTION  "Version 4 : Added rcIpConfGlobalUdpCheckSumEnable"

       ::= { rcIp 0 }

        IpIsisPlsbNodeNickName ::= TEXTUAL-CONVENTION
        STATUS current
        DESCRIPTION
            "Plsb Node Nick name."
        SYNTAX OCTET STRING (SIZE(3))

-- IP Group

rcIpConf OBJECT IDENTIFIER ::= { rcIp 1 }

-- IP Configuration Table

rcIpConfTable OBJECT-TYPE
        SYNTAX        SEQUENCE OF RcIpConfEntry
        MAX-ACCESS    not-accessible
        STATUS        current
        DESCRIPTION   "A table used to maintain IP routing information 
                      for a particular interface."
        ::= { rcIpConf 1 }
 
rcIpConfEntry OBJECT-TYPE
        SYNTAX        RcIpConfEntry
        MAX-ACCESS    not-accessible
        STATUS        current
        DESCRIPTION   "Entry containing IP routing information.  An entry
                      is automatically created in this table when routing 
		      is enabled for an interface -or- when an ip address 
                      is configured on an interface."
        INDEX         { rcIpConfIfIndex }
        ::= { rcIpConfTable 1 }
 
RcIpConfEntry ::= SEQUENCE {
                rcIpConfIfIndex               InterfaceIndexOrZero,
                rcIpConfAdvertDefRte          TruthValue,
                rcIpConfAcceptDefRte          TruthValue,
		rcIpConfRowStatus             RowStatus,
                rcIpConfRipEnable             TruthValue,
                rcIpConfOspfEnable            TruthValue,
                rcIpConfIgmpEnable            TruthValue,
                rcIpConfAddrAssigned          TruthValue,
                rcIpConfDhcpEnable            TruthValue,
                rcIpConfTriggeredUpdateEnable TruthValue,
                rcIpConfAutoAggrerateEnable   TruthValue,
                rcIpConfGenerateDefaultRoute  TruthValue,
                rcIpConfAdvertiseWhenDown     TruthValue,
                rcIpConfDirectBroadcastEnable TruthValue,
                rcIpConfRipInPolicy           DisplayString,
                rcIpConfRipOutPolicy          DisplayString,
                rcIpConfOspfIfType            INTEGER,
                rcIpConfRipCost               Integer32,
                rcIpConfRipHolddown           Integer32,
                rcIpConfRipTimeout            Integer32,
                rcIpConfRsmltEnable           TruthValue,
                rcIpConfReversePathCheckEnable    TruthValue,
                rcIpConfReversePathCheckMode      INTEGER,
                rcIpConfIsisEnable            TruthValue,
                rcIpConfBfdEnable             TruthValue,
                rcIpConfIpVpnLiteEnable       TruthValue,
                rcIpConfSpbMulticastEnable        TruthValue,
                rcIpConfSpbMulticastQuerierAddr	  IpAddress,
		rcIpConfVrrpVersion               INTEGER,
		rcIpConfPimGatewayEnable      TruthValue,
		rcIpConfVrrpChkSumComputation  INTEGER,
		rcIpConfIpsecEnable           TruthValue

        }

rcIpConfIfIndex OBJECT-TYPE
        SYNTAX        InterfaceIndexOrZero
        MAX-ACCESS    read-only
        STATUS        current
        DESCRIPTION   "An unique value to identify a physical interface 
 		      or a logical interface (VLAN)."
        ::= { rcIpConfEntry 1 }

rcIpConfAdvertDefRte OBJECT-TYPE
        SYNTAX        TruthValue
        MAX-ACCESS    read-create
        STATUS        current
        DESCRIPTION   "Used to indicate whether this interface should
		      advertize a RIP default route." 
        ::= { rcIpConfEntry 2 }

rcIpConfAcceptDefRte OBJECT-TYPE
        SYNTAX        TruthValue
        MAX-ACCESS    read-create
        STATUS        current
        DESCRIPTION   "Used to indicate whether this interface should
		      accept a RIP default route."
        ::= { rcIpConfEntry 3 }

rcIpConfRowStatus OBJECT-TYPE
        SYNTAX        RowStatus
        MAX-ACCESS    read-create
        STATUS        current
        DESCRIPTION   "Row status for this entry."
        ::= { rcIpConfEntry 4 }

rcIpConfRipEnable OBJECT-TYPE
        SYNTAX        TruthValue
        MAX-ACCESS    read-create
        STATUS        current
        DESCRIPTION   "Enable or disable RIP routing on the specified
                      interface."
        ::= { rcIpConfEntry 5 }
 
rcIpConfOspfEnable OBJECT-TYPE
        SYNTAX        TruthValue
        MAX-ACCESS    read-create
        STATUS        current
        DESCRIPTION   "Enable or disable OSPF routing on the specified
                      interface."
        ::= { rcIpConfEntry 6 }
 
rcIpConfIgmpEnable OBJECT-TYPE
        SYNTAX        TruthValue
        MAX-ACCESS    read-create
        STATUS        current
        DESCRIPTION   "Enable or disable IGMP on the specified
                      interface."
        ::= { rcIpConfEntry 7 }
 
rcIpConfAddrAssigned OBJECT-TYPE
        SYNTAX        TruthValue
        MAX-ACCESS    read-only
        STATUS        current
        DESCRIPTION   "Indicate whether IpAddress has been assigned 
                      for this interface."
        ::= { rcIpConfEntry 8 }

rcIpConfDhcpEnable OBJECT-TYPE
        SYNTAX        TruthValue
        MAX-ACCESS    read-create
        STATUS        current
        DESCRIPTION   "Enable or disable DHCP on the specified
                      interface."
        ::= { rcIpConfEntry 9 }

rcIpConfTriggeredUpdateEnable OBJECT-TYPE
        SYNTAX        TruthValue
        MAX-ACCESS    read-create
        STATUS        current
        DESCRIPTION   "Used to indicate whether the RIP triggered update
		      feature should be enabled on this interface." 
        ::= { rcIpConfEntry 10 }
 
rcIpConfAutoAggrerateEnable OBJECT-TYPE
        SYNTAX        TruthValue
        MAX-ACCESS    read-create
        STATUS        current
        DESCRIPTION   "Used to indicate whether the auto aggregation 
		      feature should be enabled on this interface." 
        ::= { rcIpConfEntry 11 }
 
rcIpConfGenerateDefaultRoute OBJECT-TYPE
        SYNTAX        TruthValue
        MAX-ACCESS    read-create
        STATUS        current
        DESCRIPTION   "Used to indicate whether to generate a default
		      RIP route	on this interface." 
        ::= { rcIpConfEntry 12 }

rcIpConfAdvertiseWhenDown OBJECT-TYPE
        SYNTAX        TruthValue
        MAX-ACCESS    read-create
        STATUS        current
        DESCRIPTION   "The value is used indicated whether vlan state change
                       should be notified to layer 3 or not, provided the vlan
                       is configured as routable interface. Also used for
                       single routable ports, in that case the criteria for
                       state is PortOperStatus.
                       Vlan is considered as UP if atleast one member of the
                       port based vlan has link up, or atleast one port member
                       of the policy based has an entry in the MGID or atleast
                       one static member of the policy based vlan has link up.
                       Otherwise, vlan is considered as DOWN.
                       If the value is 'true' then the interface state change 
                       will not be notified to layer 3. (i.e., it always stays 
                       up). If the value is 'false' then the vlan state change 
                       will be notified to layer 3 so that IP related status 
                       reflects routable interface state."
        DEFVAL        { false }
        ::= { rcIpConfEntry 13 }
 
rcIpConfDirectBroadcastEnable OBJECT-TYPE
        SYNTAX        TruthValue
        MAX-ACCESS    read-create
        STATUS        current
        DESCRIPTION   "Used to indicate whether this interface should
                      forward direct broadcast traffic"
        DEFVAL        { true }
        ::= { rcIpConfEntry 14 }

rcIpConfRipInPolicy OBJECT-TYPE
        SYNTAX        DisplayString (SIZE(0..64))
        MAX-ACCESS    read-create
        STATUS        current
        DESCRIPTION   "Used to indicate whether this interface should
            advertize a RIP default route."
        ::= { rcIpConfEntry 15 }

rcIpConfRipOutPolicy OBJECT-TYPE
        SYNTAX        DisplayString (SIZE(0..64))
        MAX-ACCESS    read-create
        STATUS        current
        DESCRIPTION   "Used to indicate whether this interface should
            accept a RIP default route."
        ::= { rcIpConfEntry 16 }

rcIpConfOspfIfType OBJECT-TYPE
        SYNTAX   INTEGER    {
                    broadcast (1),
                    nbma (2),
                    pointToPoint (3),
                    pointToMultipoint (5),
                    passive (99)
                  }
        MAX-ACCESS    read-create
        STATUS        current
        DESCRIPTION   "OSPF Interface Type."
        ::= { rcIpConfEntry 17 } 

rcIpConfRipCost OBJECT-TYPE
        SYNTAX        Integer32 (1..15)
        MAX-ACCESS    read-create
        STATUS        current
        DESCRIPTION   "Used to indicate the rip cost for this interface."
        DEFVAL        { 1 }
        ::= { rcIpConfEntry 18 }

rcIpConfRipHolddown OBJECT-TYPE
        SYNTAX        Integer32 (0..360)
        MAX-ACCESS    read-create
        STATUS        current
        DESCRIPTION   "Used to indicate the rip holddown timer for this
                       interface"
        ::= { rcIpConfEntry 19 }

rcIpConfRipTimeout OBJECT-TYPE
        SYNTAX        Integer32 (15..259200)
        MAX-ACCESS    read-create
        STATUS        current
        DESCRIPTION   "Used to indicate the rip timeout interval for this
                       interface"
        ::= { rcIpConfEntry 20 }

rcIpConfRsmltEnable OBJECT-TYPE
        SYNTAX        TruthValue
        MAX-ACCESS    read-create
        STATUS        current
        DESCRIPTION   "Used to enable Route Smlt feature."
        DEFVAL        { false }
        ::= { rcIpConfEntry 21 }
 
rcIpConfReversePathCheckEnable OBJECT-TYPE
        SYNTAX        TruthValue
        MAX-ACCESS    read-create
        STATUS        current
        DESCRIPTION   "Used to indicate whether this interface should
                      perform Reverse Path Check"
        DEFVAL        { false }
        ::= { rcIpConfEntry 22 }

rcIpConfReversePathCheckMode OBJECT-TYPE
        SYNTAX   INTEGER    {
                    exist-only (1),
                    strict (2)
                  }
        MAX-ACCESS    read-create
        STATUS        current
        DESCRIPTION   "Reverse Path Checking mode."
        DEFVAL        { exist-only }
        ::= { rcIpConfEntry 23 }
 
rcIpConfIsisEnable OBJECT-TYPE
        SYNTAX        TruthValue 
        MAX-ACCESS        read-create
        STATUS        current
        DESCRIPTION   "Enable/disable Isis on this IP interface "
        ::= { rcIpConfEntry 24 }
 
rcIpConfBfdEnable OBJECT-TYPE
        SYNTAX	      TruthValue
        MAX-ACCESS    read-create
        STATUS	      current
        DESCRIPTION   "Enable or disable BFD on the specified
                       interface."
        DEFVAL	      { false }
        ::= { rcIpConfEntry 25}
 
rcIpConfIpVpnLiteEnable OBJECT-TYPE
        SYNTAX        TruthValue
        MAX-ACCESS    read-create
        STATUS        current
        DESCRIPTION   "Enable or disable ipvpn-lite capability on the specified
                       circuitless ip interface."
        ::= { rcIpConfEntry 26 }

rcIpConfSpbMulticastEnable OBJECT-TYPE
        SYNTAX        TruthValue
        MAX-ACCESS    read-create
        STATUS        current
        DESCRIPTION   "Enable or disable spb-multicast on this port"
        DEFVAL  { false }
        ::= { rcIpConfEntry 27 }

rcIpConfSpbMulticastQuerierAddr OBJECT-TYPE
         SYNTAX        IpAddress
         MAX-ACCESS    read-create
         STATUS        current
         DESCRIPTION   "querier-addr for spb-multicast"
         DEFVAL   { '00000000'H }    -- 0.0.0.0
         ::= { rcIpConfEntry 28 }

rcIpConfVrrpVersion OBJECT-TYPE
         SYNTAX        INTEGER {
                          unspecified(1),
                          v2(2),
                          v3(3)
		       }
         MAX-ACCESS    read-create
         STATUS        current
         DESCRIPTION   "Set the VRRP version for IPv4 on the specified 
	     		interface. It does not impact the use of IPv6 VRRPv3"
         ::= { rcIpConfEntry 29 }

rcIpConfPimGatewayEnable OBJECT-TYPE
        SYNTAX        TruthValue
        MAX-ACCESS    read-create
        STATUS        current
        DESCRIPTION   "Enable/disable PIM Gateway on this interface"
        DEFVAL        { false }
        ::= { rcIpConfEntry 30 }
    
rcIpConfVrrpChkSumComputation OBJECT-TYPE
         SYNTAX        INTEGER {
	 	          withPseudoHeader(1),
                          withoutPseudoHeader(2)
                       }
         MAX-ACCESS    read-create
         STATUS        current
         DESCRIPTION   "Set the IPv4 VRRPv3 checksum computation method on the specified
                       interface."
         ::= { rcIpConfEntry 31 }

rcIpConfIpsecEnable OBJECT-TYPE
        SYNTAX        TruthValue
        MAX-ACCESS    read-write
        STATUS        current
        DESCRIPTION   "Used to indicate whether IPSec is enabled or disabled on the interface"
        DEFVAL        { false }
        ::= { rcIpConfEntry 32 }
 
 
-- rcIpConfOspfTable ::= { rcIpConf 2 } defined in rcOspf.mib

rcIpConfGlobal   OBJECT IDENTIFIER       ::= { rcIpConf 6 }

rcIpConfGlobalRipHoldDownTime OBJECT-TYPE
        SYNTAX        Integer32 (0..360)
        MAX-ACCESS    read-write
        STATUS        current
        DESCRIPTION   "Used to set the system-wide RIP hold down time
                      in seconds."
        DEFVAL        { 120 }
        ::= { rcIpConfGlobal 1 }

rcIpConfGlobalIcmpNetUnreach OBJECT-TYPE
        SYNTAX        TruthValue
        MAX-ACCESS    read-write
        STATUS        current
        DESCRIPTION   "Used to set the icmp net unreach feature
                       enable/disable."
        DEFVAL        { false }
        ::= { rcIpConfGlobal 2 }

rcIpConfGlobalEcmpEnable OBJECT-TYPE
        SYNTAX        TruthValue
        MAX-ACCESS    read-write
        STATUS        current
        DESCRIPTION   "Used to set the ecmp enable/disable."
        DEFVAL        { false }
        ::= { rcIpConfGlobal 3 }

rcIpConfGlobalEcmpMaxPath OBJECT-TYPE
        SYNTAX        Integer32 (1..8)
        MAX-ACCESS    read-write
        STATUS        current
        DESCRIPTION   "Used to globally configure maximum ECMP paths number."
        DEFVAL        { 1 }
        ::= { rcIpConfGlobal 4 }

rcIpConfGlobalAlternativeEnable OBJECT-TYPE
        SYNTAX        TruthValue
        MAX-ACCESS    read-write
        STATUS        current
        DESCRIPTION   "Used to globally configure alternative enable."
        DEFVAL        { true }
        ::= { rcIpConfGlobal 5 }

rcIpConfGlobalRouteDiscoveryEnable OBJECT-TYPE
     SYNTAX       TruthValue
     MAX-ACCESS   read-write
     STATUS       current
     DESCRIPTION  "Enable/disable ICMP Route Discovery  feature"
     DEFVAL       { true }
     ::= { rcIpConfGlobal 6 }

rcIpConfGlobalRipTimeOutInterval OBJECT-TYPE
     SYNTAX       Integer32 (15..259200)
     MAX-ACCESS   read-write
     STATUS       current
     DESCRIPTION  "Rip TimeOut Interval in seconds"
     DEFVAL       { 180 }
     ::= { rcIpConfGlobal 8 }

rcIpConfGlobalRipDefImportMetric OBJECT-TYPE
     SYNTAX       Integer32 (0..15)
     MAX-ACCESS   read-write
     STATUS       current
     DESCRIPTION  "Rip def import metric"
     DEFVAL       { 8 }
     ::= { rcIpConfGlobal 9 }

rcIpConfGlobalEcmp1PathList OBJECT-TYPE
     SYNTAX       DisplayString
     MAX-ACCESS   read-write
     STATUS       current
     DESCRIPTION  "Routes to networks specified in this prefix-list
                   can have upto 1 ECMP path, irrespective of
                   ecmp-max-path configuration"
     ::= { rcIpConfGlobal 10 }

rcIpConfGlobalEcmp2PathList OBJECT-TYPE
     SYNTAX       DisplayString
     MAX-ACCESS   read-write
     STATUS       current
     DESCRIPTION  "Routes to networks specified in this prefix-list
                   can have upto 2 ECMP path, irrespective of
                   ecmp-max-path configuration."
     ::= { rcIpConfGlobal 11 }

rcIpConfGlobalEcmp3PathList OBJECT-TYPE
     SYNTAX       DisplayString
     MAX-ACCESS   read-write
     STATUS       current
     DESCRIPTION  "Routes to networks specified in this prefix-list
                   can have upto 3 ECMP path, irrespective of
                   ecmp-max-path configuration."
     ::= { rcIpConfGlobal 12 }

rcIpConfGlobalEcmp4PathList OBJECT-TYPE
     SYNTAX       DisplayString
     MAX-ACCESS   read-write
     STATUS       current
     DESCRIPTION  "Routes to networks specified in this prefix-list
                   can have upto 4 ECMP path, irrespective of
                   ecmp-max-path configuration."
     ::= { rcIpConfGlobal 13 }

rcIpConfGlobalEcmpPathListApply OBJECT-TYPE
     SYNTAX       TruthValue
     MAX-ACCESS   read-write
     STATUS       current
     DESCRIPTION  "This is to apply any changes in ECMP path list
                   configuration or in the prefix-lists configured to
                   be used as path list"
     ::= { rcIpConfGlobal 14 }

rcIpConfGlobalIcmpRedirectMsg OBJECT-TYPE
     SYNTAX       TruthValue
     MAX-ACCESS   read-write
     STATUS       current
     DESCRIPTION  ""
     ::= { rcIpConfGlobal 15 }

rcIpConfGlobalMulticastMacFloodingStatus OBJECT-TYPE
     SYNTAX       TruthValue
     MAX-ACCESS   read-write
     STATUS       current
     DESCRIPTION  ""
     ::= { rcIpConfGlobal 16 }

rcIpConfGlobalArpThreshold OBJECT-TYPE
     SYNTAX       Integer32 (50..1000)
     MAX-ACCESS   read-write
     STATUS       current
     DESCRIPTION  "Defines the maximum number of outstanding arp request
                   a switch can generate."
     DEFVAL       { 500 }
     ::= { rcIpConfGlobal 17 }

rcIpConfGlobalAllowMoreSpecificNonLocalRouteEnable OBJECT-TYPE
     SYNTAX       TruthValue
     MAX-ACCESS   read-write
     STATUS       current
     DESCRIPTION  "Used to determine whether more specific non local routes will go into the routing table."
    DEFVAL        { false }
     ::= { rcIpConfGlobal 18 }

rcIpConfGlobalUdpCheckSumEnable OBJECT-TYPE
     SYNTAX       TruthValue
     MAX-ACCESS   read-write
     STATUS       current
     DESCRIPTION  "Enable/disable UDP checksum calculation."
     DEFVAL       { true }
     ::= { rcIpConfGlobal 19 }

rcIpConfGlobalSuperNetEnable OBJECT-TYPE
     SYNTAX       TruthValue
     MAX-ACCESS   read-write
     STATUS       current
     DESCRIPTION  "Used to globally enable Supernetting/ CIDR 
                   routing for IP"
     DEFVAL       { false }
     ::= { rcIpConfGlobal 20 }

rcIpConfGlobalEcmp5PathList OBJECT-TYPE
     SYNTAX       DisplayString
     MAX-ACCESS   read-write
     STATUS       current
     DESCRIPTION  "Routes to networks specified in this prefix-list
                   can have upto 5 ECMP path, irrespective of
                   ecmp-max-path configuration."
     ::= { rcIpConfGlobal 21 }

rcIpConfGlobalEcmp6PathList OBJECT-TYPE
     SYNTAX       DisplayString
     MAX-ACCESS   read-write
     STATUS       current
     DESCRIPTION  "Routes to networks specified in this prefix-list
                   can have upto 6 ECMP path, irrespective of
                   ecmp-max-path configuration."
     ::= { rcIpConfGlobal 22 }
rcIpConfGlobalEcmp7PathList OBJECT-TYPE
     SYNTAX       DisplayString
     MAX-ACCESS   read-write
     STATUS       current
     DESCRIPTION  "Routes to networks specified in this prefix-list
                   can have upto 7 ECMP path, irrespective of
                   ecmp-max-path configuration."
     ::= { rcIpConfGlobal 23 }

rcIpConfGlobalEcmp8PathList OBJECT-TYPE
     SYNTAX       DisplayString
     MAX-ACCESS   read-write
     STATUS       current
     DESCRIPTION  "Routes to networks specified in this prefix-list
                   can have upto 8  ECMP path, irrespective of
                   ecmp-max-path configuration."
     ::= { rcIpConfGlobal 24 }

rcIpConfGlobalGarpEnable OBJECT-TYPE
     SYNTAX       TruthValue
     MAX-ACCESS   read-write
     STATUS       current
     DESCRIPTION  "Used to set the gratuitous-arp enable/disable"
     ::= { rcIpConfGlobal 25 }

rcIpConfGlobalArpMcastMacFlooding OBJECT-TYPE
     SYNTAX       TruthValue
     MAX-ACCESS   read-write
     STATUS       current
     DESCRIPTION  "Enable/disable Ip Arp Multicast Mac Flooding feature."
     DEFVAL       { false }
     ::= { rcIpConfGlobal 26 }
 
rcIpConfGlobalSourceRouteEnable OBJECT-TYPE
     SYNTAX       TruthValue
     MAX-ACCESS	  read-write
     STATUS       current
     DESCRIPTION  "Used to globally enable/disable ip source routing feature."
     DEFVAL       { false }
     ::= { rcIpConfGlobal 27 }
 
rcIpConfGlobalIcmpEchoBroadcastRequestEnable OBJECT-TYPE
    SYNTAX	  TruthValue
    MAX-ACCESS    read-write
    STATUS	  current
    DESCRIPTION   "Used to globally enable/disable
	           ip icmp echo broadcast request feature."
    DEFVAL        { true }
    ::= { rcIpConfGlobal 28 }
 
-- IP Configuration IP Interface Table

rcIpConfV2Table OBJECT-TYPE
        SYNTAX        SEQUENCE OF RcIpConfV2Entry
        MAX-ACCESS    not-accessible
        STATUS        deprecated
        DESCRIPTION   "A table used to maintain IP routing information
                      for a particular interface."
        ::= { rcIpConf 8 }

rcIpConfV2Entry OBJECT-TYPE
        SYNTAX        RcIpConfV2Entry
        MAX-ACCESS    not-accessible
        STATUS        deprecated
        DESCRIPTION   "Entry containing IP routing information.  An entry
                      is automatically created in this table when routing
                      is enabled for an interface -or- when an ip address
                      is configured on an interface."
        INDEX         { rcIpConfV2Index, rcIpConfV2Addr }
        ::= { rcIpConfV2Table 1 }

RcIpConfV2Entry ::= SEQUENCE {
                rcIpConfV2Index               InterfaceIndexOrZero,
                rcIpConfV2Addr                  IpAddress,
                rcIpConfV2RowStatus             RowStatus,
                rcIpConfV2AdvertDefRte          TruthValue,
                rcIpConfV2AcceptDefRte          TruthValue,
                rcIpConfV2RipEnable             TruthValue,
                rcIpConfV2OspfEnable            TruthValue,
                rcIpConfV2IgmpEnable            TruthValue,
                rcIpConfV2AddrAssigned          TruthValue,
                rcIpConfV2TriggeredUpdateEnable TruthValue,
                rcIpConfV2RipAutoAggrerateEnable TruthValue,
                rcIpConfV2RipGenerateDefaultRoute TruthValue,
                rcIpConfV2AdvertiseWhenDown       TruthValue
        }

rcIpConfV2Index OBJECT-TYPE
        SYNTAX        InterfaceIndexOrZero (0..4094)
        MAX-ACCESS    read-only
        STATUS        deprecated
        DESCRIPTION   "An unique value to identify a physical interface
                      or a logical interface (VLAN)."
        ::= { rcIpConfV2Entry 1 }

rcIpConfV2Addr OBJECT-TYPE
        SYNTAX        IpAddress
        MAX-ACCESS    read-only
        STATUS        deprecated
        DESCRIPTION   "Ip interface address."
        ::= { rcIpConfV2Entry 2 }

rcIpConfV2RowStatus OBJECT-TYPE
        SYNTAX        RowStatus
        MAX-ACCESS      read-create
        STATUS        deprecated
        DESCRIPTION   "Row status for this entry."
        ::= { rcIpConfV2Entry 3 }

rcIpConfV2AdvertDefRte OBJECT-TYPE
        SYNTAX        TruthValue
        MAX-ACCESS      read-create
        STATUS        deprecated
        DESCRIPTION   "Used to indicate whether this interface should
                      advertize a RIP default route."
        ::= { rcIpConfV2Entry 4 }

rcIpConfV2AcceptDefRte OBJECT-TYPE
        SYNTAX        TruthValue
        MAX-ACCESS      read-create
        STATUS        deprecated
        DESCRIPTION   "Used to indicate whether this interface should
                      accept a RIP default route."
        ::= { rcIpConfV2Entry 5 }

rcIpConfV2RipEnable OBJECT-TYPE
        SYNTAX        TruthValue
        MAX-ACCESS      read-create
        STATUS        deprecated
        DESCRIPTION   "Enable or disable RIP routing on the specified
                      interface."
        ::= { rcIpConfV2Entry 6 }

rcIpConfV2OspfEnable OBJECT-TYPE
        SYNTAX        TruthValue
        MAX-ACCESS      read-create
        STATUS        deprecated
        DESCRIPTION   "Enable or disable OSPF routing on the specified
                      interface."
        ::= { rcIpConfV2Entry 7 }

rcIpConfV2IgmpEnable OBJECT-TYPE
        SYNTAX        TruthValue
        MAX-ACCESS      read-create
        STATUS        deprecated
        DESCRIPTION   "Enable or disable IGMP on the specified
                      interface."
        ::= { rcIpConfV2Entry 8 }

rcIpConfV2AddrAssigned OBJECT-TYPE
        SYNTAX        TruthValue
        MAX-ACCESS    read-only
        STATUS        deprecated
        DESCRIPTION   "Indicate whether IpAddress has been assigned
                      for this interface."
        ::= { rcIpConfV2Entry 9 }

rcIpConfV2TriggeredUpdateEnable OBJECT-TYPE
        SYNTAX        TruthValue
        MAX-ACCESS      read-create
        STATUS        deprecated
        DESCRIPTION   "Used to indicate whether the RIP triggered update
                      feature should be enabled on this interface."
        ::= { rcIpConfV2Entry 10 }

rcIpConfV2RipAutoAggrerateEnable OBJECT-TYPE
        SYNTAX        TruthValue
        MAX-ACCESS      read-create
        STATUS        deprecated
        DESCRIPTION   "Used to indicate whether the auto aggregation
                      feature should be enabled on this interface."
        ::= { rcIpConfV2Entry 11 }

rcIpConfV2RipGenerateDefaultRoute OBJECT-TYPE
        SYNTAX        TruthValue
        MAX-ACCESS      read-create
        STATUS        deprecated
        DESCRIPTION   "Used to indicate whether to generate a default
                      RIP route on this interface."
        ::= { rcIpConfV2Entry 12 }

rcIpConfV2AdvertiseWhenDown OBJECT-TYPE
        SYNTAX        TruthValue
        MAX-ACCESS      read-create
        STATUS        deprecated
        DESCRIPTION   "The value is used indicated whether vlan state change
                       should be notified to layer 3 or not, provided the vlan
                       is configured as routable interface. Also used for
                       single routable ports, in that case the criteria for
                       state is PortOperStatus.
                       Vlan is considered as UP if atleast one member of the
                       port based vlan has link up, or atleast one port member
                       of the policy based has an entry in the MGID or atleast
                       one static member of the policy based vlan has link up.
                       Otherwise, vlan is considered as DOWN.
                       If the value is 'true' then the interface state change
                       will not be notified to layer 3. (i.e., it always stays
                       up). If the value is 'false' then the vlan state change
                       will be notified to layer 3 so that IP related status
                       reflects routable interface state."
        DEFVAL        { false }
        ::= { rcIpConfV2Entry 13 }


-- IP Route Smlt Table

rcIpConfRsmltTable OBJECT-TYPE
        SYNTAX        SEQUENCE OF RcIpConfRsmltEntry
        MAX-ACCESS    not-accessible
        STATUS        current
        DESCRIPTION   "A table used to maintain OSPF summary route
                        metric parameter for a particular Area range.  "
       ::= { rcIpConf 11 }

rcIpConfRsmltEntry OBJECT-TYPE
        SYNTAX        RcIpConfRsmltEntry
        MAX-ACCESS    not-accessible
        STATUS        current
        DESCRIPTION   "Entry containing OSPF summary route metric
                        parameter for a particular Area range.
                        An entry is automatically created in this
                        table when an area range is configured through
                        ospfAreaAggregateTable in rfc1850rcc.mib"
        INDEX         { rcIpConfRsmltIfIndex }
        ::= { rcIpConfRsmltTable 1 }

RcIpConfRsmltEntry ::= SEQUENCE {
        rcIpConfRsmltIfIndex
            InterfaceIndex,
        rcIpConfRsmltHoldDownTimer
            Integer32,
        rcIpConfRsmltHoldUpTimer
            Integer32,
        rcIpConfRsmltRowStatus
            RowStatus
        }

rcIpConfRsmltIfIndex OBJECT-TYPE
        SYNTAX       InterfaceIndex
        MAX-ACCESS   read-only
        STATUS       current
        DESCRIPTION  "Interface Index, this is an index  of the table."
        ::= { rcIpConfRsmltEntry 1 }

rcIpConfRsmltHoldDownTimer OBJECT-TYPE
        SYNTAX       Integer32 (0..3600)
        MAX-ACCESS      read-create
        STATUS       current
        DESCRIPTION  "Timer value, the range of value is from 0 to 3600."
        ::= { rcIpConfRsmltEntry 2 }

rcIpConfRsmltHoldUpTimer OBJECT-TYPE
        SYNTAX       Integer32 (0..3600 | 9999)
        MAX-ACCESS      read-create
        STATUS       current
        DESCRIPTION  "The range of value 0 to 3600 or 9999. 9999 means
                      infinity."
        ::= { rcIpConfRsmltEntry 3 }

rcIpConfRsmltRowStatus OBJECT-TYPE
        SYNTAX       RowStatus
        MAX-ACCESS      read-create
        STATUS       current
        DESCRIPTION  "Row Status."
        ::= { rcIpConfRsmltEntry 4 }

-- IP BFD Table

rcIpConfBfdTable OBJECT-TYPE
        SYNTAX	      SEQUENCE OF RcIpConfBfdEntry
        MAX-ACCESS    not-accessible
        STATUS	      current
        DESCRIPTION   "BFD configuration table"
        ::= { rcIpConf 12 }

rcIpConfBfdEntry OBJECT-TYPE
        SYNTAX	      RcIpConfBfdEntry
        MAX-ACCESS    not-accessible
        STATUS	      current
        DESCRIPTION   "Used to configure BFD on a particular interface. An
                       entry is created automatically when the variable 
                       rcIpConfBfdEnable is set to TRUE.
                       Once created this entry will only be deleted if the
                       rcIpConfBfdRowStatus is set to 'destroy(6)'. In which
                       case, the rcIpConfBfdEnable is automatically reset to
                       the FALSE setting."
        INDEX	      { rcIpConfBfdIfIndex }
        ::= { rcIpConfBfdTable 1 }

RcIpConfBfdEntry ::= SEQUENCE {
                rcIpConfBfdIfIndex	      InterfaceIndex,
                rcIpConfBfdMinRxInterval  Integer32,
                rcIpConfBfdTxInterval	    Integer32,
                rcIpConfBfdMultiplier	    Integer32,
                rcIpConfBfdRowStatus	    RowStatus,
                rcIpConfBfdHoldOffInterval  Unsigned32,
                rcIpConfBfdStaticFlag       EnableValue,
                rcIpConfBfdVrfId            VrfIdentifier,
                rcIpConfBfdVrfName          DisplayString
        }

rcIpConfBfdIfIndex OBJECT-TYPE
        SYNTAX        InterfaceIndex
        MAX-ACCESS    not-accessible	
        STATUS        current
        DESCRIPTION   "Interface number.  The number can represent either
                       a physical or logical(VLAN) interface."
        ::= { rcIpConfBfdEntry 1 }

rcIpConfBfdMinRxInterval OBJECT-TYPE
        SYNTAX        Integer32 (100..65535)
        MAX-ACCESS    read-create
        STATUS        current
        DESCRIPTION   "the min rx interval in milliseconds"
        DEFVAL        { 200 }
        ::= { rcIpConfBfdEntry 2 }

rcIpConfBfdTxInterval	  OBJECT-TYPE
        SYNTAX        Integer32 (100..65535)
        MAX-ACCESS    read-create	
        STATUS        current
        DESCRIPTION   "the desired tx interval in milliseconds"
        DEFVAL        { 200 }
        ::= { rcIpConfBfdEntry 3 }

rcIpConfBfdMultiplier	  OBJECT-TYPE
        SYNTAX        Integer32 (1..20)
        MAX-ACCESS    read-create
        STATUS        current
        DESCRIPTION   "the multiplier BFD wait before rx timeout"
        ::= { rcIpConfBfdEntry 4 }

rcIpConfBfdRowStatus OBJECT-TYPE
        SYNTAX        RowStatus
        MAX-ACCESS    read-create
        STATUS        current
        DESCRIPTION   "Used to create/delete entries"
        ::= { rcIpConfBfdEntry 5 }

rcIpConfBfdHoldOffInterval OBJECT-TYPE
        SYNTAX        Unsigned32 (0..65535)
        MAX-ACCESS    read-create	
        STATUS        current
        DESCRIPTION 
                "This object specifies the hold off timer interval, in
                seconds. 0 means that hold off timer is disabled."
        DEFVAL        { 0 }
        ::= { rcIpConfBfdEntry 6 }

rcIpConfBfdStaticFlag  OBJECT-TYPE
        SYNTAX        EnableValue
        MAX-ACCESS    read-create
        STATUS        current
        DESCRIPTION
                "This object specifies the static-flag for bfd. When disabled,
                the static route will go down, when bfd is disabled"
       DEFVAL        { enable }  
       ::= { rcIpConfBfdEntry 7}

rcIpConfBfdVrfId  OBJECT-TYPE
       SYNTAX        VrfIdentifier
       MAX-ACCESS    read-create
       STATUS        current
       DESCRIPTION   "Indicates the Virtual Router to which the IPv4 BFD
                      instance belongs."
       ::= { rcIpConfBfdEntry 8 }

rcIpConfBfdVrfName OBJECT-TYPE
        SYNTAX         DisplayString (SIZE (0..32))
	MAX-ACCESS     read-only
	STATUS         current
	DESCRIPTION    "The Name of the Virtual Router to which the IPv4 BFD
	                instance belongs."
	::= { rcIpConfBfdEntry 9 }

rcIpRsmlt OBJECT IDENTIFIER       ::= { rcIp 26 }

rcIpRsmltGlobal OBJECT IDENTIFIER ::= { rcIpRsmlt 1 }

rcIpRsmltGlobalTableSize OBJECT-TYPE
        SYNTAX        Integer32
        MAX-ACCESS    read-only
        STATUS        current
        DESCRIPTION   "Route Smlt table size."
        ::= { rcIpRsmltGlobal 1 }

rcIpRsmltEdgeSupportEnable OBJECT-TYPE
        SYNTAX        TruthValue
        MAX-ACCESS    read-write
        STATUS        current
        DESCRIPTION   "Used to enable/disable RSMLT Edge Support feature"
        DEFVAL        { false }
        ::= { rcIpRsmltGlobal 2}

rcIpRsmltOperTable OBJECT-TYPE
        SYNTAX          SEQUENCE OF RcIpRsmltOperEntry
        MAX-ACCESS      not-accessible
        STATUS          current
        DESCRIPTION     "Route Smlt Table"
    ::= { rcIpRsmlt 2 }

rcIpRsmltOperEntry OBJECT-TYPE
        SYNTAX          RcIpRsmltOperEntry
        MAX-ACCESS       not-accessible
        STATUS          current
        DESCRIPTION     "An entry of Ip As Path Access List Table."
        INDEX           { rcIpRsmltOperIfIndex }
        ::= { rcIpRsmltOperTable 1 }

RcIpRsmltOperEntry ::=
        SEQUENCE {
                rcIpRsmltOperIfIndex                 InterfaceIndex,
                rcIpRsmltOperAdminStatus             TruthValue,
                rcIpRsmltOperHoldDownTimer           Integer32,
                rcIpRsmltOperHoldDownTimeRemaining   Integer32,
                rcIpRsmltOperHoldUpTimer             Integer32,
                rcIpRsmltOperHoldUpTimeRemaining     Integer32,
                rcIpRsmltOperIpAddr                  IpAddress,
                rcIpRsmltOperOperStatus              INTEGER,
                rcIpRsmltOperSmltId                  IdList,
                rcIpRsmltOperSltId                   IdList,
                rcIpRsmltOperVlanId                  Integer32,
                rcIpRsmltOperMacAddr                 MacAddress,
                rcIpRsmltOperRowStatus               RowStatus,
                rcIpRsmltOperVrfId                   VrfIdentifier,
                rcIpRsmltOperVrfName                 SnmpAdminString
        }

rcIpRsmltOperIfIndex OBJECT-TYPE
        SYNTAX        InterfaceIndex
        MAX-ACCESS    read-only
        STATUS        current
        DESCRIPTION   "Route Smlt Oper IfIndex."
        ::= { rcIpRsmltOperEntry 1 }

rcIpRsmltOperAdminStatus OBJECT-TYPE
        SYNTAX        TruthValue
        MAX-ACCESS      read-create
        STATUS        current
        DESCRIPTION   "is a enable/disable flag."
        DEFVAL        { false }
        ::= { rcIpRsmltOperEntry 2 }

rcIpRsmltOperHoldDownTimer OBJECT-TYPE
        SYNTAX        Integer32 (0..3600)
        MAX-ACCESS      read-create
        STATUS        current
        DESCRIPTION   "Timer value, the range of value is from 0 to 3600."
        DEFVAL        { 0 }
        ::= { rcIpRsmltOperEntry 3 }

rcIpRsmltOperHoldDownTimeRemaining OBJECT-TYPE
        SYNTAX        Integer32 (0..3600)
        MAX-ACCESS    read-only
        STATUS        current
        DESCRIPTION   "The time value that indicate how much time
                       remaining of HoldDownTimer."
        DEFVAL        { 0 }
        ::= { rcIpRsmltOperEntry  4 }

rcIpRsmltOperHoldUpTimer OBJECT-TYPE
        SYNTAX        Integer32 (0..3600 | 9999)
        MAX-ACCESS      read-create
        STATUS        current
        DESCRIPTION   "The range of value 0 to 3600 or 9999. 9999 means
                       infinity."
        DEFVAL        { 0 }
        ::= { rcIpRsmltOperEntry  5 }

rcIpRsmltOperHoldUpTimeRemaining OBJECT-TYPE
        SYNTAX        Integer32 (0..3600 | 9999)
        MAX-ACCESS    read-only
        STATUS        current
        DESCRIPTION   "The time value that indicate how much time
                       remaining of HoldUpTimer."
        DEFVAL        { 0 }
        ::= { rcIpRsmltOperEntry  6 }

rcIpRsmltOperIpAddr OBJECT-TYPE
        SYNTAX        IpAddress
        MAX-ACCESS    read-only
        STATUS        current
        DESCRIPTION   "IP Interface with RSMLT on."
        DEFVAL   { '00000000'H }    -- 0.0.0.0
        ::= { rcIpRsmltOperEntry  7 }

rcIpRsmltOperOperStatus OBJECT-TYPE
        SYNTAX        INTEGER {
                        up(1),
                        down(2)
                      }
        MAX-ACCESS    read-only
        STATUS        current
        DESCRIPTION   "The operation status of Rsmlt, up or down."
        DEFVAL        { down }
        ::= { rcIpRsmltOperEntry  8 }

rcIpRsmltOperSmltId OBJECT-TYPE
        SYNTAX        IdList
        MAX-ACCESS    read-only
        STATUS        current
        DESCRIPTION   "The id range for SMLT is 1-32."
        ::= { rcIpRsmltOperEntry  9 }

rcIpRsmltOperSltId OBJECT-TYPE
        SYNTAX        IdList
        MAX-ACCESS    read-only
        STATUS        current
        DESCRIPTION   "The id range for SLT is 1-512."
        ::= { rcIpRsmltOperEntry  10 }

rcIpRsmltOperVlanId OBJECT-TYPE
        SYNTAX        Integer32 (1..4093)
        MAX-ACCESS    read-only
        STATUS        current
        DESCRIPTION   "Vlan id."
        ::= { rcIpRsmltOperEntry  11 }

rcIpRsmltOperMacAddr OBJECT-TYPE
        SYNTAX        MacAddress
        MAX-ACCESS    read-only
        STATUS        current
        DESCRIPTION   "Mac Address."
        ::= { rcIpRsmltOperEntry  12 }

rcIpRsmltOperRowStatus OBJECT-TYPE
        SYNTAX        RowStatus
        MAX-ACCESS      read-create
        STATUS        current
        DESCRIPTION   "Row Status."
        ::= { rcIpRsmltOperEntry  13 }

rcIpRsmltOperVrfId OBJECT-TYPE
        SYNTAX         VrfIdentifier
        MAX-ACCESS     read-only
        STATUS         current
        DESCRIPTION    "Indicates the Virtual Router to which the RSMLT
                        Oper instance belongs."
        ::={ rcIpRsmltOperEntry 14 }

rcIpRsmltOperVrfName OBJECT-TYPE
        SYNTAX         SnmpAdminString (SIZE (0..64))
        MAX-ACCESS     read-only
        STATUS         current
        DESCRIPTION    "Name of the Virtual Router to which the RSMLT Oper
                        instance belongs."
        ::={rcIpRsmltOperEntry 15}


-- Route Smlt Peer Table

rcIpRsmltPeerTable OBJECT-TYPE
        SYNTAX          SEQUENCE OF RcIpRsmltPeerEntry
        MAX-ACCESS      not-accessible
        STATUS          current
        DESCRIPTION     "Route Smlt Table"
    ::= { rcIpRsmlt 3 }

rcIpRsmltPeerEntry OBJECT-TYPE
        SYNTAX          RcIpRsmltPeerEntry
        MAX-ACCESS       not-accessible
        STATUS          current
        DESCRIPTION     "An entry of Ip As Path Access List Table."
        INDEX           { rcIpRsmltPeerIfIndex }
        ::= { rcIpRsmltPeerTable 1 }

RcIpRsmltPeerEntry ::=
        SEQUENCE {
                rcIpRsmltPeerIfIndex                 InterfaceIndex,
                rcIpRsmltPeerAdminStatus             TruthValue,
                rcIpRsmltPeerHoldDownTimer           Integer32,
                rcIpRsmltPeerHoldDownTimeRemaining   Integer32,
                rcIpRsmltPeerHoldUpTimer             Integer32,
                rcIpRsmltPeerHoldUpTimeRemaining     Integer32,
                rcIpRsmltPeerIpAddr                  IpAddress,
                rcIpRsmltPeerOperStatus              INTEGER,
                rcIpRsmltPeerSmltId                  IdList,
                rcIpRsmltPeerSltId                   IdList,
                rcIpRsmltPeerVlanId                  Integer32,
                rcIpRsmltPeerMacAddr                 MacAddress,
                rcIpRsmltPeerVrfId                   VrfIdentifier,
                rcIpRsmltPeerVrfName                 SnmpAdminString
        }

rcIpRsmltPeerIfIndex OBJECT-TYPE
        SYNTAX        InterfaceIndex
        MAX-ACCESS    read-only
        STATUS        current
        DESCRIPTION   "Route Smlt Oper IfIndex."
        ::= { rcIpRsmltPeerEntry 1 }

rcIpRsmltPeerAdminStatus OBJECT-TYPE
        SYNTAX        TruthValue
        MAX-ACCESS    read-only
        STATUS        current
        DESCRIPTION   "is a enable/disable flag."
        ::= { rcIpRsmltPeerEntry 2 }

rcIpRsmltPeerHoldDownTimer OBJECT-TYPE
        SYNTAX        Integer32 (0..3600)
        MAX-ACCESS    read-only
        STATUS        current
        DESCRIPTION   "Timer value, the range of value is from 0 to 3600."
        DEFVAL        { 0 }
        ::= { rcIpRsmltPeerEntry 3 }

rcIpRsmltPeerHoldDownTimeRemaining OBJECT-TYPE
        SYNTAX        Integer32 (0..3600)
        MAX-ACCESS    read-only
        STATUS        current
        DESCRIPTION   "The time value that indicate how much time
                       remaining of HoldDownTimer."
        DEFVAL        { 0 }
        ::= { rcIpRsmltPeerEntry  4 }

rcIpRsmltPeerHoldUpTimer OBJECT-TYPE
        SYNTAX        Integer32 (0..3600 | 9999)
        MAX-ACCESS    read-only
        STATUS        current
        DESCRIPTION   "The range of value 0 to 3600 or 9999. 9999 means
                       infinity."
        DEFVAL        { 0 }
        ::= { rcIpRsmltPeerEntry  5 }

rcIpRsmltPeerHoldUpTimeRemaining OBJECT-TYPE
        SYNTAX        Integer32 (0..3600 | 9999)
        MAX-ACCESS    read-only
        STATUS        current
        DESCRIPTION   "The time value that indicate how much time
                       remaining of HoldUpTimer."
        DEFVAL        { 0 }
        ::= { rcIpRsmltPeerEntry  6 }

rcIpRsmltPeerIpAddr OBJECT-TYPE
        SYNTAX        IpAddress
        MAX-ACCESS    read-only
        STATUS        current
        DESCRIPTION   "IP Interface with RSMLT on."
        DEFVAL   { '00000000'H }    -- 0.0.0.0
        ::= { rcIpRsmltPeerEntry  7 }

rcIpRsmltPeerOperStatus OBJECT-TYPE
        SYNTAX        INTEGER {
                        up(1),
                        down(2)
                      }
        MAX-ACCESS    read-only
        STATUS        current
        DESCRIPTION   "The operation status of Rsmlt, up or down."
        DEFVAL        { down }
        ::= { rcIpRsmltPeerEntry  8 }

rcIpRsmltPeerSmltId OBJECT-TYPE
        SYNTAX        IdList
        MAX-ACCESS    read-only
        STATUS        current
        DESCRIPTION   "The id range for SMLT is 1-32."
        ::= { rcIpRsmltPeerEntry  9 }

rcIpRsmltPeerSltId OBJECT-TYPE
        SYNTAX        IdList
        MAX-ACCESS    read-only
        STATUS        current
        DESCRIPTION   "The id range for SLT is 1-512."
        ::= { rcIpRsmltPeerEntry  10 }

rcIpRsmltPeerVlanId OBJECT-TYPE
        SYNTAX        Integer32 (1..4093)
        MAX-ACCESS    read-only
        STATUS        current
        DESCRIPTION   "Vlan id."
        ::= { rcIpRsmltPeerEntry  11 }

rcIpRsmltPeerMacAddr OBJECT-TYPE
        SYNTAX        MacAddress
        MAX-ACCESS    read-only
        STATUS        current
        DESCRIPTION   "Mac Address."
        ::= { rcIpRsmltPeerEntry  12 }
        
rcIpRsmltPeerVrfId   OBJECT-TYPE
        SYNTAX        VrfIdentifier
        MAX-ACCESS    read-only
        STATUS        current
        DESCRIPTION   "Indicates the Virtual Router to which the RSMLT Peer
                       instance belongs."
        ::={ rcIpRsmltPeerEntry 13 }

rcIpRsmltPeerVrfName  OBJECT-TYPE
        SYNTAX         SnmpAdminString (SIZE(0..64))
        MAX-ACCESS     read-only
        STATUS         current
        DESCRIPTION    "Name of the Virtual Router to which the RSMLT Peer
                        instance belongs."
        ::={ rcIpRsmltPeerEntry 14 }        

rcIpRsmltEdgePeerTable OBJECT-TYPE
        SYNTAX        SEQUENCE OF RcIpRsmltEdgePeerEntry
        MAX-ACCESS    not-accessible
        STATUS        current
        DESCRIPTION   "RSMLT Edge Support Peer Info table. This 
                      table consists of the RSMLT Peers for which 
                      the switch will act as a PeerForwarder."
        ::= { rcIpRsmlt 4 }

rcIpRsmltEdgePeerEntry OBJECT-TYPE
        SYNTAX        RcIpRsmltEdgePeerEntry
        MAX-ACCESS    not-accessible
        STATUS        current
        DESCRIPTION   "RSMLT Edge Support Peer Info Entry"
        INDEX         { rcIpRsmltEdgeVlanId }
        ::= { rcIpRsmltEdgePeerTable 1 }

RcIpRsmltEdgePeerEntry ::=
        SEQUENCE { 
                rcIpRsmltEdgeVlanId         Integer32,
                rcIpRsmltEdgePeerIpAddress  IpAddress,
                rcIpRsmltEdgePeerMacAddress MacAddress,
                rcIpRsmltEdgePeerVrfId      VrfIdentifier,
                rcIpRsmltEdgePeerVrfName    SnmpAdminString
        }

rcIpRsmltEdgeVlanId  OBJECT-TYPE
        SYNTAX        Integer32 (1..4094)
        MAX-ACCESS    not-accessible
        STATUS        current
        DESCRIPTION   "A value that uniquely identifies the Virtual LAN
                      associated with this entry."
        ::= { rcIpRsmltEdgePeerEntry 1}

rcIpRsmltEdgePeerIpAddress OBJECT-TYPE
        SYNTAX        IpAddress
        MAX-ACCESS    read-only
        STATUS        current
        DESCRIPTION   "IP address of the Peer RSMLT Interface."
         ::= { rcIpRsmltEdgePeerEntry 2}

rcIpRsmltEdgePeerMacAddress OBJECT-TYPE
        SYNTAX        MacAddress
        MAX-ACCESS    read-only
        STATUS        current
        DESCRIPTION   "The MAC address of the Peer RSMLT interface."
         ::= { rcIpRsmltEdgePeerEntry 3}
         
rcIpRsmltEdgePeerVrfId  OBJECT-TYPE
        SYNTAX        VrfIdentifier
        MAX-ACCESS    read-only
        STATUS        current
        DESCRIPTION   "Indicates the Virtual Router to which the RSMLT Edge Peer
                       instance belongs."
        ::={ rcIpRsmltEdgePeerEntry 4 }

rcIpRsmltEdgePeerVrfName OBJECT-TYPE
        SYNTAX        SnmpAdminString (SIZE(0..64))
        MAX-ACCESS    read-only
        STATUS        current
        DESCRIPTION   "Name of the Virtual Router to which the RSMLT Edge Peer
                       instance belongs."
        ::={ rcIpRsmltEdgePeerEntry 5 }         

-- IP Address Table

rcIpAddrTable OBJECT-TYPE
        SYNTAX        SEQUENCE OF RcIpAddrEntry
        MAX-ACCESS    not-accessible
        STATUS        current
        DESCRIPTION   "The table of addressing information relevant to
                      this entity's IP addresses.

                      This table is identical to the ipAddrTable in
                      MIB2 except the columns rcIpAdEntIfIndex and
                      rcIpAdEntAddr are reversed.  Also, the table
                      is indexed by both these variables."
        ::= { rcIp 2 }

rcIpAddrEntry OBJECT-TYPE
        SYNTAX        RcIpAddrEntry
        MAX-ACCESS        not-accessible
        STATUS        current
        DESCRIPTION   "The addressing information for one of this
                      entity's IP addresses."
        INDEX         { rcIpAdEntIfIndex, rcIpAdEntAddr }
        ::= { rcIpAddrTable 1 }

RcIpAddrEntry ::=
        SEQUENCE {
                rcIpAdEntIfIndex InterfaceIndex,
                rcIpAdEntAddr IpAddress,
                rcIpAdEntNetMask IpAddress,
                rcIpAdEntBcastAddrFormat INTEGER,
                rcIpAdEntReasmMaxSize Integer32,
                rcIpAdEntRowStatus RowStatus,
                rcIpAdEntVlanId Integer32,
                rcIpAdEntBrouterPort TruthValue,
                rcIpAdEntMacOffset Integer32,
                rcIpAdEntIfType INTEGER,
                rcIpAdEntSecondaryIf TruthValue,
		rcIpAdEntVrfId VrfIdentifier,
                rcIpAdEntName DisplayString
        }

rcIpAdEntIfIndex OBJECT-TYPE
        SYNTAX        InterfaceIndex
        MAX-ACCESS    read-only
        STATUS        current
        DESCRIPTION   "The index value which uniquely identifies the
                      interface to which this entry is applicable.  The
                      interface identified by a particular value of this
                      index is the same interface as identified by the
                      same value of ifIndex."
        ::= { rcIpAddrEntry 1 }

rcIpAdEntAddr OBJECT-TYPE
        SYNTAX        IpAddress
        MAX-ACCESS    read-only
        STATUS        current
        DESCRIPTION   "The IP address to which this entry's addressing
                      information pertains."
        ::= { rcIpAddrEntry 2 }

rcIpAdEntNetMask OBJECT-TYPE
        SYNTAX        IpAddress
        MAX-ACCESS    read-write
        STATUS        current
        DESCRIPTION   "The subnet mask associated with the IP address of
                      this entry.  The value of the mask is an IP
                      address with all the network bits set to 1 and all
                      the hosts bits set to 0."
        ::= { rcIpAddrEntry 3 }

rcIpAdEntBcastAddrFormat OBJECT-TYPE
        SYNTAX        INTEGER {
                         zeros(0),      -- use zeros
                         ones(1)        -- use ones
                      }
        MAX-ACCESS    read-only
        STATUS        current
        DESCRIPTION   "The IP broadcast address format used on this
                      interface."
        ::= { rcIpAddrEntry 4 }

rcIpAdEntReasmMaxSize OBJECT-TYPE
        SYNTAX        Integer32 (0..65535)
        MAX-ACCESS    read-only
        STATUS        current
        DESCRIPTION   "The size of the largest IP datagram which this
                      entity can re-assemble from incoming IP fragmented
                      datagrams received on this interface."
        ::= { rcIpAddrEntry 5 }

rcIpAdEntRowStatus OBJECT-TYPE
        SYNTAX        RowStatus
        MAX-ACCESS    read-write
        STATUS        current
        DESCRIPTION   "Used to create/delete entries"
        ::= { rcIpAddrEntry 6 }

rcIpAdEntVlanId OBJECT-TYPE
        SYNTAX        Integer32 (0..4096)
        MAX-ACCESS    read-write
        STATUS        current
        DESCRIPTION   "A value that uniquely identifies the Virtual LAN
                      associated with this entry. This value corresponds
                      to the lower 12 bits in the IEEE 802.1Q VLAN Tag."
        ::= { rcIpAddrEntry 7 }

rcIpAdEntBrouterPort OBJECT-TYPE
        SYNTAX        TruthValue
        MAX-ACCESS    read-only
        STATUS        current
        DESCRIPTION   "Used to indicate whether this entry correponds
                      to a brouter port (as oppose to a routable VLAN).
                      This value cannot be changed after the row is
                      created."
        ::= { rcIpAddrEntry 8 }

rcIpAdEntMacOffset OBJECT-TYPE
        SYNTAX        Integer32 (0..511)
        MAX-ACCESS    read-write
        STATUS        current
        DESCRIPTION   "Used to translate the ip address into mac address.
                       The system has 512 mac addresses of which 0-507 are reserved
                       for Boardwalk box. 508-511 is reserved for MG. One can either
                       mention a mac offset while configuring an ip on the
                       vlan or it can be alloted by the system within the above
                       range."
        ::= { rcIpAddrEntry 9 }

rcIpAdEntIfType   OBJECT-TYPE
     SYNTAX         INTEGER {
                         circuitLessIP(1),
                         brouterPort(2),
                         vlan(3),
			 mgmtOob(4),
			 mgmtClip(5),
			 mgmtVlan(6)
                    }
     MAX-ACCESS     read-only
     STATUS         current
     DESCRIPTION    "The address entry IfType indicates the type of the
                     interface. In the case of circuit-less-IP there is
                     no association with any ports. In other words, it can
                     be thought of as a virtual interface. The value
                     'brouter port' indicates this interface is associated
                     with a specific physical port. The value 'vlan'
                     indicates a logical port that contains one or physical
                     ports/MLT ports. The value 'mgmtOob' is for the out of
		     band mgmt port. The value 'mgmtClip' is for the
		     designated management clip. The value 'mgmtVlan' is for
		     the designated management vlan."
        ::= { rcIpAddrEntry 10 }

rcIpAdEntSecondaryIf   OBJECT-TYPE
     SYNTAX         TruthValue
     MAX-ACCESS     read-write
     STATUS         current
     DESCRIPTION    "Used to indicate whether this entry correponds
                     to a secondary interface (as oppose to a primary interface).
                     This value cannot be changed after the row is
                     created."
     ::= { rcIpAddrEntry 11 }

rcIpAdEntVrfId   OBJECT-TYPE 
     SYNTAX         VrfIdentifier
     MAX-ACCESS     read-create
     STATUS         current 
     DESCRIPTION    "The VrfId used in this table is to associate VLANs
		     or Brouter ports to a VRF after the creation of VLANs
		     or Brouter ports.
		     VRFID 0 is reserved for the Administrative VRF."
        ::= { rcIpAddrEntry 12 }

rcIpAdEntName OBJECT-TYPE
     SYNTAX         DisplayString (SIZE (0..64))
     MAX-ACCESS     read-write
     STATUS         current
     DESCRIPTION    "The administratively assigned name for this address"
     ::= { rcIpAddrEntry 13 }


-- FlowContorl Group

rcIpFlowTable OBJECT-TYPE
        SYNTAX        SEQUENCE OF RcIpFlowEntry
        MAX-ACCESS    not-accessible
        STATUS        current
        DESCRIPTION   "IpFlow Table.  This table contain entries that
                      correspond to RSVP records in the switching
                      fabric Address Resolution table.

                      A connection that has a matching entry in this
                      table will be processed with a higher priority
                      than connections that do not have an entry."
        ::= { rcIp 3 }

rcIpFlowEntry OBJECT-TYPE
        SYNTAX        RcIpFlowEntry
        MAX-ACCESS    not-accessible
        STATUS        current
        DESCRIPTION   "Proprietary flow control variables."
        INDEX         { rcIpFlowSrcIpAddress, rcIpFlowSrcIpPort,
                        rcIpFlowDstIpAddress, rcIpFlowDstIpPort,
                        rcIpFlowProtocol }
        ::= { rcIpFlowTable 1 }

RcIpFlowEntry ::=
        SEQUENCE {
                rcIpFlowSrcIpAddress IpAddress,
                rcIpFlowSrcIpPort    Integer32,
                rcIpFlowDstIpAddress IpAddress,
                rcIpFlowDstIpPort    Integer32,
                rcIpFlowProtocol     INTEGER,
                rcIpFlowRowStatus    RowStatus
        }

rcIpFlowSrcIpAddress OBJECT-TYPE
        SYNTAX        IpAddress
        MAX-ACCESS    read-only
        STATUS        current
        DESCRIPTION   "The source IP address of an IP packet."
        ::= { rcIpFlowEntry 1 }

rcIpFlowSrcIpPort OBJECT-TYPE
        SYNTAX        Integer32 (0..65535)
        MAX-ACCESS    read-only
        STATUS        current
        DESCRIPTION   "The source port of an IP packet.  A zero value
                      in this field is used as a wildcard value."
        ::= { rcIpFlowEntry 2 }

rcIpFlowDstIpAddress OBJECT-TYPE
        SYNTAX        IpAddress
        MAX-ACCESS    read-only
        STATUS        current
        DESCRIPTION   "The destination IP address of an IP packet."
        ::= { rcIpFlowEntry 3 }

rcIpFlowDstIpPort OBJECT-TYPE
        SYNTAX        Integer32 (0..65535)
        MAX-ACCESS    read-only
        STATUS        current
        DESCRIPTION   "The destination port of an IP packet.  A zero
                      value in this field is used as a wildcard value."
        ::= { rcIpFlowEntry 4 }

rcIpFlowProtocol OBJECT-TYPE
        SYNTAX        INTEGER {
                         ip(4),         -- ip
                         tcp(6),        -- tcp
                         udp(17)        -- udp
                      }
        MAX-ACCESS    read-only
        STATUS        current
        DESCRIPTION   "The protocol type of an IP packet.  A zero value
                      in this field is used as a wildcard value."
        ::= { rcIpFlowEntry 5 }

rcIpFlowRowStatus OBJECT-TYPE
        SYNTAX        RowStatus
        MAX-ACCESS      read-create
        STATUS        current
        DESCRIPTION   "Status of entry."
        ::= { rcIpFlowEntry 6 }

rcIpRouting OBJECT IDENTIFIER ::= { rcIp 4 } -- defined in rcRouteXXX.mib

-- rcIpConfIgmpTable ::= { rcIp 5 } defined in rcIgmpXXX.mib
-- rcIgmpGroupTable ::= { rcIp 6 } defined in rcIgmpXXX.mib

-- rcIpRouteTable ::= { rcIp 7 } defined in rcRouteXXX.mib

-- Ip Config Dhcp Table

rcIpConfDhcpTable OBJECT-TYPE
        SYNTAX          SEQUENCE OF RcIpConfDhcpEntry
        MAX-ACCESS      not-accessible
        STATUS          current
        DESCRIPTION     "DHCP configuration table"
    ::= { rcIp 8 }

rcIpConfDhcpEntry OBJECT-TYPE
        SYNTAX          RcIpConfDhcpEntry
        MAX-ACCESS              not-accessible
        STATUS          current
        DESCRIPTION     "Used to configure DHCP on a particular port.  An
                        entry is created automatically when the variable
                        rcIpConfDhcpEnable is set to TRUE.

                        Once created this entry will only be deleted if the
                        rcIpConfDhcpRowStatus is set to 'destroy(6)'.  In
                        which case, the rcIpConfDhcpEnable is automatically
                        reset to the FALSE setting."
        INDEX           { rcIpConfDhcpIfIndex }
        ::= { rcIpConfDhcpTable 1 }

RcIpConfDhcpEntry ::=
        SEQUENCE {
                rcIpConfDhcpIfIndex            InterfaceIndexOrZero,
                rcIpConfDhcpMaxHop             Integer32,
                rcIpConfDhcpMinSec             Integer32,
                rcIpConfDhcpMode               INTEGER,
                rcIpConfDhcpRowStatus          RowStatus,
                rcIpConfDhcpNumRequests        Counter32,
                rcIpConfDhcpNumReplies         Counter32,
                rcIpConfDhcpAlwaysBroadcast    TruthValue,
                rcIpConfDhcpClearCounters      INTEGER,
                rcIpConfDhcpCounterClearTime   TimeStamp,
                rcIpConfDhcpCircuitId          TruthValue,
                rcIpConfDhcpRemoteId           TruthValue,
                rcIpConfDhcpTrusted            TruthValue,
		rcIpConfDhcpAgentAddr          IpAddress
        }

rcIpConfDhcpIfIndex OBJECT-TYPE
        SYNTAX          InterfaceIndexOrZero
        MAX-ACCESS      read-only
        STATUS          current
        DESCRIPTION     "Interface number.  The number can represent either
                        a physical or logical(VLAN) interface."
        ::= { rcIpConfDhcpEntry 1 }

rcIpConfDhcpMaxHop OBJECT-TYPE
        SYNTAX          Integer32 (1..16)
        MAX-ACCESS      read-create
        STATUS          current
        DESCRIPTION     "Used to indicate the maximum number of hops a
                        DHCP packet can take from the source device to
                        the destination device (i.e., DHCP client to
                        DHCP server)."
        DEFVAL          { 4 }
        ::= { rcIpConfDhcpEntry 2 }

rcIpConfDhcpMinSec OBJECT-TYPE
        SYNTAX          Integer32 (0..65535)
        MAX-ACCESS      read-create
        STATUS          current
        DESCRIPTION     "Used to indicate the minimum number of seconds
                        to wait between receiving a DHCP packet and
                        actually forwarding the DHCP packet to the
                        destination device.  A value of zero(0) indicates
                        forwarding should be done immediately without any
                        delay."
        DEFVAL          { 0 }
        ::= { rcIpConfDhcpEntry 3 }

rcIpConfDhcpMode OBJECT-TYPE
        SYNTAX          INTEGER {
                                none(0),
                                bootp(2),
                                dhcp(3),
                                both(4)
                        }
        MAX-ACCESS      read-create
        STATUS          current
        DESCRIPTION     "Used to indicate what type of DHCP packets this
                        interface should support.  A value of none(1) will
                        result in all incoming DHCP and BOOTP packets to
                        be dropped."
        DEFVAL          { both }
        ::= { rcIpConfDhcpEntry 4 }

rcIpConfDhcpRowStatus OBJECT-TYPE
        SYNTAX          RowStatus
        MAX-ACCESS      read-create
        STATUS          current
        DESCRIPTION     "An entry is created automatically when the variable
                        rcIpConfDhcpEnable is set to TRUE.

                        Once created this entry will only be deleted if the
                        rcIpConfDhcpRowStatus is set to 'destroy(6)'.  In
                        which case, the rcIpConfDhcpEnable is automatically
                        reset to the FALSE setting."
        ::= { rcIpConfDhcpEntry 5 }

rcIpConfDhcpNumRequests OBJECT-TYPE
        SYNTAX          Counter32
        MAX-ACCESS      read-only
        STATUS          current
        DESCRIPTION     "The total number of DHCP requests seen on this interface."
        ::= { rcIpConfDhcpEntry 6 }

rcIpConfDhcpNumReplies OBJECT-TYPE
        SYNTAX          Counter32
        MAX-ACCESS      read-only
        STATUS          current
        DESCRIPTION     "The total number of DHCP replies seen on this interface."
        ::= { rcIpConfDhcpEntry 7 }

rcIpConfDhcpAlwaysBroadcast OBJECT-TYPE
        SYNTAX          TruthValue
        MAX-ACCESS      read-create
        STATUS          current
        DESCRIPTION     "Used to indicate if DHCP Reply packets should be
                        broadcast to the DHCP client on this interface."
        DEFVAL          { false }
        ::= { rcIpConfDhcpEntry 8 }

rcIpConfDhcpClearCounters OBJECT-TYPE
        SYNTAX          INTEGER {
                            clear(1),
                            dummy(2)
                        }
        MAX-ACCESS      read-create
        STATUS          current
        DESCRIPTION     "This object is used to clear the DHCP counters
                        in an entry.  When set to clear(1), the values of
                        the counter objects in the entry will be reset to
                        0, and the value of rcIpConfDhcpCounterClearTime
                        will be set to the current value of sysUpTime.
                        When read, the value of this object is always
                        dummy(2)."
        DEFVAL          { dummy }
        ::= { rcIpConfDhcpEntry 9 }

rcIpConfDhcpCounterClearTime OBJECT-TYPE
        SYNTAX          TimeStamp
        MAX-ACCESS      read-only
        STATUS          current
        DESCRIPTION     "This object indicates the time at which the counter
                        values in this entry were last reset to 0."
        ::= { rcIpConfDhcpEntry 10 }

rcIpConfDhcpCircuitId OBJECT-TYPE
        SYNTAX          TruthValue
        MAX-ACCESS              read-write
        STATUS          current
        DESCRIPTION     "Used to indicate if DHCP packets should have
                        option82 circuitId info inserted before sent to
                        servers, for this interface."
        DEFVAL          { false }
        ::= { rcIpConfDhcpEntry 11 }

rcIpConfDhcpRemoteId OBJECT-TYPE
        SYNTAX          TruthValue         MAX-ACCESS              read-write
        STATUS          current
        DESCRIPTION     "Used to indicate if DHCP packets should have
                        option82 remoteId info inserted before sent to
                        servers, for this interface."
        DEFVAL          { false }
        ::= { rcIpConfDhcpEntry 12 }
 rcIpConfDhcpTrusted OBJECT-TYPE
        SYNTAX          TruthValue
        MAX-ACCESS              read-write
        STATUS          current
        DESCRIPTION     "Used to indicate if DHCP packets come through a
                         trusted dhcp circuit. This means that packets with
                         giaddr set to 0 having option82 in it, will be forwarded
                         if the circuit is trusted."
        DEFVAL          { false }
        ::= { rcIpConfDhcpEntry 13 }
    
rcIpConfDhcpAgentAddr OBJECT-TYPE
        SYNTAX          IpAddress
        MAX-ACCESS      read-only
        STATUS          current
        DESCRIPTION     "The IP address configured as relay on this interface; it is either the IP of the
                         physical interface or the IP of the VRRP address"
        ::= { rcIpConfDhcpEntry 14 }


-- Ip Dhcp Forward Table

rcIpDhcpForwardTable OBJECT-TYPE
        SYNTAX          SEQUENCE OF RcIpDhcpForwardEntry
        MAX-ACCESS              not-accessible
        STATUS          current
        DESCRIPTION     "DHCP forwarding table."
    ::= { rcIp 9 }

rcIpDhcpForwardEntry OBJECT-TYPE
        SYNTAX          RcIpDhcpForwardEntry
        MAX-ACCESS              not-accessible
        STATUS          current
        DESCRIPTION     "An entry used represents a DHCP forwarding directive."
        INDEX           { rcIpDhcpForwardAgentAddr, rcIpDhcpForwardServerAddr }
        ::= { rcIpDhcpForwardTable 1 }

RcIpDhcpForwardEntry ::=
        SEQUENCE {
                rcIpDhcpForwardAgentAddr   IpAddress,
                rcIpDhcpForwardServerAddr  IpAddress,
                rcIpDhcpForwardEnable      TruthValue,
                rcIpDhcpForwardMode        INTEGER,
                rcIpDhcpForwardRowStatus   RowStatus
        }

rcIpDhcpForwardAgentAddr OBJECT-TYPE
        SYNTAX          IpAddress
        MAX-ACCESS              read-only
        STATUS          current
        DESCRIPTION     "The IP address configured on an interface
                        (i.e., a locally configured IP address)."
        ::= { rcIpDhcpForwardEntry 1 }

rcIpDhcpForwardServerAddr OBJECT-TYPE
        SYNTAX          IpAddress
        MAX-ACCESS              read-only
        STATUS          current
        DESCRIPTION     "The IP address of the DHCP server.  If this
                        IP address corresponds to a locally configured
                        IP network, the DHCP packet is broadcasted out
                        the interface the IP address is assigned to.
                        This behavior is known as 'relay agent' mode.

                        If this IP address is a remote address, the DHCP
                        packet is sent via unicast to the remote device.
                        This behavior is known as 'preferred server' mode."
        ::= { rcIpDhcpForwardEntry 2 }

rcIpDhcpForwardEnable OBJECT-TYPE
        SYNTAX          TruthValue
        MAX-ACCESS      read-create
        STATUS          current
        DESCRIPTION     "Used to indicate whether is entry should be used."
        DEFVAL          { true }
        ::= { rcIpDhcpForwardEntry 3 }

rcIpDhcpForwardMode OBJECT-TYPE
        SYNTAX          INTEGER {
                                none(0),
                                bootp(2),
                                dhcp(3),
                                both(4)
                        }
        MAX-ACCESS      read-create
        STATUS          current
        DESCRIPTION     "Used to indicate whether this entry pertains to
                        BOOTP packets, DHCP packets, or both."
        DEFVAL          { both }
        ::= { rcIpDhcpForwardEntry 4 }

rcIpDhcpForwardRowStatus OBJECT-TYPE
        SYNTAX          RowStatus
        MAX-ACCESS      read-create
        STATUS          current
        DESCRIPTION     "Row status of this entry."
        ::= { rcIpDhcpForwardEntry 5 }


-- ===========================================================================
-- DHCP forwarding scalar objects
-- ===========================================================================

rcIpDhcpForwardingScalars OBJECT IDENTIFIER ::= { rcIp 28 }

rcIpDhcpForwardingEnabled OBJECT-TYPE
    SYNTAX      TruthValue
    MAX-ACCESS  read-write
    STATUS      current
    DESCRIPTION
        "Indicates whether DHCP forwarding is globally enabled."
    ::= { rcIpDhcpForwardingScalars 1 }

rcIpDhcpForwardingOption82Enabled OBJECT-TYPE
    SYNTAX      TruthValue
    MAX-ACCESS  read-write
    STATUS      current
    DESCRIPTION
        "Indicates whether the use of DHCP option 82 is enabled."
    ::= { rcIpDhcpForwardingScalars 2 }

rcIpDhcpForwardingMaxFrameLength OBJECT-TYPE
    SYNTAX      Integer32 (576..1536)
    MAX-ACCESS  read-write
    STATUS      current
    DESCRIPTION
        "Maximum DHCP frame length."
    ::= { rcIpDhcpForwardingScalars 3 }

rcIpDhcpForwardingOption82RemoteId OBJECT-TYPE
    SYNTAX       INTEGER {
                     macAddress(1),
                     ipAddress(2),
                     hostname(3),
                     customString(4)
                 }
    MAX-ACCESS   read-write
    STATUS       current
    DESCRIPTION
        "This object is used to control what value will be used for the
         DHCP option 82 remote-id suboption."
    ::= { rcIpDhcpForwardingScalars 4 }

rcIpDhcpForwardingOption82RemoteIdString OBJECT-TYPE
    SYNTAX       DisplayString (SIZE(1..64))
    MAX-ACCESS   read-write
    STATUS       current
    DESCRIPTION
        "This object is used to set the string wich will be used for the
         value of the DHCP option 82 remote-id when the value of
         rcIpDhcpForwardingOption82RemoteId is set to customString(4)."
    ::= { rcIpDhcpForwardingScalars 5 }

-- Ip DHCP Relay Agent Information Option Statistics Table


rcIpDhcpOp82StatsTable OBJECT-TYPE         SYNTAX          SEQUENCE OF RcIpDhcpOp82StatsEntry
        MAX-ACCESS      not-accessible
        STATUS          current
        DESCRIPTION     "DHCP statistics table for Relay Agent Information Option"
    ::= { rcIp 29 }

rcIpDhcpOp82StatsEntry OBJECT-TYPE
        SYNTAX          RcIpDhcpOp82StatsEntry
        MAX-ACCESS      not-accessible
        STATUS          current
        DESCRIPTION     "Used to see current statistics on interfaces that have
                         DHCP Option 82 (Relay Agent Information) enabled.
                         This table is read-only."
        INDEX           { rcIpDhcpOp82StatsIfIndex }
        ::= { rcIpDhcpOp82StatsTable 1 }

RcIpDhcpOp82StatsEntry ::=
        SEQUENCE {
                rcIpDhcpOp82StatsIfIndex            InterfaceIndexOrZero,
                rcIpDhcpOp82StatsFoundOp82          Counter32,
                rcIpDhcpOp82StatsDropped            Counter32,
                rcIpDhcpOp82StatsCircuitId          Integer32,
                rcIpDhcpOp82StatsAddedCircuitId     Counter32,
                rcIpDhcpOp82StatsRemovedCircuitId   Counter32,
                rcIpDhcpOp82StatsRemoteId           MacAddress,
                rcIpDhcpOp82StatsAddedRemoteId      Counter32,
                rcIpDhcpOp82StatsRemovedRemoteId    Counter32,
		rcIpDhcpOp82StatsAgentAddr          IpAddress
        }

rcIpDhcpOp82StatsIfIndex OBJECT-TYPE
        SYNTAX          InterfaceIndexOrZero (0..6142)
        MAX-ACCESS      not-accessible 
        STATUS          current
        DESCRIPTION     "Interface number.  The number can represent either
                        a physical or logical(VLAN) interface."
        ::= { rcIpDhcpOp82StatsEntry 1 }

rcIpDhcpOp82StatsFoundOp82 OBJECT-TYPE
        SYNTAX          Counter32
        MAX-ACCESS      read-only
        STATUS          current
        DESCRIPTION     "Represents the number of packets received on the interface
                         that already had Dhcp Option 82 inserted in them"
        ::= { rcIpDhcpOp82StatsEntry 2 }

rcIpDhcpOp82StatsDropped OBJECT-TYPE
        SYNTAX          Counter32
        MAX-ACCESS      read-only
        STATUS          current
        DESCRIPTION     "Represents the number of packets dropped because of reasons related
                         to Dhcp Option 82. These reasons could be that the packet was received
                         from an untrusted source or spoofing was detected."
        ::= { rcIpDhcpOp82StatsEntry 3 }

rcIpDhcpOp82StatsCircuitId OBJECT-TYPE
        SYNTAX          Integer32
        MAX-ACCESS      read-only
        STATUS          current
        DESCRIPTION     "Represents the value of CircuitId inserted in the packets.
                         This is the Port number of the Dhcp Relay."
        ::= { rcIpDhcpOp82StatsEntry 4 }

rcIpDhcpOp82StatsAddedCircuitId  OBJECT-TYPE
        SYNTAX          Counter32
        MAX-ACCESS      read-only
        STATUS          current
        DESCRIPTION     "Represents the number of packets which had CircuitId inserted on this interface"
        ::= { rcIpDhcpOp82StatsEntry 5 }

rcIpDhcpOp82StatsRemovedCircuitId  OBJECT-TYPE
        SYNTAX          Counter32
        MAX-ACCESS      read-only
        STATUS          current
        DESCRIPTION     "Represents the number of packets which had CircuitId removed on this interface"
        ::= { rcIpDhcpOp82StatsEntry 6 }

rcIpDhcpOp82StatsRemoteId OBJECT-TYPE
        SYNTAX          MacAddress
        MAX-ACCESS      read-only
        STATUS          current
        DESCRIPTION     "Represents the value of RemoteId inserted in the packets.
                         This is the Mac address of the Dhcp Relay."
        ::= { rcIpDhcpOp82StatsEntry 7 }

rcIpDhcpOp82StatsAddedRemoteId  OBJECT-TYPE
        SYNTAX          Counter32
        MAX-ACCESS      read-only
        STATUS          current
        DESCRIPTION     "Represents the number of packets which had RemoteId inserted on this interface"
        ::= { rcIpDhcpOp82StatsEntry 8 }

rcIpDhcpOp82StatsRemovedRemoteId  OBJECT-TYPE
        SYNTAX          Counter32
        MAX-ACCESS      read-only
        STATUS          current
        DESCRIPTION     "Represents the number of packets which had RemoteId removed on this interface"
        ::= { rcIpDhcpOp82StatsEntry 9 }

rcIpDhcpOp82StatsAgentAddr OBJECT-TYPE
        SYNTAX          IpAddress
        MAX-ACCESS      read-only
        STATUS          current
        DESCRIPTION     "The IP address configured as relay on this interface; it is either the IP of the
                         physical interface or the IP of the VRRP address"
        ::= { rcIpDhcpOp82StatsEntry 10 }

-- ===========================================================================
-- ===========================================================================

rcIpFilter OBJECT IDENTIFIER ::= { rcIp 10 } -- defined in rcFilterXXX.mib

rcIpPolicy OBJECT IDENTIFIER ::= { rcIp 11 } -- defined in rcPolicyXXX.mib

rcIpDvmrp OBJECT IDENTIFIER ::= { rcIp 12 } -- defined in rcDvmrpXXX.mib

rcIpUdp OBJECT IDENTIFIER ::= { rcIp 13 } -- defined in rcUdpXXX.mib

--IP ToS Rule
rcIpTosRule   OBJECT IDENTIFIER       ::= { rcIp 14 }    --excluded

rcIpTosRuleAndMask OBJECT-TYPE
        SYNTAX        Integer32 (0..255)
        MAX-ACCESS    read-write
        STATUS        deprecated
        DESCRIPTION   "And Mask. The Ip ToS byte in the Ip header
                       is logically ANDed with this value, and then logically
                       ORed with the one of the OrRules below."
        ::= { rcIpTosRule 1 }

rcIpTosRuleOrRule1 OBJECT-TYPE
        SYNTAX        Integer32 (0..255)
        MAX-ACCESS    read-write
        STATUS        deprecated
        DESCRIPTION   "Quid/Gid Or rule #1. The Ip ToS byte in the Ip header
                       is logically ORed with this value."
        ::= { rcIpTosRule 2 }

rcIpTosRuleOrRule2 OBJECT-TYPE
        SYNTAX        Integer32 (0..255)
        MAX-ACCESS    read-write
        STATUS        deprecated
        DESCRIPTION   "Quid/Gid Or rule #2. The Ip ToS byte in the Ip header
                       is logically ORed with this value."
        ::= { rcIpTosRule 3 }

rcIpTosRuleOrRule3 OBJECT-TYPE
        SYNTAX        Integer32 (0..255)
        MAX-ACCESS    read-write
        STATUS        deprecated
        DESCRIPTION   "Quid/Gid Or rule #3. The Ip ToS byte in the Ip header
                       is logically ORed with this value."
        ::= { rcIpTosRule 4 }

rcIpTosRuleTosPriorityEnable OBJECT-TYPE
        SYNTAX          TruthValue
        MAX-ACCESS      read-write
        STATUS          deprecated
        DESCRIPTION     "Enable Tos priority."
        ::= { rcIpTosRule 5 }

rcIpTosRuleTosThreshold OBJECT-TYPE
        SYNTAX        INTEGER {
                         level0(0),
                         level1(1),
                         level2(2),
                         level3(3),
                         level4(4),
                         level5(5),
                         level6(6),
                         level7(7)
                      }
        MAX-ACCESS    read-only
        STATUS        deprecated
        DESCRIPTION   "tos threshold"
        ::= { rcIpTosRule 6 }

--IP Static Route
rcIpStaticRoute OBJECT IDENTIFIER ::= { rcIp 15 } -- defined in rcRouteXXX.mib

rcIpPim OBJECT IDENTIFIER ::= { rcIp 16 } -- defined in rcPimXXX.mib

-- rcIpMulticastArpTable ::= { rcIp 17 } defined in rcArpXXX.mib

-- rcIpMulticastTable ::= { rcIp 18 } defined in rcMcastXXX.mib

-- IP COPS Global

rcIpCops OBJECT IDENTIFIER ::= { rcIp 19 }

rcCopsGlobalEnable OBJECT-TYPE
        SYNTAX        TruthValue
        MAX-ACCESS    read-write
        STATUS        deprecated
        DESCRIPTION   "Cops feature enable/disable"
        ::= { rcIpCops 1 }

-- defined in rcRipXXX.mib
rcIpRipInterface OBJECT IDENTIFIER ::= { rcIp 20 }

-- defined in rcMcastXXX.mib
-- rcIpMulticastTimedPruneTable OBJECT IDENTIFIER ::= { rcIp 21 }

-- ICMP Route discovery parameters

rcIpConfIcmpRdiscTable OBJECT-TYPE
        SYNTAX        SEQUENCE OF RcIpConfIcmpRdiscEntry
        MAX-ACCESS    not-accessible
        STATUS        current
        DESCRIPTION   "A table used to maintain ICMP Route discovery information
                      for a particular interface."
    ::= { rcIp 22 }

rcIpConfIcmpRdiscEntry OBJECT-TYPE
        SYNTAX        RcIpConfIcmpRdiscEntry
        MAX-ACCESS    not-accessible
        STATUS        current
        DESCRIPTION   "Entry containing ICMP Rdisc information.  An entry is
                      automatically created in this table when routing
                      is enabled for an interface -or- when an ip address
                      is configured on an interface."
        INDEX      { rcIpConfIcmpRdiscIfIndex }
        ::= { rcIpConfIcmpRdiscTable 1 }

RcIpConfIcmpRdiscEntry ::= SEQUENCE {
        rcIpConfIcmpRdiscIfIndex            Integer32,
        rcIpConfIcmpRdiscAdvAddress         IpAddress,
        rcIpConfIcmpRdiscAdvFlag            TruthValue,
        rcIpConfIcmpRdiscAdvLifetime        Integer32,
        rcIpConfIcmpRdiscMaxAdvInterval     Integer32,
        rcIpConfIcmpRdiscMinAdvInterval     Integer32,
        rcIpConfIcmpRdiscPreferenceLevel    Integer32
}

rcIpConfIcmpRdiscIfIndex OBJECT-TYPE
        SYNTAX          Integer32 (0..65535)
        MAX-ACCESS      read-only
        STATUS          current
        DESCRIPTION     "An unique value to identify a physical
                        interface or a logical interface (VLAN)."
        ::= { rcIpConfIcmpRdiscEntry 1 }

rcIpConfIcmpRdiscAdvAddress OBJECT-TYPE
         SYNTAX     IpAddress
         MAX-ACCESS read-write
         STATUS     current
         DESCRIPTION "Advertisement address to which the route discovery
                      advertisements transmitted on this interface."
         ::= { rcIpConfIcmpRdiscEntry 2 }

rcIpConfIcmpRdiscAdvFlag OBJECT-TYPE
         SYNTAX     TruthValue
         MAX-ACCESS read-write
         STATUS     current
         DESCRIPTION "Flag to indicate whether or not the address is to
                     be advertised on this interface."
         ::= { rcIpConfIcmpRdiscEntry 3 }

rcIpConfIcmpRdiscAdvLifetime OBJECT-TYPE
         SYNTAX     Integer32 (4..9000)
         MAX-ACCESS read-write
         STATUS     current
         DESCRIPTION "The value to be placed in the lifetime field of
                     Router Advertisements sent from the interface."
         ::= { rcIpConfIcmpRdiscEntry 4 }

rcIpConfIcmpRdiscMaxAdvInterval OBJECT-TYPE
         SYNTAX     Integer32 (4..1800)
         MAX-ACCESS read-write
         STATUS     current
         DESCRIPTION "The maximum time allowed between sending
                     Router Advertisements from this interface."
         ::= { rcIpConfIcmpRdiscEntry 5 }

rcIpConfIcmpRdiscMinAdvInterval OBJECT-TYPE
         SYNTAX     Integer32 (3..1800)
         MAX-ACCESS read-write
         STATUS     current
         DESCRIPTION "The minimum time allowed between sending
                      Router Advertisements from this interface."
         ::= { rcIpConfIcmpRdiscEntry 6 }


rcIpConfIcmpRdiscPreferenceLevel OBJECT-TYPE
         SYNTAX     Integer32 (-2147483648..2147483647)
         MAX-ACCESS read-write
         STATUS     current
         DESCRIPTION "Preferability of the router address as a default
                      Router "
         ::= { rcIpConfIcmpRdiscEntry 7 }

-- defined in rcMcastXXX.mib
rcIpMulticastSoftwareForwarding OBJECT IDENTIFIER ::= { rcIp 23 }
rcIpMrouteHw OBJECT IDENTIFIER ::= { rcIp 24 }

-- IP Resource Usage Global

rcIpResourceUsage OBJECT IDENTIFIER       ::= { rcIp 25 }

rcIpResourceUsageGlobal OBJECT IDENTIFIER ::= { rcIpResourceUsage 1 }

rcIpResourceUsageGlobalIngressRecInUse OBJECT-TYPE
        SYNTAX        Integer32 (0..32767)
        MAX-ACCESS    read-only
        STATUS        current
        DESCRIPTION   "Used to get the Ingress Record Usage in the switch.
                       (S-G usage)."
        ::= { rcIpResourceUsageGlobal 1 }

rcIpResourceUsageGlobalEgressRecInUse OBJECT-TYPE
        SYNTAX        Integer32 (0..32767)
        MAX-ACCESS    read-only
        STATUS        current
        DESCRIPTION   "Used to get the Egress Record Usage in the switch
                       (pepstream count)."
        ::= { rcIpResourceUsageGlobal 2 }

rcIpResourceUsageGlobalIngressThreshold OBJECT-TYPE
        SYNTAX        Integer32 (0..32767)
        MAX-ACCESS    read-write
        STATUS        current
        DESCRIPTION   "Used to get the threshold count for Ingress records."
        DEFVAL        { 0 }
        ::= { rcIpResourceUsageGlobal 3 }

rcIpResourceUsageGlobalEgressThreshold OBJECT-TYPE
        SYNTAX        Integer32 (0..32767)
        MAX-ACCESS    read-write
        STATUS        current
        DESCRIPTION   "Used to get threshold count for egress records."
        DEFVAL        { 0 }
        ::= { rcIpResourceUsageGlobal  4 }

rcIpResourceUsageGlobalSendTrapAndLog OBJECT-TYPE
        SYNTAX        EnableValue
        MAX-ACCESS    read-write
        STATUS        current
        DESCRIPTION   "A means of alerting the user. If this bool is set,
                       a message will be send to console and also a
                       duReport will be logged."
        DEFVAL        { disable }
        ::= { rcIpResourceUsageGlobal  5 }

rcIpResourceUsageGlobalSendTrapOnly OBJECT-TYPE
        SYNTAX        EnableValue
        MAX-ACCESS    read-write
        STATUS        current
        DESCRIPTION   "A means of alerting the user. If this bool is set,
                       a message will be send to console."
        DEFVAL        { disable }
        ::= { rcIpResourceUsageGlobal  6 }

rcIpResourceUsageGlobalLogMsgOnly OBJECT-TYPE
        SYNTAX        EnableValue
        MAX-ACCESS    read-write
        STATUS        current
        DESCRIPTION   "A means of alerting the user.If this bool is set,
                       a duReport will be logged."
        DEFVAL        { disable }
        ::= { rcIpResourceUsageGlobal  7 }

rcIpVpn OBJECT IDENTIFIER ::= { rcIp 27 } -- defined in rcIpVpn.mib

rcIpGenPolicy OBJECT IDENTIFIER ::= { rcIp 100 } -- defined in rcPolicyXXX.mib

rcIpBgp OBJECT IDENTIFIER ::= { rcIp 101 } -- defined in rcBgpXXX.mib

rcIpMpls OBJECT IDENTIFIER ::= { rcIp 102 } -- defined in rcMplsXXX.mib

rcIpInterVrfStaticRoute OBJECT IDENTIFIER ::= { rcIp 103} -- defined in rcIpRouting.mib

-- IP BFD

rcIpBfd OBJECT IDENTIFIER ::= { rcIp 104 }

rcIpBfdTrapEnabled OBJECT-TYPE
    SYNTAX        TruthValue
    MAX-ACCESS    read-write
    STATUS        current
    DESCRIPTION
        "Used to indicate whether BFD traps should be sent or not"
    DEFVAL { false }
    ::= { rcIpBfd 1 }

rcIpBfdHoldOffTimerInterval OBJECT-TYPE
    SYNTAX       Unsigned32 (0..65535)
    MAX-ACCESS   read-write
    STATUS       current
    DESCRIPTION
        "This object specifies the hold off timer interval, in
         second. 0 means that hold off timer is disabled."
    DEFVAL { 0 }
    ::= { rcIpBfd 2 }

rcIpStaticMRoute OBJECT IDENTIFIER ::= { rcIp 105 }

rcIpEcmp OBJECT IDENTIFIER ::= { rcIp 106 }
       

-- IP ARP Record Delete

rcIPClearArpRecordTable 	OBJECT-TYPE 
	SYNTAX		SEQUENCE OF RcIPClearArpRecordEntry
	MAX-ACCESS	not-accessible
	STATUS		current
	DESCRIPTION	"Table used to clear an IP ARP Record."
	::= { rcIp 107 }

rcIPClearArpRecordEntry OBJECT-TYPE
	SYNTAX		RcIPClearArpRecordEntry
	MAX-ACCESS	not-accessible
	STATUS		current
	DESCRIPTION	"IP Clear ARP Record Table Entry"
	INDEX	{ rcIPClearArpRecordIpAddr,
		  rcIPClearArpRecordVlanId }
	::= { rcIPClearArpRecordTable 1 }
 
RcIPClearArpRecordEntry ::= 
	SEQUENCE 
	{
		rcIPClearArpRecordIpAddr	IpAddress,
		rcIPClearArpRecordVlanId	INTEGER,
		rcIPClearArpRecordLCForceDelete	TruthValue
	}

rcIPClearArpRecordIpAddr	OBJECT-TYPE
	SYNTAX		IpAddress
	MAX-ACCESS	not-accessible
	STATUS		current
	DESCRIPTION	"IP Address that needs to be cleared."
	::= { rcIPClearArpRecordEntry 1 }

rcIPClearArpRecordVlanId		OBJECT-TYPE
	SYNTAX		INTEGER (1..4094)
	MAX-ACCESS	not-accessible
	STATUS		current
	DESCRIPTION	"Vlan Id where the ARP record has to be cleared."
	::= { rcIPClearArpRecordEntry 2 }

rcIPClearArpRecordLCForceDelete	OBJECT-TYPE
	SYNTAX		TruthValue
	MAX-ACCESS	read-write
	STATUS		current
	DESCRIPTION	"By default, when LCForceDelete (Line Card Force 
			Delete) is set to false, if the ARP record is not 
			found on the CP, then no message will be sent to 
			the line-card. When LCForceDelete is set to true, 
			a message will be sent to the line-card even when 
			the ARP record is not found on the CP."
	DEFVAL		{ false }
	::= { rcIPClearArpRecordEntry 3 }


-- IP MC Record Delete

rcIPClearIPMCRecordTable 	OBJECT-TYPE 
	SYNTAX		SEQUENCE OF RcIPClearIPMCRecordEntry
	MAX-ACCESS	not-accessible
	STATUS		current
	DESCRIPTION	"Table used to clear an IP MC Record."
	::= { rcIp 108 }

rcIPClearIPMCRecordEntry OBJECT-TYPE
	SYNTAX		RcIPClearIPMCRecordEntry
	MAX-ACCESS	not-accessible
	STATUS		current
	DESCRIPTION	"IP Clear IP MC Record Table Entry"
	INDEX		{ rcIPClearIPMCRecordGroup,
			  rcIPClearIPMCRecordVlanId }
	::= { rcIPClearIPMCRecordTable 1 }
 
RcIPClearIPMCRecordEntry ::= 
	SEQUENCE 
	{
		rcIPClearIPMCRecordGroup		IpAddress,
		rcIPClearIPMCRecordVlanId		INTEGER,
		rcIPClearIPMCRecordSource		IpAddress,
		rcIPClearIPMCRecordLCForceDelete	TruthValue
	}

rcIPClearIPMCRecordGroup	OBJECT-TYPE
	SYNTAX		IpAddress
	MAX-ACCESS	not-accessible
	STATUS		current
	DESCRIPTION	"The IP Multicast Group Address."
	::= { rcIPClearIPMCRecordEntry 1 }

rcIPClearIPMCRecordVlanId	OBJECT-TYPE
	SYNTAX		INTEGER (1..4094)
	MAX-ACCESS	not-accessible
	STATUS		current
	DESCRIPTION	"Vlan Id where the IP MC record 
			has to be cleared."
	::= { rcIPClearIPMCRecordEntry 2 }

rcIPClearIPMCRecordSource	OBJECT-TYPE
	SYNTAX		IpAddress
	MAX-ACCESS	read-write
	STATUS		current
	DESCRIPTION	"The Source IP Address."
	::= { rcIPClearIPMCRecordEntry 3 }

rcIPClearIPMCRecordLCForceDelete	OBJECT-TYPE
	SYNTAX		TruthValue
	MAX-ACCESS	read-write
	STATUS		current
	DESCRIPTION	"By default, when LCForceDelete (Line Card 
			Force Delete) is set to false, if the IP 
			MC record is not found on the CP, then no 
			message will be sent to the line-card. When 
			LCForceDelete is set to true, a message 
			will be sent to the line-card even when the 
			IP MC record is not found on the CP."
	DEFVAL		{ false }
	::= { rcIPClearIPMCRecordEntry 4 }

-- IP Mcast Square Smlt     

rcIpMulticastSquareSmlt  OBJECT IDENTIFIER ::= { rcIp 109 }

rcIpMulticastSquareSmltEnable OBJECT-TYPE
        SYNTAX        TruthValue
        MAX-ACCESS    read-write
        STATUS        current
        DESCRIPTION   "Enable/Disable multicast Square Smlt."
        DEFVAL { false }
        ::= { rcIpMulticastSquareSmlt 1 }

-- RcIpNetToMedia Table

rcIpNetToMediaTable OBJECT-TYPE 
      SYNTAX        SEQUENCE OF RcIpNetToMediaEntry 
        MAX-ACCESS    not-accessible 
        STATUS        current 
        DESCRIPTION 
                      "The IP Address Translation table used for mapping 
                      from IP addresses to physical addresses." 
        ::= { rcIp 30 } 
 
rcIpNetToMediaEntry OBJECT-TYPE 
        SYNTAX        RcIpNetToMediaEntry  
        MAX-ACCESS    not-accessible 
        STATUS        current   
        DESCRIPTION 
                      "Each entry contains one IpAddress to `physical' 
                      address equivalence." 
        INDEX         { rcIpNetToMediaNetAddress, 
                        rcIpNetToMediaIfIndex } 
      ::= { rcIpNetToMediaTable 1} 
 
RcIpNetToMediaEntry ::= 
        SEQUENCE { 
                  rcIpNetToMediaNetAddress       IpAddress,  
                  rcIpNetToMediaIfIndex          InterfaceIndex, 
                  rcIpNetToMediaPhysAddress      PhysAddress, 
                  rcIpNetToMediaType             INTEGER, 
                  rcIpNetToMediaTimeToLive       Integer32, 
                  rcIpNetToMediaRowStatus        RowStatus, 
                  rcIpNetToMediaDestIfIndex      InterfaceIndex, 
                  rcIpNetToMediaDestVlanId       Integer32,
		  rcIpNetToMediaBMac             MacAddress,
		  rcIpNetToMediaDestCvid         Integer32 
                  } 
 
rcIpNetToMediaNetAddress OBJECT-TYPE 
        SYNTAX        IpAddress 
        MAX-ACCESS    not-accessible 
        STATUS        current  
        DESCRIPTION   "The IpAddress corresponding to the media- 
                      dependent `physical' address." 
        ::= { rcIpNetToMediaEntry 1 } 
 
rcIpNetToMediaIfIndex OBJECT-TYPE 
        SYNTAX        InterfaceIndex 
        MAX-ACCESS    not-accessible 
        STATUS        current 
        DESCRIPTION   "The interface on which this entry's equivalence 
                      is effective.  The interface identified by a 
                      particular value of this index is the same 
                      interface as identified by the same value of 
                      ifIndex." 
        ::= { rcIpNetToMediaEntry 2 } 
 
rcIpNetToMediaPhysAddress OBJECT-TYPE 
        SYNTAX        PhysAddress 
        MAX-ACCESS    read-create 
        STATUS        current 
        DESCRIPTION   "The media-dependent `physical' address." 
        ::= { rcIpNetToMediaEntry 3 } 
 
rcIpNetToMediaType OBJECT-TYPE 
         SYNTAX       INTEGER { 
                          other(1),        -- none of the following 
                          dynamic(2), 
                          static(3), 
                          local(4) 
                      } 
         MAX-ACCESS   read-only 
         STATUS       current 
         DESCRIPTION  "The is ARP entry type field." 
        ::= { rcIpNetToMediaEntry 4 } 
 
rcIpNetToMediaTimeToLive OBJECT-TYPE 
        SYNTAX        Integer32 
        UNITS         "seconds" 
        MAX-ACCESS    read-only 
        STATUS        current 
        DESCRIPTION   "This is TTL (time to live) field." 
        ::= { rcIpNetToMediaEntry 5 } 
 
rcIpNetToMediaRowStatus OBJECT-TYPE 
        SYNTAX        RowStatus 
        MAX-ACCESS    read-create 
        STATUS        current 
        DESCRIPTION   "Table row status." 
        ::= { rcIpNetToMediaEntry 6 } 
 
rcIpNetToMediaDestIfIndex OBJECT-TYPE 
        SYNTAX          InterfaceIndex 
        MAX-ACCESS      read-create 
        STATUS          current 
        DESCRIPTION   "Destination IfIndex." 
        ::= { rcIpNetToMediaEntry 7 } 
 
rcIpNetToMediaDestVlanId OBJECT-TYPE 
        SYNTAX        Integer32 (0..4084) 
        MAX-ACCESS    read-create 
        STATUS        current 
        DESCRIPTION   "Destination VlanId." 
        ::= { rcIpNetToMediaEntry 8 }
    
rcIpNetToMediaBMac OBJECT-TYPE
        SYNTAX 	      MacAddress
	MAX-ACCESS    read-only
	STATUS 	      current
	DESCRIPTION  "If the rcIpNetToMediaEntry is learned from a SPBM
	    	      network, instead of using port to track where the
		      rcIpNetToMediaNetAddress come from, the backbone
		      MAC address is used to track that."
	::= { rcIpNetToMediaEntry 9 }

rcIpNetToMediaDestCvid OBJECT-TYPE
        SYNTAX        Integer32 (1..4096)
        MAX-ACCESS    read-only
        STATUS        current
        DESCRIPTION   "Used to identify customer vid of the switched uni port 
                      of this entry is associated with. 4095 is not used. 4096 
                      is reserved for untagged case."
        ::= { rcIpNetToMediaEntry 10}
    
rcIpMvpnTable   OBJECT-TYPE
    SYNTAX        SEQUENCE OF RcIpMvpnTableEntry
    MAX-ACCESS    not-accessible
    STATUS        current
    DESCRIPTION   "Table required to configure mvpn"
    ::= { rcIp 31 }

rcIpMvpnTableEntry  OBJECT-TYPE
    SYNTAX         RcIpMvpnTableEntry
    MAX-ACCESS     not-accessible
    STATUS         current
    DESCRIPTION    "Entries in this table are per rcVrfId."
    INDEX          { rcIpMvpnVrfId }
    ::= { rcIpMvpnTable 1 }

RcIpMvpnTableEntry ::=
    SEQUENCE {
              rcIpMvpnVrfId  VrfIdentifier,
              rcIpMvpnEnable EnableValue,
              rcIpMvpnFwdCacheTimeout Integer32
             }

rcIpMvpnVrfId OBJECT-TYPE
    SYNTAX        VrfIdentifier
    MAX-ACCESS    not-accessible
    STATUS        current
    DESCRIPTION   "The VrfId serves as the Index for rcVrfIpMvpnTableEntry"
    ::= { rcIpMvpnTableEntry 1 }

rcIpMvpnEnable  OBJECT-TYPE
    SYNTAX        EnableValue
    MAX-ACCESS    read-write
    STATUS        current
    DESCRIPTION   "The status of mvpn on a vrf."
    DEFVAL        { disable }
    ::= { rcIpMvpnTableEntry 2 }

  rcIpMvpnFwdCacheTimeout OBJECT-TYPE
     SYNTAX        Integer32 (10..86400)
     MAX-ACCESS    read-write
     STATUS        current
     DESCRIPTION   "Mvpn Fwd Cache Timeout in seconds"
     DEFVAL         { 210 }
     ::= {  rcIpMvpnTableEntry 3 }


-- IP Isis
rcIpIsis OBJECT IDENTIFIER ::= { rcIp 110 }

rcIpIsisGenInFilter  OBJECT IDENTIFIER ::= {rcIpIsis 1}

rcIpIsisInFilterNickNameTableSize OBJECT-TYPE
        SYNTAX        Integer32
        MAX-ACCESS    read-only
        STATUS        current
        DESCRIPTION   "Ip Isis In Filter Nick Name table size"
        ::= { rcIpIsisGenInFilter 1 }

rcIpIsisInFilterIsidTableSize OBJECT-TYPE
        SYNTAX        Integer32
        MAX-ACCESS    read-only
        STATUS        current
        DESCRIPTION   "Ip Isis In Filter Isid table size"
        ::= { rcIpIsisGenInFilter 2 }

rcIpIsisInFilterNickNameIsidTableSize OBJECT-TYPE
        SYNTAX        Integer32
        MAX-ACCESS    read-only
        STATUS        current
        DESCRIPTION   "Ip Isis In Filter Nick Name Isid table size"
        ::= { rcIpIsisGenInFilter 3 }

rcIpIsisInFilterIsidListTableSize OBJECT-TYPE
        SYNTAX        Integer32
        MAX-ACCESS    read-only
        STATUS        current
        DESCRIPTION   "Ip Isis In Filter Isid List table size"
        ::= { rcIpIsisGenInFilter 4 }

rcIpIsisInFilterNickNameIsidListTableSize OBJECT-TYPE
        SYNTAX        Integer32
        MAX-ACCESS    read-only
        STATUS        current
        DESCRIPTION   "Ip Isis In Filter Nick Name Isid List table size"
        ::= { rcIpIsisGenInFilter 5 }

rcIpIsisInFilterApply OBJECT-TYPE
        SYNTAX        INTEGER  {
                   		noAction(1),
                    		apply(2)
                                }
        MAX-ACCESS    read-write
        STATUS        current
        DESCRIPTION   "Used to Apply the Ip Isis Accept filters.
                       When the value is set to apply, all the elements in
                       the in the various Ip Isis In Filter Tables will be 
                       applied as well as rcIpIsisInFilterDefault. This may 
                       be a disruptive operation to traffic.
                       The get will always return noAction."
	DEFVAL        { noAction } 
        ::= { rcIpIsisGenInFilter 6 }

rcIpIsisInFilter  OBJECT IDENTIFIER ::= {rcIpIsis 2}

-- IP Isis In Filter Nick Name Table
rcIpIsisInFilterNickNameTable OBJECT-TYPE
        SYNTAX          SEQUENCE OF RcIpIsisInFilterNickNameEntry
        MAX-ACCESS      not-accessible
        STATUS          current
        DESCRIPTION     "IP Isis In Filter Nick Name table"
        ::= { rcIpIsisInFilter 1}

rcIpIsisInFilterNickNameEntry OBJECT-TYPE
        SYNTAX          RcIpIsisInFilterNickNameEntry
        MAX-ACCESS      not-accessible
        STATUS          current
        DESCRIPTION     "An entry of Ip Isis In Filter Nick Name Table."
        INDEX           { rcIpIsisInFilterNickNameAdvertisingRtr }
        ::= { rcIpIsisInFilterNickNameTable 1 }

RcIpIsisInFilterNickNameEntry ::=
        SEQUENCE {
               rcIpIsisInFilterNickNameAdvertisingRtr  IpIsisPlsbNodeNickName,
               rcIpIsisInFilterNickNameEnable          EnableValue,
               rcIpIsisInFilterNickNamePolicyName      DisplayString,
               rcIpIsisInFilterNickNameRowStatus       RowStatus,
               rcIpIsisInFilterNickNameBackBonePolicyName DisplayString
        }

rcIpIsisInFilterNickNameAdvertisingRtr OBJECT-TYPE
        SYNTAX        IpIsisPlsbNodeNickName
        MAX-ACCESS    not-accessible
        STATUS        current
        DESCRIPTION   "NickName used to filter by"
        ::= { rcIpIsisInFilterNickNameEntry 1 }

rcIpIsisInFilterNickNameEnable OBJECT-TYPE
        SYNTAX        EnableValue
        MAX-ACCESS    read-create
        STATUS        current
        DESCRIPTION   "Enables or disables the NickName entry.  The value
                       must be enabled to filter."
        DEFVAL        { disable }
        ::= { rcIpIsisInFilterNickNameEntry 2 }

rcIpIsisInFilterNickNamePolicyName OBJECT-TYPE
        SYNTAX        DisplayString (SIZE(0..64))
        MAX-ACCESS    read-create
        STATUS        current
        DESCRIPTION   "Route Map name used"
        ::= { rcIpIsisInFilterNickNameEntry 3 }

rcIpIsisInFilterNickNameRowStatus OBJECT-TYPE
        SYNTAX        RowStatus
        MAX-ACCESS    read-create
        STATUS        current
        DESCRIPTION   "Ip Isis In Filter Nick Name Table Row Status"
        ::= { rcIpIsisInFilterNickNameEntry 4 }

rcIpIsisInFilterNickNameBackBonePolicyName OBJECT-TYPE
        SYNTAX        DisplayString (SIZE(0..64))
        MAX-ACCESS    read-create
        STATUS        current
        DESCRIPTION   "Backbone Route Map name"
        ::= { rcIpIsisInFilterNickNameEntry 5 }

-- IP Isis In Filter ISID Table
rcIpIsisInFilterIsidTable OBJECT-TYPE
        SYNTAX          SEQUENCE OF RcIpIsisInFilterIsidEntry
        MAX-ACCESS      not-accessible
        STATUS          current
        DESCRIPTION     "IP Isis In Filter Isid Isid table"
        ::= {  rcIpIsisInFilter 2 }

rcIpIsisInFilterIsidEntry OBJECT-TYPE
        SYNTAX          RcIpIsisInFilterIsidEntry
        MAX-ACCESS      not-accessible
        STATUS          current
        DESCRIPTION     "An entry of Ip Isis In Filter Table."
        INDEX           { rcIpIsisInFilterIsid }
        ::= { rcIpIsisInFilterIsidTable 1 }

RcIpIsisInFilterIsidEntry ::=
        SEQUENCE {
                rcIpIsisInFilterIsid                Integer32,
                rcIpIsisInFilterIsidEnable          EnableValue,
                rcIpIsisInFilterIsidPolicyName      DisplayString,
                rcIpIsisInFilterIsidRowStatus       RowStatus,
                rcIpIsisInFilterIsidBackbonePolicyName DisplayString
        }

rcIpIsisInFilterIsid OBJECT-TYPE
        SYNTAX        Integer32 (0..16777215)
        MAX-ACCESS    not-accessible
        STATUS        current
        DESCRIPTION   "Isid value used to filter by.
                      The value 0 is used for Global Router."
        ::= { rcIpIsisInFilterIsidEntry 1 }

rcIpIsisInFilterIsidEnable OBJECT-TYPE
        SYNTAX        EnableValue
        MAX-ACCESS    read-create
        STATUS        current
        DESCRIPTION   "Enables or disables the Isid entry.  The value 
                       must be enabled to filter."
        DEFVAL        { disable }
        ::= { rcIpIsisInFilterIsidEntry 2 }

rcIpIsisInFilterIsidPolicyName OBJECT-TYPE
        SYNTAX        DisplayString (SIZE(0..64))
        MAX-ACCESS    read-create
        STATUS        current
        DESCRIPTION   "Route Map name used"
        ::= { rcIpIsisInFilterIsidEntry 3 }

rcIpIsisInFilterIsidRowStatus OBJECT-TYPE
        SYNTAX        RowStatus
        MAX-ACCESS    read-create
        STATUS        current
        DESCRIPTION   "Ip Isis In Filter Isid Table Row Status"
        ::= { rcIpIsisInFilterIsidEntry 4 }

rcIpIsisInFilterIsidBackbonePolicyName OBJECT-TYPE
        SYNTAX        DisplayString (SIZE(0..64))
        MAX-ACCESS    read-create
        STATUS        current
        DESCRIPTION   "Backbone Route Map name"
        ::= { rcIpIsisInFilterIsidEntry 5 }

-- IP Isis In Filter NickName ISID Table 
rcIpIsisInFilterNickNameIsidTable OBJECT-TYPE
        SYNTAX          SEQUENCE OF RcIpIsisInFilterNickNameIsidEntry
        MAX-ACCESS      not-accessible
        STATUS          current
        DESCRIPTION     "IP Isis In Filter Nick Name Isid table"
        ::= { rcIpIsisInFilter 3 }

rcIpIsisInFilterNickNameIsidEntry OBJECT-TYPE
        SYNTAX          RcIpIsisInFilterNickNameIsidEntry
        MAX-ACCESS      not-accessible
        STATUS          current
        DESCRIPTION     "An entry of Ip Isis In Filter Nick Name Isid Table."
        INDEX           { rcIpIsisInFilterNickNameIsidAdvertisingRtr,
                          rcIpIsisInFilterNickNameIsid }
        ::= { rcIpIsisInFilterNickNameIsidTable 1 }

RcIpIsisInFilterNickNameIsidEntry ::=
        SEQUENCE {
             rcIpIsisInFilterNickNameIsidAdvertisingRtr  IpIsisPlsbNodeNickName,
             rcIpIsisInFilterNickNameIsid                Integer32,
             rcIpIsisInFilterNickNameIsidEnable          EnableValue,
             rcIpIsisInFilterNickNameIsidPolicyName      DisplayString,
             rcIpIsisInFilterNickNameIsidRowStatus       RowStatus,
             rcIpIsisInFilterNickNameIsidBackBonePolicyName  DisplayString
        }

rcIpIsisInFilterNickNameIsidAdvertisingRtr OBJECT-TYPE
        SYNTAX        IpIsisPlsbNodeNickName
        MAX-ACCESS    not-accessible
        STATUS        current
        DESCRIPTION   "NickName used to filter by"
        ::= { rcIpIsisInFilterNickNameIsidEntry 1 }

rcIpIsisInFilterNickNameIsid OBJECT-TYPE
        SYNTAX        Integer32 (0..16777215)
        MAX-ACCESS    not-accessible
        STATUS        current
        DESCRIPTION   "Isid used to filter by.
                       The value 0 is used for Global Router."
        ::= { rcIpIsisInFilterNickNameIsidEntry 2 }

rcIpIsisInFilterNickNameIsidEnable OBJECT-TYPE
        SYNTAX        EnableValue
        MAX-ACCESS    read-create
        STATUS        current
        DESCRIPTION   ""
        DEFVAL        { disable }
        ::= { rcIpIsisInFilterNickNameIsidEntry 3 }

rcIpIsisInFilterNickNameIsidPolicyName OBJECT-TYPE
        SYNTAX        DisplayString (SIZE(0..64))
        MAX-ACCESS    read-create
        STATUS        current
        DESCRIPTION   "Route Map name used"
        ::= { rcIpIsisInFilterNickNameIsidEntry 4 }

rcIpIsisInFilterNickNameIsidRowStatus OBJECT-TYPE
        SYNTAX        RowStatus
        MAX-ACCESS    read-create
        STATUS        current
        DESCRIPTION   "Ip Isis In Filter Nick Name Isid Table Row Status"
        ::= { rcIpIsisInFilterNickNameIsidEntry 5 }

rcIpIsisInFilterNickNameIsidBackBonePolicyName OBJECT-TYPE
        SYNTAX        DisplayString (SIZE(0..64))
        MAX-ACCESS    read-create
        STATUS        current
        DESCRIPTION   "Backbone Route Map name"
        ::= { rcIpIsisInFilterNickNameIsidEntry 6 }
    
-- IP Isis ISID List Table

rcIpIsisIsidListTable  OBJECT-TYPE
        SYNTAX          SEQUENCE OF RcIpIsisIsidListEntry
        MAX-ACCESS      not-accessible
        STATUS          current
        DESCRIPTION     "IP Isis Isid List table"
        ::= { rcIpIsisInFilter 4 }

rcIpIsisIsidListEntry OBJECT-TYPE
        SYNTAX          RcIpIsisIsidListEntry
        MAX-ACCESS      not-accessible
        STATUS          current
        DESCRIPTION     "An entry of Ip Isis Isid List Table."
        INDEX           { rcIpIsisIsidListName,
                          rcIpIsisIsidListIsid }
        ::= { rcIpIsisIsidListTable 1 }

RcIpIsisIsidListEntry ::=
        SEQUENCE {
               rcIpIsisIsidListName                 DisplayString,
               rcIpIsisIsidListIsid                 Integer32,
               rcIpIsisIsidListRowStatus            RowStatus
        }

rcIpIsisIsidListName  OBJECT-TYPE
        SYNTAX        DisplayString(SIZE (0..32))
        MAX-ACCESS    not-accessible
        STATUS        current
        DESCRIPTION   "Name of Isid List"
        ::= { rcIpIsisIsidListEntry 1 }

rcIpIsisIsidListIsid OBJECT-TYPE
        SYNTAX        Integer32 (0..16777215)
        MAX-ACCESS    not-accessible
        STATUS        current
        DESCRIPTION   "Is a member of the specified isid list.
                       The value is the i-sid integer value or
                       the value 0 is used for Global Router."
        ::= { rcIpIsisIsidListEntry 2 }

rcIpIsisIsidListRowStatus OBJECT-TYPE
        SYNTAX        RowStatus
        MAX-ACCESS    read-create
        STATUS        current
        DESCRIPTION   "Row Status"
        ::= { rcIpIsisIsidListEntry 3 }

-- IP Isis In Filter ISID List Table
rcIpIsisInFilterIsidListTable OBJECT-TYPE
        SYNTAX          SEQUENCE OF RcIpIsisInFilterIsidListEntry
        MAX-ACCESS      not-accessible
        STATUS          current
        DESCRIPTION     "IP Isis In Filter Isid List table"
        ::= { rcIpIsisInFilter 5 }

rcIpIsisInFilterIsidListEntry OBJECT-TYPE
        SYNTAX          RcIpIsisInFilterIsidListEntry
        MAX-ACCESS      not-accessible
        STATUS          current
        DESCRIPTION     "An entry of Ip Isis In Filter Table."
        INDEX           { rcIpIsisInFilterIsidListName }
        ::= { rcIpIsisInFilterIsidListTable 1 }

RcIpIsisInFilterIsidListEntry ::=
        SEQUENCE {
               rcIpIsisInFilterIsidListName            DisplayString,
               rcIpIsisInFilterIsidListEnable          EnableValue,
               rcIpIsisInFilterIsidListPolicyName      DisplayString,
               rcIpIsisInFilterIsidListRowStatus       RowStatus,
               rcIpIsisInFilterIsidListBackBonePolicyName  DisplayString
        }

rcIpIsisInFilterIsidListName OBJECT-TYPE
        SYNTAX        DisplayString(SIZE (0..32))
        MAX-ACCESS    not-accessible
        STATUS        current
        DESCRIPTION   "Name of Isid List"
        ::= { rcIpIsisInFilterIsidListEntry 1 }

rcIpIsisInFilterIsidListEnable OBJECT-TYPE
        SYNTAX        EnableValue
        MAX-ACCESS    read-create
        STATUS        current
        DESCRIPTION   "Enables or disables the Isid List entry.  The value
                       must be enabled to filter."
        DEFVAL        { disable }
        ::= { rcIpIsisInFilterIsidListEntry 2 }

rcIpIsisInFilterIsidListPolicyName OBJECT-TYPE
        SYNTAX        DisplayString (SIZE(0..64))
        MAX-ACCESS    read-create
        STATUS        current
        DESCRIPTION   "Route Map name"
        ::= { rcIpIsisInFilterIsidListEntry 3 }

rcIpIsisInFilterIsidListRowStatus OBJECT-TYPE
        SYNTAX        RowStatus
        MAX-ACCESS    read-create
        STATUS        current
        DESCRIPTION   "Ip Isis In Filter Isid List Table Row Status"
        ::= { rcIpIsisInFilterIsidListEntry 4 }

rcIpIsisInFilterIsidListBackBonePolicyName OBJECT-TYPE
        SYNTAX        DisplayString (SIZE(0..64))
        MAX-ACCESS    read-create
        STATUS        current
        DESCRIPTION   "Backbone Route Map name"
        ::= { rcIpIsisInFilterIsidListEntry 5 }

-- IP Isis In Filter Nick Name ISID List Table 
rcIpIsisInFilterNickNameIsidListTable OBJECT-TYPE
        SYNTAX          SEQUENCE OF RcIpIsisInFilterNickNameIsidListEntry
        MAX-ACCESS      not-accessible
        STATUS          current
        DESCRIPTION     "IP Isis In Filter Nick Name Isid List table"
        ::= { rcIpIsisInFilter 6}

rcIpIsisInFilterNickNameIsidListEntry OBJECT-TYPE
        SYNTAX          RcIpIsisInFilterNickNameIsidListEntry
        MAX-ACCESS      not-accessible
        STATUS          current
        DESCRIPTION     "An entry of Ip Isis In Filter Nick Name Isid ListTable"
        INDEX           { rcIpIsisInFilterNickNameIsidListAdvertisingRtr,
                          rcIpIsisInFilterNickNameIsidListName }  
        ::= { rcIpIsisInFilterNickNameIsidListTable 1 }

RcIpIsisInFilterNickNameIsidListEntry ::=
        SEQUENCE {
          rcIpIsisInFilterNickNameIsidListAdvertisingRtr IpIsisPlsbNodeNickName,
          rcIpIsisInFilterNickNameIsidListName            DisplayString,
          rcIpIsisInFilterNickNameIsidListEnable          EnableValue,
          rcIpIsisInFilterNickNameIsidListPolicyName      DisplayString,
          rcIpIsisInFilterNickNameIsidListRowStatus       RowStatus,
          rcIpIsisInFilterNickNameIsidListBackBonePolicyName  DisplayString
        }

rcIpIsisInFilterNickNameIsidListAdvertisingRtr OBJECT-TYPE
        SYNTAX        IpIsisPlsbNodeNickName
        MAX-ACCESS    not-accessible
        STATUS        current
        DESCRIPTION   "NickName used to filter by"
        ::= { rcIpIsisInFilterNickNameIsidListEntry 1 }

rcIpIsisInFilterNickNameIsidListName OBJECT-TYPE
        SYNTAX        DisplayString(SIZE (0..32))
        MAX-ACCESS    not-accessible
        STATUS        current
        DESCRIPTION   "Name of Isid List used to filter"
        ::= { rcIpIsisInFilterNickNameIsidListEntry 2 }

rcIpIsisInFilterNickNameIsidListEnable OBJECT-TYPE
        SYNTAX        EnableValue
        MAX-ACCESS    read-create
        STATUS        current
        DESCRIPTION   "Enables or disables the NickName IsidList entry.
                       The value must be enabled to filter."
        DEFVAL        { disable }
        ::= { rcIpIsisInFilterNickNameIsidListEntry 3 }

rcIpIsisInFilterNickNameIsidListPolicyName OBJECT-TYPE
        SYNTAX        DisplayString (SIZE(0..64))
        MAX-ACCESS    read-create
        STATUS        current
        DESCRIPTION   "Route Map name"
        ::= { rcIpIsisInFilterNickNameIsidListEntry 4 }

rcIpIsisInFilterNickNameIsidListRowStatus OBJECT-TYPE
        SYNTAX        RowStatus
        MAX-ACCESS    read-create
        STATUS        current
        DESCRIPTION   "Ip Isis In Filter Nick Name Isid List Table Row Status"
        ::= { rcIpIsisInFilterNickNameIsidListEntry 5 }

rcIpIsisInFilterNickNameIsidListBackBonePolicyName OBJECT-TYPE
        SYNTAX        DisplayString (SIZE(0..64))
        MAX-ACCESS    read-create
        STATUS        current
        DESCRIPTION   "Backbone Route Map name"
        ::= { rcIpIsisInFilterNickNameIsidListEntry 6 }


rcIpIsisInFilterDefault OBJECT IDENTIFIER ::= { rcIpIsisInFilter 7 }

rcIpIsisInFilterDefaultPolicyName OBJECT-TYPE
        SYNTAX        DisplayString (SIZE(0..64))
        MAX-ACCESS    read-write
        STATUS        current
        DESCRIPTION   "Route Map name for the default filter"
        ::= { rcIpIsisInFilterDefault 1 }

rcIpIsisInFilterDefaultBackbonePolicyName OBJECT-TYPE
        SYNTAX        DisplayString (SIZE(0..64))
        MAX-ACCESS    read-write
        STATUS        current
        DESCRIPTION   "Backbone Route Map name for the default filter"
        ::= { rcIpIsisInFilterDefault 2 }
    
rcIpIpmcPimStaleSessionDelete OBJECT IDENTIFIER ::= { rcIp 111 }

rcIpIpmcPimStaleSessionDeleteEnable OBJECT-TYPE
    	SYNTAX		TruthValue
	MAX-ACCESS 	read-write
	STATUS		current
	DESCRIPTION	"Enable/Disable PIM ipmc stale session delete feature"
	DEFVAL		{ false }
	::= { rcIpIpmcPimStaleSessionDelete 1 }

--SPB PIM Gateway

rcIpSpbPimGw OBJECT IDENTIFIER ::= { rcIp 114 }

rcIpSpbPimGwGlobal OBJECT IDENTIFIER ::= { rcIpSpbPimGw 1 }

rcIpSpbPimGwGlobalHelloInterval OBJECT-TYPE
    SYNTAX        Integer32 (0..18724)
    MAX-ACCESS    read-only
    STATUS        current
    DESCRIPTION   "PIM Gateway Hello transmission interval. The PIM
                   Gateway VLAN inherits this value. The Gateway VLAN
                   Level setting will override this."
    DEFVAL        { 30 }
    ::= { rcIpSpbPimGwGlobal 1 }

rcIpSpbPimGwGlobalJoinPruneInterval OBJECT-TYPE
    SYNTAX        Integer32 (1..18724)
    MAX-ACCESS    read-only
    STATUS        current
    DESCRIPTION   "PIM Gateway Join/Prune transmission interval. The 
		   PIM Gateway VLAN inherits this value. The Gateway
		   VLAN level setting will override this."
    DEFVAL        { 60 }
    ::= { rcIpSpbPimGwGlobal 2 }

-- PIM Gateway Interface Table

rcIpSpbPimGwInterfaceTable OBJECT-TYPE 
    SYNTAX        SEQUENCE OF RcIpSpbPimGwInterfaceEntry
    MAX-ACCESS    not-accessible 
    STATUS        current 
    DESCRIPTION   "IP PIM Gateway table"
    ::= { rcIpSpbPimGw 2 }

rcIpSpbPimGwInterfaceEntry OBJECT-TYPE
    SYNTAX        RcIpSpbPimGwInterfaceEntry
    MAX-ACCESS    not-accessible
    STATUS        current
    DESCRIPTION   "An entry of Ip Pim Gateway Interface Table."
    INDEX         { rcIpSpbPimGwInterfaceIfIndex }
    ::= { rcIpSpbPimGwInterfaceTable 1 }
 
RcIpSpbPimGwInterfaceEntry ::=
    SEQUENCE {
                rcIpSpbPimGwInterfaceIfIndex       InterfaceIndex,
                rcIpSpbPimGwInterfaceOperState     INTEGER,
                rcIpSpbPimGwInterfaceAddressType   InetAddressType,
                rcIpSpbPimGwInterfaceAddress       InetAddress,
                rcIpSpbPimGwInterfaceAddressMask   InetAddress,
                rcIpSpbPimGwInterfaceHelloInterval Integer32,
                rcIpSpbPimGwInterfaceJoinPruneInterval Integer32
    }
 
rcIpSpbPimGwInterfaceIfIndex OBJECT-TYPE
    SYNTAX        InterfaceIndex
    MAX-ACCESS    not-accessible
    STATUS        current
    DESCRIPTION   "port"
    ::= { rcIpSpbPimGwInterfaceEntry 1 }

rcIpSpbPimGwInterfaceOperState OBJECT-TYPE
    SYNTAX        INTEGER { 
                          up(1), 
                          down(2) 
                  }
    MAX-ACCESS    read-only
    STATUS        current
    DESCRIPTION   "The current operational state of this PIM-gw 
		   interface."
    ::= { rcIpSpbPimGwInterfaceEntry 2 }

rcIpSpbPimGwInterfaceAddressType OBJECT-TYPE
    SYNTAX        InetAddressType
    MAX-ACCESS    read-only
    STATUS        current
    DESCRIPTION   "The address type of this PIM-gw interface."
    ::= { rcIpSpbPimGwInterfaceEntry 3 }

rcIpSpbPimGwInterfaceAddress OBJECT-TYPE
    SYNTAX        InetAddress (SIZE (0|4|8|16|20))
    MAX-ACCESS    read-only
    STATUS        current
    DESCRIPTION   "The primary IP address of this router on this PIM-gw
                   interface.  The InetAddressType is given by the
                   rcIpSpbPimGwInterfaceAddressType object."
    ::= { rcIpSpbPimGwInterfaceEntry 4 }

rcIpSpbPimGwInterfaceAddressMask OBJECT-TYPE
    SYNTAX        InetAddress (SIZE (0|4|8|16|20))
    MAX-ACCESS    read-only
    STATUS        current
    DESCRIPTION   "The primary IP address mask of this router on this PIM-gw
                   interface."
    ::= { rcIpSpbPimGwInterfaceEntry 5 }

rcIpSpbPimGwInterfaceHelloInterval OBJECT-TYPE
    SYNTAX        Integer32 (0..18724)
    MAX-ACCESS    read-write
    STATUS        current
    DESCRIPTION   "PIM Hello transmission interval. The PIM-GW
                   VLAN inherits this value. The PIM-gw VLAN level
                   setting will override this.Setting Hello
		   interval to 0 will cause PIM neighborship never to
		   expire."
    DEFVAL        { 30 }
    ::= { rcIpSpbPimGwInterfaceEntry 6 }

rcIpSpbPimGwInterfaceJoinPruneInterval OBJECT-TYPE
    SYNTAX        Integer32 (1..18724)
    MAX-ACCESS    read-write
    STATUS        current
    DESCRIPTION   "PIM Join/Prune transmission interval. The PIM-GW
                   VLAN inherits this value. The PIM-gw VLAN level
                   setting will override this."
    DEFVAL        { 60 }
    ::= { rcIpSpbPimGwInterfaceEntry 7 }

-- Pim-gw Neighbor Table

rcIpSpbPimGwNeighborTable OBJECT-TYPE
    SYNTAX        SEQUENCE OF RcIpPimGwNeighborEntry
    MAX-ACCESS    not-accessible
    STATUS        current
    DESCRIPTION   "The PIM-gw neighbor Table"
    ::= { rcIpSpbPimGw 3 }

rcIpSpbPimGwNeighborEntry OBJECT-TYPE
    SYNTAX        RcIpPimGwNeighborEntry
    MAX-ACCESS    not-accessible
    STATUS        current
    DESCRIPTION   "An entry (conceptual row) in the pimNeighborTable."
    INDEX         { rcIpSpbPimGwNeighborIfIndex,
                    rcIpSpbPimGwNeighborAddressType,
                    rcIpSpbPimGwNeighborAddress }
    ::= { rcIpSpbPimGwNeighborTable 1 }

RcIpPimGwNeighborEntry ::= SEQUENCE {
    rcIpSpbPimGwNeighborIfIndex              InterfaceIndex,
    rcIpSpbPimGwNeighborAddressType          InetAddressType,
    rcIpSpbPimGwNeighborAddress              InetAddress,
    rcIpSpbPimGwNeighborUpTime               TimeTicks,
    rcIpSpbPimGwNeighborExpiryTime           TimeTicks
} 

rcIpSpbPimGwNeighborIfIndex OBJECT-TYPE
    SYNTAX        InterfaceIndex
    MAX-ACCESS    not-accessible
    STATUS        current
    DESCRIPTION   "The value of ifIndex for the interface used to reach this
                   PIM-gw neighbor."
    ::= { rcIpSpbPimGwNeighborEntry 1 }

rcIpSpbPimGwNeighborAddressType OBJECT-TYPE
    SYNTAX        InetAddressType
    MAX-ACCESS    not-accessible
    STATUS        current
    DESCRIPTION   "The address type of this PIM-gw neighbor."
    ::= { rcIpSpbPimGwNeighborEntry 2 }

rcIpSpbPimGwNeighborAddress OBJECT-TYPE
    SYNTAX        InetAddress (SIZE (4|8|16|20))
    MAX-ACCESS    not-accessible
    STATUS        current
    DESCRIPTION   "The primary IP address of this PIM-gw neighbor.  The
                   InetAddressType is given by the rcIpSpbPimGwNeighborAddressType
                   object."
    ::= { rcIpSpbPimGwNeighborEntry 3 }

rcIpSpbPimGwNeighborUpTime OBJECT-TYPE
    SYNTAX        TimeTicks
    MAX-ACCESS    read-only
    STATUS        current
    DESCRIPTION   "The time since this PIM-gw neighbor (last) became a neighbor
                   of the local router."
    ::= { rcIpSpbPimGwNeighborEntry 4 }

rcIpSpbPimGwNeighborExpiryTime OBJECT-TYPE
    SYNTAX        TimeTicks
    MAX-ACCESS    read-only
    STATUS        current
    DESCRIPTION   "The minimum time remaining before this PIM-gw neighbor will
                   time out."
    ::= { rcIpSpbPimGwNeighborEntry 5 }

-- SPB PIM GW Controller foreign source table

rcIpSpbPimGwControllerForeignSrcTable OBJECT-TYPE 
        SYNTAX          SEQUENCE OF RcIpSpbPimGwControllerForeignSrcEntry
        MAX-ACCESS      not-accessible 
        STATUS          current 
        DESCRIPTION     "IP Multicast foreign source table from Pim-gw controller.
                         This is table of IP multicast sources from non-SPBM domain."
    ::= { rcIpSpbPimGw 4 }

rcIpSpbPimGwControllerForeignSrcEntry OBJECT-TYPE
	SYNTAX  	RcIpSpbPimGwControllerForeignSrcEntry
        MAX-ACCESS  	not-accessible
        STATUS  	current
        DESCRIPTION	"An entry of IP multicast foreign source."
        INDEX           { rcIpSpbPimGwControllerForeignSrcSourceAddress, 
                          rcIpSpbPimGwControllerForeignSrcGroupAddress }
        ::= { rcIpSpbPimGwControllerForeignSrcTable 1 }

RcIpSpbPimGwControllerForeignSrcEntry ::=
	SEQUENCE {
        	    rcIpSpbPimGwControllerForeignSrcSourceAddress IpAddress,
		    rcIpSpbPimGwControllerForeignSrcGroupAddress IpAddress,
		    rcIpSpbPimGwControllerForeignSrcRowStatus RowStatus,
		    rcIpSpbPimGwControllerForeignSrcGatewaySysId OCTET STRING,
		    rcIpSpbPimGwControllerForeignSrcGatewayHostName OCTET STRING,
		    rcIpSpbPimGwControllerForeignSrcType INTEGER,
		    rcIpSpbPimGwControllerForeignSrcOwner IpAddress
              }

rcIpSpbPimGwControllerForeignSrcSourceAddress OBJECT-TYPE
        SYNTAX  	IpAddress
        MAX-ACCESS  	not-accessible
        STATUS  	current
        DESCRIPTION 	"The source IP address from non-SPBM multicast
                      	domain."
        ::= { rcIpSpbPimGwControllerForeignSrcEntry 1 }

rcIpSpbPimGwControllerForeignSrcGroupAddress OBJECT-TYPE
        SYNTAX  	IpAddress
        MAX-ACCESS  	not-accessible
        STATUS  	current
        DESCRIPTION     "Multicast group IP address associated with the 
                         foreign source."
        ::= { rcIpSpbPimGwControllerForeignSrcEntry 2 }

rcIpSpbPimGwControllerForeignSrcRowStatus OBJECT-TYPE
        SYNTAX        	RowStatus
        MAX-ACCESS      read-create
        STATUS        	current
        DESCRIPTION   	"Used to create/delete entries."
        ::= { rcIpSpbPimGwControllerForeignSrcEntry 3 }

rcIpSpbPimGwControllerForeignSrcGatewaySysId OBJECT-TYPE
        SYNTAX        OCTET STRING (SIZE (6))
        MAX-ACCESS    read-only
        STATUS        current
        DESCRIPTION   "System ID of the node selected as the gateway for this
                       foreing source. This object has valid value if the source
		       has a gateway assigned. If the source is not assigned
		       a gateway, this object will have all 0's."
        ::= { rcIpSpbPimGwControllerForeignSrcEntry 4 }

rcIpSpbPimGwControllerForeignSrcGatewayHostName  OBJECT-TYPE
        SYNTAX        OCTET STRING (SIZE (0..255))
        MAX-ACCESS    read-only
        STATUS        current
        DESCRIPTION   "Host name of the node selected as the gateway for this
                       foreign source. This object has valid value if the source
		       has a gateway assigned. If the source is not assigned
		       a gateway, this object will have all 0's."
        ::= { rcIpSpbPimGwControllerForeignSrcEntry 5 }

rcIpSpbPimGwControllerForeignSrcType OBJECT-TYPE
        SYNTAX  	INTEGER {
				none(1), 
				msdp(2), 
				static(3)
			}
        MAX-ACCESS  	read-only
        STATUS  	current
        DESCRIPTION 	"The type of the owner of this source."
        ::= { rcIpSpbPimGwControllerForeignSrcEntry 6 }

rcIpSpbPimGwControllerForeignSrcOwner OBJECT-TYPE
        SYNTAX  	IpAddress
        MAX-ACCESS  	read-only
        STATUS  	current
        DESCRIPTION 	"The IP address of the MSDP peer if the foreign source
                      	type (rcIpSpbPimGwControllerForeignSrcType) is MSDP."
        ::= { rcIpSpbPimGwControllerForeignSrcEntry 7 }

-- SPB PIM GW Controller SPBMC source table

rcIpSpbPimGwControllerSpbmcSrcTable OBJECT-TYPE 
        SYNTAX          SEQUENCE OF RcIpSpbPimGwControllerSpbmcSrcEntry
        MAX-ACCESS      not-accessible 
        STATUS          current 
        DESCRIPTION     "SPB Multicast source table from SPB PIM GW controller.
	    		 This table is for all SPBM sources distributed to MSDP."
    ::= { rcIpSpbPimGw 5 }

rcIpSpbPimGwControllerSpbmcSrcEntry OBJECT-TYPE
	SYNTAX  	RcIpSpbPimGwControllerSpbmcSrcEntry
        MAX-ACCESS  	not-accessible
        STATUS  	current
        DESCRIPTION	"An entry of SPBMC source sent to MSDP."
        INDEX           { rcIpSpbPimGwControllerSpbmcSrcSourceAddress, 
                          rcIpSpbPimGwControllerSpbmcSrcGroupAddress }
        ::= { rcIpSpbPimGwControllerSpbmcSrcTable 1 }

RcIpSpbPimGwControllerSpbmcSrcEntry ::=
	SEQUENCE {
        	    rcIpSpbPimGwControllerSpbmcSrcSourceAddress IpAddress,
		    rcIpSpbPimGwControllerSpbmcSrcGroupAddress IpAddress,
		    rcIpSpbPimGwControllerSpbmcSrcOriginatorSysId OCTET STRING,
		    rcIpSpbPimGwControllerSpbmcSrcOriginatorHostName OCTET STRING
              }

rcIpSpbPimGwControllerSpbmcSrcSourceAddress OBJECT-TYPE
        SYNTAX  	IpAddress
        MAX-ACCESS  	not-accessible
        STATUS  	current
        DESCRIPTION 	"The source IP address from SPBM multicast domain."
        ::= { rcIpSpbPimGwControllerSpbmcSrcEntry 1 }

rcIpSpbPimGwControllerSpbmcSrcGroupAddress OBJECT-TYPE
        SYNTAX  	IpAddress
        MAX-ACCESS  	not-accessible
        STATUS  	current
        DESCRIPTION     "Multicast group IP address associated with the 
                         SPBMC source."
        ::= { rcIpSpbPimGwControllerSpbmcSrcEntry 2 }

rcIpSpbPimGwControllerSpbmcSrcOriginatorSysId OBJECT-TYPE
        SYNTAX  	OCTET STRING (SIZE (6))
        MAX-ACCESS  	read-only
        STATUS  	current
        DESCRIPTION     "System ID of the node to which the source is attached to."
        ::= { rcIpSpbPimGwControllerSpbmcSrcEntry 3 }

rcIpSpbPimGwControllerSpbmcSrcOriginatorHostName OBJECT-TYPE
        SYNTAX  	OCTET STRING (SIZE (0..255))
        MAX-ACCESS  	read-only
        STATUS  	current
        DESCRIPTION     "Host name of the node to which the source is attached to."
        ::= { rcIpSpbPimGwControllerSpbmcSrcEntry 4 }

-- SPB PIM GW Gateway foreign source table

rcIpSpbPimGwGatewayForeignSrcTable OBJECT-TYPE 
        SYNTAX          SEQUENCE OF RcIpSpbPimGwGatewayForeignSrcEntry
        MAX-ACCESS      not-accessible 
        STATUS          current 
        DESCRIPTION     "IP Multicast foreign source table from SPB PIM GW gateway."
    ::= { rcIpSpbPimGw 6 }

rcIpSpbPimGwGatewayForeignSrcEntry OBJECT-TYPE
	SYNTAX  	RcIpSpbPimGwGatewayForeignSrcEntry
        MAX-ACCESS  	not-accessible
        STATUS  	current
        DESCRIPTION	"An entry of IP multicast foreign source."
        INDEX           { rcIpSpbPimGwGatewayForeignSrcSourceAddress, 
			  rcIpSpbPimGwGatewayForeignSrcGroupAddress,
			  rcIpSpbPimGwGatewayForeignSrcControllerSysId }
        ::= { rcIpSpbPimGwGatewayForeignSrcTable 1 }

RcIpSpbPimGwGatewayForeignSrcEntry ::=
	SEQUENCE {
        	    rcIpSpbPimGwGatewayForeignSrcSourceAddress IpAddress,
		    rcIpSpbPimGwGatewayForeignSrcGroupAddress IpAddress,
		    rcIpSpbPimGwGatewayForeignSrcControllerSysId OCTET STRING,
		    rcIpSpbPimGwGatewayForeignSrcControllerHostName OCTET STRING,
		    rcIpSpbPimGwGatewayForeignSrcGatewaySysId OCTET STRING,
		    rcIpSpbPimGwGatewayForeignSrcGatewayHostName OCTET STRING,
		    rcIpSpbPimGwGatewayForeignSrcInVid INTEGER,
		    rcIpSpbPimGwGatewayForeignSrcInPort InterfaceIndex,
		    rcIpSpbPimGwGatewayForeignSrcOwnerType INTEGER
              }

rcIpSpbPimGwGatewayForeignSrcSourceAddress OBJECT-TYPE
        SYNTAX  	IpAddress
        MAX-ACCESS  	not-accessible
        STATUS  	current
        DESCRIPTION 	"The source IP address foreign source entry."
        ::= { rcIpSpbPimGwGatewayForeignSrcEntry 1 }

rcIpSpbPimGwGatewayForeignSrcGroupAddress OBJECT-TYPE
        SYNTAX  	IpAddress
        MAX-ACCESS  	not-accessible
        STATUS  	current
        DESCRIPTION     "Multicast group IP address associated with the 
                         foreign source."
        ::= { rcIpSpbPimGwGatewayForeignSrcEntry 2 }

rcIpSpbPimGwGatewayForeignSrcControllerSysId OBJECT-TYPE
        SYNTAX        	OCTET STRING (SIZE (6))
        MAX-ACCESS    	not-accessible
        STATUS        	current
        DESCRIPTION     "System ID of the controller node (preferred
	    		 controller) that sent this foreing source."
        ::= { rcIpSpbPimGwGatewayForeignSrcEntry 3 }

rcIpSpbPimGwGatewayForeignSrcControllerHostName OBJECT-TYPE
        SYNTAX        	OCTET STRING (SIZE (0..255))
        MAX-ACCESS    	read-only
        STATUS        	current
        DESCRIPTION     "Host name of the controller node that
	    		 sent this foreing source."
        ::= { rcIpSpbPimGwGatewayForeignSrcEntry 4 }

rcIpSpbPimGwGatewayForeignSrcGatewaySysId OBJECT-TYPE
        SYNTAX        	OCTET STRING (SIZE (6))
        MAX-ACCESS    	read-only
        STATUS        	current
        DESCRIPTION   	"System ID of the node selected as the gateway for this
	    		 foreing source."
    ::= { rcIpSpbPimGwGatewayForeignSrcEntry 5 }

rcIpSpbPimGwGatewayForeignSrcGatewayHostName  OBJECT-TYPE
        SYNTAX        	OCTET STRING (SIZE (0..255))
        MAX-ACCESS    	read-only
        STATUS        	current
        DESCRIPTION     "Host name of the node assigned as the gateway for this
                         foreign source."
        ::= { rcIpSpbPimGwGatewayForeignSrcEntry 6 }

rcIpSpbPimGwGatewayForeignSrcInVid OBJECT-TYPE
        SYNTAX        	INTEGER (1..4095)
        MAX-ACCESS    	read-only
        STATUS        	current
        DESCRIPTION   	"The VLAN id of the PimGw interface through which the 
                         source of this source is reachable."
        ::= { rcIpSpbPimGwGatewayForeignSrcEntry 7 }

rcIpSpbPimGwGatewayForeignSrcInPort  OBJECT-TYPE
        SYNTAX        	InterfaceIndex
        MAX-ACCESS    	read-only
        STATUS        	current
        DESCRIPTION     "A unique value to identify a physical interce through
	    		 which the source of this source is reachable."
        ::= { rcIpSpbPimGwGatewayForeignSrcEntry 8 }
    
rcIpSpbPimGwGatewayForeignSrcOwnerType OBJECT-TYPE
        SYNTAX          INTEGER {
			      none(1),
			      msdp(2),
			      static(3)
			}
        MAX-ACCESS      read-only
        STATUS          current
        DESCRIPTION     "This will specify the type of the owner -
	    		    msdp   - if the owner is MSDP
                            static - otherwise"
        ::= { rcIpSpbPimGwGatewayForeignSrcEntry 9 }

rcIpSpbPimGwNodeTable OBJECT-TYPE
    SYNTAX     SEQUENCE OF RcIpSpbPimGwNodeEntry
    MAX-ACCESS not-accessible
    STATUS     current
    DESCRIPTION
            "The PIM-gw node Table"
    ::= { rcIpSpbPimGw 7 }

rcIpSpbPimGwNodeEntry OBJECT-TYPE
    SYNTAX     RcIpSpbPimGwNodeEntry
    MAX-ACCESS not-accessible
    STATUS     current
    DESCRIPTION
	    "An entry (conceptual row) in the pimNodeTable."
    INDEX      { rcIpSpbPimGwNodeMacAddress }
    ::= { rcIpSpbPimGwNodeTable 1 }

RcIpSpbPimGwNodeEntry ::= SEQUENCE {
    rcIpSpbPimGwNodeMacAddress              MacAddress,
    rcIpSpbPimGwNodeHostName                OCTET STRING,
    rcIpSpbPimGwNodeRoleType                INTEGER,
    rcIpSpbPimGwNodeMacAddress              MacAddress
}

rcIpSpbPimGwNodeMacAddress OBJECT-TYPE
    SYNTAX     MacAddress
    MAX-ACCESS not-accessible
    STATUS     current
    DESCRIPTION
           "The Max Address of the active node."
    ::= { rcIpSpbPimGwNodeEntry 1 }

rcIpSpbPimGwNodeHostName OBJECT-TYPE
    SYNTAX     OCTET STRING (SIZE (0..255))
    MAX-ACCESS read-only
    STATUS     current
    DESCRIPTION
            "The Host name of the active node."
    ::= { rcIpSpbPimGwNodeEntry 2 }

rcIpSpbPimGwNodeRoleType OBJECT-TYPE
    SYNTAX     INTEGER {
                   controller(1),
                   gateway(2),
                   both(3)
               }
    MAX-ACCESS read-only
    STATUS     current
    DESCRIPTION
            "The role type of the node. It is either Gateway, Controller or both."
    ::= { rcIpSpbPimGwNodeEntry 3 }

-- Mroute Table
    
rcMRouteExt OBJECT IDENTIFIER ::= { rcIp 115 }
rcMRouteExtTable OBJECT-TYPE
    SYNTAX     SEQUENCE OF RcMRouteExtEntry
    MAX-ACCESS not-accessible
    STATUS     current
    DESCRIPTION
            "The (conceptual) table containing multicast routing
           information for IP datagrams sent by particular sources to
            the IP multicast groups known to this router."
    ::= { rcMRouteExt 1 }

rcMRouteExtEntry OBJECT-TYPE
    SYNTAX     RcMRouteExtEntry
    MAX-ACCESS not-accessible
    STATUS     current
    DESCRIPTION
            "An entry (conceptual row) containing the multicast routing
            information for IP datagrams from a particular source and
            addressed to a particular IP multicast group address."
    AUGMENTS {
       ipMRouteEntry
    }
    ::= { rcMRouteExtTable 1 }

RcMRouteExtEntry ::= SEQUENCE {
    rcMRouteExtProtocol              INTEGER
}

rcMRouteExtProtocol OBJECT-TYPE
    SYNTAX     INTEGER {
                   other(1),          -- none of the following
                   local(2),          -- e.g., manually configured
                   netmgmt(3),        -- set via net.mgmt protocol
                   dvmrp(4),
                   mospf(5),
                   pimSparseDense(6), -- PIMv1, both DM and SM
                   cbt(7),
                   pimSparseMode(8),  -- PIM-SMv2
                   pimDenseMode(9),   -- PIM-DMv2
                   igmpOnly(10),
                   pimSsmMode(11),
                   spb(12),
                   spbpimgw(13)
               }
    MAX-ACCESS read-only
    STATUS     current
    DESCRIPTION
            "The routing mechanism via which this route was learned."
    ::= { rcMRouteExtEntry 1 }

--
--  The IP Multicast Routing Next Hop Table
--

rcMRouteExtNextHopTable OBJECT-TYPE
    SYNTAX     SEQUENCE OF RcMRouteExtNextHopEntry
    MAX-ACCESS not-accessible
    STATUS     current
    DESCRIPTION
            "The (conceptual) table containing information on the next
            hops on outgoing interfaces for routing IP multicast
            datagrams.  Each entry is one of a list of next hops on
            outgoing interfaces for particular sources sending to a
            particular multicast group address."
    ::= { rcMRouteExt 2 }

rcMRouteExtNextHopEntry OBJECT-TYPE
    SYNTAX     RcMRouteExtNextHopEntry
    MAX-ACCESS not-accessible
    STATUS     current
    DESCRIPTION
            "An entry (conceptual row) in the list of next hops on
            outgoing interfaces to which IP multicast datagrams from
            particular sources to a IP multicast group address are
            routed."
    AUGMENTS {
          ipMRouteNextHopEntry
    }
    ::= { rcMRouteExtNextHopTable 1 } 

RcMRouteExtNextHopEntry ::= SEQUENCE {
    rcMRouteExtNextHopProtocol           INTEGER,
    rcMRouteExtNextHopL2Isid             Integer32
}

rcMRouteExtNextHopProtocol OBJECT-TYPE
    SYNTAX     INTEGER {
                   other(1),          -- none of the following
                   local(2),          -- e.g., manually configured
                   netmgmt(3),        -- set via net.mgmt protocol
                   dvmrp(4),
                   mospf(5),
                   pimSparseDense(6), -- PIMv1, both DM and SM
                   cbt(7),
                   pimSparseMode(8),  -- PIM-SMv2
                   pimDenseMode(9),   -- PIM-DMv2
                   igmpOnly(10),
                   pimSsmMode(11),
                   spb(12),
                   spbpimgw(13)
               }
    MAX-ACCESS read-only
    STATUS     current
    DESCRIPTION
            "The routing mechanism via which this next-hop was learned."
    ::= { rcMRouteExtNextHopEntry 1 }

rcMRouteExtNextHopL2Isid OBJECT-TYPE
        SYNTAX        Integer32 (0..16777215)
        MAX-ACCESS    read-only
        STATUS        current
        DESCRIPTION   "L2 ISID of the cvlan."
        ::= { rcMRouteExtNextHopEntry 2 }

--
--  The Multicast Routing Interface Table
--
rcMRouteExtInterfaceTable OBJECT-TYPE
    SYNTAX     SEQUENCE OF RcMRouteExtInterfaceEntry
    MAX-ACCESS not-accessible
    STATUS     current
    DESCRIPTION
            "The (conceptual) table containg multicast routing
            information specific to interfaces."
    ::= { rcMRouteExt 3 }

rcMRouteExtInterfaceEntry OBJECT-TYPE
    SYNTAX     RcMRouteExtInterfaceEntry
    MAX-ACCESS not-accessible
    STATUS     current
    DESCRIPTION
            "An entry (conceptual row) containing the multicast routing
            information for a particular interface."
    AUGMENTS {
          ipMRouteInterfaceEntry
    }
    ::= { rcMRouteExtInterfaceTable 1 }

RcMRouteExtInterfaceEntry ::= SEQUENCE {
    rcMRouteExtInterfaceProtocol         INTEGER
}

rcMRouteExtInterfaceProtocol OBJECT-TYPE
    SYNTAX     INTEGER {
                   other(1),          -- none of the following
                   local(2),          -- e.g., static routing
                   netmgmt(3),        -- set via net.mgmt protocol
                   dvmrp(4),
                   mospf(5),
                   pimSparseDense(6), -- PIMv1, both DM and SM
                   cbt(7),
                   pimSparseMode(8),  -- PIM-SMv2
                   pimDenseMode(9),   -- PIM-DMv2
                   igmpOnly(10),
                   pimSsmMode(11),
                   spb(12),
                   spbpimgw(13)
               }
    MAX-ACCESS read-only
    STATUS     current
    DESCRIPTION
            "The routing protocol running on this interface."
    ::= { rcMRouteExtInterfaceEntry 1 }

--
-- MRoute Ext Next Hop Port Table
--
rcMRouteExtNextHopPortTable OBJECT-TYPE
    SYNTAX     SEQUENCE OF RcMRouteExtNextHopPortEntry
    MAX-ACCESS not-accessible
    STATUS     current
    DESCRIPTION
            "The (conceptual) table containing information on the next
            hops on outgoing interfaces for routing IP multicast
            datagrams.  Each entry is one of a list of next hops on
            outgoing interfaces for particular sources sending to a
            particular multicast group address"
    ::= { rcMRouteExt 4 }

rcMRouteExtNextHopPortEntry OBJECT-TYPE
    SYNTAX     RcMRouteExtNextHopPortEntry
    MAX-ACCESS not-accessible
    STATUS     current
    DESCRIPTION
            "An entry (conceptual row) in the list of next hops on
            outgoing interfaces to which IP multicast datagrams from
            particular sources to a IP multicast group address are
            routed."
    INDEX      { rcMRouteExtNextHopPortGroup, rcMRouteExtNextHopPortSource,
                 rcMRouteExtNextHopPortSourceMask, rcMRouteExtNextHopPortIfIndex,
                 rcMRouteExtNextHopPortReceiverPort, rcMRouteExtNextHopPortAddress }
    ::= { rcMRouteExtNextHopPortTable 1 }

RcMRouteExtNextHopPortEntry ::= SEQUENCE {
    rcMRouteExtNextHopPortGroup              IpAddress,
    rcMRouteExtNextHopPortSource             IpAddress,
    rcMRouteExtNextHopPortSourceMask         IpAddress,
    rcMRouteExtNextHopPortIfIndex            InterfaceIndex,
    rcMRouteExtNextHopPortReceiverPort       InterfaceIndex,
    rcMRouteExtNextHopPortAddress            IpAddress,
    rcMRouteExtNextHopPortState              INTEGER,
    rcMRouteExtNextHopPortUpTime             TimeTicks,
    rcMRouteExtNextHopPortExpiryTime         TimeTicks,
    rcMRouteExtNextHopPortClosestMemberHops  Integer32,
    rcMRouteExtNextHopPortProtocol           INTEGER,
    rcMRouteExtNextHopPortPkts               Counter32
}

rcMRouteExtNextHopPortGroup OBJECT-TYPE
    SYNTAX     IpAddress
    MAX-ACCESS not-accessible
    STATUS     current
    DESCRIPTION
            "The IP multicast group for which this entry specifies a
            next hop on an outgoing interface."
    ::= { rcMRouteExtNextHopPortEntry 1 }

rcMRouteExtNextHopPortSource OBJECT-TYPE
    SYNTAX     IpAddress
    MAX-ACCESS not-accessible
    STATUS     current
    DESCRIPTION
            "The network address which when combined with the
            corresponding value of ipMRouteNextHopSourceMask identifies
            the sources for which this entry specifies a next hop on an
            outgoing interface."
    ::= { rcMRouteExtNextHopPortEntry 2 }

rcMRouteExtNextHopPortSourceMask OBJECT-TYPE
    SYNTAX     IpAddress
    MAX-ACCESS not-accessible
    STATUS     current
    DESCRIPTION
            "The network mask which when combined with the corresponding
            value of ipMRouteNextHopSource identifies the sources for
            which this entry specifies a next hop on an outgoing
            interface."
    ::= { rcMRouteExtNextHopPortEntry 3 }

rcMRouteExtNextHopPortIfIndex OBJECT-TYPE
    SYNTAX     InterfaceIndex
    MAX-ACCESS not-accessible
    STATUS     current
    DESCRIPTION
            "The ifIndex value of the interface for the outgoing
            interface for this next hop."

    ::= { rcMRouteExtNextHopPortEntry 4 }

rcMRouteExtNextHopPortReceiverPort OBJECT-TYPE
     SYNTAX     InterfaceIndex
     MAX-ACCESS not-accessible
     STATUS     current
     DESCRIPTION
             "The port number where the receiver exists for this next hop."
     ::= { rcMRouteExtNextHopPortEntry 5 }

rcMRouteExtNextHopPortAddress OBJECT-TYPE
    SYNTAX     IpAddress
    MAX-ACCESS not-accessible
    STATUS     current
    DESCRIPTION
            "The address of the next hop specific to this entry.  For
            most interfaces, this is identical to ipMRouteNextHopGroup.
            NBMA interfaces, however, may have multiple next hop
            addresses out a single outgoing interface."
    ::= { rcMRouteExtNextHopPortEntry 6 }

rcMRouteExtNextHopPortState OBJECT-TYPE
    SYNTAX     INTEGER { pruned(1), forwarding(2) }
    MAX-ACCESS read-only
    STATUS     current
    DESCRIPTION
            "An indication of whether the outgoing interface and next
            hop represented by this entry is currently being used to
            forward IP datagrams.  The value 'forwarding' indicates it
            is currently being used; the value 'pruned' indicates it is
            not."
    ::= { rcMRouteExtNextHopPortEntry 7 }

rcMRouteExtNextHopPortUpTime OBJECT-TYPE
    SYNTAX     TimeTicks
    MAX-ACCESS read-only
    STATUS     current
    DESCRIPTION
            "The time since the multicast routing information
            represented by this entry was learned by the router."
    ::= { rcMRouteExtNextHopPortEntry 8 }

rcMRouteExtNextHopPortExpiryTime OBJECT-TYPE
    SYNTAX     TimeTicks
    MAX-ACCESS read-only
    STATUS     current
    DESCRIPTION
            "The minimum amount of time remaining before this entry will
            be aged out.  The value 0 indicates that the entry is not
            subject to aging."
    ::= { rcMRouteExtNextHopPortEntry 9 }

rcMRouteExtNextHopPortClosestMemberHops OBJECT-TYPE
    SYNTAX     Integer32
    MAX-ACCESS read-only
    STATUS     current
    DESCRIPTION
            "The minimum number of hops between this router and any
            member of this IP multicast group reached via this next hop
            on this outgoing interface.  Any IP multicast datagrams for
            the group which have a TTL less than this number of hops
            will not be forwarded to this next hop."
    ::= { rcMRouteExtNextHopPortEntry 10 }

rcMRouteExtNextHopPortProtocol OBJECT-TYPE
    SYNTAX     INTEGER {
                   other(1),          -- none of the following
                   local(2),          -- e.g., manually configured
                   netmgmt(3),        -- set via net.mgmt protocol
                   dvmrp(4),
                   mospf(5),
                   pimSparseDense(6), -- PIMv1, both DM and SM
                   cbt(7),
                   pimSparseMode(8),  -- PIM-SMv2
                   pimDenseMode(9),   -- PIM-DMv2
                   igmpOnly(10),
                   pimSsmMode(11),
                   spb(12),
                   spbpimgw(13)
               }
    MAX-ACCESS read-only
    STATUS     current
    DESCRIPTION
            "The routing mechanism via which this next-hop was learned."
    ::= { rcMRouteExtNextHopPortEntry 11 }

rcMRouteExtNextHopPortPkts OBJECT-TYPE
    SYNTAX     Counter32
    MAX-ACCESS read-only
    STATUS     current
    DESCRIPTION
            "The number of packets which have been forwarded using this
            route."
    ::= { rcMRouteExtNextHopPortEntry 12 }
END

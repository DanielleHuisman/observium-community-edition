RC-LICENSE-MIB DEFINITIONS ::= BEGIN

IMPORTS
    MODULE-IDENTITY, OBJECT-TYPE, Integer32
        FROM SNMPv2-SMI
    DisplayString, DateAndTime, TruthValue
        FROM SNMPv2-TC
    rcLicense
        FROM RAPID-CITY;

rcLicenseMib MODULE-IDENTITY
       LAST-UPDATED     "202008240000Z"
       ORGANIZATION     "Bay Networks, Rapid-City Group"
       CONTACT-INFO     "Yu-Ten Lee
                         Postal:        Nortel Networks
                                        4655 Great America Parkway
                                        Santa Clara, CA 95052-8185
                         Fax:           408-495-6680
                         Tel:           408-495-6159
 			 E-mail:        ylee@nortelnetworks.com"
       DESCRIPTION "The MIB module is the definition for Licensing."

	   REVISION "202008240000Z" -- 24 August 2020  
       DESCRIPTION "Version 108: Add rcLicenseLicenseType - macsec type for unified
                 Requested by Oana Cristea (Oana)"

       REVISION "201905290000Z" -- 29 May 2019	
       DESCRIPTION "Version 107: Add rcLicenseDisplayType.
				 Requested by Sebastian Costache (Prem)"

       REVISION "201901080000Z" -- 08 Jan 2019	
       DESCRIPTION "Version 106: Add insight to rcLicenseLicenseType.
				 VOSS 8.0 (Prem)"

       REVISION "201812050000Z" -- 5 December 2018	
       DESCRIPTION "Version 105: Added rcLicenseGrantTable (missing in MRT file)
	   			 and rcLicenseRemainingDays.
				 Requested to fix VOSS-12241 VOSS 8.0 (Prem)"

       REVISION "201806150000Z" -- 15 June 2018	
       DESCRIPTION "Version 104: Added License bit bitrcVirtualServiceTbl"

       REVISION "201705080000Z" -- 08 May 2017	
       DESCRIPTION "Version 103: added bitvsp5k5030GSXuPWR and bitvsp5k5054GSXuPWR
	   			 Requested by Catalin Neacsu (prempa)."

       REVISION "201704180000Z" -- 18 April 2017	
       DESCRIPTION "Version 102: added option to rcLicenseLicenseType
	                         l3v(10),
                                 l3vWithMacsec(11),
                                 datacenter(12),
                                 sdniot(13)"
	   
       REVISION "201608260000Z" -- 26 Aug 2016	
       DESCRIPTION "Version 101: added option to rcLicenseLicenseType
	             port(6),
		     premierWithPort(7),
		     premierPlusMacsecWithPort(8),
		     unknown(9)" 
	   
       REVISION "201607260000Z" -- 26 Jul 2016	
       DESCRIPTION "Version 100:  Added bitrcVrfScalingGlobalGrp"
	   
       REVISION "201607250000Z" -- 25 Jul 2016	
       DESCRIPTION "Version 99:	Added bitrcVxlanVtepSourceIp(1190).
	   			Requested by Manjunath Amruta (prempa)"
	   
       REVISION "201603310000Z" -- 31 Mar 2016	
       DESCRIPTION "Version 98:	bitvsp8k8402CQ"
	   
       REVISION "201603250000Z" -- 25 Mar 2016
       DESCRIPTION "Version 97:	Added bitrcDvrGlobalGrp"
	   
       REVISION "201603020000Z" -- 02 Mar 2016
       DESCRIPTION "Version 96:	Added rcLicenseFileName, rcLicenseLicenseType,
	   rcLicenseDurationType,rcLicenseFactoryTrialPeriodRemainingDays,
	   rcLicenseDaysLeftBeforeExpiration,rcLicenseDaysAfterExpiration,
	   rcLicenseGenerationTime and rcLicenseExpirationTime"
	   
       REVISION "201512040000Z" -- 04 Dec 2015
       DESCRIPTION "Version 95:	Removed bitrcWhiteBoxLicense"
	   
       REVISION "201509220000Z" -- 22 September 2015
       DESCRIPTION "Version 94:	Added bitvsp9k9424XS, bitvsp9k9424XT,
	   			bitvsp9k9416QQ, bitvsp9k9406CQ and bitvspSF9400
				for Tsunami cards"

       REVISION "201508210000Z" -- 21 August 2015
       DESCRIPTION "Version 93:	Added bitrcWhiteBoxLicense"
	   
       REVISION "201505280000Z" -- 28 May 2015
       DESCRIPTION "Version 92: Added license bit
                               bitrcIsisGlobalIpTunnelSrcAddr(1187),
			       bitrcIsisLogicalInterfaceTbl(1188)
			       submit 24321"
			   
       REVISION "201411060000Z" -- 06 Nov 2014
       DESCRIPTION "Version 91: changed bitvsp7k7254XSQ(1748) to
                                bitvsp7k7248XS(1748) and 
				bitvsp7k7254XTQ(1749) to bitvsp7k7248XT(1749).
				Added bitvsp7k7206QQ(1751).
				Requested by P Nandan for Snowflake (Prem)"
	   
       REVISION "201411050000Z" -- 05 Nov 2014
       DESCRIPTION "Version 90: added bitvsp4k4450GSX(1750)"
	   
       REVISION "201410150000Z" -- 15 Oct 2014
       DESCRIPTION "Version 89: added bitvsp7k7254XSQ(1748) and 
	   			      bitvsp7k7254XTQ(1749)"
	   
       REVISION "201409090000Z" -- 09 Sept 2014
       DESCRIPTION "Version 88: added 
	   		        bitvsp8k8424XS(1741),
				bitvsp8k8408QQ(1742),
				bitvsp8k8418XSQ(1743),
				bitvsp8k8418XTQ(1744),
				bitvsp8k8424GS(1745),
				bitvsp8k8424GT(1746),
				bitvsp8k8424XT(1747)"	   
       REVISION "201406020000Z" -- 02 June. 2014
       DESCRIPTION "Version 87 added bitrcIpIsisInFilter(1687),
                                     bitrcIpIsisInFilterDefault(1688)" 
	   
       REVISION "201404040000Z" -- 04 April. 2014
       DESCRIPTION "Version 86 Correct the license definition for 4450GXS" 

       REVISION "201404020000Z" -- 02 April. 2014
       DESCRIPTION "Version 85 added bitrcMACSecIfConfigTbl(1184),
	   			     bitrcMACSecCATbl(1185),
				     bitsecyIfTbl(1186)"	   

       REVISION "201401100000Z" -- 10 Jan. 2014
       DESCRIPTION "Version 84 added bitvsp8k8242XSQ"

       REVISION "201311130000Z" -- 13 November 2013
       DESCRIPTION "Version 83 added bitvsp4k4950GSXPWRPLUS"

       REVISION "201301310000Z" -- 31 Jan 2013
       DESCRIPTION "Version 82 added bitrcIsisPlsbIpShortcut"
	   
       REVISION "201301140000Z" -- 14 Jan 2013
       DESCRIPTION "Version 81 added  bitrcCfmTransmitL2TraceTbl(1180),	
	   			bitrcCfmTransmitL2McastTraceTbl(1181),
				bitrcCfmTransmitLbmTbl(1182),
				bitrcCfmTransmitLtmTbl(1183)"
			    
       REVISION "201212060000Z" -- 06 Dec 2012
       DESCRIPTION "Version 80: Added bitrof48x1000SFP(1733),
	   			bitrof16x10GBaseSFP(1734),
				bitrof48x10GBaseSFP(1735),
				bitrof4x40GBaseSFP(1736),
				bitrof12x40GBaseSFP(1737)"

       REVISION "201210080000Z" -- 08 Oct 2012
       DESCRIPTION "Version 79: Added bitcbSF9610(1732)"

       REVISION "201209180000Z" -- 18 Sept 2012
       DESCRIPTION "Version 78: corrected card type vsp4k4850GTSPWRPLUS"

       REVISION "201208160000Z" -- 16 Aug 2012
       DESCRIPTION "Version 77: Added vsp4k4850GTS and vsp4k4850GTSPWR"

       REVISION "201205290000Z" -- 29 May 2012
       DESCRIPTION "Version 76: Remove the rcLic which is added by mistake"

       REVISION "201205250000Z" -- 25 May 2012
       DESCRIPTION "Version 75: Added bitrofLoadBoard(1729)"

       REVISION "201204250000Z" -- 25 April 2012
       DESCRIPTION "Version 74: bitcliPasswordPostExpiryLogins(1727),
	   	    bitrc2kPRE12X10GBaseXLJ(1728)"

       REVISION "201203070000Z" -- 07 March 2012
       DESCRIPTION "Version 73: Modifed bitrc2kPR12X10GBaseJXLRS to
	   	    bitrc2kPR12X10GBaseXLRSJ"

       REVISION "201202270000Z" -- 27 February 2012
       DESCRIPTION "Version 72:Added license
                    bitrc2kPR12X10GBaseJXLRS(1726)"

       REVISION "201108220000Z" -- 22 August 2011
       DESCRIPTION "Version 71:Added license
                    bitrcPrFilterAceIpv6TrafficClsTbl(1685)"

       REVISION "201106160000Z" -- 16 June 2011
       DESCRIPTION "Version 70:Added license
                    bitrcPortLosslessEnetTbl(1684)"

       REVISION "201105260000Z" -- 26 May 2011
       DESCRIPTION "Version 69:Added licenses
	            bitcliPasswordRuleCli(1722),
		    bitcliPasswordChangeIntervalCli(1723),
		    bitcliPasswordPreNotifyCli(1724),
		    bitcliPasswordPostNotifyCli(1725)."

       REVISION "201101060000Z" -- 06 January 2011
       DESCRIPTION "Version 68:Added licenses 
	                bitL2PingCmdCli(1175),
			bitL2TraceCmdCli(1176),
			bitL2TraceReplyCmdCli(1177),
			bitDebugL2vpnCmdCli(1178),
			bitDebugIsisCmdCli(1179)
			bitrc2kCPURed(1679),
			bitrc2kPRE48x1000BaseGB(1680),
			bitrc2kPRE48x1000BaseGT(1681),
			bitrc2kPRE12X10GBaseXL(1682),
			bitrc2kPRE34xXG(1683),
			bitrcIpRedistributeTblIsis(1721)."

       REVISION "201008230000Z" -- 23 August 2010
       DESCRIPTION "Version 67:Added license bitrcIpv6RsmltOperTbl(1678),
        				bitrc2kCPURed(1679)"

       REVISION "200908140000Z" -- 14 Aug 2009
       DESCRIPTION "Version 66:Added license bitrcIpv6DhcpForwardTbl(1672),
        				bitrcIpv6ConfDhcpTbl(1673),
        				bitrcIpv6VrrpOperTbl(1674),
        				bitrcVrrpExtScalarsGrp(1675),
        				bitrcVrrpTmpOperationsGrp(1676),
        				bitrcIpMulticastSquareSmltGrp(1677)"

       REVISION "200903110000Z" -- 11 March 2009
       DESCRIPTION "Version 65:Added license bits bitrcDHUniTbl(1173),
                                     bitrcDHUniClearRctStatsCli(1174). "

       REVISION "200902160000Z" -- 16 Feb 2009
       DESCRIPTION "Version 64: Added license bits  bitbasicrcIpBgpAggregateTbl(1714),
                                                    bitbasicrcIpBgpConfederationGrp(1715),
                                                    bitbasicrcIpBgpRouteReflectorGrp(1716),
                                                    bitbasicrcStatBgpGrp(1717),
                                                    bitbasicrcStatBgpPeerTbl(1718),
                                                    bitbasicrcIpBgpPeerGroupTbl(1719),
                                                    bitbasicrcIpBgpNetworkTbl(1720),"

       REVISION "200902050000Z" -- 05 Feb 2009
       DESCRIPTION "Version 63: Added license bits  bitrcIpConfBfdTbl(1709),
                                                    bitrcIpBfdGeneralGrp(1710),
                                                    bitbasicrcIpBgpPeerTbl(1711),
                                                    bitbasicbgpPeerTbl(1712),
                                                    bitbasicrcIpBgpGeneralGrp(1713)"

       REVISION "200809261200Z" -- 26 Sept 2008
       DESCRIPTION "Version 62: Added license bits  bitrc2kPR48x1000BaseGXRS(1668),
                                                    bitrc2kPR30x1000BaseGBRS(1669),
                                                    bitrc2kPR6X10GBaseXLRS(1670),
	                                            bitrc2kPR26xXGRS(1671)"
                                                         
       REVISION "200809260000Z" -- 26 Sept 2008
       DESCRIPTION "Version 61: Added license bits
                                                         bitrcL2cpMacTbl(1170),
                                                         bitrcL2cpProfileTbl(1171),
                                                         bitrcL2cpProfileRuleTbl(1172),
                                                         bitsysCliSetSingleMgmtIpCli(1666),
                                                         bitBcliAutoassignipCli(1667),"

       REVISION "200807140000Z" -- 14 July 2008
       DESCRIPTION "Version 60: Added license bit 1169"	    

       REVISION "200806060000Z" -- 06 June 2008
       DESCRIPTION "Version 59:modify rcLicense.mib from:
                    bitrcFilterActAdvancedTbl (1032) TO bitrcFilterActPatternTbl (1032)
                    bitrcFilterAceAdvancedTbl (1034) TO bitrcFilterAcePatternTbl (1034)"
    
       REVISION "200805170000Z" -- 17 May 2008
       DESCRIPTION "Version 58: bitlastbitnum should be 2047 instead of 4095."

       REVISION "200805090000Z" -- 09 May 2008
       DESCRIPTION "Version 57: Fixed smilint errors."

       REVISION "200804100000Z" -- 10 April 2008
       DESCRIPTION "Version 56: Added license bits 1700-1708 for CB cards"

       REVISION "200803140000Z" -- 14 March 2008
       DESCRIPTION "Version 55: Added license bit 1665"	    
 
       REVISION "200802080000Z" -- 08 February 2008
       DESCRIPTION "Version 54: Added license bit 1168"

       REVISION "200801250000Z" -- 25 January 2008
       DESCRIPTION "Version 53: Added license bit 1664 for Pluggable-Optical-Module"                 
       REVISION "200712060000Z" -- 06 December 2007
       DESCRIPTION "Version 52: Added license bit 1164-1167"
       REVISION "200710180000Z" -- 18 October 2007
       DESCRIPTION "Version 51: Added license bit 1163,
	                        Removed extra word bit at ORGANIZATION,
	                        Added missing REVISION line for Version 44"
       REVISION "200708290000Z" -- 29 August 2007
       DESCRIPTION "Version 50: Added license bits 1662-1663"
       REVISION "200708200000Z" -- 20 August 2007
       DESCRIPTION "Version 49: Added license bits 1658-1661"
       REVISION "200708150000Z" -- 15 August 2007
       DESCRIPTION "Version 48: Added license bits 1653 - 1657"
       REVISION "200706150000Z" -- 15 June 2007
       DESCRIPTION "Version 47: Added license bits 39, 1149 - 1162"
       REVISION "200705030000Z" -- 03 May 2007
       DESCRIPTION "Version 46: Added license bit 1148"
       REVISION "200704160000Z" -- 16 Apr 2007
       DESCRIPTION "Version 45: Added license bits from 1130-1147"
       REVISION "200703271000Z" -- 27 Mar 2007
       DESCRIPTION "Version 44: Added license bits from 1651-1652"
       REVISION "200703270000Z" -- 27 Mar 2007
       DESCRIPTION "Version 43: Added license bits from 1591-1592"
       REVISION "200703260000Z" -- 26 Mar 2007
       DESCRIPTION "Version 42: Added license bits from 1641-1650"
       REVISION "200701290000Z" -- 29 Jan 2007
       DESCRIPTION "Version 41: Added license bits from 1603-1640"
       REVISION "200701160000Z" -- 16 Jan 2007
       DESCRIPTION      "Version 40: Add the license bit for SLPP and NLBS"
       REVISION "200612130000Z" -- 13 Dec 2006
       DESCRIPTION      "Enterprise MIB for the Accelar product family."
       REVISION "200608080000Z" -- 08 August 2006
       DESCRIPTION "Version 39: Added bit 1129"
       REVISION "200608020000Z" -- 02 August 2006
       DESCRIPTION "Version 38: Added bits 1050-1128"
       REVISION "200607200000Z" -- 20 Jul 2006
       DESCRIPTION "Version 37: Added bitADVANCED & bitCORPORATE & 1599-1600"
       REVISION "200606150000Z" -- 15 Jun 2006
       DESCRIPTION "Version 36: Added bits 1031-1049"
       REVISION "200603210000Z" -- 21 Mar 2006
       DESCRIPTION "Version 35: Added bitrc2kPP8300-48x1000BaseSFP-2B"
       REVISION "200602150000Z" -- 15 Feb 2006
       DESCRIPTION "Version 34: Removed Thunderbolt definitions due to project cancellation"
       REVISION "200601180000Z" -- 18 Jan 2006
       DESCRIPTION "Version 33: Added 1030"
       REVISION "200511290000Z" -- 29 Nov 2005
       DESCRIPTION "Version 32: Added 1029"
       REVISION "200511220000Z" -- 22 Nov 2005
       DESCRIPTION "Version 31: Minor changes to be consistent with the code"
       REVISION "200510250000Z" -- 25 Oct 2005
       DESCRIPTION "Version 30: Added bitpoeCliSetCardPdDetectTypeCli(1028)"
       REVISION "200509200000Z" -- 20 Sep 2005
       DESCRIPTION "Version 29: Added bitBcliMezzCardBootEnableCli(1027)"
       REVISION "200508261200Z" -- 26 August 2005
       DESCRIPTION "Version 28: Added bitipmcCliSetDvmGlobPruneResendCli(1026)"
       REVISION "200505231200Z" -- 23 May 2005
       DESCRIPTION "Version 27: Updated 1587"
       REVISION "200505230000Z" -- 23 May 2005
       DESCRIPTION "Version 26: Updated 1582,1587"
       REVISION "200504191200Z" -- 19 April 2005
       DESCRIPTION "Version 25: Updated 1588, 1589"
       REVISION "200504011800Z" -- 01 April 2005
       DESCRIPTION "Version 24: Added bitBcliMd5Cli(1024),bitBcliDumpfhCli(1025)"
       REVISION "200503221800Z" -- 22 March 2005
       DESCRIPTION "Version 23: Added support for Rainier, removed (851,896,915), & moved Tacacs bits 1588-1589 to 1021-1022, and added bitPortCliSetSpoofDetectCli"
       REVISION "200503141800Z" -- 14 March 2005
       DESCRIPTION "Version 22: Added  bitPpBdgPortcli, bitLldpGlobalConfigTbl, & bitLldpPortConfigTbl (1009-1011)"
       REVISION "200503101200Z" -- 10 March 2005
       DESCRIPTION "Version 21: Added bitForeachCli & bitTiCli (1007-1008)"
       REVISION "200502181200Z" -- 18 February 2005
       DESCRIPTION "Version 20: Updated 1582 from POE to POL"
       REVISION "200502171200Z" -- 17 February 2005
       DESCRIPTION "Version 19: Updated 1579-1582, 977, & 1004-1006 to match code definitions"
       REVISION "200502160000Z" -- 16 February 2005
       DESCRIPTION "Version 18: Added bitrcBridgeFdbProtectTbl(1004)"
       REVISION "200502110000Z" -- 11 February 2005
       DESCRIPTION "Version 17: Added bits(1588-1589) for Tacacs"
       REVISION "200502090000Z" -- 09 February 2005
       DESCRIPTION "Version 16: Added bits(991-1003) for shell commands"
       REVISION "200412221600Z" -- 22 December 2004
       DESCRIPTION "Version 15: Added bitExtCpLimit(990)"
       REVISION "200410211600Z" -- 21 October 2004
       DESCRIPTION "Version 13: Added bitBcliMaintCommand(989)"
       REVISION "200409300000Z" -- 30 September 2004
       DESCRIPTION "Version 12: Remove extra quoted for descrition clause"
       REVISION "200409100000Z" -- 08 September 2004
       DESCRIPTION "Version 11: Added bitAccessLevelEnDisCli(988)"
       REVISION "200409080000Z" -- 08 September 2004
       DESCRIPTION "Version 11: Added bitAutoRecoverSet(987)"
       REVISION "200408270000Z" -- 27 August 2004
       DESCRIPTION "Version 10: Added bitrc2kPP830024x100BaseFX(1587)
                                       Change bitrc2kPP830048x100BaseTXPOL to bitrc2kPP830048x100BaseTXPOE"

       REVISION "200408240000Z" -- 24 August 2004
       DESCRIPTION "Version 9: Added bitospfSetRfc1583CompatibilityCli(986)" 

       REVISION "200407200000Z" -- 20 July 2004
       DESCRIPTION "Version 8: Added version info"  

       ::= { rcLicense 0 }

-- License scheme

rcLicenseNumber OBJECT-TYPE
    SYNTAX    INTEGER {
        bit8600BASE(0),
-- Available now (Previously Thunderbolt)
        bitPP8300BASE(2),
        bitdellBASE(3),
        bit8xx4BASE(4),
        bit8xx5BASE(5),
        bit8xx6BASE(6),
        bit8xx7BASE(7),
        bit8xx8BASE(8),
        bit8xx9BASE(9),
        bit8x10BASE(10),
        bit8x11BASE(11),
        bit8x12BASE(12),
        bit8x13BASE(13),
        bit8x14BASE(14),
        bit8x15BASE(15),
        bit8x16BASE(16),
        bit8x17BASE(17),
        bit8x18BASE(18),
        bit8x19BASE(19),
        bit8x20BASE(20),
        bit8x21BASE(21),
        bit8x22BASE(22),
        bit8x23BASE(23),
        bit8x24BASE(24),
        bit8x25BASE(25),
        bit8x26BASE(26),
        bit8x27BASE(27),
        bit8x28BASE(28),
        bit8x29BASE(29),
        bit8x30BASE(30),
        bit8x31BASE(31),
        --    /* Reserve 32 bits for base */

        --    /* Start package license */
        bitpackageStart(32),
        bitBASIC(33),
        bitUNICAST(34),
        bitMULTICAST(35),
        bitTOOL(36),
        bitADVANCED(37),
        bitCORPORATE(38),
	bitPREMIER(39),
	bitMACSEC(40),
	
        bitpackageEnd(255),
        --    /* End package license */

        --    /* Feature bit start from bit 256 */
        --    /* These bits are from xxxConsistencyCheck */
        bitfeature(256),
        bitrc2kCopyFileGrp(257),
        bitrc2kDeviceGlobalTbl(258),
        bitrcCliCustomGrp(259),
        bitrcCliGrp(260),
        bitrcCliGrpWsm(261),
        bitrcDiagMacConvSteeringTbl(262),
        bitrcDiagMirrorByPortTbl(263),
        bitrcDiagPortConvSteeringTbl(264),
        bitrcSysAccPolicyTbl(265),
        bitrcSysGrp(266),
        bitrcSysTrapTbl(267),
        bitrcUserSetTimeGrp(268),
        bitrcPortLock(269),
        bitrcSyslogGlobalGrp(270),
        bitrcSyslogHostTbl(271),
        bitrcWebGrp(272),
        bitdot1dStaticEntry(273),
        bitsnmpCommunityTbl(274),
        bitrcLoadModule(275),
        bitrcMltGrp(276),
        bitrcMltTbl(277),
        bitsmltMacTblSend(278),
        bitrc2kQosEgressQosToDscpTbl(279),
        bitrc2kQosEgressQosToTagTbl(280),
        bitrc2kQosIngressDscpToQosTbl(281),
        bitrc2kQosIngressTagToQosTbl(282),
        bitrc2kQosQosTbl(283),
        bitrcBridgeAutoLearnTbl(284),
        bitrcBridgeManualEditTbl(285),
        bitrcBridgeUnknownMacDiscardTbl(286),
        bitrcBridgeStaticMulticastTbl(287),
        bitrcSvlanGlobalGrp(288),
        bitrcSvlanTbl(289),
        bitrcVlanMacTbl(290),
        bitrcVlanPortTbl(291),
        bitrcVlanTbl(292),
        bitvlanTbl(293),
        bitrc2kBootConfigTbl(294),
        bitrc2kCpuEthernetPortRouteTbl(295),
        bitrc2kCpuEthernetPortTbl(296),
        bitrc2kCpuSerialPortTbl(297),
        bitrc2kCardTbl(298),
        bitrc2kMdaCardTbl(299),
        bitrcChassisGrp(300),
        bitrcL2RedundancyGrp(301),
        bitrcRecReservTbl(302),
        bitrcTftpGrp(303),
        bitrcFdbTbl(304),
        bitrcFilterTbl(305),
        bitrcStaticTbl(306),
        bitmgMirror(307),
        bitifTbl(308),
        bitifTestTbl(309),
        bitrcChassisPort(310),
        bitrcRateLimitTbl(311),
        bitrcTengIfTbl(312),
        bitrcLinkFlapDetectGrp(313),
        bitifTblMlt(314),
        bitposIfTbl(315),
        bitpppBridgeConfigTbl(316),
        bitpppIpConfigTbl(317),
        bitpppLinkConfigTbl(318),
        bitpppLqrConfigTbl(319),
        bitrcPosLineConfigTbl(320),
        bitrcPosPppIpxTbl(321),
        bitrcPosSioCardConfigTbl(322),
        bitrcPosSonetTbl(323),
        bitatm1483ElanTbl(324),
        bitatmPortTbl(325),
        bitatmPvcTbl(326),
        bitrc2kAtm1483ElanTbl(327),
        bitrc2kAtmPortTbl(328),
        bitrc2kAtmPvcTbl(329),
        bitrc2kAtmSioCardConfigTbl(330),
        bitbrdgStp(331),
        bitbrdgStpPortTbl(332),
        bitrcStg(333),
        bitrcStgPortTbl(334),
        bitrcStgTbl(335),
        bitigmpInterfaceTbl(336),
        bitrcIgmpAccessTbl(337),
        bitrcIgmpInterfaceExtnTbl(338),
        bitrcIgmpSenderTbl(339),
        bitrcIgmpStaticTbl(340),
        bitipfFilterModifyDs(341),
        bitrc2kQosTrafficProfileTbl(342),
        bitrcIpFilterBaseListTbl(343),
        bitrcIpFilterGlobalListTbl(344),
        bitrcIpFilterMediaDevTbl(345),
        bitrcIpFilterMediaStreamTbl(346),
        bitrcIpFilterPortTbl(347),
        bitrcIpFilterTbl(348),
        bitrcIpMulticastSoftwareForwardingGrp(349),
        bitrcIpMulticastTimedPruneTbl(350),
        bitrcMltMcastDistributionGrp(351),
        bitipMRouteInterfaceTbl(352),
        bitdvmrpInterfaceTbl(353),
        bitpimCandidateRPTbl(354),
        bitpimGrp(355),
        bitpimInterfaceTbl(356),
        bitrcNtpGlobalGrp(357),
        bitrcNtpKeyTbl(358),
        bitrcNtpServerTbl(359),
        bitospfAreaAggregateTbl(360),
        bitospfAreaTbl(361),
        bitospfGeneralGrp(362),
        bitospfHostTbl(363),
        bitospfIfMetricTbl(364),
        bitospfIfTbl(365),
        bitospfNbrTbl(366),
        bitospfStubAreaTbl(367),
        bitospfVirtIfTbl(368),
        bitwfPgmGrp(369),
        bitwfPgmIfTbl(370),
        bitwfPgmSessionTbl(371),
        bitrcRadiusGlobalGrp(372),
        bitrcRadiusServerTbl(373),
        bitrcIpFlowTbl(374),
        bitrcIpConfDhcpTbl(375),
        bitrcIpDhcpForwardTbl(376),
        bitrcIpConfDvmrpTbl(377),
        bitrcIpDvmrpGrp(378),
        bitrcArpExtTbl(379),
        bitrcIpAddrTbl(380),
        bitrcIpConfGlobalGrp(381),
        bitrcIpConfIcmpRdiscTbl(382),
        bitrcIpConfTbl(383),
        bitrcIpMulticastArpTbl(384),
        bitrcIpRoutePrefTbl(385),
        bitrcRipExtTbl(386),
        bitrcIpConfOspfAreaAggregateTbl(387),
        bitrcIpConfOspfAreaTbl(388),
        bitrcIpConfOspfTbl(389),
        bitrcIpPimGlobalGrp(390),
        bitrcIpPimStaticRPTbl(391),
        bitrcIpPimTbl(392),
        bitrcIpRipInterfaceTbl(393),
        bitrcIpRouteTbl(394),
        bitrcIpStaticRouteTbl(395),
        bittcpConnTbl(396),
        bitrcIpUdpConfBroadcastIntfTbl(397),
        bitrcIpUdpPortFwdListTbl(398),
        bitrcIpUdpPortFwdTbl(399),
        bitrcIpUdpProtocolTbl(400),
        bitvrrpAssoIpAddrTbl(401),
        bitvrrpOperTbl(402),
        bitvrrpOperationsGrp(403),
        bitvrrpRouterStatsTbl(404),
        bitrcIpxAddrTbl(405),
        bitrcIpxBrouterTbl(406),
        bitrcIpxGrp(407),
        bitrcIpxPolicyListTbl(408),
        bitrcIpxPolicyNetTbl(409),
        bitrcIpxPolicyServTbl(410),
        bitrcIpxRipInFilterTbl(411),
        bitrcIpxRipInterfaceTbl(412),
        bitrcIpxRipOutFilterTbl(413),
        bitrcIpxSapInFilterTbl(414),
        bitrcIpxSapInterfaceTbl(415),
        bitrcIpxSapOutFilterTbl(416),
        bitvlanEncap(417),
        bitrcIpAsPathAccessListTbl(418),
        bitrcIpCommunityAccessListTbl(419),
        bitrcIpGenPolicyGrp(420),
        bitrcIpOspfInFilterTbl(421),
        bitrcIpPrefixListTbl(422),
        bitrcIpRedistributeTbl(423),
        bitrcIpRoutePolicyStrEnt(424),
        bitrcIpRoutePolicyTbl(425),
        bits5EnMsTopInfoGrp(426),
        bitbgpPeerTbl(427),
        bitrcIpBgpAggregateTbl(428),
        bitrcIpBgpConfederationGrp(429),
        bitrcIpBgpGeneralGrp(430),
        bitrcIpBgpNetworkTbl(431),
        bitrcIpBgpPeerGroupTbl(432),
        bitrcIpBgpPeerTbl(433),
        bitrcIpBgpRouteReflectorGrp(434),
        bitrcStatBgpGrp(435),
        bitrcStatBgpPeerTbl(436),
        bitrcSshGlobalGrp(437),
        bitrcDiagPcapAdvancedFilterTbl(438),
        bitrcDiagPcapFilterTbl(439),
        bitrcDiagPcapGrp(440),
        bitrcPortPcapTbl(441),
        bitrcArpExtEntDoProxy(442),
        bitrcIpConfGlobalRouteDiscovery(443),
        bitSuperNetEnable(444),
        bitospfCli(445),

        -- start: import from Yiyu's CLI changes 
        bitTreeCli(446),
        bitShowCmdCli(447),
        bitInfoCmdCli(448),
        bitrcIgmpChannelLimitTbl(449),
        bitrcIgmpSsmTbl(450),
        bitrcIgmpSsmGlobalGrp(451),
        bitrcIgmpIgapGlobalGrp(452),
        bitrcIgmpGlobalParamsGrp(453),
        bitrcRadiusGlobalSnmpGrp(454),
        bitrcSltPortTbl(455),
        bitrcErrorGrp(456),
        bitrcIgmpIgapServiceAbilityTbl(457),
        bitrcVlanDsapSsapTbl(458),
        bitrcIpArpCliClearPortCli(459),
        bitrcIpArpCliClearVlanCli(460),
        bitrcIpArpCliAddCli(461),
        bitrcIpArpCliDeleteCli(462),
        bitrcIpMulticastMacFloodingCliEnableCli(463),
        bitcliMacFlapTimeLimitSetCli(464),
        bitcliWriteRtcCli(465),
        bitipfCliClearStatsCli(466),
        bitipxCliDisableGnsCli(467),
        bitipxCliDisableRipCli(468),
        bitipxCliDisableRouteCli(469),
        bitipxCliDisableSapCli(470),
        bitipxCliRipSetDefDelayTimerCli(471),
        bitipxCliRipSetHoldMultiplierCli(472),
        bitipxCliRipSetDefIntervalTimerCli(473),
        bitipxCliEnableGnsCli(474),
        bitipxCliEnableRipCli(475),
        bitipxCliEnableSapCli(476),
        bitipxCliDisableRoute(477),
        bitipxCliEnableRouteCli(478),
        bitipxCliRipStateCli(479),
        bitipxCliRipSetDelayTimerCli(480),
        bitipxCliRipSetIntervalTimerCli(481),
        bitipxCliSapAddStaticEntryCli(482),
        bitipxCliSapDeleteStaticEntryCli(483),
        bitipxCliSapSetDefDelayTimerCli(484),
        bitipxCliSapSetDefHoldMultiplierCli(485),
        bitipxCliSapSetDefIntervalTimerCli(486),
        bitipxCliSapSetHoldMultiplierCli(487),
        bitipxCliSapSetGnsTieBreakerCli(488),
        bitipxCliSapStateCli(489),
        bitipxCliSapSetDelayTimerCli(490),
        bitipxCliSapSetIntervalTimerCli(491),
        bitipxCliAddRouteEntryCli(492),
        bitipxCliDeleteRouteEntryCli(493),
        bitipxCliSetMaxRouteCli(494),
        bitipxCliSetMaxSapCli(495),
        bitipxCliSetMaxStaticRouteCli(496),
        bitipxCliSetMaxStaticSapCli(497),
        bitipxCliSetNetBiosEnableDisableCli(498),
        bitipxCliSetLearnAfterIncrementEnableDisableCli(499),
        bitcliPasswordROCli(500),
        bitcliPasswordRWL1Cli(501),
        bitcliPasswordRWL2Cli(502),
        bitcliPasswordRWL3Cli(503),
        bitcliPasswordRWCli(504),
        bitcliPasswordRWACli(505),
        bitcliPasswordSLBOPERCli(506),
        bitcliPasswordL4OPERCli(507),
        bitcliPasswordOPERCli(508),
        bitcliPasswordSLBADMINCli(509),
        bitcliPasswordL4ADMINCli(510),
        bitcliPasswordSSLADMINCli(511),
        bitcliMonitorDurationCli(512),
        bitcliMonitorIntervalCli(513),
        bitcliDefaultBannerCli(514),
        bitcliDisplayMotdCli(515),
        bitcliDefaultLoginCli(516),
        bitcliDefaultPasswordCli(517),
        bitcliMoreCli(518),
        bitcliRloginLimitCli(519),
        bitcliScrsizeCli(520),
        bitcliTelnetLimitCli(521),
        bitcliTimeoutCli(522),
        bitlogCliHostCreateCli(523),
        bitlogCliSetTransferFileNameCli(524),
        bitlogCliHostDeleteCli(525),
        bitlogcliLevelCli(526),
        bitlogcliScreenCli(527),
        bitlogCliMsgOnPcmciaCli(528),
        bitcliAddTraceModuleCli(529),
        bitsetAutoTraceStatusCli(530),
        bitsetAutoTraceHighTrackDurationCli(531),
        bitsetAutoTraceLowPercentageCli(532),
        bitsetAutoTraceLowTrackDurationCli(533),
        bitcliRemTraceModuleCli(534),
        bitrcIpxCliPolicyTraceRipOutFilterAddCli(535),
        bitrcIpxCliPolicyTraceRipOutFilterDeleteCli(536),
        bitrcIpxCliPolicyTraceRipInFilterAddCli(537),
        bitrcIpxCliPolicyTraceRipInFilterDeleteCli(538),
        bitrcIpxCliPolicyTraceSapOutFilterAddCli(539),
        bitrcIpxCliPolicyTraceSapOutFilterDelete(540),
        bitrcIpxCliPolicyTraceSapInFilterAddCli(541),
        bitrcIpxCliPolicyTraceSapInFilterDeleteCli(542),
        bittracecliClearCli(543),
        bittracecliLevelCli(544),
        bittracecliOffCli(545),
        bittracecliFilterCli(546),
        bittracecliGrepStringCli(547),
        bittraceCliPolicyCli(548),
        bitdebugcliSlotXCli(549),
        bitripCliSetDefImportMetCli(550),
        bitripCliDisableCli(551),
        bitripCliDomainCli(552),
        bitripCliEnableCli(553),
        bitripCliSetIfDomainCli(554),
        bitripCliSetIfRxModeCli(555),
        bitripCliSetIfTxModeCli(556),
        bitripCliSetHoldDownCli(557),
        bitripCliReceiveCli(558),
        bitripCliSendCli(559),
        bitsysCliSetRmonAlarmCreateCli(560),
        bitsysCliSetRmonAlarmDeleteCli(561),
        bitsysCliSetRmonEventCreateCli(562),
        bitsysCliSetRmonEventDeleteCli(563),
        bitsysCliSetRmonHistoryCreateCli(564),
        bitsysCliSetRmonHistoryDeleteCli(565),
        bitsysCliSetRmonEtherCreateCli(566),
        bitsysCliSetRmonEtherDeleteCli(567),
        bitsysCliSetRmonEtherOwnerCli(568),
        bitcliStartAtmConsoleCli(569),
        bitrebootcliCli(570),
        bittoptreeCli(571),
        bitconvert11configCli(572),
        bitcopyimageCli(573),
        bitcwccliCli(574),
        bitshowdateCli(575),
        bitdirectoryCli(576),
        bitshowDumpAsicAddrCli(577),
        bitshowHwDumpAllCli(578),
        bitshowIcmpStatCli(579),
        bitshowInetStatCli(580),
        bitshowInspectCli(581),
        bitcliinstallCli(582),
        bitreloginCli(583),
        bitshowopDumpErrorRegsCli(584),
        bitshowOspfDumpAllCli(585),
        bitshowOspfDumpSpfInfoCli(586),
        bitpeercliCli(587),
        bitpingcliCli(588),
        bitipxCliPingCli(589),
        bitpwccliCli(590),
        bitshowrarDumpRegsCli(591),
        bitshowRarCheckStatsCli(592),
        bitshowRarErrorCountCli(593),
        bitshowrcDumpIfIndexCli(594),
        bitdeleteimageCli(595),
        bitresetcliCli(596),
        bitrlogincliCli(597),
        bitrshcliCli(598),
        bitsavecliCli(599),
        bitVxshellCli(600),
        bitclisourceCli(601),
        bitshowSpyReportCli(602),
        bitshowSwipDumpCli(603),
        bittelnetcliCli(604),
        bittracerouteCli(605),
        bitshowTaskTraceCli(606),
        bitrcIpRouteCliClearPortCli(607),
        bitrcIpRouteCliClearVlanCli(608),
        bitdumpcliArCli(609),
        bitmltCliClearIstStatsCli(610),
        bitportCliClearStatsCli(611),
        bitcliResetConsoleShellCli(612),
        bitcliKillTelnetSessionCli(613),
        bitatmCliClearVPortStatsCli(614),
        bitatmCliClearF5StatsCli(615),
        bitatmCliClearPortStatsCli(616),
        bitatmCliCardResetCli(617),
        bitatmCliEnableVPortStatsCli(618),
        bitatmCliSetDebugCli(619),
        bitatmCliVPortStatsIntervalCli(620),
        bitatmCliLaneCreateCli(621),
        bitatmCliLaneDeleteCli(622),
        bitatmCliStateCli(623),
        bitigmpOldCliDelAccessListCli(624),
        bitigmpOldCliSetAccessModeCli(625),
        bitposCliCardResetCli(626),
        bitposCliSetDebugCli(627),
        bitposCliSetPosConsoleCli(628),
        bitportCliSetLinktrapCli(629),
        bitportCliFlushIgmpCli(630),
        bitsysCliAccessEnableCli(631),
        bitvlanCliIeeeDiscardRecordAgingCli(632),
        bitvlanCliIeeeAgingDisableCli(633),
        bitvlanCliIeeeAgingEnableCli(634),
        bitsysCliSetSnmpForceTrapSenderCli(635),
        bitsysResetWebPasswdCli(636),
        bitsysResetSnmpCommStringsCli(637),
        bitsysCliSetMgmtVirtualIpCli(638),
        bitsysCliSetContactCli(639),
        bitsysCliSetHighPerformanceCli(640),
        bitsysCliSetLocationCli(641),
        bitsysCliSetMessageControlCli(642),
        bitsysCliSetChassisMTUCli(643),
        bitcliPromptCli(644),
        bitsysCliSetOctapidResetThresholdCli(645),
        bitsysCliSetSmltPortUnlockTimeoutCli(646),
        bitsysCliSetUdpSourceCli(647),
        bitvlanCliFlushIeeeVlanDiscardRecordsCli(648),
        bitposCliSetLEDCli(649),
        bitvlanCliRipManualTrigCli(650),
        bitvlanCliChangeIpxEncapCli(651),
        bitvlanCliSetFdbTimeOutCli(652),
        bitvlanCliSyncFdbCli(653),
        bitportCliRipManualTrigCli(654),
        bitportCliSetCpLimitCli(655),
        bitportCliSetClockSourceCli(656),
        bitportCliSetFlowControlCli(657),
        bitportCliSetFlowControlPause0Cli(658),
        bitportCliSetFlowControlPauseTimeCli(659),
        bitportCliSetSffdCli(660),
        bitsetMgmtIpCli(661),
        bitsetWsmAutoResetCli(662),
        bitreadWSMCommunityCli(663),
        bitwriteWSMCommunityCli(664),
        bittrapWSMCommunityCli(665),
        bitauthTrapWSMCli(666),
        bitlinkTrapWSMCli(667),
        bittelnetWsmCli(668),
        bitsyslogFacilityCli(669),
        bitwsmResetCli(670),
        bitwsmSaveCli(671),
        bitwsmBootChoiceCli(672),
        bitwsmDumpCardDBCli(673),
        bitwsmDumpIPTableCli(674),
        bitwsmDumpTableCli(675),
        bithiddenModeCli(676),
        bitresetSamCli(677),
        bitsamBootBackupCli(678),
        bitsamShowClusterCli(679),
        bitoldieCli(680),
        bitipCliSetBgpRedistApplyCli(681),
        bitrcBgpPeerCli(682),
        bitCliConfigIpBgpMaxInitPeersCli(683),
        bitCliConfigIpBgpMaxTxQueueLenCli(684),
        bitCliConfigIpBgpDebugScreenCli(685),
        bitpolicySetOspfAcceptPrecedenceCli(686),
        bitpolicySetOspfAnnouncePrecedenceCli(687),
        bitpolicySetRipAcceptPrecedenceCli(688),
        bitpolicySetRipAcceptRipIfListCli(689),
        bitpolicySetRipAnnounceOutIfListCli(690),
        bitpolicySetRipAnnouncePrecedenceCli(691),
        bitpolicyRipAnnounceRemoveFromRtSrcCli(692),
        bitospfCliModRangeEffectCli(693),
        bitospfCliModRangeMetricCli(694),
        bitospfCliSetVirtIfMd5KeyTxCli(695),
        bitospfCliSetIfMd5KeyCli(696),
        bitospfCliSetMd5KeyTxCli(697),
        bitospfCliDelIfMd5KeyCli(698),
        bitipCliSetOspfAcceptApplyCli(699),
        bitospfCliSetDefMetricGrpCli(700),
        bitospfCliSetSpfHoldDownTimeCli(701),
        bitospfCliSetSpfRunCli(702),
        bitospfCliSetTrapCli(703),
        bitrcIpVrrpCliClearPortCli(704),
        bitrcIpVrrpCliClearVlanCli(705),
        bitrcIpResourceUsageGlobalGrp(706),
        bitrcIpPimInterfaceTbl(707),
        bitipmcCliSetDvmGlobDisCli(708),
        bitipmcCliSetDvmGlobEnlCli(709),
        bitipmcCliSetDvmGlobLeafTimeoutCli(710),
        bitipmcCliSetDvmGlobNbrTimeoutCli(711),
        bitipmcCliSetDvmGlobNbrProbeIntCli(712),
        bitipmcCliSetDvmGlobTrigUpdateIntervalCli(713),
        bitipmcCliSetDvmGlobUpdateIntervalCli(714),
        bitipmcCliSetDvmGlobFwdCacheTimeoutCli(715),
        bitipmcCliSetDvmGlobRouteExpireTimeoutCli(716),
        bitipmcCliSetDvmGlobRouteDiscTimeoutCli(717),
        bitipmcCliSetDvmGlobRouteSwitchTimeoutCli(718),
        bitipmcCliSetDvmGlobShowNextHopTableCli(719),
        bitipCliSetPimdebugAssertCli(720),
        bitipCliSetPimdebugBootstrapCli(721),
        bitipCliSetPimdebugGroupCli(722),
        bitipCliSetPimdebugHelloCli(723),
        bitipCliSetPimdebugJoinpruneCli(724),
        bitipCliSetPimDbgTraceCli(725),
        bitipCliSetPimDbgLogCli(726),
        bitipCliSetPimdebugRegisterCli(727),
        bitipCliSetPimdebugRegStopCli(728),
        bitipCliSetPimdebugRpadvCli(729),
        bitipCliSetPimdebugSendCli(730),
        bitipCliSetPimdebugRcvCli(731),
        bitipClienabletraceforSGentryCli(732),
        bitipClidisabletraceforSGentryCli(733),
        bitipCliSetPimGlobBrDisCli(734),
        bitipCliSetPimGlobBrEnlCli(735),
        bitportCliSetPimIfCreateCli(736),
        bitportCliSetPimIfTypeCli(737),
        bitdiagCliPingSnoopAddPortsCli(738),
        bitdiagCliPingSnoopCreateCli(739),
        bitdiagCliPingSnoopDeleteCli(740),
        bitdiagCliPingSnoopEnaDisCli(741),
        bitdiagCliPingSnoopRemPortsCli(742),
        bitrcIpBgpPeerCli(743),
        bitospfCliSetVirtIfMd5KeyCli(744),
        bitospfCliDelVirtIfMd5KeyCli(745),
        bitipSetOspfRedistApplyCli(746),
        bitospfSetAutoVlinkCli(747),
        bitospfSetTrapCli(748),
        bitipSetPimdebugSourceCli(749),
        bitportCliSetLoopDetectCli(750),
        bitlogcliClearCli(751),
        bitlogcliWriteCli(752),
        bitsetAutoTraceHighPercentageCli(753),
        bittracecliScreenCli(754),
        bitripCliCliSetIfRxModeCli(755),
        bitripSetIfTxModeCli(756),
        bitripUpdateCli(757),
        bitsysCliSetSendTrapConfigCli(758),
        bitclilsCli(759),
        bitclimkdirCli(760),
        bittelnetSamCli(761),
        bitsysCliV3UserSetCli(762),
        bitsysCliV3GrpSetCli(763),
        bitsysCliV3AccessSetCli(764),
        bitsysCliV3NotifySetCli(765),
        bitsysCliV3ViewSetCli(766),
        bitsysCliV3TargetSetCli(767),
        bitsysCliV3TargetParamsSetCli(768),
        bitsnmpCliViewSetCli(769),
        bitBcli8100Cli(770),
        bitBcliAgentHacpuCli(771),
        bitBcliAttribCli(772),
        bitBcliAutobootCli(773),
        bitBcliAutonegotiateCli(774),
        bitBcliBaudCli(775),
        bitBcliBootCli(776),
        bitBcliBootpCli(777),
        bitBcliCdCli(778),
        bitBcliCfgfileCli(779),
        bitBcliCopyCli(780),
        bitBcliCpCli(781),
        bitBcliCwcCli(782),
        bitBcliDatabitsCli(783),
        bitBcliDcdebugCli(784),
        bitBcliDebugcfgCli(785),
        bitBcliDebugmodeCli(786),
        bitBcliDelayCli(787),
        bitBcliWlandesiredssidCli(788),
        bitBcliDirCli(789),
        bitBcliDosChkdskCli(790),
        bitBcliDosFormatCli(791),
        bitBcliDstCli(792),
        bitBcliDstendCli(793),
        bitBcliDstnameCli(794),
        bitBcliDstoffCli(795),
        bitBcliDststartCli(796),
        bitBcliDumpspromCli(797),
        bitBcliEditCli(798),
        bitBcliEgressloopCli(799),
        bitBcliFactorydefaultsCli(800),
        bitBcliFmmdebugCli(801),
        bitBcliFmmFormatCli(802),
        bitBcliFtpdCli(803),
        bitBcliFtpdebugCli(804),
        bitBcliFullduplexCli(805),
        bitBcliGrepCli(806),
        bitBcliHacpuCli(807),
        bitBcliI2cdebugCli(808),
        bitBcliImagefileCli(809),
        bitBcliLsCli(810),
        bitBcliMasterCli(811),
        bitBcliMcpCli(812),
        bitBcliMfgburninCli(813),
        bitBcliMfgdCli(814),
        bitBcliMfgledCli(815),
        bitBcliMfgmCli(816),
        bitBcliMgmtrouteCli(817),
        bitBcliMkdirCli(818),
        bitBcliMnetipCli(819),
        bitBcliMoreCli(820),
        bitBcliMoreflagCli(821),
        bitBcliMulticastCli(822),
        bitBcliMvCli(823),
        bitBcliNetenableCli(824),
        bitBcliNetipCli(825),
        bitBcliNetrestartCli(826),
        bitBcliNetspeedCli(827),
        bitBcliPcdebugCli(828),
        bitBcliPclogCli(829),
        bitBcliPctraceCli(830),
        bitBcliPeerCli(831),
        bitBcliPingCli(832),
        bitBcliProgrambootCli(833),
        bitBcliPromptCli(834),
        bitBcliPwcCli(835),
        bitBcliPwdCli(836),
        bitBcliRarudipsvCli(837),
        bitBcliRarudrecCli(838),
        bitBcliReadspromCli(839),
        bitBcliRebootonerrorCli(840),
        bitBcliResetCli(841),
        bitBcliResetPasswordCli(842),
        bitBcliRloginCli(843),
        bitBcliRlogindCli(844),
        bitBcliRloginlimitCli(845),
        bitBcliRmCli(846),
        bitBcliRshCli(847),
        bitBcliSaveCli(848),
        bitBcliSavetostandbyCli(849),
        bitBcliScrsizeCli(850),
-- 851 is a duplicate and should not be used anymore
        bitBcliSetbootpimagenameCli(851),
        bitBcliSioenableCli(852),
        bitBcliSiomodeCli(853),
        bitBcliSiomtuCli(854),
        bitBcliSiomyipCli(855),
        bitBcliSiopeeripCli(856),
        bitBcliSiopppfileCli(857),
        bitBcliSiorestartCli(858),
        bitBcliSioslipcomCli(859),
        bitBcliSiosliprxcomCli(860),
        bitBcliSnmpdCli(861),
        bitBcliSourceCli(862),
        bitBcliSshdCli(863),
        bitBcliTelnetCli(864),
        bitBcliTelnetdCli(865),
        bitBcliTelnetlimitCli(866),
        bitBcliTestCli(867),
        bitBcliTestspromCli(868),
        bitBcliTftpdCli(869),
        bitBcliTftpdebugCli(870),
        bitBcliTftphashCli(871),
        bitBcliTftphostCli(872),
        bitBcliTftprexmitCli(873),
        bitBcliTftptimeoutCli(874),
        bitBcliTimeoutCli(875),
        bitBcliTupleCli(876),
        bitBcliTzCli(877),
        bitBcliTzoffCli(878),
        bitBcliUpdatebootCli(879),
        bitBcliVerifycfgCli(880),
        bitBcliVxataCli(881),
        bitBcliVxdcCli(882),
        bitBcliVxdosCli(883),
        bitBcliVxinetCli(884),
        bitBcliVxiosCli(885),
        bitBcliVxmemCli(886),
        bitBcliVxpasswordCli(887),
        bitBcliVxpppCli(888),
        bitBcliVxtiCli(889),
        bitBcliVxuserCli(890),
        bitBcliWdtCli(891),
        bitBcliWlanCli(892),
        bitBcliWlanconfigureCli(893),
        bitBcliWriteRtcCli(894),
        bitBcliWritespromCli(895),
-- 896 is a duplicate and should not be used anymore
        bitBootPCliSetImageNameCli(896),
        bitBootPCliSettingCli(897),
        bitExitTreeCli(898),
        bitMacUpgradeCli(899),
        bitPcmciaStopCli(900),
        bitBcliPrivilegeCli(901),
        bitBcliReadRtcCli(902),
        bitShowHelpCli(903),
        bitShowHistoryCli(904),
        bitOpTreeCli(905),
        bitUpOneTreeCli(906),
        bitBcliHiSecureFlagCli(907),
        bitBoxCli(908),
        bitBcliBlockSwitchOverCli(909),
        bitBcliCtrlRecOptimizeCli(910),
        bitBcliLogParmsCli(911),
        bitPasswordAgeCli(912),
        bitLicenseLoadCli(913),
        bitportCliUnknownMacDiscAddAllowMacCli(914),
-- 915 is a duplicate and should not be used anymore
        bitBootpCliSetImageNameCli(915),
        bitdot3adAggTbl(916),
        bitdot3adAggPortTbl(917),
        bitrcLacpGlobalGrp(918),
        bitrcPortLacpTbl(919),
        bitrcPortVLacpTbl(920),
        bitdot1xPaeSystemGrp(921),
        bitdot1xAuthConfigTbl(922),
        bitdot1xPaePortTbl(923),
        bitdot3adrcPortLacpTbl(924),
        bitrcPortRemoteMirroringTbl(925),
        bitrcIpRsmltCli(926),
        bitsysCliV3NotifyFilterSetCli(927),
        bitsysCliV3NotifyProfileSetCli(928),
        bitsysCliSetSnmpServerCli(929),
        bitrcIpConfRsmltTbl(930),
        bitrcIpxRsmltOperTbl(931),
        bitcliLogCli(932),
        bitipmcCliSetDvmGlobTrapEnlCli(933),
        bitipmcCliSetDvmGlobLogEnlCli(934),
        bitDismanPingTraceroute (935),
        bitBcliTxQueueCli(936),
        bitCliSet10GbDetailCli(937),
        bitbootpCliSetCommandCli(938),
        bittracecliModIdListCli(939),
        bitpoeCliSetPortPowerAdminCli(940),
        bitpoeCliSetPortPowerPriorityCli(941),
        bitpoeCliSetPortPowerLimitCli(942),
        bitpoeCliSetPortPowerDetectionControlCli(943),
        bitpoeCliSetPortTypeCli(944),
        bitpoeCliSetCardPowerAdminCli(945),
        bitpoeCliSetCardPowerLimitCli(946),
        bitpoeCliSetCardPowerPriorityCli(947),
        bitpoeCliSetCardPowerUsageThresholdCli(948),
        bitpoeCliSetCardNotificationControlCli(949),
        bitpoeCliSetCardPortPowerOnOffNotificationCli(950),
        bitpoeCliSetCardPortPowerMaintenanceStatusNotificationCli(951),
        bitpoeCliSetCardPowerBackupActivatedNotificationCli(952),
        bitpoeCliSetCardPowerUsageOnNotificationCli(953),
        bitpoeCliSetCardPowerUsageOffNotificationCli(954),
        bitpoeCliSetCardFwUpgradeCli(955),
        bitpoeCliSetSystemRedundantPowerControlCli(956),
        bittrCardCliSetTrLevelCli(957),
        bitBcliNncli(958),
        bitipSetPimdebugGraftCli(959),
        bitrcQosTxQueueTbl(960),
        bitrcQos8021pToTrafficClassMapTbl(961),
        bitrcQos8021pToDropPrecedenceMapTbl(962),
        bitrcQosTrafficClassTo8021pMapTbl(963),
        bitrcQosDscpToCosPolicedMapTbl(964),
        bitrcQosTrafficClassTo8021pPolicedMapTbl(965),
        bitrcQosPolicyTbl(966),
        bitrcQosEgressCounterTbl(967),
        bitBcliJumboFrame(968),
        bitigmpOldCliCr8AccessListCli(969),
        bitportVctResultTbl(970),
        bitrcQosPolicyStatsTbl(971),
        bitrcMstpTbl(972),
        bitrcRstpTbl(973),
        bitNaapCli(974),
        bitBcliAltLedEnableCli(975),
        bitBcliBackupCfgfileCli(976),
        bitrcBridgeFdbProtectTbl(977),
        bitrcSysDnsServer(978),
        bitBcli8616ReAutonegCli(979),
        bitBcliBootpImageNameSetCli(980),
        bitBcliMezzImageNameSetCli(981),
        bitBcliMacUpgradeCli(982),
        bitLoadConfigCli(983),
        bitBcliBootpImageNameInfo(984),
        bitospfCliSetRfc1583CompatibilityCli(985),
        bitShExecuteCli(986),
        bitsysCliSetHighThroughputModeCli(987),
        bitsysCliSetUdpChecksumCli(988),
        bitBcliMaintCommand(989),
        bitExtCpLimit(990),
-- shell commands
        bitDumpCircuitcli(991),
        bitcppStatscli(992),
        bitfbuffDumpcli(993),
        bitmemShowcli(994),
        bitcheckStackcli(995),
        bitrcDumpSnmpcli(996),
        bitppeGetPortIsLinkUpcli(997),
        bitshowPpcli(998),
        bitdumpFacli(999),
        bitsfDumpcli(1000),
        bitppDumpcli(1001),
        bitgHalCurrArpcli(1002),
        bitaclDumpcli(1003),
-- end shell commands
        bitlogFilterAdd(1004),
        bitlogFilterDelete(1005),
        bitBcliNocheckSwVersionCli(1006),
        bitForeachCli(1007),
        bitTiCli(1008),
        bitPpBdgPortcli(1009),
        bitLldpGlobalConfigTbl(1010),
        bitLldpPortConfigTbl(1011),
        bitpimVirtualNbrTbl(1012),
        bitpimVirtualNbrAdd(1013),
        bitpimVirtualNbrDelete(1014),
        bitcliPasswordLockoutCli(1015),
        bitcliPasswordHistoryCli(1016),
        bitcliPasswordDefLockoutCli(1017),
        bitospfSetRfc1583CompatibilityCli(1018),
        bitAutoRecoverSet(1019),
        bitAccessLevelEnDisCli(1020),
        bitrcTacacsGlobalGrp(1021),
        bitrcTacacsServerTbl(1022),
        bitPortCliSetSpoofDetectCli(1023),
        bitBcliMd5Cli(1024),
        bitBcliDumpfhCli(1025),
        bitipmcCliSetDvmGlobPruneResendCli(1026),
        bitBcliMezzCardBootEnableCli(1027),
        bitpoeCliSetCardPdDetectTypeCli(1028),
        bitPasswordLenCli(1029),
        bitBcliCheckSrcRouteCli(1030),
        bitdiagCliPingSnoopCli(1031),
        bitrcFilterActPatternTbl(1032),
        bitrcFilterActTbl(1033),
        bitrcFilterAcePatternTbl(1034),
        bitrcFilterAceComnTbl(1035),
        bitrcFilterAceEthTbl(1036),
        bitrcFilterAceIpTbl(1037),
        bitrcFilterAclTbl(1038),
        bitrcFilterAcgTbl(1039),
        bitrcFilterAcgIfTbl(1040),
        bitlldpGlobalConfigTbl(1041),
        bitlldpPortConfigTbl(1042),
        bitnsnaScalarsGrp(1043),
        bitnsnaNsnasTbl(1044),
        bitnsnaPortTbl(1045),
        bitnsnaVlanTbl(1046),
        bitnsnaIpPhoneSignatureTbl(1047),
        bitnsnaClientTbl(1048),
        bitnsnaStaticClientTbl(1049),
	bitrcCfmTrunkTbl(1050),
	bitrcCfmServiceGroupTbl(1051),
	bitrcCfmPbtGrp(1052),
	bitrcCfmGlobalsGrp(1053),
	bitrcOeAdmPEEdgeObjectsGrp(1054),
	bitrcIsisCircuitTbl(1055),
	bitisisCircTbl(1056),
	bitisisCircLevelTbl(1057),
	bitisisManAreaAddrTbl(1058),
	bitisisSummAddrTbl(1059),
	bitrcIsisGlobalGrp(1060),
	bitisisSysObjectGrp(1061),
	bitisisSysLevelTbl(1062),
	bitipCliSetIsisRedistApply(1063),
	bitesmCliClearStatsCli(1064),
	bitvlacpCliClearStatsCli(1065),
	bituniCliClearIpServiceStatsCli(1066),
	bitisidCliClearStatsCli(1067),
	bitipServiceCliClearStatsCli(1068),
	bitringCliClearStatsCli(1069),
	bitringCliSetDebugCli(1070),
	bitstandaloneCliSetDebugCli(1071),
	bittdcCliClearStatsCli(1072),
	bittdcCliClearHistoryCli(1073),
	bitmepCliClearStatsCli(1074),
	bittlsCliSetDebugCli(1075),
	bitisisCliClearStatsCli(1076),
	bitrcMltVlacpTbl(1077),
	bitrcTlsGlobalsGrp(1078),
	bitesmShellCli(1079),
	bitesmUpgradeCli(1080),
	bitesmResetCli(1081),
	bitesmGetInfoCli(1082),
	bitBcliSetLoadEsmImage(1083),
	bitBcliSetUnknownMacDiscard(1084),
	bitrcMltBvidPortTbl(1085),
	bitrcRingModuleTbl(1086),
	bitpwTbl(1087),
	bitrcPwEndptTbl(1088),
	bitpwCliClearStatsCli(1089),
	bitrcVlanPortCfmMepTbl(1090),
	bitLbmCmdCli(1091),
	bitLtmCmdCli(1092),
	bitrcCfmRemoteMaintenanceEndPointTbl(1093),
	bitrcCfmMaintenanceIntermediatePointTbl(1094),
	bitrcVlanPortCfmMipTbl(1095),
	bitrcIsidEndptCvidClientMepTbl(1096),
	bitrcPwEndptCvidClientMepTbl(1097),
	bitmipCliClearStatsCli(1098),
	bitrcOpmPortTbl(1099),
	bitrcCosProfileTbl(1100),
	bitrcTlsRemoteUniMacTbl(1111),
	bitrcTlsTdiUserMacTbl(1112),
	bitrcTlsUniTbl(1113),
	bitrcTlsTdiTbl(1114),
	bitrcTlsTdiEndptTbl(1115),
	bitrcIsidEndptTbl(1116),
	bitrcIsidTbl(1117),
	bitrcTlsIpServiceTbl(1118),
	bitrcTlsUniIpServiceTbl(1119),
	bitrcBanRingTbl(1120),
	bitrcBanDhRingTbl(1121),
	bitrcBanRingSaRbsTbl(1122),
	bitrcTlsTestTdcTbl(1123),
	bitrcRepeaterTbl(1124),
	bitrcCfmMaintenanceDomainTbl(1125),
	bitrcCfmMaintenanceAssociationTbl(1126),
	bitrcCfmMaintenanceEndPointTbl(1127),
	bitrcCfmTrunkGroupTbl(1128),
	bitBcliLicensefileCli(1129), 
	bitrcCfmFlrTbl(1130),
        bitrcCfmFdTbl(1131),
        bitrcCfmPmTbl(1132),
        bitrcSysExtendedPingBypassGrp(1133),
	bitrc2kQosEgressGreenColorQosToTagTbl(1134),
	bitrc2kQosEgressYellowColorQosToTagTbl(1135),
	bitrc2kQosEgressRedColorQosToTagTbl(1136),
	bitrc2kQosWredThresholdHighDropTable(1137),
	bitrc2kQosWredThresholdMediumDropTable(1138),
	bitrc2kQosWredThresholdLowDropTable(1139),
	bitrcPrQosSubportProfileTable(1140),
	bitrcPrQosSubportProfileQueueTable(1141),
	bitrcPrQosSubportQueueSetTemplateTable(1142),
	bitrcPrQosIsidRateLimitsTable(1143),
	bitrcIsidNniRateLimiterTable(1144),
	bitrc2kChassisGrp(1145),
	bitrmepCliClearStatsCli(1146),
        bitrcCsuTimerInterval(1147),
	bitBcliBootpSecImageNameSetCli(1148),
        bitrcMplsNotificationObjectsGrp(1149),
        bitmplsLsrObjectsGrp(1150),
        bitmplsTeObjectsGrp(1151),
        bitmplsTunnelHopTbl(1152),
        bitmplsTunnelTbl(1153),
        bitmplsTunnelResourceTbl(1154),
        bitrcMplsIpStaticFecTbl(1155),
        bitmplsClearLspLdpRsvpStats(1156),
        bitrcIpVpnRouteDistTbl(1157),
        bitrcIpVpnRouteTargetTbl(1158),
        bitrcVrfIpVpnTbl(1159),
        bitrcIpBgpPeerTblIpvpnLiteCap(1160),
        bitrcIpBgpPeerTblVpnv4Address(1161),
        bitmplspingcli(1162),
        bitrcRingTable(1163),
	bitrcPlsbGlobalGrp(1164),
        bitrcIsisPlsbTbl(1165),
        bitrcIsisCircuitPlsbTbl(1166),
        bitrcQosDECoding(1167),
        bitrcIsidEndptCvidClientMipTbl(1168),
        bitisisCliClearLsdbCli(1169),
        bitrcL2cpMacTbl(1170),
        bitrcL2cpProfileTbl(1171),
        bitrcL2cpProfileRuleTbl(1172),
        bitrcDHUniTbl(1173),
        bitrcDHUniClearRctStatsCli(1174),
	bitL2PingCmdCli(1175),
	bitL2TraceCmdCli(1176),
	bitL2TraceReplyCmdCli(1177),
	bitDebugL2vpnCmdCli(1178),
	bitDebugIsisCmdCli(1179),
        bitrcCfmTransmitL2TraceTbl(1180),	
        bitrcCfmTransmitL2McastTraceTbl(1181),
	bitrcCfmTransmitLbmTbl(1182),
	bitrcCfmTransmitLtmTbl(1183),
        bitrcMACSecIfConfigTbl(1184),
        bitrcMACSecCATbl(1185),
        bitsecyIfTbl(1186),
	bitrcIsisGlobalIpTunnelSrcAddr(1187),
        bitrcIsisLogicalInterfaceTbl(1188),
	bitrcDvrGlobalGrp(1189),
        bitrcVxlanVtepSourceIp (1190),
	bitrcVrfScalingGlobalGrp (1191),
-- CardType bit number start here
        bitcardType(1536),
        bitrc2kCPU(1537),
        bitrc2k48x100BaseTX(1538),
        bitrc2k24x100BaseTX(1539),
        bitrc2k24x100BaseFX(1540),
        bitrc2k2xOC12(1541),
        bitrc2k8xATM(1542),
        bitrc2kRMON(1543),
        bitrc2k8x1000BaseSXBB(1544),
        bitrc2k8x1000BaseLXBB(1545),
        bitrc2k8x1000BaseSXRBB(1546),
        bitrc2k8x1000BaseLXRBB(1547),
        bitrc2k8x1000BaseXDBB(1548),
        bitrc2k8xOC3(1549),
        bitrc2kMg32x100BaseTX(1550),
        bitrc2kMg48x100BaseTX(1551),
        bitrc2kMg16x100BaseFX(1552),
        bitrc2kMg8x1000BaseIC(1553),
        bitrc2k8x1000BaseIC(1554),
        bitrc2kMg48x100BaseTC(1555),
        bitrc2k6xPOS(1556),
        bitrc2k16x1000BaseSXBB(1557),
        bitrc2k8x1000BaseT(1558),
        bitrc2k32x100BaseTX(1559),
        bitrc2k1x10GBaseLW(1560),
        bitrc2k16x1000BaseT(1561),
        bitrc2k1x10GBaseLR(1562),
        bitrc2kAlteonWSM(1563),
        bitrc2k48x100BaseTXM(1564),
        bitrc2k32x100BaseTXM(1565),
        bitrc2k8x1000BaseICM(1566),
        bitrc2k8x1000BaseSXBBM(1567),
        bitrc2k8x1000BaseTM(1568),
        bitrc2k8xATMM(1569),
        bitrc2k6xPOSM(1570),
-- 1571 - 1578 available now (use to be Thunderbolt)
        bitrc2kPP8300-CPU8x1000BaseSFP(1579),
        bitrc2kPP8300-24x1000BaseTX(1580),
        bitrc2kPP8300-48x100BaseTX(1581),
        bitrc2kPP8300-48x100BaseTXPOE(1582),
        bitrc2kAlteonLP(1583),
        bitrc2kAlteonASFM(1584),
        bitrc2k61AlteonSAM(1585),
        bitrc2k62AlteonSAM(1586),
        bitrc2kPP8300-24x100BaseFX(1587),
        bitrc2kPP8300-48x1000BaseTX-4B(1588),
        bitrc2kPP8300-48x1000BaseTXPOE-4B(1589),
        bitrc2kPP8300-48x1000BaseSFP-2B(1590),
        bitrc2kPP8300-CPU2x10GBaseXFP(1591),
        bitrc2kPP8300-8x10GBaseXFP-4B(1592),
        bitrcLldpTbl(1599),
	bitrcSmltTbl(1600),
        bitslppCli(1601),
        bitnlbsCli(1602),
        bitrcMplsGlobalGrp(1603),
        bitrcIpMplsInterfaceTbl(1604),
        bitrcVrfConfigTbl(1605),
        bitrcVrfIfConfigTbl(1606),
        bitrcIpv6InterfaceTbl(1607),
        bitrcIpv6AddrTbl(1608),
        bitrcIpv6PrefixTbl(1609),
        bitrcIpv6RouterAdvertTbl(1610),
        bitrcIpv6StaticRouteTbl(1611),
        bitrcIpv6NetToPhysicalTbl(1612),
        bitrcIpv6Scalars(1613),
        bitrcPrFilterAceIpv6SrcAddrTbl(1614),
        bitrcPrFilterAceIpv6DstAddrTbl(1615),
        bitrcPrFilterAceIpv6NextHdr(1616),
        bitrc2kCpuEthernetPortIpv6RouteTbl(1617),
        bitrcIpv6PimGlobalGrp(1618),
        bitrcIpv6PimTbl(1619),
        bitrcIpv6PimStaticRPTbl(1620),
        bitrcIpv6pimVirtualNbrTbl(1621),
        bitrcIpv6MulticastTimedPruneTbl(1622),
        bitrcIpv6MulticastSoftwareForwarding(1623),
        bitrcIpv6PimInterfaceTbl(1624),
        bitrcIpv6MltMcastDistributionGrp(1625),
        bitrcIpv6ResourceUsageGlobalGrp(1626),
        bitIpv6InterfaceTbl(1627),
        bitIpv6RouteTbl(1628),
        bitIpv6NetToMediaTbl(1629),
        bitIpv6MIBObjects(1630),
        bittunnelIfTbl(1631),
        bittunnelInetConfigTbl(1632),
        bitmldInterfaceTbl(1633),
        bitmldCacheTbl(1634),
        bitrcIpv6Ospfv3NbmaNbrTbl(1635),
        bitrcIpv6Ospfv3IfTbl(1636),
        bitrcIpv6Ospfv3VirtIf(1637),
        bitrcIpv6Ospfv3AreaAggregateTbl(1638),
        bitrcIpv6Ospfv3AreaTbl(1639),
        bitrcIpv6Ospfv3GeneralGrp(1640),
        bitrc2kPR48X1000BaseTX (1641),
        bitrc2kPR30X1000BaseSXBB (1642),
        bitrc2kPR3X10GBaseXZW (1643),
        bitrc2kPR3X10GBaseGbic (1644),
        bitrcIpfixConfGlobalGrp (1645),
        bitrcIpfixConfSlotTbl (1646),
        bitrcIpfixCollectorTbl(1647),
        bitrcIpfixConfPortTbl(1648),
        bitrcIpfixHashStatsTbl(1649),
        bitrcIpfixExporterStatsTbl(1650),
        bitrcQosTrafficClassToDscpPolicedMapTbl(1651),
        bitrcQosPolicyRemarkDp(1652),
        bitrc2k8x1000BaseOPM(1653),
	bitTreeSnmp(1654),
        bitInfoCmdSnmp(1655),
        bitShowCmdSnmp(1656),
        bitsnmpLogSnmp(1657),
	bitrc2kPR48x1000BaseGBRS(1658),
        bitrc2kPR48x1000BaseGTRS(1659),
        bitrc2kPR12X10GBaseXLRS(1660),
        bitrc2kPR34xXGRS(1661),
	bitrcPrQosEgressQosToExpTbl(1662),
	bitrcPrQosIngressExpToQosTbl(1663),    
	bitrcPomConfGlobalGrp(1664),
        bitportCliSetMTUCli(1665),
        bitsysCliSetSingleMgmtIpCli(1666),
        bitBcliAutoassignipCli(1667),
        bitrc2kPR48x1000BaseGXRS(1668),
        bitrc2kPR30x1000BaseGBRS(1669),
        bitrc2kPR6X10GBaseXLRS(1670),
	bitrc2kPR26xXGRS(1671),
        bitrcIpv6DhcpForwardTbl(1672),
        bitrcIpv6ConfDhcpTbl(1673),
        bitrcIpv6VrrpOperTbl(1674),
        bitrcVrrpExtScalarsGrp(1675),
        bitrcVrrpTmpOperationsGrp(1676),
        bitrcIpMulticastSquareSmltGrp(1677), 
        bitrcIpv6RsmltOperTbl(1678),
        bitrc2kCPURed(1679),
	bitrc2kPRE48x1000BaseGB(1680),
        bitrc2kPRE48x1000BaseGT(1681),
        bitrc2kPRE12X10GBaseXL(1682),
        bitrc2kPRE34xXG(1683),
        bitrcPortLosslessEnetTbl(1684),
        bitrcPrFilterAceIpv6TrafficClsTbl(1685),
	bitrcIsisPlsbIpShortcut(1686),
        bitrcIpIsisInFilter(1687),
        bitrcIpIsisInFilterDefault(1688),
        bitrcVirtualServiceTbl(1689),
	bitcbAUX(1700),
	bitcbSF3200(1701),
	bitcbSF9600(1702),
	bitcbCPCSC(1703),
	bitcb48x1000BaseTX(1704),
	bitcb48x1000BaseTXPOE(1705),
	bitcb48x1000SFP(1706),
	bitcb24x10GBaseSFP(1707),
	bitcb48x10GBaseSFP(1708),
        bitrcIpConfBfdTbl(1709),
        bitrcIpBfdGeneralGrp(1710),
        bitbasicrcIpBgpPeerTbl(1711),	
        bitbasicbgpPeerTbl(1712),
        bitbasicrcIpBgpGeneralGrp(1713),
        bitbasicrcIpBgpAggregateTbl(1714),
        bitbasicrcIpBgpConfederationGrp(1715),
        bitbasicrcIpBgpRouteReflectorGrp(1716),
        bitbasicrcStatBgpGrp(1717),
        bitbasicrcStatBgpPeerTbl(1718),
        bitbasicrcIpBgpPeerGroupTbl(1719),
        bitbasicrcIpBgpNetworkTbl(1720),
        bitrcIpRedistributeTblIsis(1721),
        bitcliPasswordRuleCli(1722),
        bitcliPasswordChangeIntervalCli(1723),
        bitcliPasswordPreNotifyCli(1724),
        bitcliPasswordPostNotifyCli(1725),
        bitrc2kPR12X10GBaseXLRSJ(1726),
	bitcliPasswordPostExpiryLogins(1727),
	bitrc2kPRE12X10GBaseXLJ(1728),
	bitrofLoadBoard(1729),
	bitvsp4k4850GTS(1730),
        bitvsp4k4850GTSPWRPLUS(1731),
	bitcbSF9610(1732),
	bitrof48x1000SFP(1733),
	bitrof16x10GBaseSFP(1734),
	bitrof48x10GBaseSFP(1735),
	bitrof4x40GBaseSFP(1736),
	bitrof12x40GBaseSFP(1737),
        bitvsp4k4450GSXPWRPLUS(1738),
	bitvsp8k8242XSQ(1739),
	bitvsp4k4450GTXHTPWRPLUS(1740),
	bitvsp8k8424XS(1741),
	bitvsp8k8408QQ(1742),
	bitvsp8k8418XSQ(1743),
	bitvsp8k8418XTQ(1744),
	bitvsp8k8424GS(1745),
	bitvsp8k8424GT(1746),
	bitvsp8k8424XT(1747),
	bitvsp7k7248XS(1748),
        bitvsp7k7248XT(1749),
        bitvsp4k4450GSX(1750),
        bitvsp7k7206QQ(1751),
	bitvsp9k9424XS(1752),
	bitvsp9k9424XT(1753),
	bitvsp9k9416QQ(1754),
	bitvsp9k9406CQ(1755),
	bitvspSF9400(1756),
	bitdsg8016QQ(1757),
	bitvsp8k8402CQ(1758),
	bitdsg9016CQ(1759),
	bitdsg8032QQ(1760),
	bitvsp5k5030GSXuPWR(1761),
	bitvsp5k5054GSXuPWR(1762),
        bitlastbitnum(2047)
    }
    MAX-ACCESS  read-only
    STATUS  current
    DESCRIPTION "Bit position number of license bitmap"
    ::= { rcLicense 1 }    

rcLicenseBitMap OBJECT-TYPE
    SYNTAX OCTET STRING (SIZE(256))
    MAX-ACCESS read-only
    STATUS current
    DESCRIPTION "License bit map. Bitmap number is defined in rcLicenseNumber"
    ::= { rcLicense 2 }

rcLicenseFileName OBJECT-TYPE
     SYNTAX       DisplayString (SIZE(0..255))
     MAX-ACCESS   read-only
     STATUS       current
     DESCRIPTION  "Current running license file name.
                  Empty mean no license running. Empty means
		  there is no license file installed"
     ::= { rcLicense 3 }
	
rcLicenseLicenseType OBJECT-TYPE
     SYNTAX       INTEGER {
                     none(1),
        	     base(2),
                     advance(3),   
                     premier(4),
                     premierPlusMacsec(5),
		     port(6),
		     premierWithPort(7),
		     premierPlusMacsecWithPort(8),
		     unknown(9),
		     l3v(10),
                     l3vWithMacsec(11),
                     datacenter(12),
                     sdniot(13),
                     insight(14),
                     macsec(15)
              	  }
     MAX-ACCESS   read-only
     STATUS       current
     DESCRIPTION  "This indicates the current running license
                  level type. For 5520 family only premier and macsec licenses are supported."
     ::= { rcLicense 4}
	
rcLicenseDurationType OBJECT-TYPE
     SYNTAX       INTEGER {
                     none(1),
                     trialFactoryDefault(2),
             	     trialLicense(3),
             	     timeBased(4),
             	     perpetual(5)
                  }
     MAX-ACCESS   read-only
     STATUS       current
     DESCRIPTION  "This indicates the current running license duration type"
     ::= { rcLicense 5}
                    
rcLicenseFactoryTrialPeriodRemainingDays OBJECT-TYPE
     SYNTAX       Integer32
     MAX-ACCESS   read-only
     STATUS       current
     DESCRIPTION  "This indicates days left before the factory default
                  trial period expired. Only applicable to the
                  type trialFactoryDefault(2) iin object rcLicenseDurationType.
                  Otherwise, it will be always set to 0"
     ::= { rcLicense 6}
     
rcLicenseDaysLeftBeforeExpiration OBJECT-TYPE
        SYNTAX        Integer32
        MAX-ACCESS    accessible-for-notify
        STATUS        current
        DESCRIPTION   "This indicates days left before time based
	               license expire. Only applicable to Time
		       Based license and trial period."
        ::= { rcLicense 7}
rcLicenseDaysAfterExpiration OBJECT-TYPE
        SYNTAX        Integer32
        MAX-ACCESS    accessible-for-notify
        STATUS        current
        DESCRIPTION   "Number of days the license has been expired.
	               It is only applicable to non permanet type"
        ::= { rcLicense 8}
	
rcLicenseGenerationTime OBJECT-TYPE
     SYNTAX       DateAndTime
     MAX-ACCESS   read-only
     STATUS       current
     DESCRIPTION  "Date of the license file is generated. It
                  there is no license file, value '0000000000000000'H
		  will be returned"
     ::= { rcLicense 9}

rcLicenseExpirationTime OBJECT-TYPE
     SYNTAX       DateAndTime
     MAX-ACCESS   read-only
     STATUS       current
     DESCRIPTION  "Date of the license file is expired. If there is
     		  no license file or license file has no expiration date
                  date (perpetual license), value '0000000000000000'H
		  will be returned"
     ::= { rcLicense 10}

rcLicenseGrantTable OBJECT-TYPE
    SYNTAX          SEQUENCE OF RcLicenseGrantEntry
    MAX-ACCESS      not-accessible
    STATUS          current
    DESCRIPTION     "Slot licenses"
    ::= { rcLicense 11 }

rcLicenseGrantEntry OBJECT-TYPE
    SYNTAX          RcLicenseGrantEntry
    MAX-ACCESS      not-accessible
    STATUS          current
    DESCRIPTION     "Entry containing license status for a particular slot"
    INDEX           { rcLicenseSlot }
    ::= { rcLicenseGrantTable 1 }

RcLicenseGrantEntry ::= SEQUENCE {
            rcLicenseSlot           Integer32,
            rcLicenseSlotGrant      TruthValue
    }     

rcLicenseSlot OBJECT-TYPE
    SYNTAX          Integer32 (1..8)
    MAX-ACCESS      not-accessible
    STATUS          current
    DESCRIPTION     "Slot ID"
    ::= { rcLicenseGrantEntry 1 }

rcLicenseSlotGrant OBJECT-TYPE
    SYNTAX          TruthValue
    MAX-ACCESS      read-write
    STATUS          current
    DESCRIPTION     "license grant"
    ::= { rcLicenseGrantEntry 2 }
	      
rcLicenseRemainingDays OBJECT-TYPE
     SYNTAX       Integer32
     MAX-ACCESS   read-only
     STATUS       current
     DESCRIPTION  "This indicates days left before the license expires.
                   For license types this is not valid, a value of 0 
                   will be returned"
        ::= { rcLicense 12 }
	      
rcLicenseDisplayType OBJECT-TYPE
     SYNTAX       DisplayString (SIZE(0..255))
     MAX-ACCESS   read-only
     STATUS       current
     DESCRIPTION  "Current running license type for subscription based.
                   Empty means there is no license file installed."
        ::= { rcLicense 13 }

-- end of rcLicense

END

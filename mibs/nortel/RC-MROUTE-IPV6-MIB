RC-MROUTE-IPV6-MIB DEFINITIONS ::= BEGIN

IMPORTS
    MODULE-IDENTITY, OBJECT-TYPE, Integer32, Counter32, Counter64, TimeTicks
        FROM SNMPv2-SMI
    TruthValue, DisplayString
        FROM SNMPv2-TC
    Ipv6Address
        FROM IPV6-TC
    InterfaceIndex
        FROM IF-MIB
    PortSet, rcMRouteIpv6
        FROM RAPID-CITY;

rcMRouteIpv6Mib  MODULE-IDENTITY
       LAST-UPDATED "201702100000Z"
       ORGANIZATION "Avaya"
       CONTACT-INFO "Prem Palarapu
             Postal:  Avaya
                      600 Technology Park
                      Billerica, MA 01821
              email:  prempa@avaya.com
                      " 
       DESCRIPTION    "Enterprise MIB for the IPv6 MRoute mibs."

       REVISION "201702100000Z" -- 10 Feb 2017
       DESCRIPTION "Version 7: Corrected MIB compiler errors."

       REVISION "201509020000Z" -- 2 Sep 2015
       DESCRIPTION "Version 6: Added -
	   		       rcMRouteIpv6Scalars, rcMRouteIpv6StatsEnabled, rcMRouteIpv6StatsClear
			       and rcMRouteIpv6StatsTable.
			       Requested by Tudor Erghelegiu (submit 25341). (Prem)"

       REVISION "201506250000Z" -- 25 Jun 2015
       DESCRIPTION "Version 5: Changed -
			       rcMRouteIpv6UsageGlobalIngressRecInUse to rcMRouteIpv6IngressRecInUse,
			       rcMRouteIpv6UsageGlobalEgressRecInUse to rcMRouteIpv6EgressRecInUse,
			       rcMRouteIpv6UsageGlobalIngressThreshold to rcMRouteIpv6IngressThreshold,
			       rcMRouteIpv6UsageGlobalEgressThreshold to rcMRouteIpv6EgressThreshold,
			       rcMRouteIpv6UsageGlobalSendTrapAndLog to rcMRouteIpv6SendTrapAndLog,
			       rcMRouteIpv6UsageGlobalSendTrapOnly to rcMRouteIpv6SendTrapOnly,
			       rcMRouteIpv6UsageGlobalLogMsgOnly to rcMRouteIpv6LogMsgOnly.
			       Requested by Cristina/Andrei Erghelegiu (Prem)"

       REVISION "201506240000Z" -- 24 Jun 2015
       DESCRIPTION "Version 4: Changed the syntax of -
			       rcMRouteIpv6UsageGlobalSendTrapAndLog,
			       rcMRouteIpv6UsageGlobalSendTrapOnly and
			       rcMRouteIpv6UsageGlobalLogMsgOnly to
			       TruthValue from EnableValue (Prem)"

       REVISION "201506230000Z" -- 23 Jun 2015
       DESCRIPTION "Version 3: Added -
	   		       rcMRouteIpv6Statistics,
			       rcMRouteIpv6UsageGlobal,
			       rcMRouteIpv6UsageGlobalIngressRecInUse,
			       rcMRouteIpv6UsageGlobalEgressRecInUse,
			       rcMRouteIpv6UsageGlobalIngressThreshold,
			       rcMRouteIpv6UsageGlobalEgressThreshold,
			       rcMRouteIpv6UsageGlobalSendTrapAndLog,
			       rcMRouteIpv6UsageGlobalSendTrapOnly and
			       rcMRouteIpv6UsageGlobalLogMsgOnly.
			       Requested by Cristina/Andrei Erghelegiu (Prem)"

       REVISION "201504170000Z" -- 17 Apr 2015
       DESCRIPTION "Version 2: Added the missing END (Prem)"

       REVISION "201504130000Z" -- 13 Apr 2015
       DESCRIPTION "Version 1: Created the file.
	   		Requested by Cristina/Flavia for IPv6 MRoute
			Submit 23734 (Prem)"
       ::= { rcMRouteIpv6 0 }

rcMRouteIpv6Objects	OBJECT IDENTIFIER ::= { rcMRouteIpv6 1 }

-- Begin of IPv6 MRoute MIB
-- The commented elements are currently not supported but are left in the mib
-- for possible future implementation, as per PLM request (Seema Sirivara)

-- the IPv6 Multicast Routing MIB-Group
--
-- a collection of objects providing information about
-- IPv6 Multicast Groups

rcMRouteIpv6Table OBJECT-TYPE
    SYNTAX        SEQUENCE OF RcMRouteIpv6Entry
    MAX-ACCESS    not-accessible
    STATUS        current
    DESCRIPTION   "The (conceptual) table containing multicast routing
                   information for IPv6 datagrams sent by particular sources to
                   the IPv6 multicast groups known to this router."
    ::= { rcMRouteIpv6Objects 1 }

rcMRouteIpv6Entry OBJECT-TYPE
    SYNTAX        RcMRouteIpv6Entry
    MAX-ACCESS    not-accessible
    STATUS        current
    DESCRIPTION   "An entry (conceptual row) containing the multicast routing
                   information for IPv6 datagrams from a particular source and
                   addressed to a particular IPv6 multicast group address."
    INDEX          { rcMRouteIpv6Group,
                     rcMRouteIpv6Source,
                     rcMRouteIpv6SourceMask }
    ::= { rcMRouteIpv6Table 1 }

RcMRouteIpv6Entry ::= SEQUENCE {
         rcMRouteIpv6Group                 Ipv6Address,
         rcMRouteIpv6Source                Ipv6Address,
         rcMRouteIpv6SourceMask            Ipv6Address,
         rcMRouteIpv6UpstreamNeighbor      Ipv6Address,
         rcMRouteIpv6InIfIndex             Integer32,
--       rcMRouteIpv6UpTime                TimeTicks,
         rcMRouteIpv6ExpiryTime            TimeTicks,
--       rcMRouteIpv6Pkts                  Counter32,
--       rcMRouteIpv6DifferentInIfPackets  Counter32,
--       rcMRouteIpv6Octets                Counter32,
         rcMRouteIpv6Protocol              INTEGER
}

rcMRouteIpv6Group OBJECT-TYPE
    SYNTAX        Ipv6Address
    MAX-ACCESS    not-accessible
    STATUS        current
    DESCRIPTION   "The IPv6 multicast group address for which this entry
                   contains multicast routing information."
    ::= { rcMRouteIpv6Entry 1 }

rcMRouteIpv6Source OBJECT-TYPE
    SYNTAX        Ipv6Address
    MAX-ACCESS    not-accessible
    STATUS        current
    DESCRIPTION   "The network address which when combined with the
                   corresponding value of rcMRouteIpv6SourceMask identifies the
                   sources for which this entry contains multicast routing
                   information."
    ::= { rcMRouteIpv6Entry 2 }

rcMRouteIpv6SourceMask OBJECT-TYPE
    SYNTAX        Ipv6Address
    MAX-ACCESS    not-accessible
    STATUS        current
    DESCRIPTION   "The network mask which when combined with the corresponding
                   value of rcMRouteIpv6Source identifies the sources for which
                   this entry contains multicast routing information."
    ::= { rcMRouteIpv6Entry 3 }

 rcMRouteIpv6UpstreamNeighbor OBJECT-TYPE
    SYNTAX        Ipv6Address
    MAX-ACCESS    read-only
    STATUS        current
    DESCRIPTION   "The address of the upstream neighbor (e.g., RPF neighbor)
                   from which IPv6 datagrams from these sources to this multicast
                   address are received."
    ::= { rcMRouteIpv6Entry 4 }

rcMRouteIpv6InIfIndex OBJECT-TYPE
    SYNTAX        Integer32
    MAX-ACCESS    read-only
    STATUS        current
    DESCRIPTION   "The value of ifIndex for the interface on which IPv6
                   datagrams sent by these sources to this multicast address
                   are received.  A value of 0 indicates that datagrams are not
                   subject to an incoming interface check, but may be accepted
                   on multiple interfaces."
    ::= { rcMRouteIpv6Entry 5 }

--rcMRouteIpv6UpTime OBJECT-TYPE
--    SYNTAX     TimeTicks
--    MAX-ACCESS read-only
--    STATUS     current
--    DESCRIPTION
--            "The time since the multicast routing information
--            represented by this entry was learned by the router."
--    ::= { rcMRouteIpv6Entry 6 }

rcMRouteIpv6ExpiryTime OBJECT-TYPE
    SYNTAX        TimeTicks
    MAX-ACCESS    read-only
    STATUS        current
    DESCRIPTION   "The minimum amount of time remaining before this entry will
                   be aged out.  The value 0 indicates that the entry is not
                   subject to aging."
    ::= { rcMRouteIpv6Entry 7 }

--rcMRouteIpv6Pkts OBJECT-TYPE
--    SYNTAX     Counter32
--    MAX-ACCESS read-only
--    STATUS     current
--    DESCRIPTION
--            "The number of packets which this router has received from
--            these sources and addressed to this multicast group
--            address."
--    ::= { rcMRouteIpv6Entry 8 }

--rcMRouteIpv6DifferentInIfPackets OBJECT-TYPE
--    SYNTAX     Counter32
--    MAX-ACCESS read-only
--    STATUS     current
--    DESCRIPTION
--            "The number of packets which this router has received from
--            these sources and addressed to this multicast group address,
--            which were not received from the interface indicated by
--            rcMRouteIpv6InIfIndex."
--    ::= { rcMRouteIpv6Entry 9 }

--rcMRouteIpv6Octets OBJECT-TYPE
--    SYNTAX     Counter32
--    MAX-ACCESS read-only
--    STATUS     current
--    DESCRIPTION
--            "The number of octets contained in IPv6 datagrams which were
--            received from these sources and addressed to this multicast
--            group address, and which were forwarded by this router."
--    ::= { rcMRouteIpv6Entry 10 }

rcMRouteIpv6Protocol OBJECT-TYPE
    SYNTAX        INTEGER {
                      other(1),          -- none of the following
                      local(2),          -- e.g., manually configured
                      netmgmt(3),        -- set via net.mgmt protocol
                      dvmrp(4),
                      mospf(5),
                      pimSparseDense(6), -- PIMv1, both DM and SM
                      cbt(7),
                      pimSparseMode(8),  -- PIM-SMv2
                      pimDenseMode(9),   -- PIM-DMv2
                      igmpOnly(10),
                      pimSsmMode(11)
                  }
    MAX-ACCESS    read-only
    STATUS        current
    DESCRIPTION   "The routing mechanism via which this route was learned."
    ::= { rcMRouteIpv6Entry 11 }

--
--  The IPv6 Multicast Routing Next Hop Table
--

rcMRouteIpv6NextHopTable OBJECT-TYPE
    SYNTAX        SEQUENCE OF RcMRouteIpv6NextHopEntry
    MAX-ACCESS    not-accessible
    STATUS        current
    DESCRIPTION   "The (conceptual) table containing information on the next
                   hops on outgoing interfaces for routing IPv6 multicast
                   datagrams.  Each entry is one of a list of next hops on
                   outgoing interfaces for particular sources sending to a
                   particular multicast group address."
    ::= { rcMRouteIpv6Objects 2 }

rcMRouteIpv6NextHopEntry OBJECT-TYPE
    SYNTAX        RcMRouteIpv6NextHopEntry
    MAX-ACCESS    not-accessible
    STATUS        current
    DESCRIPTION   "An entry (conceptual row) in the list of next hops on
                   outgoing interfaces to which IPv6 multicast datagrams from
                   particular sources to a IPv6 multicast group address are
                   routed."
    INDEX         { rcMRouteIpv6NextHopGroup, rcMRouteIpv6NextHopSource,
                    rcMRouteIpv6NextHopSourceMask, rcMRouteIpv6NextHopIfIndex,
                    rcMRouteIpv6NextHopAddress }
    ::= { rcMRouteIpv6NextHopTable 1 }

RcMRouteIpv6NextHopEntry ::= SEQUENCE {
       rcMRouteIpv6NextHopGroup              Ipv6Address,
       rcMRouteIpv6NextHopSource             Ipv6Address,
       rcMRouteIpv6NextHopSourceMask         Ipv6Address,
       rcMRouteIpv6NextHopIfIndex            Integer32,
       rcMRouteIpv6NextHopAddress            Ipv6Address,
       rcMRouteIpv6NextHopState              INTEGER,
--     rcMRouteIpv6NextHopUpTime             TimeTicks,
       rcMRouteIpv6NextHopExpiryTime         TimeTicks,
       rcMRouteIpv6NextHopClosestMemberHops  Integer32,
       rcMRouteIpv6NextHopProtocol           INTEGER
--     rcMRouteIpv6NextHopPkts               Counter32
}

rcMRouteIpv6NextHopGroup OBJECT-TYPE
    SYNTAX        Ipv6Address
    MAX-ACCESS    not-accessible
    STATUS        current
    DESCRIPTION   "The IPv6 multicast group for which this entry specifies a
                   next hop on an outgoing interface."
    ::= { rcMRouteIpv6NextHopEntry 1 }

rcMRouteIpv6NextHopSource OBJECT-TYPE
    SYNTAX        Ipv6Address
    MAX-ACCESS    not-accessible
    STATUS        current
    DESCRIPTION   "The network address which when combined with the
                   corresponding value of rcMRouteIpv6NextHopSourceMask identifies
                   the sources for which this entry specifies a next hop on an
                   outgoing interface."
    ::= { rcMRouteIpv6NextHopEntry 2 }

rcMRouteIpv6NextHopSourceMask OBJECT-TYPE
    SYNTAX        Ipv6Address
    MAX-ACCESS    not-accessible
    STATUS        current
    DESCRIPTION   "The network mask which when combined with the corresponding
                   value of rcMRouteIpv6NextHopSource identifies the sources for
                   which this entry specifies a next hop on an outgoing
                   interface."
    ::= { rcMRouteIpv6NextHopEntry 3 }

rcMRouteIpv6NextHopIfIndex OBJECT-TYPE
    SYNTAX        Integer32
    MAX-ACCESS    not-accessible
    STATUS        current
    DESCRIPTION   "The ifIndex value of the interface for the outgoing
                   interface for this next hop."
    ::= { rcMRouteIpv6NextHopEntry 4 }

rcMRouteIpv6NextHopAddress OBJECT-TYPE
    SYNTAX        Ipv6Address
    MAX-ACCESS    not-accessible
    STATUS        current
    DESCRIPTION   "The address of the next hop specific to this entry.  For
                   most interfaces, this is identical to rcMRouteIpv6NextHopGroup.
                   NBMA interfaces, however, may have multiple next hop
                   addresses out a single outgoing interface."
    ::= { rcMRouteIpv6NextHopEntry 5 }

rcMRouteIpv6NextHopState OBJECT-TYPE
    SYNTAX        INTEGER { 
                      pruned(1), 
                      forwarding(2) 
		  }
    MAX-ACCESS    read-only
    STATUS        current
    DESCRIPTION   "An indication of whether the outgoing interface and next
                   hop represented by this entry is currently being used to
                   forward IPv6 datagrams.  The value 'forwarding' indicates it
                   is currently being used; the value 'pruned' indicates it is
                   not."
    ::= { rcMRouteIpv6NextHopEntry 6 }

--rcMRouteIpv6NextHopUpTime OBJECT-TYPE
--    SYNTAX     TimeTicks
--    MAX-ACCESS read-only
--    STATUS     current
--    DESCRIPTION
--            "The time since the multicast routing information
--            represented by this entry was learned by the router."
--    ::= { rcMRouteIpv6NextHopEntry 7 }

rcMRouteIpv6NextHopExpiryTime OBJECT-TYPE
    SYNTAX        TimeTicks
    MAX-ACCESS    read-only
    STATUS        current
    DESCRIPTION   "The minimum amount of time remaining before this entry will
                   be aged out.  The value 0 indicates that the entry is not
                   subject to aging."
    ::= { rcMRouteIpv6NextHopEntry 8 }

rcMRouteIpv6NextHopClosestMemberHops OBJECT-TYPE
    SYNTAX        Integer32
    MAX-ACCESS    read-only
    STATUS        current
    DESCRIPTION   "The minimum number of hops between this router and any
                   member of this IPv6 multicast group reached via this next hop
                   on this outgoing interface.  Any IPv6 multicast datagrams for
                   the group which have a TTL less than this number of hops
                   will not be forwarded to this next hop."
    ::= { rcMRouteIpv6NextHopEntry 9 }

rcMRouteIpv6NextHopProtocol OBJECT-TYPE
    SYNTAX        INTEGER {
                      other(1),          -- none of the following
                      local(2),          -- e.g., manually configured
                      netmgmt(3),        -- set via net.mgmt protocol
                      dvmrp(4),
                      mospf(5),
                      pimSparseDense(6), -- PIMv1, both DM and SM
                      cbt(7),
                      pimSparseMode(8),  -- PIM-SMv2
                      pimDenseMode(9),   -- PIM-DMv2
                      igmpOnly(10),
                      pimSsmMode(11)
                  }
    MAX-ACCESS    read-only
    STATUS        current
    DESCRIPTION   "The routing mechanism via which this next-hop was learned."
    ::= { rcMRouteIpv6NextHopEntry 10 }

--rcMRouteIpv6NextHopPkts OBJECT-TYPE
--    SYNTAX     Counter32
--    MAX-ACCESS read-only
--    STATUS     current
--    DESCRIPTION
--            "The number of packets which have been forwarded using this
--            route."
--    ::= { rcMRouteIpv6NextHopEntry 11 }

--
--  The Multicast Routing Interface Table
--

rcMRouteIpv6InterfaceTable OBJECT-TYPE
    SYNTAX        SEQUENCE OF RcMRouteIpv6InterfaceEntry
    MAX-ACCESS    not-accessible
    STATUS        current
    DESCRIPTION   "The (conceptual) table containg multicast routing
                   information specific to interfaces."
    ::= { rcMRouteIpv6Objects 3 }

rcMRouteIpv6InterfaceEntry OBJECT-TYPE
    SYNTAX        RcMRouteIpv6InterfaceEntry
    MAX-ACCESS    not-accessible
    STATUS        current
    DESCRIPTION   "An entry (conceptual row) containing the multicast routing
                   information for a particular interface."
    INDEX         { rcMRouteIpv6InterfaceIfIndex }
    ::= { rcMRouteIpv6InterfaceTable 1 }

RcMRouteIpv6InterfaceEntry ::= SEQUENCE {
       rcMRouteIpv6InterfaceIfIndex          Integer32,
       rcMRouteIpv6InterfaceTtl              Integer32,
       rcMRouteIpv6InterfaceProtocol         INTEGER
--     rcMRouteIpv6InterfaceRateLimit        Integer32,
--     rcMRouteIpv6InterfaceInMcastOctets    Counter32,
--     rcMRouteIpv6InterfaceOutMcastOctets   Counter32,
--     rcMRouteIpv6InterfaceHCInMcastOctets  Counter64,
--     rcMRouteIpv6InterfaceHCOutMcastOctets Counter64
}

rcMRouteIpv6InterfaceIfIndex OBJECT-TYPE
    SYNTAX        Integer32
    MAX-ACCESS    not-accessible
    STATUS        current
    DESCRIPTION   "The ifIndex value of the interface for which this entry
                   contains information."
    ::= { rcMRouteIpv6InterfaceEntry 1 }

rcMRouteIpv6InterfaceTtl OBJECT-TYPE
    SYNTAX        Integer32 (1..255)
    MAX-ACCESS    read-only
    STATUS        current
    DESCRIPTION   "The datagram TTL threshold for the interface. Any IPv6
                   multicast datagrams with a TTL less than this threshold will
                   not be forwarded out the interface. The default value of 0
                   means all multicast packets are forwarded out the
                   interface."
    ::= { rcMRouteIpv6InterfaceEntry 2 }

rcMRouteIpv6InterfaceProtocol OBJECT-TYPE
    SYNTAX        INTEGER {
                      other(1),          -- none of the following
                      local(2),          -- e.g., static routing
                      netmgmt(3),        -- set via net.mgmt protocol
                      dvmrp(4),
                      mospf(5),
                      pimSparseDense(6), -- PIMv1, both DM and SM
                      cbt(7),
                      pimSparseMode(8),  -- PIM-SMv2
                      pimDenseMode(9),   -- PIM-DMv2
                      igmpOnly(10),
                      pimSsmMode(11)
                  }
    MAX-ACCESS    read-only
    STATUS        current
    DESCRIPTION   "The routing protocol running on this interface."
    ::= { rcMRouteIpv6InterfaceEntry 3 }

--rcMRouteIpv6InterfaceRateLimit OBJECT-TYPE
--    SYNTAX     Integer32
--    MAX-ACCESS read-write
--    STATUS     current
--    DESCRIPTION
--            "The rate-limit, in kilobits per second, of forwarded
--            multicast traffic on the interface.  A rate-limit of 0
--            indicates that no rate limiting is done."
--    DEFVAL     { 0 }
--    ::= { rcMRouteIpv6InterfaceEntry 4 }

--rcMRouteIpv6InterfaceInMcastOctets OBJECT-TYPE
--    SYNTAX     Counter32
--    MAX-ACCESS read-only
--    STATUS     current
--    DESCRIPTION
--            "The number of octets of multicast packets that have arrived
--            on the interface."
--    ::= { rcMRouteIpv6InterfaceEntry 5 }

--rcMRouteIpv6InterfaceHCOutMcastOctets OBJECT-TYPE
--    SYNTAX     Counter64
--    MAX-ACCESS read-only
--    STATUS     current
--    DESCRIPTION
--            "The number of octets of multicast packets that have been
--            sent on the interface.  This object is a 64-bit version of
--            rcMRouteIpv6InterfaceOutMcastOctets."
--    ::= { rcMRouteIpv6InterfaceEntry 8 }


rcMRouteIpv6Statistics  OBJECT IDENTIFIER ::= { rcMRouteIpv6 2 }

rcMRouteIpv6UsageGlobal OBJECT IDENTIFIER ::= { rcMRouteIpv6Statistics 1 }

rcMRouteIpv6IngressRecInUse OBJECT-TYPE
        SYNTAX        Integer32 (0..32767)
        MAX-ACCESS    read-only
        STATUS        current
        DESCRIPTION   "Used to get the Ingress Record Usage in the switch.
                       (S-G usage)."
        ::= { rcMRouteIpv6UsageGlobal 1 }

rcMRouteIpv6EgressRecInUse OBJECT-TYPE
        SYNTAX        Integer32 (0..32767)
        MAX-ACCESS    read-only
        STATUS        current
        DESCRIPTION   "Used to get the Egress Record Usage in the switch
                       (pepstream count)."
        ::= { rcMRouteIpv6UsageGlobal 2 }

rcMRouteIpv6IngressThreshold OBJECT-TYPE
        SYNTAX        Integer32 (0..32767)
        MAX-ACCESS    read-write
        STATUS        current
        DESCRIPTION   "Used to get the threshold count for Ingress records."
        DEFVAL        { 0 }
        ::= { rcMRouteIpv6UsageGlobal 3 }

rcMRouteIpv6EgressThreshold OBJECT-TYPE
        SYNTAX        Integer32 (0..32767)
        MAX-ACCESS    read-write
        STATUS        current
        DESCRIPTION   "Used to get threshold count for egress records."
        DEFVAL        { 0 }
        ::= { rcMRouteIpv6UsageGlobal  4 }

rcMRouteIpv6SendTrapAndLog OBJECT-TYPE
        SYNTAX        TruthValue
        MAX-ACCESS    read-write
        STATUS        current
        DESCRIPTION   "A means of alerting the user. If this bool is set,
                       a trap will be generated and also a
                       message will be logged."
        DEFVAL        { false }
        ::= { rcMRouteIpv6UsageGlobal  5 }

rcMRouteIpv6SendTrapOnly OBJECT-TYPE
        SYNTAX        TruthValue
        MAX-ACCESS    read-write
        STATUS        current
        DESCRIPTION   "A means of alerting the user. If this bool is set,
                       only a trap will be generated"
        DEFVAL        { false }
        ::= { rcMRouteIpv6UsageGlobal  6 }

rcMRouteIpv6LogMsgOnly OBJECT-TYPE
        SYNTAX        TruthValue
        MAX-ACCESS    read-write
        STATUS        current
        DESCRIPTION   "A means of alerting the user.If this bool is set,
                       only a message will be logged."
        DEFVAL        { false }
        ::= { rcMRouteIpv6UsageGlobal  7 }


rcMRouteIpv6Scalars OBJECT IDENTIFIER ::= { rcMRouteIpv6Statistics 2 }

rcMRouteIpv6StatsEnabled OBJECT-TYPE
        SYNTAX        TruthValue
	MAX-ACCESS    read-write
	STATUS        current
	DESCRIPTION   "The enabled status of IPv6 Multicast statistics."
	DEFVAL        { false }
        ::= { rcMRouteIpv6Scalars 1 }

rcMRouteIpv6StatsClear OBJECT-TYPE
    	SYNTAX        TruthValue
	MAX-ACCESS    read-write
	STATUS        current
	DESCRIPTION   "Clear ipv6 mroute stats."
	DEFVAL        { false }
        ::= { rcMRouteIpv6Scalars 2 }

rcMRouteIpv6StatsTable OBJECT-TYPE
    	SYNTAX        SEQUENCE OF RcMRouteIpv6StatsEntry
	MAX-ACCESS    not-accessible
	STATUS        current
	DESCRIPTION   "the table containing IPv6 Multicast statistics."
        ::= { rcMRouteIpv6Statistics 3 }

rcMRouteIpv6StatsEntry OBJECT-TYPE
    	SYNTAX        RcMRouteIpv6StatsEntry
	MAX-ACCESS    not-accessible
	STATUS        current
	DESCRIPTION   "An entry containing the ipv6 multicast statistics
            	       information for the specific group ipv6 address."
        INDEX         { rcMRouteIpv6StatsGroupAddress }
        ::= { rcMRouteIpv6StatsTable 1 }
RcMRouteIpv6StatsEntry ::= SEQUENCE {
		rcMRouteIpv6StatsGroupAddress      Ipv6Address,
		rcMRouteIpv6StatsSourceCount       Counter32,
		rcMRouteIpv6StatsPkts              Counter64,
		rcMRouteIpv6StatsBytes             Counter64,
		rcMRouteIpv6StatsAverageSizePerPkt Integer32
}


rcMRouteIpv6StatsGroupAddress OBJECT-TYPE
    	SYNTAX        Ipv6Address
	MAX-ACCESS    not-accessible
	STATUS        current
	DESCRIPTION   "the IPv6 multicast group address for which this entry
            	       contains ipv6 multicast statistics."
        ::= { rcMRouteIpv6StatsEntry 1 }

rcMRouteIpv6StatsSourceCount OBJECT-TYPE
    	SYNTAX        Counter32
	MAX-ACCESS    read-only
	STATUS        current
	DESCRIPTION   "The number of sources corresponding to the specific group and vrf."
	::= { rcMRouteIpv6StatsEntry 2 }

rcMRouteIpv6StatsPkts OBJECT-TYPE
    	SYNTAX        Counter64
	MAX-ACCESS    read-only
	STATUS        current
	DESCRIPTION   "The total number of frames that are processed
                      corresponding to the specific group and vrf."
    ::= { rcMRouteIpv6StatsEntry 3 }
rcMRouteIpv6StatsBytes OBJECT-TYPE
    	SYNTAX        Counter64
	MAX-ACCESS    read-only
	STATUS        current
	DESCRIPTION   "The total number of bytes that are processed
                      corresponding to the specific group and vrf."
        ::= { rcMRouteIpv6StatsEntry 4 }

rcMRouteIpv6StatsAverageSizePerPkt OBJECT-TYPE
    	SYNTAX        Integer32
	MAX-ACCESS    read-only
	STATUS        current
	DESCRIPTION   "The average length of packets that are processed
                      corresponding to the specific group and vrf."
        ::= { rcMRouteIpv6StatsEntry 5 }

-- End of IPv6 MRoute MIB

END

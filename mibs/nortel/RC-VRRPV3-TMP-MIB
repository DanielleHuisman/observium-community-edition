RC-VRRPV3-TMP-MIB DEFINITIONS ::= BEGIN  

       IMPORTS
           MODULE-IDENTITY, OBJECT-TYPE,
           NOTIFICATION-TYPE, Counter32,
           Counter64,Integer32,Unsigned32      FROM SNMPv2-SMI

           RowStatus,
           MacAddress, TruthValue, TimeStamp,
           TimeInterval, StorageType           FROM SNMPv2-TC

           ifIndex, InterfaceIndex             FROM IF-MIB
           InetAddressType, InetAddress, 
           InetAddressPrefixLength             FROM INET-ADDRESS-MIB
           VrId                                FROM VRRP-MIB
           rcVrrpv3                            FROM RAPID-CITY;

       rcVrrpTmpMib  MODULE-IDENTITY
           LAST-UPDATED "201510070000Z"                                        
           ORGANIZATION "Nortel Networks"
           CONTACT-INFO "Marty Lok
                      Postal:   Nortel Networks, Inc.
                                600 Technology Park Drive
                                Billerica, MA 02478
                      Tel:              978-288-4470
                      E-mail:           malok@nortel.com"

           DESCRIPTION
               "This MIB module is based on the VRRP for IPv6 
                MIB draft-ietf-vrrp-unified-mib-06.txt.
                The object names and OIDs may be different from 
                the draft.        
                This MIB describes objects used for managing Virtual
                Router Redundancy Protocol (VRRP) over IPv4 and IPv6
                protocols.
                This MIB supports VRRP for IPv4 and IPv6 protocols
                simultaneously running on a given interface of a
                router.

                Copyright (C) The IETF Trust (2006)."

            REVISION "201510070000Z" -- 7 October 2015
	    DESCRIPTION "Added Added to Imports 
                  Counter64 FROM SNMPv2-SMI
                  InterfaceIndex  FROM IF-MIB
                  InetAddressPrefixLength  FROM INET-ADDRESS-MIB
                  Changed SYNTAX       SEQUENCE OF RcVrrpTmpRouterglobalStatisticsEntry to SYNTAX       SEQUENCE OF RcVrrpTmpRouterGlobalStatisticsEntry"
            
	    REVISION "201504140000Z" -- 14 April 2015
	    DESCRIPTION "Added rcVrrpTmpRouterGlobalStatisticsTable
		         Requested by Cristina (Prem)"

	    REVISION "201008230000Z" -- 23 August 2010
	    DESCRIPTION "Added rcVrrpTmpAssociatedIpAddrPrefixLength in 
		         rcVrrpTmpAssociatedIpAddrTable"


           REVISION "200906150000Z"    -- 15 JUN 2009
           DESCRIPTION          
                "Following changes are done in this revision :-
                
                1) Changed some MIB attributes from Unsigned32 to
                   Integer32.
                2) Changed the ordering of INDEX in rcVrrpTmpOperationsTable 
                   and rcVrrpTmpAssociatedIpAddrTable.
                3) Include rcVrrpTmpOperationsIfIndex as MIB object in the 
                   rcVrrpTmpOperationsTable."
	   
           REVISION "200903110000Z"    -- 11 Mar 2009
           DESCRIPTION          
               "Converted the draft MIB to proprietory version."
         

           ::= { rcVrrpv3 1 }      					      
    
      --
      --  Vrrp MIB Groups
      --

      rcVrrpTmpOperations      OBJECT IDENTIFIER ::= { rcVrrpTmpMib 1 }
      rcVrrpTmpStatistics      OBJECT IDENTIFIER ::= { rcVrrpTmpMib 2 }
      
      --
      --  Start of MIB objects
      --
      rcVrrpTmpNotificationCntl  OBJECT-TYPE
           SYNTAX       INTEGER {
               enabled     (1),
               disabled    (2)
           }
           MAX-ACCESS   read-write
           STATUS       current
           DESCRIPTION
              "Indicates whether the VRRP-enabled router will generate
               SNMP notifications for events defined in this MIB.
               'Enabled' results in SNMP notifications; 'disabled', no
               notifications are sent."
           DEFVAL { enabled }
           ::= { rcVrrpTmpOperations 2 }

      --
      --  Vrrp Operations Table
      --

       rcVrrpTmpOperationsTable OBJECT-TYPE
           SYNTAX       SEQUENCE OF RcVrrpTmpOperationsEntry
           MAX-ACCESS   not-accessible
           STATUS       current
           DESCRIPTION
               "Unified Operations table for a VRRP router which
                consists of a sequence (i.e., one or more conceptual
                rows) of 'rcVrrpTmpOperationsEntry' items which describe
                the operational characteristics of a virtual router."
           ::= { rcVrrpTmpOperations 7 }

       rcVrrpTmpOperationsEntry OBJECT-TYPE
           SYNTAX       RcVrrpTmpOperationsEntry
           MAX-ACCESS   not-accessible
           STATUS       current
           DESCRIPTION
               "An entry in the rcVrrpTmpOperationsTable containing the
                operational characteristics of a virtual router.  On a
                VRRP router, a given virtual router is identified by a
                combination of the IP version, VRID and ifIndex.
                ifIndex represents a physical interface of the router.
                Note that rows in this table can be distinguished on a
                multi-stacked device running VRRP over IPv4 and
                IPv6 on the same physical interface.
                Rows in the table cannot be modified unless the value
                of 'rcVrrpTmpOperationsState' has transitioned to
                'initialize'"
           INDEX    { rcVrrpTmpOperationsIfIndex,rcVrrpTmpOperationsInetAddrType,
                      rcVrrpTmpOperationsVrId}
           ::= { rcVrrpTmpOperationsTable 1 }

       RcVrrpTmpOperationsEntry ::=
           SEQUENCE {
               rcVrrpTmpOperationsIfIndex                        InterfaceIndex,
               rcVrrpTmpOperationsInetAddrType                   InetAddressType,
               rcVrrpTmpOperationsVrId                           VrId,
               rcVrrpTmpOperationsVirtualMacAddr                 MacAddress,
               rcVrrpTmpOperationsState                          INTEGER,
               rcVrrpTmpOperationsPriority                       Integer32,
               rcVrrpTmpOperationsAddrCount                      Integer32,
               rcVrrpTmpOperationsMasterIpAddr                   InetAddress,
               rcVrrpTmpOperationsPrimaryIpAddr                  InetAddress,
               rcVrrpTmpOperationsAdvInterval                    TimeInterval,
               rcVrrpTmpOperationsPreemptMode                    TruthValue,
               rcVrrpTmpOperationsAcceptMode                     TruthValue,
               rcVrrpTmpOperationsUpTime                         TimeStamp,
               rcVrrpTmpOperationsStorageType                    StorageType,
               rcVrrpTmpOperationsRowStatus                      RowStatus
       }


	rcVrrpTmpOperationsIfIndex OBJECT-TYPE
            SYNTAX       InterfaceIndex
            MAX-ACCESS   not-accessible
            STATUS       current
            DESCRIPTION  "port interface index."
            ::= { rcVrrpTmpOperationsEntry 1 }

       rcVrrpTmpOperationsInetAddrType OBJECT-TYPE
           SYNTAX       InetAddressType
           MAX-ACCESS   not-accessible
           STATUS       current
           DESCRIPTION
               "The IP address type of RcVrrpTmpOperationsEntry. This value
                applies to both rcVrrpTmpOperationsMasterIpAddr and
                rcVrrpTmpOperationsPrimaryIpAddr."
           REFERENCE "RFC 4001"
           ::= { rcVrrpTmpOperationsEntry 2 }

       rcVrrpTmpOperationsVrId OBJECT-TYPE
           SYNTAX       VrId
           MAX-ACCESS   not-accessible
           STATUS       current
           DESCRIPTION
               "This object contains the Virtual Router Identifier
                (VRID)."
           REFERENCE "RFC 4001"
           ::= { rcVrrpTmpOperationsEntry 3 }

       rcVrrpTmpOperationsVirtualMacAddr OBJECT-TYPE
           SYNTAX       MacAddress
           MAX-ACCESS   read-only
           STATUS       current
           DESCRIPTION
               "The virtual MAC address of the virtual router.
                Although this object can be derived from the
                'rcVrrpTmpOperationsVrId' object, it is defined so that it
                is easily obtainable by a management application and
                can be included in VRRP-related SNMP notifications."
           REFERENCE "STD 58 RFC 2578"
           ::= { rcVrrpTmpOperationsEntry 4 }

       rcVrrpTmpOperationsState OBJECT-TYPE
           SYNTAX       INTEGER {
               initialize(1),
               backup(2),
               master(3)
           }
           MAX-ACCESS   read-only
           STATUS       current
           DESCRIPTION
               "The current state of the virtual router. This object
               has three defined values:
                 - `initialize', which indicates that the
                   virtual router is waiting for a startup event.
                 - `backup', which indicates the virtual router is
                   monitoring the availability of the master router.
                 - `master', which indicates that the virtual router
                   is forwarding packets for IP addresses that are
                   associated with this router."
           REFERENCE " RFC 3768"
           ::= { rcVrrpTmpOperationsEntry 5 }

       rcVrrpTmpOperationsPriority OBJECT-TYPE
           SYNTAX       Integer32 (0..255)
           MAX-ACCESS   read-create
           STATUS       current
           DESCRIPTION
               "This object specifies the priority to be used for the
               virtual router master election process.  Higher values
               imply higher priority.
               A priority of '0', although not settable, is sent by
               the master router to indicate that this router has
               ceased to participate in VRRP and a backup virtual
               router should transition to become a new master.
               A priority of 255 is used for the router that owns the
               associated IP address(es) for VRRP over IPv4 and hence
               not settable.
               A 'badValue(3)' should be returned when a user tries to
               set 0 or 255 for this object. "
           DEFVAL       { 100 }
           ::= { rcVrrpTmpOperationsEntry 6 }

       rcVrrpTmpOperationsAddrCount OBJECT-TYPE
           SYNTAX       Integer32 (0..255)
           MAX-ACCESS   read-only
           STATUS       current
           DESCRIPTION
               "The number of IP addresses that are associated with
               this virtual router.  This number is equal to the
               number of rows in the rcVrrpTmpAssociatedAddrTable that
               correspond to a given IP version/VRID/ifIndex."
           REFERENCE "RFC 3768 section 5.3.5.  Count IP Addrs"
           ::= { rcVrrpTmpOperationsEntry 7 }

       rcVrrpTmpOperationsMasterIpAddr OBJECT-TYPE
           SYNTAX       InetAddress
           MAX-ACCESS   read-only
           STATUS       current
           DESCRIPTION
               "The master router's real IP address. Master router
               would set this address to rcVrrpTmpOperationsPrimaryIpAddr
               while transitioning to master state. For backup
               routers, this is the IP address listed as the source in
               VRRP advertisement last received by this virtual
               router."
           REFERENCE " RFC 3768"
           ::= { rcVrrpTmpOperationsEntry 8 }

       rcVrrpTmpOperationsPrimaryIpAddr OBJECT-TYPE
           SYNTAX       InetAddress
           MAX-ACCESS   read-create
           STATUS       current
           DESCRIPTION
               "In the case where there are more than one IP
               Address (associated IP addresses) for a given
               `ifIndex', this object is used to specify the IP
               address that will become the
               rcVrrpTmpOperationsMasterIpAddr', should the virtual router
               transition from backup state to master."
           ::= { rcVrrpTmpOperationsEntry 9 }

       rcVrrpTmpOperationsAdvInterval OBJECT-TYPE
           SYNTAX       TimeInterval (1..4096)
           UNITS        "centiseconds"
           MAX-ACCESS   read-create
           STATUS       current
           DESCRIPTION
               "The time interval, in centiseconds, between sending
               advertisement messages. Only the master router sends
               VRRP advertisements."
           REFERENCE " RFC 3768 section 5.3.7"
           DEFVAL       { 100}
           ::= { rcVrrpTmpOperationsEntry 10 }

       rcVrrpTmpOperationsPreemptMode OBJECT-TYPE
           SYNTAX       TruthValue
           MAX-ACCESS   read-create
           STATUS       current
           DESCRIPTION
               "Controls whether a higher priority virtual router will
               preempt a lower priority master."
           REFERENCE " RFC 3768 section 6.1"
           DEFVAL       { true }
           ::= { rcVrrpTmpOperationsEntry 11 }

       rcVrrpTmpOperationsAcceptMode OBJECT-TYPE
           SYNTAX       TruthValue
           MAX-ACCESS   read-create
           STATUS       current
           DESCRIPTION
               "Controls whether a virtual router in Master state
               will accept packets addressed to the address owner's
               IPv6 address as its own if it is not the IPv6 address
               owner.  Default is False.
               This object is not relevant for rows representing VRRP
               over IPv4 and should be set to false."
           DEFVAL       { false }
           ::= { rcVrrpTmpOperationsEntry 12 }

       rcVrrpTmpOperationsUpTime OBJECT-TYPE
           SYNTAX       TimeStamp
           MAX-ACCESS   read-only
           STATUS       current
           DESCRIPTION
               "This is the value of the `sysUpTime' object when this
               virtual router (i.e., the `rcVrrpTmpOperationsState')
               transitioned out of `initialized'."
           REFERENCE " RFC 3768 section 6.1"
           ::= { rcVrrpTmpOperationsEntry 13 }

       rcVrrpTmpOperationsStorageType OBJECT-TYPE
          SYNTAX      StorageType
          MAX-ACCESS  read-create
          STATUS      current
          DESCRIPTION
              "The storage type for this conceptual row. Write access
              is not required. It is optional to support nonVolatile
              StorageType enumeration."
          REFERENCE " RFC4181 section 4.6.4"
          DEFVAL       { nonVolatile }
          ::= { rcVrrpTmpOperationsEntry 14 }

       rcVrrpTmpOperationsRowStatus OBJECT-TYPE
           SYNTAX       RowStatus
           MAX-ACCESS   read-create
           STATUS       current
           DESCRIPTION
               "The RowStatus variable should be used in accordance to
               installation and removal conventions for conceptual
               rows. When `rcVrrpTmpOperationsRowStatus' is set to
               active(1), no other objects in the conceptual row can
               be modified.
               To create a row in this table, a manager sets this
               object to either createAndGo(4) or createAndWait(5).
               Until instances of all corresponding columns are
               appropriately configured, the value of the
               corresponding instance of the `rcVrrpTmpOperationsRowStatus'
               column will be read as notReady(3).
               In particular, a newly created row cannot be made
               active(1) until (minimally) the corresponding instance
               of rcVrrpTmpOperationsInetAddrType, rcVrrpTmpOperationsVrId and
               rcVrrpTmpOperationsPrimaryIpAddr has been set and there is
               at least one active row in the
               `rcVrrpTmpAssociatedIpAddrTable' defining an associated
               IP address.
               notInService(2) should be used to administratively
               bring the row down.

               A typical order of operation to add a row is:
               1. Create a row in rcVrrpTmpOperationsTable with
               createAndWait(5).
               2. Create one or more corresponding rows in
               rcVrrpTmpAssociatedIpAddrTable.
               3. Populate the rcVrrpTmpOperationsEntry.
               4. set rcVrrpTmpOperationsRowStatus to active(1).

               A typical order of operation to delete an entry is:
               1. Set rcVrrpTmpOperationsRowStatus to notInService(2).
               2. Set the corresponding rows in
               rcVrrpTmpAssociatedIpAddrTable to destroy(6) to delete the
               entry.
               3. set rcVrrpTmpOperationsRowStatus to destroy(6) to delete
               the entry."
           ::= { rcVrrpTmpOperationsEntry 15 }

      --
      --  Vrrp Associated Address Table
      --

       rcVrrpTmpAssociatedIpAddrTable OBJECT-TYPE
           SYNTAX       SEQUENCE OF RcVrrpTmpAssociatedIpAddrEntry
           MAX-ACCESS   not-accessible
           STATUS       current
           DESCRIPTION
               "The table of addresses associated with this virtual
                router."
           ::= { rcVrrpTmpOperations 8 }

       rcVrrpTmpAssociatedIpAddrEntry OBJECT-TYPE
           SYNTAX       RcVrrpTmpAssociatedIpAddrEntry
           MAX-ACCESS   not-accessible
           STATUS       current
           DESCRIPTION
               "An entry in the table contains an IP address that is
               associated with a virtual router.  The number of rows
               for a given IP version, VrID and ifIndex will equal the
               number of IP addresses associated (e.g., backed up) by
               the virtual router (equivalent to
               'rcVrrpTmpOperationsIpAddrCount').
               Rows in the table cannot be modified unless the value
               of `rcVrrpTmpOperationsState' has transitioned to
               `initialize'."
           INDEX    { rcVrrpTmpOperationsIfIndex,rcVrrpTmpOperationsInetAddrType, rcVrrpTmpOperationsVrId,
                      rcVrrpTmpAssociatedIpAddr, rcVrrpTmpAssociatedIpAddrPrefixLength }
           ::= { rcVrrpTmpAssociatedIpAddrTable 1 }

       RcVrrpTmpAssociatedIpAddrEntry ::=
           SEQUENCE {
               rcVrrpTmpAssociatedIpAddr
                   InetAddress,
	       rcVrrpTmpAssociatedIpAddrPrefixLength
	           InetAddressPrefixLength,
               rcVrrpTmpAssociatedStorageType
                   StorageType,
               rcVrrpTmpAssociatedIpAddrRowStatus
                   RowStatus
       }

       rcVrrpTmpAssociatedIpAddr OBJECT-TYPE
           SYNTAX       InetAddress (SIZE(0|4|16))
           MAX-ACCESS   not-accessible
           STATUS       current
           DESCRIPTION
               "The assigned IP addresses that a virtual router is
               responsible for backing up.
               The size of this object is either 4 or 16 depending on
               rcVrrpTmpOperationsInetAddrType."
           REFERENCE "RFC 3768 Section 5.3.9"
           ::= { rcVrrpTmpAssociatedIpAddrEntry 1 }

rcVrrpTmpAssociatedIpAddrPrefixLength OBJECT-TYPE
           SYNTAX       InetAddressPrefixLength
	   MAX-ACCESS   not-accessible
	   STATUS       current
	   DESCRIPTION
	       "The length of the prefix (in bits)."
	   ::= { rcVrrpTmpAssociatedIpAddrEntry 2 }

      rcVrrpTmpAssociatedStorageType OBJECT-TYPE
          SYNTAX      StorageType
          MAX-ACCESS  read-create
          STATUS      current
          DESCRIPTION
              "The storage type for this conceptual row. Write access
              is not required. It is optional to support nonVolatile
              StorageType enumeration."
          REFERENCE " RFC4181 section 4.6.4"
          DEFVAL       { nonVolatile }
          ::= { rcVrrpTmpAssociatedIpAddrEntry 3 }

       rcVrrpTmpAssociatedIpAddrRowStatus OBJECT-TYPE
           SYNTAX       RowStatus
           MAX-ACCESS   read-create
           STATUS       current
           DESCRIPTION
               "The RowStatus variable, used according to
               installation and removal conventions for conceptual
               rows. To create a row in this table, a manager sets
               this object to either createAndGo(4) or
               createAndWait(5). Setting this object to active(1)
               results in the addition of an associated address for a
               virtual router. Setting this object to notInService(2)
               results in administratively bringing down the row.
               Destroying the entry or setting it to destroy(6)
               removes the associated address from the virtual router.
               The use of other values is implementation-dependent.
               Only rcVrrpTmpAssociatedStorageType can be modified when the
               row is in active(1) state for Implementations
               supporting write access to rcVrrpTmpAssociatedStorageType
               Implementations should not allow deletion of the last
               row corresponding to an active row in
               rcVrrpTmpOperationsTable.
               Refer to description of rcVrrpTmpOperationsRowStatus for a
               typical row creation and deletion scenarios."
           ::= { rcVrrpTmpAssociatedIpAddrEntry 4 }

      --
      --  Vrrp Router Statistics
      --

       rcVrrpTmpRouterChecksumErrors OBJECT-TYPE

           SYNTAX       Counter32
           MAX-ACCESS   read-only
           STATUS       current
           DESCRIPTION
               "The total number of VRRP packets received with an
                invalid VRRP checksum value."
           REFERENCE "RFC3768 Section 5.3.8"
           ::= { rcVrrpTmpStatistics 1 }

       rcVrrpTmpRouterVersionErrors OBJECT-TYPE
           SYNTAX       Counter32
           MAX-ACCESS   read-only
           STATUS       current
           DESCRIPTION
               "The total number of VRRP packets received with an
               unknown or unsupported version number."
           REFERENCE "RFC3768 Section 5.3.1"
           ::= { rcVrrpTmpStatistics 2 }

       rcVrrpTmpRouterVrIdErrors OBJECT-TYPE
           SYNTAX       Counter32
           MAX-ACCESS   read-only
          STATUS       current
           DESCRIPTION
               "The total number of VRRP packets received with an
               invalid VRID for this virtual router."
           REFERENCE "RFC3768 Section 5.3.3"
           ::= { rcVrrpTmpStatistics 3 }

      --
      --  Vrrp Router Statistics Table
      --

      rcVrrpTmpRouterStatisticsTable OBJECT-TYPE
           SYNTAX       SEQUENCE OF RcVrrpTmpRouterStatisticsEntry
           MAX-ACCESS   not-accessible
           STATUS       current
           DESCRIPTION
               "Table of virtual router statistics."
           ::= { rcVrrpTmpStatistics 5 }

       rcVrrpTmpRouterStatisticsEntry OBJECT-TYPE
           SYNTAX       RcVrrpTmpRouterStatisticsEntry
           MAX-ACCESS   not-accessible
           STATUS       current
           DESCRIPTION
               "An entry in the table, containing statistics
               information about a given virtual router."
           AUGMENTS    { rcVrrpTmpOperationsEntry }
           ::= { rcVrrpTmpRouterStatisticsTable 1 }

       RcVrrpTmpRouterStatisticsEntry ::=
           SEQUENCE {
               rcVrrpTmpStatisticsMasterTransitions                   Counter32,
               rcVrrpTmpStatisticsRcvdAdvertisements                  Counter32,
               rcVrrpTmpStatisticsAdvIntervalErrors                   Counter32,
               rcVrrpTmpStatisticsIpTtlErrors                         Counter32,
               rcVrrpTmpStatisticsRcvdPriZeroPackets                  Counter32,
               rcVrrpTmpStatisticsSentPriZeroPackets                  Counter32,
               rcVrrpTmpStatisticsRcvdInvalidTypePkts                 Counter32,
               rcVrrpTmpStatisticsAddressListErrors                   Counter32,
               rcVrrpTmpStatisticsPacketLengthErrors                  Counter32,
               rcVrrpTmpStatisticsRcvdInvalidAuthentications          Counter32,
               rcVrrpTmpStatisticsDiscontinuityTime                   TimeStamp,
               rcVrrpTmpStatisticsRefreshRate                         Integer32
           }

       rcVrrpTmpStatisticsMasterTransitions OBJECT-TYPE
           SYNTAX       Counter32
           MAX-ACCESS   read-only
           STATUS       current
           DESCRIPTION
               "The total number of times that this virtual router's
               state has transitioned to MASTER.
               Discontinuities in the value of this counter can occur
               at re-initialization of the management system, and at
               other times as indicated by the value of
               rcVrrpTmpStatisticsDiscontinuityTime."
           ::= { rcVrrpTmpRouterStatisticsEntry 1 }

       rcVrrpTmpStatisticsRcvdAdvertisements OBJECT-TYPE
           SYNTAX       Counter32
           MAX-ACCESS   read-only
           STATUS       current
           DESCRIPTION
               "The total number of VRRP advertisements received by
               this virtual router.
               Discontinuities in the value of this counter can occur
               at re-initialization of the management system, and at
               other times as indicated by the value of
               rcVrrpTmpStatisticsDiscontinuityTime."
           ::= { rcVrrpTmpRouterStatisticsEntry 2 }

       rcVrrpTmpStatisticsAdvIntervalErrors OBJECT-TYPE
           SYNTAX       Counter32
           MAX-ACCESS   read-only
           STATUS       current
           DESCRIPTION
               "The total number of VRRP advertisement packets
               received for which the advertisement interval is
               different than the one configured for the local virtual
               router.
               Discontinuities in the value of this counter can occur
               at re-initialization of the management system, and at
               other times as indicated by the value of
               rcVrrpTmpStatisticsDiscontinuityTime."
           ::= { rcVrrpTmpRouterStatisticsEntry 3 }

       rcVrrpTmpStatisticsIpTtlErrors OBJECT-TYPE
           SYNTAX       Counter32
           MAX-ACCESS   read-only
           STATUS       current
           DESCRIPTION
               "The total number of VRRP packets received by the
               Virtual router with IPv4 TTL (for VRRP over IPv4) or
               IPv6 Hop Limit (for VRRP over IPv6) not equal to 255.
               Discontinuities in the value of this counter can occur
               at re-initialization of the management system, and at
               other times as indicated by the value of
               rcVrrpTmpStatisticsDiscontinuityTime."
           REFERENCE "RFC3768 Section 5.2.3"
           ::= { rcVrrpTmpRouterStatisticsEntry 4 }

       rcVrrpTmpStatisticsRcvdPriZeroPackets OBJECT-TYPE
           SYNTAX       Counter32
           MAX-ACCESS   read-only
           STATUS       current
           DESCRIPTION
               "The total number of VRRP packets received by the
               virtual router with a priority of '0'.
               Discontinuities in the value of this counter can occur
               at re-initialization of the management system, and at
               other times as indicated by the value of
               rcVrrpTmpStatisticsDiscontinuityTime."
           REFERENCE "RFC3768 Section 5.3.4"
           ::= { rcVrrpTmpRouterStatisticsEntry 5 }

       rcVrrpTmpStatisticsSentPriZeroPackets OBJECT-TYPE
           SYNTAX       Counter32
           MAX-ACCESS   read-only
           STATUS       current
           DESCRIPTION
               "The total number of VRRP packets sent by the virtual
               router with a priority of '0'.
               Discontinuities in the value of this counter can occur
               at re-initialization of the management system, and at
               other times as indicated by the value of
               rcVrrpTmpStatisticsDiscontinuityTime."
           REFERENCE "RFC3768 Section 5.3.4"
           ::= { rcVrrpTmpRouterStatisticsEntry 6 }

       rcVrrpTmpStatisticsRcvdInvalidTypePkts OBJECT-TYPE
           SYNTAX       Counter32
           MAX-ACCESS   read-only
           STATUS       current
           DESCRIPTION
               "The number of VRRP packets received by the virtual
               router with an invalid value in the 'type' field.
               Discontinuities in the value of this counter can occur
               at re-initialization of the management system, and at
               other times as indicated by the value of
               rcVrrpTmpStatisticsDiscontinuityTime."
           ::= { rcVrrpTmpRouterStatisticsEntry 7 }

       rcVrrpTmpStatisticsAddressListErrors OBJECT-TYPE
           SYNTAX       Counter32
           MAX-ACCESS   read-only
           STATUS       current
           DESCRIPTION
               "The total number of packets received for which the
               address list does not match the locally configured list
               for the virtual router.
               Discontinuities in the value of this counter can occur
               at re-initialization of the management system, and at
               other times as indicated by the value of
               rcVrrpTmpStatisticsDiscontinuityTime."
           ::= { rcVrrpTmpRouterStatisticsEntry 8 }

       rcVrrpTmpStatisticsPacketLengthErrors OBJECT-TYPE
           SYNTAX       Counter32
           MAX-ACCESS   read-only
           STATUS       current
           DESCRIPTION
               "The total number of packets received with a packet
               length less than the length of the VRRP header.
               Discontinuities in the value of this counter can occur
               at re-initialization of the management system, and at
               other times as indicated by the value of
               rcVrrpTmpStatisticsDiscontinuityTime."
           ::= { rcVrrpTmpRouterStatisticsEntry 9 }

      rcVrrpTmpStatisticsRcvdInvalidAuthentications OBJECT-TYPE
        SYNTAX       Counter32
        MAX-ACCESS   read-only
        STATUS       current
        DESCRIPTION
            "The total number of packets received with an unknown
             authentication type."
        REFERENCE "RFC3768 Section 5.3.6"
        ::= { rcVrrpTmpRouterStatisticsEntry 10 }

      rcVrrpTmpStatisticsDiscontinuityTime OBJECT-TYPE
          SYNTAX     TimeStamp
          MAX-ACCESS read-only
          STATUS     current
          DESCRIPTION
              "The value of sysUpTime on the most recent occasion at
               which any one or more of this entry's counters suffered
               a discontinuity.
               If no such discontinuities have occurred since the last  
               re-initialization of the local management subsystem,
               then this object contains a zero value."
          ::= { rcVrrpTmpRouterStatisticsEntry 11 }

      rcVrrpTmpStatisticsRefreshRate OBJECT-TYPE
          SYNTAX     Integer32
          UNITS "milli-seconds"
          MAX-ACCESS read-only
          STATUS     current
          DESCRIPTION
              "The minimum reasonable polling interval for this entry.
               This object provides an indication of the minimum
               Amount of time required to update the counters in this
               entry."
          ::= { rcVrrpTmpRouterStatisticsEntry 12 }


      --
      --  Start of global statistics based on IP address type
      --
      rcVrrpTmpRouterGlobalStatisticsTable OBJECT-TYPE
	  SYNTAX       SEQUENCE OF RcVrrpTmpRouterGlobalStatisticsEntry
	  MAX-ACCESS   not-accessible
	  STATUS       current
	  DESCRIPTION
	      "Table of virtual router global statistics. It shows the 
	       global statistics, depending on IP address type."
	  ::= { rcVrrpTmpStatistics 6 }

      rcVrrpTmpRouterGlobalStatisticsEntry OBJECT-TYPE
	  SYNTAX       RcVrrpTmpRouterGlobalStatisticsEntry
	  MAX-ACCESS   not-accessible
	  STATUS       current
	  DESCRIPTION
	      "An entry in the table, containing global statistics 
	       information about a given IP type."
	  INDEX    { rcVrrpTmpRouterGlobalStatisticsInetAddrType}
	  ::= { rcVrrpTmpRouterGlobalStatisticsTable 1 }

      RcVrrpTmpRouterGlobalStatisticsEntry ::=
      	  SEQUENCE {
	  	rcVrrpTmpRouterGlobalStatisticsInetAddrType    InetAddressType,
		rcVrrpTmpRouterGlobalStatisticsChecksumErrors  Counter64,
		rcVrrpTmpRouterGlobalStatisticsVersionErrors   Counter64,
		rcVrrpTmpRouterGlobalStatisticsVrIdErrors      Counter64
	  }

      rcVrrpTmpRouterGlobalStatisticsInetAddrType OBJECT-TYPE
	  SYNTAX       InetAddressType
	  MAX-ACCESS   not-accessible
	  STATUS       current
	  DESCRIPTION
	      "The IP address type of rcVrrpTmpRouterGlobalStatisticsEntry. 
	       It can be either IPv4 or IPv6"
	  ::= { rcVrrpTmpRouterGlobalStatisticsEntry 1 }

      rcVrrpTmpRouterGlobalStatisticsChecksumErrors OBJECT-TYPE
	  SYNTAX       Counter64
	  MAX-ACCESS   read-only
	  STATUS       current
	  DESCRIPTION
	      "The total number of VRRP packets received with 
	       an invalid VRRP checksum value."
	  ::= { rcVrrpTmpRouterGlobalStatisticsEntry 2 }

      rcVrrpTmpRouterGlobalStatisticsVersionErrors OBJECT-TYPE
	  SYNTAX       Counter64
	  MAX-ACCESS   read-only
	  STATUS       current
	  DESCRIPTION
	      "The total number of VRRP packets received with an 
	       unknown or unsupported version number."
	  ::= { rcVrrpTmpRouterGlobalStatisticsEntry 3 }

      rcVrrpTmpRouterGlobalStatisticsVrIdErrors OBJECT-TYPE
	  SYNTAX       Counter64
	  MAX-ACCESS   read-only
	  STATUS       current
	  DESCRIPTION
	      "The total number of VRRP packets received with an 
	       invalid VRID for this virtual router."
      ::= { rcVrrpTmpRouterGlobalStatisticsEntry 4 }

  
      --
      --   Notification Definitions
      --
      rcVrrpTmpNotifications   OBJECT IDENTIFIER ::= { rcVrrpTmpMib 0 }

      ---
      --- Objects used in the notifications
      ---

      rcVrrpTmpNewMasterReason OBJECT-TYPE
           SYNTAX        INTEGER {
               notmaster (0),
               priority  (1),
               preempted (2),
               masterNoResponse (3)
           }
           MAX-ACCESS   read-only
           STATUS       current
           DESCRIPTION
               "This indicates the reason for rcVrrpTmpNewMaster trap.
               Used by rcVrrpTmpTrapNewMaster trap. The object can be
               polled if the rcVrrpTmpNewMaster trap is lost to identify
               the reason for transmission. Backup router should
               return notmaster(0) when pooled. "
           ::= { rcVrrpTmpOperations 9 }

      rcVrrpTmpTrapProtoErrReason OBJECT-TYPE
           SYNTAX        INTEGER {
               hopLimitError (0),
               versionError  (1),
               checksumError (2),
               vridError(3)
           }
           MAX-ACCESS   accessible-for-notify
           STATUS       current
           DESCRIPTION
               "This indicates the reason for protocol error trap.
               Used by rcVrrpTmpTrapProtoError trap."
           ::= { rcVrrpTmpOperations 10 }


       rcVrrpTmpTrapNewMaster NOTIFICATION-TYPE
           OBJECTS      { rcVrrpTmpOperationsMasterIpAddr,
                          rcVrrpTmpNewMasterReason
                        }
           STATUS       current
           DESCRIPTION
               "The newMaster trap indicates that the sending agent
               has transitioned to 'Master' state."
           ::= { rcVrrpTmpNotifications 1 }

       rcVrrpTmpTrapProtoError NOTIFICATION-TYPE
           OBJECTS      { rcVrrpTmpTrapProtoErrReason
                        }
           STATUS       current
           DESCRIPTION
               "The error trap indicates that the sending agent has
               encountered the protocol error indicated by
               rcVrrpTmpTrapProtoErrorReason."
           ::= { rcVrrpTmpNotifications 3 }
END

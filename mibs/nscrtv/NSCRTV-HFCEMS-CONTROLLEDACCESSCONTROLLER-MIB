NSCRTV-HFCEMS-CONTROLLEDACCESSCONTROLLER-MIB DEFINITIONS ::= BEGIN


IMPORTS
    OBJECT-TYPE
        FROM RFC-1212
    DisplayString
        FROM RFC1213-MIB
    cacIdent
        FROM NSCRTV-ROOT;

    cacVendorOID OBJECT-TYPE
        SYNTAX OBJECT IDENTIFIER
        ACCESS read-only
        STATUS optional
        DESCRIPTION
            ""
        ::= { cacIdent 1 }



    cacPowerType OBJECT-TYPE
        SYNTAX INTEGER {v60(1),v220(2),other(3)}
        ACCESS read-only
        STATUS mandatory
        DESCRIPTION
            ""
        ::= { cacIdent 2 }
    
    cacACPowerVoltage OBJECT-TYPE
        SYNTAX INTEGER (0..32767)
        ACCESS read-only
        STATUS optional
        DESCRIPTION
            ""
        ::= { cacIdent 3}
    
    cacMainDCPowerVoltage OBJECT-TYPE
        SYNTAX INTEGER ( -32768..32767 )
        ACCESS read-only
        STATUS mandatory
        DESCRIPTION
            ""
        ::= { cacIdent 4 }
    
    cacInsideAmpOutputRFLevel OBJECT-TYPE
        SYNTAX INTEGER ( 0..127 )
        ACCESS read-only
        STATUS mandatory
        DESCRIPTION
            ""
        ::= { cacIdent 5 }
    
    cacUpStreamControl OBJECT-TYPE
        SYNTAX INTEGER { on (1), off (2) }
        ACCESS read-write
        STATUS mandatory
        DESCRIPTION
            ""
        ::= { cacIdent 6 }
    
    cacOutputPortNumber OBJECT-TYPE
        SYNTAX INTEGER ( 1..127 )
        ACCESS read-only
        STATUS mandatory
        DESCRIPTION
            ""
        ::= { cacIdent 7 }
    
    cacPortTable OBJECT-TYPE
        SYNTAX SEQUENCE OF CacPortTableEntry
        ACCESS not-accessible
        STATUS mandatory
        DESCRIPTION
            ""
        ::= { cacIdent 8 }
    
    cacPortTableEntry OBJECT-TYPE
        SYNTAX CacPortTableEntry
        ACCESS not-accessible
        STATUS mandatory
        DESCRIPTION
            ""
        INDEX { cacPortIndex }
        ::= { cacPortTable 1 }
    
    CacPortTableEntry ::=
        SEQUENCE
        {
            cacPortIndex
                INTEGER,
            cacPortControl
                OCTET STRING,
            cacPortRFLevel
                INTEGER
        }
    
    cacPortIndex OBJECT-TYPE
        SYNTAX INTEGER (1..127)
        ACCESS read-only
        STATUS mandatory
        DESCRIPTION
            ""
        ::= { cacPortTableEntry 1 }
    
    cacPortControl OBJECT-TYPE
        SYNTAX OCTET STRING
        ACCESS read-write
        STATUS mandatory
        DESCRIPTION
            ""
        ::= { cacPortTableEntry 2 }
    
    cacPortRFLevel OBJECT-TYPE
        SYNTAX INTEGER ( 0..127 )
        ACCESS read-only
        STATUS optional
        DESCRIPTION
            ""
        ::= { cacPortTableEntry 3 }
    
    cacAllPortsState OBJECT-TYPE
        SYNTAX OCTET STRING (SIZE(1..255))
        ACCESS read-write
        STATUS optional
        DESCRIPTION
            ""
        ::= { cacIdent 9 }
    
    cacPortStateReset OBJECT-TYPE
        SYNTAX INTEGER
        ACCESS read-write
        STATUS optional
        DESCRIPTION
            ""
        ::= { cacIdent 10 }

END

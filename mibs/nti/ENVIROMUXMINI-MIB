ENVIROMUXMINI-MIB DEFINITIONS ::= BEGIN
IMPORTS
   OBJECT-GROUP, NOTIFICATION-GROUP             FROM SNMPv2-CONF
   MODULE-IDENTITY, OBJECT-TYPE, OBJECT-IDENTITY,
   enterprises, NOTIFICATION-TYPE               FROM SNMPv2-SMI
   DisplayString, TEXTUAL-CONVENTION    	    FROM SNMPv2-TC;

enviromuxMini  MODULE-IDENTITY
     LAST-UPDATED "200909241400Z"
     ORGANIZATION "Network Technologies Inc."
     CONTACT-INFO 
         "Adrian Bica - Engineering
         
         Postal: 1275 Danner Dr,
                 Aurora, OH 442022
                 US
                 
             Tel: 330-562-7070
             Fax: 330-562-1999
             
             WEB: www.nti1.com"
     DESCRIPTION  "ENVIROMUX-MINI MIB module"
     REVISION     "200909241400Z"
     DESCRIPTION  "Rev. 1.2. Individual traps for return from alert"
     REVISION     "200704131400Z"
     DESCRIPTION  "Rev. 1.1"
     REVISION     "200503301400Z" 
     DESCRIPTION  "Rev. 1.0"
     ::= { hardware 3 }
      
-- the root of the subtree for Network Technologies Inc
nti				        OBJECT IDENTIFIER ::= {enterprises 3699}

-- subtree for products
products		        OBJECT IDENTIFIER ::= {nti 1}
hardware		        OBJECT IDENTIFIER ::= {products 1}
software		        OBJECT IDENTIFIER ::= {products 2}
otherProduct            OBJECT IDENTIFIER ::= {hardware 200}
monitoring		        OBJECT IDENTIFIER ::= {enviromuxMini 1}
administration		    OBJECT IDENTIFIER ::= {enviromuxMini 2}
envTraps                OBJECT IDENTIFIER ::= {enviromuxMini 100}
envGroups               OBJECT IDENTIFIER ::= {enviromuxMini 200}
temperatureSensor1      OBJECT IDENTIFIER ::= {monitoring 1}
temperatureSensor2      OBJECT IDENTIFIER ::= {monitoring 2}
humiditySensor1         OBJECT IDENTIFIER ::= {monitoring 3}
humiditySensor2         OBJECT IDENTIFIER ::= {monitoring 4}
dryContact1             OBJECT IDENTIFIER ::= {monitoring 5}
dryContact2             OBJECT IDENTIFIER ::= {monitoring 6}
dryContact3             OBJECT IDENTIFIER ::= {monitoring 7}
dryContact4             OBJECT IDENTIFIER ::= {monitoring 8}
waterSensor             OBJECT IDENTIFIER ::= {monitoring 9}
hostSystem		        OBJECT IDENTIFIER ::= {administration 1}	
temperatureSensor1Adm   OBJECT IDENTIFIER ::= {administration 2}
temperatureSensor2Adm   OBJECT IDENTIFIER ::= {administration 3}
humiditySensor1Adm      OBJECT IDENTIFIER ::= {administration 4}
humiditySensor2Adm      OBJECT IDENTIFIER ::= {administration 5}
dryContact1Adm          OBJECT IDENTIFIER ::= {administration 6}
dryContact2Adm          OBJECT IDENTIFIER ::= {administration 7}
dryContact3Adm          OBJECT IDENTIFIER ::= {administration 8}
dryContact4Adm          OBJECT IDENTIFIER ::= {administration 9}
waterSensorAdm          OBJECT IDENTIFIER ::= {administration 10}

-- textual conventions
DecimalPointValue ::= TEXTUAL-CONVENTION
    DISPLAY-HINT    "d-1"
    STATUS          current
    DESCRIPTION     
        "Display integer values using a decimal point before last digit"
    SYNTAX          INTEGER (-1000..1000)

-- groups
unitGroup               OBJECT-GROUP
    OBJECTS             {version,
                        temperatureSensor1CurrentValue, temperatureSensor1Alert, temperatureSensor1Name, temperatureSensor1Unit, 
                        temperatureSensor1LowThreshold, temperatureSensor1HighThreshold, 
                        temperatureSensor2CurrentValue, temperatureSensor2Alert, temperatureSensor2Name, temperatureSensor2Unit,
                        temperatureSensor2LowThreshold, temperatureSensor2HighThreshold,
                        humiditySensor1CurrentValue, humiditySensor1Alert, humiditySensor1Name, humiditySensor1LowThreshold, humiditySensor1HighThreshold,
                        humiditySensor2CurrentValue, humiditySensor2Alert, humiditySensor2Name, humiditySensor2LowThreshold, humiditySensor2HighThreshold,
                        dryContact1Status, dryContact1Alert, dryContact1Name, dryContact1AlertStatus, 
                        dryContact2Status, dryContact2Alert, dryContact2Name, dryContact2AlertStatus,
                        dryContact3Status, dryContact3Alert, dryContact3Name, dryContact3AlertStatus,
                        dryContact4Status, dryContact4Alert, dryContact4Name, dryContact4AlertStatus,
                        waterStatus, waterAlert, waterName, waterAlertStatus,
                        sysName, sysLocation, sysIP, sysMask, sysGateway, sysDNS }
    STATUS              current
    DESCRIPTION         "System parameters group"
    ::= {envGroups 1}

envTrapsGroup           NOTIFICATION-GROUP
    NOTIFICATIONS       { temperatureSensor1Trap, temperatureSensor2Trap, humiditySensor1Trap, humiditySensor2Trap,
                        dryContactSensor1Trap, dryContactSensor2Trap, dryContactSensor3Trap, dryContactSensor4Trap,
                        waterSensor1Trap, logTrap, overflowTrap }
    STATUS              current
    DESCRIPTION         "Traps group"
    ::= {envGroups 2}

-- code version
version     OBJECT-TYPE
    SYNTAX  DisplayString
    MAX-ACCESS	read-only
    STATUS  current
    DESCRIPTION
        "Code version"
    ::= {enviromuxMini 3}         

-- temperature 1   

temperatureSensor1CurrentValue  OBJECT-TYPE
    SYNTAX  DecimalPointValue
	MAX-ACCESS	read-only
    STATUS  current
    DESCRIPTION
        "Current value of the temperature sensor connected to port 1 in tenths of degrees .  
        This port is the right RJ-45 sensor port.  The value is expressed in the units 
        indicated in temperatureSensor1Unit.  
        This object is only applicable if a temperature sensor is connected to port 1."
::= {temperatureSensor1 1}

temperatureSensor1Alert  OBJECT-TYPE
    SYNTAX  INTEGER {off(0), on(1)}
	MAX-ACCESS	read-only
    STATUS  current
    DESCRIPTION
        "Current alert status of the temperature sensor connected to port 1.  
        This port is the right RJ-45 sensor port.  A value of 0 indicates 
        that the sensor has not crossed either of its specified thresholds, 
        while a value of 1 indicates that it has.  
        This object is only applicable if a temperature sensor is connected to port 1."
::= {temperatureSensor1 2}
    
temperatureSensor1Name  OBJECT-TYPE
    SYNTAX  DisplayString
	MAX-ACCESS	read-write
    STATUS  current
    DESCRIPTION
        "Current name assigned to the temperature sensor connected to port 1.  
        This port is the right RJ-45 sensor port. This value corresponds directly 
        with the name entered in the configuration page for this sensor.  
        This object is only applicable if a temperature sensor is connected to port 1."
::= {temperatureSensor1Adm 1}           

temperatureSensor1Unit  OBJECT-TYPE
    SYNTAX  DisplayString
	MAX-ACCESS	read-write
    STATUS  current
    DESCRIPTION
        "Temperature units for the value of the temperature sensor connected to port 1.  
        This port is the right RJ-45 sensor port.  The unit may either be Fahrenheit or Celsius, 
        and corresponds directly with the unit chosen on the configuration page for this sensor.  
        This object is only applicable if a temperature sensor is connected to port 1 or 2."
::= {temperatureSensor1Adm 2}

temperatureSensor1LowThreshold  OBJECT-TYPE
    SYNTAX  DisplayString
	MAX-ACCESS	read-write
    STATUS  current
    DESCRIPTION
        "Low threshold assigned to the temperature sensor connected to port 1.  
        This port is the right RJ-45 sensor port. This value corresponds directly 
        with the low threshold value entered in the configuration page for this sensor.  
        This object is only applicable if a temperature sensor is connected to port 1."
::= {temperatureSensor1Adm 3}           

temperatureSensor1HighThreshold  OBJECT-TYPE
    SYNTAX  DisplayString
	MAX-ACCESS	read-write
    STATUS  current
    DESCRIPTION
        "High threshold assigned to the temperature sensor connected to port 1.  
        This port is the right RJ-45 sensor port. This value corresponds directly 
        with the high threshold value entered in the configuration page for this sensor.  
        This object is only applicable if a temperature sensor is connected to port 1."
::= {temperatureSensor1Adm 4}

-- temperature 2          
    
temperatureSensor2CurrentValue  OBJECT-TYPE
    SYNTAX  DecimalPointValue
	MAX-ACCESS	read-only
    STATUS  current
    DESCRIPTION
        "Current value of the temperature sensor connected to port 2 in tenths of degrees .  
        This port is the left RJ-45 sensor port.  The value is expressed in the units 
        indicated in temperatureSensor2Unit.  
        This object is only applicable if a temperature sensor is connected to port 2."
::= {temperatureSensor2 1}

temperatureSensor2Alert  OBJECT-TYPE
    SYNTAX  INTEGER {off(0), on(1)}
	MAX-ACCESS	read-only
    STATUS  current
    DESCRIPTION
        "Current alert status of the temperature sensor connected to port 2.  
        This port is the left RJ-45 sensor port.  A value of 0 indicates 
        that the sensor has not crossed either of its specified thresholds, 
        while a value of 1 indicates that it has.  
        This object is only applicable if a temperature sensor is connected to port 2."
::= {temperatureSensor2 2}

temperatureSensor2Name  OBJECT-TYPE
    SYNTAX  DisplayString
	MAX-ACCESS	read-write
    STATUS  current
    DESCRIPTION
        "Current name assigned to the temperature sensor connected to port 2.  
        This port is the left RJ-45 sensor port. This value corresponds directly 
        with the name entered in the configuration page for this sensor.  
        This object is only applicable if a temperature sensor is connected to port 2."
::= {temperatureSensor2Adm 1} 

temperatureSensor2Unit  OBJECT-TYPE
    SYNTAX  DisplayString
	MAX-ACCESS	read-write
    STATUS  current
    DESCRIPTION
        "Temperature units for the value of the temperature sensor connected to port 2.  
        This port is the left RJ-45 sensor port.  The unit may either be Fahrenheit or Celsius, 
        and corresponds directly with the unit chosen on the configuration page for this sensor.  
        This object is only applicable if a temperature sensor is connected to port 1 or 2."
::= {temperatureSensor2Adm 2}

temperatureSensor2LowThreshold  OBJECT-TYPE
    SYNTAX  DisplayString
	MAX-ACCESS	read-write
    STATUS  current
    DESCRIPTION
         "Low threshold assigned to the temperature sensor connected to port 2.  
         This port is the left RJ-45 sensor port. This value corresponds directly 
         with the low threshold value entered in the configuration page for this sensor.  
         This object is only applicable if a temperature sensor is connected to port 2."
::= {temperatureSensor2Adm 3}           

temperatureSensor2HighThreshold  OBJECT-TYPE
    SYNTAX  DisplayString
	MAX-ACCESS	read-write
    STATUS  current
    DESCRIPTION
        "High threshold assigned to the temperature sensor connected to port 2.  
        This port is the left RJ-45 sensor port. This value corresponds directly 
        with the high threshold value entered in the configuration page for this sensor.  
        This object is only applicable if a temperature sensor is connected to port 2."
::= {temperatureSensor2Adm 4}  

-- humidity 1

humiditySensor1CurrentValue  OBJECT-TYPE
    SYNTAX  DecimalPointValue
	MAX-ACCESS	read-only
    STATUS  current
    DESCRIPTION
        "Current integer value in tenths of percents of the humidity sensor connected to port 1.  
        This port is the right RJ-45 sensor port.  The value corresponds directly with 
        the value displayed on the summary page and the status page for this sensor.  
        This object is only applicable if a humidity sensor is connected to port 1."
::= {humiditySensor1 1}

humiditySensor1Alert  OBJECT-TYPE
    SYNTAX  INTEGER {off(0), on(1)}
	MAX-ACCESS	read-only
    STATUS  current
    DESCRIPTION
        "Current alert status of the humidity sensor connected to port 1.  
        This port is the right RJ-45 sensor port.  A value of 0 indicates 
        that the sensor has not crossed either of its specified thresholds, 
        while a value of 1 indicates that it has.  
        This object is only applicable if a humidity sensor is connected to port 1."
::= {humiditySensor1 2}

humiditySensor1Name  OBJECT-TYPE
    SYNTAX  DisplayString
	MAX-ACCESS	read-write
    STATUS  current
    DESCRIPTION
        "Current name assigned to the humidity sensor connected to port 1.  
        This port is the right RJ-45 sensor port. This value corresponds directly 
        with the name entered in the configuration page for this sensor.  
        This object is only applicable if a humidity sensor is connected to port 1."
::= {humiditySensor1Adm 1}            

humiditySensor1LowThreshold  OBJECT-TYPE
    SYNTAX  DisplayString
	MAX-ACCESS	read-write
    STATUS  current
    DESCRIPTION
        "Low threshold assigned to the humidity sensor connected to port 1.  
        This port is the right RJ-45 sensor port. This value corresponds directly 
        with the low threshold value entered in the configuration page for this sensor.  
        This object is only applicable if a humidity sensor is connected to port 1."
::= {humiditySensor1Adm 2}           

humiditySensor1HighThreshold  OBJECT-TYPE
    SYNTAX  DisplayString
	MAX-ACCESS	read-write
    STATUS  current
    DESCRIPTION
        "High threshold assigned to the humidity sensor connected to port 1.  
        This port is the right RJ-45 sensor port. This value corresponds directly 
        with the high threshold value entered in the configuration page for this sensor.  
        This object is only applicable if a humidity sensor is connected to port 1."
::= {humiditySensor1Adm 3}

-- humidity 2

humiditySensor2CurrentValue  OBJECT-TYPE
    SYNTAX  DecimalPointValue
	MAX-ACCESS	read-only
    STATUS  current
    DESCRIPTION
        "Current integer value in tenths of percents of the humidity sensor connected to port 2.  
        This port is the left RJ-45 sensor port.  The value corresponds directly 
        with the value displayed on the summary page and the status page for this sensor.  
        This object is only applicable if a humidity sensor is connected to port 2."
::= {humiditySensor2 1}

humiditySensor2Alert  OBJECT-TYPE
    SYNTAX  INTEGER {off(0), on(1)}
	MAX-ACCESS	read-only
    STATUS  current
    DESCRIPTION
        "Current alert status of the humidity sensor connected to port 2.  
        This port is the left RJ-45 sensor port.  A value of 0 indicates 
        that the sensor has not crossed either of its specified thresholds, 
        while a value of 1 indicates that it has.  
        his object is only applicable if a humidity sensor is connected to port 2."
::= {humiditySensor2 2}

humiditySensor2Name  OBJECT-TYPE
    SYNTAX  DisplayString
	MAX-ACCESS	read-write
    STATUS  current
    DESCRIPTION
        "Current name assigned to the humidity sensor connected to port 2.  
        This port is the left RJ-45 sensor port. This value corresponds directly 
        with the name entered in the configuration page for this sensor.  
        This object is only applicable if a humidity sensor is connected to port 2."
::= {humiditySensor2Adm 1}            
    
humiditySensor2LowThreshold  OBJECT-TYPE
    SYNTAX  DisplayString
	MAX-ACCESS	read-write
    STATUS  current
    DESCRIPTION
        "Low threshold assigned to the humidity sensor connected to port 2.  
        This port is the left RJ-45 sensor port. This value corresponds directly 
        with the low threshold value entered in the configuration page for this sensor.  
        This object is only applicable if a humidity sensor is connected to port 2."
::= {humiditySensor2Adm 2}           

humiditySensor2HighThreshold  OBJECT-TYPE
    SYNTAX  DisplayString
	MAX-ACCESS	read-write
    STATUS  current
    DESCRIPTION
        "High threshold assigned to the humidity sensor connected to port 1.  
        This port is the right RJ-45 sensor port. This value corresponds directly 
        with the high threshold value entered in the configuration page for this sensor.  
        This object is only applicable if a humidity sensor is connected to port 1."
::= {humiditySensor2Adm 3}             

-- dry contact 1

dryContact1Status  OBJECT-TYPE
    SYNTAX  INTEGER {open(0), closed(1)}
	MAX-ACCESS	read-only
    STATUS  current
    DESCRIPTION
        "Current integer value of the dry contact sensor connected to port 1.  
        A value of 0 represents OPEN, and a value of 1 represents CLOSED.  
        The value corresponds directly with the value displayed on the 
        summary page and the status page for this sensor.  
        This object is only applicable if a dry contact sensor is connected to port 1."
::= {dryContact1 1}

dryContact1Alert  OBJECT-TYPE
    SYNTAX  INTEGER {off(0), on(1)}
	MAX-ACCESS	read-only
    STATUS  current
    DESCRIPTION
        "Current alert status of the dry contact sensor connected to port 1.  
        A value of 0 indicates that the sensor has not been set to its alert condition, 
        while a value of 1 indicates that it has.  
        This object is only applicable if a dry contact sensor is connected to port 1."
::= {dryContact1 2}

dryContact1Name  OBJECT-TYPE
    SYNTAX  DisplayString
	MAX-ACCESS	read-write
    STATUS  current
    DESCRIPTION
        "Current name assigned to the dry contact sensor connected to port 1.  
        This value corresponds directly with the name entered in the configuration page for this sensor.  
        This object is only applicable if a dry contact sensor is connected to port 1."
::= {dryContact1Adm 1}            

dryContact1AlertStatus  OBJECT-TYPE
    SYNTAX  INTEGER {alertWhenOpen(0), alertWhenClosed(1)}
	MAX-ACCESS	read-write
    STATUS  current
    DESCRIPTION
        "Status which generates an alert condition for the dry contact sensor connected to port 1.  
        A value of 0 represents OPEN, and a value of 1 represents CLOSED.  
        This value corresponds directly with the Alert When value entered in the configuration page for this sensor.  
        This object is only applicable if a dry contact sensor is connected to port 1."
::= {dryContact1Adm 2}

-- dry contact 2

dryContact2Status  OBJECT-TYPE
    SYNTAX  INTEGER {open(0), closed(1)}
	MAX-ACCESS	read-only
    STATUS  current
    DESCRIPTION
        "Current integer value of the dry contact sensor connected to port 2.  
        A value of 0 represents OPEN, and a value of 1 represents CLOSED.  
        The value corresponds directly with the value displayed on the summary page and the status page for this sensor.  
        This object is only applicable if a dry contact sensor is connected to port 2."
::= {dryContact2 1}

dryContact2Alert  OBJECT-TYPE
    SYNTAX  INTEGER {off(0), on(1)}
	MAX-ACCESS	read-only
    STATUS  current
    DESCRIPTION
        "Current alert status of the dry contact sensor connected to port 2.  
         value of 0 indicates that the sensor has not been set to its alert condition, 
         while a value of 1 indicates that it has.  
         This object is only applicable if a dry contact sensor is connected to port 2."
::= {dryContact2 2}

dryContact2Name  OBJECT-TYPE
    SYNTAX  DisplayString
	MAX-ACCESS	read-write
    STATUS  current
    DESCRIPTION
        "Current name assigned to the dry contact sensor connected to port 2.  
        This value corresponds directly with the name entered in the configuration page for this sensor.  
        This object is only applicable if a dry contact sensor is connected to port 2."
::= {dryContact2Adm 1}            

dryContact2AlertStatus  OBJECT-TYPE
    SYNTAX  INTEGER {alertWhenOpen(0), alertWhenClosed(1)}
	MAX-ACCESS	read-write
    STATUS  current
    DESCRIPTION
        "Status which generates an alert condition for the dry contact sensor connected to port 2.  
        A value of 0 represents OPEN, and a value of 1 represents CLOSED.  
        This value corresponds directly with the Alert When value entered in the configuration page for this sensor.  
        This object is only applicable if a dry contact sensor is connected to port 2."
::= {dryContact2Adm 2}

-- dry contact 3

dryContact3Status  OBJECT-TYPE
    SYNTAX  INTEGER {open(0), closed(1)}
	MAX-ACCESS	read-only
    STATUS  current
    DESCRIPTION
        "Current integer value of the dry contact sensor connected to port 3.  
        A value of 0 represents OPEN, and a value of 1 represents CLOSED.  
        The value corresponds directly with the value displayed on the summary page and the status page for this sensor.  
        This object is only applicable if a dry contact sensor is connected to port 3."
::= {dryContact3 1}

dryContact3Alert  OBJECT-TYPE
    SYNTAX  INTEGER {off(0), on(1)}
	MAX-ACCESS	read-only
    STATUS  current
    DESCRIPTION
        "Current alert status of the dry contact sensor connected to port 3.  
        A value of 0 indicates that the sensor has not been set to its alert condition, 
        while a value of 1 indicates that it has.  
        This object is only applicable if a dry contact sensor is connected to port 3."
::= {dryContact3 2}

dryContact3Name  OBJECT-TYPE
    SYNTAX  DisplayString
	MAX-ACCESS	read-write
    STATUS  current
    DESCRIPTION
        "Current name assigned to the dry contact sensor connected to port 3.  
        This value corresponds directly with the name entered in the configuration page for this sensor.  
        This object is only applicable if a dry contact sensor is connected to port 3."
::= {dryContact3Adm 1}            

dryContact3AlertStatus  OBJECT-TYPE
    SYNTAX  INTEGER {alertWhenOpen(0), alertWhenClosed(1)}
	MAX-ACCESS	read-write
    STATUS  current
    DESCRIPTION
        "Status which generates an alert condition for the dry contact sensor connected to port 3.  
        A value of 0 represents OPEN, and a value of 1 represents CLOSED.  
        This value corresponds directly with the Alert When value entered in the configuration page for this sensor.  
        This object is only applicable if a dry contact sensor is connected to port 3."
::= {dryContact3Adm 2}

-- dry contact 4

dryContact4Status  OBJECT-TYPE
    SYNTAX  INTEGER {open(0), closed(1)}
	MAX-ACCESS	read-only
    STATUS  current
    DESCRIPTION
        "Current integer value of the dry contact sensor connected to port 4.  
        A value of 0 represents OPEN, and a value of 1 represents CLOSED.  
        The value corresponds directly with the value displayed on the summary page and the status page for this sensor.  
        This object is only applicable if a dry contact sensor is connected to port 4."
::= {dryContact4 1}

dryContact4Alert  OBJECT-TYPE
    SYNTAX  INTEGER {off(0), on(1)}
	MAX-ACCESS	read-only
    STATUS  current
    DESCRIPTION
        "Current alert status of the dry contact sensor connected to port 4.  
        A value of 0 indicates that the sensor has not been set to its alert condition, 
        while a value of 1 indicates that it has.  
        This object is only applicable if a dry contact sensor is connected to port 4."
::= {dryContact4 2}

dryContact4Name  OBJECT-TYPE
    SYNTAX  DisplayString
	MAX-ACCESS	read-write
    STATUS  current
    DESCRIPTION
        "Current name assigned to the dry contact sensor connected to port 4.  
        This value corresponds directly with the name entered in the configuration page for this sensor.  
        This object is only applicable if a dry contact sensor is connected to port 4."
::= {dryContact4Adm 1}            

dryContact4AlertStatus  OBJECT-TYPE
    SYNTAX  INTEGER {alertWhenOpen(0), alertWhenClosed(1)}
	MAX-ACCESS	read-write
    STATUS  current
    DESCRIPTION
        "Status which generates an alert condition for the dry contact sensor connected to port 4.  
        A value of 0 represents OPEN, and a value of 1 represents CLOSED.  
        This value corresponds directly with the Alert When value entered in the configuration page for this sensor.  
        This object is only applicable if a dry contact sensor is connected to port 4."
::= {dryContact4Adm 2}

-- water 1

waterStatus  OBJECT-TYPE
    SYNTAX  INTEGER {open(0), closed(1)}
	MAX-ACCESS	read-only
    STATUS  current
    DESCRIPTION
        "Current integer value of the water sensor.  
        A value of 0 represents OPEN, and a value of 1 represents CLOSED. 
        The value corresponds directly with the value displayed on the summary page and the status page for this sensor.  
        This object is only applicable if a water sensor is connected."
::= {waterSensor 1}

waterAlert  OBJECT-TYPE
    SYNTAX  INTEGER {off(0), on(1)}
	MAX-ACCESS	read-only
    STATUS  current
    DESCRIPTION
        "Current alert status of the water sensor.  
        A value of 0 indicates that the sensor has not been set to its alert condition, 
        while a value of 1 indicates that it has.  
        This object is only applicable if a water sensor is connected."
::= {waterSensor 2}

waterName  OBJECT-TYPE
    SYNTAX  DisplayString
	MAX-ACCESS	read-write
    STATUS  current
    DESCRIPTION
        "Current name assigned to the water sensor.  
        This value corresponds directly with the name entered in the configuration page for this sensor.  
        This object is only applicable if a water sensor is connected."
::= {waterSensorAdm 1}            

waterAlertStatus  OBJECT-TYPE
    SYNTAX  INTEGER {alertWhenOpen(0), alertWhenClosed(1)}
	MAX-ACCESS	read-write
    STATUS  current
    DESCRIPTION
        "Status which generates an alert condition for the water sensor.  
        A value of 0 represents OPEN, and a value of 1 represents CLOSED.  
        This value corresponds directly with the Alert When value entered in the configuration page for this sensor.  
        This object is only applicable if a water sensor is connected."
::= {waterSensorAdm 2}

-- host system

sysName OBJECT-TYPE
    SYNTAX  DisplayString
 	MAX-ACCESS	read-only
    STATUS  current
    DESCRIPTION
        "System node name.  
        This value corresponds directly with the Node Name field on the General configuration page under the ADMINISTRATION menu."
::= {hostSystem 1}
 
sysLocation OBJECT-TYPE
    SYNTAX  DisplayString
 	MAX-ACCESS	read-only
    STATUS  current
     DESCRIPTION
        "System node location.  
        his value corresponds directly with the Node Location field on the General configuration page under the ADMINISTRATION menu."
::= {hostSystem 2}
 
sysIP OBJECT-TYPE
    SYNTAX  DisplayString
 	MAX-ACCESS	read-only
    STATUS  current
    DESCRIPTION
        "System IP address.  
        This value corresponds directly with the IP address assigned to the ENVIROMUX-MINI on the Network configuration page under the ADMINISTRATION menu."
::= {hostSystem 3}
 
sysMask OBJECT-TYPE
    SYNTAX  DisplayString
 	MAX-ACCESS	read-only
    STATUS  current
    DESCRIPTION
        "System Subnet Mask.  
        This value corresponds directly with the Subnet Mask assigned to the ENVIROMUX-MINI on the Network configuration page under the ADMINISTRATION menu."
::= {hostSystem 4}
 
sysGateway OBJECT-TYPE
    SYNTAX  DisplayString
 	MAX-ACCESS	read-only
    STATUS  current
    DESCRIPTION
        "System Default Gateway.  
        This value corresponds directly with the Default Gateway assigned to the ENVIROMUX-MINI on the Network configuration page under the ADMINISTRATION menu."
::= {hostSystem 5}
 
sysDNS OBJECT-TYPE
    SYNTAX  DisplayString
 	MAX-ACCESS	read-only
    STATUS  current
    DESCRIPTION
        "System DNS server.  
        This value corresponds directly with the DNS server assigned to the ENVIROMUX-MINI on the Network configuration page under the ADMINISTRATION menu."
::= {hostSystem 6}
    
-- traps

temperatureSensor1Trap  NOTIFICATION-TYPE
    STATUS              current
    DESCRIPTION         "Trap for alert from temperature sensor connected to port 1. Received if this sensor is configured to send SNMP traps using the Configuration page, and SNMP is enabled on the Network configuration page under the ADMINISTRATION menu."
	::= { envTraps 1 }
	
temperatureSensor2Trap  NOTIFICATION-TYPE
    STATUS              current
    DESCRIPTION         "Trap for alert from temperature sensor connected to port 2. Received if this sensor is configured to send SNMP traps using the Configuration page, and SNMP is enabled on the Network configuration page under the ADMINISTRATION menu."
	::= { envTraps 2 }
	
humiditySensor1Trap   	NOTIFICATION-TYPE
    STATUS              current
    DESCRIPTION         "Trap for alert from humidity sensor connected to port 1. Received if this sensor is configured to send SNMP traps using the Configuration page, and SNMP is enabled on the Network configuration page under the ADMINISTRATION menu."
	::= { envTraps 3 }
	
humiditySensor2Trap   	NOTIFICATION-TYPE
    STATUS              current
    DESCRIPTION         "Trap for alert from humidity sensor connected to port 2. Received if this sensor is configured to send SNMP traps using the Configuration page, and SNMP is enabled on the Network configuration page under the ADMINISTRATION menu."
	::= { envTraps 4 }
	
dryContactSensor1Trap   NOTIFICATION-TYPE
    STATUS              current
    DESCRIPTION         "Trap for alert from dry contact sensor connected to port 1. Received if this sensor is configured to send SNMP traps using the Configuration page, and SNMP is enabled on the Network configuration page under the ADMINISTRATION menu."
	::= { envTraps 5 }
    	
dryContactSensor2Trap   NOTIFICATION-TYPE
    STATUS              current
    DESCRIPTION         "Trap for alert from dry contact sensor connected to port 2. Received if this sensor is configured to send SNMP traps using the Configuration page, and SNMP is enabled on the Network configuration page under the ADMINISTRATION menu."
	::= { envTraps 6 }
	
dryContactSensor3Trap   NOTIFICATION-TYPE
    STATUS              current
    DESCRIPTION         "Trap for alert from dry contact sensor connected to port 3. Received if this sensor is configured to send SNMP traps using the Configuration page, and SNMP is enabled on the Network configuration page under the ADMINISTRATION menu."
	::= { envTraps 7 }
	
dryContactSensor4Trap   NOTIFICATION-TYPE
    STATUS              current
    DESCRIPTION         "Trap for alert from dry contact sensor connected to port 4. Received if this sensor is configured to send SNMP traps using the Configuration page, and SNMP is enabled on the Network configuration page under the ADMINISTRATION menu."
	::= { envTraps 8 }
	
waterSensor1Trap   	    NOTIFICATION-TYPE
    STATUS              current
    DESCRIPTION         "Trap for alert from water sensor. Received if this sensor is configured to send SNMP traps using the Configuration page, and SNMP is enabled on the Network configuration page under the ADMINISTRATION menu."
	::= { envTraps 9 }
	
temperatureSensor1RetTrap  NOTIFICATION-TYPE
    STATUS              current
    DESCRIPTION         "Trap for return from alert from temperature sensor connected to port 1. Received if this sensor is configured to send SNMP traps using the Configuration page, and SNMP is enabled on the Network configuration page under the ADMINISTRATION menu."
	::= { envTraps 11 }
	
temperatureSensor2RetTrap  NOTIFICATION-TYPE
    STATUS              current
    DESCRIPTION         "Trap for return from alert from temperature sensor connected to port 2. Received if this sensor is configured to send SNMP traps using the Configuration page, and SNMP is enabled on the Network configuration page under the ADMINISTRATION menu."
	::= { envTraps 12 }
	
humiditySensor1RetTrap 	NOTIFICATION-TYPE
    STATUS              current
    DESCRIPTION         "Trap for return from alert from humidity sensor connected to port 1. Received if this sensor is configured to send SNMP traps using the Configuration page, and SNMP is enabled on the Network configuration page under the ADMINISTRATION menu."
	::= { envTraps 13 }
	
humiditySensor2RetTrap 	NOTIFICATION-TYPE
    STATUS              current
    DESCRIPTION         "Trap for return from alert from humidity sensor connected to port 2. Received if this sensor is configured to send SNMP traps using the Configuration page, and SNMP is enabled on the Network configuration page under the ADMINISTRATION menu."
	::= { envTraps 14 }
	
dryContactSensor1RetTrap   NOTIFICATION-TYPE
    STATUS              current
    DESCRIPTION         "Trap for return from alert from dry contact sensor connected to port 1. Received if this sensor is configured to send SNMP traps using the Configuration page, and SNMP is enabled on the Network configuration page under the ADMINISTRATION menu."
	::= { envTraps 15 }
    	
dryContactSensor2RetTrap   NOTIFICATION-TYPE
    STATUS              current
    DESCRIPTION         "Trap for return from alert from dry contact sensor connected to port 2. Received if this sensor is configured to send SNMP traps using the Configuration page, and SNMP is enabled on the Network configuration page under the ADMINISTRATION menu."
	::= { envTraps 16 }
	
dryContactSensor3RetTrap   NOTIFICATION-TYPE
    STATUS              current
    DESCRIPTION         "Trap for return from alert from dry contact sensor connected to port 3. Received if this sensor is configured to send SNMP traps using the Configuration page, and SNMP is enabled on the Network configuration page under the ADMINISTRATION menu."
	::= { envTraps 17 }
	
dryContactSensor4RetTrap   NOTIFICATION-TYPE
    STATUS              current
    DESCRIPTION         "Trap for return from alert from dry contact sensor connected to port 4. Received if this sensor is configured to send SNMP traps using the Configuration page, and SNMP is enabled on the Network configuration page under the ADMINISTRATION menu."
	::= { envTraps 18 }
	
waterSensor1RetTrap	    NOTIFICATION-TYPE
    STATUS              current
    DESCRIPTION         "Trap for return from alert from water sensor. Received if this sensor is configured to send SNMP traps using the Configuration page, and SNMP is enabled on the Network configuration page under the ADMINISTRATION menu."
	::= { envTraps 19 }
	
logTrap 		    NOTIFICATION-TYPE
    STATUS          current
    DESCRIPTION		"Trap generated when a log entry is created.  Received if log entries are configured to be sent as SNMP traps using the Log Methods page, and SNMP is enabled on the Network configuration page under the ADMINISTRATION menu."
    ::= { envTraps 100 }
    
overflowTrap		NOTIFICATION-TYPE
    STATUS          current
    DESCRIPTION		"Trap generated when has reached 90% capacity.  Received if log overflow alerts are enabled and are configured to be sent as SNMP traps using the Log Overflow page, and SNMP is enabled on the Network configuration page under the ADMINISTRATION menu."
    ::= { envTraps 101 }
    

END

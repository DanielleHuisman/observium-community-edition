--          *****************************
--          *                           *
--          *         ONEOS MIB         *
--          *                           *
--          *****************************
--
--          ONEOS_MIB_STD_V0X.X.R0XX_XXXXX
--
--          Creation date : 16/12/2010

OA-ZBFW-STATUS-MIB DEFINITIONS ::= BEGIN
 
	IMPORTS
		Integer32, Counter32, Unsigned32,IpAddress,TimeTicks,
		OBJECT-TYPE, MODULE-IDENTITY			
			FROM SNMPv2-SMI			
        DisplayString                                                       
            FROM SNMPv2-TC                                                  
		oacExpIMZbFw, oacMIBModules
	        FROM ONEACCESS-GLOBAL-REG
		SnmpAdminString
			FROM SNMP-FRAMEWORK-MIB;
    	
	oacZbfwStatusMIB MODULE-IDENTITY

        LAST-UPDATED    "201012160001Z"
        ORGANIZATION    " OneAccess "
        CONTACT-INFO    " OneAccess Belgium"

	    DESCRIPTION     "The oacZbfwStatusMIB"
	::= { oacMIBModules 2003 }  

TableIndex ::= Unsigned32
		
--
-- Node definitions
--

oacZbfw OBJECT IDENTIFIER ::= {oacExpIMZbFw 3131}

-- Output for group performance.

oacZbfwPerf OBJECT IDENTIFIER ::= {oacZbfw 12}

-- Output for attribute router performance.

oacZbfwRtrConnPerf OBJECT IDENTIFIER ::= {oacZbfwPerf 40}

oacZbfwRtrConnPerfSSCTable OBJECT-TYPE
   SYNTAX      SEQUENCE OF OacZbfwRtrConnPerfEntry
   MAX-ACCESS  not-accessible
   STATUS      current
   DESCRIPTION
      "router connection statistics"
   ::= {oacZbfwRtrConnPerf 1}

oacZbfwRtrConnPerfEntry OBJECT-TYPE
   SYNTAX      OacZbfwRtrConnPerfEntry
   MAX-ACCESS  not-accessible
   STATUS      current
   DESCRIPTION
      "An index into the table of oacZbfwRtrConnPer"
   INDEX      { IMPLIED oacZbfwRtrConnPerfGlobalIx }
   ::= {oacZbfwRtrConnPerfSSCTable 1}

OacZbfwRtrConnPerfEntry ::=
   SEQUENCE
      {
      oacZbfwRtrConnPerfGlobalIx
         SnmpAdminString,
      oacZbfwRouterConnectionsCreated
         Counter32,
      oacZbfwRouterConnectionsClosed
         Counter32,
      oacZbfwRouterConnectionsTimedOut
         Counter32,
      oacZbfwRouterConnectionsMax
         Counter32,
      oacZbfwRouterConnectionsMaxUsed
         Counter32,
      oacZbfwRouterConnectionsUsed
         Counter32
      }

oacZbfwRtrConnPerfGlobalIx OBJECT-TYPE
   SYNTAX      SnmpAdminString
   MAX-ACCESS  not-accessible
   STATUS      current
   DESCRIPTION
      "The value of the tlsCntTreeGlobalIndex of the MANAGED OBJECT."
   ::= {oacZbfwRtrConnPerfEntry 10}

oacZbfwRouterConnectionsCreated OBJECT-TYPE
   SYNTAX      Counter32
   MAX-ACCESS  read-only
   STATUS      current
   DESCRIPTION
      "Number of (half-open) connections created by the zone-based firewall."
   ::= {oacZbfwRtrConnPerfEntry 1}

oacZbfwRouterConnectionsClosed OBJECT-TYPE
   SYNTAX      Counter32
   MAX-ACCESS  read-only
   STATUS      current
   DESCRIPTION
      "Number of zone-based firewall connections or half-open connections
      closed by a protocol or explicitly by a user."
   ::= {oacZbfwRtrConnPerfEntry 2}

oacZbfwRouterConnectionsTimedOut OBJECT-TYPE
   SYNTAX      Counter32
   MAX-ACCESS  read-only
   STATUS      current
   DESCRIPTION
      "Number of zone-based firewall connections or half-open connections
      that timed out."
   ::= {oacZbfwRtrConnPerfEntry 3}

oacZbfwRouterConnectionsMax OBJECT-TYPE
   SYNTAX      Counter32
   MAX-ACCESS  read-only
   STATUS      current
   DESCRIPTION
      "Max number of zone-based firewall connections or half-open connections
      allowed in this instance."
   ::= {oacZbfwRtrConnPerfEntry 4}

   oacZbfwRouterConnectionsMaxUsed OBJECT-TYPE
   SYNTAX      Counter32
   MAX-ACCESS  read-only
   STATUS      current
   DESCRIPTION
      "Highest number of zone-based firewall connections or half-open connections
      that were simultaneously in use."
   ::= {oacZbfwRtrConnPerfEntry 5}

   oacZbfwRouterConnectionsUsed OBJECT-TYPE
   SYNTAX      Counter32
   MAX-ACCESS  read-only
   STATUS      current
   DESCRIPTION
      "Number of zone-based firewall connections or half-open connections
      that are currenlty in use."
   ::= {oacZbfwRtrConnPerfEntry 6}
   
-- Output for attribute packets.

oacZbfwPackets OBJECT IDENTIFIER ::= {oacZbfwPerf 41}

oacZbfwPacketsSSCTable OBJECT-TYPE
   SYNTAX      SEQUENCE OF OacZbfwPacketsEntry
   MAX-ACCESS  not-accessible
   STATUS      current
   DESCRIPTION
      "packet statistics"
   ::= {oacZbfwPackets 1}

oacZbfwPacketsEntry OBJECT-TYPE
   SYNTAX      OacZbfwPacketsEntry
   MAX-ACCESS  not-accessible
   STATUS      current
   DESCRIPTION
      "Aggregated packet handling statistics of the zone-based firewall."
   INDEX      { IMPLIED oacZbfwPacketsGlobalIx }
   ::= {oacZbfwPacketsSSCTable 1}

OacZbfwPacketsEntry ::=
   SEQUENCE
      {
      oacZbfwPacketsGlobalIx
         SnmpAdminString,
      oacZbfwPacketsProcessed
         Counter32,
      oacZbfwPacketsPassed
         Counter32,
      oacZbfwPacketsDropped
         Counter32,
      oacZbfwPacketsRejected
         Counter32,
      oacZbfwPacketsRejectStatsInvalidIntf
         Counter32,
      oacZbfwPacketsRejectStatsNoPolicy
         Counter32,
      oacZbfwPacketsRejectStatsNoConnSetup
         Counter32,
      oacZbfwPacketsRejectStatsProtocol
         Counter32,
      oacZbfwPacketsRejectStatsAlg
         Counter32,
      oacZbfwPacketsRejectStatsConnExceeded
         Counter32 --,
--      oacZbfwPacketsRejectStatsBandwidth
--         Counter32
      }

oacZbfwPacketsGlobalIx OBJECT-TYPE
   SYNTAX      SnmpAdminString
   MAX-ACCESS  not-accessible
   STATUS      current
   DESCRIPTION
      "The value of the tlsCntTreeGlobalIndex of the MANAGED OBJECT."
   ::= {oacZbfwPacketsEntry 1}

oacZbfwPacketsProcessed OBJECT-TYPE
   SYNTAX      Counter32
   MAX-ACCESS  read-only
   STATUS      current
   DESCRIPTION
      "Number of packets processed by the zone-based firewall."
   ::= {oacZbfwPacketsEntry 2}

oacZbfwPacketsPassed OBJECT-TYPE
   SYNTAX      Counter32
   MAX-ACCESS  read-only
   STATUS      current
   DESCRIPTION
      "Number of packets passed by the zone-based firewall."
   ::= {oacZbfwPacketsEntry 3}

oacZbfwPacketsDropped OBJECT-TYPE
   SYNTAX      Counter32
   MAX-ACCESS  read-only
   STATUS      current
   DESCRIPTION
      "Number of packets dropped by an explicit drop rule of the zone-based firewall."
   ::= {oacZbfwPacketsEntry 4}

oacZbfwPacketsRejected OBJECT-TYPE
   SYNTAX      Counter32
   MAX-ACCESS  read-only
   STATUS      current
   DESCRIPTION
      "Number of packets rejected by the zone-based firewall because of an
      invalid interface, no matching rule could be found, no connection could be
      created, a protocol violation or an alg violation."
   ::= {oacZbfwPacketsEntry 5}

oacZbfwPacketsRejectStatsInvalidIntf OBJECT-TYPE
   SYNTAX      Counter32
   MAX-ACCESS  read-only
   STATUS      current
   DESCRIPTION
      "Number of packets rejected by the zone-based firewall because of a missing
      valid interface for the packet."
   ::= {oacZbfwPacketsEntry 6}

oacZbfwPacketsRejectStatsNoPolicy OBJECT-TYPE
   SYNTAX      Counter32
   MAX-ACCESS  read-only
   STATUS      current
   DESCRIPTION
      "Number of packets rejected by the zone-based firewall because of a missing
      matching policy database entry."
   ::= {oacZbfwPacketsEntry 7}

oacZbfwPacketsRejectStatsNoConnSetup OBJECT-TYPE
   SYNTAX      Counter32
   MAX-ACCESS  read-only
   STATUS      current
   DESCRIPTION
      "Number of packets rejected by the zone-based firewall because no
      connection could be created."
   ::= {oacZbfwPacketsEntry 8}

oacZbfwPacketsRejectStatsProtocol OBJECT-TYPE
   SYNTAX      Counter32
   MAX-ACCESS  read-only
   STATUS      current
   DESCRIPTION
      "Number of packets rejected by the zone-based firewall because of a 
      protocol violation."
   ::= {oacZbfwPacketsEntry 9}

oacZbfwPacketsRejectStatsAlg OBJECT-TYPE
   SYNTAX      Counter32
   MAX-ACCESS  read-only
   STATUS      current
   DESCRIPTION
      "Number of packets rejected by the zone-based firewall because of an 
      alg violation."
   ::= {oacZbfwPacketsEntry 10}

oacZbfwPacketsRejectStatsConnExceeded OBJECT-TYPE
   SYNTAX      Counter32
   MAX-ACCESS  read-only
   STATUS      current
   DESCRIPTION
      "Number of packets rejected by the zone-based firewall because the
      maximum number of connections was reached."
   ::= {oacZbfwPacketsEntry 11}

--oacZbfwPacketsRejectStatsBandwidth OBJECT-TYPE
--   SYNTAX      Counter32
--   MAX-ACCESS  read-only
--   STATUS      current
--   DESCRIPTION
--      "Path: zbFirewall.performance.packets.rejectStats.bandwidth
--
--       32 bit unsigned wrappable counter."
--   ::= {oacZbfwPacketsEntry 11}


-- Output for attribute PolicyRules

oacZbfwPolicyRules OBJECT IDENTIFIER ::= {oacZbfwPerf 42}

oacZbfwPolicyRulesSSCTable OBJECT-TYPE
   SYNTAX      SEQUENCE OF OacZbfwPolicyRulesEntry
   MAX-ACCESS  not-accessible
   STATUS      current
   DESCRIPTION
      "open policyrules perf"
   ::= {oacZbfwPolicyRules 1}

oacZbfwPolicyRulesEntry OBJECT-TYPE
   SYNTAX      OacZbfwPolicyRulesEntry
   MAX-ACCESS  not-accessible
   STATUS      current
   DESCRIPTION
      ""
   INDEX      { oacZbfwPolicyRulesTableIx,
                IMPLIED oacZbfwPolicyRulesGlobalIx}
   ::= {oacZbfwPolicyRulesSSCTable 1}

OacZbfwPolicyRulesEntry ::=
   SEQUENCE
      {
      oacZbfwPolicyRulesTableIx
         TableIndex,
      oacZbfwPolicyRulesGlobalIx
         SnmpAdminString,
      oacZbfwPolicyRulesZonePair
         DisplayString,
      oacZbfwPolicyRulesPolicy
         DisplayString,
      oacZbfwPolicyRulesPolicyRule
         DisplayString,
      oacZbfwPolicyRulesCountersProcessed
         Counter32,
      oacZbfwPolicyRulesCountersApplied
         Counter32,
      oacZbfwPolicyRulesCountersConnections
         Counter32,
      oacZbfwPolicyRulesCountersPackets
         Counter32,
      oacZbfwPolicyRulesCountersOctets
         Counter32,
      oacZbfwPolicyRulesCountersReversePackets
         Counter32,
      oacZbfwPolicyRulesCountersReverseOctets
         Counter32
      }

oacZbfwPolicyRulesTableIx OBJECT-TYPE
   SYNTAX      TableIndex
   MAX-ACCESS  not-accessible
   STATUS      current
   DESCRIPTION
      "The table of oacZbfwPolicyRules objects"
   ::= {oacZbfwPolicyRulesEntry 1}

oacZbfwPolicyRulesGlobalIx OBJECT-TYPE
   SYNTAX      SnmpAdminString
   MAX-ACCESS  not-accessible
   STATUS      current
   DESCRIPTION
      "The value of the tlsCntTreeGlobalIndex of the MANAGED OBJECT."
   ::= {oacZbfwPolicyRulesEntry 2}

oacZbfwPolicyRulesZonePair OBJECT-TYPE
   SYNTAX      DisplayString
   MAX-ACCESS  read-only
   STATUS      current
   DESCRIPTION
      "Name of the zone-pair of this policy rule instance."
   ::= {oacZbfwPolicyRulesEntry 3}

oacZbfwPolicyRulesPolicy OBJECT-TYPE
   SYNTAX      DisplayString
   MAX-ACCESS  read-only
   STATUS      current
   DESCRIPTION
      "Name of the policy of this policy rule instance."
   ::= {oacZbfwPolicyRulesEntry 4}

oacZbfwPolicyRulesPolicyRule OBJECT-TYPE
   SYNTAX      DisplayString
   MAX-ACCESS  read-only
   STATUS      current
   DESCRIPTION
      "Name of the policy rule instance."
   ::= {oacZbfwPolicyRulesEntry 5}

oacZbfwPolicyRulesCountersProcessed OBJECT-TYPE
   SYNTAX      Counter32
   MAX-ACCESS  read-only
   STATUS      current
   DESCRIPTION
      "Number of times this policy rule instance was checked for packet
      matching."
   ::= {oacZbfwPolicyRulesEntry 6}

oacZbfwPolicyRulesCountersApplied OBJECT-TYPE
   SYNTAX      Counter32
   MAX-ACCESS  read-only
   STATUS      current
   DESCRIPTION
      "Number of times this policy rule instance was part of a matching policy
      database rule instance."
   ::= {oacZbfwPolicyRulesEntry 7}

oacZbfwPolicyRulesCountersConnections OBJECT-TYPE
   SYNTAX      Counter32
   MAX-ACCESS  read-only
   STATUS      current
   DESCRIPTION
      "Number of connections created from a matching policy database entry
      containing this policy rule instance."
   ::= {oacZbfwPolicyRulesEntry 8}

oacZbfwPolicyRulesCountersPackets OBJECT-TYPE
   SYNTAX      Counter32
   MAX-ACCESS  read-only
   STATUS      current
   DESCRIPTION
       "Number of packets processed in a flow that was created from a matching
       policy database entry containing this policy rule instance."
   ::= {oacZbfwPolicyRulesEntry 9}

oacZbfwPolicyRulesCountersOctets OBJECT-TYPE
   SYNTAX      Counter32
   MAX-ACCESS  read-only
   STATUS      current
   DESCRIPTION
       "Number of octets processed in a flow that was created from a matching
       policy database entry containing this policy rule instance."
   ::= {oacZbfwPolicyRulesEntry 10}

oacZbfwPolicyRulesCountersReversePackets OBJECT-TYPE
   SYNTAX      Counter32
   MAX-ACCESS  read-only
   STATUS      current
   DESCRIPTION
       "Number of packets processed in a reverse flow that was created from a matching
       policy database entry containing this policy rule instance."
   ::= {oacZbfwPolicyRulesEntry 11}

oacZbfwPolicyRulesCountersReverseOctets OBJECT-TYPE
   SYNTAX      Counter32
   MAX-ACCESS  read-only
   STATUS      current
   DESCRIPTION
       "Number of octets processed in a reverse flow that was created from a matching
       policy database entry containing this policy rule instance."
   ::= {oacZbfwPolicyRulesEntry 12}

-- Output for action ClearCounters

oacZbfwClearCounters OBJECT-TYPE
   SYNTAX      Integer32
   MAX-ACCESS  read-write
   STATUS      current
   DESCRIPTION
      "Clear firewall statistics and policy database counters."
   ::= {oacZbfwPerf 43}


-- Output for group status.

oacZbfwStatus OBJECT IDENTIFIER ::= {oacZbfw 14}


-- Output for attribute zonePairs.

oacZbfwZonePairs OBJECT IDENTIFIER ::= {oacZbfwStatus 22}

oacZbfwZonePairsSSCTable OBJECT-TYPE
   SYNTAX      SEQUENCE OF OacZbfwZonePairsEntry
   MAX-ACCESS  not-accessible
   STATUS      current
   DESCRIPTION
      "runtime zone pair status table"
   ::= {oacZbfwZonePairs 1}

oacZbfwZonePairsEntry OBJECT-TYPE
   SYNTAX      OacZbfwZonePairsEntry
   MAX-ACCESS  not-accessible
   STATUS      current
   DESCRIPTION
      "Zone-pair entry in the runtime policy database."
   INDEX      { oacZbfwZonePairsTableIx,
                IMPLIED oacZbfwZonePairsGlobalIx}
   ::= {oacZbfwZonePairsSSCTable 1}

OacZbfwZonePairsEntry ::=
   SEQUENCE
      {
      oacZbfwZonePairsTableIx
         TableIndex,
      oacZbfwZonePairsGlobalIx
         SnmpAdminString,
      oacZbfwZonePairsName
         DisplayString,
      oacZbfwZonePairsSrcZone
         DisplayString,
      oacZbfwZonePairsDstZone
         DisplayString,
--      oacZbfwZonePairsOutboundNat
--         DisplayString,
      oacZbfwZonePairsPolicy
         DisplayString,
      oacZbfwZonePairsCountersProcessed
         Counter32,
      oacZbfwZonePairsCountersApplied
         Counter32,
      oacZbfwZonePairsCountersConnections
         Counter32,
      oacZbfwZonePairsCountersPackets
         Counter32,
      oacZbfwZonePairsCountersOctets
         Counter32,
      oacZbfwZonePairsCountersReversePackets
         Counter32,
      oacZbfwZonePairsCountersReverseOctets
         Counter32
      }

oacZbfwZonePairsTableIx OBJECT-TYPE
   SYNTAX      TableIndex
   MAX-ACCESS  not-accessible
   STATUS      current
   DESCRIPTION
      "The table of oacZbfwZonePairs objects"
   ::= {oacZbfwZonePairsEntry 1}

oacZbfwZonePairsGlobalIx OBJECT-TYPE
   SYNTAX      SnmpAdminString
   MAX-ACCESS  not-accessible
   STATUS      current
   DESCRIPTION
      "The value of the tlsCntTreeGlobalIndex of the MANAGED OBJECT."
   ::= {oacZbfwZonePairsEntry 2}

oacZbfwZonePairsName OBJECT-TYPE
   SYNTAX      DisplayString
   MAX-ACCESS  read-only
   STATUS      current
   DESCRIPTION
      "Name of the zone-pair."
   ::= {oacZbfwZonePairsEntry 3}

oacZbfwZonePairsSrcZone OBJECT-TYPE
   SYNTAX      DisplayString
   MAX-ACCESS  read-only
   STATUS      current
   DESCRIPTION
      "Name of the source zone of this zone-pair."
   ::= {oacZbfwZonePairsEntry 4}

oacZbfwZonePairsDstZone OBJECT-TYPE
   SYNTAX      DisplayString
   MAX-ACCESS  read-only
   STATUS      current
   DESCRIPTION
      "Name of the destination zone of this zone-pair."
   ::= {oacZbfwZonePairsEntry 5}

--oacZbfwZonePairsOutboundNat OBJECT-TYPE
--   SYNTAX      DisplayString
--   MAX-ACCESS  read-only
--   STATUS      current
--   DESCRIPTION
--      "Name of the outbound Nat used for this zone-pair."
--   ::= {oacZbfwZonePairsEntry 6}

oacZbfwZonePairsPolicy OBJECT-TYPE
   SYNTAX      DisplayString
   MAX-ACCESS  read-only
   STATUS      current
   DESCRIPTION
      "Name of the policy used for this zone-pair."
   ::= {oacZbfwZonePairsEntry 7}

oacZbfwZonePairsCountersProcessed OBJECT-TYPE
   SYNTAX      Counter32
   MAX-ACCESS  read-only
   STATUS      current
   DESCRIPTION
      "Number of times this zone-pair instance was checked for packet
      matching."
   ::= {oacZbfwZonePairsEntry 8}

oacZbfwZonePairsCountersApplied OBJECT-TYPE
   SYNTAX      Counter32
   MAX-ACCESS  read-only
   STATUS      current
   DESCRIPTION
      "Number of times this zone-pair instance was part of a matching policy
      database rule."
   ::= {oacZbfwZonePairsEntry 9}

oacZbfwZonePairsCountersConnections OBJECT-TYPE
   SYNTAX      Counter32
   MAX-ACCESS  read-only
   STATUS      current
   DESCRIPTION
      "Number of connections created from a matching policy database entry
      containing this zone-pair."
   ::= {oacZbfwZonePairsEntry 10}

oacZbfwZonePairsCountersPackets OBJECT-TYPE
   SYNTAX      Counter32
   MAX-ACCESS  read-only
   STATUS      current
   DESCRIPTION
       "Number of packets processed in a flow that was created from a matching
       policy database entry containing this zone-pair instance."
   ::= {oacZbfwZonePairsEntry 11}

oacZbfwZonePairsCountersOctets OBJECT-TYPE
   SYNTAX      Counter32
   MAX-ACCESS  read-only
   STATUS      current
   DESCRIPTION
       "Number of octets processed in a flow that was created from a matching
       policy database entry containing this zone-pair instance."
   ::= {oacZbfwZonePairsEntry 12}

oacZbfwZonePairsCountersReversePackets OBJECT-TYPE
   SYNTAX      Counter32
   MAX-ACCESS  read-only
   STATUS      current
   DESCRIPTION
       "Number of packets processed in a reverse flow that was created from a matching
       policy database entry containing this zone-pair instance."
   ::= {oacZbfwZonePairsEntry 13}

oacZbfwZonePairsCountersReverseOctets OBJECT-TYPE
   SYNTAX      Counter32
   MAX-ACCESS  read-only
   STATUS      current
   DESCRIPTION
       "Number of octets processed in a reverse flow that was created from a matching
       policy database entry containing this zone-pair instance."
   ::= {oacZbfwZonePairsEntry 14}

-- Output for attribute flows
oacZbfwFlows OBJECT IDENTIFIER ::= {oacZbfwStatus 23}

oacZbfwFlowsSSCTable OBJECT-TYPE
   SYNTAX      SEQUENCE OF OacZbfwFlowsEntry
   MAX-ACCESS  not-accessible
   STATUS      current
   DESCRIPTION
      "open flow status"
   ::= {oacZbfwFlows 1}

oacZbfwFlowsEntry OBJECT-TYPE
   SYNTAX      OacZbfwFlowsEntry
   MAX-ACCESS  not-accessible
   STATUS      current
   DESCRIPTION
      "Open flow."
   INDEX      { oacZbfwFlowsTableIx,
                IMPLIED oacZbfwFlowsGlobalIx}
   ::= {oacZbfwFlowsSSCTable 1}

OacZbfwFlowsEntry ::=
   SEQUENCE
      {
      oacZbfwFlowsTableIx
         TableIndex,
      oacZbfwFlowsGlobalIx
         SnmpAdminString,
      oacZbfwFlowsConnectionId
         Counter32,
      oacZbfwFlowsSrcIntf
         DisplayString,
      oacZbfwFlowsSrcZone
         DisplayString,
      oacZbfwFlowsDstIntf
         DisplayString,
      oacZbfwFlowsDstZone
         DisplayString,
      oacZbfwFlowsSrcAddress
         IpAddress,
      oacZbfwFlowsDstAddress
         IpAddress,
      oacZbfwFlowsProtocol
         INTEGER,
      oacZbfwFlowsSrcPort
         Integer32,
      oacZbfwFlowsDstPort
         Integer32,
      oacZbfwFlowsAge
         TimeTicks,
      oacZbfwFlowsTimeOut
         TimeTicks,
      oacZbfwFlowsRulesZonePair
         DisplayString,
      oacZbfwFlowsRulesPolicy
         DisplayString,
      oacZbfwFlowsRulesPolicyRule
         DisplayString,
      oacZbfwFlowsRulesFilter
         DisplayString,
      oacZbfwFlowsRulesFilterRule
         DisplayString,
      oacZbfwFlowsModeAlg
         INTEGER
      }

oacZbfwFlowsTableIx OBJECT-TYPE
   SYNTAX      TableIndex
   MAX-ACCESS  not-accessible
   STATUS      current
   DESCRIPTION
      " The table of oacZbfwFlows objects"
   ::= {oacZbfwFlowsEntry 1}

oacZbfwFlowsGlobalIx OBJECT-TYPE
   SYNTAX      SnmpAdminString
   MAX-ACCESS  not-accessible
   STATUS      current
   DESCRIPTION
      "The value of the tlsCntTreeGlobalIndex of the MANAGED OBJECT."
   ::= {oacZbfwFlowsEntry 2}

oacZbfwFlowsConnectionId OBJECT-TYPE
   SYNTAX      Counter32
   MAX-ACCESS  read-only
   STATUS      current
   DESCRIPTION
      "Unique Id of the connection this flow belongs to."
   ::= {oacZbfwFlowsEntry 3}

oacZbfwFlowsSrcIntf OBJECT-TYPE
   SYNTAX      DisplayString
   MAX-ACCESS  read-only
   STATUS      current
   DESCRIPTION
      "Name of the source interface of a flow."
   ::= {oacZbfwFlowsEntry 4}

oacZbfwFlowsSrcZone OBJECT-TYPE
   SYNTAX      DisplayString
   MAX-ACCESS  read-only
   STATUS      current
   DESCRIPTION
      "Name of the source zone of a flow."
   ::= {oacZbfwFlowsEntry 5}

oacZbfwFlowsDstIntf OBJECT-TYPE
   SYNTAX      DisplayString
   MAX-ACCESS  read-only
   STATUS      current
   DESCRIPTION
      "Name of the destination interface of a flow."
   ::= {oacZbfwFlowsEntry 6}

oacZbfwFlowsDstZone OBJECT-TYPE
   SYNTAX      DisplayString
   MAX-ACCESS  read-only
   STATUS      current
   DESCRIPTION
      "Name of the destination zone of a flow."
   ::= {oacZbfwFlowsEntry 7}

oacZbfwFlowsSrcAddress OBJECT-TYPE
   SYNTAX      IpAddress
   MAX-ACCESS  read-only
   STATUS      current
   DESCRIPTION
      "Source address of a flow."
   ::= {oacZbfwFlowsEntry 8}

oacZbfwFlowsDstAddress OBJECT-TYPE
   SYNTAX      IpAddress
   MAX-ACCESS  read-only
   STATUS      current
   DESCRIPTION
      "Destination address of a flow."
   ::= {oacZbfwFlowsEntry 9}

oacZbfwFlowsProtocol OBJECT-TYPE
   SYNTAX      INTEGER
               {
               any (0),
               ah (51),
               egp (8),
               esp (50),
               gre (47),
               icmp (1),
               igp (9),
               igmp (2),
               igrp (88),
               ipInIp (4),
               ospf (89),
               udp (17),
               rsvp (46),
               tcp (6)
               }
   MAX-ACCESS  read-only
   STATUS      current
   DESCRIPTION
      "Protocol of a flow.

       Possibilities:
               any   (0)
               ah   (51)
               egp   (8)
               esp   (50)
               gre   (47)
               icmp   (1)
               igp   (9)
               igmp   (2)
               igrp   (88)
               ipInIp   (4)
               ospf   (89)
               udp   (17)
               rsvp   (46)
               tcp   (6)"
   ::= {oacZbfwFlowsEntry 10}

oacZbfwFlowsSrcPort OBJECT-TYPE
   SYNTAX      Integer32
   MAX-ACCESS  read-only
   STATUS      current
   DESCRIPTION
      "Source port number of a flow."
   ::= {oacZbfwFlowsEntry 11}

oacZbfwFlowsDstPort OBJECT-TYPE
   SYNTAX      Integer32
   MAX-ACCESS  read-only
   STATUS      current
   DESCRIPTION
      "Destination port number of a flow."
   ::= {oacZbfwFlowsEntry 12}

oacZbfwFlowsAge OBJECT-TYPE
   SYNTAX      TimeTicks
   MAX-ACCESS  read-only
   STATUS      current
   DESCRIPTION
      "Age of a flow."
   ::= {oacZbfwFlowsEntry 13}

oacZbfwFlowsTimeOut OBJECT-TYPE
   SYNTAX      TimeTicks
   MAX-ACCESS  read-only
   STATUS      current
   DESCRIPTION
      "Remaining time before a flow goes in timeout and will be removed."
   ::= {oacZbfwFlowsEntry 14}

oacZbfwFlowsRulesZonePair OBJECT-TYPE
   SYNTAX      DisplayString
   MAX-ACCESS  read-only
   STATUS      current
   DESCRIPTION
      "Name of the zone-pair matching with a flow."
   ::= {oacZbfwFlowsEntry 15}

oacZbfwFlowsRulesPolicy OBJECT-TYPE
   SYNTAX      DisplayString
   MAX-ACCESS  read-only
   STATUS      current
   DESCRIPTION
      "Name of the policy matching with a flow."
   ::= {oacZbfwFlowsEntry 16}

oacZbfwFlowsRulesPolicyRule OBJECT-TYPE
   SYNTAX      DisplayString
   MAX-ACCESS  read-only
   STATUS      current
   DESCRIPTION
      "Name of the policy rule matching with a flow."
   ::= {oacZbfwFlowsEntry 17}

oacZbfwFlowsRulesFilter OBJECT-TYPE
   SYNTAX      DisplayString
   MAX-ACCESS  read-only
   STATUS      current
   DESCRIPTION
      "Name of the filter matching with a flow."
   ::= {oacZbfwFlowsEntry 18}

oacZbfwFlowsRulesFilterRule OBJECT-TYPE
   SYNTAX      DisplayString
   MAX-ACCESS  read-only
   STATUS      current
   DESCRIPTION
      "Name of the filter rule matching with a flow."
   ::= {oacZbfwFlowsEntry 19}

oacZbfwFlowsModeAlg OBJECT-TYPE
   SYNTAX      INTEGER
               {
               false (0),
               true (1)
               }
   MAX-ACCESS  read-only
   STATUS      current
   DESCRIPTION
      "Boolean indicating if a flow is created by an Alg."
   ::= {oacZbfwFlowsEntry 20}

END

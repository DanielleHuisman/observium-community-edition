--          *****************************
--          *                           *
--          *         ONEOS MIB         *
--          *                           *
--          *****************************
--
--          ONEOS_MIB_STD_V05.1.R005_E001
--
--          Creation date : 05/06/2005
--
--          Compatibility with ONEOS_V31
--
--          Compatibility with ONEOS_V32
--


     ONEACCESS-PSTN-MIB DEFINITIONS ::= BEGIN

     IMPORTS
		MODULE-IDENTITY, OBJECT-TYPE,Counter32,Unsigned32, NOTIFICATION-TYPE
			FROM SNMPv2-SMI
		DisplayString
			FROM RFC1213-MIB
        ifIndex, ifDescr, ifType, ifAdminStatus, ifOperStatus, ifName, ifAlias
            FROM IF-MIB
		MODULE-COMPLIANCE, OBJECT-GROUP
			FROM SNMPv2-CONF
 	    	oacExpIMPstn,oacExpIMPstnNotifications,oacMIBModules
			FROM ONEACCESS-GLOBAL-REG
			oacEventText
			FROM ONEACCESS-EVENTS-MIB;

     oacPstnMIBModule MODULE-IDENTITY
        LAST-UPDATED "201110270000Z"
        ORGANIZATION    " OneAccess "
         CONTACT-INFO
           "Pascal KESTELOOT
            Postal: ONE ACCESS
                    381 Avenue du Général de Gaulle
                    92140 Clamart, France
		    FRANCE

            Tel: (+33) 01 41 87 70 00
            Fax: (+33) 01 41 87 74 00

            E-mail: pascal.kesteloot@oneaccess-net.com"

         DESCRIPTION
                    	"Contact updated"
    	REVISION        "201110270000Z"

        DESCRIPTION
              "This MIB module describes Pstn Management objects."

	::= { oacMIBModules 672 }


   dialDown NOTIFICATION-TYPE
           OBJECTS { ifIndex, ifDescr, ifType, ifAdminStatus, 
                 ifOperStatus, ifName, ifAlias }

           STATUS  current
           DESCRIPTION
               "A pstnlinkDown trap signifies that the SNMPv2 entity,
               acting in an agent role, has detected that the
               ifOperStatus object for its pstn physical link
               is about to enter the down state from some other state
               (but not from the notPresent state).  This other state
               is indicated by the included value of ifOperStatus."
       ::= { oacExpIMPstnNotifications 3 }

   dialUp NOTIFICATION-TYPE
           OBJECTS { ifIndex, ifDescr, ifType, ifAdminStatus, 
                 ifOperStatus, ifName, ifAlias }
           STATUS  current
           DESCRIPTION
               "A linkDown trap signifies that the SNMPv2 entity,
               acting in an agent role, has detected that the
               ifOperStatus object for for its pstn physical communication links
               left the down state and transitioned into some other
               state (but not into the notPresent state).  This other
               state is indicated by the included value of
               ifOperStatus."
       ::= { oacExpIMPstnNotifications 4 }

END
--

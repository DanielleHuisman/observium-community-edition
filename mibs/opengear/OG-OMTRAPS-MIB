-- =========================================================================
-- == OG-OMTRAPS-MIB:                                                     ==
-- == Opengear Operations Manager notification M.I.B.			  ==
-- ==                                                                     ==
-- == (c) Copyright 2005-2020 Opengear Inc.                               ==
-- =========================================================================

OG-OMTRAPS-MIB DEFINITIONS ::= BEGIN

IMPORTS
	ogMgmt
		FROM OG-SMI-MIB
	OBJECT-TYPE, MODULE-IDENTITY, NOTIFICATION-TYPE, Integer32
		FROM SNMPv2-SMI
	MODULE-COMPLIANCE, NOTIFICATION-GROUP, OBJECT-GROUP
		FROM SNMPv2-CONF
	DisplayString
		FROM SNMPv2-TC;

ogOMTRAPSMib MODULE-IDENTITY
	LAST-UPDATED "202011101500Z"
	ORGANIZATION "Opengear Inc."
	CONTACT-INFO
		"Opengear Inc.
		630 West 9560 South,
		 Sandy, UT 84070
		 support@opengear.com"
	DESCRIPTION
		"Opengear OM Console MIB"
	REVISION "202011101500Z"
	DESCRIPTION
		"Add PSU temperature notifications"
	REVISION "201908291500Z"
	DESCRIPTION
		"Add login notifications"
	REVISION "201908071500Z"
	DESCRIPTION
		"Initial version."
		::= { ogMgmt 18 }

ogOMTRAPSObjects OBJECT IDENTIFIER ::= { ogOMTRAPSMib 1 }

ogOMTRAPSEvent OBJECT IDENTIFIER ::= { ogOMTRAPSObjects 1 }

ogOMTRAPSNotificationPrefix OBJECT IDENTIFIER ::= { ogOMTRAPSMib 2 }

ogOMTRAPSNotification OBJECT IDENTIFIER ::= { ogOMTRAPSNotificationPrefix 0 }

-- ======== OBJECTS =============

ogOMTRAPSConnectivityTestResult OBJECT-TYPE
	SYNTAX DisplayString
	MAX-ACCESS read-only
	STATUS current
	DESCRIPTION
			"Result of cellular connectivity test"
	::= { ogOMTRAPSEvent 1 }

ogOMTRAPSConnectivityTestSignal OBJECT-TYPE
	SYNTAX DisplayString
	MAX-ACCESS read-only
	STATUS current
	DESCRIPTION
			"Signal value from the cellular connectivity test"
	::= { ogOMTRAPSEvent 2 }

ogOMTRAPSConnectivityTestSignalStatus OBJECT-TYPE
	SYNTAX DisplayString
	MAX-ACCESS read-only
	STATUS current
	DESCRIPTION
			"Signal status of cellular connectivity test"
	::= { ogOMTRAPSEvent 3 }

ogOMTRAPSSSHLoginStatus OBJECT-TYPE
	SYNTAX DisplayString
	MAX-ACCESS read-only
	STATUS current
	DESCRIPTION
			"SSH Login"
	::= { ogOMTRAPSEvent 4 }

ogOMTRAPSWebLoginStatus OBJECT-TYPE
	SYNTAX DisplayString
	MAX-ACCESS read-only
	STATUS current
	DESCRIPTION
			"WebUI Login"
	::= { ogOMTRAPSEvent 5 }

ogOMTRAPSBusVoltage OBJECT-TYPE
	SYNTAX Integer32
	UNITS "0.1 Volt DC"
	MAX-ACCESS read-only
	STATUS current
	DESCRIPTION
			"The magnitude of the bus voltage."
	::= { ogOMTRAPSEvent 6 }

ogOMTRAPSRebootStatus OBJECT-TYPE
	SYNTAX DisplayString
	MAX-ACCESS read-only
	STATUS current
	DESCRIPTION
			"System Reboot"
	::= { ogOMTRAPSEvent 7 }

ogOMTRAPSCellSignal OBJECT-TYPE
	SYNTAX Integer32
	MAX-ACCESS read-only
	STATUS current
	DESCRIPTION
			"Cell Signal Strength Indicator (0 to 100)"
	::= { ogOMTRAPSEvent 8 }

ogOMTRAPSConsoleLoginStatus OBJECT-TYPE
	SYNTAX DisplayString
	MAX-ACCESS read-only
	STATUS current
	DESCRIPTION
			"Console Login"
	::= { ogOMTRAPSEvent 9 }

ogOMTRAPSSerialPortID OBJECT-TYPE
	SYNTAX DisplayString
	MAX-ACCESS read-only
	STATUS current
	DESCRIPTION
			"Serial Port Name"
	::= { ogOMTRAPSEvent 10 }

ogOMTRAPSSerialPortUser OBJECT-TYPE
	SYNTAX DisplayString
	MAX-ACCESS read-only
	STATUS current
	DESCRIPTION
			"Serial Port Login Status"
	::= { ogOMTRAPSEvent 11 }

ogOMTRAPSNetworkLinkState OBJECT-TYPE
	SYNTAX DisplayString
	MAX-ACCESS read-only
	STATUS current
	DESCRIPTION
			"Network Link State"
	::= { ogOMTRAPSEvent 12 }

ogOMTRAPSNetworkLinkDescription OBJECT-TYPE
	SYNTAX DisplayString
	MAX-ACCESS read-only
	STATUS current
	DESCRIPTION
			"Network Link Description"
	::= { ogOMTRAPSEvent 13 }

ogOMTRAPSSensorTemperature OBJECT-TYPE
	SYNTAX Integer32
	UNITS "millidegrees Celsius"
	MAX-ACCESS read-only
	STATUS current
	DESCRIPTION
			"The Sensor Temperature"
	::= { ogOMTRAPSEvent 14 }

ogOMTRAPSSensorDevice OBJECT-TYPE
	SYNTAX DisplayString
	MAX-ACCESS read-only
	STATUS current
	DESCRIPTION
			"The Sensor Device"
	::= { ogOMTRAPSEvent 15 }

ogOMTRAPSAlarmSummary OBJECT-TYPE
	SYNTAX DisplayString
	MAX-ACCESS read-only
	STATUS current
	DESCRIPTION
			"The human readable summary for this alarm"
	::= { ogOMTRAPSEvent 16 }

-- ======== NOTIFICATIONS =============

ogOMTRAPSConnectivityTest NOTIFICATION-TYPE
	OBJECTS { ogOMTRAPSConnectivityTestResult, ogOMTRAPSConnectivityTestSignal, ogOMTRAPSConnectivityTestSignalStatus }
	STATUS current
	DESCRIPTION
		"The notification sent when a connectivity test event occurs"
	::= { ogOMTRAPSNotification 1 }

ogOMTRAPSSSHLogin NOTIFICATION-TYPE
	OBJECTS { ogOMTRAPSSSHLoginStatus }
	STATUS current
	DESCRIPTION
		"The notification sent when an SSH Login event occurs"
	::= { ogOMTRAPSNotification 2 }

ogOMTRAPSWebLogin NOTIFICATION-TYPE
	OBJECTS { ogOMTRAPSWebLoginStatus }
	STATUS current
	DESCRIPTION
		"The notification sent when a WebUI Login event occurs"
	::= { ogOMTRAPSNotification 3 }

ogOMTRAPSPSU1VoltageRangeAlert NOTIFICATION-TYPE
	OBJECTS { ogOMTRAPSBusVoltage }
	STATUS current
	DESCRIPTION
		"The notification sent when power supply 1 bus voltage status changes"
	::= { ogOMTRAPSNotification 4 }

ogOMTRAPSPSU2VoltageRangeAlert NOTIFICATION-TYPE
	OBJECTS { ogOMTRAPSBusVoltage }
	STATUS current
	DESCRIPTION
		"The notification sent when power supply 2 bus voltage status changes"
	::= { ogOMTRAPSNotification 5 }

ogOMTRAPSReboot NOTIFICATION-TYPE
	OBJECTS { ogOMTRAPSRebootStatus }
	STATUS current
	DESCRIPTION
		"The notification sent when the system has just rebooted"
	::= { ogOMTRAPSNotification 6 }

ogOMTRAPSCellSignalAlert NOTIFICATION-TYPE
	OBJECTS { ogOMTRAPSCellSignal }
	STATUS current
	DESCRIPTION
		"The notification sent when the cell signal status changes"
	::= { ogOMTRAPSNotification 7 }

ogOMTRAPSConfigChange NOTIFICATION-TYPE
	STATUS current
	DESCRIPTION
		"The notification sent when the system configuration changes"
	::= { ogOMTRAPSNotification 8 }

ogOMTRAPSConsoleLogin NOTIFICATION-TYPE
	OBJECTS { ogOMTRAPSConsoleLoginStatus }
	STATUS current
	DESCRIPTION
		"The notification sent when a Console Login event occurs"
	::= { ogOMTRAPSNotification 9 }

ogOMTRAPSSerialPortLoginAlert NOTIFICATION-TYPE
	OBJECTS { ogOMTRAPSSerialPortID, ogOMTRAPSSerialPortUser }
	STATUS current
	DESCRIPTION
		"The notification sent when a Serial Port Login event occurs"
	::= { ogOMTRAPSNotification 10 }

ogOMTRAPSSerialPortLogoutAlert NOTIFICATION-TYPE
	OBJECTS { ogOMTRAPSSerialPortID, ogOMTRAPSSerialPortUser }
	STATUS current
	DESCRIPTION
		"The notification sent when a Serial Port Logout event occurs"
	::= { ogOMTRAPSNotification 11 }

ogOMTRAPSNetworkLinkStateAlert NOTIFICATION-TYPE
	OBJECTS { ogOMTRAPSNetworkLinkState, ogOMTRAPSNetworkLinkDescription}
	STATUS current
	DESCRIPTION
		"The notification sent when a Network link state changes"
	::= { ogOMTRAPSNotification 12 }

ogOMTRAPSSensorTemperatureRangeAlert NOTIFICATION-TYPE
	OBJECTS { ogOMTRAPSSensorTemperature, ogOMTRAPSSensorDevice, ogOMTRAPSAlarmSummary }
	STATUS current
	DESCRIPTION
		"The notification sent when sensor temperature status changes"
	::= { ogOMTRAPSNotification 13 }

--  ======== CONFORMANCE =============

ogOMTRAPSMibConformance OBJECT IDENTIFIER ::= { ogOMTRAPSMib 3 }
ogOMTRAPSMibCompliances OBJECT IDENTIFIER ::= { ogOMTRAPSMibConformance 1 }
ogOMTRAPSMibGroups      OBJECT IDENTIFIER ::= { ogOMTRAPSMibConformance 2 }

ogOMTRAPSMibCompliance MODULE-COMPLIANCE
	STATUS  current
	DESCRIPTION
		"The compliance statement for OM entities which implement
		the Opengear OM MIB."
	MODULE  -- this module
	MANDATORY-GROUPS { ogOMTRAPSMibGroup }

	GROUP ogOMTRAPSNotificationsGroup
		DESCRIPTION
			"The implementation of this group is
			mandatory for Opengear OM systems."
	::= { ogOMTRAPSMibCompliances 1 }

ogOMTRAPSMibGroup OBJECT-GROUP
	OBJECTS {
		ogOMTRAPSConnectivityTestResult,
		ogOMTRAPSConnectivityTestSignal,
		ogOMTRAPSConnectivityTestSignalStatus,
		ogOMTRAPSSSHLoginStatus,
		ogOMTRAPSWebLoginStatus,
		ogOMTRAPSBusVoltage,
		ogOMTRAPSRebootStatus,
		ogOMTRAPSCellSignal,
		ogOMTRAPSConsoleLoginStatus,
		ogOMTRAPSSerialPortID,
		ogOMTRAPSSerialPortUser,
		ogOMTRAPSNetworkLinkState,
		ogOMTRAPSNetworkLinkDescription,
		ogOMTRAPSSensorTemperature,
		ogOMTRAPSSensorDevice,
		ogOMTRAPSAlarmSummary}

	STATUS  current
	DESCRIPTION
		"A collection of objects providing various capabilities of the OM device."
	::= { ogOMTRAPSMibGroups 1 }

ogOMTRAPSNotificationsGroup NOTIFICATION-GROUP
	NOTIFICATIONS {
		ogOMTRAPSConnectivityTest,
		ogOMTRAPSSSHLogin,
		ogOMTRAPSWebLogin,
		ogOMTRAPSPSU1VoltageRangeAlert,
		ogOMTRAPSPSU2VoltageRangeAlert,
		ogOMTRAPSReboot,
		ogOMTRAPSCellSignalAlert,
		ogOMTRAPSConfigChange,
		ogOMTRAPSConsoleLogin,
		ogOMTRAPSSerialPortLoginAlert,
		ogOMTRAPSSerialPortLogoutAlert,
		ogOMTRAPSNetworkLinkStateAlert,
		ogOMTRAPSSensorTemperatureRangeAlert}

	STATUS  current
	DESCRIPTION
		"A collection of notification(s) for the Opengear OM device."
	::= { ogOMTRAPSMibGroups 2 }

END

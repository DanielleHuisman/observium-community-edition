TALARI-MIB DEFINITIONS ::= BEGIN

--
-- Talari MIB, last updated 09/26/2018
-- Copyright (c) 2008-2018 Talari Networks Inc. All rights Reserved.
--

IMPORTS
        MODULE-IDENTITY,
        OBJECT-IDENTITY,
        OBJECT-TYPE,
        NOTIFICATION-TYPE,
        enterprises
                FROM SNMPv2-SMI
        Integer32,
        Counter32,
        Gauge32,
        Counter64,
        IpAddress,
        TimeTicks
                FROM SNMPv2-SMI
        TEXTUAL-CONVENTION,
        DisplayString,
        PhysAddress,
        TruthValue,
        RowStatus,
        TimeStamp,
        AutonomousType,
        TestAndIncr
                FROM SNMPv2-TC;

talari MODULE-IDENTITY
    LAST-UPDATED "201808200000Z"
    ORGANIZATION "www.talari.com"
    CONTACT-INFO
         "postal:   Talari Networks
                    1 Almaden Blvd., Suite 200
                    San Jose, CA 95113

          email:    support@talari.com"

    DESCRIPTION
        "Add VT800128 and CT800128 models.
        VT800128 and CT800128 models - the names cannot have special chars like underscore"
    REVISION "201808200000Z"
    DESCRIPTION
        "In TalariEventObjectTypeEnum added wanlinkthreshold object type and
	vipduplicate vipnotduplicate waningressusagelowerthresholdexceeded waningressusagelowerthresholdok
	wanegressusagelowerthresholdexceeded wanegressusagelowerthresholdok
	waningressusagehigherthresholdexceeded waningressusagehigherthresholdok
	wanegressusagehigherthresholdexceeded wanegressusagehigherthresholdok"
    REVISION "201807180000Z"
    DESCRIPTION
        "In tnStatsRouteProtocol - changed the enumeration values to not use all
	 caps"
    REVISION "201709060000Z"
    DESCRIPTION
        "In TalariEventObjectTypeEnum added dynamicrouting and wanop object types"
    REVISION "201706060000Z"
    DESCRIPTION
        "Changed postal contact-info"
    REVISION "201701230000Z"
    DESCRIPTION
        "Added awareclientunlicensed hasecondaryunlicensed servicecontractunlicensed
	 eventstates."
    REVISION     "201701190000Z"
    DESCRIPTION
        "Added ipsectunnel virtualinterface and licensesubsystem.
         added congested uncongested viplearned vipreleased
         vipexpired vipgwnorsp viprcvdnak vipdetecteddup vipdhcpsnorsp
         licenseexpired featuremismatch configlicensemismatch
         unlicensedappliance licenseactive licensebankunreachable
         licensebankreachable bandwidthexceeded eventstates and new licensesubsystem."
    REVISION     "201701100000Z"
    DESCRIPTION
        "Added sysObjectID for the new vt800 model."
    REVISION     "201602190000Z"
    DESCRIPTION
        "Corrected ServiceType to include lan_gre and
         lan_ipsec values.  Also under Protocol value 0
         is not applicable and value 3 is APN protocol."
    REVISION     "201602030000Z"
    DESCRIPTION
        "The MIB module for managing the Talari Networks
         Adaptive Private Network Appliance."
    REVISION     "201510150000Z"
    DESCRIPTION
        "Obsolete tnStatsRouteFallback field."
    REVISION     "201504010000Z"
    DESCRIPTION
        "Added tnStatsLanGRETunnels and langretunnel event."
    REVISION     "201501190000Z"
    DESCRIPTION
        "Added wanlinkcongestion and usagecongestion events."
    REVISION     "201409050000Z"
    DESCRIPTION
        "Added sysObjectIDs for tnStatsRouteEligible, tnStatsRouteEligibilityType and
         tnStatsRouteEligibilityValue."
    REVISION     "201406300000Z"
    DESCRIPTION
        "Added sysObjectID for the new ct800 model."
    REVISION     "201406060000Z"
    DESCRIPTION
        "Added sysObjectID for the new t860 model."
    REVISION     "201403130000Z"
    DESCRIPTION
        "Added TCs for the new object and event types for
         the Network Management System."
    REVISION     "201401020000Z"
    DESCRIPTION
        "Added support for traps generated by the Network
	management system."
    REVISION     "201311120000Z"
    DESCRIPTION
        "adding dynamicconduit to TalariEventObjectTypeEnum"
    REVISION     "201311080000Z"
    DESCRIPTION
        "Added new event type for systemerror, activeha,
         standbyha, activencn, standbyncn."
    REVISION     "201310090000Z"
    DESCRIPTION
        "syntax corrections to this MIB"
    REVISION     "201309100000Z"
    DESCRIPTION
        "adding tnStatsRuleLastActiveNMinuteAgo,
         tnStatsCondutRuleLastActiveNMinuteAgo,
         tnStatsInternetRuleLastActiveNMinuteAgo,
         tnStatsIntranetRuleLastActiveNMinuteAgo,
         tnStatsDynamicCondutRuleLastActiveNMinuteAgo."
    REVISION     "201308120000Z"
    DESCRIPTION
        "tnStatsConduitPathPacketsDropped and
         tnStatsConduitPathBytesDropped changed to
         obsolete since they were not being accumulated
         by the appliance."
    REVISION     "201306240000Z"
    DESCRIPTION
        "talariNumEvents is a guage type because of events
         cleanup that are 30 days old."
    REVISION     "201306070000Z"
    DESCRIPTION
        "Update for Dynamic Conduits."
    REVISION     "201305200000Z"
    DESCRIPTION
        "Add tnStatsApplianceSerialNumber - Appliance Serial Number."
    REVISION     "201305130000Z"
    DESCRIPTION
        "Remove support for bytes dropped, packets dropped,
         bowt, jitter and packets lost counters for conduit.
         Added supported for the above counters for send and
         receive direction on the conduit.  Also added ooo
         packets on the conduit and conduit paths."
    REVISION     "201305090000Z"
    DESCRIPTION
        "Clarify rule counters are measured over 1 minute
         interval."
    REVISION     "201305070000Z"
    DESCRIPTION
        "Definition of tnStatsConduitClassType was flipped
         between realtime and bulk."
    REVISION     "201207160000Z"
    DESCRIPTION
        "Add appliance state and appliance HA state.  Added
         packets lost counters for conduit and conduit paths."
    REVISION     "201107210000Z"
    DESCRIPTION
        "Cleanup of some syntax issues and types"
    REVISION     "201106130000Z"
    DESCRIPTION
        "Added new features for the 2.3 APNWare release
          - Multiple intranet services support
          - Updated rule statistics
          - Support for new model, the T510"
    REVISION     "201103240000Z"
    DESCRIPTION
        "Reorganized the MIB and added new simplified tables
         combining identifying configuration information
         along with counters in a single set of tables for
         all object types.  Also added OIDs for each of the
         different models"
    REVISION     "201012080000Z"
    DESCRIPTION
        "Added new event types and object types for the
         the talari Events."
    REVISION     "201008120000Z"
    DESCRIPTION
        "Added traps to the talariNotifs and a table for
         the talari Events."
    REVISION     "200910260000Z"
    DESCRIPTION
        "Re-write for 2.0 Talari release"
    REVISION     "200811180000Z"
    DESCRIPTION
        "First draft"
    ::= { enterprises 34086 }

--
--
--
talariObjects     OBJECT IDENTIFIER ::= { talari 2 }
talariNotifs      OBJECT IDENTIFIER ::= { talari 3 }
talariConform     OBJECT IDENTIFIER ::= { talari 4 }
talariAgentOIDs   OBJECT IDENTIFIER ::= { talari 5 }

--
--
--
talariAPNAppliance OBJECT IDENTIFIER ::= { talariAgentOIDs 1 }
talariT200         OBJECT IDENTIFIER ::= { talariAgentOIDs 2 }
talariT700         OBJECT IDENTIFIER ::= { talariAgentOIDs 3 }
talariT730         OBJECT IDENTIFIER ::= { talariAgentOIDs 4 }
talariT750         OBJECT IDENTIFIER ::= { talariAgentOIDs 5 }
talariT3000        OBJECT IDENTIFIER ::= { talariAgentOIDs 6 }
talariVT100        OBJECT IDENTIFIER ::= { talariAgentOIDs 7 }
talariT510         OBJECT IDENTIFIER ::= { talariAgentOIDs 8 }
talariT5000        OBJECT IDENTIFIER ::= { talariAgentOIDs 9 }
talariT3010        OBJECT IDENTIFIER ::= { talariAgentOIDs 10 }
talariT860         OBJECT IDENTIFIER ::= { talariAgentOIDs 11 }
talariCT800        OBJECT IDENTIFIER ::= { talariAgentOIDs 12 }
talariVT500        OBJECT IDENTIFIER ::= { talariAgentOIDs 13 }
talariT5200        OBJECT IDENTIFIER ::= { talariAgentOIDs 14 }
talariVT800        OBJECT IDENTIFIER ::= { talariAgentOIDs 15 }
talariE100         OBJECT IDENTIFIER ::= { talariAgentOIDs 16 }
talariVCN800       OBJECT IDENTIFIER ::= { talariAgentOIDs 17 }
talariE1000        OBJECT IDENTIFIER ::= { talariAgentOIDs 18 }
talariE50          OBJECT IDENTIFIER ::= { talariAgentOIDs 19 }
talariE500         OBJECT IDENTIFIER ::= { talariAgentOIDs 20 }
talariVT800128     OBJECT IDENTIFIER ::= { talariAgentOIDs 21 }
talariCT800128     OBJECT IDENTIFIER ::= { talariAgentOIDs 22 }


--
--
--
talariConfiguration   OBJECT IDENTIFIER ::= { talariObjects 1 }
talariStatistics      OBJECT IDENTIFIER ::= { talariObjects 2 }
talariEvents          OBJECT IDENTIFIER ::= { talariObjects 3 }

--
-- Statistics sub-section.
-- This contains information for the following.
--
-- Appliances
-- Ethernet Interfaces
-- Routes
-- Rules
-- WAN Links
-- Conduits
--    ConduitPaths
--    ConduitClasses
--    ConduitRules
-- Internet Service
--    InternetRules
-- Intranet Service
--    IntranetRules
-- Passthrough Service
-- RoutesV2
-- DynamicConduits
--    DynamicConduitPaths
--    DynamicConduitClasses
--    DynamicConduitRules

--
-- Statistics for the Appliance object
--
tnStatsAppliances   OBJECT IDENTIFIER ::= { talariStatistics 12 }

tnStatsApplianceScalars   OBJECT IDENTIFIER ::= { tnStatsAppliances 1 }

tnStatsApplianceName            OBJECT-TYPE
    SYNTAX      DisplayString
    MAX-ACCESS  read-only
    STATUS      current
    DESCRIPTION
            "The string name for the appliance."
    ::= { tnStatsApplianceScalars 1 }

tnStatsApplianceModel            OBJECT-TYPE
    SYNTAX      OBJECT IDENTIFIER
    MAX-ACCESS  read-only
    STATUS      current
    DESCRIPTION
            "The OID for the model of this appliance."
    ::= { tnStatsApplianceScalars 2 }

tnStatsApplianceModelName        OBJECT-TYPE
    SYNTAX      DisplayString
    MAX-ACCESS  read-only
    STATUS      current
    DESCRIPTION
            "The string representation of the model for the appliance."
    ::= { tnStatsApplianceScalars 3 }


tnStatsApplianceBytesSent         OBJECT-TYPE
    SYNTAX      Counter64
    MAX-ACCESS  read-only
    STATUS      current
    DESCRIPTION
            "The count of the number of bytes sent for the appliance since
             the last time the Talari service was started."
    ::= { tnStatsApplianceScalars 4 }

tnStatsAppliancePacketsSent       OBJECT-TYPE
    SYNTAX      Counter64
    MAX-ACCESS  read-only
    STATUS      current
    DESCRIPTION
            "The count of the number of packets sent for the appliance since
             the last time the Talari service was started."
    ::= { tnStatsApplianceScalars 5 }

tnStatsApplianceBytesReceived     OBJECT-TYPE
    SYNTAX      Counter64
    MAX-ACCESS  read-only
    STATUS      current
    DESCRIPTION
            "The count of the number of bytes received for the appliance since
             the last time the Talari service was started."
    ::= { tnStatsApplianceScalars 6 }

tnStatsAppliancePacketsReceived   OBJECT-TYPE
    SYNTAX      Counter64
    MAX-ACCESS  read-only
    STATUS      current
    DESCRIPTION
            "The count of the number of packets received for the appliance since
             the last time the Talari service was started."
    ::= { tnStatsApplianceScalars 7 }

tnStatsApplianceBytesDropped      OBJECT-TYPE
    SYNTAX      Counter64
    MAX-ACCESS  read-only
    STATUS      current
    DESCRIPTION
            "The count of the number of bytes dropped for the appliance since
             the last time the Talari service was started."
    ::= { tnStatsApplianceScalars 8 }

tnStatsAppliancePacketsDropped    OBJECT-TYPE
    SYNTAX      Counter64
    MAX-ACCESS  read-only
    STATUS      current
    DESCRIPTION
            "The count of the number of packets dropped for the appliance since
             the last time the Talari service was started."
    ::= { tnStatsApplianceScalars 9 }

tnStatsApplianceState             OBJECT-TYPE
    SYNTAX  INTEGER {
                undefined(0),    -- Undefined state
                disabled(1),     -- Disabled
                enabled(2)       -- Enabled
            }
    MAX-ACCESS  read-only
    STATUS      current
    DESCRIPTION
            "The state of the appliance - whether or not it is enabled
             (passing traffic) or disabled."
    ::= { tnStatsApplianceScalars 10 }

tnStatsApplianceHAState           OBJECT-TYPE
    SYNTAX  INTEGER {
                undefined(0),      -- Undefined state
                notConfigured(1),  -- HA not configured
                active(2),         -- Active
                standby(3)         -- Standby
            }
    MAX-ACCESS  read-only
    STATUS      current
    DESCRIPTION
            "The High Availability state of the appliance - whether or not it
            is the currently active appliance or the standby appliance."
    ::= { tnStatsApplianceScalars 11 }

tnStatsApplianceSerialNumber     OBJECT-TYPE
    SYNTAX      DisplayString
    MAX-ACCESS  read-only
    STATUS      current
    DESCRIPTION
            "The string representation of the serial number for the appliance."
    ::= { tnStatsApplianceScalars 12 }

tnStatsApplianceOSVersion        OBJECT-TYPE
    SYNTAX      DisplayString
    MAX-ACCESS  read-only
    STATUS      current
    DESCRIPTION
            "The string representation of the OS Version."
    ::= { tnStatsApplianceScalars 13 }

tnStatsApplianceSoftwareVersion  OBJECT-TYPE
    SYNTAX      DisplayString
    MAX-ACCESS  read-only
    STATUS      current
    DESCRIPTION
            "The string representation of the Software Version running on 
             the appliance."
    ::= { tnStatsApplianceScalars 14 }

tnStatsApplianceConfigCreatedOn  OBJECT-TYPE
    SYNTAX      DisplayString
    MAX-ACCESS  read-only
    STATUS      current
    DESCRIPTION
            "Day and Time Talari Configuration was created.  Only displayed
            on client when appliance is not disabled."
    ::= { tnStatsApplianceScalars 15 }

--
-- Stats associated with Ethernet Interfaces
--
tnStatsEthernetInterfaces   OBJECT IDENTIFIER ::= { talariStatistics 13 }

tnStatsEthernetInterfaceScalars   OBJECT IDENTIFIER ::= { tnStatsEthernetInterfaces 1 }

tnStatsNumEthernetInterfaces OBJECT-TYPE
    SYNTAX         Integer32
    MAX-ACCESS     read-only
    STATUS         current
    DESCRIPTION
            "The total number of Ethernet interfaces."
    DEFVAL { 0 }
    ::= { tnStatsEthernetInterfaceScalars 1 }

tnStatsEthernetInterfaceTable OBJECT-TYPE
    SYNTAX      SEQUENCE OF TnStatsEthernetInterfaceEntry
    MAX-ACCESS  not-accessible
    STATUS      current
    DESCRIPTION
            "A collection of statistics for Ethernet Interface objects.
            Contains statistics counts for all the Ethernet Interfaces in
            the system.  Counter data in this table is updated once a
            minute and is a cumulative count since the last time the
            Talari service was started."

    ::= { tnStatsEthernetInterfaces 2 }

tnStatsEthernetInterfaceEntry OBJECT-TYPE
    SYNTAX      TnStatsEthernetInterfaceEntry
    MAX-ACCESS  not-accessible
    STATUS      current
    DESCRIPTION
            "An entry containing management information applicable to a
            particular Ethernet interface object."
    INDEX   { tnStatsEthernetInterfaceIndex }
    ::= { tnStatsEthernetInterfaceTable 1 }

TnStatsEthernetInterfaceEntry ::=
    SEQUENCE {
        tnStatsEthernetInterfaceIndex             Integer32,
        tnStatsEthernetInterfaceIfIndex           Integer32,
        tnStatsEthernetInterfaceName              DisplayString,
        tnStatsEthernetInterfaceBytesSent         Counter64,
        tnStatsEthernetInterfacePacketsSent       Counter64,
        tnStatsEthernetInterfaceBytesReceived     Counter64,
        tnStatsEthernetInterfacePacketsReceived   Counter64,
        tnStatsEthernetInterfaceBytesDropped      Counter64,
        tnStatsEthernetInterfacePacketsDropped    Counter64
    }

tnStatsEthernetInterfaceIndex              OBJECT-TYPE
    SYNTAX      Integer32
    MAX-ACCESS  read-only
    STATUS      current
    DESCRIPTION
            "The unique Talari Index value for the Ethernet
            interface."
    ::= { tnStatsEthernetInterfaceEntry 1 }

tnStatsEthernetInterfaceIfIndex            OBJECT-TYPE
    SYNTAX      Integer32
    MAX-ACCESS  read-only
    STATUS      current
    DESCRIPTION
            "The unique ifIndex value for the Ethernet
            interface.  This can be used to reference
            information in the IF-MIB about this interface."
    ::= { tnStatsEthernetInterfaceEntry 2 }

tnStatsEthernetInterfaceName              OBJECT-TYPE
    SYNTAX      DisplayString
    MAX-ACCESS  read-only
    STATUS      current
    DESCRIPTION
            "The name for the Ethernet interface.  This is the
            name shown on the front panel of the appliance and
            used in the user interfaces (Web and CLI)."
    ::= { tnStatsEthernetInterfaceEntry 3 }

tnStatsEthernetInterfaceBytesSent         OBJECT-TYPE
    SYNTAX      Counter64
    MAX-ACCESS  read-only
    STATUS      current
    DESCRIPTION
            "The count of bytes sent for this Ethernet interface."
    ::= { tnStatsEthernetInterfaceEntry 4 }

tnStatsEthernetInterfacePacketsSent       OBJECT-TYPE
    SYNTAX      Counter64
    MAX-ACCESS  read-only
    STATUS      current
    DESCRIPTION
            "The count of packets sent for this Ethernet interface."
    ::= { tnStatsEthernetInterfaceEntry 5 }

tnStatsEthernetInterfaceBytesReceived     OBJECT-TYPE
    SYNTAX      Counter64
    MAX-ACCESS  read-only
    STATUS      current
    DESCRIPTION
            "The count of bytes received for this Ethernet interface."
    ::= { tnStatsEthernetInterfaceEntry 6 }

tnStatsEthernetInterfacePacketsReceived   OBJECT-TYPE
    SYNTAX      Counter64
    MAX-ACCESS  read-only
    STATUS      current
    DESCRIPTION
            "The count of packets received for this Ethernet interface."
    ::= { tnStatsEthernetInterfaceEntry 7 }

tnStatsEthernetInterfaceBytesDropped      OBJECT-TYPE
    SYNTAX      Counter64
    MAX-ACCESS  read-only
    STATUS      current
    DESCRIPTION
            "The count of bytes dropped for this Ethernet interface."
    ::= { tnStatsEthernetInterfaceEntry 8 }

tnStatsEthernetInterfacePacketsDropped    OBJECT-TYPE
    SYNTAX      Counter64
    MAX-ACCESS  read-only
    STATUS      current
    DESCRIPTION
            "The count of packets dropped for this Ethernet interface."
    ::= { tnStatsEthernetInterfaceEntry 9 }

--
-- Stats associated with Routes
--
tnStatsRoutes   OBJECT IDENTIFIER ::= { talariStatistics 14 }

--tnStatsRouteScalars   OBJECT IDENTIFIER ::= { tnStatsRoutes 1 }

--tnStatsNumRoutes OBJECT-TYPE
--    SYNTAX         Integer32
--    MAX-ACCESS     read-only
--    STATUS         obsolete
--    DESCRIPTION
--            "The total number of routes in the system."
--    DEFVAL { 0 }
--    ::= { tnStatsRouteScalars 1 }


tnStatsRouteTable OBJECT-TYPE
    SYNTAX      SEQUENCE OF TnStatsRouteEntry
    MAX-ACCESS  not-accessible
    STATUS      obsolete
    DESCRIPTION
            "A collection of statistics for route objects.
            Contains statistics counts for all the routes in
            the system.  Counter data in this table is updated once a
            minute and is a cumulative count since the last time the
            Talari service was started."

    ::= { tnStatsRoutes 2 }

tnStatsRouteEntry OBJECT-TYPE
    SYNTAX      TnStatsRouteEntry
    MAX-ACCESS  not-accessible
    STATUS      obsolete
    DESCRIPTION
            "An entry containing management information applicable to a
            particular route object."
    INDEX   { tnStatsRouteIndex }
    ::= { tnStatsRouteTable 1 }

TnStatsRouteEntry ::=
    SEQUENCE {
        tnStatsRouteIndex             Integer32,
        tnStatsRouteID                Integer32,
        tnStatsRouteHitCount          Counter64
    }

tnStatsRouteIndex            OBJECT-TYPE
    SYNTAX      Integer32
    MAX-ACCESS  read-only
    STATUS      obsolete
    DESCRIPTION
            "The unique index value for the route."
    ::= { tnStatsRouteEntry 1 }

tnStatsRouteID               OBJECT-TYPE
    SYNTAX      Integer32
    MAX-ACCESS  read-only
    STATUS      obsolete
    DESCRIPTION
            "The internal Talari ID for the route."
    ::= { tnStatsRouteEntry 2 }

tnStatsRouteHitCount         OBJECT-TYPE
    SYNTAX      Counter64
    MAX-ACCESS  read-only
    STATUS      obsolete
    DESCRIPTION
            "The count of the number of packets that have hit this route."
    ::= { tnStatsRouteEntry 3 }

--
-- Stats associated with Rules
--
tnStatsRules   OBJECT IDENTIFIER ::= { talariStatistics 15 }

tnStatsRuleScalars   OBJECT IDENTIFIER ::= { tnStatsRules 1 }

tnStatsNumRules OBJECT-TYPE
    SYNTAX         Integer32
    MAX-ACCESS     read-only
    STATUS         current
    DESCRIPTION
            "The total number of rules in the system."
    DEFVAL { 0 }
    ::= { tnStatsRuleScalars 1 }


tnStatsRuleTable OBJECT-TYPE
    SYNTAX      SEQUENCE OF TnStatsRuleEntry
    MAX-ACCESS  not-accessible
    STATUS      current
    DESCRIPTION
            "A collection of statistics for rule objects.
            Contains statistics counts for all the rules in
            the system.  Counter data in this table is updated once a
            minute and is a cumulative count since the last time the
            Talari service was started."

    ::= { tnStatsRules 2 }

tnStatsRuleEntry OBJECT-TYPE
    SYNTAX      TnStatsRuleEntry
    MAX-ACCESS  not-accessible
    STATUS      current
    DESCRIPTION
            "An entry containing management information applicable to a
            particular route object."
    INDEX   { tnStatsRuleIndex }
    ::= { tnStatsRuleTable 1 }

TnStatsRuleEntry ::=
    SEQUENCE {
        tnStatsRuleIndex               Integer32,
        tnStatsRuleID                  Integer32,
        tnStatsRuleApplicationName     DisplayString,
        tnStatsRuleWANIngressHitCount  Gauge32,
        tnStatsRuleWANEgressHitCount   Gauge32,
        tnStatsRuleBytesSent           Gauge32,
        tnStatsRulePacketsSent         Gauge32,
        tnStatsRuleBytesReceived       Gauge32,
        tnStatsRulePacketsReceived     Gauge32,
        tnStatsRuleBytesDropped        Gauge32,
        tnStatsRulePacketsDropped      Gauge32,
        tnStatsRuleLastActiveNMinuteAgo TimeTicks
    }

tnStatsRuleIndex            OBJECT-TYPE
    SYNTAX      Integer32
    MAX-ACCESS  read-only
    STATUS      current
    DESCRIPTION
            "The unique index value for the rule."
    ::= { tnStatsRuleEntry 1 }

tnStatsRuleID               OBJECT-TYPE
    SYNTAX      Integer32
    MAX-ACCESS  read-only
    STATUS      current
    DESCRIPTION
            "The unique Talari ID for the rule."
    ::= { tnStatsRuleEntry 2 }

tnStatsRuleApplicationName         OBJECT-TYPE
    SYNTAX      DisplayString
    MAX-ACCESS  read-only
    STATUS      current
    DESCRIPTION
            "The optional string application name associated with this rule."
    ::= { tnStatsRuleEntry 3 }

tnStatsRuleWANIngressHitCount         OBJECT-TYPE
    SYNTAX      Gauge32
    MAX-ACCESS  read-only
    STATUS      current
    DESCRIPTION
            "The count of the number of WAN Ingress packets that have
             hit this rule, measured over the past active minute."
    ::= { tnStatsRuleEntry 4 }

tnStatsRuleWANEgressHitCount         OBJECT-TYPE
    SYNTAX      Gauge32
    MAX-ACCESS  read-only
    STATUS      current
    DESCRIPTION
            "The count of the number of WAN Egress packets that have
            hit this rule, measured over the past active minute."
    ::= { tnStatsRuleEntry 5 }

tnStatsRuleBytesSent                 OBJECT-TYPE
    SYNTAX      Gauge32
    MAX-ACCESS  read-only
    STATUS      current
    DESCRIPTION
            "The count of the number of bytes sent that
            matched this rule, measured over the past active minute."
    ::= { tnStatsRuleEntry 6 }

tnStatsRulePacketsSent                 OBJECT-TYPE
    SYNTAX      Gauge32
    MAX-ACCESS  read-only
    STATUS      current
    DESCRIPTION
            "The count of the number of packets sent that
            matched this rule, measured over the past active minute."
    ::= { tnStatsRuleEntry 7 }

tnStatsRuleBytesReceived                 OBJECT-TYPE
    SYNTAX      Gauge32
    MAX-ACCESS  read-only
    STATUS      current
    DESCRIPTION
            "The count of the number of bytes received that
            matched this rule, measured over the past active minute."
    ::= { tnStatsRuleEntry 8 }

tnStatsRulePacketsReceived                 OBJECT-TYPE
    SYNTAX      Gauge32
    MAX-ACCESS  read-only
    STATUS      current
    DESCRIPTION
            "The count of the number of packets received that
            matched this rule, measured over the past active minute."
    ::= { tnStatsRuleEntry 9 }

tnStatsRuleBytesDropped                 OBJECT-TYPE
    SYNTAX      Gauge32
    MAX-ACCESS  read-only
    STATUS      current
    DESCRIPTION
            "The count of the number of bytes dropped that
            matched this rule, measured over the past active minute."
    ::= { tnStatsRuleEntry 10 }

tnStatsRulePacketsDropped                 OBJECT-TYPE
    SYNTAX      Gauge32
    MAX-ACCESS  read-only
    STATUS      current
    DESCRIPTION
            "The count of the number of packets dropped that
            matched this rule, measured over the past active minute."
    ::= { tnStatsRuleEntry 11 }

tnStatsRuleLastActiveNMinuteAgo            OBJECT-TYPE
    SYNTAX      TimeTicks
    MAX-ACCESS  read-only
    STATUS      current
    DESCRIPTION
            "This rule was hit last N Minutes ago.
            If this field value is 0 and either tnStatsRuleBytesSent
            or tnStatsRuleBytesReceived is not zero, then that means
            that this rule is currently being used.  The rule
            statistics contain the latest values.
            If this field is > 0, then the rule statistics is
            plateaued to show that this rule was used N minutes ago."

    ::= { tnStatsRuleEntry 12 }

--
-- Stats associated with WAN Links
--
tnStatsWANLinks   OBJECT IDENTIFIER ::= { talariStatistics 16 }

tnStatsWANLinkScalars   OBJECT IDENTIFIER ::= { tnStatsWANLinks 1 }

tnStatsNumWANLinks OBJECT-TYPE
    SYNTAX         Integer32
    MAX-ACCESS     read-only
    STATUS         current
    DESCRIPTION
            "The total number of WAN Links on this appliance."
    DEFVAL { 0 }
    ::= { tnStatsWANLinkScalars 1 }

tnStatsWANLinkTable OBJECT-TYPE
    SYNTAX      SEQUENCE OF TnStatsWANLinkEntry
    MAX-ACCESS  not-accessible
    STATUS      current
    DESCRIPTION
            "A collection of statistics for WAN Link objects.
            Contains statistics counts for all the WAN Links in
            the system.  Counter data in this table is updated once a
            minute and is a cumulative count since the last time the
            Talari service was started."

    ::= { tnStatsWANLinks 2 }

tnStatsWANLinkEntry OBJECT-TYPE
    SYNTAX      TnStatsWANLinkEntry
    MAX-ACCESS  not-accessible
    STATUS      current
    DESCRIPTION
            "An entry containing management information applicable to a
            particular WAN Link object."
    INDEX   { tnStatsWANLinkIndex }
    ::= { tnStatsWANLinkTable 1 }

TnStatsWANLinkEntry ::=
    SEQUENCE {
        tnStatsWANLinkIndex             Integer32,
        tnStatsWANLinkID                Integer32,
        tnStatsWANLinkName              DisplayString,
        tnStatsWANLinkState             Integer32,
        tnStatsWANLinkBytesSent         Counter64,
        tnStatsWANLinkPacketsSent       Counter64,
        tnStatsWANLinkBytesReceived     Counter64,
        tnStatsWANLinkPacketsReceived   Counter64,
        tnStatsWANLinkBytesDropped      Counter64,
        tnStatsWANLinkPacketsDropped    Counter64
    }

tnStatsWANLinkIndex            OBJECT-TYPE
    SYNTAX      Integer32
    MAX-ACCESS  read-only
    STATUS      current
    DESCRIPTION
            "The unique index value for the WAN Link."
    ::= { tnStatsWANLinkEntry 1 }

tnStatsWANLinkID               OBJECT-TYPE
    SYNTAX      Integer32
    MAX-ACCESS  read-only
    STATUS      current
    DESCRIPTION
            "The unique Talari ID for the WAN Link."
    ::= { tnStatsWANLinkEntry 2 }

tnStatsWANLinkName              OBJECT-TYPE
    SYNTAX      DisplayString
    MAX-ACCESS  read-only
    STATUS      current
    DESCRIPTION
            "The name for the WAN Link."
    ::= { tnStatsWANLinkEntry 3 }

tnStatsWANLinkState OBJECT-TYPE
    SYNTAX  INTEGER {
                undefined(0),    -- Undefined state
                disabled(1),     -- Admin Disabled
                dead(2),         -- Dead
                bad(3),          -- Errors above threshold
                good(4)          -- Passing traffic
            }
    MAX-ACCESS  read-only
    STATUS      current
    DESCRIPTION
            "The current operational state of the conduit."
    ::= { tnStatsWANLinkEntry 4 }

tnStatsWANLinkBytesSent         OBJECT-TYPE
    SYNTAX      Counter64
    MAX-ACCESS  read-only
    STATUS      current
    DESCRIPTION
            "The count of bytes sent for this WAN Link."
    ::= { tnStatsWANLinkEntry 5 }

tnStatsWANLinkPacketsSent       OBJECT-TYPE
    SYNTAX      Counter64
    MAX-ACCESS  read-only
    STATUS      current
    DESCRIPTION
            "The count of packets sent for this WAN Link."
    ::= { tnStatsWANLinkEntry 6 }

tnStatsWANLinkBytesReceived     OBJECT-TYPE
    SYNTAX      Counter64
    MAX-ACCESS  read-only
    STATUS      current
    DESCRIPTION
            "The count of bytes received for this WAN Link."
    ::= { tnStatsWANLinkEntry 7 }

tnStatsWANLinkPacketsReceived   OBJECT-TYPE
    SYNTAX      Counter64
    MAX-ACCESS  read-only
    STATUS      current
    DESCRIPTION
            "The count of packets received for this WAN Link."
    ::= { tnStatsWANLinkEntry 8 }

tnStatsWANLinkBytesDropped      OBJECT-TYPE
    SYNTAX      Counter64
    MAX-ACCESS  read-only
    STATUS      current
    DESCRIPTION
            "The count of bytes dropped for this WAN Link."
    ::= { tnStatsWANLinkEntry 9 }

tnStatsWANLinkPacketsDropped    OBJECT-TYPE
    SYNTAX      Counter64
    MAX-ACCESS  read-only
    STATUS      current
    DESCRIPTION
            "The count of packets dropped for this WAN Link."
    ::= { tnStatsWANLinkEntry 10 }

--
-- Stats associated with Conduits
--
tnStatsConduits   OBJECT IDENTIFIER ::= { talariStatistics 17 }

tnStatsConduitScalars   OBJECT IDENTIFIER ::= { tnStatsConduits 1 }

tnStatsNumConduits OBJECT-TYPE
    SYNTAX         Integer32
    MAX-ACCESS     read-only
    STATUS         current
    DESCRIPTION
            "The total number of Conduits."
    DEFVAL { 0 }
    ::= { tnStatsConduitScalars 1 }

tnStatsConduitTable OBJECT-TYPE
    SYNTAX      SEQUENCE OF TnStatsConduitEntry
    MAX-ACCESS  not-accessible
    STATUS      current
    DESCRIPTION
            "A collection of statistics for Conduit objects.
            Contains statistics counts for all the Conduits in
            the system.  Counter data in this table is updated once a
            minute and is a cumulative count since the last time the
            Talari service was started."

    ::= { tnStatsConduits 2 }

tnStatsConduitEntry OBJECT-TYPE
    SYNTAX      TnStatsConduitEntry
    MAX-ACCESS  not-accessible
    STATUS      current
    DESCRIPTION
            "An entry containing management information applicable to a
            particular Conduit object."
    INDEX   { tnStatsConduitIndex }
    ::= { tnStatsConduitTable 1 }

TnStatsConduitEntry ::=
    SEQUENCE {
        tnStatsConduitIndex             Integer32,
        tnStatsConduitID                Integer32,
        tnStatsConduitName              DisplayString,
        tnStatsConduitState             Integer32,
        tnStatsConduitBytesSent         Counter64,
        tnStatsConduitPacketsSent       Counter64,
        tnStatsConduitBytesReceived     Counter64,
        tnStatsConduitPacketsReceived   Counter64,
        tnStatsConduitBytesDropped      Counter64,
        tnStatsConduitPacketsDropped    Counter64,
        tnStatsConduitBOWTms            Gauge32,
        tnStatsConduitJitterms          Gauge32,
        tnStatsConduitNumPaths          Integer32,
        tnStatsConduitNumRules          Integer32,
        tnStatsConduitPacketsLost       Counter64,
        tnStatsConduitSendBytesDropped      Counter64,
        tnStatsConduitSendPacketsDropped    Counter64,
        tnStatsConduitSendPacketsLost       Counter64,
        tnStatsConduitSendPacketsOOO        Counter64,
        tnStatsConduitSendBOWTms            Gauge32,
        tnStatsConduitSendJitterms          Gauge32,
        tnStatsConduitReceiveBytesDropped   Counter64,
        tnStatsConduitReceivePacketsDropped Counter64,
        tnStatsConduitReceivePacketsLost    Counter64,
        tnStatsConduitReceivePacketsOOO     Counter64,
        tnStatsConduitReceiveBOWTms         Gauge32,
        tnStatsConduitReceiveJitterms       Gauge32
    }

tnStatsConduitIndex            OBJECT-TYPE
    SYNTAX      Integer32
    MAX-ACCESS  read-only
    STATUS      current
    DESCRIPTION
            "The unique index value for the Conduit."
    ::= { tnStatsConduitEntry 1 }

tnStatsConduitID               OBJECT-TYPE
    SYNTAX      Integer32
    MAX-ACCESS  read-only
    STATUS      current
    DESCRIPTION
            "The unique Talari ID for the Conduit."
    ::= { tnStatsConduitEntry 2 }

tnStatsConduitName              OBJECT-TYPE
    SYNTAX      DisplayString
    MAX-ACCESS  read-only
    STATUS      current
    DESCRIPTION
            "The name for the Conduit."
    ::= { tnStatsConduitEntry 3 }

tnStatsConduitState OBJECT-TYPE
    SYNTAX  INTEGER {
                undefined(0),    -- Undefined state
                disabled(1),     -- Admin Disabled
                dead(2),         -- Dead
                bad(3),          -- Errors above threshold
                good(4)          -- Passing traffic
            }
    MAX-ACCESS  read-only
    STATUS      current
    DESCRIPTION
            "The current operational state of the conduit."
    ::= { tnStatsConduitEntry 4 }

tnStatsConduitBytesSent         OBJECT-TYPE
    SYNTAX      Counter64
    MAX-ACCESS  read-only
    STATUS      current
    DESCRIPTION
            "The count of bytes sent for this Conduit."
    ::= { tnStatsConduitEntry 5 }

tnStatsConduitPacketsSent       OBJECT-TYPE
    SYNTAX      Counter64
    MAX-ACCESS  read-only
    STATUS      current
    DESCRIPTION
            "The count of packets sent for this Conduit."
    ::= { tnStatsConduitEntry 6 }

tnStatsConduitBytesReceived     OBJECT-TYPE
    SYNTAX      Counter64
    MAX-ACCESS  read-only
    STATUS      current
    DESCRIPTION
            "The count of bytes received for this Conduit."
    ::= { tnStatsConduitEntry 7 }

tnStatsConduitPacketsReceived   OBJECT-TYPE
    SYNTAX      Counter64
    MAX-ACCESS  read-only
    STATUS      current
    DESCRIPTION
            "The count of packets received for this Conduit."
    ::= { tnStatsConduitEntry 8 }

tnStatsConduitBytesDropped      OBJECT-TYPE
    SYNTAX      Counter64
    MAX-ACCESS  read-only
    STATUS      obsolete
    DESCRIPTION
            "The count of bytes dropped for this Conduit."
    ::= { tnStatsConduitEntry 9 }

tnStatsConduitPacketsDropped    OBJECT-TYPE
    SYNTAX      Counter64
    MAX-ACCESS  read-only
    STATUS      obsolete
    DESCRIPTION
            "The count of packets dropped for this Conduit."
    ::= { tnStatsConduitEntry 10 }

tnStatsConduitBOWTms            OBJECT-TYPE
    SYNTAX      Gauge32
    MAX-ACCESS  read-only
    STATUS      obsolete
    DESCRIPTION
            "The current best one-way time (BOWT) value (in milliseconds)
            value for this Conduit."
    ::= { tnStatsConduitEntry 11 }

tnStatsConduitJitterms          OBJECT-TYPE
    SYNTAX      Gauge32
    MAX-ACCESS  read-only
    STATUS      obsolete
    DESCRIPTION
            "The current best jitter value (in milliseconds) for this
            Conduit."
    ::= { tnStatsConduitEntry 12 }

tnStatsConduitNumPaths          OBJECT-TYPE
    SYNTAX      Integer32
    MAX-ACCESS  read-only
    STATUS      current
    DESCRIPTION
            "The number of Paths associated with this conduit - this
            is the number of rows in the tnStatsConduitPathsTable for
            the current conduit.  Each conduit can have a different
            number of paths associated with it."
    ::= { tnStatsConduitEntry 13 }

tnStatsConduitNumRules          OBJECT-TYPE
    SYNTAX      Integer32
    MAX-ACCESS  read-only
    STATUS      current
    DESCRIPTION
            "The number of Rules associated with this conduit - this
            is the number of rows in the tnStatsConduitRulesTable for
            the current conduit.  Each conduit can have a different
            number of rules associated with it."
    ::= { tnStatsConduitEntry 14 }

tnStatsConduitPacketsLost       OBJECT-TYPE
    SYNTAX      Counter64
    MAX-ACCESS  read-only
    STATUS      obsolete
    DESCRIPTION
            "The current total number of packets lost for this
            Conduit."
    ::= { tnStatsConduitEntry 15 }

tnStatsConduitSendBytesDropped      OBJECT-TYPE
    SYNTAX      Counter64
    MAX-ACCESS  read-only
    STATUS      current
    DESCRIPTION
            "The count of send bytes dropped for this Conduit."
    ::= { tnStatsConduitEntry 16 }

tnStatsConduitSendPacketsDropped    OBJECT-TYPE
    SYNTAX      Counter64
    MAX-ACCESS  read-only
    STATUS      current
    DESCRIPTION
            "The count of send packets dropped for this Conduit."
    ::= { tnStatsConduitEntry 17 }

tnStatsConduitSendPacketsLost       OBJECT-TYPE
    SYNTAX      Counter64
    MAX-ACCESS  read-only
    STATUS      current
    DESCRIPTION
            "The current total number of send packets lost for this
            Conduit."
    ::= { tnStatsConduitEntry 18 }

tnStatsConduitSendPacketsOOO        OBJECT-TYPE
    SYNTAX      Counter64
    MAX-ACCESS  read-only
    STATUS      current
    DESCRIPTION
            "The current total number of send packets received out
             of order by the remote on this Conduit."
    ::= { tnStatsConduitEntry 19 }

tnStatsConduitSendBOWTms            OBJECT-TYPE
    SYNTAX      Gauge32
    MAX-ACCESS  read-only
    STATUS      current
    DESCRIPTION
            "The current best one-way time (BOWT) value (in milliseconds)
            in the send direction for this Conduit."
    ::= { tnStatsConduitEntry 20 }

tnStatsConduitSendJitterms          OBJECT-TYPE
    SYNTAX      Gauge32
    MAX-ACCESS  read-only
    STATUS      current
    DESCRIPTION
            "The current worst jitter value (in milliseconds) in the send
            direction for this Conduit."
    ::= { tnStatsConduitEntry 21 }

tnStatsConduitReceiveBytesDropped      OBJECT-TYPE
    SYNTAX      Counter64
    MAX-ACCESS  read-only
    STATUS      current
    DESCRIPTION
            "The count of receive bytes dropped for this Conduit."
    ::= { tnStatsConduitEntry 22 }

tnStatsConduitReceivePacketsDropped    OBJECT-TYPE
    SYNTAX      Counter64
    MAX-ACCESS  read-only
    STATUS      current
    DESCRIPTION
            "The count of receive packets dropped for this Conduit."
    ::= { tnStatsConduitEntry 23 }

tnStatsConduitReceivePacketsLost       OBJECT-TYPE
    SYNTAX      Counter64
    MAX-ACCESS  read-only
    STATUS      current
    DESCRIPTION
            "The current total number of receive packets lost for this
            Conduit."
    ::= { tnStatsConduitEntry 24 }

tnStatsConduitReceivePacketsOOO        OBJECT-TYPE
    SYNTAX      Counter64
    MAX-ACCESS  read-only
    STATUS      current
    DESCRIPTION
            "The current total number of received packets out
             of order on this Conduit."
    ::= { tnStatsConduitEntry 25 }

tnStatsConduitReceiveBOWTms            OBJECT-TYPE
    SYNTAX      Gauge32
    MAX-ACCESS  read-only
    STATUS      current
    DESCRIPTION
            "The current best one-way time (BOWT) value (in milliseconds)
            in the receive direction for this Conduit."
    ::= { tnStatsConduitEntry 26 }

tnStatsConduitReceiveJitterms          OBJECT-TYPE
    SYNTAX      Gauge32
    MAX-ACCESS  read-only
    STATUS      current
    DESCRIPTION
            "The current worst jitter value (in milliseconds) in the
            receive direction for this Conduit."
    ::= { tnStatsConduitEntry 27 }

--
-- Stats for Paths associated with Conduits
--
tnStatsConduitPaths   OBJECT IDENTIFIER ::= { tnStatsConduits 3 }

tnStatsConduitPathTable OBJECT-TYPE
    SYNTAX      SEQUENCE OF TnStatsConduitPathEntry
    MAX-ACCESS  not-accessible
    STATUS      current
    DESCRIPTION
            "A collection of statistics for Conduit Path objects.
            Contains statistics counts for all the Conduit Paths in
            the system.  Counter data in this table is updated once a
            minute and is a cumulative count since the last time the
            Talari service was started.  The number of conduits in
            this table is stored in tnStatsNumConduits and the number
            of Paths for each conduit is in the variable
            tnStatsConduitNumPaths which is in the tnStatsConduitTable
            and has a specific number of paths value for each conduit
            index."
    ::= { tnStatsConduitPaths 1 }

tnStatsConduitPathEntry OBJECT-TYPE
    SYNTAX      TnStatsConduitPathEntry
    MAX-ACCESS  not-accessible
    STATUS      current
    DESCRIPTION
            "An entry containing management information applicable to a
            particular Conduit object."
    INDEX   { tnStatsConduitPathConduitIndex, tnStatsConduitPathPathIndex }
    ::= { tnStatsConduitPathTable 1 }

TnStatsConduitPathEntry ::=
    SEQUENCE {
        tnStatsConduitPathConduitIndex      Integer32,
        tnStatsConduitPathPathIndex         Integer32,
        tnStatsConduitPathConduitID         Integer32,
        tnStatsConduitPathPathID            Integer32,
        tnStatsConduitPathName              DisplayString,
        tnStatsConduitPathState             Integer32,
        tnStatsConduitPathBytesSent         Counter64,
        tnStatsConduitPathPacketsSent       Counter64,
        tnStatsConduitPathBytesReceived     Counter64,
        tnStatsConduitPathPacketsReceived   Counter64,
        tnStatsConduitPathBytesDropped      Counter64,
        tnStatsConduitPathPacketsDropped    Counter64,
        tnStatsConduitPathBOWTms            Gauge32,
        tnStatsConduitPathJitterms          Gauge32,
        tnStatsConduitPathPacketsLost       Counter64,
        tnStatsConduitPathPacketsOOO        Counter64
    }

tnStatsConduitPathConduitIndex            OBJECT-TYPE
    SYNTAX      Integer32
    MAX-ACCESS  read-only
    STATUS      current
    DESCRIPTION
            "The unique index (Conduit) value for the Conduit Path."
    ::= { tnStatsConduitPathEntry 1 }

tnStatsConduitPathPathIndex            OBJECT-TYPE
    SYNTAX      Integer32
    MAX-ACCESS  read-only
    STATUS      current
    DESCRIPTION
            "The unique index (Path) value for the Conduit Path."
    ::= { tnStatsConduitPathEntry 2 }

tnStatsConduitPathConduitID               OBJECT-TYPE
    SYNTAX      Integer32
    MAX-ACCESS  read-only
    STATUS      current
    DESCRIPTION
            "The unique Talari ID (Conduit) value for the Conduit Path."
    ::= { tnStatsConduitPathEntry 3 }

tnStatsConduitPathPathID               OBJECT-TYPE
    SYNTAX      Integer32
    MAX-ACCESS  read-only
    STATUS      current
    DESCRIPTION
            "The unique Talari ID (Path) value for the Conduit Path."
    ::= { tnStatsConduitPathEntry 4 }

tnStatsConduitPathName              OBJECT-TYPE
    SYNTAX      DisplayString
    MAX-ACCESS  read-only
    STATUS      current
    DESCRIPTION
            "The name for the Conduit Path."
    ::= { tnStatsConduitPathEntry 5 }

tnStatsConduitPathState OBJECT-TYPE
    SYNTAX  INTEGER {
                undefined(0),    -- Undefined state
                disabled(1),     -- Admin Disabled
                dead(2),         -- Dead
                bad(3),          -- Errors above threshold
                good(4)          -- Passing traffic
            }
    MAX-ACCESS  read-only
    STATUS      current
    DESCRIPTION
            "The current operational state of the conduit."
    ::= { tnStatsConduitPathEntry 6 }

tnStatsConduitPathBytesSent         OBJECT-TYPE
    SYNTAX      Counter64
    MAX-ACCESS  read-only
    STATUS      current
    DESCRIPTION
            "The count of bytes sent for this Conduit Path."
    ::= { tnStatsConduitPathEntry 7 }

tnStatsConduitPathPacketsSent       OBJECT-TYPE
    SYNTAX      Counter64
    MAX-ACCESS  read-only
    STATUS      current
    DESCRIPTION
            "The count of packets sent for this Conduit Path."
    ::= { tnStatsConduitPathEntry 8 }

tnStatsConduitPathBytesReceived     OBJECT-TYPE
    SYNTAX      Counter64
    MAX-ACCESS  read-only
    STATUS      current
    DESCRIPTION
            "The count of bytes received for this Conduit Path."
    ::= { tnStatsConduitPathEntry 9 }

tnStatsConduitPathPacketsReceived   OBJECT-TYPE
    SYNTAX      Counter64
    MAX-ACCESS  read-only
    STATUS      current
    DESCRIPTION
            "The count of packets received for this Conduit Path."
    ::= { tnStatsConduitPathEntry 10 }

tnStatsConduitPathBytesDropped      OBJECT-TYPE
    SYNTAX      Counter64
    MAX-ACCESS  read-only
    STATUS      obsolete
    DESCRIPTION
            "The count of bytes dropped for this Conduit Path.
             This value was not counted by the appliance, so
             it has been removed."
    ::= { tnStatsConduitPathEntry 11 }

tnStatsConduitPathPacketsDropped    OBJECT-TYPE
    SYNTAX      Counter64
    MAX-ACCESS  read-only
    STATUS      obsolete
    DESCRIPTION
            "The count of packets dropped for this Conduit Path.
             This value was not counted by the appliance, so
             it has been removed."
    ::= { tnStatsConduitPathEntry 12 }

tnStatsConduitPathBOWTms            OBJECT-TYPE
    SYNTAX      Gauge32
    MAX-ACCESS  read-only
    STATUS      current
    DESCRIPTION
            "The current best one-way time (BOWT) value (in milliseconds)
            value for this Conduit Path."
    ::= { tnStatsConduitPathEntry 13 }

tnStatsConduitPathJitterms          OBJECT-TYPE
    SYNTAX      Gauge32
    MAX-ACCESS  read-only
    STATUS      current
    DESCRIPTION
            "The current best jitter value (in milliseconds) for this
            Conduit Path."
    ::= { tnStatsConduitPathEntry 14 }

tnStatsConduitPathPacketsLost       OBJECT-TYPE
    SYNTAX      Counter64
    MAX-ACCESS  read-only
    STATUS      current
    DESCRIPTION
            "The current total number of packets lost for this
            Conduit Path."
    ::= { tnStatsConduitPathEntry 15 }

tnStatsConduitPathPacketsOOO        OBJECT-TYPE
    SYNTAX      Counter64
    MAX-ACCESS  read-only
    STATUS      current
    DESCRIPTION
            "The current total number of out of order
             packets detected on this Conduit Path."
    ::= { tnStatsConduitPathEntry 16 }

--
-- Stats for Classes associated with Conduits
--
tnStatsConduitClasses   OBJECT IDENTIFIER ::= { tnStatsConduits 4 }

tnStatsConduitClassTable OBJECT-TYPE
    SYNTAX      SEQUENCE OF TnStatsConduitClassEntry
    MAX-ACCESS  not-accessible
    STATUS      current
    DESCRIPTION
            "A collection of statistics for Conduit Class objects.
            Contains statistics counts for all the Conduit Classes in
            the system.  Counter data in this table is updated once a
            minute and is a cumulative count since the last time the
            Talari service was started.  The number of conduits in
            this table is stored in tnStatsNumConduits and the number
            of Classes for each conduit is always 17."
    ::= { tnStatsConduitClasses 1 }

tnStatsConduitClassEntry OBJECT-TYPE
    SYNTAX      TnStatsConduitClassEntry
    MAX-ACCESS  not-accessible
    STATUS      current
    DESCRIPTION
            "An entry containing management information applicable to a
            particular Conduit object."
    INDEX   { tnStatsConduitClassConduitIndex, tnStatsConduitClassClassIndex }
    ::= { tnStatsConduitClassTable 1 }

TnStatsConduitClassEntry ::=
    SEQUENCE {
        tnStatsConduitClassConduitIndex      Integer32,
        tnStatsConduitClassClassIndex        Integer32,
        tnStatsConduitClassConduitID         Integer32,
        tnStatsConduitClassClassID           Integer32,
        tnStatsConduitClassName              DisplayString,
        tnStatsConduitClassType              Integer32,
        tnStatsConduitClassBytesSent         Counter64,
        tnStatsConduitClassPacketsSent       Counter64,
        tnStatsConduitClassBytesPending     Counter64,
        tnStatsConduitClassPacketsPending   Counter64,
        tnStatsConduitClassBytesDropped      Counter64,
        tnStatsConduitClassPacketsDropped    Counter64
    }

tnStatsConduitClassConduitIndex            OBJECT-TYPE
    SYNTAX      Integer32
    MAX-ACCESS  read-only
    STATUS      current
    DESCRIPTION
            "The unique index (Conduit) value for the Conduit Class."
    ::= { tnStatsConduitClassEntry 1 }

tnStatsConduitClassClassIndex            OBJECT-TYPE
    SYNTAX      Integer32
    MAX-ACCESS  read-only
    STATUS      current
    DESCRIPTION
            "The unique index (Class) value for the Conduit Class."
    ::= { tnStatsConduitClassEntry 2 }

tnStatsConduitClassConduitID               OBJECT-TYPE
    SYNTAX      Integer32
    MAX-ACCESS  read-only
    STATUS      current
    DESCRIPTION
            "The internal Talari ID for the Conduit object."
    ::= { tnStatsConduitClassEntry 3 }

tnStatsConduitClassClassID               OBJECT-TYPE
    SYNTAX      Integer32
    MAX-ACCESS  read-only
    STATUS      current
    DESCRIPTION
            "The internal Talari ID for the Class object."
    ::= { tnStatsConduitClassEntry 4 }

tnStatsConduitClassName              OBJECT-TYPE
    SYNTAX      DisplayString
    MAX-ACCESS  read-only
    STATUS      current
    DESCRIPTION
            "The name for the Conduit Class."
    ::= { tnStatsConduitClassEntry 5 }

tnStatsConduitClassType              OBJECT-TYPE
    SYNTAX  INTEGER {
                realtime(1),
                interactive(2),
                bulk(3),
                unknown(4)
            }
    MAX-ACCESS  read-only
    STATUS      current
    DESCRIPTION
            "The name for the Conduit Class."
    ::= { tnStatsConduitClassEntry 6 }

tnStatsConduitClassBytesSent         OBJECT-TYPE
    SYNTAX      Counter64
    MAX-ACCESS  read-only
    STATUS      current
    DESCRIPTION
            "The count of bytes sent for this Conduit Class."
    ::= { tnStatsConduitClassEntry 7 }

tnStatsConduitClassPacketsSent       OBJECT-TYPE
    SYNTAX      Counter64
    MAX-ACCESS  read-only
    STATUS      current
    DESCRIPTION
            "The count of packets sent for this Conduit Class."
    ::= { tnStatsConduitClassEntry 8 }

tnStatsConduitClassBytesPending     OBJECT-TYPE
    SYNTAX      Counter64
    MAX-ACCESS  read-only
    STATUS      current
    DESCRIPTION
            "The count of bytes pending for this Conduit Class."
    ::= { tnStatsConduitClassEntry 9 }

tnStatsConduitClassPacketsPending   OBJECT-TYPE
    SYNTAX      Counter64
    MAX-ACCESS  read-only
    STATUS      current
    DESCRIPTION
            "The count of packets pending for this Conduit Class."
    ::= { tnStatsConduitClassEntry 10 }

tnStatsConduitClassBytesDropped      OBJECT-TYPE
    SYNTAX      Counter64
    MAX-ACCESS  read-only
    STATUS      current
    DESCRIPTION
            "The count of bytes dropped for this Conduit Class."
    ::= { tnStatsConduitClassEntry 11 }

tnStatsConduitClassPacketsDropped    OBJECT-TYPE
    SYNTAX      Counter64
    MAX-ACCESS  read-only
    STATUS      current
    DESCRIPTION
            "The count of packets dropped for this Conduit Class."
    ::= { tnStatsConduitClassEntry 12 }

--
-- Stats for Rules associated with Conduits
--
tnStatsConduitRules   OBJECT IDENTIFIER ::= { tnStatsConduits 5 }

tnStatsConduitRuleTable OBJECT-TYPE
    SYNTAX      SEQUENCE OF TnStatsConduitRuleEntry
    MAX-ACCESS  not-accessible
    STATUS      current
    DESCRIPTION
            "A collection of statistics for Conduit Rule objects.
            Contains statistics counts for all the Conduit Rules in
            the system.  Counter data in this table is updated once a
            minute and is a cumulative count since the last time the
            Talari service was started.  The number of conduits in
            this table is stored in tnStatsNumConduits and the number
            of Rules for each conduit is in the variable
            tnStatsConduitNumRules which is in the tnStatsConduitTable
            and has a specific number of rules value for each conduit
            index."
    ::= { tnStatsConduitRules 1 }

tnStatsConduitRuleEntry OBJECT-TYPE
    SYNTAX      TnStatsConduitRuleEntry
    MAX-ACCESS  not-accessible
    STATUS      current
    DESCRIPTION
            "An entry containing management information applicable to a
            particular Conduit object."
    INDEX   { tnStatsConduitRuleConduitIndex, tnStatsConduitRuleRuleIndex }
    ::= { tnStatsConduitRuleTable 1 }

TnStatsConduitRuleEntry ::=
    SEQUENCE {
        tnStatsConduitRuleConduitIndex       Integer32,
        tnStatsConduitRuleRuleIndex          Integer32,
        tnStatsConduitRuleConduitID          Integer32,
        tnStatsConduitRuleRuleID             Integer32,
        tnStatsConduitRuleGlobalRuleIndex    Integer32,
        tnStatsConduitRuleApplicationName    DisplayString,
        tnStatsConduitRuleWANIngressHitCount Gauge32,
        tnStatsConduitRuleWANEgressHitCount  Gauge32,
        tnStatsConduitRuleBytesSent          Gauge32,
        tnStatsConduitRulePacketsSent        Gauge32,
        tnStatsConduitRuleBytesReceived      Gauge32,
        tnStatsConduitRulePacketsReceived    Gauge32,
        tnStatsConduitRuleBytesDropped       Gauge32,
        tnStatsConduitRulePacketsDropped     Gauge32,
        tnStatsConduitRuleLastActiveNMinuteAgo TimeTicks
    }

tnStatsConduitRuleConduitIndex            OBJECT-TYPE
    SYNTAX      Integer32
    MAX-ACCESS  read-only
    STATUS      current
    DESCRIPTION
            "The unique index (Conduit) value for the Conduit Rule."
    ::= { tnStatsConduitRuleEntry 1 }

tnStatsConduitRuleRuleIndex            OBJECT-TYPE
    SYNTAX      Integer32
    MAX-ACCESS  read-only
    STATUS      current
    DESCRIPTION
            "The unique index (Rule) value for the Conduit Rule."
    ::= { tnStatsConduitRuleEntry 2 }

tnStatsConduitRuleConduitID               OBJECT-TYPE
    SYNTAX      Integer32
    MAX-ACCESS  read-only
    STATUS      current
    DESCRIPTION
            "The unique Talari ID (Conduit) value for the Conduit Rule."
    ::= { tnStatsConduitRuleEntry 3 }

tnStatsConduitRuleRuleID               OBJECT-TYPE
    SYNTAX      Integer32
    MAX-ACCESS  read-only
    STATUS      current
    DESCRIPTION
            "The unique Talari ID (Rule) value for the Conduit Rule."
    ::= { tnStatsConduitRuleEntry 4 }

tnStatsConduitRuleGlobalRuleIndex      OBJECT-TYPE
    SYNTAX      Integer32
    MAX-ACCESS  read-only
    STATUS      current
    DESCRIPTION
            "The index of this rule in the tnStatsRuleTable."
    ::= { tnStatsConduitRuleEntry 5 }

tnStatsConduitRuleApplicationName              OBJECT-TYPE
    SYNTAX      DisplayString
    MAX-ACCESS  read-only
    STATUS      current
    DESCRIPTION
            "The optional string application name associated
            with this rule."
    ::= { tnStatsConduitRuleEntry 6 }

tnStatsConduitRuleWANIngressHitCount         OBJECT-TYPE
    SYNTAX      Gauge32
    MAX-ACCESS  read-only
    STATUS      current
    DESCRIPTION
            "The count of the number of times this rule has
            been hit for in the WAN Ingress direction, measured over
            the past active minute."
    ::= { tnStatsConduitRuleEntry 7 }

tnStatsConduitRuleWANEgressHitCount       OBJECT-TYPE
    SYNTAX      Gauge32
    MAX-ACCESS  read-only
    STATUS      current
    DESCRIPTION
            "The count of the number of times this rule has
            been hit for in the WAN Egress direction, measured over
            the past active minute."
    ::= { tnStatsConduitRuleEntry 8 }

tnStatsConduitRuleBytesSent                 OBJECT-TYPE
    SYNTAX      Gauge32
    MAX-ACCESS  read-only
    STATUS      current
    DESCRIPTION
            "The count of the number of bytes sent for packets that
            matched this rule, measured over the past active minute."
    ::= { tnStatsConduitRuleEntry 9 }

tnStatsConduitRulePacketsSent                 OBJECT-TYPE
    SYNTAX      Gauge32
    MAX-ACCESS  read-only
    STATUS      current
    DESCRIPTION
            "The count of the number of bytes received for packets that
            matched this rule, measured over the past active minute."
    ::= { tnStatsConduitRuleEntry 10 }

tnStatsConduitRuleBytesReceived                 OBJECT-TYPE
    SYNTAX      Gauge32
    MAX-ACCESS  read-only
    STATUS      current
    DESCRIPTION
            "The count of the number of packets sent for packets that
            matched this rule, measured over the past active minute."
    ::= { tnStatsConduitRuleEntry 11 }

tnStatsConduitRulePacketsReceived                 OBJECT-TYPE
    SYNTAX      Gauge32
    MAX-ACCESS  read-only
    STATUS      current
    DESCRIPTION
            "The count of the number of packets received for packets that
            matched this rule, measured over the past active minute."
    ::= { tnStatsConduitRuleEntry 12 }

tnStatsConduitRuleBytesDropped                 OBJECT-TYPE
    SYNTAX      Gauge32
    MAX-ACCESS  read-only
    STATUS      current
    DESCRIPTION
            "The count of the number of bytes dropped for packets that
            matched this rule, measured over the past active minute."
    ::= { tnStatsConduitRuleEntry 13 }

tnStatsConduitRulePacketsDropped                 OBJECT-TYPE
    SYNTAX      Gauge32
    MAX-ACCESS  read-only
    STATUS      current
    DESCRIPTION
            "The count of the number of packets dropped for packets that
            matched this rule, measured over the past active minute."
    ::= { tnStatsConduitRuleEntry 14 }

tnStatsConduitRuleLastActiveNMinuteAgo            OBJECT-TYPE
    SYNTAX      TimeTicks
    MAX-ACCESS  read-only
    STATUS      current
    DESCRIPTION
            "This rule was hit last N Minutes ago.
            If this field value is 0 and either tnStatsConduitRuleBytesSent
            or tnStatsConduitRuleBytesReceived is not zero, then that means
            that this rule is currently being used.  The rule
            statistics contain the latest values.
            If this field is > 0, then the rule statistics is
            plateaued to show that this rule was used N minutes ago."

    ::= { tnStatsConduitRuleEntry 15 }


--
-- Stats associated with Internet Service
--
tnStatsInternet   OBJECT IDENTIFIER ::= { talariStatistics 18 }

tnStatsInternetScalars   OBJECT IDENTIFIER ::= { tnStatsInternet 1 }

tnStatsInternetBytesSent         OBJECT-TYPE
    SYNTAX         Counter64
    MAX-ACCESS     read-only
    STATUS         current
    DESCRIPTION
        "The count of the bytes sent on this Internet service."
    DEFVAL { 0 }
    ::= { tnStatsInternetScalars 1 }

tnStatsInternetPacketsSent       OBJECT-TYPE
    SYNTAX         Counter64
    MAX-ACCESS     read-only
    STATUS         current
    DESCRIPTION
        "The count of the packets sent on this Internet service."
    DEFVAL { 0 }
    ::= { tnStatsInternetScalars 2 }

tnStatsInternetBytesReceived     OBJECT-TYPE
    SYNTAX         Counter64
    MAX-ACCESS     read-only
    STATUS         current
    DESCRIPTION
        "The count of the bytes received on this Internet service."
    DEFVAL { 0 }
    ::= { tnStatsInternetScalars 3 }

tnStatsInternetPacketsReceived   OBJECT-TYPE
    SYNTAX         Counter64
    MAX-ACCESS     read-only
    STATUS         current
    DESCRIPTION
        "The count of the packets received on this Internet service."
    DEFVAL { 0 }
    ::= { tnStatsInternetScalars 4 }

tnStatsInternetBytesDropped      OBJECT-TYPE
    SYNTAX         Counter64
    MAX-ACCESS     read-only
    STATUS         current
    DESCRIPTION
        "The count of the bytes dropped on this Internet service."
    DEFVAL { 0 }
    ::= { tnStatsInternetScalars 5 }

tnStatsInternetPacketsDropped    OBJECT-TYPE
    SYNTAX         Counter64
    MAX-ACCESS     read-only
    STATUS         current
    DESCRIPTION
        "The count of the packets dropped on this Internet service."
    DEFVAL { 0 }
    ::= { tnStatsInternetScalars 6 }

tnStatsInternetNumRules OBJECT-TYPE
    SYNTAX         Integer32
    MAX-ACCESS     read-only
    STATUS         current
    DESCRIPTION
        "The number of Rules associated with the Internet service."
    DEFVAL { 0 }
    ::= { tnStatsInternetScalars 7 }

tnStatsInternetRuleTable OBJECT-TYPE
    SYNTAX      SEQUENCE OF TnStatsInternetRuleEntry
    MAX-ACCESS  not-accessible
    STATUS      current
    DESCRIPTION
            "A collection of statistics for Rules associated with
            the Internet service.
            Counter data in this table is updated once a minute
            and is a cumulative count since the last time the
            Talari service was started.
            The number of rules in this table is tnStatsInternetNumRules
            and there is an entry for each of them."
    ::= { tnStatsInternet 2 }

tnStatsInternetRuleEntry OBJECT-TYPE
    SYNTAX      TnStatsInternetRuleEntry
    MAX-ACCESS  not-accessible
    STATUS      current
    DESCRIPTION
            "An entry containing management information applicable to a
            particular InternetRule object."
    INDEX   { tnStatsInternetRuleIndex }
    ::= { tnStatsInternetRuleTable 1 }

TnStatsInternetRuleEntry ::=
    SEQUENCE {
        tnStatsInternetRuleIndex               Integer32,
        tnStatsInternetRuleID                  Integer32,
        tnStatsInternetRuleGlobalRuleIndex     Integer32,
        tnStatsInternetRuleApplicationName     DisplayString,
        tnStatsInternetRuleWANIngressHitCount  Gauge32,
        tnStatsInternetRuleWANEgressHitCount   Gauge32,
        tnStatsInternetRuleBytesSent           Gauge32,
        tnStatsInternetRulePacketsSent         Gauge32,
        tnStatsInternetRuleBytesReceived       Gauge32,
        tnStatsInternetRulePacketsReceived     Gauge32,
        tnStatsInternetRuleBytesDropped        Gauge32,
        tnStatsInternetRulePacketsDropped      Gauge32,
        tnStatsInternetRuleLastActiveNMinuteAgo   TimeTicks
    }

tnStatsInternetRuleIndex            OBJECT-TYPE
    SYNTAX      Integer32
    MAX-ACCESS  read-only
    STATUS      current
    DESCRIPTION
            "The unique index value for the InternetRule."
    ::= { tnStatsInternetRuleEntry 1 }

tnStatsInternetRuleID               OBJECT-TYPE
    SYNTAX      Integer32
    MAX-ACCESS  read-only
    STATUS      current
    DESCRIPTION
            "The unique Talari ID for the InternetRule."
    ::= { tnStatsInternetRuleEntry 2 }

tnStatsInternetRuleGlobalRuleIndex      OBJECT-TYPE
    SYNTAX      Integer32
    MAX-ACCESS  read-only
    STATUS      current
    DESCRIPTION
            "The index of this rule in the tnStatsRuleTable."
    ::= { tnStatsInternetRuleEntry 3 }

tnStatsInternetRuleApplicationName     OBJECT-TYPE
    SYNTAX      DisplayString
    MAX-ACCESS  read-only
    STATUS      current
    DESCRIPTION
            "The optional string application name associated
            with this rule."
    ::= { tnStatsInternetRuleEntry 4 }

tnStatsInternetRuleWANIngressHitCount  OBJECT-TYPE
    SYNTAX      Gauge32
    MAX-ACCESS  read-only
    STATUS      current
    DESCRIPTION
            "The count of WAN Ingress packets that hit this rule,
            measured over the past active minute."
    ::= { tnStatsInternetRuleEntry 5 }

tnStatsInternetRuleWANEgressHitCount   OBJECT-TYPE
    SYNTAX      Gauge32
    MAX-ACCESS  read-only
    STATUS      current
    DESCRIPTION
            "The count of WAN Egress packets that hit this rule,
            measured over the past active minute."
    ::= { tnStatsInternetRuleEntry 6 }

tnStatsInternetRuleBytesSent                 OBJECT-TYPE
    SYNTAX      Gauge32
    MAX-ACCESS  read-only
    STATUS      current
    DESCRIPTION
            "The count of the number of bytes sent for packets that
            matched this rule, measured over the past active minute."
    ::= { tnStatsInternetRuleEntry 7 }

tnStatsInternetRulePacketsSent                 OBJECT-TYPE
    SYNTAX      Gauge32
    MAX-ACCESS  read-only
    STATUS      current
    DESCRIPTION
            "The count of the number of bytes received for packets that
            matched this rule, measured over the past active minute."
    ::= { tnStatsInternetRuleEntry 8 }

tnStatsInternetRuleBytesReceived                 OBJECT-TYPE
    SYNTAX      Gauge32
    MAX-ACCESS  read-only
    STATUS      current
    DESCRIPTION
            "The count of the number of packets sent for packets that
            matched this rule, measured over the past active minute."
    ::= { tnStatsInternetRuleEntry 9 }

tnStatsInternetRulePacketsReceived                 OBJECT-TYPE
    SYNTAX      Gauge32
    MAX-ACCESS  read-only
    STATUS      current
    DESCRIPTION
            "The count of the number of packets received for packets that
            matched this rule, measured over the past active minute."
    ::= { tnStatsInternetRuleEntry 10 }

tnStatsInternetRuleBytesDropped                 OBJECT-TYPE
    SYNTAX      Gauge32
    MAX-ACCESS  read-only
    STATUS      current
    DESCRIPTION
            "The count of the number of bytes dropped for packets that
            matched this rule, measured over the past active minute."
    ::= { tnStatsInternetRuleEntry 11 }

tnStatsInternetRulePacketsDropped                 OBJECT-TYPE
    SYNTAX      Gauge32
    MAX-ACCESS  read-only
    STATUS      current
    DESCRIPTION
            "The count of the number of packets dropped for packets that
            matched this rule, measured over the past active minute."
    ::= { tnStatsInternetRuleEntry 12 }

tnStatsInternetRuleLastActiveNMinuteAgo            OBJECT-TYPE
    SYNTAX      TimeTicks
    MAX-ACCESS  read-only
    STATUS      current
    DESCRIPTION
            "This rule was hit last N Minutes ago.
            If this field value is 0 and either tnStatsInternetRuleBytesSent
            or tnStatsInternetRuleBytesReceived is not zero, then that means
            that this rule is currently being used.  The rule
            statistics contain the latest values.
            If this field is > 0, then the rule statistics is
            plateaued to show that this rule was used N minutes ago."

    ::= { tnStatsInternetRuleEntry 13 }


--
-- Stats associated with Intranet Service
--
tnStatsIntranet   OBJECT IDENTIFIER ::= { talariStatistics 19 }

tnStatsIntranetScalars   OBJECT IDENTIFIER ::= { tnStatsIntranet 1 }

tnStatsIntranetNumIntranetServices OBJECT-TYPE
    SYNTAX         Integer32
    MAX-ACCESS     read-only
    STATUS         current
    DESCRIPTION
        "The number of Intranet Services on this site."
    DEFVAL { 0 }
    ::= { tnStatsIntranetScalars 8 }

tnStatsIntranetsTable OBJECT-TYPE
    SYNTAX      SEQUENCE OF TnStatsIntranetRulesEntry
    MAX-ACCESS  not-accessible
    STATUS      current
    DESCRIPTION
            "A collection of statistics for the Intranet
            services on this site.
            Counter data in this table is updated once a minute
            and is a cumulative count since the last time the
            Talari service was started."
    ::= { tnStatsIntranet 3 }

tnStatsIntranetsEntry OBJECT-TYPE
    SYNTAX      TnStatsIntranetsEntry
    MAX-ACCESS  not-accessible
    STATUS      current
    DESCRIPTION
            "An entry containing management information applicable to a
            particular Intranets object."
    INDEX   { tnStatsIntranetsIndex }
    ::= { tnStatsIntranetsTable 1 }

TnStatsIntranetsEntry ::=
    SEQUENCE {
        tnStatsIntranetsIndex               Integer32,
        tnStatsIntranetsID                  Integer32,
        tnStatsIntranetsName                DisplayString,
        tnStatsIntranetsBytesSent           Counter64,
        tnStatsIntranetsPacketsSent         Counter64,
        tnStatsIntranetsBytesReceived       Counter64,
        tnStatsIntranetsPacketsReceived     Counter64,
        tnStatsIntranetsBytesDropped        Counter64,
        tnStatsIntranetsPacketsDropped      Counter64,
        tnStatsIntranetsNumRules            Integer32,
        tnStatsIntranetsRoutingDomainName   DisplayString
    }

tnStatsIntranetsIndex                OBJECT-TYPE
    SYNTAX       Integer32
    MAX-ACCESS  read-only
    STATUS      current
    DESCRIPTION
            "The intranet index."
    ::= { tnStatsIntranetsEntry 1 }

tnStatsIntranetsID                   OBJECT-TYPE
    SYNTAX       Integer32
    MAX-ACCESS  read-only
    STATUS      current
    DESCRIPTION
            "The intranet id."
    ::= { tnStatsIntranetsEntry 2 }

tnStatsIntranetsName                 OBJECT-TYPE
    SYNTAX       DisplayString
    MAX-ACCESS  read-only
    STATUS      current
    DESCRIPTION
            "The intranet name."
    ::= { tnStatsIntranetsEntry 3 }

tnStatsIntranetsBytesSent            OBJECT-TYPE
    SYNTAX       Counter64
    MAX-ACCESS  read-only
    STATUS      current
    DESCRIPTION
            "The count of the bytes sent on this intranet service."
    ::= { tnStatsIntranetsEntry 4 }

tnStatsIntranetsPacketsSent          OBJECT-TYPE
    SYNTAX       Counter64
    MAX-ACCESS  read-only
    STATUS      current
    DESCRIPTION
            "The count of the packets sent on this intranet service."
    ::= { tnStatsIntranetsEntry 5 }

tnStatsIntranetsBytesReceived        OBJECT-TYPE
    SYNTAX       Counter64
    MAX-ACCESS  read-only
    STATUS      current
    DESCRIPTION
            "The count of the bytes received on this intranet service."
    ::= { tnStatsIntranetsEntry 6 }

tnStatsIntranetsPacketsReceived      OBJECT-TYPE
    SYNTAX       Counter64
    MAX-ACCESS  read-only
    STATUS      current
    DESCRIPTION
            "The count of packets received on this intranet service."
    ::= { tnStatsIntranetsEntry 7 }

tnStatsIntranetsBytesDropped         OBJECT-TYPE
    SYNTAX       Counter64
    MAX-ACCESS  read-only
    STATUS      current
    DESCRIPTION
            "The number of bytes dropped on this intranet service."
    ::= { tnStatsIntranetsEntry 8 }

tnStatsIntranetsPacketsDropped       OBJECT-TYPE
    SYNTAX       Counter64
    MAX-ACCESS  read-only
    STATUS      current
    DESCRIPTION
            "The number of packets dropped on this intranet service."
    ::= { tnStatsIntranetsEntry 9 }

tnStatsIntranetsNumRules             OBJECT-TYPE
    SYNTAX       Integer32
    MAX-ACCESS  read-only
    STATUS      current
    DESCRIPTION
            "The number of rules associated with this specific Intranet
            service."
    ::= { tnStatsIntranetsEntry 10 }

tnStatsIntranetsRoutingDomainName    OBJECT-TYPE
    SYNTAX      DisplayString
    MAX-ACCESS  read-only
    STATUS      current
    DESCRIPTION
            "The routing domain name. Each routing domain has
            its own set of interfaces and routing tables."
    ::= { tnStatsIntranetsEntry 11 }

tnStatsIntranetRulesTable OBJECT-TYPE
    SYNTAX      SEQUENCE OF TnStatsIntranetRulesEntry
    MAX-ACCESS  not-accessible
    STATUS      current
    DESCRIPTION
            "A collection of statistics for Rules associated with
            the Intranet service.
            Counter data in this table is updated once a minute
            and is a cumulative count since the last time the
            Talari service was started.
            The number of rules in this table is tnStatsIntranetNumRules
            and there is an entry for each of them."
    ::= { tnStatsIntranet 4 }

tnStatsIntranetRulesEntry OBJECT-TYPE
    SYNTAX      TnStatsIntranetRulesEntry
    MAX-ACCESS  not-accessible
    STATUS      current
    DESCRIPTION
            "An entry containing management information applicable to a
            particular IntranetRules object."
    INDEX   { tnStatsIntranetRulesIntranetIndex, tnStatsIntranetRulesRuleIndex }
    ::= { tnStatsIntranetRulesTable 1 }

TnStatsIntranetRulesEntry ::=
    SEQUENCE {
        tnStatsIntranetRulesIntranetIndex       Integer32,
        tnStatsIntranetRulesRuleIndex           Integer32,
        tnStatsIntranetRulesID                  Integer32,
        tnStatsIntranetRulesGlobalRuleIndex     Integer32,
        tnStatsIntranetRulesIntranetName        DisplayString,
        tnStatsIntranetRulesApplicationName     DisplayString,
        tnStatsIntranetRulesWANIngressHitCount  Gauge32,
        tnStatsIntranetRulesWANEgressHitCount   Gauge32,
        tnStatsIntranetRulesBytesSent           Gauge32,
        tnStatsIntranetRulesPacketsSent         Gauge32,
        tnStatsIntranetRulesBytesReceived       Gauge32,
        tnStatsIntranetRulesPacketsReceived     Gauge32,
        tnStatsIntranetRulesBytesDropped        Gauge32,
        tnStatsIntranetRulesPacketsDropped      Gauge32,
        tnStatsIntranetRulesLastActiveNMinuteAgo      TimeTicks
    }

tnStatsIntranetRulesIntranetIndex       OBJECT-TYPE
    SYNTAX      Integer32
    MAX-ACCESS  read-only
    STATUS      current
    DESCRIPTION
            "The unique index value for the Intranet service."
    ::= { tnStatsIntranetRulesEntry 1 }

tnStatsIntranetRulesRuleIndex           OBJECT-TYPE
    SYNTAX      Integer32
    MAX-ACCESS  read-only
    STATUS      current
    DESCRIPTION
            "The unique index value for the Rule corresponding to
            the current Intranet service in the IntranetRules."
    ::= { tnStatsIntranetRulesEntry 2 }

tnStatsIntranetRulesID                  OBJECT-TYPE
    SYNTAX      Integer32
    MAX-ACCESS  read-only
    STATUS      current
    DESCRIPTION
            "The unique Talari ID for this Rule in the IntranetRules."
    ::= { tnStatsIntranetRulesEntry 3 }

tnStatsIntranetRulesGlobalRuleIndex     OBJECT-TYPE
    SYNTAX      Integer32
    MAX-ACCESS  read-only
    STATUS      current
    DESCRIPTION
            "The index of this rule in the tnStatsRuleTable."
    ::= { tnStatsIntranetRulesEntry 4 }

tnStatsIntranetRulesIntranetName        OBJECT-TYPE
    SYNTAX      DisplayString
    MAX-ACCESS  read-only
    STATUS      current
    DESCRIPTION
            "The optional string name associated with this
            Intranet service."
    ::= { tnStatsIntranetRulesEntry 5 }

tnStatsIntranetRulesApplicationName     OBJECT-TYPE
    SYNTAX      DisplayString
    MAX-ACCESS  read-only
    STATUS      current
    DESCRIPTION
            "The optional string application name associated
            with this rule."
    ::= { tnStatsIntranetRulesEntry 6 }

tnStatsIntranetRulesWANIngressHitCount  OBJECT-TYPE
    SYNTAX      Gauge32
    MAX-ACCESS  read-only
    STATUS      current
    DESCRIPTION
            "The count of WAN Ingress packets that hit this rule,
            measured over the past active minute."
    ::= { tnStatsIntranetRulesEntry 7 }

tnStatsIntranetRulesWANEgressHitCount   OBJECT-TYPE
    SYNTAX      Gauge32
    MAX-ACCESS  read-only
    STATUS      current
    DESCRIPTION
            "The count of WAN Egress packets that hit this rule,
            measured over the past active minute."
    ::= { tnStatsIntranetRulesEntry 8 }

tnStatsIntranetRulesBytesSent           OBJECT-TYPE
    SYNTAX      Gauge32
    MAX-ACCESS  read-only
    STATUS      current
    DESCRIPTION
            "The count of the number of bytes sent for packets that
            matched this rule, measured over the past active minute."
    ::= { tnStatsIntranetRulesEntry 9 }

tnStatsIntranetRulesPacketsSent         OBJECT-TYPE
    SYNTAX      Gauge32
    MAX-ACCESS  read-only
    STATUS      current
    DESCRIPTION
            "The count of the number of bytes received for packets that
            matched this rule, measured over the past active minute."
    ::= { tnStatsIntranetRulesEntry 10 }

tnStatsIntranetRulesBytesReceived       OBJECT-TYPE
    SYNTAX      Gauge32
    MAX-ACCESS  read-only
    STATUS      current
    DESCRIPTION
            "The count of the number of packets sent for packets that
            matched this rule, measured over the past active minute."
    ::= { tnStatsIntranetRulesEntry 11 }

tnStatsIntranetRulesPacketsReceived     OBJECT-TYPE
    SYNTAX      Gauge32
    MAX-ACCESS  read-only
    STATUS      current
    DESCRIPTION
            "The count of the number of packets received for packets that
            matched this rule, measured over the past active minute."
    ::= { tnStatsIntranetRulesEntry 12 }

tnStatsIntranetRulesBytesDropped        OBJECT-TYPE
    SYNTAX      Gauge32
    MAX-ACCESS  read-only
    STATUS      current
    DESCRIPTION
            "The count of the number of bytes dropped for packets that
            matched this rule, measured over the past active minute."
    ::= { tnStatsIntranetRulesEntry 13 }

tnStatsIntranetRulesPacketsDropped      OBJECT-TYPE
    SYNTAX      Gauge32
    MAX-ACCESS  read-only
    STATUS      current
    DESCRIPTION
            "The count of the number of packets dropped for packets that
            matched this rule, measured over the past active minute."
    ::= { tnStatsIntranetRulesEntry 14 }

tnStatsIntranetRulesLastActiveNMinuteAgo  OBJECT-TYPE
    SYNTAX      TimeTicks
    MAX-ACCESS  read-only
    STATUS      current
    DESCRIPTION
            "This rule was hit last N Minutes ago.
            If this field value is 0 and either tnStatsIntranetRulesBytesSent
            or tnStatsIntranetRulesBytesReceived is not zero, then that means
            that this rule is currently being used.  The rule
            statistics contain the latest values.
            If this field is > 0, then the rule statistics is
            plateaued to show that this rule was used N minutes ago."

    ::= { tnStatsIntranetRulesEntry 15 }


--
-- Stats associated with Passthrough Service
--
tnStatsPassthrough   OBJECT IDENTIFIER ::= { talariStatistics 20 }

tnStatsPassthroughScalars   OBJECT IDENTIFIER ::= { tnStatsPassthrough 1 }

tnStatsPassthroughBytesSent         OBJECT-TYPE
    SYNTAX         Counter64
    MAX-ACCESS     read-only
    STATUS         current
    DESCRIPTION
        "The count of the bytes sent on this Passthrough service."
    DEFVAL { 0 }
    ::= { tnStatsPassthroughScalars 1 }

tnStatsPassthroughPacketsSent       OBJECT-TYPE
    SYNTAX         Counter64
    MAX-ACCESS     read-only
    STATUS         current
    DESCRIPTION
        "The count of the packets sent on this Passthrough service."
    DEFVAL { 0 }
    ::= { tnStatsPassthroughScalars 2 }

tnStatsPassthroughBytesReceived     OBJECT-TYPE
    SYNTAX         Counter64
    MAX-ACCESS     read-only
    STATUS         current
    DESCRIPTION
        "The count of the bytes received on this Passthrough service."
    DEFVAL { 0 }
    ::= { tnStatsPassthroughScalars 3 }

tnStatsPassthroughPacketsReceived   OBJECT-TYPE
    SYNTAX         Counter64
    MAX-ACCESS     read-only
    STATUS         current
    DESCRIPTION
        "The count of the packets received on this Passthrough service."
    DEFVAL { 0 }
    ::= { tnStatsPassthroughScalars 4 }

tnStatsPassthroughBytesDropped      OBJECT-TYPE
    SYNTAX         Counter64
    MAX-ACCESS     read-only
    STATUS         current
    DESCRIPTION
        "The count of the bytes dropped on this Passthrough service."
    DEFVAL { 0 }
    ::= { tnStatsPassthroughScalars 5 }

tnStatsPassthroughPacketsDropped    OBJECT-TYPE
    SYNTAX         Counter64
    MAX-ACCESS     read-only
    STATUS         current
    DESCRIPTION
        "The count of the packets dropped on this Passthrough service."
    DEFVAL { 0 }
    ::= { tnStatsPassthroughScalars 6 }

--
-- Stats associated with Routes Version 2
--
tnStatsRoutesV2   OBJECT IDENTIFIER ::= { talariStatistics 21 }

tnStatsRouteScalars   OBJECT IDENTIFIER ::= { tnStatsRoutesV2 1 }

tnStatsNumRoutesV2 OBJECT-TYPE
    SYNTAX         Gauge32
    MAX-ACCESS     read-only
    STATUS         current
    DESCRIPTION
            "The total number of routes in the system."
    DEFVAL { 0 }
    ::= { tnStatsRouteScalars 1 }


tnStatsRouteTableV2 OBJECT-TYPE
    SYNTAX      SEQUENCE OF TnStatsRouteEntryV2
    MAX-ACCESS  not-accessible
    STATUS      current
    DESCRIPTION
            "A collection of statistics for route objects.
            Contains statistics counts for all the routes in
            the system.  Counter data in this table is updated once a
            minute and is a cumulative count since the last time the
            Talari service was started."

    ::= { tnStatsRoutesV2 2 }

tnStatsRouteEntryV2 OBJECT-TYPE
    SYNTAX      TnStatsRouteEntryV2
    MAX-ACCESS  not-accessible
    STATUS      current
    DESCRIPTION
            "An entry containing management information applicable to a
            particular route object."
    INDEX   { tnStatsRouteIndexV2 }
    ::= { tnStatsRouteTableV2 1 }

TnStatsRouteEntryV2 ::=
    SEQUENCE {
        tnStatsRouteIndexV2           Integer32,
        tnStatsRouteNetworkAddr       IpAddress,
        tnStatsRouteNetworkPrefix     Integer32,
        tnStatsRouteGateway           IpAddress,
        tnStatsRouteFallback          INTEGER,
        tnStatsRouteServiceType       INTEGER,
        tnStatsRouteServiceID         Integer32,
        tnStatsRouteServiceName       DisplayString,
        tnStatsRouteReachable         INTEGER,
        tnStatsRouteSiteName          DisplayString,
        tnStatsRouteType              INTEGER,
        tnStatsRouteNeighborDirect    INTEGER,
        tnStatsRouteCost              Integer32,
        tnStatsRouteHitCountV2        Counter64,
        tnStatsRouteEligible          DisplayString,
        tnStatsRouteEligibilityType   DisplayString,
        tnStatsRouteEligibilityValue  DisplayString,
        tnStatsRouteProtocol          INTEGER,
        tnStatsRouteRoutingDomainName DisplayString
    }

tnStatsRouteIndexV2          OBJECT-TYPE
    SYNTAX      Integer32
    MAX-ACCESS  read-only
    STATUS      current
    DESCRIPTION
            "The unique index value for the route."
    ::= { tnStatsRouteEntryV2 1 }

tnStatsRouteNetworkAddr           OBJECT-TYPE
    SYNTAX      IpAddress
    MAX-ACCESS  read-only
    STATUS      current
    DESCRIPTION
            "This is the destination IP Address."
    ::= { tnStatsRouteEntryV2 2 }

tnStatsRouteNetworkPrefix         OBJECT-TYPE
    SYNTAX      Integer32
    MAX-ACCESS  read-only
    STATUS      current
    DESCRIPTION
            "Network Prefix indicate number of significant
            bits in the NetworkAddr field."
    ::= { tnStatsRouteEntryV2 3 }

tnStatsRouteGateway               OBJECT-TYPE
    SYNTAX      IpAddress
    MAX-ACCESS  read-only
    STATUS      current
    DESCRIPTION
            "The Gateway IP Address for Route."
    ::= { tnStatsRouteEntryV2 4 }

tnStatsRouteFallback              OBJECT-TYPE
    SYNTAX      INTEGER {
                    no(0),       -- not fallback route
                    yes(1)       -- fallback route
                }
    MAX-ACCESS  read-only
    STATUS      obsolete
    DESCRIPTION
            "Indicate whether route is Fallback."
    ::= { tnStatsRouteEntryV2 5 }

tnStatsRouteServiceType           OBJECT-TYPE
    SYNTAX      INTEGER {
                    discard(0),       -- discard route
                    passthrough(1),   -- passthrough route
                    internet(2),      -- internet route
                    intranet(3),      -- intranet route
                    conduit(4),       -- conduit route
                    langretunnel(5),  -- lan gre tunnel route
                    lanipsectunnel(6),-- lan ipsec tunnel route
                    local(7),         -- local route
                    iphost(8)         -- host route
                }
    MAX-ACCESS  read-only
    STATUS      current
    DESCRIPTION
            "Service Type for Route."
    ::= { tnStatsRouteEntryV2 6 }

tnStatsRouteServiceID             OBJECT-TYPE
    SYNTAX      Integer32
    MAX-ACCESS  read-only
    STATUS      current
    DESCRIPTION
            "The unique Talari ID for the Service ID.
            meaningful for service type conduit and intranet."
    ::= { tnStatsRouteEntryV2 7 }

tnStatsRouteServiceName           OBJECT-TYPE
    SYNTAX      DisplayString
    MAX-ACCESS  read-only
    STATUS      current
    DESCRIPTION
            "Service Name in meaning format."
    ::= { tnStatsRouteEntryV2 8 }

tnStatsRouteReachable             OBJECT-TYPE
    SYNTAX      INTEGER {
                    no(0),       -- route not reachable
                    yes(1),      -- route reachable
                    na(2)        -- not applicable i.e. passthrough
                }
    MAX-ACCESS  read-only
    STATUS      current
    DESCRIPTION
            "Indicate whether route is reachable."
    ::= { tnStatsRouteEntryV2 9 }

tnStatsRouteSiteName              OBJECT-TYPE
    SYNTAX      DisplayString
    MAX-ACCESS  read-only
    STATUS      current
    DESCRIPTION
            "Destination Talari Site Name for Conduit Routes."
    ::= { tnStatsRouteEntryV2 10 }

tnStatsRouteType                  OBJECT-TYPE
    SYNTAX      INTEGER {
                    static(0),             -- static route
                    dynamic(1),            -- dynamic route
                    dynamicConduit(2)      -- dynamic conduit route
                }
    MAX-ACCESS  read-only
    STATUS      current
    DESCRIPTION
            "Indicate whether route is static, dynamic, or
            part of dynamic conduit route."
    ::= { tnStatsRouteEntryV2 11 }

tnStatsRouteNeighborDirect        OBJECT-TYPE
    SYNTAX      INTEGER {
                    na(0),                 -- static route
                    directNeighbor (1),    -- dynamic route, learned from neighbor
                    indirectNeighbor (2)   -- dynamic route, learned from in-direct
                }
    MAX-ACCESS  read-only
    STATUS      current
    DESCRIPTION
            "If route is learned from another Talrari Site, route
            is neighbor's direct route.  Otherwise, neighbor
            learned route from its neighbor.  Field is 
            only applicable for dynamic routes."
    ::= { tnStatsRouteEntryV2 12 }

tnStatsRouteCost                  OBJECT-TYPE
    SYNTAX      Integer32
    MAX-ACCESS  read-only
    STATUS      current
    DESCRIPTION
            "Route Cost."
    ::= { tnStatsRouteEntryV2 13 }


tnStatsRouteHitCountV2         OBJECT-TYPE
    SYNTAX      Counter64
    MAX-ACCESS  read-only
    STATUS      current
    DESCRIPTION
            "The count of the number of packets that have hit this route."
    ::= { tnStatsRouteEntryV2 14 }

tnStatsRouteEligible              OBJECT-TYPE
    SYNTAX      DisplayString
    MAX-ACCESS  read-only
    STATUS      current
    DESCRIPTION
            "When eligiblility type and eligibility
             and value are specified for this route, this route is
             only available for use when the conditions specified is
             up.  If eligibility fields are not specified, then this
             route is always eligible."
    ::= { tnStatsRouteEntryV2 15 }

tnStatsRouteEligibilityType       OBJECT-TYPE
    SYNTAX      DisplayString
    MAX-ACCESS  read-only
    STATUS      current
    DESCRIPTION
            "Use route only when either a specified path or gateway
             or both are available."
    ::= { tnStatsRouteEntryV2 16 }

tnStatsRouteEligibilityValue      OBJECT-TYPE
    SYNTAX      DisplayString
    MAX-ACCESS  read-only
    STATUS      current
    DESCRIPTION
            "Either the name of the path or gateway IP or both."
    ::= { tnStatsRouteEntryV2 17 }

tnStatsRouteProtocol              OBJECT-TYPE
    SYNTAX      INTEGER {
                    na(0),        -- static or learned through SNMP
                    bgp(1),       -- BGP Protocol
                    ospf(2),      -- OSPF Protocol
                    apn(3)        -- APN Protocol
                }
    MAX-ACCESS  read-only
    STATUS      current
    DESCRIPTION
            "The Routing Protocol."
    ::= { tnStatsRouteEntryV2 18 }

tnStatsRouteRoutingDomainName       OBJECT-TYPE
    SYNTAX      DisplayString
    MAX-ACCESS  read-only
    STATUS      current
    DESCRIPTION
            "The routing domain name. Each routing domain has
            its own set of interfaces and routing tables."
    ::= { tnStatsRouteEntryV2 19 }

--
-- Stats associated with Dynamic Conduits
--
tnStatsDynamicConduits   OBJECT IDENTIFIER ::= { talariStatistics 22 }

tnStatsDynamicConduitScalars   OBJECT IDENTIFIER ::= { tnStatsDynamicConduits 1 }

tnStatsNumDynamicConduits OBJECT-TYPE
    SYNTAX         Gauge32
    MAX-ACCESS     read-only
    STATUS         current
    DESCRIPTION
            "The total number of Dynamic Conduits."
    DEFVAL { 0 }
    ::= { tnStatsDynamicConduitScalars 1 }

tnStatsDynamicConduitTable OBJECT-TYPE
    SYNTAX      SEQUENCE OF TnStatsDynamicConduitEntry
    MAX-ACCESS  not-accessible
    STATUS      current
    DESCRIPTION
            "A collection of statistics for Dynamic Conduit objects.
            Contains statistics counts for all the Dynamic Conduits in
            the system.  Counter data in this table is updated once a
            minute and is a cumulative count since the last time the
            Talari service was started.  Dynamic Conduits can be added
            and removed."

    ::= { tnStatsDynamicConduits 2 }

tnStatsDynamicConduitEntry OBJECT-TYPE
    SYNTAX      TnStatsDynamicConduitEntry
    MAX-ACCESS  not-accessible
    STATUS      current
    DESCRIPTION
            "An entry containing management information applicable to a
            particular Dynamic Conduit object."
    INDEX   { tnStatsDynamicConduitIndex }
    ::= { tnStatsDynamicConduitTable 1 }

TnStatsDynamicConduitEntry ::=
    SEQUENCE {
        tnStatsDynamicConduitIndex                 Integer32,
        tnStatsDynamicConduitID                    Integer32,
        tnStatsDynamicConduitName                  DisplayString,
        tnStatsDynamicConduitState                 Integer32,
        tnStatsDynamicConduitTimeSinceCreation     Counter64,
        tnStatsDynamicConduitBytesSent             Counter64,
        tnStatsDynamicConduitPacketsSent           Counter64,
        tnStatsDynamicConduitSendBytesDropped      Counter64,
        tnStatsDynamicConduitSendPacketsDropped    Counter64,
        tnStatsDynamicConduitSendPacketsLost       Counter64,
        tnStatsDynamicConduitSendPacketsOOO        Counter64,
        tnStatsDynamicConduitSendBOWTms            Gauge32,
        tnStatsDynamicConduitSendJitterms          Gauge32,
        tnStatsDynamicConduitBytesReceived         Counter64,
        tnStatsDynamicConduitPacketsReceived       Counter64,
        tnStatsDynamicConduitReceiveBytesDropped   Counter64,
        tnStatsDynamicConduitReceivePacketsDropped Counter64,
        tnStatsDynamicConduitReceivePacketsLost    Counter64,
        tnStatsDynamicConduitReceivePacketsOOO     Counter64,
        tnStatsDynamicConduitReceiveBOWTms         Gauge32,
        tnStatsDynamicConduitReceiveJitterms       Gauge32,
        tnStatsDynamicConduitNumPaths              Integer32,
        tnStatsDynamicConduitNumRules              Integer32
    }

tnStatsDynamicConduitIndex            OBJECT-TYPE
    SYNTAX      Integer32
    MAX-ACCESS  read-only
    STATUS      current
    DESCRIPTION
            "The unique index value for the Dynamic Conduit."
    ::= { tnStatsDynamicConduitEntry 1 }

tnStatsDynamicConduitID               OBJECT-TYPE
    SYNTAX      Integer32
    MAX-ACCESS  read-only
    STATUS      current
    DESCRIPTION
            "The unique Talari ID for the Dynamic Conduit."
    ::= { tnStatsDynamicConduitEntry 2 }

tnStatsDynamicConduitName              OBJECT-TYPE
    SYNTAX      DisplayString
    MAX-ACCESS  read-only
    STATUS      current
    DESCRIPTION
            "The name for the Dynamic Conduit."
    ::= { tnStatsDynamicConduitEntry 3 }

tnStatsDynamicConduitState OBJECT-TYPE
    SYNTAX  INTEGER {
                undefined(0),    -- Undefined state
                disabled(1),     -- Admin Disabled
                dead(2),         -- Dead
                bad(3),          -- Errors above threshold
                good(4)          -- Passing traffic
            }
    MAX-ACCESS  read-only
    STATUS      current
    DESCRIPTION
            "The current operational state of the dynamic conduit."
    ::= { tnStatsDynamicConduitEntry 4 }

tnStatsDynamicConduitTimeSinceCreation OBJECT-TYPE
    SYNTAX  Counter64
    MAX-ACCESS  read-only
    STATUS      current
    DESCRIPTION
            "Number of seconds since the dynamic conduit has been created."
    ::= { tnStatsDynamicConduitEntry 5 }

tnStatsDynamicConduitBytesSent         OBJECT-TYPE
    SYNTAX      Counter64
    MAX-ACCESS  read-only
    STATUS      current
    DESCRIPTION
            "The count of bytes sent for this Dynamic Conduit."
    ::= { tnStatsDynamicConduitEntry 6 }

tnStatsDynamicConduitPacketsSent       OBJECT-TYPE
    SYNTAX      Counter64
    MAX-ACCESS  read-only
    STATUS      current
    DESCRIPTION
            "The count of packets sent for this Dynamic Conduit."
    ::= { tnStatsDynamicConduitEntry 7 }

tnStatsDynamicConduitSendBytesDropped      OBJECT-TYPE
    SYNTAX      Counter64
    MAX-ACCESS  read-only
    STATUS      current
    DESCRIPTION
            "The count of send bytes dropped for this Dynamic Conduit."
    ::= { tnStatsDynamicConduitEntry 8 }

tnStatsDynamicConduitSendPacketsDropped    OBJECT-TYPE
    SYNTAX      Counter64
    MAX-ACCESS  read-only
    STATUS      current
    DESCRIPTION
            "The count of send packets dropped for this Dynamic Conduit."
    ::= { tnStatsDynamicConduitEntry 9 }

tnStatsDynamicConduitSendPacketsLost       OBJECT-TYPE
    SYNTAX      Counter64
    MAX-ACCESS  read-only
    STATUS      current
    DESCRIPTION
            "The current total number of send packets lost for this
            Dynamic Conduit."
    ::= { tnStatsDynamicConduitEntry 10 }

tnStatsDynamicConduitSendPacketsOOO        OBJECT-TYPE
    SYNTAX      Counter64
    MAX-ACCESS  read-only
    STATUS      current
    DESCRIPTION
            "The current total number of send packets received out
             of order by the remote on this Dynamic Conduit."
    ::= { tnStatsDynamicConduitEntry 11 }

tnStatsDynamicConduitSendBOWTms            OBJECT-TYPE
    SYNTAX      Gauge32
    MAX-ACCESS  read-only
    STATUS      current
    DESCRIPTION
            "The current best one-way time (BOWT) value (in milliseconds)
            in the send direction for this Dynamic Conduit."
    ::= { tnStatsDynamicConduitEntry 12 }

tnStatsDynamicConduitSendJitterms          OBJECT-TYPE
    SYNTAX      Gauge32
    MAX-ACCESS  read-only
    STATUS      current
    DESCRIPTION
            "The current worst jitter value (in milliseconds) in the send
            direction for this Dynamic Conduit."
    ::= { tnStatsDynamicConduitEntry 13 }

tnStatsDynamicConduitBytesReceived     OBJECT-TYPE
    SYNTAX      Counter64
    MAX-ACCESS  read-only
    STATUS      current
    DESCRIPTION
            "The count of bytes received for this Dynamic Conduit."
    ::= { tnStatsDynamicConduitEntry 14 }

tnStatsDynamicConduitPacketsReceived   OBJECT-TYPE
    SYNTAX      Counter64
    MAX-ACCESS  read-only
    STATUS      current
    DESCRIPTION
            "The count of packets received for this Dynamic Conduit."
    ::= { tnStatsDynamicConduitEntry 15 }

tnStatsDynamicConduitReceiveBytesDropped      OBJECT-TYPE
    SYNTAX      Counter64
    MAX-ACCESS  read-only
    STATUS      current
    DESCRIPTION
            "The count of receive bytes dropped for this Dynamic Conduit."
    ::= { tnStatsDynamicConduitEntry 16 }

tnStatsDynamicConduitReceivePacketsDropped    OBJECT-TYPE
    SYNTAX      Counter64
    MAX-ACCESS  read-only
    STATUS      current
    DESCRIPTION
            "The count of receive packets dropped for this Dynamic Conduit."
    ::= { tnStatsDynamicConduitEntry 17 }

tnStatsDynamicConduitReceivePacketsLost       OBJECT-TYPE
    SYNTAX      Counter64
    MAX-ACCESS  read-only
    STATUS      current
    DESCRIPTION
            "The current total number of receive packets lost for this
            Dynamic Conduit."
    ::= { tnStatsDynamicConduitEntry 18 }

tnStatsDynamicConduitReceivePacketsOOO        OBJECT-TYPE
    SYNTAX      Counter64
    MAX-ACCESS  read-only
    STATUS      current
    DESCRIPTION
            "The current total number of received packets out
             of order on this Dynamic Conduit."
    ::= { tnStatsDynamicConduitEntry 19 }

tnStatsDynamicConduitReceiveBOWTms            OBJECT-TYPE
    SYNTAX      Gauge32
    MAX-ACCESS  read-only
    STATUS      current
    DESCRIPTION
            "The current best one-way time (BOWT) value (in milliseconds)
            in the receive direction for this Dynamic Conduit."
    ::= { tnStatsDynamicConduitEntry 20 }

tnStatsDynamicConduitReceiveJitterms          OBJECT-TYPE
    SYNTAX      Gauge32
    MAX-ACCESS  read-only
    STATUS      current
    DESCRIPTION
            "The current worst jitter value (in milliseconds) in the
            receive direction for this Dynamic Conduit."
    ::= { tnStatsDynamicConduitEntry 21 }

tnStatsDynamicConduitNumPaths          OBJECT-TYPE
    SYNTAX      Integer32
    MAX-ACCESS  read-only
    STATUS      current
    DESCRIPTION
            "The number of Paths associated with this conduit - this
            is the number of rows in the tnStatsDynamicConduitPathsTable for
            the current conduit.  Each dynamic conduit can have a different
            number of paths associated with it."
    ::= { tnStatsDynamicConduitEntry 22 }

tnStatsDynamicConduitNumRules          OBJECT-TYPE
    SYNTAX      Integer32
    MAX-ACCESS  read-only
    STATUS      current
    DESCRIPTION
            "The number of Rules associated with this conduit - this
            is the number of rows in the tnStatsDynamicConduitRulesTable for
            the current conduit.  Each dynamic conduit can have a different
            number of rules associated with it."
    ::= { tnStatsDynamicConduitEntry 23 }


--
-- Stats for Paths associated with Dynamic Conduits
--
tnStatsDynamicConduitPaths   OBJECT IDENTIFIER ::= { tnStatsDynamicConduits 3 }

tnStatsDynamicConduitPathTable OBJECT-TYPE
    SYNTAX      SEQUENCE OF TnStatsDynamicConduitPathEntry
    MAX-ACCESS  not-accessible
    STATUS      current
    DESCRIPTION
            "A collection of statistics for Dynamic Conduit Path objects.
            Contains statistics counts for all the Dynamic Conduit Paths in
            the system.  Counter data in this table is updated once a
            minute and is a cumulative count since the time the
            Conduit was added.  The number of conduits in
            this table is stored in tnStatsDynamicNumConduits and the number
            of Paths for each dynamic conduit is in the variable
            tnStatsDynamicConduitNumPaths which is in the tnStatsDynamicConduitTable
            and has a specific number of paths value for each dynamic conduit
            index."
    ::= { tnStatsDynamicConduitPaths 1 }

tnStatsDynamicConduitPathEntry OBJECT-TYPE
    SYNTAX      TnStatsDynamicConduitPathEntry
    MAX-ACCESS  not-accessible
    STATUS      current
    DESCRIPTION
            "An entry containing management information applicable to a
            particular Dynamic Conduit object."
    INDEX   { tnStatsDynamicConduitPathConduitIndex, tnStatsDynamicConduitPathPathIndex }
    ::= { tnStatsDynamicConduitPathTable 1 }

TnStatsDynamicConduitPathEntry ::=
    SEQUENCE {
        tnStatsDynamicConduitPathConduitIndex      Integer32,
        tnStatsDynamicConduitPathPathIndex         Integer32,
        tnStatsDynamicConduitPathConduitID         Integer32,
        tnStatsDynamicConduitPathPathID            Integer32,
        tnStatsDynamicConduitPathName              DisplayString,
        tnStatsDynamicConduitPathState             Integer32,
        tnStatsDynamicConduitPathBytesSent         Counter64,
        tnStatsDynamicConduitPathPacketsSent       Counter64,
        tnStatsDynamicConduitPathBytesReceived     Counter64,
        tnStatsDynamicConduitPathPacketsReceived   Counter64,
        tnStatsDynamicConduitPathBytesDropped      Counter64,
        tnStatsDynamicConduitPathPacketsDropped    Counter64,
        tnStatsDynamicConduitPathBOWTms            Gauge32,
        tnStatsDynamicConduitPathJitterms          Gauge32,
        tnStatsDynamicConduitPathPacketsLost       Counter64,
        tnStatsDynamicConduitPathPacketsOOO        Counter64
    }

tnStatsDynamicConduitPathConduitIndex            OBJECT-TYPE
    SYNTAX      Integer32
    MAX-ACCESS  read-only
    STATUS      current
    DESCRIPTION
            "The unique index (Conduit) value for the Dynamic Conduit Path."
    ::= { tnStatsDynamicConduitPathEntry 1 }

tnStatsDynamicConduitPathPathIndex            OBJECT-TYPE
    SYNTAX      Integer32
    MAX-ACCESS  read-only
    STATUS      current
    DESCRIPTION
            "The unique index (Path) value for the Dynamic Conduit Path."
    ::= { tnStatsDynamicConduitPathEntry 2 }

tnStatsDynamicConduitPathConduitID               OBJECT-TYPE
    SYNTAX      Integer32
    MAX-ACCESS  read-only
    STATUS      current
    DESCRIPTION
            "The unique Talari ID (Conduit) value for the Dynamic Conduit Path."
    ::= { tnStatsDynamicConduitPathEntry 3 }

tnStatsDynamicConduitPathPathID               OBJECT-TYPE
    SYNTAX      Integer32
    MAX-ACCESS  read-only
    STATUS      current
    DESCRIPTION
            "The unique Talari ID (Path) value for the Dynamic Conduit Path."
    ::= { tnStatsDynamicConduitPathEntry 4 }

tnStatsDynamicConduitPathName              OBJECT-TYPE
    SYNTAX      DisplayString
    MAX-ACCESS  read-only
    STATUS      current
    DESCRIPTION
            "The name for the Dynamic Conduit Path."
    ::= { tnStatsDynamicConduitPathEntry 5 }

tnStatsDynamicConduitPathState OBJECT-TYPE
    SYNTAX  INTEGER {
                undefined(0),    -- Undefined state
                disabled(1),     -- Admin Disabled
                dead(2),         -- Dead
                bad(3),          -- Errors above threshold
                good(4)          -- Passing traffic
            }
    MAX-ACCESS  read-only
    STATUS      current
    DESCRIPTION
            "The current operational state of the dynamic conduit path."
    ::= { tnStatsDynamicConduitPathEntry 6 }

tnStatsDynamicConduitPathBytesSent         OBJECT-TYPE
    SYNTAX      Counter64
    MAX-ACCESS  read-only
    STATUS      current
    DESCRIPTION
            "The count of bytes sent for this Dynamic Conduit Path."
    ::= { tnStatsDynamicConduitPathEntry 7 }

tnStatsDynamicConduitPathPacketsSent       OBJECT-TYPE
    SYNTAX      Counter64
    MAX-ACCESS  read-only
    STATUS      current
    DESCRIPTION
            "The count of packets sent for this Dynamic Conduit Path."
    ::= { tnStatsDynamicConduitPathEntry 8 }

tnStatsDynamicConduitPathBytesReceived     OBJECT-TYPE
    SYNTAX      Counter64
    MAX-ACCESS  read-only
    STATUS      current
    DESCRIPTION
            "The count of bytes received for this Dynamic Conduit Path."
    ::= { tnStatsDynamicConduitPathEntry 9 }

tnStatsDynamicConduitPathPacketsReceived   OBJECT-TYPE
    SYNTAX      Counter64
    MAX-ACCESS  read-only
    STATUS      current
    DESCRIPTION
            "The count of packets received for this Dynamic Conduit Path."
    ::= { tnStatsDynamicConduitPathEntry 10 }

tnStatsDynamicConduitPathBytesDropped      OBJECT-TYPE
    SYNTAX      Counter64
    MAX-ACCESS  read-only
    STATUS      current
    DESCRIPTION
            "The count of bytes dropped for this Dynamic Conduit Path."
    ::= { tnStatsDynamicConduitPathEntry 11 }

tnStatsDynamicConduitPathPacketsDropped    OBJECT-TYPE
    SYNTAX      Counter64
    MAX-ACCESS  read-only
    STATUS      current
    DESCRIPTION
            "The count of packets dropped for this Dynamic Conduit Path."
    ::= { tnStatsDynamicConduitPathEntry 12 }

tnStatsDynamicConduitPathBOWTms            OBJECT-TYPE
    SYNTAX      Gauge32
    MAX-ACCESS  read-only
    STATUS      current
    DESCRIPTION
            "The current best one-way time (BOWT) value (in milliseconds)
            value for this Dynamic Conduit Path."
    ::= { tnStatsDynamicConduitPathEntry 13 }

tnStatsDynamicConduitPathJitterms          OBJECT-TYPE
    SYNTAX      Gauge32
    MAX-ACCESS  read-only
    STATUS      current
    DESCRIPTION
            "The current best jitter value (in milliseconds) for this
            Dynamic Conduit Path."
    ::= { tnStatsDynamicConduitPathEntry 14 }

tnStatsDynamicConduitPathPacketsLost       OBJECT-TYPE
    SYNTAX      Counter64
    MAX-ACCESS  read-only
    STATUS      current
    DESCRIPTION
            "The current total number of packets lost for this
            Dynamic Conduit Path."
    ::= { tnStatsDynamicConduitPathEntry 15 }

tnStatsDynamicConduitPathPacketsOOO        OBJECT-TYPE
    SYNTAX      Counter64
    MAX-ACCESS  read-only
    STATUS      current
    DESCRIPTION
            "The current total number of out of order
             packets detected on this Dynamic Conduit Path."
    ::= { tnStatsDynamicConduitPathEntry 16 }

--
-- Stats for Classes associated with Conduits
--
tnStatsDynamicConduitClasses   OBJECT IDENTIFIER ::= { tnStatsDynamicConduits 4 }

tnStatsDynamicConduitClassTable OBJECT-TYPE
    SYNTAX      SEQUENCE OF TnStatsDynamicConduitClassEntry
    MAX-ACCESS  not-accessible
    STATUS      current
    DESCRIPTION
            "A collection of statistics for Dynamic Conduit Class objects.
            Contains statistics counts for all the Dynamic Conduit
            Classes in the system.  Counter data in this table is
            updated once a minute and is a cumulative count since the
            conduit has been added.  The number of conduits in
            this table is stored in tnStatsNumDynamicConduits and the number
            of Classes for each conduit is always 17."
    ::= { tnStatsDynamicConduitClasses 1 }

tnStatsDynamicConduitClassEntry OBJECT-TYPE
    SYNTAX      TnStatsDynamicConduitClassEntry
    MAX-ACCESS  not-accessible
    STATUS      current
    DESCRIPTION
            "An entry containing management information applicable to a
            particular Dynamic Conduit object."
    INDEX   { tnStatsDynamicConduitClassConduitIndex, tnStatsDynamicConduitClassClassIndex }
    ::= { tnStatsDynamicConduitClassTable 1 }

TnStatsDynamicConduitClassEntry ::=
    SEQUENCE {
        tnStatsDynamicConduitClassConduitIndex      Integer32,
        tnStatsDynamicConduitClassClassIndex        Integer32,
        tnStatsDynamicConduitClassConduitID         Integer32,
        tnStatsDynamicConduitClassClassID           Integer32,
        tnStatsDynamicConduitClassName              DisplayString,
        tnStatsDynamicConduitClassType              Integer32,
        tnStatsDynamicConduitClassBytesSent         Counter64,
        tnStatsDynamicConduitClassPacketsSent       Counter64,
        tnStatsDynamicConduitClassBytesPending      Counter64,
        tnStatsDynamicConduitClassPacketsPending    Counter64,
        tnStatsDynamicConduitClassBytesDropped      Counter64,
        tnStatsDynamicConduitClassPacketsDropped    Counter64
    }

tnStatsDynamicConduitClassConduitIndex            OBJECT-TYPE
    SYNTAX      Integer32
    MAX-ACCESS  read-only
    STATUS      current
    DESCRIPTION
            "The unique index (Conduit) value for the Dynamic Conduit Class."
    ::= { tnStatsDynamicConduitClassEntry 1 }

tnStatsDynamicConduitClassClassIndex            OBJECT-TYPE
    SYNTAX      Integer32
    MAX-ACCESS  read-only
    STATUS      current
    DESCRIPTION
            "The unique index (Class) value for the Dynamic Conduit Class."
    ::= { tnStatsDynamicConduitClassEntry 2 }

tnStatsDynamicConduitClassConduitID               OBJECT-TYPE
    SYNTAX      Integer32
    MAX-ACCESS  read-only
    STATUS      current
    DESCRIPTION
            "The internal Talari ID for the Dynamic Conduit object."
    ::= { tnStatsDynamicConduitClassEntry 3 }

tnStatsDynamicConduitClassClassID               OBJECT-TYPE
    SYNTAX      Integer32
    MAX-ACCESS  read-only
    STATUS      current
    DESCRIPTION
            "The internal Talari ID for the Dynamic Conduit Class object."
    ::= { tnStatsDynamicConduitClassEntry 4 }

tnStatsDynamicConduitClassName              OBJECT-TYPE
    SYNTAX      DisplayString
    MAX-ACCESS  read-only
    STATUS      current
    DESCRIPTION
            "The name for the Dynamic Conduit Class."
    ::= { tnStatsDynamicConduitClassEntry 5 }

tnStatsDynamicConduitClassType              OBJECT-TYPE
    SYNTAX  INTEGER {
                realtime(1),
                interactive(2),
                bulk(3),
                unknown(4)
            }
    MAX-ACCESS  read-only
    STATUS      current
    DESCRIPTION
            "The type of the Dynamic Conduit Class."
    ::= { tnStatsDynamicConduitClassEntry 6 }

tnStatsDynamicConduitClassBytesSent         OBJECT-TYPE
    SYNTAX      Counter64
    MAX-ACCESS  read-only
    STATUS      current
    DESCRIPTION
            "The count of bytes sent for this Dynamic Conduit Class."
    ::= { tnStatsDynamicConduitClassEntry 7 }

tnStatsDynamicConduitClassPacketsSent       OBJECT-TYPE
    SYNTAX      Counter64
    MAX-ACCESS  read-only
    STATUS      current
    DESCRIPTION
            "The count of packets sent for this Dynamic Conduit Class."
    ::= { tnStatsDynamicConduitClassEntry 8 }

tnStatsDynamicConduitClassBytesPending     OBJECT-TYPE
    SYNTAX      Counter64
    MAX-ACCESS  read-only
    STATUS      current
    DESCRIPTION
            "The count of bytes pending for this Dynamic Conduit Class."
    ::= { tnStatsDynamicConduitClassEntry 9 }

tnStatsDynamicConduitClassPacketsPending   OBJECT-TYPE
    SYNTAX      Counter64
    MAX-ACCESS  read-only
    STATUS      current
    DESCRIPTION
            "The count of packets pending for this Dynamic Conduit Class."
    ::= { tnStatsDynamicConduitClassEntry 10 }

tnStatsDynamicConduitClassBytesDropped      OBJECT-TYPE
    SYNTAX      Counter64
    MAX-ACCESS  read-only
    STATUS      current
    DESCRIPTION
            "The count of bytes dropped for this Dynamic Conduit Class."
    ::= { tnStatsDynamicConduitClassEntry 11 }

tnStatsDynamicConduitClassPacketsDropped    OBJECT-TYPE
    SYNTAX      Counter64
    MAX-ACCESS  read-only
    STATUS      current
    DESCRIPTION
            "The count of packets dropped for this Dynamic Conduit Class."
    ::= { tnStatsDynamicConduitClassEntry 12 }

--
-- Stats for Rules associated with Dynamic Conduits
--
tnStatsDynamicConduitRules   OBJECT IDENTIFIER ::= { tnStatsDynamicConduits 5 }

tnStatsDynamicConduitRuleTable OBJECT-TYPE
    SYNTAX      SEQUENCE OF TnStatsDynamicConduitRuleEntry
    MAX-ACCESS  not-accessible
    STATUS      current
    DESCRIPTION
            "A collection of statistics for Dynamic Conduit Rule objects.
            Contains statistics counts for all the Dynamic Conduit Rules in
            the system.  Counter data in this table is updated once a
            minute and is a cumulative count since the time that the 
            conduit has been added.  The number of conduits in this table 
            is stored in tnStatsNumDynamicConduits and the number of Rules 
            for each conduit is in the variable tnStatsDynamicConduitNumRules 
            which is in the tnStatsDynamicConduitTable
            and has a specific number of rules value for each conduit
            index."
    ::= { tnStatsDynamicConduitRules 1 }

tnStatsDynamicConduitRuleEntry OBJECT-TYPE
    SYNTAX      TnStatsDynamicConduitRuleEntry
    MAX-ACCESS  not-accessible
    STATUS      current
    DESCRIPTION
            "An entry containing management information applicable to a
            particular Dynamic Conduit object."
    INDEX   { tnStatsDynamicConduitRuleConduitIndex, tnStatsDynamicConduitRuleRuleIndex }
    ::= { tnStatsDynamicConduitRuleTable 1 }

TnStatsDynamicConduitRuleEntry ::=
    SEQUENCE {
        tnStatsDynamicConduitRuleConduitIndex       Integer32,
        tnStatsDynamicConduitRuleRuleIndex          Integer32,
        tnStatsDynamicConduitRuleConduitID          Integer32,
        tnStatsDynamicConduitRuleRuleID             Integer32,
        tnStatsDynamicConduitRuleGlobalRuleIndex    Integer32,
        tnStatsDynamicConduitRuleApplicationName    DisplayString,
        tnStatsDynamicConduitRuleWANIngressHitCount Gauge32,
        tnStatsDynamicConduitRuleWANEgressHitCount  Gauge32,
        tnStatsDynamicConduitRuleBytesSent          Gauge32,
        tnStatsDynamicConduitRulePacketsSent        Gauge32,
        tnStatsDynamicConduitRuleBytesReceived      Gauge32,
        tnStatsDynamicConduitRulePacketsReceived    Gauge32,
        tnStatsDynamicConduitRuleBytesDropped       Gauge32,
        tnStatsDynamicConduitRulePacketsDropped     Gauge32,
        tnStatsDynamicConduitRuleLastActiveNMinuteAgo     TimeTicks
    }

tnStatsDynamicConduitRuleConduitIndex            OBJECT-TYPE
    SYNTAX      Integer32
    MAX-ACCESS  read-only
    STATUS      current
    DESCRIPTION
            "The unique index (Conduit) value for the Dynamic Conduit Rule."
    ::= { tnStatsDynamicConduitRuleEntry 1 }

tnStatsDynamicConduitRuleRuleIndex            OBJECT-TYPE
    SYNTAX      Integer32
    MAX-ACCESS  read-only
    STATUS      current
    DESCRIPTION
            "The unique index (Rule) value for the Dynamic Conduit Rule."
    ::= { tnStatsDynamicConduitRuleEntry 2 }

tnStatsDynamicConduitRuleConduitID               OBJECT-TYPE
    SYNTAX      Integer32
    MAX-ACCESS  read-only
    STATUS      current
    DESCRIPTION
            "The unique Talari ID (Conduit) value for the Dynamic Conduit Rule."
    ::= { tnStatsDynamicConduitRuleEntry 3 }

tnStatsDynamicConduitRuleRuleID               OBJECT-TYPE
    SYNTAX      Integer32
    MAX-ACCESS  read-only
    STATUS      current
    DESCRIPTION
            "The unique Talari ID (Rule) value for the Dynamic Conduit Rule."
    ::= { tnStatsDynamicConduitRuleEntry 4 }

tnStatsDynamicConduitRuleGlobalRuleIndex      OBJECT-TYPE
    SYNTAX      Integer32
    MAX-ACCESS  read-only
    STATUS      current
    DESCRIPTION
            "The index of this rule in the tnStatsRuleTable."
    ::= { tnStatsDynamicConduitRuleEntry 5 }

tnStatsDynamicConduitRuleApplicationName              OBJECT-TYPE
    SYNTAX      DisplayString
    MAX-ACCESS  read-only
    STATUS      current
    DESCRIPTION
            "The optional string application name associated
            with this dynamic conduit rule."
    ::= { tnStatsDynamicConduitRuleEntry 6 }

tnStatsDynamicConduitRuleWANIngressHitCount         OBJECT-TYPE
    SYNTAX      Gauge32
    MAX-ACCESS  read-only
    STATUS      current
    DESCRIPTION
            "The count of the number of times this rule has
            been hit for in the WAN Ingress direction, measured over
            the past active minute."
    ::= { tnStatsDynamicConduitRuleEntry 7 }

tnStatsDynamicConduitRuleWANEgressHitCount       OBJECT-TYPE
    SYNTAX      Gauge32
    MAX-ACCESS  read-only
    STATUS      current
    DESCRIPTION
            "The count of the number of times this rule has
            been hit for in the WAN Egress direction, measured over
            the past active minute."
    ::= { tnStatsDynamicConduitRuleEntry 8 }

tnStatsDynamicConduitRuleBytesSent                 OBJECT-TYPE
    SYNTAX      Gauge32
    MAX-ACCESS  read-only
    STATUS      current
    DESCRIPTION
            "The count of the number of bytes sent for packets that
            matched this rule, measured over the past active minute."
    ::= { tnStatsDynamicConduitRuleEntry 9 }

tnStatsDynamicConduitRulePacketsSent                 OBJECT-TYPE
    SYNTAX      Gauge32
    MAX-ACCESS  read-only
    STATUS      current
    DESCRIPTION
            "The count of the number of bytes received for packets that
            matched this rule, measured over the past active minute."
    ::= { tnStatsDynamicConduitRuleEntry 10 }

tnStatsDynamicConduitRuleBytesReceived                 OBJECT-TYPE
    SYNTAX      Gauge32
    MAX-ACCESS  read-only
    STATUS      current
    DESCRIPTION
            "The count of the number of packets sent for packets that
            matched this rule, measured over the past active minute."
    ::= { tnStatsDynamicConduitRuleEntry 11 }

tnStatsDynamicConduitRulePacketsReceived                 OBJECT-TYPE
    SYNTAX      Gauge32
    MAX-ACCESS  read-only
    STATUS      current
    DESCRIPTION
            "The count of the number of packets received for packets that
            matched this rule, measured over the past active minute."
    ::= { tnStatsDynamicConduitRuleEntry 12 }

tnStatsDynamicConduitRuleBytesDropped                 OBJECT-TYPE
    SYNTAX      Gauge32
    MAX-ACCESS  read-only
    STATUS      current
    DESCRIPTION
            "The count of the number of bytes dropped for packets that
            matched this rule, measured over the past active minute."
    ::= { tnStatsDynamicConduitRuleEntry 13 }

tnStatsDynamicConduitRulePacketsDropped                 OBJECT-TYPE
    SYNTAX      Gauge32
    MAX-ACCESS  read-only
    STATUS      current
    DESCRIPTION
            "The count of the number of packets dropped for packets that
            matched this rule, measured over the past active minute."
    ::= { tnStatsDynamicConduitRuleEntry 14 }

tnStatsDynamicConduitRuleLastActiveNMinuteAgo            OBJECT-TYPE
    SYNTAX      TimeTicks
    MAX-ACCESS  read-only
    STATUS      current
    DESCRIPTION
            "This rule was hit last N Minutes ago.
            If this field value is 0 and either tnStatsDynamicConduitRuleBytesSent
            or tnStatsDynamicConduitRuleBytesReceived is not zero, then that means
            that this rule is currently being used.  The rule
            statistics contain the latest values.
            If this field is > 0, then the rule statistics is
            plateaued to show that this rule was used N minutes ago."

    ::= { tnStatsDynamicConduitRuleEntry 15 }

--
-- Stats associated with Arp
--
tnStatsArp   OBJECT IDENTIFIER ::= { talariStatistics 23 }

tnStatsArpScalars   OBJECT IDENTIFIER ::= { tnStatsArp 1 }

tnStatsNumArpEntries OBJECT-TYPE
    SYNTAX         Integer32
    MAX-ACCESS     read-only
    STATUS         current
    DESCRIPTION
            "The total number of Arp entries."
    DEFVAL { 0 }
    ::= { tnStatsArpScalars 1 }

tnStatsArpTable OBJECT-TYPE
    SYNTAX      SEQUENCE OF TnStatsArpEntry
    MAX-ACCESS  not-accessible
    STATUS      current
    DESCRIPTION
            "A collection of statistics for Arp entry objects.
            Contains statistics counts for all the Arp entries in
            the system. Counter data in this table is updated once a
            minute."

    ::= { tnStatsArp 2 }

tnStatsArpEntry OBJECT-TYPE
    SYNTAX      TnStatsArpEntry
    MAX-ACCESS  not-accessible
    STATUS      current
    DESCRIPTION
            "An entry containing all the information for a ARP entry object."
    INDEX   { tnStatsArpID }
    ::= { tnStatsArpTable 1 }

TnStatsArpEntry ::=
    SEQUENCE {
        tnStatsArpID            Integer32,
        tnStatsArpIfIndex       DisplayString,
        tnStatsArpVlanTag       Counter64,
        tnStatsArpIpAddr        IpAddress,
        tnStatsArpPhysAddr     	PhysAddress,
        tnStatsArpState   	DisplayString,
        tnStatsArpType      	DisplayString,
        tnStatsArpReplyAgeMs    Counter64
    }

tnStatsArpID              OBJECT-TYPE
    SYNTAX      Integer32
    MAX-ACCESS  read-only
    STATUS      current
    DESCRIPTION
            "The unique Talari Index value for the Arp
            entry."
    ::= { tnStatsArpEntry 1 }

tnStatsArpIfIndex            OBJECT-TYPE
    SYNTAX      DisplayString
    MAX-ACCESS  read-only
    STATUS      current
    DESCRIPTION
            "The interface name corresponding to the Arp entry. This is the
            name shown on the front panel of the appliance and
            used in the user interfaces (Web and CLI)."
    ::= { tnStatsArpEntry 2 }

tnStatsArpVlanTag              OBJECT-TYPE
    SYNTAX      Counter64
    MAX-ACCESS  read-only
    STATUS      current
    DESCRIPTION
            "The VLAN ID associated with the Arp entry."
    ::= { tnStatsArpEntry 3 }

tnStatsArpIpAddr         OBJECT-TYPE
    SYNTAX      IpAddress
    MAX-ACCESS  read-only
    STATUS      current
    DESCRIPTION
            "The IP address mapping for the physical address."
    ::= { tnStatsArpEntry 4 }

tnStatsArpPhysAddr       OBJECT-TYPE
    SYNTAX      PhysAddress
    MAX-ACCESS  read-only
    STATUS      current
    DESCRIPTION
            "The destination MAC address in a frame to which
        this entry's filtering information applies."
    ::= { tnStatsArpEntry 5 }

tnStatsArpState     OBJECT-TYPE
    SYNTAX      DisplayString
    MAX-ACCESS  read-only
    STATUS      current
    DESCRIPTION
            "The state of the Arp entry."
    ::= { tnStatsArpEntry 6 }

tnStatsArpType     OBJECT-TYPE
    SYNTAX      DisplayString
    MAX-ACCESS  read-only
    STATUS      current
    DESCRIPTION
            "The type of Arp entry describes whether it is persistent or end-user. "
    ::= { tnStatsArpEntry 7 }

tnStatsArpReplyAgeMs   OBJECT-TYPE
    SYNTAX      Counter64
    MAX-ACCESS  read-only
    STATUS      current
    DESCRIPTION
            "The age of arp reply we received in milliseconds."
    ::= { tnStatsArpEntry 8 }

--
-- Stats associated with LAN GRE Tunnels
--
tnStatsLanGRETunnels   OBJECT IDENTIFIER ::= { talariStatistics 24 }

tnStatsLanGRETunnelScalars   OBJECT IDENTIFIER ::= { tnStatsLanGRETunnels 1 }

tnStatsNumLanGRETunnels OBJECT-TYPE
    SYNTAX         Integer32
    MAX-ACCESS     read-only
    STATUS         current
    DESCRIPTION
            "The total number of LAN-side GRE Tunnels."
    DEFVAL { 0 }
    ::= { tnStatsLanGRETunnelScalars 1 }

tnStatsLanGRETunnelTable OBJECT-TYPE
    SYNTAX      SEQUENCE OF TnStatsLanGRETunnelEntry
    MAX-ACCESS  not-accessible
    STATUS      current
    DESCRIPTION
            "A collection of statistics for LAN-side GRE tunnel objects.
            Contains statistics counts and state for all the LAN-side GRE 
            tunnels in the system.  Counter data in this table is updated 
            once a minute and is a cumulative count since the last time 
            the Talari service was started."

    ::= { tnStatsLanGRETunnels 2 }

tnStatsLanGRETunnelEntry OBJECT-TYPE
    SYNTAX      TnStatsLanGRETunnelEntry
    MAX-ACCESS  not-accessible
    STATUS      current
    DESCRIPTION
            "An entry containing management information applicable to a
            particular LAN-side GRE tunnel object."
    INDEX   { tnStatsLanGRETunnelIndex }
    ::= { tnStatsLanGRETunnelTable 1 }

TnStatsLanGRETunnelEntry ::=
    SEQUENCE {
        tnStatsLanGRETunnelIndex                    Integer32,
        tnStatsLanGRETunnelName                     DisplayString, 
        tnStatsLanGRETunnelState                    DisplayString, 
        tnStatsLanGRETunnelKeepaliveRequestSent     Counter64,
        tnStatsLanGRETunnelKeepaliveReplyReceived   Counter64,
        tnStatsLanGRETunnelKeepaliveReplySent       Counter64,
        tnStatsLanGRETunnelPacketsSent              Counter64,
        tnStatsLanGRETunnelBytesSent                Counter64,
        tnStatsLanGRETunnelPacketsSentDropped       Counter64,
        tnStatsLanGRETunnelPacketsSentFragmented    Counter64,
        tnStatsLanGRETunnelBytesSentDropped         Counter64,
        tnStatsLanGRETunnelPacketsReceived          Counter64,
        tnStatsLanGRETunnelBytesReceived            Counter64,
        tnStatsLanGRETunnelPacketsReceivedDropped   Counter64,
        tnStatsLanGRETunnelBytesReceivedDropped     Counter64,
        tnStatsLanGRETunnelRoutingDomainName        DisplayString
    }

tnStatsLanGRETunnelIndex              OBJECT-TYPE
    SYNTAX      Integer32
    MAX-ACCESS  read-only
    STATUS      current
    DESCRIPTION
            "The unique Talari Index value for the LAN-side
            GRE tunnel."
    ::= { tnStatsLanGRETunnelEntry 1 }

tnStatsLanGRETunnelName              OBJECT-TYPE
    SYNTAX      DisplayString
    MAX-ACCESS  read-only
    STATUS      current
    DESCRIPTION
            "The name for the LAN-side GRE tunnel.  This is the
            tunnel IP adddress of the configured tunnel."
    ::= { tnStatsLanGRETunnelEntry 2 }

tnStatsLanGRETunnelState              OBJECT-TYPE
    SYNTAX      DisplayString
    MAX-ACCESS  read-only
    STATUS      current
    DESCRIPTION
            "The state of the LAN-side GRE tunnel.  This can 
            be up or down."
    ::= { tnStatsLanGRETunnelEntry 3 }

tnStatsLanGRETunnelKeepaliveRequestSent         OBJECT-TYPE
    SYNTAX      Counter64
    MAX-ACCESS  read-only
    STATUS      current
    DESCRIPTION
            "The count of keepalive request packets sent for this 
            LAN-side GRE tunnel."
    ::= { tnStatsLanGRETunnelEntry 4 }

tnStatsLanGRETunnelKeepaliveReplyReceived         OBJECT-TYPE
    SYNTAX      Counter64
    MAX-ACCESS  read-only
    STATUS      current
    DESCRIPTION
            "The count of keepalive reply packets received for this 
            LAN-side GRE tunnel."
    ::= { tnStatsLanGRETunnelEntry 5 }

tnStatsLanGRETunnelKeepaliveReplySent         OBJECT-TYPE
    SYNTAX      Counter64
    MAX-ACCESS  read-only
    STATUS      current
    DESCRIPTION
            "The count of keepalive reply packets sent for this 
            LAN-side GRE tunnel."
    ::= { tnStatsLanGRETunnelEntry 6 }

tnStatsLanGRETunnelPacketsSent       OBJECT-TYPE
    SYNTAX      Counter64
    MAX-ACCESS  read-only
    STATUS      current
    DESCRIPTION
            "The count of packets sent for this LAN-side
            GRE tunnel."
    ::= { tnStatsLanGRETunnelEntry 7 }

tnStatsLanGRETunnelBytesSent         OBJECT-TYPE
    SYNTAX      Counter64
    MAX-ACCESS  read-only
    STATUS      current
    DESCRIPTION
            "The count of bytes sent for this LAN-side
            GRE tunnel."
    ::= { tnStatsLanGRETunnelEntry 8 }

tnStatsLanGRETunnelPacketsSentDropped       OBJECT-TYPE
    SYNTAX      Counter64
    MAX-ACCESS  read-only
    STATUS      current
    DESCRIPTION
            "The count of packets failed to sent for this LAN-side
            GRE tunnel."
    ::= { tnStatsLanGRETunnelEntry 9 }

tnStatsLanGRETunnelBytesSentDropped         OBJECT-TYPE
    SYNTAX      Counter64
    MAX-ACCESS  read-only
    STATUS      current
    DESCRIPTION
            "The count of bytes fail to sent for this LAN-side
            GRE tunnel."
    ::= { tnStatsLanGRETunnelEntry 10 }

tnStatsLanGRETunnelPacketsSentFragmented       OBJECT-TYPE
    SYNTAX      Counter64
    MAX-ACCESS  read-only
    STATUS      current
    DESCRIPTION
            "The count of packets fragmented before sent for this LAN-side
            GRE tunnel."
    ::= { tnStatsLanGRETunnelEntry 11 }

tnStatsLanGRETunnelPacketsReceived       OBJECT-TYPE
    SYNTAX      Counter64
    MAX-ACCESS  read-only
    STATUS      current
    DESCRIPTION
            "The count of packets received for this LAN-side
            GRE tunnel."
    ::= { tnStatsLanGRETunnelEntry 12 }

tnStatsLanGRETunnelBytesReceived         OBJECT-TYPE
    SYNTAX      Counter64
    MAX-ACCESS  read-only
    STATUS      current
    DESCRIPTION
            "The count of bytes received for this LAN-side
            GRE tunnel."
    ::= { tnStatsLanGRETunnelEntry 13 }

tnStatsLanGRETunnelPacketsReceivedDropped       OBJECT-TYPE
    SYNTAX      Counter64
    MAX-ACCESS  read-only
    STATUS      current
    DESCRIPTION
            "The count of packets dropped after received for this LAN-side
            GRE tunnel."
    ::= { tnStatsLanGRETunnelEntry 14 }

tnStatsLanGRETunnelBytesReceivedDropped         OBJECT-TYPE
    SYNTAX      Counter64
    MAX-ACCESS  read-only
    STATUS      current
    DESCRIPTION
            "The count of bytes dropped after received for this LAN-side
            GRE tunnel."
    ::= { tnStatsLanGRETunnelEntry 15 }

 tnStatsLanGRETunnelRoutingDomainName             OBJECT-TYPE
    SYNTAX      DisplayString
    MAX-ACCESS  read-only
    STATUS      current
    DESCRIPTION
            "The routing domain name. Each routing domain has
            its own set of interfaces and routing tables."
    ::= { tnStatsLanGRETunnelEntry 16 }

--
-- Events sub-section - contains a table with
-- the current event database and up to the
-- latest 1000 events in the system.
--
-- Events Objects
--   Events Scalars
--   Events Table
--
--
-- Some Textual conventions used in the events
--

TalariEventObjectTypeEnum ::= TEXTUAL-CONVENTION
    STATUS       current
    DESCRIPTION
            "Describes an enumeration of values used to represent the
            severity of an event generated by the talari Appliance."
    SYNTAX       INTEGER {
                     undefined(1),
                     service(2),
                     conduit(3),
                     wanlink(4),
                     path(5),
                     harddisk(6),
                     fan(7),
                     apna(8),
                     apnuser(9),
                     powersupply(10),
                     configupdate(11),
                     softwareupdate(12),
                     proxyarp(13),
                     ethernet(14),
                     watchdog(15),
                     dynamicconduit(16),
                     waningresspath(17),
                     wanegresspath(18),
                     appliancesettingsupdate(19),
                     discoveredmtu(20),
		     wanlinkcongestion(21),
		     usagecongestion(22),
                     langretunnel(23),
                     ipsectunnel(24),
                     virtualinterface(25),
                     licensesubsystem(26),
		     dynamicrouting(27),
		     wanop(28),
		     wanlinkusagethreshold(29),
                     awaresystem(1001),
                     awareuser(1002),
                     awarestorage(1003),
                     awaredatabase(1004),
                     connectiontoapna(1005)
                 }

TalariEventSeverityEnum ::= TEXTUAL-CONVENTION
    STATUS       current
    DESCRIPTION
            "Describes an enumeration of values used to represent the
            severity of an event generated by the talari Appliance."
    SYNTAX       INTEGER {
                     debug(1),
                     info(2),
                     notice(3),
                     warning(4),
                     error(5),
                     critical(6),
                     alert(7),
                     emergency(8)
                 }

TalariEventStateEnum ::= TEXTUAL-CONVENTION
    STATUS       current
    DESCRIPTION
            "Describes an enumeration of values used to represent the
            current state of the object that generated the event or
            trap in the TalariAppliance."
    SYNTAX       INTEGER {
                     undefined(1),
                     disabled(2),
                     dead(3),
                     bad(4),
                     good(5),
                     warning(6),
                     error(7),
                     restart(8),
                     reboot(9),
                     active(10),
                     standby(11),
                     success(12),
                     failure(13),
                     enabled(14),
                     pending(15),
                     created(16),
                     removed(17),
                     systemerror(18),
                     activeha(19),
                     standbyha(20),
                     activencn(21),
                     standbyncn(22),
                     congested(23),
                     uncongested(24),
                     viplearned(25),
                     vipreleased(26),
                     vipexpired(27),
                     vipgwnorsp(28),
                     viprcvdnak(29),
                     vipdetecteddup(30),
                     vipdhcpsnorsp(31),
                     licenseexpired(32),
                     featuremismatch(33),
                     configlicensemismatch(34),
                     unlicensedappliance(35),
                     licenseactive(36),
                     licensebankunreachable(37),
                     licensebankreachable(38),
                     bandwidthexceeded(39),
                     awareclientunlicensed(40),
                     hasecondaryunlicensed(41),
                     servicecontractunlicensed(42),
                     vipduplicate(43),
                     vipnotduplicate(44),
                     waningressusagelowerthresholdexceeded(45),
                     waningressusagelowerthresholdok(46),
                     wanegressusagelowerthresholdexceeded(47),
                     wanegressusagelowerthresholdok(48),
                     waningressusagehigherthresholdexceeded(49),
                     waningressusagehigherthresholdok(50),
                     wanegressusagehigherthresholdexceeded(51),
                     wanegressusagehigherthresholdok(52),
                     thresholdok(1001),
                     thresholdexceeded(1002),
                     pollingthresholdok(1003),
                     pollingthresholdexceeded(1004)
                 }

talariEventScalars   OBJECT IDENTIFIER ::= { talariEvents 1 }

talariNumEvents OBJECT-TYPE
    SYNTAX         Gauge32
    MAX-ACCESS     read-only
    STATUS         current
    DESCRIPTION
        "The current number of Events in the system."
    DEFVAL { 0 }
    ::= { talariEventScalars 1 }

talariEventTable OBJECT-TYPE
    SYNTAX      SEQUENCE OF TalariEventEntry
    MAX-ACCESS  not-accessible
    STATUS      current
    DESCRIPTION
            "A table containing the latest set of events that have
            been generated by the Talari system."
    ::= { talariEvents 2 }

talariEventEntry OBJECT-TYPE
    SYNTAX      TalariEventEntry
    MAX-ACCESS  not-accessible
    STATUS      current
    DESCRIPTION
            "An entry containing information describing an event that
            occurred in the system."
    INDEX   { talariEventIndex }
    ::= { talariEventTable 1 }

TalariEventEntry ::=
    SEQUENCE {
        talariEventIndex        Integer32,
        talariEventID           Integer32,
        talariEventObjectID     Integer32,
        talariEventObjectName   DisplayString,
        talariEventObjectType   TalariEventObjectTypeEnum,
        talariEventTime         DisplayString,
        talariEventType         TalariEventStateEnum,
        talariEventSeverity     TalariEventSeverityEnum,
        talariEventDescription  DisplayString
    }

talariEventIndex OBJECT-TYPE
    SYNTAX      Integer32
    MAX-ACCESS  read-only
    STATUS      current
    DESCRIPTION
            "A unique value, greater than zero, for each event.  It
            is recommended that values are assigned contiguously
            starting from 1.  The value for each interface sub-layer
            must remain constant at least from one re-initialization of
            the entity's network management system to the next re-
            initialization."
    ::= { talariEventEntry 1 }

talariEventID    OBJECT-TYPE
    SYNTAX      Integer32
    MAX-ACCESS  read-only
    STATUS      current
    DESCRIPTION
            "A unique value, used for the internal identification
            of the event.  This ID will match the ID used in the
            other User Interfaces."
    ::= { talariEventEntry 2 }

talariEventObjectID    OBJECT-TYPE
    SYNTAX      Integer32
    MAX-ACCESS  read-only
    STATUS      current
    DESCRIPTION
            "The ID of the object associated with the event."
    ::= { talariEventEntry 3 }

talariEventObjectName   OBJECT-TYPE
    SYNTAX    DisplayString
    MAX-ACCESS  read-only
    STATUS      current
    DESCRIPTION
            "A String representing the object that generated the event."
    ::= { talariEventEntry 4 }

talariEventObjectType    OBJECT-TYPE
    SYNTAX    TalariEventObjectTypeEnum
    MAX-ACCESS  read-only
    STATUS      current
    DESCRIPTION
            "An enumerated value representing the object type of the
            object that generated the event."
    ::= { talariEventEntry 5 }

talariEventTime    OBJECT-TYPE
    SYNTAX    DisplayString
    MAX-ACCESS  read-only
    STATUS      current
    DESCRIPTION
            "The localtime on the appliance as a String when the
            event occurred."
    ::= { talariEventEntry 6 }

talariEventType    OBJECT-TYPE
    SYNTAX    TalariEventStateEnum
    MAX-ACCESS  read-only
    STATUS      current
    DESCRIPTION
            "The type of the event - basically an enumeration of
            State transitions that can occur in the appliance that
            will generate an event."
    ::= { talariEventEntry 7 }

talariEventSeverity    OBJECT-TYPE
    SYNTAX    TalariEventSeverityEnum
    MAX-ACCESS  read-only
    STATUS      current
    DESCRIPTION
            "The severity of the event."
    ::= { talariEventEntry 8 }

talariEventDescription    OBJECT-TYPE
    SYNTAX    DisplayString
    MAX-ACCESS  read-only
    STATUS      current
    DESCRIPTION
            "A string description of the event."
    ::= { talariEventEntry 9 }

--
-- Trap definitions
--

talariEventNotification NOTIFICATION-TYPE
    OBJECTS            { talariEventIndex,
                         talariEventID,
                         talariEventObjectID,
                         talariEventObjectName,
                         talariEventObjectType,
                         talariEventTime,
                         talariEventType,
                         talariEventSeverity,
                         talariEventDescription }
    STATUS             current
    DESCRIPTION
            "Trap sent when a Talari event occurs.  These events
            can be from any of several talariEventObjectType
            object types in the system, and can represent a state
            transition or error condition in the talariEventType."
   ::= { talariNotifs 1 }

talariNetworkEventNotification NOTIFICATION-TYPE
    OBJECTS            { talariNetworkEventAPNID,
                         talariNetworkEventSiteID,
                         talariNetworkEventApplianceID,
                         talariNetworkEventSiteName,
                         talariEventID,
                         talariEventObjectID,
                         talariEventObjectName,
                         talariEventObjectType,
                         talariEventTime,
                         talariEventType,
                         talariEventSeverity,
                         talariEventDescription }
    STATUS             current
    DESCRIPTION
            "Trap sent from the Talari Aware network management/
            monitoring system when a Talari event occurs.  These
            events can be from any of the appliances in the network
            managed by the Aware system.
            Events can be from any of several talariEventObjectType
            object types in the system, and represent a state
            transition or error condition in the talariEventType."
   ::= { talariNotifs 2 }

talariNetworkEventScalars   OBJECT IDENTIFIER ::= { talariEvents 3 }

talariNetworkEventAPNID OBJECT-TYPE
    SYNTAX      Integer32
    MAX-ACCESS  read-only
    STATUS      current
    DESCRIPTION
            "A unique value, used for the internal identification
            of the APN (network) ID for an event.  This ID will match
            the ID used in the other User Interfaces within the Aware
            system."
    ::= { talariNetworkEventScalars 1 }

talariNetworkEventSiteID OBJECT-TYPE
    SYNTAX      Integer32
    MAX-ACCESS  read-only
    STATUS      current
    DESCRIPTION
            "A unique value, used for the internal identification
            of the site ID for an event.  This ID will match
            the ID used in the other User Interfaces."
    ::= { talariNetworkEventScalars 2 }

talariNetworkEventApplianceID OBJECT-TYPE
    SYNTAX      Integer32
    MAX-ACCESS  read-only
    STATUS      current
    DESCRIPTION
            "A unique value, used for the internal identification
            of the appliance ID for an event.  This ID will match
            the ID used in the other User Interfaces."
    ::= { talariNetworkEventScalars 3 }

talariNetworkEventSiteName OBJECT-TYPE
    SYNTAX      DisplayString
    MAX-ACCESS  read-only
    STATUS      current
    DESCRIPTION
            "A unique value, used for the identification of the
            site that is the source of the event."
    ::= { talariNetworkEventScalars 4 }

--
--
END

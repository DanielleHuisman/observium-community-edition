PANASAS-ROOT-MIB	DEFINITIONS	::= BEGIN

--	This mib document specifies the root of the
--	Panasas mib.
--
--	@author: Abbie Matthews & Bob Haigler
--	@last_modified: February, 14, 2006.
--	@version @PANASAS_VERSION@
--
--	@PANASAS_COPYRIGHT@
--
-- This Panasas Inc SNMP Management Information Base Specification
-- (Specification) embodies Panasas Inc's confidential and proprietary
-- intellectual property.  Panasas Inc retains all title and ownership
-- to the Specification, including any revisions.
--
-- This Specification is supplied "AS IS", and Panasas Inc makes
-- no warranty, either express or implied, as to the use,
-- operation, condition, or performance of the Specification.

IMPORTS
	MODULE-IDENTITY, enterprises
		FROM SNMPv2-SMI;

panasas	MODULE-IDENTITY
	LAST-UPDATED	"201104070000Z"
	ORGANIZATION	"Panasas, Inc"
	CONTACT-INFO
		"postal:	Panasas, Inc
			969 W. Maude Avenue
			Sunnyvale, CA 94085
		phone:     +1 408 215-6800
		email:     info@panasas.com"
	DESCRIPTION
		"This is the root of the Panasas Enterprise MIB."
    REVISION        "201104070000Z"
	DESCRIPTION
        "1. Changed Panasas, Inc. company contact information."
	::= { enterprises 10159 }

-- Primary nodes.
panProducts		OBJECT IDENTIFIER	::= { panasas 1 }
-- panTemporary		OBJECT IDENTIFIER	::= { panasas 2 }
-- panRegistration		OBJECT IDENTIFIER	::= { panasas 3 }

panNotifications	OBJECT IDENTIFIER	::= { panProducts 1 }
panHw			OBJECT IDENTIFIER	::= { panProducts 2 }
panFs			OBJECT IDENTIFIER	::= { panProducts 3 }

END

PANASAS-TC-MIB DEFINITIONS ::= BEGIN

--	This mib document specifies the textual conventions employed in the
--	Panasas mib.
--
--	@author: Abbie Matthews & Bob Haigler
--	@last_modified: February, 14, 2006.
--	@version @PANASAS_VERSION@
--
--	@PANASAS_COPYRIGHT@
--
-- This Panasas Inc SNMP Management Information Base Specification
-- (Specification) embodies Panasas Inc's confidential and proprietary
-- intellectual property.  Panasas Inc retains all title and ownership
-- to the Specification, including any revisions.
--
-- This Specification is supplied "AS IS", and Panasas Inc makes
-- no warranty, either express or implied, as to the use,
-- operation, condition, or performance of the Specification.

IMPORTS
	TEXTUAL-CONVENTION
		FROM SNMPv2-TC;

--
-- Textual conventions used in Panasas Enterprise MINs.
--

PanSerialNumber	::= TEXTUAL-CONVENTION
	DISPLAY-HINT	"255a"
	STATUS	current
	DESCRIPTION
		"Serial Number representation"
	SYNTAX	OCTET STRING (SIZE (8..32))

PanBoolean	::= TEXTUAL-CONVENTION
	STATUS	current
	DESCRIPTION
		"A boolean value of true(yes) or false(no)."
	SYNTAX	INTEGER {
			panFalse(0),
			panTrue(1)
		}

PanTemperature	::= TEXTUAL-CONVENTION
	STATUS	current
	DESCRIPTION
		"Temperature in degrees Celcius."
	SYNTAX	INTEGER (-100..200)

PanUtilization	::= TEXTUAL-CONVENTION
	DISPLAY-HINT	"d"
	STATUS	current
	DESCRIPTION
		"Utilization as a percentage, ie. 15 is 15 percent"
	SYNTAX	INTEGER (0..100)

END

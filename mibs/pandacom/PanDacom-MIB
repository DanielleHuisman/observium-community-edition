PanDacom-MIB
DEFINITIONS	::= BEGIN

IMPORTS
	enterprises	FROM RFC1155-SMI
	DisplayString	FROM RFC1213-MIB
	OBJECT-TYPE	FROM RFC-1212
;

--      PanDacom       OBJECT IDENTIFIER ::= { enterprises 3652 }

	PanDacom MODULE-IDENTITY
		 LAST-UPDATED "1105231700Z"
		 ORGANIZATION "Pan Dacom Direkt GmbH"
		 CONTACT-INFO
				"Pan Dacom Direkt GmbH
				Bereich Entwicklung und Produktion
				Dreieich Plaza 1B
				63303 Dreieich / Germany
				Tel. : +49 6103/83483-333
				Fax. : +49 6103/83483-444
				email: kontakt@pandacomdirekt.de
				web  : www.pandacomdirekt.de"
		 DESCRIPTION	 "Rev. 3.0"
		 ::= { enterprises 3652 }

--****************
--***  Trap's  ***
--****************
        Traps           OBJECT IDENTIFIER ::= { PanDacom 0 }

	Descr OBJECT-TYPE
		SYNTAX DisplayString (SIZE (0..255))
		ACCESS  read-only
		STATUS  mandatory
		DESCRIPTION
			"Trap Description"
              ::= { Traps 100 }

	Slot OBJECT-TYPE
		SYNTAX INTEGER
		ACCESS  read-only
		STATUS  mandatory
		DESCRIPTION
			"Slot No"
               ::= { Traps 101 }

	Port OBJECT-TYPE
		SYNTAX INTEGER
		ACCESS  read-only
		STATUS  mandatory
		DESCRIPTION
			"Port No"
               ::= { Traps 102 }

	IFCard OBJECT-TYPE
		SYNTAX INTEGER
		ACCESS  read-only
		STATUS  mandatory
		DESCRIPTION
		         "IFCard No from variable Interface-Cards like FO155"
               ::= { Traps 103 }
END

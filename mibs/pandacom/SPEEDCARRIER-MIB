SPEEDCARRIER-MIB	DEFINITIONS	::= BEGIN

--*****   Version History   ***************************************************************

--V1.0  09.11.2006 ML: first version SPEEDCARRIER-MIB
--V3.0  08.04.2009 GD: added new subtrees for multiplexer and ammplifier
--V5.0	20.04.2011 ML: added SW update and config handling over Backplane
--  Supported Modules:
--	SPEED-DUALLINE SFP 3R
--	SPEED-DUALLINE SFP 3R PROTECTION
--	SPEED-DUALLINE SFP
--	SPEED-SINGLELINE SFP
--	SPEED-SINGLELINE XFP (SPEEDSINGLELINE-XFP-MIB)
--	SPEED-SINGLELINE XFP 3R (SPEEDSINGLELINE-XFP-MIB)
--	SPEED-DUALLINE FC SFP+ and XFP (SPEED-DUALLINE-FC, also 16G cards)
--	SPEED-DUALLINE 10G SFP+ and XFP (obsolete. Is supported in SPEED-DUALLINE-FC)
--	SPEED-AMP's (EDFA and RAMAN) (SPEED-AMP-MIB)


IMPORTS
	DisplayString	FROM RFC1213-MIB
	OBJECT-TYPE	FROM RFC-1212
	TRAP-TYPE	FROM RFC-1215
	enterprises, IpAddress, TimeTicks, MODULE-IDENTITY	FROM SNMPv2-SMI
	PanDacom	FROM PanDacom-MIB;

--	SPEEDCARRIER	OBJECT IDENTIFIER ::= { PanDacom 3 }
	nmSPEEDCARRIER MODULE-IDENTITY
		LAST-UPDATED "1312120000Z"
		ORGANIZATION "Pan Dacom Direkt GmbH"
		CONTACT-INFO
			"Pan Dacom Direkt GmbH
			Dreieich Plaza 1B
			63303 Dreieich
			Germany
			Tel. : +49 6103/83483-333
			Fax. : +49 6103/83483-444
			email: kontakt@pandacomdirekt.de
			web  : www.pandacomdirekt.de"
		DESCRIPTION "Revision 2.0"

		REVISION      "1312120000Z"  -- Dec. 12, 2013
		DESCRIPTION "Revision 5.2.0
			- change of table indexes to slot or port
			- IPv6 support. So changed parameters like Trapsinks, NTP
			  and RADIUS server address from IpAddress to
			  DisplayString
			- new table for RADIUS server configs"

		::= { PanDacom 3 }



	nmAgent  OBJECT IDENTIFIER ::= { nmSPEEDCARRIER 1 }


	nmAgentGeneralInfo OBJECT IDENTIFIER ::= { nmAgent 1 }

	nmAVersion OBJECT-TYPE
		SYNTAX  DisplayString (SIZE(0..32))
		MAX-ACCESS  read-only
		STATUS  current
		DESCRIPTION
			"SPEED-NMS Ramdisk Version"
		::= { nmAgentGeneralInfo 1 }

	nmASlot OBJECT-TYPE
		SYNTAX  INTEGER (0..20)
		MAX-ACCESS  read-only
		STATUS  current
		DESCRIPTION
			"Slot in which the SPEED-NMS card is inserted"
		::= { nmAgentGeneralInfo 2 }

	nmADate OBJECT-TYPE
		SYNTAX  DisplayString (SIZE(0..15))
		MAX-ACCESS  read-only
		STATUS  current
		DESCRIPTION
			"Date of the SPEED-NMS system"
		::= { nmAgentGeneralInfo 3 }

	nmATime OBJECT-TYPE
		SYNTAX  DisplayString (SIZE(0..15))
		MAX-ACCESS  read-only
		STATUS  current
		DESCRIPTION
			"Actual Time of the SPEED-NMS system"
		::= { nmAgentGeneralInfo 4 }

	nmAUpTime OBJECT-TYPE
		SYNTAX  DisplayString (SIZE(0..15))
		MAX-ACCESS  read-only
		STATUS  current
		DESCRIPTION
			"System uptime of the SPEED-NMS system"
		::= { nmAgentGeneralInfo 5 }

	nmATemperature OBJECT-TYPE
		SYNTAX  INTEGER
		MAX-ACCESS  read-only
		STATUS  current
		DESCRIPTION
			"Board temperature of the SPEED-NMS system"
		::= { nmAgentGeneralInfo 6 }

	nmAAlarmState OBJECT-TYPE
		SYNTAX  INTEGER
		{
			noAlarms(0),
			activeAlarms(1)
		}
		MAX-ACCESS  read-only
		STATUS  current
		DESCRIPTION
			"Alarm state of the SPEED-NMS system"
		::= { nmAgentGeneralInfo 7 }

	nmASerialNumber OBJECT-TYPE
		SYNTAX  DisplayString (SIZE(0..15))
		MAX-ACCESS  read-only
		STATUS  current
		DESCRIPTION
			"Serial number of the SPEED-NMS system"
		::= { nmAgentGeneralInfo 8 }

	nmAKernelVersion OBJECT-TYPE
		SYNTAX  DisplayString (SIZE(0..32))
		MAX-ACCESS  read-only
		STATUS  current
		DESCRIPTION
			"SPEED-NMS Kernel Version"
		::= { nmAgentGeneralInfo 9 }

--*************************************************************
--	nmAgentConfig (2)

	nmAgentConfig OBJECT IDENTIFIER ::= { nmAgent 2 }

--*************************************************************
--	nmAgentConfigNetwork (1)

	nmAgentConfigNetwork OBJECT IDENTIFIER ::= { nmAgentConfig 1 }

	nmAgentConfigNetworkIP OBJECT-TYPE
		SYNTAX IpAddress
		MAX-ACCESS  read-write
		STATUS  current
		DESCRIPTION
			"IP-address of the management boards Ethernet interface"
		::= { nmAgentConfigNetwork 1 }

	nmAgentConfigNetworkMask OBJECT-TYPE
		SYNTAX IpAddress
		MAX-ACCESS  read-write
		STATUS  current
		DESCRIPTION
			"IP-netmask of the management boards Ethernet interface"
		::= { nmAgentConfigNetwork 2 }

	nmAgentConfigNetworkGateway OBJECT-TYPE
		SYNTAX IpAddress
		MAX-ACCESS  read-write
		STATUS  current
		DESCRIPTION
			"default gateway of the management boards Ethernet interface"
		::= { nmAgentConfigNetwork 3 }

	nmAgentConfigNetworkIPv6 OBJECT-TYPE
		SYNTAX  DisplayString (SIZE(0..50))
		MAX-ACCESS  read-write
		STATUS  current
		DESCRIPTION
			"IPv6-address of the management boards Ethernet interface"
		::= { nmAgentConfigNetwork 5 }

	nmAgentConfigNetworkGatewayv6 OBJECT-TYPE
		SYNTAX  DisplayString (SIZE(0..50))
		MAX-ACCESS  read-write
		STATUS  current
		DESCRIPTION
			"default gatewayv6 of the management boards Ethernet interface"
		::= { nmAgentConfigNetwork 6 }

--*************************************************************
--	nmAgentConfigSnmp (2)

	nmAgentConfigSnmp OBJECT IDENTIFIER ::= { nmAgentConfig 2 }

	nmAgentConfigSnmpReadCommunity OBJECT-TYPE
		SYNTAX DisplayString (SIZE(0..255))
		MAX-ACCESS  read-write
		STATUS  current
		DESCRIPTION
			"SNMP read community name"
		::= { nmAgentConfigSnmp 1 }

	nmAgentConfigSnmpWriteCommunity OBJECT-TYPE
		SYNTAX DisplayString (SIZE(0..255))
		MAX-ACCESS  read-write
		STATUS  current
		DESCRIPTION
			"SNMP write community name"
		::= { nmAgentConfigSnmp 2 }

	nmAgentConfigSnmpSysLocation OBJECT-TYPE
		SYNTAX DisplayString (SIZE(0..255))
		MAX-ACCESS  read-write
		STATUS  current
		DESCRIPTION
			"location of the SPEED-CARRIER system"
		::= { nmAgentConfigSnmp 3 }

	nmAgentConfigSnmpSysContact OBJECT-TYPE
		SYNTAX DisplayString (SIZE(0..255))
		MAX-ACCESS  read-write
		STATUS  current
		DESCRIPTION
			"administrator of the SPEED-CARRIER system"
		::= { nmAgentConfigSnmp 4 }

	nmAgentConfigSnmpTrapSink1 OBJECT-TYPE
		SYNTAX DisplayString (SIZE(0..50))
		MAX-ACCESS read-write
		STATUS current
		DESCRIPTION
			"Trap destination 1 for SNMP traps. Clear value is 0.0.0.0"
		::= { nmAgentConfigSnmp 5 }

	nmAgentConfigSnmpTrapSink2 OBJECT-TYPE
		SYNTAX DisplayString (SIZE(0..50))
		MAX-ACCESS read-write
		STATUS current
		DESCRIPTION
			"Trap destination 2 for SNMP traps. Clear value is 0.0.0.0"
		::= { nmAgentConfigSnmp 6 }

	nmAgentConfigSnmpTrapSink3 OBJECT-TYPE
		SYNTAX DisplayString (SIZE(0..50))
		MAX-ACCESS  read-write
		STATUS  current
		DESCRIPTION
			"Trap destination 3 for SNMP traps. Clear value is 0.0.0.0"
		::= { nmAgentConfigSnmp 7 }

	nmAgentConfigSnmpTrapSink4 OBJECT-TYPE
		SYNTAX DisplayString (SIZE(0..50))
		MAX-ACCESS  read-write
		STATUS  current
		DESCRIPTION
			"Trap destination 4 for SNMP traps. Clear value is 0.0.0.0"
		::= { nmAgentConfigSnmp 8 }

	nmAgentConfigSnmpTrapSink5 OBJECT-TYPE
		SYNTAX DisplayString (SIZE(0..50))
		MAX-ACCESS  read-write
		STATUS  current
		DESCRIPTION
			"Trap destination 5 for SNMP traps. Clear value is 0.0.0.0"
		::= { nmAgentConfigSnmp 9 }

	nmAgentConfigSnmpAgent OBJECT-TYPE
		SYNTAX INTEGER
		{
			off(0),
			snmpV1-V2c(1),
			snmpV3(2),
			notAvailable(255)
		}
		MAX-ACCESS  read-write
		STATUS  current
		DESCRIPTION
			"enable or disable the SNMP agent on the management board"
		::= { nmAgentConfigSnmp 10 }

-- ****************************************************
	nmAgentConfigSNMPv3UserConfigTable OBJECT-TYPE
		SYNTAX SEQUENCE OF NMAgentConfigSNMPv3UserConfigEntry
		MAX-ACCESS  not-accessible
		STATUS  current
		DESCRIPTION
			"SNMPv3 user configuration table"
		::= { nmAgentConfigSnmp 11 }

	nmAgentConfigSNMPv3UserConfigEntry OBJECT-TYPE
		SYNTAX NMAgentConfigSNMPv3UserConfigEntry
		MAX-ACCESS  not-accessible
		STATUS  current
		DESCRIPTION
			"SNMPv3 user configuration table"
		INDEX { nmAgentConfigSNMPv3UserConfigIndex }
		::= { nmAgentConfigSNMPv3UserConfigTable 1 }

	NMAgentConfigSNMPv3UserConfigEntry ::= SEQUENCE
		{
			nmAgentConfigSNMPv3UserConfigIndex INTEGER,
			nmAgentConfigSnmpv3UserConfigName DisplayString,
			nmAgentConfigSnmpv3UserConfigUserLevel INTEGER,
			nmAgentConfigSnmpv3UserConfigAuthType INTEGER,
			nmAgentConfigSnmpv3UserConfigAuthPassPhrase DisplayString,
			nmAgentConfigSnmpv3UserConfigEncType INTEGER,
			nmAgentConfigSnmpv3UserConfigPrivPassPhrase DisplayString
		}

	nmAgentConfigSNMPv3UserConfigIndex OBJECT-TYPE
		SYNTAX INTEGER (0..2)
		MAX-ACCESS  read-only
		STATUS  current
		DESCRIPTION
			"user index"
		::= { nmAgentConfigSNMPv3UserConfigEntry 1 }

	nmAgentConfigSnmpv3UserConfigName OBJECT-TYPE
		SYNTAX DisplayString (SIZE(0..32))
		MAX-ACCESS  read-write
		STATUS  current
		DESCRIPTION
			"user name"
		::= { nmAgentConfigSNMPv3UserConfigEntry 2 }

	nmAgentConfigSnmpv3UserConfigUserLevel OBJECT-TYPE
		SYNTAX INTEGER
		{
			notAvailable(0),
			rouser(1),
			rwuser(2)
		}
		MAX-ACCESS  read-write
		STATUS  current
		DESCRIPTION
			"user rights read-only (ro) or read-write (rw)"
		::= { nmAgentConfigSNMPv3UserConfigEntry 3 }

	nmAgentConfigSnmpv3UserConfigAuthType OBJECT-TYPE
		SYNTAX INTEGER
		{
			notAvailable(0),
			mD5(1),
			sHA(2)
		}
		MAX-ACCESS  read-write
		STATUS  current
		DESCRIPTION
			"authentication types"
		::= { nmAgentConfigSNMPv3UserConfigEntry 4 }

	nmAgentConfigSnmpv3UserConfigAuthPassPhrase OBJECT-TYPE
		SYNTAX DisplayString (SIZE(0..32))
		MAX-ACCESS  read-write
		STATUS  current
		DESCRIPTION
			"authentication passphrase"
		::= { nmAgentConfigSNMPv3UserConfigEntry 5 }

	nmAgentConfigSnmpv3UserConfigEncType OBJECT-TYPE
		SYNTAX INTEGER
		{
			notAvailable(0),
			dES(1),
			aES(2)
		}
		MAX-ACCESS  read-write
		STATUS  current
		DESCRIPTION
			"privacy protocols"
		::= { nmAgentConfigSNMPv3UserConfigEntry 6 }

	nmAgentConfigSnmpv3UserConfigPrivPassPhrase OBJECT-TYPE
		SYNTAX DisplayString (SIZE(0..32))
		MAX-ACCESS  read-write
		STATUS  current
		DESCRIPTION
			"privacy passphrase"
		::= { nmAgentConfigSNMPv3UserConfigEntry 7 }


--*************************************************************
--	nmAgentConfigSlotAlarms(3)

	nmAgentConfigSlotAlarmsTable OBJECT-TYPE
		SYNTAX SEQUENCE OF NMAgentConfigSlotAlarmsEntry
		MAX-ACCESS  not-accessible
		STATUS  current
		DESCRIPTION
			"Table for Slot 'alarm relay' configuration"
		::= { nmAgentConfig 3 }

	nmAgentConfigSlotAlarmsEntry OBJECT-TYPE
		SYNTAX NMAgentConfigSlotAlarmsEntry
		MAX-ACCESS  not-accessible
		STATUS  current
		DESCRIPTION
			"activate or deactivate slot for 'alarm relay' configuration"
    		INDEX   { nmAgentConfigSlotAlarmsSlotNumber }
		::= { nmAgentConfigSlotAlarmsTable 1 }

	NMAgentConfigSlotAlarmsEntry ::= SEQUENCE
		{
		nmAgentConfigSlotAlarmsSlotNumber	INTEGER,
		nmAgentConfigSlotAlarmsInsertedCard	DisplayString,
		nmAgentConfigSlotAlarmsConfig		INTEGER
		}

	nmAgentConfigSlotAlarmsSlotNumber OBJECT-TYPE
		SYNTAX INTEGER (1..20)
		MAX-ACCESS  read-only
		STATUS  current
		DESCRIPTION
			"Slot number for alarm relay configuration"
		::= { nmAgentConfigSlotAlarmsEntry 1 }

	nmAgentConfigSlotAlarmsInsertedCard OBJECT-TYPE
		SYNTAX DisplayString (SIZE(0..64))
		MAX-ACCESS  read-only
		STATUS  current
		DESCRIPTION
			"Card type of inserted card in this slot"
		::= { nmAgentConfigSlotAlarmsEntry 2 }

	nmAgentConfigSlotAlarmsConfig OBJECT-TYPE
		SYNTAX INTEGER
		{
			alarmsEnabled(0),
			alarmsDisabled(1),
			fail(255)
		}
		MAX-ACCESS  read-write
		STATUS  current
		DESCRIPTION
			"set alarm reporting to 'on' or 'off' for this slot"
		::= { nmAgentConfigSlotAlarmsEntry 3 }

--*************************************************************
--	nmAgentConfigModules (4)

	nmAgentConfigSlotModulesTable OBJECT-TYPE
		SYNTAX SEQUENCE OF NMAgentConfigSlotModulesEntry
		MAX-ACCESS  not-accessible
		STATUS  current
		DESCRIPTION
			"Table for card configuration"
		::= { nmAgentConfig 4 }

	nmAgentConfigSlotModulesEntry OBJECT-TYPE
		SYNTAX NMAgentConfigSlotModulesEntry
		MAX-ACCESS  not-accessible
		STATUS  current
		DESCRIPTION
			"Table for card configuration"
		INDEX { nmAgentConfigModulesSlotNumber }
		::= { nmAgentConfigSlotModulesTable 1 }

	NMAgentConfigSlotModulesEntry ::= SEQUENCE
		{
			nmAgentConfigModulesSlotNumber INTEGER,
			nmAgentConfigModulesInstalledCard DisplayString,
			nmAgentConfigModulesExpectedCard INTEGER,
			nmAgentConfigModulesSlotText DisplayString,
			nmAgentConfigModulesInstalledState DisplayString
		}

	nmAgentConfigModulesSlotNumber OBJECT-TYPE
		SYNTAX INTEGER (1..20)
		MAX-ACCESS  read-only
		STATUS  current
		DESCRIPTION
			"slot number for card configuration"
		::= { nmAgentConfigSlotModulesEntry 1 }

	nmAgentConfigModulesInstalledCard OBJECT-TYPE
		SYNTAX DisplayString (SIZE(0..64))
		MAX-ACCESS  read-only
		STATUS  current
		DESCRIPTION
			"Card type of inserted card in this slot"
		::= { nmAgentConfigSlotModulesEntry 2 }

	nmAgentConfigModulesExpectedCard OBJECT-TYPE
		SYNTAX INTEGER
		{
			notConfigured(0),
			speedCWDM21(11),
			speedCWDM41(12),
			speedCWDM41E(13),
			speedCWDM51(14),
			speedCWDM81(15),
			speedCWDM81E(16),
			speedCWDM91(17),
			speedADCWDM(18),
			oneSlotPassiveCard(19),
			twoSlotPassiveCard(20),
			speedNMS(50),
			speedProtect3R(51),
			speedDuallineSfp3R(52),
			speedDuallineSfp(53),
			speedSinglelineSfp(54),
			speedSinglelineXFP3R(55),
			speedSinglelineXFP(56),
			speedDuallineFcXFP(57),
			speedDuallineFcSfp(58),
			speedDualline10GXFP(59),
			speedDualline10GSfp(60),
			speedDualline16GXFP(61),
			speedDualline16GSfp(62),
			speedAmpEdfaPREAMP14(101),
			speedAmpEdfaBOOSTER17(102),
			speedAmpEdfaBOOSTER17OSC(103),
			speedAmpEdfaBOOSTER23OSC(104),
			speedAmpEdfaINLINE17OSC(105),
			speedAmpEdfaINLINE23OSC(106),
			speedAmpRamanMASTER10(107),
			speedAmpRamanMASTER15(108),
			speedAmpRamanSLAVE10(109),
			speedAmpRamanSLAVE15(110),
			speedAmpRamanSTANDALONE10(111),
			speedAmpRamanSTANDALONE15(112),
			reserved(255)
		}
		MAX-ACCESS  read-write
		STATUS  current
		DESCRIPTION
			"set the type of card, which is inserted in slot"
		::= { nmAgentConfigSlotModulesEntry 3 }

	nmAgentConfigModulesSlotText OBJECT-TYPE
		SYNTAX DisplayString (SIZE(0..32))
		MAX-ACCESS  read-write
		STATUS  current
		DESCRIPTION
			"set the user defined text for passive card, which is inserted in slot"
		::= { nmAgentConfigSlotModulesEntry 4 }

	nmAgentConfigModulesInstalledState OBJECT-TYPE
		SYNTAX DisplayString (SIZE(0..32))
		MAX-ACCESS  read-only
		STATUS  current
		DESCRIPTION
			"Check the installed module against the expected module"
		::= { nmAgentConfigSlotModulesEntry 5 }


--*************************************************************
--	nmAgentConfigAgentPorts (5) (for later RELEASE)

--	nmAgentConfigAgentPorts OBJECT IDENTIFIER ::= { nmAgentConfig 5 }

--*************************************************************
--	nmAgentConfig (2)


	nmAgentConfigCarrierName OBJECT-TYPE
		SYNTAX DisplayString (SIZE(0..60))
		MAX-ACCESS  read-write
		STATUS  current
		DESCRIPTION
			"name or location of the SPEED-CARRIER system"
		::= { nmAgentConfig 6 }

	nmAgentConfigAlarmRelay OBJECT-TYPE
		SYNTAX INTEGER
		{
			off(0),
			psu(1),
			fan(2),
			psuFan(3),
			slots(4),
			psuSlots(5),
			fanSlots(6),
			psuFanSlots(7),
			notAvailable(255)
		}
		MAX-ACCESS  read-write
		STATUS  current
		DESCRIPTION
			"configure alarm relay for different sources"
		::= { nmAgentConfig 7 }

	nmAgentConfigFAN OBJECT-TYPE
		SYNTAX INTEGER
		{
			allOn(1),
			auto(2)
		}
		MAX-ACCESS  read-write
		STATUS  current
		DESCRIPTION
			"configure fans to 'allOn' or 'auto'"
		::= { nmAgentConfig 8 }

	nmAgentConfigNtpServer OBJECT-TYPE
		SYNTAX DisplayString (SIZE(0..50))
		MAX-ACCESS  read-write
		STATUS  current
		DESCRIPTION
			"IP address of the Network Time Protocol server. Clear value is '0.0.0.0'."
		::= { nmAgentConfig 9 }

	nmAgentConfigTftpServer OBJECT-TYPE
		SYNTAX INTEGER
		{
			off(0),
			on(1),
			notAvailable(255)
		}
		MAX-ACCESS  read-write
		STATUS  current
		DESCRIPTION
			"enable or disable the TFTP server on the management board"
		::= { nmAgentConfig 10 }

	nmAgentConfigWebServer OBJECT-TYPE
		SYNTAX INTEGER
		{
			off(0),
			http(1),
			https(2),
			notAvailable(255)
		}
		MAX-ACCESS  read-write
		STATUS  current
		DESCRIPTION
			"enable or disable the web server on the management board"
		::= { nmAgentConfig 11 }

	nmAgentConfigMyWebView OBJECT-TYPE
		SYNTAX INTEGER
		{
			pictureAndDeviceList(1),
			pictureAndActiveAlarms(2),
			deviceListAndActiveAlarms(3),
			notAvailable(255)
		}
		MAX-ACCESS  read-write
		STATUS  current
		DESCRIPTION
			"configures the start screen of WebView for the web interface"
		::= { nmAgentConfig 12 }

	nmAgentConfigPSU1Type OBJECT-TYPE
		SYNTAX INTEGER
		{
			slotEmpty(0),
			psu230VAC75W(1),
			psu230VAC160W(2),
			psu48VDC75W(3),
			psu48VDC150W(4),
			psu48VDC60W(5),
			psu230VAC60W(6),
			psu48VDC250W(7),
			psu230VAC250W(8),
			notDefined(254),
			notAvailable(255)
		}
		MAX-ACCESS  read-write
		STATUS  current
		DESCRIPTION
			"configures the type of PSU 1"
		::= { nmAgentConfig 13 }

	nmAgentConfigPSU2Type OBJECT-TYPE
		SYNTAX INTEGER
		{
			slotEmpty(0),
			psu230VAC75W(1),
			psu230VAC160W(2),
			psu48VDC75W(3),
			psu48VDC150W(4),
			psu48VDC60W(5),
			psu230VAC60W(6),
			psu48VDC250W(7),
			psu230VAC250W(8),
			notDefined(254),
			notAvailable(255)
		}
		MAX-ACCESS  read-write
		STATUS  current
		DESCRIPTION
			"configures the type of PSU 2"
		::= { nmAgentConfig 14 }

	nmAgentConfigTimezone OBJECT-TYPE
		SYNTAX INTEGER
		{
			utc(0),
			met(1),
			notAvailable(255)
		}
		MAX-ACCESS  read-write
		STATUS  current
		DESCRIPTION
			"sets the system time zone. Has only effect after reboot"
		::= { nmAgentConfig 15 }

	nmAgentConfigAccess OBJECT-TYPE
		SYNTAX INTEGER
		{
			unknown(0),
			off(1),
			telnet(2),
			ssh2(3),
			sshWithPreSharedKeys(4)
		}
		MAX-ACCESS  read-write
		STATUS  current
		DESCRIPTION
			"sets system access to telnet, SSH version 2 or off"
		::= { nmAgentConfig 16 }

	nmAgentConfigCliTimeout OBJECT-TYPE
		SYNTAX INTEGER (120..3600)
		MAX-ACCESS  read-write
		STATUS  current
		DESCRIPTION
			"time without user interaction before exiting CLI. Valid range 120-3600 seconds."
		::= { nmAgentConfig 17 }

	nmAgentConfigRadiusServerAddress OBJECT-TYPE
		SYNTAX	IpAddress
		MAX-ACCESS	read-write
		STATUS	current
		DESCRIPTION
			"IP address of the radius server"
		::= { nmAgentConfig 18 }

	nmAgentConfigRadiusStateConfig OBJECT-TYPE
		SYNTAX INTEGER
		{
			notAvailable(0),
			useLocalPasswords(1),
			useRadiusAuthentication(2)
		}
		MAX-ACCESS	read-write
		STATUS	current
		DESCRIPTION
			"IP address of the radius server"
		::= { nmAgentConfig 19 }

	nmAgentConfigRadiusSharedSecret OBJECT-TYPE
		SYNTAX DisplayString (SIZE(0..32))
		MAX-ACCESS	read-write
		STATUS	current
		DESCRIPTION
			"shared secret for RADIUS server communication"
		::= { nmAgentConfig 20 }

	nmAgentConfigNMSState OBJECT-TYPE
		SYNTAX INTEGER
		{
			notAvailable(0),
			running(1),
			resetSystem(2),
			resetConfig(3)
		}
		MAX-ACCESS	read-write
		STATUS	current
		DESCRIPTION
			"running state of NMS module. Reboot is NOT traffic effecting!"
		::= { nmAgentConfig 21 }

	nmAgentConfigPSU1Text OBJECT-TYPE
		SYNTAX DisplayString (SIZE(0..32))
		MAX-ACCESS	read-write
		STATUS  current
		DESCRIPTION
			"configures passive text of PSU 1"
		::= { nmAgentConfig 22 }

	nmAgentConfigPSU2Text OBJECT-TYPE
		SYNTAX DisplayString (SIZE(0..32))
		MAX-ACCESS	read-write
		STATUS  current
		DESCRIPTION
			"configures passive text of PSU 2"
		::= { nmAgentConfig 23 }

	nmAgentConfigPSU3Text OBJECT-TYPE
		SYNTAX DisplayString (SIZE(0..32))
		MAX-ACCESS	read-write
		STATUS  current
		DESCRIPTION
			"configures passive text of PSU 3"
		::= { nmAgentConfig 24 }

	nmAgentConfigPSU3Type OBJECT-TYPE
		SYNTAX INTEGER
		{
			slotEmpty(0),
			psu48VDC250W(7),
			psu230VAC250W(8),
			notDefined(254),
			notAvailable(255)
		}
		MAX-ACCESS  read-write
		STATUS  current
		DESCRIPTION
			"configures the type of PSU 3"
		::= { nmAgentConfig 25 }

-- ****************************************************
	nmAgentConfigRadiusServerConfigTable OBJECT-TYPE
		SYNTAX SEQUENCE OF NMAgentConfigRadiusServerConfigEntry
		MAX-ACCESS  not-accessible
		STATUS  current
		DESCRIPTION
			"RADIUS server configuration table"
		::= { nmAgentConfig 26 }

	nmAgentConfigRadiusServerConfigEntry OBJECT-TYPE
		SYNTAX NMAgentConfigRadiusServerConfigEntry
		MAX-ACCESS  not-accessible
		STATUS  current
		DESCRIPTION
			"RADIUS server configuration table"
		INDEX { nmAgentConfigRadiusServerConfigNumber }
		::= { nmAgentConfigRadiusServerConfigTable 1 }

	NMAgentConfigRadiusServerConfigEntry ::= SEQUENCE
		{
			nmAgentConfigRadiusServerConfigNumber INTEGER,
			nmAgentConfigRadiusServerConfigIPAddress DisplayString,
			nmAgentConfigRadiusServerConfigSharedSecret DisplayString
		}

	nmAgentConfigRadiusServerConfigNumber OBJECT-TYPE
		SYNTAX INTEGER (1..2)
		MAX-ACCESS  read-only
		STATUS  current
		DESCRIPTION
			"RADIUS server number"
		::= { nmAgentConfigRadiusServerConfigEntry 1 }

	nmAgentConfigRadiusServerConfigIPAddress  OBJECT-TYPE
		SYNTAX DisplayString (SIZE(0..50))
		MAX-ACCESS  read-write
		STATUS  current
		DESCRIPTION
			"RADIUS server IPv4 or IPv6 address"
		::= { nmAgentConfigRadiusServerConfigEntry 2 }

	nmAgentConfigRadiusServerConfigSharedSecret OBJECT-TYPE
		SYNTAX DisplayString (SIZE(0..32))
		MAX-ACCESS  read-write
		STATUS  current
		DESCRIPTION
			"RADIUS server shared secret"
		::= { nmAgentConfigRadiusServerConfigEntry 3 }

--*************************************************************
	nmAgentPortsStatus OBJECT IDENTIFIER ::= { nmAgent 3 }

	nmAgentPort1OperStatus OBJECT-TYPE
		SYNTAX INTEGER
		{
			notAvailable(0),
			notInserted(1),
			up(2),
			down(3),
			txFault(4),
			txDisabled(5)
		}
		MAX-ACCESS  read-only
		STATUS  current
		DESCRIPTION
			"first SFP port operational status"
		::= { nmAgentPortsStatus 1 }

	nmAgentPort2OperStatus OBJECT-TYPE
		SYNTAX INTEGER
		{
			notAvailable(0),
			notInserted(1),
			up(2),
			down(3),
			txFault(4),
			txDisabled(5)
		}
		MAX-ACCESS  read-only
		STATUS  current
		DESCRIPTION
			"second SFP port operational status"
		::= { nmAgentPortsStatus 2 }

--*************************************************************
--	nmCarrier (2)

	nmCarrier OBJECT IDENTIFIER ::= { nmSPEEDCARRIER 2 }

--*************************************************************
--	nmCarrierGerneralInfo (1)

	nmCarrierGerneralInfo OBJECT IDENTIFIER ::= { nmCarrier 1 }

	nmCarrierName OBJECT-TYPE
		SYNTAX DisplayString (SIZE(0..64))
		MAX-ACCESS  read-only
		STATUS  current
		DESCRIPTION
			"name or location of the SPEED-CARRIER system. Allowed characters are 0-9 a-z A-Z '-' and '_'"
		::= { nmCarrierGerneralInfo 1 }

	nmCarrierType OBJECT-TYPE
		SYNTAX INTEGER
		{
			unknown (0),
			carrier4U (1),
			carrier1U (2),
			carrier45U (3),
			carrier5U (4)
		}
		MAX-ACCESS  read-only
		STATUS  current
		DESCRIPTION
			"Type of SPEED-CARRIER system (1U / 4 slots, 4U or 4,5U with 17 slots)"
		::= { nmCarrierGerneralInfo 2 }

	nmPSU1Status OBJECT-TYPE
		SYNTAX INTEGER
		{
			notInstalled (0),
			fail (1),
			temperatureWarning (2),
			pass (3)
		}
		MAX-ACCESS  read-only
		STATUS  current
		DESCRIPTION
			"Status of PSU 1"
		::= { nmCarrierGerneralInfo 3 }

	nmPSU2Status OBJECT-TYPE
		SYNTAX INTEGER
		{
			notInstalled (0),
			fail (1),
			temperatureWarning (2),
			pass (3)
		}
		MAX-ACCESS  read-only
		STATUS  current
		DESCRIPTION
			"Status of PSU 2"
		::= { nmCarrierGerneralInfo 4 }

	nmFanState OBJECT-TYPE
		SYNTAX INTEGER
		{
			notAvailable (0),
			pass (3),
			fail (4),
			notInstalled (5)
		}
		MAX-ACCESS  read-only
		STATUS  current
		DESCRIPTION
			"Fan state of the SPEED-CARRIER system"
		::= { nmCarrierGerneralInfo 5 }

	nmCarrierPSU1Type OBJECT-TYPE
		SYNTAX INTEGER
		{
			notConfigured(0),
			psu230VAC75W(1),
			psu230VAC160W(2),
			psu48VDC75W(3),
			psu48VDC150W(4),
			psu48VDC60W(5),
			psu230VAC60W(6),
			psu48VDC250W(7),
			psu230VAC250W(8),
			notAvailable(255)
		}
		MAX-ACCESS  read-only
		STATUS  current
		DESCRIPTION
			"type of PSU 1"
		::= { nmCarrierGerneralInfo 6 }

	nmCarrierPSU2Type OBJECT-TYPE
		SYNTAX INTEGER
		{
			notConfigured(0),
			psu230VAC75W(1),
			psu230VAC160W(2),
			psu48VDC75W(3),
			psu48VDC150W(4),
			psu48VDC60W(5),
			psu230VAC60W(6),
			psu48VDC250W(7),
			psu230VAC250W(8),
			notAvailable(255)
		}
		MAX-ACCESS  read-only
		STATUS  current
		DESCRIPTION
			"type of PSU 2"
		::= { nmCarrierGerneralInfo 7 }

	nmCarrierPSU1Text OBJECT-TYPE
		SYNTAX DisplayString (SIZE(0..32))
		MAX-ACCESS  read-only
		STATUS  current
		DESCRIPTION
			"PSU 1 customer description"
		::= { nmCarrierGerneralInfo 8 }

	nmCarrierPSU2Text OBJECT-TYPE
		SYNTAX DisplayString (SIZE(0..32))
		MAX-ACCESS  read-only
		STATUS  current
		DESCRIPTION
			"PSU 2 customer description"
		::= { nmCarrierGerneralInfo 9 }

	nmCarrierPSU3Text OBJECT-TYPE
		SYNTAX DisplayString (SIZE(0..32))
		MAX-ACCESS  read-only
		STATUS  current
		DESCRIPTION
			"PSU 3 customer description"
		::= { nmCarrierGerneralInfo 10 }

	nmCarrierPSU3Type OBJECT-TYPE
		SYNTAX INTEGER
		{
			notConfigured(0),
			psu230VAC75W(1),
			psu230VAC160W(2),
			psu48VDC75W(3),
			psu48VDC150W(4),
			psu48VDC60W(5),
			psu230VAC60W(6),
			psu48VDC250W(7),
			psu230VAC250W(8),
			notAvailable(255)
		}
		MAX-ACCESS  read-only
		STATUS  current
		DESCRIPTION
			"type of PSU 3"
		::= { nmCarrierGerneralInfo 11 }

	nmPSU3Status OBJECT-TYPE
		SYNTAX INTEGER
		{
			notInstalled (0),
			fail (1),
			temperatureWarning (2),
			pass (3),
			notAvailable(255)
		}
		MAX-ACCESS  read-only
		STATUS  current
		DESCRIPTION
			"Status of PSU 3"
		::= { nmCarrierGerneralInfo 12 }

--*************************************************************
--	nmCarrierSlotOverviewTable (2)

	nmCarrierSlotOverviewTable OBJECT-TYPE
		SYNTAX SEQUENCE OF NMCarrierSlotOverviewEntry
		MAX-ACCESS  not-accessible
		STATUS  current
		DESCRIPTION
			"Carrier slot overview table"
		::= { nmCarrier 2  }

	nmCarrierSlotOverviewEntry OBJECT-TYPE
		SYNTAX NMCarrierSlotOverviewEntry
		MAX-ACCESS  not-accessible
		STATUS  current
		DESCRIPTION
			"Carrier slot overview"
		INDEX { nmCarrierSlotNumber }
		::= { nmCarrierSlotOverviewTable 1 }

	NMCarrierSlotOverviewEntry ::= SEQUENCE
		{
		nmCarrierSlotNumber	INTEGER,
		nmCarrierSlotType	DisplayString,
		nmCarrierSlotPassiveText	DisplayString
		}

 	nmCarrierSlotNumber OBJECT-TYPE
		SYNTAX INTEGER (1..17)
		MAX-ACCESS  read-only
		STATUS  current
		DESCRIPTION
			"Slot Number 1..17 for 4,xU Carrier or 1..4 for 1U Carrier"
		::= { nmCarrierSlotOverviewEntry 1 }

	nmCarrierSlotType OBJECT-TYPE
		SYNTAX DisplayString (SIZE(0..32))
		MAX-ACCESS  read-only
		STATUS  current
		DESCRIPTION
			"installed card type in this slot"
		::= { nmCarrierSlotOverviewEntry 2 }

	nmCarrierSlotPassiveText OBJECT-TYPE
		SYNTAX DisplayString (SIZE(0..32))
		MAX-ACCESS  read-only
		STATUS  current
		DESCRIPTION
			"user defined text for passive cards. Is only available, if passive card is configured"
		::= { nmCarrierSlotOverviewEntry 3 }

--*************************************************************
--	nmFanOverview(3)

 	nmFanOverviewTable OBJECT-TYPE
		SYNTAX SEQUENCE OF NMFanOverviewEntry
		MAX-ACCESS  not-accessible
		STATUS  current
		DESCRIPTION
			"Fan overview table"
		::= { nmCarrier 3 }

	nmFanOverviewEntry OBJECT-TYPE
		SYNTAX NMFanOverviewEntry
		MAX-ACCESS  not-accessible
		STATUS  current
		DESCRIPTION
			"Fan overview table"
		INDEX { nmFanGroupNumber }
		::= { nmFanOverviewTable 1 }

	NMFanOverviewEntry ::= SEQUENCE
		{
		nmFanGroupNumber	INTEGER,
		nmFanGroupStatus	INTEGER
		}

	nmFanGroupNumber OBJECT-TYPE
		SYNTAX INTEGER (1..10)
		MAX-ACCESS read-only
		STATUS  current
		DESCRIPTION
			"Fan group number"
		::= { nmFanOverviewEntry 1 }

	nmFanGroupStatus OBJECT-TYPE
		SYNTAX INTEGER
		{
			notAvailable (0),
			on (1),
			off (2),
			pass (3),
			fail (4),
			notInstalled (5),
			auto(6)
		}
		MAX-ACCESS read-only
		STATUS  current
		DESCRIPTION
			"For 1U Carrier group1 is the front fan and group2 the rear fan
			For 4.5U Carrier: group 1 and 2 are PSU 1 and 2. group 3 is the
			front fan below the slots and group 4 the rear fans."
		::= { nmFanOverviewEntry 2 }

--**********************
--	nmCarrierFWUpdate(4)

	nmCarrierFWUpdate OBJECT IDENTIFIER ::= { nmCarrier 4 }

	nmCarrierFWUpdateFilename OBJECT-TYPE
		SYNTAX  DisplayString (SIZE(0..32))
		MAX-ACCESS  read-write
		STATUS  current
		DESCRIPTION
			"filename for copying to slots"
		::= { nmCarrierFWUpdate 1 }

	nmCarrierFirmwareTransferConfig OBJECT-TYPE
		SYNTAX INTEGER
		{
			notAvailable(0),
			idle(1),
			startTransfer(2),
			transferReady(3),
			transferActive(4),
			transferFailure(5),
			abortTransfer(6)
		}
		MAX-ACCESS  read-write
		STATUS  current
		DESCRIPTION
			"Control and status of upload procedure"
		::= { nmCarrierFWUpdate 2 }

	nmCarrierFWTransferProgress OBJECT-TYPE
		SYNTAX INTEGER
		MAX-ACCESS  read-only
		STATUS  current
		DESCRIPTION
			"copy progress in percent"
		::= { nmCarrierFWUpdate 3 }

	nmCarrierFWUpdateConfig OBJECT-TYPE
		SYNTAX INTEGER
		{
			notAvailable(0),
			idle(1),
			updateRunning(2),
			updateReady(3),
			copyToFlash(4),
			copyToFlashAndRestart(5),
			restartOnly(6),
			updateFailure(7)
		}
		MAX-ACCESS  read-write
		STATUS  current
		DESCRIPTION
			"copy and activates SW-images after next restart"
		::= { nmCarrierFWUpdate 4 }

--**********************

 	nmCarrierFWUpdatePolicyTable OBJECT-TYPE
		SYNTAX SEQUENCE OF NMCarrierFWUpdatePolicy
		MAX-ACCESS  not-accessible
		STATUS  current
		DESCRIPTION
			"update policy table"
		::= { nmCarrier 5 }

	nmCarrierFWUpdatePolicyEntry OBJECT-TYPE
		SYNTAX NMCarrierFWUpdatePolicy
		MAX-ACCESS  not-accessible
		STATUS  current
		DESCRIPTION
			"update policy"
		INDEX { nmCarrierFWUpdatePolicySlot }
		::= { nmCarrierFWUpdatePolicyTable 1 }

	NMCarrierFWUpdatePolicy ::= SEQUENCE
		{
			nmCarrierFWUpdatePolicySlot	INTEGER,
			nmCarrierFWUpdatePolicyCardName	DisplayString,
			nmCarrierFWUpdatePolicyConfig	INTEGER,
			nmCarrierFWUpdatePolicyTransferState	INTEGER
		}

	nmCarrierFWUpdatePolicySlot OBJECT-TYPE
		SYNTAX INTEGER (1..17)
		MAX-ACCESS  read-only
		STATUS  current
		DESCRIPTION
			"slot address"
		::= { nmCarrierFWUpdatePolicyEntry 1 }

	nmCarrierFWUpdatePolicyCardName OBJECT-TYPE
		SYNTAX DisplayString
		MAX-ACCESS  read-only
		STATUS  current
		DESCRIPTION
			"card name"
		::= { nmCarrierFWUpdatePolicyEntry 2 }

	nmCarrierFWUpdatePolicyConfig OBJECT-TYPE
		SYNTAX INTEGER
		{
			notAvailable(0),
			updatesEnabled(1),
			updatesDisabled(2),
			notApplicable(3)
		}
		MAX-ACCESS  read-write
		STATUS  current
		DESCRIPTION
			"enable or disable updates for this slot"
		::= { nmCarrierFWUpdatePolicyEntry 3 }

	nmCarrierFWUpdatePolicyTransferState OBJECT-TYPE
		SYNTAX INTEGER
		{
			notAvailable(0),
			idle(1),
			running(2),
			ready(3),
			fail(7)
		}
		MAX-ACCESS  read-only
		STATUS  current
		DESCRIPTION
			"file transfer state"
		::= { nmCarrierFWUpdatePolicyEntry 4 }

--**********************

	nmCarrierConfigTransferTable OBJECT-TYPE
		SYNTAX SEQUENCE OF NMCarrierFWConfigTransfer
		MAX-ACCESS  not-accessible
		STATUS  current
		DESCRIPTION
			"update policy table"
		::= { nmCarrier 6 }

	nmCarrierConfigTransferEntry OBJECT-TYPE
		SYNTAX NMCarrierFWConfigTransfer
		MAX-ACCESS  not-accessible
		STATUS  current
		DESCRIPTION
			"update policy"
		INDEX { nmCarrierConfigSlot }
		::= { nmCarrierConfigTransferTable 1 }

	NMCarrierFWConfigTransfer ::= SEQUENCE
		{
			nmCarrierConfigSlot INTEGER,
			nmCarrierConfigModuleName DisplayString,
			nmCarrierConfigTransferState INTEGER,
			nmCarrierConfigTransfer INTEGER,
			nmCarrierConfigFilename DisplayString,
			nmCarrierConfigActivation INTEGER
		}

	nmCarrierConfigSlot OBJECT-TYPE
		SYNTAX INTEGER (1..17)
		MAX-ACCESS read-only
		STATUS current
		DESCRIPTION
			"Module slot index"
		::= { nmCarrierConfigTransferEntry 1 }

	nmCarrierConfigModuleName OBJECT-TYPE
		SYNTAX DisplayString (SIZE (0..32))
		MAX-ACCESS  read-only
		STATUS  current
		DESCRIPTION
			"Module name"
		::= { nmCarrierConfigTransferEntry 2 }

	nmCarrierConfigTransferState OBJECT-TYPE
		SYNTAX INTEGER
		{
			notAvailable (0),
			upToDate (1),
			fileUpdateScheduled (2),
			updating (3),
			invalidConfigFile (4),
			error (5)
		}
		MAX-ACCESS read-only
		STATUS current
		DESCRIPTION
			"config state"
		::= { nmCarrierConfigTransferEntry 3 }

	nmCarrierConfigTransfer OBJECT-TYPE
		SYNTAX INTEGER
		{
			notAvailable (0),
			idle(1),
			pushToSlot(2),
			updateFromSlot(3),
			transferReady(4),
			transferRunning(5),
			transferERROR(6),
			abortTransfer(7)
		}
		MAX-ACCESS read-write
		STATUS current
		DESCRIPTION
			"config command for transfering files"
		::= { nmCarrierConfigTransferEntry 4 }

	nmCarrierConfigFilename OBJECT-TYPE
		SYNTAX DisplayString (SIZE (0..256))
		MAX-ACCESS  read-write
		STATUS  current
		DESCRIPTION
			"actual stored config file or filename to be send"
		::= { nmCarrierConfigTransferEntry 5 }

	nmCarrierConfigActivation OBJECT-TYPE
		SYNTAX INTEGER
		{
			notAvailable(0),
			idle(1),
			activating(2),
			ready(3),
			copyToFlash(4),
			copyToFlashAndRestart(5),
			restartOnly(6),
			failure(7)
		}
		MAX-ACCESS read-write
		STATUS current
		DESCRIPTION
			"config file activation at slot"
		::= { nmCarrierConfigTransferEntry 6 }


--*************************************************************
--	nmCarrierInventoryTable (7)

	nmCarrierInventoryTable OBJECT-TYPE
		SYNTAX SEQUENCE OF NMCarrierInventoryEntry
		MAX-ACCESS  not-accessible
		STATUS  current
		DESCRIPTION
			"Carrier inventory table"
		::= { nmCarrier 7  }

	nmCarrierInventoryEntry OBJECT-TYPE
		SYNTAX NMCarrierInventoryEntry
		MAX-ACCESS  not-accessible
		STATUS  current
		DESCRIPTION
			"Carrier inventory"
		INDEX { nmCarrierInventoryIndex }
		::= { nmCarrierInventoryTable 1 }

	NMCarrierInventoryEntry ::= SEQUENCE
		{
		nmCarrierInventoryIndex		INTEGER,
		nmCarrierInventorySlotNumber	INTEGER,
		nmCarrierInventoryPort		DisplayString,
		nmCarrierInventoryModuleName	DisplayString,
		nmCarrierInventoryPartNumber	DisplayString,
		nmCarrierInventorySerialNumber	DisplayString,
		nmCarrierInventoryFirmwareRelease	DisplayString,
		nmCarrierInventoryKernelLoader	DisplayString
		}

	nmCarrierInventoryIndex OBJECT-TYPE
		SYNTAX INTEGER (1..18000)
		MAX-ACCESS  read-only
		STATUS  current
		DESCRIPTION  "Inventory Index"
		::= { nmCarrierInventoryEntry 1 }

 	nmCarrierInventorySlotNumber OBJECT-TYPE
		SYNTAX INTEGER (1..17)
		MAX-ACCESS  read-only
		STATUS  current
		DESCRIPTION
			"Slot Number 1..17 for 4,xU Carrier or 1..4 for 1U Carrier"
		::= { nmCarrierInventoryEntry 2 }

	nmCarrierInventoryPort OBJECT-TYPE
		SYNTAX DisplayString (SIZE(0..32))
		MAX-ACCESS  read-only
		STATUS  current
		DESCRIPTION
			"port number in this slot"
		::= { nmCarrierInventoryEntry 3 }

	nmCarrierInventoryModuleName OBJECT-TYPE
		SYNTAX DisplayString (SIZE(0..32))
		MAX-ACCESS  read-only
		STATUS  current
		DESCRIPTION
			"name of the module"
		::= { nmCarrierInventoryEntry 4 }

	nmCarrierInventoryPartNumber OBJECT-TYPE
		SYNTAX DisplayString (SIZE(0..32))
		MAX-ACCESS  read-only
		STATUS  current
		DESCRIPTION
			"part number"
		::= { nmCarrierInventoryEntry 5 }

	nmCarrierInventorySerialNumber OBJECT-TYPE
		SYNTAX DisplayString (SIZE(0..32))
		MAX-ACCESS  read-only
		STATUS  current
		DESCRIPTION
			"serial number"
		::= { nmCarrierInventoryEntry 6 }

	nmCarrierInventoryFirmwareRelease OBJECT-TYPE
		SYNTAX DisplayString (SIZE(0..32))
		MAX-ACCESS  read-only
		STATUS  current
		DESCRIPTION
			"firmware release of the module"
		::= { nmCarrierInventoryEntry 7 }

	nmCarrierInventoryKernelLoader OBJECT-TYPE
		SYNTAX DisplayString (SIZE(0..32))
		MAX-ACCESS  read-only
		STATUS  current
		DESCRIPTION
			"Kernel/Loader version of the module"
		::= { nmCarrierInventoryEntry 8 }


--*******************************************************************
	converter		OBJECT IDENTIFIER ::= { nmSPEEDCARRIER 3 }
	multiplexer		OBJECT IDENTIFIER ::= { nmSPEEDCARRIER 4 }
	amplifier		OBJECT IDENTIFIER ::= { nmSPEEDCARRIER 5 }
	convSPEEDDUALLINE	OBJECT IDENTIFIER ::= { converter 1 }
--*******************************************************************

	convSxLModuleOverviewTable OBJECT-TYPE
		SYNTAX SEQUENCE OF ConvSxLModuleOverviewEntry
		MAX-ACCESS not-accessible
		STATUS current
		DESCRIPTION
				"SPEEDDUALLINE module overview table"
		::= { convSPEEDDUALLINE 1 }

	convSxLModuleOverviewEntry OBJECT-TYPE
		SYNTAX ConvSxLModuleOverviewEntry
		MAX-ACCESS not-accessible
		STATUS current
		DESCRIPTION
				"Module overview entries"
		INDEX { convSxLMSlot }
		::= { convSxLModuleOverviewTable 1 }

	ConvSxLModuleOverviewEntry ::=
		SEQUENCE
		{
			convSxLMSlot		INTEGER,
			convSxLMDevice		INTEGER,
			convSxLMStatus		INTEGER,
			convSxLMSysUpTime	TimeTicks,
			convSxLMTemp		INTEGER,
			convSxLMAlarmState	INTEGER,
			convSxLMBootSWVersion	DisplayString,
			convSxLMAppSWVersion	DisplayString,
			convSxLMHWVersion	DisplayString,
			convSxLMPLDVersion	DisplayString,
			convSxLMSerialNumber	DisplayString
		}

	convSxLMSlot OBJECT-TYPE
		SYNTAX INTEGER (1..17)
		MAX-ACCESS  read-only
		STATUS  current
		DESCRIPTION
				"Slot No. in Carrier"
		::= { convSxLModuleOverviewEntry 2 }

	convSxLMDevice OBJECT-TYPE
		SYNTAX INTEGER
		{
			devSPEEDSINGLELINE (0),
			devSPEEDDUALLINE (1),
			devSPEEDDUALLINE3R (2),
			devSPEEDPROTECT3R (3),
			devunknown (255)
		}
		MAX-ACCESS  read-only
		STATUS  current
		DESCRIPTION
			"Module DeviceType"
		::= { convSxLModuleOverviewEntry 3 }

	convSxLMStatus OBJECT-TYPE
		SYNTAX INTEGER
		{
			running (0),
			resetHardware (1),
			resetConfig (2),
			resetCAN (3),
			resetSoftware (4),
			unknown (255)
		}
		MAX-ACCESS  read-write
		STATUS  current
		DESCRIPTION
			"Status of inserted module. resetSoftware does not affect traffic"
		::= { convSxLModuleOverviewEntry 4 }

	convSxLMSysUpTime OBJECT-TYPE
		SYNTAX TimeTicks
		MAX-ACCESS  read-only
		STATUS  current
		DESCRIPTION
			"System uptime in seconds"
		::= { convSxLModuleOverviewEntry 5 }

	convSxLMTemp OBJECT-TYPE
		SYNTAX INTEGER
		MAX-ACCESS  read-only
		STATUS  current
		DESCRIPTION
			"Module temperature"
		::= { convSxLModuleOverviewEntry 6 }

	convSxLMAlarmState OBJECT-TYPE
		SYNTAX INTEGER
		{
			noAlarm (0),
			activeAlarms (1),
			unknown (255)
		}
		MAX-ACCESS  read-only
		STATUS  current
		DESCRIPTION
			"Module alarm states, if they are active see Event-Table"
		::= { convSxLModuleOverviewEntry 7 }

	convSxLMBootSWVersion OBJECT-TYPE
		SYNTAX DisplayString (SIZE (0..4))
		MAX-ACCESS  read-only
		STATUS  current
		DESCRIPTION
			"Module bootloader software version"
		::= { convSxLModuleOverviewEntry 8 }

	convSxLMAppSWVersion OBJECT-TYPE
		SYNTAX DisplayString (SIZE (0..4))
		MAX-ACCESS  read-only
		STATUS  current
		DESCRIPTION
			"Module application software Version"
		::= { convSxLModuleOverviewEntry 9 }

	convSxLMHWVersion OBJECT-TYPE
		SYNTAX DisplayString (SIZE (0..4))
		MAX-ACCESS  read-only
		STATUS  current
		DESCRIPTION
			"Module board hardware version"
		::= { convSxLModuleOverviewEntry 10 }

	convSxLMPLDVersion OBJECT-TYPE
		SYNTAX DisplayString (SIZE (0..4))
		MAX-ACCESS  read-only
		STATUS  current
		DESCRIPTION
			"Module firmware version"
		::= { convSxLModuleOverviewEntry 11 }

	convSxLMSerialNumber OBJECT-TYPE
		SYNTAX DisplayString (SIZE (0..17))
		MAX-ACCESS  read-only
		STATUS  current
		DESCRIPTION
			"Modules serial number"
		::= { convSxLModuleOverviewEntry 12 }

--************************Table**************************************
	convSxLSWImagesOverviewTable OBJECT-TYPE
		SYNTAX SEQUENCE OF ConvSxLSWImagesOverviewEntry
		MAX-ACCESS not-accessible
		STATUS current
		DESCRIPTION
			"SPEEDDUALLINE software images Overview Table"
		::= { convSPEEDDUALLINE 2 }

	convSxLSWImagesOverviewEntry OBJECT-TYPE
		SYNTAX ConvSxLSWImagesOverviewEntry
		MAX-ACCESS not-accessible
		STATUS current
		DESCRIPTION
			"Module overview entries"
		INDEX { convSxLSWSlot }
		::= { convSxLSWImagesOverviewTable 1 }

	ConvSxLSWImagesOverviewEntry ::=
		SEQUENCE
		{
			convSxLSWSlot		INTEGER,
			convSxLSWBootImage	DisplayString,
			convSxLSWAppImage1	DisplayString,
			convSxLSWAppImage2	DisplayString,
			convSxLSWUploadStatus	INTEGER,
			convSxLSWUpdateStatus	INTEGER
		}

	convSxLSWSlot OBJECT-TYPE
		SYNTAX INTEGER (1..17)
		MAX-ACCESS  read-only
		STATUS  current
		DESCRIPTION
			"Slot No. in Carrier"
		::= { convSxLSWImagesOverviewEntry 2 }

	convSxLSWBootImage OBJECT-TYPE
		SYNTAX DisplayString (SIZE (0..36))
		MAX-ACCESS  read-only
		STATUS  current
		DESCRIPTION
			"Identification of bootimage"
		::= { convSxLSWImagesOverviewEntry 3 }

	convSxLSWAppImage1 OBJECT-TYPE
		SYNTAX DisplayString (SIZE (0..36))
		MAX-ACCESS  read-only
		STATUS  current
		DESCRIPTION
			"Identification of application image1"
		::= { convSxLSWImagesOverviewEntry 4 }

	convSxLSWAppImage2 OBJECT-TYPE
		SYNTAX DisplayString (SIZE (0..36))
		MAX-ACCESS  read-only
		STATUS  current
		DESCRIPTION
			"Identification of application image2"
		::= { convSxLSWImagesOverviewEntry 5 }

	convSxLSWUploadStatus OBJECT-TYPE
		SYNTAX INTEGER
		{
			ready (0),
			startUpload (1),
			uploadActive (2),
			uploadFailure (255)
		}
		MAX-ACCESS  read-only
		STATUS  current
		DESCRIPTION
			"Control and status of upload procedure"
		::= { convSxLSWImagesOverviewEntry 6 }

	convSxLSWUpdateStatus OBJECT-TYPE
		SYNTAX INTEGER
		{
			idle (0),
			activateImage1 (1),
			activateImage2 (2),
			invalidImages (3)
		}
		MAX-ACCESS  read-only
		STATUS  current
		DESCRIPTION
			"activates SW-image after next reset"
		::= { convSxLSWImagesOverviewEntry 7 }

--************************Table**************************************
	convSxLModuleConfigTable OBJECT-TYPE
		SYNTAX SEQUENCE OF ConvSxLModuleConfigEntry
		MAX-ACCESS not-accessible
		STATUS current
		DESCRIPTION
			"SPEEDDUALLINE config table"
		::= { convSPEEDDUALLINE 3 }

	convSxLModuleConfigEntry OBJECT-TYPE
		SYNTAX ConvSxLModuleConfigEntry
		MAX-ACCESS not-accessible
		STATUS current
		DESCRIPTION
			"Module config entries"
		INDEX { convSxLMSlot  }
		::= { convSxLModuleConfigTable 1 }

	ConvSxLModuleConfigEntry ::=
		SEQUENCE
		{
			convSxLMSlot INTEGER,
			convSxLMIpAddress IpAddress,
			convSxLMIpNetmask IpAddress,
			convSxLMIpGateway IpAddress,
			convSxLMIpTftpServer IpAddress,
			convSxLMIpTrapSink IpAddress,
			convSxLMSNMPReadCommunity DisplayString,
			convSxLMSNMPWriteCommunity DisplayString,
			convSxLMTempWarningLevel INTEGER,
			convSxLMTempAlarmLevel INTEGER,
			convSxLMAlarmReport INTEGER,
			convSxLMEthPortConfig INTEGER,
			convSxLMEthPortState INTEGER,
			convSxLMCliUserTimeout INTEGER
		}

	convSxLMIpAddress OBJECT-TYPE
		SYNTAX	IpAddress
		MAX-ACCESS	read-only
		STATUS	current
		DESCRIPTION
			"Module IP address"
		::= { convSxLModuleConfigEntry 3 }

	convSxLMIpNetmask OBJECT-TYPE
		SYNTAX	IpAddress
		MAX-ACCESS	read-only
		STATUS	current
		DESCRIPTION
			"Module netmask"
		::= { convSxLModuleConfigEntry 4 }

	convSxLMIpGateway OBJECT-TYPE
		SYNTAX	IpAddress
		MAX-ACCESS	read-only
		STATUS	current
		DESCRIPTION
			"Default gateway"
		::= { convSxLModuleConfigEntry 5 }

	convSxLMIpTftpServer OBJECT-TYPE
		SYNTAX	IpAddress
		MAX-ACCESS	read-only
		STATUS	current
		DESCRIPTION
			"TFTP server address for SW-Update"
		::= { convSxLModuleConfigEntry 6 }

	convSxLMIpTrapSink OBJECT-TYPE
		SYNTAX	IpAddress
		MAX-ACCESS	read-only
		STATUS	current
		DESCRIPTION
			"SNMP TrapSink-address"
		::= { convSxLModuleConfigEntry 7 }

	convSxLMSNMPReadCommunity OBJECT-TYPE
		SYNTAX	DisplayString  (SIZE (0..17))
		MAX-ACCESS	read-only
		STATUS	current
		DESCRIPTION
			"SNMP ReadCommunity"
		::= { convSxLModuleConfigEntry 8 }

	convSxLMSNMPWriteCommunity OBJECT-TYPE
		SYNTAX	DisplayString   (SIZE (0..17))
		MAX-ACCESS	read-only
		STATUS	current
		DESCRIPTION
			"SNMP WriteCommunity"
		::= { convSxLModuleConfigEntry 9 }

	convSxLMTempWarningLevel OBJECT-TYPE
		SYNTAX	INTEGER(0..60)
		MAX-ACCESS	read-write
		STATUS	current
		DESCRIPTION
			"Warning level for module ambient temperature (0 - 60 degree Celsius)"
		::= { convSxLModuleConfigEntry 10 }

	convSxLMTempAlarmLevel OBJECT-TYPE
		SYNTAX	INTEGER
		MAX-ACCESS	read-only
		STATUS	current
		DESCRIPTION
			"Alarm level for module ambient temperature"
		::= { convSxLModuleConfigEntry 11 }

	convSxLMAlarmReport OBJECT-TYPE
		SYNTAX	INTEGER
		{
			disable (0),
			toNMA   (1),
			toETH   (2),
			toNMAandETH (3),
			notavailable (255)
		}
		MAX-ACCESS read-only
		STATUS current
		DESCRIPTION
			"Controls alarm signaling modes of module"
		::= { convSxLModuleConfigEntry 12 }

	convSxLMEthPortConfig OBJECT-TYPE
		SYNTAX	INTEGER
		{
			unknown (0),
			portDown (1),
			portUp (2),
			notavailable (255)
		}
		MAX-ACCESS read-write
		STATUS current
		DESCRIPTION
			"Module Ethernet Port config"
		::= { convSxLModuleConfigEntry 13 }

	convSxLMEthPortState OBJECT-TYPE
		SYNTAX	INTEGER
		{
			unknown (0),
			portDown (1),
			portUp (2),
			notavailable (255)
		}
		MAX-ACCESS read-only
		STATUS current
		DESCRIPTION
			"Module Ethernet Port state"
		::= { convSxLModuleConfigEntry 14 }

	convSxLMCliUserTimeout OBJECT-TYPE
		SYNTAX INTEGER(120..3600)
		MAX-ACCESS read-write
		STATUS current
		DESCRIPTION
			"Module CLI User Timeout"
		::= { convSxLModuleConfigEntry 15 }

--************************Table**************************************
	convSxLModuleProtectionTable OBJECT-TYPE
		SYNTAX SEQUENCE OF ConvSxLModuleProtectionEntry
		MAX-ACCESS not-accessible
		STATUS current
		DESCRIPTION
			"SPEEDDUALLINE protection table"
		::= { convSPEEDDUALLINE 4 }

	convSxLModuleProtectionEntry OBJECT-TYPE
		SYNTAX ConvSxLModuleProtectionEntry
		MAX-ACCESS not-accessible
		STATUS current
		DESCRIPTION
			"Protection table entries"
		INDEX { convSxLMSlot  }
		::= { convSxLModuleProtectionTable 1 }

	ConvSxLModuleProtectionEntry ::=
		SEQUENCE
		{
			convSxLMSlot INTEGER,
			convSxLMLinkProtectionConfig INTEGER,
			convSxLMLinkProtectionStatus INTEGER,
			convSxLMLinkProtectionFallback INTEGER
		}

	convSxLMLinkProtectionConfig OBJECT-TYPE
		SYNTAX INTEGER
		{
			unknown(0),
			fallbackPort1(1),
			fallbackPort2(2),
			staticPort1(3),
			staticPort2(4),
			protectionOFF(5),
			notAvailable(255)
		}
		MAX-ACCESS  read-write
		STATUS  current
		DESCRIPTION
			"Status of protection module"
		::= { convSxLModuleProtectionEntry 3 }

	convSxLMLinkProtectionStatus OBJECT-TYPE
		SYNTAX INTEGER
		{
			unknown(0),
			port1active(1),
			port2active(2),
			testing(3),
			noneActive(4),
			notAvailable(255)
		}
		MAX-ACCESS  read-only
		STATUS  current
		DESCRIPTION
			"Status of protection functionality regarding the link port. The link port are always port1 (main) and port2 (backup). The local port is port4"
		::= { convSxLModuleProtectionEntry 4 }

	convSxLMLinkProtectionFallback OBJECT-TYPE
		SYNTAX INTEGER(5..65535)
		MAX-ACCESS  read-write
		STATUS  current
		DESCRIPTION
			"Fallback time of errorfree seconds before switching back to MainPath. If there is an error during the Fallback-Time the timer will be restarted again"
		::= { convSxLModuleProtectionEntry 5 }

--************************Table**************************************
	convSxLPortOverviewTable OBJECT-TYPE
		SYNTAX SEQUENCE OF ConvSxLPortOverviewEntry
		MAX-ACCESS not-accessible
		STATUS current
		DESCRIPTION
			"Port status table"
		::= { convSPEEDDUALLINE 5 }

	convSxLPortOverviewEntry OBJECT-TYPE
		SYNTAX ConvSxLPortOverviewEntry
		MAX-ACCESS not-accessible
		STATUS current
		DESCRIPTION
			"Port status entries"
		INDEX { convSxLPortIndex }
		::= { convSxLPortOverviewTable 1 }

	ConvSxLPortOverviewEntry ::=
		SEQUENCE
		{
			convSxLPortIndex INTEGER,
			convSxLSlot INTEGER,
			convSxLPort INTEGER,
			convSxLDescription DisplayString,
			convSxLAdminState INTEGER,
			convSxLOperState INTEGER,
			convSxLAlarmState INTEGER,
			convSxLSFPState INTEGER,
			convSxLLLCFState INTEGER,
			convSxLLoopState INTEGER,
			convSxLSpeed INTEGER,
			convSxLTxPortConnection INTEGER,
			convSxLDMIState INTEGER
		}

	convSxLPortIndex OBJECT-TYPE
		SYNTAX INTEGER (1..1800)
		MAX-ACCESS  read-only
		STATUS  current
		DESCRIPTION
			"Port Index"
		::= { convSxLPortOverviewEntry 1 }

	convSxLSlot OBJECT-TYPE
		SYNTAX INTEGER (1..17)
		MAX-ACCESS  read-only
		STATUS  current
		DESCRIPTION
			"Slot number"
		::= { convSxLPortOverviewEntry 2 }

	convSxLPort OBJECT-TYPE
		SYNTAX INTEGER
		MAX-ACCESS  read-only
		STATUS  current
		DESCRIPTION
			"Port number"
		::= { convSxLPortOverviewEntry 3 }

	convSxLDescription OBJECT-TYPE
		SYNTAX DisplayString (SIZE (0..31))
		MAX-ACCESS  read-write
		STATUS  current
		DESCRIPTION
			"Port desription string"
		::= { convSxLPortOverviewEntry 4 }

	convSxLAdminState OBJECT-TYPE
		SYNTAX INTEGER
		{
			adminDown (0),
			adminUp (1),
			notAvailable (255)
		}
		MAX-ACCESS  read-only
		STATUS  current
		DESCRIPTION
			"Port configuration mode"
		::= { convSxLPortOverviewEntry 5 }

	convSxLOperState OBJECT-TYPE
		SYNTAX INTEGER
		{
			down(0),
			up(1),
			loop(2),
			downLLCF(3),
			downTxFault(4),
			downRxLevel(5),
			downTxLevel(6),
		        notAvailable(255)
		}
		MAX-ACCESS  read-only
		STATUS  current
		DESCRIPTION
			"Port operational state"
		::= { convSxLPortOverviewEntry 6 }

	convSxLSFPState OBJECT-TYPE
		SYNTAX INTEGER
		{
			sfpRemoved (0),
			sfpInstalled (1),
			sfpTxFault (2),
			notAvailable (255)
		}
		MAX-ACCESS  read-only
		STATUS  current
		DESCRIPTION
			"SFP-Port state"
		::= { convSxLPortOverviewEntry 7 }

	convSxLLLCFState OBJECT-TYPE
		SYNTAX INTEGER
		{
			off (0),
			on (1),
			notAvailable (255)
		}
		MAX-ACCESS  read-only
		STATUS  current
		DESCRIPTION
			"Status of linkloss configuration"
		::= { convSxLPortOverviewEntry 8 }

	convSxLLoopState OBJECT-TYPE
		SYNTAX INTEGER
		{
			off (0),
			on (1),
			notAvailable (255)
		}
		MAX-ACCESS  read-only
		STATUS  current
		DESCRIPTION
			"Status of loop configuration"
		::= { convSxLPortOverviewEntry 9 }

	convSxLSpeed OBJECT-TYPE
		SYNTAX INTEGER
		{
			speedTransparent (0),
			speedSTM1-155Mbit (1),
			speedSTM4-622Mbit (2),
			speedSTM16-2488Mbit (3),
			sSTM16FEC2666Mbit (4),
			sFastEthernet125Mbit (5),
			sGigabitEthernet1250Mbit (6),
			sFibreChannel133Mbit (7),
			sFibreChannel266Mbit (8),
			sFibreChannel531Mbit (9),
			sFibreChannel1062Mbit (10),
			sFibreChannel2125Mbit (11),
			sESCON200Mbit (12),
			notAvailable (255)
		}
		MAX-ACCESS  read-only
		STATUS  current
		DESCRIPTION
			"TxPort 3R regeneration speed and protocol"
		::= { convSxLPortOverviewEntry 10 }

	convSxLTxPortConnection OBJECT-TYPE
		SYNTAX INTEGER
		{
			notConnected (0),
			toPort1 (1),
			toPort2 (2),
			toPort3 (3),
			toPort4 (4),
			notAvailable (255)
		}
		MAX-ACCESS  read-only
		STATUS  current
		DESCRIPTION
			"Status of port to port connection"
		::= { convSxLPortOverviewEntry 11 }

	convSxLAlarmState OBJECT-TYPE
		SYNTAX INTEGER
		{
			noAlarm (0),
			alarmLOS (1),
			alarmCDR (2),
			alarmTxFault (3),
			alarmRxLevel (4),
			warningRxLevel (5),
			warningTxLevel (6),
			activeAlarms (16),
			activeWarnigs (32),
			notAvailable (255)
		}
		MAX-ACCESS  read-only
		STATUS  current
		DESCRIPTION
			"Port warning / alarm states"
		::= { convSxLPortOverviewEntry 12 }

	convSxLDMIState OBJECT-TYPE
		SYNTAX INTEGER
		{
			notAvailable (0),
			sff-8472Rev9-3 (1),
			sff-8472Rev9-4 (2)
		}
		MAX-ACCESS  read-only
		STATUS  current
		DESCRIPTION
			"Availability or version of Diagnostic Monitoring Information (DMI)"
		::= { convSxLPortOverviewEntry 13 }

--************************Table**************************************
	convSxLPortConfigTable OBJECT-TYPE
		SYNTAX SEQUENCE OF ConvSxLPortConfigEntry
		MAX-ACCESS not-accessible
		STATUS current
		DESCRIPTION
			"Port config table"
		::= { convSPEEDDUALLINE 6 }

	convSxLPortConfigEntry OBJECT-TYPE
		SYNTAX ConvSxLPortConfigEntry
		MAX-ACCESS not-accessible
		STATUS current
		DESCRIPTION
			"Port config entry"
		INDEX { convSxLPortIndex }
		::= { convSxLPortConfigTable 1 }

	ConvSxLPortConfigEntry ::=
		SEQUENCE
		{
			convSxLPortIndex INTEGER,
			convSxLSlot INTEGER,
			convSxLPort INTEGER,
			convSxLAdminConfig INTEGER,
			convSxLLLCFConfig INTEGER,
			convSxLLoopConfig INTEGER,
			convSxLSpeedConfig INTEGER,
			convSxLPortConnection INTEGER,
			convSxLPortAlarmDeactivation INTEGER,
			convSxLPortAlarmSchedule  INTEGER
		}

	convSxLAdminConfig OBJECT-TYPE
		SYNTAX INTEGER
		{
			adminDown (0),
			adminUp (1),
			notAvailable (255)
		}
		MAX-ACCESS  read-write
		STATUS  current
		DESCRIPTION
			"Admin configuration of a specific port"
		::= { convSxLPortConfigEntry 4 }

	convSxLLLCFConfig OBJECT-TYPE
		SYNTAX INTEGER
		{
			off (0),
			on (1),
			notAvailable (255)
		}
		MAX-ACCESS  read-write
		STATUS  current
		DESCRIPTION
			"Configuration of Link Loss Carry Forward (LLCF) function. If a link down event occurs on the link port the local port will be disabled to signal the error state to the locally connected device e.g. router"
		::= { convSxLPortConfigEntry 5 }

	convSxLLoopConfig OBJECT-TYPE
		SYNTAX INTEGER
		{
			off (0),
			on (1),
			notAvailable (255)
		}
		MAX-ACCESS  read-write
		STATUS  current
		DESCRIPTION
			"Setup of loops. After a reset, all loops will be switched off"
		::= { convSxLPortConfigEntry 6 }

	convSxLSpeedConfig OBJECT-TYPE
		SYNTAX INTEGER
		{
			speedTransparent (0),
			speedSTM1-155Mbit (1),
			speedSTM4-622Mbit (2),
			speedSTM16-2488Mbit (3),
			sSTM16FEC2666Mbit (4),
			sFastEthernet125Mbit (5),
			sGigabitEthernet1250Mbit (6),
			sFibreChannel133Mbit (7),
			sFibreChannel266Mbit (8),
			sFibreChannel531Mbit (9),
			sFibreChannel1062Mbit (10),
			sFibreChannel2125Mbit (11),
			sESCON200Mbit (12),
			sVIDEO143Mbit (13),
			sVIDEO177Mbit (14),
			sVIDEO270Mbit (15),
			sVIDEO360Mbit (16),
			sVIDEO540Mbit (17),
			sVIDEO1001Mbit (18),
			sVIDEO1485Mbit (19),
			sVIDEO2970Mbit (20),
			notAvailable (255)
		}
		MAX-ACCESS  read-write
		STATUS  current
		DESCRIPTION
			"TxPort 3R regeneration speed and protocol"
		::= { convSxLPortConfigEntry 7 }

	convSxLPortConnection OBJECT-TYPE
		SYNTAX INTEGER
		{
			noConnection (0),
			fromPort1 (1),
			fromPort2 (2),
			fromPort3 (3),
			fromPort4 (4),
			notPossible (255)
		}
		MAX-ACCESS  read-write
		STATUS  current
		DESCRIPTION
			"Setup of connections. toPortx means a connection between Rx-input to Tx-output"
		::= { convSxLPortConfigEntry 8 }

	convSxLPortAlarmDeactivation OBJECT-TYPE
		SYNTAX INTEGER
		{
			notAvailable(0),
			alarmReportingEnabled(1),
			alarmReportingDisabledbySchedule(2),
			alarmReportingDisabledPermanent(3),
			unknown(255)
		}
		MAX-ACCESS  read-write
		STATUS  current
		DESCRIPTION
			"Port alarm deactivation schedule"
		::= { convSxLPortConfigEntry 9 }

	convSxLPortAlarmSchedule OBJECT-TYPE
		SYNTAX INTEGER (0..1200)
		MAX-ACCESS  read-write
		STATUS  current
		DESCRIPTION
			"Port alarm deactivation schedule. Value in hours. After this time has elapsed, the alarms are active again. Valid range: 1..1200. 0 means less then 1 hour"
		::= { convSxLPortConfigEntry 10 }

--*******************************************************************
	convSxSFPIdentifikation    OBJECT IDENTIFIER ::= { convSPEEDDUALLINE 7 }
--************************Table**************************************
	convSXLSFPDescriptionTable  OBJECT-TYPE
		SYNTAX SEQUENCE OF ConvSXLSFPDescriptionEntry
		MAX-ACCESS not-accessible
		STATUS current
		DESCRIPTION
			"Optical transceiver parameter table"
		::= { convSxSFPIdentifikation 1 }

	convSXLSFPDescriptionEntry OBJECT-TYPE
		SYNTAX ConvSXLSFPDescriptionEntry
		MAX-ACCESS not-accessible
		STATUS current
		DESCRIPTION
			"Talbe entries"
		INDEX { convSxLPortIndex }
		::= { convSXLSFPDescriptionTable 1 }

	ConvSXLSFPDescriptionEntry ::=
		SEQUENCE
		{
			convSxLPortIndex INTEGER,
			convSxLSlot INTEGER,
			convSxLPort INTEGER,
			convSxLSFPVendor DisplayString,
			convSxLSFPVendorOUI DisplayString,
			convSxLSFPVendorCode DisplayString,
			convSxLSFPVendorRevisionCode DisplayString,
			convSxLSFPVendorDateCode DisplayString,
			convSxLSFPVendorSerialNumber DisplayString,
			convSxLSFPType INTEGER,
			convSxLSFPConnector INTEGER,
			convSxLSFPWavelength DisplayString
		}

	convSxLSFPVendor OBJECT-TYPE
		SYNTAX DisplayString (SIZE (0..255))
		MAX-ACCESS  read-only
		STATUS  current
		DESCRIPTION
			"SFP vendor name"
		::= { convSXLSFPDescriptionEntry 4 }

	convSxLSFPVendorOUI OBJECT-TYPE
		SYNTAX DisplayString (SIZE (0..3))
		MAX-ACCESS  read-only
		STATUS  current
		DESCRIPTION
				"Vendor specific IEEE-OUI"
		::= { convSXLSFPDescriptionEntry 5 }

	convSxLSFPVendorCode OBJECT-TYPE
		SYNTAX DisplayString (SIZE (0..17))
		MAX-ACCESS  read-only
		STATUS  current
		DESCRIPTION
			"Part identification code, vendor specific"
		::= { convSXLSFPDescriptionEntry 6 }

	convSxLSFPVendorRevisionCode OBJECT-TYPE
		SYNTAX DisplayString (SIZE (0..5))
		MAX-ACCESS  read-only
		STATUS  current
		DESCRIPTION
			"Parts revision code, vendor specific"
		::= { convSXLSFPDescriptionEntry 7 }

	convSxLSFPVendorDateCode OBJECT-TYPE
		SYNTAX DisplayString (SIZE (0..9))
		MAX-ACCESS  read-only
		STATUS  current
		DESCRIPTION
			"The vendor date code for the transceiver. The date code is specified in the following format: YYYY.MM.DD/LL;   YYYY = year;   MM = month;   DD = day of month;   LL   = vendor lot code"
		::= { convSXLSFPDescriptionEntry 8 }

	convSxLSFPVendorSerialNumber OBJECT-TYPE
		SYNTAX DisplayString (SIZE (0..17))
		MAX-ACCESS  read-only
		STATUS  current
		DESCRIPTION
			"Parts serial number "
		::= { convSXLSFPDescriptionEntry 9 }

	convSxLSFPType OBJECT-TYPE
		SYNTAX INTEGER
		{
			unspecified (0),
			tGBIC       (1),
			tModuleSolderedToMotherboard (2),
			tSFPTransceiver (3),
			tDWDMSFPTransceiver (11),
			tCopperSFPTransceiver(254),
			vendorSpecific (255)
		}
		MAX-ACCESS  read-only
		STATUS  current
		DESCRIPTION
			"Physical type of device"
		::= { convSXLSFPDescriptionEntry 10 }

	convSxLSFPConnector OBJECT-TYPE
		SYNTAX INTEGER
		{
			unspecified (0),
			cSC (1),
			cFibreChannelStyle1CopperConnector (2),
			cFibreChannelStyle2CopperConnector (3),
			cBncTnc (4),
			cFibreChannerCoaxialHeader (5),
			cFibreJack (6),
			cLC (7),
			cMTRJ (8),
			cMU (9),
			cSG (10),
			cOpticalPigtail(11),
			cHSSDCII (32),
			cCopperPigtail (33),
			cRJ45 (34),
			unknown(255)
		}
		MAX-ACCESS  read-only
		STATUS  current
		DESCRIPTION
			"The connector value indicates the external connector provided on the interface."
		::= { convSXLSFPDescriptionEntry 11 }

	convSxLSFPWavelength OBJECT-TYPE
		SYNTAX DisplayString (SIZE (0..8))
		MAX-ACCESS  read-only
		STATUS  current
		DESCRIPTION
			"The laser wavelength is the nominal transmitter output wavelength at room temperature. The value is in nanometers [nm]. This field allows the user to read the laser wavelength directly, so it is not necessary to infer it from the transceiver 'Code for Electronic Compatibility'."
		::= { convSXLSFPDescriptionEntry 12 }

--************************Table**************************************
	convSxLSFPBitrateTable  OBJECT-TYPE
		SYNTAX SEQUENCE OF ConvSxLSFPBitrateEntry
		MAX-ACCESS not-accessible
		STATUS current
		DESCRIPTION
			"Optical transceiver bitrate table"
		::= { convSxSFPIdentifikation 2 }

	convSxLSFPBitrateEntry OBJECT-TYPE
		SYNTAX ConvSxLSFPBitrateEntry
		MAX-ACCESS not-accessible
		STATUS current
		DESCRIPTION
			"Transceiver bitrate"
		INDEX { convSxLPortIndex }
		::= { convSxLSFPBitrateTable 1 }

	ConvSxLSFPBitrateEntry ::=
		SEQUENCE
		{
			convSxLPortIndex INTEGER,
			convSxLSlot INTEGER,
			convSxLPort INTEGER,
			convSxLSFPBitrateNominal INTEGER,
			convSxLSFPBitrateMax INTEGER,
			convSxLSFPBitrateMin INTEGER
		}

	convSxLSFPBitrateNominal OBJECT-TYPE
		SYNTAX INTEGER
		{
			notAvailable (255)
		}
		MAX-ACCESS  read-only
		STATUS  current
		DESCRIPTION
			"The nominal bit rate is specified in units of 1 Megabit per second, rounded up to the next 100 Megabits per second. The bit rate includes those bits necessary to encode and delimit the signal as well as those bits carrying data information. A value of 0 indicates that the bit rate is not specified and must be determined from the transceiver technology. The actual information transfer rate will depend on the data encoding defined by the encoding value."
		::= { convSxLSFPBitrateEntry 4 }

	convSxLSFPBitrateMax OBJECT-TYPE
		SYNTAX INTEGER
		{
			notAvailable (255)
		}
		MAX-ACCESS  read-only
		STATUS  current
		DESCRIPTION
			"The upper bit rate limit at which the SFP transceiver will still meet its specifications is specified in units of 1 Megabit per second. A value of 0 indicates that this field is not specified."
		::= { convSxLSFPBitrateEntry 5 }

	convSxLSFPBitrateMin OBJECT-TYPE
		SYNTAX INTEGER
		{
			notAvailable (255)
		}
		MAX-ACCESS  read-only
		STATUS  current
		DESCRIPTION
			"The lower bit rate limit at which the SFP transceiver will still meet its specifications is specified in units of 1 Megabit per second. A value of 0 indicates that this field is not specified."
		::= { convSxLSFPBitrateEntry 6 }

--************************Table**************************************
	convSxLSFPLengthTable  OBJECT-TYPE
		SYNTAX SEQUENCE OF ConvSxLSFPLengthEntry
		MAX-ACCESS not-accessible
		STATUS current
		DESCRIPTION
			"Optical Transceiver Length Table"
		::= { convSxSFPIdentifikation 3 }

	convSxLSFPLengthEntry OBJECT-TYPE
		SYNTAX ConvSxLSFPLengthEntry
		MAX-ACCESS not-accessible
		STATUS current
		DESCRIPTION
			"Optical Transceiver Length Coding Entries"
		INDEX { convSxLPortIndex }
		::= { convSxLSFPLengthTable 1 }

	ConvSxLSFPLengthEntry ::=
		SEQUENCE
		{
			convSxLPortIndex INTEGER,
			convSxLSlot INTEGER,
			convSxLPort INTEGER,
			convSxLSFPLength9km INTEGER,
			convSxLSFPLength9m INTEGER,
			convSxLSFPLength50 INTEGER,
			convSxLSFPLength62 INTEGER,
			convSxLSFPLengthCopper INTEGER
		}

	convSxLSFPLength9km OBJECT-TYPE
		SYNTAX INTEGER
		{
			grater254km(255)
		}
		MAX-ACCESS  read-only
		STATUS  current
		DESCRIPTION
			"This value specifies the link length that is supported by the SFP transceiver while operating in compliance with the applicable standards using single mode fiber. The value is in units of kilometers. A value of 255 means that the transceiver supports a link greater than 254 km. A value of 0 means that the transceiver does not support single mode fiber or that the length information must be determined from the transceiver technology."
		::= { convSxLSFPLengthEntry 4 }

	convSxLSFPLength9m OBJECT-TYPE
		SYNTAX INTEGER
		{
			greater25km(255)
		}
		MAX-ACCESS  read-only
		STATUS  current
		DESCRIPTION
			"This value specifies the link length that is supported by the SFP transceiver while operating in compliance with the applicable standards using single mode fiber. The value is in units of 100 meters. A value of 255 means that the transceiver supports a link greater than 25.4 km. A value of 0 means that the transceiver does not support single mode fiber or that the length information must be determined from the transceiver technology."
		::= { convSxLSFPLengthEntry 5 }

	convSxLSFPLength50 OBJECT-TYPE
		SYNTAX INTEGER
		{
			greater2540m(255)
		}
		MAX-ACCESS  read-only
		STATUS  current
		DESCRIPTION
			"This value specifies the link length that is supported by the SFP transceiver while operating in compliance with the applicable standards using 50 micron multi mode fiber. The value is in units of 10 meters. A value of 255 means that the transceiver supports a link greater than 2.54 km. A value of 0 means that the transceiver does not support 50 micron multi mode fiber or that the length information must be determined from the transceiver technology."
		::= { convSxLSFPLengthEntry 6 }

	convSxLSFPLength62 OBJECT-TYPE
		SYNTAX INTEGER
		{
			greater2540m(255)
		}
		MAX-ACCESS  read-only
		STATUS  current
		DESCRIPTION
			"This value specifies the link length that is supported	by the SFP transceiver while operating in compliance with the applicable standards using 62.5 micron multi mode fiber. The value is in units of 10 meters. A value of 255 means that the transceiver supports a link greater than 2.54 km. A value of 0 means that the transceiver does not support 62.5 micron multi mode fiber or that the length information must be determined from the transceiver technology."
		::= { convSxLSFPLengthEntry 7 }

	convSxLSFPLengthCopper OBJECT-TYPE
		SYNTAX INTEGER
		{
			greater254m(255)
		}
		MAX-ACCESS  read-only
		STATUS  current
		DESCRIPTION
			"This value specifies the link length that is supported by the SFP transceiver while operating in compliance with the applicable standards using copper cable. The value is in units of 1 meter. A value of 255 means that the transceiver supports a link greater than 254 m. A value of 0 means that the transceiver does not support copper cable or that the length information must be determined from the transceiver technology. Further information about the cable design, equalization, and connectors is usually required to guarantee meeting of particular length information."
		::= { convSxLSFPLengthEntry 8 }

--************************Table**************************************
       convSxLSFPCompCodes    OBJECT IDENTIFIER ::= { convSxSFPIdentifikation 4 }

--************************Table**************************************
	convSxLSFPCompCodeSonetTable  OBJECT-TYPE
		SYNTAX SEQUENCE OF ConvSxLSFPCompCodeSonetEntry
		MAX-ACCESS not-accessible
		STATUS current
		DESCRIPTION
			"Optical transceiver sonet compatibility table"
		::= { convSxLSFPCompCodes 1 }

	convSxLSFPCompCodeSonetEntry OBJECT-TYPE
		SYNTAX ConvSxLSFPCompCodeSonetEntry
		MAX-ACCESS not-accessible
		STATUS current
		DESCRIPTION
			"Transceiver compatibility code entries"
		INDEX { convSxLPortIndex }
		::= { convSxLSFPCompCodeSonetTable 1 }

	ConvSxLSFPCompCodeSonetEntry ::=
		SEQUENCE
		{
			convSxLPortIndex INTEGER,
			convSxLSlot INTEGER,
			convSxLPort INTEGER,
			convSxLSFPCSProtocol INTEGER,
			convSxLSFPCSRange INTEGER,
			convSxLSFPCSFiberType INTEGER
		}

	convSxLSFPCSProtocol OBJECT-TYPE
		SYNTAX INTEGER
		{
			notSupported (0),
			sOC3 (1),
			sOC12 (2),
			sOC48 (3)
		}
		MAX-ACCESS  read-only
		STATUS  current
		DESCRIPTION
			"Supported protocol"
		::= { convSxLSFPCompCodeSonetEntry 4 }

	convSxLSFPCSRange OBJECT-TYPE
		SYNTAX INTEGER
		{
			notSupported (0),
			short         (1),
			intermediate  (2),
			long          (3)
		}
		MAX-ACCESS  read-only
		STATUS  current
		DESCRIPTION
			"Optical transceivers range"
		::= { convSxLSFPCompCodeSonetEntry 5 }

	convSxLSFPCSFiberType OBJECT-TYPE
		SYNTAX INTEGER
		{
			notSupported (0),
			multimode     (1),
			singlemode    (4)
		}
		MAX-ACCESS  read-only
		STATUS  current
		DESCRIPTION
			"Supported fiber type"
		::= { convSxLSFPCompCodeSonetEntry 6 }

--************************Table**************************************
	convSxLSFPCompCodeGigabitEthernetTable  OBJECT-TYPE
		SYNTAX SEQUENCE OF ConvSxLSFPCompCodeGigabitEthernetEntry
		MAX-ACCESS not-accessible
		STATUS current
		DESCRIPTION
			"Optical transceiver gigabit Ethernet compatibility table"
		::= { convSxLSFPCompCodes 2 }

	convSxLSFPCompCodeGigabitEthernetEntry OBJECT-TYPE
		SYNTAX ConvSxLSFPCompCodeGigabitEthernetEntry
		MAX-ACCESS not-accessible
		STATUS current
		DESCRIPTION
			"Table entries"
		INDEX { convSxLPortIndex }
		::= { convSxLSFPCompCodeGigabitEthernetTable 1 }

	ConvSxLSFPCompCodeGigabitEthernetEntry ::=
		SEQUENCE
		{
			convSxLPortIndex INTEGER,
			convSxLSlot INTEGER,
			convSxLPort INTEGER,
			convSxLSFPCGType INTEGER
		}

	convSxLSFPCGType OBJECT-TYPE
		SYNTAX INTEGER
		{
			notSupported (0),
			g1000BASE-SX (1),
			g1000BASE-LX (2),
			g1000BASE-CX (4),
			g1000BASE-T (8),
			g100Base-Fx (32),
			g100Base-Fx-LX (48)
		}
		MAX-ACCESS read-only
		STATUS current
		DESCRIPTION
			"Supported protocol"
		::= { convSxLSFPCompCodeGigabitEthernetEntry 4 }

--************************Table**************************************
	convSxLSFPCompCodeFibreChannelTable  OBJECT-TYPE
		SYNTAX SEQUENCE OF ConvSxLSFPCompCodeFibreChannelEntry
		MAX-ACCESS not-accessible
		STATUS current
		DESCRIPTION
			"Optical transceiver fibre channel compatibility table"
		::= { convSxLSFPCompCodes 3 }

	convSxLSFPCompCodeFibreChannelEntry OBJECT-TYPE
		SYNTAX ConvSxLSFPCompCodeFibreChannelEntry
		MAX-ACCESS not-accessible
		STATUS current
		DESCRIPTION
			"Table entries"
		INDEX { convSxLPortIndex }
		::= { convSxLSFPCompCodeFibreChannelTable 1 }

	ConvSxLSFPCompCodeFibreChannelEntry ::=
		SEQUENCE
		{
			convSxLPortIndex INTEGER,
			convSxLSlot INTEGER,
			convSxLPort INTEGER,
			convSxLSFPCFcMedia INTEGER,
			convSxLSFPCFcTech INTEGER,
			convSxLSFPCFcLinkLength INTEGER,
			convSxLSFPCFcSpeed INTEGER
		}

	convSxLSFPCFcMedia OBJECT-TYPE
		SYNTAX INTEGER
		{
			mnotSupported (0),
			mSingleMode (1),
			reserved (2),
			mMultiMode50 (4),
			mMultiMode62-5 (8),
			mMultiMode50m-62-5m(12),
			mVideoCoax (16),
			mMiniatureCoax (32),
			mShieldedTwistedPair (64),
			mTwinAxialPair (128)
		}
		MAX-ACCESS  read-only
		STATUS  current
		DESCRIPTION
			"Supported media types"
		::= { convSxLSFPCompCodeFibreChannelEntry 4 }

	convSxLSFPCFcTech OBJECT-TYPE
		SYNTAX INTEGER
		{
			notSupported (0),
			tLongwaveLaserLL (10),
			tLongwaveLaserLC (11),
			tShortwaveLaserW-OFC (12),
			tShortwaveLaserW-O-OFC (13),
			tElectricalInterenclosure (20),
			tElectricalIntraenclosure (21)
		}
		MAX-ACCESS  read-only
		STATUS  current
		DESCRIPTION
			"Transmitter technology"
		::= { convSxLSFPCompCodeFibreChannelEntry 5 }

	convSxLSFPCFcLinkLength OBJECT-TYPE
		SYNTAX INTEGER
		{
			notSupported (0),
			longDistance (16),
			intermediateDistance (32),
			shortDistance (64),
			verylongDistance (128)
		}
		MAX-ACCESS  read-only
		STATUS  current
		DESCRIPTION
			"Link length supported by transceiver"
		::= { convSxLSFPCompCodeFibreChannelEntry 6 }

	convSxLSFPCFcSpeed OBJECT-TYPE
		SYNTAX INTEGER
		{
			notSupported(0),
			fcSpeed100MByte(1),
			fcSpeed200MByte(4),
			fcSpeed100-200MByte(5),
			fcSpeed400MByte(16),
			fcSpeed100-200-400MByte(21)
		}
		MAX-ACCESS  read-only
		STATUS  current
		DESCRIPTION
			"Fibre channel speed"
		::= { convSxLSFPCompCodeFibreChannelEntry 7 }

--************************Table**************************************
	convSxLCopperSFPTable  OBJECT-TYPE
		SYNTAX SEQUENCE OF ConvSxLCopperSFPEntry
		MAX-ACCESS not-accessible
		STATUS current
		DESCRIPTION
			"Overview and configuration of copper SFP table"
		::= { convSxSFPIdentifikation 5 }

	convSxLCopperSFPEntry OBJECT-TYPE
		SYNTAX ConvSxLCopperSFPEntry
		MAX-ACCESS not-accessible
		STATUS current
		DESCRIPTION
			"Transceiver overview and configuration entries"
		INDEX { convSxLPortIndex }
		::= { convSxLCopperSFPTable 1 }

	ConvSxLCopperSFPEntry ::=
		SEQUENCE
		{
			convSxLPortIndex INTEGER,
			convSxLSlot INTEGER,
			convSxLPort INTEGER,
			convSxLConfigSpeed INTEGER,
			convSxLConfigDuplex INTEGER,
			convSxLCuPhyId INTEGER,
			convSxLCuSFPLink INTEGER,
			convSxLCuSFPSpeed INTEGER,
			convSxLCuSFPDuplex INTEGER,
			convSxLCuSFPAutoMDIx INTEGER,
			convSxLCuSFPConfigMode INTEGER
		}

	convSxLConfigSpeed OBJECT-TYPE
		SYNTAX INTEGER
		{
			s10Mbit (1),
			s100Mbit (2),
			s1000Mbit (3),
			notSupported (255)
		}
		MAX-ACCESS  read-write
		STATUS  current
		DESCRIPTION
			"User defined configuration of speed"
		::= { convSxLCopperSFPEntry 3 }

	convSxLConfigDuplex OBJECT-TYPE
		SYNTAX INTEGER
		{
			halfduplex (1),
			fullduplex (2),
			notSupported (255)
		}
		MAX-ACCESS  read-write
		STATUS  current
		DESCRIPTION
			"User defined configuration of duplex mode"
		::= { convSxLCopperSFPEntry 4 }

	convSxLCuPhyId OBJECT-TYPE
		SYNTAX INTEGER
		{
			unknown (0),
			marvellPhy (1),
			notSupported (255)
		}
		MAX-ACCESS  read-only
		STATUS  current
		DESCRIPTION
			"Physical transceiver installed in SFP, if unkown the transceiver is not supported"
		::= { convSxLCopperSFPEntry 5 }

	convSxLCuSFPLink OBJECT-TYPE
		SYNTAX INTEGER
		{
			down (0),
			up (1),
			notSupported (255)
		}
		MAX-ACCESS  read-only
		STATUS  current
		DESCRIPTION
			"Link status of internal physical in copper SFP"
		::= { convSxLCopperSFPEntry 6 }

	convSxLCuSFPSpeed OBJECT-TYPE
		SYNTAX INTEGER
		{
			down (0),
			s10Mbit (1),
			s100Mbit (2),
			s1000Mbit (3),
			notSupported (255)
		}
		MAX-ACCESS  read-only
		STATUS  current
		DESCRIPTION
			"actual speed status of internal physical in copper SFP"
		::= { convSxLCopperSFPEntry 7 }

	convSxLCuSFPDuplex OBJECT-TYPE
		SYNTAX INTEGER
		{
			down (0),
			halfduplex (1),
			fullduplex (2),
			notSupported (255)
		}
		MAX-ACCESS  read-only
		STATUS  current
		DESCRIPTION
			"actual duplex mode status of internal physical in copper SFP"
		::= { convSxLCopperSFPEntry 8 }

	convSxLCuSFPAutoMDIx OBJECT-TYPE
		SYNTAX INTEGER
		{
			on (0),
			off (1),
			notSupported (255)
		}
		MAX-ACCESS  read-write
		STATUS  current
		DESCRIPTION
			"actual of status MDI-connection in copper SFP"
		::= { convSxLCopperSFPEntry 9 }

	convSxLCuSFPConfigMode OBJECT-TYPE
		SYNTAX INTEGER
		{
			unknown (0),
			auto (1),
			forced (2),
			notSupported (255)
		}
		MAX-ACCESS  read-write
		STATUS  current
		DESCRIPTION
			"actual config mode in copper SFP"
		::= { convSxLCopperSFPEntry 10 }

--************************Table**************************************
	convSxLDWDMSFPTable  OBJECT-TYPE
		SYNTAX SEQUENCE OF ConvSxLDWDMSFPEntry
		MAX-ACCESS not-accessible
		STATUS current
		DESCRIPTION
			"Overview and configuration of DWDM SFP table"
		::= { convSxSFPIdentifikation 6 }

	convSxLDWDMSFPEntry OBJECT-TYPE
		SYNTAX ConvSxLDWDMSFPEntry
		MAX-ACCESS not-accessible
		STATUS current
		DESCRIPTION
			"Transceiver overview and configuration entries"
		INDEX { convSxLPortIndex }
		::= { convSxLDWDMSFPTable 1 }

	ConvSxLDWDMSFPEntry ::=
		SEQUENCE
		{
			convSxLPortIndex INTEGER,
			convSxLSlot INTEGER,
			convSxLPort INTEGER,
			convSxLDWDMPowerClass INTEGER,
			convSxLDWDMMaxSupplyCurrent INTEGER,
			convSxLChannelSpacing INTEGER,
			convSxLNumberofChannels INTEGER
		}

	convSxLDWDMPowerClass OBJECT-TYPE
		SYNTAX INTEGER
		{
			p-upto1W (0),
			p-between1Wand1-5W (1),
			p-morethan1-5W (2),
			notSupported (255)
		}
		MAX-ACCESS  read-only
		STATUS  current
		DESCRIPTION
			"Power class of installed DWDM-SFP "
		::= { convSxLDWDMSFPEntry 4 }

	convSxLDWDMMaxSupplyCurrent OBJECT-TYPE
		SYNTAX INTEGER
		MAX-ACCESS  read-only
		STATUS  current
		DESCRIPTION
			"Defines the maximum supply current the module will consume under worst conditions in units of 4mA"
		::= { convSxLDWDMSFPEntry 5 }

	convSxLChannelSpacing OBJECT-TYPE
		SYNTAX INTEGER
		{
			g200GHz (0),
			g100GHz (1),
			g50GHz (2),
			notSupported (255)
		}
		MAX-ACCESS  read-only
		STATUS  current
		DESCRIPTION
			"Identifies the densest channel spacing the module is compatible with"
		::= { convSxLDWDMSFPEntry 6 }

	convSxLNumberofChannels OBJECT-TYPE
		SYNTAX INTEGER
		MAX-ACCESS  read-only
		STATUS  current
		DESCRIPTION
			"Identifies the number of channels over which the module may be tuned by user command. If not tunable the number is 1"
		::= { convSxLDWDMSFPEntry 7 }


--************************Table**************************************
	convSxLSFPDMIParamTable OBJECT-TYPE
		SYNTAX SEQUENCE OF ConvSxLSFPDMIParamEntry
		MAX-ACCESS not-accessible
		STATUS current
		DESCRIPTION
			"Optical transceiver measurement parameter table"
		::= { convSPEEDDUALLINE 8 }

	convSxLSFPDMIParamEntry OBJECT-TYPE
		SYNTAX ConvSxLSFPDMIParamEntry
		MAX-ACCESS not-accessible
		STATUS current
		DESCRIPTION
			"Table entries"
		INDEX { convSxLPortIndex }
		::= { convSxLSFPDMIParamTable 1 }

	ConvSxLSFPDMIParamEntry ::=
		SEQUENCE
		{
			convSxLPortIndex INTEGER,
			convSxLSlot INTEGER,
			convSxLPort INTEGER,
			convSxLSFPDMIRxLevel INTEGER,
			convSxLSFPDMIRxHighAlarm INTEGER,
			convSxLSFPDMITxLevel INTEGER,
			convSxLSFPDMITxBias INTEGER,
			convSxLSFPDMIVcc INTEGER,
			convSxLSFPDMITemp INTEGER
		}

	convSxLSFPDMIRxLevel OBJECT-TYPE
		SYNTAX INTEGER
		MAX-ACCESS  read-only
		STATUS  current
		DESCRIPTION
			"Optical receive power "
		::= { convSxLSFPDMIParamEntry 4 }

	convSxLSFPDMIRxHighAlarm OBJECT-TYPE
		SYNTAX INTEGER
		{
			normal (0),
			active (1)
		}
		MAX-ACCESS  read-only
		STATUS  current
		DESCRIPTION
			"Status of receive optical power, active when overloaded"
		::= { convSxLSFPDMIParamEntry 5 }

	convSxLSFPDMITxLevel OBJECT-TYPE
		SYNTAX INTEGER
		MAX-ACCESS  read-only
		STATUS  current
		DESCRIPTION
			"Optical transmit power "
		::= { convSxLSFPDMIParamEntry 6 }

	convSxLSFPDMITxBias OBJECT-TYPE
		SYNTAX INTEGER
		MAX-ACCESS  read-only
		STATUS  current
		DESCRIPTION
			"Transceiver hardware parameter: laser bias current"
		::= { convSxLSFPDMIParamEntry 7 }

	convSxLSFPDMIVcc OBJECT-TYPE
		SYNTAX INTEGER
		MAX-ACCESS  read-only
		STATUS  current
		DESCRIPTION
			"Transceiver hardware parameter: supply voltage"
		::= { convSxLSFPDMIParamEntry 8 }

	convSxLSFPDMITemp OBJECT-TYPE
		SYNTAX INTEGER
		MAX-ACCESS  read-only
		STATUS  current
		DESCRIPTION
			"Transceiver hardware parameter: temperature value"
		::= { convSxLSFPDMIParamEntry 9 }

--************************Table**************************************
	convSxLSFPDMIThresholdTable OBJECT-TYPE
		SYNTAX SEQUENCE OF ConvSxLSFPDMIThresholdEntry
		MAX-ACCESS not-accessible
		STATUS current
		DESCRIPTION
			"Optical transceiver measurement threshold table"
		::= { convSPEEDDUALLINE 9 }

	convSxLSFPDMIThresholdEntry OBJECT-TYPE
		SYNTAX ConvSxLSFPDMIThresholdEntry
		MAX-ACCESS not-accessible
		STATUS current
		DESCRIPTION
			"Measurement parameter overview"
		INDEX { convSxLPortIndex }
		::= { convSxLSFPDMIThresholdTable 1 }

	ConvSxLSFPDMIThresholdEntry ::=
		SEQUENCE
		{
			convSxLPortIndex INTEGER,
			convSxLSlot INTEGER,
			convSxLPort INTEGER,
			convSxLSFPDMIRxLowThresholdWarningLevel INTEGER,
			convSxLSFPDMIRxLowThresholdAlarmLevel INTEGER,
			convSxLSFPDMITxLowThresholdWarningLevel INTEGER,
			convSxLSFPDMITxLowThresholdAlarmLevel INTEGER,
			convSxLSFPDMIThresholdsUsage INTEGER
		}

	convSxLSFPDMIRxLowThresholdWarningLevel OBJECT-TYPE
		SYNTAX INTEGER
		MAX-ACCESS  read-write
		STATUS  current
		DESCRIPTION
			"Optical receive power warning level. Value display and set is dBm/100"
		::= { convSxLSFPDMIThresholdEntry 4 }

	convSxLSFPDMIRxLowThresholdAlarmLevel OBJECT-TYPE
		SYNTAX INTEGER
		MAX-ACCESS  read-only
		STATUS  current
		DESCRIPTION
			"Optical receive power alarm level. Value display is dBm/100"
		::= { convSxLSFPDMIThresholdEntry 5 }

	convSxLSFPDMITxLowThresholdWarningLevel OBJECT-TYPE
		SYNTAX INTEGER
		MAX-ACCESS  read-write
		STATUS  current
		DESCRIPTION
			"Optical transmit power warning level. Value display and set is dBm/100"
		::= { convSxLSFPDMIThresholdEntry 6 }

	convSxLSFPDMITxLowThresholdAlarmLevel OBJECT-TYPE
		SYNTAX INTEGER
		MAX-ACCESS  read-only
		STATUS  current
		DESCRIPTION
			"Optical transmit power alarm level. Value display is dBm/100"
		::= { convSxLSFPDMIThresholdEntry 7 }

	convSxLSFPDMIThresholdsUsage OBJECT-TYPE
		SYNTAX INTEGER
		{
			userDefinedThresholds (0),
			sFPVendorThresholds(1),
			notAvailable (255)
		}
		MAX-ACCESS  read-write
		STATUS  current
		DESCRIPTION
			"Set threshold usage. Activate user defined or vendor defined thresholds"
		::= { convSxLSFPDMIThresholdEntry 8 }

--************************Table**************************************
	convSxLPortEventTable OBJECT-TYPE
		SYNTAX SEQUENCE OF ConvSxLPortEventEntry
		MAX-ACCESS not-accessible
		STATUS current
		DESCRIPTION
			"Port event Table"
		::= { convSPEEDDUALLINE 10 }

	convSxLPortEventEntry OBJECT-TYPE
		SYNTAX ConvSxLPortEventEntry
		MAX-ACCESS not-accessible
		STATUS current
		DESCRIPTION
			"Port event table entries"
		INDEX { convSxLPortIndex }
		::= { convSxLPortEventTable 1 }

	ConvSxLPortEventEntry ::=
		SEQUENCE
		{
			convSxLPortIndex INTEGER,
			convSxLSlot INTEGER,
			convSxLPort INTEGER,
			convSxLSFPDMIRxLowWarningEvent INTEGER,
			convSxLSFPDMIRxLowAlarmEvent INTEGER,
			convSxLSFPDMITxLowWarningEvent INTEGER,
			convSxLSFPDMITxLowAlarmEvent INTEGER,
			convSxLSFPDMIBiasAlarmEvent INTEGER,
			convSxLSFPDMIRxHighAlarmEvent INTEGER,
			convSxLSFPDWDMLaserTHighAlarmEvent INTEGER,
			convSxLSFPDWDMLaserTLowAlarmEvent INTEGER,
			convSxLSFPDWDMTECHighAlarmEvent INTEGER,
			convSxLSFPDWDMTECLowAlarmEvent INTEGER,
			convSxLSFPDMITempHighWarningEvent INTEGER,
			convSxLSFPDMITempHighAlarmEvent INTEGER
		}

	convSxLSFPDMIRxLowWarningEvent OBJECT-TYPE
		SYNTAX INTEGER
		{
			normal (0),
			active (1),
			notimplemented (255)
		}
		MAX-ACCESS  read-only
		STATUS  current
		DESCRIPTION
			"Receive power - low warning"
		::= { convSxLPortEventEntry 4 }

	convSxLSFPDMIRxLowAlarmEvent OBJECT-TYPE
		SYNTAX INTEGER
		{
			normal (0),
			active (1),
			notimplemented (255)
		}
		MAX-ACCESS  read-only
		STATUS  current
		DESCRIPTION
			"Receive power - low alarm"
		::= { convSxLPortEventEntry 5 }

	convSxLSFPDMITxLowWarningEvent OBJECT-TYPE
		SYNTAX INTEGER
		{
			normal (0),
			active (1),
			notimplemented (255)
		}
		MAX-ACCESS  read-only
		STATUS  current
		DESCRIPTION
			"Output power - low warning"
		::= { convSxLPortEventEntry 6 }

	convSxLSFPDMITxLowAlarmEvent OBJECT-TYPE
		SYNTAX INTEGER
		{
			normal (0),
			active (1),
			notimplemented (255)
		}
		MAX-ACCESS  read-only
		STATUS  current
		DESCRIPTION
			"Output power - low alarm"
		::= { convSxLPortEventEntry 7 }

	convSxLSFPDMIBiasAlarmEvent OBJECT-TYPE
		SYNTAX INTEGER
		{
			normal (0),
			active (1),
			notimplemented (255)
		}
		MAX-ACCESS  read-only
		STATUS  current
		DESCRIPTION
			"Transmitter bias current is low"
		::= { convSxLPortEventEntry 8 }

	convSxLSFPDMIRxHighAlarmEvent OBJECT-TYPE
		SYNTAX INTEGER
		{
			normal (0),
			active (1),
			notimplemented (255)
		}
		MAX-ACCESS  read-only
		STATUS  current
		DESCRIPTION
			"Receiver input power is high"
		::= { convSxLPortEventEntry 9 }

	convSxLSFPDWDMLaserTHighAlarmEvent OBJECT-TYPE
		SYNTAX INTEGER
		{
			normal (0),
			active (1),
			notimplemented (255)
		}
		MAX-ACCESS read-only
		STATUS current
		DESCRIPTION
			"Set when laser temperature or wavelength exceeds high alarm level."
		::= { convSxLPortEventEntry 10 }

	convSxLSFPDWDMLaserTLowAlarmEvent OBJECT-TYPE
		SYNTAX INTEGER
		{
			normal (0),
			active (1),
			notimplemented (255)
		}
		MAX-ACCESS read-only
		STATUS current
		DESCRIPTION
			"Set when laser temperature or wavelength exceeds low alarm level."
		::= { convSxLPortEventEntry 11 }

	convSxLSFPDWDMTECHighAlarmEvent OBJECT-TYPE
		SYNTAX INTEGER
		{
			normal (0),
			active (1),
			notimplemented (255)
		}
		MAX-ACCESS read-only
		STATUS current
		DESCRIPTION
			"Set when TEC current exceeds high alarm level (cooling problem)"
		::= { convSxLPortEventEntry 12 }

	convSxLSFPDWDMTECLowAlarmEvent OBJECT-TYPE
		SYNTAX INTEGER
		{
			normal (0),
			active (1),
			notimplemented (255)
		}
		MAX-ACCESS read-only
		STATUS current
		DESCRIPTION
			"Set when TEC current exceeds low alarm level (heating problem)"
		::= { convSxLPortEventEntry 13 }

	convSxLSFPDMITempHighWarningEvent OBJECT-TYPE
		SYNTAX INTEGER
		{
			normal (0),
			active (1),
			notimplemented (255)
		}
		MAX-ACCESS read-only
		STATUS current
		DESCRIPTION
			"Transceiver DMI temperature high warning event"
		::= { convSxLPortEventEntry 14 }

	convSxLSFPDMITempHighAlarmEvent OBJECT-TYPE
		SYNTAX INTEGER
		{
			normal (0),
			active (1),
			notimplemented (255)
		}
		MAX-ACCESS read-only
		STATUS current
		DESCRIPTION
			"Transceiver DMI temperature high alarm event"
		::= { convSxLPortEventEntry 15 }

--************************Table**************************************
	convSxLInventoryTable OBJECT-TYPE
		SYNTAX SEQUENCE OF ConvSxLInventoryEntry
		MAX-ACCESS not-accessible
		STATUS current
		DESCRIPTION
			"Table of all serial numbers installed in module"
		::= { convSPEEDDUALLINE 11 }

	convSxLInventoryEntry OBJECT-TYPE
		SYNTAX ConvSxLInventoryEntry
		MAX-ACCESS not-accessible
		STATUS current
		DESCRIPTION
			"Table entries"
		INDEX { convSxLMSlot }
		::= { convSxLInventoryTable 1 }

	ConvSxLInventoryEntry ::=
		SEQUENCE
		{
			convSxLMSlot INTEGER,
			convSxLModuleSerialNumber DisplayString,
			convSxLSFPPort1SerialNumber  DisplayString,
			convSxLSFPPort2SerialNumber  DisplayString,
			convSxLSFPPort3SerialNumber  DisplayString,
			convSxLSFPPort4SerialNumber  DisplayString
		}

	convSxLModuleSerialNumber OBJECT-TYPE
		SYNTAX DisplayString (SIZE (0..17))
		MAX-ACCESS  read-only
		STATUS  current
		DESCRIPTION
			"Serial number of module "
		::= { convSxLInventoryEntry 3 }

	convSxLSFPPort1SerialNumber OBJECT-TYPE
		SYNTAX DisplayString (SIZE (0..17))
		MAX-ACCESS  read-only
		STATUS  current
		DESCRIPTION
			"Serial number of installed transceiver"
		::= { convSxLInventoryEntry 4 }

	convSxLSFPPort2SerialNumber OBJECT-TYPE
		SYNTAX DisplayString (SIZE (0..17))
		MAX-ACCESS  read-only
		STATUS  current
		DESCRIPTION
			"Serial number of installed transceiver"
		::= { convSxLInventoryEntry 5 }

	convSxLSFPPort3SerialNumber OBJECT-TYPE
		SYNTAX DisplayString (SIZE (0..17))
		MAX-ACCESS  read-only
		STATUS  current
		DESCRIPTION
			"Serial number of installed transceiver"
		::= { convSxLInventoryEntry 6 }

	convSxLSFPPort4SerialNumber OBJECT-TYPE
		SYNTAX DisplayString (SIZE (0..17))
		MAX-ACCESS  read-only
		STATUS  current
		DESCRIPTION
			"Serial number of installed transceiver"
		::= { convSxLInventoryEntry 7 }

--*****************************************************************
--*************   Trap's   ****************************************

	coldStart TRAP-TYPE
		ENTERPRISE PanDacom
		VARIABLES { Descr, Slot}
		DESCRIPTION
			"ColdStart"
		::= 40

	reboot TRAP-TYPE
		ENTERPRISE PanDacom
		VARIABLES { Descr, Slot}
		DESCRIPTION
			"Reboot"
		::= 41

	fanError TRAP-TYPE
		ENTERPRISE PanDacom
		VARIABLES { Descr, Slot}
		DESCRIPTION
			"FANError"
		::= 42

	fanOK TRAP-TYPE
		ENTERPRISE PanDacom
		VARIABLES { Descr, Slot}
		DESCRIPTION
			"FANOK"
		::= 43

	powerFailure TRAP-TYPE
		ENTERPRISE PanDacom
		VARIABLES { Descr, Slot }
		DESCRIPTION
			"PowerFailure"
		::= 44

	powerOK TRAP-TYPE
		ENTERPRISE PanDacom
		VARIABLES { Descr, Slot }
		DESCRIPTION
			"PowerOK"
		::= 45

	highTemp TRAP-TYPE
		ENTERPRISE PanDacom
		VARIABLES { Descr, Slot, Port }
		DESCRIPTION
			"HighTemp"
		::= 46

	tempOK TRAP-TYPE
		ENTERPRISE PanDacom
		VARIABLES { Descr, Slot, Port }
		DESCRIPTION
			"TempOK"
		::= 47

	transceiverRemoved TRAP-TYPE
		ENTERPRISE PanDacom
		VARIABLES { Descr, Slot, Port }
		DESCRIPTION
			"SFPRemoved"
		::= 48

	transceiverInserted TRAP-TYPE
		ENTERPRISE PanDacom
		VARIABLES { Descr, Slot, Port }
		DESCRIPTION
			"SFPInserted"
		::= 49

	moduleInserted TRAP-TYPE
		ENTERPRISE PanDacom
		VARIABLES { Descr, Slot}
		DESCRIPTION
			"ModuleInserted"
		::= 50

	moduleRemoved TRAP-TYPE
		ENTERPRISE PanDacom
		VARIABLES { Descr, Slot}
		DESCRIPTION
			"ModuleRemoved"
		::= 51

	portTxUp TRAP-TYPE
		ENTERPRISE PanDacom
		VARIABLES { Descr, Slot, Port }
		DESCRIPTION
			"PortTxUp"
		::= 52

	portTxDown TRAP-TYPE
		ENTERPRISE PanDacom
		VARIABLES { Descr, Slot, Port }
		DESCRIPTION
			"PortTxDown"
		::= 53

	portUp TRAP-TYPE
		ENTERPRISE PanDacom
		VARIABLES { Descr, Slot, Port }
		DESCRIPTION
			"PortUp"
		::= 54

	portDown TRAP-TYPE
		ENTERPRISE PanDacom
		VARIABLES { Descr, Slot, Port }
		DESCRIPTION
			"PortDown"
		::= 55

	txFault TRAP-TYPE
		ENTERPRISE PanDacom
		VARIABLES { Descr, Slot, Port }
		DESCRIPTION
			"TxFault"
		::= 56

	badPasswd TRAP-TYPE
		ENTERPRISE PanDacom
		VARIABLES { Descr, Slot }
		DESCRIPTION
			"BadPasswd"
		::= 57

	softwareUpdateReady TRAP-TYPE
		ENTERPRISE PanDacom
		VARIABLES { Descr, Slot }
		DESCRIPTION
			"SoftwareUpdateReady"
		::= 58

	hardwareTrap TRAP-TYPE
		ENTERPRISE PanDacom
		VARIABLES { Descr, Slot }
		DESCRIPTION
			"HardwareTrap"
		::= 59

	cdrAlarm TRAP-TYPE
		ENTERPRISE PanDacom
		VARIABLES { Descr, Slot }
		DESCRIPTION
			"CDRAlarm"
		::= 60

	protectionMain TRAP-TYPE
		ENTERPRISE PanDacom
		VARIABLES { Descr, Slot, Port }
		DESCRIPTION
			"ProtectionMain"
		::= 61

	protectionBackup TRAP-TYPE
		ENTERPRISE PanDacom
		VARIABLES { Descr, Slot, Port }
		DESCRIPTION
			"ProtectionBackup"
		::= 62

	optRxLevelWarning TRAP-TYPE
		ENTERPRISE PanDacom
		VARIABLES { Descr, Slot, Port }
		DESCRIPTION
			"OptRxLevelWarning"
		::= 63

	optRxLevelAlarm TRAP-TYPE
		ENTERPRISE PanDacom
		VARIABLES { Descr, Slot, Port }
		DESCRIPTION
			"OptRxLevelAlarm"
		::= 64

	optRxLevelOK TRAP-TYPE
		ENTERPRISE PanDacom
		VARIABLES { Descr, Slot, Port }
		DESCRIPTION
			"OptRxLevelOK"
		::= 65

	optTxLevelWarning TRAP-TYPE
		ENTERPRISE PanDacom
		VARIABLES { Descr, Slot, Port }
		DESCRIPTION
			"OptTxLevelWarning"
		::= 66

	optTxLevelAlarm TRAP-TYPE
		ENTERPRISE PanDacom
		VARIABLES { Descr, Slot, Port }
		DESCRIPTION
			"OptTxLevelAlarm"
		::= 67

	optTxLevelOK TRAP-TYPE
		ENTERPRISE PanDacom
		VARIABLES { Descr, Slot, Port }
		DESCRIPTION
			"OptTxLevelOK"
		::= 68

	optTxBiasAlarm TRAP-TYPE
		ENTERPRISE PanDacom
		VARIABLES { Descr, Slot, Port }
		DESCRIPTION
			"TX Bias Alarm"
		::= 69

	optTxBiasOK TRAP-TYPE
		ENTERPRISE PanDacom
		VARIABLES { Descr, Slot, Port }
		DESCRIPTION
			"TX Bias OK"
		::= 70

	optRxPowerOverload TRAP-TYPE
		ENTERPRISE PanDacom
		VARIABLES { Descr, Slot, Port }
		DESCRIPTION
			"High optical input power Alarm"
		::= 71

	configError TRAP-TYPE
		ENTERPRISE PanDacom
		VARIABLES { Descr, Slot, Port }
		DESCRIPTION
			"Configuration error. An set command or config file transfer was not successful."
		::= 72

	configuration TRAP-TYPE
		ENTERPRISE PanDacom
		VARIABLES { Descr, Slot, Port }
		DESCRIPTION
			"Configuration file information"
		::= 73

	maintenance TRAP-TYPE
		ENTERPRISE PanDacom
		VARIABLES { Descr, Slot, Port }
		DESCRIPTION
			"Maintennance Change"
		::= 74

	ampFail TRAP-TYPE
		ENTERPRISE PanDacom
		VARIABLES { Descr, Slot, Port }
		DESCRIPTION
			"AMP error is occured"
		::= 75

	ampOk TRAP-TYPE
		ENTERPRISE PanDacom
		VARIABLES { Descr, Slot, Port }
		DESCRIPTION
			"AMP error is cleared"
		::= 76

	dwdmAlarm TRAP-TYPE
		ENTERPRISE PanDacom
		VARIABLES { Descr, Slot, Port }
		DESCRIPTION
			"DWDM transceiver alarm occured"
		::= 77

	dwdmOk TRAP-TYPE
		ENTERPRISE PanDacom
		VARIABLES { Descr, Slot, Port }
		DESCRIPTION
			"DWDM transceiver alarm cleared"
		::= 78

	firmwareError TRAP-TYPE
		ENTERPRISE PanDacom
		VARIABLES { Descr, Slot, Port }
		DESCRIPTION
			"firmware or kernel transfer or flashing error"
		::= 79

	unspecified TRAP-TYPE
		ENTERPRISE PanDacom
		VARIABLES { Descr, Slot, Port }
		DESCRIPTION
			"Unspecified"
		::= 255

END

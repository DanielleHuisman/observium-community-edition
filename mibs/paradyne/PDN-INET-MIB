PDN-INET-MIB DEFINITIONS ::= BEGIN

-- Version :  1.1 APPROVED
-- Enterprise Inet mib
-- Copyright (C) 2000 Paradyne Corporation.

 
IMPORTS
Integer32,IpAddress,
OBJECT-TYPE, MODULE-IDENTITY
FROM SNMPv2-SMI
ifIndex
  FROM RFC1213-MIB
RowStatus
  FROM SNMPv2-TC
pdn-common
  FROM PDN-HEADER-MIB
;

pdn-inet MODULE-IDENTITY
   LAST-UPDATED    "0202210000Z"
   ORGANIZATION    "Paradyne Corporation
		    MIB Working Group"

   CONTACT-INFO    "Paradyne Corporation
		    8545 126th Avenue North
		    Largo, FL 33733
		    www.paradyne.com

		    General Comments to: mibwg_team@paradyne.com

		    Editors
		    Prakash Easwar
		    Dragana Gough"

  DESCRIPTION
     "This mib is used to configure ip address of some interface"

   REVISION "0202210000Z"
   DESCRIPTION "Changed to SMIv2" 

   REVISION "0005100000Z"
   DESCRIPTION "changed pdnInetIpSubnetMask to read-write"

   REVISION "0004270000Z"
   DESCRIPTION "removed pdnInetIpSubnetMask from the INDEX clause for
   		pdnInetIpAddressTable"

   ::= { pdn-common 26 }



pdnInetMIBObjects OBJECT IDENTIFIER ::= { pdn-inet 1 }
pdnInetMIBTraps   OBJECT IDENTIFIER ::= { pdn-inet 2 }

pdnInetTelnetServerPort OBJECT-TYPE
  SYNTAX INTEGER (1..65535)
  MAX-ACCESS read-write
  STATUS current
  DESCRIPTION
     "This object contains the telnet server (daemon) tcp
      port number."
  DEFVAL { 23 }
::= { pdnInetMIBObjects 1 }

pdnInetFtpServerControlPort OBJECT-TYPE
  SYNTAX INTEGER (1..65535)
  MAX-ACCESS read-write
  STATUS current
  DESCRIPTION
     "This object contains the ftp server control (daemon) tcp
      port number."
  DEFVAL { 21 }
::= { pdnInetMIBObjects 2 }

pdnInetFtpServerDataPort OBJECT-TYPE
  SYNTAX INTEGER (1..65535)
  MAX-ACCESS read-write
  STATUS current
  DESCRIPTION
     "This object contains the ftp server data connection tcp
      port number."
  DEFVAL { 20 }
::= { pdnInetMIBObjects 3 }
 
pdnInetIpAddressTableMaxIpSubnets OBJECT-TYPE
  SYNTAX Integer32
  MAX-ACCESS read-only
  STATUS current
  DESCRIPTION
    "This object  indicates the maximum number of entries in
     the pdnInetAddressTable"
::= { pdnInetMIBObjects 4 }

pdnInetIpAddressTableCurrentIpSubnets OBJECT-TYPE
  SYNTAX Integer32
  MAX-ACCESS read-only
  STATUS current
  DESCRIPTION
    "This object  indicates the number of entries configured in
     the pdnInetAddressTable"
::= { pdnInetMIBObjects 5 }
 
pdnInetIpAddressTable OBJECT-TYPE
  SYNTAX SEQUENCE OF PdnInetIpAddressTableEntry
  MAX-ACCESS  not-accessible
  STATUS  current
  DESCRIPTION
    "This table used to configure ipaddresses for an interface
     which support the internet (IP) protocol"
::= { pdnInetMIBObjects 6 }
 
pdnInetIpAddressTableEntry OBJECT-TYPE
  SYNTAX  PdnInetIpAddressTableEntry
  MAX-ACCESS  not-accessible
  STATUS  current
  DESCRIPTION
    "This object corresponds to an entry in the IP address table."
  INDEX { ifIndex, pdnInetIpAddress }
::= { pdnInetIpAddressTable 1 }

PdnInetIpAddressTableEntry ::=
  SEQUENCE
  {
    pdnInetIpAddress IpAddress,
    pdnInetIpSubnetMask IpAddress,
    pdnInetIpAddressType INTEGER,
    pdnInetIpRowStatus RowStatus,
    pdnInetIpGateway IpAddress
  }
 
pdnInetIpAddress OBJECT-TYPE
  SYNTAX IpAddress
  MAX-ACCESS not-accessible
  STATUS current
  DESCRIPTION
    "This object is used to configure an IP address for an interface"
::= { pdnInetIpAddressTableEntry 1 }

pdnInetIpSubnetMask OBJECT-TYPE
  SYNTAX IpAddress
  MAX-ACCESS read-create
  STATUS current
  DESCRIPTION
    "This object is used to configure an IP subnet mask for an interface.
	  subnet mask should result in contiguous subnets"
::= { pdnInetIpAddressTableEntry 2 }

pdnInetIpAddressType OBJECT-TYPE
  SYNTAX INTEGER { primary (1),
		  secondary(2),
		  primaryBootp(3),
		  secondaryBootp(4)
		  }
	
  MAX-ACCESS read-create
  STATUS current
  DESCRIPTION
    "This object is used to configure the address type for an interface
	  an interface can have only one primary ip address and more than one
	  secondary ip address. the primary ip address is essentially the
	  router ID. The secondary ip address would result in the interface
	  being multi-homed. The default value is primary type."
::= { pdnInetIpAddressTableEntry 3 }

pdnInetIpRowStatus OBJECT-TYPE
  SYNTAX RowStatus
  MAX-ACCESS read-create
  STATUS current
  DESCRIPTION
    "This object is used to manage rows (add/delete/modify) in this table"
::= { pdnInetIpAddressTableEntry 4 }

pdnInetIpGateway  OBJECT-TYPE
  SYNTAX IpAddress
  MAX-ACCESS read-create
  STATUS current
  DESCRIPTION
    "This object is used to configure an gateway for an interface."
::= { pdnInetIpAddressTableEntry 5 }
END

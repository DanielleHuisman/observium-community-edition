PDN-MPE-HEALTH-AND-STATUS-MIB DEFINITIONS ::= BEGIN

-- Last-Updated: 6/16/00

-- Enterprise Health and Status  MIB (mpe support)
-- Copyright (C) 2000 Paradyne Corporation.
--
-- Created by : Wayne Jadoo / Prakash Easwar

IMPORTS
DisplayString
  FROM SNMPv2-TC
OBJECT-TYPE
  FROM RFC-1212
entPhysicalIndex
  FROM ENTITY-MIB  
mpe-devHealth
  FROM PDN-HEADER-MIB
TRAP-TYPE
  FROM RFC-1215
;

mpeDevHealthAndStatusMIBObjects  OBJECT IDENTIFIER ::= { mpe-devHealth  1 }
mpeDevHealthAndStatusMIBTraps    OBJECT IDENTIFIER ::= { mpe-devHealth  2 }

 -- groups for Paradyne  health and Status MIB

mpeDevHealthAndStatusTable OBJECT-TYPE
  SYNTAX  SEQUENCE OF MpeDevHealthAndStatusEntry
  ACCESS  not-accessible
  STATUS  mandatory
  DESCRIPTION
    "A table that contains information about an Entity's health."
::= { mpeDevHealthAndStatusMIBObjects 1 }

mpeDevHealthAndStatusEntry OBJECT-TYPE
  SYNTAX  MpeDevHealthAndStatusEntry
  ACCESS  not-accessible
  STATUS  mandatory
  DESCRIPTION
    "A list of information for an entity's health."
  INDEX  { entPhysicalIndex }
::= { mpeDevHealthAndStatusTable 1 }

MpeDevHealthAndStatusEntry ::=
  SEQUENCE 
  {
     mpeDevSelfTestResults DisplayString
  }

mpeDevSelfTestResults OBJECT-TYPE
  SYNTAX  DisplayString (SIZE (0..255))
  ACCESS  read-only
  STATUS  mandatory
  DESCRIPTION
    "Self-test results. Self-test (or power-up test) results
     summarizes the test results of each CCA, where each CCA test
     result is separated by a semi-colon. Refer to device-specific 
     user documentation for a complete description of the self test
     codes and messages."
::= { mpeDevHealthAndStatusEntry  1 }

-- Traps for Device failure 

mpeSelfTestFailure TRAP-TYPE
  ENTERPRISE  mpeDevHealthAndStatusMIBTraps
  VARIABLES { mpeDevSelfTestResults }
  DESCRIPTION
    "This trap signifies that the sending protocol's
     device has failed self test.
     The variable binding for this trap would be the selfTest
     devSelfTestResults object of the Health and Status MIB. The
     exact format of this display string will be well-documented
     in the Operational Specifications of the device."
::= 1

END

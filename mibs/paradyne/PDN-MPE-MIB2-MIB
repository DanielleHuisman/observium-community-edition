PDN-MPE-MIB2-MIB DEFINITIONS ::= BEGIN

-- Last-Updated: 1/28/2002

-- Enterprise mib-2 mib (mpe support)
-- Copyright (C) 2000 Paradyne Corporation.

-- Created by : Prakash Easwar

 IMPORTS
 DisplayString
 FROM SNMPv2-TC
 TimeTicks
 FROM RFC1155-SMI
 OBJECT-TYPE
 FROM RFC-1212
 TRAP-TYPE
 FROM RFC-1215
 entPhysicalIndex
 FROM ENTITY-MIB 
 mpe-mib2
 FROM PDN-HEADER-MIB
 ;

--Test
mpeMib2MIBObjects OBJECT IDENTIFIER ::= { mpe-mib2 1 }
mpeMib2MIBTraps   OBJECT IDENTIFIER ::= { mpe-mib2 2 }

mpeSystem OBJECT IDENTIFIER ::= { mpeMib2MIBObjects 1 }

-- the Enterprise System group

mpeSystemsTable OBJECT-TYPE
    SYNTAX  SEQUENCE OF MpeSystemsEntry
    ACCESS  not-accessible
    STATUS  mandatory
    DESCRIPTION
            "A table that contains general information about an Entity ."
    ::= { mpeSystem 1 }

mpeSystemsEntry OBJECT-TYPE
    SYNTAX  MpeSystemsEntry
    ACCESS  not-accessible
    STATUS  mandatory
    DESCRIPTION
            "A list of system information about an Entity  ."
              INDEX  { entPhysicalIndex }
   ::= { mpeSystemsTable 1 }

MpeSystemsEntry ::=
    SEQUENCE {
        mpeSysDescr    DisplayString (SIZE (0..255)),
        mpeSysObjectID OBJECT IDENTIFIER,
        mpeSysUpTime   TimeTicks,
        mpeSysContact  DisplayString (SIZE (0..255)),
        mpeSysName     DisplayString (SIZE (0..255)),
        mpeSysLocation DisplayString (SIZE (0..255)),
        mpeSysServices INTEGER (0..127)
   }

mpeSysDescr OBJECT-TYPE
    SYNTAX  DisplayString (SIZE (0..255))
    ACCESS  read-only
    STATUS  mandatory
    DESCRIPTION
            "A textual description of the entity.  This value
            should include the full name and version
            identification of the system's hardware type,
            software operating-system, and networking
            software.  It is mandatory that this only contain
            printable ASCII characters."
    ::= { mpeSystemsEntry 1 }

mpeSysObjectID OBJECT-TYPE
    SYNTAX  OBJECT IDENTIFIER
    ACCESS  read-only
    STATUS  mandatory
    DESCRIPTION
            "The vendor's authoritative identification of the
            network management subsystem contained in the
            entity.  This value is allocated within the SMI
            enterprises subtree (1.3.6.1.4.1) and provides an
            easy and unambiguous means for determining `what
            kind of box' is being managed.  For example, if
            vendor `Flintstones, Inc.' was assigned the
            subtree 1.3.6.1.4.1.4242, it could assign the
            identifier 1.3.6.1.4.1.4242.1.1 to its `Fred
            Router'."
    ::= { mpeSystemsEntry 2 }

mpeSysUpTime OBJECT-TYPE
    SYNTAX  TimeTicks
    ACCESS  read-only
    STATUS  mandatory
    DESCRIPTION
            "The time (in hundredths of a second) since the
            network management portion of the system was last
            re-initialized."
    ::= { mpeSystemsEntry  3 }

mpeSysContact OBJECT-TYPE
    SYNTAX  DisplayString (SIZE (0..255))
    ACCESS  read-write
    STATUS  mandatory
    DESCRIPTION
            "The textual identification of the contact person
            for this managed node, together with information
            on how to contact this person."
    ::= { mpeSystemsEntry  4 }

mpeSysName OBJECT-TYPE
    SYNTAX  DisplayString (SIZE (0..255))
    ACCESS  read-write
    STATUS  mandatory
    DESCRIPTION
            "An administratively-assigned name for this
            managed node.  By convention, this is the node's
            fully-qualified domain name."
    ::= { mpeSystemsEntry  5 }

mpeSysLocation OBJECT-TYPE
    SYNTAX  DisplayString (SIZE (0..255))
    ACCESS  read-write
    STATUS  mandatory
    DESCRIPTION
            "The physical location of this node (e.g.,
            `telephone closet, 3rd floor')."
    ::= { mpeSystemsEntry  6 }
          
mpeSysServices OBJECT-TYPE
    SYNTAX  INTEGER (0..127)
    ACCESS  read-only
    STATUS  mandatory
    DESCRIPTION
      "A value which indicates the set of services that
       this entity primarily offers.

       The value is a sum.  This sum initially takes the
       value zero, Then, for each layer, L, in the range
       1 through 7, that this node performs transactions
       for, 2 raised to (L - 1) is added to the sum.  For
       example, a node which performs primarily routing
       functions would have a value of 4 (2^(3-1)).  In
       contrast, a node which is a host offering
       application services would have a value of 72
       (2^(4-1) + 2^(7-1)).  Note that in the context of
       the Internet suite of protocols, values should be
       calculated accordingly:

       layer  functionality
         1  physical (e.g., repeaters)
         2  datalink/subnetwork (e.g., bridges)
         3  internet (e.g., IP gateways)
         4  end-to-end  (e.g., IP hosts)
         7  applications (e.g., mail relays)

       For systems including OSI protocols, layers 5 and
       6 may also be counted."
   ::= { mpeSystemsEntry 7 }

END

PDN-SOCKET-MIB DEFINITIONS ::= BEGIN

-- Version :  0.1 DRAFT
-- Enterprise Socket mib
-- Copyright (C) 2000 Paradyne Corporation.

-- Created by : Prakash Easwar

IMPORTS
entPhysicalIndex
FROM ENTITY-MIB
OBJECT-TYPE
FROM RFC-1212
SocketState,
SocketFamily,
SocketType
FROM PDN-TC
TAddress, DisplayString
FROM SNMPv2-TC
pdn-socket
FROM PDN-HEADER-MIB
;

devSocketStatsMIBObjects  OBJECT IDENTIFIER ::= { pdn-socket 1 }
devSocketStatsMIBTraps    OBJECT IDENTIFIER ::= { pdn-socket 2 }

        devSocketStatsTable OBJECT-TYPE
              SYNTAX  SEQUENCE OF DevSocketStatsEntry
              ACCESS  not-accessible
              STATUS  mandatory
              DESCRIPTION
              "This table gives statistics on the sockets 
               currently being used by the device"
              ::= { devSocketStatsMIBObjects 1 }

        devSocketStatsEntry OBJECT-TYPE
              SYNTAX  DevSocketStatsEntry
              ACCESS  not-accessible
              STATUS  mandatory
              DESCRIPTION
                 "This table gives statistics on the sockets 
                   currently being used by the device"
              INDEX  { entPhysicalIndex, devSocketNumber }
              ::= { devSocketStatsTable 1 }

        DevSocketStatsEntry ::=
                SEQUENCE
                {
                        devSocketNumber         INTEGER,
                        devSocketName           DisplayString,
                        devSocketFamily         SocketFamily,
                        devSocketType           SocketType,
                        devSocketLocalAddress   TAddress,
                        devSocketRemoteAddress  TAddress,
                        devSocketState          SocketState,
                        devSocketInputBytes     INTEGER,
                        devSocketOutputBytes    INTEGER,
                        devSocketPDUDrops       INTEGER,
                        devSocketByteDrops      INTEGER

                }

        devSocketNumber OBJECT-TYPE
                SYNTAX  INTEGER
                ACCESS  read-only
                STATUS  mandatory
                DESCRIPTION
                        "a unique number associated with a socket"
                ::= { devSocketStatsEntry 1 }

        devSocketName OBJECT-TYPE
                SYNTAX  DisplayString
                ACCESS  read-only
                STATUS  mandatory
                DESCRIPTION
                        "the Name given to this socket by the device"
                ::= { devSocketStatsEntry 2 }

        devSocketFamily OBJECT-TYPE
                SYNTAX  SocketFamily
                ACCESS  read-only
                STATUS  mandatory
                DESCRIPTION
                       "The Family associated with this socket"
                ::= { devSocketStatsEntry 3 }

        devSocketType OBJECT-TYPE
                SYNTAX  SocketType
                ACCESS  read-only
                STATUS  mandatory
                DESCRIPTION
                        "the "
                ::= { devSocketStatsEntry 4 }

        devSocketLocalAddress OBJECT-TYPE
                SYNTAX  TAddress
                ACCESS  read-only
                STATUS  mandatory
                DESCRIPTION
                     "the local address (ipaddress + port) for this socket"
                ::= { devSocketStatsEntry 5 }

        devSocketRemoteAddress OBJECT-TYPE
                SYNTAX  TAddress
                ACCESS  read-only
                STATUS  mandatory
                DESCRIPTION
                    "the remote address (ipaddress + port) for this socket"
                ::= { devSocketStatsEntry 6 }

        devSocketState OBJECT-TYPE
                SYNTAX  SocketState
                ACCESS  read-only
                STATUS  mandatory
                DESCRIPTION
                        "The State the socket is in. This 
                         is valid for stream sockets only"
                ::= { devSocketStatsEntry 7 }

        devSocketInputBytes OBJECT-TYPE
                SYNTAX  INTEGER
                ACCESS  read-only
                STATUS  mandatory
                DESCRIPTION
                        "The number of bytes received on this socket"
                ::= { devSocketStatsEntry 8 }

        devSocketOutputBytes OBJECT-TYPE
                SYNTAX  INTEGER
                ACCESS  read-only
                STATUS  mandatory
                DESCRIPTION
                        "The number of bytes transmitted on this socket"
                ::= { devSocketStatsEntry 9 }

        devSocketPDUDrops OBJECT-TYPE
                SYNTAX  INTEGER
                ACCESS  read-only
                STATUS  mandatory
                DESCRIPTION
                   "The number of incoming packets that 
                    were dropped due to the socket receive
                    queue being full"
                ::= { devSocketStatsEntry 10 }

        devSocketByteDrops OBJECT-TYPE
                SYNTAX  INTEGER
                ACCESS  read-only
                STATUS  mandatory
                DESCRIPTION
                        "The number of imcoming bytes that were dropped 
                         due to the socket receive  queue being full"
                ::= { devSocketStatsEntry 11 }

END

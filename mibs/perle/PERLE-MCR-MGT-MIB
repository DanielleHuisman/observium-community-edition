--
-- Copyright (C) 2014 - Perle Systems Limited
--
-- Private MIB module for the Perle Managed Media Converters.
-- This MIB will be used in Windows and UNIX Environment.
--
--  Documentation References:
--    Please reference the following user guides found at
--    http://www.perle.com/downloads/managed-media-converter.shtml
--    to obtain more information on the media converters operation
--    and configuration fields.
--       MCR-MGT Management Module User’s Guide
--       MCR1900 Media Converter 19-Slot Chassis Installation Guide
--       Perle Gigabit Media Converter Module Installation Guide
--       Perle 10/100/1000 Ethernet Media Converter Module Installation Guide
--       Perle Fast Ethernet Media Converter Module Installation Guide
--       Perle 10/100 Ethernet Media Converter Module Installation Guide
--       Perle Fast Ethernet Fiber to Fiber Module Installation Guide
--       Perle Gigabit Fiber to Fiber Module Installation Guide
--       Perle 10G Media Converter Module Installation Guide
--       Perle eX-1CM Media Converter Module Installation Guide
--       Perle CM-4GPT Media Converter Module Installation Guide
--       Perle CM-10GT Media Converter Module Installation Guide
--
-- Version:  14.09.03 (year.month.day)
--
-- History:
--   14.09.03  - Added support for SGMII mode on the CM-1110 Module and SNTP authentication
--   13.03.22  - Added support for ex-1CM, CM-4GPT and CM-10GT Media Converter Modules
--   12.11.15  - Added support for CM-10G Media Converter Modules
--   12.02.20  - Added support for PerleView features.
--   11.01.20  - Added support for advanced switch features and dual-fiber modules
--   11.01.12  - Added support for 2-slot chassis
--   10.09.10  - Initial release
--

PERLE-MCR-MGT-MIB DEFINITIONS ::= BEGIN


  IMPORTS
        MODULE-IDENTITY, NOTIFICATION-TYPE, OBJECT-TYPE,
        IpAddress, Counter32, Unsigned32, Integer32, Counter64, enterprises, TimeTicks
                FROM SNMPv2-SMI
        TEXTUAL-CONVENTION, DisplayString, MacAddress, DateAndTime
                FROM SNMPv2-TC
        MODULE-COMPLIANCE, OBJECT-GROUP, NOTIFICATION-GROUP
                FROM SNMPv2-CONF
        SnmpEngineID
                FROM SNMP-FRAMEWORK-MIB;

--
-- MODULE IDENTITY for the private MIB of Perle Managed Media Converters
--

mcrMGTMIB         MODULE-IDENTITY
    LAST-UPDATED
          "201409030000Z"
    ORGANIZATION
          "Perle Systems Limited"
    CONTACT-INFO
           "Postal: Perle Systems Limited 
                     60 Renfrew Drive 
                     Markham, Ontario 
                     Canada 
                     L3R 0E1 
 
             http://www.perle.com/"
    DESCRIPTION
            "The private MIB module for the Perle Managed Media Converters"
    REVISION
            "201409030000Z"
        DESCRIPTION
             "Added support for SGMII mode on the CM-1110 Module and SNTP authentication"
    REVISION
            "201303020000Z"
        DESCRIPTION
             "Added support for ex-1CM, CM-4GPT and CM-10GT Media Converter Modules"
    REVISION
            "201211150000Z"
        DESCRIPTION
             "Added support for CM-10G Media Converter Modules"
    REVISION
            "201202010000Z"
        DESCRIPTION
             "Added support for PerleView features, alarm/warning table, port status table and tftp file transfer"
    REVISION
            "201101200000Z"
        DESCRIPTION
             "Added support for advanced switch features and dual-fiber modules"
    REVISION
            "201101120000Z"
        DESCRIPTION
             "Added support for 2-slot chassis"
    REVISION
            "201009100000Z"
        DESCRIPTION
             "Initial Release"
      ::= { mediaconverterMIB 1  }


--
-- OID tree for  perle MIBs
--
perle OBJECT IDENTIFIER ::= { enterprises 1966 }

productId 			OBJECT IDENTIFIER ::= { perle 20 }
mediaConverter 	OBJECT IDENTIFIER ::= { productId 1 }
mcrMGT			OBJECT IDENTIFIER ::= { mediaConverter 1 }

productMIB					 OBJECT IDENTIFIER ::= { perle 21 }
mediaconverterMIB			 OBJECT IDENTIFIER ::= { productMIB 1 }

mcrMGTMIBNotifications	OBJECT IDENTIFIER ::= { mcrMGTMIB 0 }
mcrMGTMIBObjects		 	OBJECT IDENTIFIER ::= { mcrMGTMIB 1 }
mcrMGTMIBConformance 	OBJECT IDENTIFIER ::= { mcrMGTMIB 2 }

mcrChassisGroup		OBJECT IDENTIFIER ::= { mcrMGTMIBObjects 1 }
mcrManagementGroup	OBJECT IDENTIFIER ::= { mcrMGTMIBObjects 2 }

--
-- Textual conventions
--
YesNoValue ::= TEXTUAL-CONVENTION
    STATUS        current
    DESCRIPTION
              "Represents a YES or NO value."
    SYNTAX        INTEGER { notApplicable(-1), no(0), yes(1) }

OnOffValue ::= TEXTUAL-CONVENTION
    STATUS        current
    DESCRIPTION
        "Represents an ON or OFF value."
    SYNTAX        INTEGER { notApplicable(-1), off(0), on(1) }

EnableDisableValue ::= TEXTUAL-CONVENTION
    STATUS        current
    DESCRIPTION
        "Represents an ON or OFF value."
    SYNTAX        INTEGER { notApplicable(-1), disable(0), enable(1) }

Ipv4v6Address ::= TEXTUAL-CONVENTION
    DISPLAY-HINT	"255a"
    STATUS			current
    DESCRIPTION
        "An IPv4 or IPv6 address"
    SYNTAX  OCTET STRING (SIZE (0..255))


GenericTableIndex ::= TEXTUAL-CONVENTION
    DISPLAY-HINT	"d"
    STATUS			current
    DESCRIPTION
        "An arbitrary value that uniquely identifies the entity. The value
         should be a small, positive integer. Index values for different
         entities are not necessarily contiguous."
    SYNTAX Unsigned32 (1..2147483647)

 SlotNumber ::= TEXTUAL-CONVENTION
    DISPLAY-HINT      "d"
    STATUS            current
    DESCRIPTION
            "Chassis slot number. Valid values are 1 to the highest slot number
             the chassis supports. For example a MCR-1900 chassis the valid slot
             numbers are 1 to 19"
    SYNTAX Unsigned32(1..2147483647)


ContainerStatus ::= TEXTUAL-CONVENTION
    STATUS        current
    DESCRIPTION
        "When you perform a GET on this variable, one of
         the following values will be returned:
         1-Indicates that the container folder is active with no changes.
         2-Indicates that the container folder is active with change(s).
         Once you have completed setting the variables in a folder, you
         will want to submit your changes to the management module. To do
         this, set the Status variable to 4. If you want to discard the
         changes, set the Status variable to 6.
         4-Indicates that the changes in the container folder are to be
          submitted to the management module.
         6-Indicates that the changes in the container folder are to be
          discarded."
    SYNTAX		INTEGER {
         active(1),
         modified(2),
         applyChanges(4),
         discardChanges(6)
     }

AlertSeverityLevel ::= TEXTUAL-CONVENTION
    STATUS		current
    DESCRIPTION
        "The alert severity level of an event."
    SYNTAX	INTEGER {
        systemLevelFault(0),
        moduleLevelFault(1),
        persistantError(2),
        oneTimeError(3),
        significantEvent(4),
        normalOperation(5)
    }
--
-- mcrChassisGroup
--
--
-- mcrChassisTable
--
mcrChassisTable OBJECT-TYPE
    SYNTAX		SEQUENCE OF McrChassisEntry
    MAX-ACCESS	not-accessible
    STATUS		current
    DESCRIPTION
        "Table of chassis diagnostic type information."
    ::= { mcrChassisGroup 1 }

mcrChassisEntry OBJECT-TYPE
    SYNTAX		McrChassisEntry
    MAX-ACCESS	not-accessible
    STATUS		current
    DESCRIPTION
        "Entries of the table, each relating to a separate chassis."
    INDEX			{ mcrChassisIndex }
    ::= { mcrChassisTable 1 }

    McrChassisEntry ::=
        SEQUENCE {
            mcrChassisIndex					Unsigned32,
            chassisModelName					DisplayString,
            chassisModelDesc					DisplayString,
            chassisSerialNumber				DisplayString,
            chassisBootloaderVersion		DisplayString,
            chassisFirmwareVersion			DisplayString,
            chassisOutStandWarnAlarms		Unsigned32,
            chassisDiagStatus					Unsigned32,
            chassisTemperature				Integer32,
            chassisCfgHighTempThreshold	Integer32,
            chassisReset						YesNoValue,
            chassisCfgMgmtSlot						Unsigned32
        }

    mcrChassisIndex	OBJECT-TYPE
        SYNTAX		Unsigned32
        MAX-ACCESS	accessible-for-notify
        STATUS		current
        DESCRIPTION
            "This object identifies the chassis number."
        ::= { mcrChassisEntry 1 }

    chassisModelName	OBJECT-TYPE
        SYNTAX		DisplayString
        MAX-ACCESS	read-only
        STATUS		current
        DESCRIPTION
            "This object identifies the name of the chassis model.  For
             the 2-slot chassis, this is the product model."
        ::= { mcrChassisEntry 2 }

    chassisModelDesc		OBJECT-TYPE
        SYNTAX		DisplayString
        MAX-ACCESS	read-only
        STATUS		current
        DESCRIPTION
            "This object identifies a static description of the chassis."
    ::= { mcrChassisEntry 3 }

    chassisSerialNumber	OBJECT-TYPE
        SYNTAX		DisplayString (SIZE(0..16))
        MAX-ACCESS	read-write
        STATUS		current
        DESCRIPTION
            "This object identifies the chassis serial number.
             For the 2-slot chassis, this is writeable (and user-defined).  For
             other chassis, this is read-only (and reflects the chassis'
             actual serial number)."
        ::= { mcrChassisEntry 4 }

    chassisBootloaderVersion	OBJECT-TYPE
        SYNTAX		DisplayString
        MAX-ACCESS	read-only
        STATUS		current
        DESCRIPTION
            "This object identifies the chassis bootloader version.
             (Not applicable to 2-slot chassis.)"
        ::= { mcrChassisEntry 5 }

    chassisFirmwareVersion	OBJECT-TYPE
        SYNTAX		DisplayString
        MAX-ACCESS	read-only
        STATUS		current
        DESCRIPTION
            "This object identifies the chassis firmware version.
             (Not applicable to 2-slot chassis.)"
        ::= { mcrChassisEntry 6 }

    chassisOutStandWarnAlarms	OBJECT-TYPE
        SYNTAX		Unsigned32
        MAX-ACCESS	read-only
        STATUS		current
        DESCRIPTION
            "This object identifies the number of outstanding warnings and alarms for
             this chassis. If this value is not zero then user intervention is needed
             to resolve the outstanding warnings and alarms.
             (Not applicable to 2-slot chassis.)"
        ::= { mcrChassisEntry 7 }

    chassisDiagStatus	OBJECT-TYPE
        SYNTAX		Unsigned32
        MAX-ACCESS	read-only
        STATUS		current
        DESCRIPTION
            "This object identifies the chassis self-test diagnostics result.
             It will return zero if it passed and non-zero error code if it
             failed.  The following are possible non-zero error codes:
              1 - Firmware download required
              2 - Temperature sensor not functional
             (Not applicable to 2-slot chassis.)"
        ::= { mcrChassisEntry 8 }

    chassisTemperature	OBJECT-TYPE
        SYNTAX		Integer32
        MAX-ACCESS	read-only
        STATUS		current
        DESCRIPTION
            "This object identifies the current temperature of the chassis. The
             temperature returned will be either Celsius or Fahrenheit based on your
             current regional display settings.  If the temperature returned is -1
             then a problem with the temperature sensor has occurred and the current
             temperature is unknown.
             (Not applicable to 2-slot chassis.)"
        ::= { mcrChassisEntry 9 }

    chassisCfgHighTempThreshold	OBJECT-TYPE
        SYNTAX		Integer32
        MAX-ACCESS	read-write
        STATUS		current
        DESCRIPTION
            "This object identifies the chassis temperature high threshold. If the
             chassis temperature exceeds this threshold then an alert will be generated.
             The value read/written will be either Celsius or Fahrenheit based on your
             current regional display settings. The valid range for this threshold
             is 0 to 70 degrees Celsius or 32 to 158 degrees Fahrenheit.
             (Not applicable to 2-slot chassis.)"
        ::= { mcrChassisEntry 10 }

    chassisReset	OBJECT-TYPE
        SYNTAX		YesNoValue
        MAX-ACCESS	read-write
        STATUS		current
        DESCRIPTION
            "This object allows the resetting of the chassis (all modules). Reading this
             object always returns 0."
        ::= { mcrChassisEntry 11 }

    chassisCfgMgmtSlot	OBJECT-TYPE
        SYNTAX		Unsigned32(1..2)
        MAX-ACCESS	read-write
        STATUS		current
        DESCRIPTION
            "For the 2-slot chassis, this is the configured slot index of the
             management module.  This value only needs to be changed if the
             management module is physically installed in slot 2, rather than
             slot 1.  The management module should be restarted after changing
             this value."
        ::= { mcrChassisEntry 12 }

-- end of mcrChassisTable
--

--
-- mcrPsmuTable
--
mcrPsmuTable OBJECT-TYPE
    SYNTAX		SEQUENCE OF McrPsmuEntry
    MAX-ACCESS	not-accessible
    STATUS		current
    DESCRIPTION
        "Table of PSMU (Power Supply Monitoring Unit) diagnostic type
         information.
         (Not applicable to 2-slot chassis.)"
    ::= { mcrChassisGroup 2 }

mcrPsmuEntry OBJECT-TYPE
    SYNTAX		McrPsmuEntry
    MAX-ACCESS	not-accessible
    STATUS		current
    DESCRIPTION
        "Entries of the table, each relating to a separate PSMU."
    INDEX			{ mcrChassisIndex, mcrPsmuIndex }
    ::= { mcrPsmuTable 1 }

    McrPsmuEntry ::=
        SEQUENCE {
            mcrPsmuIndex						INTEGER,
            mcrPsmuModelName					DisplayString,
            mcrPsmuModelDesc					DisplayString,
            mcrPsmuPsuSerialNumber			DisplayString,
            mcrPsmuBootloaderVersion		DisplayString,
            mcrPsmuFirmwareVersion			DisplayString,
            mcrPsmuOutStandWarnAlarms		Unsigned32,
            mcrPsmuPsuStatus					INTEGER,
            mcrPsmuPsuVoltage					DisplayString,
            mcrPsmuPsuPowerUsage				DisplayString,
            mcrPsmuFanStatus					INTEGER,
            mcrPsmuFanSpeed					Unsigned32
    }

    mcrPsmuIndex	OBJECT-TYPE
        SYNTAX		INTEGER {
            a(1),
            b(2)
        }
        MAX-ACCESS	accessible-for-notify
        STATUS		current
        DESCRIPTION
            "This object identifies the PSMU bay as either A or B."
        ::= { mcrPsmuEntry 2 }

    mcrPsmuModelName	OBJECT-TYPE
        SYNTAX		DisplayString
        MAX-ACCESS	read-only
        STATUS		current
        DESCRIPTION
            "This object identifies the PSMU model."
        ::= { mcrPsmuEntry 3 }

    mcrPsmuModelDesc		OBJECT-TYPE
        SYNTAX		DisplayString
        MAX-ACCESS	read-only
        STATUS		current
        DESCRIPTION
            "This object identifies a static description of the power supply model
             present in the chassis"
    ::= { mcrPsmuEntry 4 }

    mcrPsmuPsuSerialNumber	OBJECT-TYPE
        SYNTAX		DisplayString (SIZE(0..16))
        MAX-ACCESS	read-only
        STATUS		current
        DESCRIPTION
            "This object identifies the PSU serial number."
        ::= { mcrPsmuEntry 5 }

    mcrPsmuBootloaderVersion	OBJECT-TYPE
        SYNTAX		DisplayString
        MAX-ACCESS	read-only
        STATUS		current
        DESCRIPTION
            "This object identifies the PSMU bootloader version."
        ::= { mcrPsmuEntry 6 }

    mcrPsmuFirmwareVersion	OBJECT-TYPE
        SYNTAX		DisplayString
        MAX-ACCESS	read-only
        STATUS		current
        DESCRIPTION
            "This object identifies the PSMU firmware version."
        ::= { mcrPsmuEntry 7 }

    mcrPsmuOutStandWarnAlarms	OBJECT-TYPE
        SYNTAX		Unsigned32
        MAX-ACCESS	read-only
        STATUS		current
        DESCRIPTION
            "This object identifies the number of outstanding warnings and alarms for
             this chassis. If this value is not zero then user intervention is needed
             to resolve the outstanding warnings and alarms"
        ::= { mcrPsmuEntry 8 }

    mcrPsmuPsuStatus	OBJECT-TYPE
        SYNTAX		INTEGER {
            notPresent(0),
            good(1),
            fail(2)
        }
        MAX-ACCESS	read-only
        STATUS		current
        DESCRIPTION
            "This object identifies if the PSMU power supply unit (PSU) status."
        ::= { mcrPsmuEntry 9 }

    mcrPsmuPsuVoltage	OBJECT-TYPE
        SYNTAX		DisplayString
        MAX-ACCESS	read-only
        STATUS		current
        DESCRIPTION
            "This object identifies the current PSU voltage being supplied."
        ::= { mcrPsmuEntry 10 }

    mcrPsmuPsuPowerUsage	OBJECT-TYPE
        SYNTAX		DisplayString
        MAX-ACCESS	read-only
        STATUS		current
        DESCRIPTION
            "This object identifies power currently being supplied to the chassis,
             in milliwatts.  A value of 0 indicate that the power supply is
             not in use"
        ::= { mcrPsmuEntry 11 }

    mcrPsmuFanStatus	OBJECT-TYPE
        SYNTAX		INTEGER {
            notPresent(0),
            good(1),
            fail(2)
        }
        MAX-ACCESS	read-only
        STATUS		current
        DESCRIPTION
            "This object identifies the fan status."
        ::= { mcrPsmuEntry 12 }

    mcrPsmuFanSpeed	OBJECT-TYPE
        SYNTAX		Unsigned32
        MAX-ACCESS	read-only
        STATUS		current
        DESCRIPTION
            "This object identifies the speed of the fan in RPM."
        ::= { mcrPsmuEntry 13 }

--
-- end of mcrPsmuTable
--

--
-- mcrChassisSlotTable
--
mcrChassisSlotTable OBJECT-TYPE
    SYNTAX		SEQUENCE OF McrChassisSlotEntry
    MAX-ACCESS	not-accessible
    STATUS		current
    DESCRIPTION
        "Table of chassis slot configuration, status and diagnostic type
         information."
    ::= { mcrChassisGroup 3 }

    mcrChassisSlotEntry OBJECT-TYPE
        SYNTAX      McrChassisSlotEntry
        MAX-ACCESS  not-accessible
        STATUS      current
        DESCRIPTION
            "Entries of the table, each relating to a separate slot in a chassis."
        INDEX   { mcrChassisIndex, mcrChassisSlotIndex }
        ::= { mcrChassisSlotTable 1 }

    McrChassisSlotEntry ::=
        SEQUENCE {
            mcrChassisSlotIndex					SlotNumber,
            mcrUserDefinedModuleName			DisplayString,
            mcrModuleModelName					DisplayString,
            mcrUnManagedModuleSlotName			DisplayString,
            mcrModuleSerialNumber				DisplayString,
            mcrModuleBootloaderVersion			DisplayString,
            mcrModuleFirmwareVersion			DisplayString,
            mcrModuleoOutStandWarnAlarms		Unsigned32,
            mcrModuleDiagStatus					Integer32,
            mcrModuleTypeInserted				INTEGER,
            mcrMediaConfigBackupRestore			INTEGER,
            mcrMediaBackedupModuleType			INTEGER,
            mcrChassisPwrUpSlotPwrState			OnOffValue,
            mcrCurrentPowerState				OnOffValue,
            mcrPowerScheduleEnable				INTEGER,
            mcrModuleReset						INTEGER,
            mcrModuleResetToFactory				INTEGER,
            mcrModuleModelDesc					DisplayString
        }

    mcrChassisSlotIndex	OBJECT-TYPE
        SYNTAX		SlotNumber
        MAX-ACCESS	accessible-for-notify
        STATUS		current
        DESCRIPTION
            "This object identifies the chassis slot number."
        ::= { mcrChassisSlotEntry 2 }

    mcrUserDefinedModuleName	OBJECT-TYPE
        SYNTAX		DisplayString
        MAX-ACCESS	read-only
        STATUS		current
        DESCRIPTION
            "This object identifies the user defined name of the module inserted
             in the slot.  The default name is the model name of the media converter module"
        ::= { mcrChassisSlotEntry 3 }

    mcrModuleModelName	OBJECT-TYPE
        SYNTAX		DisplayString
        MAX-ACCESS	read-only
        STATUS		current
        DESCRIPTION
            "This object identifies the model name of the module inserted
             in the slot."
        ::= { mcrChassisSlotEntry 4 }

    mcrUnManagedModuleSlotName	OBJECT-TYPE
        SYNTAX		DisplayString
        MAX-ACCESS	read-write
        STATUS		current
        DESCRIPTION
            "This object identifies the user defined name for an unmanaged
             module inserted in the slot. Unmanaged modules include all  perle
             C-1000, C-100, C-1110 and c-110 type modules."
        ::= { mcrChassisSlotEntry 5 }

    mcrModuleSerialNumber	OBJECT-TYPE
        SYNTAX		DisplayString (SIZE(0..16))
        MAX-ACCESS	read-only
        STATUS		current
        DESCRIPTION
            "This object identifies the serial number of the module inserted
             in the slot."
        ::= { mcrChassisSlotEntry 6 }

    mcrModuleBootloaderVersion	OBJECT-TYPE
        SYNTAX		DisplayString
        MAX-ACCESS	read-only
        STATUS		current
        DESCRIPTION
            "This object identifies the bootloader version of the module inserted
             in the slot."
        ::= { mcrChassisSlotEntry 7 }

    mcrModuleFirmwareVersion	OBJECT-TYPE
        SYNTAX		DisplayString
        MAX-ACCESS	read-only
        STATUS		current
        DESCRIPTION
            "This object identifies the firmware version of the module inserted
             in the slot."
        ::= { mcrChassisSlotEntry 8 }

    mcrModuleoOutStandWarnAlarms	OBJECT-TYPE
        SYNTAX		Unsigned32
        MAX-ACCESS	read-only
        STATUS		current
        DESCRIPTION
            "This object identifies the number of outstanding warnings and alarms for
             this module. If this value is not zero then user intervention is needed
             to resolve the outstanding warnings and alarms"
        ::= { mcrChassisSlotEntry 9 }

    mcrModuleDiagStatus	OBJECT-TYPE
        SYNTAX		Integer32
        MAX-ACCESS	read-only
        STATUS		current
        DESCRIPTION
            "This object identifies the module's self-test diagnostics result. It will
             return zero if it passed and non-zero error code if the module has
             failed.The following are possible non-zero error codes:
              1 - Media converter module's PHY is not functional.
              2 - Firmware download required"
        ::= { mcrChassisSlotEntry 10 }

    mcrModuleTypeInserted	OBJECT-TYPE
        SYNTAX		INTEGER {
            unManaged(-3),
            mcrMgt(-2),
            unknown(-1),
            empty(0),
            cm1000Fixed(1),
            cm100Fixed(2),
            cm1110RateConv(3),
            cm110RateConv(4),
            cm100mmFixed(5),
            cm1000mmFixed(6),
            cm10gFixed(7),
            exCM(8),
            cm10gt(9),
            cm4gpt(10)
        }
        MAX-ACCESS	read-only
        STATUS		current
        DESCRIPTION
            "This object identifies the module type inserted for this chassis slot."
        ::= { mcrChassisSlotEntry 11 }

    mcrMediaConfigBackupRestore	OBJECT-TYPE
        SYNTAX		INTEGER {
            disable(0),
            enable(1),
            notApplicable(2)
        }
        MAX-ACCESS	read-write
        STATUS		current
        DESCRIPTION
            "This object is applicable to media converter modules only. It identifies
             whether the media configuration will be automatically backed up to
             or restored from the management card's non-volatile memory"
        ::= { mcrChassisSlotEntry 12 }


    mcrMediaBackedupModuleType	OBJECT-TYPE
        SYNTAX		INTEGER {
            none(0),
            cm1000Fixed(1),
            cm100Fixed(2),
            cm1110RateConv(3),
            cm110RateConv(4),
            cm100mmFixed(5),
            cm1000mmFixed(6),
            cm10gFixed(7),
            exCM(8),
            cm10gt(9),
            cm4gpt(10)
        }
        MAX-ACCESS	read-only
        STATUS		current
        DESCRIPTION
            "This object identifies the media converter module type of the configuration that
             was backed up for the slot on the management card's non-volatile
             memory when the mcrMediaConfigBackupRestore object was enabled. "
        ::= { mcrChassisSlotEntry 13 }

    mcrChassisPwrUpSlotPwrState	OBJECT-TYPE
        SYNTAX		OnOffValue
        MAX-ACCESS	read-write
        STATUS		current
        DESCRIPTION
            "This object identifies the default power state of the slot when the
             chassis is initially powered up.  The current power state of the slot
             can be manually changed by writing to mcrCurrentPowerState object or
             dynamically changed via slot power schedule configuration.
             (Not applicable to 2-slot chassis.)"
        ::= { mcrChassisSlotEntry 14 }

    mcrCurrentPowerState	OBJECT-TYPE
        SYNTAX		OnOffValue
        MAX-ACCESS	read-write
        STATUS		current
        DESCRIPTION
            "Writing this object allows the current power state of the slot to be
             turned on or off. This object is not writable for management modules
             or the 2-slot chassis.
             Reading this object will return the current slot power state."
        ::= { mcrChassisSlotEntry 15 }

    mcrPowerScheduleEnable	OBJECT-TYPE
        SYNTAX		INTEGER {
            no(0),
            yes(1),
            notApplicable(2)
        }
        MAX-ACCESS	read-write
        STATUS		current
        DESCRIPTION
            "This object is not applicable to management modules. It identifies
             if power schedule is enabled for the slot.
             (Not applicable to 2-slot chassis.)"
        ::= { mcrChassisSlotEntry 16 }

    mcrModuleReset	OBJECT-TYPE
        SYNTAX		INTEGER {
            no(0),
            yes(1),
            notApplicable(2)
        }
        MAX-ACCESS	read-write
        STATUS		current
        DESCRIPTION
            "This object allows you to reset the module inserted in the slot."
        ::= { mcrChassisSlotEntry 17 }

    mcrModuleResetToFactory OBJECT-TYPE
        SYNTAX		INTEGER {
            no(0),
            yes(1),
            notApplicable(2)
        }
        MAX-ACCESS	read-write
        STATUS		current
        DESCRIPTION
            "This object allows you to reset to factory the module inserted in
             the slot. "
        ::= { mcrChassisSlotEntry 18 }

    mcrModuleModelDesc	OBJECT-TYPE
        SYNTAX		DisplayString
        MAX-ACCESS	read-only
        STATUS		current
        DESCRIPTION
            "This object identifies a static description of the media converter module present
             in the slot."
        ::= { mcrChassisSlotEntry 19 }


--
-- end of mcrChassisSlotTable
--

--
-- mcrModuleTypes
--
mcrModuleTypes	OBJECT IDENTIFIER
        ::= { mcrChassisGroup 4 }

--
-- cm1000Fixed - 1000 Mb fixed media Converter type modules
--
cm1000Fixed	OBJECT IDENTIFIER ::= { mcrModuleTypes 1 }

--
-- cm1000FixedTable
--
cm1000FixedTable	OBJECT-TYPE
    SYNTAX		SEQUENCE OF Cm1000FixedEntry
    MAX-ACCESS	not-accessible
    STATUS		current
    DESCRIPTION
        "Table of CM-1000 type media converter module's status type information."
    ::= { cm1000Fixed 1 }

    cm1000FixedEntry OBJECT-TYPE
        SYNTAX      Cm1000FixedEntry
        MAX-ACCESS  not-accessible
        STATUS      current
        DESCRIPTION
            "Entries of the table, each relating to a separate CM-1000 type
             media converter module."
        INDEX   { mcrChassisIndex, cm1000SlotIndex }
        ::= { cm1000FixedTable 1 }

    Cm1000FixedEntry ::=
        SEQUENCE {
            cm1000SlotIndex					SlotNumber,
            cm1000Modelname					DisplayString,
            cm1000ModelDesc					DisplayString,
            cm1000HwJmp5ConfigMode			INTEGER,
            cm1000HwSw1FiberAutoNeg			INTEGER,
            cm1000HwSw2LinkMode				INTEGER,
            cm1000HwSw3FiberFaultAlert		INTEGER,
            cm1000HwSw4Duplex					INTEGER,
            cm1000HwSw5Pause					INTEGER,
            cm1000HwSw6Loopback				INTEGER,
            cm1000FiberLinkStatus			INTEGER,
            cm1000FiberConnType				INTEGER,
            cm1000FiberAutoNegState			INTEGER,
            cm1000FiberSpeed					INTEGER,
            cm1000FiberDuplex					INTEGER,
            cm1000FiberPauseEnh				INTEGER,
            cm1000FiberLPRFStatus			INTEGER,
            cm1000FiberReceiveStatus		INTEGER,
            cm1000FiberLoopBack				EnableDisableValue,
            cm1000CopperLinkStatus			INTEGER,
            cm1000CopperConnType				INTEGER,
            cm1000CopperAutoNegState		INTEGER,
            cm1000CopperSpeed					INTEGER,
            cm1000CopperDuplex				INTEGER,
            cm1000CopperCrossOver			INTEGER,
            cm1000CopperPauseEnh				INTEGER,
            cm1000CopperLPRFStatus			INTEGER
        }

    cm1000SlotIndex	OBJECT-TYPE
        SYNTAX		SlotNumber
        MAX-ACCESS	not-accessible
        STATUS		current
        DESCRIPTION
            "The Slot number the CM-1000 type module is currently inserted"
    ::= { cm1000FixedEntry 2 }

    cm1000Modelname	OBJECT-TYPE
        SYNTAX		DisplayString
        MAX-ACCESS	read-only
        STATUS		current
        DESCRIPTION
            "This object identifies the model of media converter module present in the
             chassis"
    ::= { cm1000FixedEntry 3 }

    cm1000ModelDesc		OBJECT-TYPE
        SYNTAX		DisplayString
        MAX-ACCESS	read-only
        STATUS		current
        DESCRIPTION
            "This object identifies a static description of the media converter module present
             in the chassis"
    ::= { cm1000FixedEntry 4 }

    cm1000HwJmp5ConfigMode		OBJECT-TYPE
        SYNTAX		INTEGER {
            hardwareSwitches(0),
            auto(1)
        }
        MAX-ACCESS	read-only
        STATUS		current
        DESCRIPTION
            "This object identifies the media converter module's ConfigMode, set by hardware
             jumper J5 on the media converter module. When this object is set to
             hardwareSwitches(0), the media converter module will disable configuration
             control from the management module's software and all configuration
             control comes from the media converter module's hardware switches or jumpers. "
    ::= { cm1000FixedEntry 5 }


    cm1000HwSw1FiberAutoNeg  OBJECT-TYPE
        SYNTAX 		INTEGER{
            swDownDisabled(0),
            swUpEnabled(1)
        }
        MAX-ACCESS read-only
        STATUS 		current
        DESCRIPTION
            "Media converter module's current switch setting for fiber Auto-Negotiation."
    ::= { cm1000FixedEntry 6 }

    cm1000HwSw2LinkMode OBJECT-TYPE
        SYNTAX 		INTEGER {
            swDownSmartLinkPassthrough(0),
            swUpStandard(1)
        }
        MAX-ACCESS read-only
        STATUS 		current
        DESCRIPTION
            "Media converter module's current switch setting for Link Mode."
    ::= { cm1000FixedEntry 7 }

    cm1000HwSw3FiberFaultAlert OBJECT-TYPE
        SYNTAX 		INTEGER {
            swDownDisabled(0),
            swUpEnabled(1)
        }
        MAX-ACCESS read-only
        STATUS 		current
        DESCRIPTION
            "Media converter module's current switch setting for Fiber Fault Alert."
    ::= { cm1000FixedEntry 8 }

    cm1000HwSw4Duplex OBJECT-TYPE
        SYNTAX 		INTEGER {
            swDownHalf(0),
            swUpAuto(1)
        }
        MAX-ACCESS read-only
        STATUS 		current
        DESCRIPTION
            "Media converter module's current switch setting for copper duplex."
    ::= { cm1000FixedEntry 9 }

    cm1000HwSw5Pause OBJECT-TYPE
        SYNTAX 		INTEGER {
            swDownDisabled(0),
            swUpEnabled(1)
        }
        MAX-ACCESS read-only
        STATUS 		current
        DESCRIPTION
            "Media converter module's current switch setting for copper pause (flow control)."
    ::= { cm1000FixedEntry 10 }

    cm1000HwSw6Loopback OBJECT-TYPE
        SYNTAX 		INTEGER {
            swDownEnabled(0),
            swUpDisabled(1)
        }
        MAX-ACCESS read-only
        STATUS 		current
        DESCRIPTION
            "Media converter module's current switch setting for fiber loopback mode."
    ::= { cm1000FixedEntry 11 }

    cm1000FiberLinkStatus OBJECT-TYPE
        SYNTAX 		INTEGER {
            down(0),
            up(1)
        }
        MAX-ACCESS read-only
        STATUS 		current
        DESCRIPTION
            "Media converter module's current fiber link status."
    ::= { cm1000FixedEntry 12 }

    cm1000FiberConnType OBJECT-TYPE
        SYNTAX 		INTEGER {
            sc(0),
            lc(1),
            st(2),
            sfp(3),
            fc(5),
            mtrj(6)
        }
        MAX-ACCESS read-only
        STATUS 		current
        DESCRIPTION
            "Media converter module's fiber port connector type."
    ::= { cm1000FixedEntry 13 }

    cm1000FiberAutoNegState OBJECT-TYPE
        SYNTAX		INTEGER {
            disabled(0),
            complete(1),
            inProgress(2)
        }
        MAX-ACCESS	read-only
        STATUS 		current
        DESCRIPTION
            "Media converter module's current fiber auto-negotiation state."
    ::= { cm1000FixedEntry 14 }

    cm1000FiberSpeed OBJECT-TYPE
        SYNTAX 		INTEGER {
            speed1000Mbps(2)
        }
        MAX-ACCESS	read-only
        STATUS 		current
        DESCRIPTION
            "Media converter module's fiber port speed in megabits per second."
    ::= { cm1000FixedEntry 15 }

    cm1000FiberDuplex OBJECT-TYPE
        SYNTAX		INTEGER {
            half(0),
            full(1)
        }
        MAX-ACCESS	read-only
        STATUS		current
        DESCRIPTION
            "If fiber auto-negotiation state is complete then this object
            indicates the media converter module's current fiber auto-negotiated duplex
            setting. If auto-negotiation is not complete then the value returned should be
             ignored."
    ::= { cm1000FixedEntry 16 }

    cm1000FiberPauseEnh OBJECT-TYPE
        SYNTAX INTEGER {
            disabled(0),
            symmetrical(1),
            asymmetricalTx(2),
            asymmetricalRx(3)
        }
        MAX-ACCESS read-only
        STATUS current
        DESCRIPTION
            "If fiber auto-negotiation state is complete then this object indicates
             the media converter module's current fiber auto-negotiated pause setting. If
             auto-negotiation is not complete then the value returned should be ignored."
    ::= { cm1000FixedEntry 17 }

    cm1000FiberLPRFStatus OBJECT-TYPE
        SYNTAX	INTEGER {
            ok(0),
            offline(1),
            linkFault(2),
            autoNegError(3)
        }
        MAX-ACCESS	read-only
        STATUS	current
        DESCRIPTION
            "Media converter module's fiber Link Partner Remote Fault status."
    ::= { cm1000FixedEntry 18 }

    cm1000FiberReceiveStatus		OBJECT-TYPE
        SYNTAX	INTEGER {
            fault(0),
            ok(1)
        }
        MAX-ACCESS	read-write
        STATUS	current
        DESCRIPTION
            "This object identifies the status of whether light is being received
             on the fiber port"
    ::= { cm1000FixedEntry 19 }

    cm1000FiberLoopBack		OBJECT-TYPE
        SYNTAX	EnableDisableValue
        MAX-ACCESS	read-write
        STATUS	current
        DESCRIPTION
            "Media converter module's current fiber loopback mode setting. Writing to this
             object will change the current settings. This object is read-only if
             the media converter module's ConfigMode jumper is set to hardwareSwitches(0)."
    ::= { cm1000FixedEntry 20 }

    cm1000CopperLinkStatus OBJECT-TYPE
        SYNTAX	INTEGER {
            down(0),
            up(1)
        }
        MAX-ACCESS	read-only
        STATUS	current
        DESCRIPTION
            "Media converter module's current copper link status."
    ::= { cm1000FixedEntry 21 }

    cm1000CopperConnType OBJECT-TYPE
        SYNTAX INTEGER {
            rj45(0)
        }
        MAX-ACCESS read-only
        STATUS current
        DESCRIPTION
            "Media converter module's copper connector type."
    ::= { cm1000FixedEntry 22 }

    cm1000CopperAutoNegState OBJECT-TYPE
        SYNTAX INTEGER {
            disabled(0),
            complete(1),
            inProgress(2)
        }
        MAX-ACCESS read-only
        STATUS current
        DESCRIPTION
            "Media converter module's current copper auto-negotiation state."
    ::= { cm1000FixedEntry 23 }

    cm1000CopperSpeed OBJECT-TYPE
        SYNTAX 		INTEGER {
            speed1000Mbps(2)
        }
        MAX-ACCESS	read-only
        STATUS 		current
        DESCRIPTION
            "Media converter module's copper port speed in megabits per second."
    ::= { cm1000FixedEntry 24 }

    cm1000CopperDuplex OBJECT-TYPE
        SYNTAX INTEGER {
            half(0),
            full(1)
        }
        MAX-ACCESS read-only
        STATUS current
        DESCRIPTION
            "If copper auto-negotiation state is complete then this object
            indicates the media converter module's current copper auto-negotiated duplex
            setting. If auto-negotiation is not complete then the value returned
            should be ignored."
    ::= { cm1000FixedEntry 25 }

    cm1000CopperCrossOver OBJECT-TYPE
        SYNTAX INTEGER {
            mdi(0),
            mdix(1)
        }
        MAX-ACCESS read-only
        STATUS current
        DESCRIPTION
            "If copper auto-negotiation state is complete then this object
            indicates the media converter module's current copper auto-negotiated MDI/MDI-X
            setting. If auto-negotiation is not complete then the value returned
            should be ignored."
    ::= { cm1000FixedEntry 26 }

    cm1000CopperPauseEnh OBJECT-TYPE
        SYNTAX INTEGER {
            disabled(0),
            symmetrical(1),
            asymmetricalTx(2),
            asymmetricalRx(3)
        }
        MAX-ACCESS read-only
        STATUS current
        DESCRIPTION
            "If copper auto-negotiation state is complete then this object indicates
             the media converter module's current copper auto-negotiated pause setting. If
             auto-negotiation is not complete then the value returned should be ignored."
    ::= { cm1000FixedEntry 27 }

    cm1000CopperLPRFStatus OBJECT-TYPE
        SYNTAX INTEGER {
            ok(0),
            remoteFault(1)
        }
        MAX-ACCESS read-only
        STATUS current
        DESCRIPTION
            "Media converter module's copper Link Partner Remote Fault status."
    ::= { cm1000FixedEntry 28 }
--
-- cm1000FixedTable
--
--
-- cm1000ConfigTable
--
cm1000ConfigTable	OBJECT-TYPE
    SYNTAX		SEQUENCE OF Cm1000ConfigEntry
    MAX-ACCESS	not-accessible
    STATUS		current
    DESCRIPTION
        "Table of CM-1000 type media converter module's configuration type information."
    ::= { cm1000Fixed 2 }

    cm1000ConfigEntry OBJECT-TYPE
        SYNTAX      Cm1000ConfigEntry
        MAX-ACCESS  not-accessible
        STATUS      current
        DESCRIPTION
            "Entries of the table, each relating to a separate CM-1000 type
             media converter module."
        INDEX   { mcrChassisIndex, cm1000ConfigSlotIndex }
        ::= { cm1000ConfigTable 1 }

    Cm1000ConfigEntry ::=
        SEQUENCE {
            cm1000ConfigSlotIndex			SlotNumber,
            cm1000ConfigStatus				ContainerStatus,
            cm1000ConfigModuleName			DisplayString,
            cm1000ConfigLinkMode				INTEGER,
            cm1000ConfigFiberFaultAlert	EnableDisableValue,
            cm1000ConfigJumboPackets		EnableDisableValue,
            cm1000ConfigFiberPortName		DisplayString,
            cm1000ConfigFiberPortEnable	YesNoValue,
            cm1000ConfigFiberAutoNeg		EnableDisableValue,
            cm1000ConfigCopperPortName		DisplayString,
            cm1000ConfigCopperPortEnable	YesNoValue,
            cm1000ConfigCopperDuplex		INTEGER,
            cm1000ConfigCopperPauseEnh		INTEGER,
            cm1000ConfigCopperLowPower		OnOffValue
        }

    cm1000ConfigSlotIndex	OBJECT-TYPE
        SYNTAX		SlotNumber
        MAX-ACCESS	not-accessible
        STATUS		current
        DESCRIPTION
            "The Slot number the CM-1000 type module is currently inserted"
    ::= { cm1000ConfigEntry 2 }

    cm1000ConfigStatus OBJECT-TYPE
        SYNTAX      ContainerStatus
        MAX-ACCESS  read-write
        STATUS      current
        DESCRIPTION
          "When you perform a GET on this variable, one of
            the following values will be returned:
            1-Indicates that the container folder is active with no changes.
            2-Indicates that the container folder is active with change(s).
            Once you have completed setting the variables in a folder, you
            will want to submit your changes to the management module. To do
            this, set the Status variable to 4. If you want to discard the
            changes, set the Status variable to 6.
            4-Indicates that the changes in the container folder are to be
              submitted to the management module, verified and and saved to flash.
            6-Indicates that the changes in the container folder are to be
              discarded."
        ::= { cm1000ConfigEntry 3 }

    cm1000ConfigModuleName OBJECT-TYPE
        SYNTAX		DisplayString(SIZE(0..63))
        MAX-ACCESS	read-write
        STATUS		current
        DESCRIPTION
            "This object identifies a user configurable name for the media converter module
             present in the chassis. "
    ::= { cm1000ConfigEntry 4 }

    cm1000ConfigLinkMode	OBJECT-TYPE
        SYNTAX		INTEGER {
            standard(0),
            smartLinkPassthrough(1)
        }
        MAX-ACCESS	read-write
        STATUS		current
        DESCRIPTION
            "This object identifies the Link Mode for the media converter module. This object
            is read-only if the media converter module's ConfigMode jumper is set to
            hardwareSwitches(0)."
    ::= { cm1000ConfigEntry 5 }

    cm1000ConfigFiberFaultAlert	OBJECT-TYPE
        SYNTAX		EnableDisableValue
        MAX-ACCESS	read-write
        STATUS		current
        DESCRIPTION
            "This object identifies the Fiber Fault Alert setting for the media
             module. This object is read-only if the media converter module's ConfigMode
             jumper is set to hardwareSwitches(0). "
    ::= { cm1000ConfigEntry 6 }

    cm1000ConfigJumboPackets OBJECT-TYPE
        SYNTAX		EnableDisableValue
        MAX-ACCESS	read-write
        STATUS		current
        DESCRIPTION
            "This object identifies the Jumbo Packet setting for the media converter module
             present in the chassis. "
    ::= { cm1000ConfigEntry 7 }

    cm1000ConfigFiberPortName OBJECT-TYPE
        SYNTAX		DisplayString(SIZE(0..8))
        MAX-ACCESS	read-write
        STATUS 		current
        DESCRIPTION
            "This object identifies a user definable name for the fiber port."
    ::= { cm1000ConfigEntry 8 }

    cm1000ConfigFiberPortEnable OBJECT-TYPE
        SYNTAX		YesNoValue
        MAX-ACCESS	read-write
        STATUS 		current
        DESCRIPTION
            "This object identifies whether the fiber port is enabled. "
    ::= { cm1000ConfigEntry 9 }

    cm1000ConfigFiberAutoNeg OBJECT-TYPE
        SYNTAX 		EnableDisableValue
        MAX-ACCESS	read-write
        STATUS 		current
        DESCRIPTION
            "This object identifies the wither fiber auto-negotiation  is
             enabled. This object is read-only if the media converter module's ConfigMode
             jumper is set to hardwareSwitches(0)."
    ::= { cm1000ConfigEntry 10 }

    cm1000ConfigCopperPortName OBJECT-TYPE
        SYNTAX DisplayString(SIZE(0..8))
        MAX-ACCESS read-write
        STATUS current
        DESCRIPTION
            "This object identifies a user definable name for the copper port. "
    ::= { cm1000ConfigEntry 11 }

    cm1000ConfigCopperPortEnable OBJECT-TYPE
        SYNTAX	YesNoValue
        MAX-ACCESS	read-write
        STATUS	current
        DESCRIPTION
            "This object identifies whether the fiber port is enabled. "
    ::= { cm1000ConfigEntry 12 }

    cm1000ConfigCopperDuplex	OBJECT-TYPE
        SYNTAX INTEGER {
            half(1),
            auto(2)
        }
        MAX-ACCESS read-write
        STATUS current
        DESCRIPTION
            "This object identifies the duplex settings for the copper port.
             This object is read-only if the media converter module's ConfigMode jumper
             is set to hardwareSwitches(0)."
    ::= { cm1000ConfigEntry 13 }

    cm1000ConfigCopperPauseEnh OBJECT-TYPE
        SYNTAX INTEGER {
            disabled(0),
            symmetrical(1),
            asymmetricalTx(2),
            symmAsymRx(3)
        }
        MAX-ACCESS read-write
        STATUS current
        DESCRIPTION
            "This object identifies the copper pause (flow control) setting that
             is a advertised. The settings can be disabled, advertise symmetrical,
             advertise asymmetrical TX or advertise symmetrical and asymmetrical
             RX. This object is read-only if the media converter module's ConfigMode jumper
             is set to hardwareSwitches(0)."
    ::= { cm1000ConfigEntry 14 }

    cm1000ConfigCopperLowPower OBJECT-TYPE
        SYNTAX OnOffValue
        MAX-ACCESS read-write
        STATUS current
        DESCRIPTION
            "This object identifies the copper low power setting for the media converter module
             present in the chassis. "
    ::= { cm1000ConfigEntry 15 }
--
-- cm1000ConfigTable
--

--
-- cm1000LedTable
--
cm1000LedTable	OBJECT-TYPE
    SYNTAX		SEQUENCE OF Cm1000LedEntry
    MAX-ACCESS	not-accessible
    STATUS		current
    DESCRIPTION
        "Table of CM-1000 type media converter module's LED status information."
    ::= { cm1000Fixed 3 }

    cm1000LedEntry OBJECT-TYPE
        SYNTAX      Cm1000LedEntry
        MAX-ACCESS  not-accessible
        STATUS      current
        DESCRIPTION
            "Entries of the table, each relating to a separate CM-1000 type
             media converter module."
        INDEX   { mcrChassisIndex, cm1000LedSlotIndex }
        ::= { cm1000LedTable 1 }

    Cm1000LedEntry ::=
        SEQUENCE {
            cm1000LedSlotIndex	SlotNumber,
            cm1000LedPWR			INTEGER,
            cm1000LedLKF			INTEGER,
            cm1000LedLKC			INTEGER
        }

    cm1000LedSlotIndex	OBJECT-TYPE
        SYNTAX		SlotNumber
        MAX-ACCESS	not-accessible
        STATUS		current
        DESCRIPTION
            "The Slot number the CM-1000 type module is currently inserted"
    ::= { cm1000LedEntry 2 }

    cm1000LedPWR	OBJECT-TYPE
        SYNTAX		INTEGER {
            off(0),
            onGreen(1),
            blinking(2)
        }
        MAX-ACCESS	read-only
        STATUS		current
        DESCRIPTION
            "This object identifies the status of the power (PWR) LED on the media converter module.
             Possible status values are:
                 off(0) - No power to the module
                 onGreen(1) - Power being applied to module
                 blinking(2) - Fiber loopback enabled"
    ::= { cm1000LedEntry 3 }

    cm1000LedLKF	OBJECT-TYPE
        SYNTAX		INTEGER {
            off(0),
            on(1)
        }
        MAX-ACCESS	read-only
        STATUS		current
        DESCRIPTION
            "This object identifies the status of the link copper (LKC) LED on the
             media converter module.
             Possible status values are:
                 off(0) - No fiber link
                 on(1) - Fiber link present"
    ::= { cm1000LedEntry 4 }

    cm1000LedLKC	OBJECT-TYPE
        SYNTAX		INTEGER {
            off(0),
            on(1)
        }
        MAX-ACCESS	read-only
        STATUS		current
        DESCRIPTION
            "This object identifies the status of the link copper (LKC) LED on the
             media converter module.
             Possible status values are:
                 off(0) - No copper link
                 on(1) - Copper link present"
    ::= { cm1000LedEntry 5 }

--
-- end of cm1000LedTable
--

--
-- end of cm1000Fixed
--

-- cm1000mmFixed - 1000 Mb fixed media Converter type modules
--
cm1000mmFixed	OBJECT IDENTIFIER ::= { mcrModuleTypes 6 }

--
-- cm1000mmFixedTable
--
cm1000mmFixedTable	OBJECT-TYPE
    SYNTAX		SEQUENCE OF Cm1000mmFixedEntry
    MAX-ACCESS	not-accessible
    STATUS		current
    DESCRIPTION
        "Table of CM-1000MM type media converter module's status type information."
    ::= { cm1000mmFixed 1 }

    cm1000mmFixedEntry OBJECT-TYPE
        SYNTAX      Cm1000mmFixedEntry
        MAX-ACCESS  not-accessible
        STATUS      current
        DESCRIPTION
            "Entries of the table, each relating to a separate CM-1000MM type
             media converter module."
        INDEX   { mcrChassisIndex, cm1000mmSlotIndex }
        ::= { cm1000mmFixedTable 1 }

    Cm1000mmFixedEntry ::=
        SEQUENCE {
            cm1000mmSlotIndex					SlotNumber,
            cm1000mmModelname					DisplayString,
            cm1000mmModelDesc					DisplayString,
            cm1000mmHwJmp5ConfigMode			INTEGER,
            cm1000mmHwSw1FiberAutoNeg			INTEGER,
            cm1000mmHwSw2LinkMode				INTEGER,
            cm1000mmHwSw3FiberFaultAlert		INTEGER,
            cm1000mmHwSw4Loopback1				INTEGER,
            cm1000mmHwSw5Loopback2				INTEGER,

            cm1000mmFiber1LinkStatus			INTEGER,
            cm1000mmFiber1ConnType				INTEGER,
            cm1000mmFiber1AutoNegState			INTEGER,
            cm1000mmFiber1Speed					INTEGER,
            cm1000mmFiber1Duplex					INTEGER,
            cm1000mmFiber1PauseEnh				INTEGER,
            cm1000mmFiber1LPRFStatus			INTEGER,
            cm1000mmFiber1ReceiveStatus		INTEGER,

            cm1000mmFiber2LinkStatus			INTEGER,
            cm1000mmFiber2ConnType				INTEGER,
            cm1000mmFiber2AutoNegState			INTEGER,
            cm1000mmFiber2Speed					INTEGER,
            cm1000mmFiber2Duplex					INTEGER,
            cm1000mmFiber2PauseEnh				INTEGER,
            cm1000mmFiber2LPRFStatus			INTEGER,
            cm1000mmFiber2ReceiveStatus		INTEGER,

            cm1000mmFiberLoopBack				INTEGER
        }

    cm1000mmSlotIndex	OBJECT-TYPE
        SYNTAX		SlotNumber
        MAX-ACCESS	not-accessible
        STATUS		current
        DESCRIPTION
            "The Slot number the CM-1000MM type module is currently inserted"
    ::= { cm1000mmFixedEntry 2 }

    cm1000mmModelname	OBJECT-TYPE
        SYNTAX		DisplayString
        MAX-ACCESS	read-only
        STATUS		current
        DESCRIPTION
            "This object identifies the model of media converter module present in the
             chassis"
    ::= { cm1000mmFixedEntry 3 }

    cm1000mmModelDesc		OBJECT-TYPE
        SYNTAX		DisplayString
        MAX-ACCESS	read-only
        STATUS		current
        DESCRIPTION
            "This object identifies a static description of the media converter module present
             in the chassis"
    ::= { cm1000mmFixedEntry 4 }

    cm1000mmHwJmp5ConfigMode		OBJECT-TYPE
        SYNTAX		INTEGER {
            hardwareSwitches(0),
            auto(1)
        }
        MAX-ACCESS	read-only
        STATUS		current
        DESCRIPTION
            "This object identifies the media converter module's ConfigMode, set by hardware
             jumper J5 on the media converter module. When this object is set to
             hardwareSwitches(0), the media converter module will disable configuration
             control from the management module's software and all configuration
             control comes from the media converter module's hardware switches or jumpers. "
    ::= { cm1000mmFixedEntry 5 }


    cm1000mmHwSw1FiberAutoNeg  OBJECT-TYPE
        SYNTAX 		INTEGER{
            swDownDisabled(0),
            swUpEnabled(1)
        }
        MAX-ACCESS read-only
        STATUS 		current
        DESCRIPTION
            "Media converter module's current switch setting for fiber Auto-Negotiation."
    ::= { cm1000mmFixedEntry 6 }

    cm1000mmHwSw2LinkMode OBJECT-TYPE
        SYNTAX 		INTEGER {
            swDownSmartLinkPassthrough(0),
            swUpStandard(1)
        }
        MAX-ACCESS read-only
        STATUS 		current
        DESCRIPTION
            "Media converter module's current switch setting for Link Mode."
    ::= { cm1000mmFixedEntry 7 }

    cm1000mmHwSw3FiberFaultAlert OBJECT-TYPE
        SYNTAX 		INTEGER {
            swDownDisabled(0),
            swUpEnabled(1)
        }
        MAX-ACCESS read-only
        STATUS 		current
        DESCRIPTION
            "Media converter module's current switch setting for Fiber Fault Alert."
    ::= { cm1000mmFixedEntry 8 }

    cm1000mmHwSw4Loopback1 OBJECT-TYPE
        SYNTAX 		INTEGER {
            swDownEnabled(0),
            swUpDisabled(1)
        }
        MAX-ACCESS read-only
        STATUS 		current
        DESCRIPTION
            "Media converter module's current switch setting for loopback (fiber port 1)."
    ::= { cm1000mmFixedEntry 9 }

    cm1000mmHwSw5Loopback2 OBJECT-TYPE
        SYNTAX 		INTEGER {
            swDownEnabled(0),
            swUpDisabled(1)
        }
        MAX-ACCESS read-only
        STATUS 		current
        DESCRIPTION
            "Media converter module's current switch setting for loopback (fiber port 2)."
    ::= { cm1000mmFixedEntry 10 }

    cm1000mmFiber1LinkStatus OBJECT-TYPE
        SYNTAX 		INTEGER {
            down(0),
            up(1)
        }
        MAX-ACCESS read-only
        STATUS 		current
        DESCRIPTION
            "Media converter module's current fiber link status (port 1)."
    ::= { cm1000mmFixedEntry 12 }

    cm1000mmFiber1ConnType OBJECT-TYPE
        SYNTAX 		INTEGER {
            sc(0),
            lc(1),
            st(2),
            sfp(3),
            fc(5),
            mtrj(6)
        }
        MAX-ACCESS read-only
        STATUS 		current
        DESCRIPTION
            "Media converter module's fiber port connector type (port 1)."
    ::= { cm1000mmFixedEntry 13 }

    cm1000mmFiber1AutoNegState OBJECT-TYPE
        SYNTAX		INTEGER {
            disabled(0),
            complete(1),
            inProgress(2)
        }
        MAX-ACCESS	read-only
        STATUS 		current
        DESCRIPTION
            "Media converter module's current fiber auto-negotiation state (port 1)."
    ::= { cm1000mmFixedEntry 14 }

    cm1000mmFiber1Speed OBJECT-TYPE
        SYNTAX 		INTEGER {
            speed1000Mbps(2)
        }
        MAX-ACCESS	read-only
        STATUS 		current
        DESCRIPTION
            "Media converter module's fiber port speed in megabits per second (port 1)."
    ::= { cm1000mmFixedEntry 15 }

    cm1000mmFiber1Duplex OBJECT-TYPE
        SYNTAX		INTEGER {
            half(0),
            full(1)
        }
        MAX-ACCESS	read-only
        STATUS		current
        DESCRIPTION
            "If fiber auto-negotiation state is complete then this object
            indicates the media converter module's current fiber auto-negotiated duplex
            setting. If auto-negotiation is not complete then the value returned should be
             ignored. (Port 1)"
    ::= { cm1000mmFixedEntry 16 }

    cm1000mmFiber1PauseEnh OBJECT-TYPE
        SYNTAX INTEGER {
            disabled(0),
            symmetrical(1),
            asymmetricalTx(2),
            asymmetricalRx(3)
        }
        MAX-ACCESS read-only
        STATUS current
        DESCRIPTION
            "If fiber auto-negotiation state is complete then this object indicates
             the media converter module's current fiber auto-negotiated pause setting. If
             auto-negotiation is not complete then the value returned should be ignored.
             (Port 1)"
    ::= { cm1000mmFixedEntry 17 }

    cm1000mmFiber1LPRFStatus OBJECT-TYPE
        SYNTAX	INTEGER {
            ok(0),
            offline(1),
            linkFault(2),
            autoNegError(3)
        }
        MAX-ACCESS	read-only
        STATUS	current
        DESCRIPTION
            "Media converter module's fiber Link Partner Remote Fault status (port 1)."
    ::= { cm1000mmFixedEntry 18 }

    cm1000mmFiber1ReceiveStatus		OBJECT-TYPE
        SYNTAX	INTEGER {
            fault(0),
            ok(1)
        }
        MAX-ACCESS	read-write
        STATUS	current
        DESCRIPTION
            "This object identifies the status of whether light is being received
             on the fiber port (port 1)"
    ::= { cm1000mmFixedEntry 19 }

    cm1000mmFiber2LinkStatus OBJECT-TYPE
        SYNTAX 		INTEGER {
            down(0),
            up(1)
        }
        MAX-ACCESS read-only
        STATUS 		current
        DESCRIPTION
            "Media converter module's current fiber link status (port 2)."
    ::= { cm1000mmFixedEntry 20 }

    cm1000mmFiber2ConnType OBJECT-TYPE
        SYNTAX 		INTEGER {
            sc(0),
            lc(1),
            st(2),
            sfp(3),
            fc(5),
            mtrj(6)
        }
        MAX-ACCESS read-only
        STATUS 		current
        DESCRIPTION
            "Media converter module's fiber port connector type (port 2)."
    ::= { cm1000mmFixedEntry 21 }

    cm1000mmFiber2AutoNegState OBJECT-TYPE
        SYNTAX		INTEGER {
            disabled(0),
            complete(1),
            inProgress(2)
        }
        MAX-ACCESS	read-only
        STATUS 		current
        DESCRIPTION
            "Media converter module's current fiber auto-negotiation state (port 2)."
    ::= { cm1000mmFixedEntry 22 }

    cm1000mmFiber2Speed OBJECT-TYPE
        SYNTAX 		INTEGER {
            speed1000Mbps(2)
        }
        MAX-ACCESS	read-only
        STATUS 		current
        DESCRIPTION
            "Media converter module's fiber port speed in megabits per second (port 2)."
    ::= { cm1000mmFixedEntry 23 }

    cm1000mmFiber2Duplex OBJECT-TYPE
        SYNTAX		INTEGER {
            half(0),
            full(1)
        }
        MAX-ACCESS	read-only
        STATUS		current
        DESCRIPTION
            "If fiber auto-negotiation state is complete then this object
            indicates the media converter module's current fiber auto-negotiated duplex
            setting. If auto-negotiation is not complete then the value returned should be
             ignored. (Port 2)"
    ::= { cm1000mmFixedEntry 24 }

    cm1000mmFiber2PauseEnh OBJECT-TYPE
        SYNTAX INTEGER {
            disabled(0),
            symmetrical(1),
            asymmetricalTx(2),
            asymmetricalRx(3)
        }
        MAX-ACCESS read-only
        STATUS current
        DESCRIPTION
            "If fiber auto-negotiation state is complete then this object indicates
             the media converter module's current fiber auto-negotiated pause setting. If
             auto-negotiation is not complete then the value returned should be ignored.
             (Port 2)"
    ::= { cm1000mmFixedEntry 25 }

    cm1000mmFiber2LPRFStatus OBJECT-TYPE
        SYNTAX	INTEGER {
            ok(0),
            offline(1),
            linkFault(2),
            autoNegError(3)
        }
        MAX-ACCESS	read-only
        STATUS	current
        DESCRIPTION
            "Media converter module's fiber Link Partner Remote Fault status (port 2)."
    ::= { cm1000mmFixedEntry 26 }

    cm1000mmFiber2ReceiveStatus		OBJECT-TYPE
        SYNTAX	INTEGER {
            fault(0),
            ok(1)
        }
        MAX-ACCESS	read-write
        STATUS	current
        DESCRIPTION
            "This object identifies the status of whether light is being received
             on the fiber port (port 2)"
    ::= { cm1000mmFixedEntry 27 }

    cm1000mmFiberLoopBack		OBJECT-TYPE
        SYNTAX	INTEGER {
            disabled(0),
            port1(1),
            port2(2)
        }
        MAX-ACCESS	read-write
        STATUS	current
        DESCRIPTION
            "Media converter module's current fiber loopback mode setting. Writing to this
             object will change the current settings. This object is read-only if
             the media converter module's ConfigMode jumper is set to hardwareSwitches(0)."
    ::= { cm1000mmFixedEntry 28 }

--
-- cm1000mmFixedTable
--
--
-- cm1000mmConfigTable
--
cm1000mmConfigTable	OBJECT-TYPE
    SYNTAX		SEQUENCE OF Cm1000mmConfigEntry
    MAX-ACCESS	not-accessible
    STATUS		current
    DESCRIPTION
        "Table of CM-1000MM type media converter module's configuration type information."
    ::= { cm1000mmFixed 2 }

    cm1000mmConfigEntry OBJECT-TYPE
        SYNTAX      Cm1000mmConfigEntry
        MAX-ACCESS  not-accessible
        STATUS      current
        DESCRIPTION
            "Entries of the table, each relating to a separate CM-1000MM type
             media converter module."
        INDEX   { mcrChassisIndex, cm1000mmConfigSlotIndex }
        ::= { cm1000mmConfigTable 1 }

    Cm1000mmConfigEntry ::=
        SEQUENCE {
            cm1000mmConfigSlotIndex			SlotNumber,
            cm1000mmConfigStatus				ContainerStatus,
            cm1000mmConfigModuleName			DisplayString,
            cm1000mmConfigLinkMode				INTEGER,
            cm1000mmConfigFiberFaultAlert	EnableDisableValue,
            cm1000mmConfigJumboPackets		EnableDisableValue,
            cm1000mmConfigFiberAutoNeg		EnableDisableValue,
            cm1000mmConfigFiber1PortName		DisplayString,
            cm1000mmConfigFiber1PortEnable	YesNoValue,
            cm1000mmConfigFiber2PortName		DisplayString,
            cm1000mmConfigFiber2PortEnable	YesNoValue
        }

    cm1000mmConfigSlotIndex	OBJECT-TYPE
        SYNTAX		SlotNumber
        MAX-ACCESS	not-accessible
        STATUS		current
        DESCRIPTION
            "The Slot number the CM-1000MM type module is currently inserted"
    ::= { cm1000mmConfigEntry 2 }

    cm1000mmConfigStatus OBJECT-TYPE
        SYNTAX      ContainerStatus
        MAX-ACCESS  read-write
        STATUS      current
        DESCRIPTION
          "When you perform a GET on this variable, one of
            the following values will be returned:
            1-Indicates that the container folder is active with no changes.
            2-Indicates that the container folder is active with change(s).
            Once you have completed setting the variables in a folder, you
            will want to submit your changes to the management module. To do
            this, set the Status variable to 4. If you want to discard the
            changes, set the Status variable to 6.
            4-Indicates that the changes in the container folder are to be
              submitted to the management module, verified and and saved to flash.
            6-Indicates that the changes in the container folder are to be
              discarded."
        ::= { cm1000mmConfigEntry 3 }

    cm1000mmConfigModuleName OBJECT-TYPE
        SYNTAX		DisplayString(SIZE(0..63))
        MAX-ACCESS	read-write
        STATUS		current
        DESCRIPTION
            "This object identifies a user configurable name for the media converter module
             present in the chassis. "
    ::= { cm1000mmConfigEntry 4 }

    cm1000mmConfigLinkMode	OBJECT-TYPE
        SYNTAX		INTEGER {
            standard(0),
            smartLinkPassthrough(1)
        }
        MAX-ACCESS	read-write
        STATUS		current
        DESCRIPTION
            "This object identifies the Link Mode for the media converter module. This object
            is read-only if the media converter module's ConfigMode jumper is set to
            hardwareSwitches(0)."
    ::= { cm1000mmConfigEntry 5 }

    cm1000mmConfigFiberFaultAlert	OBJECT-TYPE
        SYNTAX		EnableDisableValue
        MAX-ACCESS	read-write
        STATUS		current
        DESCRIPTION
            "This object identifies the Fiber Fault Alert setting for the media
             module. This object is read-only if the media converter module's ConfigMode
             jumper is set to hardwareSwitches(0). "
    ::= { cm1000mmConfigEntry 6 }

    cm1000mmConfigJumboPackets OBJECT-TYPE
        SYNTAX		EnableDisableValue
        MAX-ACCESS	read-write
        STATUS		current
        DESCRIPTION
            "This object identifies the Jumbo Packet setting for the media converter module
             present in the chassis. "
    ::= { cm1000mmConfigEntry 7 }

    cm1000mmConfigFiberAutoNeg OBJECT-TYPE
        SYNTAX 		EnableDisableValue
        MAX-ACCESS	read-write
        STATUS 		current
        DESCRIPTION
            "This object identifies the wither fiber auto-negotiation  is
             enabled for both ports. This object is read-only if the media
             module's ConfigMode jumper is set to hardwareSwitches(0)."
    ::= { cm1000mmConfigEntry 8 }

    cm1000mmConfigFiber1PortName OBJECT-TYPE
        SYNTAX		DisplayString(SIZE(0..8))
        MAX-ACCESS	read-write
        STATUS 		current
        DESCRIPTION
            "This object identifies a user definable name for the fiber port (port 1)."
    ::= { cm1000mmConfigEntry 9 }

    cm1000mmConfigFiber1PortEnable OBJECT-TYPE
        SYNTAX		YesNoValue
        MAX-ACCESS	read-write
        STATUS 		current
        DESCRIPTION
            "This object identifies whether the fiber port is enabled (port 1)."
    ::= { cm1000mmConfigEntry 10 }

    cm1000mmConfigFiber2PortName OBJECT-TYPE
        SYNTAX		DisplayString(SIZE(0..8))
        MAX-ACCESS	read-write
        STATUS 		current
        DESCRIPTION
            "This object identifies a user definable name for the fiber port (port 2)."
    ::= { cm1000mmConfigEntry 11 }

    cm1000mmConfigFiber2PortEnable OBJECT-TYPE
        SYNTAX		YesNoValue
        MAX-ACCESS	read-write
        STATUS 		current
        DESCRIPTION
            "This object identifies whether the fiber port is enabled (port 2)."
    ::= { cm1000mmConfigEntry 12 }


--
-- cm1000mmConfigTable
--

--
-- cm1000mmLedTable
--
cm1000mmLedTable	OBJECT-TYPE
    SYNTAX		SEQUENCE OF Cm1000mmLedEntry
    MAX-ACCESS	not-accessible
    STATUS		current
    DESCRIPTION
        "Table of CM-1000MM type media converter module's LED status information."
    ::= { cm1000mmFixed 3 }

    cm1000mmLedEntry OBJECT-TYPE
        SYNTAX      Cm1000mmLedEntry
        MAX-ACCESS  not-accessible
        STATUS      current
        DESCRIPTION
            "Entries of the table, each relating to a separate CM-1000MM type
             media converter module."
        INDEX   { mcrChassisIndex, cm1000mmLedsSlotIndex }
        ::= { cm1000mmLedTable 1 }

    Cm1000mmLedEntry ::=
        SEQUENCE {
            cm1000mmLedsSlotIndex	SlotNumber,
            cm1000mmLedPWR			INTEGER,
            cm1000mmLedLK1			INTEGER,
            cm1000mmLedLK2			INTEGER
        }

    cm1000mmLedsSlotIndex	OBJECT-TYPE
        SYNTAX		SlotNumber
        MAX-ACCESS	not-accessible
        STATUS		current
        DESCRIPTION
            "The Slot number the CM-1000 type module is currently inserted"
    ::= { cm1000mmLedEntry 2 }

    cm1000mmLedPWR	OBJECT-TYPE
        SYNTAX		INTEGER {
            off(0),
            onGreen(1),
            blinking(2)
        }
        MAX-ACCESS	read-only
        STATUS		current
        DESCRIPTION
            "This object identifies the status of the power (PWR) LED on the media converter module.
             Possible status values are:
                 off(0) - No power to the module
                 onGreen(1) - Power being applied to module
                 blinking(2) - Fiber loopback enabled"
    ::= { cm1000mmLedEntry 3 }

    cm1000mmLedLK1	OBJECT-TYPE
        SYNTAX		INTEGER {
            off(0),
            on(1)
        }
        MAX-ACCESS	read-only
        STATUS		current
        DESCRIPTION
            "This object identifies the status of the link fiber port 1 (LK1) LED on the
             media converter module.
             Possible status values are:
                 off(0) - No fiber link
                 on(1) - Fiber link present"
    ::= { cm1000mmLedEntry 4 }

    cm1000mmLedLK2	OBJECT-TYPE
        SYNTAX		INTEGER {
            off(0),
            on(1)
        }
        MAX-ACCESS	read-only
        STATUS		current
        DESCRIPTION
            "This object identifies the status of the link fiber port 2 (LK2) LED on the
             media converter module.
             Possible status values are:
                 off(0) - No fiber link
                 on(1) - Fiber link present"
    ::= { cm1000mmLedEntry 5 }

--
-- end of cm1000mmLedTable
--

--
-- end of cm1000mmFixed

--
-- cm100Fixed - 100 Mb fixed media Converter type modules
--
cm100Fixed	OBJECT IDENTIFIER ::= { mcrModuleTypes 2 }

--
-- cm100FixedTable
--
cm100FixedTable	OBJECT-TYPE
    SYNTAX		SEQUENCE OF Cm100FixedEntry
    MAX-ACCESS	not-accessible
    STATUS		current
    DESCRIPTION
        "Table of CM-100 type media converter module's configuration and status type
         information."
    ::= { cm100Fixed 1 }

    cm100FixedEntry OBJECT-TYPE
        SYNTAX      Cm100FixedEntry
        MAX-ACCESS  not-accessible
        STATUS      current
        DESCRIPTION
            "Entries of the table, each relating to a separate CM-1000 type
             media converter module."
        INDEX   { mcrChassisIndex, cm100SlotIndex }
        ::= { cm100FixedTable 1 }

    Cm100FixedEntry ::=
        SEQUENCE {
            cm100SlotIndex						SlotNumber,
            cm100ModelName						DisplayString,
            cm100ModelDesc						DisplayString,
            cm100HwJmp5ConfigMode			INTEGER,
            cm100HwJmp6AutoMDI				INTEGER,
            cm100HwSw1AutoNegotiation		INTEGER,
            cm100HwSw2LinkMode				INTEGER,
            cm100HwSw3FarEndFault			INTEGER,
            cm100HwSw5Pause					INTEGER,
            cm100HwSw6Loopback				INTEGER,
            cm100FiberLinkStatus				INTEGER,
            cm100FiberConnType				INTEGER,
            cm100FiberSpeed					INTEGER,
            cm100FiberFarEndFault			INTEGER,
            cm100FiberReceiveStatus			INTEGER,
            cm100FiberLoopBack				EnableDisableValue,
            cm100CopperLinkStatus			INTEGER,
            cm100CopperConnType				INTEGER,
            cm100CopperAutoNegState			INTEGER,
            cm100CopperSpeed					INTEGER,
            cm100CopperDuplex					INTEGER,
            cm100CopperCrossOver				INTEGER,
            cm100CopperPause					INTEGER,
            cm100CopperLPRFStatus			INTEGER
        }

    cm100SlotIndex	OBJECT-TYPE
        SYNTAX		SlotNumber
        MAX-ACCESS	not-accessible
        STATUS		current
        DESCRIPTION
            "The Slot number the CM-100 type module is currently inserted"
    ::= { cm100FixedEntry 2 }

    cm100ModelName	OBJECT-TYPE
        SYNTAX		DisplayString
        MAX-ACCESS	read-only
        STATUS		current
        DESCRIPTION
            "This object identifies the model of media converter module present in the
             chassis"
    ::= { cm100FixedEntry 3 }

    cm100ModelDesc		OBJECT-TYPE
        SYNTAX		DisplayString
        MAX-ACCESS	read-only
        STATUS		current
        DESCRIPTION
            "This object identifies a static description of the media converter module present
             in the chassis"
    ::= { cm100FixedEntry 4 }

    cm100HwJmp5ConfigMode	OBJECT-TYPE
        SYNTAX		INTEGER {
            hardwareSwitches(0),
            auto(1)
        }
        MAX-ACCESS	read-only
        STATUS		current
        DESCRIPTION
            "This object identifies the media converter module's ConfigMode, set by hardware
             switch on the media converter module. When this object is set to hardwareSwitches(0), the
             media converter module will disable configuration control from the management
             module's software and all configuration control comes from the media
             module's hardware switches or jumpers. "
    ::= { cm100FixedEntry 5 }

    cm100HwJmp6AutoMDI OBJECT-TYPE
        SYNTAX 		INTEGER {
            mdi(0),
            auto(1)
        }
        MAX-ACCESS read-only
        STATUS 		current
        DESCRIPTION
            "This object identifies the media converter module's hardware Auto MDIX jumper
             settings. "
    ::= { cm100FixedEntry 6 }


    cm100HwSw1AutoNegotiation OBJECT-TYPE
        SYNTAX 		INTEGER {
            swDownDisabled(0),
            swUpEnabled(1)
        }
        MAX-ACCESS read-only
        STATUS 		current
        DESCRIPTION
            "Media converter module's current switch setting for fiber Auto-Negotiation."
    ::= { cm100FixedEntry 7 }

    cm100HwSw2LinkMode OBJECT-TYPE
        SYNTAX 		INTEGER {
            swDownStandardMode(0),
            swUpLinkPassthroughMode(1)
        }
        MAX-ACCESS read-only
        STATUS 		current
        DESCRIPTION
            "Media converter module's current switch setting for Link Mode."
    ::= { cm100FixedEntry 8 }

    cm100HwSw3FarEndFault OBJECT-TYPE
        SYNTAX 		INTEGER {
            swDownDisabled(0),
            swUpEnabled(1)
        }
        MAX-ACCESS read-only
        STATUS 		current
        DESCRIPTION
            "Media converter module's current switch setting for Far End Fault."
    ::= { cm100FixedEntry 9 }

-- cm100HwSw4   unused switch

    cm100HwSw5Pause OBJECT-TYPE
        SYNTAX 		INTEGER {
            swDownDisabled(0),
            swUpEnabled(1)
        }
        MAX-ACCESS read-only
        STATUS 		current
        DESCRIPTION
            "Media converter module's current switch setting for copper pause (flow control)."
    ::= { cm100FixedEntry 10 }


    cm100HwSw6Loopback OBJECT-TYPE
        SYNTAX 		INTEGER {
            swDownEnabled(0),
            swUpDisabled(1)
        }
        MAX-ACCESS read-only
        STATUS 		current
        DESCRIPTION
            "Media converter module's current switch setting for fiber loopback mode."
    ::= { cm100FixedEntry 11 }


    cm100FiberLinkStatus OBJECT-TYPE
        SYNTAX 		INTEGER {
            down(0),
            up(1)
        }
        MAX-ACCESS	read-only
        STATUS 		current
        DESCRIPTION
            "Media converter module's current fiber link status."
    ::= { cm100FixedEntry 12 }

    cm100FiberConnType OBJECT-TYPE
        SYNTAX 		INTEGER {
            sc(0),
            lc(1),
            st(2),
            sfp(3),
            fc(5),
            mtrj(6)
        }
        MAX-ACCESS read-only
        STATUS 		current
        DESCRIPTION
            "Media converter module's fiber port connector type."
    ::= { cm100FixedEntry 13 }

    cm100FiberSpeed OBJECT-TYPE
        SYNTAX 		INTEGER {
            speed100Mbps(1)
        }
        MAX-ACCESS	read-only
        STATUS 		current
        DESCRIPTION
            "Media converter module's fiber port speed in megabits per second."
    ::= { cm100FixedEntry 14 }

    cm100FiberFarEndFault		OBJECT-TYPE
        SYNTAX		INTEGER {
            disable(0),
            ok(1),
            receivingFEF(2),
            sendingFEF(3)
        }
        MAX-ACCESS	read-only
        STATUS		current
        DESCRIPTION
            "Media converter module's current fiber Far End Fault status."
    ::= { cm100FixedEntry 15 }

    cm100FiberReceiveStatus		OBJECT-TYPE
        SYNTAX	INTEGER {
            fault(0),
            ok(1)
        }
        MAX-ACCESS	read-write
        STATUS	current
        DESCRIPTION
            "This object identifies the status of whether light is being received
             on the fiber port"
    ::= { cm100FixedEntry 16 }

    cm100FiberLoopBack		OBJECT-TYPE
        SYNTAX	EnableDisableValue
        MAX-ACCESS	read-write
        STATUS	current
        DESCRIPTION
            "
             This object is read-only if the media converter module's ConfigMode jumper is
             set to hardwareSwitches(0)."
    ::= { cm100FixedEntry 17 }

    cm100CopperLinkStatus OBJECT-TYPE
        SYNTAX	INTEGER {
            down(0),
            up(1)
        }
        MAX-ACCESS	read-only
        STATUS	current
        DESCRIPTION
            "Media converter module's current copper link status."
    ::= { cm100FixedEntry 18 }

    cm100CopperConnType OBJECT-TYPE
        SYNTAX INTEGER {
            rj45(0)
        }
        MAX-ACCESS read-only
        STATUS current
        DESCRIPTION
            "Media converter module's copper connector type."
    ::= { cm100FixedEntry 19 }


    cm100CopperAutoNegState OBJECT-TYPE
        SYNTAX INTEGER {
            disabled(0),
            complete(1),
            inProgress(2)
        }
        MAX-ACCESS read-only
        STATUS current
        DESCRIPTION
            "Media converter module's current copper auto-negotiation state."
    ::= { cm100FixedEntry 20 }

    cm100CopperSpeed OBJECT-TYPE
        SYNTAX 		INTEGER {
            speed100Mbps(1)
        }
        MAX-ACCESS	read-only
        STATUS 		current
        DESCRIPTION
            "This object identifies the  copper port speed in megabits per second."
    ::= { cm100FixedEntry 21 }

    cm100CopperDuplex OBJECT-TYPE
        SYNTAX INTEGER {
            half(0),
            full(1)
        }
        MAX-ACCESS read-only
        STATUS current
        DESCRIPTION
            "If copper auto-negotiation state is complete then this object
            indicates the media converter module's current copper auto-negotiated duplex
            setting. If auto-negotiation is not complete then the value returned
            should be ignored."
    ::= { cm100FixedEntry 22 }

    cm100CopperCrossOver OBJECT-TYPE
        SYNTAX INTEGER {
            mdi(0),
            mdix(1)
        }
        MAX-ACCESS read-only
        STATUS current
        DESCRIPTION
            "If copper auto-negotiation state is complete then this object
            indicates the media converter module's current copper auto-negotiated MDI/MDI-X
            setting. If auto-negotiation is not complete then the value returned
            should be ignored."
    ::= { cm100FixedEntry 23 }

    cm100CopperPause OBJECT-TYPE
        SYNTAX INTEGER {
            disabled(0),
            symmetrical(1)
        }
        MAX-ACCESS read-only
        STATUS current
        DESCRIPTION
            "If copper auto-negotiation state is complete then this object indicates
             the media converter module's current copper auto-negotiated pause (flow control)
             setting. If auto-negotiation is not complete then the value returned
             should be ignored."
    ::= { cm100FixedEntry 24 }

 cm100CopperLPRFStatus OBJECT-TYPE
        SYNTAX INTEGER {
            ok(0),
            remoteFault(1)
        }
        MAX-ACCESS read-only
        STATUS current
        DESCRIPTION
            "Media converter module's copper Link Partner Remote Fault status."
    ::= { cm100FixedEntry 25}

--
-- end of cm100FixedTable
--


--
-- cm100ConfigTable
--
cm100ConfigTable	OBJECT-TYPE
    SYNTAX		SEQUENCE OF Cm100ConfigEntry
    MAX-ACCESS	not-accessible
    STATUS		current
    DESCRIPTION
        "Table of CM-100 type media converter module's configuration and status type
         information."
    ::= { cm100Fixed 2 }

    cm100ConfigEntry OBJECT-TYPE
        SYNTAX      Cm100ConfigEntry
        MAX-ACCESS  not-accessible
        STATUS      current
        DESCRIPTION
            "Entries of the table, each relating to a separate CM-1000 type
             media converter module."
        INDEX   { mcrChassisIndex, cm100ConfigSlotIndex }
        ::= { cm100ConfigTable 1 }

    Cm100ConfigEntry ::=
        SEQUENCE {
            cm100ConfigSlotIndex						SlotNumber,
            cm100ConfigStatus							ContainerStatus,
            cm100ConfigModuleName					DisplayString,
            cm100ConfigLinkMode						INTEGER,
            cm100ConfigFiberFarEndFault			EnableDisableValue,
            cm100ConfigFiberPortName				DisplayString,
            cm100ConfigFiberPortEnable				YesNoValue,
            cm100ConfigCopperPortName				DisplayString,
            cm100ConfigCopperPortEnable			YesNoValue,
            cm100ConfigCopperAutoNegotiation		EnableDisableValue,
            cm100ConfigCopperCrossOver				INTEGER,
            cm100ConfigCopperPause					INTEGER
        }

    cm100ConfigSlotIndex	OBJECT-TYPE
        SYNTAX		SlotNumber
        MAX-ACCESS	not-accessible
        STATUS		current
        DESCRIPTION
            "The Slot number the CM-1000 type module is currently inserted"
    ::= { cm100ConfigEntry 2 }

    cm100ConfigStatus OBJECT-TYPE
        SYNTAX      ContainerStatus
        MAX-ACCESS  read-write
        STATUS      current
        DESCRIPTION
          "When you perform a GET on this variable, one of
            the following values will be returned:
            1-Indicates that the container folder is active with no changes.
            2-Indicates that the container folder is active with change(s).
            Once you have completed setting the variables in a folder, you
            will want to submit your changes to the management module. To do
            this, set the Status variable to 4. If you want to discard the
            changes, set the Status variable to 6.
            4-Indicates that the changes in the container folder are to be
              submitted to the management module, verified and and saved to flash.
            6-Indicates that the changes in the container folder are to be
              discarded."
        ::= { cm100ConfigEntry 3 }

    cm100ConfigModuleName OBJECT-TYPE
        SYNTAX		DisplayString(SIZE(0..63))
        MAX-ACCESS	read-write
        STATUS		current
        DESCRIPTION
            "This object identifies a user configurable name for the media converter module
             present in the chassis. "
    ::= { cm100ConfigEntry 4 }


    cm100ConfigLinkMode	OBJECT-TYPE
        SYNTAX		INTEGER {
            standard(0),
            linkPassthrough(1)
        }
        MAX-ACCESS	read-write
        STATUS		current
        DESCRIPTION
            "This object identifies the Link Mode for the media converter module. This object
            is read-only if the media converter module's ConfigMode jumper is set to
            hardwareSwitches(0)."
    ::= { cm100ConfigEntry 5 }

    cm100ConfigFiberFarEndFault	OBJECT-TYPE
        SYNTAX		EnableDisableValue
        MAX-ACCESS	read-write
        STATUS		current
        DESCRIPTION
            "This object identifies the fiber Far End Fault setting for the media
             module. This setting is always enabled if Link Mode is set to linkPassthrough.
             This object is read-only if the media converter module's ConfigMode
             jumper is set to hardwareSwitches(0). "
    ::= { cm100ConfigEntry 6 }

    cm100ConfigFiberPortName OBJECT-TYPE
        SYNTAX		DisplayString(SIZE(0..8))
        MAX-ACCESS	read-write
        STATUS 		current
        DESCRIPTION
            "This object identifies a user definable name for the fiber port."
    ::= { cm100ConfigEntry 7 }

    cm100ConfigFiberPortEnable OBJECT-TYPE
        SYNTAX		YesNoValue
        MAX-ACCESS	read-write
        STATUS 		current
        DESCRIPTION
            "This object identifies whether the fiber port is enabled. "
    ::= { cm100ConfigEntry 8 }

    cm100ConfigCopperPortName OBJECT-TYPE
        SYNTAX DisplayString(SIZE(0..8))
        MAX-ACCESS read-write
        STATUS current
        DESCRIPTION
            "This object identifies a user definable name for the copper port. "
    ::= { cm100ConfigEntry 9 }

    cm100ConfigCopperPortEnable OBJECT-TYPE
        SYNTAX	YesNoValue
        MAX-ACCESS	read-write
        STATUS	current
        DESCRIPTION
            "This object identifies whether the fiber port is enabled. "
    ::= { cm100ConfigEntry 10 }


    cm100ConfigCopperAutoNegotiation OBJECT-TYPE
        SYNTAX 		EnableDisableValue
        MAX-ACCESS	read-write
        STATUS 		current
        DESCRIPTION
            "This object identifies the whether copper auto-negotiation is
             enabled. This object is read-only if the media converter module's ConfigMode
             jumper is set to hardwareSwitches(0)."
    ::= { cm100ConfigEntry 11 }


    cm100ConfigCopperCrossOver OBJECT-TYPE
        SYNTAX INTEGER {
            auto(0),
            mdi(1),
            mdix(2)
        }
        MAX-ACCESS read-write
        STATUS current
        DESCRIPTION
            "This object identifies the copper MDI/MDI-X setting.This object
            is read-only if the media converter module's ConfigMode jumper is set to"
    ::= { cm100ConfigEntry 12 }

    cm100ConfigCopperPause OBJECT-TYPE
        SYNTAX INTEGER {
            disabled(0),
            symmetrical(1)
        }
        MAX-ACCESS read-write
        STATUS current
        DESCRIPTION
            "This object identifies the copper's port pause (flow control) settings.
             This object is read-only if the media converter module's ConfigMode jumper is
             set to hardwareSwitches(0)."
    ::= { cm100ConfigEntry 13 }

--
-- end of cm100ConfigTable
--


--
-- cm100LedTable
--
cm100LedTable	OBJECT-TYPE
    SYNTAX		SEQUENCE OF Cm100LedEntry
    MAX-ACCESS	not-accessible
    STATUS		current
    DESCRIPTION
        "Table of CM-100 type media converter module's LED status information."
    ::= { cm100Fixed 3 }

    cm100LedEntry OBJECT-TYPE
        SYNTAX      Cm100LedEntry
        MAX-ACCESS  not-accessible
        STATUS      current
        DESCRIPTION
            "Entries of the table, each relating to a separate CM-100 type
             media converter module."
        INDEX   { mcrChassisIndex, cm100LedSlotIndex }
        ::= { cm100LedTable 1 }

    Cm100LedEntry ::=
        SEQUENCE {
            cm100LedSlotIndex	SlotNumber,
            cm100LedPWR				INTEGER,
            cm100LedLKF				INTEGER,
            cm100LedLKC				INTEGER
        }

    cm100LedSlotIndex	OBJECT-TYPE
        SYNTAX		SlotNumber
        MAX-ACCESS	not-accessible
        STATUS		current
        DESCRIPTION
            "The Slot number the CM-100 type module is currently inserted"
    ::= { cm100LedEntry 2 }

    cm100LedPWR	OBJECT-TYPE
        SYNTAX		INTEGER {
            off(0),
            onGreen(1),
            blinking(2)
        }
        MAX-ACCESS	read-only
        STATUS		current
        DESCRIPTION
            "This object identifies the status of the power (PWR) LED on the media converter module.
             Possible status values are:
                 off(0) - No power to the module
                 onGreen(1) - Power being applied to module
                 blinking(2) - Fiber loopback enabled"
    ::= { cm100LedEntry 3 }

    cm100LedLKF	OBJECT-TYPE
        SYNTAX		INTEGER {
            off(0),
            on(1)
        }
        MAX-ACCESS	read-only
        STATUS		current
        DESCRIPTION
            "This object identifies the status of the link fiber (LKF) LED on the media converter module.
             Possible status values are:
                 off(0) - No fiber link
                 on(1) - Fiber link present"
    ::= { cm100LedEntry 4 }

    cm100LedLKC	OBJECT-TYPE
        SYNTAX		INTEGER {
            off(0),
            on(1)
        }
        MAX-ACCESS	read-only
        STATUS		current
        DESCRIPTION
            "This object identifies the status of the link copper (LKC) LED on the
             media converter module.
             Possible status values are:
                 off(0) - No copper link
                 on(1) - Copper link present"
    ::= { cm100LedEntry 5 }

--
-- end of cm100LedTable
--

--
-- end of cm100Fixed
--

-- cm100mmFixed - 100 Mb fixed media Converter type modules
--
cm100mmFixed	OBJECT IDENTIFIER ::= { mcrModuleTypes 7 }

--
-- cm100mmFixedTable
--
cm100mmFixedTable	OBJECT-TYPE
    SYNTAX		SEQUENCE OF Cm100mmFixedEntry
    MAX-ACCESS	not-accessible
    STATUS		current
    DESCRIPTION
        "Table of CM-100MM type media converter module's configuration and status type
         information."
    ::= { cm100mmFixed 1 }

    cm100mmFixedEntry OBJECT-TYPE
        SYNTAX      Cm100mmFixedEntry
        MAX-ACCESS  not-accessible
        STATUS      current
        DESCRIPTION
            "Entries of the table, each relating to a separate CM-100MM type
             media converter module."
        INDEX   { mcrChassisIndex, cm100mmSlotIndex }
        ::= { cm100mmFixedTable 1 }

    Cm100mmFixedEntry ::=
        SEQUENCE {
            cm100mmSlotIndex						SlotNumber,
            cm100mmModelName						DisplayString,
            cm100mmModelDesc						DisplayString,
            cm100mmHwJmp5ConfigMode			INTEGER,
            cm100mmHwSw1LinkPassthrough		INTEGER,
            cm100mmHwSw2FarEndFault				INTEGER,
            cm100mmHwSw3Loopback1			INTEGER,
            cm100mmHwSw4Loopback2					INTEGER,
            cm100mmFiber1LinkStatus				INTEGER,
            cm100mmFiber1ConnType				INTEGER,
            cm100mmFiber1Speed					INTEGER,
            cm100mmFiber1FarEndFault			INTEGER,
            cm100mmFiber1ReceiveStatus			INTEGER,
            cm100mmFiber2LinkStatus				INTEGER,
            cm100mmFiber2ConnType				INTEGER,
            cm100mmFiber2Speed					INTEGER,
            cm100mmFiber2FarEndFault			INTEGER,
            cm100mmFiber2ReceiveStatus			INTEGER,
            cm100mmFiberLoopBack				INTEGER
        }

    cm100mmSlotIndex	OBJECT-TYPE
        SYNTAX		SlotNumber
        MAX-ACCESS	not-accessible
        STATUS		current
        DESCRIPTION
            "The Slot number the CM-100MM type module is currently inserted"
    ::= { cm100mmFixedEntry 2 }

    cm100mmModelName	OBJECT-TYPE
        SYNTAX		DisplayString
        MAX-ACCESS	read-only
        STATUS		current
        DESCRIPTION
            "This object identifies the model of media converter module present in the
             chassis"
    ::= { cm100mmFixedEntry 3 }

    cm100mmModelDesc		OBJECT-TYPE
        SYNTAX		DisplayString
        MAX-ACCESS	read-only
        STATUS		current
        DESCRIPTION
            "This object identifies a static description of the media converter module present
             in the chassis"
    ::= { cm100mmFixedEntry 4 }

    cm100mmHwJmp5ConfigMode	OBJECT-TYPE
        SYNTAX		INTEGER {
            hardwareSwitches(0),
            auto(1)
        }
        MAX-ACCESS	read-only
        STATUS		current
        DESCRIPTION
            "This object identifies the media converter module's ConfigMode, set by hardware
             switch on the media converter module. When this object is set to hardwareSwitches(0), the
             media converter module will disable configuration control from the management
             module's software and all configuration control comes from the media
             module's hardware switches or jumpers. "
    ::= { cm100mmFixedEntry 5 }


    cm100mmHwSw1LinkPassthrough OBJECT-TYPE
        SYNTAX 		INTEGER {
            swDownDisabled(0),
            swUpEnabled(1)
        }
        MAX-ACCESS read-only
        STATUS 		current
        DESCRIPTION
            "Media converter module's current switch setting for Link Passthrough."
    ::= { cm100mmFixedEntry 6 }

    cm100mmHwSw2FarEndFault OBJECT-TYPE
        SYNTAX 		INTEGER {
            swDownDisabled(0),
            swUpEnabled(1)
        }
        MAX-ACCESS read-only
        STATUS 		current
        DESCRIPTION
            "Media converter module's current switch setting for Far-End Fault."
    ::= { cm100mmFixedEntry 7 }

    cm100mmHwSw3Loopback1 OBJECT-TYPE
        SYNTAX 		INTEGER {
            swDownEnabled(0),
            swUpDisabled(1)
        }
        MAX-ACCESS read-only
        STATUS 		current
        DESCRIPTION
            "Media converter module's current switch setting for Loopback (fiber port 1)."
    ::= { cm100mmFixedEntry 8 }

    cm100mmHwSw4Loopback2 OBJECT-TYPE
        SYNTAX 		INTEGER {
            swDownEnabled(0),
            swUpDisabled(1)
        }
        MAX-ACCESS read-only
        STATUS 		current
        DESCRIPTION
            "Media converter module's current switch setting for Loopback (fiber port 2)."
    ::= { cm100mmFixedEntry 9 }

    cm100mmFiber1LinkStatus OBJECT-TYPE
        SYNTAX 		INTEGER {
            down(0),
            up(1)
        }
        MAX-ACCESS	read-only
        STATUS 		current
        DESCRIPTION
            "Media converter module's current fiber link status (port 1)."
    ::= { cm100mmFixedEntry 12 }

    cm100mmFiber1ConnType OBJECT-TYPE
        SYNTAX 		INTEGER {
            sc(0),
            lc(1),
            st(2),
            sfp(3),
            fc(5),
            mtrj(6)
        }
        MAX-ACCESS read-only
        STATUS 		current
        DESCRIPTION
            "Media converter module's fiber port connector type (port 1)."
    ::= { cm100mmFixedEntry 13 }

    cm100mmFiber1Speed OBJECT-TYPE
        SYNTAX 		INTEGER {
            speed100Mbps(1)
        }
        MAX-ACCESS	read-only
        STATUS 		current
        DESCRIPTION
            "Media converter module's fiber port speed in megabits per second (port 1)."
    ::= { cm100mmFixedEntry 14 }

    cm100mmFiber1FarEndFault	OBJECT-TYPE
        SYNTAX		INTEGER {
            disable(0),
            ok(1),
            receivingFEF(2),
            sendingFEF(3)
        }
        MAX-ACCESS	read-only
        STATUS		current
        DESCRIPTION
            "Media converter module's current fiber Far End Fault status (port 1)."
    ::= { cm100mmFixedEntry 15 }

    cm100mmFiber1ReceiveStatus		OBJECT-TYPE
        SYNTAX	INTEGER {
            fault(0),
            ok(1)
        }
        MAX-ACCESS	read-write
        STATUS	current
        DESCRIPTION
            "This object identifies the status of whether light is being received
             on the fiber port (port 1)"
    ::= { cm100mmFixedEntry 16 }

    cm100mmFiber2LinkStatus OBJECT-TYPE
        SYNTAX 		INTEGER {
            down(0),
            up(1)
        }
        MAX-ACCESS	read-only
        STATUS 		current
        DESCRIPTION
            "Media converter module's current fiber link status (port 2)."
    ::= { cm100mmFixedEntry 17 }

    cm100mmFiber2ConnType OBJECT-TYPE
        SYNTAX 		INTEGER {
            sc(0),
            lc(1),
            st(2),
            sfp(3),
            fc(5),
            mtrj(6)
        }
        MAX-ACCESS read-only
        STATUS 		current
        DESCRIPTION
            "Media converter module's fiber port connector type (port 2)."
    ::= { cm100mmFixedEntry 18 }

    cm100mmFiber2Speed OBJECT-TYPE
        SYNTAX 		INTEGER {
            speed100Mbps(1)
        }
        MAX-ACCESS	read-only
        STATUS 		current
        DESCRIPTION
            "Media converter module's fiber port speed in megabits per second (port 2)."
    ::= { cm100mmFixedEntry 19 }

    cm100mmFiber2FarEndFault	OBJECT-TYPE
        SYNTAX		INTEGER {
            disable(0),
            ok(1),
            receivingFEF(2),
            sendingFEF(3)
        }
        MAX-ACCESS	read-only
        STATUS		current
        DESCRIPTION
            "Media converter module's current fiber Far End Fault status (port 2)."
    ::= { cm100mmFixedEntry 20 }

    cm100mmFiber2ReceiveStatus		OBJECT-TYPE
        SYNTAX	INTEGER {
            fault(0),
            ok(1)
        }
        MAX-ACCESS	read-write
        STATUS	current
        DESCRIPTION
            "This object identifies the status of whether light is being received
             on the fiber port (port 2)"
    ::= { cm100mmFixedEntry 21 }

    cm100mmFiberLoopBack		OBJECT-TYPE
        SYNTAX	INTEGER {
            disabled(0),
            port1(1),
            port2(2)
        }
        MAX-ACCESS	read-write
        STATUS	current
        DESCRIPTION
            "
             This object is read-only if the media converter module's ConfigMode jumper is
             set to hardwareSwitches(0)."
    ::= { cm100mmFixedEntry 22 }

--
-- end of cm100mmFixedTable
--


--
-- cm100mmConfigTable
--
cm100mmConfigTable	OBJECT-TYPE
    SYNTAX		SEQUENCE OF Cm100mmConfigEntry
    MAX-ACCESS	not-accessible
    STATUS		current
    DESCRIPTION
        "Table of CM-100MM type media converter module's configuration and status type
         information."
    ::= { cm100mmFixed 2 }

    cm100mmConfigEntry OBJECT-TYPE
        SYNTAX      Cm100mmConfigEntry
        MAX-ACCESS  not-accessible
        STATUS      current
        DESCRIPTION
            "Entries of the table, each relating to a separate CM-100MM type
             media converter module."
        INDEX   { mcrChassisIndex, cm100mmConfigSlotIndex }
        ::= { cm100mmConfigTable 1 }

    Cm100mmConfigEntry ::=
        SEQUENCE {
            cm100mmConfigSlotIndex						SlotNumber,
            cm100mmConfigStatus							ContainerStatus,
            cm100mmConfigModuleName					DisplayString,
            cm100mmConfigLinkMode						INTEGER,
            cm100mmConfigFiberFarEndFault			EnableDisableValue,
            cm100mmConfigFiber1PortName				DisplayString,
            cm100mmConfigFiber1PortEnable				YesNoValue,
            cm100mmConfigFiber2PortName				DisplayString,
            cm100mmConfigFiber2PortEnable				YesNoValue
        }

    cm100mmConfigSlotIndex	OBJECT-TYPE
        SYNTAX		SlotNumber
        MAX-ACCESS	not-accessible
        STATUS		current
        DESCRIPTION
            "The Slot number the CM-100MM type module is currently inserted"
    ::= { cm100mmConfigEntry 2 }

    cm100mmConfigStatus OBJECT-TYPE
        SYNTAX      ContainerStatus
        MAX-ACCESS  read-write
        STATUS      current
        DESCRIPTION
          "When you perform a GET on this variable, one of
            the following values will be returned:
            1-Indicates that the container folder is active with no changes.
            2-Indicates that the container folder is active with change(s).
            Once you have completed setting the variables in a folder, you
            will want to submit your changes to the management module. To do
            this, set the Status variable to 4. If you want to discard the
            changes, set the Status variable to 6.
            4-Indicates that the changes in the container folder are to be
              submitted to the management module, verified and and saved to flash.
            6-Indicates that the changes in the container folder are to be
              discarded."
        ::= { cm100mmConfigEntry 3 }

    cm100mmConfigModuleName OBJECT-TYPE
        SYNTAX		DisplayString(SIZE(0..63))
        MAX-ACCESS	read-write
        STATUS		current
        DESCRIPTION
            "This object identifies a user configurable name for the media converter module
             present in the chassis. "
    ::= { cm100mmConfigEntry 4 }


    cm100mmConfigLinkMode	OBJECT-TYPE
        SYNTAX		INTEGER {
            standard(0),
            linkPassthrough(1)
        }
        MAX-ACCESS	read-write
        STATUS		current
        DESCRIPTION
            "This object identifies the Link Mode for the media converter module. This object
            is read-only if the media converter module's ConfigMode jumper is set to
            hardwareSwitches(0)."
    ::= { cm100mmConfigEntry 5 }

    cm100mmConfigFiberFarEndFault	OBJECT-TYPE
        SYNTAX		EnableDisableValue
        MAX-ACCESS	read-write
        STATUS		current
        DESCRIPTION
            "This object identifies the fiber Far End Fault setting for the media
             module. This setting is always enabled if Link Mode is set to linkPassthrough.
             This object is read-only if the media converter module's ConfigMode
             jumper is set to hardwareSwitches(0). "
    ::= { cm100mmConfigEntry 6 }

    cm100mmConfigFiber1PortName OBJECT-TYPE
        SYNTAX		DisplayString(SIZE(0..8))
        MAX-ACCESS	read-write
        STATUS 		current
        DESCRIPTION
            "This object identifies a user definable name for the fiber port (port 1)."
    ::= { cm100mmConfigEntry 7 }

    cm100mmConfigFiber1PortEnable OBJECT-TYPE
        SYNTAX		YesNoValue
        MAX-ACCESS	read-write
        STATUS 		current
        DESCRIPTION
            "This object identifies whether the fiber port is enabled (port 2). "
    ::= { cm100mmConfigEntry 8 }

    cm100mmConfigFiber2PortName OBJECT-TYPE
        SYNTAX		DisplayString(SIZE(0..8))
        MAX-ACCESS	read-write
        STATUS 		current
        DESCRIPTION
            "This object identifies a user definable name for the fiber port (port 2)."
    ::= { cm100mmConfigEntry 9 }

    cm100mmConfigFiber2PortEnable OBJECT-TYPE
        SYNTAX		YesNoValue
        MAX-ACCESS	read-write
        STATUS 		current
        DESCRIPTION
            "This object identifies whether the fiber port is enabled (port 2). "
    ::= { cm100mmConfigEntry 10 }

--
-- end of cm100mmConfigTable
--


--
-- cm100mmLedTable
--
cm100mmLedTable	OBJECT-TYPE
    SYNTAX		SEQUENCE OF Cm100mmLedEntry
    MAX-ACCESS	not-accessible
    STATUS		current
    DESCRIPTION
        "Table of CM-100MM type media converter module's LED status information."
    ::= { cm100mmFixed 3 }

    cm100mmLedEntry OBJECT-TYPE
        SYNTAX      Cm100mmLedEntry
        MAX-ACCESS  not-accessible
        STATUS      current
        DESCRIPTION
            "Entries of the table, each relating to a separate CM-100MM type
             media converter module."
        INDEX   { mcrChassisIndex, cm100mmLedSlotIndex }
        ::= { cm100mmLedTable 1 }

    Cm100mmLedEntry ::=
        SEQUENCE {
            cm100mmLedSlotIndex	SlotNumber,
            cm100mmLedPWR				INTEGER,
            cm100mmLedLK1				INTEGER,
            cm100mmLedLK2				INTEGER
        }

    cm100mmLedSlotIndex	OBJECT-TYPE
        SYNTAX		SlotNumber
        MAX-ACCESS	not-accessible
        STATUS		current
        DESCRIPTION
            "The Slot number the CM-100MM type module is currently inserted"
    ::= { cm100mmLedEntry 2 }

    cm100mmLedPWR	OBJECT-TYPE
        SYNTAX		INTEGER {
            off(0),
            onGreen(1),
            blinking(2)
        }
        MAX-ACCESS	read-only
        STATUS		current
        DESCRIPTION
            "This object identifies the status of the power (PWR) LED on the media converter module.
             Possible status values are:
                 off(0) - No power to the module
                 onGreen(1) - Power being applied to module
                 blinking(2) - Fiber loopback enabled"
    ::= { cm100mmLedEntry 3 }

    cm100mmLedLK1	OBJECT-TYPE
        SYNTAX		INTEGER {
            off(0),
            on(1)
        }
        MAX-ACCESS	read-only
        STATUS		current
        DESCRIPTION
            "This object identifies the status of the link fiber port 1 (LK1) LED on the media converter module.
             Possible status values are:
                 off(0) - No fiber link
                 on(1) - Fiber link present"
    ::= { cm100mmLedEntry 4 }

    cm100mmLedLK2	OBJECT-TYPE
        SYNTAX		INTEGER {
            off(0),
            on(1)
        }
        MAX-ACCESS	read-only
        STATUS		current
        DESCRIPTION
            "This object identifies the status of the link fiber port 2 (LK2) LED on the
             media converter module.
             Possible status values are:
                 off(0) - No fiber link
                 on(1) - Fiber link present"
    ::= { cm100mmLedEntry 5 }

--
-- end of cm100mmLedTable
--

--
-- end of cm100mmFixed
--

--
-- cm1110RateConv - 10/100/100 Mb Rate Converting media Converter type modules
--
cm1110RateConv	OBJECT IDENTIFIER ::= { mcrModuleTypes 3 }

--
-- cm1110RateConvTable
--
cm1110RateConvTable	OBJECT-TYPE
    SYNTAX		SEQUENCE OF Cm1110RateConvEntry
    MAX-ACCESS	not-accessible
    STATUS		current
    DESCRIPTION
        "Table of CM-1110 type media converter module's configuration and status type
         information."
    ::= { cm1110RateConv 1 }

    cm1110RateConvEntry OBJECT-TYPE
        SYNTAX      Cm1110RateConvEntry
        MAX-ACCESS  not-accessible
        STATUS      current
        DESCRIPTION
            "Entries of the table, each relating to a separate CM-1110 type
             media converter module."
        INDEX   { mcrChassisIndex, cm1110SlotIndex}
        ::= { cm1110RateConvTable 1 }

    Cm1110RateConvEntry ::=
        SEQUENCE {
            cm1110SlotIndex						SlotNumber,
            cm1110ModelName						DisplayString,
            cm1110ModelDesc						DisplayString,
            cm1110HwJmp5ConfigMode				INTEGER,
            cm1110HwJmp6AutoMDIX					INTEGER,
            cm1110HwSw1TpAutoNegotiation		INTEGER,
            cm1110HwSw2LinkMode					INTEGER,
            cm1110HwSw3FiberFaultAlert			INTEGER,
            cm1110HwSw4TpDuplex					INTEGER,
            cm1110HwSw5TpSpeed					INTEGER,
            cm1110HwSw6FiberAutoNegotiation	INTEGER,
            cm1110HwSw6FiberSfp100Duplex		INTEGER,
            cm1110HwSw7Loopback					INTEGER,
            cm1110FiberLinkStatus				INTEGER,
            cm1110FiberConnType					INTEGER,
            cm1110FiberAutoNegState				INTEGER,
            cm1110FiberSpeed						INTEGER,
            cm1110FiberDuplex						INTEGER,
            cm1110FiberPauseEnh					INTEGER,
            cm1110FiberLPRFStatus				INTEGER,
            cm1110FiberSfp100FarEndFault		INTEGER,
            cm1110FiberReceiveStatus			INTEGER,
            cm1110FiberLoopBack					EnableDisableValue,
            cm1110CopperLinkStatus				INTEGER,
            cm1110CopperConnType					INTEGER,
            cm1110CopperAutoNegState			INTEGER,
            cm1110CopperSpeed						INTEGER,
            cm1110CopperDuplex					INTEGER,
            cm1110CopperCrossOver				INTEGER,
            cm1110CopperPauseEnh					INTEGER,
            cm1110CopperLPRFStatus				INTEGER,
            cm1110CopperAutoSpeedDownshift 	INTEGER
        }

    cm1110SlotIndex	OBJECT-TYPE
        SYNTAX		SlotNumber
        MAX-ACCESS	not-accessible
        STATUS		current
        DESCRIPTION
            "The Slot number the CM-1110 type module is currently inserted"
    ::= { cm1110RateConvEntry 2 }

    cm1110ModelName	OBJECT-TYPE
        SYNTAX		DisplayString
        MAX-ACCESS	read-only
        STATUS		current
        DESCRIPTION
            "This object identifies the model of media converter module present in the
             chassis"
    ::= { cm1110RateConvEntry 3 }

    cm1110ModelDesc		OBJECT-TYPE
        SYNTAX		DisplayString
        MAX-ACCESS	read-only
        STATUS		current
        DESCRIPTION
            "This object identifies a static description of the media converter module present
             in the chassis"
    ::= { cm1110RateConvEntry 4 }

    cm1110HwJmp5ConfigMode	OBJECT-TYPE
        SYNTAX		INTEGER {
            hardwareSwitches(0),
            auto(1)
        }
        MAX-ACCESS	read-only
        STATUS		current
        DESCRIPTION
            "This object identifies the media converter module's ConfigMode, set by hardware
             switch on the media converter module. When this object is set to hardwareSwitches(0), the
             media converter module will disable configuration control from the management
             module's software and all configuration control comes from the media
             module's hardware switches or jumpers. "
    ::= { cm1110RateConvEntry 5 }

    cm1110HwJmp6AutoMDIX OBJECT-TYPE
        SYNTAX 		INTEGER {
            mdix(0),
            auto(1)
        }
        MAX-ACCESS read-only
        STATUS 		current
        DESCRIPTION
            "This object identifies the media converter module's hardware Auto MDIX jumper
             settings. "
    ::= { cm1110RateConvEntry 6 }

    cm1110HwSw1TpAutoNegotiation OBJECT-TYPE
        SYNTAX 		INTEGER {
            swDownDisabled(0),
            swUpEnabled(1)
        }
        MAX-ACCESS read-only
        STATUS 		current
        DESCRIPTION
            "Media converter module's current switch setting for copper Auto-Negotiation."
    ::= { cm1110RateConvEntry 7 }

    cm1110HwSw2LinkMode OBJECT-TYPE
        SYNTAX 		INTEGER {
            swDownNormalMode(0),
            swUpSmartLinkPassthroughMode(1)
        }
        MAX-ACCESS read-only
        STATUS 		current
        DESCRIPTION
            "Media converter module's current switch setting for Link Mode."
    ::= { cm1110RateConvEntry 8 }

    cm1110HwSw3FiberFaultAlert OBJECT-TYPE
        SYNTAX 		INTEGER {
            swDownDisabled(0),
            swUpEnabled(1)
        }
        MAX-ACCESS read-only
        STATUS 		current
        DESCRIPTION
            "Media converter module's current switch setting for Fiber Fault Alert."
    ::= { cm1110RateConvEntry 9 }

    cm1110HwSw4TpDuplex OBJECT-TYPE
        SYNTAX 		INTEGER {
            swDownHalf(0),
            swUpFull(1)
        }
        MAX-ACCESS read-only
        STATUS 		current
        DESCRIPTION
            "Media converter module's current switch setting for copper duplex."
    ::= { cm1110RateConvEntry 10 }

    cm1110HwSw5TpSpeed OBJECT-TYPE
        SYNTAX 		INTEGER {
            swDown10Mbps(0),
            swUp100Mbps(1)
        }
        MAX-ACCESS read-only
        STATUS 		current
        DESCRIPTION
            "Media converter module's current switch setting for Link Mode."
    ::= { cm1110RateConvEntry 11 }

    cm1110HwSw6FiberAutoNegotiation OBJECT-TYPE
        SYNTAX 		INTEGER {
            swDownDisabled(0),
            swUpEnabled(1),
            notApplicable(2)
        }
        MAX-ACCESS read-only
        STATUS 		current
        DESCRIPTION
            "Media converter module's current switch setting for fiber Auto-Ngotiation.
             This object is not applicable if there is a 100 Mbps SFP modules
             inserted."
    ::= { cm1110RateConvEntry 12 }

    cm1110HwSw6FiberSfp100Duplex OBJECT-TYPE
        SYNTAX 		INTEGER {
            swDownHalfDuplex(0),
            swUpFullDuplex(1),
            notApplicable(2)
        }
        MAX-ACCESS read-only
        STATUS 		current
        DESCRIPTION
            "Media converter module's current switch setting for fiber duplex if a 100 Mbps
             SFP module is inserted.  Otherwise this object is not applicable."
    ::= { cm1110RateConvEntry 13 }

    cm1110HwSw7Loopback OBJECT-TYPE
        SYNTAX 		INTEGER {
            swDownEnabled(0),
            swUpDisabled(1)
        }
        MAX-ACCESS read-only
        STATUS 		current
        DESCRIPTION
            "Media converter module's current switch setting for fiber loopback mode."
    ::= { cm1110RateConvEntry 14 }

    cm1110FiberLinkStatus OBJECT-TYPE
        SYNTAX 		INTEGER {
            down(0),
            up(1)
        }
        MAX-ACCESS read-only
        STATUS 		current
        DESCRIPTION
            "Media converter module's current fiber link status."
    ::= { cm1110RateConvEntry 15 }

    cm1110FiberConnType OBJECT-TYPE
        SYNTAX 		INTEGER {
            sc(0),
            lc(1),
            st(2),
            sfp(3),
            fc(5),
            mtrj(6)
        }
        MAX-ACCESS read-only
        STATUS 		current
        DESCRIPTION
            "Media converter module's fiber port connector type."
    ::= { cm1110RateConvEntry 16 }


    cm1110FiberAutoNegState OBJECT-TYPE
        SYNTAX		INTEGER {
            disabled(0),
            complete(1),
            inProgress(2),
            notApplicable(99)
        }
        MAX-ACCESS	read-only
        STATUS 		current
        DESCRIPTION
            "Media converter module's current fiber auto-negotiation state. This object is
             not applicable if the fiber connector type is a 100 Mbps SFP module."
    ::= { cm1110RateConvEntry 17 }

    cm1110FiberSpeed OBJECT-TYPE
        SYNTAX 		INTEGER {
            speed100Mbps(1),
            speed1000Mbps(2)
        }
        MAX-ACCESS	read-only
        STATUS 		current
        DESCRIPTION
            "If fiber auto-negotiation state is complete then this object indicates
             the media converter module's current fiber auto-negotiated duplex setting. If
             auto-negotiation is not complete then the value returned should be
             ignored."
    ::= { cm1110RateConvEntry 18 }

    cm1110FiberDuplex OBJECT-TYPE
        SYNTAX		INTEGER {
            half(0),
            full(1)
        }
        MAX-ACCESS	read-only
        STATUS		current
        DESCRIPTION
            "This object identifies the current fiber port duplex state. "
    ::= { cm1110RateConvEntry 19 }

    cm1110FiberPauseEnh OBJECT-TYPE
        SYNTAX INTEGER {
            disabled(0),
            symmetrical(1),
            asymmetricalTx(2),
            asymmetricalRx(3)
        }
        MAX-ACCESS read-only
        STATUS current
        DESCRIPTION
            "If fiber auto-negotiation state is complete then this object indicates
             the media converter module's current fiber auto-negotiated pause setting. If
             auto-negotiation is not complete then the value returned should be
             ignored."
    ::= { cm1110RateConvEntry 20 }

    cm1110FiberLPRFStatus OBJECT-TYPE
        SYNTAX	INTEGER {
            ok(0),
            offline(1),
            linkFault(2),
            autoNegError(3),
            notApplicable(99)
        }
        MAX-ACCESS	read-only
        STATUS	current
        DESCRIPTION
            "Media converter module's fiber Link Partner Remote Fault status. This object
             is not applicable if there is a 100 Mbps SFP module inserted."
    ::= { cm1110RateConvEntry 21 }

    cm1110FiberSfp100FarEndFault OBJECT-TYPE
        SYNTAX	INTEGER {
            disable(0),
            ok(1),
            receivingFEF(2),
            sendingFEF(3),
            notApplicable(99)
        }
        MAX-ACCESS	read-only
        STATUS	current
        DESCRIPTION
            "Media converter module's current fiber Far End Fault status if a 100 Mbps SFP
             module is inserted. Otherwise this object is not applicable."
    ::= { cm1110RateConvEntry 22 }

    cm1110FiberReceiveStatus		OBJECT-TYPE
        SYNTAX	INTEGER {
            fault(0),
            ok(1)
        }
        MAX-ACCESS	read-write
        STATUS	current
        DESCRIPTION
            "This object identifies the status of whether light is being received
             on the fiber port"
    ::= { cm1110RateConvEntry 23 }

    cm1110FiberLoopBack		OBJECT-TYPE
        SYNTAX	EnableDisableValue
        MAX-ACCESS	read-write
        STATUS	current
        DESCRIPTION
            "
             This object is read-only if the media converter module's ConfigMode jumper is
             set to hardwareSwitches(0)."
    ::= { cm1110RateConvEntry 24 }


    cm1110CopperLinkStatus OBJECT-TYPE
        SYNTAX	INTEGER {
            down(0),
            up(1)
        }
        MAX-ACCESS	read-only
        STATUS	current
        DESCRIPTION
            "Media converter module's current copper link status."
    ::= { cm1110RateConvEntry 25 }

    cm1110CopperConnType OBJECT-TYPE
        SYNTAX INTEGER {
            rj45(0)
        }
        MAX-ACCESS read-only
        STATUS current
        DESCRIPTION
            "Media converter module's copper connector type."
    ::= { cm1110RateConvEntry 26 }

    cm1110CopperAutoNegState OBJECT-TYPE
        SYNTAX INTEGER {
            disabled(0),
            complete(1),
            inProgress(2)
        }
        MAX-ACCESS read-only
        STATUS current
        DESCRIPTION
            "Media converter module's current copper auto-negotiation state."
    ::= { cm1110RateConvEntry 27 }

        cm1110CopperSpeed OBJECT-TYPE
        SYNTAX 		INTEGER {
            speed10Mbs(0),
            speed100Mbps(1),
            speed1000Mbps(2)
        }
        MAX-ACCESS	read-only
        STATUS 		current
        DESCRIPTION
            "If copper auto-negotiation state is complete then this object
            indicates the media converter module's current copper auto-negotiated speed
            setting. If auto-negotiation is not complete then the value returned
            should be ignored."
    ::= { cm1110RateConvEntry 28 }

    cm1110CopperDuplex OBJECT-TYPE
        SYNTAX INTEGER {
            half(0),
            full(1)
        }
        MAX-ACCESS read-only
        STATUS current
        DESCRIPTION
            "If copper auto-negotiation state is complete then this object
            indicates the media converter module's current copper auto-negotiated duplex
            setting. If auto-negotiation is not complete then the value returned
            should be ignored."
    ::= { cm1110RateConvEntry 29 }

    cm1110CopperCrossOver OBJECT-TYPE
        SYNTAX INTEGER {
            mdi(0),
            mdix(1)
        }
        MAX-ACCESS read-only
        STATUS current
        DESCRIPTION
            "If copper auto-negotiation state is complete then this object
            indicates the media converter module's current copper auto-negotiated MDI/MDI-X
            setting. If auto-negotiation is not complete then the value returned
            should be ignored."
    ::= { cm1110RateConvEntry 30 }

    cm1110CopperPauseEnh OBJECT-TYPE
        SYNTAX INTEGER {
            disabled(0),
            symmetrical(1),
            asymmetricalTx(2),
            asymmetricalRx(3)
        }
        MAX-ACCESS read-only
        STATUS current
        DESCRIPTION
            "If copper auto-negotiation state is complete then this object indicates
             the media converter module's current copper auto-negotiated pause setting. If
             auto-negotiation is not complete then the value returned should be ignored."
    ::= { cm1110RateConvEntry 31 }

    cm1110CopperLPRFStatus OBJECT-TYPE
        SYNTAX INTEGER {
            ok(0),
            remoteFault(1)
        }
        MAX-ACCESS read-only
        STATUS current
        DESCRIPTION
            "Media converter module's copper Link Partner Remote Fault status."
    ::= { cm1110RateConvEntry 32 }

    cm1110CopperAutoSpeedDownshift OBJECT-TYPE
        SYNTAX INTEGER {
            noDownshift(0),
            downshift(1)
        }
        MAX-ACCESS read-only
        STATUS current
        DESCRIPTION
            "This object identifies the status of the copper auto speed downshift
             feature. noDownshift indicates that an automatic downshift of the
             copper speed has not occurred."
    ::= { cm1110RateConvEntry 33 }

--
-- cm1110RateConvTable
--

--
-- cm1110ConfigTable
--
cm1110ConfigTable	OBJECT-TYPE
    SYNTAX		SEQUENCE OF Cm1110ConfigEntry
    MAX-ACCESS	not-accessible
    STATUS		current
    DESCRIPTION
        "Table of CM-1110 type media converter module's configuration type
         information."
    ::= { cm1110RateConv 2 }

    cm1110ConfigEntry OBJECT-TYPE
        SYNTAX      Cm1110ConfigEntry
        MAX-ACCESS  not-accessible
        STATUS      current
        DESCRIPTION
            "Entries of the table, each relating to a separate CM-1110 type
             media converter module."
        INDEX   { mcrChassisIndex, cm1110ConfigSlotIndex}
        ::= { cm1110ConfigTable 1 }

    Cm1110ConfigEntry ::=
        SEQUENCE {
            cm1110ConfigSlotIndex						SlotNumber,
            cm1110ConfigStatus							ContainerStatus,
            cm1110ConfigModuleName						DisplayString,
            cm1110ConfigLinkMode							INTEGER,
            cm1110ConfigFiberFaultAlert				EnableDisableValue,
            cm1110ConfigMaxPacketsSize					INTEGER,
            cm1110ConfigFiberPortName					DisplayString,
            cm1110ConfigFiberPortEnable				YesNoValue,
            cm1110ConfigFiberAutoNegotiation			EnableDisableValue,
            cm1110ConfigFiberSfp100duplex				INTEGER,
            cm1110ConfigCopperPortName					DisplayString,
            cm1110ConfigCopperPortEnable				YesNoValue,
            cm1110ConfigCopperAutoNegotiation		EnableDisableValue,
            cm1110ConfigCopperAutoNegAdv10HDX		YesNoValue,
            cm1110ConfigCopperAutoNegAdv10FDX		YesNoValue,
            cm1110ConfigCopperAutoNegAdv100HDX		YesNoValue,
            cm1110ConfigCopperAutoNegAdv100FDX		YesNoValue,
            cm1110ConfigCopperAutoNegAdv1000FDX		YesNoValue,
            cm1110ConfigCopperSpeed						INTEGER,
            cm1110ConfigCopperDuplex					INTEGER,
            cm1110ConfigCopperCrossOver				INTEGER,
            cm1110ConfigCopperPauseEnh					INTEGER,
            cm1110ConfigCopperAutoSpeedDownshift	INTEGER,
            cm1110ConfigCopper10BaseTDistance		INTEGER,

            cm1110ConfigUnidirectionalEthernet	INTEGER,
            cm1110ConfigPriorityToEgressQueueMap0	INTEGER,
            cm1110ConfigPriorityToEgressQueueMap1	INTEGER,
            cm1110ConfigPriorityToEgressQueueMap2	INTEGER,
            cm1110ConfigPriorityToEgressQueueMap3	INTEGER,
            cm1110ConfigPriorityToEgressQueueMap4	INTEGER,
            cm1110ConfigPriorityToEgressQueueMap5	INTEGER,
            cm1110ConfigPriorityToEgressQueueMap6	INTEGER,
            cm1110ConfigPriorityToEgressQueueMap7	INTEGER,

            cm1110ConfigCopper8021pPriority			OnOffValue,
            cm1110ConfigCopperIpTosPriority			OnOffValue,
            cm1110ConfigCopperPriorityPrecedence	INTEGER,
            cm1110ConfigCopperCongestionPolicy		INTEGER,

            cm1110ConfigCopperPriorityMap0			INTEGER,
            cm1110ConfigCopperPriorityMap1			INTEGER,
            cm1110ConfigCopperPriorityMap2			INTEGER,
            cm1110ConfigCopperPriorityMap3			INTEGER,
            cm1110ConfigCopperPriorityMap4			INTEGER,
            cm1110ConfigCopperPriorityMap5			INTEGER,
            cm1110ConfigCopperPriorityMap6			INTEGER,
            cm1110ConfigCopperPriorityMap7			INTEGER,

            cm1110ConfigCopperIngressLimit			INTEGER,
            cm1110ConfigCopperEgressLimit			INTEGER,
            cm1110ConfigCopperDiscardTaggedFrames	OnOffValue,
            cm1110ConfigCopperDiscardUntaggedFrames	OnOffValue,
            cm1110ConfigCopperDefaultVlanId			INTEGER,
            cm1110ConfigCopperDefaultPriority		INTEGER,
            cm1110ConfigCopperVlanTaggingAction		INTEGER,
            cm1110ConfigCopperFilterUnknownMulticast		OnOffValue,
            cm1110ConfigCopperFilterUnknownUnicast		OnOffValue,

            cm1110ConfigFiber8021pPriority			OnOffValue,
            cm1110ConfigFiberIpTosPriority			OnOffValue,
            cm1110ConfigFiberPriorityPrecedence	INTEGER,
            cm1110ConfigFiberCongestionPolicy		INTEGER,

            cm1110ConfigFiberPriorityMap0			INTEGER,
            cm1110ConfigFiberPriorityMap1			INTEGER,
            cm1110ConfigFiberPriorityMap2			INTEGER,
            cm1110ConfigFiberPriorityMap3			INTEGER,
            cm1110ConfigFiberPriorityMap4			INTEGER,
            cm1110ConfigFiberPriorityMap5			INTEGER,
            cm1110ConfigFiberPriorityMap6			INTEGER,
            cm1110ConfigFiberPriorityMap7			INTEGER,

            cm1110ConfigFiberIngressLimit			INTEGER,
            cm1110ConfigFiberEgressLimit			INTEGER,
            cm1110ConfigFiberDiscardTaggedFrames	OnOffValue,
            cm1110ConfigFiberDiscardUntaggedFrames	OnOffValue,
            cm1110ConfigFiberDefaultVlanId			INTEGER,
            cm1110ConfigFiberDefaultPriority		INTEGER,
            cm1110ConfigFiberVlanTaggingAction		INTEGER,
            cm1110ConfigFiberFilterUnknownMulticast		OnOffValue,
            cm1110ConfigFiberFilterUnknownUnicast		OnOffValue,
            cm1110ConfigFiberSgmiiInterface                     EnableDisableValue
        }

    cm1110ConfigSlotIndex	OBJECT-TYPE
        SYNTAX		SlotNumber
        MAX-ACCESS	not-accessible
        STATUS		current
        DESCRIPTION
            "The Slot number the CM-1110 type module is currently inserted"
    ::= { cm1110ConfigEntry 2 }

    cm1110ConfigStatus OBJECT-TYPE
        SYNTAX      ContainerStatus
        MAX-ACCESS  read-write
        STATUS      current
        DESCRIPTION
          "When you perform a GET on this variable, one of
            the following values will be returned:
            1-Indicates that the container folder is active with no changes.
            2-Indicates that the container folder is active with change(s).
            Once you have completed setting the variables in a folder, you
            will want to submit your changes to the management module. To do
            this, set the Status variable to 4. If you want to discard the
            changes, set the Status variable to 6.
            4-Indicates that the changes in the container folder are to be
              submitted to the management module, verified and and saved to flash.
            6-Indicates that the changes in the container folder are to be
              discarded."
        ::= { cm1110ConfigEntry 3 }

    cm1110ConfigModuleName OBJECT-TYPE
        SYNTAX		DisplayString(SIZE(0..63))
        MAX-ACCESS	read-write
        STATUS		current
        DESCRIPTION
            "This object identifies a user configurable name for the media converter module
             present in the chassis. "
    ::= { cm1110ConfigEntry 4 }

    cm1110ConfigLinkMode	OBJECT-TYPE
        SYNTAX		INTEGER {
            standard(0),
            smartLinkPassthrough(1)
        }
        MAX-ACCESS	read-write
        STATUS		current
        DESCRIPTION
            "This object identifies the Link Mode for the media converter module. This object
            is read-only if the media converter module's ConfigMode jumper is set to
            hardwareSwitches(0)."
    ::= { cm1110ConfigEntry 5 }

    cm1110ConfigFiberFaultAlert	OBJECT-TYPE
        SYNTAX		EnableDisableValue
        MAX-ACCESS	read-write
        STATUS		current
        DESCRIPTION
            "This object identifies the Fiber Fault Alert setting for the media
             module. For 100 Mbps SFP modules, this setting is always effectively
             enabled if Link Mode is set to smartLinkPassthrough.
             This object is read-only if the media converter module's ConfigMode
             jumper is set to hardwareSwitches(0). "
    ::= { cm1110ConfigEntry 6 }

    cm1110ConfigMaxPacketsSize OBJECT-TYPE
        SYNTAX		INTEGER {
            maxPacket1522(0),
            maxPacket2048(1),
            maxPacket10240(2)
        }
        MAX-ACCESS	read-write
        STATUS		current
        DESCRIPTION
            "This object identifies the media converter module's maximum packet size setting
             This object is read-only if the media converter module's ConfigMode  jumper is
             set to hardwareSwitches(0)."
    ::= { cm1110ConfigEntry 7 }

    cm1110ConfigFiberPortName OBJECT-TYPE
        SYNTAX		DisplayString(SIZE(0..8))
        MAX-ACCESS	read-write
        STATUS 		current
        DESCRIPTION
            "This object identifies a user definable name for the fiber port."
    ::= { cm1110ConfigEntry 8 }

    cm1110ConfigFiberPortEnable OBJECT-TYPE
        SYNTAX		YesNoValue
        MAX-ACCESS	read-write
        STATUS 		current
        DESCRIPTION
            "This object identifies whether the fiber port is enabled. "
    ::= { cm1110ConfigEntry 9 }

    cm1110ConfigFiberAutoNegotiation OBJECT-TYPE
        SYNTAX 		EnableDisableValue
        MAX-ACCESS	read-write
        STATUS 		current
        DESCRIPTION
            "This object identifies whether fiber auto-negotiation  is enabled.
             This object does not apply if the fiber connector type is a 100 Mbps
             SFP module.  This object is read-only if the media converter module's ConfigMode
             jumper is set to hardwareSwitches(0)."
    ::= { cm1110ConfigEntry 10 }

    cm1110ConfigFiberSfp100duplex	OBJECT-TYPE
        SYNTAX INTEGER {
            full(0),
            half(1)
        }
        MAX-ACCESS read-write
        STATUS current
        DESCRIPTION
            "If the fiber connector type is SFP and it is a 100 Mbps fiber module then
             this object identifies the duplex setting for the 100 Mbps fiber port.
             Duplex for 1000 Mbps has to be auto negotiated. This object is read-only if the
             media converter module's ConfigMode jumper is set to hardwareSwitches(0)."
    ::= { cm1110ConfigEntry 11 }

    cm1110ConfigCopperPortName OBJECT-TYPE
        SYNTAX DisplayString(SIZE(0..8))
        MAX-ACCESS read-write
        STATUS current
        DESCRIPTION
            "This object identifies a user definable name for the copper port. "
    ::= { cm1110ConfigEntry 12 }

    cm1110ConfigCopperPortEnable OBJECT-TYPE
        SYNTAX	YesNoValue
        MAX-ACCESS	read-write
        STATUS	current
        DESCRIPTION
            "This object identifies whether the fiber port is enabled. "
    ::= { cm1110ConfigEntry 13 }

    cm1110ConfigCopperAutoNegotiation OBJECT-TYPE
        SYNTAX 		EnableDisableValue
        MAX-ACCESS	read-write
        STATUS 		current
        DESCRIPTION
            "This object identifies the whether copper auto-negotiation is
             enabled. This object is read-only if the media converter module's ConfigMode
             jumper is set to hardwareSwitches(0)."
    ::= { cm1110ConfigEntry 14 }

    cm1110ConfigCopperAutoNegAdv10HDX OBJECT-TYPE
        SYNTAX 		YesNoValue
        MAX-ACCESS	read-write
        STATUS 		current
        DESCRIPTION
        "This object controls whether or the copper port advertises willingness
         to connect at 10Mbps, half duplex.  This setting is ignored when
         auto-negotiation is disabled."
    ::= { cm1110ConfigEntry 15 }

    cm1110ConfigCopperAutoNegAdv10FDX OBJECT-TYPE
        SYNTAX 		YesNoValue
        MAX-ACCESS	read-write
        STATUS 		current
        DESCRIPTION
        "This object controls whether or the copper port advertises willingness
         to connect at 10Mbps, full duplex.  This setting is ignored when
         auto-negotiation is disabled."
    ::= { cm1110ConfigEntry 16 }

    cm1110ConfigCopperAutoNegAdv100HDX OBJECT-TYPE
        SYNTAX 		YesNoValue
        MAX-ACCESS	read-write
        STATUS 		current
        DESCRIPTION
        "This object controls whether or the copper port advertises willingness
         to connect at 100Mbps, half duplex.  This setting is ignored when
         auto-negotiation is disabled."
    ::= { cm1110ConfigEntry 17 }

    cm1110ConfigCopperAutoNegAdv100FDX OBJECT-TYPE
        SYNTAX 		YesNoValue
        MAX-ACCESS	read-write
        STATUS 		current
        DESCRIPTION
        "This object controls whether or the copper port advertises willingness
         to connect at 100Mbps, full duplex.  This setting is ignored when
         auto-negotiation is disabled."
    ::= { cm1110ConfigEntry 18 }

    cm1110ConfigCopperAutoNegAdv1000FDX OBJECT-TYPE
        SYNTAX 		YesNoValue
        MAX-ACCESS	read-write
        STATUS 		current
        DESCRIPTION
        "This object controls whether or the copper port advertises willingness
         to connect at 1000Mbps, full duplex.  This setting is ignored when
         auto-negotiation is disabled."
    ::= { cm1110ConfigEntry 19 }

    cm1110ConfigCopperSpeed OBJECT-TYPE
        SYNTAX 		INTEGER {
            speed10Mbs(0),
            speed100Mbps(1)
        }
        MAX-ACCESS	read-write
        STATUS 		current
        DESCRIPTION
            "If copper auto-negotiation is disabled then this object identifies
             the configured cooper speed. 1000 Mbps speed can only be auto
             negotiated. If copper auto-negotiation is enabled then this object
             is ignored.  This object is read-only if the media converter module's ConfigMode
             jumper is set to hardwareSwitches(0)."
    ::= { cm1110ConfigEntry 20 }

    cm1110ConfigCopperDuplex	OBJECT-TYPE
        SYNTAX INTEGER {
            full(0),
            half(1)
        }
        MAX-ACCESS read-write
        STATUS current
        DESCRIPTION
            "If copper auto-negotiation is disabled then this object identifies
             the duplex setting for 10 & 100 Mbps for the copper port.  Duplex for
             1000 Mbps has to be auto negotiated. This object is read-only if the
             media converter module's ConfigMode jumper is set to hardwareSwitches(0)."
    ::= { cm1110ConfigEntry 21 }

    cm1110ConfigCopperCrossOver OBJECT-TYPE
        SYNTAX INTEGER {
            auto(0),
            mdi(1),
            mdix(2)
        }
        MAX-ACCESS read-write
        STATUS current
        DESCRIPTION
            "This object identifies the copper MDI/MDI-X setting.This object
            is read-only if the media converter module's ConfigMode jumper is set to"
        ::= { cm1110ConfigEntry 22 }


    cm1110ConfigCopperPauseEnh OBJECT-TYPE
        SYNTAX INTEGER {
            disabled(0),
            symmetrical(1),
            asymmetricalTx(2),
            symmAsymRx(3)
        }
        MAX-ACCESS read-write
        STATUS current
        DESCRIPTION
            "This object identifies the copper pause (flow control) setting that
             is a advertised. The settings can be disabled, advertise symmetrical,
             advertise asymmetrical TX or advertise symmetrical and asymmetrical
             RX. This object is read-only if the media converter module's ConfigMode jumper
             is set to hardwareSwitches(0)."
    ::= { cm1110ConfigEntry 23 }

    cm1110ConfigCopperAutoSpeedDownshift OBJECT-TYPE
        SYNTAX INTEGER(0..8)
        MAX-ACCESS read-write
        STATUS current
        DESCRIPTION
            "This object identifies the number of times the PHY attempts to
             establish a Gigabit link before the PHY downshift to the next
             highest speed.  A value of 0 indicates the auto downshift is
             disabled"
    ::= { cm1110ConfigEntry 24 }

    cm1110ConfigCopper10BaseTDistance OBJECT-TYPE
        SYNTAX INTEGER {
            normal(0),
            extended(1)
        }
        MAX-ACCESS read-write
        STATUS current
        DESCRIPTION
            "When using cable exceeding 100 meters in 10BASE-T mode this feature
             should be set to extended(1)."
    ::= { cm1110ConfigEntry 25 }


    cm1110ConfigUnidirectionalEthernet OBJECT-TYPE
        SYNTAX INTEGER {
            notApplicable(-1),
            disabled(0),
            copperToFiber(1),
            fiberToCopper(2)
        }
        MAX-ACCESS read-write
        STATUS current
        DESCRIPTION
            "Restrict the flow of Ethernet traffic to a single direction.
             A value of -1 signifies that this feature is not supported
             by the current media converter module firmware.
             (This feature may require a media converter module firmware upgrade)."
    ::= { cm1110ConfigEntry 26 }

    cm1110ConfigPriorityToEgressQueueMap0 OBJECT-TYPE
        SYNTAX INTEGER(0..3)
        MAX-ACCESS read-write
        STATUS current
        DESCRIPTION
            "Set the egress queue of frames tagged with 802.1p priority 0.
             A value of -1 signifies that this feature is not supported
             by the current media converter module firmware.
             (This feature may require a media converter module firmware upgrade)."
    ::= { cm1110ConfigEntry 27 }

    cm1110ConfigPriorityToEgressQueueMap1 OBJECT-TYPE
        SYNTAX INTEGER(0..3)
        MAX-ACCESS read-write
        STATUS current
        DESCRIPTION
            "Set the egress queue of frames tagged with 802.1p priority 1.
             A value of -1 signifies that this feature is not supported
             by the current media converter module firmware.
             (This feature may require a media converter module firmware upgrade)."
    ::= { cm1110ConfigEntry 28 }

    cm1110ConfigPriorityToEgressQueueMap2 OBJECT-TYPE
        SYNTAX INTEGER(0..3)
        MAX-ACCESS read-write
        STATUS current
        DESCRIPTION
            "Set the egress queue of frames tagged with 802.1p priority 2.
             A value of -1 signifies that this feature is not supported
             by the current media converter module firmware.
             (This feature may require a media converter module firmware upgrade)."
    ::= { cm1110ConfigEntry 29 }

    cm1110ConfigPriorityToEgressQueueMap3 OBJECT-TYPE
        SYNTAX INTEGER(0..3)
        MAX-ACCESS read-write
        STATUS current
        DESCRIPTION
            "Set the egress queue of frames tagged with 802.1p priority 3.
             A value of -1 signifies that this feature is not supported
             by the current media converter module firmware.
             (This feature may require a media converter module firmware upgrade)."
    ::= { cm1110ConfigEntry 30 }

    cm1110ConfigPriorityToEgressQueueMap4 OBJECT-TYPE
        SYNTAX INTEGER(0..3)
        MAX-ACCESS read-write
        STATUS current
        DESCRIPTION
            "Set the egress queue of frames tagged with 802.1p priority 4.
             A value of -1 signifies that this feature is not supported
             by the current media converter module firmware.
             (This feature may require a media converter module firmware upgrade)."
    ::= { cm1110ConfigEntry 31 }

    cm1110ConfigPriorityToEgressQueueMap5 OBJECT-TYPE
        SYNTAX INTEGER(0..3)
        MAX-ACCESS read-write
        STATUS current
        DESCRIPTION
            "Set the egress queue of frames tagged with 802.1p priority 5.
             A value of -1 signifies that this feature is not supported
             by the current media converter module firmware.
             (This feature may require a media converter module firmware upgrade)."
    ::= { cm1110ConfigEntry 32 }

    cm1110ConfigPriorityToEgressQueueMap6 OBJECT-TYPE
        SYNTAX INTEGER(0..3)
        MAX-ACCESS read-write
        STATUS current
        DESCRIPTION
            "Set the egress queue of frames tagged with 802.1p priority 6.
             A value of -1 signifies that this feature is not supported
             by the current media converter module firmware.
             (This feature may require a media converter module firmware upgrade)."
    ::= { cm1110ConfigEntry 33 }

    cm1110ConfigPriorityToEgressQueueMap7 OBJECT-TYPE
        SYNTAX INTEGER(0..3)
        MAX-ACCESS read-write
        STATUS current
        DESCRIPTION
            "Set the egress queue of frames tagged with 802.1p priority 7.
             A value of -1 signifies that this feature is not supported
             by the current media converter module firmware.
             (This feature may require a media converter module firmware upgrade)."
    ::= { cm1110ConfigEntry 34 }

    cm1110ConfigCopper8021pPriority OBJECT-TYPE
        SYNTAX      OnOffValue
        MAX-ACCESS read-write
        STATUS current
        DESCRIPTION
            "Use 802.1p tag priority.
             (This feature may require a media converter module firmware upgrade)."
    ::= { cm1110ConfigEntry 35 }

    cm1110ConfigCopperIpTosPriority OBJECT-TYPE
        SYNTAX      OnOffValue
        MAX-ACCESS read-write
        STATUS current
        DESCRIPTION
            "Use IP TOS priority.
             (This feature may require a media converter module firmware upgrade)."
    ::= { cm1110ConfigEntry 36 }

    cm1110ConfigCopperPriorityPrecedence OBJECT-TYPE
        SYNTAX INTEGER {
            notApplicable(-1),
            priority8021p(0),
            priorityIpTos(1)
        }
        MAX-ACCESS read-write
        STATUS current
        DESCRIPTION
            "Configure priority precedence.
             (This feature may require a media converter module firmware upgrade)."
    ::= { cm1110ConfigEntry 37 }

    cm1110ConfigCopperCongestionPolicy OBJECT-TYPE
        SYNTAX INTEGER {
            notApplicable(-1),
            strict(0),
            weighted(1)
        }
        MAX-ACCESS read-write
        STATUS current
        DESCRIPTION
            "Configure priority congestion policy.
             (This feature may require a media converter module firmware upgrade)."
    ::= { cm1110ConfigEntry 38 }

    cm1110ConfigCopperPriorityMap0 OBJECT-TYPE
        SYNTAX INTEGER(0..7)
        MAX-ACCESS read-write
        STATUS current
        DESCRIPTION
            "Change the priority of frames tagged with 802.1p priority 0.
             A value of -1 signifies that this feature is not supported
             by the current media converter module firmware.
             (This feature may require a media converter module firmware upgrade)."
    ::= { cm1110ConfigEntry 39 }

    cm1110ConfigCopperPriorityMap1 OBJECT-TYPE
        SYNTAX INTEGER(0..7)
        MAX-ACCESS read-write
        STATUS current
        DESCRIPTION
            "Change the priority of frames tagged with 802.1p priority 1.
             A value of -1 signifies that this feature is not supported
             by the current media converter module firmware.
             (This feature may require a media converter module firmware upgrade)."
    ::= { cm1110ConfigEntry 40 }

    cm1110ConfigCopperPriorityMap2 OBJECT-TYPE
        SYNTAX INTEGER(0..7)
        MAX-ACCESS read-write
        STATUS current
        DESCRIPTION
            "Change the priority of frames tagged with 802.1p priority 2.
             A value of -1 signifies that this feature is not supported
             by the current media converter module firmware.
             (This feature may require a media converter module firmware upgrade)."
    ::= { cm1110ConfigEntry 41 }

    cm1110ConfigCopperPriorityMap3 OBJECT-TYPE
        SYNTAX INTEGER(0..7)
        MAX-ACCESS read-write
        STATUS current
        DESCRIPTION
            "Change the priority of frames tagged with 802.1p priority 3.
             A value of -1 signifies that this feature is not supported
             by the current media converter module firmware.
             (This feature may require a media converter module firmware upgrade)."
    ::= { cm1110ConfigEntry 42 }

    cm1110ConfigCopperPriorityMap4 OBJECT-TYPE
        SYNTAX INTEGER(0..7)
        MAX-ACCESS read-write
        STATUS current
        DESCRIPTION
            "Change the priority of frames tagged with 802.1p priority 4.
             A value of -1 signifies that this feature is not supported
             by the current media converter module firmware.
             (This feature may require a media converter module firmware upgrade)."
    ::= { cm1110ConfigEntry 43 }

    cm1110ConfigCopperPriorityMap5 OBJECT-TYPE
        SYNTAX INTEGER(0..7)
        MAX-ACCESS read-write
        STATUS current
        DESCRIPTION
            "Change the priority of frames tagged with 802.1p priority 5.
             A value of -1 signifies that this feature is not supported
             by the current media converter module firmware.
             (This feature may require a media converter module firmware upgrade)."
    ::= { cm1110ConfigEntry 44 }

    cm1110ConfigCopperPriorityMap6 OBJECT-TYPE
        SYNTAX INTEGER(0..7)
        MAX-ACCESS read-write
        STATUS current
        DESCRIPTION
            "Change the priority of frames tagged with 802.1p priority 6.
             A value of -1 signifies that this feature is not supported
             by the current media converter module firmware.
             (This feature may require a media converter module firmware upgrade)."
    ::= { cm1110ConfigEntry 45 }

    cm1110ConfigCopperPriorityMap7 OBJECT-TYPE
        SYNTAX INTEGER(0..7)
        MAX-ACCESS read-write
        STATUS current
        DESCRIPTION
            "Change the priority of frames tagged with 802.1p priority 7.
             A value of -1 signifies that this feature is not supported
             by the current media converter module firmware.
             (This feature may require a media converter module firmware upgrade)."
    ::= { cm1110ConfigEntry 46 }

    cm1110ConfigCopperIngressLimit OBJECT-TYPE
        SYNTAX INTEGER {
            notApplicable(-1),
            rateUnlimited(0),
            rate64kbps(1),
            rate128kbps(2),
            rate192kbps(3),
            rate256kbps(4),
            rate320kbps(5),
            rate384kbps(6),
            rate512kbps(7),
            rate768kbps(8),
            rate1mbps  (9),
            rate2mbps  (10),
            rate3mbps  (11),
            rate4mbps  (12),
            rate5mbps  (13),
            rate6mbps  (14),
            rate7mbps  (15),
            rate8mbps  (16),
            rate9mbps  (17),
            rate10mbps (18),
            rate20mbps (19),
            rate30mbps (20),
            rate40mbps (21),
            rate50mbps (22),
            rate60mbps (23),
            rate70mbps (24),
            rate80mbps (25),
            rate90mbps (26),
            rate100mbps(27),
            rate200mbps(28),
            rate300mbps(29),
            rate400mbps(30),
            rate500mbps(31),
            rate600mbps(32),
            rate700mbps(33),
            rate800mbps(34),
            rate900mbps(35)
        }
        MAX-ACCESS read-write
        STATUS current
        DESCRIPTION
            "Set a limit on the rate of incoming packets.
             (This feature may require a media converter module firmware upgrade)."
    ::= { cm1110ConfigEntry 47 }

    cm1110ConfigCopperEgressLimit OBJECT-TYPE
        SYNTAX INTEGER {
            notApplicable(-1),
            rateUnlimited(0),
            rate64kbps(1),
            rate128kbps(2),
            rate192kbps(3),
            rate256kbps(4),
            rate320kbps(5),
            rate384kbps(6),
            rate512kbps(7),
            rate768kbps(8),
            rate1mbps  (9),
            rate2mbps  (10),
            rate3mbps  (11),
            rate4mbps  (12),
            rate5mbps  (13),
            rate6mbps  (14),
            rate7mbps  (15),
            rate8mbps  (16),
            rate9mbps  (17),
            rate10mbps (18),
            rate20mbps (19),
            rate30mbps (20),
            rate40mbps (21),
            rate50mbps (22),
            rate60mbps (23),
            rate70mbps (24),
            rate80mbps (25),
            rate90mbps (26),
            rate100mbps(27),
            rate200mbps(28),
            rate300mbps(29),
            rate400mbps(30),
            rate500mbps(31),
            rate600mbps(32),
            rate700mbps(33),
            rate800mbps(34),
            rate900mbps(35)
        }
        MAX-ACCESS read-write
        STATUS current
        DESCRIPTION
            "Set a limit on the rate of outgoing packets.
             (This feature may require a media converter module firmware upgrade)."
    ::= { cm1110ConfigEntry 48 }

    cm1110ConfigCopperDiscardTaggedFrames OBJECT-TYPE
        SYNTAX      OnOffValue
        MAX-ACCESS read-write
        STATUS current
        DESCRIPTION
            "Enable discarding of tagged frames.
             (This feature may require a media converter module firmware upgrade)."
    ::= { cm1110ConfigEntry 49 }

    cm1110ConfigCopperDiscardUntaggedFrames OBJECT-TYPE
        SYNTAX      OnOffValue
        MAX-ACCESS read-write
        STATUS current
        DESCRIPTION
            "Enable discarding of untagged frames.
             (This feature may require a media converter module firmware upgrade)."
    ::= { cm1110ConfigEntry 50 }

    cm1110ConfigCopperDefaultVlanId OBJECT-TYPE
        SYNTAX      INTEGER(0..4095)
        MAX-ACCESS read-write
        STATUS current
        DESCRIPTION
            "Set the default VLAN ID to insert when tagging frames.
             (This feature may require a media converter module firmware upgrade)."
    ::= { cm1110ConfigEntry 51 }

    cm1110ConfigCopperDefaultPriority OBJECT-TYPE
        SYNTAX      INTEGER(0..7)
        MAX-ACCESS read-write
        STATUS current
        DESCRIPTION
            "Set the default frame priority.
             (This feature may require a media converter module firmware upgrade)."
    ::= { cm1110ConfigEntry 52 }

    cm1110ConfigCopperVlanTaggingAction OBJECT-TYPE
        SYNTAX INTEGER {
            notApplicable(-1),
            none(0),
            untag(1),
            tag(2),
            doubleTag(3)
        }
        MAX-ACCESS read-write
        STATUS current
        DESCRIPTION
            "Set the default tagging action.
             (This feature may require a media converter module firmware upgrade)."
    ::= { cm1110ConfigEntry 53 }

    cm1110ConfigCopperFilterUnknownMulticast OBJECT-TYPE
        SYNTAX      OnOffValue
        MAX-ACCESS read-write
        STATUS current
        DESCRIPTION
            "Enable filtering of multicast frames with an unknown destination
             (This feature may require a media converter module firmware upgrade)."
    ::= { cm1110ConfigEntry 54 }

    cm1110ConfigCopperFilterUnknownUnicast OBJECT-TYPE
        SYNTAX      OnOffValue
        MAX-ACCESS read-write
        STATUS current
        DESCRIPTION
            "Enable filtering of unicast frames with an unknown destination
             (This feature may require a media converter module firmware upgrade)."
    ::= { cm1110ConfigEntry 55 }

    cm1110ConfigFiber8021pPriority OBJECT-TYPE
        SYNTAX      OnOffValue
        MAX-ACCESS read-write
        STATUS current
        DESCRIPTION
            "Use 802.1p tag priority.
             (This feature may require a media converter module firmware upgrade)."
    ::= { cm1110ConfigEntry 56 }

    cm1110ConfigFiberIpTosPriority OBJECT-TYPE
        SYNTAX      OnOffValue
        MAX-ACCESS read-write
        STATUS current
        DESCRIPTION
            "Use IP TOS priority.
             (This feature may require a media converter module firmware upgrade)."
    ::= { cm1110ConfigEntry 57 }

    cm1110ConfigFiberPriorityPrecedence OBJECT-TYPE
        SYNTAX INTEGER {
            notApplicable(-1),
            priority8021p(0),
            priorityIpTos(1)
        }
        MAX-ACCESS read-write
        STATUS current
        DESCRIPTION
            "Configure priority precedence.
             (This feature may require a media converter module firmware upgrade)."
    ::= { cm1110ConfigEntry 58 }

    cm1110ConfigFiberCongestionPolicy OBJECT-TYPE
        SYNTAX INTEGER {
            notApplicable(-1),
            strict(0),
            weighted(1)
        }
        MAX-ACCESS read-write
        STATUS current
        DESCRIPTION
            "Configure priority congestion policy.
             (This feature may require a media converter module firmware upgrade)."
    ::= { cm1110ConfigEntry 59 }

    cm1110ConfigFiberPriorityMap0 OBJECT-TYPE
        SYNTAX INTEGER(0..7)
        MAX-ACCESS read-write
        STATUS current
        DESCRIPTION
            "Change the priority of frames tagged with 802.1p priority 0.
             A value of -1 signifies that this feature is not supported
             by the current media converter module firmware.
             (This feature may require a media converter module firmware upgrade)."
    ::= { cm1110ConfigEntry 60 }

    cm1110ConfigFiberPriorityMap1 OBJECT-TYPE
        SYNTAX INTEGER(0..7)
        MAX-ACCESS read-write
        STATUS current
        DESCRIPTION
            "Change the priority of frames tagged with 802.1p priority 1.
             A value of -1 signifies that this feature is not supported
             by the current media converter module firmware.
             (This feature may require a media converter module firmware upgrade)."
    ::= { cm1110ConfigEntry 61 }

    cm1110ConfigFiberPriorityMap2 OBJECT-TYPE
        SYNTAX INTEGER(0..7)
        MAX-ACCESS read-write
        STATUS current
        DESCRIPTION
            "Change the priority of frames tagged with 802.1p priority 2.
             A value of -1 signifies that this feature is not supported
             by the current media converter module firmware.
             (This feature may require a media converter module firmware upgrade)."
    ::= { cm1110ConfigEntry 62 }

    cm1110ConfigFiberPriorityMap3 OBJECT-TYPE
        SYNTAX INTEGER(0..7)
        MAX-ACCESS read-write
        STATUS current
        DESCRIPTION
            "Change the priority of frames tagged with 802.1p priority 3.
             A value of -1 signifies that this feature is not supported
             by the current media converter module firmware.
             (This feature may require a media converter module firmware upgrade)."
    ::= { cm1110ConfigEntry 63 }

    cm1110ConfigFiberPriorityMap4 OBJECT-TYPE
        SYNTAX INTEGER(0..7)
        MAX-ACCESS read-write
        STATUS current
        DESCRIPTION
            "Change the priority of frames tagged with 802.1p priority 4.
             A value of -1 signifies that this feature is not supported
             by the current media converter module firmware.
             (This feature may require a media converter module firmware upgrade)."
    ::= { cm1110ConfigEntry 64 }

    cm1110ConfigFiberPriorityMap5 OBJECT-TYPE
        SYNTAX INTEGER(0..7)
        MAX-ACCESS read-write
        STATUS current
        DESCRIPTION
            "Change the priority of frames tagged with 802.1p priority 5.
             A value of -1 signifies that this feature is not supported
             by the current media converter module firmware.
             (This feature may require a media converter module firmware upgrade)."
    ::= { cm1110ConfigEntry 65 }

    cm1110ConfigFiberPriorityMap6 OBJECT-TYPE
        SYNTAX INTEGER(0..7)
        MAX-ACCESS read-write
        STATUS current
        DESCRIPTION
            "Change the priority of frames tagged with 802.1p priority 6.
             A value of -1 signifies that this feature is not supported
             by the current media converter module firmware.
             (This feature may require a media converter module firmware upgrade)."
    ::= { cm1110ConfigEntry 66 }

    cm1110ConfigFiberPriorityMap7 OBJECT-TYPE
        SYNTAX INTEGER(0..7)
        MAX-ACCESS read-write
        STATUS current
        DESCRIPTION
            "Change the priority of frames tagged with 802.1p priority 7.
             A value of -1 signifies that this feature is not supported
             by the current media converter module firmware.
             (This feature may require a media converter module firmware upgrade)."
    ::= { cm1110ConfigEntry 67 }

    cm1110ConfigFiberIngressLimit OBJECT-TYPE
        SYNTAX INTEGER {
            notApplicable(-1),
            rateUnlimited(0),
            rate64kbps(1),
            rate128kbps(2),
            rate192kbps(3),
            rate256kbps(4),
            rate320kbps(5),
            rate384kbps(6),
            rate512kbps(7),
            rate768kbps(8),
            rate1mbps  (9),
            rate2mbps  (10),
            rate3mbps  (11),
            rate4mbps  (12),
            rate5mbps  (13),
            rate6mbps  (14),
            rate7mbps  (15),
            rate8mbps  (16),
            rate9mbps  (17),
            rate10mbps (18),
            rate20mbps (19),
            rate30mbps (20),
            rate40mbps (21),
            rate50mbps (22),
            rate60mbps (23),
            rate70mbps (24),
            rate80mbps (25),
            rate90mbps (26),
            rate100mbps(27),
            rate200mbps(28),
            rate300mbps(29),
            rate400mbps(30),
            rate500mbps(31),
            rate600mbps(32),
            rate700mbps(33),
            rate800mbps(34),
            rate900mbps(35)
        }
        MAX-ACCESS read-write
        STATUS current
        DESCRIPTION
            "Set a limit on the rate of incoming packets.
             (This feature may require a media converter module firmware upgrade)."
    ::= { cm1110ConfigEntry 68 }

    cm1110ConfigFiberEgressLimit OBJECT-TYPE
        SYNTAX INTEGER {
            notApplicable(-1),
            rateUnlimited(0),
            rate64kbps(1),
            rate128kbps(2),
            rate192kbps(3),
            rate256kbps(4),
            rate320kbps(5),
            rate384kbps(6),
            rate512kbps(7),
            rate768kbps(8),
            rate1mbps  (9),
            rate2mbps  (10),
            rate3mbps  (11),
            rate4mbps  (12),
            rate5mbps  (13),
            rate6mbps  (14),
            rate7mbps  (15),
            rate8mbps  (16),
            rate9mbps  (17),
            rate10mbps (18),
            rate20mbps (19),
            rate30mbps (20),
            rate40mbps (21),
            rate50mbps (22),
            rate60mbps (23),
            rate70mbps (24),
            rate80mbps (25),
            rate90mbps (26),
            rate100mbps(27),
            rate200mbps(28),
            rate300mbps(29),
            rate400mbps(30),
            rate500mbps(31),
            rate600mbps(32),
            rate700mbps(33),
            rate800mbps(34),
            rate900mbps(35)
        }
        MAX-ACCESS read-write
        STATUS current
        DESCRIPTION
            "Set a limit on the rate of outgoing packets.
             (This feature may require a media converter module firmware upgrade)."
    ::= { cm1110ConfigEntry 69 }

    cm1110ConfigFiberDiscardTaggedFrames OBJECT-TYPE
        SYNTAX      OnOffValue
        MAX-ACCESS read-write
        STATUS current
        DESCRIPTION
            "Enable discarding of tagged frames.
             (This feature may require a media converter module firmware upgrade)."
    ::= { cm1110ConfigEntry 70 }

    cm1110ConfigFiberDiscardUntaggedFrames OBJECT-TYPE
        SYNTAX      OnOffValue
        MAX-ACCESS read-write
        STATUS current
        DESCRIPTION
            "Enable discarding of untagged frames.
             (This feature may require a media converter module firmware upgrade)."
    ::= { cm1110ConfigEntry 71 }

    cm1110ConfigFiberDefaultVlanId OBJECT-TYPE
        SYNTAX      INTEGER(0..4095)
        MAX-ACCESS read-write
        STATUS current
        DESCRIPTION
            "Set the default VLAN ID to insert when tagging frames.
             (This feature may require a media converter module firmware upgrade)."
    ::= { cm1110ConfigEntry 72 }

    cm1110ConfigFiberDefaultPriority OBJECT-TYPE
        SYNTAX      INTEGER(0..7)
        MAX-ACCESS read-write
        STATUS current
        DESCRIPTION
            "Set the default frame priority.
             (This feature may require a media converter module firmware upgrade)."
    ::= { cm1110ConfigEntry 73 }

    cm1110ConfigFiberVlanTaggingAction OBJECT-TYPE
        SYNTAX INTEGER {
            notApplicable(-1),
            none(0),
            untag(1),
            tag(2),
            doubleTag(3)
        }
        MAX-ACCESS read-write
        STATUS current
        DESCRIPTION
            "Set the default tagging action.
             (This feature may require a media converter module firmware upgrade)."
    ::= { cm1110ConfigEntry 74 }

    cm1110ConfigFiberFilterUnknownMulticast OBJECT-TYPE
        SYNTAX      OnOffValue
        MAX-ACCESS read-write
        STATUS current
        DESCRIPTION
            "Enable filtering of multicast frames with an unknown destination
             (This feature may require a media converter module firmware upgrade)."
    ::= { cm1110ConfigEntry 75 }

    cm1110ConfigFiberFilterUnknownUnicast OBJECT-TYPE
        SYNTAX      OnOffValue
        MAX-ACCESS read-write
        STATUS current
        DESCRIPTION
            "Enable filtering of unicast frames with an unknown destination
             (This feature may require a media converter module firmware upgrade)."
    ::= { cm1110ConfigEntry 76 }

    cm1110ConfigFiberSgmiiInterface OBJECT-TYPE
        SYNTAX 		EnableDisableValue
        MAX-ACCESS	read-write
        STATUS 		current
        DESCRIPTION
            "This object identifies whether fiber SGMII interface is enabled."
   ::= { cm1110ConfigEntry 77 }


--
--
-- cm1110ConfigEntry
--
--
-- cm1110LedTable
--
cm1110LedTable	OBJECT-TYPE
    SYNTAX		SEQUENCE OF Cm1110LedEntry
    MAX-ACCESS	not-accessible
    STATUS		current
    DESCRIPTION
        "Table of CM-1110 type media converter module's LED status information."
    ::= { cm1110RateConv 3 }

    cm1110LedEntry OBJECT-TYPE
        SYNTAX      Cm1110LedEntry
        MAX-ACCESS  not-accessible
        STATUS      current
        DESCRIPTION
            "Entries of the table, each relating to a separate CM-1110 type
             media converter module."
        INDEX   { mcrChassisIndex, cm1110LedSlotIndex }
        ::= { cm1110LedTable 1 }

    Cm1110LedEntry ::=
        SEQUENCE {
            cm1110LedSlotIndex	SlotNumber,
            cm1110LedPWR			INTEGER,
            cm1110LedFDF			INTEGER,
            cm1110LedLKF			INTEGER,
            cm1110LedCopperSpeed	INTEGER,
            cm1110LedFDC			INTEGER,
            cm1110LedLKC			INTEGER
        }

    cm1110LedSlotIndex	OBJECT-TYPE
        SYNTAX		SlotNumber
        MAX-ACCESS	not-accessible
        STATUS		current
        DESCRIPTION
            "The Slot number the CM-1110 type module is currently inserted"
    ::= { cm1110LedEntry 2 }

    cm1110LedPWR	OBJECT-TYPE
        SYNTAX		INTEGER {
            off(0),
            onGreen(1),
            blinking(2)
        }
        MAX-ACCESS	read-only
        STATUS		current
        DESCRIPTION
            "This object identifies the status of the power (PWR) LED on the media converter module.
             Possible status values are:
                 off(0) - No power to the module
                 onGreen(1) - Power being applied to module
                 blinking(2) - Fiber loopback enabled"
    ::= { cm1110LedEntry 3 }

    cm1110LedFDF	OBJECT-TYPE
        SYNTAX		INTEGER {
            offHalfDuplex(0),
            onFullDuplex(1)
        }
        MAX-ACCESS	read-only
        STATUS		current
        DESCRIPTION
            "This object identifies the status of the Full Duplex Fiber (FDF) LED
             on the media converter module."
    ::= { cm1110LedEntry 4 }

    cm1110LedLKF	OBJECT-TYPE
        SYNTAX		INTEGER {
            off(0),
            on(1)
        }
        MAX-ACCESS	read-only
        STATUS		current
        DESCRIPTION
            "This object identifies the status of the link fiber (LKF) LED on the
             media converter module.
             Possible status values are:
                 off(0) - No fiber link
                 on(1) - Fiber link present"
    ::= { cm1110LedEntry 5 }

    cm1110LedCopperSpeed	OBJECT-TYPE
        SYNTAX		INTEGER {
            off10Mbps(0),
            onYellow100Mbps(1),
            onGreen1000Mbps(2)
        }
        MAX-ACCESS	read-only
        STATUS		current
        DESCRIPTION
            "This object identifies the status of the link copper speed (100/1000)
             LED on the management module."
    ::= { cm1110LedEntry 6 }

    cm1110LedFDC	OBJECT-TYPE
        SYNTAX		INTEGER {
            offHalfDuplex(0),
            onFullDuplex(1)
        }
        MAX-ACCESS	read-only
        STATUS		current
        DESCRIPTION
            "This object identifies the status of the Full Duplex Copper (FDC) LED
             on the media converter module."
    ::= { cm1110LedEntry 7 }

    cm1110LedLKC	OBJECT-TYPE
        SYNTAX		INTEGER {
            off(0),
            on(1)
        }
        MAX-ACCESS	read-only
        STATUS		current
        DESCRIPTION
            "This object identifies the status of the link copper (LKC) LED on the
             media converter module. Possible status values are:
                 off(0) - No copper link
                 on(1) - Copper link present"
    ::= { cm1110LedEntry 8 }

--
-- end of cm1110LedTable
--
--
-- cm1110RateConvStatsTable
--
cm1110RateConvStatsTable	OBJECT-TYPE
    SYNTAX		SEQUENCE OF Cm1110RateConvStatsEntry
    MAX-ACCESS	not-accessible
    STATUS		current
    DESCRIPTION
        "Table of CM-1110 type media converter module's configuration and status type
         information."
    ::= { cm1110RateConv 4 }

    cm1110RateConvStatsEntry OBJECT-TYPE
        SYNTAX      Cm1110RateConvStatsEntry
        MAX-ACCESS  not-accessible
        STATUS      current
        DESCRIPTION
            "Entries of the table, each relating to a separate CM-1110 type
             media converter module."
        INDEX   { mcrChassisIndex, cm1110StatsSlotIndex, cm1110MediaPortIndex }
        ::= { cm1110RateConvStatsTable 1 }

    Cm1110RateConvStatsEntry ::=
        SEQUENCE {
            cm1110StatsSlotIndex				SlotNumber,
            cm1110MediaPortIndex				INTEGER,

            cm1110PortInDiscards 			Counter32,
            cm1110PortInFiltered				INTEGER,
            cm1110PortInGoodOctets			Counter32,
            cm1110PortHCInGoodOctets		Counter64,
            cm1110PortInBadOctets			Counter32,
            cm1110PortInUnicasts				Counter32,
            cm1110PortInBroadcasts			Counter32,
            cm1110PortInMulticasts			Counter32,
            cm1110PortInPauses					Counter32,
            cm1110PortInUnderSizes			Counter32,
            cm1110PortInFragments			Counter32,
            cm1110PortInOversizes			Counter32,
            cm1110PortInJabbers				Counter32,
            cm1110PortInRxErrs				Counter32,
            cm1110PortInFcsErrs				Counter32,

            cm1110PortPkts64Octets			Counter32,
            cm1110PortPkts65to127Octets	Counter32,
            cm1110PortPkts128to255Octets	Counter32,
            cm1110PortPkts256to511Octets	Counter32,
            cm1110PortPkts512to1023Octets	Counter32,
            cm1110PortPkts1024toMaxOctets	Counter32,

            cm1110PortOutOctets				Counter32,
            cm1110PortHCOutOctets			Counter64,
            cm1110PortOutFiltered			INTEGER,
            cm1110PortOutUnicasts			Counter32,
            cm1110PortOutBroadcasts			Counter32,
            cm1110PortOutMulticasts			Counter32,
            cm1110PortOutPauses				Counter32,
            cm1110PortDeferreds				Counter32,
            cm1110PortCollisions				Counter32,
            cm1110PortSingles					Counter32,
            cm1110PortMultiples				Counter32,
            cm1110PortExcessives				Counter32,
            cm1110PortLates					Counter32,
            cm1110PortOutFcsErrs				Counter32,

            cm1110PortResetCounters			YesNoValue
        }

    cm1110StatsSlotIndex	OBJECT-TYPE
        SYNTAX		SlotNumber
        MAX-ACCESS	not-accessible
        STATUS		current
        DESCRIPTION
            "The Slot number the CM-1110 type module is currently inserted"
    ::= { cm1110RateConvStatsEntry 2 }

    cm1110MediaPortIndex OBJECT-TYPE
        SYNTAX INTEGER {
            copper(1),
            fiber(2)
        }
        MAX-ACCESS not-accessible
        STATUS current
        DESCRIPTION
            "Media converter module port index indicating which media port the statistical
             counters are associated with."
    ::= { cm1110RateConvStatsEntry 3 }

    cm1110PortInDiscards OBJECT-TYPE
        SYNTAX      Counter32
        MAX-ACCESS  read-only
        STATUS      current
        DESCRIPTION
            "A counter that counts the number of good, non-filtered frames that
             normally would have been forwarded, but could not due to lack of
             buffer space."
        ::= { cm1110RateConvStatsEntry 4 }

    cm1110PortInFiltered OBJECT-TYPE
        SYNTAX      INTEGER(0..65535)
        MAX-ACCESS  read-only
        STATUS      current
        DESCRIPTION
            "A counter that counts the number of good frames that were filtered
             due to ingress switch policy rules. "
        ::= { cm1110RateConvStatsEntry 5 }

    cm1110PortInGoodOctets OBJECT-TYPE
        SYNTAX      Counter32
        MAX-ACCESS  read-only
        STATUS      current
        DESCRIPTION
            "An ingress counter that is the sum of lengths of all good Ethernet
             frames received on the media port."
        ::= { cm1110RateConvStatsEntry 6 }

    cm1110PortHCInGoodOctets OBJECT-TYPE
        SYNTAX      Counter64
        MAX-ACCESS  read-only
        STATUS      current
        DESCRIPTION
            "An ingress counter that is the sum of lengths of all good Ethernet
             frames received on the media port. This object is a 64-bit version of
             cm1110PortInGoodOctets."
        ::= { cm1110RateConvStatsEntry 7 }

    cm1110PortInBadOctets OBJECT-TYPE
        SYNTAX      Counter32
        MAX-ACCESS  read-only
        STATUS      current
        DESCRIPTION
            "An ingress counter that is the sum of lengths of all bad Ethernet
             frames received on the media port.."
        ::= { cm1110RateConvStatsEntry 8 }

    cm1110PortInUnicasts OBJECT-TYPE
        SYNTAX      Counter32
        MAX-ACCESS  read-only
        STATUS      current
        DESCRIPTION
            "An ingress counter that counts the number of good frames received that
             have a Unicast destination MAC address."
        ::= { cm1110RateConvStatsEntry 9 }

    cm1110PortInBroadcasts OBJECT-TYPE
        SYNTAX      Counter32
        MAX-ACCESS  read-only
        STATUS      current
        DESCRIPTION
            "An ingress counter that counts the number of good frames received that
             have a Broadcast destination MAC address."
        ::= { cm1110RateConvStatsEntry 10 }

    cm1110PortInMulticasts OBJECT-TYPE
        SYNTAX      Counter32
        MAX-ACCESS  read-only
        STATUS      current
        DESCRIPTION
            "An ingress counter that counts the number of good frames received that
             have a Multicast destination MAC address. This count does not include
             frames counted in the cm1110PortInPauses or the cm1110PortInBroadcasts
             objects."
        ::= { cm1110RateConvStatsEntry 11 }

    cm1110PortInPauses OBJECT-TYPE
        SYNTAX      Counter32
        MAX-ACCESS  read-only
        STATUS      current
        DESCRIPTION
            "An ingress counter that counts the number of good frames reachieved that
             have a Pause destination MAC address."
        ::= { cm1110RateConvStatsEntry 12 }

    cm1110PortInUnderSizes OBJECT-TYPE
        SYNTAX      Counter32
        MAX-ACCESS  read-only
        STATUS      current
        DESCRIPTION
            "An ingress counter that counts the number of frames received with a
             length less that 64 octets but with a valid FCS."
        ::= { cm1110RateConvStatsEntry 13 }

    cm1110PortInFragments OBJECT-TYPE
        SYNTAX      Counter32
        MAX-ACCESS  read-only
        STATUS      current
        DESCRIPTION
            "An ingress counter that counts the number of frames received with a
             length less that 64 octets and an invalid FCS."
        ::= { cm1110RateConvStatsEntry 14 }

    cm1110PortInOversizes OBJECT-TYPE
        SYNTAX      Counter32
        MAX-ACCESS  read-only
        STATUS      current
        DESCRIPTION
            "An ingress counter that counts the number of frames received with a
             length more than the maximum packet size but with a valid FCS.
             The maximum packet size can be set using the cm1110ConfigMaxPacketsSize
             object."
        ::= { cm1110RateConvStatsEntry 15 }

    cm1110PortInJabbers OBJECT-TYPE
        SYNTAX      Counter32
        MAX-ACCESS  read-only
        STATUS      current
        DESCRIPTION
            "An ingress counter that counts the number of frames received with a
             length more than the maximum packet size but with a invalid FCS.
             The maximum packet size can be set using the cm1110ConfigMaxPacketsSize
             object."
        ::= { cm1110RateConvStatsEntry 16 }

    cm1110PortInRxErrs OBJECT-TYPE
        SYNTAX      Counter32
        MAX-ACCESS  read-only
        STATUS      current
        DESCRIPTION
            "An ingress counter that counts the number of frames received with an
             RxErr signal from the PHY."
        ::= { cm1110RateConvStatsEntry 17 }

    cm1110PortInFcsErrs OBJECT-TYPE
        SYNTAX      Counter32
        MAX-ACCESS  read-only
        STATUS      current
        DESCRIPTION
            "An ingress counter that counts the number of frames received with a
             CRC error not counted in the cm1110PortInFragments,
             cm1110PortInFcsErr, or the cm1110PortInRxErr objects."
        ::= { cm1110RateConvStatsEntry 18 }

    cm1110PortPkts64Octets OBJECT-TYPE
        SYNTAX      Counter32
        MAX-ACCESS  read-only
        STATUS      current
        DESCRIPTION
            "A Histogram counter that counts the number of frames received and
             transmitted with a length of exactly 64 Octets, including those with
             errors."
        ::= { cm1110RateConvStatsEntry 19 }

    cm1110PortPkts65to127Octets OBJECT-TYPE
        SYNTAX      Counter32
        MAX-ACCESS  read-only
        STATUS      current
        DESCRIPTION
            "A Histogram counter that counts the number of frames received and
             transmitted with a length of between 65 and 127 Octets inclusive,
             including those with errors."
        ::= { cm1110RateConvStatsEntry 20 }

    cm1110PortPkts128to255Octets OBJECT-TYPE
        SYNTAX      Counter32
        MAX-ACCESS  read-only
        STATUS      current
        DESCRIPTION
            "A Histogram counter that counts the number of frames received and
             transmitted with a length of between 128 and 255 Octets inclusive,
             including those with errors."
        ::= { cm1110RateConvStatsEntry 21 }

    cm1110PortPkts256to511Octets OBJECT-TYPE
        SYNTAX      Counter32
        MAX-ACCESS  read-only
        STATUS      current
        DESCRIPTION
            "A Histogram counter that counts the number of frames received and
             transmitted with a length of between 256 and 511 Octets inclusive,
             including those with errors."
        ::= { cm1110RateConvStatsEntry 22 }

    cm1110PortPkts512to1023Octets OBJECT-TYPE
        SYNTAX      Counter32
        MAX-ACCESS  read-only
        STATUS      current
        DESCRIPTION
            "A Histogram counter that counts the number of frames received and
             transmitted with a length of between 512 and 1023 Octets inclusive,
             including those with errors."
        ::= { cm1110RateConvStatsEntry 23 }

    cm1110PortPkts1024toMaxOctets OBJECT-TYPE
        SYNTAX      Counter32
        MAX-ACCESS  read-only
        STATUS      current
        DESCRIPTION
            "A Histogram counter that counts the number of frames received and
             transmitted with a length of between 1024 and maximum packet size
             octets inclusive, including those with errors.
             The maximum packet size can be set using the cm1110ConfigMaxPacketsSize
             object."
        ::= { cm1110RateConvStatsEntry 24 }

     cm1110PortOutOctets OBJECT-TYPE
        SYNTAX      Counter32
        MAX-ACCESS  read-only
        STATUS      current
        DESCRIPTION
            "An Egress counter that is the sum of lengths of all good Ethernet
             frames sent on the media port."
        ::= { cm1110RateConvStatsEntry 25 }

    cm1110PortHCOutOctets OBJECT-TYPE
        SYNTAX      Counter64
        MAX-ACCESS  read-only
        STATUS      current
        DESCRIPTION
            "An Egress counter that is the sum of lengths of all good Ethernet
             frames sent on the media port. This object is a 64-bit version of
             cm1110PortOutOctets."
        ::= { cm1110RateConvStatsEntry 26 }

    cm1110PortOutFiltered OBJECT-TYPE
        SYNTAX      INTEGER(0..65535)
        MAX-ACCESS  read-only
        STATUS      current
        DESCRIPTION
            "A counter that counts the number of good frames that were filtered
             due to egress switch policy rules."
        ::= { cm1110RateConvStatsEntry 27 }

    cm1110PortOutUnicasts OBJECT-TYPE
        SYNTAX      Counter32
        MAX-ACCESS  read-only
        STATUS      current
        DESCRIPTION
            "An Egress counter that counts the number of good frames sent that
             have a Unicast destination MAC address."
        ::= { cm1110RateConvStatsEntry 28 }

    cm1110PortOutBroadcasts OBJECT-TYPE
        SYNTAX      Counter32
        MAX-ACCESS  read-only
        STATUS      current
        DESCRIPTION
            "An Egress counter that counts the number of good frames sent that
             have a Broadcast destination MAC address."
        ::= { cm1110RateConvStatsEntry 29 }

    cm1110PortOutMulticasts OBJECT-TYPE
        SYNTAX		Counter32
        MAX-ACCESS	read-only
        STATUS		current
        DESCRIPTION
            "An Egress counter that counts the number of good frames sent that
             have a Multicast destination MAC address. This count does not include
             frames counted in the cm1110PortOutPauses or the cm1110PortOutBroadcasts
             objects."
        ::= { cm1110RateConvStatsEntry 30 }

    cm1110PortOutPauses OBJECT-TYPE
        SYNTAX      Counter32
        MAX-ACCESS  read-only
        STATUS      current
        DESCRIPTION
            "An Egress counter that counts the number of good frames reachieved that
             have a Pause destination MAC address."
        ::= { cm1110RateConvStatsEntry 31 }

    cm1110PortDeferreds OBJECT-TYPE
        SYNTAX      Counter32
        MAX-ACCESS  read-only
        STATUS      current
        DESCRIPTION
            "An Egress counter that counts the number of successfully transmitted
             frames that experienced no collisions but are delayed because the
             medium was busy during the first attempt. This counter is applicable
             in half-duplex only."
        ::= { cm1110RateConvStatsEntry 32 }

    cm1110PortCollisions OBJECT-TYPE
        SYNTAX      Counter32
        MAX-ACCESS  read-only
        STATUS      current
        DESCRIPTION
            "An Egress counter that counts the number of collision events seen by
             the MAC not including those counted in cm1110PortSingles,
             cm1110PortMultiple , cm1110PortExcessives or cm1110PortLates objects.
             This counter is applicable in half-duplex only."
        ::= { cm1110RateConvStatsEntry 33 }

    cm1110PortSingles OBJECT-TYPE
        SYNTAX      Counter32
        MAX-ACCESS  read-only
        STATUS      current
        DESCRIPTION
            "An Egress counter that counts the number of successfully transmitted
             frames that experienced exactly one collision. This counter is
             applicable in half-duplex only."
        ::= { cm1110RateConvStatsEntry 34 }

    cm1110PortMultiples OBJECT-TYPE
        SYNTAX      Counter32
        MAX-ACCESS  read-only
        STATUS      current
        DESCRIPTION
            "An Egress counter that counts the number of successfully transmitted
             frames that experienced more than one collision. This counter is
             aplicable in half-duplex only."
        ::= { cm1110RateConvStatsEntry 35 }

    cm1110PortExcessives OBJECT-TYPE
        SYNTAX      Counter32
        MAX-ACCESS  read-only
        STATUS      current
        DESCRIPTION
            "An Egress counter that counts the number frames dropped in the transmit
             MAC because the frame experienced 16 consecutive collisions.  This
             counter is applicable in half-duplex only. "
        ::= { cm1110RateConvStatsEntry 36 }

    cm1110PortLates OBJECT-TYPE
        SYNTAX      Counter32
        MAX-ACCESS  read-only
        STATUS      current
        DESCRIPTION
            "An Egress counter that counts the number times a collision is detected
             later than 512 bits-times into the transmission of a frame. This
             counter is applicable in half-duplex only."
        ::= { cm1110RateConvStatsEntry 37 }

    cm1110PortOutFcsErrs OBJECT-TYPE
        SYNTAX      Counter32
        MAX-ACCESS  read-only
        STATUS      current
        DESCRIPTION
            "An Egress counter that counts the number frames transmitted with an
             invalid FCS. "
        ::= { cm1110RateConvStatsEntry 38 }

    cm1110PortResetCounters OBJECT-TYPE
        SYNTAX      YesNoValue
        MAX-ACCESS  read-write
        STATUS      current
        DESCRIPTION
            "Allows the resetting of all cm1110RateConvStats statistical counters
             for this port. "
        ::= { cm1110RateConvStatsEntry 39 }
--
-- end of cm1110RateConvStatsTable
--

--
-- cm1110RateConvAvctTable
--
cm1110RateConvAvctTable	OBJECT-TYPE
    SYNTAX		SEQUENCE OF Cm1110RateConvAvctEntry
    MAX-ACCESS	not-accessible
    STATUS		current
    DESCRIPTION
        "Table of CM-1110 type media converter module's "
    ::= { cm1110RateConv 5 }

    cm1110RateConvAvctEntry OBJECT-TYPE
        SYNTAX      Cm1110RateConvAvctEntry
        MAX-ACCESS  not-accessible
        STATUS      current
        DESCRIPTION
            "Entries of the table, each relating to a separate fiber or copper
             port on the CM-1110 type media converter module."
        INDEX   { mcrChassisIndex, cm1110AvctSlotIndex }
        ::= { cm1110RateConvAvctTable 1 }

    Cm1110RateConvAvctEntry ::=
        SEQUENCE {
            cm1110AvctSlotIndex					SlotNumber,
            cm1110AvctStart						YesNoValue,
            cm1110AvctStatus						INTEGER,
            cm1110AvctTxRxPair1Results			INTEGER,
            cm1110AvctTxRxPair1Amplitude		DisplayString,
            cm1110AvctTxRxPair1Distance		DisplayString,
            cm1110AvctTxRxPair2Results			INTEGER,
            cm1110AvctTxRxPair2Amplitude		DisplayString,
            cm1110AvctTxRxPair2Distance		DisplayString,
            cm1110AvctTxRxPair3Results			INTEGER,
            cm1110AvctTxRxPair3Amplitude		DisplayString,
            cm1110AvctTxRxPair3Distance		DisplayString,
            cm1110AvctTxRxPair4Results			INTEGER,
            cm1110AvctTxRxPair4Amplitude		DisplayString,
            cm1110AvctTxRxPair4Distance		DisplayString
        }

    cm1110AvctSlotIndex	OBJECT-TYPE
        SYNTAX		SlotNumber
        MAX-ACCESS	not-accessible
        STATUS		current
        DESCRIPTION
            "The Slot number the CM-1110 type module is currently inserted"
    ::= { cm1110RateConvAvctEntry 2 }

    cm1110AvctStart OBJECT-TYPE
        SYNTAX YesNoValue
        MAX-ACCESS read-write
        STATUS current
        DESCRIPTION
            "Set this self-clearing variable to yes initiate the Advanced Virtual
             Cable Test. Note: During the test, no network data will be passed. "
        ::= { cm1110RateConvAvctEntry 3 }

    cm1110AvctStatus OBJECT-TYPE
        SYNTAX INTEGER {
            notStarted(0),
            inProgress(1),
            testComplete(2)
        }
        MAX-ACCESS read-only
        STATUS current
        DESCRIPTION
            "This object identifies the state of the Advanced Virtual Cable Tester. "
        ::= { cm1110RateConvAvctEntry 4 }

    cm1110AvctTxRxPair1Results OBJECT-TYPE
        SYNTAX INTEGER {
            normal(0),
            shortDetected(1),
            openDetected(2),
            testFailed(3)
        }
        MAX-ACCESS read-only
        STATUS current
        DESCRIPTION
            "Test result code returned from Virtual Cable Test of the Tx/Rx
             pair one."
        ::= { cm1110RateConvAvctEntry 5 }

    cm1110AvctTxRxPair1Amplitude OBJECT-TYPE
        SYNTAX DisplayString(SIZE(0..20))
        MAX-ACCESS read-only
        STATUS current
        DESCRIPTION
            "Amplitude of Tx/Rx pair one in millivolts when test result codes is
             short or open."
        ::= { cm1110RateConvAvctEntry 6 }

    cm1110AvctTxRxPair1Distance OBJECT-TYPE
        SYNTAX		DisplayString(SIZE(0..20))
        MAX-ACCESS read-only
        STATUS current
        DESCRIPTION
            "Distance in meters to fault when test result codes for Tx/Rx pair
             one is short or open. "
        ::= { cm1110RateConvAvctEntry 7 }

    cm1110AvctTxRxPair2Results OBJECT-TYPE
        SYNTAX INTEGER {
            normal(0),
            shortDetected(1),
            openDetected(2),
            testFailed(3)
        }
        MAX-ACCESS read-only
        STATUS current
        DESCRIPTION
            "Test result code returned from Virtual Cable Test of the Tx/Rx
             pair two."
        ::= { cm1110RateConvAvctEntry 8 }

    cm1110AvctTxRxPair2Amplitude OBJECT-TYPE
        SYNTAX DisplayString(SIZE(0..20))
        MAX-ACCESS read-only
        STATUS current
        DESCRIPTION
            "Amplitude of Tx/Rx pair two in millivolts when test result codes is
             short or open."
        ::= { cm1110RateConvAvctEntry 9 }

    cm1110AvctTxRxPair2Distance OBJECT-TYPE
        SYNTAX		DisplayString(SIZE(0..20))
        MAX-ACCESS read-only
        STATUS current
        DESCRIPTION
            "Distance in meters to fault when test result codes for Tx/Rx pair
             two is short or open. "
        ::= { cm1110RateConvAvctEntry 10 }

    cm1110AvctTxRxPair3Results OBJECT-TYPE
        SYNTAX INTEGER {
            normal(0),
            shortDetected(1),
            openDetected(2),
            testFailed(3)
        }
        MAX-ACCESS read-only
        STATUS current
        DESCRIPTION
            "Test result code returned from Virtual Cable Test of the Tx/Rx
             pair three."
        ::= { cm1110RateConvAvctEntry 11 }

    cm1110AvctTxRxPair3Amplitude OBJECT-TYPE
        SYNTAX DisplayString(SIZE(0..20))
        MAX-ACCESS read-only
        STATUS current
        DESCRIPTION
            "Amplitude of Tx/Rx pair three in millivolts when test result codes is
             short or open."
        ::= { cm1110RateConvAvctEntry 12 }

    cm1110AvctTxRxPair3Distance OBJECT-TYPE
        SYNTAX		DisplayString(SIZE(0..20))
        MAX-ACCESS read-only
        STATUS current
        DESCRIPTION
            "Distance in meters to fault when test result codes for Tx/Rx pair
             three is short or open. "
        ::= { cm1110RateConvAvctEntry 13 }

    cm1110AvctTxRxPair4Results OBJECT-TYPE
        SYNTAX INTEGER {
            normal(0),
            shortDetected(1),
            openDetected(2),
            testFailed(3)
        }
        MAX-ACCESS read-only
        STATUS current
        DESCRIPTION
            "Test result code returned from Virtual Cable Test of Tx/Rx
             pair four."
        ::= { cm1110RateConvAvctEntry 14 }

    cm1110AvctTxRxPair4Amplitude OBJECT-TYPE
        SYNTAX DisplayString(SIZE(0..20))
        MAX-ACCESS read-only
        STATUS current
        DESCRIPTION
            "Amplitude of Tx/Rx pair four in millivolts when test result codes is
             short or open."
        ::= { cm1110RateConvAvctEntry 15 }

    cm1110AvctTxRxPair4Distance OBJECT-TYPE
        SYNTAX		DisplayString(SIZE(0..20))
        MAX-ACCESS read-only
        STATUS current
        DESCRIPTION
            "Distance in meters to fault when test result codes for Tx/Rx pair
             four is short or open. "
        ::= { cm1110RateConvAvctEntry 16 }

--
-- cm1110RateConvAvctTable
--
--
-- end of cm1110RateConv
--


--
-- cm110RateConv  	  - 10/100 rate converter media converter modules
--
cm110RateConv	OBJECT IDENTIFIER ::= { mcrModuleTypes 4 }

--
-- cm110RateConvTable
--
cm110RateConvTable	OBJECT-TYPE
    SYNTAX		SEQUENCE OF Cm110RateConvEntry
    MAX-ACCESS	not-accessible
    STATUS		current
    DESCRIPTION
        "Table of CM-110 type media converter module's configuration and status type
         information."
    ::= { cm110RateConv 1 }

    cm110RateConvEntry OBJECT-TYPE
        SYNTAX      Cm110RateConvEntry
        MAX-ACCESS  not-accessible
        STATUS      current
        DESCRIPTION
            "Entries of the table, each relating to a separate CM-110 type
             media converter module."
        INDEX   { mcrChassisIndex, cm110SlotIndex }
        ::= { cm110RateConvTable 1 }

    Cm110RateConvEntry ::=
        SEQUENCE {
            cm110SlotIndex							SlotNumber,
            cm110Modelname							DisplayString,
            cm110ModelDesc							DisplayString,
            cm110HwJmp5ConfigMode				INTEGER,
            cm110HwJmp6AutoMDIX					INTEGER,
            cm110HwSw1TpAutoNegotiation		INTEGER,
            cm110HwSw2LinkMode					INTEGER,
            cm110HwSw3FarEndFault				INTEGER,
            cm110HwSw4TpDuplex					INTEGER,
            cm110HwSw5TpSpeed						INTEGER,
            cm110HwSw6FiberDuplex				INTEGER,
            cm110HwSw7Loopback					INTEGER,
            cm110FiberLinkStatus					INTEGER,
            cm110FiberConnType					INTEGER,
            cm110FiberSpeed						INTEGER,
            cm110FiberFarEndFault				INTEGER,
            cm110FiberReceiveStatus				INTEGER,
            cm110FiberLoopBack					EnableDisableValue,
            cm110CopperLinkStatus				INTEGER,
            cm110CopperConnType					INTEGER,
            cm110CopperAutoNegState				INTEGER,
            cm110CopperSpeed						INTEGER,
            cm110CopperDuplex						INTEGER,
            cm110CopperCrossOver					INTEGER,
            cm110CopperPause						INTEGER,
            cm110CopperLPRFStatus				INTEGER
        }

    cm110SlotIndex	OBJECT-TYPE
        SYNTAX		SlotNumber
        MAX-ACCESS	not-accessible
        STATUS		current
        DESCRIPTION
            "The Slot number the CM-110 type module is currently inserted"
    ::= { cm110RateConvEntry 2 }

    cm110Modelname	OBJECT-TYPE
        SYNTAX		DisplayString
        MAX-ACCESS	read-only
        STATUS		current
        DESCRIPTION
            "This object identifies the model of media converter module present in the
             chassis"
    ::= { cm110RateConvEntry 3 }

    cm110ModelDesc		OBJECT-TYPE
        SYNTAX		DisplayString
        MAX-ACCESS	read-only
        STATUS		current
        DESCRIPTION
            "This object identifies a static description of the media converter module present
             in the chassis"
    ::= { cm110RateConvEntry 4 }

    cm110HwJmp5ConfigMode	OBJECT-TYPE
        SYNTAX		INTEGER {
            hardwareSwitches(0),
            auto(1)
        }
        MAX-ACCESS	read-only
        STATUS		current
        DESCRIPTION
            "This object identifies the media converter module's ConfigMode, set by hardware
             switch on the media converter module. When this object is set to hardwareSwitches(0), the
             media converter module will disable configuration control from the management
             module's software and all configuration control comes from the media
             module's hardware switches or jumpers. "
    ::= { cm110RateConvEntry 5 }

    cm110HwJmp6AutoMDIX OBJECT-TYPE
        SYNTAX 		INTEGER {
            mdix(0),
            auto(1)
        }
        MAX-ACCESS read-only
        STATUS 		current
        DESCRIPTION
            "This object identifies the media converter module's hardware Auto MDIX jumper
             settings. "
    ::= { cm110RateConvEntry 6 }

    cm110HwSw1TpAutoNegotiation OBJECT-TYPE
        SYNTAX 		INTEGER {
            swDownDisabled(0),
            swUpEnabled(1)
        }
        MAX-ACCESS read-only
        STATUS 		current
        DESCRIPTION
            "Media converter module's current switch setting for copper auto-negotiation."
    ::= { cm110RateConvEntry 7 }

    cm110HwSw2LinkMode OBJECT-TYPE
        SYNTAX 		INTEGER {
            swDownNormalMode(0),
            swUpSmartLinkPassthroughMode(1)
        }
        MAX-ACCESS read-only
        STATUS 		current
        DESCRIPTION
            "Media converter module's current switch setting for Link Mode."
    ::= { cm110RateConvEntry 8 }

    cm110HwSw3FarEndFault OBJECT-TYPE
        SYNTAX 		INTEGER {
            swDownDisabled(0),
            swUpEnabled(1)
        }
        MAX-ACCESS read-only
        STATUS 		current
        DESCRIPTION
            "Media converter module's current switch setting for Far End Fault."
    ::= { cm110RateConvEntry 9 }

    cm110HwSw4TpDuplex OBJECT-TYPE
        SYNTAX 		INTEGER {
            swDownHalf(0),
            swUpFull(1)
        }
        MAX-ACCESS read-only
        STATUS 		current
        DESCRIPTION
            "Media converter module's current switch setting for copper duplex."
    ::= { cm110RateConvEntry 10 }

    cm110HwSw5TpSpeed OBJECT-TYPE
        SYNTAX 		INTEGER {
            swDown10Mbps(0),
            swUp100Mbps(1)
        }
        MAX-ACCESS read-only
        STATUS 		current
        DESCRIPTION
            "Media converter module's current switch setting for Link Mode."
    ::= { cm110RateConvEntry 11 }

    cm110HwSw6FiberDuplex OBJECT-TYPE
        SYNTAX 		INTEGER {
            swDownHalf(0),
            swUpFull(1)
        }
        MAX-ACCESS read-only
        STATUS 		current
        DESCRIPTION
            "Media converter module's current switch setting for fiber duplex."
    ::= { cm110RateConvEntry 12 }

    cm110HwSw7Loopback OBJECT-TYPE
        SYNTAX 		INTEGER {
            swDownEnabled(0),
            swUpDisabled(1)
        }
        MAX-ACCESS read-only
        STATUS 		current
        DESCRIPTION
            "Media converter module's current switch setting for fiber loopback mode."
    ::= { cm110RateConvEntry 13 }

    cm110FiberLinkStatus OBJECT-TYPE
        SYNTAX 		INTEGER {
            down(0),
            up(1)
        }
        MAX-ACCESS	read-only
        STATUS 		current
        DESCRIPTION
            "Media converter module's current fiber link status."
    ::= { cm110RateConvEntry 14 }

    cm110FiberConnType OBJECT-TYPE
        SYNTAX 		INTEGER {
            sc(0),
            lc(1),
            st(2),
            sfp(3),
            fc(5),
            mtrj(6)
        }
        MAX-ACCESS read-only
        STATUS 		current
        DESCRIPTION
            "Media converter module's fiber port connector type."
    ::= { cm110RateConvEntry 15 }

    cm110FiberSpeed OBJECT-TYPE
        SYNTAX 		INTEGER {
            speed100Mbps(1)
        }
        MAX-ACCESS	read-only
        STATUS 		current
        DESCRIPTION
            "Media converter module's fiber port speed in megabits per second."
    ::= { cm110RateConvEntry 16 }


    cm110FiberFarEndFault	OBJECT-TYPE
        SYNTAX		INTEGER {
            disable(0),
            ok(1),
            receivingFEF(2),
            sendingFEF(3)
        }
        MAX-ACCESS	read-only
        STATUS		current
        DESCRIPTION
            "Media converter module's current fiber Far End Fault status."
    ::= { cm110RateConvEntry 17 }

    cm110FiberReceiveStatus		OBJECT-TYPE
        SYNTAX	INTEGER {
            fault(0),
            ok(1)
        }
        MAX-ACCESS	read-write
        STATUS	current
        DESCRIPTION
            "This object identifies the status of whether light is being received
             on the fiber port"
    ::= { cm110RateConvEntry 18 }

    cm110FiberLoopBack		OBJECT-TYPE
        SYNTAX	EnableDisableValue
        MAX-ACCESS	read-write
        STATUS	current
        DESCRIPTION
            "
             This object is read-only if the media converter module's ConfigMode jumper is
             set to hardwareSwitches(0)."
    ::= { cm110RateConvEntry 19 }

    cm110CopperLinkStatus OBJECT-TYPE
        SYNTAX	INTEGER {
            down(0),
            up(1)
        }
        MAX-ACCESS	read-only
        STATUS	current
        DESCRIPTION
            "Media converter module's current copper link status."
    ::= { cm110RateConvEntry 20 }

    cm110CopperConnType OBJECT-TYPE
        SYNTAX INTEGER {
            rj45(0)
        }
        MAX-ACCESS read-only
        STATUS current
        DESCRIPTION
            "Media converter module's copper connector type."
    ::= { cm110RateConvEntry 21 }

    cm110CopperAutoNegState OBJECT-TYPE
        SYNTAX INTEGER {
            disabled(0),
            complete(1),
            inProgress(2)
        }
        MAX-ACCESS read-only
        STATUS current
        DESCRIPTION
            "Media converter module's current copper auto-negotiation state."
    ::= { cm110RateConvEntry 22 }

    cm110CopperSpeed OBJECT-TYPE
        SYNTAX 		INTEGER {
            speed10Mbs(0),
            speed100Mbps(1)
        }
        MAX-ACCESS	read-only
        STATUS 		current
        DESCRIPTION
            "If copper auto-negotiation state is complete then this object
            indicates the media converter module's current copper auto-negotiated speed
            setting. If auto-negotiation is not complete then the value returned
            should be ignored."
    ::= { cm110RateConvEntry 23 }

    cm110CopperDuplex OBJECT-TYPE
        SYNTAX INTEGER {
            half(0),
            full(1)
        }
        MAX-ACCESS read-only
        STATUS current
        DESCRIPTION
            "If copper auto-negotiation state is complete then this object
            indicates the media converter module's current copper auto-negotiated duplex
            setting. If auto-negotiation is not complete then the value returned
            should be ignored."
    ::= { cm110RateConvEntry 24 }

    cm110CopperCrossOver OBJECT-TYPE
        SYNTAX INTEGER {
            mdi(0),
            mdix(1)
        }
        MAX-ACCESS read-only
        STATUS current
        DESCRIPTION
            "If copper auto-negotiation state is complete then this object
            indicates the media converter module's current copper auto-negotiated MDI/MDI-X
            setting. If auto-negotiation is not complete then the value returned
            should be ignored."
    ::= { cm110RateConvEntry 25 }

    cm110CopperPause OBJECT-TYPE
        SYNTAX INTEGER {
            disabled(0),
            symmetrical(1)
        }
        MAX-ACCESS read-only
        STATUS current
        DESCRIPTION
            "If copper auto-negotiation state is complete then this object indicates
             the media converter module's current copper auto-negotiated pause (flow control)
             setting. If auto-negotiation is not complete then the value returned
             should be ignored."
    ::= { cm110RateConvEntry 26 }

    cm110CopperLPRFStatus OBJECT-TYPE
        SYNTAX INTEGER {
            ok(0),
            remoteFault(1)
        }
        MAX-ACCESS read-only
        STATUS current
        DESCRIPTION
            "Media converter module's fiber Link Partner Remote Fault status."
    ::= { cm110RateConvEntry 27 }

--
-- end of cm110RateConvTable
--
--
-- cm110ConfigTable
--
cm110ConfigTable	OBJECT-TYPE
    SYNTAX		SEQUENCE OF Cm110ConfigEntry
    MAX-ACCESS	not-accessible
    STATUS		current
    DESCRIPTION
        "Table of CM-110 type media converter module's configuration and status type
         information."
    ::= { cm110RateConv 2 }

    cm110ConfigEntry OBJECT-TYPE
        SYNTAX      Cm110ConfigEntry
        MAX-ACCESS  not-accessible
        STATUS      current
        DESCRIPTION
            "Entries of the table, each relating to a separate CM-110 type
             media converter module."
        INDEX   { mcrChassisIndex, cm110ConfigSlotIndex }
        ::= { cm110ConfigTable 1 }

    Cm110ConfigEntry ::=
        SEQUENCE {
            cm110ConfigSlotIndex							SlotNumber,
            cm110ConfigStatus								ContainerStatus,
            cm110ConfigModuleName						DisplayString,
            cm110ConfigLinkMode							INTEGER,
            cm110ConfigFiberFarEndFault				INTEGER,
            cm110ConfigMaxPacketSize					INTEGER,
            cm110ConfigFiberPortName					DisplayString,
            cm110ConfigFiberPortEnable					YesNoValue,
            cm110ConfigFiberDuplex						INTEGER,
            cm110ConfigCopperPortName					DisplayString,
            cm110ConfigCopperPortEnable				YesNoValue,
            cm110ConfigCopperAutoNegotiation			INTEGER,
            cm110ConfigCopperAutoNegAdv10HDX			YesNoValue,
            cm110ConfigCopperAutoNegAdv10FDX			YesNoValue,
            cm110ConfigCopperAutoNegAdv100HDX		YesNoValue,
            cm110ConfigCopperAutoNegAdv100FDX		YesNoValue,
            cm110ConfigCopperSpeed						INTEGER,
            cm110ConfigCopperDuplex						INTEGER,
            cm110ConfigCopperCrossOver					INTEGER,
            cm110ConfigCopperPause						INTEGER,
            cm110ConfigCopperExtendDistance			EnableDisableValue,

            cm110ConfigUnidirectionalEthernet	INTEGER,
            cm110ConfigPriorityToEgressQueueMap0	INTEGER,
            cm110ConfigPriorityToEgressQueueMap1	INTEGER,
            cm110ConfigPriorityToEgressQueueMap2	INTEGER,
            cm110ConfigPriorityToEgressQueueMap3	INTEGER,
            cm110ConfigPriorityToEgressQueueMap4	INTEGER,
            cm110ConfigPriorityToEgressQueueMap5	INTEGER,
            cm110ConfigPriorityToEgressQueueMap6	INTEGER,
            cm110ConfigPriorityToEgressQueueMap7	INTEGER,

            cm110ConfigCopper8021pPriority			OnOffValue,
            cm110ConfigCopperIpTosPriority			OnOffValue,
            cm110ConfigCopperPriorityPrecedence	INTEGER,
            cm110ConfigCopperCongestionPolicy		INTEGER,

            cm110ConfigCopperPriorityMap0			INTEGER,
            cm110ConfigCopperPriorityMap1			INTEGER,
            cm110ConfigCopperPriorityMap2			INTEGER,
            cm110ConfigCopperPriorityMap3			INTEGER,
            cm110ConfigCopperPriorityMap4			INTEGER,
            cm110ConfigCopperPriorityMap5			INTEGER,
            cm110ConfigCopperPriorityMap6			INTEGER,
            cm110ConfigCopperPriorityMap7			INTEGER,

            cm110ConfigCopperIngressLimit			INTEGER,
            cm110ConfigCopperEgressLimit			INTEGER,
            cm110ConfigCopperDiscardTaggedFrames	OnOffValue,
            cm110ConfigCopperDiscardUntaggedFrames	OnOffValue,
            cm110ConfigCopperDefaultVlanId			INTEGER,
            cm110ConfigCopperDefaultPriority		INTEGER,
            cm110ConfigCopperVlanTaggingAction		INTEGER,
            cm110ConfigCopperFilterUnknownMulticast		OnOffValue,
            cm110ConfigCopperFilterUnknownUnicast		OnOffValue,

            cm110ConfigFiber8021pPriority			OnOffValue,
            cm110ConfigFiberIpTosPriority			OnOffValue,
            cm110ConfigFiberPriorityPrecedence	INTEGER,
            cm110ConfigFiberCongestionPolicy		INTEGER,

            cm110ConfigFiberPriorityMap0			INTEGER,
            cm110ConfigFiberPriorityMap1			INTEGER,
            cm110ConfigFiberPriorityMap2			INTEGER,
            cm110ConfigFiberPriorityMap3			INTEGER,
            cm110ConfigFiberPriorityMap4			INTEGER,
            cm110ConfigFiberPriorityMap5			INTEGER,
            cm110ConfigFiberPriorityMap6			INTEGER,
            cm110ConfigFiberPriorityMap7			INTEGER,

            cm110ConfigFiberIngressLimit			INTEGER,
            cm110ConfigFiberEgressLimit			INTEGER,
            cm110ConfigFiberDiscardTaggedFrames	OnOffValue,
            cm110ConfigFiberDiscardUntaggedFrames	OnOffValue,
            cm110ConfigFiberDefaultVlanId			INTEGER,
            cm110ConfigFiberDefaultPriority		INTEGER,
            cm110ConfigFiberVlanTaggingAction		INTEGER,
            cm110ConfigFiberFilterUnknownMulticast		OnOffValue,
            cm110ConfigFiberFilterUnknownUnicast		OnOffValue

        }
    cm110ConfigSlotIndex	OBJECT-TYPE
        SYNTAX		SlotNumber
        MAX-ACCESS	not-accessible
        STATUS		current
        DESCRIPTION
            "The Slot number the CM-110 type module is currently inserted"
    ::= { cm110ConfigEntry 2 }

    cm110ConfigStatus OBJECT-TYPE
        SYNTAX      ContainerStatus
        MAX-ACCESS  read-write
        STATUS      current
        DESCRIPTION
          "When you perform a GET on this variable, one of
            the following values will be returned:
            1-Indicates that the container folder is active with no changes.
            2-Indicates that the container folder is active with change(s).
            Once you have completed setting the variables in a folder, you
            will want to submit your changes to the management module. To do
            this, set the Status variable to 4. If you want to discard the
            changes, set the Status variable to 6.
            4-Indicates that the changes in the container folder are to be
              submitted to the management module, verified and and saved to flash.
            6-Indicates that the changes in the container folder are to be
              discarded."
        ::= { cm110ConfigEntry 3 }

    cm110ConfigModuleName OBJECT-TYPE
        SYNTAX		DisplayString(SIZE(0..63))
        MAX-ACCESS	read-write
        STATUS		current
        DESCRIPTION
            "This object identifies a user configurable name for the media converter module
             present in the chassis. "
    ::= { cm110ConfigEntry 4 }

    cm110ConfigLinkMode	OBJECT-TYPE
        SYNTAX		INTEGER {
            standard(0),
            linkPassthrough(1)
        }
        MAX-ACCESS	read-write
        STATUS		current
        DESCRIPTION
            "This object identifies the Link Mode for the media converter module. This object
            is read-only if the media converter module's ConfigMode jumper is set to
            hardwareSwitches(0)."
    ::= { cm110ConfigEntry 5 }

    cm110ConfigFiberFarEndFault	OBJECT-TYPE
        SYNTAX		INTEGER {
            disable(0),
            enable(1)
        }
        MAX-ACCESS	read-write
        STATUS		current
        DESCRIPTION
            "This object identifies the Fiber Fault Alert setting for the media
             module. This setting is always enabled if Link Mode is set to linkPassthrough.
             This object is read-only if the media converter module's ConfigMode
             jumper is set to hardwareSwitches(0). "
    ::= { cm110ConfigEntry 6 }

    cm110ConfigMaxPacketSize OBJECT-TYPE
        SYNTAX		INTEGER {
            maxpacket1522(0),
            maxpacket2048(1)
        }
        MAX-ACCESS	read-write
        STATUS		current
        DESCRIPTION
            "This object identifies the media converter module's maximum packet size setting
             This object is read-only if the media converter module's ConfigMode  jumper is
             set to hardwareSwitches(0)."
    ::= { cm110ConfigEntry 7 }

    cm110ConfigFiberPortName OBJECT-TYPE
        SYNTAX		DisplayString(SIZE(0..8))
        MAX-ACCESS	read-write
        STATUS 		current
        DESCRIPTION
            "This object identifies a user definable name for the fiber port."
    ::= { cm110ConfigEntry 8 }

    cm110ConfigFiberPortEnable OBJECT-TYPE
        SYNTAX		YesNoValue
        MAX-ACCESS	read-write
        STATUS 		current
        DESCRIPTION
            "This object identifies whether the fiber port is enabled. "
    ::= { cm110ConfigEntry 9 }

    cm110ConfigFiberDuplex OBJECT-TYPE
        SYNTAX		INTEGER {
            full(0),
            half(1)
        }
        MAX-ACCESS	read-only
        STATUS		current
        DESCRIPTION
            "This object identifies the fiber port duplex setting. "
    ::= { cm110ConfigEntry 10 }

    cm110ConfigCopperPortName OBJECT-TYPE
        SYNTAX DisplayString(SIZE(0..8))
        MAX-ACCESS read-write
        STATUS current
        DESCRIPTION
            "This object identifies a user definable name for the copper port. "
    ::= { cm110ConfigEntry 11 }

    cm110ConfigCopperPortEnable OBJECT-TYPE
        SYNTAX	YesNoValue
        MAX-ACCESS	read-write
        STATUS	current
        DESCRIPTION
            "This object identifies whether the fiber port is enabled. "
    ::= { cm110ConfigEntry 12 }

    cm110ConfigCopperAutoNegotiation OBJECT-TYPE
        SYNTAX 		INTEGER {
            disable(0),
            enable(1)
        }
        MAX-ACCESS	read-write
        STATUS 		current
        DESCRIPTION
            "This object identifies the whether copper auto-negotiation is
             enabled. This object is read-only if the media converter module's ConfigMode
             jumper is set to hardwareSwitches(0)."
    ::= { cm110ConfigEntry 13 }

    cm110ConfigCopperAutoNegAdv10HDX OBJECT-TYPE
        SYNTAX 		YesNoValue
        MAX-ACCESS	read-write
        STATUS 		current
        DESCRIPTION
        "This object controls whether or the copper port advertises willingness
         to connect at 10Mbps, half duplex.  This setting is ignored when
         auto-negotiation is disabled."
    ::= { cm110ConfigEntry 14 }

    cm110ConfigCopperAutoNegAdv10FDX OBJECT-TYPE
        SYNTAX 		YesNoValue
        MAX-ACCESS	read-write
        STATUS 		current
        DESCRIPTION
        "This object controls whether or the copper port advertises willingness
         to connect at 10Mbps, full duplex.  This setting is ignored when
         auto-negotiation is disabled."
    ::= { cm110ConfigEntry 15 }

    cm110ConfigCopperAutoNegAdv100HDX OBJECT-TYPE
        SYNTAX 		YesNoValue
        MAX-ACCESS	read-write
        STATUS 		current
        DESCRIPTION
        "This object controls whether or the copper port advertises willingness
         to connect at 100Mbps, half duplex.  This setting is ignored when
         auto-negotiation is disabled."
    ::= { cm110ConfigEntry 16 }

    cm110ConfigCopperAutoNegAdv100FDX OBJECT-TYPE
        SYNTAX 		YesNoValue
        MAX-ACCESS	read-write
        STATUS 		current
        DESCRIPTION
        "This object controls whether or the copper port advertises willingness
         to connect at 100Mbps, full duplex.  This setting is ignored when
         auto-negotiation is disabled."
    ::= { cm110ConfigEntry 17 }

    cm110ConfigCopperSpeed OBJECT-TYPE
        SYNTAX 		INTEGER {
            speed10Mbs(0),
            speed100Mbps(1)
        }
        MAX-ACCESS	read-write
        STATUS 		current
        DESCRIPTION
            "This object identifies the current copper speed in megabits per
             second. This object is ignored if auto-negotiation is enabled.
             This object is ignored if auto-negotiation is enabled "
    ::= { cm110ConfigEntry 18 }

    cm110ConfigCopperDuplex	OBJECT-TYPE
        SYNTAX INTEGER {
            full(0),
            half(1)
        }
        MAX-ACCESS read-write
        STATUS current
        DESCRIPTION
            "This object identifies the copper duplex setting. This object is
             ignored if auto-negotiation is enabled   This object is read-only
             if the media converter module's ConfigMode jumper is set to hardwareSwitches(0)."
    ::= { cm110ConfigEntry 19 }

    cm110ConfigCopperCrossOver	OBJECT-TYPE
        SYNTAX INTEGER {
            auto(0),
            mdi(1),
            mdix(2)
        }
        MAX-ACCESS read-write
        STATUS current
        DESCRIPTION
            "This object identifies the copper MDI/MDI-X setting.This object
            is read-only if the media converter module's ConfigMode jumper is set to"
    ::= { cm110ConfigEntry 20 }

    cm110ConfigCopperPause OBJECT-TYPE
        SYNTAX INTEGER {
            disabled(0),
            enable(1)
        }
        MAX-ACCESS read-write
        STATUS current
        DESCRIPTION
            "This object identifies the copper's pause (flow control) settings.
             This object is read-only if the media converter module's ConfigMode jumper
             is set to hardwareSwitches(0)."
    ::= { cm110ConfigEntry 21 }

    cm110ConfigCopperExtendDistance OBJECT-TYPE
        SYNTAX 		EnableDisableValue
        MAX-ACCESS read-write
        STATUS 		current
        DESCRIPTION
            "When using cable exceeding 100 meters, the 10BASE-T this feature
             should be enabled."
    ::= { cm110ConfigEntry 22 }

    cm110ConfigUnidirectionalEthernet OBJECT-TYPE
        SYNTAX INTEGER {
            notApplicable(-1),
            disabled(0),
            copperToFiber(1),
            fiberToCopper(2)
        }
        MAX-ACCESS read-write
        STATUS current
        DESCRIPTION
            "Restrict the flow of Ethernet traffic to a single direction.
             A value of -1 signifies that this feature is not supported
             by the current media converter module firmware.
             (This feature may require a media converter module firmware upgrade)."
    ::= { cm110ConfigEntry 23 }

    cm110ConfigPriorityToEgressQueueMap0 OBJECT-TYPE
        SYNTAX INTEGER(0..3)
        MAX-ACCESS read-write
        STATUS current
        DESCRIPTION
            "Set the egress queue of frames tagged with 802.1p priority 0.
             A value of -1 signifies that this feature is not supported
             by the current media converter module firmware.
             (This feature may require a media converter module firmware upgrade)."
    ::= { cm110ConfigEntry 24 }

    cm110ConfigPriorityToEgressQueueMap1 OBJECT-TYPE
        SYNTAX INTEGER(0..3)
        MAX-ACCESS read-write
        STATUS current
        DESCRIPTION
            "Set the egress queue of frames tagged with 802.1p priority 1.
             A value of -1 signifies that this feature is not supported
             by the current media converter module firmware.
             (This feature may require a media converter module firmware upgrade)."
    ::= { cm110ConfigEntry 25 }

    cm110ConfigPriorityToEgressQueueMap2 OBJECT-TYPE
        SYNTAX INTEGER(0..3)
        MAX-ACCESS read-write
        STATUS current
        DESCRIPTION
            "Set the egress queue of frames tagged with 802.1p priority 2.
             A value of -1 signifies that this feature is not supported
             by the current media converter module firmware.
             (This feature may require a media converter module firmware upgrade)."
    ::= { cm110ConfigEntry 26 }

    cm110ConfigPriorityToEgressQueueMap3 OBJECT-TYPE
        SYNTAX INTEGER(0..3)
        MAX-ACCESS read-write
        STATUS current
        DESCRIPTION
            "Set the egress queue of frames tagged with 802.1p priority 3.
             A value of -1 signifies that this feature is not supported
             by the current media converter module firmware.
             (This feature may require a media converter module firmware upgrade)."
    ::= { cm110ConfigEntry 27 }

    cm110ConfigPriorityToEgressQueueMap4 OBJECT-TYPE
        SYNTAX INTEGER(0..3)
        MAX-ACCESS read-write
        STATUS current
        DESCRIPTION
            "Set the egress queue of frames tagged with 802.1p priority 4.
             A value of -1 signifies that this feature is not supported
             by the current media converter module firmware.
             (This feature may require a media converter module firmware upgrade)."
    ::= { cm110ConfigEntry 28 }

    cm110ConfigPriorityToEgressQueueMap5 OBJECT-TYPE
        SYNTAX INTEGER(0..3)
        MAX-ACCESS read-write
        STATUS current
        DESCRIPTION
            "Set the egress queue of frames tagged with 802.1p priority 5.
             A value of -1 signifies that this feature is not supported
             by the current media converter module firmware.
             (This feature may require a media converter module firmware upgrade)."
    ::= { cm110ConfigEntry 29 }

    cm110ConfigPriorityToEgressQueueMap6 OBJECT-TYPE
        SYNTAX INTEGER(0..3)
        MAX-ACCESS read-write
        STATUS current
        DESCRIPTION
            "Set the egress queue of frames tagged with 802.1p priority 6.
             A value of -1 signifies that this feature is not supported
             by the current media converter module firmware.
             (This feature may require a media converter module firmware upgrade)."
    ::= { cm110ConfigEntry 30 }

    cm110ConfigPriorityToEgressQueueMap7 OBJECT-TYPE
        SYNTAX INTEGER(0..3)
        MAX-ACCESS read-write
        STATUS current
        DESCRIPTION
            "Set the egress queue of frames tagged with 802.1p priority 7.
             A value of -1 signifies that this feature is not supported
             by the current media converter module firmware.
             (This feature may require a media converter module firmware upgrade)."
    ::= { cm110ConfigEntry 31 }

    cm110ConfigCopper8021pPriority OBJECT-TYPE
        SYNTAX      OnOffValue
        MAX-ACCESS read-write
        STATUS current
        DESCRIPTION
            "Use 802.1p tag priority.
             (This feature may require a media converter module firmware upgrade)."
    ::= { cm110ConfigEntry 32 }

    cm110ConfigCopperIpTosPriority OBJECT-TYPE
        SYNTAX      OnOffValue
        MAX-ACCESS read-write
        STATUS current
        DESCRIPTION
            "Use IP TOS priority.
             (This feature may require a media converter module firmware upgrade)."
    ::= { cm110ConfigEntry 33 }

    cm110ConfigCopperPriorityPrecedence OBJECT-TYPE
        SYNTAX INTEGER {
            notApplicable(-1),
            priority8021p(0),
            priorityIpTos(1)
        }
        MAX-ACCESS read-write
        STATUS current
        DESCRIPTION
            "Configure priority precedence.
             (This feature may require a media converter module firmware upgrade)."
    ::= { cm110ConfigEntry 34 }

    cm110ConfigCopperCongestionPolicy OBJECT-TYPE
        SYNTAX INTEGER {
            notApplicable(-1),
            strict(0),
            weighted(1)
        }
        MAX-ACCESS read-write
        STATUS current
        DESCRIPTION
            "Configure priority congestion policy.
             (This feature may require a media converter module firmware upgrade)."
    ::= { cm110ConfigEntry 35 }

    cm110ConfigCopperPriorityMap0 OBJECT-TYPE
        SYNTAX INTEGER(0..7)
        MAX-ACCESS read-write
        STATUS current
        DESCRIPTION
            "Change the priority of frames tagged with 802.1p priority 0.
             A value of -1 signifies that this feature is not supported
             by the current media converter module firmware.
             (This feature may require a media converter module firmware upgrade)."
    ::= { cm110ConfigEntry 36 }

    cm110ConfigCopperPriorityMap1 OBJECT-TYPE
        SYNTAX INTEGER(0..7)
        MAX-ACCESS read-write
        STATUS current
        DESCRIPTION
            "Change the priority of frames tagged with 802.1p priority 1.
             A value of -1 signifies that this feature is not supported
             by the current media converter module firmware.
             (This feature may require a media converter module firmware upgrade)."
    ::= { cm110ConfigEntry 37 }

    cm110ConfigCopperPriorityMap2 OBJECT-TYPE
        SYNTAX INTEGER(0..7)
        MAX-ACCESS read-write
        STATUS current
        DESCRIPTION
            "Change the priority of frames tagged with 802.1p priority 2.
             A value of -1 signifies that this feature is not supported
             by the current media converter module firmware.
             (This feature may require a media converter module firmware upgrade)."
    ::= { cm110ConfigEntry 38 }

    cm110ConfigCopperPriorityMap3 OBJECT-TYPE
        SYNTAX INTEGER(0..7)
        MAX-ACCESS read-write
        STATUS current
        DESCRIPTION
            "Change the priority of frames tagged with 802.1p priority 3.
             A value of -1 signifies that this feature is not supported
             by the current media converter module firmware.
             (This feature may require a media converter module firmware upgrade)."
    ::= { cm110ConfigEntry 39 }

    cm110ConfigCopperPriorityMap4 OBJECT-TYPE
        SYNTAX INTEGER(0..7)
        MAX-ACCESS read-write
        STATUS current
        DESCRIPTION
            "Change the priority of frames tagged with 802.1p priority 4.
             A value of -1 signifies that this feature is not supported
             by the current media converter module firmware.
             (This feature may require a media converter module firmware upgrade)."
    ::= { cm110ConfigEntry 40 }

    cm110ConfigCopperPriorityMap5 OBJECT-TYPE
        SYNTAX INTEGER(0..7)
        MAX-ACCESS read-write
        STATUS current
        DESCRIPTION
            "Change the priority of frames tagged with 802.1p priority 5.
             A value of -1 signifies that this feature is not supported
             by the current media converter module firmware.
             (This feature may require a media converter module firmware upgrade)."
    ::= { cm110ConfigEntry 41 }

    cm110ConfigCopperPriorityMap6 OBJECT-TYPE
        SYNTAX INTEGER(0..7)
        MAX-ACCESS read-write
        STATUS current
        DESCRIPTION
            "Change the priority of frames tagged with 802.1p priority 6.
             A value of -1 signifies that this feature is not supported
             by the current media converter module firmware.
             (This feature may require a media converter module firmware upgrade)."
    ::= { cm110ConfigEntry 42 }

    cm110ConfigCopperPriorityMap7 OBJECT-TYPE
        SYNTAX INTEGER(0..7)
        MAX-ACCESS read-write
        STATUS current
        DESCRIPTION
            "Change the priority of frames tagged with 802.1p priority 7.
             A value of -1 signifies that this feature is not supported
             by the current media converter module firmware.
             (This feature may require a media converter module firmware upgrade)."
    ::= { cm110ConfigEntry 43 }

    cm110ConfigCopperIngressLimit OBJECT-TYPE
        SYNTAX INTEGER {
            notApplicable(-1),
            rateUnlimited(0),
            rate64kbps(1),
            rate128kbps(2),
            rate192kbps(3),
            rate256kbps(4),
            rate320kbps(5),
            rate384kbps(6),
            rate512kbps(7),
            rate768kbps(8),
            rate1mbps  (9),
            rate2mbps  (10),
            rate3mbps  (11),
            rate4mbps  (12),
            rate5mbps  (13),
            rate6mbps  (14),
            rate7mbps  (15),
            rate8mbps  (16),
            rate9mbps  (17),
            rate10mbps (18),
            rate20mbps (19),
            rate30mbps (20),
            rate40mbps (21),
            rate50mbps (22),
            rate60mbps (23),
            rate70mbps (24),
            rate80mbps (25),
            rate90mbps (26)
        }
        MAX-ACCESS read-write
        STATUS current
        DESCRIPTION
            "Set a limit on the rate of incoming packets.
             (This feature may require a media converter module firmware upgrade)."
    ::= { cm110ConfigEntry 44 }

    cm110ConfigCopperEgressLimit OBJECT-TYPE
        SYNTAX INTEGER {
            notApplicable(-1),
            rateUnlimited(0),
            rate64kbps(1),
            rate128kbps(2),
            rate192kbps(3),
            rate256kbps(4),
            rate320kbps(5),
            rate384kbps(6),
            rate512kbps(7),
            rate768kbps(8),
            rate1mbps  (9),
            rate2mbps  (10),
            rate3mbps  (11),
            rate4mbps  (12),
            rate5mbps  (13),
            rate6mbps  (14),
            rate7mbps  (15),
            rate8mbps  (16),
            rate9mbps  (17),
            rate10mbps (18),
            rate20mbps (19),
            rate30mbps (20),
            rate40mbps (21),
            rate50mbps (22),
            rate60mbps (23),
            rate70mbps (24),
            rate80mbps (25),
            rate90mbps (26)
        }
        MAX-ACCESS read-write
        STATUS current
        DESCRIPTION
            "Set a limit on the rate of outgoing packets.
             (This feature may require a media converter module firmware upgrade)."
    ::= { cm110ConfigEntry 45 }

    cm110ConfigCopperDiscardTaggedFrames OBJECT-TYPE
        SYNTAX      OnOffValue
        MAX-ACCESS read-write
        STATUS current
        DESCRIPTION
            "Enable discarding of tagged frames.
             (This feature may require a media converter module firmware upgrade)."
    ::= { cm110ConfigEntry 46 }

    cm110ConfigCopperDiscardUntaggedFrames OBJECT-TYPE
        SYNTAX      OnOffValue
        MAX-ACCESS read-write
        STATUS current
        DESCRIPTION
            "Enable discarding of untagged frames.
             (This feature may require a media converter module firmware upgrade)."
    ::= { cm110ConfigEntry 47 }

    cm110ConfigCopperDefaultVlanId OBJECT-TYPE
        SYNTAX      INTEGER(0..4095)
        MAX-ACCESS read-write
        STATUS current
        DESCRIPTION
            "Set the default VLAN ID to insert when tagging frames.
             (This feature may require a media converter module firmware upgrade)."
    ::= { cm110ConfigEntry 48 }

    cm110ConfigCopperDefaultPriority OBJECT-TYPE
        SYNTAX      INTEGER(0..7)
        MAX-ACCESS read-write
        STATUS current
        DESCRIPTION
            "Set the default frame priority.
             (This feature may require a media converter module firmware upgrade)."
    ::= { cm110ConfigEntry 49 }

    cm110ConfigCopperVlanTaggingAction OBJECT-TYPE
        SYNTAX INTEGER {
            notApplicable(-1),
            none(0),
            untag(1),
            tag(2),
            doubleTag(3)
        }
        MAX-ACCESS read-write
        STATUS current
        DESCRIPTION
            "Set the default tagging action.
             (This feature may require a media converter module firmware upgrade)."
    ::= { cm110ConfigEntry 50 }

    cm110ConfigCopperFilterUnknownMulticast OBJECT-TYPE
        SYNTAX      OnOffValue
        MAX-ACCESS read-write
        STATUS current
        DESCRIPTION
            "Enable filtering of multicast frames with an unknown destination
             (This feature may require a media converter module firmware upgrade)."
    ::= { cm110ConfigEntry 51 }

    cm110ConfigCopperFilterUnknownUnicast OBJECT-TYPE
        SYNTAX      OnOffValue
        MAX-ACCESS read-write
        STATUS current
        DESCRIPTION
            "Enable filtering of unicast frames with an unknown destination
             (This feature may require a media converter module firmware upgrade)."
    ::= { cm110ConfigEntry 52 }

    cm110ConfigFiber8021pPriority OBJECT-TYPE
        SYNTAX      OnOffValue
        MAX-ACCESS read-write
        STATUS current
        DESCRIPTION
            "Use 802.1p tag priority.
             (This feature may require a media converter module firmware upgrade)."
    ::= { cm110ConfigEntry 53 }

    cm110ConfigFiberIpTosPriority OBJECT-TYPE
        SYNTAX      OnOffValue
        MAX-ACCESS read-write
        STATUS current
        DESCRIPTION
            "Use IP TOS priority.
             (This feature may require a media converter module firmware upgrade)."
    ::= { cm110ConfigEntry 54 }

    cm110ConfigFiberPriorityPrecedence OBJECT-TYPE
        SYNTAX INTEGER {
            notApplicable(-1),
            priority8021p(0),
            priorityIpTos(1)
        }
        MAX-ACCESS read-write
        STATUS current
        DESCRIPTION
            "Configure priority precedence.
             (This feature may require a media converter module firmware upgrade)."
    ::= { cm110ConfigEntry 55 }

    cm110ConfigFiberCongestionPolicy OBJECT-TYPE
        SYNTAX INTEGER {
            notApplicable(-1),
            strict(0),
            weighted(1)
        }
        MAX-ACCESS read-write
        STATUS current
        DESCRIPTION
            "Configure priority congestion policy.
             (This feature may require a media converter module firmware upgrade)."
    ::= { cm110ConfigEntry 56 }

    cm110ConfigFiberPriorityMap0 OBJECT-TYPE
        SYNTAX INTEGER(0..7)
        MAX-ACCESS read-write
        STATUS current
        DESCRIPTION
            "Change the priority of frames tagged with 802.1p priority 0.
             A value of -1 signifies that this feature is not supported
             by the current media converter module firmware.
             (This feature may require a media converter module firmware upgrade)."
    ::= { cm110ConfigEntry 57 }

    cm110ConfigFiberPriorityMap1 OBJECT-TYPE
        SYNTAX INTEGER(0..7)
        MAX-ACCESS read-write
        STATUS current
        DESCRIPTION
            "Change the priority of frames tagged with 802.1p priority 1.
             A value of -1 signifies that this feature is not supported
             by the current media converter module firmware.
             (This feature may require a media converter module firmware upgrade)."
    ::= { cm110ConfigEntry 58 }

    cm110ConfigFiberPriorityMap2 OBJECT-TYPE
        SYNTAX INTEGER(0..7)
        MAX-ACCESS read-write
        STATUS current
        DESCRIPTION
            "Change the priority of frames tagged with 802.1p priority 2.
             A value of -1 signifies that this feature is not supported
             by the current media converter module firmware.
             (This feature may require a media converter module firmware upgrade)."
    ::= { cm110ConfigEntry 59 }

    cm110ConfigFiberPriorityMap3 OBJECT-TYPE
        SYNTAX INTEGER(0..7)
        MAX-ACCESS read-write
        STATUS current
        DESCRIPTION
            "Change the priority of frames tagged with 802.1p priority 3.
             A value of -1 signifies that this feature is not supported
             by the current media converter module firmware.
             (This feature may require a media converter module firmware upgrade)."
    ::= { cm110ConfigEntry 60 }

    cm110ConfigFiberPriorityMap4 OBJECT-TYPE
        SYNTAX INTEGER(0..7)
        MAX-ACCESS read-write
        STATUS current
        DESCRIPTION
            "Change the priority of frames tagged with 802.1p priority 4.
             A value of -1 signifies that this feature is not supported
             by the current media converter module firmware.
             (This feature may require a media converter module firmware upgrade)."
    ::= { cm110ConfigEntry 61 }

    cm110ConfigFiberPriorityMap5 OBJECT-TYPE
        SYNTAX INTEGER(0..7)
        MAX-ACCESS read-write
        STATUS current
        DESCRIPTION
            "Change the priority of frames tagged with 802.1p priority 5.
             A value of -1 signifies that this feature is not supported
             by the current media converter module firmware.
             (This feature may require a media converter module firmware upgrade)."
    ::= { cm110ConfigEntry 62 }

    cm110ConfigFiberPriorityMap6 OBJECT-TYPE
        SYNTAX INTEGER(0..7)
        MAX-ACCESS read-write
        STATUS current
        DESCRIPTION
            "Change the priority of frames tagged with 802.1p priority 6.
             A value of -1 signifies that this feature is not supported
             by the current media converter module firmware.
             (This feature may require a media converter module firmware upgrade)."
    ::= { cm110ConfigEntry 63 }

    cm110ConfigFiberPriorityMap7 OBJECT-TYPE
        SYNTAX INTEGER(0..7)
        MAX-ACCESS read-write
        STATUS current
        DESCRIPTION
            "Change the priority of frames tagged with 802.1p priority 7.
             A value of -1 signifies that this feature is not supported
             by the current media converter module firmware.
             (This feature may require a media converter module firmware upgrade)."
    ::= { cm110ConfigEntry 64 }

    cm110ConfigFiberIngressLimit OBJECT-TYPE
        SYNTAX INTEGER {
            notApplicable(-1),
            rateUnlimited(0),
            rate64kbps(1),
            rate128kbps(2),
            rate192kbps(3),
            rate256kbps(4),
            rate320kbps(5),
            rate384kbps(6),
            rate512kbps(7),
            rate768kbps(8),
            rate1mbps  (9),
            rate2mbps  (10),
            rate3mbps  (11),
            rate4mbps  (12),
            rate5mbps  (13),
            rate6mbps  (14),
            rate7mbps  (15),
            rate8mbps  (16),
            rate9mbps  (17),
            rate10mbps (18),
            rate20mbps (19),
            rate30mbps (20),
            rate40mbps (21),
            rate50mbps (22),
            rate60mbps (23),
            rate70mbps (24),
            rate80mbps (25),
            rate90mbps (26)
        }
        MAX-ACCESS read-write
        STATUS current
        DESCRIPTION
            "Set a limit on the rate of incoming packets.
             (This feature may require a media converter module firmware upgrade)."
    ::= { cm110ConfigEntry 65 }

    cm110ConfigFiberEgressLimit OBJECT-TYPE
        SYNTAX INTEGER {
            notApplicable(-1),
            rateUnlimited(0),
            rate64kbps(1),
            rate128kbps(2),
            rate192kbps(3),
            rate256kbps(4),
            rate320kbps(5),
            rate384kbps(6),
            rate512kbps(7),
            rate768kbps(8),
            rate1mbps  (9),
            rate2mbps  (10),
            rate3mbps  (11),
            rate4mbps  (12),
            rate5mbps  (13),
            rate6mbps  (14),
            rate7mbps  (15),
            rate8mbps  (16),
            rate9mbps  (17),
            rate10mbps (18),
            rate20mbps (19),
            rate30mbps (20),
            rate40mbps (21),
            rate50mbps (22),
            rate60mbps (23),
            rate70mbps (24),
            rate80mbps (25),
            rate90mbps (26)
        }
        MAX-ACCESS read-write
        STATUS current
        DESCRIPTION
            "Set a limit on the rate of outgoing packets.
             (This feature may require a media converter module firmware upgrade)."
    ::= { cm110ConfigEntry 66 }

    cm110ConfigFiberDiscardTaggedFrames OBJECT-TYPE
        SYNTAX      OnOffValue
        MAX-ACCESS read-write
        STATUS current
        DESCRIPTION
            "Enable discarding of tagged frames.
             (This feature may require a media converter module firmware upgrade)."
    ::= { cm110ConfigEntry 67 }

    cm110ConfigFiberDiscardUntaggedFrames OBJECT-TYPE
        SYNTAX      OnOffValue
        MAX-ACCESS read-write
        STATUS current
        DESCRIPTION
            "Enable discarding of untagged frames.
             (This feature may require a media converter module firmware upgrade)."
    ::= { cm110ConfigEntry 68 }

    cm110ConfigFiberDefaultVlanId OBJECT-TYPE
        SYNTAX      INTEGER(0..4095)
        MAX-ACCESS read-write
        STATUS current
        DESCRIPTION
            "Set the default VLAN ID to insert when tagging frames.
             (This feature may require a media converter module firmware upgrade)."
    ::= { cm110ConfigEntry 69}

    cm110ConfigFiberDefaultPriority OBJECT-TYPE
        SYNTAX      INTEGER(0..7)
        MAX-ACCESS read-write
        STATUS current
        DESCRIPTION
            "Set the default frame priority.
             (This feature may require a media converter module firmware upgrade)."
    ::= { cm110ConfigEntry 70 }

    cm110ConfigFiberVlanTaggingAction OBJECT-TYPE
        SYNTAX INTEGER {
            notApplicable(-1),
            none(0),
            untag(1),
            tag(2),
            doubleTag(3)
        }
        MAX-ACCESS read-write
        STATUS current
        DESCRIPTION
            "Set the default tagging action.
             (This feature may require a media converter module firmware upgrade)."
    ::= { cm110ConfigEntry 71 }

    cm110ConfigFiberFilterUnknownMulticast OBJECT-TYPE
        SYNTAX      OnOffValue
        MAX-ACCESS read-write
        STATUS current
        DESCRIPTION
            "Enable filtering of multicast frames with an unknown destination
             (This feature may require a media converter module firmware upgrade)."
    ::= { cm110ConfigEntry 72}

    cm110ConfigFiberFilterUnknownUnicast OBJECT-TYPE
        SYNTAX      OnOffValue
        MAX-ACCESS read-write
        STATUS current
        DESCRIPTION
            "Enable filtering of unicast frames with an unknown destination
             (This feature may require a media converter module firmware upgrade)."
    ::= { cm110ConfigEntry 73 }




--
-- end of cm110ConfigTable
--

--
-- cm110LedTable
--
cm110LedTable	OBJECT-TYPE
    SYNTAX		SEQUENCE OF Cm110LedEntry
    MAX-ACCESS	not-accessible
    STATUS		current
    DESCRIPTION
        "Table of CM-110 type media converter module's LED status information."
    ::= { cm110RateConv 3 }

    cm110LedEntry OBJECT-TYPE
        SYNTAX      Cm110LedEntry
        MAX-ACCESS  not-accessible
        STATUS      current
        DESCRIPTION
            "Entries of the table, each relating to a separate CM-110 type
             media converter module."
        INDEX   { mcrChassisIndex, cm110LedSlotIndex }
        ::= { cm110LedTable 1 }

    Cm110LedEntry ::=
        SEQUENCE {
            cm110LedSlotIndex		SlotNumber,
            cm110LedPWR				INTEGER,
            cm110LedFDF				INTEGER,
            cm110LedLKF				INTEGER,
            cm110LedCopperSpeed	INTEGER,
            cm110LedFDC 			INTEGER,
            cm110LedLKC				INTEGER
        }

    cm110LedSlotIndex	OBJECT-TYPE
        SYNTAX		SlotNumber
        MAX-ACCESS	not-accessible
        STATUS		current
        DESCRIPTION
            "The Slot number the CM-110 type module is currently inserted"
    ::= { cm110LedEntry 2 }

    cm110LedPWR	OBJECT-TYPE
        SYNTAX		INTEGER {
            off(0),
            onGreen(1),
            blinking(2)
        }
        MAX-ACCESS	read-only
        STATUS		current
        DESCRIPTION
            "This object identifies the status of the power (PWR) LED on the media converter module.
             Possible status values are:
                 off(0) - No power to the module
                 onGreen(1) - Power being applied to module
                 blinking(2) - Fiber loopback enabled"
    ::= { cm110LedEntry 3 }

    cm110LedFDF	OBJECT-TYPE
        SYNTAX		INTEGER {
            offHalfDuplex(0),
            onFullDuplex(1)
        }
        MAX-ACCESS	read-only
        STATUS		current
        DESCRIPTION
            "This object identifies the status of the Full Duplex Fiber (FDF) LED
             on the media converter module."
    ::= { cm110LedEntry 4 }

    cm110LedLKF	OBJECT-TYPE
        SYNTAX		INTEGER {
            off(0),
            on(1)
        }
        MAX-ACCESS	read-only
        STATUS		current
        DESCRIPTION
            "This object identifies the status of the link fiber (LKF) LED on the
             media converter module.
             Possible status values are:
                 off(0) - No fiber link
                 on(1) - Fiber link present"
    ::= { cm110LedEntry 5 }

    cm110LedCopperSpeed	OBJECT-TYPE
        SYNTAX		INTEGER {
            off10Mbps(0),
            onGreen100Mbps(1)
        }
        MAX-ACCESS	read-only
        STATUS		current
        DESCRIPTION
            "This object identifies the status of the link copper speed (100/1000)
             LED on the media converter module."
    ::= { cm110LedEntry 6 }

    cm110LedFDC	OBJECT-TYPE
        SYNTAX		INTEGER {
            offHalfDuplex(0),
            onFullDuplex(1)
        }
        MAX-ACCESS	read-only
        STATUS		current
        DESCRIPTION
            "This object identifies the status of the Full Duplex Copper (FDC) LED
             on the media converter module."
    ::= { cm110LedEntry 7 }

    cm110LedLKC	OBJECT-TYPE
        SYNTAX		INTEGER {
            off(0),
            on(1)
        }
        MAX-ACCESS	read-only
        STATUS		current
        DESCRIPTION
            "This object identifies the status of the link copper (LKC) LED on the
             media converter module. Possible status values are:
                 off(0) - No copper link
                 on(1) - Copper link present"
    ::= { cm110LedEntry 8 }

--
-- end of cm110LedTable
--

--
-- cm110RateConvStatsTable
--
cm110RateConvStatsTable	OBJECT-TYPE
    SYNTAX		SEQUENCE OF Cm110RateConvStatsEntry
    MAX-ACCESS	not-accessible
    STATUS		current
    DESCRIPTION
        "Table of CM-110 media converter module's configuration and status type
         information."
    ::= { cm110RateConv 4 }

    cm110RateConvStatsEntry OBJECT-TYPE
        SYNTAX      Cm110RateConvStatsEntry
        MAX-ACCESS  not-accessible
        STATUS      current
        DESCRIPTION
            "Entries of the table, each relating to a separate CM-110 type
             media converter module."
        INDEX   { mcrChassisIndex, cm110StatsSlotIndex, cm110MediaPortIndex }
        ::= { cm110RateConvStatsTable 1 }

    Cm110RateConvStatsEntry ::=
        SEQUENCE {
            cm110StatsSlotIndex				SlotNumber,
            cm110MediaPortIndex				INTEGER,

            cm110PortRxErrors					INTEGER,
            cm110PortTxCollisions			INTEGER,
            cm110PortInFiltered				INTEGER,

            cm110PortInGoodOctets			Counter32,
            cm110PortInBadOctets				Counter32,
            cm110PortInUnicasts				Counter32,
            cm110PortInBroadcasts			Counter32,
            cm110PortInMulticasts			Counter32,
            cm110PortInPauses					Counter32,
            cm110PortInUnderSizes			Counter32,
            cm110PortInFragments				Counter32,
            cm110PortInOversizes				Counter32,
            cm110PortInJabbers				Counter32,
            cm110PortInMACRcvErrs			Counter32,
            cm110PortInFcsErrs				Counter32,

            cm110PortPkts64Octets			Counter32,
            cm110PortPkts65to127Octets		Counter32,
            cm110PortPkts128to255Octets	Counter32,
            cm110PortPkts256to511Octets	Counter32,
            cm110PortPkts512to1023Octets	Counter32,
            cm110PortPkts1024toMaxOctets	Counter32,

            cm110PortOutOctets				Counter32,
            cm110PortOutUnicasts				Counter32,
            cm110PortOutBroadcasts			Counter32,
            cm110PortOutMulticasts			Counter32,
            cm110PortOutPauses				Counter32,
            cm110PortDeferreds				Counter32,
            cm110PortCollisions				Counter32,
            cm110PortSingles					Counter32,
            cm110PortMultiples					Counter32,
            cm110PortExcessives				Counter32,
            cm110PortLates						Counter32,
            cm110PortOutFcsErrs				Counter32,

            cm110PortResetCounters			YesNoValue
        }

    cm110StatsSlotIndex	OBJECT-TYPE
        SYNTAX		SlotNumber
        MAX-ACCESS	not-accessible
        STATUS		current
        DESCRIPTION
            "The Slot number the CM-110 type module is currently inserted"
    ::= { cm110RateConvStatsEntry 2 }

    cm110MediaPortIndex OBJECT-TYPE
        SYNTAX INTEGER {
            copper(1),
            fiber(2)
        }
        MAX-ACCESS not-accessible
        STATUS current
        DESCRIPTION
            "Media converter module port index indicating which media port the statistical
             counters are associated with."
    ::= { cm110RateConvStatsEntry 3 }

    cm110PortRxErrors OBJECT-TYPE
        SYNTAX      INTEGER(0..65535)
        MAX-ACCESS  read-only
        STATUS      current
        DESCRIPTION
            "Total number of bad frames received."
        ::= { cm110RateConvStatsEntry 4 }

    cm110PortTxCollisions OBJECT-TYPE
        SYNTAX      INTEGER(0..65535)
        MAX-ACCESS  read-only
        STATUS      current
        DESCRIPTION
            "Total number of TX collisions encountered."
        ::= { cm110RateConvStatsEntry 5 }

    cm110PortInFiltered OBJECT-TYPE
        SYNTAX      INTEGER(0..65535)
        MAX-ACCESS  read-only
        STATUS      current
        DESCRIPTION
            "A counter that counts the number of good frames that were filtered
             due to ingress switch policy rules. "
        ::= { cm110RateConvStatsEntry 6 }

    cm110PortInGoodOctets OBJECT-TYPE
        SYNTAX      Counter32
        MAX-ACCESS  read-only
        STATUS      current
        DESCRIPTION
            "An ingress counter that is the sum of lengths of all good Ethernet
             frames received on the media port."
        ::= { cm110RateConvStatsEntry 7 }

    cm110PortInBadOctets OBJECT-TYPE
        SYNTAX      Counter32
        MAX-ACCESS  read-only
        STATUS      current
        DESCRIPTION
            "An ingress counter that is the sum of lengths of all bad Ethernet
             frames received on the media port.."
        ::= { cm110RateConvStatsEntry 8 }

    cm110PortInUnicasts OBJECT-TYPE
        SYNTAX      Counter32
        MAX-ACCESS  read-only
        STATUS      current
        DESCRIPTION
            "An ingress counter that counts the number of good frames received that
             have a Unicast destination MAC address."
        ::= { cm110RateConvStatsEntry 9 }

    cm110PortInBroadcasts OBJECT-TYPE
        SYNTAX      Counter32
        MAX-ACCESS  read-only
        STATUS      current
        DESCRIPTION
            "An ingress counter that counts the number of good frames received that
             have a Broadcast destination MAC address."
        ::= { cm110RateConvStatsEntry 10 }

    cm110PortInMulticasts OBJECT-TYPE
        SYNTAX      Counter32
        MAX-ACCESS  read-only
        STATUS      current
        DESCRIPTION
            "An ingress counter that counts the number of good frames received that
             have a Multicast destination MAC address. This count does not include
             frames counted in the cm1110PortInPauses or the cm1110PortInBroadcasts
             objects."
        ::= { cm110RateConvStatsEntry 11 }

    cm110PortInPauses OBJECT-TYPE
        SYNTAX      Counter32
        MAX-ACCESS  read-only
        STATUS      current
        DESCRIPTION
            "An ingress counter that counts the number of good frames received that
             have a Pause destination MAC address."
        ::= { cm110RateConvStatsEntry 12 }

    cm110PortInUnderSizes OBJECT-TYPE
        SYNTAX      Counter32
        MAX-ACCESS  read-only
        STATUS      current
        DESCRIPTION
            "An ingress counter that counts the number of frames received with a
             length less that 64 octets but with a valid FCS."
        ::= { cm110RateConvStatsEntry 13 }

    cm110PortInFragments OBJECT-TYPE
        SYNTAX      Counter32
        MAX-ACCESS  read-only
        STATUS      current
        DESCRIPTION
            "An ingress counter that counts the number of frames received with a
             length less that 64 octets and an invalid FCS."
        ::= { cm110RateConvStatsEntry 14 }

    cm110PortInOversizes OBJECT-TYPE
        SYNTAX      Counter32
        MAX-ACCESS  read-only
        STATUS      current
        DESCRIPTION
            "An ingress counter that counts the number of frames received with a
             length more than the maximum packet size but with a valid FCS.
             The maximum packet size can be set using the cm110ConfigMaxPacketsSize
             object."
        ::= { cm110RateConvStatsEntry 15 }

    cm110PortInJabbers OBJECT-TYPE
        SYNTAX      Counter32
        MAX-ACCESS  read-only
        STATUS      current
        DESCRIPTION
            "An ingress counter that counts the number of frames received with a
             length more than the maximum packet size but with a invalid FCS.
             The maximum packet size can be set using the cm110ConfigMaxPacketsSize
             object."
        ::= { cm110RateConvStatsEntry 16 }

    cm110PortInMACRcvErrs OBJECT-TYPE
        SYNTAX      Counter32
        MAX-ACCESS  read-only
        STATUS      current
        DESCRIPTION
            "An ingress counter of the number of Rx errors on the receive
             side of the  MAC"
        ::= { cm110RateConvStatsEntry 17 }

    cm110PortInFcsErrs OBJECT-TYPE
        SYNTAX      Counter32
        MAX-ACCESS  read-only
        STATUS      current
        DESCRIPTION
            "An ingress counter of the number of FCS Errors."
        ::= { cm110RateConvStatsEntry 18 }

    cm110PortPkts64Octets OBJECT-TYPE
        SYNTAX      Counter32
        MAX-ACCESS  read-only
        STATUS      current
        DESCRIPTION
            "A Histogram counter that counts the number of frames received and
             transmitted with a length of exactly 64 Octets, including those with
             errors."
        ::= { cm110RateConvStatsEntry 19 }

    cm110PortPkts65to127Octets OBJECT-TYPE
        SYNTAX      Counter32
        MAX-ACCESS  read-only
        STATUS      current
        DESCRIPTION
            "A Histogram counter that counts the number of frames received and
             transmitted with a length of between 65 and 127 Octets inclusive,
             including those with errors."
        ::= { cm110RateConvStatsEntry 20 }

    cm110PortPkts128to255Octets OBJECT-TYPE
        SYNTAX      Counter32
        MAX-ACCESS  read-only
        STATUS      current
        DESCRIPTION
            "A Histogram counter that counts the number of frames received and
             transmitted with a length of between 128 and 255 Octets inclusive,
             including those with errors."
        ::= { cm110RateConvStatsEntry 21 }

    cm110PortPkts256to511Octets OBJECT-TYPE
        SYNTAX      Counter32
        MAX-ACCESS  read-only
        STATUS      current
        DESCRIPTION
            "A Histogram counter that counts the number of frames received and
             transmitted with a length of between 256 and 511 Octets inclusive,
             including those with errors."

        ::= { cm110RateConvStatsEntry 22 }

    cm110PortPkts512to1023Octets OBJECT-TYPE
        SYNTAX      Counter32
        MAX-ACCESS  read-only
        STATUS      current
        DESCRIPTION
            "A Histogram counter that counts the number of frames received and
             transmitted with a length of between 512 and 1023 Octets inclusive,
             including those with errors."
        ::= { cm110RateConvStatsEntry 23 }

    cm110PortPkts1024toMaxOctets OBJECT-TYPE
        SYNTAX      Counter32
        MAX-ACCESS  read-only
        STATUS      current
        DESCRIPTION
            "A Histogram counter that counts the number of frames received and
             transmitted with a length of between 1024 and maximum packet size
             octets inclusive, including those with errors.
             The maximum packet size can be set using the cm1110ConfigMaxPacketsSize
             object."
        ::= { cm110RateConvStatsEntry 24 }

     cm110PortOutOctets OBJECT-TYPE
        SYNTAX      Counter32
        MAX-ACCESS  read-only
        STATUS      current
        DESCRIPTION
            "An Egress counter that is the sum of lengths of all good Ethernet
             frames sent on the media port."
        ::= { cm110RateConvStatsEntry 25 }


    cm110PortOutUnicasts OBJECT-TYPE
        SYNTAX      Counter32
        MAX-ACCESS  read-only
        STATUS      current
        DESCRIPTION
            "An Egress counter that counts the number of good frames sent that
             have a Unicast destination MAC address."
        ::= { cm110RateConvStatsEntry 26 }

    cm110PortOutBroadcasts OBJECT-TYPE
        SYNTAX      Counter32
        MAX-ACCESS  read-only
        STATUS      current
        DESCRIPTION
            "An Egress counter that counts the number of good frames sent that
             have a Broadcast destination MAC address."
        ::= { cm110RateConvStatsEntry 27 }

    cm110PortOutMulticasts OBJECT-TYPE
        SYNTAX      Counter32
        MAX-ACCESS  read-only
        STATUS      current
        DESCRIPTION
            "An Egress counter that counts the number of good frames sent that
             have a Multicast destination MAC address. This count does not include
             frames counted in the cm1110PortOutPauses or the cm1110PortOutBroadcasts
             objects."
        ::= { cm110RateConvStatsEntry 28 }

    cm110PortOutPauses OBJECT-TYPE
        SYNTAX      Counter32
        MAX-ACCESS  read-only
        STATUS      current
        DESCRIPTION
            "An Egress counter that counts the number of good frames received that
             have a Pause destination MAC address."
        ::= { cm110RateConvStatsEntry 29 }

    cm110PortDeferreds OBJECT-TYPE
        SYNTAX      Counter32
        MAX-ACCESS  read-only
        STATUS      current
        DESCRIPTION
            "An Egress counter that counts the number of successfully transmitted
             frames that experienced no collsions but are delayed because the
             medium was busy during the first attempt. This counter is applicable
             in half-duplex only."
        ::= { cm110RateConvStatsEntry 30 }

    cm110PortCollisions OBJECT-TYPE
        SYNTAX      Counter32
        MAX-ACCESS  read-only
        STATUS      current
        DESCRIPTION
            "An Egress counter that counts the number of collision events seen by
             the MAC not including those counted in cm110PortSingles,
             cm110PortMultiple , cm1110PortExcessives or cm110PortLates objects.
             This counter is applicable in half-duplex only."
        ::= { cm110RateConvStatsEntry 31 }

    cm110PortSingles OBJECT-TYPE
        SYNTAX      Counter32
        MAX-ACCESS  read-only
        STATUS      current
        DESCRIPTION
            "An Egress counter that counts the number of successfully transmitted
             frames that experienced exactly one collision. This counter is
             applicable in half-duplex only."
        ::= { cm110RateConvStatsEntry 32 }

    cm110PortMultiples OBJECT-TYPE
        SYNTAX      Counter32
        MAX-ACCESS  read-only
        STATUS      current
        DESCRIPTION
            "An Egress counter that counts the number of successfully transmitted
             frames that experienced more than one collision. This counter is
             aplicable in half-duplex only."
        ::= { cm110RateConvStatsEntry 33 }

    cm110PortExcessives OBJECT-TYPE
        SYNTAX      Counter32
        MAX-ACCESS  read-only
        STATUS      current
        DESCRIPTION
            "An Egress counter that counts the number frames dropped in the transmit
             MAC because the frame experienced 16 consecutive collisions.  This
             counter is applicable in half-duplex only. "
        ::= { cm110RateConvStatsEntry 34 }

    cm110PortLates OBJECT-TYPE
        SYNTAX      Counter32
        MAX-ACCESS  read-only
        STATUS      current
        DESCRIPTION
            "An Egress counter that counts the number times a collision is detected
             later than 512 bits-times into the transmission of a frame. This
             counter is applicable in half-duplex only."
        ::= { cm110RateConvStatsEntry 35 }

    cm110PortOutFcsErrs OBJECT-TYPE
        SYNTAX      Counter32
        MAX-ACCESS  read-only
        STATUS      current
        DESCRIPTION
            "An Egress counter that counts the number frames transmitted with an
             invalid FCS. "
        ::= { cm110RateConvStatsEntry 36 }

    cm110PortResetCounters OBJECT-TYPE
        SYNTAX      YesNoValue
        MAX-ACCESS  read-write
        STATUS      current
        DESCRIPTION
            "Allows the resetting of all cm110RateConvStats statistical counters
             for this port."
        ::= { cm110RateConvStatsEntry 37 }
--
-- end of cm110RateConvStatsTable
--

--
-- cm110RateConvVctTable
--
cm110RateConvVctTable	OBJECT-TYPE
    SYNTAX		SEQUENCE OF Cm110RateConvVctEntry
    MAX-ACCESS	not-accessible
    STATUS		current
    DESCRIPTION
        "Table of CM-110 type media converter module's "
    ::= { cm110RateConv 5 }

    cm110RateConvVctEntry OBJECT-TYPE
        SYNTAX      Cm110RateConvVctEntry
        MAX-ACCESS  not-accessible
        STATUS      current
        DESCRIPTION
            "Entries of the table, each relating to a separate fiber or copper
             port on the CM-110 type media converter module."
        INDEX   { mcrChassisIndex, cm110VctSlotIndex }
        ::= { cm110RateConvVctTable 1 }

    Cm110RateConvVctEntry ::=
        SEQUENCE {
            cm110VctSlotIndex				SlotNumber,
            cm110VctStart					YesNoValue,
            cm110VctStatus					INTEGER,
            cm110VctTxPairResults		INTEGER,
            cm110VctTxPairAmplitude		DisplayString,
            cm110VctTxPairDistance		DisplayString,
            cm110VctRxPairResults		INTEGER,
            cm110VctRxPairAmplitude		DisplayString,
            cm110VctRxPairDistance		DisplayString
            }

    cm110VctSlotIndex	OBJECT-TYPE
        SYNTAX		SlotNumber
        MAX-ACCESS	not-accessible
        STATUS		current
        DESCRIPTION
            "The Slot number the CM-1110 type module is currently inserted"
    ::= { cm110RateConvVctEntry 2 }

    cm110VctStart OBJECT-TYPE
        SYNTAX		YesNoValue
        MAX-ACCESS	read-write
        STATUS		current
        DESCRIPTION
            "Set this self-clearing variable to yes initiate the Advanced Virtual
             Cable Test. Note: During the test, no network data will be passed."
        ::= { cm110RateConvVctEntry 3 }

    cm110VctStatus OBJECT-TYPE
        SYNTAX 		INTEGER {
            notStarted(0),
            inProgress(1),
            testComplete(2)
        }
        MAX-ACCESS	read-only
        STATUS 		current
        DESCRIPTION
            "This object identifies the stat of the Advanced Virtual Cable Test. "
        ::= { cm110RateConvVctEntry 4 }

    cm110VctTxPairResults OBJECT-TYPE
        SYNTAX INTEGER {
            normal(0),
            shortDetected(1),
            openDetected(2),
            testFailed(3)
        }
        MAX-ACCESS read-only
        STATUS current
        DESCRIPTION
            "Test result code returned from Virtual Cable Test of the Tx
             pair."
        ::= { cm110RateConvVctEntry 5 }

    cm110VctTxPairAmplitude OBJECT-TYPE
        SYNTAX DisplayString(SIZE(0..20))
        MAX-ACCESS read-only
        STATUS current
        DESCRIPTION
            "Amplitude of Tx pair in Volts."
        ::= { cm110RateConvVctEntry 6 }

    cm110VctTxPairDistance OBJECT-TYPE
        SYNTAX		DisplayString(SIZE(0..20))
        MAX-ACCESS read-only
        STATUS current
        DESCRIPTION
            "Distance in meters to fault when test result codes is
             short or open. "
        ::= { cm110RateConvVctEntry 7 }

    cm110VctRxPairResults OBJECT-TYPE
        SYNTAX INTEGER {
            normal(0),
            shortDetected(1),
            openDetected(2),
            testFailed(3)
        }
        MAX-ACCESS read-only
        STATUS current
        DESCRIPTION
            "Test result code returned from Virtual Cable Test of the Rx
             pair."
        ::= { cm110RateConvVctEntry 8 }

    cm110VctRxPairAmplitude OBJECT-TYPE
        SYNTAX DisplayString(SIZE(0..20))
        MAX-ACCESS read-only
        STATUS current
        DESCRIPTION
            "Amplitude of Rx pair in Volts."
        ::= { cm110RateConvVctEntry 9 }

    cm110VctRxPairDistance OBJECT-TYPE
        SYNTAX		DisplayString(SIZE(0..20))
        MAX-ACCESS read-only
        STATUS current
        DESCRIPTION
            "Distance in meters to fault when test result codes is
             short or open. "
        ::= { cm110RateConvVctEntry 10 }


--
-- cm110RateConvVctTable
--

--
-- end of cm110RateConv
--


--
-- mcrMgt -  MCR-MGT management type modules.
--
mcrMgt	OBJECT IDENTIFIER ::= { mcrModuleTypes 5 }

--
-- mcrMgtTable
--
mcrMgtTable	OBJECT-TYPE
    SYNTAX		SEQUENCE OF McrMgtEntry
    MAX-ACCESS	not-accessible
    STATUS		current
    DESCRIPTION
        "Table of MCR-MGT management module status type information."
    ::= { mcrMgt 1 }

    mcrMgtEntry OBJECT-TYPE
        SYNTAX      McrMgtEntry
        MAX-ACCESS  not-accessible
        STATUS      current
        DESCRIPTION
            "Entries of the table, each relating to a separate MCR-MGT type
             management module."
        INDEX   { mcrChassisIndex, mcrMgtSlotIndex }
        ::= { mcrMgtTable 1 }

    McrMgtEntry ::=
        SEQUENCE {
            mcrMgtSlotIndex					SlotNumber,
            mcrMgtModelName					DisplayString,
            mcrMgtModelDesc					DisplayString,
            mcrMgtFailSafeBootLoaderVer	DisplayString,
            mcrMgtUpTime						TimeTicks,
            mcrMgtConsoleDSR					OnOffValue
        }

    mcrMgtSlotIndex	OBJECT-TYPE
        SYNTAX		SlotNumber
        MAX-ACCESS	not-accessible
        STATUS		current
        DESCRIPTION
            "The Slot number the MCR-MGT module is currently inserted"
    ::= { mcrMgtEntry 2 }


    mcrMgtModelName	OBJECT-TYPE
        SYNTAX		DisplayString
        MAX-ACCESS	read-only
        STATUS		current
        DESCRIPTION
            "This object identifies the model name of management module present in the
             chassis"
    ::= { mcrMgtEntry 3 }

    mcrMgtModelDesc		OBJECT-TYPE
        SYNTAX		DisplayString
        MAX-ACCESS	read-only
        STATUS		current
        DESCRIPTION
            "This object identifies a static description of the management module present
             in the chassis"
    ::= { mcrMgtEntry 4 }

    mcrMgtFailSafeBootLoaderVer		OBJECT-TYPE
        SYNTAX		DisplayString
        MAX-ACCESS	read-only
        STATUS		current
        DESCRIPTION
            "This object identifies the fail-safe bootloader version of the
             management module present in the chassis"
    ::= { mcrMgtEntry 5 }

    mcrMgtUpTime	OBJECT-TYPE
        SYNTAX      TimeTicks
        MAX-ACCESS	read-only
        STATUS		current
        DESCRIPTION
            "This object identifies the time (in hundredths of a second) since the
              management module was last re-initialized."
        ::= { mcrMgtEntry 6 }

    mcrMgtConsoleDSR OBJECT-TYPE
        SYNTAX      OnOffValue
        MAX-ACCESS  read-only
        STATUS      current
        DESCRIPTION
            "This object identifies the current status of the DSR signal, (active or
             inactive)"
        ::= { mcrMgtEntry 7 }

--
-- mcrMgtTable
--
--
-- mcrMgtConfigTable
--
mcrMgtConfigTable	OBJECT-TYPE
    SYNTAX		SEQUENCE OF McrMgtConfigEntry
    MAX-ACCESS	not-accessible
    STATUS		current
    DESCRIPTION
        "Table of MCR-MGT management module Hardware configuration type information."
    ::= { mcrMgt 2 }

    mcrMgtConfigEntry OBJECT-TYPE
        SYNTAX      McrMgtConfigEntry
        MAX-ACCESS  not-accessible
        STATUS      current
        DESCRIPTION
            "Entries of the table, each relating to a separate MCR-MGT type
             management module."
        INDEX   { mcrChassisIndex, mcrMgtConfigSlotIndex }
        ::= { mcrMgtConfigTable 1 }

    McrMgtConfigEntry ::=
        SEQUENCE {
            mcrMgtConfigSlotIndex				SlotNumber,
            mcrMgtConfigStatus					ContainerStatus,
            mcrMgtConfigEthSpeedDuplex			INTEGER,
            mcrMgtConfigEthCrossover			INTEGER,
            mcrMgtConfigConsolePortEnabled	YesNoValue,
            mcrMgtConfigConsoleSpeed			INTEGER,
            mcrMgtConfigConsoleDataBits		INTEGER,
            mcrMgtConfigConsoleParity			INTEGER,
            mcrMgtConfigConsoleStopBits		INTEGER,
            mcrMgtConfigConsoleFlowControl	INTEGER,
            mcrMgtConfigConsoleMonitorDSR		OnOffValue
        }

    mcrMgtConfigSlotIndex	OBJECT-TYPE
        SYNTAX		SlotNumber
        MAX-ACCESS	not-accessible
        STATUS		current
        DESCRIPTION
            "The Slot number the MCR-MGT module is currently inserted"
    ::= { mcrMgtConfigEntry 2 }

    mcrMgtConfigStatus OBJECT-TYPE
        SYNTAX      ContainerStatus
        MAX-ACCESS  read-write
        STATUS      current
        DESCRIPTION
          "When you perform a GET on this variable, one of
            the following values will be returned:
            1-Indicates that the container folder is active with no changes.
            2-Indicates that the container folder is active with change(s).
            Once you have completed setting the variables in a folder, you
            will want to submit your changes to the management module. To do
            this, set the Status variable to 4. If you want to discard the
            changes, set the Status variable to 6.
            4-Indicates that the changes in the container folder are to be
              submitted to the management module, verified and and saved to flash.
            6-Indicates that the changes in the container folder are to be
              discarded."
        ::= { mcrMgtConfigEntry 3 }

    mcrMgtConfigEthSpeedDuplex OBJECT-TYPE
        SYNTAX      INTEGER {
            auto(0),
            speed10Half(1),
            speed10Full(2),
            speed100Half(3),
            speed100Full(4),
            speed1000(7)
        }
        MAX-ACCESS  read-write
        STATUS      current
        DESCRIPTION
            "Define the Ethernet connection speed/duplex of the twisted pair interface."
        ::= { mcrMgtConfigEntry 4 }

    mcrMgtConfigEthCrossover OBJECT-TYPE
        SYNTAX      INTEGER {
            auto(0),
            mdi(1),
            mdix(2)
        }
        MAX-ACCESS  read-write
        STATUS      current
        DESCRIPTION
            "Define the Ethernet connection crossover TX/RX Pair orientation of the
             twisted pair interface as auto(0), mdi(1) (straight through) or mdix(2)
             (crossed over)."
        ::= { mcrMgtConfigEntry 5 }

    mcrMgtConfigConsolePortEnabled OBJECT-TYPE
        SYNTAX      YesNoValue
        MAX-ACCESS  read-write
        STATUS      current
        DESCRIPTION
            "Determines whether the management module's console port is enabled."
        ::= { mcrMgtConfigEntry 6 }

    mcrMgtConfigConsoleSpeed OBJECT-TYPE
        SYNTAX      INTEGER {
            b9600(13),
            b19200(14),
            b38400(15),
            b57600(16),
            b115200(17)
        }
        MAX-ACCESS  read-write
        STATUS      current
        DESCRIPTION
            "Specifies the baud rate of the console port; keep in mind that
             speed is affected by the length of the cable."
        ::= { mcrMgtConfigEntry 7 }

    mcrMgtConfigConsoleDataBits OBJECT-TYPE
        SYNTAX      INTEGER {
            d7(2),
            d8(3)
        }
        MAX-ACCESS  read-write
        STATUS      current
        DESCRIPTION
            "Specifies the number of bits in a byte."
        ::= { mcrMgtConfigEntry 8 }

    mcrMgtConfigConsoleParity OBJECT-TYPE
        SYNTAX      INTEGER {
          none(0),
          odd(1),
          even(2)
        }
        MAX-ACCESS  read-write
        STATUS      current
        DESCRIPTION
            "Specifies if you are using Even, Odd, or No parity on the console."
        ::= { mcrMgtConfigEntry 9 }

    mcrMgtConfigConsoleStopBits OBJECT-TYPE
        SYNTAX      INTEGER {
          s1(0),
          s2(1)
        }
        MAX-ACCESS  read-write
        STATUS      current
        DESCRIPTION
            "Specifies the number of stop bits that follow a byte."
        ::= { mcrMgtConfigEntry 10 }

    mcrMgtConfigConsoleFlowControl OBJECT-TYPE
        SYNTAX      INTEGER {
            none(0),
            soft(1),
            hard(2),
            both(3)
        }
        MAX-ACCESS  read-write
        STATUS      current
        DESCRIPTION
            "Defines whether the data flow is handled by the software (Soft), hardware (Hard),
             both or None."
        ::= { mcrMgtConfigEntry 11 }

    mcrMgtConfigConsoleMonitorDSR OBJECT-TYPE
        SYNTAX      OnOffValue
        MAX-ACCESS  read-write
        STATUS      current
        DESCRIPTION
            "Specifies whether the RS-232 signal DSR (Data Set Ready) should
             be monitored, for the console port.

             When DSR is monitored and the management module detects the DSR signal go inactive
             then the current console management session will be reset. "
        ::= { mcrMgtConfigEntry 12 }

--
-- mcrMgtConfigTable
--

--
-- mcrMgtLedTable
--
mcrMgtLedTable	OBJECT-TYPE
    SYNTAX		SEQUENCE OF McrMgtLedEntry
    MAX-ACCESS	not-accessible
    STATUS		current
    DESCRIPTION
        "Table of MCR-MGT management module LED information."
    ::= { mcrMgt 3 }

    mcrMgtLedEntry OBJECT-TYPE
        SYNTAX      McrMgtLedEntry
        MAX-ACCESS  not-accessible
        STATUS      current
        DESCRIPTION
            "Entries of the table, each relating to a separate MCR-MGT type
             management module."
        INDEX   { mcrChassisIndex, mcrMgtLedSlotIndex }
        ::= { mcrMgtLedTable 1 }

    McrMgtLedEntry ::=
        SEQUENCE {
            mcrMgtLedSlotIndex		SlotNumber,
            mcrMgtLedPWR				INTEGER,
            mcrMgtLedALM				INTEGER,
            mcrMgtLedLKC				INTEGER,
            mcrMgtLedCopperSpeed	INTEGER
        }

    mcrMgtLedSlotIndex	OBJECT-TYPE
        SYNTAX		SlotNumber
        MAX-ACCESS	not-accessible
        STATUS		current
        DESCRIPTION
            "The Slot number the MCR-MGT module is currently inserted"
    ::= { mcrMgtLedEntry 2 }

    mcrMgtLedPWR	OBJECT-TYPE
        SYNTAX		INTEGER {
            off(0),
            onGreen(1)
    }
        MAX-ACCESS	read-only
        STATUS		current
        DESCRIPTION
            "This object identifies the status of the power (PWR) LED on the management module.
             Possible status values are:
                 off(0) - No power to the module
                 onGreen(1) - Power being applied to module"
    ::= { mcrMgtLedEntry 3 }

    mcrMgtLedALM	OBJECT-TYPE
        SYNTAX		INTEGER {
            offNoAlarms(0),
            onRedAlarmsPresent(1)
        }
        MAX-ACCESS	read-only
        STATUS		current
        DESCRIPTION
            "This object identifies the status of the alarm (ALM) LED on the management module.
             Possible status values are:
                 offNoAlarms(0) - Normal operating condition
                 onRedAlarmsPresent(1) - System hardware or software alarms present"
    ::= { mcrMgtLedEntry 4 }

    mcrMgtLedLKC	OBJECT-TYPE
        SYNTAX		INTEGER {
            offLinkDown(0),
            onGreenLinkUp(1)
        }
        MAX-ACCESS	read-only
        STATUS		current
        DESCRIPTION
            "This object identifies the status of the link copper (LKC) LED on the management module.
             Possible status values are:
                 offLinkDown(0) - Copper link status is DOWN
                 onGreenLinkUp(1) - Copper link status is UP"
    ::= { mcrMgtLedEntry 5 }

    mcrMgtLedCopperSpeed	OBJECT-TYPE
        SYNTAX		INTEGER {
            off10Mbps(0),
            onYellow100Mbps(1),
            onGreen1000Mbps(2)
        }
        MAX-ACCESS	read-only
        STATUS		current
        DESCRIPTION
            "This object identifies the status of the link copper speed (100/1000)
             LED on the management module."
    ::= { mcrMgtLedEntry 6 }
--
-- end of mcrMgtLedTable
--


--
-- mcrMgtEthStatsTable
--
mcrMgtEthStatsTable OBJECT-TYPE
    SYNTAX      SEQUENCE OF McrMgtEthStatsEntry
    MAX-ACCESS  not-accessible
    STATUS      current
    DESCRIPTION
              "Table of MCR-MGT management module Ethernet status and statistics
               information."
    ::= { mcrMgt 4 }

    mcrMgtEthStatsEntry OBJECT-TYPE
        SYNTAX      McrMgtEthStatsEntry
        MAX-ACCESS  not-accessible
        STATUS      current
        DESCRIPTION
                  "An entry in the Ethernet statistics table, each relating to an Ethernet interface."
        INDEX   { mcrChassisIndex, mgtEthSlotIndex }
        ::= { mcrMgtEthStatsTable 1 }

    McrMgtEthStatsEntry ::=
        SEQUENCE {
            mgtEthSlotIndex					SlotNumber,
            mgtEthStatsIfIndex				GenericTableIndex,
            mgtEthStatsName					DisplayString,
            mgtEthStatsMacAddress			MacAddress,
            mgtEthStatsStatus					INTEGER,
            mgtEthStatsSpeedDuplex			INTEGER,
            mgtEthStatsBroadcast				YesNoValue,
            mgtEthStatsDebug					YesNoValue,
            mgtEthStatsLoopback				YesNoValue,
            mgtEthStatsPointtoPoint			YesNoValue,
            mgtEthStatsNoTrailers			YesNoValue,
            mgtEthStatsRunning				YesNoValue,
            mgtEthStatsNoArp					YesNoValue,
            mgtEthStatsPromiscuous			YesNoValue,
            mgtEthStatsRxMulticast			YesNoValue,
            mgtEthStatsMasterLoadBalancer	YesNoValue,
            mgtEthStatsSlaveLoadBalancer	YesNoValue,
            mgtEthStatsMulticast				YesNoValue,
            mgtEthStatsSetMedia				YesNoValue,
            mgtEthStatsAutoMedia				YesNoValue,
            mgtEthStatsDynamic				YesNoValue,
            mgtEthStatsLocalAddress			IpAddress,
            mgtEthStatsSubnetMask			IpAddress,
            mgtEthStatsBroadcastAddress	IpAddress,
            mgtEthStatsMtu						Unsigned32,
            mgtEthStatsTxQLen					Unsigned32,
            mgtEthStatsRxBytes				Counter32,
            mgtEthStatsTxBytes				Counter32,
            mgtEthStatsRxPackets				Counter32,
            mgtEthStatsTxPackets				Counter32,
            mgtEthStatsRxErrors				Counter32,
            mgtEthStatsTxPktErrors			Counter32,
            mgtEthStatsRxDroppedPkts		Counter32,
            mgtEthStatsTxDroppedPkts		Counter32,
            mgtEthStatsRxOverruns			Counter32,
            mgtEthStatsTxOverruns			Counter32,
            mgtEthStatsRxFrameErrs			Counter32,
            mgtEthStatsTxCarrierErrs		Counter32,
            mgtEthStatsCollisions			Counter32
        }

    mgtEthSlotIndex	OBJECT-TYPE
        SYNTAX		SlotNumber
        MAX-ACCESS	not-accessible
        STATUS		current
        DESCRIPTION
            "The Slot number the MCR-MGT module is currently inserted."
    ::= { mcrMgtEthStatsEntry 2 }

    mgtEthStatsIfIndex OBJECT-TYPE
        SYNTAX      GenericTableIndex
        MAX-ACCESS not-accessible
        STATUS      current
        DESCRIPTION
                  "The Ethernet interface number."
        ::= { mcrMgtEthStatsEntry 3 }

    mgtEthStatsName OBJECT-TYPE
        SYNTAX      DisplayString
        MAX-ACCESS  read-only
        STATUS      current
        DESCRIPTION
            "Displays Ethernet interface name."
        ::= { mcrMgtEthStatsEntry 4 }

    mgtEthStatsMacAddress OBJECT-TYPE
        SYNTAX      MacAddress
        MAX-ACCESS  read-only
        STATUS      current
        DESCRIPTION
            "Displays the MAC address."
        ::= { mcrMgtEthStatsEntry 5 }

    mgtEthStatsStatus OBJECT-TYPE
        SYNTAX      INTEGER {
          down(0),
          up(1)
        }
        MAX-ACCESS  read-only
        STATUS      current
        DESCRIPTION
            "Displays the Ethernet link status - down(0) or up(1)."
        ::= { mcrMgtEthStatsEntry 6 }

    mgtEthStatsSpeedDuplex OBJECT-TYPE
        SYNTAX      INTEGER {
            unknown(0),
            speed10Half(1),
            speed10Full(2),
            speed100Half(3),
            speed100Full(4),
            speed1000Half(5),
            speed1000Full(6)
        }
        MAX-ACCESS  read-only
        STATUS      current
        DESCRIPTION
            "Current status of the Ethernet connection speed/duplex twisted pair interface.
             When the management module does not know the pair speed/duplex, this variable
             has the value unknown(0). 	"
        ::= { mcrMgtEthStatsEntry 7 }

    mgtEthStatsBroadcast OBJECT-TYPE
        SYNTAX      YesNoValue
        MAX-ACCESS  read-only
        STATUS      current
        DESCRIPTION
            "The management module's Ethernet Broadcast Flags status."
        ::= { mcrMgtEthStatsEntry 8 }

    mgtEthStatsDebug OBJECT-TYPE
        SYNTAX      YesNoValue
        MAX-ACCESS  read-only
        STATUS      current
        DESCRIPTION
            "The management module's Ethernet Debug Flags status."
        ::= { mcrMgtEthStatsEntry 9 }

    mgtEthStatsLoopback OBJECT-TYPE
        SYNTAX      YesNoValue
        MAX-ACCESS  read-only
        STATUS      current
        DESCRIPTION
            "The management module's Ethernet Loopback Flags status."
        ::= { mcrMgtEthStatsEntry 10 }

    mgtEthStatsPointtoPoint OBJECT-TYPE
        SYNTAX      YesNoValue
        MAX-ACCESS  read-only
        STATUS      current
        DESCRIPTION
            "The management module's Ethernet Point to Point Flags status."
        ::= { mcrMgtEthStatsEntry 11 }

    mgtEthStatsNoTrailers OBJECT-TYPE
        SYNTAX      YesNoValue
        MAX-ACCESS  read-only
        STATUS      current
        DESCRIPTION
            "The management module's Ethernet No Trailers Flags status."
        ::= { mcrMgtEthStatsEntry 12 }

    mgtEthStatsRunning OBJECT-TYPE
        SYNTAX      YesNoValue
        MAX-ACCESS  read-only
        STATUS      current
        DESCRIPTION
            "The management module's Ethernet Running Flags status."
        ::= { mcrMgtEthStatsEntry 13 }

    mgtEthStatsNoArp OBJECT-TYPE
        SYNTAX      YesNoValue
        MAX-ACCESS  read-only
        STATUS      current
        DESCRIPTION
            "The management module's Ethernet No Arp Protocol Flags status."
        ::= { mcrMgtEthStatsEntry 14 }

    mgtEthStatsPromiscuous OBJECT-TYPE
        SYNTAX      YesNoValue
        MAX-ACCESS  read-only
        STATUS      current
        DESCRIPTION
            "The management module's Ethernet Promiscuous Flags status."
        ::= { mcrMgtEthStatsEntry 15 }

    mgtEthStatsRxMulticast OBJECT-TYPE
        SYNTAX      YesNoValue
        MAX-ACCESS  read-only
        STATUS      current
        DESCRIPTION
            "The management module's Ethernet Receive all Multicast Flags status."
        ::= { mcrMgtEthStatsEntry 16}

    mgtEthStatsMasterLoadBalancer OBJECT-TYPE
        SYNTAX      YesNoValue
        MAX-ACCESS  read-only
        STATUS      current
        DESCRIPTION
            "The management module's Ethernet Master Load Balancer Flags status."
        ::= { mcrMgtEthStatsEntry 17 }

    mgtEthStatsSlaveLoadBalancer OBJECT-TYPE
        SYNTAX      YesNoValue
        MAX-ACCESS  read-only
        STATUS      current
        DESCRIPTION
            "The management module's Ethernet Slave Load Balancer Flags status."
        ::= { mcrMgtEthStatsEntry 18 }

    mgtEthStatsMulticast OBJECT-TYPE
        SYNTAX      YesNoValue
        MAX-ACCESS  read-only
        STATUS      current
        DESCRIPTION
            "The management module's Ethernet Multicast Flags status."
        ::= { mcrMgtEthStatsEntry 19 }

    mgtEthStatsSetMedia OBJECT-TYPE
        SYNTAX      YesNoValue
        MAX-ACCESS  read-only
        STATUS      current
        DESCRIPTION
            "The management module's Ethernet Set Media Flags status."
        ::= { mcrMgtEthStatsEntry 20 }

    mgtEthStatsAutoMedia OBJECT-TYPE
        SYNTAX      YesNoValue
        MAX-ACCESS  read-only
        STATUS      current
        DESCRIPTION
            "The management module's Ethernet Auto Media Flags status."
        ::= { mcrMgtEthStatsEntry 21 }

    mgtEthStatsDynamic OBJECT-TYPE
        SYNTAX      YesNoValue
        MAX-ACCESS  read-only
        STATUS      current
        DESCRIPTION
            "The management module's Ethernet Dynamic Flags status."
        ::= { mcrMgtEthStatsEntry 22 }

    mgtEthStatsLocalAddress OBJECT-TYPE
        SYNTAX      IpAddress
        MAX-ACCESS  read-only
        STATUS      current
        DESCRIPTION
            "The management module's Ethernet local IPv4 address."
        ::= { mcrMgtEthStatsEntry 23  }

    mgtEthStatsSubnetMask OBJECT-TYPE
        SYNTAX      IpAddress
        MAX-ACCESS  read-only
        STATUS      current
        DESCRIPTION
            "The management module's Ethernet  IPv4 subnet mask."
        ::= { mcrMgtEthStatsEntry 24 }

    mgtEthStatsBroadcastAddress OBJECT-TYPE
        SYNTAX      IpAddress
        MAX-ACCESS  read-only
        STATUS      current
        DESCRIPTION
            "The management module's Ethernet Broadcast address."
        ::= { mcrMgtEthStatsEntry 25 }

    mgtEthStatsMtu OBJECT-TYPE
        SYNTAX      Unsigned32
        MAX-ACCESS  read-only
        STATUS      current
        DESCRIPTION
            "The management module's Ethernet MTU."
        ::= { mcrMgtEthStatsEntry 26 }

    mgtEthStatsTxQLen OBJECT-TYPE
        SYNTAX      Unsigned32
        MAX-ACCESS  read-only
        STATUS      current
        DESCRIPTION
            "The management module's Ethernet TX Queue Length."
        ::= { mcrMgtEthStatsEntry 27 }

    mgtEthStatsRxBytes OBJECT-TYPE
        SYNTAX      Counter32
        MAX-ACCESS  read-only
        STATUS      current
        DESCRIPTION
            "The management module's Ethernet RX Bytes count."
        ::= { mcrMgtEthStatsEntry 28 }

    mgtEthStatsTxBytes OBJECT-TYPE
        SYNTAX      Counter32
        MAX-ACCESS  read-only
        STATUS      current
        DESCRIPTION
            "The management module's Ethernet TX Bytes count."
        ::= { mcrMgtEthStatsEntry 29 }

    mgtEthStatsRxPackets OBJECT-TYPE
        SYNTAX      Counter32
        MAX-ACCESS  read-only
        STATUS      current
        DESCRIPTION
            "The management module's Ethernet RX Packets count."
        ::= { mcrMgtEthStatsEntry 30 }

    mgtEthStatsTxPackets OBJECT-TYPE
        SYNTAX      Counter32
        MAX-ACCESS  read-only
        STATUS      current
        DESCRIPTION
            "The management module's Ethernet TX Packets count."
        ::= { mcrMgtEthStatsEntry 31 }

    mgtEthStatsRxErrors OBJECT-TYPE
        SYNTAX      Counter32
        MAX-ACCESS  read-only
        STATUS      current
        DESCRIPTION
            "The management module's Ethernet RX Packets Errors count."
        ::= { mcrMgtEthStatsEntry 32 }

    mgtEthStatsTxPktErrors OBJECT-TYPE
        SYNTAX      Counter32
        MAX-ACCESS  read-only
        STATUS      current
        DESCRIPTION
            "The management module's Ethernet TX Packets Errors count."
        ::= { mcrMgtEthStatsEntry 33 }

    mgtEthStatsRxDroppedPkts OBJECT-TYPE
        SYNTAX      Counter32
        MAX-ACCESS  read-only
        STATUS      current
        DESCRIPTION
            "The management module's Ethernet RX Dropped packets count."
        ::= { mcrMgtEthStatsEntry 34 }

    mgtEthStatsTxDroppedPkts OBJECT-TYPE
        SYNTAX      Counter32
        MAX-ACCESS  read-only
        STATUS      current
        DESCRIPTION
            "The management module's Ethernet TX Dropped packets count."
        ::= { mcrMgtEthStatsEntry 35 }

    mgtEthStatsRxOverruns OBJECT-TYPE
        SYNTAX      Counter32
        MAX-ACCESS  read-only
        STATUS      current
        DESCRIPTION
            "The management module's Ethernet RX Overruns count"
        ::= { mcrMgtEthStatsEntry 36 }

    mgtEthStatsTxOverruns OBJECT-TYPE
        SYNTAX      Counter32
        MAX-ACCESS  read-only
        STATUS      current
        DESCRIPTION
            "The management module's Ethernet TX Overruns count."
        ::= { mcrMgtEthStatsEntry 37 }

    mgtEthStatsRxFrameErrs OBJECT-TYPE
        SYNTAX      Counter32
        MAX-ACCESS  read-only
        STATUS      current
        DESCRIPTION
            "The management module's Ethernet RX Frame Errors count."
        ::= { mcrMgtEthStatsEntry 38 }

    mgtEthStatsTxCarrierErrs OBJECT-TYPE
        SYNTAX      Counter32
        MAX-ACCESS  read-only
        STATUS      current
        DESCRIPTION
            "The management module's Ethernet TX Carrier Errors count"
        ::= { mcrMgtEthStatsEntry 39 }

    mgtEthStatsCollisions OBJECT-TYPE
        SYNTAX      Counter32
        MAX-ACCESS  read-only
        STATUS      current
        DESCRIPTION
            "The management module's Ethernet Collisions count."
        ::= { mcrMgtEthStatsEntry 40 }
--
-- end of mcrMgtEthStatsTable
--


--
-- ************* end of mcrMgt -  modules ***********
--


-- cm10gFixed - 10 Gb fixed media Converter type modules
--
cm10gFixed	OBJECT IDENTIFIER ::= { mcrModuleTypes 8 }

--
-- cm10gFixedTable
--
cm10gFixedTable	OBJECT-TYPE
    SYNTAX		SEQUENCE OF Cm10gFixedEntry
    MAX-ACCESS	not-accessible
    STATUS		current
    DESCRIPTION
        "Table of CM-10G type media converter module's status type information."
    ::= { cm10gFixed 1 }

    cm10gFixedEntry OBJECT-TYPE
        SYNTAX      Cm10gFixedEntry
        MAX-ACCESS  not-accessible
        STATUS      current
        DESCRIPTION
            "Entries of the table, each relating to a separate CM-10G type
             media converter module."
        INDEX   { mcrChassisIndex, cm10gSlotIndex }
        ::= { cm10gFixedTable 1 }

    Cm10gFixedEntry ::=
        SEQUENCE {
            cm10gSlotIndex				SlotNumber,
            cm10gModelname				DisplayString,
            cm10gModelDesc				DisplayString,
            cm10gHwJmp5ConfigMode		INTEGER,
            cm10gHwSw1OperationMode		INTEGER,
            cm10gHwSw2LinkMode			INTEGER,
            cm10gHwSw3FiberFaultAlert	INTEGER,
            cm10gHwSw4Port1EdcMode		INTEGER,
            cm10gHwSw5Port2EdcMode		INTEGER,

            cm10gPort1LinkStatus		INTEGER,
            cm10gPort1ConnType			INTEGER,
            cm10gPort1AutoNegState		INTEGER,
            cm10gPort1Speed				INTEGER,
            cm10gPort1Duplex			INTEGER,
            cm10gPort1PauseEnh			INTEGER,
            cm10gPort1ReceiveStatus		INTEGER,

            cm10gPort2LinkStatus		INTEGER,
            cm10gPort2ConnType			INTEGER,
            cm10gPort2AutoNegState		INTEGER,
            cm10gPort2Speed				INTEGER,
            cm10gPort2Duplex			INTEGER,
            cm10gPort2PauseEnh			INTEGER,
            cm10gPort2ReceiveStatus		INTEGER,

            cm10gPortLoopBack			INTEGER,
            cm10gPortTestMode           INTEGER
        }

    cm10gSlotIndex	OBJECT-TYPE
        SYNTAX		SlotNumber
        MAX-ACCESS	not-accessible
        STATUS		current
        DESCRIPTION
            "The Slot number the CM-10G type module is currently inserted"
        ::= { cm10gFixedEntry 2 }

    cm10gModelname	OBJECT-TYPE
        SYNTAX		DisplayString
        MAX-ACCESS	read-only
        STATUS		current
        DESCRIPTION
            "This object identifies the model of media converter module present in the
             chassis"
        ::= { cm10gFixedEntry 3 }

    cm10gModelDesc		OBJECT-TYPE
        SYNTAX		DisplayString
        MAX-ACCESS	read-only
        STATUS		current
        DESCRIPTION
            "This object identifies a static description of the media converter module present
             in the chassis"
        ::= { cm10gFixedEntry 4 }

    cm10gHwJmp5ConfigMode		OBJECT-TYPE
        SYNTAX		INTEGER {
            hardwareSwitches(0),
            auto(1)
        }
        MAX-ACCESS	read-only
        STATUS		current
        DESCRIPTION
            "This object identifies the media converter module's ConfigMode, set by hardware
             jumper J5 on the media converter module. When this object is set to
             hardwareSwitches(0), the media converter module will disable configuration
             control from the management module's software and all configuration
             control comes from the media converter module's hardware switches or jumpers. "
        ::= { cm10gFixedEntry 5 }


    cm10gHwSw1OperationMode  OBJECT-TYPE
        SYNTAX 		INTEGER{
            test(0),
            data(1)
        }
        MAX-ACCESS read-only
        STATUS 		current
        DESCRIPTION
            "Media converter module's current switch setting for operation mode.
            Data mode is for normal data transmission."
        ::= { cm10gFixedEntry 6 }

    cm10gHwSw2LinkMode OBJECT-TYPE
        SYNTAX 		INTEGER {
            swDownSmartLinkPassthrough(0),
            swUpStandard(1)
        }
        MAX-ACCESS read-only
        STATUS 		current
        DESCRIPTION
            "Media converter module's current switch setting for Link Mode. If 
            the Operation switch is set to Test, then this object indicates 
            whether the port is in loopback or performing the build in link-test."
        ::= { cm10gFixedEntry 7 }

    cm10gHwSw3FiberFaultAlert OBJECT-TYPE
        SYNTAX 		INTEGER {
            swDownDisabled(0),
            swUpEnabled(1)
        }
        MAX-ACCESS read-only
        STATUS 		current
        DESCRIPTION
            "Media converter module's current switch setting for Fiber Fault 
            Alert.  If the Operation switch is set to Test, then this object 
            indicates which port is in test mode"
        ::= { cm10gFixedEntry 8 }

    cm10gHwSw4Port1EdcMode OBJECT-TYPE
        SYNTAX 		INTEGER {
            disabled(0),
            enabled(1)
        }
        MAX-ACCESS read-only
        STATUS 		current
        DESCRIPTION
            "This oject indicates the current switch setting for EDC auto mode 
            for port 1. This object only applies to SFP moudles." 
        ::= { cm10gFixedEntry 9 }

    cm10gHwSw5Port2EdcMode OBJECT-TYPE
        SYNTAX 		INTEGER {
            disabled(0),
            enabled(1)
        }
        MAX-ACCESS read-only
        STATUS 		current
        DESCRIPTION
            "This oject indicates the current switch setting for EDC auto mode 
            for port 2. This object only applies to SFP moudles." 
        ::= { cm10gFixedEntry 10 }

    cm10gPort1LinkStatus OBJECT-TYPE
        SYNTAX 		INTEGER {
            down(0),
            up(1),
            shutdown(2)
        }
        MAX-ACCESS read-only
        STATUS 		current
        DESCRIPTION
            "Media converter module's current fiber link status (port 1)."
        ::= { cm10gFixedEntry 11 }

    cm10gPort1ConnType OBJECT-TYPE
        SYNTAX 		INTEGER {
            sc(0),
            lc(1),
            st(2),
            sfp(3),
            fc(5),
            mtrj(6),
            xfp(7),
            sfpPlus(8)
        }
        MAX-ACCESS read-only
        STATUS 		current
        DESCRIPTION
            "Media converter module's fiber port connector type (port 1)."
        ::= { cm10gFixedEntry 12 }

    cm10gPort1AutoNegState OBJECT-TYPE
        SYNTAX		INTEGER {
            disabled(0),
            complete(1),
            inProgress(2)
        }
        MAX-ACCESS	read-only
        STATUS 		current
        DESCRIPTION
            "Media converter module's current fiber auto-negotiation state (port 1)."
        ::= { cm10gFixedEntry 13 }

    cm10gPort1Speed OBJECT-TYPE
        SYNTAX 		INTEGER {
            speed10Mbps(0),
            speed100Mbps(1),
            speed1000Mbps(2),
            speed10Gbps(3)
        }
        MAX-ACCESS	read-only
        STATUS 		current
        DESCRIPTION
            "Media converter module's fiber port speed in megabits per second (port 1)."
        ::= { cm10gFixedEntry 14 }

    cm10gPort1Duplex OBJECT-TYPE
        SYNTAX		INTEGER {
            half(0),
            full(1)
        }
        MAX-ACCESS	read-only
        STATUS		current
        DESCRIPTION
            "If fiber auto-negotiation state is complete then this object
            indicates the media converter module's current fiber auto-negotiated duplex
            setting. If auto-negotiation is not complete then the value returned should be
             ignored. (Port 1)"
        ::= { cm10gFixedEntry 15 }

    cm10gPort1PauseEnh OBJECT-TYPE
        SYNTAX INTEGER {
            disabled(0),
            symmetrical(1),
            asymmetricalTx(2),
            asymmetricalRx(3)
        }
        MAX-ACCESS read-only
        STATUS current
        DESCRIPTION
            "If fiber auto-negotiation state is complete then this object indicates
             the media converter module's current fiber auto-negotiated pause setting. If
             auto-negotiation is not complete then the value returned should be ignored.
             (Port 1)"
        ::= { cm10gFixedEntry 16 }

    cm10gPort1ReceiveStatus		OBJECT-TYPE
        SYNTAX	INTEGER {
            fault(0),
            ok(1)
        }
        MAX-ACCESS	read-only
        STATUS	current
        DESCRIPTION
            "This object identifies the status of whether light is being received
             on the fiber port (port 1)"
        ::= { cm10gFixedEntry 17 }

    cm10gPort2LinkStatus OBJECT-TYPE
        SYNTAX 		INTEGER {
            down(0),
            up(1),
            shutdown(2)
        }
        MAX-ACCESS read-only
        STATUS 		current
        DESCRIPTION
            "Media converter module's current fiber link status (port 2)."
        ::= { cm10gFixedEntry 18 }

    cm10gPort2ConnType OBJECT-TYPE
        SYNTAX 		INTEGER {
            sc(0),
            lc(1),
            st(2),
            sfp(3),
            fc(5),
            mtrj(6),
            xfp(7),
            sfpPlus(8)
        }
        MAX-ACCESS read-only
        STATUS 		current
        DESCRIPTION
            "Media converter module's fiber port connector type (port 2)."
        ::= { cm10gFixedEntry 19 }

    cm10gPort2AutoNegState OBJECT-TYPE
        SYNTAX		INTEGER {
            disabled(0),
            complete(1),
            inProgress(2)
        }
        MAX-ACCESS	read-only
        STATUS 		current
        DESCRIPTION
            "Media converter module's current fiber auto-negotiation state (port 2)."
        ::= { cm10gFixedEntry 20 }

    cm10gPort2Speed OBJECT-TYPE
        SYNTAX 		INTEGER {
            speed10Mbps(0),
            speed100Mbps(1),
            speed1000Mbps(2),
            speed10Gbps(3)
        }
        MAX-ACCESS	read-only
        STATUS 		current
        DESCRIPTION
            "Media converter module's fiber port speed in megabits per second (port 2)."
        ::= { cm10gFixedEntry 21 }

    cm10gPort2Duplex OBJECT-TYPE
        SYNTAX		INTEGER {
            half(0),
            full(1)
        }
        MAX-ACCESS	read-only
        STATUS		current
        DESCRIPTION
            "If fiber auto-negotiation state is complete then this object
            indicates the media converter module's current fiber auto-negotiated duplex
            setting. If auto-negotiation is not complete then the value returned should be
             ignored. (Port 2)"
        ::= { cm10gFixedEntry 22 }

    cm10gPort2PauseEnh OBJECT-TYPE
        SYNTAX INTEGER {
            disabled(0),
            symmetrical(1),
            asymmetricalTx(2),
            asymmetricalRx(3)
        }
        MAX-ACCESS read-only
        STATUS current
        DESCRIPTION
            "If fiber auto-negotiation state is complete then this object indicates
             the media converter module's current fiber auto-negotiated pause setting. If
             auto-negotiation is not complete then the value returned should be ignored.
             (Port 2)"
        ::= { cm10gFixedEntry 23 }

    cm10gPort2ReceiveStatus		OBJECT-TYPE
        SYNTAX	INTEGER {
            fault(0),
            ok(1)
        }
        MAX-ACCESS	read-only
        STATUS	current
        DESCRIPTION
            "This object identifies the status of whether light is being received
             on the fiber port (port 2)"
        ::= { cm10gFixedEntry 24 }

    cm10gPortLoopBack		OBJECT-TYPE
        SYNTAX	INTEGER {
            disabled(0),
            port1(1),
            port2(2)
        }
        MAX-ACCESS	read-write
        STATUS	current
        DESCRIPTION
            "Media converter module's current port loopback mode setting. Writing to this
             object will change the current settings. This object is read-only if
             the media converter module's ConfigMode jumper is set to hardwareSwitches(0)."
        ::= { cm10gFixedEntry 25 }

    cm10gPortTestMode	OBJECT-TYPE
        SYNTAX	INTEGER {
            disabled(0),
            port1(1),
            port2(2)
        }
        MAX-ACCESS	read-only
        STATUS	current
        DESCRIPTION
            "Media converter module's current port test mode setting."
        ::= { cm10gFixedEntry 26 }
--
-- cm10gFixedTable
--
--
-- cm10gConfigTable
--
cm10gConfigTable	OBJECT-TYPE
    SYNTAX		SEQUENCE OF Cm10gConfigEntry
    MAX-ACCESS	not-accessible
    STATUS		current
    DESCRIPTION
        "Table of CM-10G type media converter module's configuration type information."
    ::= { cm10gFixed 2 }

    cm10gConfigEntry OBJECT-TYPE
        SYNTAX      Cm10gConfigEntry
        MAX-ACCESS  not-accessible
        STATUS      current
        DESCRIPTION
            "Entries of the table, each relating to a separate CM-10G type
             media converter module."
        INDEX   { mcrChassisIndex, cm10gConfigSlotIndex }
        ::= { cm10gConfigTable 1 }

    Cm10gConfigEntry ::=
        SEQUENCE {
            cm10gConfigSlotIndex                SlotNumber,
            cm10gConfigStatus                   ContainerStatus,
            cm10gConfigModuleName               DisplayString,
            cm10gConfigLinkMode                 INTEGER,
            cm10gConfigFiberFaultAlert          EnableDisableValue,
            cm10gConfigFiberAutoNeg             EnableDisableValue,
            cm10gConfigPort1Name                DisplayString,
            cm10gConfigPort1Enable              YesNoValue,
            cm10gConfigPort1EdcMode             INTEGER,
            cm10gConfigPort1FecEnable           YesNoValue,
            cm10gConfigPort1FecAmplitude        INTEGER,
            cm10gConfigPort1FecPhase            INTEGER,
            cm10gConfigPort1WavelengthEnable    YesNoValue,
            cm10gConfigPort1WavelengthValue     INTEGER,
            cm10gConfigPort1ChannelEnable       YesNoValue,
            cm10gConfigPort1ChannelNumber       INTEGER,
            cm10gConfigPort1TxDitherEnable      YesNoValue,
            cm10gConfigPort1TxDitherValue       EnableDisableValue,
            
            cm10gConfigPort2Name                DisplayString,
            cm10gConfigPort2Enable              YesNoValue,
            cm10gConfigPort2EdcMode             INTEGER,
            cm10gConfigPort2FecEnable           YesNoValue,
            cm10gConfigPort2FecAmplitude        INTEGER,
            cm10gConfigPort2FecPhase            INTEGER,
            cm10gConfigPort2WavelengthEnable    YesNoValue,
            cm10gConfigPort2WavelengthValue     INTEGER,
            cm10gConfigPort2ChannelEnable       YesNoValue,
            cm10gConfigPort2ChannelNumber       INTEGER,
            cm10gConfigPort2TxDitherEnable      YesNoValue,
            cm10gConfigPort2TxDitherValue       EnableDisableValue
        }

    cm10gConfigSlotIndex	OBJECT-TYPE
        SYNTAX		SlotNumber
        MAX-ACCESS	not-accessible
        STATUS		current
        DESCRIPTION
            "The Slot number the CM-10G type module is currently inserted"
    ::= { cm10gConfigEntry 2 }

    cm10gConfigStatus OBJECT-TYPE
        SYNTAX      ContainerStatus
        MAX-ACCESS  read-write
        STATUS      current
        DESCRIPTION
          "When you perform a GET on this variable, one of
            the following values will be returned:
            1-Indicates that the container folder is active with no changes.
            2-Indicates that the container folder is active with change(s).
            Once you have completed setting the variables in a folder, you
            will want to submit your changes to the management module. To do
            this, set the Status variable to 4. If you want to discard the
            changes, set the Status variable to 6.
            4-Indicates that the changes in the container folder are to be
              submitted to the management module, verified and and saved to flash.
            6-Indicates that the changes in the container folder are to be
              discarded."
        ::= { cm10gConfigEntry 3 }

    cm10gConfigModuleName OBJECT-TYPE
        SYNTAX		DisplayString(SIZE(0..63))
        MAX-ACCESS	read-write
        STATUS		current
        DESCRIPTION
            "This object identifies a user configurable name for the media converter module
             present in the chassis. "
        ::= { cm10gConfigEntry 4 }

    cm10gConfigLinkMode OBJECT-TYPE
        SYNTAX		INTEGER {
            standard(0),
            smartLinkPassthrough(1)
        }
        MAX-ACCESS	read-write
        STATUS		current
        DESCRIPTION
            "This object identifies the Link Mode for the media converter module. This object
            is read-only if the media converter module's ConfigMode jumper is set to
            hardwareSwitches(0)."
        ::= { cm10gConfigEntry 5 }

    cm10gConfigFiberFaultAlert	OBJECT-TYPE
        SYNTAX		EnableDisableValue
        MAX-ACCESS	read-write
        STATUS		current
        DESCRIPTION
            "This object identifies the Fiber Fault Alert setting for the media
             module. This object is read-only if the media converter module's ConfigMode
             jumper is set to hardwareSwitches(0). "
        ::= { cm10gConfigEntry 6 }

    cm10gConfigFiberAutoNeg OBJECT-TYPE
        SYNTAX 		EnableDisableValue
        MAX-ACCESS	read-write
        STATUS 		current
        DESCRIPTION
            "This object identifies the wither fiber auto-negotiation  is
             enabled for both ports. This only applies if 1G SFP modules are in
             use. This object is read-only if the media module's ConfigMode 
             jumper is set to hardwareSwitches(0)."
        ::= { cm10gConfigEntry 7 }

    cm10gConfigPort1Name OBJECT-TYPE
        SYNTAX		DisplayString(SIZE(0..8))
        MAX-ACCESS	read-write
        STATUS 		current
        DESCRIPTION
            "This object identifies a user definable name for port 1."
        ::= { cm10gConfigEntry 8 }

    cm10gConfigPort1Enable OBJECT-TYPE
        SYNTAX		YesNoValue
        MAX-ACCESS	read-write
        STATUS 		current
        DESCRIPTION
            "This object identifies whether port 1 is enabled."
        ::= { cm10gConfigEntry 9 }

    cm10gConfigPort1EdcMode  OBJECT-TYPE
        SYNTAX		INTEGER {
            auto(0),
            alternate(1),
            linear(2),
            limiting(3),
            cx1(4)
        }
        MAX-ACCESS	read-write
        STATUS		current
        DESCRIPTION
            "This object identifies the EDC mode for this port. This config 
            option only applies for an SFP module. This object is read-only if the 
            media converter module's ConfigMode jumper is set to 
            hardwareSwitches(0)."
        ::= { cm10gConfigEntry 10 }

    cm10gConfigPort1FecEnable  OBJECT-TYPE
        SYNTAX 		YesNoValue
        MAX-ACCESS	read-write
        STATUS 		current
        DESCRIPTION
            "This object identifies the whether FEC control is enabled for this 
            port.  This config option only applies for an XFP module. This 
            object is read-only if the media module's ConfigMode jumper is set 
            to hardwareSwitches(0)."
        ::= { cm10gConfigEntry 11 }
    
    cm10gConfigPort1FecAmplitude OBJECT-TYPE
        SYNTAX      INTEGER(-128..127)
        MAX-ACCESS	read-write
        STATUS		current
        DESCRIPTION
            "This object identifies the FEC Amplitude value for this port. This 
            config option only applies for an XFP module. This object is 
            read-only if the media converter module's ConfigMode jumper is set to
            hardwareSwitches(0)."
        ::= { cm10gConfigEntry 12 }

    cm10gConfigPort1FecPhase OBJECT-TYPE
        SYNTAX      INTEGER(-128..127)
        MAX-ACCESS	read-write
        STATUS		current
        DESCRIPTION
            "This object identifies the FEC phase value for this port. This 
            config option only applies for an XFP module. This object is 
            read-only if the media converter module's ConfigMode jumper is set to
            hardwareSwitches(0)."
        ::= { cm10gConfigEntry 13 }

    cm10gConfigPort1WavelengthEnable OBJECT-TYPE
        SYNTAX 		YesNoValue
        MAX-ACCESS	read-write
        STATUS 		current
        DESCRIPTION
            "This object identifies whether Wavelength fine tuning is enabled for
            this port. This object is read-only if the media module's ConfigMode 
            jumper is set to hardwareSwitches(0)."
        ::= { cm10gConfigEntry 14 }
  
    cm10gConfigPort1WavelengthValue OBJECT-TYPE
        SYNTAX		INTEGER(0..65535)
        MAX-ACCESS	read-write
        STATUS		current
        DESCRIPTION
            "This object identifies Wavelength fine tuning value for this port.
            This object is read-only if the media converter module's ConfigMode 
            jumper is set to hardwareSwitches(0)."
        ::= { cm10gConfigEntry 15 }

    cm10gConfigPort1ChannelEnable  OBJECT-TYPE
        SYNTAX 		YesNoValue
        MAX-ACCESS	read-write
        STATUS 		current
        DESCRIPTION
            "This object identifies whether channel number fine tuning is enabled
            for this port. This config option only applies for an XFP module. 
            This object is read-only if the media module's ConfigMode jumper is 
            set to hardwareSwitches(0)."
        ::= { cm10gConfigEntry 16 }
     
    cm10gConfigPort1ChannelNumber OBJECT-TYPE
        SYNTAX		INTEGER(1..65535)
        MAX-ACCESS	read-write
        STATUS		current
        DESCRIPTION
            "This object identifies the channel number fine tuning value for this
            port. This object is read-only if the media converter module's 
            ConfigMode jumper is set to hardwareSwitches(0)."
        ::= { cm10gConfigEntry 17 }

    cm10gConfigPort1TxDitherEnable OBJECT-TYPE
        SYNTAX 		YesNoValue
        MAX-ACCESS	read-write
        STATUS 		current
        DESCRIPTION
            "This object identifies the whether TX Dither control is enabled on
            this port. If not enabled the default TX Dither value will be used.
            This object is read-only if the media module's ConfigMode jumper is 
            set to hardwareSwitches(0)."
        ::= { cm10gConfigEntry 18 }
    
    cm10gConfigPort1TxDitherValue OBJECT-TYPE
        SYNTAX 		EnableDisableValue
        MAX-ACCESS	read-write
        STATUS 		current
        DESCRIPTION
            "This object identifies the whether TX Dither is enabled for this 
             port. This object is read-only if the media module's ConfigMode 
             jumper is set to hardwareSwitches(0)."
        ::= { cm10gConfigEntry 19 }

     
    cm10gConfigPort2Name OBJECT-TYPE
        SYNTAX		DisplayString(SIZE(0..8))
        MAX-ACCESS	read-write
        STATUS 		current
        DESCRIPTION
            "This object identifies a user definable name for port 2."
        ::= { cm10gConfigEntry 20 }

    cm10gConfigPort2Enable OBJECT-TYPE
        SYNTAX		YesNoValue
        MAX-ACCESS	read-write
        STATUS 		current
        DESCRIPTION
            "This object identifies whether port 2 is enabled."
        ::= { cm10gConfigEntry 21 }

    cm10gConfigPort2EdcMode  OBJECT-TYPE
        SYNTAX		INTEGER {
            auto(0),
            alternate(1),
            linear(2),
            limiting(3),
            cx1(4)
        }
        MAX-ACCESS	read-write
        STATUS		current
        DESCRIPTION
            "This object identifies the EDC mode for this port. This config 
            option only applies for an SFP module. This object is read-only if the 
            media converter module's ConfigMode jumper is set to 
            hardwareSwitches(0)."
        ::= { cm10gConfigEntry 22 }

    cm10gConfigPort2FecEnable  OBJECT-TYPE
        SYNTAX 		YesNoValue
        MAX-ACCESS	read-write
        STATUS 		current
        DESCRIPTION
            "This object identifies the whether FEC control is enabled for this 
            port.  This config option only applies for an XFP module. This 
            object is read-only if the media module's ConfigMode jumper is set 
            to hardwareSwitches(0)."
        ::= { cm10gConfigEntry 23 }
    
    cm10gConfigPort2FecAmplitude OBJECT-TYPE
        SYNTAX      INTEGER(-128..127)
        MAX-ACCESS	read-write
        STATUS		current
        DESCRIPTION
            "This object identifies the FEC Amplitude value for this port. This 
            config option only applies for an XFP module. This object is 
            read-only if the media converter module's ConfigMode jumper is set to
            hardwareSwitches(0)."
        ::= { cm10gConfigEntry 24 }

    cm10gConfigPort2FecPhase OBJECT-TYPE
        SYNTAX      INTEGER(-128..127)
        MAX-ACCESS	read-write
        STATUS		current
        DESCRIPTION
            "This object identifies the FEC phase value for this port. This 
            config option only applies for an XFP module. This object is 
            read-only if the media converter module's ConfigMode jumper is set to
            hardwareSwitches(0)."
        ::= { cm10gConfigEntry 25 }

    cm10gConfigPort2WavelengthEnable OBJECT-TYPE
        SYNTAX 		YesNoValue
        MAX-ACCESS	read-write
        STATUS 		current
        DESCRIPTION
            "This object identifies whether Wavelength fine tuning is enabled for
            this port. This object is read-only if the media module's ConfigMode 
            jumper is set to hardwareSwitches(0)."
        ::= { cm10gConfigEntry 26 }
  
    cm10gConfigPort2WavelengthValue OBJECT-TYPE
        SYNTAX		INTEGER(0..65535)
        MAX-ACCESS	read-write
        STATUS		current
        DESCRIPTION
            "This object identifies Wavelength fine tuning value for this port.
            This object is read-only if the media converter module's ConfigMode 
            jumper is set to hardwareSwitches(0)."
        ::= { cm10gConfigEntry 27 }

    cm10gConfigPort2ChannelEnable  OBJECT-TYPE
        SYNTAX 		YesNoValue
        MAX-ACCESS	read-write
        STATUS 		current
        DESCRIPTION
            "This object identifies whether channel number fine tuning is enabled
            for this port. This object is read-only if the media module's 
            ConfigMode jumper is set to hardwareSwitches(0)."
        ::= { cm10gConfigEntry 28 }
     
    cm10gConfigPort2ChannelNumber OBJECT-TYPE
        SYNTAX		INTEGER(1..65535)
        MAX-ACCESS	read-write
        STATUS		current
        DESCRIPTION
            "This object identifies the channel number fine tuning value for this
            port. This object is read-only if the media converter module's 
            ConfigMode jumper is set to hardwareSwitches(0)."
        ::= { cm10gConfigEntry 29 }

    cm10gConfigPort2TxDitherEnable OBJECT-TYPE
        SYNTAX 		YesNoValue
        MAX-ACCESS	read-write
        STATUS 		current
        DESCRIPTION
            "This object identifies the whether TX Dither control is enabled on
            this port. If not enabled the default TX Dither value will be used.
            This object is read-only if the media module's ConfigMode jumper is 
            set to hardwareSwitches(0)."
        ::= { cm10gConfigEntry 30 }
    
    cm10gConfigPort2TxDitherValue OBJECT-TYPE
        SYNTAX 		EnableDisableValue
        MAX-ACCESS	read-write
        STATUS 		current
        DESCRIPTION
            "This object identifies the whether TX Dither is enabled for this 
             port. This object is read-only if the media module's ConfigMode 
             jumper is set to hardwareSwitches(0)."
        ::= { cm10gConfigEntry 31 }


--
-- cm10gConfigTable
--

--
-- cm10gLedTable
--
cm10gLedTable	OBJECT-TYPE
    SYNTAX		SEQUENCE OF Cm10gLedEntry
    MAX-ACCESS	not-accessible
    STATUS		current
    DESCRIPTION
        "Table of CM-10G type media converter module's LED status information."
    ::= { cm10gFixed 3 }

    cm10gLedEntry OBJECT-TYPE
        SYNTAX      Cm10gLedEntry
        MAX-ACCESS  not-accessible
        STATUS      current
        DESCRIPTION
            "Entries of the table, each relating to a separate CM-10G type
             media converter module."
        INDEX   { mcrChassisIndex, cm10gLedsSlotIndex }
        ::= { cm10gLedTable 1 }

    Cm10gLedEntry ::=
        SEQUENCE {
            cm10gLedsSlotIndex	SlotNumber,
            cm10gLedPWR			INTEGER,
            cm10gLedLK1			INTEGER,
            cm10gLedLK2			INTEGER
        }

    cm10gLedsSlotIndex	OBJECT-TYPE
        SYNTAX		SlotNumber
        MAX-ACCESS	not-accessible
        STATUS		current
        DESCRIPTION
            "The Slot number the CM-10G type module is currently inserted"
    ::= { cm10gLedEntry 2 }

    cm10gLedPWR	OBJECT-TYPE
        SYNTAX		INTEGER {
            off(0),
            onGreen(1),
            blinking(2)
        }
        MAX-ACCESS	read-only
        STATUS		current
        DESCRIPTION
            "This object identifies the status of the power (PWR) LED on the media converter module.
             Possible status values are:
                 off(0) - No power to the module
                 onGreen(1) - Power being applied to module
                 blinking(2) - Loopback or Link-Test enabled"
    ::= { cm10gLedEntry 3 }

    cm10gLedLK1	OBJECT-TYPE
        SYNTAX		INTEGER {
            off(0),
            on(1)
        }
        MAX-ACCESS	read-only
        STATUS		current
        DESCRIPTION
            "This object identifies the status of the port 1 link (LK1) LED on the
             media converter module.
             Possible status values are:
                 off(0) - No link
                 on(1) - Port link present"
    ::= { cm10gLedEntry 4 }

    cm10gLedLK2	OBJECT-TYPE
        SYNTAX		INTEGER {
            off(0),
            on(1)
        }
        MAX-ACCESS	read-only
        STATUS		current
        DESCRIPTION
            "This object identifies the status of the port 2 link (LK2) LED on the
             media converter module.
             Possible status values are:
                 off(0) - No link
                 on(1) - Port link present"
    ::= { cm10gLedEntry 5 }

--
-- end of cm10gLedTable
--

--
-- end of cm10gFixed

-- exCM - 10/100/100 Mb Rate Converting media Converter type modules
--
exCM	OBJECT IDENTIFIER ::= { mcrModuleTypes 9 }

--
-- exCMTable
--
exCMTable	OBJECT-TYPE
    SYNTAX		SEQUENCE OF ExCMEntry
    MAX-ACCESS	not-accessible
    STATUS		current
    DESCRIPTION
        "Table of CM-1110 type media converter module's configuration and status type
         information."
    ::= { exCM 1 }

    exCMEntry OBJECT-TYPE
        SYNTAX      ExCMEntry
        MAX-ACCESS  not-accessible
        STATUS      current
        DESCRIPTION
            "Entries of the table, each relating to a separate CM-1110 type
             media converter module."
        INDEX   { mcrChassisIndex, exCMSlotIndex}
        ::= { exCMTable 1 }

    ExCMEntry ::=
        SEQUENCE {
            exCMSlotIndex						SlotNumber,
            exCMModelName						DisplayString,
            exCMModelDesc						DisplayString,
            exCMHwJmp5ConfigMode				INTEGER,
            exCMHwSw1AutoLocalRemote		INTEGER,
            exCMHwSw2Rate					INTEGER,
            exCMHwSw3SymmetricAsymmetric			INTEGER,
            exCMHwSw4SnrRatio					INTEGER,
            exCMHwSw5Loopback					INTEGER,
            exCMHwSw6EthAutoNeg		INTEGER,
            exCMHwSw7EthSpeed					INTEGER,
            exCMHwSw8EthDuplex					INTEGER,
            exCMHwSw9LinkMode					INTEGER,
            exCMHwSw10InterlinkFaultFeedback	INTEGER,

            exCMVdslLinkStatus				INTEGER,
            exCMVdslConnType					INTEGER,
            exCMVdslLoopBack					EnableDisableValue,
            exCMVdslRole			INTEGER,
            exCMVdslProfile			INTEGER,
            exCMVdslBitswapping			INTEGER,

            exCMVdslStatusAttainableDataRateUp         Integer32,
            exCMVdslStatusAttainableDataRateDown       Integer32,
            
            exCMVdslStatusActualDataRateUp             Integer32,
            exCMVdslStatusActualDataRateDown           Integer32,
            
            exCMVdslStatusPrevDataRateUp               Integer32,
            exCMVdslStatusPrevDataRateDown             Integer32,
            
            exCMVdslStatusActualSnrUp                   Integer32,
            exCMVdslStatusActualSnrDown                 Integer32,
            exCMVdslStatusActualSnrUs0                  Integer32,
            exCMVdslStatusActualSnrUs1                  Integer32,
            exCMVdslStatusActualSnrDs1                  Integer32,
            exCMVdslStatusActualSnrUs2                  Integer32,
            exCMVdslStatusActualSnrDs2                  Integer32,
            exCMVdslStatusActualSnrUs3                  Integer32,
            exCMVdslStatusActualSnrDs3                  Integer32,
            exCMVdslStatusActualSnrUs4                  Integer32,
            exCMVdslStatusActualSnrDs4                  Integer32,
            
            exCMVdslStatusActualSignalAttenuationUp    Integer32,
            exCMVdslStatusActualSignalAttenuationDown  Integer32,
            exCMVdslStatusActualSignalAttenuationUs0   Integer32,
            exCMVdslStatusActualSignalAttenuationUs1   Integer32,
            exCMVdslStatusActualSignalAttenuationDs1   Integer32,
            exCMVdslStatusActualSignalAttenuationUs2   Integer32,
            exCMVdslStatusActualSignalAttenuationDs2   Integer32,
            exCMVdslStatusActualSignalAttenuationUs3   Integer32,
            exCMVdslStatusActualSignalAttenuationDs3   Integer32,
            exCMVdslStatusActualSignalAttenuationUs4   Integer32,
            exCMVdslStatusActualSignalAttenuationDs4   Integer32,
            
            exCMVdslStatusActualLineAttenuationUp      Integer32,
            exCMVdslStatusActualLineAttenuationDown    Integer32,
            exCMVdslStatusActualLineAttenuationUs0     Integer32,
            exCMVdslStatusActualLineAttenuationUs1     Integer32,
            exCMVdslStatusActualLineAttenuationDs1     Integer32,
            exCMVdslStatusActualLineAttenuationUs2     Integer32,
            exCMVdslStatusActualLineAttenuationDs2     Integer32,
            exCMVdslStatusActualLineAttenuationUs3     Integer32,
            exCMVdslStatusActualLineAttenuationDs3     Integer32,
            exCMVdslStatusActualLineAttenuationUs4     Integer32,
            exCMVdslStatusActualLineAttenuationDs4     Integer32,
            
            exCMVdslStatusActualInterleaveDelayUp      Integer32,
            exCMVdslStatusActualInterleaveDelayDown    Integer32,
            
            exCMVdslStatusActualInpUp                   Integer32,
            exCMVdslStatusActualInpDown                 Integer32,
            
            exCMVdslStatusActualInterleavingDepthUp    Integer32,
            exCMVdslStatusActualInterleavingDepthDown  Integer32,
            
            exCMVdslStatusActualInterleavingBlockUp    Integer32,
            exCMVdslStatusActualInterleavingBlockDown  Integer32,
            
            exCMVdslStatusActualTransmitPowerUp        Integer32,
            exCMVdslStatusActualTransmitPowerDown      Integer32,
            
            exCMVdslStatusMaxDataRateUp                Integer32,
            exCMVdslStatusMaxDataRateDown              Integer32,
            
            exCMVdslStatusMinDataRateUp                Integer32,
            exCMVdslStatusMinDataRateDown              Integer32,
            
            exCMVdslStatusTargetSnrUp                   Integer32,
            exCMVdslStatusTargetSnrDown                 Integer32,
            
            exCMVdslStatusMaxInterleaveDelayUp         Integer32,
            exCMVdslStatusMaxInterleaveDelayDown       Integer32,
            
            exCMVdslStatusMinInpUp                      Integer32,
            exCMVdslStatusMinInpDown                    Integer32,
            exCMVdslRemoteLoopback                        INTEGER,
            exCMVdslRemoteReset                           INTEGER,            
            
            exCMEthernetLinkStatus				INTEGER,
            exCMEthernetConnType					INTEGER,
            exCMEthernetAutoNegState			INTEGER,
            exCMEthernetSpeed						INTEGER,
            exCMEthernetDuplex					INTEGER,
            exCMEthernetCrossOver				INTEGER,
            exCMEthernetPauseEnh					INTEGER,
            exCMEthernetLPRFStatus				INTEGER,
            exCMEthernetAutoSpeedDownshift 	INTEGER,
            exCMEthernetMDI 	INTEGER,
            
            exCMVdslFirmwareVersion                   DisplayString,
            exCMVdslFirmwareDate                      DateAndTime,
            exCMVdslFirmwareDateString                DisplayString
        }

    exCMSlotIndex	OBJECT-TYPE
        SYNTAX		SlotNumber
        MAX-ACCESS	not-accessible
        STATUS		current
        DESCRIPTION
            "The Slot number the CM-1110 type module is currently inserted"
    ::= { exCMEntry 2 }

    exCMModelName	OBJECT-TYPE
        SYNTAX		DisplayString
        MAX-ACCESS	read-only
        STATUS		current
        DESCRIPTION
            "This object identifies the model of media converter module present in the
             chassis"
    ::= { exCMEntry 3 }

    exCMModelDesc		OBJECT-TYPE
        SYNTAX		DisplayString
        MAX-ACCESS	read-only
        STATUS		current
        DESCRIPTION
            "This object identifies a static description of the media converter module present
             in the chassis"
    ::= { exCMEntry 4 }

    exCMHwJmp5ConfigMode	OBJECT-TYPE
        SYNTAX		INTEGER {
            hardwareSwitches(0),
            auto(1)
        }
        MAX-ACCESS	read-only
        STATUS		current
        DESCRIPTION
            "This object identifies the media converter module's ConfigMode, set by hardware
             switch on the media converter module. When this object is set to hardwareSwitches(0), the
             media converter module will disable configuration control from the management
             module's software and all configuration control comes from the media
             module's hardware switches or jumpers. "
    ::= { exCMEntry 5 }

    exCMHwSw1AutoLocalRemote OBJECT-TYPE
        SYNTAX 		INTEGER {
            swDownRemote(0),
            swUpAutoLocal(1)
        }
        MAX-ACCESS read-only
        STATUS 		current
        DESCRIPTION
            "Media converter module's current switch setting for VDSL role."
    ::= { exCMEntry 6 }

    exCMHwSw2Rate OBJECT-TYPE
        SYNTAX 		INTEGER {
            swDownLongRange(0),
            swUpHighSpeed(1)
        }
        MAX-ACCESS read-only
        STATUS 		current
        DESCRIPTION
            "Media converter module's current switch setting for VDSL rate/reach."
    ::= { exCMEntry 7 }

    exCMHwSw3SymmetricAsymmetric OBJECT-TYPE
        SYNTAX 		INTEGER {
            swDownDisabled(0),
            swUpEnabled(1)
        }
        MAX-ACCESS read-only
        STATUS 		current
        DESCRIPTION
            "Media converter module's current switch setting for VDSL band plan."
    ::= { exCMEntry 8 }

    exCMHwSw4SnrRatio OBJECT-TYPE
        SYNTAX 		INTEGER {
            swDown6db(0),
            swUp9db(1)
        }
        MAX-ACCESS read-only
        STATUS 		current
        DESCRIPTION
            "Media converter module's current switch setting for VDSL signal-to-noise ratio."
    ::= { exCMEntry 9 }

    exCMHwSw5Loopback OBJECT-TYPE
        SYNTAX 		INTEGER {
            swDownDisabled(0),
            swUpEnabled(1)
        }
        MAX-ACCESS read-only
        STATUS 		current
        DESCRIPTION
            "Media converter module's current switch setting for VDSL loopback."
    ::= { exCMEntry 10 }

    exCMHwSw6EthAutoNeg OBJECT-TYPE
        SYNTAX 		INTEGER {
            swDownDisabled(0),
            swUpEnabled(1)
        }
        MAX-ACCESS read-only
        STATUS 		current
        DESCRIPTION
            "Media converter module's current switch setting for ethernet auto-negotiation."
    ::= { exCMEntry 11 }

    exCMHwSw7EthSpeed OBJECT-TYPE
        SYNTAX 		INTEGER {
            swDown10Mbps(0),
            swUp100Mbps(1)
        }
        MAX-ACCESS read-only
        STATUS 		current
        DESCRIPTION
            "Media converter module's current switch setting for ethernet speed (when auto-negotiation is disabled)."
    ::= { exCMEntry 12 }

    exCMHwSw8EthDuplex OBJECT-TYPE
        SYNTAX 		INTEGER {
            swDownHalf(0),
            swUpFull(1)
        }
        MAX-ACCESS read-only
        STATUS 		current
        DESCRIPTION
            "Media converter module's current switch setting for ethernet duplex (when auto-negotiation is disabled)."
    ::= { exCMEntry 13 }

    exCMHwSw9LinkMode OBJECT-TYPE
        SYNTAX 		INTEGER {
            swDownLinkPassthrough(0),
            swUpStandard(1)
        }
        MAX-ACCESS read-only
        STATUS 		current
        DESCRIPTION
            "Media converter module's current switch setting for link mode."
    ::= { exCMEntry 14 }

    exCMHwSw10InterlinkFaultFeedback OBJECT-TYPE
        SYNTAX 		INTEGER {
            swDownEnabled(0),
            swUpDisabled(1)
        }
        MAX-ACCESS read-only
        STATUS 		current
        DESCRIPTION
            "Media converter module's current switch setting for interlink fault feedback."
    ::= { exCMEntry 15 }

    exCMVdslLinkStatus OBJECT-TYPE
        SYNTAX 		INTEGER {
            idle(0),
            handshake(1),
            training(2),
            up(3),
            upLogicallyDown(4)
        }
        MAX-ACCESS read-only
        STATUS 		current
        DESCRIPTION
            "Media converter module's current VDSL link status."
    ::= { exCMEntry 16 }

    exCMVdslConnType OBJECT-TYPE
        SYNTAX 		INTEGER {
            rj45(9),
            terminalBlock(10),
            bnc(11)
        }
        MAX-ACCESS read-only
        STATUS 		current
        DESCRIPTION
            "Media converter module's VDSL port connector type."
    ::= { exCMEntry 17 }


   exCMVdslLoopBack		OBJECT-TYPE
        SYNTAX	EnableDisableValue
        MAX-ACCESS	read-write
        STATUS	current
        DESCRIPTION
            "
             This object is read-only if the media converter module's ConfigMode jumper is
             set to hardwareSwitches(0)."
    ::= { exCMEntry 18 }


    exCMVdslRole		OBJECT-TYPE
        SYNTAX	INTEGER {
            local(0),
            remote(1)
        }
        MAX-ACCESS	read-only
        STATUS	current
        DESCRIPTION
            "This object identifies the VDSL port's current role."
    ::= { exCMEntry 19 }

    exCMVdslProfile		OBJECT-TYPE
        SYNTAX	INTEGER {
            notApplicable(0),
            profile1-AnnexA-R-POTS-D-32-EU-32-30a(1),
            profile2-AnnexA-R-POTS-D-32-EU-32-17a(2),
            profile3-AnnexA-R-POTS-D-32-EU-32-12b(3),
            profile4-AnnexA-R-POTS-D-32-EU-32-12a(4),
            profile5-AnnexA-R-POTS-D-32-EU-32-8a(5),
            profile6-AnnexA-R-POTS-D-32-EU-32-8b(6),
            profile7-AnnexA-R-POTS-D-32-EU-32-8c(7),
            profile8-AnnexA-R-POTS-D-32-EU-32-8d(8),
            profile9-AnnexA-R-POTS-D-64-EU-64-30a-NUS0(9),
            profile10-AnnexA-R-POTS-D-64-EU-64-17a(10),
            profile11-AnnexB-B7-3-997-M1x-M(11),
            profile12-AnnexB-B7-4-997-M2x-M-8(12),
            profile13-AnnexB-B7-5-997-M2x-A(13),
            profile14-AnnexB-B7-6-997-M2x-M(14),
            profile15-AnnexB-B7-9-997E17-M2x-A(15),
            profile16-AnnexB-B7-10-997E30-M2x-NUS0(16),
            profile17-AnnexB-B8-1-998-M1x-A(17),
            profile18-AnnexB-B8-2-998-M1x-B(18),
            profile19-AnnexB-B8-4-998-M2x-A(19),
            profile20-AnnexB-B8-5-998-M2x-M(20),
            profile21-AnnexB-B8-6-998-M2x-B(21),
            profile22-AnnexB-B8-8-998E17-M2x-NUS0(22),
            profile23-AnnexB-B8-9-998E17-M2x-NUS0-M(23),
            profile24-AnnexB-B8-10-998ADE17-M2x-NUS0-M(24),
            profile25-AnnexB-B8-11-998E17-M2x-A(25),
            profile26-AnnexB-B8-12-998E17-M2x-B(26),
            profile27-AnnexB-B8-13-998E30-M2x-NUS0(27),
            profile28-AnnexB-B8-14-998E30-M2x-NUS0-M(28),
            profile29-AnnexB-B8-15-998ADE30-M2x-NUS0-M(29),
            profile30-AnnexB-B8-16-998ADE30-M2x-NUS0-A(30),
            profile31-AnnexC-POTS-25-138-b(31),
            profile32-AnnexC-POTS-25-276-b(32),
            profile33-AnnexC-TMC-ISDN(33)            
        }
        MAX-ACCESS	read-only
        STATUS	current
        DESCRIPTION
            "This object identifies the VDSL port's current profile.  This value has no meaning
             when the VDSL role is remote."
    ::= { exCMEntry 20 }

    exCMVdslBitswapping		OBJECT-TYPE
        SYNTAX	INTEGER {
            notApplicable(-1),
            off(0),
            on(1)
        }
        MAX-ACCESS	read-only
        STATUS	current
        DESCRIPTION
            "This object identifies the VDSL port's current bitswapping status. This value has no meaning
             when the VDSL role is remote."
    ::= { exCMEntry 21 }

    exCMVdslStatusAttainableDataRateUp		OBJECT-TYPE
        SYNTAX  Integer32
        MAX-ACCESS	read-only
        STATUS	current
        DESCRIPTION
            "This object identifies the VDSL port's attainable data rate (upstream) in kbps."
    ::= { exCMEntry 22 }

    exCMVdslStatusAttainableDataRateDown		OBJECT-TYPE
        SYNTAX  Integer32
        MAX-ACCESS	read-only
        STATUS	current
        DESCRIPTION
            "This object identifies the VDSL port's attainable data rate (downstream) in kbps."
    ::= { exCMEntry 23 }

    exCMVdslStatusActualDataRateUp		OBJECT-TYPE
        SYNTAX  Integer32
        MAX-ACCESS	read-only
        STATUS	current
        DESCRIPTION
            "This object identifies the VDSL port's actual data rate (upstream) in kbps."
    ::= { exCMEntry 24 }

    exCMVdslStatusActualDataRateDown		OBJECT-TYPE
        SYNTAX  Integer32
        MAX-ACCESS	read-only
        STATUS	current
        DESCRIPTION
            "This object identifies the VDSL port's actual data rate (downstream) in kbps."
    ::= { exCMEntry 25 }

    exCMVdslStatusPrevDataRateUp		OBJECT-TYPE
        SYNTAX  Integer32
        MAX-ACCESS	read-only
        STATUS	current
        DESCRIPTION
            "This object identifies the VDSL port's previous data rate (upstream) in kbps."
    ::= { exCMEntry 26 }

    exCMVdslStatusPrevDataRateDown		OBJECT-TYPE
        SYNTAX  Integer32
        MAX-ACCESS	read-only
        STATUS	current
        DESCRIPTION
            "This object identifies the VDSL port's previous data rate (downstream) in kbps."
    ::= { exCMEntry 27 }

    exCMVdslStatusActualSnrUp		OBJECT-TYPE
        SYNTAX  Integer32
        MAX-ACCESS	read-only
        STATUS	current
        DESCRIPTION
            "This object identifies the VDSL port's actual signal-to-noise ratio (upstream) in 0.1 dB."
    ::= { exCMEntry 28 }

    exCMVdslStatusActualSnrDown		OBJECT-TYPE
        SYNTAX  Integer32
        MAX-ACCESS	read-only
        STATUS	current
        DESCRIPTION
            "This object identifies the VDSL port's actual signal-to-noise ratio (downstream) in 0.1 dB."
    ::= { exCMEntry 29 }

    exCMVdslStatusActualSnrUs0		OBJECT-TYPE
        SYNTAX  Integer32
        MAX-ACCESS	read-only
        STATUS	current
        DESCRIPTION
            "This object identifies the VDSL port's actual signal-to-noise ratio (upstream 0) in 0.1 dB."
    ::= { exCMEntry 30 }

    exCMVdslStatusActualSnrUs1		OBJECT-TYPE
        SYNTAX  Integer32
        MAX-ACCESS	read-only
        STATUS	current
        DESCRIPTION
            "This object identifies the VDSL port's actual signal-to-noise ratio (upstream 1) in 0.1 dB."
    ::= { exCMEntry 31 }

    exCMVdslStatusActualSnrDs1		OBJECT-TYPE
        SYNTAX  Integer32
        MAX-ACCESS	read-only
        STATUS	current
        DESCRIPTION
            "This object identifies the VDSL port's actual signal-to-noise ratio (downstream 1) in 0.1 dB."
    ::= { exCMEntry 32 }

    exCMVdslStatusActualSnrUs2		OBJECT-TYPE
        SYNTAX  Integer32
        MAX-ACCESS	read-only
        STATUS	current
        DESCRIPTION
            "This object identifies the VDSL port's actual signal-to-noise ratio (upstream 2) in 0.2 dB."
    ::= { exCMEntry 33 }

    exCMVdslStatusActualSnrDs2		OBJECT-TYPE
        SYNTAX  Integer32
        MAX-ACCESS	read-only
        STATUS	current
        DESCRIPTION
            "This object identifies the VDSL port's actual signal-to-noise ratio (downstream 2) in 0.2 dB."
    ::= { exCMEntry 34 }

    exCMVdslStatusActualSnrUs3		OBJECT-TYPE
        SYNTAX  Integer32
        MAX-ACCESS	read-only
        STATUS	current
        DESCRIPTION
            "This object identifies the VDSL port's actual signal-to-noise ratio (upstream 3) in 0.3 dB."
    ::= { exCMEntry 35 }

    exCMVdslStatusActualSnrDs3		OBJECT-TYPE
        SYNTAX  Integer32
        MAX-ACCESS	read-only
        STATUS	current
        DESCRIPTION
            "This object identifies the VDSL port's actual signal-to-noise ratio (downstream 3) in 0.3 dB."
    ::= { exCMEntry 36 }

    exCMVdslStatusActualSnrUs4		OBJECT-TYPE
        SYNTAX  Integer32
        MAX-ACCESS	read-only
        STATUS	current
        DESCRIPTION
            "This object identifies the VDSL port's actual signal-to-noise ratio (upstream 4) in 0.4 dB."
    ::= { exCMEntry 37 }

    exCMVdslStatusActualSnrDs4		OBJECT-TYPE
        SYNTAX  Integer32
        MAX-ACCESS	read-only
        STATUS	current
        DESCRIPTION
            "This object identifies the VDSL port's actual signal-to-noise ratio (downstream 4) in 0.4 dB."
    ::= { exCMEntry 38 }

   exCMVdslStatusActualSignalAttenuationUp		OBJECT-TYPE
        SYNTAX  Integer32
        MAX-ACCESS	read-only
        STATUS	current
        DESCRIPTION
            "This object identifies the VDSL port's actual signal attenuation (upstream) in 0.1 dB."
    ::= { exCMEntry 39 }

    exCMVdslStatusActualSignalAttenuationDown		OBJECT-TYPE
        SYNTAX  Integer32
        MAX-ACCESS	read-only
        STATUS	current
        DESCRIPTION
            "This object identifies the VDSL port's actual signal attenuation (downstream) in 0.1 dB."
    ::= { exCMEntry 40 }

    exCMVdslStatusActualSignalAttenuationUs0		OBJECT-TYPE
        SYNTAX  Integer32
        MAX-ACCESS	read-only
        STATUS	current
        DESCRIPTION
            "This object identifies the VDSL port's actual signal attenuation (upstream 0) in 0.1 dB."
    ::= { exCMEntry 41 }

    exCMVdslStatusActualSignalAttenuationUs1		OBJECT-TYPE
        SYNTAX  Integer32
        MAX-ACCESS	read-only
        STATUS	current
        DESCRIPTION
            "This object identifies the VDSL port's actual signal attenuation (upstream 1) in 0.1 dB."
    ::= { exCMEntry 42 }

    exCMVdslStatusActualSignalAttenuationDs1		OBJECT-TYPE
        SYNTAX  Integer32
        MAX-ACCESS	read-only
        STATUS	current
        DESCRIPTION
            "This object identifies the VDSL port's actual signal attenuation (downstream 1) in 0.1 dB."
    ::= { exCMEntry 43 }

    exCMVdslStatusActualSignalAttenuationUs2		OBJECT-TYPE
        SYNTAX  Integer32
        MAX-ACCESS	read-only
        STATUS	current
        DESCRIPTION
            "This object identifies the VDSL port's actual signal attenuation (upstream 2) in 0.2 dB."
    ::= { exCMEntry 44 }

    exCMVdslStatusActualSignalAttenuationDs2		OBJECT-TYPE
        SYNTAX  Integer32
        MAX-ACCESS	read-only
        STATUS	current
        DESCRIPTION
            "This object identifies the VDSL port's actual signal attenuation (downstream 2) in 0.2 dB."
    ::= { exCMEntry 45 }

    exCMVdslStatusActualSignalAttenuationUs3		OBJECT-TYPE
        SYNTAX  Integer32
        MAX-ACCESS	read-only
        STATUS	current
        DESCRIPTION
            "This object identifies the VDSL port's actual signal attenuation (upstream 3) in 0.3 dB."
    ::= { exCMEntry 46 }

    exCMVdslStatusActualSignalAttenuationDs3		OBJECT-TYPE
        SYNTAX  Integer32
        MAX-ACCESS	read-only
        STATUS	current
        DESCRIPTION
            "This object identifies the VDSL port's actual signal attenuation (downstream 3) in 0.3 dB."
    ::= { exCMEntry 47 }

    exCMVdslStatusActualSignalAttenuationUs4		OBJECT-TYPE
        SYNTAX  Integer32
        MAX-ACCESS	read-only
        STATUS	current
        DESCRIPTION
            "This object identifies the VDSL port's actual signal attenuation (upstream 4) in 0.4 dB."
    ::= { exCMEntry 48 }

    exCMVdslStatusActualSignalAttenuationDs4		OBJECT-TYPE
        SYNTAX  Integer32
        MAX-ACCESS	read-only
        STATUS	current
        DESCRIPTION
            "This object identifies the VDSL port's actual signal attenuation (downstream 4) in 0.4 dB."
    ::= { exCMEntry 49 }

   exCMVdslStatusActualLineAttenuationUp		OBJECT-TYPE
        SYNTAX  Integer32
        MAX-ACCESS	read-only
        STATUS	current
        DESCRIPTION
            "This object identifies the VDSL port's actual line attenuation (upstream) in 0.1 dB."
    ::= { exCMEntry 50 }

    exCMVdslStatusActualLineAttenuationDown		OBJECT-TYPE
        SYNTAX  Integer32
        MAX-ACCESS	read-only
        STATUS	current
        DESCRIPTION
            "This object identifies the VDSL port's actual line attenuation (downstream) in 0.1 dB."
    ::= { exCMEntry 51 }

    exCMVdslStatusActualLineAttenuationUs0		OBJECT-TYPE
        SYNTAX  Integer32
        MAX-ACCESS	read-only
        STATUS	current
        DESCRIPTION
            "This object identifies the VDSL port's actual line attenuation (upstream 0) in 0.1 dB."
    ::= { exCMEntry 52 }

    exCMVdslStatusActualLineAttenuationUs1		OBJECT-TYPE
        SYNTAX  Integer32
        MAX-ACCESS	read-only
        STATUS	current
        DESCRIPTION
            "This object identifies the VDSL port's actual line attenuation (upstream 1) in 0.1 dB."
    ::= { exCMEntry 53 }

    exCMVdslStatusActualLineAttenuationDs1		OBJECT-TYPE
        SYNTAX  Integer32
        MAX-ACCESS	read-only
        STATUS	current
        DESCRIPTION
            "This object identifies the VDSL port's actual line attenuation (downstream 1) in 0.1 dB."
    ::= { exCMEntry 54 }

    exCMVdslStatusActualLineAttenuationUs2		OBJECT-TYPE
        SYNTAX  Integer32
        MAX-ACCESS	read-only
        STATUS	current
        DESCRIPTION
            "This object identifies the VDSL port's actual line attenuation (upstream 2) in 0.2 dB."
    ::= { exCMEntry 55 }

    exCMVdslStatusActualLineAttenuationDs2		OBJECT-TYPE
        SYNTAX  Integer32
        MAX-ACCESS	read-only
        STATUS	current
        DESCRIPTION
            "This object identifies the VDSL port's actual line attenuation (downstream 2) in 0.2 dB."
    ::= { exCMEntry 56 }

    exCMVdslStatusActualLineAttenuationUs3		OBJECT-TYPE
        SYNTAX  Integer32
        MAX-ACCESS	read-only
        STATUS	current
        DESCRIPTION
            "This object identifies the VDSL port's actual line attenuation (upstream 3) in 0.3 dB."
    ::= { exCMEntry 57 }

    exCMVdslStatusActualLineAttenuationDs3		OBJECT-TYPE
        SYNTAX  Integer32
        MAX-ACCESS	read-only
        STATUS	current
        DESCRIPTION
            "This object identifies the VDSL port's actual line attenuation (downstream 3) in 0.3 dB."
    ::= { exCMEntry 58 }

    exCMVdslStatusActualLineAttenuationUs4		OBJECT-TYPE
        SYNTAX  Integer32
        MAX-ACCESS	read-only
        STATUS	current
        DESCRIPTION
            "This object identifies the VDSL port's actual line attenuation (upstream 4) in 0.4 dB."
    ::= { exCMEntry 59 }

    exCMVdslStatusActualLineAttenuationDs4		OBJECT-TYPE
        SYNTAX  Integer32
        MAX-ACCESS	read-only
        STATUS	current
        DESCRIPTION
            "This object identifies the VDSL port's actual line attenuation (downstream 4) in 0.4 dB."
    ::= { exCMEntry 60 }

    exCMVdslStatusActualInterleaveDelayUp		OBJECT-TYPE
        SYNTAX  Integer32
        MAX-ACCESS	read-only
        STATUS	current
        DESCRIPTION
            "This object identifies the VDSL port's actual interleave delay (upstream) in ms."
    ::= { exCMEntry 61 }

    exCMVdslStatusActualInterleaveDelayDown		OBJECT-TYPE
        SYNTAX  Integer32
        MAX-ACCESS	read-only
        STATUS	current
        DESCRIPTION
            "This object identifies the VDSL port's actual interleave delay (downstream) in ms."
    ::= { exCMEntry 62 }

    exCMVdslStatusActualInpUp		OBJECT-TYPE
        SYNTAX  Integer32
        MAX-ACCESS	read-only
        STATUS	current
        DESCRIPTION
            "This object identifies the VDSL port's actual INP (impulse noise protection) (upstream)."
    ::= { exCMEntry 63 }

    exCMVdslStatusActualInpDown		OBJECT-TYPE
        SYNTAX  Integer32
        MAX-ACCESS	read-only
        STATUS	current
        DESCRIPTION
            "This object identifies the VDSL port's actual INP (impulse noise protection) (downstream) in ms."
    ::= { exCMEntry 64 }

   exCMVdslStatusActualInterleavingDepthUp		OBJECT-TYPE
        SYNTAX  Integer32
        MAX-ACCESS	read-only
        STATUS	current
        DESCRIPTION
            "This object identifies the VDSL port's actual interleaving depth (upstream)."
    ::= { exCMEntry 65 }

    exCMVdslStatusActualInterleavingDepthDown		OBJECT-TYPE
        SYNTAX  Integer32
        MAX-ACCESS	read-only
        STATUS	current
        DESCRIPTION
            "This object identifies the VDSL port's actual interleaving depth (impulse noise protection) (downstream) in ms."
    ::= { exCMEntry 66 }

   exCMVdslStatusActualInterleavingBlockUp		OBJECT-TYPE
        SYNTAX  Integer32
        MAX-ACCESS	read-only
        STATUS	current
        DESCRIPTION
            "This object identifies the VDSL port's actual interleaving block (upstream)."
    ::= { exCMEntry 67 }

    exCMVdslStatusActualInterleavingBlockDown		OBJECT-TYPE
        SYNTAX  Integer32
        MAX-ACCESS	read-only
        STATUS	current
        DESCRIPTION
            "This object identifies the VDSL port's actual interleaving block (impulse noise protection) (downstream) in ms."
    ::= { exCMEntry 68 }

   exCMVdslStatusActualTransmitPowerUp		OBJECT-TYPE
        SYNTAX  Integer32
        MAX-ACCESS	read-only
        STATUS	current
        DESCRIPTION
            "This object identifies the VDSL port's actual transmit power (upstream) in 0.1 dBm."
    ::= { exCMEntry 69 }

    exCMVdslStatusActualTransmitPowerDown		OBJECT-TYPE
        SYNTAX  Integer32
        MAX-ACCESS	read-only
        STATUS	current
        DESCRIPTION
            "This object identifies the VDSL port's actual transmit power (downstream) in 0.1 dBm."
    ::= { exCMEntry 70 }

    exCMVdslStatusMaxDataRateUp		OBJECT-TYPE
        SYNTAX  Integer32
        MAX-ACCESS	read-only
        STATUS	current
        DESCRIPTION
            "This object identifies the VDSL port's maximum data rate (upstream) in kbps."
    ::= { exCMEntry 71 }

    exCMVdslStatusMaxDataRateDown		OBJECT-TYPE
        SYNTAX  Integer32
        MAX-ACCESS	read-only
        STATUS	current
        DESCRIPTION
            "This object identifies the VDSL port's maximum data rate (downstream) in kbps."
    ::= { exCMEntry 72 }

    exCMVdslStatusMinDataRateUp		OBJECT-TYPE
        SYNTAX  Integer32
        MAX-ACCESS	read-only
        STATUS	current
        DESCRIPTION
            "This object identifies the VDSL port's minimum data rate (upstream) in kbps."
    ::= { exCMEntry 73 }

    exCMVdslStatusMinDataRateDown		OBJECT-TYPE
        SYNTAX  Integer32
        MAX-ACCESS	read-only
        STATUS	current
        DESCRIPTION
            "This object identifies the VDSL port's minimum data rate (downstream) in kbps."
    ::= { exCMEntry 74 }

    exCMVdslStatusTargetSnrUp		OBJECT-TYPE
        SYNTAX  Integer32
        MAX-ACCESS	read-only
        STATUS	current
        DESCRIPTION
            "This object identifies the VDSL port's target signal-to-noise ratio (upstream) in 0.1 dB."
    ::= { exCMEntry 75 }

    exCMVdslStatusTargetSnrDown		OBJECT-TYPE
        SYNTAX  Integer32
        MAX-ACCESS	read-only
        STATUS	current
        DESCRIPTION
            "This object identifies the VDSL port's target signal-to-noise ratio (downstream) in 0.1 dB."
    ::= { exCMEntry 76 }

    exCMVdslStatusMaxInterleaveDelayUp		OBJECT-TYPE
        SYNTAX  Integer32
        MAX-ACCESS	read-only
        STATUS	current
        DESCRIPTION
            "This object identifies the VDSL port's maximum interleave delay (upstream) in ms."
    ::= { exCMEntry 77 }

    exCMVdslStatusMaxInterleaveDelayDown		OBJECT-TYPE
        SYNTAX  Integer32
        MAX-ACCESS	read-only
        STATUS	current
        DESCRIPTION
            "This object identifies the VDSL port's maximum interleave delay (downstream) in ms."
    ::= { exCMEntry 78 }

    exCMVdslStatusMinInpUp		OBJECT-TYPE
        SYNTAX  Integer32
        MAX-ACCESS	read-only
        STATUS	current
        DESCRIPTION
            "This object identifies the VDSL port's minimum INP (impulse noise protection) (upstream)."
    ::= { exCMEntry 79 }

    exCMVdslStatusMinInpDown		OBJECT-TYPE
        SYNTAX  Integer32
        MAX-ACCESS	read-only
        STATUS	current
        DESCRIPTION
            "This object identifies the VDSL port's minimum INP (impulse noise protection) (downstream) in ms."
    ::= { exCMEntry 80 }


    exCMVdslRemoteLoopback		OBJECT-TYPE
        SYNTAX	INTEGER {
            none(0),
            remoteLoopbackOff(1),
            remoteLoopbackOn(2)
        }
        MAX-ACCESS	read-write
        STATUS	current
        DESCRIPTION
            "Write remoteLoopbackOff(1) or remoteLoopbackOn(2) to this object to
             set the loopback state of the remote VDSL peer.  This object's value represents
             the last loopback command sent to the peer."
    ::= { exCMEntry 81 }

    exCMVdslRemoteReset		OBJECT-TYPE
        SYNTAX	INTEGER {
            notApplicable(0),
            resetRemotePeer(1)
        }
        MAX-ACCESS	read-write
        STATUS	current
        DESCRIPTION
            "Write resetRemotePeer(1) to this object to reset the remote VDSL peer.  This object's value has no meaning"
    ::= { exCMEntry 82 }

    exCMEthernetLinkStatus OBJECT-TYPE
        SYNTAX	INTEGER {
            down(0),
            up(1)
        }
        MAX-ACCESS	read-only
        STATUS	current
        DESCRIPTION
            "Media converter module's current Ethernet link status."
    ::= { exCMEntry 83 }

    exCMEthernetConnType OBJECT-TYPE
        SYNTAX INTEGER {
            rj45(0)
        }
        MAX-ACCESS read-only
        STATUS current
        DESCRIPTION
            "Media converter module's Ethernet connector type."
    ::= { exCMEntry 84 }

    exCMEthernetAutoNegState OBJECT-TYPE
        SYNTAX INTEGER {
            disabled(0),
            complete(1),
            inProgress(2)
        }
        MAX-ACCESS read-only
        STATUS current
        DESCRIPTION
            "Media converter module's current Ethernet auto-negotiation state."
    ::= { exCMEntry 85 }

        exCMEthernetSpeed OBJECT-TYPE
        SYNTAX 		INTEGER {
            speed10Mbs(0),
            speed100Mbps(1),
            speed1000Mbps(2)
        }
        MAX-ACCESS	read-only
        STATUS 		current
        DESCRIPTION
            "If Ethernet auto-negotiation state is complete then this object
            indicates the media converter module's current Ethernet auto-negotiated speed
            setting. If auto-negotiation is not complete then the value returned
            should be ignored."
    ::= { exCMEntry 86 }

    exCMEthernetDuplex OBJECT-TYPE
        SYNTAX INTEGER {
            half(0),
            full(1)
        }
        MAX-ACCESS read-only
        STATUS current
        DESCRIPTION
            "If Ethernet auto-negotiation state is complete then this object
            indicates the media converter module's current Ethernet auto-negotiated duplex
            setting. If auto-negotiation is not complete then the value returned
            should be ignored."
    ::= { exCMEntry 87 }

    exCMEthernetCrossOver OBJECT-TYPE
        SYNTAX INTEGER {
            mdi(0),
            mdix(1)
        }
        MAX-ACCESS read-only
        STATUS current
        DESCRIPTION
            "If Ethernet auto-negotiation state is complete then this object
            indicates the media converter module's current Ethernet auto-negotiated MDI/MDI-X
            setting. If auto-negotiation is not complete then the value returned
            should be ignored."
    ::= { exCMEntry 88 }

    exCMEthernetPauseEnh OBJECT-TYPE
        SYNTAX INTEGER {
            disabled(0),
            symmetrical(1),
            asymmetricalTx(2),
            asymmetricalRx(3)
        }
        MAX-ACCESS read-only
        STATUS current
        DESCRIPTION
            "If Ethernet auto-negotiation state is complete then this object indicates
             the media converter module's current Ethernet auto-negotiated pause setting. If
             auto-negotiation is not complete then the value returned should be ignored."
    ::= { exCMEntry 89 }

    exCMEthernetLPRFStatus OBJECT-TYPE
        SYNTAX INTEGER {
            ok(0),
            remoteFault(1)
        }
        MAX-ACCESS read-only
        STATUS current
        DESCRIPTION
            "Media converter module's Ethernet Link Partner Remote Fault status."
    ::= { exCMEntry 90 }

    exCMEthernetAutoSpeedDownshift OBJECT-TYPE
        SYNTAX INTEGER {
            noDownshift(0),
            downshift(1)
        }
        MAX-ACCESS read-only
        STATUS current
        DESCRIPTION
            "This object identifies the status of the Ethernet auto speed downshift
             feature. noDownshift indicates that an automatic downshift of the
             Ethernet speed has not occurred."
    ::= { exCMEntry 91 }


    exCMEthernetMDI OBJECT-TYPE
        SYNTAX INTEGER {
            mdi(0),
            mdix(1)
        }
        MAX-ACCESS read-only
        STATUS current
        DESCRIPTION
            "This object identifies the Ethernet port's crossover status: MDI or MDI-X."
    ::= { exCMEntry 92 }


    exCMVdslFirmwareVersion	OBJECT-TYPE
        SYNTAX      DisplayString
        MAX-ACCESS  read-only
        STATUS      current
        DESCRIPTION
            "This object identifies the version of the VDSL firmware."
    ::= { exCMEntry 93 }


    exCMVdslFirmwareDate	OBJECT-TYPE
        SYNTAX      DateAndTime
        MAX-ACCESS  read-only
        STATUS      current
        DESCRIPTION
            "This object identifies the date of the VDSL firmware"
    ::= { exCMEntry 94 }


    exCMVdslFirmwareDateString	OBJECT-TYPE
        SYNTAX      DisplayString
        MAX-ACCESS  read-only
        STATUS      current
        DESCRIPTION
            "This object identifies the version of the VDSL firmware, in human-readable format."
    ::= { exCMEntry 95 }

--
-- /exCMTable
--

--
-- exCMConfigTable
--
exCMConfigTable	OBJECT-TYPE
    SYNTAX		SEQUENCE OF ExCMConfigEntry
    MAX-ACCESS	not-accessible
    STATUS		current
    DESCRIPTION
        "Table of CM-1110 type media converter module's configuration type
         information."
    ::= { exCM 2 }

    exCMConfigEntry OBJECT-TYPE
        SYNTAX      ExCMConfigEntry
        MAX-ACCESS  not-accessible
        STATUS      current
        DESCRIPTION
            "Entries of the table, each relating to a separate CM-1110 type
             media converter module."
        INDEX   { mcrChassisIndex, exCMConfigSlotIndex}
        ::= { exCMConfigTable 1 }

    ExCMConfigEntry ::=
        SEQUENCE {
            exCMConfigSlotIndex						SlotNumber,
            exCMConfigStatus							ContainerStatus,

            exCMConfigModuleName						DisplayString,
            exCMConfigLinkMode							INTEGER,
            exCMConfigInterlinkFaultFeedback				EnableDisableValue,
            
            exCMConfigVdslPortName					DisplayString,
            exCMConfigVdslPortEnable				YesNoValue,

            exCMConfigVdslProfileMode               INTEGER,
            exCMConfigVdslRole                      INTEGER,
            exCMConfigVdslRate                      INTEGER,
            exCMConfigVdslSymmetry                  INTEGER,
        
            exCMConfigVdslProfile                   INTEGER,
            exCMConfigVdslOverrideProfile           EnableDisableValue,
            
            exCMConfigVdslSignalToNoiseRatioUp      Integer32,
            exCMConfigVdslMinDataRateUp             Integer32,
            exCMConfigVdslMaxDataRateUp             Integer32,
            exCMConfigVdslMaxInterleaveDelayUp                Integer32,
            exCMConfigVdslMinInpUp                  Integer32,
            
            exCMConfigVdslSignalToNoiseRatioDown    Integer32,
            exCMConfigVdslMinDataRateDown           Integer32,
            exCMConfigVdslMaxDataRateDown           Integer32,
            exCMConfigVdslMaxInterleaveDelayDown              Integer32,
            exCMConfigVdslMinInpDown                Integer32,
            
            exCMConfigVdslBitswapping               EnableDisableValue,
            
            exCMConfigVdslLowBandwidthAlarmUp      Integer32,            
            exCMConfigVdslLowBandwidthAlarmDown    Integer32,            

            exCMConfigEthernetPortName					DisplayString,
            exCMConfigEthernetPortEnable				YesNoValue,
            exCMConfigEthernetAutoNegotiation		EnableDisableValue,
            exCMConfigEthernetAutoNegAdv10HDX		YesNoValue,
            exCMConfigEthernetAutoNegAdv10FDX		YesNoValue,
            exCMConfigEthernetAutoNegAdv100HDX		YesNoValue,
            exCMConfigEthernetAutoNegAdv100FDX		YesNoValue,
            exCMConfigEthernetAutoNegAdv1000FDX		YesNoValue,
            exCMConfigEthernetSpeed						INTEGER,
            exCMConfigEthernetDuplex					INTEGER,
            exCMConfigEthernetCrossOver				INTEGER,
            exCMConfigEthernetPauseEnh					INTEGER,
            exCMConfigEthernetAutoSpeedDownshift	INTEGER,
            exCMConfigEthernet10BaseTDistance		INTEGER,

            exCMConfigUnidirectionalEthernet	INTEGER,
            exCMConfigPriorityToEgressQueueMap0	INTEGER,
            exCMConfigPriorityToEgressQueueMap1	INTEGER,
            exCMConfigPriorityToEgressQueueMap2	INTEGER,
            exCMConfigPriorityToEgressQueueMap3	INTEGER,
            exCMConfigPriorityToEgressQueueMap4	INTEGER,
            exCMConfigPriorityToEgressQueueMap5	INTEGER,
            exCMConfigPriorityToEgressQueueMap6	INTEGER,
            exCMConfigPriorityToEgressQueueMap7	INTEGER,

            exCMConfigEthernet8021pPriority			OnOffValue,
            exCMConfigEthernetIpTosPriority			OnOffValue,
            exCMConfigEthernetPriorityPrecedence	INTEGER,
            exCMConfigEthernetCongestionPolicy		INTEGER,

            exCMConfigEthernetPriorityMap0			INTEGER,
            exCMConfigEthernetPriorityMap1			INTEGER,
            exCMConfigEthernetPriorityMap2			INTEGER,
            exCMConfigEthernetPriorityMap3			INTEGER,
            exCMConfigEthernetPriorityMap4			INTEGER,
            exCMConfigEthernetPriorityMap5			INTEGER,
            exCMConfigEthernetPriorityMap6			INTEGER,
            exCMConfigEthernetPriorityMap7			INTEGER,

            exCMConfigEthernetIngressLimit			INTEGER,
            exCMConfigEthernetEgressLimit			INTEGER,
            exCMConfigEthernetDiscardTaggedFrames	OnOffValue,
            exCMConfigEthernetDiscardUntaggedFrames	OnOffValue,
            exCMConfigEthernetDefaultVlanId			INTEGER,
            exCMConfigEthernetDefaultPriority		INTEGER,
            exCMConfigEthernetVlanTaggingAction		INTEGER,
            exCMConfigEthernetFilterUnknownMulticast		OnOffValue,
            exCMConfigEthernetFilterUnknownUnicast		OnOffValue,

            exCMConfigVdsl8021pPriority			OnOffValue,
            exCMConfigVdslIpTosPriority			OnOffValue,
            exCMConfigVdslPriorityPrecedence	INTEGER,
            exCMConfigVdslCongestionPolicy		INTEGER,

            exCMConfigVdslPriorityMap0			INTEGER,
            exCMConfigVdslPriorityMap1			INTEGER,
            exCMConfigVdslPriorityMap2			INTEGER,
            exCMConfigVdslPriorityMap3			INTEGER,
            exCMConfigVdslPriorityMap4			INTEGER,
            exCMConfigVdslPriorityMap5			INTEGER,
            exCMConfigVdslPriorityMap6			INTEGER,
            exCMConfigVdslPriorityMap7			INTEGER,
                                         
            exCMConfigVdslIngressLimit			INTEGER,
            exCMConfigVdslEgressLimit			INTEGER,
            exCMConfigVdslDiscardTaggedFrames	OnOffValue,
            exCMConfigVdslDiscardUntaggedFrames	OnOffValue,
            exCMConfigVdslDefaultVlanId			INTEGER,
            exCMConfigVdslDefaultPriority		INTEGER,
            exCMConfigVdslVlanTaggingAction		INTEGER,
            exCMConfigVdslFilterUnknownMulticast		OnOffValue,
            exCMConfigVdslFilterUnknownUnicast		OnOffValue,
            
            exCMConfigVdslFastMode               EnableDisableValue
        }

    exCMConfigSlotIndex	OBJECT-TYPE
        SYNTAX		SlotNumber
        MAX-ACCESS	not-accessible
        STATUS		current
        DESCRIPTION
            "The Slot number the ex-CM type module is currently inserted"
    ::= { exCMConfigEntry 2 }

    exCMConfigStatus OBJECT-TYPE
        SYNTAX      ContainerStatus
        MAX-ACCESS  read-write
        STATUS      current
        DESCRIPTION
          "When you perform a GET on this variable, one of
            the following values will be returned:
            1-Indicates that the container folder is active with no changes.
            2-Indicates that the container folder is active with change(s).
            Once you have completed setting the variables in a folder, you
            will want to submit your changes to the management module. To do
            this, set the Status variable to 4. If you want to discard the
            changes, set the Status variable to 6.
            4-Indicates that the changes in the container folder are to be
              submitted to the management module, verified and and saved to flash.
            6-Indicates that the changes in the container folder are to be
              discarded."
        ::= { exCMConfigEntry 3 }

    exCMConfigModuleName OBJECT-TYPE
        SYNTAX		DisplayString(SIZE(0..63))
        MAX-ACCESS	read-write
        STATUS		current
        DESCRIPTION
            "This object identifies a user configurable name for the media converter module
             present in the chassis. "
    ::= { exCMConfigEntry 4 }

    exCMConfigLinkMode	OBJECT-TYPE
        SYNTAX		INTEGER {
            standard(0),
            smartLinkPassthrough(1)
        }
        MAX-ACCESS	read-write
        STATUS		current
        DESCRIPTION
            "This object identifies the Link Mode for the media converter module. This object
            is read-only if the media converter module's ConfigMode jumper is set to
            hardwareSwitches(0)."
    ::= { exCMConfigEntry 5 }

    exCMConfigInterlinkFaultFeedback	OBJECT-TYPE
        SYNTAX		EnableDisableValue
        MAX-ACCESS	read-write
        STATUS		current
        DESCRIPTION
            "This object identifies the interlink fault feedback setting for the media
             module. 
             This object is read-only if the media converter module's ConfigMode
             jumper is set to hardwareSwitches(0). "
    ::= { exCMConfigEntry 6 }

    exCMConfigVdslPortName OBJECT-TYPE
        SYNTAX		DisplayString(SIZE(0..8))
        MAX-ACCESS	read-write
        STATUS 		current
        DESCRIPTION
            "This object identifies a user definable name for the VDSL port."
    ::= { exCMConfigEntry 7 }

    exCMConfigVdslPortEnable OBJECT-TYPE
        SYNTAX		YesNoValue
        MAX-ACCESS	read-write
        STATUS 		current
        DESCRIPTION
            "This object identifies whether the VDSL port is enabled. "
    ::= { exCMConfigEntry 8 }

    exCMConfigVdslProfileMode OBJECT-TYPE
        SYNTAX		INTEGER {
            auto(0),
            manual(1)
        }
        MAX-ACCESS	read-write
        STATUS 		current
        DESCRIPTION
            "This object specifies how the VDSL profile is selected.
             Auto: select through exCMConfigVdslRate and exCMConfigVdslSymmetry
             Manual: select through exCMConfigVdslProfile."
    ::= { exCMConfigEntry 9 }

    exCMConfigVdslRole OBJECT-TYPE
        SYNTAX		INTEGER {
            auto(0),
            local(1),
            remote(2)
        }
        MAX-ACCESS	read-write
        STATUS 		current
        DESCRIPTION
            "This object specifies the VDSL role: auto, local (CO), or remote (CPE)."
    ::= { exCMConfigEntry 10 }

    exCMConfigVdslRate OBJECT-TYPE
        SYNTAX		INTEGER {
            highSpeed(0),
            longRange(1)
        }
        MAX-ACCESS	read-write
        STATUS 		current
        DESCRIPTION
            "This object specifies the VDSL rate/reach."
    ::= { exCMConfigEntry 11 }

    exCMConfigVdslSymmetry OBJECT-TYPE
        SYNTAX		INTEGER {
            asymmetric(0),
            symmetric(1)
        }
        MAX-ACCESS	read-write
        STATUS 		current
        DESCRIPTION
            "This object specifies the VDSL band plan or symmetry."
    ::= { exCMConfigEntry 12 }

    exCMConfigVdslProfile OBJECT-TYPE
        SYNTAX		INTEGER {
            profile1-AnnexA-R-POTS-D-32-EU-32-30a(1),
            profile2-AnnexA-R-POTS-D-32-EU-32-17a(2),
            profile3-AnnexA-R-POTS-D-32-EU-32-12b(3),
            profile4-AnnexA-R-POTS-D-32-EU-32-12a(4),
            profile5-AnnexA-R-POTS-D-32-EU-32-8a(5),
            profile6-AnnexA-R-POTS-D-32-EU-32-8b(6),
            profile7-AnnexA-R-POTS-D-32-EU-32-8c(7),
            profile8-AnnexA-R-POTS-D-32-EU-32-8d(8),
            profile9-AnnexA-R-POTS-D-64-EU-64-30a-NUS0(9),
            profile10-AnnexA-R-POTS-D-64-EU-64-17a(10),
            profile11-AnnexB-B7-3-997-M1x-M(11),
            profile12-AnnexB-B7-4-997-M2x-M-8(12),
            profile13-AnnexB-B7-5-997-M2x-A(13),
            profile14-AnnexB-B7-6-997-M2x-M(14),
            profile15-AnnexB-B7-9-997E17-M2x-A(15),
            profile16-AnnexB-B7-10-997E30-M2x-NUS0(16),
            profile17-AnnexB-B8-1-998-M1x-A(17),
            profile18-AnnexB-B8-2-998-M1x-B(18),
            profile19-AnnexB-B8-4-998-M2x-A(19),
            profile20-AnnexB-B8-5-998-M2x-M(20),
            profile21-AnnexB-B8-6-998-M2x-B(21),
            profile22-AnnexB-B8-8-998E17-M2x-NUS0(22),
            profile23-AnnexB-B8-9-998E17-M2x-NUS0-M(23),
            profile24-AnnexB-B8-10-998ADE17-M2x-NUS0-M(24),
            profile25-AnnexB-B8-11-998E17-M2x-A(25),
            profile26-AnnexB-B8-12-998E17-M2x-B(26),
            profile27-AnnexB-B8-13-998E30-M2x-NUS0(27),
            profile28-AnnexB-B8-14-998E30-M2x-NUS0-M(28),
            profile29-AnnexB-B8-15-998ADE30-M2x-NUS0-M(29),
            profile30-AnnexB-B8-16-998ADE30-M2x-NUS0-A(30),
            profile31-AnnexC-POTS-25-138-b(31),
            profile32-AnnexC-POTS-25-276-b(32),
            profile33-AnnexC-TMC-ISDN(33)            
        }
        MAX-ACCESS	read-write
        STATUS 		current
        DESCRIPTION
            "This object specifies the VDSL profile."
    ::= { exCMConfigEntry 13 }

    exCMConfigVdslOverrideProfile OBJECT-TYPE
        SYNTAX		EnableDisableValue
        MAX-ACCESS	read-write
        STATUS 		current
        DESCRIPTION
            "This object specifies whether to override advanced VDSL profile 
             settings (e.g exCMConfigVdslSignalToNoiseRatioUp)."
    ::= { exCMConfigEntry 14 }

    exCMConfigVdslSignalToNoiseRatioUp OBJECT-TYPE
        SYNTAX		Integer32(30..240)
        MAX-ACCESS	read-write
        STATUS 		current
        DESCRIPTION
            "This object represents the advanced VDSL profile setting
             signal-to-noise ratio (upstream) in 0.1 dB."
    ::= { exCMConfigEntry 15 }

    exCMConfigVdslMinDataRateUp OBJECT-TYPE
        SYNTAX		Integer32(128..101064)
        MAX-ACCESS	read-write
        STATUS 		current
        DESCRIPTION
            "This object represents the advanced VDSL profile setting
             minimum data rate (upstream) in kbps."
    ::= { exCMConfigEntry 16 }

    exCMConfigVdslMaxDataRateUp OBJECT-TYPE
        SYNTAX		Integer32(128..101064)
        MAX-ACCESS	read-write
        STATUS 		current
        DESCRIPTION
            "This object represents the advanced VDSL profile setting
             maximum data rate (upstream) in kbps."
    ::= { exCMConfigEntry 17 }

    exCMConfigVdslMaxInterleaveDelayUp OBJECT-TYPE
        SYNTAX		Integer32(0..16)
        MAX-ACCESS	read-write
        STATUS 		current
        DESCRIPTION
            "This object represents the advanced VDSL profile setting
             maximum delay (upstream) in ms."
    ::= { exCMConfigEntry 18 }

    exCMConfigVdslMinInpUp OBJECT-TYPE
        SYNTAX		Integer32(1..18)
        MAX-ACCESS	read-write
        STATUS 		current
        DESCRIPTION
            "This object represents the advanced VDSL profile setting
             minimum INP (impulse noise protection) (upstream)."
    ::= { exCMConfigEntry 19 }

    exCMConfigVdslSignalToNoiseRatioDown OBJECT-TYPE
        SYNTAX		Integer32(30..240)
        MAX-ACCESS	read-write
        STATUS 		current
        DESCRIPTION
            "This object represents the advanced VDSL profile setting
             signal-to-noise ratio (downstream) in 0.1 dB."
    ::= { exCMConfigEntry 20 }

    exCMConfigVdslMinDataRateDown OBJECT-TYPE
        SYNTAX		Integer32(128..101064)
        MAX-ACCESS	read-write
        STATUS 		current
        DESCRIPTION
            "This object represents the advanced VDSL profile setting
             minimum data rate (downstream) in kbps."
    ::= { exCMConfigEntry 21 }

    exCMConfigVdslMaxDataRateDown OBJECT-TYPE
        SYNTAX		Integer32(128..101064)
        MAX-ACCESS	read-write
        STATUS 		current
        DESCRIPTION
            "This object represents the advanced VDSL profile setting
             maximum data rate (downstream) in kbps."
    ::= { exCMConfigEntry 22 }

    exCMConfigVdslMaxInterleaveDelayDown OBJECT-TYPE
        SYNTAX		Integer32(0..16)
        MAX-ACCESS	read-write
        STATUS 		current
        DESCRIPTION
            "This object represents the advanced VDSL profile setting
             maximum delay (downstream) in ms."
    ::= { exCMConfigEntry 23 }

    exCMConfigVdslMinInpDown OBJECT-TYPE
        SYNTAX		Integer32(1..18)
        MAX-ACCESS	read-write
        STATUS 		current
        DESCRIPTION
            "This object represents the advanced VDSL profile setting
             minimum INP (impulse noise protection) (downstream)."
    ::= { exCMConfigEntry 24 }

    exCMConfigVdslBitswapping OBJECT-TYPE
        SYNTAX		EnableDisableValue
        MAX-ACCESS	read-write
        STATUS 		current
        DESCRIPTION
            "This object represents the advanced VDSL profile 
             setting bitswapping."
    ::= { exCMConfigEntry 25 }

    exCMConfigVdslLowBandwidthAlarmUp OBJECT-TYPE
        SYNTAX		Integer32(0..90000)
        MAX-ACCESS	read-write
        STATUS 		current
        DESCRIPTION
            "This object represents the VDSL low bandwidth alarm threshold (upstream) in kbps."
    ::= { exCMConfigEntry 26 }

    exCMConfigVdslLowBandwidthAlarmDown OBJECT-TYPE
        SYNTAX		Integer32(0..90000)
        MAX-ACCESS	read-write
        STATUS 		current
        DESCRIPTION
            "This object represents the VDSL low bandwidth alarm threshold (downstream) in kbps."
    ::= { exCMConfigEntry 27 }


    exCMConfigEthernetPortName OBJECT-TYPE
        SYNTAX DisplayString(SIZE(0..8))
        MAX-ACCESS read-write
        STATUS current
        DESCRIPTION
            "This object identifies a user definable name for the ethernet port. "
    ::= { exCMConfigEntry 28 }

    exCMConfigEthernetPortEnable OBJECT-TYPE
        SYNTAX	YesNoValue
        MAX-ACCESS	read-write
        STATUS	current
        DESCRIPTION
            "This object identifies whether the VDSL port is enabled. "
    ::= { exCMConfigEntry 29 }

    exCMConfigEthernetAutoNegotiation OBJECT-TYPE
        SYNTAX 		EnableDisableValue
        MAX-ACCESS	read-write
        STATUS 		current
        DESCRIPTION
            "This object identifies the whether ethernet auto-negotiation is
             enabled. This object is read-only if the media converter module's ConfigMode
             jumper is set to hardwareSwitches(0)."
    ::= { exCMConfigEntry 30 }

    exCMConfigEthernetAutoNegAdv10HDX OBJECT-TYPE
        SYNTAX 		YesNoValue
        MAX-ACCESS	read-write
        STATUS 		current
        DESCRIPTION
        "This object controls whether or the ethernet port advertises willingness
         to connect at 10Mbps, half duplex.  This setting is ignored when
         auto-negotiation is disabled."
    ::= { exCMConfigEntry 31 }

    exCMConfigEthernetAutoNegAdv10FDX OBJECT-TYPE
        SYNTAX 		YesNoValue
        MAX-ACCESS	read-write
        STATUS 		current
        DESCRIPTION
        "This object controls whether or the ethernet port advertises willingness
         to connect at 10Mbps, full duplex.  This setting is ignored when
         auto-negotiation is disabled."
    ::= { exCMConfigEntry 32 }

    exCMConfigEthernetAutoNegAdv100HDX OBJECT-TYPE
        SYNTAX 		YesNoValue
        MAX-ACCESS	read-write
        STATUS 		current
        DESCRIPTION
        "This object controls whether or the ethernet port advertises willingness
         to connect at 100Mbps, half duplex.  This setting is ignored when
         auto-negotiation is disabled."
    ::= { exCMConfigEntry 33 }

    exCMConfigEthernetAutoNegAdv100FDX OBJECT-TYPE
        SYNTAX 		YesNoValue
        MAX-ACCESS	read-write
        STATUS 		current
        DESCRIPTION
        "This object controls whether or the ethernet port advertises willingness
         to connect at 100Mbps, full duplex.  This setting is ignored when
         auto-negotiation is disabled."
    ::= { exCMConfigEntry 34 }

    exCMConfigEthernetAutoNegAdv1000FDX OBJECT-TYPE
        SYNTAX 		YesNoValue
        MAX-ACCESS	read-write
        STATUS 		current
        DESCRIPTION
        "This object controls whether or the ethernet port advertises willingness
         to connect at 1000Mbps, full duplex.  This setting is ignored when
         auto-negotiation is disabled."
    ::= { exCMConfigEntry 35 }

    exCMConfigEthernetSpeed OBJECT-TYPE
        SYNTAX 		INTEGER {
            speed10Mbs(0),
            speed100Mbps(1)
        }
        MAX-ACCESS	read-write
        STATUS 		current
        DESCRIPTION
            "If ethernet auto-negotiation is disabled then this object identifies
             the configured cooper speed. 1000 Mbps speed can only be auto
             negotiated. If ethernet auto-negotiation is enabled then this object
             is ignored.  This object is read-only if the media converter module's ConfigMode
             jumper is set to hardwareSwitches(0)."
    ::= { exCMConfigEntry 36 }

    exCMConfigEthernetDuplex	OBJECT-TYPE
        SYNTAX INTEGER {
            full(0),
            half(1)
        }
        MAX-ACCESS read-write
        STATUS current
        DESCRIPTION
            "If ethernet auto-negotiation is disabled then this object identifies
             the duplex setting for 10 & 100 Mbps for the ethernet port.  Duplex for
             1000 Mbps has to be auto negotiated. This object is read-only if the
             media converter module's ConfigMode jumper is set to hardwareSwitches(0)."
    ::= { exCMConfigEntry 37 }

    exCMConfigEthernetCrossOver OBJECT-TYPE
        SYNTAX INTEGER {
            auto(0),
            mdi(1),
            mdix(2)
        }
        MAX-ACCESS read-write
        STATUS current
        DESCRIPTION
            "This object identifies the ethernet MDI/MDI-X setting.This object
            is read-only if the media converter module's ConfigMode jumper is set to"
        ::= { exCMConfigEntry 38 }


    exCMConfigEthernetPauseEnh OBJECT-TYPE
        SYNTAX INTEGER {
            disabled(0),
            symmetrical(1),
            asymmetricalTx(2),
            symmAsymRx(3)
        }
        MAX-ACCESS read-write
        STATUS current
        DESCRIPTION
            "This object identifies the ethernet pause (flow control) setting that
             is a advertised. The settings can be disabled, advertise symmetrical,
             advertise asymmetrical TX or advertise symmetrical and asymmetrical
             RX. This object is read-only if the media converter module's ConfigMode jumper
             is set to hardwareSwitches(0)."
    ::= { exCMConfigEntry 39 }

    exCMConfigEthernetAutoSpeedDownshift OBJECT-TYPE
        SYNTAX INTEGER(0..8)
        MAX-ACCESS read-write
        STATUS current
        DESCRIPTION
            "This object identifies the number of times the PHY attempts to
             establish a Gigabit link before the PHY downshift to the next
             highest speed.  A value of 0 indicates the auto downshift is
             disabled"
    ::= { exCMConfigEntry 40 }

    exCMConfigEthernet10BaseTDistance OBJECT-TYPE
        SYNTAX INTEGER {
            normal(0),
            extended(1)
        }
        MAX-ACCESS read-write
        STATUS current
        DESCRIPTION
            "When using cable exceeding 100 meters in 10BASE-T mode this feature
             should be set to extended(1)."
    ::= { exCMConfigEntry 41 }


    exCMConfigUnidirectionalEthernet OBJECT-TYPE
        SYNTAX INTEGER {
            notApplicable(-1),
            disabled(0),
            ethernetToVdsl(1),
            vdslToEthernet(2)
        }
        MAX-ACCESS read-write
        STATUS current
        DESCRIPTION
            "Restrict the flow of Ethernet traffic to a single direction.
             A value of -1 signifies that this feature is not supported
             by the current media converter module firmware.
             (This feature may require a media converter module firmware upgrade)."
    ::= { exCMConfigEntry 42 }

    exCMConfigPriorityToEgressQueueMap0 OBJECT-TYPE
        SYNTAX INTEGER(0..3)
        MAX-ACCESS read-write
        STATUS current
        DESCRIPTION
            "Set the egress queue of frames tagged with 802.1p priority 0.
             A value of -1 signifies that this feature is not supported
             by the current media converter module firmware.
             (This feature may require a media converter module firmware upgrade)."
    ::= { exCMConfigEntry 43 }

    exCMConfigPriorityToEgressQueueMap1 OBJECT-TYPE
        SYNTAX INTEGER(0..3)
        MAX-ACCESS read-write
        STATUS current
        DESCRIPTION
            "Set the egress queue of frames tagged with 802.1p priority 1.
             A value of -1 signifies that this feature is not supported
             by the current media converter module firmware.
             (This feature may require a media converter module firmware upgrade)."
    ::= { exCMConfigEntry 44 }

    exCMConfigPriorityToEgressQueueMap2 OBJECT-TYPE
        SYNTAX INTEGER(0..3)
        MAX-ACCESS read-write
        STATUS current
        DESCRIPTION
            "Set the egress queue of frames tagged with 802.1p priority 2.
             A value of -1 signifies that this feature is not supported
             by the current media converter module firmware.
             (This feature may require a media converter module firmware upgrade)."
    ::= { exCMConfigEntry 45 }

    exCMConfigPriorityToEgressQueueMap3 OBJECT-TYPE
        SYNTAX INTEGER(0..3)
        MAX-ACCESS read-write
        STATUS current
        DESCRIPTION
            "Set the egress queue of frames tagged with 802.1p priority 3.
             A value of -1 signifies that this feature is not supported
             by the current media converter module firmware.
             (This feature may require a media converter module firmware upgrade)."
    ::= { exCMConfigEntry 46 }

    exCMConfigPriorityToEgressQueueMap4 OBJECT-TYPE
        SYNTAX INTEGER(0..3)
        MAX-ACCESS read-write
        STATUS current
        DESCRIPTION
            "Set the egress queue of frames tagged with 802.1p priority 4.
             A value of -1 signifies that this feature is not supported
             by the current media converter module firmware.
             (This feature may require a media converter module firmware upgrade)."
    ::= { exCMConfigEntry 47 }

    exCMConfigPriorityToEgressQueueMap5 OBJECT-TYPE
        SYNTAX INTEGER(0..3)
        MAX-ACCESS read-write
        STATUS current
        DESCRIPTION
            "Set the egress queue of frames tagged with 802.1p priority 5.
             A value of -1 signifies that this feature is not supported
             by the current media converter module firmware.
             (This feature may require a media converter module firmware upgrade)."
    ::= { exCMConfigEntry 48 }

    exCMConfigPriorityToEgressQueueMap6 OBJECT-TYPE
        SYNTAX INTEGER(0..3)
        MAX-ACCESS read-write
        STATUS current
        DESCRIPTION
            "Set the egress queue of frames tagged with 802.1p priority 6.
             A value of -1 signifies that this feature is not supported
             by the current media converter module firmware.
             (This feature may require a media converter module firmware upgrade)."
    ::= { exCMConfigEntry 49 }

    exCMConfigPriorityToEgressQueueMap7 OBJECT-TYPE
        SYNTAX INTEGER(0..3)
        MAX-ACCESS read-write
        STATUS current
        DESCRIPTION
            "Set the egress queue of frames tagged with 802.1p priority 7.
             A value of -1 signifies that this feature is not supported
             by the current media converter module firmware.
             (This feature may require a media converter module firmware upgrade)."
    ::= { exCMConfigEntry 50 }

    exCMConfigEthernet8021pPriority OBJECT-TYPE
        SYNTAX      OnOffValue
        MAX-ACCESS read-write
        STATUS current
        DESCRIPTION
            "Use 802.1p tag priority.
             (This feature may require a media converter module firmware upgrade)."
    ::= { exCMConfigEntry 51 }

    exCMConfigEthernetIpTosPriority OBJECT-TYPE
        SYNTAX      OnOffValue
        MAX-ACCESS read-write
        STATUS current
        DESCRIPTION
            "Use IP TOS priority.
             (This feature may require a media converter module firmware upgrade)."
    ::= { exCMConfigEntry 52 }

    exCMConfigEthernetPriorityPrecedence OBJECT-TYPE
        SYNTAX INTEGER {
            notApplicable(-1),
            priority8021p(0),
            priorityIpTos(1)
        }
        MAX-ACCESS read-write
        STATUS current
        DESCRIPTION
            "Configure priority precedence.
             (This feature may require a media converter module firmware upgrade)."
    ::= { exCMConfigEntry 53 }

    exCMConfigEthernetCongestionPolicy OBJECT-TYPE
        SYNTAX INTEGER {
            notApplicable(-1),
            strict(0),
            weighted(1)
        }
        MAX-ACCESS read-write
        STATUS current
        DESCRIPTION
            "Configure priority congestion policy.
             (This feature may require a media converter module firmware upgrade)."
    ::= { exCMConfigEntry 54 }

    exCMConfigEthernetPriorityMap0 OBJECT-TYPE
        SYNTAX INTEGER(0..7)
        MAX-ACCESS read-write
        STATUS current
        DESCRIPTION
            "Change the priority of frames tagged with 802.1p priority 0.
             A value of -1 signifies that this feature is not supported
             by the current media converter module firmware.
             (This feature may require a media converter module firmware upgrade)."
    ::= { exCMConfigEntry 55 }

    exCMConfigEthernetPriorityMap1 OBJECT-TYPE
        SYNTAX INTEGER(0..7)
        MAX-ACCESS read-write
        STATUS current
        DESCRIPTION
            "Change the priority of frames tagged with 802.1p priority 1.
             A value of -1 signifies that this feature is not supported
             by the current media converter module firmware.
             (This feature may require a media converter module firmware upgrade)."
    ::= { exCMConfigEntry 56 }

    exCMConfigEthernetPriorityMap2 OBJECT-TYPE
        SYNTAX INTEGER(0..7)
        MAX-ACCESS read-write
        STATUS current
        DESCRIPTION
            "Change the priority of frames tagged with 802.1p priority 2.
             A value of -1 signifies that this feature is not supported
             by the current media converter module firmware.
             (This feature may require a media converter module firmware upgrade)."
    ::= { exCMConfigEntry 57 }

    exCMConfigEthernetPriorityMap3 OBJECT-TYPE
        SYNTAX INTEGER(0..7)
        MAX-ACCESS read-write
        STATUS current
        DESCRIPTION
            "Change the priority of frames tagged with 802.1p priority 3.
             A value of -1 signifies that this feature is not supported
             by the current media converter module firmware.
             (This feature may require a media converter module firmware upgrade)."
    ::= { exCMConfigEntry 58 }

    exCMConfigEthernetPriorityMap4 OBJECT-TYPE
        SYNTAX INTEGER(0..7)
        MAX-ACCESS read-write
        STATUS current
        DESCRIPTION
            "Change the priority of frames tagged with 802.1p priority 4.
             A value of -1 signifies that this feature is not supported
             by the current media converter module firmware.
             (This feature may require a media converter module firmware upgrade)."
    ::= { exCMConfigEntry 59 }

    exCMConfigEthernetPriorityMap5 OBJECT-TYPE
        SYNTAX INTEGER(0..7)
        MAX-ACCESS read-write
        STATUS current
        DESCRIPTION
            "Change the priority of frames tagged with 802.1p priority 5.
             A value of -1 signifies that this feature is not supported
             by the current media converter module firmware.
             (This feature may require a media converter module firmware upgrade)."
    ::= { exCMConfigEntry 60 }

    exCMConfigEthernetPriorityMap6 OBJECT-TYPE
        SYNTAX INTEGER(0..7)
        MAX-ACCESS read-write
        STATUS current
        DESCRIPTION
            "Change the priority of frames tagged with 802.1p priority 6.
             A value of -1 signifies that this feature is not supported
             by the current media converter module firmware.
             (This feature may require a media converter module firmware upgrade)."
    ::= { exCMConfigEntry 61 }

    exCMConfigEthernetPriorityMap7 OBJECT-TYPE
        SYNTAX INTEGER(0..7)
        MAX-ACCESS read-write
        STATUS current
        DESCRIPTION
            "Change the priority of frames tagged with 802.1p priority 7.
             A value of -1 signifies that this feature is not supported
             by the current media converter module firmware.
             (This feature may require a media converter module firmware upgrade)."
    ::= { exCMConfigEntry 62 }

    exCMConfigEthernetIngressLimit OBJECT-TYPE
        SYNTAX INTEGER {
            notApplicable(-1),
            rateUnlimited(0),
            rate64kbps(1),
            rate128kbps(2),
            rate192kbps(3),
            rate256kbps(4),
            rate320kbps(5),
            rate384kbps(6),
            rate512kbps(7),
            rate768kbps(8),
            rate1mbps  (9),
            rate2mbps  (10),
            rate3mbps  (11),
            rate4mbps  (12),
            rate5mbps  (13),
            rate6mbps  (14),
            rate7mbps  (15),
            rate8mbps  (16),
            rate9mbps  (17),
            rate10mbps (18),
            rate20mbps (19),
            rate30mbps (20),
            rate40mbps (21),
            rate50mbps (22),
            rate60mbps (23),
            rate70mbps (24),
            rate80mbps (25),
            rate90mbps (26)
        }
        MAX-ACCESS read-write
        STATUS current
        DESCRIPTION
            "Set a limit on the rate of incoming packets.
             (This feature may require a media converter module firmware upgrade)."
    ::= { exCMConfigEntry 63 }

    exCMConfigEthernetEgressLimit OBJECT-TYPE
        SYNTAX INTEGER {
            notApplicable(-1),
            rateUnlimited(0),
            rate64kbps(1),
            rate128kbps(2),
            rate192kbps(3),
            rate256kbps(4),
            rate320kbps(5),
            rate384kbps(6),
            rate512kbps(7),
            rate768kbps(8),
            rate1mbps  (9),
            rate2mbps  (10),
            rate3mbps  (11),
            rate4mbps  (12),
            rate5mbps  (13),
            rate6mbps  (14),
            rate7mbps  (15),
            rate8mbps  (16),
            rate9mbps  (17),
            rate10mbps (18),
            rate20mbps (19),
            rate30mbps (20),
            rate40mbps (21),
            rate50mbps (22),
            rate60mbps (23),
            rate70mbps (24),
            rate80mbps (25),
            rate90mbps (26)
        }
        MAX-ACCESS read-write
        STATUS current
        DESCRIPTION
            "Set a limit on the rate of outgoing packets.
             (This feature may require a media converter module firmware upgrade)."
    ::= { exCMConfigEntry 64 }

    exCMConfigEthernetDiscardTaggedFrames OBJECT-TYPE
        SYNTAX      OnOffValue
        MAX-ACCESS read-write
        STATUS current
        DESCRIPTION
            "Enable discarding of tagged frames.
             (This feature may require a media converter module firmware upgrade)."
    ::= { exCMConfigEntry 65 }

    exCMConfigEthernetDiscardUntaggedFrames OBJECT-TYPE
        SYNTAX      OnOffValue
        MAX-ACCESS read-write
        STATUS current
        DESCRIPTION
            "Enable discarding of untagged frames.
             (This feature may require a media converter module firmware upgrade)."
    ::= { exCMConfigEntry 66 }

    exCMConfigEthernetDefaultVlanId OBJECT-TYPE
        SYNTAX      INTEGER(0..4095)
        MAX-ACCESS read-write
        STATUS current
        DESCRIPTION
            "Set the default VLAN ID to insert when tagging frames.
             (This feature may require a media converter module firmware upgrade)."
    ::= { exCMConfigEntry 67 }

    exCMConfigEthernetDefaultPriority OBJECT-TYPE
        SYNTAX      INTEGER(0..7)
        MAX-ACCESS read-write
        STATUS current
        DESCRIPTION
            "Set the default frame priority.
             (This feature may require a media converter module firmware upgrade)."
    ::= { exCMConfigEntry 68 }

    exCMConfigEthernetVlanTaggingAction OBJECT-TYPE
        SYNTAX INTEGER {
            notApplicable(-1),
            none(0),
            untag(1),
            tag(2),
            doubleTag(3)
        }
        MAX-ACCESS read-write
        STATUS current
        DESCRIPTION
            "Set the default tagging action.
             (This feature may require a media converter module firmware upgrade)."
    ::= { exCMConfigEntry 69 }

    exCMConfigEthernetFilterUnknownMulticast OBJECT-TYPE
        SYNTAX      OnOffValue
        MAX-ACCESS read-write
        STATUS current
        DESCRIPTION
            "Enable filtering of multicast frames with an unknown destination
             (This feature may require a media converter module firmware upgrade)."
    ::= { exCMConfigEntry 70 }

    exCMConfigEthernetFilterUnknownUnicast OBJECT-TYPE
        SYNTAX      OnOffValue
        MAX-ACCESS read-write
        STATUS current
        DESCRIPTION
            "Enable filtering of unicast frames with an unknown destination
             (This feature may require a media converter module firmware upgrade)."
    ::= { exCMConfigEntry 71 }

    exCMConfigVdsl8021pPriority OBJECT-TYPE
        SYNTAX      OnOffValue
        MAX-ACCESS read-write
        STATUS current
        DESCRIPTION
            "Use 802.1p tag priority.
             (This feature may require a media converter module firmware upgrade)."
    ::= { exCMConfigEntry 72 }

    exCMConfigVdslIpTosPriority OBJECT-TYPE
        SYNTAX      OnOffValue
        MAX-ACCESS read-write
        STATUS current
        DESCRIPTION
            "Use IP TOS priority.
             (This feature may require a media converter module firmware upgrade)."
    ::= { exCMConfigEntry 73 }

    exCMConfigVdslPriorityPrecedence OBJECT-TYPE
        SYNTAX INTEGER {
            notApplicable(-1),
            priority8021p(0),
            priorityIpTos(1)
        }
        MAX-ACCESS read-write
        STATUS current
        DESCRIPTION
            "Configure priority precedence.
             (This feature may require a media converter module firmware upgrade)."
    ::= { exCMConfigEntry 74 }

    exCMConfigVdslCongestionPolicy OBJECT-TYPE
        SYNTAX INTEGER {
            notApplicable(-1),
            strict(0),
            weighted(1)
        }
        MAX-ACCESS read-write
        STATUS current
        DESCRIPTION
            "Configure priority congestion policy.
             (This feature may require a media converter module firmware upgrade)."
    ::= { exCMConfigEntry 75 }

    exCMConfigVdslPriorityMap0 OBJECT-TYPE
        SYNTAX INTEGER(0..7)
        MAX-ACCESS read-write
        STATUS current
        DESCRIPTION
            "Change the priority of frames tagged with 802.1p priority 0.
             A value of -1 signifies that this feature is not supported
             by the current media converter module firmware.
             (This feature may require a media converter module firmware upgrade)."
    ::= { exCMConfigEntry 76 }

    exCMConfigVdslPriorityMap1 OBJECT-TYPE
        SYNTAX INTEGER(0..7)
        MAX-ACCESS read-write
        STATUS current
        DESCRIPTION
            "Change the priority of frames tagged with 802.1p priority 1.
             A value of -1 signifies that this feature is not supported
             by the current media converter module firmware.
             (This feature may require a media converter module firmware upgrade)."
    ::= { exCMConfigEntry 77 }

    exCMConfigVdslPriorityMap2 OBJECT-TYPE
        SYNTAX INTEGER(0..7)
        MAX-ACCESS read-write
        STATUS current
        DESCRIPTION
            "Change the priority of frames tagged with 802.1p priority 2.
             A value of -1 signifies that this feature is not supported
             by the current media converter module firmware.
             (This feature may require a media converter module firmware upgrade)."
    ::= { exCMConfigEntry 78 }

    exCMConfigVdslPriorityMap3 OBJECT-TYPE
        SYNTAX INTEGER(0..7)
        MAX-ACCESS read-write
        STATUS current
        DESCRIPTION
            "Change the priority of frames tagged with 802.1p priority 3.
             A value of -1 signifies that this feature is not supported
             by the current media converter module firmware.
             (This feature may require a media converter module firmware upgrade)."
    ::= { exCMConfigEntry 79 }

    exCMConfigVdslPriorityMap4 OBJECT-TYPE
        SYNTAX INTEGER(0..7)
        MAX-ACCESS read-write
        STATUS current
        DESCRIPTION
            "Change the priority of frames tagged with 802.1p priority 4.
             A value of -1 signifies that this feature is not supported
             by the current media converter module firmware.
             (This feature may require a media converter module firmware upgrade)."
    ::= { exCMConfigEntry 80 }

    exCMConfigVdslPriorityMap5 OBJECT-TYPE
        SYNTAX INTEGER(0..7)
        MAX-ACCESS read-write
        STATUS current
        DESCRIPTION
            "Change the priority of frames tagged with 802.1p priority 5.
             A value of -1 signifies that this feature is not supported
             by the current media converter module firmware.
             (This feature may require a media converter module firmware upgrade)."
    ::= { exCMConfigEntry 81 }

    exCMConfigVdslPriorityMap6 OBJECT-TYPE
        SYNTAX INTEGER(0..7)
        MAX-ACCESS read-write
        STATUS current
        DESCRIPTION
            "Change the priority of frames tagged with 802.1p priority 6.
             A value of -1 signifies that this feature is not supported
             by the current media converter module firmware.
             (This feature may require a media converter module firmware upgrade)."
    ::= { exCMConfigEntry 82 }

    exCMConfigVdslPriorityMap7 OBJECT-TYPE
        SYNTAX INTEGER(0..7)
        MAX-ACCESS read-write
        STATUS current
        DESCRIPTION
            "Change the priority of frames tagged with 802.1p priority 7.
             A value of -1 signifies that this feature is not supported
             by the current media converter module firmware.
             (This feature may require a media converter module firmware upgrade)."
    ::= { exCMConfigEntry 83 }

    exCMConfigVdslIngressLimit OBJECT-TYPE
        SYNTAX INTEGER {
            notApplicable(-1),
            rateUnlimited(0),
            rate64kbps(1),
            rate128kbps(2),
            rate192kbps(3),
            rate256kbps(4),
            rate320kbps(5),
            rate384kbps(6),
            rate512kbps(7),
            rate768kbps(8),
            rate1mbps  (9),
            rate2mbps  (10),
            rate3mbps  (11),
            rate4mbps  (12),
            rate5mbps  (13),
            rate6mbps  (14),
            rate7mbps  (15),
            rate8mbps  (16),
            rate9mbps  (17),
            rate10mbps (18),
            rate20mbps (19),
            rate30mbps (20),
            rate40mbps (21),
            rate50mbps (22),
            rate60mbps (23),
            rate70mbps (24),
            rate80mbps (25),
            rate90mbps (26)
        }
        MAX-ACCESS read-write
        STATUS current
        DESCRIPTION
            "Set a limit on the rate of incoming packets.
             (This feature may require a media converter module firmware upgrade)."
    ::= { exCMConfigEntry 84 }

    exCMConfigVdslEgressLimit OBJECT-TYPE
        SYNTAX INTEGER {
            notApplicable(-1),
            rateUnlimited(0),
            rate64kbps(1),
            rate128kbps(2),
            rate192kbps(3),
            rate256kbps(4),
            rate320kbps(5),
            rate384kbps(6),
            rate512kbps(7),
            rate768kbps(8),
            rate1mbps  (9),
            rate2mbps  (10),
            rate3mbps  (11),
            rate4mbps  (12),
            rate5mbps  (13),
            rate6mbps  (14),
            rate7mbps  (15),
            rate8mbps  (16),
            rate9mbps  (17),
            rate10mbps (18),
            rate20mbps (19),
            rate30mbps (20),
            rate40mbps (21),
            rate50mbps (22),
            rate60mbps (23),
            rate70mbps (24),
            rate80mbps (25),
            rate90mbps (26)
        }
        MAX-ACCESS read-write
        STATUS current
        DESCRIPTION
            "Set a limit on the rate of outgoing packets.
             (This feature may require a media converter module firmware upgrade)."
    ::= { exCMConfigEntry 85 }

    exCMConfigVdslDiscardTaggedFrames OBJECT-TYPE
        SYNTAX      OnOffValue
        MAX-ACCESS read-write
        STATUS current
        DESCRIPTION
            "Enable discarding of tagged frames.
             (This feature may require a media converter module firmware upgrade)."
    ::= { exCMConfigEntry 86 }

    exCMConfigVdslDiscardUntaggedFrames OBJECT-TYPE
        SYNTAX      OnOffValue
        MAX-ACCESS read-write
        STATUS current
        DESCRIPTION
            "Enable discarding of untagged frames.
             (This feature may require a media converter module firmware upgrade)."
    ::= { exCMConfigEntry 87 }

    exCMConfigVdslDefaultVlanId OBJECT-TYPE
        SYNTAX      INTEGER(0..4095)
        MAX-ACCESS read-write
        STATUS current
        DESCRIPTION
            "Set the default VLAN ID to insert when tagging frames.
             (This feature may require a media converter module firmware upgrade)."
    ::= { exCMConfigEntry 88 }

    exCMConfigVdslDefaultPriority OBJECT-TYPE
        SYNTAX      INTEGER(0..7)
        MAX-ACCESS read-write
        STATUS current
        DESCRIPTION
            "Set the default frame priority.
             (This feature may require a media converter module firmware upgrade)."
    ::= { exCMConfigEntry 89 }

    exCMConfigVdslVlanTaggingAction OBJECT-TYPE
        SYNTAX INTEGER {
            notApplicable(-1),
            none(0),
            untag(1),
            tag(2),
            doubleTag(3)
        }
        MAX-ACCESS read-write
        STATUS current
        DESCRIPTION
            "Set the default tagging action.
             (This feature may require a media converter module firmware upgrade)."
    ::= { exCMConfigEntry 90 }

    exCMConfigVdslFilterUnknownMulticast OBJECT-TYPE
        SYNTAX      OnOffValue
        MAX-ACCESS read-write
        STATUS current
        DESCRIPTION
            "Enable filtering of multicast frames with an unknown destination
             (This feature may require a media converter module firmware upgrade)."
    ::= { exCMConfigEntry 91 }

    exCMConfigVdslFilterUnknownUnicast OBJECT-TYPE
        SYNTAX      OnOffValue
        MAX-ACCESS read-write
        STATUS current
        DESCRIPTION
            "Enable filtering of unicast frames with an unknown destination
             (This feature may require a media converter module firmware upgrade)."
    ::= { exCMConfigEntry 92 }

    exCMConfigVdslFastMode OBJECT-TYPE
        SYNTAX		EnableDisableValue
        MAX-ACCESS	read-write
        STATUS 		current
        DESCRIPTION
            "This object represents the VDSL fast mode setting."
    ::= { exCMConfigEntry 93 }


--
--
-- exCMConfigEntry
--
--
-- exCMLedTable
--
exCMLedTable	OBJECT-TYPE
    SYNTAX		SEQUENCE OF ExCMLedEntry
    MAX-ACCESS	not-accessible
    STATUS		current
    DESCRIPTION
        "Table of CM-1110 type media converter module's LED status information."
    ::= { exCM 3 }

    exCMLedEntry OBJECT-TYPE
        SYNTAX      ExCMLedEntry
        MAX-ACCESS  not-accessible
        STATUS      current
        DESCRIPTION
            "Entries of the table, each relating to a separate CM-1110 type
             media converter module."
        INDEX   { mcrChassisIndex, exCMLedSlotIndex }
        ::= { exCMLedTable 1 }

    ExCMLedEntry ::=
        SEQUENCE {
            exCMLedSlotIndex	SlotNumber,
            exCMLedILNK			INTEGER,
            exCMLedLOC			INTEGER,
            exCMLedPWR			INTEGER,
            exCMLedETH			INTEGER,
            exCMLedRMT			INTEGER
        }

    exCMLedSlotIndex	OBJECT-TYPE
        SYNTAX		SlotNumber
        MAX-ACCESS	not-accessible
        STATUS		current
        DESCRIPTION
            "The Slot number of the module"
    ::= { exCMLedEntry 2 }

    exCMLedILNK	OBJECT-TYPE
        SYNTAX		INTEGER {
            off(0),
            slowBlinkingGreen(1),
            fastBlinkingGreen(2),
            green(3)
        }
        MAX-ACCESS	read-only
        STATUS		current
        DESCRIPTION
            "This object identifies the status of the ILNK (InterLink) LED on the media converter module.
             Possible status values are:
                 slowBlinkingGreen(1) - ILNK port is idle or handshaking
                 fastBlinkingGreen(2) - ILNK port is training
                 green(3)             - ILNK port is up"
    ::= { exCMLedEntry 3 }

    exCMLedLOC	OBJECT-TYPE
        SYNTAX		INTEGER {
            off(0),
            green(1)
        }
        MAX-ACCESS	read-only
        STATUS		current
        DESCRIPTION
            "This object identifies the status of the Local (LOC) LED
             on the media converter module.  When this LED is green, it indicates
             that the InterLink port's VDSL role is local."
    ::= { exCMLedEntry 4 }

    exCMLedPWR	OBJECT-TYPE
        SYNTAX		INTEGER {
            off(0),
            onGreen(1),
            blinking(2)
        }
        MAX-ACCESS	read-only
        STATUS		current
        DESCRIPTION
            "This object identifies the status of the power (PWR) LED on the media converter module.
             Possible status values are:
                 off(0) - No power to the module
                 onGreen(1) - Power being applied to module
                 blinking(2) - InterLink loopback enabled"
    ::= { exCMLedEntry 5 }

    exCMLedETH	OBJECT-TYPE
        SYNTAX		INTEGER {
            off(0),
            slowBlinkingGreen(1),
            green(2)
        }
        MAX-ACCESS	read-only
        STATUS		current
        DESCRIPTION
            "This object identifies the status of the ETH (Ethernet) LED on the media converter module.
             Possible status values are:
                 off(0)               - ETH port is down
                 slowBlinkingGreen(1) - ETH port is down, due to the VDSL port or peer copper ethernet port being down 
                 green(2)             - ETH port is up"
    ::= { exCMLedEntry 6 }

    exCMLedRMT	OBJECT-TYPE
        SYNTAX		INTEGER {
            off(0),
            green(1)
        }
        MAX-ACCESS	read-only
        STATUS		current
        DESCRIPTION
            "This object identifies the status of the Remote (RMT) LED
             on the media converter module.  When this LED is green, it indicates
             that the InterLink port's VDSL role is remote."
    ::= { exCMLedEntry 7 }


--
-- end of exCMLedTable
--
--
-- exCMStatsTable
--
exCMStatsTable	OBJECT-TYPE
    SYNTAX		SEQUENCE OF ExCMStatsEntry
    MAX-ACCESS	not-accessible
    STATUS		current
    DESCRIPTION
        "Table of CM-1110 type media converter module's configuration and status type
         information."
    ::= { exCM 4 }

    exCMStatsEntry OBJECT-TYPE
        SYNTAX      ExCMStatsEntry
        MAX-ACCESS  not-accessible
        STATUS      current
        DESCRIPTION
            "Entries of the table, each relating to a separate CM-1110 type
             media converter module."
        INDEX   { mcrChassisIndex, exCMStatsSlotIndex, exCMMediaPortIndex }
        ::= { exCMStatsTable 1 }

    ExCMStatsEntry ::=
        SEQUENCE {
            exCMStatsSlotIndex				SlotNumber,
            exCMMediaPortIndex				INTEGER,

            exCMPortInDiscards 			Counter32,
            exCMPortInFiltered				INTEGER,
            exCMPortInGoodOctets			Counter32,
            exCMPortHCInGoodOctets		Counter64,
            exCMPortInBadOctets			Counter32,
            exCMPortInUnicasts				Counter32,
            exCMPortInBroadcasts			Counter32,
            exCMPortInMulticasts			Counter32,
            exCMPortInPauses					Counter32,
            exCMPortInUnderSizes			Counter32,
            exCMPortInFragments			Counter32,
            exCMPortInOversizes			Counter32,
            exCMPortInJabbers				Counter32,
            exCMPortInRxErrs				Counter32,
            exCMPortInFcsErrs				Counter32,

            exCMPortPkts64Octets			Counter32,
            exCMPortPkts65to127Octets	Counter32,
            exCMPortPkts128to255Octets	Counter32,
            exCMPortPkts256to511Octets	Counter32,
            exCMPortPkts512to1023Octets	Counter32,
            exCMPortPkts1024toMaxOctets	Counter32,

            exCMPortOutOctets				Counter32,
            exCMPortHCOutOctets			Counter64,
            exCMPortOutFiltered			INTEGER,
            exCMPortOutUnicasts			Counter32,
            exCMPortOutBroadcasts			Counter32,
            exCMPortOutMulticasts			Counter32,
            exCMPortOutPauses				Counter32,
            exCMPortDeferreds				Counter32,
            exCMPortCollisions				Counter32,
            exCMPortSingles					Counter32,
            exCMPortMultiples				Counter32,
            exCMPortExcessives				Counter32,
            exCMPortLates					Counter32,
            exCMPortOutFcsErrs				Counter32,

            exCMPortResetCounters			YesNoValue
        }

    exCMStatsSlotIndex	OBJECT-TYPE
        SYNTAX		SlotNumber
        MAX-ACCESS	not-accessible
        STATUS		current
        DESCRIPTION
            "The Slot number the ex-1CM type module is currently inserted"
    ::= { exCMStatsEntry 2 }

    exCMMediaPortIndex OBJECT-TYPE
        SYNTAX INTEGER (1..2) 
        MAX-ACCESS not-accessible
        STATUS current
        DESCRIPTION
            "Media converter module port index indicating which media port the statistical
             counters are associated with."
    ::= { exCMStatsEntry 3 }

    exCMPortInDiscards OBJECT-TYPE
        SYNTAX      Counter32
        MAX-ACCESS  read-only
        STATUS      current
        DESCRIPTION
            "A counter that counts the number of good, non-filtered frames that
             normally would have been forwarded, but could not due to lack of
             buffer space."
        ::= { exCMStatsEntry 4 }

    exCMPortInFiltered OBJECT-TYPE
        SYNTAX      INTEGER(0..65535)
        MAX-ACCESS  read-only
        STATUS      current
        DESCRIPTION
            "A counter that counts the number of good frames that were filtered
             due to ingress switch policy rules. "
        ::= { exCMStatsEntry 5 }

    exCMPortInGoodOctets OBJECT-TYPE
        SYNTAX      Counter32
        MAX-ACCESS  read-only
        STATUS      current
        DESCRIPTION
            "An ingress counter that is the sum of lengths of all good Ethernet
             frames received on the media port."
        ::= { exCMStatsEntry 6 }

    exCMPortHCInGoodOctets OBJECT-TYPE
        SYNTAX      Counter64
        MAX-ACCESS  read-only
        STATUS      current
        DESCRIPTION
            "An ingress counter that is the sum of lengths of all good Ethernet
             frames received on the media port. This object is a 64-bit version of
             exCMPortInGoodOctets."
        ::= { exCMStatsEntry 7 }

    exCMPortInBadOctets OBJECT-TYPE
        SYNTAX      Counter32
        MAX-ACCESS  read-only
        STATUS      current
        DESCRIPTION
            "An ingress counter that is the sum of lengths of all bad Ethernet
             frames received on the media port.."
        ::= { exCMStatsEntry 8 }

    exCMPortInUnicasts OBJECT-TYPE
        SYNTAX      Counter32
        MAX-ACCESS  read-only
        STATUS      current
        DESCRIPTION
            "An ingress counter that counts the number of good frames received that
             have a Unicast destination MAC address."
        ::= { exCMStatsEntry 9 }

    exCMPortInBroadcasts OBJECT-TYPE
        SYNTAX      Counter32
        MAX-ACCESS  read-only
        STATUS      current
        DESCRIPTION
            "An ingress counter that counts the number of good frames received that
             have a Broadcast destination MAC address."
        ::= { exCMStatsEntry 10 }

    exCMPortInMulticasts OBJECT-TYPE
        SYNTAX      Counter32
        MAX-ACCESS  read-only
        STATUS      current
        DESCRIPTION
            "An ingress counter that counts the number of good frames received that
             have a Multicast destination MAC address. This count does not include
             frames counted in the exCMPortInPauses or the exCMPortInBroadcasts
             objects."
        ::= { exCMStatsEntry 11 }

    exCMPortInPauses OBJECT-TYPE
        SYNTAX      Counter32
        MAX-ACCESS  read-only
        STATUS      current
        DESCRIPTION
            "An ingress counter that counts the number of good frames reachieved that
             have a Pause destination MAC address."
        ::= { exCMStatsEntry 12 }

    exCMPortInUnderSizes OBJECT-TYPE
        SYNTAX      Counter32
        MAX-ACCESS  read-only
        STATUS      current
        DESCRIPTION
            "An ingress counter that counts the number of frames received with a
             length less that 64 octets but with a valid FCS."
        ::= { exCMStatsEntry 13 }

    exCMPortInFragments OBJECT-TYPE
        SYNTAX      Counter32
        MAX-ACCESS  read-only
        STATUS      current
        DESCRIPTION
            "An ingress counter that counts the number of frames received with a
             length less that 64 octets and an invalid FCS."
        ::= { exCMStatsEntry 14 }

    exCMPortInOversizes OBJECT-TYPE
        SYNTAX      Counter32
        MAX-ACCESS  read-only
        STATUS      current
        DESCRIPTION
            "An ingress counter that counts the number of frames received with a
             length more than the maximum packet size but with a valid FCS.
             The maximum packet size can be set using the exCMConfigMaxPacketsSize
             object."
        ::= { exCMStatsEntry 15 }

    exCMPortInJabbers OBJECT-TYPE
        SYNTAX      Counter32
        MAX-ACCESS  read-only
        STATUS      current
        DESCRIPTION
            "An ingress counter that counts the number of frames received with a
             length more than the maximum packet size but with a invalid FCS.
             The maximum packet size can be set using the exCMConfigMaxPacketsSize
             object."
        ::= { exCMStatsEntry 16 }

    exCMPortInRxErrs OBJECT-TYPE
        SYNTAX      Counter32
        MAX-ACCESS  read-only
        STATUS      current
        DESCRIPTION
            "An ingress counter that counts the number of frames received with an
             RxErr signal from the PHY."
        ::= { exCMStatsEntry 17 }

    exCMPortInFcsErrs OBJECT-TYPE
        SYNTAX      Counter32
        MAX-ACCESS  read-only
        STATUS      current
        DESCRIPTION
            "An ingress counter that counts the number of frames received with a
             CRC error not counted in the exCMPortInFragments,
             exCMPortInFcsErr, or the exCMPortInRxErr objects."
        ::= { exCMStatsEntry 18 }

    exCMPortPkts64Octets OBJECT-TYPE
        SYNTAX      Counter32
        MAX-ACCESS  read-only
        STATUS      current
        DESCRIPTION
            "A Histogram counter that counts the number of frames received and
             transmitted with a length of exactly 64 Octets, including those with
             errors."
        ::= { exCMStatsEntry 19 }

    exCMPortPkts65to127Octets OBJECT-TYPE
        SYNTAX      Counter32
        MAX-ACCESS  read-only
        STATUS      current
        DESCRIPTION
            "A Histogram counter that counts the number of frames received and
             transmitted with a length of between 65 and 127 Octets inclusive,
             including those with errors."
        ::= { exCMStatsEntry 20 }

    exCMPortPkts128to255Octets OBJECT-TYPE
        SYNTAX      Counter32
        MAX-ACCESS  read-only
        STATUS      current
        DESCRIPTION
            "A Histogram counter that counts the number of frames received and
             transmitted with a length of between 128 and 255 Octets inclusive,
             including those with errors."
        ::= { exCMStatsEntry 21 }

    exCMPortPkts256to511Octets OBJECT-TYPE
        SYNTAX      Counter32
        MAX-ACCESS  read-only
        STATUS      current
        DESCRIPTION
            "A Histogram counter that counts the number of frames received and
             transmitted with a length of between 256 and 511 Octets inclusive,
             including those with errors."
        ::= { exCMStatsEntry 22 }

    exCMPortPkts512to1023Octets OBJECT-TYPE
        SYNTAX      Counter32
        MAX-ACCESS  read-only
        STATUS      current
        DESCRIPTION
            "A Histogram counter that counts the number of frames received and
             transmitted with a length of between 512 and 1023 Octets inclusive,
             including those with errors."
        ::= { exCMStatsEntry 23 }

    exCMPortPkts1024toMaxOctets OBJECT-TYPE
        SYNTAX      Counter32
        MAX-ACCESS  read-only
        STATUS      current
        DESCRIPTION
            "A Histogram counter that counts the number of frames received and
             transmitted with a length of between 1024 and maximum packet size
             octets inclusive, including those with errors.
             The maximum packet size can be set using the exCMConfigMaxPacketsSize
             object."
        ::= { exCMStatsEntry 24 }

     exCMPortOutOctets OBJECT-TYPE
        SYNTAX      Counter32
        MAX-ACCESS  read-only
        STATUS      current
        DESCRIPTION
            "An Egress counter that is the sum of lengths of all good Ethernet
             frames sent on the media port."
        ::= { exCMStatsEntry 25 }

    exCMPortHCOutOctets OBJECT-TYPE
        SYNTAX      Counter64
        MAX-ACCESS  read-only
        STATUS      current
        DESCRIPTION
            "An Egress counter that is the sum of lengths of all good Ethernet
             frames sent on the media port. This object is a 64-bit version of
             exCMPortOutOctets."
        ::= { exCMStatsEntry 26 }

    exCMPortOutFiltered OBJECT-TYPE
        SYNTAX      INTEGER(0..65535)
        MAX-ACCESS  read-only
        STATUS      current
        DESCRIPTION
            "A counter that counts the number of good frames that were filtered
             due to egress switch policy rules."
        ::= { exCMStatsEntry 27 }

    exCMPortOutUnicasts OBJECT-TYPE
        SYNTAX      Counter32
        MAX-ACCESS  read-only
        STATUS      current
        DESCRIPTION
            "An Egress counter that counts the number of good frames sent that
             have a Unicast destination MAC address."
        ::= { exCMStatsEntry 28 }

    exCMPortOutBroadcasts OBJECT-TYPE
        SYNTAX      Counter32
        MAX-ACCESS  read-only
        STATUS      current
        DESCRIPTION
            "An Egress counter that counts the number of good frames sent that
             have a Broadcast destination MAC address."
        ::= { exCMStatsEntry 29 }

    exCMPortOutMulticasts OBJECT-TYPE
        SYNTAX		Counter32
        MAX-ACCESS	read-only
        STATUS		current
        DESCRIPTION
            "An Egress counter that counts the number of good frames sent that
             have a Multicast destination MAC address. This count does not include
             frames counted in the exCMPortOutPauses or the exCMPortOutBroadcasts
             objects."
        ::= { exCMStatsEntry 30 }

    exCMPortOutPauses OBJECT-TYPE
        SYNTAX      Counter32
        MAX-ACCESS  read-only
        STATUS      current
        DESCRIPTION
            "An Egress counter that counts the number of good frames reachieved that
             have a Pause destination MAC address."
        ::= { exCMStatsEntry 31 }

    exCMPortDeferreds OBJECT-TYPE
        SYNTAX      Counter32
        MAX-ACCESS  read-only
        STATUS      current
        DESCRIPTION
            "An Egress counter that counts the number of successfully transmitted
             frames that experienced no collisions but are delayed because the
             medium was busy during the first attempt. This counter is applicable
             in half-duplex only."
        ::= { exCMStatsEntry 32 }

    exCMPortCollisions OBJECT-TYPE
        SYNTAX      Counter32
        MAX-ACCESS  read-only
        STATUS      current
        DESCRIPTION
            "An Egress counter that counts the number of collision events seen by
             the MAC not including those counted in exCMPortSingles,
             exCMPortMultiple , exCMPortExcessives or exCMPortLates objects.
             This counter is applicable in half-duplex only."
        ::= { exCMStatsEntry 33 }

    exCMPortSingles OBJECT-TYPE
        SYNTAX      Counter32
        MAX-ACCESS  read-only
        STATUS      current
        DESCRIPTION
            "An Egress counter that counts the number of successfully transmitted
             frames that experienced exactly one collision. This counter is
             applicable in half-duplex only."
        ::= { exCMStatsEntry 34 }

    exCMPortMultiples OBJECT-TYPE
        SYNTAX      Counter32
        MAX-ACCESS  read-only
        STATUS      current
        DESCRIPTION
            "An Egress counter that counts the number of successfully transmitted
             frames that experienced more than one collision. This counter is
             aplicable in half-duplex only."
        ::= { exCMStatsEntry 35 }

    exCMPortExcessives OBJECT-TYPE
        SYNTAX      Counter32
        MAX-ACCESS  read-only
        STATUS      current
        DESCRIPTION
            "An Egress counter that counts the number frames dropped in the transmit
             MAC because the frame experienced 16 consecutive collisions.  This
             counter is applicable in half-duplex only. "
        ::= { exCMStatsEntry 36 }

    exCMPortLates OBJECT-TYPE
        SYNTAX      Counter32
        MAX-ACCESS  read-only
        STATUS      current
        DESCRIPTION
            "An Egress counter that counts the number times a collision is detected
             later than 512 bits-times into the transmission of a frame. This
             counter is applicable in half-duplex only."
        ::= { exCMStatsEntry 37 }

    exCMPortOutFcsErrs OBJECT-TYPE
        SYNTAX      Counter32
        MAX-ACCESS  read-only
        STATUS      current
        DESCRIPTION
            "An Egress counter that counts the number frames transmitted with an
             invalid FCS. "
        ::= { exCMStatsEntry 38 }

    exCMPortResetCounters OBJECT-TYPE
        SYNTAX      YesNoValue
        MAX-ACCESS  read-write
        STATUS      current
        DESCRIPTION
            "Allows the resetting of all exCMStats statistical counters
             for this port. "
        ::= { exCMStatsEntry 39 }
--
-- end of exCMStatsTable
--

-- exCMStatsTable
--
exCMVdslStatsTable	OBJECT-TYPE
    SYNTAX		SEQUENCE OF ExCMVdslStatsEntry
    MAX-ACCESS	not-accessible
    STATUS		current
    DESCRIPTION
        "Table of CM-1110 type media converter module's configuration and status type
         information."
    ::= { exCM 5 }

    exCMVdslStatsEntry OBJECT-TYPE
        SYNTAX      ExCMVdslStatsEntry
        MAX-ACCESS  not-accessible
        STATUS      current
        DESCRIPTION
            "Entries of the table, each relating to a separate CM-1110 type
             media converter module."
        INDEX   { mcrChassisIndex, exCMVdslStatsSlotIndex, exCMVdslStatsMediaPortIndex, exCMVdslStatsTimePeriod }
        ::= { exCMVdslStatsTable 1 }

    ExCMVdslStatsEntry ::=
        SEQUENCE {
            exCMVdslStatsSlotIndex				SlotNumber,
            exCMVdslStatsMediaPortIndex         Unsigned32,
            exCMVdslStatsTimePeriod             INTEGER,
            
            exCMVdslStatsFullInitLocal            Integer32,
            exCMVdslStatsCodeViolationLocal       Integer32,
            exCMVdslStatsCorrectedLocal           Integer32,
            exCMVdslStatsFecSecsLocal             Integer32,
            exCMVdslStatsErroredSecsLocal         Integer32,
            exCMVdslStatsSeverelyErroredSecsLocal Integer32,
            exCMVdslStatsLossOfSignalSecsLocal    Integer32,
            exCMVdslStatsUnavailableSecsLocal     Integer32,
            exCMVdslStatsTimeElapsedLocal         Integer32,

            exCMVdslStatsFullInitRemote            Integer32,
            exCMVdslStatsCodeViolationRemote       Integer32,
            exCMVdslStatsCorrectedRemote           Integer32,
            exCMVdslStatsFecSecsRemote             Integer32,
            exCMVdslStatsErroredSecsRemote         Integer32,
            exCMVdslStatsSeverelyErroredSecsRemote Integer32,
            exCMVdslStatsLossOfSignalSecsRemote    Integer32,
            exCMVdslStatsUnavailableSecsRemote     Integer32,
            exCMVdslStatsTimeElapsedRemote         Integer32
        }

    exCMVdslStatsSlotIndex	OBJECT-TYPE
        SYNTAX		SlotNumber
        MAX-ACCESS	not-accessible
        STATUS		current
        DESCRIPTION
            "The Slot number the ex-1CM type module is currently inserted"
    ::= { exCMVdslStatsEntry 2 }

    exCMVdslStatsMediaPortIndex OBJECT-TYPE
        SYNTAX Unsigned32 
        MAX-ACCESS not-accessible
        STATUS current
        DESCRIPTION
            "Media converter module port index indicating which media port the statistical
             counters are associated with."
    ::= { exCMVdslStatsEntry 3 }

    exCMVdslStatsTimePeriod OBJECT-TYPE
        SYNTAX INTEGER {
            sinceLinkup(1),
            current15Minutes(2),
            previous15Minutes(3),
            current24Hours(4),
            previous24Hours(5)
        }
        MAX-ACCESS read-only
        STATUS current
        DESCRIPTION
            "Media converter module port index indicating which media port the statistical
             counters are associated with."
    ::= { exCMVdslStatsEntry 4 }

    exCMVdslStatsFullInitLocal OBJECT-TYPE
        SYNTAX      Integer32
        MAX-ACCESS  read-only
        STATUS      current
        DESCRIPTION
            "The VDSL port's fully initialized (local) count."
    ::= { exCMVdslStatsEntry 5 }

    exCMVdslStatsCodeViolationLocal OBJECT-TYPE
        SYNTAX      Integer32
        MAX-ACCESS  read-only
        STATUS      current
        DESCRIPTION
            "The VDSL port's code violation (local) count."
    ::= { exCMVdslStatsEntry 6 }

    exCMVdslStatsCorrectedLocal OBJECT-TYPE
        SYNTAX      Integer32
        MAX-ACCESS  read-only
        STATUS      current
        DESCRIPTION
            "The VDSL port's corrected (local) count."
    ::= { exCMVdslStatsEntry 7 }

    exCMVdslStatsFecSecsLocal OBJECT-TYPE
        SYNTAX      Integer32
        MAX-ACCESS  read-only
        STATUS      current
        DESCRIPTION
            "The VDSL port's forward error correction seconds (local) count."
    ::= { exCMVdslStatsEntry 8 }

    exCMVdslStatsErroredSecsLocal OBJECT-TYPE
        SYNTAX      Integer32
        MAX-ACCESS  read-only
        STATUS      current
        DESCRIPTION
            "The VDSL port's errored seconds (local) count."
    ::= { exCMVdslStatsEntry 9 }

    exCMVdslStatsSeverelyErroredSecsLocal OBJECT-TYPE
        SYNTAX      Integer32
        MAX-ACCESS  read-only
        STATUS      current
        DESCRIPTION
            "The VDSL port's severely errored seconds (local) count."
    ::= { exCMVdslStatsEntry 10 }

    exCMVdslStatsLossOfSignalSecsLocal OBJECT-TYPE
        SYNTAX      Integer32
        MAX-ACCESS  read-only
        STATUS      current
        DESCRIPTION
            "The VDSL port's loss of signal seconds (local) count."
    ::= { exCMVdslStatsEntry 11 }

    exCMVdslStatsUnavailableSecsLocal OBJECT-TYPE
        SYNTAX      Integer32
        MAX-ACCESS  read-only
        STATUS      current
        DESCRIPTION
            "The VDSL port's unavailable seconds (local) count."
    ::= { exCMVdslStatsEntry 12 }

    exCMVdslStatsTimeElapsedLocal OBJECT-TYPE
        SYNTAX      Integer32
        MAX-ACCESS  read-only
        STATUS      current
        DESCRIPTION
            "The VDSL port's elapsed time in seconds (local) count."
    ::= { exCMVdslStatsEntry 13 }

    exCMVdslStatsFullInitRemote OBJECT-TYPE
        SYNTAX      Integer32
        MAX-ACCESS  read-only
        STATUS      current
        DESCRIPTION
            "The VDSL port's fully initialized (remote) count."
    ::= { exCMVdslStatsEntry 14 }

    exCMVdslStatsCodeViolationRemote OBJECT-TYPE
        SYNTAX      Integer32
        MAX-ACCESS  read-only
        STATUS      current
        DESCRIPTION
            "The VDSL port's code violation (remote) count."
    ::= { exCMVdslStatsEntry 15 }

    exCMVdslStatsCorrectedRemote OBJECT-TYPE
        SYNTAX      Integer32
        MAX-ACCESS  read-only
        STATUS      current
        DESCRIPTION
            "The VDSL port's corrected (remote) count."
    ::= { exCMVdslStatsEntry 16 }

    exCMVdslStatsFecSecsRemote OBJECT-TYPE
        SYNTAX      Integer32
        MAX-ACCESS  read-only
        STATUS      current
        DESCRIPTION
            "The VDSL port's forward error correction seconds (remote) count."
    ::= { exCMVdslStatsEntry 17 }

    exCMVdslStatsErroredSecsRemote OBJECT-TYPE
        SYNTAX      Integer32
        MAX-ACCESS  read-only
        STATUS      current
        DESCRIPTION
            "The VDSL port's errored seconds (remote) count."
    ::= { exCMVdslStatsEntry 18 }

    exCMVdslStatsSeverelyErroredSecsRemote OBJECT-TYPE
        SYNTAX      Integer32
        MAX-ACCESS  read-only
        STATUS      current
        DESCRIPTION
            "The VDSL port's severely errored seconds (remote) count."
    ::= { exCMVdslStatsEntry 19 }

    exCMVdslStatsLossOfSignalSecsRemote OBJECT-TYPE
        SYNTAX      Integer32
        MAX-ACCESS  read-only
        STATUS      current
        DESCRIPTION
            "The VDSL port's loss of signal seconds (remote) count."
    ::= { exCMVdslStatsEntry 20 }

    exCMVdslStatsUnavailableSecsRemote OBJECT-TYPE
        SYNTAX      Integer32
        MAX-ACCESS  read-only
        STATUS      current
        DESCRIPTION
            "The VDSL port's unavailable seconds (remote) count."
    ::= { exCMVdslStatsEntry 21 }

    exCMVdslStatsTimeElapsedRemote OBJECT-TYPE
        SYNTAX      Integer32
        MAX-ACCESS  read-only
        STATUS      current
        DESCRIPTION
            "The VDSL port's elapsed time in seconds (remote) count."
    ::= { exCMVdslStatsEntry 22 }

--
-- exCMAvctTable
--
exCMAvctTable	OBJECT-TYPE
    SYNTAX		SEQUENCE OF ExCMAvctEntry
    MAX-ACCESS	not-accessible
    STATUS		current
    DESCRIPTION
        "Table of ex-CM media converter modules."
    ::= { exCM 6 }

    exCMAvctEntry OBJECT-TYPE
        SYNTAX      ExCMAvctEntry
        MAX-ACCESS  not-accessible
        STATUS      current
        DESCRIPTION
            "Entries of the table, each relating to a copper Ethernet
             port on the eX-CM type media converter module."
        INDEX   { mcrChassisIndex, exCMAvctSlotIndex }
        ::= { exCMAvctTable 1 }

    ExCMAvctEntry ::=
        SEQUENCE {
            exCMAvctSlotIndex					SlotNumber,
            exCMAvctStart						YesNoValue,
            exCMAvctStatus						INTEGER,
            exCMAvctTxRxPair1Results			INTEGER,
            exCMAvctTxRxPair1Amplitude		DisplayString,
            exCMAvctTxRxPair1Distance		DisplayString,
            exCMAvctTxRxPair2Results			INTEGER,
            exCMAvctTxRxPair2Amplitude		DisplayString,
            exCMAvctTxRxPair2Distance		DisplayString,
            exCMAvctTxRxPair3Results			INTEGER,
            exCMAvctTxRxPair3Amplitude		DisplayString,
            exCMAvctTxRxPair3Distance		DisplayString,
            exCMAvctTxRxPair4Results			INTEGER,
            exCMAvctTxRxPair4Amplitude		DisplayString,
            exCMAvctTxRxPair4Distance		DisplayString
        }

    exCMAvctSlotIndex	OBJECT-TYPE
        SYNTAX		SlotNumber
        MAX-ACCESS	not-accessible
        STATUS		current
        DESCRIPTION
            "The Slot number the eX-CM type module is currently inserted"
    ::= { exCMAvctEntry 2 }

    exCMAvctStart OBJECT-TYPE
        SYNTAX YesNoValue
        MAX-ACCESS read-write
        STATUS current
        DESCRIPTION
            "Set this self-clearing variable to yes initiate the Advanced Virtual
             Cable Test. Note: During the test, no network data will be passed. "
        ::= { exCMAvctEntry 3 }

    exCMAvctStatus OBJECT-TYPE
        SYNTAX INTEGER {
            notStarted(0),
            inProgress(1),
            testComplete(2)
        }
        MAX-ACCESS read-only
        STATUS current
        DESCRIPTION
            "This object identifies the state of the Advanced Virtual Cable Tester. "
        ::= { exCMAvctEntry 4 }

    exCMAvctTxRxPair1Results OBJECT-TYPE
        SYNTAX INTEGER {
            normal(0),
            shortDetected(1),
            openDetected(2),
            testFailed(3)
        }
        MAX-ACCESS read-only
        STATUS current
        DESCRIPTION
            "Test result code returned from Virtual Cable Test of the Tx/Rx
             pair one."
        ::= { exCMAvctEntry 5 }

    exCMAvctTxRxPair1Amplitude OBJECT-TYPE
        SYNTAX DisplayString(SIZE(0..20))
        MAX-ACCESS read-only
        STATUS current
        DESCRIPTION
            "Amplitude of Tx/Rx pair one in millivolts when test result codes is
             short or open."
        ::= { exCMAvctEntry 6 }

    exCMAvctTxRxPair1Distance OBJECT-TYPE
        SYNTAX		DisplayString(SIZE(0..20))
        MAX-ACCESS read-only
        STATUS current
        DESCRIPTION
            "Distance in meters to fault when test result codes for Tx/Rx pair
             one is short or open. "
        ::= { exCMAvctEntry 7 }

    exCMAvctTxRxPair2Results OBJECT-TYPE
        SYNTAX INTEGER {
            normal(0),
            shortDetected(1),
            openDetected(2),
            testFailed(3)
        }
        MAX-ACCESS read-only
        STATUS current
        DESCRIPTION
            "Test result code returned from Virtual Cable Test of the Tx/Rx
             pair two."
        ::= { exCMAvctEntry 8 }

    exCMAvctTxRxPair2Amplitude OBJECT-TYPE
        SYNTAX DisplayString(SIZE(0..20))
        MAX-ACCESS read-only
        STATUS current
        DESCRIPTION
            "Amplitude of Tx/Rx pair two in millivolts when test result codes is
             short or open."
        ::= { exCMAvctEntry 9 }

    exCMAvctTxRxPair2Distance OBJECT-TYPE
        SYNTAX		DisplayString(SIZE(0..20))
        MAX-ACCESS read-only
        STATUS current
        DESCRIPTION
            "Distance in meters to fault when test result codes for Tx/Rx pair
             two is short or open. "
        ::= { exCMAvctEntry 10 }

    exCMAvctTxRxPair3Results OBJECT-TYPE
        SYNTAX INTEGER {
            normal(0),
            shortDetected(1),
            openDetected(2),
            testFailed(3)
        }
        MAX-ACCESS read-only
        STATUS current
        DESCRIPTION
            "Test result code returned from Virtual Cable Test of the Tx/Rx
             pair three."
        ::= { exCMAvctEntry 11 }

    exCMAvctTxRxPair3Amplitude OBJECT-TYPE
        SYNTAX DisplayString(SIZE(0..20))
        MAX-ACCESS read-only
        STATUS current
        DESCRIPTION
            "Amplitude of Tx/Rx pair three in millivolts when test result codes is
             short or open."
        ::= { exCMAvctEntry 12 }

    exCMAvctTxRxPair3Distance OBJECT-TYPE
        SYNTAX		DisplayString(SIZE(0..20))
        MAX-ACCESS read-only
        STATUS current
        DESCRIPTION
            "Distance in meters to fault when test result codes for Tx/Rx pair
             three is short or open. "
        ::= { exCMAvctEntry 13 }

    exCMAvctTxRxPair4Results OBJECT-TYPE
        SYNTAX INTEGER {
            normal(0),
            shortDetected(1),
            openDetected(2),
            testFailed(3)
        }
        MAX-ACCESS read-only
        STATUS current
        DESCRIPTION
            "Test result code returned from Virtual Cable Test of Tx/Rx
             pair four."
        ::= { exCMAvctEntry 14 }

    exCMAvctTxRxPair4Amplitude OBJECT-TYPE
        SYNTAX DisplayString(SIZE(0..20))
        MAX-ACCESS read-only
        STATUS current
        DESCRIPTION
            "Amplitude of Tx/Rx pair four in millivolts when test result codes is
             short or open."
        ::= { exCMAvctEntry 15 }

    exCMAvctTxRxPair4Distance OBJECT-TYPE
        SYNTAX		DisplayString(SIZE(0..20))
        MAX-ACCESS read-only
        STATUS current
        DESCRIPTION
            "Distance in meters to fault when test result codes for Tx/Rx pair
             four is short or open. "
        ::= { exCMAvctEntry 16 }

--
-- exCMAvctTable
--
--
-- end of exCM
--

-- cm10gt - 10 Gb fixed media Converter type modules
--
cm10gt	OBJECT IDENTIFIER ::= { mcrModuleTypes 10 }

--
-- cm10gtTable
--
cm10gtTable	OBJECT-TYPE
    SYNTAX		SEQUENCE OF Cm10gtEntry
    MAX-ACCESS	not-accessible
    STATUS		current
    DESCRIPTION
        "Table of CM-10G type media converter module's status type information."
    ::= { cm10gt 1 }

    cm10gtEntry OBJECT-TYPE
        SYNTAX      Cm10gtEntry
        MAX-ACCESS  not-accessible
        STATUS      current
        DESCRIPTION
            "Entries of the table, each relating to a separate CM-10G type
             media converter module."
        INDEX   { mcrChassisIndex, cm10gtSlotIndex }
        ::= { cm10gtTable 1 }

    Cm10gtEntry ::=
        SEQUENCE {
            cm10gtSlotIndex				SlotNumber,
            cm10gtModelname				DisplayString,
            cm10gtModelDesc				DisplayString,
            cm10gtHwJmp5ConfigMode		INTEGER,
            cm10gtHwSw1OperationMode		INTEGER,
            cm10gtHwSw2LinkMode			INTEGER,
            cm10gtHwSw3FiberFaultAlert	INTEGER,
            cm10gtHwSw4EnergyEfficentEthernet		INTEGER,
            cm10gtHwSw5Unused		INTEGER,

            cm10gtPort1LinkStatus		INTEGER,
            cm10gtPort1ConnType			INTEGER,
            cm10gtPort1AutoNegState		INTEGER,
            cm10gtPort1Speed				INTEGER,
            cm10gtPort1Duplex			INTEGER,
            cm10gtPort1PauseEnh			INTEGER,
            cm10gtPort1ReceiveStatus		INTEGER,
            cm10gtPort1LPRFStatus			INTEGER,

            cm10gtPort2LinkStatus		INTEGER,
            cm10gtPort2ConnType			INTEGER,
            cm10gtPort2AutoNegState		INTEGER,
            cm10gtPort2Speed				INTEGER,
            cm10gtPort2Duplex			INTEGER,
            cm10gtPort2PauseEnh			INTEGER,
            cm10gtPort2LPRFStatus			INTEGER,

            cm10gtPortLoopBack			INTEGER,
            
            cm10gtPortTestMode           INTEGER
        }

    cm10gtSlotIndex	OBJECT-TYPE
        SYNTAX		SlotNumber
        MAX-ACCESS	not-accessible
        STATUS		current
        DESCRIPTION
            "The Slot number the CM-10G type module is currently inserted"
        ::= { cm10gtEntry 2 }

    cm10gtModelname	OBJECT-TYPE
        SYNTAX		DisplayString
        MAX-ACCESS	read-only
        STATUS		current
        DESCRIPTION
            "This object identifies the model of media converter module present in the
             chassis"
        ::= { cm10gtEntry 3 }

    cm10gtModelDesc		OBJECT-TYPE
        SYNTAX		DisplayString
        MAX-ACCESS	read-only
        STATUS		current
        DESCRIPTION
            "This object identifies a static description of the media converter module present
             in the chassis"
        ::= { cm10gtEntry 4 }

    cm10gtHwJmp5ConfigMode		OBJECT-TYPE
        SYNTAX		INTEGER {
            hardwareSwitches(0),
            auto(1)
        }
        MAX-ACCESS	read-only
        STATUS		current
        DESCRIPTION
            "This object identifies the media converter module's ConfigMode, set by hardware
             jumper J5 on the media converter module. When this object is set to
             hardwareSwitches(0), the media converter module will disable configuration
             control from the management module's software and all configuration
             control comes from the media converter module's hardware switches or jumpers. "
        ::= { cm10gtEntry 5 }


    cm10gtHwSw1OperationMode  OBJECT-TYPE
        SYNTAX 		INTEGER{
            test(0),
            data(1)
        }
        MAX-ACCESS read-only
        STATUS 		current
        DESCRIPTION
            "Media converter module's current switch setting for operation mode.
            Data mode is for normal data transmission."
        ::= { cm10gtEntry 6 }

    cm10gtHwSw2LinkMode OBJECT-TYPE
        SYNTAX 		INTEGER {
            swDownSmartLinkPassthrough(0),
            swUpStandard(1)
        }
        MAX-ACCESS read-only
        STATUS 		current
        DESCRIPTION
            "Media converter module's current switch setting for Link Mode. If 
            the Operation switch is set to Test, then this object indicates 
            whether the port is in loopback or performing the build in link-test."
        ::= { cm10gtEntry 7 }

    cm10gtHwSw3FiberFaultAlert OBJECT-TYPE
        SYNTAX 		INTEGER {
            swDownDisabled(0),
            swUpEnabled(1)
        }
        MAX-ACCESS read-only
        STATUS 		current
        DESCRIPTION
            "Media converter module's current switch setting for Fiber Fault 
            Alert.  If the Operation switch is set to Test, then this object 
            indicates which port is in test mode"
        ::= { cm10gtEntry 8 }

    cm10gtHwSw4EnergyEfficentEthernet OBJECT-TYPE
        SYNTAX 		INTEGER {
            disabled(0),
            enabled(1)
        }
        MAX-ACCESS read-only
        STATUS 		current
        DESCRIPTION
            "This object indicates the current switch setting for Energy Efficient
            Ethernet on port 2." 
        ::= { cm10gtEntry 9 }

    cm10gtHwSw5Unused OBJECT-TYPE
        SYNTAX 		INTEGER {
            disabled(0),
            enabled(1)
        }
        MAX-ACCESS read-only
        STATUS 		current
        DESCRIPTION
            "This object indicates the current switch setting for dip switch 5,
             which is unused." 
        ::= { cm10gtEntry 10 }

    cm10gtPort1LinkStatus OBJECT-TYPE
        SYNTAX 		INTEGER {
            down(0),
            up(1),
            shutdown(2)
        }
        MAX-ACCESS read-only
        STATUS 		current
        DESCRIPTION
            "Media converter module's current fiber link status (port 1)."
        ::= { cm10gtEntry 11 }

    cm10gtPort1ConnType OBJECT-TYPE
        SYNTAX 		INTEGER {
            sc(0),
            lc(1),
            st(2),
            sfp(3),
            fc(5),
            mtrj(6),
            xfp(7),
            sfpPlus(8)
        }
        MAX-ACCESS read-only
        STATUS 		current
        DESCRIPTION
            "Media converter module's fiber port connector type (port 1)."
        ::= { cm10gtEntry 12 }

    cm10gtPort1AutoNegState OBJECT-TYPE
        SYNTAX		INTEGER {
            disabled(0),
            complete(1),
            inProgress(2)
        }
        MAX-ACCESS	read-only
        STATUS 		current
        DESCRIPTION
            "Media converter module's current fiber auto-negotiation state (port 1)."
        ::= { cm10gtEntry 13 }

    cm10gtPort1Speed OBJECT-TYPE
        SYNTAX 		INTEGER {
            speed10Mbps(0),
            speed100Mbps(1),
            speed1000Mbps(2),
            speed10Gbps(3)
        }
        MAX-ACCESS	read-only
        STATUS 		current
        DESCRIPTION
            "Media converter module's fiber port speed in megabits per second (port 1)."
        ::= { cm10gtEntry 14 }

    cm10gtPort1Duplex OBJECT-TYPE
        SYNTAX		INTEGER {
            half(0),
            full(1)
        }
        MAX-ACCESS	read-only
        STATUS		current
        DESCRIPTION
            "If fiber auto-negotiation state is complete then this object
            indicates the media converter module's current fiber auto-negotiated duplex
            setting. If auto-negotiation is not complete then the value returned should be
             ignored. (Port 1)"
        ::= { cm10gtEntry 15 }

    cm10gtPort1PauseEnh OBJECT-TYPE
        SYNTAX INTEGER {
            disabled(0),
            symmetrical(1),
            asymmetricalTx(2),
            asymmetricalRx(3)
        }
        MAX-ACCESS read-only
        STATUS current
        DESCRIPTION
            "If fiber auto-negotiation state is complete then this object indicates
             the media converter module's current fiber auto-negotiated pause setting. If
             auto-negotiation is not complete then the value returned should be ignored.
             (Port 1)"
        ::= { cm10gtEntry 16 }

    cm10gtPort1ReceiveStatus		OBJECT-TYPE
        SYNTAX	INTEGER {
            fault(0),
            ok(1)
        }
        MAX-ACCESS	read-only
        STATUS	current
        DESCRIPTION
            "This object identifies the status of whether light is being received
             on the fiber port (port 1)"
        ::= { cm10gtEntry 17 }

    cm10gtPort1LPRFStatus OBJECT-TYPE
        SYNTAX INTEGER {
            notApplicable(-1),
            ok(0),
            offline(1),
            linkFault(2),
            autoNegError(3)
        }
        MAX-ACCESS read-only
        STATUS current
        DESCRIPTION
            "Media converter module's Link Partner Remote Fault status (port 1).  This object
             only applies to SFP modules running at 1G, with auto-negotiation enabled."
    ::= { cm10gtEntry 18 }

    cm10gtPort2LinkStatus OBJECT-TYPE
        SYNTAX 		INTEGER {
            down(0),
            up(1),
            shutdown(2)
        }
        MAX-ACCESS read-only
        STATUS 		current
        DESCRIPTION
            "Media converter module's current fiber link status (port 2)."
        ::= { cm10gtEntry 19 }

    cm10gtPort2ConnType OBJECT-TYPE
        SYNTAX 		INTEGER {
            rj45(4)
        }
        MAX-ACCESS read-only
        STATUS 		current
        DESCRIPTION
            "Media converter module's fiber port connector type (port 2)."
        ::= { cm10gtEntry 20 }

    cm10gtPort2AutoNegState OBJECT-TYPE
        SYNTAX		INTEGER {
            disabled(0),
            complete(1),
            inProgress(2)
        }
        MAX-ACCESS	read-only
        STATUS 		current
        DESCRIPTION
            "Media converter module's current fiber auto-negotiation state (port 2)."
        ::= { cm10gtEntry 21 }

    cm10gtPort2Speed OBJECT-TYPE
        SYNTAX 		INTEGER {
            speed10Mbps(0),
            speed100Mbps(1),
            speed1000Mbps(2),
            speed10Gbps(3)
        }
        MAX-ACCESS	read-only
        STATUS 		current
        DESCRIPTION
            "Media converter module's fiber port speed in megabits per second (port 2)."
        ::= { cm10gtEntry 22 }

    cm10gtPort2Duplex OBJECT-TYPE
        SYNTAX		INTEGER {
            half(0),
            full(1)
        }
        MAX-ACCESS	read-only
        STATUS		current
        DESCRIPTION
            "If fiber auto-negotiation state is complete then this object
            indicates the media converter module's current fiber auto-negotiated duplex
            setting. If auto-negotiation is not complete then the value returned should be
             ignored. (Port 2)"
        ::= { cm10gtEntry 23 }

    cm10gtPort2PauseEnh OBJECT-TYPE
        SYNTAX INTEGER {
            disabled(0),
            symmetrical(1),
            asymmetricalTx(2),
            asymmetricalRx(3)
        }
        MAX-ACCESS read-only
        STATUS current
        DESCRIPTION
            "If fiber auto-negotiation state is complete then this object indicates
             the media converter module's current fiber auto-negotiated pause setting. If
             auto-negotiation is not complete then the value returned should be ignored.
             (Port 2)"
        ::= { cm10gtEntry 24 }

    cm10gtPort2LPRFStatus OBJECT-TYPE
        SYNTAX INTEGER {
            ok(0),
            remoteFault(1)
        }
        MAX-ACCESS read-only
        STATUS current
        DESCRIPTION
            "Media converter module's copper Link Partner Remote Fault status."
    ::= { cm10gtEntry 25 }
    

    cm10gtPortLoopBack		OBJECT-TYPE
        SYNTAX	INTEGER {
            disabled(0),
            port1(1),
            port2(2)
        }
        MAX-ACCESS	read-write
        STATUS	current
        DESCRIPTION
            "Media converter module's current port loopback mode setting. Writing to this
             object will change the current settings. This object is read-only if
             the media converter module's ConfigMode jumper is set to hardwareSwitches(0)."
        ::= { cm10gtEntry 26 }

    cm10gtPortTestMode	OBJECT-TYPE
        SYNTAX	INTEGER {
            disabled(0),
            port1(1)
        }
        MAX-ACCESS	read-only
        STATUS	current
        DESCRIPTION
            "Media converter module's current port test mode setting."
        ::= { cm10gtEntry 27 }
--
-- cm10gtTable
--
--
-- cm10gtConfigTable
--
cm10gtConfigTable	OBJECT-TYPE
    SYNTAX		SEQUENCE OF Cm10gtConfigEntry
    MAX-ACCESS	not-accessible
    STATUS		current
    DESCRIPTION
        "Table of CM-10G type media converter module's configuration type information."
    ::= { cm10gt 2 }

    cm10gtConfigEntry OBJECT-TYPE
        SYNTAX      Cm10gtConfigEntry
        MAX-ACCESS  not-accessible
        STATUS      current
        DESCRIPTION
            "Entries of the table, each relating to a separate CM-10G type
             media converter module."
        INDEX   { mcrChassisIndex, cm10gtConfigSlotIndex }
        ::= { cm10gtConfigTable 1 }

    Cm10gtConfigEntry ::=
        SEQUENCE {
            cm10gtConfigSlotIndex                SlotNumber,
            cm10gtConfigStatus                   ContainerStatus,
            cm10gtConfigModuleName               DisplayString,
            cm10gtConfigLinkMode                 INTEGER,
            cm10gtConfigFiberFaultAlert          EnableDisableValue,
            cm10gtConfigFiberAutoNeg             EnableDisableValue,
            cm10gtConfigPort1Name                DisplayString,
            cm10gtConfigPort1Enable              YesNoValue,
            cm10gtConfigPort1FecEnable           YesNoValue,
            cm10gtConfigPort1FecAmplitude        INTEGER,
            cm10gtConfigPort1FecPhase            INTEGER,
            cm10gtConfigPort1WavelengthEnable    YesNoValue,
            cm10gtConfigPort1WavelengthValue     INTEGER,
            cm10gtConfigPort1ChannelEnable       YesNoValue,
            cm10gtConfigPort1ChannelNumber       INTEGER,
            cm10gtConfigPort1TxDitherEnable      YesNoValue,
            cm10gtConfigPort1TxDitherValue       EnableDisableValue,
            
            cm10gtConfigPort2Name                DisplayString,
            cm10gtConfigPort2Enable              YesNoValue,
            cm10gtConfigPort2CopperDuplex		INTEGER,
            cm10gtConfigPort2CopperPauseEnh		INTEGER,
            cm10gtConfigPort2CopperEnergyEfficientEthernet		OnOffValue
        }

    cm10gtConfigSlotIndex	OBJECT-TYPE
        SYNTAX		SlotNumber
        MAX-ACCESS	not-accessible
        STATUS		current
        DESCRIPTION
            "The Slot number the CM-10G type module is currently inserted"
    ::= { cm10gtConfigEntry 2 }

    cm10gtConfigStatus OBJECT-TYPE
        SYNTAX      ContainerStatus
        MAX-ACCESS  read-write
        STATUS      current
        DESCRIPTION
          "When you perform a GET on this variable, one of
            the following values will be returned:
            1-Indicates that the container folder is active with no changes.
            2-Indicates that the container folder is active with change(s).
            Once you have completed setting the variables in a folder, you
            will want to submit your changes to the management module. To do
            this, set the Status variable to 4. If you want to discard the
            changes, set the Status variable to 6.
            4-Indicates that the changes in the container folder are to be
              submitted to the management module, verified and and saved to flash.
            6-Indicates that the changes in the container folder are to be
              discarded."
        ::= { cm10gtConfigEntry 3 }

    cm10gtConfigModuleName OBJECT-TYPE
        SYNTAX		DisplayString(SIZE(0..63))
        MAX-ACCESS	read-write
        STATUS		current
        DESCRIPTION
            "This object identifies a user configurable name for the media converter module
             present in the chassis. "
        ::= { cm10gtConfigEntry 4 }

    cm10gtConfigLinkMode OBJECT-TYPE
        SYNTAX		INTEGER {
            standard(0),
            smartLinkPassthrough(1)
        }
        MAX-ACCESS	read-write
        STATUS		current
        DESCRIPTION
            "This object identifies the Link Mode for the media converter module. This object
            is read-only if the media converter module's ConfigMode jumper is set to
            hardwareSwitches(0)."
        ::= { cm10gtConfigEntry 5 }

    cm10gtConfigFiberFaultAlert	OBJECT-TYPE
        SYNTAX		EnableDisableValue
        MAX-ACCESS	read-write
        STATUS		current
        DESCRIPTION
            "This object identifies the Fiber Fault Alert setting for the media
             module. This object is read-only if the media converter module's ConfigMode
             jumper is set to hardwareSwitches(0). "
        ::= { cm10gtConfigEntry 6 }

    cm10gtConfigFiberAutoNeg OBJECT-TYPE
        SYNTAX 		EnableDisableValue
        MAX-ACCESS	read-write
        STATUS 		current
        DESCRIPTION
            "This object identifies the wither fiber auto-negotiation  is
             enabled for both ports. This only applies if 1G SFP modules are in
             use. This object is read-only if the media module's ConfigMode 
             jumper is set to hardwareSwitches(0)."
        ::= { cm10gtConfigEntry 7 }

    cm10gtConfigPort1Name OBJECT-TYPE
        SYNTAX		DisplayString(SIZE(0..8))
        MAX-ACCESS	read-write
        STATUS 		current
        DESCRIPTION
            "This object identifies a user definable name for port 1."
        ::= { cm10gtConfigEntry 8 }

    cm10gtConfigPort1Enable OBJECT-TYPE
        SYNTAX		YesNoValue
        MAX-ACCESS	read-write
        STATUS 		current
        DESCRIPTION
            "This object identifies whether port 1 is enabled."
        ::= { cm10gtConfigEntry 9 }

    cm10gtConfigPort1FecEnable  OBJECT-TYPE
        SYNTAX 		YesNoValue
        MAX-ACCESS	read-write
        STATUS 		current
        DESCRIPTION
            "This object identifies the whether FEC control is enabled for this 
            port.  This config option only applies for an XFP module. This 
            object is read-only if the media module's ConfigMode jumper is set 
            to hardwareSwitches(0)."
        ::= { cm10gtConfigEntry 10 }
    
    cm10gtConfigPort1FecAmplitude OBJECT-TYPE
        SYNTAX      INTEGER(-128..127)
        MAX-ACCESS	read-write
        STATUS		current
        DESCRIPTION
            "This object identifies the FEC Amplitude value for this port. This 
            config option only applies for an XFP module. This object is 
            read-only if the media converter module's ConfigMode jumper is set to
            hardwareSwitches(0)."
        ::= { cm10gtConfigEntry 11 }

    cm10gtConfigPort1FecPhase OBJECT-TYPE
        SYNTAX      INTEGER(-128..127)
        MAX-ACCESS	read-write
        STATUS		current
        DESCRIPTION
            "This object identifies the FEC phase value for this port. This 
            config option only applies for an XFP module. This object is 
            read-only if the media converter module's ConfigMode jumper is set to
            hardwareSwitches(0)."
        ::= { cm10gtConfigEntry 12 }

    cm10gtConfigPort1WavelengthEnable OBJECT-TYPE
        SYNTAX 		YesNoValue
        MAX-ACCESS	read-write
        STATUS 		current
        DESCRIPTION
            "This object identifies whether Wavelength fine tuning is enabled for
            this port. This object is read-only if the media module's ConfigMode 
            jumper is set to hardwareSwitches(0)."
        ::= { cm10gtConfigEntry 13 }
  
    cm10gtConfigPort1WavelengthValue OBJECT-TYPE
        SYNTAX		INTEGER(0..65535)
        MAX-ACCESS	read-write
        STATUS		current
        DESCRIPTION
            "This object identifies Wavelength fine tuning value for this port.
            This object is read-only if the media converter module's ConfigMode 
            jumper is set to hardwareSwitches(0)."
        ::= { cm10gtConfigEntry 14 }

    cm10gtConfigPort1ChannelEnable  OBJECT-TYPE
        SYNTAX 		YesNoValue
        MAX-ACCESS	read-write
        STATUS 		current
        DESCRIPTION
            "This object identifies whether channel number fine tuning is enabled
            for this port. This object is read-only if the media module's 
            ConfigMode jumper is set to hardwareSwitches(0)."
        ::= { cm10gtConfigEntry 15 }
     
    cm10gtConfigPort1ChannelNumber OBJECT-TYPE
        SYNTAX		INTEGER(1..65535)
        MAX-ACCESS	read-write
        STATUS		current
        DESCRIPTION
            "This object identifies the channel number fine tuning value for this
            port. This object is read-only if the media converter module's 
            ConfigMode jumper is set to hardwareSwitches(0)."
        ::= { cm10gtConfigEntry 16 }

    cm10gtConfigPort1TxDitherEnable OBJECT-TYPE
        SYNTAX 		YesNoValue
        MAX-ACCESS	read-write
        STATUS 		current
        DESCRIPTION
            "This object identifies the whether TX Dither control is enabled on
            this port. If not enabled the default TX Dither value will be used.
            This object is read-only if the media module's ConfigMode jumper is 
            set to hardwareSwitches(0)."
        ::= { cm10gtConfigEntry 17 }
    
    cm10gtConfigPort1TxDitherValue OBJECT-TYPE
        SYNTAX 		EnableDisableValue
        MAX-ACCESS	read-write
        STATUS 		current
        DESCRIPTION
            "This object identifies the whether TX Dither is enabled for this 
             port. This object is read-only if the media module's ConfigMode 
             jumper is set to hardwareSwitches(0)."
        ::= { cm10gtConfigEntry 18 }

     
    cm10gtConfigPort2Name OBJECT-TYPE
        SYNTAX		DisplayString(SIZE(0..8))
        MAX-ACCESS	read-write
        STATUS 		current
        DESCRIPTION
            "This object identifies a user definable name for port 2."
        ::= { cm10gtConfigEntry 19 }

    cm10gtConfigPort2Enable OBJECT-TYPE
        SYNTAX		YesNoValue
        MAX-ACCESS	read-write
        STATUS 		current
        DESCRIPTION
            "This object identifies whether port 2 is enabled."
        ::= { cm10gtConfigEntry 20 }

    cm10gtConfigPort2CopperDuplex	OBJECT-TYPE
        SYNTAX INTEGER {
            half(1),
            auto(2)
        }
        MAX-ACCESS read-write
        STATUS current
        DESCRIPTION
            "This object identifies the duplex settings for the copper port."
    ::= { cm10gtConfigEntry 21 }

    cm10gtConfigPort2CopperPauseEnh OBJECT-TYPE
        SYNTAX INTEGER {
            disabled(0),
            symmetrical(1),
            asymmetricalTx(2),
            symmAsymRx(3)
        }
        MAX-ACCESS read-write
        STATUS current
        DESCRIPTION
            "This object identifies the copper pause (flow control) setting that
             is a advertised. The settings can be disabled, advertise symmetrical,
             advertise asymmetrical TX or advertise symmetrical and asymmetrical
             RX."
    ::= { cm10gtConfigEntry 22 }

    cm10gtConfigPort2CopperEnergyEfficientEthernet OBJECT-TYPE
        SYNTAX OnOffValue
        MAX-ACCESS read-write
        STATUS current
        DESCRIPTION
            "This object identifies the copper Energy-Efficient Ethernet setting for the media converter module
             present in the chassis. "
    ::= { cm10gtConfigEntry 23 }


--
-- cm10gtConfigTable
--

--
-- cm10gtLedTable
--
cm10gtLedTable	OBJECT-TYPE
    SYNTAX		SEQUENCE OF Cm10gtLedEntry
    MAX-ACCESS	not-accessible
    STATUS		current
    DESCRIPTION
        "Table of CM-10G type media converter module's LED status information."
    ::= { cm10gt 3 }

    cm10gtLedEntry OBJECT-TYPE
        SYNTAX      Cm10gtLedEntry
        MAX-ACCESS  not-accessible
        STATUS      current
        DESCRIPTION
            "Entries of the table, each relating to a separate CM-10G type
             media converter module."
        INDEX   { mcrChassisIndex, cm10gtLedsSlotIndex }
        ::= { cm10gtLedTable 1 }

    Cm10gtLedEntry ::=
        SEQUENCE {
            cm10gtLedsSlotIndex	SlotNumber,
            cm10gtLedPWR			INTEGER,
            cm10gtLedLK1			INTEGER,
            cm10gtLedLK2			INTEGER
        }

    cm10gtLedsSlotIndex	OBJECT-TYPE
        SYNTAX		SlotNumber
        MAX-ACCESS	read-only
        STATUS		current
        DESCRIPTION
            "The Slot number the CM-10G type module is currently inserted"
    ::= { cm10gtLedEntry 2 }

    cm10gtLedPWR	OBJECT-TYPE
        SYNTAX		INTEGER {
            off(0),
            onGreen(1),
            blinking(2)
        }
        MAX-ACCESS	read-only
        STATUS		current
        DESCRIPTION
            "This object identifies the status of the power (PWR) LED on the media converter module.
             Possible status values are:
                 off(0) - No power to the module
                 onGreen(1) - Power being applied to module
                 blinking(2) - Loopback or Link-Test enabled"
    ::= { cm10gtLedEntry 3 }

    cm10gtLedLK1	OBJECT-TYPE
        SYNTAX		INTEGER {
            off(0),
            on(1)
        }
        MAX-ACCESS	read-only
        STATUS		current
        DESCRIPTION
            "This object identifies the status of the port 1 link (LK1) LED on the
             media converter module.
             Possible status values are:
                 off(0) - No link
                 on(1) - Port link present"
    ::= { cm10gtLedEntry 4 }

    cm10gtLedLK2	OBJECT-TYPE
        SYNTAX		INTEGER {
            off(0),
            on(1)
        }
        MAX-ACCESS	read-only
        STATUS		current
        DESCRIPTION
            "This object identifies the status of the port 2 link (LK2) LED on the
             media converter module.
             Possible status values are:
                 off(0) - No link
                 on(1) - Port link present"
    ::= { cm10gtLedEntry 5 }

--
-- end of cm10gtLedTable
--

-- cm4gpt - CM-4GPT media Converter type modules
--
cm4gpt	OBJECT IDENTIFIER ::= { mcrModuleTypes 11 }

--
-- cm4gptTable
--
cm4gptTable	OBJECT-TYPE
    SYNTAX		SEQUENCE OF Cm4gptEntry
    MAX-ACCESS	not-accessible
    STATUS		current
    DESCRIPTION
        "Table of CM-4GPT type media converter module's status type information."
    ::= { cm4gpt 1 }

    cm4gptEntry OBJECT-TYPE
        SYNTAX      Cm4gptEntry
        MAX-ACCESS  not-accessible
        STATUS      current
        DESCRIPTION
            "Entries of the table, each relating to a separate CM-4GPT type
             media converter module."
        INDEX   { mcrChassisIndex, cm4gptSlotIndex }
        ::= { cm4gptTable 1 }

    Cm4gptEntry ::=
        SEQUENCE {
            cm4gptSlotIndex				SlotNumber,
            cm4gptModelname				DisplayString,
            cm4gptModelDesc				DisplayString,
            cm4gptHwJmp5ConfigMode		INTEGER,
            cm4gptHwSw1LinkMode		INTEGER,
            cm4gptHwSw2FiberFaultAlert			INTEGER,
            cm4gptHwSw3RateSelect	INTEGER,
            cm4gptHwSw4Unused		INTEGER,

            cm4gptPort1LinkStatus		INTEGER,
            cm4gptPort1ConnType			INTEGER,

            cm4gptPort2LinkStatus		INTEGER,
            cm4gptPort2ConnType			INTEGER
        }

    cm4gptSlotIndex	OBJECT-TYPE
        SYNTAX		SlotNumber
        MAX-ACCESS	not-accessible
        STATUS		current
        DESCRIPTION
            "The Slot number the CM-4GPT type module is currently inserted"
        ::= { cm4gptEntry 2 }

    cm4gptModelname	OBJECT-TYPE
        SYNTAX		DisplayString
        MAX-ACCESS	read-only
        STATUS		current
        DESCRIPTION
            "This object identifies the model of media converter module present in the
             chassis"
        ::= { cm4gptEntry 3 }

    cm4gptModelDesc		OBJECT-TYPE
        SYNTAX		DisplayString
        MAX-ACCESS	read-only
        STATUS		current
        DESCRIPTION
            "This object identifies a static description of the media converter module present
             in the chassis"
        ::= { cm4gptEntry 4 }

    cm4gptHwJmp5ConfigMode		OBJECT-TYPE
        SYNTAX		INTEGER {
            hardwareSwitches(0),
            auto(1)
        }
        MAX-ACCESS	read-only
        STATUS		current
        DESCRIPTION
            "This object identifies the media converter module's ConfigMode, set by hardware
             jumper J5 on the media converter module. When this object is set to
             hardwareSwitches(0), the media converter module will disable configuration
             control from the management module's software and all configuration
             control comes from the media converter module's hardware switches or jumpers. "
        ::= { cm4gptEntry 5 }


    cm4gptHwSw1LinkMode OBJECT-TYPE
        SYNTAX 		INTEGER {
            swDownSmartLinkPassthrough(0),
            swUpStandard(1)
        }
        MAX-ACCESS read-only
        STATUS 		current
        DESCRIPTION
            "Media converter module's current switch setting for Link Mode."
        ::= { cm4gptEntry 6 }

    cm4gptHwSw2FiberFaultAlert OBJECT-TYPE
        SYNTAX 		INTEGER {
            swDownDisabled(0),
            swUpEnabled(1)
        }
        MAX-ACCESS read-only
        STATUS 		current
        DESCRIPTION
            "Media converter module's current switch setting for Fiber Fault 
            Alert."
        ::= { cm4gptEntry 7 }

    cm4gptHwSw3RateSelect OBJECT-TYPE
        SYNTAX 		INTEGER {
            swDownLow(0),
            swUpHigh(1)
        }
        MAX-ACCESS read-only
        STATUS 		current
        DESCRIPTION
            "Media converter module's current switch setting for Rate Select."
        ::= { cm4gptEntry 8 }

    cm4gptHwSw4Unused OBJECT-TYPE
        SYNTAX 		INTEGER {
            disabled(0),
            enabled(1)
        }
        MAX-ACCESS read-only
        STATUS 		current
        DESCRIPTION
            "This object indicates the current switch setting for the 4th, unused switch." 
        ::= { cm4gptEntry 9 }

    cm4gptPort1LinkStatus OBJECT-TYPE
        SYNTAX 		INTEGER {
            down(0),
            up(1)
        }
        MAX-ACCESS read-only
        STATUS 		current
        DESCRIPTION
            "Media converter module's current fiber link status (port 1)."
        ::= { cm4gptEntry 10 }

    cm4gptPort1ConnType OBJECT-TYPE
        SYNTAX 		INTEGER {
            sc(0),
            lc(1),
            st(2),
            sfp(3),
            fc(5),
            mtrj(6),
            xfp(7),
            sfpPlus(8)
        }
        MAX-ACCESS read-only
        STATUS 		current
        DESCRIPTION
            "Media converter module's fiber port connector type (port 1)."
        ::= { cm4gptEntry 11 }

    cm4gptPort2LinkStatus OBJECT-TYPE
        SYNTAX 		INTEGER {
            down(0),
            up(1)
        }
        MAX-ACCESS read-only
        STATUS 		current
        DESCRIPTION
            "Media converter module's current fiber link status (port 2)."
        ::= { cm4gptEntry 12 }

    cm4gptPort2ConnType OBJECT-TYPE
        SYNTAX 		INTEGER {
            sc(0),
            lc(1),
            st(2),
            sfp(3),
            fc(5),
            mtrj(6),
            xfp(7),
            sfpPlus(8)
        }
        MAX-ACCESS read-only
        STATUS 		current
        DESCRIPTION
            "Media converter module's fiber port connector type (port 2)."
        ::= { cm4gptEntry 13 }

--
-- cm4gptTable
--
--
-- cm4gptConfigTable
--
cm4gptConfigTable	OBJECT-TYPE
    SYNTAX		SEQUENCE OF Cm4gptConfigEntry
    MAX-ACCESS	not-accessible
    STATUS		current
    DESCRIPTION
        "Table of CM-4GPT type media converter module's configuration type information."
    ::= { cm4gpt 2 }

    cm4gptConfigEntry OBJECT-TYPE
        SYNTAX      Cm4gptConfigEntry
        MAX-ACCESS  not-accessible
        STATUS      current
        DESCRIPTION
            "Entries of the table, each relating to a separate CM-4GPT type
             media converter module."
        INDEX   { mcrChassisIndex, cm4gptConfigSlotIndex }
        ::= { cm4gptConfigTable 1 }

    Cm4gptConfigEntry ::=
        SEQUENCE {
            cm4gptConfigSlotIndex                SlotNumber,
            cm4gptConfigStatus                   ContainerStatus,
            cm4gptConfigModuleName               DisplayString,
            cm4gptConfigLinkMode                 INTEGER,
            cm4gptConfigFiberFaultAlert          EnableDisableValue,
            cm4gptConfigRateSelect               INTEGER,

            cm4gptConfigPort1Name                DisplayString,
            cm4gptConfigPort1Enable              YesNoValue,
            
            cm4gptConfigPort2Name                DisplayString,
            cm4gptConfigPort2Enable              YesNoValue
        }

    cm4gptConfigSlotIndex	OBJECT-TYPE
        SYNTAX		SlotNumber
        MAX-ACCESS	not-accessible
        STATUS		current
        DESCRIPTION
            "The Slot number the CM-4GPT type module is currently inserted"
    ::= { cm4gptConfigEntry 2 }

    cm4gptConfigStatus OBJECT-TYPE
        SYNTAX      ContainerStatus
        MAX-ACCESS  read-write
        STATUS      current
        DESCRIPTION
          "When you perform a GET on this variable, one of
            the following values will be returned:
            1-Indicates that the container folder is active with no changes.
            2-Indicates that the container folder is active with change(s).
            Once you have completed setting the variables in a folder, you
            will want to submit your changes to the management module. To do
            this, set the Status variable to 4. If you want to discard the
            changes, set the Status variable to 6.
            4-Indicates that the changes in the container folder are to be
              submitted to the management module, verified and and saved to flash.
            6-Indicates that the changes in the container folder are to be
              discarded."
        ::= { cm4gptConfigEntry 3 }

    cm4gptConfigModuleName OBJECT-TYPE
        SYNTAX		DisplayString(SIZE(0..63))
        MAX-ACCESS	read-write
        STATUS		current
        DESCRIPTION
            "This object identifies a user configurable name for the media converter module
             present in the chassis. "
        ::= { cm4gptConfigEntry 4 }

    cm4gptConfigLinkMode OBJECT-TYPE
        SYNTAX		INTEGER {
            standard(0),
            smartLinkPassthrough(1)
        }
        MAX-ACCESS	read-write
        STATUS		current
        DESCRIPTION
            "This object identifies the Link Mode for the media converter module. This object
            is read-only if the media converter module's ConfigMode jumper is set to
            hardwareSwitches(0)."
        ::= { cm4gptConfigEntry 5 }

    cm4gptConfigFiberFaultAlert	OBJECT-TYPE
        SYNTAX		EnableDisableValue
        MAX-ACCESS	read-write
        STATUS		current
        DESCRIPTION
            "This object identifies the Fiber Fault Alert setting for the media
             module. This object is read-only if the media converter module's ConfigMode
             jumper is set to hardwareSwitches(0). "
        ::= { cm4gptConfigEntry 6 }

    cm4gptConfigRateSelect OBJECT-TYPE
        SYNTAX		INTEGER {
            low(0),
            high(1)
        }
        MAX-ACCESS	read-write
        STATUS		current
        DESCRIPTION
            "This object identifies the Rate Select setting for the media converter module. This object
            is read-only if the media converter module's ConfigMode jumper is set to
            hardwareSwitches(0)."
        ::= { cm4gptConfigEntry 7 }

    cm4gptConfigPort1Name OBJECT-TYPE
        SYNTAX		DisplayString(SIZE(0..8))
        MAX-ACCESS	read-write
        STATUS 		current
        DESCRIPTION
            "This object identifies a user definable name for port 1."
        ::= { cm4gptConfigEntry 8 }

    cm4gptConfigPort1Enable OBJECT-TYPE
        SYNTAX		YesNoValue
        MAX-ACCESS	read-write
        STATUS 		current
        DESCRIPTION
            "This object identifies whether port 1 is enabled."
        ::= { cm4gptConfigEntry 9 }

    cm4gptConfigPort2Name OBJECT-TYPE
        SYNTAX		DisplayString(SIZE(0..8))
        MAX-ACCESS	read-write
        STATUS 		current
        DESCRIPTION
            "This object identifies a user definable name for port 2."
        ::= { cm4gptConfigEntry 10 }

    cm4gptConfigPort2Enable OBJECT-TYPE
        SYNTAX		YesNoValue
        MAX-ACCESS	read-write
        STATUS 		current
        DESCRIPTION
            "This object identifies whether port 2 is enabled."
        ::= { cm4gptConfigEntry 11 }


--
-- cm4gptConfigTable
--

--
-- cm4gptLedTable
--
cm4gptLedTable	OBJECT-TYPE
    SYNTAX		SEQUENCE OF Cm4gptLedEntry
    MAX-ACCESS	not-accessible
    STATUS		current
    DESCRIPTION
        "Table of CM-4GPT type media converter module's LED status information."
    ::= { cm4gpt 3 }

    cm4gptLedEntry OBJECT-TYPE
        SYNTAX      Cm4gptLedEntry
        MAX-ACCESS  not-accessible
        STATUS      current
        DESCRIPTION
            "Entries of the table, each relating to a separate CM-4GPT type
             media converter module."
        INDEX   { mcrChassisIndex, cm4gptLedsSlotIndex }
        ::= { cm4gptLedTable 1 }

    Cm4gptLedEntry ::=
        SEQUENCE {
            cm4gptLedsSlotIndex	SlotNumber,
            cm4gptLedPWR			INTEGER,
            cm4gptLedLK1			INTEGER,
            cm4gptLedLK2			INTEGER
        }

    cm4gptLedsSlotIndex	OBJECT-TYPE
        SYNTAX		SlotNumber
        MAX-ACCESS	not-accessible
        STATUS		current
        DESCRIPTION
            "The Slot number the CM-4GPT type module is currently inserted"
    ::= { cm4gptLedEntry 2 }

    cm4gptLedPWR	OBJECT-TYPE
        SYNTAX		INTEGER {
            off(0),
            onGreen(1),
            blinking(2)
        }
        MAX-ACCESS	read-only
        STATUS		current
        DESCRIPTION
            "This object identifies the status of the power (PWR) LED on the media converter module.
             Possible status values are:
                 off(0) - No power to the module
                 onGreen(1) - Power being applied to module
                 blinking(2) - Loopback or Link-Test enabled"
    ::= { cm4gptLedEntry 3 }

    cm4gptLedLK1	OBJECT-TYPE
        SYNTAX		INTEGER {
            off(0),
            on(1)
        }
        MAX-ACCESS	read-only
        STATUS		current
        DESCRIPTION
            "This object identifies the status of the port 1 link (LK1) LED on the
             media converter module.
             Possible status values are:
                 off(0) - No link
                 on(1) - Port link present"
    ::= { cm4gptLedEntry 4 }

    cm4gptLedLK2	OBJECT-TYPE
        SYNTAX		INTEGER {
            off(0),
            on(1)
        }
        MAX-ACCESS	read-only
        STATUS		current
        DESCRIPTION
            "This object identifies the status of the port 2 link (LK2) LED on the
             media converter module.
             Possible status values are:
                 off(0) - No link
                 on(1) - Port link present"
    ::= { cm4gptLedEntry 5 }

--
-- end of cm4gptLedTable
--

--
-- end of cm4gpt


--
-- end of mcrModuleTypes
--

--
-- mcrSfpDmiModuleTable
--
mcrSfpDmiModuleTable OBJECT-TYPE
    SYNTAX		SEQUENCE OF McrSfpDmiModuleEntry
    MAX-ACCESS	not-accessible
    STATUS		current
    DESCRIPTION
        "Table of SFP Diagnostic Monitoring Interface information for
         Optical Transceivers"
    ::= { mcrChassisGroup 5 }

    mcrSfpDmiModuleEntry OBJECT-TYPE
        SYNTAX      McrSfpDmiModuleEntry
        MAX-ACCESS  not-accessible
        STATUS      current
        DESCRIPTION
            "Entries of the table, each relating to a separate SFP module."
        INDEX   { mcrChassisIndex, sfpDmiSlotIndex, sfpDmiMediaPortIndex}
        ::= {mcrSfpDmiModuleTable 1 }

    McrSfpDmiModuleEntry ::=
        SEQUENCE {
            sfpDmiSlotIndex				SlotNumber,
            sfpDmiMediaPortIndex		Unsigned32,
            sfpDmiStatus				BITS,
            sfpDmiConnectorType			INTEGER,
            sfpDmiNominalBitRate		Unsigned32,
            sfpDmiLinkReach9125			Integer32,
            sfpDmiLinkReach50125		Integer32,
            sfpDmiLinkReach625125		Integer32,
            sfpDmiFiberWaveLength		Unsigned32,
            sfpDmiCurrentTempState		INTEGER,
            sfpDmiRealTimeTemp			DisplayString,
            sfpDmiHighTempWarn			DisplayString,
            sfpDmiHighTempAlarm			DisplayString,
            sfpDmiLowTempWarn			DisplayString,
            sfpDmiLowTempAlarm			DisplayString,
            sfpDmiCurrentVoltState		INTEGER,
            sfpDmiRealTimeVolt			DisplayString,
            sfpDmiHighVoltWarn			DisplayString,
            sfpDmiHighVoltAlarm			DisplayString,
            sfpDmiLowVoltWarn			DisplayString,
            sfpDmiLowVoltAlarm			DisplayString,
            sfpDmiCurrentTxBiasState	INTEGER,
            sfpDmiRealTimeTxBias		DisplayString,
            sfpDmiHighTxBiasWarn		DisplayString,
            sfpDmiHighTxBiasAlarm		DisplayString,
            sfpDmiLowTxBiasWarn			DisplayString,
            sfpDmiLowTxBiasAlarm		DisplayString,
            sfpDmiCurrentTxPowerState	INTEGER,
            sfpDmiRealTimeTxPower		DisplayString,
            sfpDmiHighTxPowerWarn		DisplayString,
            sfpDmiHighTxPowerAlarm		DisplayString,
            sfpDmiLowTxPowerWarn		DisplayString,
            sfpDmiLowTxPowerAlarm		DisplayString,
            sfpDmiCurrentRxPowerState	INTEGER,
            sfpDmiRealTimeRxPower		DisplayString,
            sfpDmiHighRxPowerWarn		DisplayString,
            sfpDmiHighRxPowerAlarm		DisplayString,
            sfpDmiLowRxPowerWarn		DisplayString,
            sfpDmiLowRxPowerAlarm		DisplayString,
            sfpDmiStatus2				Unsigned32,
            sfpDmiVendorSerialNumber	DisplayString,
            sfpDmiVendorName			DisplayString,
            sfpDmiVendorPartNumber      DisplayString,
            xfpDmiAux1Type              INTEGER,
            xfpDmiAux1State             INTEGER,
            xfpDmiRealTimeAux1          DisplayString,
            xfpDmiHighAux1Warn          DisplayString,
            xfpDmiHighAux1Alarm         DisplayString,
            xfpDmiLowAux1Warn           DisplayString,
            xfpDmiLowAux1Alarm          DisplayString,
            xfpDmiAux2Type              INTEGER,
            xfpDmiAux2State             INTEGER,
            xfpDmiRealTimeAux2          DisplayString,
            xfpDmiHighAux2Warn          DisplayString,
            xfpDmiHighAux2Alarm         DisplayString,
            xfpDmiLowAux2Warn           DisplayString,
            xfpDmiLowAux2Alarm          DisplayString,
            xfpDmiMinBitRate            Integer32,
            xfpDmiMaxBitRate            Integer32,
            xfpDmiReachEBW50125         Integer32,
            sfpDmiReachCopper           Integer32
        }

    sfpDmiSlotIndex	OBJECT-TYPE
        SYNTAX		SlotNumber
        MAX-ACCESS	not-accessible
        STATUS		current
        DESCRIPTION
            "The Slot number of the media converter module containing this SFP/XFP"
    ::= { mcrSfpDmiModuleEntry 2 }

    sfpDmiMediaPortIndex OBJECT-TYPE
        SYNTAX      Unsigned32
        MAX-ACCESS not-accessible
        STATUS current
        DESCRIPTION
            "Media converter module port index."
    ::= { mcrSfpDmiModuleEntry 3 }


    sfpDmiStatus	OBJECT-TYPE
        SYNTAX		BITS {
            sfpModuleInserted(24),
            sfpCommFailed(25),
            sfpDmiSupported(26)
        }
        MAX-ACCESS	read-only
        STATUS		current
        DESCRIPTION
            "This object identifies the status of the SFP module. If sfpCommFailed
             bit is set then the rest of the data in this entry is invalid"
        ::= { mcrSfpDmiModuleEntry 4 }

    sfpDmiConnectorType	OBJECT-TYPE
        SYNTAX		INTEGER {
            unknownUnspecified(0),
            sc(1),
            fiberChannelStyle1Copper(2),
            fiberChannelStyle2Copper(3),
            bncTnc(4),
            fiberChannelCoaxHeader(5),
            fiberJack(6),
            lc(7),
            mtrj(8),
            mu(9),
            sg(10),
            opticalPigtail(11),
            hssdcII(32),
            copperPigtail(33)
        }
        MAX-ACCESS	read-only
        STATUS		current
        DESCRIPTION
            "This object identifies the SFP DMI connector type."
        ::= { mcrSfpDmiModuleEntry 5 }

    sfpDmiNominalBitRate	OBJECT-TYPE
        SYNTAX		Unsigned32
        MAX-ACCESS	read-only
        STATUS		current
        DESCRIPTION
            "This object identifies the SFP DMI nominal bit rate of fiber
             interface, in megabits per second."
        ::= { mcrSfpDmiModuleEntry 6 }

    sfpDmiLinkReach9125	OBJECT-TYPE
        SYNTAX		Integer32
        MAX-ACCESS	read-only
        STATUS		current
        DESCRIPTION
            "This object identifies the SFP DMI maximum length in meters of media
             supported by the fiber transceiver for 9 micron (125 micron jacket)
             single-mode fiber. "
        ::= { mcrSfpDmiModuleEntry 7 }

    sfpDmiLinkReach50125	OBJECT-TYPE
        SYNTAX		Integer32
        MAX-ACCESS	read-only
        STATUS		current
        DESCRIPTION
            "This object identifies the SFP DMI maximum length in meters of media
             supported by the fiber transceiver for 50 micron (125 micron jacket)
             multi-mode fiber."
        ::= { mcrSfpDmiModuleEntry 8 }

    sfpDmiLinkReach625125	OBJECT-TYPE
        SYNTAX		Integer32
        MAX-ACCESS	read-only
        STATUS		current
        DESCRIPTION
            "This object identifies the SFP DMI maximum length in meters of media
             supported by the fiber transceiver for 62.5 micron (125 micron jacket)
             multi-mode fiber."
        ::= { mcrSfpDmiModuleEntry 9 }

    sfpDmiFiberWaveLength	OBJECT-TYPE
        SYNTAX		Unsigned32
        MAX-ACCESS	read-only
        STATUS		current
        DESCRIPTION
            "This object identifies the  wavelength of the fiber interface's
             optical transceiver, in nanometers."
        ::= { mcrSfpDmiModuleEntry 10 }

    sfpDmiCurrentTempState	OBJECT-TYPE
        SYNTAX		INTEGER {
            invalid(0),
            notSupported(1),
            normal(2),
            highWarn(3),
            highAlarm(4),
            lowWarn(5),
            lowAlarm(6)
        }
        MAX-ACCESS	read-only
        STATUS		current
        DESCRIPTION
            "This object identifies the current alarm status for SFP DMI internally
             measured temperature. "
        ::= { mcrSfpDmiModuleEntry 11 }

    sfpDmiRealTimeTemp	OBJECT-TYPE
        SYNTAX	DisplayString (SIZE(0..32))
        MAX-ACCESS	read-only
        STATUS		current
        DESCRIPTION
            "This object identifies the SFP DMI real time temperature. The value
             displayed will be either Celsius or Fahrenheit based on your
             current regional display settings. "
        ::= { mcrSfpDmiModuleEntry 12 }

    sfpDmiHighTempWarn	OBJECT-TYPE
        SYNTAX	DisplayString (SIZE(0..32))
        MAX-ACCESS	read-only
        STATUS		current
        DESCRIPTION
            "This object identifies the SFP DMI high temperature warning threshold.
             The value displayed will be either Celsius or Fahrenheit based on your
             current regional display settings. "
        ::= { mcrSfpDmiModuleEntry 13 }

    sfpDmiHighTempAlarm	OBJECT-TYPE
        SYNTAX	DisplayString (SIZE(0..32))
        MAX-ACCESS	read-only
        STATUS		current
        DESCRIPTION
            "This object identifies the SFP DMI high temperature warning threshold.
             The value displayed will be either Celsius or Fahrenheit based on your
             current regional display settings. "
        ::= { mcrSfpDmiModuleEntry 14 }

    sfpDmiLowTempWarn	OBJECT-TYPE
        SYNTAX	DisplayString (SIZE(0..32))
        MAX-ACCESS	read-only
        STATUS		current
        DESCRIPTION
            "This object identifies the SFP DMI high temperature warning threshold.
             The value displayed will be either Celsius or Fahrenheit based on your
             current regional display settings. "
        ::= { mcrSfpDmiModuleEntry 15 }

    sfpDmiLowTempAlarm	OBJECT-TYPE
        SYNTAX	DisplayString (SIZE(0..32))
        MAX-ACCESS	read-only
        STATUS		current
        DESCRIPTION
            "This object identifies the SFP DMI high temperature warning threshold.
             The value displayed will be either Celsius or Fahrenheit based on your
             current regional display settings. "
        ::= { mcrSfpDmiModuleEntry 16 }

    sfpDmiCurrentVoltState	OBJECT-TYPE
        SYNTAX		INTEGER {
            invalid(0),
            notSupported(1),
            normal(2),
            highWarn(3),
            highAlarm(4),
            lowWarn(5),
            lowAlarm(6)
        }
        MAX-ACCESS	read-only
        STATUS		current
        DESCRIPTION
            "This object identifies current alarm status for SFP DMI internally
             measured voltage. "
        ::= { mcrSfpDmiModuleEntry 17 }

    sfpDmiRealTimeVolt	OBJECT-TYPE
        SYNTAX	DisplayString (SIZE(0..32))
        MAX-ACCESS	read-only
        STATUS		current
        DESCRIPTION
            "This object identifies the SFP DMI real time voltage in Volts. "
        ::= { mcrSfpDmiModuleEntry 18 }

    sfpDmiHighVoltWarn	OBJECT-TYPE
        SYNTAX	DisplayString (SIZE(0..32))
        MAX-ACCESS	read-only
        STATUS		current
        DESCRIPTION
            "This object identifies the SFP DMI high voltage warning threshold in
             Volts "
        ::= { mcrSfpDmiModuleEntry 19 }

    sfpDmiHighVoltAlarm	OBJECT-TYPE
        SYNTAX	DisplayString (SIZE(0..32))
        MAX-ACCESS	read-only
        STATUS		current
        DESCRIPTION
            "This object identifies the SFP DMI high voltage warning threshold in
             Volts "
        ::= { mcrSfpDmiModuleEntry 20 }

    sfpDmiLowVoltWarn	OBJECT-TYPE
        SYNTAX	DisplayString (SIZE(0..32))
        MAX-ACCESS	read-only
        STATUS		current
        DESCRIPTION
            "This object identifies the SFP DMI high voltage warning threshold in
             Volts"
        ::= { mcrSfpDmiModuleEntry 21 }

    sfpDmiLowVoltAlarm	OBJECT-TYPE
        SYNTAX	DisplayString (SIZE(0..32))
        MAX-ACCESS	read-only
        STATUS		current
        DESCRIPTION
            "This object identifies the SFP DMI high voltage warning threshold in
             Volts"
        ::= { mcrSfpDmiModuleEntry 22 }

    sfpDmiCurrentTxBiasState	OBJECT-TYPE
        SYNTAX		INTEGER {
            invalid(0),
            notSupported(1),
            normal(2),
            highWarn(3),
            highAlarm(4),
            lowWarn(5),
            lowAlarm(6)
        }
        MAX-ACCESS	read-only
        STATUS		current
        DESCRIPTION
            "This object identifies current alarm status for SFP DMI internally
             measured transmit bias current in milliamps. "
        ::= { mcrSfpDmiModuleEntry 23 }

    sfpDmiRealTimeTxBias	OBJECT-TYPE
        SYNTAX	DisplayString (SIZE(0..32))
        MAX-ACCESS	read-only
        STATUS		current
        DESCRIPTION
            "This object identifies the SFP DMI high TX Bias current in milliamps. "
        ::= { mcrSfpDmiModuleEntry 24 }

    sfpDmiHighTxBiasWarn	OBJECT-TYPE
        SYNTAX	DisplayString (SIZE(0..32))
        MAX-ACCESS	read-only
        STATUS		current
        DESCRIPTION
            "This object identifies the SFP DMI high TX Bias current warning
             threshold in milliamps."
        ::= { mcrSfpDmiModuleEntry 25 }

    sfpDmiHighTxBiasAlarm	OBJECT-TYPE
        SYNTAX	DisplayString (SIZE(0..32))
        MAX-ACCESS	read-only
        STATUS		current
        DESCRIPTION
            "This object identifies the SFP DMI high TX Bias current alarm
             threshold in milliamps."
        ::= { mcrSfpDmiModuleEntry 26 }

    sfpDmiLowTxBiasWarn	OBJECT-TYPE
        SYNTAX	DisplayString (SIZE(0..32))
        MAX-ACCESS	read-only
        STATUS		current
        DESCRIPTION
            "This object identifies the SFP DMI low TX Bias current warning
             threshold in milliamps."
        ::= { mcrSfpDmiModuleEntry 27 }

    sfpDmiLowTxBiasAlarm	OBJECT-TYPE
        SYNTAX	DisplayString (SIZE(0..32))
        MAX-ACCESS	read-only
        STATUS		current
        DESCRIPTION
            "This object identifies the SFP DMI low TX Bias current alarm
             threshold in milliamps."
        ::= { mcrSfpDmiModuleEntry 28 }

    sfpDmiCurrentTxPowerState	OBJECT-TYPE
        SYNTAX		INTEGER {
            invalid(0),
            notSupported(1),
            normal(2),
            highWarn(3),
            highAlarm(4),
            lowWarn(5),
            lowAlarm(6)
        }
        MAX-ACCESS	read-only
        STATUS		current
        DESCRIPTION
            "This object identifies current alarm status for SFP DMI internally
             measured transmit power. "
        ::= { mcrSfpDmiModuleEntry 29 }

    sfpDmiRealTimeTxPower	OBJECT-TYPE
        SYNTAX	DisplayString (SIZE(0..32))
        MAX-ACCESS	read-only
        STATUS		current
        DESCRIPTION
            "This object identifies the SFP DMI real time TX output power.
             The value displayed will be either millwatts or Dbm based on your
             current regional display settings. "

        ::= { mcrSfpDmiModuleEntry 30 }

    sfpDmiHighTxPowerWarn	OBJECT-TYPE
        SYNTAX	DisplayString (SIZE(0..32))
        MAX-ACCESS	read-only
        STATUS		current
        DESCRIPTION
            "This object identifies the SFP DMI high TX output power warning
             threshold. The value displayed will be either millwatts or Dbm based
             on your current regional display settings. "

        ::= { mcrSfpDmiModuleEntry 31 }

    sfpDmiHighTxPowerAlarm	OBJECT-TYPE
        SYNTAX	DisplayString (SIZE(0..32))
        MAX-ACCESS	read-only
        STATUS		current
        DESCRIPTION
            "This object identifies the SFP DMI high TX output power alarm
             threshold. The value displayed will be either millwatts or Dbm based
             on your current regional display settings. "
        ::= { mcrSfpDmiModuleEntry 32 }

    sfpDmiLowTxPowerWarn	OBJECT-TYPE
        SYNTAX	DisplayString (SIZE(0..32))
        MAX-ACCESS	read-only
        STATUS		current
        DESCRIPTION
            "This object identifies the SFP DMI low TX output power warning
             threshold. The value displayed will be either millwatts or Dbm based
             on your current regional display settings. "
        ::= { mcrSfpDmiModuleEntry 33 }

    sfpDmiLowTxPowerAlarm	OBJECT-TYPE
        SYNTAX	DisplayString (SIZE(0..32))
        MAX-ACCESS	read-only
        STATUS		current
        DESCRIPTION
            "This object identifies the SFP DMI low TX output power alarm
             threshold. The value displayed will be either millwatts or Dbm based
             on your current regional display settings. "
        ::= { mcrSfpDmiModuleEntry 34 }

    sfpDmiCurrentRxPowerState	OBJECT-TYPE
        SYNTAX		INTEGER {
            invalid(0),
            notSupported(1),
            normal(2),
            highWarn(3),
            highAlarm(4),
            lowWarn(5),
            lowAlarm(6)
        }
        MAX-ACCESS	read-only
        STATUS		current
        DESCRIPTION
            "This object identifies current alarm status for SFP DMI internally
             measured receive power. "
        ::= { mcrSfpDmiModuleEntry 35 }

    sfpDmiRealTimeRxPower	OBJECT-TYPE
        SYNTAX	DisplayString (SIZE(0..32))
        MAX-ACCESS	read-only
        STATUS		current
        DESCRIPTION
            "This object identifies the SFP DMI real time RX received optical power.
             The value displayed will be either millwatts or Dbm based
             on your current regional display settings. "
        ::= { mcrSfpDmiModuleEntry 36 }

    sfpDmiHighRxPowerWarn	OBJECT-TYPE
        SYNTAX	DisplayString (SIZE(0..32))
        MAX-ACCESS	read-only
        STATUS		current
        DESCRIPTION
            "This object identifies the SFP DMI high RX received optical warning
             threshold. The value displayed will be either millwatts or Dbm based
             on your current regional display settings. "
        ::= { mcrSfpDmiModuleEntry 37 }

    sfpDmiHighRxPowerAlarm	OBJECT-TYPE
        SYNTAX	DisplayString (SIZE(0..32))
        MAX-ACCESS	read-only
        STATUS		current
        DESCRIPTION
            "This object identifies the SFP DMI high RX received optical alarm
             threshold. The value displayed will be either millwatts or Dbm based
             on your current regional display settings. "
        ::= { mcrSfpDmiModuleEntry 38 }

    sfpDmiLowRxPowerWarn	OBJECT-TYPE
        SYNTAX	DisplayString (SIZE(0..32))
        MAX-ACCESS	read-only
        STATUS		current
        DESCRIPTION
            "This object identifies the SFP DMI low RX received optical warning
             threshold. The value displayed will be either millwatts or Dbm based
             on your current regional display settings. "
        ::= { mcrSfpDmiModuleEntry 39 }

    sfpDmiLowRxPowerAlarm	OBJECT-TYPE
        SYNTAX	DisplayString (SIZE(0..32))
        MAX-ACCESS	read-only
        STATUS		current
        DESCRIPTION
            "This object identifies the SFP DMI low RX received optical alarm
             threshold. The value displayed will be either millwatts or Dbm based
             on your current regional display settings. "
        ::= { mcrSfpDmiModuleEntry 40 }

    sfpDmiStatus2	OBJECT-TYPE
        SYNTAX		Unsigned32
        MAX-ACCESS	read-only
        STATUS		current
        DESCRIPTION
            "This object identifies the status of the SFP module. If sfpCommFailed
             value is set then the rest of the data in this entry is invalid
            0x80 - sfpModuleInserted
            0x40	 - sfpCommFailed
            0x20 - sfpDmiSupported"
        ::= { mcrSfpDmiModuleEntry 41 }

    sfpDmiVendorSerialNumber	OBJECT-TYPE
        SYNTAX	DisplayString (SIZE(0..32))
        MAX-ACCESS	read-only
        STATUS		current
        DESCRIPTION
            "This object identifies the SFP DMI serial number. "
        ::= { mcrSfpDmiModuleEntry 42 }

    sfpDmiVendorName		OBJECT-TYPE
        SYNTAX	DisplayString (SIZE(0..32))
        MAX-ACCESS	read-only
        STATUS		current
        DESCRIPTION
            "This object identifies the SFP DMI serial number. "
        ::= { mcrSfpDmiModuleEntry 43 }

    sfpDmiVendorPartNumber	OBJECT-TYPE
        SYNTAX	DisplayString (SIZE(0..32))
        MAX-ACCESS	read-only
        STATUS		current
        DESCRIPTION
            "This object identifies the SFP DMI serial number. "
        ::= { mcrSfpDmiModuleEntry 44 }

    xfpDmiAux1Type	OBJECT-TYPE
        SYNTAX		INTEGER {
            notSupported(0),
            apdBiasVoltmv(1),
            tecCurrentma(3),
            laserTemperature(4),
            laserWavelength(5),
            p5Voltv(6),
            p33Voltv(7),
            p18Voltv(8),
            m52Voltv(9),
            p5vCurrentma(10),
            p33vCurrentma(13),
            p18vCurrentma(14),
            m52vCurrentma(15)
        }
        MAX-ACCESS	read-only
        STATUS		current
        DESCRIPTION
            "This object identifies the type of value that is being measured by
            the Auxillary 1 registers on the XFP"
        ::= { mcrSfpDmiModuleEntry 45 }

    xfpDmiAux1State	OBJECT-TYPE
        SYNTAX		INTEGER {
            invalid(0),
            notSupported(1),
            normal(2),
            highWarn(3),
            highAlarm(4),
            lowWarn(5),
            lowAlarm(6)
        }
        MAX-ACCESS	read-only
        STATUS		current
        DESCRIPTION
            "This object identifies current alarm status for the XFP Aux1 registers"
        ::= { mcrSfpDmiModuleEntry 46 }

    xfpDmiRealTimeAux1	OBJECT-TYPE
        SYNTAX	DisplayString (SIZE(0..32))
        MAX-ACCESS	read-only
        STATUS		current
        DESCRIPTION
            "This object identifies the XFP DMI real time values for the Aux1
            registers"
        ::= { mcrSfpDmiModuleEntry 47 }

    xfpDmiHighAux1Warn	OBJECT-TYPE
        SYNTAX	DisplayString (SIZE(0..32))
        MAX-ACCESS	read-only
        STATUS		current
        DESCRIPTION
            "This object identifies the XFP DMI high warning threshold for Aux1"
        ::= { mcrSfpDmiModuleEntry 48 }

    xfpDmiHighAux1Alarm	OBJECT-TYPE
        SYNTAX	DisplayString (SIZE(0..32))
        MAX-ACCESS	read-only
        STATUS		current
        DESCRIPTION
            "This object identifies the XFP DMI alarm alarm threshold for Aux1"
        ::= { mcrSfpDmiModuleEntry 49 }

    xfpDmiLowAux1Warn	OBJECT-TYPE
        SYNTAX	DisplayString (SIZE(0..32))
        MAX-ACCESS	read-only
        STATUS		current
        DESCRIPTION
            "This object identifies the XFP DMI low warning threshold for Aux1"
        ::= { mcrSfpDmiModuleEntry 50 }

    xfpDmiLowAux1Alarm	OBJECT-TYPE
        SYNTAX	DisplayString (SIZE(0..32))
        MAX-ACCESS	read-only
        STATUS		current
        DESCRIPTION
            "This object identifies the XFP DMI low alarm threshold for Aux1"
        ::= { mcrSfpDmiModuleEntry 51 }

    xfpDmiAux2Type	OBJECT-TYPE
        SYNTAX		INTEGER {
            notSupported(0),
            apdBiasVoltmv(1),
            tecCurrentma(3),
            laserTemperature(4),
            laserWavelength(5),
            p5Voltv(6),
            p33Voltv(7),
            p18Voltv(8),
            m52Voltv(9),
            p5vCurrentma(10),
            p33vCurrentma(13),
            p18vCurrentma(14),
            m52vCurrentma(15)
        }
        MAX-ACCESS	read-only
        STATUS		current
        DESCRIPTION
            "This object identifies the type of value that is being measured by
            the Auxillary 1 registers on the XFP"
        ::= { mcrSfpDmiModuleEntry 52 }

    xfpDmiAux2State	OBJECT-TYPE
        SYNTAX		INTEGER {
            invalid(0),
            notSupported(1),
            normal(2),
            highWarn(3),
            highAlarm(4),
            lowWarn(5),
            lowAlarm(6)
        }
        MAX-ACCESS	read-only
        STATUS		current
        DESCRIPTION
            "This object identifies current alarm status for the XFP Aux2 registers"
        ::= { mcrSfpDmiModuleEntry 53 }

    xfpDmiRealTimeAux2	OBJECT-TYPE
        SYNTAX	DisplayString (SIZE(0..32))
        MAX-ACCESS	read-only
        STATUS		current
        DESCRIPTION
            "This object identifies the SFP DMI real time values for the Aux2
            registers"
        ::= { mcrSfpDmiModuleEntry 54 }

    xfpDmiHighAux2Warn	OBJECT-TYPE
        SYNTAX	DisplayString (SIZE(0..32))
        MAX-ACCESS	read-only
        STATUS		current
        DESCRIPTION
            "This object identifies the XFP DMI high warning threshold for Aux2"
        ::= { mcrSfpDmiModuleEntry 55 }

    xfpDmiHighAux2Alarm	OBJECT-TYPE
        SYNTAX	DisplayString (SIZE(0..32))
        MAX-ACCESS	read-only
        STATUS		current
        DESCRIPTION
            "This object identifies the XFP DMI alarm alarm threshold for Aux2"
        ::= { mcrSfpDmiModuleEntry 56 }

    xfpDmiLowAux2Warn	OBJECT-TYPE
        SYNTAX	DisplayString (SIZE(0..32))
        MAX-ACCESS	read-only
        STATUS		current
        DESCRIPTION
            "This object identifies the XFP DMI low warning threshold for Aux2"
        ::= { mcrSfpDmiModuleEntry 57 }

    xfpDmiLowAux2Alarm      OBJECT-TYPE
        SYNTAX	DisplayString (SIZE(0..32))
        MAX-ACCESS	read-only
        STATUS		current
        DESCRIPTION
            "This object identifies the XFP DMI low alarm threshold for Aux2"
        ::= { mcrSfpDmiModuleEntry 58 }

    xfpDmiMinBitRate     OBJECT-TYPE
        SYNTAX		Integer32
        MAX-ACCESS	read-only
        STATUS		current
        DESCRIPTION
            "This object specifies the XFP minimum bit rate."
        ::= { mcrSfpDmiModuleEntry 59 }

    xfpDmiMaxBitRate     OBJECT-TYPE
        SYNTAX		Integer32
        MAX-ACCESS	read-only
        STATUS		current
        DESCRIPTION
            "This object specifies the XFP maximum bit rate."
        ::= { mcrSfpDmiModuleEntry 60 }

    xfpDmiReachEBW50125     OBJECT-TYPE
        SYNTAX		Integer32
        MAX-ACCESS	read-only
        STATUS		current
        DESCRIPTION
            "This object specifies the link length that is supported by the fiber
            transceiver using extended bandwidth 50 micron core (125 micron jacket)
            multimode fiber"
        ::= { mcrSfpDmiModuleEntry 61 }

    sfpDmiReachCopper     OBJECT-TYPE
        SYNTAX		Integer32
        MAX-ACCESS	read-only
        STATUS		current
        DESCRIPTION
            "This object identifies the maximum length in meters that is 
             supported by the SFP/XFP interface using copper cable."
        ::= { mcrSfpDmiModuleEntry 62 }


--
-- end of mcrSfpDmiModuleTable
--

--
-- mcrAlarmsWarningsTable
--
mcrAlarmsWarningsTable OBJECT-TYPE
    SYNTAX		SEQUENCE OF McrAlarmsWarningsEntry
    MAX-ACCESS	not-accessible
    STATUS		current
    DESCRIPTION
        "Table of outstanding alarms and warnings."
    ::= { mcrChassisGroup 6 }

mcrAlarmsWarningsEntry OBJECT-TYPE
    SYNTAX		McrAlarmsWarningsEntry
    MAX-ACCESS	not-accessible
    STATUS		current
    DESCRIPTION
        "Entries of the table, each relating to a separate alarm or warning."
    INDEX { mcrChassisIndex, alarmWarnSequenceIndex }
    ::= { mcrAlarmsWarningsTable 1 }

    McrAlarmsWarningsEntry ::=
        SEQUENCE {
            alarmWarnSequenceIndex	Unsigned32,
            alarmWarnType			Unsigned32,
            alarmWarnSeverity 		Unsigned32,
            alarmWarnFlags			Unsigned32,
            alarmWarnChassisNum		Unsigned32,
            alarmWarnDeviceNum		Unsigned32,
            alarmWarnTimeStamp		TimeTicks,
            alarmWarnMessage		DisplayString,
            alarmWarnPortNum		Unsigned32
        }


    alarmWarnSequenceIndex	OBJECT-TYPE
        SYNTAX		Unsigned32
        MAX-ACCESS	not-accessible
        STATUS		current
        DESCRIPTION
            "This object identifies the sequence in which the alarms or
              warnings were generated. Gaps in the sequence numbers are normal."
        ::= { mcrAlarmsWarningsEntry 2 }


    alarmWarnType	OBJECT-TYPE
        SYNTAX		Unsigned32
        MAX-ACCESS	read-only
        STATUS		current
        DESCRIPTION
            "This object identifies the alert/Trap number associated with
            this alarm/warning."
        ::= { mcrAlarmsWarningsEntry 3 }

    alarmWarnSeverity		OBJECT-TYPE
        SYNTAX		Unsigned32
        MAX-ACCESS	read-only
        STATUS		current
        DESCRIPTION
            "This object identifies the severity level of the alarm/warning.
            Value will be one of the top three levels."
        ::= { mcrAlarmsWarningsEntry 4 }

    alarmWarnFlags		OBJECT-TYPE
        SYNTAX		Unsigned32
        MAX-ACCESS	read-only
        STATUS		current
        DESCRIPTION
            "This object identifies the flags defining the alarm/warning.
            0x00000002	- chassis type alert
            0x00000004	- Power Supply Monitoring Unit type alert
            0x00000008	- PSMU power supply type alert
            0x00000010	- PSMU fan type alert
            0x00000020	- Management module type alert
            0x00000040	- Media converter module type alert
            0x00000080	- Media converter module SFP module type alert."
        ::= { mcrAlarmsWarningsEntry 5 }

    alarmWarnChassisNum	OBJECT-TYPE
        SYNTAX		Unsigned32
        MAX-ACCESS	read-only
        STATUS		current
        DESCRIPTION
            "This object identifies the chassis number associated with this
            alarm/warning."
        ::= { mcrAlarmsWarningsEntry 6 }

    alarmWarnDeviceNum	OBJECT-TYPE
        SYNTAX		Unsigned32
        MAX-ACCESS	read-only
        STATUS		current
        DESCRIPTION
            "This object identifies the Hardware slot/bay location of the
            hardware associated with this alarm or warning.
            - 0 indicates alarm/warning occurred on the chassis backplane.
            - If AlarmWarnFlags indicates a power supply then this value
              the power supply bay number.
            - Otherwise it is the chassis slot number."
        ::= { mcrAlarmsWarningsEntry 7 }

    alarmWarnTimeStamp	OBJECT-TYPE
        SYNTAX		TimeTicks
        MAX-ACCESS	read-only
        STATUS		current
        DESCRIPTION
            "This object identifies the time stamp of when the alarm/warning
            was reported.  (in seconds since the Epoch, defined as 0:00:00 UTC
            on the morning  of  January 1, 1970), that the alert was reported
            on the MCR-MGT.)"
        ::= { mcrAlarmsWarningsEntry 8 }

    alarmWarnMessage	OBJECT-TYPE
        SYNTAX		DisplayString
        MAX-ACCESS	read-only
        STATUS		current
        DESCRIPTION
            "This object identifies the alarm/warning message string
            which will contain any values of bound variables."
        ::= { mcrAlarmsWarningsEntry 9 }

    alarmWarnPortNum	OBJECT-TYPE
        SYNTAX		Unsigned32
        MAX-ACCESS	read-only
        STATUS		current
        DESCRIPTION
            "This object identifies the location of the media
            port associated with this alarm or warning."
        ::= { mcrAlarmsWarningsEntry 10 }
        
--
-- end of mcrAlarmsWarningsTable
--

--
-- mcrMediaPortTable
--
mcrMediaPortTable OBJECT-TYPE
    SYNTAX		SEQUENCE OF McrMediaPortEntry
    MAX-ACCESS	not-accessible
    STATUS		current
    DESCRIPTION
        "Table of general port status information."
    ::= { mcrChassisGroup 7 }

mcrMediaPortEntry OBJECT-TYPE
    SYNTAX		McrMediaPortEntry
    MAX-ACCESS	not-accessible
    STATUS		current
    DESCRIPTION
        "Entries of the table, each relating to a separate media converter module port."
    INDEX { mcrChassisIndex, mediaPortSlotIndex, mediaPortPortIndex }
    ::= { mcrMediaPortTable 1 }

    McrMediaPortEntry ::=
        SEQUENCE {
            mediaPortSlotIndex			Unsigned32,
            mediaPortPortIndex			Unsigned32,
            moduleModel					DisplayString,
            portName						DisplayString,
            portEnable					INTEGER,
            portType						INTEGER,
            portLinkStatus				INTEGER,
            portConnType			 		INTEGER,
            portAutoNegState				INTEGER,
            portSpeed					INTEGER,
            portDuplex					INTEGER,
            portPause					INTEGER,
            portRemoteStatus				INTEGER,
            portMediaType				INTEGER,
            portPhysicalProtocol		INTEGER
        }


    mediaPortSlotIndex		OBJECT-TYPE
        SYNTAX		Unsigned32
        MAX-ACCESS	not-accessible
        STATUS		current
        DESCRIPTION
            "Slot number for the media converter module containing this port."
         ::= { mcrMediaPortEntry 2 }

     mediaPortPortIndex		OBJECT-TYPE
        SYNTAX		Unsigned32
        MAX-ACCESS	not-accessible
        STATUS		current
        DESCRIPTION
            "Port number on media card. Valid values are 1 to the highest number
             of ports available on a media card. There are usually two ports"
         ::= { mcrMediaPortEntry 3 }

    moduleModel		OBJECT-TYPE
        SYNTAX		DisplayString
        MAX-ACCESS	read-only
        STATUS		current
        DESCRIPTION
            "This object identifies the model name of the module containing
            this port."
        ::= { mcrMediaPortEntry 4 }

    portName	OBJECT-TYPE
        SYNTAX		DisplayString
        MAX-ACCESS	read-only
        STATUS		current
        DESCRIPTION
            "This object identifies the name configured for this port."
        ::= { mcrMediaPortEntry 5 }

    portEnable	OBJECT-TYPE
        SYNTAX INTEGER {
            disabled(0),
            enable(1)
        }
        MAX-ACCESS	read-only
        STATUS		current
        DESCRIPTION
            "This object indicates whether the port has been enabled."
        ::= { mcrMediaPortEntry 6 }

    portType		OBJECT-TYPE
        SYNTAX		INTEGER {
            copper(0),
            fiber(1),
            sfp(2),
            xfp(3),
            sfpPlus(4)
        }
        MAX-ACCESS	read-only
        STATUS		current
        DESCRIPTION
            "The type of port (copper, fiber, etc.) ."
        ::= { mcrMediaPortEntry 7}

    portLinkStatus	OBJECT-TYPE
        SYNTAX		INTEGER {
            down(0),
            up(1),
            shutdown(2)
        }
        MAX-ACCESS	read-only
        STATUS		current
        DESCRIPTION
            "The port's current link status."
        ::= { mcrMediaPortEntry 8}

    portConnType		OBJECT-TYPE
        SYNTAX		INTEGER {
            rj45(0),
            sc(1),
            lc(2),
            st(3),
            sfp(4),
            fc(5),
            mtrj(6),
            xfp(7),
            sfpPlus(8)
        }
        MAX-ACCESS	read-only
        STATUS		current
        DESCRIPTION
            "The port's connector type"
        ::= { mcrMediaPortEntry 9 }

    portAutoNegState		OBJECT-TYPE
        SYNTAX		INTEGER {
            notApplicable(-1),
            disabled(0),
            complete(1),
            inProgress(2)
        }
        MAX-ACCESS	read-only
        STATUS		current
        DESCRIPTION
            "The port's auto-negotiation state"
        ::= { mcrMediaPortEntry 10 }

    portSpeed		OBJECT-TYPE
        SYNTAX		INTEGER {
            notApplicable(-1),
            speed10Mbs(0),
            speed100Mbps(1),
            speed1000Mbps(2),
            speed10Gbps(3)
        }
        MAX-ACCESS	read-only
        STATUS		current
        DESCRIPTION
            "If the port auto-negotiation state is complete then this object
            indicates the ports current auto-negotiated speed setting.
            If auto-negotiation is not complete then the value returned
            should be ignored"
        ::= { mcrMediaPortEntry 11 }

    portDuplex	OBJECT-TYPE
        SYNTAX INTEGER {
            notApplicable(-1),
            half(0),
            full(1)
        }
        MAX-ACCESS	read-only
        STATUS		current
        DESCRIPTION
            "If port auto-negotiation state is complete then this object
            indicates the media converter module's current auto-negotiated duplex
            setting for this port. If auto-negotiation is not complete then the
            value returned should be ignored."
        ::= { mcrMediaPortEntry 12 }

    portPause	OBJECT-TYPE
        SYNTAX INTEGER {
            notApplicable(-1),
            disabled(0),
            symmetrical(1),
            asymmetricalTx(2),
            asymmetricalRx(3)
        }
        MAX-ACCESS	read-only
        STATUS		current
        DESCRIPTION
            "If port auto-negotiation state is complete then this object indicates
             the media converter module's current auto-negotiated pause setting for this
             port. If auto-negotiation is not complete then the value returned
             should be ignored."
        ::= { mcrMediaPortEntry 13 }

    portRemoteStatus		OBJECT-TYPE
        SYNTAX INTEGER {
            notApplicable(-1),
            ok(0),
            remoteFault(1),
            offline(2),
            linkFault(3),
            autoNegError(4),
            disable(5),
            receivingFEF(6),
            sendingFEF(7)
        }
        MAX-ACCESS	read-only
        STATUS		current
        DESCRIPTION
            "This port's Link Partner Remote Fault status or Far End Fault status"
        ::= { mcrMediaPortEntry 14 }

    portMediaType	OBJECT-TYPE
        SYNTAX		INTEGER {
            unknown(-1),
            copper(0),
            fiber(1)
        }
        MAX-ACCESS	read-only
        STATUS		current
        DESCRIPTION
            "The type of port (copper, fiber, etc.) ."
        ::= { mcrMediaPortEntry 15}
    portPhysicalProtocol	OBJECT-TYPE
        SYNTAX		INTEGER {
            unknown(0),
            ethernet(1),
            vdsl(2)
        }
        MAX-ACCESS	read-only
        STATUS		current
        DESCRIPTION
            "The physical networking protocol used by the port."
        ::= { mcrMediaPortEntry 16}

--
-- end of mcrMediaPortTable
--

--
-- end of mcrChassisGroup
--



--
-- mcrManagementGroup
--
mgtNetworkGroup			OBJECT IDENTIFIER ::= { mcrManagementGroup 1 }
mgtAccessGroup				OBJECT IDENTIFIER ::= { mcrManagementGroup 2 }
mgtAlertGroup				OBJECT IDENTIFIER ::= { mcrManagementGroup 3 }
mgtUsersGroup				OBJECT IDENTIFIER ::= { mcrManagementGroup 4 }
mgtDateTimeGroup			OBJECT IDENTIFIER ::= { mcrManagementGroup 5 }
mgtFilesGroup				OBJECT IDENTIFIER ::= { mcrManagementGroup 6 }
mgtAdminGroup				OBJECT IDENTIFIER ::= { mcrManagementGroup 7 }
mgtDisplayFormatGroup	OBJECT IDENTIFIER ::= { mcrManagementGroup 8 }
mgtChassisCfgGroup 		OBJECT IDENTIFIER ::= { mcrManagementGroup 9 }

--
-- mgtNetworkGroup
--
--
--  systemGroup.
--
systemGroup		OBJECT IDENTIFIER  ::= { mgtNetworkGroup 1 }

systemStatus OBJECT-TYPE
    SYNTAX      ContainerStatus
    MAX-ACCESS  read-write
    STATUS      current
    DESCRIPTION
      "When you perform a GET on this variable, one of
        the following values will be returned:
        1-Indicates that the container folder is active with no changes.
        2-Indicates that the container folder is active with change(s).
        Once you have completed setting the variables in a folder, you
        will want to submit your changes to the management module. To do
        this, set the Status variable to 4. If you want to discard the
        changes, set the Status variable to 6.
        4-Indicates that the changes in the container folder are to be
          submitted to the management module.
        6-Indicates that the changes in the container folder are to be
          discarded."
    ::= { systemGroup 1 }

systemName OBJECT-TYPE
    SYNTAX      DisplayString(SIZE(1..63))
    MAX-ACCESS  read-write
    STATUS      current
    DESCRIPTION
      "The name of the system management module."
    ::= { systemGroup 2 }

systemDomainName OBJECT-TYPE
    SYNTAX      DisplayString(SIZE(0..32))
    MAX-ACCESS  read-write
    STATUS      current
    DESCRIPTION
        "The domain name of the management module."
    ::= { systemGroup 3 }

systemIpAddress OBJECT-TYPE
    SYNTAX      IpAddress
    MAX-ACCESS  read-write
    STATUS      current
    DESCRIPTION
        "The management module's unique IPv4 network IP address.
         If you are using the management module in an IPv6 network,
         this field can be left blank."
    ::= { systemGroup 4 }

systemSubnetBits OBJECT-TYPE
    SYNTAX      Integer32(0..32)
    MAX-ACCESS  read-write
    STATUS      current
    DESCRIPTION
        "The number of bits in the subnet mask. For example, a subnet mask
         of 255.255.0.0 has 16 subnet/prefix bits. Valid values are 0-32.
         The default is 0. When the value is 0, the correct value is determined
         based on the class of the IP Address."
    ::= { systemGroup 5 }

systemDHCPUpdateDNS OBJECT-TYPE
    SYNTAX      OnOffValue
    MAX-ACCESS  read-write
    STATUS      current
    DESCRIPTION
        "If enabled, the DNS system will be updated after the management module
         gets the IP address via DHCP."
    ::= { systemGroup 6 }

systemAutoObtainDNS OBJECT-TYPE
    SYNTAX      OnOffValue
    MAX-ACCESS  read-write
    STATUS      current
    DESCRIPTION
        "If on, the DNS server IP address will be obtained automatically
         automatically via DHCP."
    ::= { systemGroup 7 }

systemAutoObtainGW OBJECT-TYPE
    SYNTAX      OnOffValue
    MAX-ACCESS  read-write
    STATUS      current
    DESCRIPTION
        "If enabled, the default gateway IP address will be get automatically via DHCP."
    ::= { systemGroup 8 }

systemDomainPrefix OBJECT-TYPE
    SYNTAX      DisplayString(SIZE(0..7))
    MAX-ACCESS  read-write
    STATUS      current
    DESCRIPTION
              "The domain prefix for primary Ethernet interface of the management module."
    ::= { systemGroup 9 }


systemTFTPRetry OBJECT-TYPE
    SYNTAX      Integer32(0..5)
    MAX-ACCESS  read-write
    STATUS      current
    DESCRIPTION
              "The number of times the management module will attempt to
                transfer (using TFTP) a file to/from a host. Default is 5.
                A value of 0 (zero) means that the management module will not
                attempt a retry should TFTP fail."
    ::= { systemGroup 10 }

systemTFTPTimeOut OBJECT-TYPE
    SYNTAX      Integer32(3..10)
    MAX-ACCESS  read-write
    STATUS      current
    DESCRIPTION
              "The time, in seconds, that the management module will wait for
                a successful transmit or receipt of TFTP packets before retrying
                a TFTP transfer. Default is 3 seconds."
    ::= { systemGroup 11 }

--
--  end of systemGroup
--
--
--
-- gatewayTable
--
gatewayTable OBJECT-TYPE
    SYNTAX      SEQUENCE OF GatewayEntry
    MAX-ACCESS  not-accessible
    STATUS      current
    DESCRIPTION
        "Table of configured gateway."
    ::= { mgtNetworkGroup 2}

    gatewayEntry OBJECT-TYPE
        SYNTAX      GatewayEntry
        MAX-ACCESS  not-accessible
        STATUS      current
        DESCRIPTION
            "Entries of the table, each relating to a separate configured gateway. "
        INDEX   { gatewayIndex }
        ::= { gatewayTable 1 }

    GatewayEntry ::=
        SEQUENCE {
            gatewayIndex			GenericTableIndex,
            gatewayStatus        ContainerStatus,
            gatewayHost          DisplayString,
            gatewayType          INTEGER,
            gatewayIpAddress     Ipv4v6Address,
            gatewaySubnetBits    Integer32,
            gatewayInterface     DisplayString
        }

    gatewayIndex OBJECT-TYPE
        SYNTAX      GenericTableIndex
        MAX-ACCESS  not-accessible
        STATUS      current
        DESCRIPTION
                  "gatewayIndex"
        ::= { gatewayEntry 1}

    gatewayStatus OBJECT-TYPE
        SYNTAX      ContainerStatus
        MAX-ACCESS  read-write
        STATUS      current
        DESCRIPTION
                  "When you perform a GET on this variable, one of
                    the following values will be returned:
                    1-Indicates that the container folder is active with no changes.
                    2-Indicates that the container folder is active with change(s).
                    Once you have completed setting the variables in a folder, you
                    will want to submit your changes to the management module. To do
                    this, set the Status variable to 4. If you want to discard the
                    changes, set the Status variable to 6.
                    4-Indicates that the changes in the container folder are to be
                      submitted to the management module and verified. To save the
                      changes to flash a write of writeToFlash(1) in the adminFunction
                      object is required.
                    6-Indicates that the changes in the container folder are to be
                      discarded."
        ::= { gatewayEntry 2}

    gatewayHost OBJECT-TYPE
        SYNTAX      DisplayString(SIZE(0..14))
        MAX-ACCESS  read-write
        STATUS      current
        DESCRIPTION
                  "You can specify up to twenty hosts to act as gateways
                    in your network. Each gateway host must be defined in
                    the management module host table."
        ::= { gatewayEntry 3}

    gatewayType OBJECT-TYPE
        SYNTAX      INTEGER {
          host(0),
          network(1),
          default(2)
        }
        MAX-ACCESS  read-write
        STATUS      current
        DESCRIPTION
                  "Specify the type of gateway:
                    Default-A gateway which provides general access beyond
                          your local network.
                    Host-A gateway reserved for accessing a specific host
                          external to your local network.
                    Network-A gateway reserved for accessing a specific
                          network external to your local network."
        ::= { gatewayEntry 4}

    gatewayIpAddress OBJECT-TYPE
        SYNTAX      Ipv4v6Address
        MAX-ACCESS  read-write
        STATUS      current
        DESCRIPTION
                  "When the gateway is a Host or Network gateway, you must
                    specify the IP address of the target host machine/network."
        ::= { gatewayEntry 5}

    gatewaySubnetBits OBJECT-TYPE
        SYNTAX      Integer32(0..128)
        MAX-ACCESS  read-write
        STATUS      current
        DESCRIPTION
                  "When the gateway is a Network gateway, you must specify the
                    subnet/prefix bits for that network. If the IP address is IPv4,
                    then the Subnet/Prefix Bits range is 0-32. If the IP address
                    is IPv6, then the Subnet/Prefix Bits range is 0-128."
        ::= { gatewayEntry 6}

    gatewayInterface OBJECT-TYPE
        SYNTAX      DisplayString(SIZE(0..20))
        MAX-ACCESS  read-write
        STATUS      current
        DESCRIPTION
                  "The interface that the management module is going to use to access the
                    Remote Host."

        ::= { gatewayEntry 7}
--
-- end of gatewayTable
--


--  hostTable
--
hostTable OBJECT-TYPE
    SYNTAX      SEQUENCE OF HostEntry
    MAX-ACCESS  not-accessible
    STATUS      current
    DESCRIPTION
        "The hosts Group table."
    ::= { mgtNetworkGroup 3 }

    hostEntry OBJECT-TYPE
        SYNTAX      HostEntry
        MAX-ACCESS  not-accessible
        STATUS      current
        DESCRIPTION
            "An entry in the host table, each relating to a separate host."
        INDEX   { hostIndex }
        ::= { hostTable 1 }

    HostEntry ::=
        SEQUENCE {
          hostIndex			GenericTableIndex,
          hostStatus		ContainerStatus,
          hostName			DisplayString,
          hostIpAddr		Ipv4v6Address,
          hostFqdn			DisplayString
        }

    hostIndex OBJECT-TYPE
        SYNTAX      GenericTableIndex
        MAX-ACCESS  not-accessible
        STATUS      current
        DESCRIPTION
            "The table entry number for this host."
        ::= { hostEntry 1 }

    hostStatus OBJECT-TYPE
        SYNTAX      ContainerStatus
        MAX-ACCESS  read-write
        STATUS      current
        DESCRIPTION
            "When you perform a GET on this variable, one of
             the following values will be returned:
             1-Indicates that the container folder is active with no changes.
             2-Indicates that the container folder is active with change(s).
               Once you have completed setting the variables in a folder, you
               will want to submit your changes to the management module. To do
               this, set the Status variable to 4. If you want to discard the
               changes, set the Status variable to 6.
             4-Indicates that the changes in the container folder are to be
              submitted to the management module and verified. To save the
              changes to flash a write of writeToFlash(1) in the adminFunction
              object is required.
             6-Indicates that the changes in the container folder are to be
                discarded."
        ::= { hostEntry 2 }

    hostName OBJECT-TYPE
        SYNTAX      DisplayString(SIZE(0..14))
        MAX-ACCESS  read-write
        STATUS      current
        DESCRIPTION
            "The host name used for this host entry.
             To delete an entry, blank out this field.
             If blank, this entry is currently unused."
        ::= { hostEntry 3 }

    hostIpAddr OBJECT-TYPE
        SYNTAX      Ipv4v6Address
        MAX-ACCESS  read-write
        STATUS      current
        DESCRIPTION
            "The host IP address used for this entry."
        ::= { hostEntry 4 }

    hostFqdn OBJECT-TYPE
        SYNTAX      DisplayString(SIZE(0..255))
        MAX-ACCESS  read-write
        STATUS      current
        DESCRIPTION
            "The host full qualified domain name for the host entry.
             If blank, this entry is currently unused."
        ::= { hostEntry 5 }
--
--  end of hostTable
--

--
-- dnsTable
--
dnsTable OBJECT-TYPE
    SYNTAX      SEQUENCE OF DnsEntry
    MAX-ACCESS  not-accessible
    STATUS      current
    DESCRIPTION
        "Table of DNS hosts"
    ::= { mgtNetworkGroup 4 }

    dnsEntry OBJECT-TYPE
        SYNTAX      DnsEntry
        MAX-ACCESS  not-accessible
        STATUS      current
        DESCRIPTION
            "Entries of the table, each relating to a separate DNS host."
        INDEX   { dnsIndex }
        ::= { dnsTable 1 }

    DnsEntry ::=
        SEQUENCE {
            dnsIndex			GenericTableIndex,
            dnsStatus		ContainerStatus,
            dnsIpAddress	Ipv4v6Address,
            dnsActive		OnOffValue
        }

    dnsIndex OBJECT-TYPE
        SYNTAX      GenericTableIndex
        MAX-ACCESS  not-accessible
        STATUS      current
        DESCRIPTION
            "DNS host index "
        ::= { dnsEntry 1}

    dnsStatus OBJECT-TYPE
        SYNTAX      ContainerStatus
        MAX-ACCESS  read-write
        STATUS      current
        DESCRIPTION
                  "When you perform a GET on this variable, one of
                    the following values will be returned:
                    1-Indicates that the container folder is active with no changes.
                    2-Indicates that the container folder is active with change(s).
                     Once you have completed setting the variables in a folder, you
                     will want to submit your changes to the management module. To do
                     this, set the Status variable to 4. If you want to discard the
                     changes, set the Status variable to 6.
                    4-Indicates that the changes in the container folder are to be
                      submitted to the management module and verified. To save the
                      changes to flash a write of writeToFlash(1) in the adminFunction
                      object is required.
                    6-Indicates that the changes in the container folder are to be
                      discarded."
        ::= { dnsEntry 2 }

    dnsIpAddress OBJECT-TYPE
        SYNTAX      Ipv4v6Address
        MAX-ACCESS  read-write
        STATUS      current
        DESCRIPTION
            "You can specify the IP addresses for up to two DNS
             (Domain Name Servers) hosts in your network. The first
             DNS entry in the list is the primary DNS and the second
             DNS entry is the secondary server."
        ::= { dnsEntry 3}

    dnsActive OBJECT-TYPE
        SYNTAX      OnOffValue
        MAX-ACCESS  read-write
        STATUS      current
        DESCRIPTION
            "Activates/deactivates a DNS entry."
        ::= { dnsEntry 4}
--
-- end of dnsTable
--

--
-- dynamicDNSGroup
--
dynamicDNSGroup       OBJECT IDENTIFIER  ::= { mgtNetworkGroup 5 }

dynamicDNSStatus OBJECT-TYPE
    SYNTAX      ContainerStatus
    MAX-ACCESS  read-write
    STATUS      current
    DESCRIPTION
        "When you perform a GET on this variable, one of
         the following values will be returned:
           1-Indicates that the container folder is active with no changes.
            2-Indicates that the container folder is active with change(s).
              Once you have completed setting the variables in a folder, you
              will want to submit your changes to the management module. To do
              this, set the Status variable to 4. If you want to discard the
              changes, set the Status variable to 6.
            4-Indicates that the changes in the container folder are to be
              submitted to the management module and verified. To save the
              changes to flash a write of writeToFlash(1) in the adminFunction
              object is required.
            6-Indicates that the changes in the container folder are to be
              discarded."
    ::= {dynamicDNSGroup 1}

dynamicDNS OBJECT-TYPE
    SYNTAX      OnOffValue
    MAX-ACCESS  read-write
    STATUS      current
    DESCRIPTION
        "Enable/disable dynamic DNS."
    ::= { dynamicDNSGroup 2}

dynamicDNSHostname OBJECT-TYPE
    SYNTAX      DisplayString(SIZE(1..14))
    MAX-ACCESS  read-write
    STATUS      current
    DESCRIPTION
        "Host name."
    ::= { dynamicDNSGroup 3}

dynamicDNSUserName OBJECT-TYPE
    SYNTAX      DisplayString(SIZE(1..16))
    MAX-ACCESS  read-write
    STATUS      current
    DESCRIPTION
        "User name."
    ::= { dynamicDNSGroup 4}

dynamicDNSPassword OBJECT-TYPE
SYNTAX      DisplayString(SIZE(1..16))
MAX-ACCESS  read-write
STATUS      current
DESCRIPTION
    "This object identifies the dynamic DNS password. Reading of this object will
     always return a blank string"
::= { dynamicDNSGroup 5}

dynamicDNSSystemType OBJECT-TYPE
    SYNTAX      INTEGER {
      dynamic(0),
      static(1),
      custom(2)
    }
    MAX-ACCESS  read-write
    STATUS      current
    DESCRIPTION
        "System type."
    ::= { dynamicDNSGroup 6}

dynamicDNSWildCard OBJECT-TYPE
    SYNTAX      INTEGER {
      enable(0),
      disable(1),
      nochange(2)
    }
    MAX-ACCESS  read-write
    STATUS      current
    DESCRIPTION
        "Specifies whether to add a alias such as * to your registered host name."
    ::= { dynamicDNSGroup 7}

dynamicDNSConnectionMethod OBJECT-TYPE
    SYNTAX      INTEGER {
      http(0),
      httpport8245(1),
      https(2)
    }
    MAX-ACCESS  read-write
    STATUS      current
    DESCRIPTION
        "Specifies how the management module is going to connection to the
       DynDNS.org server."
    ::= { dynamicDNSGroup 8}

dynamicDNSSSLVerifyPeerCertificate  OBJECT-TYPE
    SYNTAX   OnOffValue
    MAX-ACCESS    read-write
    STATUS        current
    DESCRIPTION
         "Enable this option when you want the Validation Criteria
          to match the Peer Certificate for authentication to pass.
          If you enable this option, you need to download an
          SSL/TLS certificate authority (CA) list file to the
          management module. Any values that are entered in the validation
          criteria must match the peer certificate for an SSL connection;
          any fields left blank will not be validated against the peer
          certificate."
    ::= {dynamicDNSGroup 9}

dynamicDNSSSLCountry    OBJECT-TYPE
    SYNTAX      DisplayString(SIZE(0..2))
    MAX-ACCESS    read-write
    STATUS        current
    DESCRIPTION
        "A two character country code; for example, US."
    ::= {dynamicDNSGroup 10}

dynamicDNSSSLStateProv    OBJECT-TYPE
    SYNTAX      DisplayString(SIZE(0..128))
    MAX-ACCESS    read-write
    STATUS        current
    DESCRIPTION
        "Up to a 128 character entry for the state/province;
         for example, IL."
    ::= {dynamicDNSGroup 11}

dynamicDNSSSLLocality    OBJECT-TYPE
    SYNTAX      DisplayString(SIZE(0..128))
    MAX-ACCESS    read-write
    STATUS        current
    DESCRIPTION
         "Up to a 128 character entry for the location;
          for example, a city."
    ::= {dynamicDNSGroup 12}

dynamicDNSSSLOrganisation    OBJECT-TYPE
    SYNTAX      DisplayString(SIZE(0..64))
    MAX-ACCESS    read-write
    STATUS        current
    DESCRIPTION
         "Up to a 64 character entry for the organization;
          for example, Accounting."
    ::= {dynamicDNSGroup 13}

dynamicDNSSSLOrganisationUnit    OBJECT-TYPE
    SYNTAX      DisplayString(SIZE(0..64))
    MAX-ACCESS    read-write
    STATUS        current
    DESCRIPTION
         "Up to a 64 character entry for the unit in the
          organization; for example, Payroll."
    ::= {dynamicDNSGroup 14}

dynamicDNSSSLCommonName    OBJECT-TYPE
    SYNTAX      DisplayString(SIZE(0..64))
    MAX-ACCESS    read-write
    STATUS        current
    DESCRIPTION
        "Up to a 64 character entry for common name; for example,
         the host name or fully qualified domain name."
    ::= {dynamicDNSGroup 15}

dynamicDNSSSLEmail    OBJECT-TYPE
    SYNTAX      DisplayString(SIZE(0..128))
    MAX-ACCESS    read-write
    STATUS        current
    DESCRIPTION
        "Up to a 64 character entry for an email address;
         for example, acct@anycompany.com."
    ::= {dynamicDNSGroup 16}

dynamicDNSStatusString OBJECT-TYPE
    SYNTAX      OCTET STRING (SIZE(0..1024))
    MAX-ACCESS  read-only
    STATUS      current
    DESCRIPTION
        "Dynamic DNS statistics"
    ::= {dynamicDNSGroup 17}
--
-- dynamicDNSSSLCipherTable
--
dynamicDNSSSLCipherTable OBJECT-TYPE
    SYNTAX      SEQUENCE OF DynamicDNSSSLCipherEntry
    MAX-ACCESS  not-accessible
    STATUS      current
    DESCRIPTION
        "SSL Cipher."
    ::= {dynamicDNSGroup 18}

    dynamicDNSSSLCipherEntry OBJECT-TYPE
        SYNTAX      DynamicDNSSSLCipherEntry
        MAX-ACCESS  not-accessible
        STATUS      current
        DESCRIPTION
            "An entry in the dynamicDNSSSLCipherTable, each relating to a cipher entry."
        INDEX   { dynamicDNSSSLCipherPriority }
        ::= { dynamicDNSSSLCipherTable 1 }

    DynamicDNSSSLCipherEntry ::=
        SEQUENCE {
            dynamicDNSSSLCipherPriority        Integer32,
            dynamicDNSSSLCipherStatus        ContainerStatus,
            dynamicDNSSSLCipherEncryption        INTEGER,
            dynamicDNSSSLCipherKeySizeMin        INTEGER,
            dynamicDNSSSLCipherKeySizeMax        INTEGER,
            dynamicDNSSSLCipherKeyExchange        INTEGER,
            dynamicDNSSSLCipherHMAC        INTEGER
        }

    dynamicDNSSSLCipherPriority OBJECT-TYPE
        SYNTAX      Integer32(1..5)
        MAX-ACCESS  not-accessible
        STATUS      current
        DESCRIPTION
            "The cipher priority. 1- highest 5 - lowest."
        ::= { dynamicDNSSSLCipherEntry 1 }

    dynamicDNSSSLCipherStatus OBJECT-TYPE
        SYNTAX      ContainerStatus
        MAX-ACCESS  read-write
        STATUS      current
        DESCRIPTION
            "When you perform a GET on this variable, one of
             the following values will be returned:
              1-Indicates that the container folder is active with no changes.
              2-Indicates that the container folder is active with change(s).
                Once you have completed setting the variables in a folder, you
                will want to submit your changes to the management module. To do
                this, set the Status variable to 4. If you want to discard the
                changes, set the Status variable to 6.
              4-Indicates that the changes in the container folder are to be
                 submitted to the management module and verified. To save the
                 changes to flash a write of writeToFlash(1) in the adminFunction
                 object is required.
              6-Indicates that the changes in the container folder are to be
                 discarded."
        ::= { dynamicDNSSSLCipherEntry 2 }

    dynamicDNSSSLCipherEncryption OBJECT-TYPE
        SYNTAX      INTEGER {
          none(0),
          any(1),
          aes(2),
          tripledes(3),
          des(4),
          arctwo(5),
          arcfour(6)
        }
        MAX-ACCESS  read-write
        STATUS      current
        DESCRIPTION
                  "SSL Encryption. None is not allowed for priority 1.
                    Any will use the first encryption format that can be
                    negotiated. The default is any."
        ::= { dynamicDNSSSLCipherEntry 3 }

    dynamicDNSSSLCipherKeySizeMin OBJECT-TYPE
        SYNTAX      INTEGER {
          min40(0),
          min56(1),
          min64(2),
          min128(3),
          min168(4),
          min256(5)
        }
        MAX-ACCESS  read-write
        STATUS      current
        DESCRIPTION
                  "The minimum key size value that will be used for
                    the specified encryption type. The default is 40."
        ::= { dynamicDNSSSLCipherEntry 4 }

    dynamicDNSSSLCipherKeySizeMax OBJECT-TYPE
        SYNTAX      INTEGER {
          max40(0),
          max56(1),
          max64(2),
          max128(3),
          max168(4),
          max256(5)
        }
        MAX-ACCESS  read-write
        STATUS      current
        DESCRIPTION
                  "The maximum key size value that will be used for the
                    specified encryption type. The default is 256."
        ::= { dynamicDNSSSLCipherEntry 5 }

    dynamicDNSSSLCipherKeyExchange OBJECT-TYPE
        SYNTAX      INTEGER {
          any(0),
          rsa(1),
          edhrsa(2),
          edhdss(3),
          adh(4)
        }
        MAX-ACCESS  read-write
        STATUS      current
        DESCRIPTION
                  "The type of key to exchange for the encryption format:
                    Any-Any key exchange that is valid is used (this does
                         not, however, include ADH keys).
                    RSA-This is an RSA key exchange using an RSA key and
                         certificate.
                    EDHRSA-This is an EDH key exchange using an RSA key
                         and certificate.
                    EDHDSS-This is an EDH key exchange using a DSA key
                         and certificate.
                    ADH-This is an anonymous key exchange which does not
                         require a private key or certificate. Choose this
                         key if you do not want to authenticate the peer device,
                         but you want the data encrypted on the SSL/TLS connection.
                    The default is Any."
        ::= { dynamicDNSSSLCipherEntry 6 }

    dynamicDNSSSLCipherHMAC OBJECT-TYPE
        SYNTAX      INTEGER {
          any(0),
          sha(1),
          md5(2)
        }
        MAX-ACCESS  read-write
        STATUS      current
        DESCRIPTION
                  "Select the key-hashing for message authentication method
                    for your encryption type: Any, MD5, or SHA1.
                    The default is Any."
        ::= { dynamicDNSSSLCipherEntry 7 }
--
-- end of dynamicDNSSSLCipherTable
--
--
-- end of dynamicDNSGroup
--

--
-- ipv6Group
--
ipv6Group	OBJECT IDENTIFIER  ::= { mgtNetworkGroup 6 }

--
-- ipv6ServicesGroup
--
  ipv6ServicesGroup          OBJECT IDENTIFIER ::= { ipv6Group 1 }

  ipv6serviceStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
                 Once you have completed setting the variables in a folder, you
                 will want to submit your changes to the management module. To do
                 this, set the Status variable to 4. If you want to discard the
                 changes, set the Status variable to 6.
                    4-Indicates that the changes in the container folder are to be
                      submitted to the management module and verified. To save the
                      changes to flash a write of writeToFlash(1) in the adminFunction
                      object is required.
               6-Indicates that the changes in the container folder are to be
                 discarded."
      ::= {ipv6ServicesGroup 1}

  serviceAutoDiscovery OBJECT-TYPE
      SYNTAX      OnOffValue
      MAX-ACCESS  read-write
      STATUS      current
      DESCRIPTION
              "When on, the management module will send out a Router Solicitation
               message. If a Router Advertisement message is received, the
               management module will configure the IPv6 address(es) and configuration
               parameters based on the information contained in the advertisement.
               If no Router Advertisement message is received, the management module
               will attempt to connect to a DHCPv6 server to obtain IPv6 addresses
               and other configuration parameters. Default on."
      ::= { ipv6ServicesGroup 2 }

  serviceDHCPv6 OBJECT-TYPE
      SYNTAX      OnOffValue
      MAX-ACCESS  read-write
      STATUS      current
      DESCRIPTION
              "When on, requests IPv6 address(es) and configuration
               information from the DHCPv6 server. Default off."
      ::= { ipv6ServicesGroup 3 }

  serviceDHCPv6IPAddresses OBJECT-TYPE
      SYNTAX      OnOffValue
      MAX-ACCESS  read-write
      STATUS      current
      DESCRIPTION
        "When on, the management module will accept IPv6 address(es)
         from the DHCPv6 server."
      ::= { ipv6ServicesGroup 4 }

  serviceDHCPv6NetworkPrefix OBJECT-TYPE
      SYNTAX      OnOffValue
      MAX-ACCESS  read-write
      STATUS      current
      DESCRIPTION
              "When on, the management module will accept the network prefix
               from the DHCPv6 server."
      ::= { ipv6ServicesGroup 5 }

  serviceDHCPv6AutoObtainDNS OBJECT-TYPE
    SYNTAX      OnOffValue
    MAX-ACCESS  read-write
    STATUS      current
    DESCRIPTION
        "If on, the DNS server IP address will be obtained automatically
         automatically via DHCP."
    ::= { ipv6ServicesGroup 6 }

--
-- end of ipv6ServicesGroup
--

--
-- ipv6AddressTable
--
ipv6AddressTable OBJECT-TYPE
    SYNTAX      SEQUENCE OF Ipv6AddressEntry
    MAX-ACCESS  not-accessible
    STATUS      current
    DESCRIPTION
              "IPv6 custom address table."
    ::= { ipv6Group 2 }

ipv6AddressEntry OBJECT-TYPE
    SYNTAX      Ipv6AddressEntry
    MAX-ACCESS  not-accessible
    STATUS      current
    DESCRIPTION
              "IPv6 custom entry."
    INDEX   { ipv6AddressIndex }
    ::= { ipv6AddressTable 1 }

    Ipv6AddressEntry ::=
        SEQUENCE {
            ipv6AddressIndex				GenericTableIndex,
            ipv6AddressStatus				ContainerStatus,
            ipv6AddressAddr				Ipv4v6Address,
            ipv6AddressPrefixBits		Integer32,
            ipv6AddressAuto				OnOffValue,
            ipv6AddressSendAdvertise	OnOffValue
        }

    ipv6AddressIndex OBJECT-TYPE
        SYNTAX      GenericTableIndex
        MAX-ACCESS  not-accessible
        STATUS      current
        DESCRIPTION
            "Custom IPv6 address index."
        ::= { ipv6AddressEntry 1 }

    ipv6AddressStatus OBJECT-TYPE
        SYNTAX      ContainerStatus
        MAX-ACCESS  read-write
        STATUS      current
        DESCRIPTION
            "When you perform a GET on this variable, one of
             the following values will be returned:
          1-Indicates that the container folder is active with no changes.
          2-Indicates that the container folder is active with change(s).
            Once you have completed setting the variables in a folder, you
            will want to submit your changes to the management module. To do
            this, set the Status variable to 4. If you want to discard the
            changes, set the Status variable to 6.
          4-Indicates that the changes in the container folder are to be
            submitted to the management module and verified. To save the
            changes to flash a write of writeToFlash(1) in the adminFunction
            object is required.
             6-Indicates that the changes in the container folder are to be
                discarded."
        ::= { ipv6AddressEntry 2 }

    ipv6AddressAddr OBJECT-TYPE
        SYNTAX      Ipv4v6Address
        MAX-ACCESS  read-write
        STATUS      current
        DESCRIPTION
            "Either enter a network prefix that the Device
            Server will use to derive an IPv6 address using the Device
            Server's MAC address (must turn ipv6AddressAuto1 on)
            or enter a specific IPv6 address."
        ::= { ipv6AddressEntry 3 }

    ipv6AddressPrefixBits OBJECT-TYPE
        SYNTAX      Integer32(0..128)
        MAX-ACCESS  read-write
        STATUS      current
        DESCRIPTION
            "The IPv6 prefix bits of either the network or
            IPv6 address."
        ::= { ipv6AddressEntry 4 }

    ipv6AddressAuto  OBJECT-TYPE
        SYNTAX   OnOffValue
        MAX-ACCESS    read-write
        STATUS        current
        DESCRIPTION
            "When on, the management module will derive
             an IPv6 address from the entered network prefix and the
             management module's MAC address."
        ::= {ipv6AddressEntry 5}

    ipv6AddressSendAdvertise  OBJECT-TYPE
        SYNTAX   OnOffValue
        MAX-ACCESS    read-write
        STATUS        current
        DESCRIPTION
            "When on, the management module will include
             the IPv6 address in router advertisements."
        ::= {ipv6AddressEntry 6}
--
-- end of ipv6AddressTable
--

--
-- interfacev6StatsTable
--
interfacev6StatsTable OBJECT-TYPE
    SYNTAX      SEQUENCE OF Interfacev6StatsEntry
    MAX-ACCESS  not-accessible
    STATUS      current
    DESCRIPTION
        "The interface IPv6 Group table."
    ::= { ipv6Group 3 }

interfacev6StatsEntry OBJECT-TYPE
    SYNTAX      Interfacev6StatsEntry
    MAX-ACCESS  not-accessible
    STATUS      current
    DESCRIPTION
        "An entry in the interface IPv6 table"
    INDEX   { interfacev6Index }
    ::= { interfacev6StatsTable 1 }

    Interfacev6StatsEntry ::=
        SEQUENCE {
          interfacev6Index             GenericTableIndex,
          interfacev6Name              DisplayString,
          interfacev6Address           DisplayString,
          interfacev6PrefixBits        Integer32,
          interfacev6Scope             INTEGER
        }

    interfacev6Index OBJECT-TYPE
        SYNTAX      GenericTableIndex
        MAX-ACCESS  not-accessible
        STATUS      current
        DESCRIPTION
            "The IPv6 interface index."
        ::= { interfacev6StatsEntry 1}

    interfacev6Name OBJECT-TYPE
        SYNTAX      DisplayString
        MAX-ACCESS  read-only
        STATUS      current
        DESCRIPTION
            "The IPv6 interface name."
        ::= { interfacev6StatsEntry 2}

    interfacev6Address OBJECT-TYPE
        SYNTAX      DisplayString
        MAX-ACCESS  read-only
        STATUS      current
        DESCRIPTION
            "The IPv6 interface IP address."
        ::= { interfacev6StatsEntry 3}

    interfacev6PrefixBits OBJECT-TYPE
        SYNTAX      Integer32(0..128)
        MAX-ACCESS  read-only
        STATUS      current
        DESCRIPTION
            "The IPv6 interface Prefix bits"
        ::= { interfacev6StatsEntry 4}

    interfacev6Scope OBJECT-TYPE
        SYNTAX      INTEGER {
            global(0),
            host(1),
            link(2),
            site(3),
            compatv4(4),
            unknown(5)
        }
        MAX-ACCESS  read-only
        STATUS      current
        DESCRIPTION
            "The IPv6 interface scope."
        ::= { interfacev6StatsEntry 5}
--
-- end of interfacev6StatsTable
--

--
-- ipv6TunnelTable
--
ipv6TunnelTable OBJECT-TYPE
    SYNTAX      SEQUENCE OF Ipv6TunnelEntry
    MAX-ACCESS  not-accessible
    STATUS      current
    DESCRIPTION
        "IPv6 tunnel table."
    ::= { ipv6Group 4 }

ipv6TunnelEntry OBJECT-TYPE
    SYNTAX      Ipv6TunnelEntry
    MAX-ACCESS  not-accessible
    STATUS      current
    DESCRIPTION
        "IPv6 tunnel entry."
    INDEX   { ipv6TunnelIndex }
    ::= { ipv6TunnelTable 1 }

Ipv6TunnelEntry ::=
    SEQUENCE {
        ipv6TunnelIndex			GenericTableIndex,
        ipv6TunnelStatus			ContainerStatus,
        ipv6TunnelName				DisplayString,
        ipv6TunnelMode				INTEGER,
        ipv6TunnelRemoteHost		DisplayString
    }

ipv6TunnelIndex OBJECT-TYPE
    SYNTAX      GenericTableIndex
    MAX-ACCESS  not-accessible
    STATUS      current
    DESCRIPTION
        "The IPv6 tunnel index."
    ::= { ipv6TunnelEntry 1 }

ipv6TunnelStatus OBJECT-TYPE
    SYNTAX      ContainerStatus
    MAX-ACCESS  read-write
    STATUS      current
    DESCRIPTION
        "When you perform a GET on this variable, one of
         the following values will be returned:
         1-Indicates that the container folder is active with no changes.
         2-Indicates that the container folder is active with change(s).
           Once you have completed setting the variables in a folder, you
           will want to submit your changes to the management module. To do
           this, set the Status variable to 4. If you want to discard the
           changes, set the Status variable to 6.
         4-Indicates that the changes in the container folder are to be
           submitted to the management module and verified. To save the
           changes to flash a write of writeToFlash(1) in the adminFunction
           object is required.
         6-Indicates that the changes in the container folder are to be
           discarded."
    ::= { ipv6TunnelEntry 2 }

ipv6TunnelName OBJECT-TYPE
    SYNTAX      DisplayString
    MAX-ACCESS  read-write
    STATUS      current
    DESCRIPTION
        "The name of the IPv6 tunnel. Maximum 16 alphanumeric characters."
    ::= { ipv6TunnelEntry 3 }

ipv6TunnelMode OBJECT-TYPE
    SYNTAX      INTEGER {
      manual(0),
      ip6to4(1),
      teredo(2)
    }
    MAX-ACCESS  read-write
    STATUS      current
    DESCRIPTION
        "The method or protocol that is used to create the IPv6 tunnel.
         o Manual-When specified, the management module will manually create the IPv6
         tunnel to the specified Remote Host through the specified Interface.
            o ip6to4-When specified, the MCR-MGT will broadcast to the multicast
              address 192.88.99.1 through the specified Interface. When the
              closest ip6to4 router responds, it will create the IPv6 tunnel,
              encapsulating and decapsulating IPv6 traffic sent to and from
              the management module.
            o Teredo-When specified, the Teredo protocol encapsulates the IPv6
              packet as an IPv4 UDP message, allowing it to pass through most
              network address translator (NAT) boxes and create an IPv6 tunnel
              to the specified Remote Host (a Teredo server) through the
              specified Interface.
              Default is Manual."
    ::= { ipv6TunnelEntry 4 }

ipv6TunnelRemoteHost OBJECT-TYPE
    SYNTAX      DisplayString
    MAX-ACCESS  read-write
    STATUS      current
    DESCRIPTION
        "The IPv4 host that can access the IPv6 network when the Mode
         is Manual. The Teredo server when the Mode is Teredo. "
    ::= { ipv6TunnelEntry 5 }

--
-- end of ipv6TunnelTable
--

--
-- end of ipv6Group
--
--
--  end of mgtNetworkGroup
--


--
-- mgtAcessServicesGroup
--


-- mgtServicesGroup
--
mgtAcessServicesGroup	OBJECT IDENTIFIER  ::= { mgtAccessGroup 1 }

accessServicesStatus OBJECT-TYPE
    SYNTAX      ContainerStatus
    MAX-ACCESS  read-write
    STATUS      current
    DESCRIPTION
        "When you perform a GET on this variable, one of
         the following values will be returned:
         1-Indicates that the container folder is active with no changes.
         2-Indicates that the container folder is active with change(s).
           Once you have completed setting the variables in a folder, you
           will want to submit your changes to the management module. To do
           this, set the Status variable to 4. If you want to discard the
           changes, set the Status variable to 6.
         4-Indicates that the changes in the container folder are to be
           submitted to the management module and verified. To save the
           changes to flash a write of writeToFlash(1) in the adminFunction
           object is required.
         6-Indicates that the changes in the container folder are to be
           discarded."
    ::= { mgtAcessServicesGroup 1}

accessServicesSessInactTimeout OBJECT-TYPE
    SYNTAX      Integer32(0..4294967)
    MAX-ACCESS  read-write
    STATUS      current
    DESCRIPTION
        "The amount of time, in seconds, that the management session inactivity timer
         will run. When the  timer expires, becuase no activity on the management session
         within the specified time, the management module will reset the management session.
         A value of 0 (zero), means that the inactivity timer will not expire (the session
         is open permanently, or until the user logs out)."
    ::= { mgtAcessServicesGroup 2 }
--
accessServiceHTTPD OBJECT-TYPE
    SYNTAX      OnOffValue
    MAX-ACCESS  read-write
    STATUS      current
    DESCRIPTION
        "Turn on/off the HTTPD Service"
    ::= { mgtAcessServicesGroup 3 }

accessServiceHTTPSD OBJECT-TYPE
    SYNTAX      OnOffValue
    MAX-ACCESS  read-write
    STATUS      current
    DESCRIPTION
        "Turn on/off the HTTPSD Service"
    ::= { mgtAcessServicesGroup 4 }

accessServiceTelnetD OBJECT-TYPE
    SYNTAX      OnOffValue
    MAX-ACCESS  read-write
    STATUS      current
    DESCRIPTION
        "Turn on/off the TelnetD Service"
    ::= { mgtAcessServicesGroup 5 }

acessServiceSSHD OBJECT-TYPE
    SYNTAX      OnOffValue
    MAX-ACCESS  read-write
    STATUS      current
    DESCRIPTION
        "Turn on/off the SSHD Service"
    ::= { mgtAcessServicesGroup 6 }

acessServiceSnmpD OBJECT-TYPE
    SYNTAX      OnOffValue
    MAX-ACCESS  read-write
    STATUS      current
    DESCRIPTION
        "Turn on/off the SnmpD Service"
    ::= { mgtAcessServicesGroup 7 }

acessServiceSetIP OBJECT-TYPE
    SYNTAX      OnOffValue
    MAX-ACCESS  read-write
    STATUS      current
    DESCRIPTION
        "Turn on/off the SetIP Service"
    ::= { mgtAcessServicesGroup 8 }

acessIncomingPings OBJECT-TYPE
    SYNTAX      EnableDisableValue
    MAX-ACCESS  read-write
    STATUS      current
    DESCRIPTION
        "Allow incoming ping requests."
    ::= { mgtAcessServicesGroup 9 }

--
--
-- end of mgtAcessServicesGroup
--

--
-- webManagerGroup
--
webManagerGroup	OBJECT IDENTIFIER  ::= { mgtAccessGroup 2 }

webManagerStatus OBJECT-TYPE
    SYNTAX      ContainerStatus
    MAX-ACCESS  read-write
    STATUS      current
    DESCRIPTION
        "When you perform a GET on this variable, one of
         the following values will be returned:
         1-Indicates that the container folder is active with no changes.
         2-Indicates that the container folder is active with change(s).
           Once you have completed setting the variables in a folder, you
           will want to submit your changes to the management module. To do
           this, set the Status variable to 4. If you want to discard the
           changes, set the Status variable to 6.
         4-Indicates that the changes in the container folder are to be
           submitted to the management module and verified. To save the
           changes to flash a write of writeToFlash(1) in the adminFunction
           object is required.
         6-Indicates that the changes in the container folder are to be
           discarded."
    ::= { webManagerGroup 1}

httpsPassphrase OBJECT-TYPE
    SYNTAX      DisplayString(SIZE(1..16))
    MAX-ACCESS  read-write
    STATUS      current
    DESCRIPTION
        "This object identifies the HTTPS SSL certificate passphrase. Reading of this object will
         always return a blank string"
    ::= { webManagerGroup 2}
--
-- end of webManagerGroup
--

--
-- sshServerGroup
--
sshServerGroup			OBJECT IDENTIFIER  ::= { mgtAccessGroup 3 }

sshServerStatus OBJECT-TYPE
    SYNTAX      ContainerStatus
    MAX-ACCESS  read-write
    STATUS      current
    DESCRIPTION
        "When you perform a GET on this variable, one of
         the following values will be returned:
         1-Indicates that the container folder is active with no changes.
         2-Indicates that the container folder is active with change(s).
           Once you have completed setting the variables in a folder, you
           will want to submit your changes to the management module. To do
           this, set the Status variable to 4. If you want to discard the
           changes, set the Status variable to 6.
         4-Indicates that the changes in the container folder are to be
           submitted to the management module and verified. To save the
           changes to flash a write of writeToFlash(1) in the adminFunction
           object is required.
         6-Indicates that the changes in the container folder are to be
           discarded."
    ::= {sshServerGroup 1 }

sshServerAuthRSA OBJECT-TYPE
    SYNTAX   OnOffValue
    MAX-ACCESS    read-write
    STATUS        current
    DESCRIPTION
        "When a client SSH session requests RSA authentication,
         the management module's SSH server will authenticate the
         user via RSA."
    ::= {sshServerGroup 2}

sshServerAuthDSA OBJECT-TYPE
    SYNTAX   OnOffValue
    MAX-ACCESS    read-write
    STATUS        current
    DESCRIPTION
        "When a client SSH session requests DSA authentication,
         the management module's SSH server will authenticate the
         user via DSA"
    ::= {sshServerGroup 3}

sshServerAuthKeyboard OBJECT-TYPE
    SYNTAX   OnOffValue
    MAX-ACCESS    read-write
    STATUS        current
    DESCRIPTION
        "The user types in a password for authentication."
    ::= {sshServerGroup 4}

sshServerAuthPassword OBJECT-TYPE
    SYNTAX   OnOffValue
    MAX-ACCESS    read-write
    STATUS        current
    DESCRIPTION
        "The user types in a password for authentication."
    ::= {sshServerGroup 5}

sshServerCipher3Des OBJECT-TYPE
    SYNTAX   OnOffValue
    MAX-ACCESS    read-write
    STATUS        current
    DESCRIPTION
        "The management module SSH server's 3DES encryption is enable/disabled."
    ::= {sshServerGroup 6}

sshServerCipherBlowfish OBJECT-TYPE
    SYNTAX   OnOffValue
    MAX-ACCESS    read-write
    STATUS        current
    DESCRIPTION
        "The management module SSH server's Blowfish encryption is enabled/disabled."
    ::= {sshServerGroup 7}

sshServerCipherCipherAES OBJECT-TYPE
    SYNTAX   OnOffValue
    MAX-ACCESS    read-write
    STATUS        current
    DESCRIPTION
        "The management module SSH server's AES encryption is enabled/disabled"
    ::= {sshServerGroup 8}

sshServerCipherCAST OBJECT-TYPE
    SYNTAX   OnOffValue
    MAX-ACCESS    read-write
    STATUS        current
    DESCRIPTION
        "The management module SSH server's CAST encryption is enabled/disabled"
    ::= {sshServerGroup 9}

sshServerCipherArcfour OBJECT-TYPE
    SYNTAX   OnOffValue
    MAX-ACCESS    read-write
    STATUS        current
    DESCRIPTION
        "The management module SSH server's Arcfour encryption is enabled/disabled."
    ::= {sshServerGroup 10}

sshServerVerbose OBJECT-TYPE
    SYNTAX   OnOffValue
    MAX-ACCESS    read-write
    STATUS        current
    DESCRIPTION
        "Displays debug messages on the terminal."
    ::= {sshServerGroup 11}

sshServerCompression OBJECT-TYPE
    SYNTAX   OnOffValue
    MAX-ACCESS    read-write
    STATUS        current
    DESCRIPTION
        "Requests compression of all data. Compression is desirable on slow
         connections, but will only slow down things on fast networks."
    ::= {sshServerGroup 12}

sshServerSSH1 OBJECT-TYPE
    SYNTAX   OnOffValue
    MAX-ACCESS    read-write
    STATUS        current
    DESCRIPTION
        "Enable/Disable SSH-1 on the server."
    ::= {sshServerGroup 13}
--
-- end of sshServerGroup
--

--
-- snmpAgentGroup
--
snmpAgentGroup			OBJECT IDENTIFIER  ::= { mgtAccessGroup 4 }

snmpAgentStatus OBJECT-TYPE
    SYNTAX      ContainerStatus
    MAX-ACCESS  read-write
    STATUS      current
    DESCRIPTION
        "When you perform a GET on this variable, one of
         the following values will be returned:
         1-Indicates that the container folder is active with no changes.
         2-Indicates that the container folder is active with change(s).
           Once you have completed setting the variables in a folder, you
           will want to submit your changes to the management module. To do
           this, set the Status variable to 4. If you want to discard the
           changes, set the Status variable to 6.
         4-Indicates that the changes in the container folder are to be
           submitted to the management module and verified. To save the
           changes to flash a write of writeToFlash(1) in the adminFunction
           object is required.
         6-Indicates that the changes in the container folder are to be
           discarded."
    ::= { snmpAgentGroup 1}

snmpContact OBJECT-TYPE
    SYNTAX      DisplayString(SIZE(0..14))
    MAX-ACCESS  read-write
    STATUS      current
    DESCRIPTION
        "The name and contract information of the person who manages this SMNP node."
    ::= { snmpAgentGroup 2}

snmpLocation OBJECT-TYPE
    SYNTAX      DisplayString(SIZE(0..32))
    MAX-ACCESS  read-write
    STATUS      current
    DESCRIPTION
        "The physical location of the SNMP node."
    ::= { snmpAgentGroup 3}
--
-- snmpCommunityTable
--
snmpCommunityTable OBJECT-TYPE
    SYNTAX      SEQUENCE OF SnmpCommunityEntry
    MAX-ACCESS  not-accessible
    STATUS      current
    DESCRIPTION
        "Table of SNMP communities configured for the MCR-MGT agent"
    ::= { snmpAgentGroup 4}

    snmpCommunityEntry OBJECT-TYPE
        SYNTAX      SnmpCommunityEntry
        MAX-ACCESS  not-accessible
        STATUS      current
        DESCRIPTION
            "Entries of the table, each relating to a separate SNMP community
             definition "
        INDEX   { snmpCommunityIndex }
        ::= { snmpCommunityTable 1 }

    SnmpCommunityEntry ::=
        SEQUENCE {
            snmpCommunityIndex		GenericTableIndex,
            snmpCommunityStatus		ContainerStatus,
            snmpCommunityName			DisplayString,
            snmpCommunityIpAddress	Ipv4v6Address,
            snmpCommunityPermission	INTEGER
        }

    snmpCommunityIndex OBJECT-TYPE
        SYNTAX      GenericTableIndex
        MAX-ACCESS  not-accessible
        STATUS      current
        DESCRIPTION
            "The MCR-MGT agent community index"
        ::= { snmpCommunityEntry 1}

    snmpCommunityStatus OBJECT-TYPE
        SYNTAX      ContainerStatus
        MAX-ACCESS  read-write
        STATUS      current
        DESCRIPTION
            "When you perform a GET on this variable, one of
             the following values will be returned:
             1-Indicates that the container folder is active with no changes.
             2-Indicates that the container folder is active with change(s).
               Once you have completed setting the variables in a folder, you
               will want to submit your changes to the management module. To do
               this, set the Status variable to 4. If you want to discard the
               changes, set the Status variable to 6.
             4-Indicates that the changes in the container folder are to be
               submitted to the management module and verified. To save the
               changes to flash a write of writeToFlash(1) in the adminFunction
               object is required.
             6-Indicates that the changes in the container folder are to be
                discarded."
        ::= { snmpCommunityEntry 2}

    snmpCommunityName OBJECT-TYPE
        SYNTAX      DisplayString(SIZE(0..14))
        MAX-ACCESS  read-write
        STATUS      current
        DESCRIPTION
            "A name that will be sent to the management module from an SNMP
             manager. This name will define the permissions of the manager."
        ::= { snmpCommunityEntry 3}

    snmpCommunityIpAddress OBJECT-TYPE
        SYNTAX      Ipv4v6Address
        MAX-ACCESS  read-write
        STATUS      current
        DESCRIPTION
            "The IP address of the SNMP manager that will send requests to
             the management module. If the address is 0.0.0.0, any SNMP manager
             with the Community Name can access the management module."
        ::= { snmpCommunityEntry 4}

    snmpCommunityPermission OBJECT-TYPE
        SYNTAX      INTEGER {
          none(0),
          readonly(1),
          readwrite(2)
        }
        MAX-ACCESS  read-write
        STATUS      current
        DESCRIPTION
            "Permits the management module to respond to SNMP requests by:
               None -There is no response to requests from SNMP.
               Readonly -Responds only to Read requests from SNMP.
               Readwrite -Responds to both Read and Write requests from SNMP."
        ::= { snmpCommunityEntry 5}
--
-- snmpV3ReadOnlyUser
--
snmpV3ReadOnlyUser	OBJECT IDENTIFIER  ::= { snmpAgentGroup 5 }

    snmpV3ReadOnlyStatus OBJECT-TYPE
        SYNTAX      ContainerStatus
        MAX-ACCESS  read-write
        STATUS      current
        DESCRIPTION
            "When you perform a GET on this variable, one of
             the following values will be returned:
             1-Indicates that the container folder is active with no changes.
             2-Indicates that the container folder is active with change(s).
               Once you have completed setting the variables in a folder, you
               will want to submit your changes to the management module. To do
               this, set the Status variable to 4. If you want to discard the
               changes, set the Status variable to 6.
             4-Indicates that the changes in the container folder are to be
               submitted to the management module and verified. To save the
               changes to flash a write of writeToFlash(1) in the adminFunction
               object is required.
             6-Indicates that the changes in the container folder are to be
                discarded."
        ::= { snmpV3ReadOnlyUser 1 }

    snmpV3ReadOnlyUserName OBJECT-TYPE
        SYNTAX      DisplayString(SIZE(0..16))
        MAX-ACCESS  read-write
        STATUS      current
        DESCRIPTION
            "SNMP v3 read-only user name. This SNMP v3 user will have read-only S
             SNMP access permissions."
        ::= { snmpV3ReadOnlyUser 2 }

    snmpV3ReadOnlySecurityLevel OBJECT-TYPE
        SYNTAX      INTEGER {
            none(0),
            authNoPriv(1),
            authPriv(2)
        }
        MAX-ACCESS  read-write
        STATUS      current
        DESCRIPTION
          "Specifies the SNMP v3 read-only user security level."
        ::= {snmpV3ReadOnlyUser 3 }

    snmpV3ReadOnlyAuthAlgorithm OBJECT-TYPE
        SYNTAX      INTEGER {
            md5(0),
            sha(1)
        }
        MAX-ACCESS  read-write
        STATUS      current
        DESCRIPTION
            "Specifies the SNMP v3 read-only user authentication method."
        ::= {snmpV3ReadOnlyUser 4 }

    snmpV3ReadOnlyAuthPasswd OBJECT-TYPE
        SYNTAX      DisplayString(SIZE(0..128))
        MAX-ACCESS  read-write
        STATUS      current
        DESCRIPTION
            "Specifies the SNMP v3 read-only user authentication password."
        ::= { snmpV3ReadOnlyUser 5 }

    snmpV3ReadOnlyPrivacyAlgorithm OBJECT-TYPE
        SYNTAX      INTEGER {
            des(0),
            aes(1)
        }
        MAX-ACCESS  read-write
        STATUS      current
        DESCRIPTION
            "Specifies the SNMP v3 read-only user privacy algorithm."
        ::= {snmpV3ReadOnlyUser 6 }

    snmpV3ReadOnlyPrivacyPasswd OBJECT-TYPE
        SYNTAX      DisplayString(SIZE(0..128))
        MAX-ACCESS  read-write
        STATUS      current
        DESCRIPTION
            "Specifies the SNMP v3 read-only user privacy password."
        ::= { snmpV3ReadOnlyUser 7 }
--
-- snmpV3ReadWriteUser
--
snmpV3ReadWriteUser	OBJECT IDENTIFIER  ::= { snmpAgentGroup 6 }

    snmpV3ReadWriteStatus OBJECT-TYPE
        SYNTAX      ContainerStatus
        MAX-ACCESS  read-write
        STATUS      current
        DESCRIPTION
            "When you perform a GET on this variable, one of
             the following values will be returned:
             1-Indicates that the container folder is active with no changes.
             2-Indicates that the container folder is active with change(s).
               Once you have completed setting the variables in a folder, you
               will want to submit your changes to the management module. To do
               this, set the Status variable to 4. If you want to discard the
               changes, set the Status variable to 6.
             4-Indicates that the changes in the container folder are to be
               submitted to the management module and verified. To save the
               changes to flash a write of writeToFlash(1) in the adminFunction
               object is required.
             6-Indicates that the changes in the container folder are to be
                discarded."
        ::= { snmpV3ReadWriteUser 1}

    snmpV3ReadWriteUserName OBJECT-TYPE
        SYNTAX      DisplayString(SIZE(0..16))
        MAX-ACCESS  read-write
        STATUS      current
        DESCRIPTION
            "Specifies the SNMP v3 read-write user name. This SNMP v3 user will
             have read-write SNMP access permissions."
        ::= { snmpV3ReadWriteUser 2 }

    snmpV3ReadWriteSecurityLevel OBJECT-TYPE
        SYNTAX      INTEGER {
          none(0),
          authNoPriv(1),
          authPriv(2)
        }
        MAX-ACCESS  read-write
        STATUS      current
        DESCRIPTION
            "Specifies the SNMP v3 read-write user security level."
        ::= {snmpV3ReadWriteUser 3 }

    snmpV3ReadWriteAuthAlgorithm OBJECT-TYPE
        SYNTAX      INTEGER {
            md5(0),
            sha(1)
        }
        MAX-ACCESS  read-write
        STATUS      current
        DESCRIPTION
            "Specifies the SNMP v3 read-write user authentication method."
        ::= {snmpV3ReadWriteUser 4 }

    snmpV3ReadWriteAuthPasswd OBJECT-TYPE
        SYNTAX      DisplayString(SIZE(0..128))
        MAX-ACCESS  read-write
        STATUS      current
        DESCRIPTION
            "Specifies the SNMP v3 read-write  user authentication password."
        ::= { snmpV3ReadWriteUser 5 }

    snmpV3ReadWritePrivacyAlgorithm OBJECT-TYPE
        SYNTAX      INTEGER {
            des(0),
            aes(1)
        }
        MAX-ACCESS  read-write
        STATUS      current
        DESCRIPTION
            "Specifies the SNMP v3 read-write user privacy algorithm."
        ::= {snmpV3ReadWriteUser 6 }

    snmpV3ReadWritePrivacyPasswd OBJECT-TYPE
        SYNTAX      DisplayString(SIZE(0..128))
        MAX-ACCESS  read-write
        STATUS      current
        DESCRIPTION
            "Specifies the SNMP v3 read-write user privacy password."
        ::= { snmpV3ReadWriteUser 7 }
--
-- end of snmpV3ReadWriteUser
--



--
-- end of snmpAgentGroup
--

--
-- authorizedHostGroup
--
authorizedHostGroup	OBJECT IDENTIFIER  ::= { mgtAccessGroup 5 }

authHostsStatus OBJECT-TYPE
    SYNTAX      ContainerStatus
    MAX-ACCESS  read-write
    STATUS      current
    DESCRIPTION
        "When you perform a GET on this variable, one of
         the following values will be returned:
         1-Indicates that the container folder is active with no changes.
         2-Indicates that the container folder is active with change(s).
           Once you have completed setting the variables in a folder, you
           will want to submit your changes to the management module. To do
           this, set the Status variable to 4. If you want to discard the
           changes, set the Status variable to 6.
         4-Indicates that the changes in the container folder are to be
           submitted to the management module and verified. To save the
           changes to flash a write of writeToFlash(1) in the adminFunction
           object is required.
         6-Indicates that the changes in the container folder are to be
            discarded."
    ::= { authorizedHostGroup 1}


authHostOnly OBJECT-TYPE
    SYNTAX      YesNoValue
    MAX-ACCESS  read-write
    STATUS      current
    DESCRIPTION
        "Determines whether only authorized hosts are allowed to access the
         management module. If set to yes then the management module will only
         respond to, and allow access to and from, the IP or MAC addresses
         of hosts configured in the authorized IP and MAC hosts tables."
    ::= { authorizedHostGroup 2 }

--
-- authIpHostTable
--
authIpHostTable OBJECT-TYPE
    SYNTAX      SEQUENCE OF AuthIpHostEntry
    MAX-ACCESS  not-accessible
    STATUS      current
    DESCRIPTION
        "The hosts Group table."
    ::= { authorizedHostGroup 3 }

    authIpHostEntry OBJECT-TYPE
        SYNTAX      AuthIpHostEntry
        MAX-ACCESS  not-accessible
        STATUS      current
        DESCRIPTION
            "An entry in the AuthIpHostTable, each relating to a IP host."
        INDEX   { authHostIpIndex }
        ::= { authIpHostTable 1 }

    AuthIpHostEntry ::=
        SEQUENCE {
          authHostIpIndex			GenericTableIndex,
          authHostIpStatus		ContainerStatus,
          authHostIpAddr			Ipv4v6Address,
          authHostIpDescr			DisplayString
        }

    authHostIpIndex OBJECT-TYPE
        SYNTAX      GenericTableIndex
        MAX-ACCESS  not-accessible
        STATUS      current
        DESCRIPTION
            "The table entry number for this host."
        ::= { authIpHostEntry 1 }

    authHostIpStatus OBJECT-TYPE
        SYNTAX      ContainerStatus
        MAX-ACCESS  read-write
        STATUS      current
        DESCRIPTION
            "When you perform a GET on this variable, one of
             the following values will be returned:
             1-Indicates that the container folder is active with no changes.
             2-Indicates that the container folder is active with change(s).
               Once you have completed setting the variables in a folder, you
               will want to submit your changes to the management module. To do
               this, set the Status variable to 4. If you want to discard the
               changes, set the Status variable to 6.
             4-Indicates that the changes in the container folder are to be
               submitted to the management module and verified. To save the
               changes to flash a write of writeToFlash(1) in the adminFunction
               object is required.
             6-Indicates that the changes in the container folder are to be
                discarded."
        ::= { authIpHostEntry 2 }

    authHostIpAddr OBJECT-TYPE
        SYNTAX      Ipv4v6Address
        MAX-ACCESS  read-write
        STATUS      current
        DESCRIPTION
            "The host IP address used for this entry."
        ::= { authIpHostEntry 3 }

    authHostIpDescr OBJECT-TYPE
        SYNTAX      DisplayString(SIZE(0..21))
        MAX-ACCESS  read-write
        STATUS      current
        DESCRIPTION
            "The host IP entry description."
        ::= { authIpHostEntry 4 }

--
-- end of authIpHostTable
--

--
-- authMacHostTable
--
authMacHostTable OBJECT-TYPE
    SYNTAX      SEQUENCE OF AuthMacHostEntry
    MAX-ACCESS  not-accessible
    STATUS      current
    DESCRIPTION
        "The hosts Group table."
    ::= { authorizedHostGroup 4 }

    authMacHostEntry OBJECT-TYPE
        SYNTAX      AuthMacHostEntry
        MAX-ACCESS  not-accessible
        STATUS      current
        DESCRIPTION
            "An entry in the AuthIpHostTable, each relating to a host."
        INDEX   { authHostMacIndex }
        ::= { authMacHostTable 1 }

    AuthMacHostEntry ::=
        SEQUENCE {
          authHostMacIndex	GenericTableIndex,
          authHostMacStatus	ContainerStatus,
          authHostMacAddr		MacAddress,
          authHostMacDescr	DisplayString
        }

    authHostMacIndex OBJECT-TYPE
        SYNTAX      GenericTableIndex
        MAX-ACCESS  not-accessible
        STATUS      current
        DESCRIPTION
            "The table entry number for this host."
        ::= { authMacHostEntry 1 }

    authHostMacStatus OBJECT-TYPE
        SYNTAX      ContainerStatus
        MAX-ACCESS  read-write
        STATUS      current
        DESCRIPTION
            "When you perform a GET on this variable, one of
             the following values will be returned:
             1-Indicates that the container folder is active with no changes.
             2-Indicates that the container folder is active with change(s).
               Once you have completed setting the variables in a folder, you
               will want to submit your changes to the management module. To do
               this, set the Status variable to 4. If you want to discard the
               changes, set the Status variable to 6.
             4-Indicates that the changes in the container folder are to be
               submitted to the management module and verified. To save the
               changes to flash a write of writeToFlash(1) in the adminFunction
               object is required.
             6-Indicates that the changes in the container folder are to be
                discarded."
        ::= { authMacHostEntry 2 }


    authHostMacAddr OBJECT-TYPE
        SYNTAX      MacAddress
        MAX-ACCESS  read-write
        STATUS      current
        DESCRIPTION
            "The host MAC address used for this entry."
        ::= { authMacHostEntry 3 }

    authHostMacDescr OBJECT-TYPE
        SYNTAX      DisplayString(SIZE(0..21))
        MAX-ACCESS  read-write
        STATUS      current
        DESCRIPTION
            "The host MAC address entry description."
        ::= { authMacHostEntry 4 }


--
-- end of authMacHostTable
--
--
-- end of authorizedHostGroup
--
--
-- end of mgtAccessGroup
--

--
-- mgtAlertGroup
--
alertLocalEventGroup	OBJECT IDENTIFIER  ::= { mgtAlertGroup 1 }

localEventLogStatus OBJECT-TYPE
    SYNTAX      ContainerStatus
    MAX-ACCESS  read-write
    STATUS      current
    DESCRIPTION
        "When you perform a GET on this variable, one of
         the following values will be returned:
         1-Indicates that the container folder is active with no changes.
         2-Indicates that the container folder is active with change(s).
           Once you have completed setting the variables in a folder, you
           will want to submit your changes to the management module. To do
           this, set the Status variable to 4. If you want to discard the
           changes, set the Status variable to 6.
         4-Indicates that the changes in the container folder are to be
           submitted to the management module and verified. To save the
           changes to flash a write of writeToFlash(1) in the adminFunction
           object is required.
         6-Indicates that the changes in the container folder are to be
            discarded."
    ::= { alertLocalEventGroup 1 }


localEventLogEnabled OBJECT-TYPE
    SYNTAX      YesNoValue
    MAX-ACCESS  read-write
    STATUS      current
    DESCRIPTION
        "Determines whether alert events are logged to the internal local event
         log."
    ::= { alertLocalEventGroup 2 }

localEventLogAlertLevel OBJECT-TYPE
    SYNTAX      AlertSeverityLevel
    MAX-ACCESS  read-write
    STATUS      current
    DESCRIPTION
        "Choose the alert level that will trigger a local event being stored
         in the local event log. When you select an alert level, all alerts that
         appear above it in the list will also trigger a local event log message.
         For example, if you select oneTimeError, all oneTimeError, persistantError,
         moduleLevelFault, and systemLevelFault alert events will be generate a local
         event message."
    ::= { alertLocalEventGroup 3 }

localEventLogClear		OBJECT-TYPE
    SYNTAX	YesNoValue
    MAX-ACCESS  read-write
    STATUS      current
    DESCRIPTION
        "Writing a yes(1) to this object will clear the local event log on the
         management module.  Reading of this object will always return 0"
    ::= { alertLocalEventGroup 4 }
--
-- alertSyslogGroup
--
alertSyslogGroup		OBJECT IDENTIFIER  ::= { mgtAlertGroup 2 }

syslogStatus OBJECT-TYPE
    SYNTAX      ContainerStatus
    MAX-ACCESS  read-write
    STATUS      current
    DESCRIPTION
        "When you perform a GET on this variable, one of
         the following values will be returned:
         1-Indicates that the container folder is active with no changes.
         2-Indicates that the container folder is active with change(s).
           Once you have completed setting the variables in a folder, you
           will want to submit your changes to the management module. To do
           this, set the Status variable to 4. If you want to discard the
           changes, set the Status variable to 6.
         4-Indicates that the changes in the container folder are to be
           submitted to the management module and verified. To save the
           changes to flash a write of writeToFlash(1) in the adminFunction
           object is required.
         6-Indicates that the changes in the container folder are to be
           discarded."
    ::= { alertSyslogGroup 1}

syslogEnabled OBJECT-TYPE
    SYNTAX      YesNoValue
    MAX-ACCESS  read-write
    STATUS      current
    DESCRIPTION
              "Determines whether syslog is enabled."
    ::= { alertSyslogGroup 2}

syslogSeverityLevel OBJECT-TYPE
    SYNTAX          INTEGER {
      emergency(0),
      alert(1),
      critical(2),
      error(3),
      warning(4),
      notice(5),
      informational(6),
      debug(7)
    }
    MAX-ACCESS  read-write
    STATUS      current
    DESCRIPTION
        "Choose the severity level that will trigger a syslog message:
         Emergency, Alert, Critical, Error, Warning, Notice, Info, Debug
         When you select a severity level, all the levels that appear above it in
         the list will also trigger a syslog message. For example, if you select
         Error, all Error, Critical, Alert, and Emergency events will generate a
         syslog message.
         NOTE: In addition to alert events, syslog message will also be generated
               for several non-alert system events"
    ::= { alertSyslogGroup 3}

syslogPrimaryHost OBJECT-TYPE
    SYNTAX      DisplayString(SIZE(0..14))
    MAX-ACCESS  read-write
    STATUS      current
    DESCRIPTION
        "The first preconfigured host that the management module will attempt
         to send system log messages to; messages will be displayed on the
         host's monitor."
    ::= { alertSyslogGroup 4}

syslogSecondaryHost OBJECT-TYPE
    SYNTAX      DisplayString(SIZE(0..14))
    MAX-ACCESS  read-write
    STATUS      current
    DESCRIPTION
        "If the management module cannot communicate with the primary host,
         then the management module will attempt to send system log messages to
         this preconfigured host; messages will be displayed on the host's monitor."
    ::= { alertSyslogGroup 5}
--
-- alertSnmpTrapGroup
--
alertSnmpTrapGroup	OBJECT IDENTIFIER  ::= { mgtAlertGroup 3 }

snmpTrapStatus OBJECT-TYPE
    SYNTAX      ContainerStatus
    MAX-ACCESS  read-write
    STATUS      current
    DESCRIPTION
        "When you perform a GET on this variable, one of
         the following values will be returned:
         1-Indicates that the container folder is active with no changes.
         2-Indicates that the container folder is active with change(s).
           Once you have completed setting the variables in a folder, you
           will want to submit your changes to the management module. To do
           this, set the Status variable to 4. If you want to discard the
           changes, set the Status variable to 6.
         4-Indicates that the changes in the container folder are to be
           submitted to the management module and verified. To save the
           changes to flash a write of writeToFlash(1) in the adminFunction
           object is required.
         6-Indicates that the changes in the container folder are to be
           discarded."
    ::= { alertSnmpTrapGroup 1}

snmpTrapEnabled OBJECT-TYPE
    SYNTAX      YesNoValue
    MAX-ACCESS  read-write
    STATUS      current
    DESCRIPTION
              "Determines whether SNMP Traps are enabled."
    ::= { alertSnmpTrapGroup 2}

snmpTrapAlertLevel OBJECT-TYPE
    SYNTAX      AlertSeverityLevel
    MAX-ACCESS  read-write
    STATUS      current
    DESCRIPTION
        "Choose the alert level that will trigger a SNMP trap message to be sent
         if SNMP traps is enabled. When you select an alert level, all alerts that
         appear above it in the list will also trigger a local event log message.
         For example, if you select oneTimeError, all oneTimeError, persistantError,
         moduleLevelFault, and systemLevelFault alert events will be generate a SNMP
         trap message."
    ::= { alertSnmpTrapGroup 3}

--
-- snmpTrapHostTable  - SNMP Trap target host Table
--
snmpTrapHostTable OBJECT-TYPE
    SYNTAX		SEQUENCE OF SnmpTrapHostEntry
    MAX-ACCESS not-accessible
    STATUS		current
    DESCRIPTION
        "Table of SNMP Trap Hosts information."
    ::= { alertSnmpTrapGroup 4}

    snmpTrapHostEntry OBJECT-TYPE
        SYNTAX      SnmpTrapHostEntry
        MAX-ACCESS not-accessible
        STATUS      current
        DESCRIPTION
            "Entries of the table, each relating to a separate SNMP trap host."
        INDEX   { snmpTrapHostIndex }
        ::= { snmpTrapHostTable 1 }

    SnmpTrapHostEntry ::=
        SEQUENCE {
            snmpTrapHostIndex		GenericTableIndex,
            snmpTrapHostStatus		ContainerStatus,
            snmpTrapHostIpAddress		Ipv4v6Address,
            snmpTrapHostUdpPort		Integer32,
            snmpTrapHostVersion		INTEGER,
            snmpTrapHostType			INTEGER,
            snmpTrapHostCommunity		DisplayString,
            snmpTrapHostEnable		YesNoValue
         }

    snmpTrapHostIndex OBJECT-TYPE
        SYNTAX      GenericTableIndex
        MAX-ACCESS accessible-for-notify
        STATUS      current
        DESCRIPTION
            "This object identifies the SNMP trap host index."
        ::= { snmpTrapHostEntry 1 }

    snmpTrapHostStatus OBJECT-TYPE
        SYNTAX      ContainerStatus
        MAX-ACCESS read-write
        STATUS      current
        DESCRIPTION
            "When you perform a GET on this variable, one of
             the following values will be returned:
             1-Indicates that the container folder is active with no changes.
             2-Indicates that the container folder is active with change(s).
               Once you have completed setting the variables in a folder, you
               will want to submit your changes to the management module. To do
               this, set the Status variable to 4. If you want to discard the
               changes, set the Status variable to 6.
             4-Indicates that the changes in the container folder are to be
               submitted to the management module and verified. To save the
               changes to flash a write of writeToFlash(1) in the adminFunction
               object is required.
              6-Indicates that the changes in the container folder are to be
                 discarded."
        ::= { snmpTrapHostEntry 2 }

    snmpTrapHostIpAddress OBJECT-TYPE
        SYNTAX      Ipv4v6Address
        MAX-ACCESS read-write
        STATUS      current
        DESCRIPTION
            "Defines the hosts (by IP address) that will receive trap messages
             generated by the management module. "
        ::= { snmpTrapHostEntry 3 }

    snmpTrapHostUdpPort OBJECT-TYPE
        SYNTAX      Integer32(1..65535)
        MAX-ACCESS read-write
        STATUS      current
        DESCRIPTION
            "Defines the UDP port number the SNMP trap host will listen on to
            receive	trap messages generated by the management module."
        ::= { snmpTrapHostEntry 4 }

    snmpTrapHostVersion OBJECT-TYPE
        SYNTAX		INTEGER {
            snmpTrapV1(0),
            snmpTrapV2c(1),
            snmpTrapV3(2)
        }
        MAX-ACCESS read-write
        STATUS      current
        DESCRIPTION
            "Defines the SNMP version of the traps sent to this host. If
             snmpTrapV3 is selected then the SNMP trap v3 user "
        ::= { snmpTrapHostEntry 5 }

    snmpTrapHostType OBJECT-TYPE
        SYNTAX		INTEGER {
            snmpTrap(0),
            snmpInform(1)
        }
        MAX-ACCESS read-write
        STATUS      current
        DESCRIPTION
            "If set to snmpInform(1) the management module will send traps via an
             INFORM-PDU, expecting a response from the trap host, retransmitting
             if required. Otherwise it will send them via a TRAP-PDU or TRAP2-PDU.
             This object is ignored for for SNMP v1"
        ::= { snmpTrapHostEntry 6 }

    snmpTrapHostCommunity OBJECT-TYPE
        SYNTAX      DisplayString(SIZE(0..14))
        MAX-ACCESS read-write
        STATUS      current
        DESCRIPTION
            "An arbitrary trap community name. This object is ignored for SNMP v3"
        ::= { snmpTrapHostEntry 7 }

    snmpTrapHostEnable OBJECT-TYPE
        SYNTAX		YesNoValue
        MAX-ACCESS read-write
        STATUS      current
        DESCRIPTION
            "If set to No, the management module will not use this
             table entry to send traps."
        ::= { snmpTrapHostEntry 8 }


--
-- snmpTrapHostTable  - SNMP Trap target host Table
--
--
-- snmpV3TrapUser
--
snmpV3TrapUser	OBJECT IDENTIFIER  ::= { alertSnmpTrapGroup 5 }

    snmpV3TrapUserStatus OBJECT-TYPE
        SYNTAX      ContainerStatus
        MAX-ACCESS  read-write
        STATUS      current
        DESCRIPTION
            "When you perform a GET on this variable, one of
             the following values will be returned:
             1-Indicates that the container folder is active with no changes.
             2-Indicates that the container folder is active with change(s).
               Once you have completed setting the variables in a folder, you
               will want to submit your changes to the management module. To do
               this, set the Status variable to 4. If you want to discard the
               changes, set the Status variable to 6.
             4-Indicates that the changes in the container folder are to be
               submitted to the management module and verified. To save the
               changes to flash a write of writeToFlash(1) in the adminFunction
               object is required.
             6-Indicates that the changes in the container folder are to be
                discarded."
        ::= { snmpV3TrapUser 1}

    snmpV3TrapUserUserName OBJECT-TYPE
        SYNTAX      DisplayString(SIZE(0..16))
        MAX-ACCESS  read-write
        STATUS      current
        DESCRIPTION
            "SNMP trap v3 user name. This user will be used for every SNMP trap
             host that is using snmpTrapHostVersion of snmpTrapV3(2) "
        ::= { snmpV3TrapUser 2}

    snmpV3TrapUserSecurityLevel OBJECT-TYPE
        SYNTAX      INTEGER {
            none(0),
            authNoPriv(1),
            authPriv(2)
        }
        MAX-ACCESS  read-write
        STATUS      current
        DESCRIPTION
            "SNMP trap v3 user security level."
        ::= {snmpV3TrapUser 3 }

    snmpV3TrapUserAuthAlgorithm OBJECT-TYPE
        SYNTAX      INTEGER {
            md5(0),
            sha(1)
        }
        MAX-ACCESS  read-write
        STATUS      current
        DESCRIPTION
            "SNMP trap v3 user authentication method."
        ::= {snmpV3TrapUser 4 }

    snmpV3TrapUserAuthPasswd OBJECT-TYPE
        SYNTAX      DisplayString(SIZE(0..128))
        MAX-ACCESS  read-write
        STATUS      current
        DESCRIPTION
            "SNMP trap v3 user authentication password."
        ::= { snmpV3TrapUser 5 }

    snmpV3TrapUserPrivacyAlgorithm OBJECT-TYPE
        SYNTAX      INTEGER {
            des(0),
            aes(1)
        }
        MAX-ACCESS  read-write
        STATUS      current
        DESCRIPTION
            "SNMP trap v3 user privacy algorithm."
        ::= {snmpV3TrapUser 6 }

    snmpV3TrapUserPrivacyPasswd OBJECT-TYPE
        SYNTAX      DisplayString(SIZE(0..128))
        MAX-ACCESS  read-write
        STATUS      current
        DESCRIPTION
            "SNMP trap v3 user privacy password."
        ::= { snmpV3TrapUser 7 }

--
-- end of snmpV3TrapUser
--

snmpTrapGlbHostTimeout OBJECT-TYPE
    SYNTAX      Integer32(0..65535)
    MAX-ACCESS read-write
    STATUS      current
    DESCRIPTION
        "Defines the timeout in miliseconds between retries of sending the SNMP
         INFORM-PDU if no response is received for the trap host.  "
    ::= { alertSnmpTrapGroup 6 }

snmpTapGlobHostRetries OBJECT-TYPE
    SYNTAX      Integer32(0..65535)
    MAX-ACCESS read-write
    STATUS      current
    DESCRIPTION
        "Defines the number of retries to send the SNMP INFORM-PDU trap if no
         response is received from the trap host."
    ::= { alertSnmpTrapGroup 7 }

snmpV3LocalEngineID OBJECT-TYPE
    SYNTAX      SnmpEngineID
    MAX-ACCESS  read-only
    STATUS      current
    DESCRIPTION
        "An SNMPv3 engine ID used by the MCR-MGT for identification when sending
         SNMP v3 traps."
    ::= { alertSnmpTrapGroup 8}

snmpV3LocalEngineIDTextSuffix OBJECT-TYPE
    SYNTAX      DisplayString(SIZE(0..27))
    MAX-ACCESS  read-write
    STATUS      current
    DESCRIPTION
        "This configured text is used to build the suffix of the SNMPv3
         engine ID"
    ::= { alertSnmpTrapGroup 9}
--
-- end of alertSnmpTrapGroup
--
--
-- snmpTrapVarsGroup
--
snmpTrapVarsGroup	OBJECT IDENTIFIER  ::= { alertSnmpTrapGroup 10 }

    mgtAccessMethod OBJECT-TYPE
        SYNTAX      INTEGER {
            mgtConsole(1),
            mgtSnmp(2),
            mgtTelnet(3),
            mgtSSH(4),
            mgtHTTP(5),
            mgtHTTPS(6)
        }
        MAX-ACCESS accessible-for-notify
        STATUS      current
        DESCRIPTION
            "Defines the management protocol used to access the management module"
        ::= { snmpTrapVarsGroup 1 }

    remoteMgtIpAddress OBJECT-TYPE
        SYNTAX		DisplayString
        MAX-ACCESS accessible-for-notify
        STATUS      current
        DESCRIPTION
            "Defines the remote IP address accessing the management module"
        ::= { snmpTrapVarsGroup 2 }

    remoteTftpHost OBJECT-TYPE
        SYNTAX		DisplayString(SIZE(0..64))
        MAX-ACCESS accessible-for-notify
        STATUS      current
        DESCRIPTION
            "Defines the remote TFTP server IP address or host name performing the
             TFP file transfer"
        ::= { snmpTrapVarsGroup 3 }

    remoteTftpFileName OBJECT-TYPE
        SYNTAX		DisplayString(SIZE(0..64))
        MAX-ACCESS accessible-for-notify
        STATUS      current
        DESCRIPTION
            "Defines the remote TFTP file name "
        ::= { snmpTrapVarsGroup 4 }

    networkIpAddress OBJECT-TYPE
        SYNTAX		Ipv4v6Address
        MAX-ACCESS accessible-for-notify
        STATUS      current
        DESCRIPTION
            "Defines the IP address assigned to the management module "
        ::= { snmpTrapVarsGroup 5 }

    mcrMediaPortNum OBJECT-TYPE
        SYNTAX Unsigned32(1..2)
        MAX-ACCESS accessible-for-notify
        STATUS current
        DESCRIPTION
            "This object identifies the media converter module port number."
    ::= { snmpTrapVarsGroup 6 }

    mcrMediaPortDescr OBJECT-TYPE
        SYNTAX DisplayString
        MAX-ACCESS accessible-for-notify
        STATUS current
        DESCRIPTION
            "A description of the media port that consists of the user defined
             media port name, followed by the system name for the port."
    ::= { snmpTrapVarsGroup 7 }

    eventSeverityLevel  OBJECT-TYPE
        SYNTAX      AlertSeverityLevel
        MAX-ACCESS accessible-for-notify
        STATUS current
        DESCRIPTION
            "The severity level of  the event that generated this trap."
        ::= { snmpTrapVarsGroup 8 }

    xfpDmiRealTimeAux	OBJECT-TYPE
        SYNTAX	DisplayString (SIZE(0..32))
        MAX-ACCESS	read-only
        STATUS		current
        DESCRIPTION
            "This object identifies the XFP DMI real time values for one of the
            auxillary register sets."
        ::= { snmpTrapVarsGroup 9 }

    xfpDmiHighAuxWarn	OBJECT-TYPE
        SYNTAX	DisplayString (SIZE(0..32))
        MAX-ACCESS	read-only
        STATUS		current
        DESCRIPTION
            "This object identifies the XFP DMI high warning threshold for one 
            of the auxillary register sets."
        ::= { snmpTrapVarsGroup 10 }

    xfpDmiHighAuxAlarm	OBJECT-TYPE
        SYNTAX	DisplayString (SIZE(0..32))
        MAX-ACCESS	read-only
        STATUS		current
        DESCRIPTION
            "This object identifies the XFP DMI alarm alarm threshold for one 
            of the auxillary register sets."
        ::= { snmpTrapVarsGroup 11 }

    xfpDmiLowAuxWarn	OBJECT-TYPE
        SYNTAX	DisplayString (SIZE(0..32))
        MAX-ACCESS	read-only
        STATUS		current
        DESCRIPTION
            "This object identifies the XFP DMI low warning threshold for one 
            of the auxillary register sets."
        ::= { snmpTrapVarsGroup 12 }

    xfpDmiLowAuxAlarm	OBJECT-TYPE
        SYNTAX	DisplayString (SIZE(0..32))
        MAX-ACCESS	read-only
        STATUS		current
        DESCRIPTION
            "This object identifies the XFP DMI low alarm threshold for one 
            of the auxillary register sets."
        ::= { snmpTrapVarsGroup 13 }

    mcrModuleSubTypeInserted	OBJECT-TYPE
        SYNTAX		INTEGER {
            blank(-1),
            sts(0),
            xts(1),
            xtsh(2),
            xtx(3),
            xtxh(4)
        }
        MAX-ACCESS	read-only
        STATUS		current
        DESCRIPTION
            "This object identifies the module sub-type inserted in the slot."
        ::= { snmpTrapVarsGroup 14 }

    mcrMediaBackedupModuleSubType	OBJECT-TYPE
        SYNTAX		INTEGER {
            blank(-1),
            sts(0),
            xts(1),
            xtsh(2),
            xtx(3),
            xtxh(4)
        }
        MAX-ACCESS	read-only
        STATUS		current
        DESCRIPTION
            "This object identifies the module sub-type of the backup configuration."
        ::= { snmpTrapVarsGroup 15 }

    mcrMediaPortBandwidth OBJECT-TYPE
        SYNTAX Unsigned32
        MAX-ACCESS accessible-for-notify
        STATUS current
        DESCRIPTION
            "This object identifies the media converter module port's current bandwith in kbps."
    ::= { snmpTrapVarsGroup 16 }

    mcrMediaPortBandwidthThreshold OBJECT-TYPE
        SYNTAX Unsigned32
        MAX-ACCESS accessible-for-notify
        STATUS current
        DESCRIPTION
            "This object identifies the media converter module port's bandwith threshold in kbps."
    ::= { snmpTrapVarsGroup 17 }

    -- end of snmpTrapBoundVarsGroup
--
--
-- end of alertSnmpTrapGroup
--

--
-- alertEmailGroup
--
alertEmailGroup			OBJECT IDENTIFIER  ::= { mgtAlertGroup 4 }
emailStatus OBJECT-TYPE
    SYNTAX      ContainerStatus
    MAX-ACCESS  read-write
    STATUS      current
    DESCRIPTION
        "When you perform a GET on this variable, one of
         the following values will be returned:
         1-Indicates that the container folder is active with no changes.
         2-Indicates that the container folder is active with change(s).
           Once you have completed setting the variables in a folder, you
           will want to submit your changes to the management module. To do
           this, set the Status variable to 4. If you want to discard the
           changes, set the Status variable to 6.
         4-Indicates that the changes in the container folder are to be
           submitted to the management module and verified. To save the
           changes to flash a write of writeToFlash(1) in the adminFunction
           object is required.
          6-Indicates that the changes in the container folder are to be
            discarded."
    ::= { alertEmailGroup 1}

emailEnabled OBJECT-TYPE
    SYNTAX      YesNoValue
    MAX-ACCESS  read-write
    STATUS      current
    DESCRIPTION
        "Determines whether or not email notification is turned on. Default is Off."
    ::= { alertEmailGroup 2}

emailAlertLevel OBJECT-TYPE
    SYNTAX      AlertSeverityLevel
    MAX-ACCESS  read-write
    STATUS      current
    DESCRIPTION
        "Choose the alert level that will trigger a email message to be sent
         if alert email is enabled. When you select an alert level, all alerts that
         appear above it in the list will also trigger a local event log message.
         For example, if you select oneTimeError, all oneTimeError, persistantError,
         moduleLevelFault, and systemLevelFault alert events will be generate a email
         message."
    ::= { alertEmailGroup 3}

emailTo OBJECT-TYPE
    SYNTAX      DisplayString(SIZE(0..64))
    MAX-ACCESS  read-write
    STATUS      current
    DESCRIPTION
              "An email address or list of email addresses that will
                receive the email notification."
    ::= { alertEmailGroup 4}

emailFrom OBJECT-TYPE
    SYNTAX      DisplayString(SIZE(0..32))
    MAX-ACCESS  read-write
    STATUS      current
    DESCRIPTION
              "This field can contain an email address that might
                identify the management module name or some other value."
    ::= { alertEmailGroup 5}

emailSMTPHost OBJECT-TYPE
    SYNTAX      DisplayString(SIZE(0..64))
    MAX-ACCESS  read-write
    STATUS      current
    DESCRIPTION
              "The SMTP host (email server) that will process the
                email notification request. This can be either a host
                name defined in the management module host table or the
                SMTP host IP address."
    ::= { alertEmailGroup 6}

emailReply OBJECT-TYPE
    SYNTAX      DisplayString(SIZE(0..32))
    MAX-ACCESS  read-write
    STATUS      current
    DESCRIPTION
              "The email address to whom all replies to the email
                notification should go."
    ::= { alertEmailGroup 7}

emailSubject OBJECT-TYPE
        SYNTAX		DisplayString(SIZE(0..48))
    MAX-ACCESS  read-write
    STATUS      current
    DESCRIPTION
              "A text string, which can contain spaces, that will
                display in the Subject field of the email notification."
    ::= { alertEmailGroup 8}

emailSMTPUsername OBJECT-TYPE
    SYNTAX      DisplayString(SIZE(0..64))
    MAX-ACCESS  read-write
    STATUS      current
    DESCRIPTION
              "The user name for the SMTP server, if the server requires
                authentication."
    ::= { alertEmailGroup 9}

emailSMTPPassword OBJECT-TYPE
    SYNTAX      DisplayString(SIZE(0..64))
    MAX-ACCESS  read-write
    STATUS      current
    DESCRIPTION
              "The password for the SMTP server, if the server requires
                authentication."
    ::= { alertEmailGroup 10}

emailSMTPEncryption OBJECT-TYPE
    SYNTAX      INTEGER {
      none(1),
      tls(2),
      ssl(3)
    }
    MAX-ACCESS  read-write
    STATUS      current
    DESCRIPTION
              "The encryption method for the SMTP server."
    ::= { alertEmailGroup 11}

emailSMTPValidatePeerCertificate OBJECT-TYPE
    SYNTAX      OnOffValue
    MAX-ACCESS  read-write
    STATUS      current
    DESCRIPTION
              "Validate peer SSL/TLS certificate, when SSL or TLS
                encryption is used."
    ::= { alertEmailGroup 12}

emailSMTPTcpPort OBJECT-TYPE
    SYNTAX      Integer32(1..65535)
    MAX-ACCESS  read-write
    STATUS      current
    DESCRIPTION
              "The TCP port used for communicating with the SMTP server.
                For no encryption or TLS encryption, use port 25.
                For SSL encryption, use port 465."
    ::= { alertEmailGroup 13 }

emailSMTPDomain OBJECT-TYPE
    SYNTAX      DisplayString(SIZE(0..32))
    MAX-ACCESS  read-write
    STATUS      current
    DESCRIPTION
              "The domain for NTLM authentication with the SMTP server, if
                applicable."
    ::= { alertEmailGroup 14 }
--
-- end of mgtAlertGroup
--

--
-- mgtUsersGroup
--
mgtUsersStatus OBJECT-TYPE
    SYNTAX      ContainerStatus
    MAX-ACCESS  read-write
    STATUS      current
    DESCRIPTION
        "When you perform a GET on this variable, one of
         the following values will be returned:
         1-Indicates that the container folder is active with no changes.
         2-Indicates that the container folder is active with change(s).
           Once you have completed setting the variables in a folder, you
           will want to submit your changes to the management module. To do
           this, set the Status variable to 4. If you want to discard the
           changes, set the Status variable to 6.
         4-Indicates that the changes in the container folder are to be
           submitted to the management module and verified. To save the
           changes to flash a write of writeToFlash(1) in the adminFunction
           object is required.
         6-Indicates that the changes in the container folder are to be
            discarded."
    ::= { mgtUsersGroup 1}

mgtUsersByPassLoginEnabled OBJECT-TYPE
    SYNTAX      OnOffValue
    MAX-ACCESS  read-write
    STATUS      current
    DESCRIPTION
        "Indicates whether by pass login is enabled.  When enable users will be
         automatically login as admin user.  The will not be prompted for a user
          ID or password when accessing the management module.  "
    ::= { mgtUsersGroup 2}


mgtUsersPrimaryAuthMethod OBJECT-TYPE
  SYNTAX INTEGER {
      local(1),
      radius(2),
      kerberos(3),
      ldap(4),
      tacacs(5),
      securid(6),
      nis(7)
}
  MAX-ACCESS  read-write
  STATUS      current
  DESCRIPTION
      "The first authentication method that the management module attempts.
                Some type of authentication must be done by the management module."
  ::= { mgtUsersGroup 3 }

mgtUsersSecondaryAuthMethod OBJECT-TYPE
    SYNTAX      INTEGER {
        none(1),
        local(2),
        radius(3),
        kerberos(4),
        ldap(5),
        tacacs(6),
        securid(7),
        nis(8)
    }
    MAX-ACCESS  read-write
    STATUS      current
    DESCRIPTION
        "If the Primary Authentication Method fails, the next
         authentication method that the management module attempts. You
         can choose to use authentication methods in combination.
         For example, you can specify the Primary Authentication
         Method as Local and the Secondary Authentication Method as
         RADIUS. Therefore, some users can be defined in the Device
         Server (Local) others in RADIUS."
    ::= { mgtUsersGroup 4 }

mgtUsersAlwaysAttemptSecond OBJECT-TYPE
    SYNTAX      OnOffValue
    MAX-ACCESS  read-write
    STATUS      current
    DESCRIPTION
              "If enabled, the secondary authentication method will always be used."
    ::= { mgtUsersGroup 5 }

--
-- localUserAccountsTable
--
localUserAccountsTable OBJECT-TYPE
    SYNTAX      SEQUENCE OF LocalUserAccountsEntry
    MAX-ACCESS  not-accessible
    STATUS      current
    DESCRIPTION
        " Table of locally defined user information"
    ::= { mgtUsersGroup 6 }

    localUserAccountsEntry OBJECT-TYPE
        SYNTAX      LocalUserAccountsEntry
        MAX-ACCESS  not-accessible
        STATUS      current
        DESCRIPTION
            "Entries of the table, each relating to separate user defined locally."
        INDEX   { userIndex }
        ::= { localUserAccountsTable 1 }

    LocalUserAccountsEntry ::=
        SEQUENCE {
            userIndex		GenericTableIndex,
            userStatus		ContainerStatus,
            userName			DisplayString,
            userPassword	DisplayString,
            userLevel		INTEGER
        }

    userIndex OBJECT-TYPE
        SYNTAX      GenericTableIndex
        MAX-ACCESS  not-accessible
        STATUS      current
        DESCRIPTION
            "The table entry number for this user."
        ::= { localUserAccountsEntry 1 }

    userStatus OBJECT-TYPE
        SYNTAX      ContainerStatus
        MAX-ACCESS  read-write
        STATUS      current
        DESCRIPTION
            "When you perform a GET on this variable, one of
             the following values will be returned:
             1-Indicates that the container folder is active with no changes.
             2-Indicates that the container folder is active with change(s).
               Once you have completed setting the variables in a folder, you
               will want to submit your changes to the management module. To do
               this, set the Status variable to 4. If you want to discard the
               changes, set the Status variable to 6.
             4-Indicates that the changes in the container folder are to be
               submitted to the management module and verified. To save the
               changes to flash a write of writeToFlash(1) in the adminFunction
               object is required.
             6-Indicates that the changes in the container folder are to be
                discarded."
        ::= { localUserAccountsEntry 2}

    userName OBJECT-TYPE
        SYNTAX      DisplayString(SIZE(0..16))
        MAX-ACCESS  read-write
        STATUS      current
        DESCRIPTION
                  "The user name.
                    To delete a user, set this field to blank.
                    If blank, this entry is currently unused."
        ::= { localUserAccountsEntry 3 }

    userPassword OBJECT-TYPE
        SYNTAX      DisplayString(SIZE(0..64))
        MAX-ACCESS  read-write
        STATUS      current
        DESCRIPTION
              "The password for the local user."
        ::= { localUserAccountsEntry 4}

    userLevel OBJECT-TYPE
        SYNTAX      INTEGER
        {
          admin(0),
          operator(1)
        }
        MAX-ACCESS  read-write
        STATUS      current
        DESCRIPTION
            "Admin:
                Total access to the management module. More than one admin user
                account can exist, but we recommend that you only have one.
             operator:
                Full read only access to configuration and limited control commands "
        ::= { localUserAccountsEntry 5}

--
-- end of localUserAccountsTable
--

--
-- localUsersStatusTable
--
localUsersStatusTable OBJECT-TYPE
    SYNTAX      SEQUENCE OF LocalUsersStatusEntry
    MAX-ACCESS  not-accessible
    STATUS      current
    DESCRIPTION
        " Table of locally defined user information"
    ::= { mgtUsersGroup 7 }

    localUsersStatusEntry OBJECT-TYPE
        SYNTAX      LocalUsersStatusEntry
        MAX-ACCESS  not-accessible
        STATUS      current
        DESCRIPTION
            "Entries of the table, each relating to separate user defined locally."
        INDEX   { userStatusIndex }
        ::= { localUsersStatusTable 1 }

    LocalUsersStatusEntry ::=
        SEQUENCE {
            userStatusIndex				GenericTableIndex,
            userStatusName					DisplayString,
            userStatusMgtAccessType		INTEGER,
            userStatusRemoteIPAddress	Ipv4v6Address,
            userStatusStartTime			DisplayString,
            userStatusLevel				INTEGER
        }

    userStatusIndex OBJECT-TYPE
        SYNTAX      GenericTableIndex
        MAX-ACCESS  not-accessible
        STATUS      current
        DESCRIPTION
            "The table entry number for this user status."
        ::= { localUsersStatusEntry 1 }


    userStatusName OBJECT-TYPE
        SYNTAX      DisplayString(SIZE(0..16))
        MAX-ACCESS  read-only
        STATUS      current
        DESCRIPTION
            "The user name. To delete a user, set this field to blank. If blank,
             this entry is currently unused."
        ::= { localUsersStatusEntry 2 }

    userStatusMgtAccessType OBJECT-TYPE
        SYNTAX      INTEGER {
            mgtAccessHTTP(1),
            mgtAccessHTTPS(2),
            mgtAccessTelnet(3),
            mgtAccessSSH(4),
            mgtAccessConsole(5)
        }
        MAX-ACCESS not-accessible
        STATUS      current
        DESCRIPTION
            "Defines the management protocol used to access the management module"
        ::= { localUsersStatusEntry 3 }


    userStatusRemoteIPAddress OBJECT-TYPE
        SYNTAX      Ipv4v6Address
        MAX-ACCESS  read-only
        STATUS      current
        DESCRIPTION
                  "This object specifies the remote IP address user management session."
        ::= { localUsersStatusEntry 4 }

    userStatusStartTime OBJECT-TYPE
        SYNTAX DisplayString
        MAX-ACCESS  read-only
        STATUS      current
        DESCRIPTION
                  "This object identifies the date and time that the current user's
                    management session started."
        ::= { localUsersStatusEntry 5 }


    userStatusLevel OBJECT-TYPE
        SYNTAX      INTEGER
        {
          admin(0),
          operator(1)
        }
        MAX-ACCESS  read-only
        STATUS      current
        DESCRIPTION
            "Admin:
                Total access to the management module. More than one admin user
                account can exist, but we recommend that you only have one.
             operator:
                Full read only access to configuration and limited control commands "
        ::= { localUsersStatusEntry 6 }
--
--
-- end of localUsersStatusTable
--


--
-- radiusGroup
--
radiusGroup           OBJECT IDENTIFIER  ::= { mgtUsersGroup 8 }

radiusStatus OBJECT-TYPE
    SYNTAX      ContainerStatus
    MAX-ACCESS  read-write
    STATUS      current
    DESCRIPTION
        "When you perform a GET on this variable, one of
         the following values will be returned:
         1-Indicates that the container folder is active with no changes.
         2-Indicates that the container folder is active with change(s).
           Once you have completed setting the variables in a folder, you
           will want to submit your changes to the management module. To do
           this, set the Status variable to 4. If you want to discard the
           changes, set the Status variable to 6.
         4-Indicates that the changes in the container folder are to be
           submitted to the management module.
         6-Indicates that the changes in the container folder are to be
           discarded."
    ::= {radiusGroup 1}

radiusPrimaryAuthHost OBJECT-TYPE
    SYNTAX   DisplayString(SIZE(0..14))
    MAX-ACCESS    read-write
    STATUS        current
    DESCRIPTION
        "Primary Radius Authentication Host"
    ::= {radiusGroup 2}

radiusSecondaryAuthHost OBJECT-TYPE
    SYNTAX   DisplayString(SIZE(0..14))
    MAX-ACCESS    read-write
    STATUS        current
    DESCRIPTION
        "Secondary Radius Authentication Host"
    ::= {radiusGroup 3}

radiusAuthenticationPort OBJECT-TYPE
    SYNTAX   Integer32(0..65535)
    MAX-ACCESS    read-write
    STATUS        current
    DESCRIPTION
        "The port that the RADIUS host listens to for
         authentication requests. The default port is 1812."
    ::= {radiusGroup 4}

radiusAccounting OBJECT-TYPE
    SYNTAX   OnOffValue
    MAX-ACCESS    read-write
    STATUS        current
    DESCRIPTION
        "Radius Accounting "
    ::= {radiusGroup 5}

radiusPrimaryAcctHost OBJECT-TYPE
    SYNTAX   DisplayString(SIZE(0..14))
    MAX-ACCESS    read-write
    STATUS        current
    DESCRIPTION
        "Name of the primary RADIUS authentication host."
    ::= {radiusGroup 6}

radiusSecondaryAcctHost OBJECT-TYPE
    SYNTAX   DisplayString(SIZE(0..14))
    MAX-ACCESS    read-write
    STATUS        current
    DESCRIPTION
        "Name of the secondary RADIUS authentication host."
    ::= {radiusGroup 7}

radiusAccountingPort OBJECT-TYPE
    SYNTAX   Integer32(0..65535)
    MAX-ACCESS    read-write
    STATUS        current
    DESCRIPTION
        "The port that the RADIUS host listens to for
         accounting requests. The default port is 1813."
    ::= {radiusGroup 8}

radiusAcctAuth OBJECT-TYPE
    SYNTAX   OnOffValue
    MAX-ACCESS    read-write
    STATUS        current
    DESCRIPTION
        "Radius Accounting Authenticator "
    ::= {radiusGroup 9}

radiusRetryLimit OBJECT-TYPE
    SYNTAX   Integer32(0..255)
    MAX-ACCESS    read-write
    STATUS        current
    DESCRIPTION
        "The number of times the management module tries
         to connect to the RADIUS server before erroring
         out. Valid values are 0-255. The default is 5."
    ::= {radiusGroup 10}

radiusTimeout OBJECT-TYPE
    SYNTAX   Integer32(1..255)
    MAX-ACCESS    read-write
    STATUS        current
    DESCRIPTION
        "The time, in seconds, that the management module waits
         to receive a reply after sending out a request to
         a RADIUS accounting or authentication host. If no
         reply is received before the timeout period expires,
         the management module will retry the same host up to and
         including the number of retry attempts. Valid values
         are 1-255. The default is 3 seconds."
    ::= {radiusGroup 11}

radiusNasIdentifier OBJECT-TYPE
    SYNTAX      DisplayString(SIZE(0..32))
    MAX-ACCESS  read-write
    STATUS      current
    DESCRIPTION
        "The NAS identifier name.
         To delete this , set this field to blank."
    ::= { radiusGroup 12 }

radiusNasIpAddress OBJECT-TYPE
    SYNTAX      OnOffValue
    MAX-ACCESS  read-write
    STATUS      current
    DESCRIPTION
        "When on, the NAS Identifier obtains ipv4 address automatically.
         Default is on."
    ::= { radiusGroup 13 }

radiusNasSpecifyIpAddress OBJECT-TYPE
    SYNTAX      IpAddress
    MAX-ACCESS  read-write
    STATUS      current
    DESCRIPTION
        "Specify the unique IPv4 address that NAS Identifier will use"
    ::= { radiusGroup 14}

radiusNasIpv6Address OBJECT-TYPE
    SYNTAX      OnOffValue
    MAX-ACCESS  read-write
    STATUS      current
    DESCRIPTION

        "When on, the NAS Identifier obtains ipv6 address automatically.
         Default is on."
    ::= { radiusGroup 15 }

radiusNasSpecifyIpv6Address OBJECT-TYPE
    SYNTAX      DisplayString
    MAX-ACCESS  read-write
    STATUS      current
    DESCRIPTION
        "Specify the unique IPv6 address that NAS Identifier will use"
    ::= { radiusGroup 16}
--
-- end of radiusGroup
--

--
-- kerberosGroup
--
kerberosGroup         OBJECT IDENTIFIER  ::= { mgtUsersGroup 9 }

kerberosStatus OBJECT-TYPE
    SYNTAX      ContainerStatus
    MAX-ACCESS  read-write
    STATUS      current
    DESCRIPTION
        "When you perform a GET on this variable, one of
         the following values will be returned:
         1-Indicates that the container folder is active with no changes.
         2-Indicates that the container folder is active with change(s).
           Once you have completed setting the variables in a folder, you
           will want to submit your changes to the management module. To do
           this, set the Status variable to 4. If you want to discard the
           changes, set the Status variable to 6.
         4-Indicates that the changes in the container folder are to be
           submitted to the management module and verified. To save the
           changes to flash a write of writeToFlash(1) in the adminFunction
           object is required.
        6-Indicates that the changes in the container folder are to be
          discarded."
    ::= {kerberosGroup 1}

kerberosRealm OBJECT-TYPE
    SYNTAX   DisplayString(SIZE(0..32))
    MAX-ACCESS    read-write
    STATUS        current
    DESCRIPTION
        "The Kerberos realm is the Kerberos host domain name,
         in upper-case letters."
    ::= {kerberosGroup 2}

kerberosDomain OBJECT-TYPE
    SYNTAX   DisplayString(SIZE(0..32))
    MAX-ACCESS    read-write
    STATUS        current
    DESCRIPTION
        "The name of a host running the KDC (Key Distribution Center) for the specified
         realm. The host name that you specify must either be defined in the management
         module's host Table before the last reboot or be resolved by DNS."
    ::= {kerberosGroup 3}

kerberosPort OBJECT-TYPE
    SYNTAX   Integer32(0..65535)
    MAX-ACCESS    read-write
    STATUS        current
    DESCRIPTION
        "The port that the Kerberos server listens to for authentication requests.
         If no port is specified, the default port 88 is used."
    ::= {kerberosGroup 4}
--
-- end of kerberosGroup
--
--
-- ldapGroup
--
ldapGroup             OBJECT IDENTIFIER  ::= { mgtUsersGroup 10 }

ldapStatus OBJECT-TYPE
    SYNTAX      ContainerStatus
    MAX-ACCESS  read-write
    STATUS      current
    DESCRIPTION
        "When you perform a GET on this variable, one of
         the following values will be returned:
         1-Indicates that the container folder is active with no changes.
         2-Indicates that the container folder is active with change(s).
           Once you have completed setting the variables in a folder, you
           will want to submit your changes to the management module. To do
           this, set the Status variable to 4. If you want to discard the
           changes, set the Status variable to 6.
         4-Indicates that the changes in the container folder are to be
           submitted to the management module and verified. To save the
           changes to flash a write of writeToFlash(1) in the adminFunction
           object is required.
        6-Indicates that the changes in the container folder are to be
          discarded."
    ::= {ldapGroup 1}

ldapHost OBJECT-TYPE
    SYNTAX   DisplayString(SIZE(0..64))
    MAX-ACCESS    read-write
    STATUS        current
    DESCRIPTION
        "The name or IP address of the LDAP host. If you use
        a host name, that host must either have been defined
        in the management module's Host Table before the last
        reboot or be resolved by DNS. If you are using TLS,
        you must enter the same string you used to create
                    the LDAP certificate. "
    ::= {ldapGroup 2}

ldapPort OBJECT-TYPE
    SYNTAX   Integer32(0..65535)
    MAX-ACCESS    read-write
    STATUS        current
    DESCRIPTION
        "The port that the LDAP host listens to for authentication requests. The default port is 389."
    ::= {ldapGroup 3}

ldapBase OBJECT-TYPE
    SYNTAX   DisplayString(SIZE(0..64))
    MAX-ACCESS    read-write
    STATUS        current
    DESCRIPTION
        "The domain component (dc) that is the starting point for the search for user
         authentication."
    ::= {ldapGroup 4}

ldapEnableTLS OBJECT-TYPE
    SYNTAX   OnOffValue
    MAX-ACCESS    read-write
    STATUS        current
    DESCRIPTION
        "Enables/disables the Transport Layer Security (TLS) with the LDAP host."
    ::= {ldapGroup 5}

ldapTLSPort OBJECT-TYPE
    SYNTAX   Integer32(0..65535)
    MAX-ACCESS    read-write
    STATUS        current
    DESCRIPTION
        "Specify the port number that LDAP will use for TLS. The default is port 636."
    ::= {ldapGroup 6}

ldapUID OBJECT-TYPE
    SYNTAX        DisplayString(SIZE(0..32))
    MAX-ACCESS    read-write
    STATUS        current
    DESCRIPTION
        "LDAP user attribute.
           e.g.
           uid                (OpenLDAP)
           sAMAccountName     (Active Directory)

           The default is 'uid'."
    ::= {ldapGroup 7}

ldapPasswordEncryption OBJECT-TYPE
    SYNTAX      INTEGER {
                        none(1),
                        md5(2)
                    }
    MAX-ACCESS    read-write
    STATUS        current
    DESCRIPTION
        "LDAP password encryption method."
    ::= {ldapGroup 8}

ldapClientAuth OBJECT-TYPE
    SYNTAX   OnOffValue
    MAX-ACCESS    read-write
    STATUS        current
    DESCRIPTION
        "LDAP client authentication."
    ::= {ldapGroup 9}

ldapClientName OBJECT-TYPE
    SYNTAX        DisplayString(SIZE(0..64))
    MAX-ACCESS    read-write
    STATUS        current
    DESCRIPTION
        "LDAP client name.  Identifies the unit to the LDAP server, when client
         authentication is ."
    ::= {ldapGroup 10}

ldapClientAppendBase OBJECT-TYPE
    SYNTAX   OnOffValue
    MAX-ACCESS    read-write
    STATUS        current
    DESCRIPTION
        "Append base to LDAP client name."
    ::= {ldapGroup 11}

ldapClientPassword OBJECT-TYPE
    SYNTAX        DisplayString(SIZE(0..64))
    MAX-ACCESS    read-write
    STATUS        current
    DESCRIPTION
        "LDAP client password.  Identifies the unit to the LDAP server, when client
         authentication is ."
    ::= {ldapGroup 12}
--
-- end of ldapGroup
--
--
-- tacacsGroup
--
tacacsGroup           OBJECT IDENTIFIER  ::= { mgtUsersGroup 11 }

tacacsStatus OBJECT-TYPE
    SYNTAX      ContainerStatus
    MAX-ACCESS  read-write
    STATUS      current
    DESCRIPTION
        "When you perform a GET on this variable, one of
         the following values will be returned:
         1-Indicates that the container folder is active with no changes.
         2-Indicates that the container folder is active with change(s).
           Once you have completed setting the variables in a folder, you
           will want to submit your changes to the management module. To do
           this, set the Status variable to 4. If you want to discard the
           changes, set the Status variable to 6.
         4-Indicates that the changes in the container folder are to be
           submitted to the management module and verified. To save the
           changes to flash a write of writeToFlash(1) in the adminFunction
           object is required.
         6-Indicates that the changes in the container folder are to be
           discarded."
    ::= {tacacsGroup 1}

tacacsPrimaryHost OBJECT-TYPE
    SYNTAX   DisplayString(SIZE(0..14))
    MAX-ACCESS    read-write
    STATUS        current
    DESCRIPTION
        "The primary TACACS+ host that is used for authentication."
    ::= {tacacsGroup 2}

tacacsSecondaryHost OBJECT-TYPE
    SYNTAX   DisplayString(SIZE(0..14))
    MAX-ACCESS    read-write
    STATUS        current
    DESCRIPTION
        "The secondary TACACS+ host that is used for authentication, should the primary
         TACACS+ host fail to respond."
    ::= {tacacsGroup 3}

tacacsPort OBJECT-TYPE
    SYNTAX   Integer32(0..65535)
    MAX-ACCESS    read-write
    STATUS        current
    DESCRIPTION
        "The port number that TACACS+ listens to for authentication requests. The default
         port number is 49."
    ::= {tacacsGroup 4}

tacacsAccounting OBJECT-TYPE
    SYNTAX   OnOffValue
    MAX-ACCESS    read-write
    STATUS        current
    DESCRIPTION
        "Enable/Disable TACACS+ accounting"
    ::= {tacacsGroup 5}

tacacsAccountingPrimaryHost OBJECT-TYPE
    SYNTAX   DisplayString(SIZE(0..14))
    MAX-ACCESS    read-write
    STATUS        current
    DESCRIPTION
        "The primary TACACS+ accounting host that is used for."
    ::= {tacacsGroup 6}

tacacsAccountingSecondaryHost OBJECT-TYPE
    SYNTAX   DisplayString(SIZE(0..14))
    MAX-ACCESS    read-write
    STATUS        current
    DESCRIPTION
        "The secondary TACACS+ accounting host that is used for , should the primary
        TACACS+ host fail to respond."
    ::= {tacacsGroup 7}

tacacsAccountingPort OBJECT-TYPE
    SYNTAX   Integer32(0..65535)
    MAX-ACCESS    read-write
    STATUS        current
    DESCRIPTION
        "The port number that TACACS+ listens to for accounting requests. The default
         port number is 49."
    ::= {tacacsGroup 8}

tacacsAuthorization OBJECT-TYPE
    SYNTAX   OnOffValue
    MAX-ACCESS    read-write
    STATUS        current
    DESCRIPTION
        "Enable/Disable TACACS+ authorization"
    ::= {tacacsGroup 9}

tacacsAlternateServiceNames OBJECT-TYPE
    SYNTAX   OnOffValue
    MAX-ACCESS    read-write
    STATUS        current
    DESCRIPTION
        "Enable alternate service names for TACACS+."
    ::= {tacacsGroup 10}
--
-- tacacsGroup
--
--
-- securidGroup
--
securidGroup          OBJECT IDENTIFIER  ::= { mgtUsersGroup 12 }

securidStatus OBJECT-TYPE
    SYNTAX      ContainerStatus
    MAX-ACCESS  read-write
    STATUS      current
    DESCRIPTION
      "When you perform a GET on this variable, one of
         the following values will be returned:
         1-Indicates that the container folder is active with no changes.
         2-Indicates that the container folder is active with change(s).
           Once you have completed setting the variables in a folder, you
           will want to submit your changes to the management module. To do
           this, set the Status variable to 4. If you want to discard the
           changes, set the Status variable to 6.
         4-Indicates that the changes in the container folder are to be
           submitted to the management module and verified. To save the
           changes to flash a write of writeToFlash(1) in the adminFunction
           object is required.
         6-Indicates that the changes in the container folder are to be
           discarded."
    ::= {securidGroup 1}

securidMasterHost OBJECT-TYPE
    SYNTAX   DisplayString(SIZE(0..14))
    MAX-ACCESS    read-write
    STATUS        current
    DESCRIPTION
        "The first SecurID server that is tried for
         user authentication."
    ::= {securidGroup 2}

securidSlaveHost OBJECT-TYPE
    SYNTAX   DisplayString(SIZE(0..14))
    MAX-ACCESS    read-write
    STATUS        current
    DESCRIPTION
        "If the first SecurID server does not respond
         to an authentication request, this is the next
         SecurID server that is tried for user authentication."
    ::= {securidGroup 3}

securidPort OBJECT-TYPE
    SYNTAX   Integer32(0..65535)
    MAX-ACCESS    read-write
    STATUS        current
    DESCRIPTION
        "The port number that SecurID listens to for
         authentication requests. The default port number is 5500."
    ::= {securidGroup 4}

securidType OBJECT-TYPE
    SYNTAX   INTEGER {
            des(1),
      sdi(2)
      }
    MAX-ACCESS    read-write
    STATUS        current
    DESCRIPTION
        "You can specify either SDI or DES encryption for SecurID
         server communication. The default is SDI encryption."
    ::= {securidGroup 5}

  securidLegacy OBJECT-TYPE
     SYNTAX   YesNoValue
      MAX-ACCESS    read-write
      STATUS        current
      DESCRIPTION
        "If you are running SecurID 3.x or 4.x, you need to run
         in Legacy Mode. If you are running SecurID 5.x or above,
         do not select Legacy Mode."
      ::= {securidGroup 6}
--
-- end of securidGroup
--
--

-- nisGroup
--
nisGroup              OBJECT IDENTIFIER  ::= { mgtUsersGroup 13 }

nisStatus OBJECT-TYPE
    SYNTAX      ContainerStatus
    MAX-ACCESS  read-write
    STATUS      current
    DESCRIPTION
        "When you perform a GET on this variable, one of
         the following values will be returned:
         1-Indicates that the container folder is active with no changes.
         2-Indicates that the container folder is active with change(s).
           Once you have completed setting the variables in a folder, you
           will want to submit your changes to the management module. To do
           this, set the Status variable to 4. If you want to discard the
           changes, set the Status variable to 6.
         4-Indicates that the changes in the container folder are to be
           submitted to the management module and verified. To save the
           changes to flash a write of writeToFlash(1) in the adminFunction
           object is required.
         6-Indicates that the changes in the container folder are to be
           discarded."
    ::= {nisGroup 1}

nisDomain OBJECT-TYPE
    SYNTAX   DisplayString(SIZE(0..32))
    MAX-ACCESS    read-write
    STATUS        current
    DESCRIPTION
        "The NIS domain name."
    ::= {nisGroup 2}

nisPrimaryHost OBJECT-TYPE
    SYNTAX   DisplayString(SIZE(0..14))
    MAX-ACCESS    read-write
    STATUS        current
    DESCRIPTION
        "The primary NIS host that is used for authentication."
    ::= {nisGroup 3}

nisSecondaryHost OBJECT-TYPE
    SYNTAX   DisplayString(SIZE(0..14))
    MAX-ACCESS    read-write
    STATUS        current
    DESCRIPTION
        "The secondary NIS host that is used for authentication,
         should the primary NIS host fail to respond."
    ::= {nisGroup 4}
--
-- end of nisGroup
--
--
-- end of mgtUsersGroup
--

--
-- mgtDateTimeGroup
--
mgtDateTimeStatus OBJECT-TYPE
    SYNTAX      ContainerStatus
    MAX-ACCESS  read-write
    STATUS      current
    DESCRIPTION
        "When you perform a GET on this variable, one of
         the following values will be returned:
         1-Indicates that the container folder is active with no changes.
         2-Indicates that the container folder is active with change(s).
           Once you have completed setting the variables in a folder, you
           will want to submit your changes to the management module. To do
           this, set the Status variable to 4. If you want to discard the
           changes, set the Status variable to 6.
         4-Indicates that the changes in the container folder are to be
           submitted to the management module and verified. To save the
           changes to flash a write of writeToFlash(1) in the adminFunction
           object is required.
         6-Indicates that the changes in the container folder are to be
           discarded."
    ::= {mgtDateTimeGroup 1}

systemDate OBJECT-TYPE
    SYNTAX      DisplayString
    MAX-ACCESS  read-write
    STATUS      current
    DESCRIPTION
        "The system date. Format dd/mm/yyyy."
    ::= { mgtDateTimeGroup  2 }

systemTime OBJECT-TYPE
    SYNTAX      DisplayString
    MAX-ACCESS  read-write
    STATUS      current
    DESCRIPTION
        "The system time (local time). Format hh:mm:ss."
    ::= { mgtDateTimeGroup  3 }

systemDateTimeAndOffset OBJECT-TYPE
    SYNTAX      DisplayString
    MAX-ACCESS  read-only
    STATUS      current
    DESCRIPTION
        "This read only object identifies the current system date, time and GMT offset. The
         date and time will be displayed in the regional time format configured."
    ::= { mgtDateTimeGroup  4 }


timeZoneListEnable OBJECT-TYPE
    SYNTAX      OnOffValue
    MAX-ACCESS  read-write
    STATUS      current
    DESCRIPTION
        "When the time zone list is enabled then the time zone being use is the
         one selected form the predefined list of time zones. If not enabled then
         the customTimeZoneGroup will define the time zone being used"
    ::= { mgtDateTimeGroup  5 }

selectionFromTimeZoneList OBJECT-TYPE
    SYNTAX      INTEGER {
        tzAfricaAbidjan(0),
        tzAfricaAccra(1),
        tzAfricaAddisAbaba(2),
        tzAfricaAlgiers(3),
        tzAfricaAsmera(4),
        tzAfricaBamako(5),
        tzAfricaBangui(6),
        tzAfricaBanjul(7),
        tzAfricaBissau(8),
        tzAfricaBlantyre(9),
        tzAfricaBrazzaville(10),
        tzAfricaBujumbura(11),
        tzAfricaCairo(12),
        tzAfricaCasablanca(13),
        tzAfricaCeuta(14),
        tzAfricaConakry(15),
        tzAfricaDakar(16),
        tzAfricaDaresSalaam(17),
        tzAfricaDjibouti(18),
        tzAfricaDouala(19),
        tzAfricaElAaiun(20),
        tzAfricaFreetown(21),
        tzAfricaGaborone(22),
        tzAfricaHarare(23),
        tzAfricaJohannesburg(24),
        tzAfricaKampala(25),
        tzAfricaKhartoum(26),
        tzAfricaKigali(27),
        tzAfricaKinshasa(28),
        tzAfricaLagos(29),
        tzAfricaLibreville(30),
        tzAfricaLome(31),
        tzAfricaLuanda(32),
        tzAfricaLubumbashi(33),
        tzAfricaLusaka(34),
        tzAfricaMalabo(35),
        tzAfricaMaputo(36),
        tzAfricaMaseru(37),
        tzAfricaMbabane(38),
        tzAfricaMogadishu(39),
        tzAfricaMonrovia(40),
        tzAfricaNairobi(41),
        tzAfricaNdjamena(42),
        tzAfricaNiamey(43),
        tzAfricaNouakchott(44),
        tzAfricaOuagadougou(45),
        tzAfricaPortoNovo(46),
        tzAfricaSaoTome(47),
        tzAfricaTimbuktu(48),
        tzAfricaTripoli(49),
        tzAfricaTunis(50),
        tzAfricaWindhoek(51),
        tzAmericaAdak(52),
        tzAmericaAnchorage(53),
        tzAmericaAnguilla(54),
        tzAmericaAntigua(55),
        tzAmericaAraguaina(56),
        tzAmericaAruba(57),
        tzAmericaAsuncion(58),
        tzAmericaAtka(59),
        tzAmericaBarbados(60),
        tzAmericaBelem(61),
        tzAmericaBelize(62),
        tzAmericaBoaVista(63),
        tzAmericaBogota(64),
        tzAmericaBoise(65),
        tzAmericaBuenosAires(66),
        tzAmericaCambridgeBay(67),
        tzAmericaCancun(68),
        tzAmericaCaracas(69),
        tzAmericaCatamarca(70),
        tzAmericaCayenne(71),
        tzAmericaCayman(72),
        tzAmericaChicago(73),
        tzAmericaChihuahua(74),
        tzAmericaCordoba(75),
        tzAmericaCostaRica(76),
        tzAmericaCuiaba(77),
        tzAmericaCuracao(78),
        tzAmericaDanmarkshavn(79),
        tzAmericaDawson(80),
        tzAmericaDawsonCreek(81),
        tzAmericaDenver(82),
        tzAmericaDetroit(83),
        tzAmericaDominica(84),
        tzAmericaEdmonton(85),
        tzAmericaEirunepe(86),
        tzAmericaElSalvador(87),
        tzAmericaEnsenada(88),
        tzAmericaFortWayne(89),
        tzAmericaFortaleza(90),
        tzAmericaGlaceBay(91),
        tzAmericaGodthab(92),
        tzAmericaGooseBay(93),
        tzAmericaGrandTurk(94),
        tzAmericaGrenada(95),
        tzAmericaGuadeloupe(96),
        tzAmericaGuatemala(97),
        tzAmericaGuayaquil(98),
        tzAmericaGuyana(99),
        tzAmericaHalifax(100),
        tzAmericaHavana(101),
        tzAmericaHermosillo(102),
        tzAmericaIndianaIndianapolis(103),
        tzAmericaIndianaKnox(104),
        tzAmericaIndianaMarengo(105),
        tzAmericaIndianaVevay(106),
        tzAmericaIndianapolis(107),
        tzAmericaInuvik(108),
        tzAmericaIqaluit(109),
        tzAmericaJamaica(110),
        tzAmericaJujuy(111),
        tzAmericaJuneau(112),
        tzAmericaKentuckyLouisville(113),
        tzAmericaKentuckyMonticello(114),
        tzAmericaKnoxIN(115),
        tzAmericaLaPaz(116),
        tzAmericaLima(117),
        tzAmericaLosAngeles(118),
        tzAmericaLouisville(119),
        tzAmericaMaceio(120),
        tzAmericaManagua(121),
        tzAmericaManaus(122),
        tzAmericaMartinique(123),
        tzAmericaMazatlan(124),
        tzAmericaMendoza(125),
        tzAmericaMenominee(126),
        tzAmericaMerida(127),
        tzAmericaMexicoCity(128),
        tzAmericaMiquelon(129),
        tzAmericaMonterrey(130),
        tzAmericaMontevideo(131),
        tzAmericaMontreal(132),
        tzAmericaMontserrat(133),
        tzAmericaNassau(134),
        tzAmericaNewYork(135),
        tzAmericaNipigon(136),
        tzAmericaNome(137),
        tzAmericaNoronha(138),
        tzAmericaNorthDakotaCenter(139),
        tzAmericaPanama(140),
        tzAmericaPangnirtung(141),
        tzAmericaParamaribo(142),
        tzAmericaPhoenix(143),
        tzAmericaPortofSpain(144),
        tzAmericaPortauPrince(145),
        tzAmericaPortoAcre(146),
        tzAmericaPortoVelho(147),
        tzAmericaPuertoRico(148),
        tzAmericaRainyRiver(149),
        tzAmericaRankinInlet(150),
        tzAmericaRecife(151),
        tzAmericaRegina(152),
        tzAmericaRioBranco(153),
        tzAmericaRosario(154),
        tzAmericaSantiago(155),
        tzAmericaSantoDomingo(156),
        tzAmericaSaoPaulo(157),
        tzAmericaScoresbysund(158),
        tzAmericaShiprock(159),
        tzAmericaStJohns(160),
        tzAmericaStKitts(161),
        tzAmericaStLucia(162),
        tzAmericaStThomas(163),
        tzAmericaStVincent(164),
        tzAmericaSwiftCurrent(165),
        tzAmericaTegucigalpa(166),
        tzAmericaThule(167),
        tzAmericaThunderBay(168),
        tzAmericaTijuana(169),
        tzAmericaTortola(170),
        tzAmericaVancouver(171),
        tzAmericaVirgin(172),
        tzAmericaWhitehorse(173),
        tzAmericaWinnipeg(174),
        tzAmericaYakutat(175),
        tzAmericaYellowknife(176),
        tzAntarcticaCasey(177),
        tzAntarcticaDavis(178),
        tzAntarcticaDumontDUrville(179),
        tzAntarcticaMawson(180),
        tzAntarcticaMcMurdo(181),
        tzAntarcticaPalmer(182),
        tzAntarcticaSouthPole(183),
        tzAntarcticaSyowa(184),
        tzAntarcticaVostok(185),
        tzArcticLongyearbyen(186),
        tzAsiaAden(187),
        tzAsiaAlmaty(188),
        tzAsiaAmman(189),
        tzAsiaAnadyr(190),
        tzAsiaAqtau(191),
        tzAsiaAqtobe(192),
        tzAsiaAshgabat(193),
        tzAsiaAshkhabad(194),
        tzAsiaBaghdad(195),
        tzAsiaBahrain(196),
        tzAsiaBaku(197),
        tzAsiaBangkok(198),
        tzAsiaBeirut(199),
        tzAsiaBishkek(200),
        tzAsiaBrunei(201),
        tzAsiaCalcutta(202),
        tzAsiaChoibalsan(203),
        tzAsiaChongqing(204),
        tzAsiaChungking(205),
        tzAsiaColombo(206),
        tzAsiaDacca(207),
        tzAsiaDamascus(208),
        tzAsiaDhaka(209),
        tzAsiaDili(210),
        tzAsiaDubai(211),
        tzAsiaDushanbe(212),
        tzAsiaGaza(213),
        tzAsiaHarbin(214),
        tzAsiaHongKong(215),
        tzAsiaHovd(216),
        tzAsiaIrkutsk(217),
        tzAsiaIstanbul(218),
        tzAsiaJakarta(219),
        tzAsiaJayapura(220),
        tzAsiaJerusalem(221),
        tzAsiaKabul(222),
        tzAsiaKamchatka(223),
        tzAsiaKarachi(224),
        tzAsiaKashgar(225),
        tzAsiaKatmandu(226),
        tzAsiaKrasnoyarsk(227),
        tzAsiaKualaLumpur(228),
        tzAsiaKuching(229),
        tzAsiaKuwait(230),
        tzAsiaMacao(231),
        tzAsiaMagadan(232),
        tzAsiaManila(233),
        tzAsiaMuscat(234),
        tzAsiaNicosia(235),
        tzAsiaNovosibirsk(236),
        tzAsiaOmsk(237),
        tzAsiaPhnomPenh(238),
        tzAsiaPontianak(239),
        tzAsiaPyongyang(240),
        tzAsiaQatar(241),
        tzAsiaRangoon(242),
        tzAsiaRiyadh(243),
        tzAsiaSaigon(244),
        tzAsiaSakhalin(245),
        tzAsiaSamarkand(246),
        tzAsiaSeoul(247),
        tzAsiaShanghai(248),
        tzAsiaSingapore(249),
        tzAsiaTaipei(250),
        tzAsiaTashkent(251),
        tzAsiaTbilisi(252),
        tzAsiaTehran(253),
        tzAsiaTelAviv(254),
        tzAsiaThimbu(255),
        tzAsiaThimphu(256),
        tzAsiaTokyo(257),
        tzAsiaUjungPandang(258),
        tzAsiaUlaanbaatar(259),
        tzAsiaUlanBator(260),
        tzAsiaUrumqi(261),
        tzAsiaVientiane(262),
        tzAsiaVladivostok(263),
        tzAsiaYakutsk(264),
        tzAsiaYekaterinburg(265),
        tzAsiaYerevan(266),
        tzAtlanticAzores(267),
        tzAtlanticBermuda(268),
        tzAtlanticCanary(269),
        tzAtlanticCapeVerde(270),
        tzAtlanticFaeroe(271),
        tzAtlanticJanMayen(272),
        tzAtlanticMadeira(273),
        tzAtlanticReykjavik(274),
        tzAtlanticSouthGeorgia(275),
        tzAtlanticStHelena(276),
        tzAtlanticStanley(277),
        tzAustraliaACT(278),
        tzAustraliaAdelaide(279),
        tzAustraliaBrisbane(280),
        tzAustraliaBrokenHill(281),
        tzAustraliaCanberra(282),
        tzAustraliaDarwin(283),
        tzAustraliaHobart(284),
        tzAustraliaLHI(285),
        tzAustraliaLindeman(286),
        tzAustraliaLordHowe(287),
        tzAustraliaMelbourne(288),
        tzAustraliaNSW(289),
        tzAustraliaNorth(290),
        tzAustraliaPerth(291),
        tzAustraliaQueensland(292),
        tzAustraliaSouth(293),
        tzAustraliaSydney(294),
        tzAustraliaTasmania(295),
        tzAustraliaVictoria(296),
        tzAustraliaWest(297),
        tzAustraliaYancowinna(298),
        tzBrazilDeNoronha(299),
        tzBrazilEast(300),
        tzBrazilWest(301),
        tzCanadaAtlantic(302),
        tzCanadaCentral(303),
        tzCanadaEastSaskatchewan(304),
        tzCanadaEastern(305),
        tzCanadaMountain(306),
        tzCanadaNewfoundland(307),
        tzCanadaPacific(308),
        tzCanadaSaskatchewan(309),
        tzCanadaYukon(310),
        tzChileContinental(311),
        tzChileEasterIsland(312),
        tzCuba(313),
        tzEgypt(314),
        tzEire(315),
        tzEuropeAmsterdam(316),
        tzEuropeAndorra(317),
        tzEuropeAthens(318),
        tzEuropeBelfast(319),
        tzEuropeBelgrade(320),
        tzEuropeBerlin(321),
        tzEuropeBratislava(322),
        tzEuropeBrussels(323),
        tzEuropeBucharest(324),
        tzEuropeBudapest(325),
        tzEuropeChisinau(326),
        tzEuropeCopenhagen(327),
        tzEuropeDublin(328),
        tzEuropeGibraltar(329),
        tzEuropeHelsinki(330),
        tzEuropeIstanbul(331),
        tzEuropeKaliningrad(332),
        tzEuropeKiev(333),
        tzEuropeLisbon(334),
        tzEuropeLjubljana(335),
        tzEuropeLondon(336),
        tzEuropeLuxembourg(337),
        tzEuropeMadrid(338),
        tzEuropeMalta(339),
        tzEuropeMinsk(340),
        tzEuropeMonaco(341),
        tzEuropeMoscow(342),
        tzEuropeNicosia(343),
        tzEuropeOslo(344),
        tzEuropeParis(345),
        tzEuropePrague(346),
        tzEuropeRiga(347),
        tzEuropeRome(348),
        tzEuropeSamara(349),
        tzEuropeSanMarino(350),
        tzEuropeSarajevo(351),
        tzEuropeSimferopol(352),
        tzEuropeSkopje(353),
        tzEuropeSofia(354),
        tzEuropeStockholm(355),
        tzEuropeTallinn(356),
        tzEuropeTirane(357),
        tzEuropeTiraspol(358),
        tzEuropeUzhgorod(359),
        tzEuropeVaduz(360),
        tzEuropeVatican(361),
        tzEuropeVienna(362),
        tzEuropeVilnius(363),
        tzEuropeWarsaw(364),
        tzEuropeZagreb(365),
        tzEuropeZaporozhye(366),
        tzEuropeZurich(367),
        tzGreatBritainEire(368),
        tzGreatBritainGreatBritain(369),
        tzHongKong(370),
        tzIceland(371),
        tzIndianAntananarivo(372),
        tzIndianChagos(373),
        tzIndianChristmas(374),
        tzIndianCocos(375),
        tzIndianComoro(376),
        tzIndianKerguelen(377),
        tzIndianMahe(378),
        tzIndianMaldives(379),
        tzIndianMauritius(380),
        tzIndianMayotte(381),
        tzIndianReunion(382),
        tzIran(383),
        tzIsrael(384),
        tzJamaica(385),
        tzJapan(386),
        tzKwajalein(387),
        tzLibya(388),
        tzMexicoBajaNorte(389),
        tzMexicoBajaSur(390),
        tzMexicoGeneral(391),
        tzNavajo(392),
        tzNewZealandChatham(393),
        tzNewZealandNewZealand(394),
        tzPacificApia(395),
        tzPacificAuckland(396),
        tzPacificChatham(397),
        tzPacificEaster(398),
        tzPacificEfate(399),
        tzPacificEnderbury(400),
        tzPacificFakaofo(401),
        tzPacificFiji(402),
        tzPacificFunafuti(403),
        tzPacificGalapagos(404),
        tzPacificGambier(405),
        tzPacificGuadalcanal(406),
        tzPacificGuam(407),
        tzPacificHonolulu(408),
        tzPacificJohnston(409),
        tzPacificKiritimati(410),
        tzPacificKosrae(411),
        tzPacificKwajalein(412),
        tzPacificMajuro(413),
        tzPacificMarquesas(414),
        tzPacificMidway(415),
        tzPacificNauru(416),
        tzPacificNiue(417),
        tzPacificNorfolk(418),
        tzPacificNoumea(419),
        tzPacificPagoPago(420),
        tzPacificPalau(421),
        tzPacificPitcairn(422),
        tzPacificPonape(423),
        tzPacificPortMoresby(424),
        tzPacificRarotonga(425),
        tzPacificSaipan(426),
        tzPacificSamoa(427),
        tzPacificTahiti(428),
        tzPacificTarawa(429),
        tzPacificTongatapu(430),
        tzPacificTruk(431),
        tzPacificWake(432),
        tzPacificWallis(433),
        tzPacificYap(434),
        tzPoland(435),
        tzPortugal(436),
        tzSingapore(437),
        tzTurkey(438),
        tzUSAlaska(439),
        tzUSAleutian(440),
        tzUSArizona(441),
        tzUSCentral(442),
        tzUSEastIndiana(443),
        tzUSEastern(444),
        tzUSHawaii(445),
        tzUSIndianaStarke(446),
        tzUSMichigan(447),
        tzUSMountain(448),
        tzUSPacific(449),
        tzUSSamoa(450)
    }
    MAX-ACCESS  read-write
    STATUS      current
    DESCRIPTION
        "This object identifies the predefined time zone selected. This time zone
         will be used if timeZoneListEnable  object is set to yes.
         configured."
    ::= { mgtDateTimeGroup  6 }


timeZoneAdjustForDST OBJECT-TYPE
    SYNTAX      YesNoValue
    MAX-ACCESS  read-write
    STATUS      current
    DESCRIPTION
        "This object identifies if the time will be adjusted for DST (Daylight
         Savings Time) or not."
    ::= { mgtDateTimeGroup  7 }

customTimeZoneGroup	OBJECT IDENTIFIER ::= { mgtDateTimeGroup 8 }

    customTimeZoneStatus OBJECT-TYPE
        SYNTAX      ContainerStatus
        MAX-ACCESS  read-write
        STATUS      current
        DESCRIPTION
            "When you perform a GET on this variable, one of
             the following values will be returned:
         1-Indicates that the container folder is active with no changes.
         2-Indicates that the container folder is active with change(s).
           Once you have completed setting the variables in a folder, you
           will want to submit your changes to the management module. To do
           this, set the Status variable to 4. If you want to discard the
           changes, set the Status variable to 6.
         4-Indicates that the changes in the container folder are to be
           submitted to the management module and verified. To save the
           changes to flash a write of writeToFlash(1) in the adminFunction
           object is required.
         6-Indicates that the changes in the container folder are to be
           discarded."
        ::= {customTimeZoneGroup 1}

    timeZoneName OBJECT-TYPE
        SYNTAX      DisplayString(SIZE(0..4))
        MAX-ACCESS  read-write
        STATUS      current
        DESCRIPTION
            "The name of the time zone when using standard time."
        ::= { customTimeZoneGroup 2 }

    timeOffset OBJECT-TYPE
        SYNTAX      Integer32(-720..840)
        MAX-ACCESS  read-write
        STATUS      current
        DESCRIPTION
            "The offset of summer time from standard time in minutes."
        ::= { customTimeZoneGroup 3 }

    timeSummerName OBJECT-TYPE
        SYNTAX      DisplayString(SIZE(0..4))
        MAX-ACCESS  read-write
        STATUS      current
        DESCRIPTION
            "The name of the time zone when using summer time."
        ::= { customTimeZoneGroup 4 }

    timeSummerOffset OBJECT-TYPE
        SYNTAX      Integer32(0..180)
        MAX-ACCESS  read-write
        STATUS      current
        DESCRIPTION
                  "The offset of summer time from standard time in minutes."
        ::= { customTimeZoneGroup 5 }

    timeSummerMode OBJECT-TYPE
        SYNTAX      INTEGER {
          disabled(0),
          fixed(1),
          recurring(2)
        }
        MAX-ACCESS  read-write
        STATUS      current
        DESCRIPTION
            "You can configure the summer time to take effect:
                None-No summer time change.
                Fixed-The summer time change goes into effect at
                        the specified time every year. For example,
                        April 15 at 1:00 pm.
                Recurring-The summer time changes goes into effect
                             every year at same relative time. For example,
                            on the third week in April on a Tuesday at 1:00 pm."
        ::= { customTimeZoneGroup 6 }

    timeSummerRecStartMonth OBJECT-TYPE
        SYNTAX      INTEGER {
          january(0),
          february(1),
          march(2),
          april(3),
          may(4),
          june(5),
          july(6),
          august(7),
          september(8),
          october(9),
          november(10),
          december(11)
        }
        MAX-ACCESS  read-write
        STATUS      current
        DESCRIPTION
            "The recurring summer time start month."
        ::= { customTimeZoneGroup 7 }

    timeSummerRecStartWeek OBJECT-TYPE
        SYNTAX      INTEGER {
          first(0),
          second(1),
          third(2),
          fourth(3),
          last(4)
        }
        MAX-ACCESS  read-write
        STATUS      current
        DESCRIPTION
            "The recurring summer time start week."
        ::= { customTimeZoneGroup 8 }

    timeSummerRecStartDay OBJECT-TYPE
        SYNTAX      INTEGER {
          sunday(0),
          monday(1),
          tuesday(2),
          wednesday(3),
          thursday(4),
          friday(5),
          saturday(6)
        }
        MAX-ACCESS  read-write
        STATUS      current
        DESCRIPTION
            "The recurring summer time start day."
        ::= { customTimeZoneGroup 9 }

    timeSummerRecStartHour OBJECT-TYPE
        SYNTAX      Integer32(0..23)
        MAX-ACCESS  read-write
        STATUS      current
        DESCRIPTION
            "The recurring summer time start hour."
        ::= { customTimeZoneGroup 10 }

    timeSummerRecStartMin OBJECT-TYPE
        SYNTAX      Integer32(0..59)
        MAX-ACCESS  read-write
        STATUS      current
        DESCRIPTION
            "The recurring summer time start minute"
        ::= { customTimeZoneGroup 11 }

    timeSummerRecEndMonth OBJECT-TYPE
        SYNTAX      INTEGER {
          january(0),
          february(1),
          march(2),
          april(3),
          may(4),
          june(5),
          july(6),
          august(7),
          september(8),
          october(9),
          november(10),
          december(11)
        }
        MAX-ACCESS  read-write
        STATUS      current
        DESCRIPTION
            "The recurring summer time end month."
        ::= { customTimeZoneGroup 12 }

    timeSummerRecEndWeek OBJECT-TYPE
        SYNTAX      INTEGER {
          first(0),
          second(1),
          third(2),
          fourth(3),
          last(4)
        }
        MAX-ACCESS  read-write
        STATUS      current
        DESCRIPTION
            "The recurring summer time end week."
        ::= { customTimeZoneGroup 13 }

    timeSummerRecEndDay OBJECT-TYPE
        SYNTAX      INTEGER {
          sunday(0),
          monday(1),
          tuesday(2),
          wednesday(3),
          thursday(4),
          friday(5),
          saturday(6)
        }
        MAX-ACCESS  read-write
        STATUS      current
        DESCRIPTION
            "The recurring summer time end day."
        ::= { customTimeZoneGroup 14 }

    timeSummerRecEndHour OBJECT-TYPE
        SYNTAX      Integer32(0..23)
        MAX-ACCESS  read-write
        STATUS      current
        DESCRIPTION
            "The recurring summer time end hour"
        ::= { customTimeZoneGroup 15 }

    timeSummerRecEndMin OBJECT-TYPE
        SYNTAX      Integer32(0..59)
        MAX-ACCESS  read-write
        STATUS      current
        DESCRIPTION
            "The recurring summer time end minute"
        ::= { customTimeZoneGroup 16 }

    timeSummerFixStartMonth OBJECT-TYPE
        SYNTAX      INTEGER {
          january(0),
          february(1),
          march(2),
          april(3),
          may(4),
          june(5),
          july(6),
          august(7),
          september(8),
          october(9),
          november(10),
          december(11)
        }
        MAX-ACCESS  read-write
        STATUS      current
        DESCRIPTION
            "The fixed summer time start month"
        ::= { customTimeZoneGroup 17 }

    timeSummerFixStartDay OBJECT-TYPE
        SYNTAX      Integer32(1..31)
        MAX-ACCESS  read-write
        STATUS      current
        DESCRIPTION
            "The fixed summer time start day"
        ::= { customTimeZoneGroup 18 }

    timeSummerFixStartHour OBJECT-TYPE
        SYNTAX      Integer32(0..23)
        MAX-ACCESS  read-write
        STATUS      current
        DESCRIPTION
            "The fixed summer time start hour"
        ::= { customTimeZoneGroup 19 }

    timeSummerFixStartMinute OBJECT-TYPE
        SYNTAX      Integer32(0..59)
        MAX-ACCESS  read-write
        STATUS      current
        DESCRIPTION
            "The fixed summer time start minute"
        ::= { customTimeZoneGroup 20 }

    timeSummerFixEndMonth OBJECT-TYPE
        SYNTAX      INTEGER {
          january(0),
          february(1),
          march(2),
          april(3),
          may(4),
          june(5),
          july(6),
          august(7),
          september(8),
          october(9),
          november(10),
          december(11)
        }
        MAX-ACCESS  read-write
        STATUS      current
        DESCRIPTION
            "The fixed summer time End month"
        ::= { customTimeZoneGroup 21 }

    timeSummerFixEndDay OBJECT-TYPE
        SYNTAX      Integer32(1..31)
        MAX-ACCESS  read-write
        STATUS      current
        DESCRIPTION
            "The fixed summer time End day"
        ::= { customTimeZoneGroup 22 }

    timeSummerFixEndHour OBJECT-TYPE
        SYNTAX      Integer32(0..23)
        MAX-ACCESS  read-write
        STATUS      current
        DESCRIPTION
            "The fixed summer time End hour"
        ::= { customTimeZoneGroup 23 }

    timeSummerFixEndMinute OBJECT-TYPE
        SYNTAX      Integer32(0..59)
        MAX-ACCESS  read-write
        STATUS      current
        DESCRIPTION
            "The fixed summer time End minute"
        ::= { customTimeZoneGroup 24 }
--
-- end of customTimeZoneGroup
--

networkTimeGroup             OBJECT IDENTIFIER  ::= { mgtDateTimeGroup 9 }
--
-- networkTimeGroup
--
timeStatus OBJECT-TYPE
    SYNTAX      ContainerStatus
    MAX-ACCESS  read-write
    STATUS      current
    DESCRIPTION
        "When you perform a GET on this variable, one of
         the following values will be returned:
         1-Indicates that the container folder is active with no changes.
         2-Indicates that the container folder is active with change(s).
           Once you have completed setting the variables in a folder, you
           will want to submit your changes to the management module. To do
           this, set the Status variable to 4. If you want to discard the
           changes, set the Status variable to 6.
         4-Indicates that the changes in the container folder are to be
           submitted to the management module and verified. To save the
           changes to flash a write of writeToFlash(1) in the adminFunction
           object is required.
         6-Indicates that the changes in the container folder are to be
           discarded."
    ::= { networkTimeGroup 1 }

timeSntpMode OBJECT-TYPE
    SYNTAX      INTEGER {
      disabled(0),
      unicast(1),
      multicast(2),
      anycast(3)
    }
    MAX-ACCESS  read-write
    STATUS      current
    DESCRIPTION
        "The SNTP client mode.  Valid modes are Disabled, Unicast, Multicast or Anycast"
    ::= { networkTimeGroup 2 }

timeSntpVersion OBJECT-TYPE
    SYNTAX      INTEGER  {
      version1(0),
      version2(1),
      version3(2),
      version4(3)
    }
    MAX-ACCESS  read-write
    STATUS      current
    DESCRIPTION
        "The sntp client version."
    ::= { networkTimeGroup 3 }

timeSntpHost1 OBJECT-TYPE
    SYNTAX      DisplayString(SIZE(0..14))
    MAX-ACCESS  read-write
    STATUS      current
    DESCRIPTION
        "The first remote SNTP host name that the device server communicates with."
    ::= { networkTimeGroup 4 }

timeSntpHost2 OBJECT-TYPE
    SYNTAX      DisplayString(SIZE(0..14))
    MAX-ACCESS  read-write
    STATUS      current
    DESCRIPTION
        "The second remote SNTP host name that the device server communicates with."
    ::= { networkTimeGroup 5 }

sntpStatGroup        OBJECT IDENTIFIER  ::= { networkTimeGroup 6 }
--
-- sntpStatGroup
--
sntpStatAddress OBJECT-TYPE
    SYNTAX      DisplayString
    MAX-ACCESS  read-only
    STATUS      current
    DESCRIPTION
        "The address of the remote SNMP host that updated the time."
    ::= { sntpStatGroup 1}

sntpStatLastUpdate OBJECT-TYPE
    SYNTAX      DisplayString
    MAX-ACCESS  read-only
    STATUS      current
    DESCRIPTION
        "The time of the last update."
    ::= { sntpStatGroup 2}

sntpStatLeapIndicator OBJECT-TYPE
    SYNTAX      INTEGER {
        noWarning(0),
        minutes61(1),
        minutes59(2),
        alarm(3)
    }
    MAX-ACCESS  read-only
    STATUS      current
    DESCRIPTION
        "The leap year indicator."
    ::= { sntpStatGroup 3}

sntpStatVersion OBJECT-TYPE
    SYNTAX      INTEGER {
        ipV4(3),
        ipv4ipv6osi(4)
    }
    MAX-ACCESS  read-only
    STATUS      current
    DESCRIPTION
        "The SNTP version. "
    ::= { sntpStatGroup 4}

sntpStatMode OBJECT-TYPE
    SYNTAX      INTEGER {
        reserved(0),
        symmetricActive(1),
        symmetricPassive(2),
        client(3),
        server(4),
        broadcast(5),
        reservedNTP(6),
        reserved2(7)
    }
    MAX-ACCESS  read-only
    STATUS      current
    DESCRIPTION
        "The current SNTP mode"
    ::= { sntpStatGroup 5}

sntpStatStratum OBJECT-TYPE
    SYNTAX      Integer32(0..15)
    MAX-ACCESS  read-only
    STATUS      current
    DESCRIPTION
        "The SNTP stratum."
    ::= { sntpStatGroup 6}

sntpStatRefId OBJECT-TYPE
    SYNTAX      Unsigned32
    MAX-ACCESS  read-only
    STATUS      current
    DESCRIPTION
        "The SNTP reference ID."
    ::= { sntpStatGroup 7}

sntpStatOffset OBJECT-TYPE
    SYNTAX      Unsigned32
    MAX-ACCESS  read-only
    STATUS      current
    DESCRIPTION
        "The SNTP offset"
    ::= { sntpStatGroup 8}
--
-- end of sntpStatGroup
--
timeSntpServerAuthentication OBJECT-TYPE
      SYNTAX      INTEGER {
               off(1),
               on(2)
      }
      MAX-ACCESS  read-write
      STATUS      current
      DESCRIPTION
              "Specifies whether to authenticate with the ntp time server."
      ::= { networkTimeGroup 7 }

timeSntpKeyID OBJECT-TYPE
      SYNTAX      INTEGER
      MAX-ACCESS  read-write
      STATUS      current
      DESCRIPTION
              "Specifies the key ID to use for host 1 during server authentication."
      ::= { networkTimeGroup 8 }
  
timeSntpKeyID2 OBJECT-TYPE
      SYNTAX      INTEGER
      MAX-ACCESS  read-write
      STATUS      current
      DESCRIPTION
              "Specifies the key ID to use for host 2 during server authentication."
      ::= { networkTimeGroup 9 }
  
--
-- end of networkTimeGroup
--
--
-- end of mgtDateTimeGroup
--


--
-- mgtBootFilesGroup
--
mgtBootFilesGroup	OBJECT IDENTIFIER  ::= { mgtFilesGroup 1 }

bootFileStatus OBJECT-TYPE
    SYNTAX      ContainerStatus
    MAX-ACCESS  read-write
    STATUS      current
    DESCRIPTION
        "When you perform a GET on this variable, one of
         the following values will be returned:
         1-Indicates that the container folder is active with no changes.
         2-Indicates that the container folder is active with change(s).
           Once you have completed setting the variables in a folder, you
           will want to submit your changes to the management module. To do
           this, set the Status variable to 4. If you want to discard the
           changes, set the Status variable to 6.
         4-Indicates that the changes in the container folder are to be
           submitted to the management module and verified. To save the
           changes to flash a write of writeToFlash(1) in the adminFunction
           object is required.
         6-Indicates that the changes in the container folder are to be
           discarded."
    ::= { mgtBootFilesGroup 1}

fileFirmwareHost OBJECT-TYPE
    SYNTAX      DisplayString(SIZE(0..46))
    MAX-ACCESS  read-write
    STATUS      current
    DESCRIPTION
        "The host name or IP address of the server that contains the firmware file.
         If you use a host name, it must exist in the management module's host table
         or be resolved by DNS."
    ::= { mgtBootFilesGroup 2}

fileFirmwareName OBJECT-TYPE
    SYNTAX      DisplayString(SIZE(0..64))
    MAX-ACCESS  read-write
    STATUS      current
    DESCRIPTION
        "The path and file name (do not use a drive letter), relative to the default
         path of your TFTP server software, of the update software for the management
         module that will be loaded when the management module is rebooted."
    ::= { mgtBootFilesGroup 3}

fileConfigurationHost OBJECT-TYPE
    SYNTAX      DisplayString(SIZE(0..46))
    MAX-ACCESS  read-write
    STATUS      current
    DESCRIPTION
        "The host name or IP address of the server that contains the configuration file.
         If you use a host name, it must exist in the management module's host table
         or be resolved by DNS."
    ::= { mgtBootFilesGroup 4}

fileConfigurationName OBJECT-TYPE
    SYNTAX      DisplayString(SIZE(0..64))
    MAX-ACCESS  read-write
    STATUS      current
    DESCRIPTION
        "The path and file name (do not use a drive letter), relative to the default
         path of your TFTP server software, of the new configuration file for the Device
         Server that will be loaded when the management module is rebooted."
    ::= { mgtBootFilesGroup 5}
--
-- end of mgtBootFilesGroup
--

--
-- mgtfirmwareUpdatesGroup
--
mgtfirmwareUpdatesGroup	OBJECT IDENTIFIER  ::= { mgtFilesGroup 2 }

firmwareUpdateStatus OBJECT-TYPE
    SYNTAX      ContainerStatus
    MAX-ACCESS  read-write
    STATUS      current
    DESCRIPTION
        "When you perform a GET on this variable, one of
         the following values will be returned:
         1-Indicates that the container folder is active with no changes.
         2-Indicates that the container folder is active with change(s).
           Once you have completed setting the variables in a folder, you
           will want to submit your changes to the management module. To do
           this, set the Status variable to 4. If you want to discard the
           changes, set the Status variable to 6.
         4-Indicates that the changes in the container folder are to be
           submitted to the management module and verified. To save the
           changes to flash a write of writeToFlash(1) in the adminFunction
           object is required.
         6-Indicates that the changes in the container folder are to be
           discarded."
    ::= { mgtfirmwareUpdatesGroup 1}

firmwareUpdateAuto OBJECT-TYPE
    SYNTAX      OnOffValue
    MAX-ACCESS  read-write
    STATUS      current
    DESCRIPTION
        "Enable automatic updates of installed media converter modules from firmware
         bundle on management module.."
    ::= { mgtfirmwareUpdatesGroup 2}

firmwareUpdateBundleVersionCm100	OBJECT-TYPE
    SYNTAX		DisplayString
    MAX-ACCESS	read-only
    STATUS		current
    DESCRIPTION
        "This object identifies the bundled firmware version for CM-100 modules."
    ::= { mgtfirmwareUpdatesGroup 3 }

firmwareUpdateBundleVersionCm110	OBJECT-TYPE
    SYNTAX		DisplayString
    MAX-ACCESS	read-only
    STATUS		current
    DESCRIPTION
        "This object identifies the bundled firmware version for CM-110 modules."
    ::= { mgtfirmwareUpdatesGroup 4 }

firmwareUpdateBundleVersionCm1000OrCm1000Sfp	OBJECT-TYPE
    SYNTAX		DisplayString
    MAX-ACCESS	read-only
    STATUS		current
    DESCRIPTION
        "This object identifies the bundled firmware version for CM-1000 or CM-1000-SFP modules."
    ::= { mgtfirmwareUpdatesGroup 5 }

firmwareUpdateBundleVersionCm1110	OBJECT-TYPE
    SYNTAX		DisplayString
    MAX-ACCESS	read-only
    STATUS		current
    DESCRIPTION
        "This object identifies the bundled firmware version for CM-1110 modules."
    ::= { mgtfirmwareUpdatesGroup 6 }

firmwareUpdateBundleVersionCm1110Sfp	OBJECT-TYPE
    SYNTAX		DisplayString
    MAX-ACCESS	read-only
    STATUS		current
    DESCRIPTION
        "This object identifies the bundled firmware version for CM-1110-SFP modules."
    ::= { mgtfirmwareUpdatesGroup 7 }

firmwareUpdateBundleVersionCm100mm	OBJECT-TYPE
    SYNTAX		DisplayString
    MAX-ACCESS	read-only
    STATUS		current
    DESCRIPTION
        "This object identifies the bundled firmware version for CM-100MM modules."
    ::= { mgtfirmwareUpdatesGroup 8 }

firmwareUpdateBundleVersionCm1000mm	OBJECT-TYPE
    SYNTAX		DisplayString
    MAX-ACCESS	read-only
    STATUS		current
    DESCRIPTION
        "This object identifies the bundled firmware version for CM-1000MM modules."
    ::= { mgtfirmwareUpdatesGroup 9 }

firmwareUpdateBundleVersionCm10g	OBJECT-TYPE
    SYNTAX		DisplayString
    MAX-ACCESS	read-only
    STATUS		current
    DESCRIPTION
        "This object identifies the bundled firmware version for CM-10G modules."
    ::= { mgtfirmwareUpdatesGroup 10 }

--
-- end of mgtfirmwareUpdatesGroup
--

--------------------------------------------------------------------------------
-- nettxfrTable
--
nettxfrTable  OBJECT-TYPE
    SYNTAX      SEQUENCE OF NettxfrEntry
    MAX-ACCESS  not-accessible
    STATUS      current
    DESCRIPTION
        "Table of snmp file transfer sessions."
    ::= { mgtFilesGroup 3 }

nettxfrEntry OBJECT-TYPE
    SYNTAX      NettxfrEntry
    MAX-ACCESS  not-accessible
    STATUS      current
    DESCRIPTION
        "Entries of the table, each relating to a SNMP file transfer session. "
    INDEX   { nettxfrSessionID }
    ::= { nettxfrTable 1 }

    NettxfrEntry ::=
        SEQUENCE {
            nettxfrSessionID		Unsigned32,
            nettxfrStatus   		INTEGER,
            nettxfrDirection		INTEGER,
            nettxfrFileType 		INTEGER,
            nettxfrFileHost   	DisplayString,
            nettxfrFileName   	DisplayString,
            nettxfrMCSlotNumber  	SlotNumber,
            nettxfrUserName   	DisplayString,
            nettxfrSSHKeyType    INTEGER,
            nettxfrSSLType    	INTEGER,
            nettxfrSessionInUse	INTEGER,
            nettxfrTftpPort 		Unsigned32
        }


    nettxfrSessionID	OBJECT-TYPE
        SYNTAX      Unsigned32
        MAX-ACCESS  not-accessible
        STATUS      current
        DESCRIPTION
            "This indicates if the net transfer is to be loaded to the management
            module or saved from the management module."
        ::= { nettxfrEntry 1}

    nettxfrStatus OBJECT-TYPE
        SYNTAX      INTEGER {
            fileNotFound(-3),
            busy(-2),
            error(-1),
            idle(0),
            start(1),
            transferringFile(2),
            erassingFlash(3),
            programmingFlash(4),
            verifyingFlash(5),
            moduleReset(6),
            processingScriptFile(7),
            finished(8)
        }
        MAX-ACCESS  read-write
        STATUS      current
        DESCRIPTION
            "This field indicates the status of the nettxfr process.
            A value of start(1) should be written to this field to start the nettxfr
            process with the specified parameters in the rest of this group."
        ::= { nettxfrEntry 2}

    nettxfrDirection	OBJECT-TYPE
        SYNTAX      INTEGER  {
            load(0),
            save(1)
        }
        MAX-ACCESS  read-write
        STATUS      current
        DESCRIPTION
            "This indicates if the net transfer is to be loaded to the management
            module or saved from the management module."
        ::= { nettxfrEntry 3}

    nettxfrFileType OBJECT-TYPE
        SYNTAX      INTEGER  {
            configuration(0),
            firmware(1),
            media-converter(2),
            script(3),
            serialt-buf(4),
            ssh-server(5),
            ssl(6),
            text-config(7),
            diagnostic-file(8),
            sntp-keys(9)
        }
        MAX-ACCESS  read-write
        STATUS      current
        DESCRIPTION
            "This indicates the type of file to be transfered to/from the management module."
        ::= { nettxfrEntry 4}

    nettxfrFileHost OBJECT-TYPE
        SYNTAX      DisplayString(SIZE(0..46))
        MAX-ACCESS  read-write
        STATUS      current
        DESCRIPTION
            "The host name or IP address of the server that contains the file to be
            transfered to/from the management module..
            If you use a host name, it must exist in the management module's host table
            or be resolved by DNS."
        ::= { nettxfrEntry 5}

    nettxfrFileName OBJECT-TYPE
        SYNTAX      DisplayString(SIZE(0..64))
        MAX-ACCESS  read-write
        STATUS   	   current
        DESCRIPTION
            "The path and file name (do not use a drive letter), relative to the default
            path of your TFTP server software, of the file to be transfered to/from the
            management module."
        ::= { nettxfrEntry 6}

    nettxfrMCSlotNumber OBJECT-TYPE
        SYNTAX      SlotNumber
        MAX-ACCESS  read-write
        STATUS      current
        DESCRIPTION
            "Specifies the slot number of the Media Converter Module to which the
            firmware will be transfered."
        ::= { nettxfrEntry 7}

    nettxfrUserName OBJECT-TYPE
        SYNTAX      DisplayString(SIZE(0..64))
        MAX-ACCESS  read-write
        STATUS      current
        DESCRIPTION
            "Specifies the user login name who owns the ssh public key that is to
            be transfered to the management module."
        ::= { nettxfrEntry 8}

    nettxfrSSHKeyType OBJECT-TYPE
        SYNTAX      INTEGER  {
            dsa(0),
            rsa(1)
        }
        MAX-ACCESS  read-write
        STATUS      current
        DESCRIPTION
            "Specifies the authentication method used by the ssh-server public key
            that is to be transfered  to/from the management module"
        ::= { nettxfrEntry 9}

    nettxfrSSLType OBJECT-TYPE
        SYNTAX      INTEGER  {
            ca-list(0),
            certificate(1),
            private-key(2)
        }
        MAX-ACCESS  read-write
        STATUS      current
        DESCRIPTION
            "Specifies the type of SSL file to be transfered to the management module.
            These files are needed if you are using the secure version of the
            WebManager (HTTPS), or LDAP authentication with TLS."
        ::= { nettxfrEntry 10}

    nettxfrSessionInUse OBJECT-TYPE
        SYNTAX      	INTEGER  {
            idle(0),
            in-use(1)
        }
        MAX-ACCESS  read-write
        STATUS      current
        DESCRIPTION
            "Specifies whether this net transfer session entry is in use. If a
            manager tries to write a 1 to this field and the session is already
            in use, then an error is returned."
        ::= { nettxfrEntry 11}

    nettxfrTftpPort OBJECT-TYPE
        SYNTAX      Unsigned32(1..65536)
        MAX-ACCESS  read-write
        STATUS      current
        DESCRIPTION
            "Specifies a UDP port number for the TFTP host server.
            Default is 69. "
        ::= { nettxfrEntry 12}

-- end of nettxfrTable
--------------------------------------------------------------------------------


--
-- mgtAdminGroup
--
adminFunction OBJECT-TYPE
    SYNTAX INTEGER {
      writeToFlash(1),
      resetToFactoryDefaults(2),
      reboot(3),
      resetSecurIDNodeSecret(4)
    }
    MAX-ACCESS read-write
    STATUS current
    DESCRIPTION
            "Perform a specific function on the management module.
             If you want to save all the changes that have been
             submitted to the management module, you need to expand
             the adminGroup container folder and SET the adminFunction
             to 1 to write to FLASH. To make the configuration
             changes take effect, SET the adminFunction to 3 to
             reboot the management module."
    ::= {mgtAdminGroup  1 }

adminLastFunction OBJECT-TYPE
    SYNTAX INTEGER {
      writeToFlash(1),
      resetToFactoryDefaults(2),
      reboot(3),
      resetSecurIDNodeSecret(4)
    }
    MAX-ACCESS read-only
    STATUS current
    DESCRIPTION
            "The last function requested"
    ::= {mgtAdminGroup  2 }

adminStatus OBJECT-TYPE
    SYNTAX INTEGER {
      successful(0),
      error(1),
      inProgress(2)
    }
    MAX-ACCESS read-only
    STATUS current
    DESCRIPTION
            "The status of the last function performed."
    ::= {mgtAdminGroup  3 }

adminbootReason	OBJECT-TYPE
    SYNTAX BITS {
      bootCrash(29),
      bootWarmStart(30),
      bootNormal(31)
    }
    MAX-ACCESS read-only
    STATUS current
    DESCRIPTION
        "The reason(s) why the management module last rebooted."
    ::= { mgtAdminGroup  4 }

adminDiagFileAvailable	OBJECT-TYPE
    SYNTAX YesNoValue
    MAX-ACCESS read-only
    STATUS current
    DESCRIPTION
        "This object indicates that a diagnostic file is available. "
    ::= { mgtAdminGroup  5 }

-- end of mgtAdminGroup
--

--
-- mgtDisplayFormatGroup
--
displayFormatStatus OBJECT-TYPE
    SYNTAX      ContainerStatus
    MAX-ACCESS  read-write
    STATUS      current
    DESCRIPTION
        "When you perform a GET on this variable, one of
         the following values will be returned:
         1-Indicates that the container folder is active with no changes.
         2-Indicates that the container folder is active with change(s).
           Once you have completed setting the variables in a folder, you
           will want to submit your changes to the management module. To do
           this, set the Status variable to 4. If you want to discard the
           changes, set the Status variable to 6.
         4-Indicates that the changes in the container folder are to be
           submitted to the management module and verified. To save the
           changes to flash a write of writeToFlash(1) in the adminFunction
           object is required.
         6-Indicates that the changes in the container folder are to be
           discarded."
    ::= { mgtDisplayFormatGroup 1}

cfgTemperatureUnits	OBJECT-TYPE
    SYNTAX INTEGER {
      celsius(0),
      fahrenheit(1)
    }
    MAX-ACCESS read-write
    STATUS current
    DESCRIPTION
        "This object identifies the units to display any internally measured
         temperature. The units can be Celsius or Fahrenheit."
    ::= { mgtDisplayFormatGroup  2 }

cfgSfpPowerUnits	OBJECT-TYPE
    SYNTAX INTEGER {
      milliwats(0),
      decibelmilliwatts(1)
    }
    MAX-ACCESS read-write
    STATUS current
    DESCRIPTION
        "This object identifies the units to display any SFP DMI internally
         measured transmit/receive power. The units can be milliwatts (mW) or
         Decibel milliwatts (dBm)."
    ::= { mgtDisplayFormatGroup  3 }

cfgTimeFormat	OBJECT-TYPE
    SYNTAX INTEGER {
      time12HourFmt(0),
      time24HourFmt(1)
    }
    MAX-ACCESS read-write
    STATUS current
    DESCRIPTION
        "This object identifies the format to display the time."
    ::= { mgtDisplayFormatGroup  4 }

cfgDateFormat	OBJECT-TYPE
    SYNTAX INTEGER {
        dateMonthDayYearFmt(0),
        dateDayMonthYearFmt(1),
        dateYearMonthDayFmt(2)
    }
    MAX-ACCESS read-write
    STATUS current
    DESCRIPTION
        "This object identifies the format to display date."
    ::= { mgtDisplayFormatGroup  5 }

--
-- end of mgtDisplayFormatGroup
--

--
-- mgtChassisCfgGroup
--

--
-- mgtChassisSlotPowerScheduleTable
--
mgtChassisSlotPowerScheduleTable OBJECT-TYPE
    SYNTAX		SEQUENCE OF MgtChassisSlotPowerScheduleEntry
    MAX-ACCESS	not-accessible
    STATUS		current
    DESCRIPTION
        "Table of power schedule configuration for chassis slots.
         (Not applicable to 2-slot chassis.)"
    ::= { mgtChassisCfgGroup 1 }

    mgtChassisSlotPowerScheduleEntry OBJECT-TYPE
        SYNTAX      MgtChassisSlotPowerScheduleEntry
        MAX-ACCESS  not-accessible
        STATUS      current
        DESCRIPTION
            "Entries of the table, each relating to a separate slot in a chassis."
        INDEX   { mcrChassisIndex, powerSchedSlotIndex, powerSchedDayOfWeek }
        ::= { mgtChassisSlotPowerScheduleTable 1 }

    MgtChassisSlotPowerScheduleEntry ::=
        SEQUENCE {
            powerSchedSlotIndex		SlotNumber,
            powerSchedDayOfWeek		INTEGER,
            powerSchedConifgStatus	ContainerStatus,
            powerSchedOnHour			INTEGER,
            powerSchedOnMinute		INTEGER,
            powerSchedOffHour			INTEGER,
            powerSchedOffMinute		INTEGER
        }

    powerSchedSlotIndex	OBJECT-TYPE
        SYNTAX		SlotNumber
        MAX-ACCESS	not-accessible
        STATUS		current
        DESCRIPTION
            "This object identifies the chassis slot number."
        ::= { mgtChassisSlotPowerScheduleEntry 2 }


    powerSchedDayOfWeek	OBJECT-TYPE
        SYNTAX		INTEGER {
            sunday(1),
            monday(2),
            tuesday(3),
            wednesday(4),
            thursday(5),
            friday(6),
            saturday(7)
        }
        MAX-ACCESS	not-accessible
        STATUS		current
        DESCRIPTION
            "This object identifies the day of the week."
        ::= { mgtChassisSlotPowerScheduleEntry 3 }

    powerSchedConifgStatus OBJECT-TYPE
        SYNTAX      ContainerStatus
        MAX-ACCESS  read-write
        STATUS      current
        DESCRIPTION
            "When you perform a GET on this variable, one of
             the following values will be returned:
         1-Indicates that the container folder is active with no changes.
         2-Indicates that the container folder is active with change(s).
           Once you have completed setting the variables in a folder, you
           will want to submit your changes to the management module. To do
           this, set the Status variable to 4. If you want to discard the
           changes, set the Status variable to 6.
         4-Indicates that the changes in the container folder are to be
           submitted to the management module and verified. To save the
           changes to flash a write of writeToFlash(1) in the adminFunction
           object is required.
         6-Indicates that the changes in the container folder are to be
           discarded."
        ::= { mgtChassisSlotPowerScheduleEntry 4 }

    powerSchedOnHour	OBJECT-TYPE
        SYNTAX		INTEGER (0..23)
        MAX-ACCESS	read-write
        STATUS		current
        DESCRIPTION
            "This object identifies the hour (0-23) of the day to schedule a
             power on of the chassis slot"
        ::= { mgtChassisSlotPowerScheduleEntry 5 }

    powerSchedOnMinute	OBJECT-TYPE
        SYNTAX		INTEGER (0..59)
        MAX-ACCESS	read-write
        STATUS		current
        DESCRIPTION
            "This object identifies the minute (0-59) of the hour to schedule a
            power on of the chassis slot"
        ::= { mgtChassisSlotPowerScheduleEntry 6 }

    powerSchedOffHour	OBJECT-TYPE
        SYNTAX		INTEGER (0..23)
        MAX-ACCESS	read-write
        STATUS		current
        DESCRIPTION
            "This object identifies the hour (0-23) of the day to schedule a
             power off of the chassis slot"
        ::= { mgtChassisSlotPowerScheduleEntry 7 }

    powerSchedOffMinute	OBJECT-TYPE
        SYNTAX		INTEGER (0..59)
        MAX-ACCESS	read-write
        STATUS		current
        DESCRIPTION
            "This object identifies the minute (0-59) of the hour to schedule a
             power off of the chassis slot"
        ::= { mgtChassisSlotPowerScheduleEntry 8 }

--
-- end of mgtChassisSlotPowerScheduleTable
--


-- end of mgtChassisCfgGroup
--


--
-- end of mcrManagementGroup
--

--
-- end of mcrMIBObjects
--

--
-- mcrMGTMIBNotifications ***************************************
--
mcrMgtModuleInserted		NOTIFICATION-TYPE
    OBJECTS	{ eventSeverityLevel, mcrChassisIndex, mcrChassisSlotIndex,
                  mcrModuleModelName, mcrModuleSerialNumber}
    STATUS	current
    DESCRIPTION
        "Trap being sent indicates that a management module has been inserted int the chassis."
    ::= { mcrMGTMIBNotifications 1 }

mcrMgtSystemBoot	NOTIFICATION-TYPE
    OBJECTS	{ eventSeverityLevel, adminbootReason}
    STATUS	current
    DESCRIPTION
        "Trap being sent indicates that the management module's system firmware is
         being booted up and has completed system initialization. In some case this alert
         will indicate a cold start like a user resetting the management module or
         warm start if the module automatically resets because of a detected crash."
    ::= { mcrMGTMIBNotifications 2 }

mcrMgtReset	NOTIFICATION-TYPE
    OBJECTS	{ eventSeverityLevel}
    STATUS	current
    DESCRIPTION
        "Trap being sent indicates that the management module has been manually reset
         via the reset button or one of the managers."
    ::= { mcrMGTMIBNotifications 3 }

mcrMgtResetFactory	NOTIFICATION-TYPE
    OBJECTS	{ eventSeverityLevel}
    STATUS	current
    DESCRIPTION
        "Trap being sent indicates that the management module has been manually reset
         to factory by holding the reset button for 3 or more seconds, or one of the
         managers.  This means that any files downloaded to the management module will
         be erase and the management configuration file is reset back to the default
         configuration. "
    ::= { mcrMGTMIBNotifications 4 }

mcrMgtEtheLinkUp	 NOTIFICATION-TYPE
    OBJECTS { eventSeverityLevel }
    STATUS  current
    DESCRIPTION
        "Trap being sent indicates that the current link status of the Ethernet
         port on the management module is up. "
    ::= { mcrMGTMIBNotifications 5 }

mcrMgtEtheLinkDown		NOTIFICATION-TYPE
    OBJECTS	{ eventSeverityLevel }
    STATUS	current
    DESCRIPTION
        "Trap being sent indicates that the current link status of the Ethernet
         port on the management module is down."
    ::= { mcrMGTMIBNotifications 6 }

mcrMgtConMonDSRSigChg	NOTIFICATION-TYPE
    OBJECTS	{ eventSeverityLevel, mcrMgtConsoleDSR}
    STATUS	current
    DESCRIPTION
        "Trap being sent indicates that monitor console DSR is configured and the
         status of one of these signal has changed on the console port. "
    ::= { mcrMGTMIBNotifications 7 }

mcrMgtAuthFail	NOTIFICATION-TYPE
    OBJECTS	{ eventSeverityLevel, mgtAccessMethod, remoteMgtIpAddress }
    STATUS	current
    DESCRIPTION
        "Trap being sent indicates that a user failed authentication via Telnet, SSH,
         WebManager, SNMP or the serial console."
    ::= { mcrMGTMIBNotifications 8 }


mcrMgtAuthSuccess	NOTIFICATION-TYPE
    OBJECTS	{ eventSeverityLevel, mgtAccessMethod, remoteMgtIpAddress }
    STATUS	current
    DESCRIPTION
        "Trap being sent indicates that a user failed authentication via Telnet, SSH,
         WebManager or the serial console. "
    ::= { mcrMGTMIBNotifications 9 }


mcrMgtDateTimeChg	NOTIFICATION-TYPE
    OBJECTS	{ eventSeverityLevel, systemDateTimeAndOffset }
    STATUS	current
    DESCRIPTION
        "Trap being sent indicates that the system date and/or time has been changed. "
    ::= { mcrMGTMIBNotifications 10 }

mcrMgtSntpServFail	NOTIFICATION-TYPE
    OBJECTS	{ eventSeverityLevel, timeSntpHost1, timeSntpHost2 }
    STATUS	current
    DESCRIPTION
        "Trap being sent indicates that SNTP is configured and the management module can
         not communicate with the configured SNTP server. "
    ::= { mcrMGTMIBNotifications 11 }

mcrMgtSntpServRec	NOTIFICATION-TYPE
    OBJECTS	{ eventSeverityLevel, timeSntpHost1, timeSntpHost2 }
    STATUS	current
    DESCRIPTION
        "Trap being sent indicates that the SNTP is configured and the management module
         has recovered communications with the configured SNTP server."
    ::= { mcrMGTMIBNotifications 12 }

mcrMgtSnmpTrapHostFail	NOTIFICATION-TYPE
    OBJECTS	{ eventSeverityLevel, snmpTrapHostIndex, snmpTrapHostIpAddress }
    STATUS	current
    DESCRIPTION
        "Trap being sent indicates that SNMP traps is  and the management module
         can not communicate with the configured SNMP trap host. This trap will only be
         sent for SNMP trap hosts configured for 'Inform' type traps. "
    ::= { mcrMGTMIBNotifications 13 }

mcrMgtSnmpTrapHostRec		NOTIFICATION-TYPE
    OBJECTS	{ eventSeverityLevel, snmpTrapHostIndex, snmpTrapHostIpAddress }
    STATUS	current
    DESCRIPTION
        "Trap being sent indicates that SNMP traps is  and the management module
         has recovered communications with the configured SNMP trap host."
    ::= { mcrMGTMIBNotifications 14 }

mcrMgtEmailServFail	NOTIFICATION-TYPE
    OBJECTS	{ eventSeverityLevel, emailSMTPHost }
    STATUS	current
    DESCRIPTION
        "Trap being sent indicates that an alert email server is configured and the management
         module can not communicate with the configured email server. "
    ::= { mcrMGTMIBNotifications 15 }

mcrMgtEmailServRec		NOTIFICATION-TYPE
    OBJECTS	{ eventSeverityLevel, emailSMTPHost }
    STATUS	current
    DESCRIPTION
        "Trap being sent indicates that an alert email server is configured and the management
         module has recovered communications with the configured email server."
    ::= { mcrMGTMIBNotifications 16 }

mcrMgtConfSavedFlash	NOTIFICATION-TYPE
    OBJECTS	{ eventSeverityLevel }
    STATUS	current
    DESCRIPTION
        "Trap being sent indicates that the configuration has been saved to flash  on the
         management module. "
    ::= { mcrMGTMIBNotifications 17 }

mcrMgtIpAddrDynChg	NOTIFICATION-TYPE
    OBJECTS	{ eventSeverityLevel, networkIpAddress }
    STATUS	current
    DESCRIPTION
        "Trap being sent indicates that the system IP address has been dynamically
         changed. "
    ::= { mcrMGTMIBNotifications 18 }

mcrMgtTftpUploadFail	NOTIFICATION-TYPE
    OBJECTS	{ eventSeverityLevel, remoteTftpFileName, remoteTftpHost }
    STATUS	current
    DESCRIPTION
        "Trap being sent indicates that an attempt to transfer a file via TFTP, off the
         management module to a remote host has failed. "
    ::= { mcrMGTMIBNotifications 19 }

mcrMgtTftpUploadSuccess	NOTIFICATION-TYPE
    OBJECTS	{ eventSeverityLevel, remoteTftpFileName, remoteTftpHost }
    STATUS	current
    DESCRIPTION
        "Trap being sent indicates that an attempt to transfer a file via TFTP, off the
         management module to a remote host was successful. "
    ::= { mcrMGTMIBNotifications 20 }

mcrMgtTftpDownloadFail	NOTIFICATION-TYPE
    OBJECTS	{ eventSeverityLevel, remoteTftpFileName, remoteTftpHost }
    STATUS	current
    DESCRIPTION
        "Trap being sent indicates that an attempt to transfer a file via TFTP, from a
         remote host to the management module has failed."
    ::= { mcrMGTMIBNotifications 21 }

mcrMgtTftpDownloadSuccess NOTIFICATION-TYPE
    OBJECTS	{ eventSeverityLevel, remoteTftpFileName, remoteTftpHost }
    STATUS	current
    DESCRIPTION
        "Trap being sent indicates that an attempt to transfer a file via TFTP, from a
         remote host to the management module was successful. "
    ::= { mcrMGTMIBNotifications 22 }

mcrMgtChassisMismatch NOTIFICATION-TYPE
    OBJECTS	{ eventSeverityLevel  }
    STATUS	current
    DESCRIPTION
        "Trap being sent indicates that the management module has been inserted into a
         chassis that does not match it's Backup media converter module configuration. Backup media
         module configurations will be reset to factory default. "
    ::= { mcrMGTMIBNotifications 23 }

-- Possible future release
mcrChassisAdd	NOTIFICATION-TYPE
    OBJECTS	{ eventSeverityLevel, mcrChassisIndex, chassisModelName,
               chassisSerialNumber }
    STATUS	current
    DESCRIPTION
        "Trap being sent indicates that a new chassis as been added to the chain of chassis. "
    ::= { mcrMGTMIBNotifications 24 }

-- Possible future release
mcrChassisRemove	NOTIFICATION-TYPE
    OBJECTS	{ eventSeverityLevel, mcrChassisIndex }
    STATUS	current
    DESCRIPTION
        "Trap being sent indicates that that a chassis has been removed from the chain of
         chassis. "
    ::= { mcrMGTMIBNotifications 25 }

mcrChassisReset	NOTIFICATION-TYPE
    OBJECTS	{ eventSeverityLevel,  mcrChassisIndex }
    STATUS	current
    DESCRIPTION
        "Trap being sent indicates that the chassis back-plane has been manually reset by
         a user managing the unit. "
    ::= { mcrMGTMIBNotifications 26 }

mcrChassisTemperatureAlarm	NOTIFICATION-TYPE
    OBJECTS	{ eventSeverityLevel, cfgTemperatureUnits,  mcrChassisIndex,
               chassisTemperature, chassisCfgHighTempThreshold}
    STATUS	current
    DESCRIPTION
        "Trap being sent indicates that the chassis temperature has exceeded the configured
         high temperature threshold temperature. "
    ::= { mcrMGTMIBNotifications 27 }

mcrChassisTemperatureRecover	NOTIFICATION-TYPE
    OBJECTS	{ eventSeverityLevel, cfgTemperatureUnits,  mcrChassisIndex, chassisTemperature }
    STATUS	current
    DESCRIPTION
        "Trap being sent indicates that the chassis temperature has recovered back to
         normal operating temperature. "
    ::= { mcrMGTMIBNotifications 28 }

mcrChassisSlotPoweredOn	NOTIFICATION-TYPE
    OBJECTS	{ eventSeverityLevel, mcrChassisIndex, mcrChassisSlotIndex,
                  mcrModuleModelName, mcrModuleSerialNumber, mcrUserDefinedModuleName }
    STATUS	current
    DESCRIPTION
        "Trap being sent indicates that the chassis slot has been powered off either manually
         or through the configured chassis slot power schedule. "
    ::= { mcrMGTMIBNotifications 29 }

mcrChassisSlotPoweredOff	NOTIFICATION-TYPE
    OBJECTS	{ eventSeverityLevel, mcrChassisIndex, mcrChassisSlotIndex }
    STATUS	current
    DESCRIPTION
        "Trap being sent indicates that the chassis slot has been powered on either manually
         or through the configured chassis slot power schedule. "
    ::= { mcrMGTMIBNotifications 30 }

mcrChassisFail	NOTIFICATION-TYPE
    OBJECTS	{ eventSeverityLevel, mcrChassisIndex }
    STATUS	current
    DESCRIPTION
        "Trap being sent indicates that the management module has detected a failure
         condition in the chassis.  "
    ::= { mcrMGTMIBNotifications 31 }

mcrChassisOk	NOTIFICATION-TYPE
    OBJECTS	{ eventSeverityLevel, mcrChassisIndex }
    STATUS	current
    DESCRIPTION
        "Trap being sent indicates that the chassis has recovered from a failure
         and is now operating normally."
    ::= { mcrMGTMIBNotifications 32 }

mcrPsmuInserted	NOTIFICATION-TYPE
    OBJECTS	{ eventSeverityLevel, mcrChassisIndex, mcrPsmuIndex, mcrPsmuModelName }
    STATUS	current
    DESCRIPTION
        "Trap being sent indicates that a power supply has been inserted into the chassis."
    ::= { mcrMGTMIBNotifications 33 }

mcrPsmuRemoved	NOTIFICATION-TYPE
    OBJECTS	{ eventSeverityLevel,  mcrChassisIndex, mcrPsmuIndex }
    STATUS	current
    DESCRIPTION
        "Trap being sent indicates that a power supply's has been removed from the chassis."
    ::= { mcrMGTMIBNotifications 34 }

mcrPsmuPsuFail	NOTIFICATION-TYPE
    OBJECTS	{ eventSeverityLevel, mcrChassisIndex, mcrPsmuIndex, mcrPsmuPsuStatus }
    STATUS	current
    DESCRIPTION
        "Trap being sent indicates that the power supply has failed it's self-test
         diagnostics. "
    ::= { mcrMGTMIBNotifications 35 }

mcrPsmuPsuOk	NOTIFICATION-TYPE
    OBJECTS	{ eventSeverityLevel, mcrChassisIndex, mcrPsmuIndex }
    STATUS	current
    DESCRIPTION
        "Trap being sent indicates that the power supply has passed it's self-test
         diagnostics. "
    ::= { mcrMGTMIBNotifications 36 }

mcrPsmuPsuVoltageFail	NOTIFICATION-TYPE
    OBJECTS	{ eventSeverityLevel, mcrChassisIndex, mcrPsmuIndex }
    STATUS	current
    DESCRIPTION
        "Trap being sent indicates that the voltage being supplied by the indicated
         power supply is insufficient."
    ::= { mcrMGTMIBNotifications 37 }

mcrPsmuPsuVoltageOk	NOTIFICATION-TYPE
    OBJECTS	{ eventSeverityLevel, mcrChassisIndex, mcrPsmuIndex}
    STATUS	current
    DESCRIPTION
        "Trap being sent indicates that the voltage being supplied by the indicated
         power supply is now in the normal operating range."
    ::= { mcrMGTMIBNotifications 38 }


mcrPsmuFanFail	NOTIFICATION-TYPE
    OBJECTS	{ eventSeverityLevel, mcrChassisIndex, mcrPsmuIndex }
    STATUS	current
    DESCRIPTION
        "Trap being sent indicates that the fan has failed. "
    ::= { mcrMGTMIBNotifications 39 }

mcrPsmuFanOk	NOTIFICATION-TYPE
    OBJECTS	{ eventSeverityLevel, mcrChassisIndex, mcrPsmuIndex }
    STATUS	current
    DESCRIPTION
        "Trap being sent indicates that the fan currently operating normally. "
    ::= { mcrMGTMIBNotifications 40 }

-- currently not used
--	::= { mcrMGTMIBNotifications 41 }

mcrMediaInserted	NOTIFICATION-TYPE
    OBJECTS	{ eventSeverityLevel, mcrChassisIndex, mcrChassisSlotIndex,
                  mcrModuleModelName, mcrModuleSerialNumber, mcrUserDefinedModuleName }
    STATUS	current
    DESCRIPTION
        "Trap being sent indicates that a media converter module has been inserted into the chassis. "
    ::= { mcrMGTMIBNotifications 42 }

mcrMediaRemoved	NOTIFICATION-TYPE
    OBJECTS	{ eventSeverityLevel, mcrChassisIndex, mcrChassisSlotIndex,
                  mcrUserDefinedModuleName }
    STATUS	current
    DESCRIPTION
        "Trap being sent indicates that a media converter module has been removed  from the chassis. "
    ::= { mcrMGTMIBNotifications 43 }

mcrMediaReset	NOTIFICATION-TYPE
    OBJECTS	{ eventSeverityLevel, mcrChassisIndex, mcrChassisSlotIndex,
                  mcrUserDefinedModuleName }
    STATUS	current
    DESCRIPTION
        "Trap being sent indicates that the media converter module has been manually reset by a user
         managing the unit. "
    ::= { mcrMGTMIBNotifications 44 }

mcrMediaLostCommunication	NOTIFICATION-TYPE
    OBJECTS	{ eventSeverityLevel, mcrChassisIndex, mcrChassisSlotIndex,
                  mcrUserDefinedModuleName }
    STATUS	current
    DESCRIPTION
        "Trap being sent indicates that the management module can no longer communicate
         with the media converter module "
    ::= { mcrMGTMIBNotifications 45 }

mcrMediaRecovCommunication	NOTIFICATION-TYPE
    OBJECTS	{ eventSeverityLevel, mcrChassisIndex, mcrChassisSlotIndex,
                  mcrUserDefinedModuleName }
    STATUS	current
    DESCRIPTION
        "Trap being sent indicates that the management module recovered communication
         with a media converter module "
    ::= { mcrMGTMIBNotifications 46 }

mcrMediaFail	NOTIFICATION-TYPE
    OBJECTS	{ eventSeverityLevel, mcrChassisIndex, mcrChassisSlotIndex,
                  mcrUserDefinedModuleName, mcrModuleDiagStatus }
    STATUS	current
    DESCRIPTION
        "Trap being sent indicates that the media converter module has failed its self-test
         diagnostics "
    ::= { mcrMGTMIBNotifications 47 }

mcrMediaOk	NOTIFICATION-TYPE
    OBJECTS	{ eventSeverityLevel, mcrChassisIndex, mcrChassisSlotIndex,
                  mcrUserDefinedModuleName }
    STATUS	current
    DESCRIPTION
        "Trap being sent indicates that the media converter module has passed its self-test
         diagnostics "
    ::= { mcrMGTMIBNotifications 48 }

mcrMediaLinkUp	NOTIFICATION-TYPE
    OBJECTS	{ eventSeverityLevel, mcrChassisIndex, mcrChassisSlotIndex,
                  mcrUserDefinedModuleName, mcrMediaPortNum, mcrMediaPortDescr}
    STATUS	current
    DESCRIPTION
        "Trap being sent indicates that the current link status of the Fiber or Copper
         port on the media converter module is up."
    ::= { mcrMGTMIBNotifications 49 }

mcrMediaLinkDown	NOTIFICATION-TYPE
    OBJECTS	{ eventSeverityLevel, mcrChassisIndex, mcrChassisSlotIndex,
                  mcrUserDefinedModuleName, mcrMediaPortNum, mcrMediaPortDescr }
    STATUS	current
    DESCRIPTION
        "Trap being sent indicates that the current link status of the Fiber or Copper
         port on the media converter module is down. "
    ::= { mcrMGTMIBNotifications 50 }

mcrMediaConfUpdateFail	NOTIFICATION-TYPE
    OBJECTS	{ eventSeverityLevel, mcrChassisIndex, mcrChassisSlotIndex,
                  mcrUserDefinedModuleName }
    STATUS	current
    DESCRIPTION
        "Trap being sent indicates that the configuration update on the media converter module
         has failed."
    ::= { mcrMGTMIBNotifications 51 }

mcrMediaConfUpdateSuccess	NOTIFICATION-TYPE
    OBJECTS	{ eventSeverityLevel, mcrChassisIndex, mcrChassisSlotIndex,
                  mcrUserDefinedModuleName }
    STATUS	current
    DESCRIPTION
        "Trap being sent indicates that the configuration update on the media converter module
         was successful.  The media converter module configuration can be updated manually or automatically. "
    ::= { mcrMGTMIBNotifications 52 }

mcrMediaConfMismatch	NOTIFICATION-TYPE
    OBJECTS	{ eventSeverityLevel, mcrChassisIndex, mcrChassisSlotIndex,
                mcrUserDefinedModuleName, mcrModuleTypeInserted, mcrMediaBackedupModuleType, 
                mcrModuleSubTypeInserted,mcrMediaBackedupModuleSubType }
    STATUS	current
    DESCRIPTION
        "Trap being sent indicates that a chassis slot is configured with Backup/Restore
         and the media converter module type configured for the slot does not match the media converter module
         type inserted into the slot.  "
    ::= { mcrMGTMIBNotifications 53 }

mcrMediaConfMismatchResolv NOTIFICATION-TYPE
    OBJECTS	{ eventSeverityLevel, mcrChassisIndex, mcrChassisSlotIndex,
                mcrUserDefinedModuleName, mcrModuleTypeInserted, mcrMediaBackedupModuleType, 
                mcrModuleSubTypeInserted,mcrMediaBackedupModuleSubType }
    STATUS	current
    DESCRIPTION
        "Trap being sent indicates that a user has taken action to resolved media converter module
         configuration mismatch "
    ::= { mcrMGTMIBNotifications 54 }

mcrMediaFirmwareUpdateFail	NOTIFICATION-TYPE
    OBJECTS	{ eventSeverityLevel, mcrChassisIndex, mcrChassisSlotIndex,
                  mcrUserDefinedModuleName, mcrModuleModelName }
    STATUS	current
    DESCRIPTION
        "Trap being sent indicates that an attempt to update a media converter module's firmware has Failed. "
    ::= { mcrMGTMIBNotifications 55 }

mcrMediaFirmwareUpdateSuccess	NOTIFICATION-TYPE
    OBJECTS	{ eventSeverityLevel, mcrChassisIndex, mcrChassisSlotIndex,
                  mcrUserDefinedModuleName,  mcrModuleModelName }
    STATUS	current
    DESCRIPTION
        "Trap being sent indicates that an attempt to update a media converter module's firmware was successful. "
    ::= { mcrMGTMIBNotifications 56 }


mcrSfpInserted	NOTIFICATION-TYPE
    OBJECTS	{ eventSeverityLevel, mcrChassisIndex, mcrChassisSlotIndex,
                  mcrUserDefinedModuleName }
    STATUS	current
    DESCRIPTION
        "Trap being sent indicates that a SFP module has been inserted into a media converter module"
    ::= { mcrMGTMIBNotifications 57 }

mcrSfpRemoved	NOTIFICATION-TYPE
    OBJECTS	{ eventSeverityLevel, mcrChassisIndex, mcrChassisSlotIndex,
                  mcrUserDefinedModuleName }
    STATUS	current
    DESCRIPTION
        "Trap being sent indicates that a SFP module has been removed from a media converter module "
    ::= { mcrMGTMIBNotifications 58 }

mcrSfpHighTempWarn	NOTIFICATION-TYPE
    OBJECTS	{ eventSeverityLevel, cfgTemperatureUnits, mcrChassisIndex, mcrChassisSlotIndex,
                  mcrUserDefinedModuleName, sfpDmiRealTimeTemp, sfpDmiHighTempWarn, mcrMediaPortNum }
    STATUS	current
    DESCRIPTION
        "Trap being sent indicates that a SFP module's temperature has exceeded the high
         temperature warning threshold. "
    ::= { mcrMGTMIBNotifications 59 }

mcrSfpHighTempWarnRecov	NOTIFICATION-TYPE
    OBJECTS	{ eventSeverityLevel, cfgTemperatureUnits, mcrChassisIndex, mcrChassisSlotIndex,
                  mcrUserDefinedModuleName, sfpDmiRealTimeTemp, mcrMediaPortNum }
    STATUS	current
    DESCRIPTION
        "Trap being sent indicates that a SFP module's temperature has recovered to normal
         operating level. "
    ::= { mcrMGTMIBNotifications 60 }

mcrSfpHighTempAlarm	NOTIFICATION-TYPE
    OBJECTS	{ eventSeverityLevel, cfgTemperatureUnits, mcrChassisIndex, mcrChassisSlotIndex,
                  mcrUserDefinedModuleName, sfpDmiRealTimeTemp, sfpDmiHighTempAlarm, mcrMediaPortNum }
    STATUS	current
    DESCRIPTION
        "Trap being sent indicates that a SFP module's temperature has exceeded the high
         temperature alarm threshold. "
    ::= { mcrMGTMIBNotifications 61 }

mcrSfpHighTempAlarmRecov	NOTIFICATION-TYPE
    OBJECTS	{ eventSeverityLevel, cfgTemperatureUnits, mcrChassisIndex, mcrChassisSlotIndex,
                  mcrUserDefinedModuleName, sfpDmiRealTimeTemp, mcrMediaPortNum }
    STATUS	current
    DESCRIPTION
        "Trap being sent indicates that a SFP module's temperature has recovered to normal
         operating level. "
    ::= { mcrMGTMIBNotifications 62 }

mcrSfpLowTempWarn	NOTIFICATION-TYPE
    OBJECTS	{ eventSeverityLevel, cfgTemperatureUnits, mcrChassisIndex, mcrChassisSlotIndex,
                  mcrUserDefinedModuleName, sfpDmiRealTimeTemp, sfpDmiLowTempWarn, mcrMediaPortNum}
    STATUS	current
    DESCRIPTION
        "Trap being sent indicates that a SFP module's temperature has gone below the low
         temperature warning threshold. "
    ::= { mcrMGTMIBNotifications 63 }

mcrSfpLowTempWarnRecov	NOTIFICATION-TYPE
    OBJECTS	{ eventSeverityLevel, cfgTemperatureUnits, mcrChassisIndex, mcrChassisSlotIndex,
                  mcrUserDefinedModuleName, sfpDmiRealTimeTemp, mcrMediaPortNum }
    STATUS	current
    DESCRIPTION
        "Trap being sent indicates that a SFP module's temperature has recovered to normal
         operating level. "
    ::= { mcrMGTMIBNotifications 64 }

mcrSfpLowTempAlarm	NOTIFICATION-TYPE
    OBJECTS	{ eventSeverityLevel, cfgTemperatureUnits, mcrChassisIndex, mcrChassisSlotIndex,
                  mcrUserDefinedModuleName,sfpDmiRealTimeTemp, sfpDmiLowTempAlarm, mcrMediaPortNum }
    STATUS	current
    DESCRIPTION
        "Trap being sent indicates that a SFP module's temperature has gone below the low
         temperature alarm threshold. "
    ::= { mcrMGTMIBNotifications 65 }

mcrSfpLowTempAlarmRecov	NOTIFICATION-TYPE
    OBJECTS	{ eventSeverityLevel, cfgTemperatureUnits, mcrChassisIndex, mcrChassisSlotIndex,
                  mcrUserDefinedModuleName, sfpDmiRealTimeTemp, mcrMediaPortNum }
    STATUS	current
    DESCRIPTION
        "Trap being sent indicates that a SFP module's temperature has recovered to normal
         operating level. "
    ::= { mcrMGTMIBNotifications 66 }

mcrSfpHighVoltWarn	NOTIFICATION-TYPE
    OBJECTS	{ eventSeverityLevel, mcrChassisIndex, mcrChassisSlotIndex,
                  mcrUserDefinedModuleName, sfpDmiRealTimeVolt, sfpDmiHighVoltWarn, mcrMediaPortNum }
    STATUS	current
    DESCRIPTION
        "Trap being sent indicates that a SFP module's voltage has exceeded the high
         voltage warning threshold. "
    ::= { mcrMGTMIBNotifications 67 }

mcrSfpHighVoltWarnRecov	NOTIFICATION-TYPE
    OBJECTS	{ eventSeverityLevel, mcrChassisIndex, mcrChassisSlotIndex,
                  mcrUserDefinedModuleName, sfpDmiRealTimeVolt, mcrMediaPortNum }
    STATUS	current
    DESCRIPTION
        "Trap being sent indicates that a SFP module's voltage has recovered to normal
         operating level. "
    ::= { mcrMGTMIBNotifications 68 }

mcrSfpHighVoltAlarm	NOTIFICATION-TYPE
    OBJECTS	{ eventSeverityLevel, mcrChassisIndex, mcrChassisSlotIndex,
                  mcrUserDefinedModuleName, sfpDmiRealTimeVolt, sfpDmiHighVoltAlarm, mcrMediaPortNum }
    STATUS	current
    DESCRIPTION
        "Trap being sent indicates that a SFP module's voltage has exceeded the high
         voltage alarm threshold. "
    ::= { mcrMGTMIBNotifications 69 }

mcrSfpHighVoltAlarmRecov	NOTIFICATION-TYPE
    OBJECTS	{ eventSeverityLevel, mcrChassisIndex, mcrChassisSlotIndex,
                  mcrUserDefinedModuleName, sfpDmiRealTimeVolt, mcrMediaPortNum }
    STATUS	current
    DESCRIPTION
        "Trap being sent indicates that a SFP module's voltage has recovered to normal
         operating level. "
    ::= { mcrMGTMIBNotifications 70 }

mcrSfpLowVoltWarn	NOTIFICATION-TYPE
    OBJECTS	{ eventSeverityLevel, mcrChassisIndex, mcrChassisSlotIndex,
                  mcrUserDefinedModuleName, sfpDmiRealTimeVolt, sfpDmiLowVoltWarn, mcrMediaPortNum}
    STATUS	current
    DESCRIPTION
        "Trap being sent indicates that a SFP module's voltage has gone below the low
         voltage warning threshold. "
    ::= { mcrMGTMIBNotifications 71 }

mcrSfpLowVoltWarnRecov	NOTIFICATION-TYPE
    OBJECTS	{ eventSeverityLevel, mcrChassisIndex, mcrChassisSlotIndex,
                  mcrUserDefinedModuleName, sfpDmiRealTimeVolt, mcrMediaPortNum }
    STATUS	current
    DESCRIPTION
        "Trap being sent indicates that a SFP module's voltage has recovered to normal
         operating level. "
    ::= { mcrMGTMIBNotifications 72 }

mcrSfpLowVoltAlarm	NOTIFICATION-TYPE
    OBJECTS	{ eventSeverityLevel, mcrChassisIndex, mcrChassisSlotIndex,
                  mcrUserDefinedModuleName, sfpDmiRealTimeVolt, sfpDmiLowVoltAlarm, mcrMediaPortNum }
    STATUS	current
    DESCRIPTION
        "Trap being sent indicates that a SFP module's voltage has gone below the low
         voltage alarm threshold. "
    ::= { mcrMGTMIBNotifications 73 }

mcrSfpLowVoltAlarmRecov	NOTIFICATION-TYPE
    OBJECTS	{ eventSeverityLevel, mcrChassisIndex, mcrChassisSlotIndex,
                  mcrUserDefinedModuleName, sfpDmiRealTimeVolt, mcrMediaPortNum }
    STATUS	current
    DESCRIPTION
        "Trap being sent indicates that a SFP module's voltage has recovered to normal
         operating level. "
    ::= { mcrMGTMIBNotifications 74 }

mcrSfpHighTxBiasWarn	NOTIFICATION-TYPE
    OBJECTS	{ eventSeverityLevel, mcrChassisIndex, mcrChassisSlotIndex,
                  mcrUserDefinedModuleName, sfpDmiRealTimeTxBias, sfpDmiHighTxBiasWarn, mcrMediaPortNum }
    STATUS	current
    DESCRIPTION
        "Trap being sent indicates that a SFP module's TX Bias current has exceeded the high
         TX Bias current warning threshold. "
    ::= { mcrMGTMIBNotifications 75 }

mcrSfpHighTxBiasWarnRecov	NOTIFICATION-TYPE
    OBJECTS	{ eventSeverityLevel, mcrChassisIndex, mcrChassisSlotIndex,
                  mcrUserDefinedModuleName, sfpDmiRealTimeTxBias, mcrMediaPortNum }
    STATUS	current
    DESCRIPTION
        "Trap being sent indicates that a SFP module's TX Bias current has recovered to normal
         operating level. "
    ::= { mcrMGTMIBNotifications 76 }

mcrSfpHighTxBiasAlarm	NOTIFICATION-TYPE
    OBJECTS	{ eventSeverityLevel, mcrChassisIndex, mcrChassisSlotIndex,
                  mcrUserDefinedModuleName, sfpDmiRealTimeTxBias, sfpDmiHighTxBiasAlarm, mcrMediaPortNum }
    STATUS	current
    DESCRIPTION
        "Trap being sent indicates that a SFP module's TX Bias current has exceeded the high
         TX Bias current alarm threshold. "
    ::= { mcrMGTMIBNotifications 77 }

mcrSfpHighTxBiasAlarmRecov	NOTIFICATION-TYPE
    OBJECTS	{ eventSeverityLevel, mcrChassisIndex, mcrChassisSlotIndex,
                  mcrUserDefinedModuleName, sfpDmiRealTimeTxBias, mcrMediaPortNum }
    STATUS	current
    DESCRIPTION
        "Trap being sent indicates that a SFP module's TX Bias current has recovered to normal
         operating level. "
    ::= { mcrMGTMIBNotifications 78 }

mcrSfpLowTxBiasWarn	NOTIFICATION-TYPE
    OBJECTS	{ eventSeverityLevel, mcrChassisIndex, mcrChassisSlotIndex,
                  mcrUserDefinedModuleName, sfpDmiRealTimeTxBias, sfpDmiLowTxBiasWarn, mcrMediaPortNum }
    STATUS	current
    DESCRIPTION
        "Trap being sent indicates that a SFP module's TX Bias current has gone below the low
         Tx Bias current warning threshold. "
    ::= { mcrMGTMIBNotifications 79 }

mcrSfpLowTxBiasWarnRecov	NOTIFICATION-TYPE
    OBJECTS	{ eventSeverityLevel, mcrChassisIndex, mcrChassisSlotIndex,
                  mcrUserDefinedModuleName,   sfpDmiRealTimeTxBias, mcrMediaPortNum }
    STATUS	current
    DESCRIPTION
        "Trap being sent indicates that a SFP module's TX Bias current has recovered to normal
         operating level. "
    ::= { mcrMGTMIBNotifications 80 }

mcrSfpLowTxBiasAlarm	NOTIFICATION-TYPE
    OBJECTS	{ eventSeverityLevel, mcrChassisIndex, mcrChassisSlotIndex,
                  mcrUserDefinedModuleName, sfpDmiRealTimeTxBias, sfpDmiLowTxBiasAlarm, mcrMediaPortNum }
    STATUS	current
    DESCRIPTION
        "Trap being sent indicates that a SFP module's TX Bias current has gone below the low
         Tx Bias current alarm threshold. "
    ::= { mcrMGTMIBNotifications 81 }

mcrSfpLowTxBiasAlarmRecov	NOTIFICATION-TYPE
    OBJECTS	{ eventSeverityLevel, mcrChassisIndex, mcrChassisSlotIndex,
                  mcrUserDefinedModuleName,   sfpDmiRealTimeTxBias, mcrMediaPortNum }
    STATUS	current
    DESCRIPTION
        "Trap being sent indicates that a SFP module's TX Bias current has recovered to normal
         operating level. "
    ::= { mcrMGTMIBNotifications 82 }

mcrSfpHighTxPowerWarn	NOTIFICATION-TYPE
    OBJECTS	{ eventSeverityLevel, cfgSfpPowerUnits, mcrChassisIndex, mcrChassisSlotIndex,
                  mcrUserDefinedModuleName, sfpDmiRealTimeTxPower, sfpDmiHighTxPowerWarn, mcrMediaPortNum }
    STATUS	current
    DESCRIPTION
        "Trap being sent indicates that a SFP module's TX power has exceeded the high
         TX power warning threshold. "
    ::= { mcrMGTMIBNotifications 83 }

mcrSfpHighTxPowerWarnRecov	NOTIFICATION-TYPE
    OBJECTS	{ eventSeverityLevel, cfgSfpPowerUnits, mcrChassisIndex, mcrChassisSlotIndex,
                  mcrUserDefinedModuleName, sfpDmiRealTimeTxPower, mcrMediaPortNum }
    STATUS	current
    DESCRIPTION
        "Trap being sent indicates that a SFP module's TX power has recovered to normal
         operating level. "
    ::= { mcrMGTMIBNotifications 84 }

mcrSfpHighTxPowerAlarm	NOTIFICATION-TYPE
    OBJECTS	{ eventSeverityLevel, cfgSfpPowerUnits, mcrChassisIndex, mcrChassisSlotIndex,
                  mcrUserDefinedModuleName, sfpDmiRealTimeTxPower, sfpDmiHighTxPowerAlarm, mcrMediaPortNum }
    STATUS	current
    DESCRIPTION
        "Trap being sent indicates that a SFP module's TX power has exceeded the high
         TX power alarm threshold. "
    ::= { mcrMGTMIBNotifications 85 }

mcrSfpHighTxPowerAlarmRecov	NOTIFICATION-TYPE
    OBJECTS	{ eventSeverityLevel, cfgSfpPowerUnits, mcrChassisIndex, mcrChassisSlotIndex,
                  mcrUserDefinedModuleName, sfpDmiRealTimeTxPower, mcrMediaPortNum }
    STATUS	current
    DESCRIPTION
        "Trap being sent indicates that a SFP module's TX power has recovered to normal
         operating level. "
    ::= { mcrMGTMIBNotifications 86 }

mcrSfpLowTxPowerWarn	NOTIFICATION-TYPE
    OBJECTS	{ eventSeverityLevel, cfgSfpPowerUnits,mcrChassisIndex, mcrChassisSlotIndex,
                  mcrUserDefinedModuleName, sfpDmiRealTimeTxPower, sfpDmiLowTxPowerWarn, mcrMediaPortNum }
    STATUS	current
    DESCRIPTION
        "Trap being sent indicates that a SFP module's TX power has gone below the low
         TX power warning threshold. "
    ::= { mcrMGTMIBNotifications 87 }

mcrSfpLowTxPowerWarnRecov	NOTIFICATION-TYPE
    OBJECTS	{ eventSeverityLevel,cfgSfpPowerUnits, mcrChassisIndex, mcrChassisSlotIndex,
                  mcrUserDefinedModuleName, sfpDmiRealTimeTxPower, mcrMediaPortNum }
    STATUS	current
    DESCRIPTION
        "Trap being sent indicates that a SFP module's TX power has recovered to normal
         operating level. "
    ::= { mcrMGTMIBNotifications 88 }

mcrSfpLowTxPowerAlarm	NOTIFICATION-TYPE
    OBJECTS	{ eventSeverityLevel, cfgSfpPowerUnits, mcrChassisIndex, mcrChassisSlotIndex,
                  mcrUserDefinedModuleName,  sfpDmiRealTimeTxPower, sfpDmiLowTxPowerAlarm, mcrMediaPortNum }
    STATUS	current
    DESCRIPTION
        "Trap being sent indicates that a SFP module's TX power has gone below the low
         TX power alarm threshold. "
    ::= { mcrMGTMIBNotifications 89 }

mcrSfpLowTxPowerAlarmRecov	NOTIFICATION-TYPE
    OBJECTS	{ eventSeverityLevel,cfgSfpPowerUnits, mcrChassisIndex, mcrChassisSlotIndex,
                  mcrUserDefinedModuleName, sfpDmiRealTimeTxPower, mcrMediaPortNum }
    STATUS	current
    DESCRIPTION
        "Trap being sent indicates that a SFP module's TX power has recovered to normal
         operating level. "
    ::= { mcrMGTMIBNotifications 90 }

---*****************************************************************************

mcrSfpHighRxPowerWarn	NOTIFICATION-TYPE
    OBJECTS	{ eventSeverityLevel, cfgSfpPowerUnits, mcrChassisIndex, mcrChassisSlotIndex,
                  mcrUserDefinedModuleName, sfpDmiRealTimeRxPower, sfpDmiHighRxPowerWarn, mcrMediaPortNum }
    STATUS	current
    DESCRIPTION
        "Trap being sent indicates that a SFP module's RX power has exceeded the high
         RX power warning threshold. "
    ::= { mcrMGTMIBNotifications 91 }

mcrSfpHighRxPowerWarnRecov	NOTIFICATION-TYPE
    OBJECTS	{ eventSeverityLevel, cfgSfpPowerUnits, mcrChassisIndex, mcrChassisSlotIndex,
                  mcrUserDefinedModuleName, sfpDmiRealTimeRxPower, mcrMediaPortNum }
    STATUS	current
    DESCRIPTION
        "Trap being sent indicates that a SFP module's RX power has recovered to normal
         operating level. "
    ::= { mcrMGTMIBNotifications 92 }

mcrSfpHighRxPowerAlarm	NOTIFICATION-TYPE
    OBJECTS	{ eventSeverityLevel, cfgSfpPowerUnits, mcrChassisIndex, mcrChassisSlotIndex,
                  mcrUserDefinedModuleName, sfpDmiRealTimeRxPower, sfpDmiHighRxPowerAlarm, mcrMediaPortNum }
    STATUS	current
    DESCRIPTION
        "Trap being sent indicates that a SFP module's RX power has exceeded the high
         RX power alarm threshold. "
    ::= { mcrMGTMIBNotifications 93 }

mcrSfpHighRxPowerAlarmRecov	NOTIFICATION-TYPE
    OBJECTS	{ eventSeverityLevel, cfgSfpPowerUnits, mcrChassisIndex, mcrChassisSlotIndex,
                  mcrUserDefinedModuleName, sfpDmiRealTimeRxPower, mcrMediaPortNum }
    STATUS	current
    DESCRIPTION
        "Trap being sent indicates that a SFP module's RX power has recovered to normal
         operating level. "
    ::= { mcrMGTMIBNotifications 94 }

mcrSfpLowRxPowerWarn	NOTIFICATION-TYPE
    OBJECTS	{ eventSeverityLevel, cfgSfpPowerUnits, mcrChassisIndex, mcrChassisSlotIndex,
                  mcrUserDefinedModuleName, sfpDmiRealTimeRxPower, sfpDmiLowRxPowerWarn, mcrMediaPortNum }
    STATUS	current
    DESCRIPTION
        "Trap being sent indicates that a SFP module's RX power has gone below the low
         RX power warning threshold. "
    ::= { mcrMGTMIBNotifications 95 }

mcrSfpLowRxPowerWarnRecov	NOTIFICATION-TYPE
    OBJECTS	{ eventSeverityLevel, cfgSfpPowerUnits, mcrChassisIndex, mcrChassisSlotIndex,
                  mcrUserDefinedModuleName,  sfpDmiRealTimeRxPower, mcrMediaPortNum}
    STATUS	current
    DESCRIPTION
        "Trap being sent indicates that a SFP module's RX power has recovered to normal
         operating level. "
    ::= { mcrMGTMIBNotifications 96 }
--
mcrSfpLowRxPowerAlarm	NOTIFICATION-TYPE
    OBJECTS	{ eventSeverityLevel, cfgSfpPowerUnits, mcrChassisIndex, mcrChassisSlotIndex,
                  mcrUserDefinedModuleName, sfpDmiRealTimeRxPower, sfpDmiLowRxPowerAlarm, mcrMediaPortNum}
    STATUS	current
    DESCRIPTION
        "Trap being sent indicates that a SFP module's RX power has gone below the low
         RX power alarm threshold. "
    ::= { mcrMGTMIBNotifications 97 }

mcrSfpLowRxPowerAlarmRecov	NOTIFICATION-TYPE
    OBJECTS	{ eventSeverityLevel, cfgSfpPowerUnits, mcrChassisIndex, mcrChassisSlotIndex,
                  mcrUserDefinedModuleName,  sfpDmiRealTimeRxPower, mcrMediaPortNum}
    STATUS	current
    DESCRIPTION
        "Trap being sent indicates that a SFP module's RX power has recovered to normal
         operating level. "
    ::= { mcrMGTMIBNotifications 98 }

---*****************************************************************************

mcrChassisCommTempSensorFail	NOTIFICATION-TYPE
    OBJECTS	{ eventSeverityLevel, mcrChassisIndex}
    STATUS	current
    DESCRIPTION
        "Trap being sent indicates that communication with the chassis temperature
         sensor has failed. The current chassis temperature reading will be unknown"
    ::= { mcrMGTMIBNotifications 99 }

mcrChassisCommTempSensorRecov	NOTIFICATION-TYPE
    OBJECTS	{ eventSeverityLevel, mcrChassisIndex}
    STATUS	current
    DESCRIPTION
        "Trap being sent indicates that communication with the chassis temperature
         sensor has recovered."
    ::= { mcrMGTMIBNotifications 100 }


mcrMediaDetectFail	NOTIFICATION-TYPE
    OBJECTS	{ eventSeverityLevel, mcrChassisIndex, mcrChassisSlotIndex,mcrUserDefinedModuleName }
    STATUS	current
    DESCRIPTION
        "Trap being sent indicates that the indicated media card is being powered
         down due to the detection of a hardware failure."
    ::= { mcrMGTMIBNotifications 101 }

mcrMediaBadImage	NOTIFICATION-TYPE
    OBJECTS	{ eventSeverityLevel, mcrChassisIndex, mcrChassisSlotIndex, mcrUserDefinedModuleName }
    STATUS	current
    DESCRIPTION
        "Trap being sent indicates that the CRC of the media converter module firmware is
         incorrect. This can be caused if there is no image on the module or the
         image is corrupt."
    ::= { mcrMGTMIBNotifications  102 }

mcrSfpLostComm	NOTIFICATION-TYPE
    OBJECTS	{ eventSeverityLevel, mcrChassisIndex, mcrChassisSlotIndex, mcrUserDefinedModuleName }
    STATUS	current
    DESCRIPTION
        "Trap being sent indicates that the media converter module's microcode can no longer
         communicate with the SFP module."
    ::= { mcrMGTMIBNotifications 103 }

mcrSfpRecovComm	NOTIFICATION-TYPE
    OBJECTS	{ eventSeverityLevel, mcrChassisIndex, mcrChassisSlotIndex, mcrUserDefinedModuleName}
    STATUS	current
    DESCRIPTION
        "Trap being sent indicates that the media converter module's microcode had previously
         lost communication with, but has now regained communication with the SFP
         module."
    ::= { mcrMGTMIBNotifications  104 }


mcrModuleNotSupported	NOTIFICATION-TYPE
    OBJECTS	{ eventSeverityLevel, mcrChassisIndex, mcrChassisSlotIndex, mcrUserDefinedModuleName}
    STATUS	current
    DESCRIPTION
        "Trap being sent indicates that the media converter module is not fully supported by
         the management module. Update the management module firmware to rectify
         this issue."
    ::= { mcrMGTMIBNotifications  105 }

mcrModuleFirmwareUpdate	NOTIFICATION-TYPE
    OBJECTS	{ eventSeverityLevel, mcrChassisIndex, mcrChassisSlotIndex, mcrUserDefinedModuleName}
    STATUS	current
    DESCRIPTION
        "Trap being sent indicates that the media converter module firmware is being updated."
    ::= { mcrMGTMIBNotifications  106 }

--- ****************************************************************************

mcrSfpPortShutdown	NOTIFICATION-TYPE
    OBJECTS	{ eventSeverityLevel, mcrChassisIndex, mcrChassisSlotIndex, mcrUserDefinedModuleName, mcrMediaPortNum}
    STATUS	current
    DESCRIPTION
        "Trap being sent indicates that the Sfp/Xfp port has been shutdown due to
        high temperature."
    ::= { mcrMGTMIBNotifications  107 }

mcrSfpPortShutdownRecov	NOTIFICATION-TYPE
    OBJECTS	{ eventSeverityLevel, mcrChassisIndex, mcrChassisSlotIndex, mcrUserDefinedModuleName, mcrMediaPortNum}
    STATUS	current
    DESCRIPTION
        "Trap being sent indicates that the Sfp/Xfp port shutdown has recovered."
    ::= { mcrMGTMIBNotifications  108 }

--- ****************************************************************************

mcrXfpHighApdBiasWarn	NOTIFICATION-TYPE
    OBJECTS	{ eventSeverityLevel, mcrChassisIndex, mcrChassisSlotIndex,
                  mcrUserDefinedModuleName, xfpDmiRealTimeAux, xfpDmiHighAuxWarn, mcrMediaPortNum }
    STATUS	current
    DESCRIPTION
        "Trap being sent indicates that an XFP module's APD Bias Current has 
        exceeded the high APD Bias warning threshold. "
    ::= { mcrMGTMIBNotifications 109 }

mcrXfpHighApdBiasWarnRecov	NOTIFICATION-TYPE
    OBJECTS	{ eventSeverityLevel, mcrChassisIndex, mcrChassisSlotIndex,
                  mcrUserDefinedModuleName, xfpDmiRealTimeAux, mcrMediaPortNum }
    STATUS	current
    DESCRIPTION
        "Trap being sent indicates that an XFP module's APD Bias Current has 
        recovered to normal operating level."
    ::= { mcrMGTMIBNotifications 110 }

mcrXfpHighApdBiasAlarm	NOTIFICATION-TYPE
    OBJECTS	{ eventSeverityLevel, mcrChassisIndex, mcrChassisSlotIndex,
                  mcrUserDefinedModuleName, xfpDmiRealTimeAux, xfpDmiHighAuxAlarm, mcrMediaPortNum }
    STATUS	current
    DESCRIPTION
        "Trap being sent indicates that an XFP module's APD Bias Current has 
        exceeded the high APD Bias alarm threshold. "
    ::= { mcrMGTMIBNotifications 111 }

mcrXfpHighApdBiasAlarmRecov	NOTIFICATION-TYPE
    OBJECTS	{ eventSeverityLevel, mcrChassisIndex, mcrChassisSlotIndex,
                  mcrUserDefinedModuleName, xfpDmiRealTimeAux, mcrMediaPortNum }
    STATUS	current
    DESCRIPTION
        "Trap being sent indicates that an XFP module's APD Bias Current has 
        recovered to normal operating level. "
    ::= { mcrMGTMIBNotifications 112 }

mcrXfpLowApdBiasWarn	NOTIFICATION-TYPE
    OBJECTS	{ eventSeverityLevel, mcrChassisIndex, mcrChassisSlotIndex,
                  mcrUserDefinedModuleName, xfpDmiRealTimeAux, xfpDmiLowAuxWarn, mcrMediaPortNum }
    STATUS	current
    DESCRIPTION
        "Trap being sent indicates that an XFP module's APD Bias Current has gone 
        below the low APD Bias warning threshold. "
    ::= { mcrMGTMIBNotifications 113 }

mcrXfpLowApdBiasWarnRecov	NOTIFICATION-TYPE
    OBJECTS	{ eventSeverityLevel, mcrChassisIndex, mcrChassisSlotIndex,
                  mcrUserDefinedModuleName,  xfpDmiRealTimeAux, mcrMediaPortNum}
    STATUS	current
    DESCRIPTION
        "Trap being sent indicates that an XFP module's APD Bias Current has 
        recovered to normal operating level. "
    ::= { mcrMGTMIBNotifications 114 }
--
mcrXfpLowApdBiasAlarm	NOTIFICATION-TYPE
    OBJECTS	{ eventSeverityLevel, mcrChassisIndex, mcrChassisSlotIndex,
                  mcrUserDefinedModuleName, xfpDmiRealTimeAux, xfpDmiLowAuxAlarm, mcrMediaPortNum}
    STATUS	current
    DESCRIPTION
        "Trap being sent indicates that an XFP module's APD Bias Current has gone 
        below the low APD Bias alarm threshold. "
    ::= { mcrMGTMIBNotifications 115}

mcrXfpLowApdBiasAlarmRecov	NOTIFICATION-TYPE
    OBJECTS	{ eventSeverityLevel, mcrChassisIndex, mcrChassisSlotIndex,
                  mcrUserDefinedModuleName,  xfpDmiRealTimeAux, mcrMediaPortNum}
    STATUS	current
    DESCRIPTION
        "Trap being sent indicates that an XFP module's APD Bias Current has 
        recovered to normal operating level. "
    ::= { mcrMGTMIBNotifications 116 }

--- ****************************************************************************

mcrXfpHighTecCurrentWarn	NOTIFICATION-TYPE
    OBJECTS	{ eventSeverityLevel, mcrChassisIndex, mcrChassisSlotIndex,
                  mcrUserDefinedModuleName, xfpDmiRealTimeAux, xfpDmiHighAuxWarn, mcrMediaPortNum }
    STATUS	current
    DESCRIPTION
        "Trap being sent indicates that an XFP module's TEC Current has 
        exceeded the high TEC Current warning threshold. "
    ::= { mcrMGTMIBNotifications 117 }

mcrXfpHighTecCurrentWarnRecov	NOTIFICATION-TYPE
    OBJECTS	{ eventSeverityLevel, mcrChassisIndex, mcrChassisSlotIndex,
                  mcrUserDefinedModuleName, xfpDmiRealTimeAux, mcrMediaPortNum }
    STATUS	current
    DESCRIPTION
        "Trap being sent indicates that an XFP module's TEC Current has 
        recovered to normal operating level."
    ::= { mcrMGTMIBNotifications 118 }

mcrXfpHighTecCurrentAlarm	NOTIFICATION-TYPE
    OBJECTS	{ eventSeverityLevel, mcrChassisIndex, mcrChassisSlotIndex,
                  mcrUserDefinedModuleName, xfpDmiRealTimeAux, xfpDmiHighAuxAlarm, mcrMediaPortNum }
    STATUS	current
    DESCRIPTION
        "Trap being sent indicates that an XFP module's TEC Current has 
        exceeded the high TEC Current alarm threshold. "
    ::= { mcrMGTMIBNotifications 119 }

mcrXfpHighTecCurrentAlarmRecov	NOTIFICATION-TYPE
    OBJECTS	{ eventSeverityLevel, mcrChassisIndex, mcrChassisSlotIndex,
                  mcrUserDefinedModuleName, xfpDmiRealTimeAux, mcrMediaPortNum }
    STATUS	current
    DESCRIPTION
        "Trap being sent indicates that an XFP module's TEC Current has 
        recovered to normal operating level. "
    ::= { mcrMGTMIBNotifications 120 }

mcrXfpLowTecCurrentWarn	NOTIFICATION-TYPE
    OBJECTS	{ eventSeverityLevel, mcrChassisIndex, mcrChassisSlotIndex,
                  mcrUserDefinedModuleName, xfpDmiRealTimeAux, xfpDmiLowAuxWarn, mcrMediaPortNum }
    STATUS	current
    DESCRIPTION
        "Trap being sent indicates that an XFP module's TEC Current has gone 
        below the low TEC Current warning threshold. "
    ::= { mcrMGTMIBNotifications 121 }

mcrXfpLowTecCurrentWarnRecov	NOTIFICATION-TYPE
    OBJECTS	{ eventSeverityLevel, mcrChassisIndex, mcrChassisSlotIndex,
                  mcrUserDefinedModuleName,  xfpDmiRealTimeAux, mcrMediaPortNum}
    STATUS	current
    DESCRIPTION
        "Trap being sent indicates that an XFP module's TEC Current has 
        recovered to normal operating level. "
    ::= { mcrMGTMIBNotifications 122 }
--
mcrXfpLowTecCurrentAlarm	NOTIFICATION-TYPE
    OBJECTS	{ eventSeverityLevel, mcrChassisIndex, mcrChassisSlotIndex,
                  mcrUserDefinedModuleName, xfpDmiRealTimeAux, xfpDmiLowAuxAlarm, mcrMediaPortNum}
    STATUS	current
    DESCRIPTION
        "Trap being sent indicates that an XFP module's TEC Current has gone 
        below the low TEC Current alarm threshold. "
    ::= { mcrMGTMIBNotifications 123}

mcrXfpLowTecCurrentAlarmRecov	NOTIFICATION-TYPE
    OBJECTS	{ eventSeverityLevel, mcrChassisIndex, mcrChassisSlotIndex,
                  mcrUserDefinedModuleName,  xfpDmiRealTimeAux, mcrMediaPortNum}
    STATUS	current
    DESCRIPTION
        "Trap being sent indicates that an XFP module's TEC Current has 
        recovered to normal operating level. "
    ::= { mcrMGTMIBNotifications 124 }

--- ****************************************************************************

mcrXfpHighLaserTempWarn	NOTIFICATION-TYPE
    OBJECTS	{ eventSeverityLevel, cfgTemperatureUnits, mcrChassisIndex, mcrChassisSlotIndex,
                  mcrUserDefinedModuleName, xfpDmiRealTimeAux, xfpDmiHighAuxWarn, mcrMediaPortNum }
    STATUS	current
    DESCRIPTION
        "Trap being sent indicates that an XFP module's Laser Temperature has 
        exceeded the high Laser Temperature warning threshold. "
    ::= { mcrMGTMIBNotifications 125 }

mcrXfpHighLaserTempWarnRecov	NOTIFICATION-TYPE
    OBJECTS	{ eventSeverityLevel, cfgTemperatureUnits, mcrChassisIndex, mcrChassisSlotIndex,
                  mcrUserDefinedModuleName, xfpDmiRealTimeAux, mcrMediaPortNum }
    STATUS	current
    DESCRIPTION
        "Trap being sent indicates that an XFP module's Laser Temperature has 
        recovered to normal operating level."
    ::= { mcrMGTMIBNotifications 126 }

mcrXfpHighLaserTempAlarm	NOTIFICATION-TYPE
    OBJECTS	{ eventSeverityLevel, cfgTemperatureUnits, mcrChassisIndex, mcrChassisSlotIndex,
                  mcrUserDefinedModuleName, xfpDmiRealTimeAux, xfpDmiHighAuxAlarm, mcrMediaPortNum }
    STATUS	current
    DESCRIPTION
        "Trap being sent indicates that an XFP module's Laser Temperature has 
        exceeded the high Laser Temperature alarm threshold. "
    ::= { mcrMGTMIBNotifications 127 }

mcrXfpHighLaserTempAlarmRecov	NOTIFICATION-TYPE
    OBJECTS	{ eventSeverityLevel, cfgTemperatureUnits, mcrChassisIndex, mcrChassisSlotIndex,
                  mcrUserDefinedModuleName, xfpDmiRealTimeAux, mcrMediaPortNum }
    STATUS	current
    DESCRIPTION
        "Trap being sent indicates that an XFP module's Laser Temperature has 
        recovered to normal operating level. "
    ::= { mcrMGTMIBNotifications 128 }

mcrXfpLowLaserTempWarn	NOTIFICATION-TYPE
    OBJECTS	{ eventSeverityLevel, cfgTemperatureUnits, mcrChassisIndex, mcrChassisSlotIndex,
                  mcrUserDefinedModuleName, xfpDmiRealTimeAux, xfpDmiLowAuxWarn, mcrMediaPortNum }
    STATUS	current
    DESCRIPTION
        "Trap being sent indicates that an XFP module's Laser Temperature has gone 
        below the low Laser Temperature warning threshold. "
    ::= { mcrMGTMIBNotifications 129 }

mcrXfpLowLaserTempWarnRecov	NOTIFICATION-TYPE
    OBJECTS	{ eventSeverityLevel, cfgTemperatureUnits, mcrChassisIndex, mcrChassisSlotIndex,
                  mcrUserDefinedModuleName,  xfpDmiRealTimeAux, mcrMediaPortNum}
    STATUS	current
    DESCRIPTION
        "Trap being sent indicates that an XFP module's Laser Temperature has 
        recovered to normal operating level. "
    ::= { mcrMGTMIBNotifications 130 }
--
mcrXfpLowLaserTempAlarm	NOTIFICATION-TYPE
    OBJECTS	{ eventSeverityLevel, cfgTemperatureUnits, mcrChassisIndex, mcrChassisSlotIndex,
                  mcrUserDefinedModuleName, xfpDmiRealTimeAux, xfpDmiLowAuxAlarm, mcrMediaPortNum}
    STATUS	current
    DESCRIPTION
        "Trap being sent indicates that an XFP module's Laser Temperature has gone 
        below the low Laser Temperature alarm threshold. "
    ::= { mcrMGTMIBNotifications 131}

mcrXfpLowLaserTempAlarmRecov	NOTIFICATION-TYPE
    OBJECTS	{ eventSeverityLevel, cfgTemperatureUnits, mcrChassisIndex, mcrChassisSlotIndex,
                  mcrUserDefinedModuleName,  xfpDmiRealTimeAux, mcrMediaPortNum}
    STATUS	current
    DESCRIPTION
        "Trap being sent indicates that an XFP module's Laser Temperature has 
        recovered to normal operating level. "
    ::= { mcrMGTMIBNotifications 132 }

--- ****************************************************************************

mcrXfpHighLaserWavelengthWarn	NOTIFICATION-TYPE
    OBJECTS	{ eventSeverityLevel, mcrChassisIndex, mcrChassisSlotIndex,
                  mcrUserDefinedModuleName, xfpDmiRealTimeAux, xfpDmiHighAuxWarn, mcrMediaPortNum }
    STATUS	current
    DESCRIPTION
        "Trap being sent indicates that an XFP module's Laser Wavelength has 
        exceeded the high Laser Wavelength warning threshold. "
    ::= { mcrMGTMIBNotifications 133 }

mcrXfpHighLaserWavelengthWarnRecov	NOTIFICATION-TYPE
    OBJECTS	{ eventSeverityLevel, mcrChassisIndex, mcrChassisSlotIndex,
                  mcrUserDefinedModuleName, xfpDmiRealTimeAux, mcrMediaPortNum }
    STATUS	current
    DESCRIPTION
        "Trap being sent indicates that an XFP module's Laser Wavelength has 
        recovered to normal operating level."
    ::= { mcrMGTMIBNotifications 134 }

mcrXfpHighLaserWavelengthAlarm	NOTIFICATION-TYPE
    OBJECTS	{ eventSeverityLevel, mcrChassisIndex, mcrChassisSlotIndex,
                  mcrUserDefinedModuleName, xfpDmiRealTimeAux, xfpDmiHighAuxAlarm, mcrMediaPortNum }
    STATUS	current
    DESCRIPTION
        "Trap being sent indicates that an XFP module's Laser Wavelength has 
        exceeded the high Laser Wavelength alarm threshold. "
    ::= { mcrMGTMIBNotifications 135 }

mcrXfpHighLaserWavelengthAlarmRecov	NOTIFICATION-TYPE
    OBJECTS	{ eventSeverityLevel, mcrChassisIndex, mcrChassisSlotIndex,
                  mcrUserDefinedModuleName, xfpDmiRealTimeAux, mcrMediaPortNum }
    STATUS	current
    DESCRIPTION
        "Trap being sent indicates that an XFP module's Laser Wavelength has 
        recovered to normal operating level. "
    ::= { mcrMGTMIBNotifications 136 }

mcrXfpLowLaserWavelengthWarn	NOTIFICATION-TYPE
    OBJECTS	{ eventSeverityLevel, mcrChassisIndex, mcrChassisSlotIndex,
                  mcrUserDefinedModuleName, xfpDmiRealTimeAux, xfpDmiLowAuxWarn, mcrMediaPortNum }
    STATUS	current
    DESCRIPTION
        "Trap being sent indicates that an XFP module's Laser Wavelength has gone 
        below the low Laser Wavelength warning threshold. "
    ::= { mcrMGTMIBNotifications 137 }

mcrXfpLowLaserWavelengthWarnRecov	NOTIFICATION-TYPE
    OBJECTS	{ eventSeverityLevel, mcrChassisIndex, mcrChassisSlotIndex,
                  mcrUserDefinedModuleName,  xfpDmiRealTimeAux, mcrMediaPortNum}
    STATUS	current
    DESCRIPTION
        "Trap being sent indicates that an XFP module's Laser Wavelength has 
        recovered to normal operating level. "
    ::= { mcrMGTMIBNotifications 138 }
--
mcrXfpLowLaserWavelengthAlarm	NOTIFICATION-TYPE
    OBJECTS	{ eventSeverityLevel, mcrChassisIndex, mcrChassisSlotIndex,
                  mcrUserDefinedModuleName, xfpDmiRealTimeAux, xfpDmiLowAuxAlarm, mcrMediaPortNum}
    STATUS	current
    DESCRIPTION
        "Trap being sent indicates that an XFP module's Laser Wavelength has gone 
        below the low Laser Wavelength alarm threshold. "
    ::= { mcrMGTMIBNotifications 139}

mcrXfpLowLaserWavelengthAlarmRecov	NOTIFICATION-TYPE
    OBJECTS	{ eventSeverityLevel, mcrChassisIndex, mcrChassisSlotIndex,
                  mcrUserDefinedModuleName,  xfpDmiRealTimeAux, mcrMediaPortNum}
    STATUS	current
    DESCRIPTION
        "Trap being sent indicates that an XFP module's Laser Wavelength has 
        recovered to normal operating level. "
    ::= { mcrMGTMIBNotifications 140 }

--- ****************************************************************************

mcrXfpHigh5VoltWarn	NOTIFICATION-TYPE
    OBJECTS	{ eventSeverityLevel, mcrChassisIndex, mcrChassisSlotIndex,
                  mcrUserDefinedModuleName, xfpDmiRealTimeAux, xfpDmiHighAuxWarn, mcrMediaPortNum }
    STATUS	current
    DESCRIPTION
        "Trap being sent indicates that an XFP module's +5v supply has 
        exceeded the high +5v supply warning threshold. "
    ::= { mcrMGTMIBNotifications 141 }

mcrXfpHigh5VoltWarnRecov	NOTIFICATION-TYPE
    OBJECTS	{ eventSeverityLevel, mcrChassisIndex, mcrChassisSlotIndex,
                  mcrUserDefinedModuleName, xfpDmiRealTimeAux, mcrMediaPortNum }
    STATUS	current
    DESCRIPTION
        "Trap being sent indicates that an XFP module's +5v supply has 
        recovered to normal operating level."
    ::= { mcrMGTMIBNotifications 142 }

mcrXfpHigh5VoltAlarm	NOTIFICATION-TYPE
    OBJECTS	{ eventSeverityLevel, mcrChassisIndex, mcrChassisSlotIndex,
                  mcrUserDefinedModuleName, xfpDmiRealTimeAux, xfpDmiHighAuxAlarm, mcrMediaPortNum }
    STATUS	current
    DESCRIPTION
        "Trap being sent indicates that an XFP module's +5v supply has 
        exceeded the high +5v supply alarm threshold. "
    ::= { mcrMGTMIBNotifications 143 }

mcrXfpHigh5VoltAlarmRecov	NOTIFICATION-TYPE
    OBJECTS	{ eventSeverityLevel, mcrChassisIndex, mcrChassisSlotIndex,
                  mcrUserDefinedModuleName, xfpDmiRealTimeAux, mcrMediaPortNum }
    STATUS	current
    DESCRIPTION
        "Trap being sent indicates that an XFP module's +5v supply has 
        recovered to normal operating level. "
    ::= { mcrMGTMIBNotifications 144 }

mcrXfpLow5VoltWarn	NOTIFICATION-TYPE
    OBJECTS	{ eventSeverityLevel, mcrChassisIndex, mcrChassisSlotIndex,
                  mcrUserDefinedModuleName, xfpDmiRealTimeAux, xfpDmiLowAuxWarn, mcrMediaPortNum }
    STATUS	current
    DESCRIPTION
        "Trap being sent indicates that an XFP module's +5v supply has gone 
        below the low +5v supply warning threshold. "
    ::= { mcrMGTMIBNotifications 145 }

mcrXfpLow5VoltWarnRecov	NOTIFICATION-TYPE
    OBJECTS	{ eventSeverityLevel, mcrChassisIndex, mcrChassisSlotIndex,
                  mcrUserDefinedModuleName,  xfpDmiRealTimeAux, mcrMediaPortNum}
    STATUS	current
    DESCRIPTION
        "Trap being sent indicates that an XFP module's +5v supply has 
        recovered to normal operating level. "
    ::= { mcrMGTMIBNotifications 146 }
--
mcrXfpLow5VoltAlarm	NOTIFICATION-TYPE
    OBJECTS	{ eventSeverityLevel, mcrChassisIndex, mcrChassisSlotIndex,
                  mcrUserDefinedModuleName, xfpDmiRealTimeAux, xfpDmiLowAuxAlarm, mcrMediaPortNum}
    STATUS	current
    DESCRIPTION
        "Trap being sent indicates that an XFP module's +5v supply has gone 
        below the low +5v supply alarm threshold. "
    ::= { mcrMGTMIBNotifications 147 }

mcrXfpLow5VoltAlarmRecov	NOTIFICATION-TYPE
    OBJECTS	{ eventSeverityLevel, mcrChassisIndex, mcrChassisSlotIndex,
                  mcrUserDefinedModuleName,  xfpDmiRealTimeAux, mcrMediaPortNum}
    STATUS	current
    DESCRIPTION
        "Trap being sent indicates that an XFP module's +5v supply has 
        recovered to normal operating level. "
    ::= { mcrMGTMIBNotifications 148 }

--- ****************************************************************************

mcrXfpHigh33VoltWarn	NOTIFICATION-TYPE
    OBJECTS	{ eventSeverityLevel, mcrChassisIndex, mcrChassisSlotIndex,
                  mcrUserDefinedModuleName, xfpDmiRealTimeAux, xfpDmiHighAuxWarn, mcrMediaPortNum }
    STATUS	current
    DESCRIPTION
        "Trap being sent indicates that an XFP module's +3.3v supply has 
        exceeded the high +3.3v supply warning threshold. "
    ::= { mcrMGTMIBNotifications 149 }

mcrXfpHigh33VoltWarnRecov	NOTIFICATION-TYPE
    OBJECTS	{ eventSeverityLevel, mcrChassisIndex, mcrChassisSlotIndex,
                  mcrUserDefinedModuleName, xfpDmiRealTimeAux, mcrMediaPortNum }
    STATUS	current
    DESCRIPTION
        "Trap being sent indicates that an XFP module's +3.3v supply has 
        recovered to normal operating level."
    ::= { mcrMGTMIBNotifications 150 }

mcrXfpHigh33VoltAlarm	NOTIFICATION-TYPE
    OBJECTS	{ eventSeverityLevel, mcrChassisIndex, mcrChassisSlotIndex,
                  mcrUserDefinedModuleName, xfpDmiRealTimeAux, xfpDmiHighAuxAlarm, mcrMediaPortNum }
    STATUS	current
    DESCRIPTION
        "Trap being sent indicates that an XFP module's +3.3v supply has 
        exceeded the high +3.3v supply alarm threshold. "
    ::= { mcrMGTMIBNotifications 151 }

mcrXfpHigh33VoltAlarmRecov	NOTIFICATION-TYPE
    OBJECTS	{ eventSeverityLevel, mcrChassisIndex, mcrChassisSlotIndex,
                  mcrUserDefinedModuleName, xfpDmiRealTimeAux, mcrMediaPortNum }
    STATUS	current
    DESCRIPTION
        "Trap being sent indicates that an XFP module's +3.3v supply has 
        recovered to normal operating level. "
    ::= { mcrMGTMIBNotifications 152 }

mcrXfpLow33VoltWarn	NOTIFICATION-TYPE
    OBJECTS	{ eventSeverityLevel, mcrChassisIndex, mcrChassisSlotIndex,
                  mcrUserDefinedModuleName, xfpDmiRealTimeAux, xfpDmiLowAuxWarn, mcrMediaPortNum }
    STATUS	current
    DESCRIPTION
        "Trap being sent indicates that an XFP module's +3.3v supply has gone 
        below the low +3.3v supply warning threshold. "
    ::= { mcrMGTMIBNotifications 153 }

mcrXfpLow33VoltWarnRecov	NOTIFICATION-TYPE
    OBJECTS	{ eventSeverityLevel, mcrChassisIndex, mcrChassisSlotIndex,
                  mcrUserDefinedModuleName,  xfpDmiRealTimeAux, mcrMediaPortNum}
    STATUS	current
    DESCRIPTION
        "Trap being sent indicates that an XFP module's +3.3v supply has 
        recovered to normal operating level. "
    ::= { mcrMGTMIBNotifications 154 }
--
mcrXfpLow33VoltAlarm	NOTIFICATION-TYPE
    OBJECTS	{ eventSeverityLevel, mcrChassisIndex, mcrChassisSlotIndex,
                  mcrUserDefinedModuleName, xfpDmiRealTimeAux, xfpDmiLowAuxAlarm, mcrMediaPortNum}
    STATUS	current
    DESCRIPTION
        "Trap being sent indicates that an XFP module's +3.3v supply has gone 
        below the low +3.3v supply alarm threshold. "
    ::= { mcrMGTMIBNotifications 155}

mcrXfpLow33VoltAlarmRecov	NOTIFICATION-TYPE
    OBJECTS	{ eventSeverityLevel, mcrChassisIndex, mcrChassisSlotIndex,
                  mcrUserDefinedModuleName,  xfpDmiRealTimeAux, mcrMediaPortNum}
    STATUS	current
    DESCRIPTION
        "Trap being sent indicates that an XFP module's +3.3v supply has 
        recovered to normal operating level. "
    ::= { mcrMGTMIBNotifications 156 }

--
--- ****************************************************************************

mcrXfpHigh18VoltWarn	NOTIFICATION-TYPE
    OBJECTS	{ eventSeverityLevel, mcrChassisIndex, mcrChassisSlotIndex,
                  mcrUserDefinedModuleName, xfpDmiRealTimeAux, xfpDmiHighAuxWarn, mcrMediaPortNum }
    STATUS	current
    DESCRIPTION
        "Trap being sent indicates that an XFP module's +1.8v supply has 
        exceeded the high +1.8v supply warning threshold. "
    ::= { mcrMGTMIBNotifications 157 }

mcrXfpHigh18VoltWarnRecov	NOTIFICATION-TYPE
    OBJECTS	{ eventSeverityLevel, mcrChassisIndex, mcrChassisSlotIndex,
                  mcrUserDefinedModuleName, xfpDmiRealTimeAux, mcrMediaPortNum }
    STATUS	current
    DESCRIPTION
        "Trap being sent indicates that an XFP module's +1.8v supply has 
        recovered to normal operating level."
    ::= { mcrMGTMIBNotifications 158 }

mcrXfpHigh18VoltAlarm	NOTIFICATION-TYPE
    OBJECTS	{ eventSeverityLevel, mcrChassisIndex, mcrChassisSlotIndex,
                  mcrUserDefinedModuleName, xfpDmiRealTimeAux, xfpDmiHighAuxAlarm, mcrMediaPortNum }
    STATUS	current
    DESCRIPTION
        "Trap being sent indicates that an XFP module's +1.8v supply has 
        exceeded the high +1.8v supply alarm threshold. "
    ::= { mcrMGTMIBNotifications 159 }

mcrXfpHigh18VoltAlarmRecov	NOTIFICATION-TYPE
    OBJECTS	{ eventSeverityLevel, mcrChassisIndex, mcrChassisSlotIndex,
                  mcrUserDefinedModuleName, xfpDmiRealTimeAux, mcrMediaPortNum }
    STATUS	current
    DESCRIPTION
        "Trap being sent indicates that an XFP module's +1.8v supply has 
        recovered to normal operating level. "
    ::= { mcrMGTMIBNotifications 160 }

mcrXfpLow18VoltWarn	NOTIFICATION-TYPE
    OBJECTS	{ eventSeverityLevel, mcrChassisIndex, mcrChassisSlotIndex,
                  mcrUserDefinedModuleName, xfpDmiRealTimeAux, xfpDmiLowAuxWarn, mcrMediaPortNum }
    STATUS	current
    DESCRIPTION
        "Trap being sent indicates that an XFP module's +1.8v supply has gone 
        below the low +1.8v supply warning threshold. "
    ::= { mcrMGTMIBNotifications 161 }

mcrXfpLow18VoltWarnRecov	NOTIFICATION-TYPE
    OBJECTS	{ eventSeverityLevel, mcrChassisIndex, mcrChassisSlotIndex,
                  mcrUserDefinedModuleName,  xfpDmiRealTimeAux, mcrMediaPortNum}
    STATUS	current
    DESCRIPTION
        "Trap being sent indicates that an XFP module's +1.8v supply has 
        recovered to normal operating level. "
    ::= { mcrMGTMIBNotifications 162 }
--
mcrXfpLow18VoltAlarm	NOTIFICATION-TYPE
    OBJECTS	{ eventSeverityLevel, mcrChassisIndex, mcrChassisSlotIndex,
                  mcrUserDefinedModuleName, xfpDmiRealTimeAux, xfpDmiLowAuxAlarm, mcrMediaPortNum}
    STATUS	current
    DESCRIPTION
        "Trap being sent indicates that an XFP module's +1.8v supply has gone 
        below the low +1.8v supply alarm threshold. "
    ::= { mcrMGTMIBNotifications 163}

mcrXfpLow18VoltAlarmRecov	NOTIFICATION-TYPE
    OBJECTS	{ eventSeverityLevel, mcrChassisIndex, mcrChassisSlotIndex,
                  mcrUserDefinedModuleName,  xfpDmiRealTimeAux, mcrMediaPortNum}
    STATUS	current
    DESCRIPTION
        "Trap being sent indicates that an XFP module's +1.8v supply has 
        recovered to normal operating level. "
    ::= { mcrMGTMIBNotifications 164 }

--- ****************************************************************************

mcrXfpHighM52VoltWarn	NOTIFICATION-TYPE
    OBJECTS	{ eventSeverityLevel, mcrChassisIndex, mcrChassisSlotIndex,
                  mcrUserDefinedModuleName, xfpDmiRealTimeAux, xfpDmiHighAuxWarn, mcrMediaPortNum }
    STATUS	current
    DESCRIPTION
        "Trap being sent indicates that an XFP module's -5.2v supply has 
        exceeded the high -5.2v supply warning threshold. "
    ::= { mcrMGTMIBNotifications 165 }

mcrXfpHighM52VoltWarnRecov	NOTIFICATION-TYPE
    OBJECTS	{ eventSeverityLevel, mcrChassisIndex, mcrChassisSlotIndex,
                  mcrUserDefinedModuleName, xfpDmiRealTimeAux, mcrMediaPortNum }
    STATUS	current
    DESCRIPTION
        "Trap being sent indicates that an XFP module's -5.2v supply has 
        recovered to normal operating level."
    ::= { mcrMGTMIBNotifications 166 }

mcrXfpHighM52VoltAlarm	NOTIFICATION-TYPE
    OBJECTS	{ eventSeverityLevel, mcrChassisIndex, mcrChassisSlotIndex,
                  mcrUserDefinedModuleName, xfpDmiRealTimeAux, xfpDmiHighAuxAlarm, mcrMediaPortNum }
    STATUS	current
    DESCRIPTION
        "Trap being sent indicates that an XFP module's -5.2v supply has 
        exceeded the high -5.2v supply alarm threshold. "
    ::= { mcrMGTMIBNotifications 167 }

mcrXfpHighM52VoltAlarmRecov	NOTIFICATION-TYPE
    OBJECTS	{ eventSeverityLevel, mcrChassisIndex, mcrChassisSlotIndex,
                  mcrUserDefinedModuleName, xfpDmiRealTimeAux, mcrMediaPortNum }
    STATUS	current
    DESCRIPTION
        "Trap being sent indicates that an XFP module's -5.2v supply has 
        recovered to normal operating level. "
    ::= { mcrMGTMIBNotifications 168 }

mcrXfpLowM52VoltWarn	NOTIFICATION-TYPE
    OBJECTS	{ eventSeverityLevel, mcrChassisIndex, mcrChassisSlotIndex,
                  mcrUserDefinedModuleName, xfpDmiRealTimeAux, xfpDmiLowAuxWarn, mcrMediaPortNum }
    STATUS	current
    DESCRIPTION
        "Trap being sent indicates that an XFP module's -5.2v supply has gone 
        below the low -5.2v supply warning threshold. "
    ::= { mcrMGTMIBNotifications 169 }

mcrXfpLowM52VoltWarnRecov	NOTIFICATION-TYPE
    OBJECTS	{ eventSeverityLevel, mcrChassisIndex, mcrChassisSlotIndex,
                  mcrUserDefinedModuleName,  xfpDmiRealTimeAux, mcrMediaPortNum}
    STATUS	current
    DESCRIPTION
        "Trap being sent indicates that an XFP module's -5.2v supply has 
        recovered to normal operating level. "
    ::= { mcrMGTMIBNotifications 170 }
--
mcrXfpLowM52VoltAlarm	NOTIFICATION-TYPE
    OBJECTS	{ eventSeverityLevel, mcrChassisIndex, mcrChassisSlotIndex,
                  mcrUserDefinedModuleName, xfpDmiRealTimeAux, xfpDmiLowAuxAlarm, mcrMediaPortNum}
    STATUS	current
    DESCRIPTION
        "Trap being sent indicates that an XFP module's -5.2v supply has gone 
        below the low -5.2v supply alarm threshold. "
    ::= { mcrMGTMIBNotifications 171}

mcrXfpLowM52VoltAlarmRecov	NOTIFICATION-TYPE
    OBJECTS	{ eventSeverityLevel, mcrChassisIndex, mcrChassisSlotIndex,
                  mcrUserDefinedModuleName,  xfpDmiRealTimeAux, mcrMediaPortNum}
    STATUS	current
    DESCRIPTION
        "Trap being sent indicates that an XFP module's -5.2v supply has 
        recovered to normal operating level. "
    ::= { mcrMGTMIBNotifications 172 }

--- ****************************************************************************

mcrXfpHigh5VCurrentWarn	NOTIFICATION-TYPE
    OBJECTS	{ eventSeverityLevel, mcrChassisIndex, mcrChassisSlotIndex,
                  mcrUserDefinedModuleName, xfpDmiRealTimeAux, xfpDmiHighAuxWarn, mcrMediaPortNum }
    STATUS	current
    DESCRIPTION
        "Trap being sent indicates that an XFP module's +5v supply current has 
        exceeded the high +5v supply current warning threshold. "
    ::= { mcrMGTMIBNotifications 173 }

mcrXfpHigh5VCurrentWarnRecov	NOTIFICATION-TYPE
    OBJECTS	{ eventSeverityLevel, mcrChassisIndex, mcrChassisSlotIndex,
                  mcrUserDefinedModuleName, xfpDmiRealTimeAux, mcrMediaPortNum }
    STATUS	current
    DESCRIPTION
        "Trap being sent indicates that an XFP module's +5v supply current has 
        recovered to normal operating level."
    ::= { mcrMGTMIBNotifications 174 }

mcrXfpHigh5VCurrentAlarm	NOTIFICATION-TYPE
    OBJECTS	{ eventSeverityLevel, mcrChassisIndex, mcrChassisSlotIndex,
                  mcrUserDefinedModuleName, xfpDmiRealTimeAux, xfpDmiHighAuxAlarm, mcrMediaPortNum }
    STATUS	current
    DESCRIPTION
        "Trap being sent indicates that an XFP module's +5v supply current has 
        exceeded the high +5v supply current alarm threshold. "
    ::= { mcrMGTMIBNotifications 175 }

mcrXfpHigh5VCurrentAlarmRecov	NOTIFICATION-TYPE
    OBJECTS	{ eventSeverityLevel, mcrChassisIndex, mcrChassisSlotIndex,
                  mcrUserDefinedModuleName, xfpDmiRealTimeAux, mcrMediaPortNum }
    STATUS	current
    DESCRIPTION
        "Trap being sent indicates that an XFP module's +5v supply current has 
        recovered to normal operating level. "
    ::= { mcrMGTMIBNotifications 176 }

mcrXfpLow5VCurrentWarn	NOTIFICATION-TYPE
    OBJECTS	{ eventSeverityLevel, mcrChassisIndex, mcrChassisSlotIndex,
                  mcrUserDefinedModuleName, xfpDmiRealTimeAux, xfpDmiLowAuxWarn, mcrMediaPortNum }
    STATUS	current
    DESCRIPTION
        "Trap being sent indicates that an XFP module's +5v supply current has gone 
        below the low +5v supply current warning threshold. "
    ::= { mcrMGTMIBNotifications 177 }

mcrXfpLow5VCurrentWarnRecov	NOTIFICATION-TYPE
    OBJECTS	{ eventSeverityLevel, mcrChassisIndex, mcrChassisSlotIndex,
                  mcrUserDefinedModuleName,  xfpDmiRealTimeAux, mcrMediaPortNum}
    STATUS	current
    DESCRIPTION
        "Trap being sent indicates that an XFP module's +5v supply current has 
        recovered to normal operating level. "
    ::= { mcrMGTMIBNotifications 178 }
--
mcrXfpLow5VCurrentAlarm	NOTIFICATION-TYPE
    OBJECTS	{ eventSeverityLevel, mcrChassisIndex, mcrChassisSlotIndex,
                  mcrUserDefinedModuleName, xfpDmiRealTimeAux, xfpDmiLowAuxAlarm, mcrMediaPortNum}
    STATUS	current
    DESCRIPTION
        "Trap being sent indicates that an XFP module's +5v supply current has gone 
        below the low +5v supply current alarm threshold. "
    ::= { mcrMGTMIBNotifications 179}

mcrXfpLow5VCurrentAlarmRecov	NOTIFICATION-TYPE
    OBJECTS	{ eventSeverityLevel, mcrChassisIndex, mcrChassisSlotIndex,
                  mcrUserDefinedModuleName,  xfpDmiRealTimeAux, mcrMediaPortNum}
    STATUS	current
    DESCRIPTION
        "Trap being sent indicates that an XFP module's +5v supply current has 
        recovered to normal operating level. "
    ::= { mcrMGTMIBNotifications 180 }

--- ****************************************************************************

mcrXfpHigh33VCurrentWarn	NOTIFICATION-TYPE
    OBJECTS	{ eventSeverityLevel, mcrChassisIndex, mcrChassisSlotIndex,
                  mcrUserDefinedModuleName, xfpDmiRealTimeAux, xfpDmiHighAuxWarn, mcrMediaPortNum }
    STATUS	current
    DESCRIPTION
        "Trap being sent indicates that an XFP module's +3.3v supply current has 
        exceeded the high +3.3v supply current warning threshold. "
    ::= { mcrMGTMIBNotifications 181 }

mcrXfpHigh33VCurrentWarnRecov	NOTIFICATION-TYPE
    OBJECTS	{ eventSeverityLevel, mcrChassisIndex, mcrChassisSlotIndex,
                  mcrUserDefinedModuleName, xfpDmiRealTimeAux, mcrMediaPortNum }
    STATUS	current
    DESCRIPTION
        "Trap being sent indicates that an XFP module's +3.3v supply current has 
        recovered to normal operating level."
    ::= { mcrMGTMIBNotifications 182 }

mcrXfpHigh33VCurrentAlarm	NOTIFICATION-TYPE
    OBJECTS	{ eventSeverityLevel, mcrChassisIndex, mcrChassisSlotIndex,
                  mcrUserDefinedModuleName, xfpDmiRealTimeAux, xfpDmiHighAuxAlarm, mcrMediaPortNum }
    STATUS	current
    DESCRIPTION
        "Trap being sent indicates that an XFP module's +3.3v supply current has 
        exceeded the high +3.3v supply current alarm threshold. "
    ::= { mcrMGTMIBNotifications 183 }

mcrXfpHigh33VCurrentAlarmRecov	NOTIFICATION-TYPE
    OBJECTS	{ eventSeverityLevel, mcrChassisIndex, mcrChassisSlotIndex,
                  mcrUserDefinedModuleName, xfpDmiRealTimeAux, mcrMediaPortNum }
    STATUS	current
    DESCRIPTION
        "Trap being sent indicates that an XFP module's +3.3v supply current has 
        recovered to normal operating level. "
    ::= { mcrMGTMIBNotifications 184 }

mcrXfpLow33VCurrentWarn	NOTIFICATION-TYPE
    OBJECTS	{ eventSeverityLevel, mcrChassisIndex, mcrChassisSlotIndex,
                  mcrUserDefinedModuleName, xfpDmiRealTimeAux, xfpDmiLowAuxWarn, mcrMediaPortNum }
    STATUS	current
    DESCRIPTION
        "Trap being sent indicates that an XFP module's +3.3v supply current has gone 
        below the low +3.3v supply current warning threshold. "
    ::= { mcrMGTMIBNotifications 185 }

mcrXfpLow33VCurrentWarnRecov	NOTIFICATION-TYPE
    OBJECTS	{ eventSeverityLevel, mcrChassisIndex, mcrChassisSlotIndex,
                  mcrUserDefinedModuleName,  xfpDmiRealTimeAux, mcrMediaPortNum}
    STATUS	current
    DESCRIPTION
        "Trap being sent indicates that an XFP module's +3.3v supply current has 
        recovered to normal operating level. "
    ::= { mcrMGTMIBNotifications 186 }
--
mcrXfpLow33VCurrentAlarm	NOTIFICATION-TYPE
    OBJECTS	{ eventSeverityLevel, mcrChassisIndex, mcrChassisSlotIndex,
                  mcrUserDefinedModuleName, xfpDmiRealTimeAux, xfpDmiLowAuxAlarm, mcrMediaPortNum}
    STATUS	current
    DESCRIPTION
        "Trap being sent indicates that an XFP module's +3.3v supply current has gone 
        below the low +3.3v supply current alarm threshold. "
    ::= { mcrMGTMIBNotifications 187}

mcrXfpLow33VCurrentAlarmRecov	NOTIFICATION-TYPE
    OBJECTS	{ eventSeverityLevel, mcrChassisIndex, mcrChassisSlotIndex,
                  mcrUserDefinedModuleName,  xfpDmiRealTimeAux, mcrMediaPortNum}
    STATUS	current
    DESCRIPTION
        "Trap being sent indicates that an XFP module's +3.3v supply current has 
        recovered to normal operating level. "
    ::= { mcrMGTMIBNotifications 188 }

--- ****************************************************************************

mcrXfpHigh18VCurrentWarn	NOTIFICATION-TYPE
    OBJECTS	{ eventSeverityLevel, mcrChassisIndex, mcrChassisSlotIndex,
                  mcrUserDefinedModuleName, xfpDmiRealTimeAux, xfpDmiHighAuxWarn, mcrMediaPortNum }
    STATUS	current
    DESCRIPTION
        "Trap being sent indicates that an XFP module's +1.8v supply current has 
        exceeded the high +1.8v supply current warning threshold. "
    ::= { mcrMGTMIBNotifications 189 }

mcrXfpHigh18VCurrentWarnRecov	NOTIFICATION-TYPE
    OBJECTS	{ eventSeverityLevel, mcrChassisIndex, mcrChassisSlotIndex,
                  mcrUserDefinedModuleName, xfpDmiRealTimeAux, mcrMediaPortNum }
    STATUS	current
    DESCRIPTION
        "Trap being sent indicates that an XFP module's +1.8v supply current has 
        recovered to normal operating level."
    ::= { mcrMGTMIBNotifications 190 }

mcrXfpHigh18VCurrentAlarm	NOTIFICATION-TYPE
    OBJECTS	{ eventSeverityLevel, mcrChassisIndex, mcrChassisSlotIndex,
                  mcrUserDefinedModuleName, xfpDmiRealTimeAux, xfpDmiHighAuxAlarm, mcrMediaPortNum }
    STATUS	current
    DESCRIPTION
        "Trap being sent indicates that an XFP module's +1.8v supply current has 
        exceeded the high +1.8v supply current alarm threshold. "
    ::= { mcrMGTMIBNotifications 191 }

mcrXfpHigh18VCurrentAlarmRecov	NOTIFICATION-TYPE
    OBJECTS	{ eventSeverityLevel, mcrChassisIndex, mcrChassisSlotIndex,
                  mcrUserDefinedModuleName, xfpDmiRealTimeAux, mcrMediaPortNum }
    STATUS	current
    DESCRIPTION
        "Trap being sent indicates that an XFP module's +1.8v supply current has 
        recovered to normal operating level. "
    ::= { mcrMGTMIBNotifications 192 }

mcrXfpLow18VCurrentWarn	NOTIFICATION-TYPE
    OBJECTS	{ eventSeverityLevel, mcrChassisIndex, mcrChassisSlotIndex,
                  mcrUserDefinedModuleName, xfpDmiRealTimeAux, xfpDmiLowAuxWarn, mcrMediaPortNum }
    STATUS	current
    DESCRIPTION
        "Trap being sent indicates that an XFP module's +1.8v supply current has gone 
        below the low +1.8v supply current warning threshold. "
    ::= { mcrMGTMIBNotifications 193 }

mcrXfpLow18VCurrentWarnRecov	NOTIFICATION-TYPE
    OBJECTS	{ eventSeverityLevel, mcrChassisIndex, mcrChassisSlotIndex,
                  mcrUserDefinedModuleName,  xfpDmiRealTimeAux, mcrMediaPortNum}
    STATUS	current
    DESCRIPTION
        "Trap being sent indicates that an XFP module's +1.8v supply current has 
        recovered to normal operating level. "
    ::= { mcrMGTMIBNotifications 194 }
--
mcrXfpLow18VCurrentAlarm	NOTIFICATION-TYPE
    OBJECTS	{ eventSeverityLevel, mcrChassisIndex, mcrChassisSlotIndex,
                  mcrUserDefinedModuleName, xfpDmiRealTimeAux, xfpDmiLowAuxAlarm, mcrMediaPortNum}
    STATUS	current
    DESCRIPTION
        "Trap being sent indicates that an XFP module's +1.8v supply current has gone 
        below the low +1.8v supply current alarm threshold. "
    ::= { mcrMGTMIBNotifications 195}

mcrXfpLow18VCurrentAlarmRecov	NOTIFICATION-TYPE
    OBJECTS	{ eventSeverityLevel, mcrChassisIndex, mcrChassisSlotIndex,
                  mcrUserDefinedModuleName,  xfpDmiRealTimeAux, mcrMediaPortNum}
    STATUS	current
    DESCRIPTION
        "Trap being sent indicates that an XFP module's +1.8v supply current has 
        recovered to normal operating level. "
    ::= { mcrMGTMIBNotifications 196 }

--- ****************************************************************************

mcrXfpHighM52VCurrentWarn	NOTIFICATION-TYPE
    OBJECTS	{ eventSeverityLevel, mcrChassisIndex, mcrChassisSlotIndex,
                  mcrUserDefinedModuleName, xfpDmiRealTimeAux, xfpDmiHighAuxWarn, mcrMediaPortNum }
    STATUS	current
    DESCRIPTION
        "Trap being sent indicates that an XFP module's -5.2v supply current has 
        exceeded the high -5.2v supply current warning threshold. "
    ::= { mcrMGTMIBNotifications 197 }

mcrXfpHighM52VCurrentWarnRecov	NOTIFICATION-TYPE
    OBJECTS	{ eventSeverityLevel, mcrChassisIndex, mcrChassisSlotIndex,
                  mcrUserDefinedModuleName, xfpDmiRealTimeAux, mcrMediaPortNum }
    STATUS	current
    DESCRIPTION
        "Trap being sent indicates that an XFP module's -5.2v supply current has 
        recovered to normal operating level."
    ::= { mcrMGTMIBNotifications 198 }

mcrXfpHighM52VCurrentAlarm	NOTIFICATION-TYPE
    OBJECTS	{ eventSeverityLevel, mcrChassisIndex, mcrChassisSlotIndex,
                  mcrUserDefinedModuleName, xfpDmiRealTimeAux, xfpDmiHighAuxAlarm, mcrMediaPortNum }
    STATUS	current
    DESCRIPTION
        "Trap being sent indicates that an XFP module's -5.2v supply current has 
        exceeded the high -5.2v supply current alarm threshold. "
    ::= { mcrMGTMIBNotifications 199 }

mcrXfpHighM52VCurrentAlarmRecov	NOTIFICATION-TYPE
    OBJECTS	{ eventSeverityLevel, mcrChassisIndex, mcrChassisSlotIndex,
                  mcrUserDefinedModuleName, xfpDmiRealTimeAux, mcrMediaPortNum }
    STATUS	current
    DESCRIPTION
        "Trap being sent indicates that an XFP module's -5.2v supply current has 
        recovered to normal operating level. "
    ::= { mcrMGTMIBNotifications 200 }

mcrXfpLowM52VCurrentWarn	NOTIFICATION-TYPE
    OBJECTS	{ eventSeverityLevel, mcrChassisIndex, mcrChassisSlotIndex,
                  mcrUserDefinedModuleName, xfpDmiRealTimeAux, xfpDmiLowAuxWarn, mcrMediaPortNum }
    STATUS	current
    DESCRIPTION
        "Trap being sent indicates that an XFP module's -5.2v supply current has gone 
        below the low -5.2v supply current warning threshold. "
    ::= { mcrMGTMIBNotifications 201 }

mcrXfpLowM52VCurrentWarnRecov	NOTIFICATION-TYPE
    OBJECTS	{ eventSeverityLevel, mcrChassisIndex, mcrChassisSlotIndex,
                  mcrUserDefinedModuleName,  xfpDmiRealTimeAux, mcrMediaPortNum}
    STATUS	current
    DESCRIPTION
        "Trap being sent indicates that an XFP module's -5.2v supply current has 
        recovered to normal operating level. "
    ::= { mcrMGTMIBNotifications 202 }
--
mcrXfpLowM52VCurrentAlarm	NOTIFICATION-TYPE
    OBJECTS	{ eventSeverityLevel, mcrChassisIndex, mcrChassisSlotIndex,
                  mcrUserDefinedModuleName, xfpDmiRealTimeAux, xfpDmiLowAuxAlarm, mcrMediaPortNum}
    STATUS	current
    DESCRIPTION
        "Trap being sent indicates that an XFP module's -5.2v supply current has gone 
        below the low -5.2v supply current alarm threshold. "
    ::= { mcrMGTMIBNotifications 203}

mcrXfpLowM52VCurrentAlarmRecov	NOTIFICATION-TYPE
    OBJECTS	{ eventSeverityLevel, mcrChassisIndex, mcrChassisSlotIndex,
                  mcrUserDefinedModuleName,  xfpDmiRealTimeAux, mcrMediaPortNum}
    STATUS	current
    DESCRIPTION
        "Trap being sent indicates that an XFP module's -5.2v supply current has 
        recovered to normal operating level. "
    ::= { mcrMGTMIBNotifications 204 }

--- ****************************************************************************

mcrXfpHighVCC5Warn	NOTIFICATION-TYPE
    OBJECTS	{ eventSeverityLevel, mcrChassisIndex, mcrChassisSlotIndex,
                  mcrUserDefinedModuleName, mcrMediaPortNum }
    STATUS	current
    DESCRIPTION
        "Trap being sent indicates that an XFP module's +5v supply has 
        exceeded the high +5v supply warning threshold."
    ::= { mcrMGTMIBNotifications 205 }

mcrXfpHighVCC5WarnRecov	NOTIFICATION-TYPE
    OBJECTS	{ eventSeverityLevel, mcrChassisIndex, mcrChassisSlotIndex,
                  mcrUserDefinedModuleName, mcrMediaPortNum }
    STATUS	current
    DESCRIPTION
        "Trap being sent indicates that an XFP module's +5v supply has 
        recovered to normal operating level."
    ::= { mcrMGTMIBNotifications 206 }

mcrXfpHighVCC5Alarm	NOTIFICATION-TYPE
    OBJECTS	{ eventSeverityLevel, mcrChassisIndex, mcrChassisSlotIndex,
                  mcrUserDefinedModuleName, mcrMediaPortNum }
    STATUS	current
    DESCRIPTION
        "Trap being sent indicates that an XFP module's +5v supply has 
        exceeded the high +5v supply alarm threshold. "
    ::= { mcrMGTMIBNotifications 207 }

mcrXfpHighVCC5AlarmRecov	NOTIFICATION-TYPE
    OBJECTS	{ eventSeverityLevel, mcrChassisIndex, mcrChassisSlotIndex,
                  mcrUserDefinedModuleName, mcrMediaPortNum }
    STATUS	current
    DESCRIPTION
        "Trap being sent indicates that an XFP module's +5v supply has 
        recovered to normal operating level. "
    ::= { mcrMGTMIBNotifications 208 }

mcrXfpLowVCC5Warn	NOTIFICATION-TYPE
    OBJECTS	{ eventSeverityLevel, mcrChassisIndex, mcrChassisSlotIndex,
                  mcrUserDefinedModuleName, mcrMediaPortNum }
    STATUS	current
    DESCRIPTION
        "Trap being sent indicates that an XFP module's +5v supply has gone 
        below the low +5v supply warning threshold. "
    ::= { mcrMGTMIBNotifications 209 }

mcrXfpLowVCC5WarnRecov	NOTIFICATION-TYPE
    OBJECTS	{ eventSeverityLevel, mcrChassisIndex, mcrChassisSlotIndex,
                  mcrUserDefinedModuleName, mcrMediaPortNum}
    STATUS	current
    DESCRIPTION
        "Trap being sent indicates that an XFP module's +5v supply has 
        recovered to normal operating level. "
    ::= { mcrMGTMIBNotifications 210 }
--
mcrXfpLowVCC5Alarm	NOTIFICATION-TYPE
    OBJECTS	{ eventSeverityLevel, mcrChassisIndex, mcrChassisSlotIndex,
                  mcrUserDefinedModuleName, mcrMediaPortNum}
    STATUS	current
    DESCRIPTION
        "Trap being sent indicates that an XFP module's +5v supply has gone 
        below the low +5v supply alarm threshold. "
    ::= { mcrMGTMIBNotifications 211 }

mcrXfpLowVCC5AlarmRecov	NOTIFICATION-TYPE
    OBJECTS	{ eventSeverityLevel, mcrChassisIndex, mcrChassisSlotIndex,
                  mcrUserDefinedModuleName, mcrMediaPortNum}
    STATUS	current
    DESCRIPTION
        "Trap being sent indicates that an XFP module's +5v supply has 
        recovered to normal operating level. "
    ::= { mcrMGTMIBNotifications 212 }

--- ****************************************************************************

mcrXfpHighVCC3Warn	NOTIFICATION-TYPE
    OBJECTS	{ eventSeverityLevel, mcrChassisIndex, mcrChassisSlotIndex,
                  mcrUserDefinedModuleName, mcrMediaPortNum }
    STATUS	current
    DESCRIPTION
        "Trap being sent indicates that an XFP module's +3.3v supply has 
        exceeded the high +3.3v supply warning threshold."
    ::= { mcrMGTMIBNotifications 213 }

mcrXfpHighVCC3WarnRecov	NOTIFICATION-TYPE
    OBJECTS	{ eventSeverityLevel, mcrChassisIndex, mcrChassisSlotIndex,
                  mcrUserDefinedModuleName, mcrMediaPortNum }
    STATUS	current
    DESCRIPTION
        "Trap being sent indicates that an XFP module's +3.3v supply has 
        recovered to normal operating level."
    ::= { mcrMGTMIBNotifications 214 }

mcrXfpHighVCC3Alarm	NOTIFICATION-TYPE
    OBJECTS	{ eventSeverityLevel, mcrChassisIndex, mcrChassisSlotIndex,
                  mcrUserDefinedModuleName, mcrMediaPortNum }
    STATUS	current
    DESCRIPTION
        "Trap being sent indicates that an XFP module's +3.3v supply has 
        exceeded the high +3.3v supply alarm threshold. "
    ::= { mcrMGTMIBNotifications 215 }

mcrXfpHighVCC3AlarmRecov	NOTIFICATION-TYPE
    OBJECTS	{ eventSeverityLevel, mcrChassisIndex, mcrChassisSlotIndex,
                  mcrUserDefinedModuleName, mcrMediaPortNum }
    STATUS	current
    DESCRIPTION
        "Trap being sent indicates that an XFP module's +3.3v supply has 
        recovered to normal operating level. "
    ::= { mcrMGTMIBNotifications 216 }

mcrXfpLowVCC3Warn	NOTIFICATION-TYPE
    OBJECTS	{ eventSeverityLevel, mcrChassisIndex, mcrChassisSlotIndex,
                  mcrUserDefinedModuleName, mcrMediaPortNum }
    STATUS	current
    DESCRIPTION
        "Trap being sent indicates that an XFP module's +3.3v supply has gone 
        below the low +3.3v supply warning threshold. "
    ::= { mcrMGTMIBNotifications 217 }

mcrXfpLowVCC3WarnRecov	NOTIFICATION-TYPE
    OBJECTS	{ eventSeverityLevel, mcrChassisIndex, mcrChassisSlotIndex,
                  mcrUserDefinedModuleName, mcrMediaPortNum}
    STATUS	current
    DESCRIPTION
        "Trap being sent indicates that an XFP module's +3.3v supply has 
        recovered to normal operating level. "
    ::= { mcrMGTMIBNotifications 218 }
--
mcrXfpLowVCC3Alarm	NOTIFICATION-TYPE
    OBJECTS	{ eventSeverityLevel, mcrChassisIndex, mcrChassisSlotIndex,
                  mcrUserDefinedModuleName, mcrMediaPortNum}
    STATUS	current
    DESCRIPTION
        "Trap being sent indicates that an XFP module's +3.3v supply has gone 
        below the low +3.3v supply alarm threshold. "
    ::= { mcrMGTMIBNotifications 219 }

mcrXfpLowVCC3AlarmRecov	NOTIFICATION-TYPE
    OBJECTS	{ eventSeverityLevel, mcrChassisIndex, mcrChassisSlotIndex,
                  mcrUserDefinedModuleName, mcrMediaPortNum}
    STATUS	current
    DESCRIPTION
        "Trap being sent indicates that an XFP module's +3.3v supply has 
        recovered to normal operating level. "
    ::= { mcrMGTMIBNotifications 220 }

--- ****************************************************************************

mcrXfpHighVCC2Warn	NOTIFICATION-TYPE
    OBJECTS	{ eventSeverityLevel, mcrChassisIndex, mcrChassisSlotIndex,
                  mcrUserDefinedModuleName, mcrMediaPortNum }
    STATUS	current
    DESCRIPTION
        "Trap being sent indicates that an XFP module's +1.8v supply has 
        exceeded the high +1.8v supply warning threshold."
    ::= { mcrMGTMIBNotifications 221 }

mcrXfpHighVCC2WarnRecov	NOTIFICATION-TYPE
    OBJECTS	{ eventSeverityLevel, mcrChassisIndex, mcrChassisSlotIndex,
                  mcrUserDefinedModuleName, mcrMediaPortNum }
    STATUS	current
    DESCRIPTION
        "Trap being sent indicates that an XFP module's +1.8v supply has 
        recovered to normal operating level."
    ::= { mcrMGTMIBNotifications 222 }

mcrXfpHighVCC2Alarm	NOTIFICATION-TYPE
    OBJECTS	{ eventSeverityLevel, mcrChassisIndex, mcrChassisSlotIndex,
                  mcrUserDefinedModuleName, mcrMediaPortNum }
    STATUS	current
    DESCRIPTION
        "Trap being sent indicates that an XFP module's +1.8v supply has 
        exceeded the high +1.8v supply alarm threshold. "
    ::= { mcrMGTMIBNotifications 223 }

mcrXfpHighVCC2AlarmRecov	NOTIFICATION-TYPE
    OBJECTS	{ eventSeverityLevel, mcrChassisIndex, mcrChassisSlotIndex,
                  mcrUserDefinedModuleName, mcrMediaPortNum }
    STATUS	current
    DESCRIPTION
        "Trap being sent indicates that an XFP module's +1.8v supply has 
        recovered to normal operating level. "
    ::= { mcrMGTMIBNotifications 224 }

mcrXfpLowVCC2Warn	NOTIFICATION-TYPE
    OBJECTS	{ eventSeverityLevel, mcrChassisIndex, mcrChassisSlotIndex,
                  mcrUserDefinedModuleName, mcrMediaPortNum }
    STATUS	current
    DESCRIPTION
        "Trap being sent indicates that an XFP module's +1.8v supply has gone 
        below the low +1.8v supply warning threshold. "
    ::= { mcrMGTMIBNotifications 225 }

mcrXfpLowVCC2WarnRecov	NOTIFICATION-TYPE
    OBJECTS	{ eventSeverityLevel, mcrChassisIndex, mcrChassisSlotIndex,
                  mcrUserDefinedModuleName, mcrMediaPortNum}
    STATUS	current
    DESCRIPTION
        "Trap being sent indicates that an XFP module's +1.8v supply has 
        recovered to normal operating level. "
    ::= { mcrMGTMIBNotifications 226 }
--
mcrXfpLowVCC2Alarm	NOTIFICATION-TYPE
    OBJECTS	{ eventSeverityLevel, mcrChassisIndex, mcrChassisSlotIndex,
                  mcrUserDefinedModuleName, mcrMediaPortNum}
    STATUS	current
    DESCRIPTION
        "Trap being sent indicates that an XFP module's +1.8v supply has gone 
        below the low +1.8v supply alarm threshold. "
    ::= { mcrMGTMIBNotifications 227 }

mcrXfpLowVCC2AlarmRecov	NOTIFICATION-TYPE
    OBJECTS	{ eventSeverityLevel, mcrChassisIndex, mcrChassisSlotIndex,
                  mcrUserDefinedModuleName, mcrMediaPortNum}
    STATUS	current
    DESCRIPTION
        "Trap being sent indicates that an XFP module's +1.8v supply has 
        recovered to normal operating level. "
    ::= { mcrMGTMIBNotifications 228 }

--- ****************************************************************************

mcrXfpHighVEE5Warn	NOTIFICATION-TYPE
    OBJECTS	{ eventSeverityLevel, mcrChassisIndex, mcrChassisSlotIndex,
                  mcrUserDefinedModuleName, mcrMediaPortNum }
    STATUS	current
    DESCRIPTION
        "Trap being sent indicates that an XFP module's -5.2v supply has 
        exceeded the high -5.2v supply warning threshold."
    ::= { mcrMGTMIBNotifications 229 }

mcrXfpHighVEE5WarnRecov	NOTIFICATION-TYPE
    OBJECTS	{ eventSeverityLevel, mcrChassisIndex, mcrChassisSlotIndex,
                  mcrUserDefinedModuleName, mcrMediaPortNum }
    STATUS	current
    DESCRIPTION
        "Trap being sent indicates that an XFP module's -5.2v supply has 
        recovered to normal operating level."
    ::= { mcrMGTMIBNotifications 230 }

mcrXfpHighVEE5Alarm	NOTIFICATION-TYPE
    OBJECTS	{ eventSeverityLevel, mcrChassisIndex, mcrChassisSlotIndex,
                  mcrUserDefinedModuleName, mcrMediaPortNum }
    STATUS	current
    DESCRIPTION
        "Trap being sent indicates that an XFP module's -5.2v supply has 
        exceeded the high -5.2v supply alarm threshold. "
    ::= { mcrMGTMIBNotifications 231 }

mcrXfpHighVEE5AlarmRecov	NOTIFICATION-TYPE
    OBJECTS	{ eventSeverityLevel, mcrChassisIndex, mcrChassisSlotIndex,
                  mcrUserDefinedModuleName, mcrMediaPortNum }
    STATUS	current
    DESCRIPTION
        "Trap being sent indicates that an XFP module's -5.2v supply has 
        recovered to normal operating level. "
    ::= { mcrMGTMIBNotifications 232 }

mcrXfpLowVEE5Warn	NOTIFICATION-TYPE
    OBJECTS	{ eventSeverityLevel, mcrChassisIndex, mcrChassisSlotIndex,
                  mcrUserDefinedModuleName, mcrMediaPortNum }
    STATUS	current
    DESCRIPTION
        "Trap being sent indicates that an XFP module's -5.2v supply has gone 
        below the low -5.2v supply warning threshold. "
    ::= { mcrMGTMIBNotifications 233 }

mcrXfpLowVEE5WarnRecov	NOTIFICATION-TYPE
    OBJECTS	{ eventSeverityLevel, mcrChassisIndex, mcrChassisSlotIndex,
                  mcrUserDefinedModuleName, mcrMediaPortNum}
    STATUS	current
    DESCRIPTION
        "Trap being sent indicates that an XFP module's -5.2v supply has 
        recovered to normal operating level. "
    ::= { mcrMGTMIBNotifications 234 }
--
mcrXfpLowVEE5Alarm	NOTIFICATION-TYPE
    OBJECTS	{ eventSeverityLevel, mcrChassisIndex, mcrChassisSlotIndex,
                  mcrUserDefinedModuleName, mcrMediaPortNum}
    STATUS	current
    DESCRIPTION
        "Trap being sent indicates that an XFP module's -5.2v supply has gone 
        below the low -5.2v supply alarm threshold. "
    ::= { mcrMGTMIBNotifications 235 }

mcrXfpLowVEE5AlarmRecov	NOTIFICATION-TYPE
    OBJECTS	{ eventSeverityLevel, mcrChassisIndex, mcrChassisSlotIndex,
                  mcrUserDefinedModuleName, mcrMediaPortNum}
    STATUS	current
    DESCRIPTION
        "Trap being sent indicates that an XFP module's -5.2v supply has 
        recovered to normal operating level. "
    ::= { mcrMGTMIBNotifications 236 }

--- ****************************************************************************

mcrSfpSpeedMismatch 	NOTIFICATION-TYPE
    OBJECTS	{ eventSeverityLevel, mcrChassisIndex, mcrChassisSlotIndex, mcrUserDefinedModuleName}
    STATUS	current
    DESCRIPTION
        "Trap being sent indicates that there is a speed mismatch between the 
        two SFP modules installed in the media converter."
    ::= { mcrMGTMIBNotifications  237 }

mcrSfpSpeedMismatchRecov 	NOTIFICATION-TYPE
    OBJECTS	{ eventSeverityLevel, mcrChassisIndex, mcrChassisSlotIndex, mcrUserDefinedModuleName}
    STATUS	current
    DESCRIPTION
        "Trap being sent indicates that the speed mismatch between the two SFP
        modules has recovered."
    ::= { mcrMGTMIBNotifications  238 }


mcrXfpPowerExceeded 	NOTIFICATION-TYPE
    OBJECTS	{ eventSeverityLevel, mcrChassisIndex, mcrChassisSlotIndex, mcrUserDefinedModuleName}
    STATUS	current
    DESCRIPTION
        "Trap being sent indicates that an XFP module's power requirements has 
        exceeded card capacity."
    ::= { mcrMGTMIBNotifications  239 }

mcrXfpPowerExceededRecov 	NOTIFICATION-TYPE
    OBJECTS	{ eventSeverityLevel, mcrChassisIndex, mcrChassisSlotIndex, mcrUserDefinedModuleName}
    STATUS	current
    DESCRIPTION
        "Trap being sent indicates that the XFP excessive power alarm has recovered."
    ::= { mcrMGTMIBNotifications  240 }

mcrLinkTestError 	NOTIFICATION-TYPE
    OBJECTS	{ eventSeverityLevel, mcrChassisIndex, mcrChassisSlotIndex, mcrUserDefinedModuleName}
    STATUS	current
    DESCRIPTION
        "Trap being sent indicates that the link test running on the media 
        converter has detected errors."
    ::= { mcrMGTMIBNotifications  241 }

mcrAlarmRelayEngaged	NOTIFICATION-TYPE
    OBJECTS	{ eventSeverityLevel, mcrChassisIndex}
    STATUS	current
    DESCRIPTION
        "Trap being sent indicates that the chassis alarm relay has engaged"
    ::= { mcrMGTMIBNotifications  242 }

mcrAlarmRelayDisengaged	NOTIFICATION-TYPE
    OBJECTS	{ eventSeverityLevel, mcrChassisIndex}
    STATUS	current
    DESCRIPTION
        "Trap being sent indicates that the chassis alarm relay has disengaged"
    ::= { mcrMGTMIBNotifications  243 }

mcrBandwidthLevelUpstreamLow	NOTIFICATION-TYPE
    OBJECTS	{ eventSeverityLevel, mcrChassisIndex, mcrChassisSlotIndex,
              mcrUserDefinedModuleName, mcrMediaPortNum, 
              mcrMediaPortBandwidth, mcrMediaPortBandwidthThreshold }
    STATUS	current
    DESCRIPTION
        "Trap being sent indicates the media port is in a low upstream bandwidth condition.  This happens when the bandwidth
        is below the configured threshold."
    ::= { mcrMGTMIBNotifications  244 }

mcrBandwidthLevelUpstreamRecov	NOTIFICATION-TYPE
    OBJECTS	{ eventSeverityLevel, mcrChassisIndex, mcrChassisSlotIndex,
              mcrUserDefinedModuleName, mcrMediaPortNum, 
              mcrMediaPortBandwidth, mcrMediaPortBandwidthThreshold }
    STATUS	current
    DESCRIPTION
        "Trap being sent indicates the media port has recovered from a low upstream bandwidth condition."
    ::= { mcrMGTMIBNotifications  245 }

mcrBandwidthLevelDownstreamLow	NOTIFICATION-TYPE
    OBJECTS	{ eventSeverityLevel, mcrChassisIndex, mcrChassisSlotIndex,
              mcrUserDefinedModuleName, mcrMediaPortNum, 
              mcrMediaPortBandwidth, mcrMediaPortBandwidthThreshold }
    STATUS	current
    DESCRIPTION
        "Trap being sent indicates the media port is in a low downstream bandwidth condition.  This happens when the bandwidth
        is below the configured threshold."
    ::= { mcrMGTMIBNotifications  246 }

mcrBandwidthLevelDownstreamRecov	NOTIFICATION-TYPE
    OBJECTS	{ eventSeverityLevel, mcrChassisIndex, mcrChassisSlotIndex,
              mcrUserDefinedModuleName, mcrMediaPortNum, 
              mcrMediaPortBandwidth, mcrMediaPortBandwidthThreshold }
    STATUS	current
    DESCRIPTION
        "Trap being sent indicates the media port has recovered from a low downstream bandwidth condition."
    ::= { mcrMGTMIBNotifications  247 }

mcrMediaRemoteReset	NOTIFICATION-TYPE
    OBJECTS	{ eventSeverityLevel, mcrChassisIndex, mcrChassisSlotIndex,
                  mcrUserDefinedModuleName }
    STATUS	current
    DESCRIPTION
        "Trap being sent indicates that the media converter module's peer has been manually reset by a user
         managing the unit. "
    ::= { mcrMGTMIBNotifications 248 }


--  end of mcrMGTMIBNotifications
--


--
-- mcrMGTMIBConformance
--
mcrMGTMIBCompliances OBJECT IDENTIFIER
    ::= {   mcrMGTMIBConformance 1 }

mcrMGTMIBGroups       OBJECT IDENTIFIER
    ::= { mcrMGTMIBConformance 2 }

--
-- compliance statements
--
--

mcrMGTMIBCompliance MODULE-COMPLIANCE
    STATUS       current
    DESCRIPTION
        "The compliance statement for mcrMGT which implement
         the Perle Managed Media Converters MIB."
    MODULE    -- this module
    MANDATORY-GROUPS {
        mcrMGTMIBChassisGroup,
        mcrMGTMIBMediaGroup,
        mcrMGTMIBMgtGroup,
        mcrMGTMIBNotificationsGroup
    }
    ::= {  mcrMGTMIBCompliances  1 }


-- units of conformance
--
-- mcrMGTMIBChassisGroup
--
mcrMGTMIBChassisGroup  OBJECT-GROUP
    OBJECTS {
        mcrChassisIndex, mcrChassisSlotIndex, mcrPsmuIndex,

        chassisModelName,chassisModelDesc	,chassisSerialNumber,chassisBootloaderVersion,
        chassisFirmwareVersion,chassisOutStandWarnAlarms,
        chassisDiagStatus,chassisTemperature,chassisCfgHighTempThreshold,chassisReset,
        chassisCfgMgmtSlot,

        mcrPsmuModelName,mcrPsmuModelDesc,mcrPsmuPsuSerialNumber,mcrPsmuBootloaderVersion,
        mcrPsmuFirmwareVersion,mcrPsmuOutStandWarnAlarms,mcrPsmuPsuStatus,
        mcrPsmuPsuVoltage,mcrPsmuPsuPowerUsage,mcrPsmuFanStatus,mcrPsmuFanSpeed,

        mcrUserDefinedModuleName,mcrModuleModelName,mcrUnManagedModuleSlotName,mcrModuleSerialNumber,
        mcrModuleBootloaderVersion,mcrModuleFirmwareVersion,mcrModuleoOutStandWarnAlarms,mcrModuleDiagStatus,
        mcrModuleTypeInserted,mcrMediaConfigBackupRestore,mcrMediaBackedupModuleType,mcrChassisPwrUpSlotPwrState,
        mcrCurrentPowerState,mcrPowerScheduleEnable,mcrModuleReset,mcrModuleResetToFactory,mcrModuleModelDesc,

        alarmWarnSeverity, alarmWarnType, alarmWarnFlags,
        alarmWarnChassisNum, alarmWarnDeviceNum, alarmWarnTimeStamp, alarmWarnMessage, alarmWarnPortNum,

        moduleModel, portName, portEnable, portType, portLinkStatus, portConnType, portAutoNegState,
        portSpeed, portDuplex, portPause, portRemoteStatus, portMediaType, portPhysicalProtocol

    }
    STATUS       current
    DESCRIPTION
        "The group of objects for identifying and determining the configuration and
         current timeliness values of the Perle Managed Media Converters chassis."
    ::= { mcrMGTMIBGroups 1 }
--
-- end of  mcrMGTMIBChassisGroup
--
--
-- mcrMGTMIBMediaGroup
--
mcrMGTMIBMediaGroup  OBJECT-GROUP
    OBJECTS {
        cm1000Modelname,cm1000ModelDesc	,cm1000HwJmp5ConfigMode	,cm1000HwSw1FiberAutoNeg,
        cm1000HwSw2LinkMode,cm1000HwSw3FiberFaultAlert,cm1000HwSw4Duplex,cm1000HwSw5Pause,cm1000HwSw6Loopback,
        cm1000FiberLinkStatus,cm1000FiberConnType,cm1000FiberAutoNegState,cm1000FiberSpeed,
        cm1000FiberDuplex,cm1000FiberPauseEnh,cm1000FiberLPRFStatus,cm1000FiberReceiveStatus,cm1000FiberLoopBack,
        cm1000CopperLinkStatus,cm1000CopperConnType,cm1000CopperAutoNegState,cm1000CopperSpeed,
        cm1000CopperDuplex,cm1000CopperCrossOver,cm1000CopperPauseEnh,cm1000CopperLPRFStatus,

        cm1000ConfigStatus,cm1000ConfigModuleName,cm1000ConfigLinkMode,cm1000ConfigFiberFaultAlert,
        cm1000ConfigJumboPackets,cm1000ConfigFiberPortName,cm1000ConfigFiberPortEnable,
        cm1000ConfigFiberAutoNeg,cm1000ConfigCopperPortName,cm1000ConfigCopperPortEnable,
        cm1000ConfigCopperDuplex,cm1000ConfigCopperPauseEnh,cm1000ConfigCopperLowPower,

        cm1000LedPWR,cm1000LedLKF,cm1000LedLKC,

        cm1000mmModelname,cm1000mmModelDesc	,cm1000mmHwJmp5ConfigMode	,
        cm1000mmHwSw1FiberAutoNeg,
        cm1000mmHwSw2LinkMode,
        cm1000mmHwSw3FiberFaultAlert,
        cm1000mmHwSw4Loopback1,
        cm1000mmHwSw5Loopback2,
        cm1000mmFiber1LinkStatus,cm1000mmFiber1ConnType,cm1000mmFiber1AutoNegState,cm1000mmFiber1Speed,
        cm1000mmFiber1Duplex,cm1000mmFiber1PauseEnh,cm1000mmFiber1LPRFStatus,cm1000mmFiber1ReceiveStatus,
        cm1000mmFiber2LinkStatus,cm1000mmFiber2ConnType,cm1000mmFiber2AutoNegState,cm1000mmFiber2Speed,
        cm1000mmFiber2Duplex,cm1000mmFiber2PauseEnh,cm1000mmFiber2LPRFStatus,cm1000mmFiber2ReceiveStatus,

        cm1000mmFiberLoopBack,

        cm1000mmConfigStatus,cm1000mmConfigModuleName,cm1000mmConfigLinkMode,cm1000mmConfigFiberFaultAlert,
        cm1000mmConfigJumboPackets,cm1000mmConfigFiberAutoNeg,
        cm1000mmConfigFiber1PortName,cm1000mmConfigFiber1PortEnable,
        cm1000mmConfigFiber2PortName,cm1000mmConfigFiber2PortEnable,

        cm1000mmLedPWR,cm1000mmLedLK1,cm1000mmLedLK2,

        cm100ModelName,cm100ModelDesc	,cm100HwJmp5ConfigMode,cm100HwJmp6AutoMDI,cm100HwSw1AutoNegotiation,
        cm100HwSw2LinkMode,cm100HwSw3FarEndFault,cm100HwSw5Pause,cm100HwSw6Loopback,cm100FiberLinkStatus,
        cm100FiberConnType,cm100FiberSpeed,cm100FiberFarEndFault,cm100FiberReceiveStatus,cm100FiberLoopBack,
        cm100CopperLinkStatus,cm100CopperConnType,cm100CopperAutoNegState,cm100CopperSpeed,cm100CopperDuplex,
        cm100CopperCrossOver,cm100CopperPause,cm100CopperLPRFStatus,

        cm100ConfigStatus,cm100ConfigModuleName,cm100ConfigLinkMode,cm100ConfigFiberFarEndFault,
        cm100ConfigFiberPortName,cm100ConfigFiberPortEnable,cm100ConfigCopperPortName,
        cm100ConfigCopperPortEnable,cm100ConfigCopperAutoNegotiation,cm100ConfigCopperCrossOver,
        cm100ConfigCopperPause,

        cm100LedPWR,cm100LedLKC,cm100LedLKF,

        cm100mmModelName,cm100mmModelDesc	,cm100mmHwJmp5ConfigMode,
        cm100mmHwSw1LinkPassthrough,
        cm100mmHwSw2FarEndFault,
        cm100mmHwSw3Loopback1,
        cm100mmHwSw4Loopback2,
        cm100mmFiber1LinkStatus,cm100mmFiber1ConnType,cm100mmFiber1Speed,cm100mmFiber1FarEndFault,cm100mmFiber1ReceiveStatus,
        cm100mmFiber2LinkStatus,cm100mmFiber2ConnType,cm100mmFiber2Speed,cm100mmFiber2FarEndFault,cm100mmFiber2ReceiveStatus,
        cm100mmFiberLoopBack,
        cm100mmConfigStatus,cm100mmConfigModuleName,cm100mmConfigLinkMode,cm100mmConfigFiberFarEndFault,
        cm100mmConfigFiber1PortName,cm100mmConfigFiber1PortEnable,
        cm100mmConfigFiber2PortName,cm100mmConfigFiber2PortEnable,

        cm100mmLedPWR,cm100mmLedLK1,cm100mmLedLK2,

        cm1110ModelName,cm1110ModelDesc	,cm1110HwJmp5ConfigMode,cm1110HwJmp6AutoMDIX,cm1110HwSw1TpAutoNegotiation,
        cm1110HwSw2LinkMode,cm1110HwSw3FiberFaultAlert,cm1110HwSw4TpDuplex,cm1110HwSw5TpSpeed,
        cm1110HwSw6FiberAutoNegotiation,cm1110HwSw6FiberSfp100Duplex,cm1110HwSw7Loopback,cm1110FiberLinkStatus,cm1110FiberConnType,
        cm1110FiberAutoNegState,cm1110FiberSpeed,cm1110FiberDuplex,cm1110FiberPauseEnh,
        cm1110FiberLPRFStatus,cm1110FiberSfp100FarEndFault,cm1110FiberReceiveStatus,cm1110FiberLoopBack	,cm1110CopperLinkStatus,cm1110CopperConnType,
        cm1110CopperAutoNegState,cm1110CopperSpeed,cm1110CopperDuplex,cm1110CopperCrossOver,
        cm1110CopperPauseEnh,cm1110CopperLPRFStatus,cm1110CopperAutoSpeedDownshift,

        cm1110ConfigStatus,cm1110ConfigModuleName,cm1110ConfigLinkMode,cm1110ConfigFiberFaultAlert,
        cm1110ConfigMaxPacketsSize,cm1110ConfigFiberPortName,cm1110ConfigFiberPortEnable,
        cm1110ConfigFiberAutoNegotiation,cm1110ConfigFiberSfp100duplex,cm1110ConfigCopperPortName,cm1110ConfigCopperPortEnable,
        cm1110ConfigCopperAutoNegotiation,cm1110ConfigCopperAutoNegAdv10HDX,cm1110ConfigCopperAutoNegAdv10FDX,
        cm1110ConfigCopperAutoNegAdv100HDX,cm1110ConfigCopperAutoNegAdv100FDX,cm1110ConfigCopperAutoNegAdv1000FDX,
        cm1110ConfigCopperSpeed,cm1110ConfigCopperDuplex,cm1110ConfigCopperCrossOver,
        cm1110ConfigCopperPauseEnh,cm1110ConfigCopperAutoSpeedDownshift,cm1110ConfigCopper10BaseTDistance,

        cm1110ConfigUnidirectionalEthernet	,
        cm1110ConfigPriorityToEgressQueueMap0	,
        cm1110ConfigPriorityToEgressQueueMap1	,
        cm1110ConfigPriorityToEgressQueueMap2	,
        cm1110ConfigPriorityToEgressQueueMap3	,
        cm1110ConfigPriorityToEgressQueueMap4	,
        cm1110ConfigPriorityToEgressQueueMap5	,
        cm1110ConfigPriorityToEgressQueueMap6	,
        cm1110ConfigPriorityToEgressQueueMap7	,
        cm1110ConfigCopper8021pPriority			,
        cm1110ConfigCopperIpTosPriority			,
        cm1110ConfigCopperPriorityPrecedence	,
        cm1110ConfigCopperCongestionPolicy		,
        cm1110ConfigCopperPriorityMap0			,
        cm1110ConfigCopperPriorityMap1			,
        cm1110ConfigCopperPriorityMap2			,
        cm1110ConfigCopperPriorityMap3			,
        cm1110ConfigCopperPriorityMap4			,
        cm1110ConfigCopperPriorityMap5			,
        cm1110ConfigCopperPriorityMap6			,
        cm1110ConfigCopperPriorityMap7			,
        cm1110ConfigCopperIngressLimit			,
        cm1110ConfigCopperEgressLimit			,
        cm1110ConfigCopperDiscardTaggedFrames	,
        cm1110ConfigCopperDiscardUntaggedFrames,
        cm1110ConfigCopperDefaultVlanId			,
        cm1110ConfigCopperDefaultPriority		,
        cm1110ConfigCopperVlanTaggingAction		,
        cm1110ConfigCopperFilterUnknownMulticast,
        cm1110ConfigCopperFilterUnknownUnicast	,
        cm1110ConfigFiber8021pPriority			,
        cm1110ConfigFiberIpTosPriority			,
        cm1110ConfigFiberPriorityPrecedence	    ,
        cm1110ConfigFiberCongestionPolicy		,
        cm1110ConfigFiberPriorityMap0			,
        cm1110ConfigFiberPriorityMap1			,
        cm1110ConfigFiberPriorityMap2			,
        cm1110ConfigFiberPriorityMap3			,
        cm1110ConfigFiberPriorityMap4			,
        cm1110ConfigFiberPriorityMap5			,
        cm1110ConfigFiberPriorityMap6			,
        cm1110ConfigFiberPriorityMap7			,
        cm1110ConfigFiberIngressLimit			,
        cm1110ConfigFiberEgressLimit			,
        cm1110ConfigFiberDiscardTaggedFrames	,
        cm1110ConfigFiberDiscardUntaggedFrames	,
        cm1110ConfigFiberDefaultVlanId			,
        cm1110ConfigFiberDefaultPriority		,
        cm1110ConfigFiberVlanTaggingAction		,
        cm1110ConfigFiberFilterUnknownMulticast	,
        cm1110ConfigFiberFilterUnknownUnicast	,
        cm1110ConfigFiberSgmiiInterface ,

        cm1110LedPWR,cm1110LedFDF,cm1110LedLKF,cm1110LedCopperSpeed,cm1110LedFDC,cm1110LedLKC,

        cm1110PortInDiscards,cm1110PortInFiltered,cm1110PortInGoodOctets,cm1110PortHCInGoodOctets,
        cm1110PortInBadOctets,cm1110PortInUnicasts,cm1110PortInBroadcasts,cm1110PortInMulticasts,
        cm1110PortInPauses,cm1110PortInUnderSizes,cm1110PortInFragments,cm1110PortInOversizes,
        cm1110PortInJabbers,cm1110PortInRxErrs,cm1110PortInFcsErrs,cm1110PortPkts64Octets,
        cm1110PortPkts65to127Octets,cm1110PortPkts128to255Octets,cm1110PortPkts256to511Octets,
        cm1110PortPkts512to1023Octets,cm1110PortPkts1024toMaxOctets,cm1110PortOutOctets,
        cm1110PortHCOutOctets,cm1110PortOutFiltered,cm1110PortOutUnicasts,cm1110PortOutBroadcasts,
        cm1110PortOutMulticasts,cm1110PortOutPauses,cm1110PortDeferreds,cm1110PortCollisions,
        cm1110PortSingles,cm1110PortMultiples,cm1110PortExcessives,cm1110PortLates,cm1110PortOutFcsErrs,
        cm1110PortResetCounters,

        cm1110AvctStart,cm1110AvctStatus,cm1110AvctTxRxPair1Results,cm1110AvctTxRxPair1Amplitude,
        cm1110AvctTxRxPair1Distance,cm1110AvctTxRxPair2Results,cm1110AvctTxRxPair2Amplitude,
        cm1110AvctTxRxPair2Distance,cm1110AvctTxRxPair3Results,cm1110AvctTxRxPair3Amplitude,
        cm1110AvctTxRxPair3Distance,cm1110AvctTxRxPair4Results,cm1110AvctTxRxPair4Amplitude,
        cm1110AvctTxRxPair4Distance,

        cm110Modelname,cm110ModelDesc	,cm110HwJmp5ConfigMode,cm110HwJmp6AutoMDIX,cm110HwSw1TpAutoNegotiation,
        cm110HwSw2LinkMode,cm110HwSw3FarEndFault,cm110HwSw4TpDuplex,cm110HwSw5TpSpeed,
        cm110HwSw6FiberDuplex,cm110HwSw7Loopback,cm110FiberLinkStatus,cm110FiberConnType,
        cm110FiberSpeed,cm110FiberFarEndFault,cm110FiberReceiveStatus,cm110FiberLoopBack	,cm110CopperLinkStatus,
        cm110CopperConnType,cm110CopperAutoNegState,cm110CopperSpeed,cm110CopperDuplex,
        cm110CopperCrossOver,cm110CopperPause,cm110CopperLPRFStatus,

        cm110ConfigStatus,cm110ConfigModuleName,cm110ConfigLinkMode,cm110ConfigFiberFarEndFault,
        cm110ConfigMaxPacketSize,cm110ConfigFiberPortName,cm110ConfigFiberPortEnable,cm110ConfigFiberDuplex,
        cm110ConfigCopperPortName,cm110ConfigCopperPortEnable,cm110ConfigCopperAutoNegotiation,
        cm110ConfigCopperAutoNegAdv10HDX,cm110ConfigCopperAutoNegAdv10FDX,cm110ConfigCopperAutoNegAdv100HDX,
        cm110ConfigCopperAutoNegAdv100FDX,cm110ConfigCopperSpeed,cm110ConfigCopperDuplex,
        cm110ConfigCopperCrossOver,cm110ConfigCopperPause,cm110ConfigCopperExtendDistance,

        cm110ConfigUnidirectionalEthernet	,
        cm110ConfigPriorityToEgressQueueMap0	,
        cm110ConfigPriorityToEgressQueueMap1	,
        cm110ConfigPriorityToEgressQueueMap2	,
        cm110ConfigPriorityToEgressQueueMap3	,
        cm110ConfigPriorityToEgressQueueMap4	,
        cm110ConfigPriorityToEgressQueueMap5	,
        cm110ConfigPriorityToEgressQueueMap6	,
        cm110ConfigPriorityToEgressQueueMap7	,
        cm110ConfigCopper8021pPriority			,
        cm110ConfigCopperIpTosPriority			,
        cm110ConfigCopperPriorityPrecedence	,
        cm110ConfigCopperCongestionPolicy		,
        cm110ConfigCopperPriorityMap0			,
        cm110ConfigCopperPriorityMap1			,
        cm110ConfigCopperPriorityMap2			,
        cm110ConfigCopperPriorityMap3			,
        cm110ConfigCopperPriorityMap4			,
        cm110ConfigCopperPriorityMap5			,
        cm110ConfigCopperPriorityMap6			,
        cm110ConfigCopperPriorityMap7			,
        cm110ConfigCopperIngressLimit			,
        cm110ConfigCopperEgressLimit			,
        cm110ConfigCopperDiscardTaggedFrames	,
        cm110ConfigCopperDiscardUntaggedFrames,
        cm110ConfigCopperDefaultVlanId			,
        cm110ConfigCopperDefaultPriority		,
        cm110ConfigCopperVlanTaggingAction		,
        cm110ConfigCopperFilterUnknownMulticast,
        cm110ConfigCopperFilterUnknownUnicast	,
        cm110ConfigFiber8021pPriority			,
        cm110ConfigFiberIpTosPriority			,
        cm110ConfigFiberPriorityPrecedence		,
        cm110ConfigFiberCongestionPolicy		,
        cm110ConfigFiberPriorityMap0			,
        cm110ConfigFiberPriorityMap1			,
        cm110ConfigFiberPriorityMap2			,
        cm110ConfigFiberPriorityMap3			,
        cm110ConfigFiberPriorityMap4			,
        cm110ConfigFiberPriorityMap5			,
        cm110ConfigFiberPriorityMap6			,
        cm110ConfigFiberPriorityMap7			,
        cm110ConfigFiberIngressLimit			,
        cm110ConfigFiberEgressLimit			,
        cm110ConfigFiberDiscardTaggedFrames	,
        cm110ConfigFiberDiscardUntaggedFrames	,
        cm110ConfigFiberDefaultVlanId			,
        cm110ConfigFiberDefaultPriority		,
        cm110ConfigFiberVlanTaggingAction		,
        cm110ConfigFiberFilterUnknownMulticast	,
        cm110ConfigFiberFilterUnknownUnicast	,

        cm110LedPWR,cm110LedFDF,cm110LedLKF,cm110LedCopperSpeed,cm110LedFDC,cm110LedLKC,

        cm110PortRxErrors,cm110PortTxCollisions,cm110PortInFiltered,cm110PortInGoodOctets,
        cm110PortInBadOctets,cm110PortInUnicasts,cm110PortInBroadcasts,cm110PortInMulticasts,
        cm110PortInPauses,cm110PortInUnderSizes,cm110PortInFragments,cm110PortInOversizes,
        cm110PortInJabbers,cm110PortInMACRcvErrs,cm110PortInFcsErrs,cm110PortPkts64Octets,
        cm110PortPkts65to127Octets,cm110PortPkts128to255Octets,cm110PortPkts256to511Octets,
        cm110PortPkts512to1023Octets,cm110PortPkts1024toMaxOctets,cm110PortOutOctets,
        cm110PortOutUnicasts,cm110PortOutBroadcasts,cm110PortOutMulticasts,cm110PortOutPauses,
        cm110PortExcessives,cm110PortCollisions,cm110PortDeferreds,cm110PortSingles,cm110PortMultiples,
        cm110PortOutFcsErrs,cm110PortLates,cm110PortResetCounters,

        cm110VctStart,cm110VctStatus,cm110VctTxPairResults,cm110VctTxPairAmplitude,cm110VctTxPairDistance,
        cm110VctRxPairResults,cm110VctRxPairAmplitude,cm110VctRxPairDistance,

        mcrMgtModelName,mcrMgtModelDesc,mcrMgtFailSafeBootLoaderVer	,mcrMgtUpTime,mcrMgtConsoleDSR,

        mcrMgtConfigStatus,mcrMgtConfigEthSpeedDuplex,mcrMgtConfigEthCrossover,mcrMgtConfigConsolePortEnabled,
        mcrMgtConfigConsoleSpeed,mcrMgtConfigConsoleDataBits,mcrMgtConfigConsoleParity,
        mcrMgtConfigConsoleStopBits,mcrMgtConfigConsoleFlowControl,mcrMgtConfigConsoleMonitorDSR,

        mcrMgtLedPWR,mcrMgtLedALM,mcrMgtLedLKC,mcrMgtLedCopperSpeed,

        cm10gModelname,cm10gModelDesc	,cm10gHwJmp5ConfigMode	,
        cm10gHwSw1OperationMode,
        cm10gHwSw2LinkMode,
        cm10gHwSw3FiberFaultAlert,
        cm10gHwSw4Port1EdcMode,
        cm10gHwSw5Port2EdcMode,
        cm10gPort1LinkStatus,cm10gPort1ConnType,cm10gPort1AutoNegState,cm10gPort1Speed,
        cm10gPort1Duplex,cm10gPort1PauseEnh,cm10gPort1ReceiveStatus,
        cm10gPort2LinkStatus,cm10gPort2ConnType,cm10gPort2AutoNegState,cm10gPort2Speed,
        cm10gPort2Duplex,cm10gPort2PauseEnh,cm10gPort2ReceiveStatus,
        cm10gPortLoopBack,cm10gPortTestMode,

        

        cm10gConfigStatus,cm10gConfigModuleName,cm10gConfigLinkMode,cm10gConfigFiberFaultAlert,cm10gConfigFiberAutoNeg,
        cm10gConfigPort1Name,cm10gConfigPort1Enable, cm10gConfigPort1EdcMode, cm10gConfigPort1FecEnable,        
        cm10gConfigPort1FecAmplitude, cm10gConfigPort1FecPhase, cm10gConfigPort1WavelengthEnable, cm10gConfigPort1WavelengthValue,  
        cm10gConfigPort1ChannelEnable, cm10gConfigPort1ChannelNumber, cm10gConfigPort1TxDitherEnable, cm10gConfigPort1TxDitherValue,    
                                             
        cm10gConfigPort2Name,cm10gConfigPort2Enable, cm10gConfigPort2EdcMode, cm10gConfigPort2FecEnable,        
        cm10gConfigPort2FecAmplitude, cm10gConfigPort2FecPhase, cm10gConfigPort2WavelengthEnable, cm10gConfigPort2WavelengthValue,  
        cm10gConfigPort2ChannelEnable, cm10gConfigPort2ChannelNumber, cm10gConfigPort2TxDitherEnable, cm10gConfigPort2TxDitherValue,

        cm10gLedPWR,cm10gLedLK1,cm10gLedLK2,
        
        exCMModelName,
        exCMModelDesc,
        exCMHwJmp5ConfigMode,
        exCMHwSw1AutoLocalRemote,
        exCMHwSw2Rate,
        exCMHwSw3SymmetricAsymmetric,
        exCMHwSw4SnrRatio,
        exCMHwSw5Loopback,
        exCMHwSw6EthAutoNeg,
        exCMHwSw7EthSpeed,
        exCMHwSw8EthDuplex,
        exCMHwSw9LinkMode,
        exCMHwSw10InterlinkFaultFeedback,
        
        exCMVdslLinkStatus,
        exCMVdslConnType,
        exCMVdslLoopBack,
        exCMVdslRole,
        exCMVdslProfile,
        exCMVdslBitswapping,

        exCMVdslStatusAttainableDataRateUp,
        exCMVdslStatusAttainableDataRateDown,

        exCMVdslStatusActualDataRateUp,
        exCMVdslStatusActualDataRateDown,

        exCMVdslStatusPrevDataRateUp,
        exCMVdslStatusPrevDataRateDown,

        exCMVdslStatusActualSnrUp,
        exCMVdslStatusActualSnrDown,
        exCMVdslStatusActualSnrUs0,
        exCMVdslStatusActualSnrUs1,
        exCMVdslStatusActualSnrDs1,
        exCMVdslStatusActualSnrUs2,
        exCMVdslStatusActualSnrDs2,
        exCMVdslStatusActualSnrUs3,
        exCMVdslStatusActualSnrDs3,
        exCMVdslStatusActualSnrUs4,
        exCMVdslStatusActualSnrDs4,

        exCMVdslStatusActualSignalAttenuationUp,
        exCMVdslStatusActualSignalAttenuationDown,
        exCMVdslStatusActualSignalAttenuationUs0,
        exCMVdslStatusActualSignalAttenuationUs1,
        exCMVdslStatusActualSignalAttenuationDs1,
        exCMVdslStatusActualSignalAttenuationUs2,
        exCMVdslStatusActualSignalAttenuationDs2,
        exCMVdslStatusActualSignalAttenuationUs3,
        exCMVdslStatusActualSignalAttenuationDs3,
        exCMVdslStatusActualSignalAttenuationUs4,
        exCMVdslStatusActualSignalAttenuationDs4,

        exCMVdslStatusActualLineAttenuationUp,
        exCMVdslStatusActualLineAttenuationDown,
        exCMVdslStatusActualLineAttenuationUs0,
        exCMVdslStatusActualLineAttenuationUs1,
        exCMVdslStatusActualLineAttenuationDs1,
        exCMVdslStatusActualLineAttenuationUs2,
        exCMVdslStatusActualLineAttenuationDs2,
        exCMVdslStatusActualLineAttenuationUs3,
        exCMVdslStatusActualLineAttenuationDs3,
        exCMVdslStatusActualLineAttenuationUs4,
        exCMVdslStatusActualLineAttenuationDs4,

        exCMVdslStatusActualInterleaveDelayUp,
        exCMVdslStatusActualInterleaveDelayDown,

        exCMVdslStatusActualInpUp,
        exCMVdslStatusActualInpDown,

        exCMVdslStatusActualInterleavingDepthUp,
        exCMVdslStatusActualInterleavingDepthDown,

        exCMVdslStatusActualInterleavingBlockUp,
        exCMVdslStatusActualInterleavingBlockDown,

        exCMVdslStatusActualTransmitPowerUp,
        exCMVdslStatusActualTransmitPowerDown,

        exCMVdslStatusMaxDataRateUp,
        exCMVdslStatusMaxDataRateDown,

        exCMVdslStatusMinDataRateUp,
        exCMVdslStatusMinDataRateDown,

        exCMVdslStatusTargetSnrUp,
        exCMVdslStatusTargetSnrDown,

        exCMVdslStatusMaxInterleaveDelayUp,
        exCMVdslStatusMaxInterleaveDelayDown,

        exCMVdslStatusMinInpUp,
        exCMVdslStatusMinInpDown,
        exCMVdslRemoteLoopback,
        exCMVdslRemoteReset,

        exCMEthernetLinkStatus,
        exCMEthernetConnType,
        exCMEthernetAutoNegState,
        exCMEthernetSpeed,
        exCMEthernetDuplex,
        exCMEthernetCrossOver,
        exCMEthernetPauseEnh,
        exCMEthernetLPRFStatus,
        exCMEthernetAutoSpeedDownshift,
        exCMEthernetMDI,
        exCMVdslFirmwareVersion,
        exCMVdslFirmwareDate,
        exCMVdslFirmwareDateString,
 
        exCMConfigStatus,

        exCMConfigModuleName,
        exCMConfigLinkMode,
        exCMConfigInterlinkFaultFeedback,

        exCMConfigVdslPortName,
        exCMConfigVdslPortEnable,

        exCMConfigVdslProfileMode,
        exCMConfigVdslRole,
        exCMConfigVdslRate,
        exCMConfigVdslSymmetry,

        exCMConfigVdslProfile,
        exCMConfigVdslOverrideProfile,

        exCMConfigVdslSignalToNoiseRatioUp,
        exCMConfigVdslMinDataRateUp,
        exCMConfigVdslMaxDataRateUp,
        exCMConfigVdslMaxInterleaveDelayUp,
        exCMConfigVdslMinInpUp,

        exCMConfigVdslSignalToNoiseRatioDown,
        exCMConfigVdslMinDataRateDown,
        exCMConfigVdslMaxDataRateDown,
        exCMConfigVdslMaxInterleaveDelayDown,
        exCMConfigVdslMinInpDown,

        exCMConfigVdslBitswapping,

        exCMConfigVdslLowBandwidthAlarmUp,
        exCMConfigVdslLowBandwidthAlarmDown,

        exCMConfigEthernetPortName,
        exCMConfigEthernetPortEnable,
        exCMConfigEthernetAutoNegotiation,
        exCMConfigEthernetAutoNegAdv10HDX,
        exCMConfigEthernetAutoNegAdv10FDX,
        exCMConfigEthernetAutoNegAdv100HDX,
        exCMConfigEthernetAutoNegAdv100FDX,
        exCMConfigEthernetAutoNegAdv1000FDX,
        exCMConfigEthernetSpeed,
        exCMConfigEthernetDuplex,
        exCMConfigEthernetCrossOver,
        exCMConfigEthernetPauseEnh,
        exCMConfigEthernetAutoSpeedDownshift,
        exCMConfigEthernet10BaseTDistance,

        exCMConfigUnidirectionalEthernet,
        exCMConfigPriorityToEgressQueueMap0,
        exCMConfigPriorityToEgressQueueMap1,
        exCMConfigPriorityToEgressQueueMap2,
        exCMConfigPriorityToEgressQueueMap3,
        exCMConfigPriorityToEgressQueueMap4,
        exCMConfigPriorityToEgressQueueMap5,
        exCMConfigPriorityToEgressQueueMap6,
        exCMConfigPriorityToEgressQueueMap7,

        exCMConfigEthernet8021pPriority,
        exCMConfigEthernetIpTosPriority,
        exCMConfigEthernetPriorityPrecedence,
        exCMConfigEthernetCongestionPolicy,

        exCMConfigEthernetPriorityMap0,
        exCMConfigEthernetPriorityMap1,
        exCMConfigEthernetPriorityMap2,
        exCMConfigEthernetPriorityMap3,
        exCMConfigEthernetPriorityMap4,
        exCMConfigEthernetPriorityMap5,
        exCMConfigEthernetPriorityMap6,
        exCMConfigEthernetPriorityMap7,

        exCMConfigEthernetIngressLimit,
        exCMConfigEthernetEgressLimit,
        exCMConfigEthernetDiscardTaggedFrames,
        exCMConfigEthernetDiscardUntaggedFrames,
        exCMConfigEthernetDefaultVlanId,
        exCMConfigEthernetDefaultPriority,
        exCMConfigEthernetVlanTaggingAction,
        exCMConfigEthernetFilterUnknownMulticast,
        exCMConfigEthernetFilterUnknownUnicast,

        exCMConfigVdsl8021pPriority,
        exCMConfigVdslIpTosPriority,
        exCMConfigVdslPriorityPrecedence,
        exCMConfigVdslCongestionPolicy,

        exCMConfigVdslPriorityMap0,
        exCMConfigVdslPriorityMap1,
        exCMConfigVdslPriorityMap2,
        exCMConfigVdslPriorityMap3,
        exCMConfigVdslPriorityMap4,
        exCMConfigVdslPriorityMap5,
        exCMConfigVdslPriorityMap6,
        exCMConfigVdslPriorityMap7,

        exCMConfigVdslIngressLimit,
        exCMConfigVdslEgressLimit,
        exCMConfigVdslDiscardTaggedFrames,
        exCMConfigVdslDiscardUntaggedFrames,
        exCMConfigVdslDefaultVlanId,
        exCMConfigVdslDefaultPriority,
        exCMConfigVdslVlanTaggingAction,
        exCMConfigVdslFilterUnknownMulticast,
        exCMConfigVdslFilterUnknownUnicast,
        
        exCMConfigVdslFastMode,
        
        exCMLedILNK, exCMLedLOC, exCMLedPWR, exCMLedETH, exCMLedRMT,
        

        exCMPortInDiscards,
        exCMPortInFiltered,
        exCMPortInGoodOctets,
        exCMPortHCInGoodOctets,
        exCMPortInBadOctets,
        exCMPortInUnicasts,
        exCMPortInBroadcasts,
        exCMPortInMulticasts,
        exCMPortInPauses,
        exCMPortInUnderSizes,
        exCMPortInFragments,
        exCMPortInOversizes,
        exCMPortInJabbers,
        exCMPortInRxErrs,
        exCMPortInFcsErrs,
        exCMPortPkts64Octets,
        exCMPortPkts65to127Octets,
        exCMPortPkts128to255Octets,
        exCMPortPkts256to511Octets,
        exCMPortPkts512to1023Octets,
        exCMPortPkts1024toMaxOctets,
        exCMPortOutOctets,
        exCMPortHCOutOctets,
        exCMPortOutFiltered,
        exCMPortOutUnicasts,
        exCMPortOutBroadcasts,
        exCMPortOutMulticasts,
        exCMPortOutPauses,
        exCMPortDeferreds,
        exCMPortCollisions,
        exCMPortSingles,
        exCMPortMultiples,
        exCMPortExcessives,
        exCMPortLates,
        exCMPortOutFcsErrs,
        exCMPortResetCounters,
        
        exCMVdslStatsTimePeriod,
        exCMVdslStatsFullInitLocal,
        exCMVdslStatsCodeViolationLocal,
        exCMVdslStatsCorrectedLocal,
        exCMVdslStatsFecSecsLocal,
        exCMVdslStatsErroredSecsLocal,
        exCMVdslStatsSeverelyErroredSecsLocal,
        exCMVdslStatsLossOfSignalSecsLocal,
        exCMVdslStatsUnavailableSecsLocal,
        exCMVdslStatsTimeElapsedLocal,
        exCMVdslStatsFullInitRemote,
        exCMVdslStatsCodeViolationRemote,
        exCMVdslStatsCorrectedRemote,
        exCMVdslStatsFecSecsRemote,
        exCMVdslStatsErroredSecsRemote,
        exCMVdslStatsSeverelyErroredSecsRemote,
        exCMVdslStatsLossOfSignalSecsRemote,
        exCMVdslStatsUnavailableSecsRemote,
        exCMVdslStatsTimeElapsedRemote,
        
        exCMAvctStart,
        exCMAvctStatus,
        exCMAvctTxRxPair1Results,
        exCMAvctTxRxPair1Amplitude,
        exCMAvctTxRxPair1Distance,
        exCMAvctTxRxPair2Results,
        exCMAvctTxRxPair2Amplitude,
        exCMAvctTxRxPair2Distance,
        exCMAvctTxRxPair3Results,
        exCMAvctTxRxPair3Amplitude,
        exCMAvctTxRxPair3Distance,
        exCMAvctTxRxPair4Results,
        exCMAvctTxRxPair4Amplitude,
        exCMAvctTxRxPair4Distance,

        cm10gtModelname,
        cm10gtModelDesc,
        cm10gtHwJmp5ConfigMode,
        cm10gtHwSw1OperationMode,
        cm10gtHwSw2LinkMode,
        cm10gtHwSw3FiberFaultAlert,
        cm10gtHwSw4EnergyEfficentEthernet,
        cm10gtHwSw5Unused,

        cm10gtPort1LinkStatus,
        cm10gtPort1ConnType,
        cm10gtPort1AutoNegState,
        cm10gtPort1Speed,
        cm10gtPort1Duplex,
        cm10gtPort1PauseEnh,
        cm10gtPort1ReceiveStatus,
        cm10gtPort1LPRFStatus,

        cm10gtPort2LinkStatus,
        cm10gtPort2ConnType,
        cm10gtPort2AutoNegState,
        cm10gtPort2Speed,
        cm10gtPort2Duplex,
        cm10gtPort2PauseEnh,
        cm10gtPort2LPRFStatus,

        cm10gtPortLoopBack,
        cm10gtPortTestMode,

        cm10gtConfigStatus,
        cm10gtConfigModuleName,
        cm10gtConfigLinkMode,
        cm10gtConfigFiberFaultAlert,
        cm10gtConfigFiberAutoNeg,
        cm10gtConfigPort1Name,
        cm10gtConfigPort1Enable,
        cm10gtConfigPort1FecEnable,
        cm10gtConfigPort1FecAmplitude,
        cm10gtConfigPort1FecPhase,
        cm10gtConfigPort1WavelengthEnable,
        cm10gtConfigPort1WavelengthValue,
        cm10gtConfigPort1ChannelEnable,
        cm10gtConfigPort1ChannelNumber,
        cm10gtConfigPort1TxDitherEnable,
        cm10gtConfigPort1TxDitherValue,

        cm10gtConfigPort2Name,
        cm10gtConfigPort2Enable,
        cm10gtConfigPort2CopperDuplex,
        cm10gtConfigPort2CopperPauseEnh,
        cm10gtConfigPort2CopperEnergyEfficientEthernet,
        
        cm10gtLedsSlotIndex,
        cm10gtLedPWR,
        cm10gtLedLK1,
        cm10gtLedLK2,
       
        cm4gptModelname,
        cm4gptModelDesc,
        cm4gptHwJmp5ConfigMode,
        cm4gptHwSw1LinkMode,
        cm4gptHwSw2FiberFaultAlert,
        cm4gptHwSw3RateSelect,
        cm4gptHwSw4Unused,

        cm4gptPort1LinkStatus,
        cm4gptPort1ConnType,

        cm4gptPort2LinkStatus,
        cm4gptPort2ConnType,
        
        cm4gptConfigStatus,
        cm4gptConfigModuleName,
        cm4gptConfigLinkMode,
        cm4gptConfigFiberFaultAlert,
        cm4gptConfigRateSelect,

        cm4gptConfigPort1Name,
        cm4gptConfigPort1Enable,

        cm4gptConfigPort2Name,
        cm4gptConfigPort2Enable,
        
        cm4gptLedPWR,
        cm4gptLedLK1,
        cm4gptLedLK2,
        
        mgtEthStatsName,mgtEthStatsMacAddress,mgtEthStatsStatus,mgtEthStatsSpeedDuplex,
        mgtEthStatsBroadcast,mgtEthStatsDebug,mgtEthStatsLoopback,mgtEthStatsPointtoPoint,
        mgtEthStatsNoTrailers,mgtEthStatsRunning,mgtEthStatsNoArp,mgtEthStatsPromiscuous,
        mgtEthStatsRxMulticast,mgtEthStatsMasterLoadBalancer,mgtEthStatsSlaveLoadBalancer,
        mgtEthStatsMulticast,mgtEthStatsSetMedia,mgtEthStatsAutoMedia,mgtEthStatsDynamic,
        mgtEthStatsLocalAddress,mgtEthStatsSubnetMask,mgtEthStatsBroadcastAddress,mgtEthStatsMtu,
        mgtEthStatsTxQLen,mgtEthStatsRxBytes,mgtEthStatsTxBytes,mgtEthStatsRxPackets,mgtEthStatsTxPackets,
        mgtEthStatsRxErrors,mgtEthStatsTxPktErrors,mgtEthStatsRxDroppedPkts,mgtEthStatsTxDroppedPkts,
        mgtEthStatsRxOverruns,mgtEthStatsTxOverruns,mgtEthStatsRxFrameErrs,mgtEthStatsTxCarrierErrs,
        mgtEthStatsCollisions,

        sfpDmiStatus,sfpDmiConnectorType,sfpDmiNominalBitRate,sfpDmiLinkReach9125,sfpDmiLinkReach50125,
        sfpDmiLinkReach625125,sfpDmiFiberWaveLength,sfpDmiCurrentTempState,sfpDmiRealTimeTemp,sfpDmiHighTempWarn,
        sfpDmiHighTempAlarm,sfpDmiLowTempWarn,sfpDmiLowTempAlarm,sfpDmiCurrentVoltState,
        sfpDmiRealTimeVolt,sfpDmiHighVoltWarn,sfpDmiHighVoltAlarm,sfpDmiLowVoltWarn,sfpDmiLowVoltAlarm,
        sfpDmiCurrentTxBiasState,sfpDmiRealTimeTxBias,sfpDmiHighTxBiasWarn,sfpDmiHighTxBiasAlarm,
        sfpDmiLowTxBiasWarn,sfpDmiLowTxBiasAlarm,sfpDmiCurrentTxPowerState,sfpDmiRealTimeTxPower,
        sfpDmiHighTxPowerWarn,sfpDmiHighTxPowerAlarm,sfpDmiLowTxPowerWarn,sfpDmiLowTxPowerAlarm,
        sfpDmiCurrentRxPowerState,sfpDmiRealTimeRxPower,sfpDmiHighRxPowerWarn,sfpDmiHighRxPowerAlarm,
        sfpDmiLowRxPowerWarn,sfpDmiLowRxPowerAlarm,sfpDmiStatus2,
        sfpDmiVendorSerialNumber, sfpDmiVendorName, sfpDmiVendorPartNumber,
        xfpDmiAux1Type, xfpDmiAux1State, xfpDmiRealTimeAux1, xfpDmiHighAux1Warn, xfpDmiHighAux1Alarm,
        xfpDmiLowAux1Warn, xfpDmiLowAux1Alarm, 
        xfpDmiAux2Type, xfpDmiAux2State, xfpDmiRealTimeAux2, xfpDmiHighAux2Warn, xfpDmiHighAux2Alarm,
        xfpDmiLowAux2Warn, xfpDmiLowAux2Alarm, 
        xfpDmiMinBitRate, xfpDmiMaxBitRate, xfpDmiReachEBW50125, sfpDmiReachCopper
    }
    STATUS       current
    DESCRIPTION
        "The group of objects for identifying and determining the configuration and
         current timeliness values of the Perle Managed Media Converters media converter modules"
    ::= { mcrMGTMIBGroups 2 }
--
-- end of  mcrMGTMIBMediaGroup
--
--
-- mcrMGTMIBMgtGroup
--
mcrMGTMIBMgtGroup  OBJECT-GROUP
    OBJECTS {

        systemStatus,systemName,systemDomainName,systemIpAddress,systemSubnetBits,systemDHCPUpdateDNS,
        systemAutoObtainDNS,systemAutoObtainGW,systemDomainPrefix,
        systemTFTPRetry,systemTFTPTimeOut,

        gatewayStatus,gatewayHost,gatewayType,gatewayIpAddress,gatewaySubnetBits,gatewayInterface,

        hostStatus,hostName,hostIpAddr,hostFqdn,

        dnsStatus,dnsIpAddress,dnsActive,

        dynamicDNSStatus,dynamicDNS,dynamicDNSHostname,dynamicDNSUserName,dynamicDNSPassword,
        dynamicDNSSystemType,dynamicDNSWildCard,dynamicDNSConnectionMethod,dynamicDNSSSLVerifyPeerCertificate,
        dynamicDNSSSLCountry   ,dynamicDNSSSLStateProv   ,dynamicDNSSSLLocality   ,dynamicDNSSSLOrganisation,
        dynamicDNSSSLOrganisationUnit   ,dynamicDNSSSLCommonName   ,dynamicDNSSSLEmail,
        dynamicDNSStatusString,

        dynamicDNSSSLCipherStatus,dynamicDNSSSLCipherEncryption,
        dynamicDNSSSLCipherKeySizeMin,dynamicDNSSSLCipherKeySizeMax,dynamicDNSSSLCipherKeyExchange,
        dynamicDNSSSLCipherHMAC,

        ipv6serviceStatus, serviceAutoDiscovery, serviceDHCPv6,
        serviceDHCPv6IPAddresses, serviceDHCPv6NetworkPrefix,serviceDHCPv6AutoObtainDNS,

        ipv6AddressStatus,ipv6AddressAddr,ipv6AddressPrefixBits,ipv6AddressAuto ,ipv6AddressSendAdvertise,

        interfacev6Name,interfacev6Address,interfacev6PrefixBits,interfacev6Scope,

        ipv6TunnelStatus,ipv6TunnelName,ipv6TunnelMode,ipv6TunnelRemoteHost,

        accessServicesStatus,accessServicesSessInactTimeout,accessServiceHTTPD,accessServiceHTTPSD,
        accessServiceTelnetD,acessServiceSSHD,acessServiceSnmpD,acessServiceSetIP,acessIncomingPings,

        webManagerStatus,httpsPassphrase,

        sshServerStatus,sshServerAuthRSA,sshServerAuthDSA,sshServerAuthKeyboard,sshServerAuthPassword,
        sshServerCipher3Des,sshServerCipherBlowfish,sshServerCipherCipherAES,sshServerCipherCAST,
        sshServerCipherArcfour,sshServerVerbose,sshServerCompression,sshServerSSH1,

        snmpAgentStatus,snmpContact,snmpLocation,

        snmpCommunityStatus,snmpCommunityName,snmpCommunityIpAddress,snmpCommunityPermission,
        snmpV3ReadOnlyStatus,snmpV3ReadOnlyUserName,snmpV3ReadOnlySecurityLevel,snmpV3ReadOnlyAuthAlgorithm,
        snmpV3ReadOnlyAuthPasswd,snmpV3ReadOnlyPrivacyAlgorithm,snmpV3ReadOnlyPrivacyPasswd,
        snmpV3ReadWriteStatus,snmpV3ReadWriteUserName,snmpV3ReadWriteSecurityLevel,
        snmpV3ReadWriteAuthAlgorithm,snmpV3ReadWriteAuthPasswd,snmpV3ReadWritePrivacyAlgorithm,
        snmpV3ReadWritePrivacyPasswd,snmpV3LocalEngineID, snmpV3LocalEngineIDTextSuffix,

        authHostsStatus, authHostOnly,

        authHostIpStatus,authHostIpAddr,authHostIpDescr,

        authHostMacStatus,authHostMacAddr,authHostMacDescr,

        localEventLogStatus,localEventLogEnabled,localEventLogAlertLevel,localEventLogClear,

        syslogStatus,syslogEnabled,syslogSeverityLevel,snmpTrapHostIndex,syslogPrimaryHost,syslogSecondaryHost,

        snmpTrapStatus,snmpTrapEnabled,snmpTrapAlertLevel,

        snmpTrapHostStatus,snmpTrapHostIpAddress,snmpTrapHostUdpPort,snmpTrapHostVersion,
        snmpTrapHostType,snmpTrapHostCommunity,snmpTrapHostEnable, snmpV3TrapUserStatus,
        snmpV3TrapUserUserName,snmpV3TrapUserSecurityLevel,snmpV3TrapUserAuthAlgorithm,
        snmpV3TrapUserAuthPasswd,snmpV3TrapUserPrivacyAlgorithm,snmpV3TrapUserPrivacyPasswd,
        snmpTrapGlbHostTimeout,snmpTapGlobHostRetries,

        mgtAccessMethod,remoteMgtIpAddress,remoteTftpHost,remoteTftpFileName,networkIpAddress,
        mcrMediaPortNum,mcrMediaPortDescr, eventSeverityLevel,
        xfpDmiRealTimeAux, xfpDmiHighAuxWarn, xfpDmiHighAuxAlarm, xfpDmiLowAuxWarn, xfpDmiLowAuxAlarm,
        mcrModuleSubTypeInserted, mcrMediaBackedupModuleSubType, mcrMediaPortBandwidth, mcrMediaPortBandwidthThreshold,
 

        emailStatus,emailEnabled,emailAlertLevel,emailTo,emailFrom,emailSMTPHost,emailReply,
        emailSubject,emailSMTPUsername,emailSMTPPassword,emailSMTPEncryption,emailSMTPValidatePeerCertificate,
        emailSMTPTcpPort,emailSMTPDomain,

        mgtUsersStatus,mgtUsersByPassLoginEnabled,mgtUsersPrimaryAuthMethod,mgtUsersSecondaryAuthMethod,
        mgtUsersAlwaysAttemptSecond,

        userStatus,userName,userPassword,userLevel,

        userStatusName,userStatusRemoteIPAddress,userStatusStartTime,
        userStatusLevel,

        radiusStatus,radiusPrimaryAuthHost,radiusSecondaryAuthHost,radiusAuthenticationPort,
        radiusAccounting,radiusPrimaryAcctHost,radiusSecondaryAcctHost,radiusAccountingPort,
        radiusAcctAuth,radiusRetryLimit,radiusTimeout,radiusNasIdentifier,radiusNasIpAddress,
        radiusNasSpecifyIpAddress,radiusNasIpv6Address,radiusNasSpecifyIpv6Address,

        kerberosStatus,kerberosRealm,kerberosDomain,kerberosPort,

        ldapStatus,ldapHost,ldapPort,ldapBase,ldapEnableTLS,ldapTLSPort,ldapUID,ldapPasswordEncryption,
        ldapClientAuth,ldapClientName,ldapClientAppendBase,ldapClientPassword,

        tacacsStatus,tacacsPrimaryHost,tacacsSecondaryHost,tacacsPort,tacacsAccounting,
        tacacsAccountingPrimaryHost,tacacsAccountingSecondaryHost,tacacsAccountingPort,
        tacacsAuthorization,tacacsAlternateServiceNames,

        securidStatus,securidMasterHost,securidSlaveHost,securidPort,securidType,securidLegacy,

        nisStatus,nisDomain,nisPrimaryHost,nisSecondaryHost,

        mgtDateTimeStatus,systemDate,systemTime,systemDateTimeAndOffset,timeZoneListEnable,
        selectionFromTimeZoneList,timeZoneAdjustForDST,

        customTimeZoneStatus,timeZoneName,timeOffset,timeSummerName,timeSummerOffset,
        timeSummerMode,timeSummerRecStartMonth,timeSummerRecStartWeek,timeSummerRecStartDay,
        timeSummerRecStartHour,timeSummerRecStartMin,timeSummerRecEndMonth,timeSummerRecEndWeek,
        timeSummerRecEndDay,timeSummerRecEndHour,timeSummerRecEndMin,timeSummerFixStartMonth,
        timeSummerFixStartDay,timeSummerFixStartHour,timeSummerFixStartMinute,timeSummerFixEndMonth,
        timeSummerFixEndDay,timeSummerFixEndHour,timeSummerFixEndMinute,

        timeStatus,timeSntpMode,timeSntpVersion,timeSntpHost1,timeSntpHost2,timeSntpServerAuthentication,
        timeSntpKeyID,timeSntpKeyID2,

        sntpStatAddress,sntpStatLastUpdate,sntpStatLeapIndicator,sntpStatVersion,sntpStatMode,
        sntpStatStratum,sntpStatRefId,sntpStatOffset,

        bootFileStatus,fileFirmwareHost,fileFirmwareName,fileConfigurationHost,fileConfigurationName,

        firmwareUpdateStatus, firmwareUpdateAuto,
        firmwareUpdateBundleVersionCm100, firmwareUpdateBundleVersionCm110,
        firmwareUpdateBundleVersionCm1000OrCm1000Sfp,
        firmwareUpdateBundleVersionCm1110, firmwareUpdateBundleVersionCm1110Sfp,
        firmwareUpdateBundleVersionCm100mm, firmwareUpdateBundleVersionCm1000mm, firmwareUpdateBundleVersionCm10g,

        nettxfrStatus, nettxfrDirection, nettxfrFileType, nettxfrFileHost, nettxfrFileName,
        nettxfrMCSlotNumber, nettxfrUserName, nettxfrSSHKeyType, nettxfrSSLType, nettxfrSessionInUse,
        nettxfrTftpPort,

        adminFunction,adminLastFunction,adminStatus,adminbootReason,adminDiagFileAvailable,

        displayFormatStatus,cfgTemperatureUnits,cfgSfpPowerUnits,cfgTimeFormat,cfgDateFormat,
        powerSchedConifgStatus,powerSchedOnHour,powerSchedOnMinute,
        powerSchedOffHour,powerSchedOffMinute

    }
    STATUS       current
    DESCRIPTION
        "The group of objects for identifying and determining the configuration and
         current timeliness values of the Perle Managed Media Converters media converter modules"
    ::= { mcrMGTMIBGroups 3 }
--
-- end of  mcrMGTMIBMgtGroup
--
--
-- mcrMGTMIBNotificationsGroup
--
mcrMGTMIBNotificationsGroup  NOTIFICATION-GROUP
    NOTIFICATIONS {
        mcrMgtModuleInserted,mcrMgtSystemBoot,mcrMgtReset,
        mcrMgtResetFactory,mcrMgtEtheLinkUp,mcrMgtEtheLinkDown,
        mcrMgtConMonDSRSigChg,mcrMgtAuthFail,mcrMgtAuthSuccess,
        mcrMgtDateTimeChg,mcrMgtSntpServFail,mcrMgtSntpServRec,
        mcrMgtSnmpTrapHostFail,mcrMgtSnmpTrapHostRec,mcrMgtEmailServFail,
        mcrMgtEmailServRec,mcrMgtConfSavedFlash,mcrMgtIpAddrDynChg,
        mcrMgtTftpUploadFail,mcrMgtTftpUploadSuccess,mcrMgtTftpDownloadFail,
        mcrMgtTftpDownloadSuccess,mcrMgtChassisMismatch,

        mcrChassisAdd,mcrChassisRemove,mcrChassisReset,
        mcrChassisTemperatureAlarm,mcrChassisTemperatureRecover,
        mcrChassisSlotPoweredOn,mcrChassisSlotPoweredOff,mcrChassisFail,
        mcrChassisOk,mcrPsmuInserted,

        mcrPsmuRemoved,mcrPsmuPsuFail,mcrPsmuPsuOk,
        mcrPsmuPsuVoltageFail,mcrPsmuPsuVoltageOk,mcrPsmuFanFail,
        mcrPsmuFanOk,

        mcrMediaInserted,mcrMediaRemoved,mcrMediaReset,
        mcrMediaLostCommunication,mcrMediaRecovCommunication,
        mcrMediaFail,mcrMediaOk,mcrMediaLinkUp,
        mcrMediaLinkDown,mcrMediaConfUpdateFail,mcrMediaConfUpdateSuccess,
        mcrMediaConfMismatch,mcrMediaConfMismatchResolv,mcrMediaFirmwareUpdateFail,
        mcrMediaFirmwareUpdateSuccess,

        mcrSfpInserted,mcrSfpRemoved,

        mcrSfpHighTempWarn,mcrSfpHighTempWarnRecov,mcrSfpHighTempAlarm,
        mcrSfpHighTempAlarmRecov,mcrSfpLowTempWarn,mcrSfpLowTempWarnRecov,
        mcrSfpLowTempAlarm,mcrSfpLowTempAlarmRecov,

        mcrSfpHighVoltWarn,mcrSfpHighVoltWarnRecov,mcrSfpHighVoltAlarm,
        mcrSfpHighVoltAlarmRecov,mcrSfpLowVoltWarn,mcrSfpLowVoltWarnRecov,
        mcrSfpLowVoltAlarm,mcrSfpLowVoltAlarmRecov,

        mcrSfpHighTxBiasWarn,mcrSfpHighTxBiasWarnRecov,mcrSfpHighTxBiasAlarm,
        mcrSfpHighTxBiasAlarmRecov,mcrSfpLowTxBiasWarn,mcrSfpLowTxBiasWarnRecov,
        mcrSfpLowTxBiasAlarm,mcrSfpLowTxBiasAlarmRecov,

        mcrSfpHighTxPowerWarn,mcrSfpHighTxPowerWarnRecov,mcrSfpHighTxPowerAlarm,
        mcrSfpHighTxPowerAlarmRecov,mcrSfpLowTxPowerWarn,mcrSfpLowTxPowerWarnRecov,
        mcrSfpLowTxPowerAlarm,mcrSfpLowTxPowerAlarmRecov,

        mcrSfpHighRxPowerWarn,mcrSfpHighRxPowerWarnRecov,mcrSfpHighRxPowerAlarm,
        mcrSfpHighRxPowerAlarmRecov,mcrSfpLowRxPowerWarn,mcrSfpLowRxPowerWarnRecov,
        mcrSfpLowRxPowerAlarm,mcrSfpLowRxPowerAlarmRecov,

        mcrChassisCommTempSensorFail,mcrChassisCommTempSensorRecov,
        mcrMediaDetectFail,mcrMediaBadImage,mcrSfpLostComm,mcrSfpRecovComm,

        mcrModuleNotSupported, mcrModuleFirmwareUpdate,

        mcrSfpPortShutdown, mcrSfpPortShutdownRecov, 

        mcrXfpHighApdBiasWarn, mcrXfpHighApdBiasWarnRecov, mcrXfpHighApdBiasAlarm, mcrXfpHighApdBiasAlarmRecov,
        mcrXfpLowApdBiasWarn, mcrXfpLowApdBiasWarnRecov, mcrXfpLowApdBiasAlarm, mcrXfpLowApdBiasAlarmRecov,

        mcrXfpHighTecCurrentWarn, mcrXfpHighTecCurrentWarnRecov, mcrXfpHighTecCurrentAlarm, mcrXfpHighTecCurrentAlarmRecov,
        mcrXfpLowTecCurrentWarn, mcrXfpLowTecCurrentWarnRecov, mcrXfpLowTecCurrentAlarm, mcrXfpLowTecCurrentAlarmRecov,

        mcrXfpHighLaserTempWarn, mcrXfpHighLaserTempWarnRecov, mcrXfpHighLaserTempAlarm, mcrXfpHighLaserTempAlarmRecov,
        mcrXfpLowLaserTempWarn, mcrXfpLowLaserTempWarnRecov, mcrXfpLowLaserTempAlarm, mcrXfpLowLaserTempAlarmRecov,

        mcrXfpHighLaserWavelengthWarn, mcrXfpHighLaserWavelengthWarnRecov, mcrXfpHighLaserWavelengthAlarm, mcrXfpHighLaserWavelengthAlarmRecov,
        mcrXfpLowLaserWavelengthWarn, mcrXfpLowLaserWavelengthWarnRecov, mcrXfpLowLaserWavelengthAlarm, mcrXfpLowLaserWavelengthAlarmRecov,

        mcrXfpHigh5VoltWarn, mcrXfpHigh5VoltWarnRecov, mcrXfpHigh5VoltAlarm, mcrXfpHigh5VoltAlarmRecov,
        mcrXfpLow5VoltWarn, mcrXfpLow5VoltWarnRecov, mcrXfpLow5VoltAlarm, mcrXfpLow5VoltAlarmRecov,

        mcrXfpHigh33VoltWarn, mcrXfpHigh33VoltWarnRecov, mcrXfpHigh33VoltAlarm, mcrXfpHigh33VoltAlarmRecov,
        mcrXfpLow33VoltWarn, mcrXfpLow33VoltWarnRecov, mcrXfpLow33VoltAlarm, mcrXfpLow33VoltAlarmRecov,

        mcrXfpHigh18VoltWarn, mcrXfpHigh18VoltWarnRecov, mcrXfpHigh18VoltAlarm, mcrXfpHigh18VoltAlarmRecov,
        mcrXfpLow18VoltWarn, mcrXfpLow18VoltWarnRecov, mcrXfpLow18VoltAlarm, mcrXfpLow18VoltAlarmRecov,

        mcrXfpHighM52VoltWarn, mcrXfpHighM52VoltWarnRecov, mcrXfpHighM52VoltAlarm, mcrXfpHighM52VoltAlarmRecov,
        mcrXfpLowM52VoltWarn, mcrXfpLowM52VoltWarnRecov, mcrXfpLowM52VoltAlarm, mcrXfpLowM52VoltAlarmRecov,

        mcrXfpHigh5VCurrentWarn, mcrXfpHigh5VCurrentWarnRecov, mcrXfpHigh5VCurrentAlarm, mcrXfpHigh5VCurrentAlarmRecov,
        mcrXfpLow5VCurrentWarn, mcrXfpLow5VCurrentWarnRecov, mcrXfpLow5VCurrentAlarm, mcrXfpLow5VCurrentAlarmRecov,

        mcrXfpHigh33VCurrentWarn, mcrXfpHigh33VCurrentWarnRecov, mcrXfpHigh33VCurrentAlarm, mcrXfpHigh33VCurrentAlarmRecov,
        mcrXfpLow33VCurrentWarn, mcrXfpLow33VCurrentWarnRecov, mcrXfpLow33VCurrentAlarm, mcrXfpLow33VCurrentAlarmRecov,

        mcrXfpHigh18VCurrentWarn, mcrXfpHigh18VCurrentWarnRecov, mcrXfpHigh18VCurrentAlarm, mcrXfpHigh18VCurrentAlarmRecov,
        mcrXfpLow18VCurrentWarn, mcrXfpLow18VCurrentWarnRecov, mcrXfpLow18VCurrentAlarm, mcrXfpLow18VCurrentAlarmRecov,

        mcrXfpHighM52VCurrentWarn, mcrXfpHighM52VCurrentWarnRecov, mcrXfpHighM52VCurrentAlarm, mcrXfpHighM52VCurrentAlarmRecov,
        mcrXfpLowM52VCurrentWarn, mcrXfpLowM52VCurrentWarnRecov, mcrXfpLowM52VCurrentAlarm, mcrXfpLowM52VCurrentAlarmRecov,

        mcrXfpHighVCC5Warn, mcrXfpHighVCC5WarnRecov, mcrXfpHighVCC5Alarm, mcrXfpHighVCC5AlarmRecov,
        mcrXfpLowVCC5Warn, mcrXfpLowVCC5WarnRecov, mcrXfpLowVCC5Alarm, mcrXfpLowVCC5AlarmRecov,

        mcrXfpHighVCC3Warn, mcrXfpHighVCC3WarnRecov, mcrXfpHighVCC3Alarm, mcrXfpHighVCC3AlarmRecov,
        mcrXfpLowVCC3Warn, mcrXfpLowVCC3WarnRecov, mcrXfpLowVCC3Alarm, mcrXfpLowVCC3AlarmRecov,

        mcrXfpHighVCC2Warn, mcrXfpHighVCC2WarnRecov, mcrXfpHighVCC2Alarm, mcrXfpHighVCC2AlarmRecov,
        mcrXfpLowVCC2Warn, mcrXfpLowVCC2WarnRecov, mcrXfpLowVCC2Alarm, mcrXfpLowVCC2AlarmRecov,

        mcrXfpHighVEE5Warn, mcrXfpHighVEE5WarnRecov, mcrXfpHighVEE5Alarm, mcrXfpHighVEE5AlarmRecov,
        mcrXfpLowVEE5Warn, mcrXfpLowVEE5WarnRecov, mcrXfpLowVEE5Alarm, mcrXfpLowVEE5AlarmRecov,
        
        mcrSfpSpeedMismatch, mcrSfpSpeedMismatchRecov, mcrXfpPowerExceeded, mcrXfpPowerExceededRecov,
        mcrLinkTestError, mcrAlarmRelayEngaged, mcrAlarmRelayDisengaged,
        
        mcrBandwidthLevelUpstreamLow, mcrBandwidthLevelUpstreamRecov,
        mcrBandwidthLevelDownstreamLow, mcrBandwidthLevelDownstreamRecov,
        mcrMediaRemoteReset
        
    }
    STATUS        current
    DESCRIPTION
        "The group of notifications (traps) which is implemented for the
         Perle Managed Media Converters."
         ::= { mcrMGTMIBGroups 4 }
--
-- end of  mcrMGTMIBNotificationsGroup
--

 END

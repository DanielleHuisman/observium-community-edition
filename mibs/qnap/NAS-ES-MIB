NAS-ES-MIB DEFINITIONS ::= BEGIN

   IMPORTS
      enterprises, Counter, TimeTicks
         FROM RFC1155-SMI
      Integer32, Counter32, IpAddress, Unsigned32, Counter64, OBJECT-TYPE
         FROM SNMPv2-SMI
      TRAP-TYPE
         FROM RFC-1215;

      -- From RFC-1213 (MIB-II)
      DisplayString ::= OCTET STRING

    storage     OBJECT IDENTIFIER ::= { enterprises 24681 }


    es-storageSystem        OBJECT IDENTIFIER ::= { storage 2 }
-- system Event
    es-SystemEventMsg        OBJECT IDENTIFIER ::= { es-storageSystem 1 }

es-SystemEventTable OBJECT-TYPE
    SYNTAX  SEQUENCE OF es-EventInfoEntryDef
    ACCESS  not-accessible
    STATUS  mandatory
    DESCRIPTION
        "A list of system event entries."
    ::= { es-SystemEventMsg 101 }
es-EventInfoEntry OBJECT-TYPE
    SYNTAX  es-EventInfoEntryDef
    ACCESS  not-accessible
    STATUS  mandatory
    DESCRIPTION
        "An info event interface entry."
    INDEX   { es-EventInfoIndex }
    ::= { es-SystemEventTable 1 }
es-EventInfoEntryDef ::=
    SEQUENCE {
        es-EventInfoIndex
            INTEGER,
        es-EventInfoMessage
            DisplayString
    }
es-EventInfoIndex OBJECT-TYPE
    SYNTAX  INTEGER
    ACCESS  read-only
    STATUS  mandatory
    DESCRIPTION
            "A unique value for each event."
    ::= { es-EventInfoEntry 1 }
es-EventInfoMessage OBJECT-TYPE
    SYNTAX  DisplayString (SIZE (0..255))
    ACCESS  read-only
    STATUS  mandatory
    DESCRIPTION
            "A textual string containing information about the event."
    ::= { es-EventInfoEntry 2 }
es-EventWarnEntry OBJECT-TYPE
    SYNTAX  es-EventWarnEntryDef
    ACCESS  not-accessible
    STATUS  mandatory
    DESCRIPTION
        "An warning event interface entry."
    INDEX   { es-EventWarnIndex }
    ::= { es-SystemEventTable 1 }
es-EventWarnEntryDef ::=
    SEQUENCE {
        es-EventWarnIndex
            INTEGER,
        es-EventWarnMessage
            DisplayString
    }
es-EventWarnIndex OBJECT-TYPE
    SYNTAX  INTEGER
    ACCESS  read-only
    STATUS  mandatory
    DESCRIPTION
            "A unique value for each event."
    ::= { es-EventWarnEntry 1 }
es-EventWarnMessage OBJECT-TYPE
    SYNTAX  DisplayString (SIZE (0..255))
    ACCESS  read-only
    STATUS  mandatory
    DESCRIPTION
            "A textual string containing information about the event."
    ::= { es-EventWarnEntry 2 }
es-EventErrorEntry OBJECT-TYPE
    SYNTAX  es-EventErrorEntryDef
    ACCESS  not-accessible
    STATUS  mandatory
    DESCRIPTION
        "An error interface entry."
    INDEX   { es-EventErrorIndex }
    ::= { es-SystemEventTable 1 }
es-EventErrorEntryDef ::=
    SEQUENCE {
        es-EventErrorIndex
            INTEGER,
        es-EventErrorMessage
            DisplayString
    }
es-EventErrorIndex OBJECT-TYPE
    SYNTAX  INTEGER
    ACCESS  read-only
    STATUS  mandatory
    DESCRIPTION
            "A unique value for each event."
    ::= { es-EventErrorEntry 1 }
es-EventErrorMessage OBJECT-TYPE
    SYNTAX  DisplayString (SIZE (0..255))
    ACCESS  read-only
    STATUS  mandatory
    DESCRIPTION
            "A textual string containing information about the event."
    ::= { es-EventErrorEntry 2 }

 -- ES system inform
    es-SystemInfo        OBJECT IDENTIFIER ::= { es-storageSystem 2 }

es-SystemCPU-Usage OBJECT-TYPE
    SYNTAX DisplayString
    MAX-ACCESS read-only
    STATUS     current
    DESCRIPTION
        "System CPU usage"
    ::= { es-SystemInfo 1 }
es-SystemTotalMem OBJECT-TYPE
    SYNTAX DisplayString
    MAX-ACCESS read-only
    STATUS     current
    DESCRIPTION
        "System total memory"
    ::= { es-SystemInfo 2 }
es-SystemFreeMem OBJECT-TYPE
    SYNTAX DisplayString
    MAX-ACCESS read-only
    STATUS     current
    DESCRIPTION
        "System free memory"
    ::= { es-SystemInfo 3 }
es-SystemUptime OBJECT-TYPE
    SYNTAX     TimeTicks
    MAX-ACCESS read-only
    STATUS     current
    DESCRIPTION
        "The amount of time since this host was last
        initialized.  Note that this is different from
        sysUpTime in the SNMPv2-MIB [RFC1907] because
        sysUpTime is the uptime of the network management
        portion of the system."
    ::= { es-SystemInfo 4 }
es-CPU-Temperature OBJECT-TYPE
    SYNTAX DisplayString
    MAX-ACCESS read-only
    STATUS     current
    DESCRIPTION
        "CPU temperature"
    ::= { es-SystemInfo 5 }
es-SystemTemperature1 OBJECT-TYPE
    SYNTAX DisplayString
    MAX-ACCESS read-only
    STATUS     current
    DESCRIPTION
        "System temperature"
    ::= { es-SystemInfo 6 }
es-SystemTemperature2 OBJECT-TYPE
    SYNTAX DisplayString
    MAX-ACCESS read-only
    STATUS     current
    DESCRIPTION
        "System temperature"
    ::= { es-SystemInfo 7 }

es-IfNumber OBJECT-TYPE
    SYNTAX  INTEGER
    ACCESS  read-only
    STATUS  mandatory
    DESCRIPTION
        "The number of network interfaces (regardless of
        their current state) present on this system."
    ::= { es-SystemInfo 8 }
es-SystemIfTable OBJECT-TYPE
    SYNTAX  SEQUENCE OF es-IfEntryDef
    ACCESS  not-accessible
    STATUS  mandatory
    DESCRIPTION
        "A list of interface entries.  The number of
        entries is given by the value of ifNumber."
    ::= { es-SystemInfo 9 }
es-IfEntry OBJECT-TYPE
    SYNTAX  es-IfEntryDef
    ACCESS  not-accessible
    STATUS  mandatory
    DESCRIPTION
        "An interface entry containing objects at the
        subnetwork layer and below for a particular
        interface."
    INDEX   { es-IfIndex }
    ::= { es-SystemIfTable 1 }
es-IfEntryDef ::=
    SEQUENCE {
        es-IfIndex
            INTEGER,
        es-IfDescr
            DisplayString,
        es-IfPacketsReceived
            Counter,
        es-IfPacketsSent
            Counter,
        es-IfErrorPackets
            Counter
    }
es-IfIndex OBJECT-TYPE
    SYNTAX  INTEGER
    ACCESS  read-only
    STATUS  mandatory
    DESCRIPTION
            "A unique value for each interface.  Its value
            ranges between 1 and the value of ifNumber.  The
            value for each interface must remain constant at
            least from one re-initialization of the entity's
            network management system to the next re-
            initialization."
    ::= { es-IfEntry 1 }
es-IfDescr OBJECT-TYPE
    SYNTAX  DisplayString (SIZE (0..255))
    ACCESS  read-only
    STATUS  mandatory
    DESCRIPTION
            "A textual string containing information about the
            interface.  This string should include the name of
            the manufacturer, the product name and the version
            of the hardware interface."
    ::= { es-IfEntry 2 }
es-IfPacketsReceived OBJECT-TYPE
    SYNTAX  Counter
    ACCESS  read-only
    STATUS  mandatory
    DESCRIPTION
            "System packets received."
    ::= { es-IfEntry 3 }
es-IfPacketsSent OBJECT-TYPE
    SYNTAX  Counter
    ACCESS  read-only
    STATUS  mandatory
    DESCRIPTION
            "System packets sent."
    ::= { es-IfEntry 4 }
es-IfErrorPackets OBJECT-TYPE
    SYNTAX  Counter
    ACCESS  read-only
    STATUS  mandatory
    DESCRIPTION
            "System error packets."
    ::= { es-IfEntry 5 }

es-HdNumber OBJECT-TYPE
    SYNTAX  INTEGER
    ACCESS  read-only
    STATUS  mandatory
    DESCRIPTION
            "The number of hard disk (regardless of
            their current state) present on this system."
    ::= { es-SystemInfo 10 }
es-SystemHdTable OBJECT-TYPE
    SYNTAX  SEQUENCE OF es-HdEntryDef
    ACCESS  not-accessible
    STATUS  mandatory
    DESCRIPTION
            "A list of interface entries.  The number of
            entries is given by the value of ifNumber."
    ::= { es-SystemInfo 11 }
es-HdEntry OBJECT-TYPE
    SYNTAX  es-HdEntryDef
    ACCESS  not-accessible
    STATUS  mandatory
    DESCRIPTION
            "An interface entry containing objects at the
            subnetwork layer and below for a particular
            interface."
    INDEX   { es-HdIndex }
    ::= { es-SystemHdTable 1 }
es-HdEntryDef ::=
    SEQUENCE {
        es-HdIndex
            INTEGER,
        es-HdDescr
            DisplayString,
        es-HdTemperature
            DisplayString,
        es-HdStatus
            INTEGER,
    es-HdModel DisplayString,
    es-HdCapacity DisplayString,
    es-HdSmartInfo DisplayString
    }
es-HdIndex OBJECT-TYPE
    SYNTAX  INTEGER
    ACCESS  read-only
    STATUS  mandatory
    DESCRIPTION
            "A unique value for each hard disk.  Its value
            ranges between 1 and the value of ifNumber.  The
            value for each interface must remain constant at
            least from one re-initialization of the entity's
            network management system to the next re-
            initialization."
    ::= { es-HdEntry 1 }
es-HdDescr OBJECT-TYPE
    SYNTAX  DisplayString (SIZE (0..255))
    ACCESS  read-only
    STATUS  mandatory
    DESCRIPTION
            "A textual string containing information about the
            interface.  This string should include the name of
            the manufacturer, the product name and the version
            of the hardware interface."
    ::= { es-HdEntry 2 }
es-HdTemperature OBJECT-TYPE
    SYNTAX  DisplayString
    ACCESS  read-only
    STATUS  mandatory
    DESCRIPTION
            "Hard disk temperature."
    ::= { es-HdEntry 3 }
es-HdStatus OBJECT-TYPE
    SYNTAX  DisplayString
    ACCESS  read-only
    STATUS  mandatory
    DESCRIPTION "HDD status."
    ::= { es-HdEntry 4 }
es-HdModel OBJECT-TYPE
    SYNTAX  DisplayString
    ACCESS  read-only
    STATUS  mandatory
    DESCRIPTION "Hard disk model."
    ::= { es-HdEntry 5 }
es-HdCapacity OBJECT-TYPE
    SYNTAX  DisplayString
    ACCESS  read-only
    STATUS  mandatory
    DESCRIPTION "Hard disk capacity."
    ::= { es-HdEntry 6 }
es-HdSmartInfo OBJECT-TYPE
    SYNTAX  DisplayString
    ACCESS  read-only
    STATUS  mandatory
    DESCRIPTION "Hard disk SMART information."
    ::= { es-HdEntry 7 }

    es-ModelName OBJECT-TYPE
        SYNTAX DisplayString
        MAX-ACCESS read-only
        STATUS     current
        DESCRIPTION
            "Model name"
        ::= { es-SystemInfo 12 }
    es-HostName OBJECT-TYPE
        SYNTAX DisplayString
        MAX-ACCESS read-only
        STATUS     current
        DESCRIPTION
            "Model name"
        ::= { es-SystemInfo 13 }

es-SysFanNumber OBJECT-TYPE
    SYNTAX  INTEGER
    ACCESS  read-only
    STATUS  mandatory
    DESCRIPTION
            "The number of system fan (regardless of
            their current state) present on this system."
    ::= { es-SystemInfo 14 }
es-SystemFanTable OBJECT-TYPE
    SYNTAX  SEQUENCE OF es-SysFanEntryDef
    ACCESS  not-accessible
    STATUS  mandatory
    DESCRIPTION
            "A list of interface entries.  The number of
            entries is given by the value of sysFanNumber."
    ::= { es-SystemInfo 15 }
es-SysFanEntry OBJECT-TYPE
    SYNTAX  es-SysFanEntryDef
    ACCESS  not-accessible
    STATUS  mandatory
    DESCRIPTION
            "An system fan entry containing objects at the
            subnetwork layer and below for a particular
            interface."
    INDEX   { es-SysFanIndex }
    ::= { es-SystemFanTable 1 }
es-SysFanEntryDef ::=
    SEQUENCE {
        es-SysFanIndex
            INTEGER,
        es-SysFanDescr
            DisplayString,
        es-SysFanSpeed
            DisplayString
    }
es-SysFanIndex OBJECT-TYPE
    SYNTAX  INTEGER
    ACCESS  read-only
    STATUS  mandatory
    DESCRIPTION
            "A unique value for each system fan. Its value
            ranges between 1 and the value of sysFanNumber.  The
            value for each interface must remain constant at
            least from one re-initialization of the entity's
            network management system to the next re-
            initialization."
    ::= { es-SysFanEntry 1 }
es-SysFanDescr OBJECT-TYPE
    SYNTAX  DisplayString (SIZE (0..255))
    ACCESS  read-only
    STATUS  mandatory
    DESCRIPTION
            "A textual string containing information about the
            interface.  This string should include the name of
            the manufacturer, the product name and the version
            of the hardware interface."
    ::= { es-SysFanEntry 2 }
es-SysFanSpeed OBJECT-TYPE
    SYNTAX  DisplayString (SIZE (0..255))
    ACCESS  read-only
    STATUS  mandatory
    DESCRIPTION
            "System fan speed."
    ::= { es-SysFanEntry 3 }

es-SysSharedFolderNumber OBJECT-TYPE
    SYNTAX  INTEGER
    ACCESS  read-only
    STATUS  mandatory
    DESCRIPTION
            "The number of system SharedFolders (regardless of
            their current state) present on this system."
    ::= { es-SystemInfo 16 }
es-SystemSharedFolderTable OBJECT-TYPE
    SYNTAX  SEQUENCE OF es-SysSharedFolderEntryDef
    ACCESS  not-accessible
    STATUS  mandatory
    DESCRIPTION
            "A list of SharedFolder entries.  The number of
            entries is given by the value of SysSharedFolderNumber."
    ::= { es-SystemInfo 17 }
es-SysSharedFolderEntry OBJECT-TYPE
    SYNTAX  es-SysSharedFolderEntryDef
    ACCESS  not-accessible
    STATUS  mandatory
    DESCRIPTION
            "An system SharedFolder entry"
    INDEX   { es-SysSharedFolderIndex }
    ::= { es-SystemSharedFolderTable 1 }
es-SysSharedFolderEntryDef ::=
    SEQUENCE {
        es-SysSharedFolderIndex    INTEGER,
        es-SysSharedFolderDescr    DisplayString,
        es-SysSharedFolderTotalSize    DisplayString,
        es-SysSharedFolderFreeSize DisplayString,
        es-SysSharedFolderStatus   DisplayString
    }
es-SysSharedFolderIndex OBJECT-TYPE
    SYNTAX  INTEGER
    ACCESS  read-only
    STATUS  mandatory
    DESCRIPTION
            "A unique value for each system SharedFolder. Its value
            ranges between 1 and the value of SysSharedFolderNumber.  The
            value for each SharedFolder must remain constant at
            least from one re-initialization of the entity's
            SharedFolder system to the next re-initialization."
    ::= { es-SysSharedFolderEntry 1 }
es-SysSharedFolderDescr OBJECT-TYPE
    SYNTAX  DisplayString (SIZE (0..255))
    ACCESS  read-only
    STATUS  mandatory
    DESCRIPTION "A textual string containing information about the SharedFolder."
    ::= { es-SysSharedFolderEntry 2 }
es-SysSharedFolderTotalSize OBJECT-TYPE
    SYNTAX  DisplayString (SIZE (0..15))
    ACCESS  read-only
    STATUS  mandatory
    DESCRIPTION "System SharedFolder total size."
    ::= { es-SysSharedFolderEntry 3 }
es-SysSharedFolderFreeSize OBJECT-TYPE
    SYNTAX  DisplayString (SIZE (0..15))
    ACCESS  read-only
    STATUS  mandatory
    DESCRIPTION "System SharedFolder free size."
    ::= { es-SysSharedFolderEntry 4 }
es-SysSharedFolderStatus OBJECT-TYPE
    SYNTAX  DisplayString (SIZE (0..255))
    ACCESS  read-only
    STATUS  mandatory
    DESCRIPTION "System SharedFolder status."
    ::= { es-SysSharedFolderEntry 5 }

es-SysLunNumber OBJECT-TYPE
    SYNTAX  INTEGER
    ACCESS  read-only
    STATUS  mandatory
    DESCRIPTION
            "The number of system Luns (regardless of
            their current state) present on this system."
    ::= { es-SystemInfo 18 }
es-SystemLunTable OBJECT-TYPE
    SYNTAX  SEQUENCE OF es-SysLunEntryDef
    ACCESS  not-accessible
    STATUS  mandatory
    DESCRIPTION
            "A list of Lun entries.  The number of
            entries is given by the value of SysLunNumber."
    ::= { es-SystemInfo 19 }
es-SysLunEntry OBJECT-TYPE
    SYNTAX  es-SysLunEntryDef
    ACCESS  not-accessible
    STATUS  mandatory
    DESCRIPTION
            "An system lun entry"
    INDEX   { es-SysLunIndex }
    ::= { es-SystemLunTable 1 }
es-SysLunEntryDef ::=
    SEQUENCE {
        es-SysLunIndex  INTEGER,
        es-SysLunDescr  DisplayString,
        es-SysLunTotalSize  DisplayString,
        es-SysLunUsedSize   DisplayString,
        es-SysLunStatus DisplayString
    }
es-SysLunIndex OBJECT-TYPE
    SYNTAX  INTEGER
    ACCESS  read-only
    STATUS  mandatory
    DESCRIPTION
            "A unique value for each system Lun. Its value
            ranges between 1 and the value of SysLunNumber.  The
            value for each Lun must remain constant at
            least from one re-initialization of the entity's
            Lun system to the next re-initialization."
    ::= { es-SysLunEntry 1 }
es-SysLunDescr OBJECT-TYPE
    SYNTAX  DisplayString (SIZE (0..255))
    ACCESS  read-only
    STATUS  mandatory
    DESCRIPTION "A textual string containing information about the Lun."
    ::= { es-SysLunEntry 2 }
es-SysLunTotalSize OBJECT-TYPE
    SYNTAX  DisplayString (SIZE (0..15))
    ACCESS  read-only
    STATUS  mandatory
    DESCRIPTION "System Lun total size."
    ::= { es-SysLunEntry 3 }
es-SysLunUsedSize OBJECT-TYPE
    SYNTAX  DisplayString (SIZE (0..15))
    ACCESS  read-only
    STATUS  mandatory
    DESCRIPTION "System Lun used size."
    ::= { es-SysLunEntry 4 }
es-SysLunStatus OBJECT-TYPE
    SYNTAX  DisplayString (SIZE (0..255))
    ACCESS  read-only
    STATUS  mandatory
    DESCRIPTION "System Lun status."
    ::= { es-SysLunEntry 5 }

es-SysPowerNumber OBJECT-TYPE
    SYNTAX  INTEGER
    ACCESS  read-only
    STATUS  mandatory
    DESCRIPTION
            "The number of system power (regardless of
            their current state) present on this system."
    ::= { es-SystemInfo 20 }
es-SystemPowerTable OBJECT-TYPE
    SYNTAX  SEQUENCE OF es-SysPowerEntryDef
    ACCESS  not-accessible
    STATUS  mandatory
    DESCRIPTION
            "A list of interface entries.  The number of
            entries is given by the value of sysPowerNumber."
    ::= { es-SystemInfo 21 }
es-SysPowerEntry OBJECT-TYPE
    SYNTAX  es-SysPowerEntryDef
    ACCESS  not-accessible
    STATUS  mandatory
    DESCRIPTION
            "An system power entry containing objects at the
            subnetwork layer and below for a particular
            interface."
    INDEX   { es-SysPowerIndex }
    ::= { es-SystemPowerTable 1 }
es-SysPowerEntryDef ::=
    SEQUENCE {
        es-SysPowerIndex
            INTEGER,
        es-SysPowerID
            INTEGER,
        es-SysEnclosureID
            INTEGER,
        es-SysPowerStatus
            DisplayString,
        es-SysPowerFanSpeed
            DisplayString,
        es-SysPowerTemp
            DisplayString
    }
es-SysPowerIndex OBJECT-TYPE
    SYNTAX  INTEGER
    ACCESS  read-only
    STATUS  mandatory
    DESCRIPTION
            "A unique value for each system power. Its value
            ranges between 1 and the value of sysPowerNumber.  The
            value for each interface must remain constant at
            least from one re-initialization of the entity's
            network management system to the next re-
            initialization."
    ::= { es-SysPowerEntry 1 }
es-SysPowerID OBJECT-TYPE
    SYNTAX  INTEGER
    ACCESS  read-only
    STATUS  mandatory
    DESCRIPTION
            "Each power ID on enclosure."
    ::= { es-SysPowerEntry 2 }
es-SysEnclosureID OBJECT-TYPE
    SYNTAX  INTEGER
    ACCESS  read-only
    STATUS  mandatory
    DESCRIPTION
            "A unique value for each enclosure ID."
    ::= { es-SysPowerEntry 3 }
es-SysPowerStatus OBJECT-TYPE
    SYNTAX  DisplayString (SIZE (0..255))
    ACCESS  read-only
    STATUS  mandatory
    DESCRIPTION
            "System power status."
    ::= { es-SysPowerEntry 4 }
es-SysPowerFanSpeed OBJECT-TYPE
    SYNTAX  DisplayString (SIZE (0..255))
    ACCESS  read-only
    STATUS  mandatory
    DESCRIPTION
            "System power fan speed."
    ::= { es-SysPowerEntry 5 }
es-SysPowerTemp OBJECT-TYPE
    SYNTAX  DisplayString (SIZE (0..255))
    ACCESS  read-only
    STATUS  mandatory
    DESCRIPTION
            "System power temperature."
    ::= { es-SysPowerEntry 6 }

es-SysPoolNumber OBJECT-TYPE
    SYNTAX  INTEGER
    ACCESS  read-only
    STATUS  mandatory
    DESCRIPTION
            "The number of system Pools (regardless of
            their current state) present on this system."
    ::= { es-SystemInfo 22 }
es-SystemPoolTable OBJECT-TYPE
    SYNTAX  SEQUENCE OF es-SysPoolEntryDef
    ACCESS  not-accessible
    STATUS  mandatory
    DESCRIPTION
            "A list of Pool entries.  The number of
            entries is given by the value of SysPoolNumber."
    ::= { es-SystemInfo 23 }
es-SysPoolEntry OBJECT-TYPE
    SYNTAX  es-SysPoolEntryDef
    ACCESS  not-accessible
    STATUS  mandatory
    DESCRIPTION
            "An system pool entry"
    INDEX   { es-SysPoolIndex }
    ::= { es-SystemPoolTable 1 }
es-SysPoolEntryDef ::=
    SEQUENCE {
        es-SysPoolIndex  INTEGER,
        es-SysPoolID  DisplayString,
        es-SysPoolCapacity  DisplayString,
        es-SysPoolFreeSize   DisplayString,
        es-SysPoolStatus DisplayString
    }
es-SysPoolIndex OBJECT-TYPE
    SYNTAX  INTEGER
    ACCESS  read-only
    STATUS  mandatory
    DESCRIPTION
            "A unique value for each system Pool. Its value
            ranges between 1 and the value of SysPoolNumber.  The
            value for each Pool must remain constant at
            least from one re-initialization of the entity's
            Pool system to the next re-initialization."
    ::= { es-SysPoolEntry 1 }
es-SysPoolID OBJECT-TYPE
    SYNTAX  DisplayString (SIZE (0..255))
    ACCESS  read-only
    STATUS  mandatory
    DESCRIPTION "A textual string containing Pool ID of the Pool."
    ::= { es-SysPoolEntry 2 }
es-SysPoolCapacity OBJECT-TYPE
    SYNTAX  DisplayString (SIZE (0..15))
    ACCESS  read-only
    STATUS  mandatory
    DESCRIPTION "System Pool capacity."
    ::= { es-SysPoolEntry 3 }
es-SysPoolFreeSize OBJECT-TYPE
    SYNTAX  DisplayString (SIZE (0..15))
    ACCESS  read-only
    STATUS  mandatory
    DESCRIPTION "System Pool free size."
    ::= { es-SysPoolEntry 4 }
es-SysPoolStatus OBJECT-TYPE
    SYNTAX  DisplayString (SIZE (0..255))
    ACCESS  read-only
    STATUS  mandatory
    DESCRIPTION "System Pool status."
    ::= { es-SysPoolEntry 5 }

    
END

-- *******************************************************************
-- QTECH-AC-DOT11-MIB.mib : Qtech AC DOT11 MIB 
-- 
-- Oct 2009, kangxk@qtech.com.cn
--
-- Copyright (c) 2009 by Qtech Networks Co.,Ltd.
-- All rights reserved.
-- *******************************************************************

QTECH-AC-DOT11-MIB DEFINITIONS ::= BEGIN 
IMPORTS
    MODULE-IDENTITY,
    OBJECT-TYPE,
    Integer32
        FROM SNMPv2-SMI 
    TruthValue,
    MacAddress,
    DisplayString
        FROM SNMPv2-TC 
    MODULE-COMPLIANCE,
    OBJECT-GROUP        
        FROM SNMPv2-CONF
    qtechMgmt          
        FROM QTECH-SMI;   
                         

-- **********************************************
-- * MODULE IDENTITY 
-- ********************************************** 
qtechAcDot11MIB MODULE-IDENTITY 
    LAST-UPDATED    "200911290000Z"
    ORGANIZATION
        "Qtech Networks Co.,Ltd."
    CONTACT-INFO
        "Tel: 4008-111-000 
           E-mail: service@qtech.com.cn "
        
    DESCRIPTION
       "
       802.11N Module in AC for Qtech SNC
       This is AC device manage MIB.
       "
    REVISION      "200911290000Z"
    DESCRIPTION
       "Initial version of this MIB module."
          
    ::= { qtechMgmt  65 }


-- ***************************************************************************
-- * Major sections 
-- ***************************************************************************
qtechAcDot11MIBObjects OBJECT IDENTIFIER  ::= { qtechAcDot11MIB 1 }
qtechApDot11MIBObjects OBJECT IDENTIFIER  ::= { qtechAcDot11MIB 2 }
qtechWlanDot11MIBObjects OBJECT IDENTIFIER  ::= { qtechAcDot11MIB 3 }

-- ***************************************************************************
-- * AC MIB object 
-- ***************************************************************************

-- linktest sta_mac
qtechAcDot11LinkTestStaTable OBJECT-TYPE
    SYNTAX SEQUENCE OF QtechAcDot11LinkTestStaEntry
    MAX-ACCESS not-accessible
    STATUS  current
    DESCRIPTION
            "DOT11 Link test a station."
    ::= { qtechAcDot11MIBObjects 1 }

qtechAcDot11LinkTestStaEntry OBJECT-TYPE
    SYNTAX QtechAcDot11LinkTestStaEntry
    MAX-ACCESS not-accessible
    STATUS current
    DESCRIPTION
        "DOT11 Link test a station."
    INDEX   { qtechAcDot11LinkMac }
    ::= { qtechAcDot11LinkTestStaTable 1 }

QtechAcDot11LinkTestStaEntry ::=
    SEQUENCE {
             qtechAcDot11LinkMac MacAddress,
             qtechAcDot11Link DisplayString
    }
    
qtechAcDot11LinkMac OBJECT-TYPE
    SYNTAX MacAddress
    MAX-ACCESS not-accessible
    STATUS current
    DESCRIPTION
            "Link Test MAC."
    ::= { qtechAcDot11LinkTestStaEntry 1 }
    
qtechAcDot11Link OBJECT-TYPE
    SYNTAX DisplayString (SIZE (0..255))
    MAX-ACCESS read-only
    STATUS current
    DESCRIPTION
            "Link Test Detail."
    ::= { qtechAcDot11LinkTestStaEntry 2 }

-- show client details mac
qtechAcDot11ShowClientTable OBJECT-TYPE
    SYNTAX SEQUENCE OF QtechAcDot11ShowClientEntry
    MAX-ACCESS not-accessible
    STATUS  current
    DESCRIPTION
            "Show client detail."
    ::= { qtechAcDot11MIBObjects 2 }

qtechAcDot11ShowClientEntry OBJECT-TYPE
    SYNTAX QtechAcDot11ShowClientEntry
    MAX-ACCESS not-accessible
    STATUS current
    DESCRIPTION
        "Show client detail entry."
    INDEX   { qtechAcDot11ClientMac }
    ::= { qtechAcDot11ShowClientTable 1 }

QtechAcDot11ShowClientEntry ::=
    SEQUENCE {
           qtechAcDot11ClientMac MacAddress,
           qtechAcDot11Client DisplayString
    }
    
qtechAcDot11ClientMac OBJECT-TYPE
    SYNTAX MacAddress
    MAX-ACCESS not-accessible
    STATUS current
    DESCRIPTION
            "Client MAC."
    ::= { qtechAcDot11ShowClientEntry 1 }
    
qtechAcDot11Client OBJECT-TYPE
    SYNTAX DisplayString (SIZE (0..255))
    MAX-ACCESS read-only
    STATUS current
    DESCRIPTION
            "Client Detail."
    ::= { qtechAcDot11ShowClientEntry 2 }

-- auth-timeout
qtechAcDot11AuthTimeout OBJECT-TYPE
    SYNTAX  Integer32
    MAX-ACCESS  read-write
    STATUS  current
    DESCRIPTION
            "Auth timeout."
    ::= { qtechAcDot11MIBObjects 3 }
    
-- country country_code
qtechAcDot11CountryTable OBJECT-TYPE
    SYNTAX SEQUENCE OF QtechAcDot11CountryEntry
    MAX-ACCESS not-accessible
    STATUS  current
    DESCRIPTION
            "The country code table."
    ::= { qtechAcDot11MIBObjects 4 }

qtechAcDot11CountryEntry OBJECT-TYPE
    SYNTAX QtechAcDot11CountryEntry
    MAX-ACCESS not-accessible
    STATUS current
    DESCRIPTION
        "The country code entry."
    INDEX   { qtechAcDot11CountryNum }
    ::= { qtechAcDot11CountryTable 1 }

QtechAcDot11CountryEntry ::=
    SEQUENCE {
        qtechAcDot11CountryNum    Integer32,
        qtechAcDot11Country       DisplayString,
        qtechAcDot11CountryEnable TruthValue
    }

qtechAcDot11CountryNum OBJECT-TYPE 
    SYNTAX Integer32
    MAX-ACCESS not-accessible 
    STATUS current 
    DESCRIPTION
        "Country Code Index NUM."
    ::= { qtechAcDot11CountryEntry 1}

qtechAcDot11Country OBJECT-TYPE
    SYNTAX DisplayString (SIZE (0..3))
    MAX-ACCESS read-write
    STATUS current
    DESCRIPTION
        "AC's Country code."
    ::= { qtechAcDot11CountryEntry 2 }
    
qtechAcDot11CountryEnable OBJECT-TYPE
    SYNTAX TruthValue
    MAX-ACCESS read-write
    STATUS current
    DESCRIPTION
        "AC's Country code enable."
    ::= { qtechAcDot11CountryEntry 3 }


-- ***************************************************************************
-- * AP MIB object 
-- ***************************************************************************

-- (config-ap)#poe enable
qtechApDot11PoeTable OBJECT-TYPE
    SYNTAX SEQUENCE OF QtechApDot11PoeEntry
    MAX-ACCESS not-accessible 
    STATUS current 
    DESCRIPTION
      "Qtech AP POE MIB"
    ::={ qtechApDot11MIBObjects 1 }

qtechApDot11PoeEntry OBJECT-TYPE 
    SYNTAX QtechApDot11PoeEntry
    MAX-ACCESS not-accessible
    STATUS current
    DESCRIPTION
      "AP ID is the index of this MIB table."
    INDEX { qtechApDot11PoeAPID }
    ::={ qtechApDot11PoeTable 1 }

QtechApDot11PoeEntry ::=
    SEQUENCE {
        qtechApDot11PoeAPID               INTEGER,
        qtechApDot11PoeEnable             TruthValue    
    }
    
qtechApDot11PoeAPID OBJECT-TYPE 
    SYNTAX TruthValue
    MAX-ACCESS not-accessible
    STATUS current 
    DESCRIPTION
      "AP ID"
    ::= { qtechApDot11PoeEntry 1}
    
qtechApDot11PoeEnable OBJECT-TYPE 
    SYNTAX TruthValue
    MAX-ACCESS read-write
    STATUS current 
    DESCRIPTION
      "POE Enable."
    ::= { qtechApDot11PoeEntry 2}
    
-- (config-ap)#[no]chan-width {20 | 40}
qtechApDot11ChannelTable OBJECT-TYPE
    SYNTAX SEQUENCE OF QtechApDot11ChannelEntry
    MAX-ACCESS not-accessible 
    STATUS current 
    DESCRIPTION
      "Qtech AP Channel width MIB"
    ::={ qtechApDot11MIBObjects 2 }

qtechApDot11ChannelEntry OBJECT-TYPE 
    SYNTAX QtechApDot11ChannelEntry
    MAX-ACCESS not-accessible
    STATUS current
    DESCRIPTION
      "AP ID is the index of this MIB table."
    INDEX { qtechApDot11ChannelAPID  }
    ::={ qtechApDot11ChannelTable 1 }

QtechApDot11ChannelEntry ::=
    SEQUENCE {
        qtechApDot11ChannelAPID            INTEGER,
        qtechApDot11ChannelWidthA          INTEGER,
        qtechApDot11ChannelWidthB          INTEGER
    }
    
qtechApDot11ChannelAPID OBJECT-TYPE 
    SYNTAX INTEGER
    MAX-ACCESS not-accessible
    STATUS current 
    DESCRIPTION
      "AP ID"
    ::= { qtechApDot11ChannelEntry 1}    
    
qtechApDot11ChannelWidthA OBJECT-TYPE 
    SYNTAX INTEGER
    MAX-ACCESS read-write 
    STATUS current 
    DESCRIPTION
      "Radio 1 Channel width."
    DEFVAL { 20 }
    ::= { qtechApDot11ChannelEntry 2}
  
qtechApDot11ChannelWidthB OBJECT-TYPE 
    SYNTAX INTEGER
    MAX-ACCESS read-write 
    STATUS current 
    DESCRIPTION
      "Radio 2 Channel width."
    DEFVAL { 20 }
    ::= { qtechApDot11ChannelEntry 3}  

-- (config-ap)#[no]antenne {receive|transmit} {number}
qtechApDot11AntenneTable OBJECT-TYPE
    SYNTAX SEQUENCE OF QtechApDot11AntenneEntry
    MAX-ACCESS not-accessible 
    STATUS current 
    DESCRIPTION
      "Qtech AP Antenne MIB"
    ::={ qtechApDot11MIBObjects 3 }

qtechApDot11AntenneEntry OBJECT-TYPE 
    SYNTAX QtechApDot11AntenneEntry
    MAX-ACCESS not-accessible
    STATUS current
    DESCRIPTION
      "AP ID is the index of this MIB table."
    INDEX { qtechApDot11AntenneAPID  }
    ::={ qtechApDot11AntenneTable 1 }

QtechApDot11AntenneEntry ::=
    SEQUENCE {
        qtechApDot11AntenneAPID            INTEGER,
        qtechApDot11AntenneRxA             INTEGER,
        qtechApDot11AntenneTxA             INTEGER,
        qtechApDot11AntenneRxB             INTEGER,
        qtechApDot11AntenneTxB             INTEGER     
    }
    
qtechApDot11AntenneAPID OBJECT-TYPE 
    SYNTAX INTEGER
    MAX-ACCESS not-accessible
    STATUS current 
    DESCRIPTION
      "AP ID"
    ::= { qtechApDot11AntenneEntry 1}  
    
qtechApDot11AntenneRxA OBJECT-TYPE 
    SYNTAX INTEGER (0..7)
    MAX-ACCESS read-write 
    STATUS current 
    DESCRIPTION
      "Radio 1 Antenne Receive."
    DEFVAL { 7 }
    ::= { qtechApDot11AntenneEntry 2}
    
qtechApDot11AntenneTxA OBJECT-TYPE 
    SYNTAX INTEGER (0..7)
    MAX-ACCESS read-write 
    STATUS current 
    DESCRIPTION
      "Radio 1 Antenne Transmit."
    DEFVAL { 7 }
    ::= { qtechApDot11AntenneEntry 3}

qtechApDot11AntenneRxB OBJECT-TYPE 
    SYNTAX INTEGER (0..7)
    MAX-ACCESS read-write 
    STATUS current 
    DESCRIPTION
      "Radio 2 Antenne Receive."
    DEFVAL { 7 }
    ::= { qtechApDot11AntenneEntry 4}
    
qtechApDot11AntenneTxB OBJECT-TYPE 
    SYNTAX INTEGER (0..7)
    MAX-ACCESS read-write 
    STATUS current 
    DESCRIPTION
      "Radio 2 Antenne Transmit."
    DEFVAL { 7 }
    ::= { qtechApDot11AntenneEntry 5}


--***************************************************************************
--* WLAN MIB object 
--***************************************************************************

qtechWlanDot11LoadTable OBJECT-TYPE
    SYNTAX SEQUENCE OF QtechWlanDot11LoadTEntry
    MAX-ACCESS not-accessible 
    STATUS current 
    DESCRIPTION
      "Qtech WLAN Load MIB"
    ::={ qtechWlanDot11MIBObjects 1 }

qtechWlanDot11LoadTEntry  OBJECT-TYPE 
    SYNTAX QtechWlanDot11LoadTEntry
    MAX-ACCESS not-accessible
    STATUS current
    DESCRIPTION
      "An agent MAY process one or more WLAN, which is identifed by qtechApgWlanId.
      In other words, wlan ID is the index of this MIB table."
    INDEX { qtechWlanDot11WlanId }
    ::={ qtechWlanDot11LoadTable 1 }

QtechWlanDot11LoadTEntry ::=
    SEQUENCE {
        qtechWlanDot11WlanId             INTEGER,
        qtechWlanDot11Enable             TruthValue,
        qtechWlanDot11Window             INTEGER,
        qtechWlanDot11Flow               INTEGER      
    }

qtechWlanDot11WlanId OBJECT-TYPE 
    SYNTAX INTEGER
    MAX-ACCESS not-accessible
    STATUS current 
    DESCRIPTION
      "WLAN ID."
    ::= { qtechWlanDot11LoadTEntry 1}


qtechWlanDot11Enable OBJECT-TYPE 
    SYNTAX TruthValue
    MAX-ACCESS read-write
    STATUS current 
    DESCRIPTION
      "Load Balancing Enable."
    DEFVAL { false } 
    ::= { qtechWlanDot11LoadTEntry 2}

qtechWlanDot11Window OBJECT-TYPE 
    SYNTAX INTEGER (0..20)      
    MAX-ACCESS read-write
    STATUS current 
    DESCRIPTION
      "Load Balancing Window Clients"   
    ::= { qtechWlanDot11LoadTEntry 3}

qtechWlanDot11Flow OBJECT-TYPE 
    SYNTAX INTEGER (0..130)
    MAX-ACCESS read-write 
    STATUS current 
    DESCRIPTION
      "Load Balancing Flow Threshold"
    ::= { qtechWlanDot11LoadTEntry 4}

--***************************************************************************
--* 802.11N MIB object 
--***************************************************************************
-- (config-ac)#11A 11nsupport

qtechNetDot11AEnable OBJECT-TYPE 
    SYNTAX TruthValue
    MAX-ACCESS read-write
    STATUS current 
    DESCRIPTION
      "Radio 1 11N Enable."
    DEFVAL { true } 
    ::= { qtechAcDot11MIBObjects 5}
    
qtechNetDot11AMCS0 OBJECT-TYPE 
    SYNTAX TruthValue     
    MAX-ACCESS read-write
    STATUS current 
    DESCRIPTION
      "Radio 1 11N Support MCS 0"   
    ::= { qtechAcDot11MIBObjects 6}

qtechNetDot11AMCS1 OBJECT-TYPE 
    SYNTAX TruthValue     
    MAX-ACCESS read-write
    STATUS current 
    DESCRIPTION
      "Radio 1 11N Support MCS 1"   
    ::= { qtechAcDot11MIBObjects 7}
    
qtechNetDot11AMCS2 OBJECT-TYPE 
    SYNTAX TruthValue     
    MAX-ACCESS read-write
    STATUS current 
    DESCRIPTION
      "Radio 1 11N Support MCS 2"   
    ::= { qtechAcDot11MIBObjects 8}

qtechNetDot11AMCS3 OBJECT-TYPE 
    SYNTAX TruthValue     
    MAX-ACCESS read-write
    STATUS current 
    DESCRIPTION
      "Radio 1 11N Support MCS 3"   
    ::= { qtechAcDot11MIBObjects 9}
    
qtechNetDot11AMCS4 OBJECT-TYPE 
    SYNTAX TruthValue     
    MAX-ACCESS read-write
    STATUS current 
    DESCRIPTION
      "Radio 1 11N Support MCS 4"   
    ::= { qtechAcDot11MIBObjects 10}
    
qtechNetDot11AMCS5 OBJECT-TYPE 
    SYNTAX TruthValue     
    MAX-ACCESS read-write
    STATUS current 
    DESCRIPTION
      "Radio 1 11N Support MCS 5"   
    ::= { qtechAcDot11MIBObjects 11}
    
qtechNetDot11AMCS6 OBJECT-TYPE 
    SYNTAX TruthValue     
    MAX-ACCESS read-write
    STATUS current 
    DESCRIPTION
      "Radio 1 11N Support MCS 6"   
    ::= { qtechAcDot11MIBObjects 12}

qtechNetDot11AMCS7 OBJECT-TYPE 
    SYNTAX TruthValue     
    MAX-ACCESS read-write
    STATUS current 
    DESCRIPTION
      "Radio 1 11N Support MCS 7"   
    ::= { qtechAcDot11MIBObjects 13}
    
qtechNetDot11AMCS8 OBJECT-TYPE 
    SYNTAX TruthValue     
    MAX-ACCESS read-write
    STATUS current 
    DESCRIPTION
      "Radio 1 11N Support MCS 8"   
    ::= { qtechAcDot11MIBObjects 14}
    
qtechNetDot11AMCS9 OBJECT-TYPE 
    SYNTAX TruthValue     
    MAX-ACCESS read-write
    STATUS current 
    DESCRIPTION
      "Radio 1 11N Support MCS 9"   
    ::= { qtechAcDot11MIBObjects 15}
    
qtechNetDot11AMCS10 OBJECT-TYPE 
    SYNTAX TruthValue     
    MAX-ACCESS read-write
    STATUS current 
    DESCRIPTION
      "Radio 1 11N Support MCS 10"   
    ::= { qtechAcDot11MIBObjects 16}
    
qtechNetDot11AMCS11 OBJECT-TYPE 
    SYNTAX TruthValue     
    MAX-ACCESS read-write
    STATUS current 
    DESCRIPTION
      "Radio 1 11N Support MCS 11"   
    ::= { qtechAcDot11MIBObjects 17}
    
qtechNetDot11AMCS12 OBJECT-TYPE 
    SYNTAX TruthValue     
    MAX-ACCESS read-write
    STATUS current 
    DESCRIPTION
      "Radio 1 11N Support MCS 12"   
    ::= { qtechAcDot11MIBObjects 18}
    
qtechNetDot11AMCS13 OBJECT-TYPE 
    SYNTAX TruthValue     
    MAX-ACCESS read-write
    STATUS current 
    DESCRIPTION
      "Radio 1 11N Support MCS 13"   
    ::= { qtechAcDot11MIBObjects 19}
    
qtechNetDot11AMCS14 OBJECT-TYPE 
    SYNTAX TruthValue     
    MAX-ACCESS read-write
    STATUS current 
    DESCRIPTION
      "Radio 1 11N Support MCS 14"   
    ::= { qtechAcDot11MIBObjects 20}
    
qtechNetDot11AMCS15 OBJECT-TYPE 
    SYNTAX TruthValue     
    MAX-ACCESS read-write
    STATUS current 
    DESCRIPTION
      "Radio 1 11N Support MCS 15"   
    ::= { qtechAcDot11MIBObjects 21}   

qtechNetDot11AAMPDU OBJECT-TYPE 
    SYNTAX INTEGER (0..7)
    MAX-ACCESS read-write 
    STATUS current 
    DESCRIPTION
      "Radio 1 11N Support AMPUD"
    ::= { qtechAcDot11MIBObjects 22}
    
-- (config-ac)#11nsupport enable radio 1

qtechNetDot11BEnable OBJECT-TYPE 
    SYNTAX TruthValue
    MAX-ACCESS read-write
    STATUS current 
    DESCRIPTION
      "Radio 2 11N Enable."
    DEFVAL { true } 
    ::= { qtechAcDot11MIBObjects 23}

qtechNetDot11BMCS0 OBJECT-TYPE 
    SYNTAX INTEGER (0..15)      
    MAX-ACCESS read-write
    STATUS current 
    DESCRIPTION
      "Radio 2 11N Support MCS0"   
    ::= { qtechAcDot11MIBObjects 24}
   
qtechNetDot11BMCS1 OBJECT-TYPE 
    SYNTAX INTEGER (0..15)      
    MAX-ACCESS read-write
    STATUS current 
    DESCRIPTION
      "Radio 2 11N Support MCS1"   
    ::= { qtechAcDot11MIBObjects 25}
   
qtechNetDot11BMCS2 OBJECT-TYPE 
    SYNTAX INTEGER (0..15)      
    MAX-ACCESS read-write
    STATUS current 
    DESCRIPTION
      "Radio 2 11N Support MCS2"   
    ::= { qtechAcDot11MIBObjects 26}
   
qtechNetDot11BMCS3 OBJECT-TYPE 
    SYNTAX INTEGER (0..15)      
    MAX-ACCESS read-write
    STATUS current 
    DESCRIPTION
      "Radio 2 11N Support MCS3"   
    ::= { qtechAcDot11MIBObjects 27}
   
qtechNetDot11BMCS4 OBJECT-TYPE 
    SYNTAX INTEGER (0..15)      
    MAX-ACCESS read-write
    STATUS current 
    DESCRIPTION
      "Radio 2 11N Support MCS4"   
    ::= { qtechAcDot11MIBObjects 28}
    
qtechNetDot11BMCS5 OBJECT-TYPE 
    SYNTAX INTEGER (0..15)      
    MAX-ACCESS read-write
    STATUS current 
    DESCRIPTION
      "Radio 2 11N Support MCS5"   
    ::= { qtechAcDot11MIBObjects 29}  
   
qtechNetDot11BMCS6 OBJECT-TYPE 
    SYNTAX INTEGER (0..15)      
    MAX-ACCESS read-write
    STATUS current 
    DESCRIPTION
      "Radio 2 11N Support MCS6"   
    ::= { qtechAcDot11MIBObjects 30}
   
qtechNetDot11BMCS7 OBJECT-TYPE 
    SYNTAX INTEGER (0..15)      
    MAX-ACCESS read-write
    STATUS current 
    DESCRIPTION
      "Radio 2 11N Support MCS7"   
    ::= { qtechAcDot11MIBObjects 31}
   
qtechNetDot11BMCS8 OBJECT-TYPE 
    SYNTAX INTEGER (0..15)      
    MAX-ACCESS read-write
    STATUS current 
    DESCRIPTION
      "Radio 2 11N Support MCS8"   
    ::= { qtechAcDot11MIBObjects 32}
    
qtechNetDot11BMCS9 OBJECT-TYPE 
    SYNTAX INTEGER (0..15)      
    MAX-ACCESS read-write
    STATUS current 
    DESCRIPTION
      "Radio 2 11N Support MCS9"   
    ::= { qtechAcDot11MIBObjects 33}
    
qtechNetDot11BMCS10 OBJECT-TYPE 
    SYNTAX INTEGER (0..15)      
    MAX-ACCESS read-write
    STATUS current 
    DESCRIPTION
      "Radio 2 11N Support MCS10"   
    ::= { qtechAcDot11MIBObjects 34}

qtechNetDot11BMCS11 OBJECT-TYPE 
    SYNTAX INTEGER (0..15)      
    MAX-ACCESS read-write
    STATUS current 
    DESCRIPTION
      "Radio 2 11N Support MCS11"   
    ::= { qtechAcDot11MIBObjects 35}
    
qtechNetDot11BMCS12 OBJECT-TYPE 
    SYNTAX INTEGER (0..15)      
    MAX-ACCESS read-write
    STATUS current 
    DESCRIPTION
      "Radio 2 11N Support MCS12"   
    ::= { qtechAcDot11MIBObjects 36}

qtechNetDot11BMCS13 OBJECT-TYPE 
    SYNTAX INTEGER (0..15)      
    MAX-ACCESS read-write
    STATUS current 
    DESCRIPTION
      "Radio 2 11N Support MCS13"   
    ::= { qtechAcDot11MIBObjects 37}
    
qtechNetDot11BMCS14 OBJECT-TYPE 
    SYNTAX INTEGER (0..15)      
    MAX-ACCESS read-write
    STATUS current 
    DESCRIPTION
      "Radio 2 11N Support MCS14"   
    ::= { qtechAcDot11MIBObjects 38}

qtechNetDot11BMCS15 OBJECT-TYPE 
    SYNTAX INTEGER (0..15)      
    MAX-ACCESS read-write
    STATUS current 
    DESCRIPTION
      "Radio 2 11N Support MCS15"   
    ::= { qtechAcDot11MIBObjects 39}
            
qtechNetDot11BAMPDU OBJECT-TYPE 
    SYNTAX INTEGER (0..7)
    MAX-ACCESS read-write 
    STATUS current 
    DESCRIPTION
      "Radio 2 11N Support AMPUD"
    ::= { qtechAcDot11MIBObjects 40}

-- (config-ac)#11gsupport radio 1
qtechNetDot11AGEnable OBJECT-TYPE 
    SYNTAX TruthValue
    MAX-ACCESS read-write
    STATUS current 
    DESCRIPTION
      "Radio 1 11G Spport Enable."
    DEFVAL { true } 
    ::= { qtechAcDot11MIBObjects 41}
    
-- (config-ac)#11gsupport radio 2
qtechNetDot11BGEnable OBJECT-TYPE 
    SYNTAX TruthValue
    MAX-ACCESS read-write
    STATUS current 
    DESCRIPTION
      "Radio 2 11G Spport Enable."
    DEFVAL { true } 
    ::= { qtechAcDot11MIBObjects 42}
    
    
--********************************************************************
--                                                                  **
--           conformance information                                **
--                                                                  **
--********************************************************************
qtechAcDot11MIBConformance OBJECT IDENTIFIER ::= { qtechAcDot11MIB 5 }
qtechAcDot11MIBCompliances OBJECT IDENTIFIER ::= { qtechAcDot11MIBConformance 1 }
qtechAcDot11MIBGroups      OBJECT IDENTIFIER ::= { qtechAcDot11MIBConformance 2 }


--********************************************************************
--                                                                  **
--           compliance statements                                  **
--                                                                  **
--********************************************************************
qtechAcDot11MIBCompliance MODULE-COMPLIANCE
        STATUS  current
        DESCRIPTION
                "The compliance statement for entities which implement
                the Qtech Ac dot11 Manager."
        MODULE  -- this module
                MANDATORY-GROUPS { qtechAcDot11MIBGroup}
        ::= { qtechAcDot11MIBCompliances 1 }


--********************************************************************
--                                                                  **
--           units of conformance                                   **
--                                                                  **
--********************************************************************
qtechAcDot11MIBGroup OBJECT-GROUP
        OBJECTS {
            qtechAcDot11Link,
            qtechAcDot11Client,
            qtechAcDot11AuthTimeout,
            qtechAcDot11Country,
            qtechAcDot11CountryEnable,
            qtechApDot11PoeEnable,
            qtechApDot11ChannelWidthA,
            qtechApDot11ChannelWidthB,
            qtechApDot11AntenneRxA,
            qtechApDot11AntenneTxA,
            qtechApDot11AntenneRxB,
            qtechApDot11AntenneTxB,
            qtechWlanDot11Enable,
            qtechWlanDot11Window,
            qtechWlanDot11Flow,
            qtechNetDot11AEnable,
            qtechNetDot11AMCS0,
            qtechNetDot11AMCS1,
            qtechNetDot11AMCS2,
            qtechNetDot11AMCS3,
            qtechNetDot11AMCS4,
            qtechNetDot11AMCS5,
            qtechNetDot11AMCS6,
            qtechNetDot11AMCS7,
            qtechNetDot11AMCS8,
            qtechNetDot11AMCS9,
            qtechNetDot11AMCS10,
            qtechNetDot11AMCS11,
            qtechNetDot11AMCS12,
            qtechNetDot11AMCS13,
            qtechNetDot11AMCS14,
            qtechNetDot11AMCS15,
            qtechNetDot11AAMPDU,
            qtechNetDot11BEnable,
            qtechNetDot11BMCS0,
            qtechNetDot11BMCS1,
            qtechNetDot11BMCS2,
            qtechNetDot11BMCS3,
            qtechNetDot11BMCS4,
            qtechNetDot11BMCS5,
            qtechNetDot11BMCS6,
            qtechNetDot11BMCS7,
            qtechNetDot11BMCS8,
            qtechNetDot11BMCS9,
            qtechNetDot11BMCS10,
            qtechNetDot11BMCS11,
            qtechNetDot11BMCS12,
            qtechNetDot11BMCS13,
            qtechNetDot11BMCS14,
            qtechNetDot11BMCS15,
            qtechNetDot11BAMPDU,
            qtechNetDot11AGEnable,
            qtechNetDot11BGEnable    
        }
        STATUS  current
        DESCRIPTION
                "A collection of objects providing ac dot11 manager (echo) ability to a
                Qtech agent."
        ::= { qtechAcDot11MIBGroups 1 }
END

-- *****************************************************************
-- QTECH-ACL-CONTEXT-MIB.mib:  Qtech Acl MIB file for multiple context
--
--
-- December 2009, rendh
--
-- Copyright (c) 2009 by Qtech Networks Co.,Ltd.
-- All rights reserved.
-- 
-- *****************************************************************
--

QTECH-ACL-CONTEXT-MIB DEFINITIONS ::= BEGIN

IMPORTS
        MODULE-IDENTITY,
        OBJECT-TYPE,
        Integer32,
        Unsigned32,
        IpAddress
                FROM SNMPv2-SMI
        TruthValue,
        DisplayString,
        RowStatus,
        MacAddress
                FROM SNMPv2-TC
        MODULE-COMPLIANCE,
        OBJECT-GROUP
                FROM SNMPv2-CONF
        IfIndex,
        ConfigStatus
                FROM QTECH-TC        
        qtechMgmt
                FROM QTECH-SMI;

qtechAclVCMIB MODULE-IDENTITY
        LAST-UPDATED "200912060000Z"
        ORGANIZATION "Qtech Networks Co.,Ltd."
        CONTACT-INFO
                " 
                Tel: 4008-111-000 

                E-mail: service@qtech.com.cn"
        DESCRIPTION
                "This module defines qtech acl mibs for multiple context."
        REVISION      "200912060000Z"
        DESCRIPTION
                "Initial version of this MIB module."
        ::= { qtechMgmt 66}

--ACLNO ::= TEXTUAL-CONVENTION
--    STATUS current
--    DESCRIPTION
--        " Serial number of Access control list entry, Access control list entry of 
--          bigger ACL number will have  higher implement priority. One ACL number 
--          corresponding to only one entry."
--    SYNTAX      INTEGER

-- Access control list
qtechAclVCMIBObjects OBJECT IDENTIFIER ::= { qtechAclVCMIB 1 }


qtechAclVCTable OBJECT-TYPE
        SYNTAX SEQUENCE OF QtechAclVCEntry
        MAX-ACCESS not-accessible
        STATUS current
        DESCRIPTION
               "A table of acl request entries."
        ::= { qtechAclVCMIBObjects 1 }
    
qtechAclVCEntry OBJECT-TYPE
        SYNTAX QtechAclVCEntry
        MAX-ACCESS not-accessible
        STATUS current
        DESCRIPTION
                "Entry contains acl name and mode."  
        INDEX { qtechAclContextNameVC,  qtechAclNameVC }
        ::= { qtechAclVCTable 1 }
        
QtechAclVCEntry ::= 
        SEQUENCE {
                qtechAclContextNameVC   DisplayString,
                qtechAclNameVC          DisplayString,
                qtechAclModeVC          INTEGER,
                qtechAclEntryStatusVC   ConfigStatus
        } 

qtechAclContextNameVC OBJECT-TYPE
        SYNTAX DisplayString(SIZE (1..31))
        MAX-ACCESS read-only
        STATUS current
        DESCRIPTION
            "context name of this entry."
        ::= { qtechAclVCEntry  1 }        
           
qtechAclNameVC OBJECT-TYPE
        SYNTAX DisplayString(SIZE (1..32))
        MAX-ACCESS read-only
        STATUS current
        DESCRIPTION
            "Access list name of this entry.This value is unique for every entry
            When this string be used as an index,Value of a sub-identifier equal 
            ASCII value of corresponding character(first sub-identifier corresponds
            first character of string). The number of sub-identifiers of this string
            must be 32,If length of string is less than 32 the sub-identifier(0x0) 
            will be filled in tail."
        ::= { qtechAclVCEntry  2 }
                
qtechAclModeVC OBJECT-TYPE
        SYNTAX INTEGER{
               acl-ip-standard(1),   
               acl-ip-extended(2),   
               acl-mac-extended(3),  
               acl-expert(4), 
               acl-ipv6-extended(5)
            }
        MAX-ACCESS read-create
        STATUS current
        DESCRIPTION
               " Config mode of this ACL"
        ::= { qtechAclVCEntry 3 }    

qtechAclEntryStatusVC OBJECT-TYPE
        SYNTAX ConfigStatus
        MAX-ACCESS read-create
        STATUS current
        DESCRIPTION
            "Status of this entry, set its value to invalid will delete this entry.
            set its value to valid has no effect."
        ::= { qtechAclVCEntry 4 }

-- if table ******************************************
    

        

qtechAclIfVCTable OBJECT-TYPE
        SYNTAX SEQUENCE OF QtechAclIfVCEntry
        MAX-ACCESS not-accessible
        STATUS current
        DESCRIPTION
            "list of ACL interface objects."
        ::= { qtechAclVCMIBObjects 2 }
    
qtechAclIfVCEntry OBJECT-TYPE
        SYNTAX QtechAclIfVCEntry
        MAX-ACCESS not-accessible
        STATUS current
        DESCRIPTION
            "Entry ACL interface information."
        INDEX { qtechAclIfContextNameVC, qtechAclIfIndexVC }
        ::= { qtechAclIfVCTable 1 }
        
        

QtechAclIfVCEntry ::=
        SEQUENCE {
            qtechAclIfContextNameVC      DisplayString,
            qtechAclIfIndexVC            IfIndex,
            qtechAclIfMaxEntryNumVC      Integer32,
            qtechAclIfCurruntEntryNumVC  Integer32,
            qtechIfInAclNameVC           DisplayString,
            qtechIfOutAclNameVC          DisplayString
        }

qtechAclIfContextNameVC   OBJECT-TYPE
        SYNTAX DisplayString(SIZE (1..31))
        MAX-ACCESS read-only
        STATUS current
        DESCRIPTION
            "context name of this entry."
        ::= { qtechAclIfVCEntry 1 }   
    

qtechAclIfIndexVC OBJECT-TYPE
        SYNTAX IfIndex
        MAX-ACCESS read-only
        STATUS current
        DESCRIPTION
            " "
        ::= { qtechAclIfVCEntry 2 }

qtechAclIfMaxEntryNumVC OBJECT-TYPE
        SYNTAX Integer32
        MAX-ACCESS read-only
        STATUS current
        DESCRIPTION
               "Max num of ACL entry(ACE) in a interface."
        ::= { qtechAclIfVCEntry 3 }

qtechAclIfCurruntEntryNumVC OBJECT-TYPE
        SYNTAX Integer32
        MAX-ACCESS read-only
        STATUS current
        DESCRIPTION
               "Currunt valid num of ACL entry(ACE) in a interface."
        ::= { qtechAclIfVCEntry 4 }
        
qtechIfInAclNameVC OBJECT-TYPE
        SYNTAX DisplayString(SIZE (0..32))
        MAX-ACCESS read-write
        STATUS current
        DESCRIPTION
            "Access list name of ACL of this interface match for input. 
            It indicate that this interface doesn't match any ACL for input 
            if this string is null"
        ::= { qtechAclIfVCEntry  5 }        
        
qtechIfOutAclNameVC OBJECT-TYPE
        SYNTAX DisplayString(SIZE (0..32))
        MAX-ACCESS read-write
        STATUS current
        DESCRIPTION
            "Access list name of ACL of this interface match for output. 
            It indicate that this interface doesn't match any ACL for output 
            if this string is null
            
            This relation function apply only L3 interface."
        ::= { qtechAclIfVCEntry  6 }
        
        
-- AceExt************************************************

qtechAceExtVCTable OBJECT-TYPE
        SYNTAX SEQUENCE OF QtechAceExtVCEntry
        MAX-ACCESS not-accessible
        STATUS current
        DESCRIPTION
               "A table of ACE request entries."
        ::= { qtechAclVCMIBObjects 3 }
  
qtechAceExtVCEntry OBJECT-TYPE
        SYNTAX QtechAceExtVCEntry
        MAX-ACCESS not-accessible
        STATUS current
        DESCRIPTION
                "Entry contains ace parameters and results.
                
                A management station wishing to create an entry should
                first generate a pseudo-random serial number to be used
                as the index to a ace entry of a acl.  The station should
                then create the associated entry.
                
                We must set all specifies valid values for the 
                non-defaulted configuration objects, certainly, it should
                also modify  the default values for the other configuration 
                objects if the defaults are not appropriate.
                                       
                Once the appropriate instance of all the configuration
                objects have been created or set,the row status should be set
                to active to initiate the request."  
        INDEX {  qtechAceExtContextNameVC, qtechAceExtAclNameVC,qtechAceExtIndexVC }
        ::= { qtechAceExtVCTable 1 }
        
QtechAceExtVCEntry ::= 
        SEQUENCE {
                qtechAceExtContextNameVC DisplayString,
                qtechAceExtAclNameVC DisplayString,
                qtechAceExtIndexVC Integer32,
                qtechAceExtIfAnyVIDVC TruthValue,
                qtechAceExtVIDVC Unsigned32,
                qtechAceExtIfAnySourceIpVC TruthValue,
                qtechAceExtSourceIpVC IpAddress,
                qtechAceExtIfAnySourceWildCardVC TruthValue,
                qtechAceExtSourceWildCardVC IpAddress,
                qtechAceExtIfAnySourceMacAddrVC TruthValue,
                qtechAceExtSourceMacAddrVC MacAddress,
                qtechAceExtIfAnyDestIpVC TruthValue,
                qtechAceExtDestIpVC IpAddress,
                qtechAceExtIfAnyDestWildCardVC TruthValue,
                qtechAceExtDestIpWildCardVC IpAddress,
                qtechAceExtIfAnyDestMacAddrVC TruthValue,
                qtechAceExtDestMacAddrVC MacAddress,
                qtechAceExtIfAnyEtherLikeTypeVC TruthValue,
                qtechAceExtEtherLikeTypeVC Integer32,
                qtechAceExtIfAnyIpProtocolFieldVC TruthValue,
                qtechAceExtIpProtocolFieldVC Integer32,
                qtechAceExtSourceProtocolPortVC Integer32,
                qtechAceExtDestProtocolPortVC Integer32,
                qtechAceExtIfAnyProtocolTypeVC TruthValue,
                qtechAceExtProtocolTypeVC Integer32,
                qtechAceExtFlowActionVC INTEGER,
                qtechAceExtEntryStautsVC RowStatus,
                qtechAceExtTimeRangeNameVC DisplayString,
                qtechAceExtSourcePortOpVC INTEGER,
                qtechAceExtSourceProtocolPortRangeVC Integer32,
                qtechAceExtDestPortOpVC INTEGER,
                qtechAceExtDestProtocolPortRangeVC Integer32,
                qtechAceExtIfAnyCosVC TruthValue,
                qtechAceExtCosVC Integer32,
                qtechAceExtIfAnyIpPrecVC TruthValue,
                qtechAceExtIpPrecVC Integer32,
                qtechAceExtIfAnyDscpVC TruthValue,
                qtechAceExtDscpVC Integer32,
                qtechAceExtIfAnySourceMacAddrWildCardVC TruthValue,
                qtechAceExtSourceMacAddrWildCardVC MacAddress,
                qtechAceExtIfAnyDestMacAddrWildCardVC TruthValue,
                qtechAceExtDestMacAddrWildCardVC MacAddress,
                qtechAceExtIfAnyTcpFlagVC TruthValue,
                qtechAceExtTcpFlagVC Integer32,
                qtechAceExtIfAnySourceIp6VC TruthValue,
                qtechAceExtSourceIp6VC OCTET STRING,
                qtechAceExtIfAnySourceIp6WildCardVC TruthValue,
                qtechAceExtSourceIp6WildCardVC OCTET STRING,
                qtechAceExtIfAnyDestIp6VC TruthValue,
                qtechAceExtDestIp6VC OCTET STRING,
                qtechAceExtIfAnyDestIp6WildCardVC TruthValue,
                qtechAceExtDestIp6WildCardVC OCTET STRING
        }
        
qtechAceExtContextNameVC   OBJECT-TYPE
        SYNTAX DisplayString(SIZE (1..31))
        MAX-ACCESS read-only
        STATUS current
        DESCRIPTION
            "context name of this entry."
        ::= { qtechAceExtVCEntry  1 }      

qtechAceExtAclNameVC OBJECT-TYPE
        SYNTAX DisplayString(SIZE (1..32))
        MAX-ACCESS read-only
        STATUS current
        DESCRIPTION
            "Access list name of this ace belong to.
            When this string be used as an index,Value of a sub-identifier equal 
            ASCII value of corresponding character(first sub-identifier corresponds
            first character of string). The number of sub-identifiers of this string
            must be 32,If length of string is less than 32 the sub-identifier(0x0) 
            will be filled in tail."
        ::= { qtechAceExtVCEntry  2 }

qtechAceExtIndexVC OBJECT-TYPE
        SYNTAX Integer32(1..2147483647)
        MAX-ACCESS read-only
        STATUS current
        DESCRIPTION
               "Object which specifies a unique entry in the
                qtechAclTable.  A management station wishing
                to initiate a acl operation should use a
                pseudo-random value for this object when creating
                or modifying an instance of a qtechAclEntry.
                The RowStatus semantics of the qtechAclEntryStatus
                object will prevent access conflicts."
        ::= { qtechAceExtVCEntry 3 }
   
qtechAceExtIfAnyVIDVC OBJECT-TYPE
        SYNTAX TruthValue
        MAX-ACCESS read-create
        STATUS current
        DESCRIPTION
            "VID of class will not be checked if this value is true."
        DEFVAL{ true }
        ::= { qtechAceExtVCEntry 4 }
   
qtechAceExtVIDVC OBJECT-TYPE
        SYNTAX Unsigned32(0..4094)
        MAX-ACCESS read-create
        STATUS current
        DESCRIPTION
            "VID of Ace flow definition."
        ::= { qtechAceExtVCEntry 5 }
    
qtechAceExtIfAnySourceIpVC OBJECT-TYPE
        SYNTAX TruthValue
        MAX-ACCESS read-create
        STATUS current
        DESCRIPTION
            "Source Ip of class will not be checked if this value is true."
        DEFVAL{ true }
        ::= { qtechAceExtVCEntry 6 }
            
qtechAceExtSourceIpVC OBJECT-TYPE
        SYNTAX IpAddress
        MAX-ACCESS read-create
        STATUS current
        DESCRIPTION
            "Sourece ip address of Ace flow definition."
        ::= { qtechAceExtVCEntry 7 }

qtechAceExtIfAnySourceWildCardVC OBJECT-TYPE
        SYNTAX TruthValue
        MAX-ACCESS read-create
        STATUS current
        DESCRIPTION
            "Source Ip wild card of class will not be checked if this value is true."
        DEFVAL{ true }
        ::= { qtechAceExtVCEntry 8 }
                
qtechAceExtSourceWildCardVC OBJECT-TYPE
        SYNTAX IpAddress
        MAX-ACCESS read-create
        STATUS current
        DESCRIPTION
            "Sourece ip wild card(in reverse ip address mask)of Ace flow definition."
        ::= { qtechAceExtVCEntry 9 }        

qtechAceExtIfAnySourceMacAddrVC OBJECT-TYPE
        SYNTAX TruthValue
        MAX-ACCESS read-create
        STATUS current
        DESCRIPTION
            "Source mac address of class will not be checked if this value is true."
        DEFVAL{ true }
        ::= { qtechAceExtVCEntry 10 }
                
qtechAceExtSourceMacAddrVC OBJECT-TYPE
        SYNTAX MacAddress
        MAX-ACCESS read-create
        STATUS current
        DESCRIPTION
            "Sourece Mac address of Ace flow definition."
        ::= { qtechAceExtVCEntry 11 }                
 
qtechAceExtIfAnyDestIpVC OBJECT-TYPE
        SYNTAX TruthValue
        MAX-ACCESS read-create
        STATUS current
        DESCRIPTION
            "Destination Ip wild card of class will not be checked if this value is true."
        DEFVAL{ true }
        ::= { qtechAceExtVCEntry 12 }
         
qtechAceExtDestIpVC OBJECT-TYPE
        SYNTAX IpAddress
        MAX-ACCESS read-create
        STATUS current
        DESCRIPTION
            "Destination ip address of Ace flow definition."
        ::= { qtechAceExtVCEntry 13 }

qtechAceExtIfAnyDestWildCardVC OBJECT-TYPE
        SYNTAX TruthValue
        MAX-ACCESS read-create
        STATUS current
        DESCRIPTION
            "Source Ip wild card of class will not be checked if this value is true."
        DEFVAL{ true }
        ::= { qtechAceExtVCEntry 14 }
                
qtechAceExtDestIpWildCardVC OBJECT-TYPE
        SYNTAX IpAddress
        MAX-ACCESS read-create
        STATUS current
        DESCRIPTION
            "Destination ip wild card(in reverse ip address mask) of Ace flow definition."
        ::= { qtechAceExtVCEntry 15 }        

qtechAceExtIfAnyDestMacAddrVC OBJECT-TYPE
        SYNTAX TruthValue
        MAX-ACCESS read-create
        STATUS current
        DESCRIPTION
            "Source Ip wild card of class will not be checked if this value is true."
        DEFVAL{ true }
        ::= { qtechAceExtVCEntry 16 }
                
qtechAceExtDestMacAddrVC OBJECT-TYPE
        SYNTAX MacAddress
        MAX-ACCESS read-create
        STATUS current
        DESCRIPTION
            "Destination Mac address of Ace flow definition."
        ::= { qtechAceExtVCEntry 17 }

qtechAceExtIfAnyEtherLikeTypeVC OBJECT-TYPE
        SYNTAX TruthValue
        MAX-ACCESS read-create
        STATUS current
        DESCRIPTION
            "Ether Like Type in MAC packet will not be checked if this value is true."
        DEFVAL{ true }
        ::= { qtechAceExtVCEntry 18 }
            
qtechAceExtEtherLikeTypeVC OBJECT-TYPE
        SYNTAX Integer32
        MAX-ACCESS read-create
        STATUS current
        DESCRIPTION
            "Ether Like Type in MAC packet of Ace flow definition. "
        ::= { qtechAceExtVCEntry 19 }

qtechAceExtIfAnyIpProtocolFieldVC OBJECT-TYPE
        SYNTAX TruthValue
        MAX-ACCESS read-create
        STATUS current
        DESCRIPTION
            "Source Ip wild card of class will not be checked if this value is true."
        DEFVAL{ true }
        ::= { qtechAceExtVCEntry 20 }
            
qtechAceExtIpProtocolFieldVC OBJECT-TYPE
        SYNTAX Integer32
        MAX-ACCESS read-create
        STATUS current
        DESCRIPTION
            "The value of protocol field in IP packet of Ace flow definition."
        ::= { qtechAceExtVCEntry 21 }
      
qtechAceExtSourceProtocolPortVC OBJECT-TYPE
        SYNTAX Integer32
        MAX-ACCESS read-create
        STATUS current
        DESCRIPTION
            "The value of source protocol port in IP packet of Ace flow definition. It is 
             significative only to those protocol which support this field."
        ::= { qtechAceExtVCEntry 22 }

qtechAceExtDestProtocolPortVC OBJECT-TYPE
        SYNTAX Integer32
        MAX-ACCESS read-create
        STATUS current
        DESCRIPTION
            "The value of destination protocol port in IP packet of Ace flow definition. It is 
             significative only to those protocol which support this field(tcp,udp)."
        ::= { qtechAceExtVCEntry 23 }        

qtechAceExtIfAnyProtocolTypeVC OBJECT-TYPE
        SYNTAX TruthValue
        MAX-ACCESS read-create
        STATUS current
        DESCRIPTION
            "The value of protocol type field in IP packet will not be checked if this 
            value is true."
        DEFVAL{ true }
        ::= { qtechAceExtVCEntry 24 }
            
qtechAceExtProtocolTypeVC OBJECT-TYPE
        SYNTAX Integer32
        MAX-ACCESS read-create
        STATUS current
        DESCRIPTION
            "The value of protocol type field in IP packet of Ace flow definition. It is 
             significative only to those protocol which support this field(icmp,igmp)."
        ::= { qtechAceExtVCEntry 25 }            
                
qtechAceExtFlowActionVC OBJECT-TYPE
        SYNTAX INTEGER{
               permit(1),
               deny(2) 
        }
        MAX-ACCESS read-create
        STATUS current
        DESCRIPTION
            "Permit indicate that the kind of  flow which entry define will be allow to access ,
             deny indicate that the kind of flow which entry define will be refuse to access"
        ::= { qtechAceExtVCEntry 26 }
    
qtechAceExtEntryStautsVC OBJECT-TYPE
        SYNTAX RowStatus
        MAX-ACCESS read-create
        STATUS current
        DESCRIPTION
            "entry status for this list."
        ::= { qtechAceExtVCEntry 27 }

qtechAceExtTimeRangeNameVC OBJECT-TYPE
    SYNTAX      DisplayString(SIZE (0..32))
    MAX-ACCESS  read-create
    STATUS      current
    DESCRIPTION
        "Name of time-range of this ACE match. It indicate that 
         this ACE doesn't match any time-range if this string is null"
    ::= { qtechAceExtVCEntry 28 }

qtechAceExtSourcePortOpVC OBJECT-TYPE
        SYNTAX   INTEGER {
               noOperator(1), 
               lt(2), 
               gt(3),
               eq(4), 
               neq(5), 
               range(6) 
        }
        MAX-ACCESS read-create
        STATUS current
        DESCRIPTION
            "noOperator(1), which is the default value, means that no
             comparison is to be made with the Source TCP/UDP port
             number.
             lt(2) means less than.
             gt(3) means greater than.
             eq(4) means equal. 
             neq(5) means not equal." 
        ::= { qtechAceExtVCEntry 29 }

qtechAceExtSourceProtocolPortRangeVC OBJECT-TYPE
        SYNTAX Integer32
        MAX-ACCESS read-create
        STATUS current
        DESCRIPTION
            "The ending value of source protocol port in IP packet of Ace flow definition. It is 
             significative only to those protocol which support this field. The qtechAceExtSourcePortOp
             must set to range(6)."
        ::= { qtechAceExtVCEntry 30 }

qtechAceExtDestPortOpVC OBJECT-TYPE
        SYNTAX   INTEGER {
               noOperator(1), 
               lt(2), 
               gt(3),
               eq(4), 
               neq(5), 
               range(6) 
        }
        MAX-ACCESS read-create
        STATUS current
        DESCRIPTION
            "noOperator(1), which is the default value, means that no
             comparison is to be made with the Dest TCP/UDP port
             number.
             lt(2) means less than.
             gt(3) means greater than.
             eq(4) means equal. 
             neq(5) means not equal." 
        ::= { qtechAceExtVCEntry 31 }

qtechAceExtDestProtocolPortRangeVC OBJECT-TYPE
        SYNTAX Integer32
        MAX-ACCESS read-create
        STATUS current
        DESCRIPTION
            "The ending value of dest protocol port in IP packet of Ace flow definition. It is 
             significative only to those protocol which support this field. The qtechAceExtSourcePortOp
             must set to range(6)."
        ::= { qtechAceExtVCEntry 32 }

qtechAceExtIfAnyCosVC OBJECT-TYPE
        SYNTAX TruthValue
        MAX-ACCESS read-create
        STATUS current
        DESCRIPTION
            "Cos will not be checked if this value is true."
        DEFVAL{ true }
        ::= { qtechAceExtVCEntry 33 }
   
qtechAceExtCosVC OBJECT-TYPE
        SYNTAX Integer32
        MAX-ACCESS read-create
        STATUS current
        DESCRIPTION
            "Cos of Ace flow definition."
        ::= { qtechAceExtVCEntry 34 }

qtechAceExtIfAnyIpPrecVC OBJECT-TYPE
        SYNTAX TruthValue
        MAX-ACCESS read-create
        STATUS current
        DESCRIPTION
            "Ip precedence will not be checked if this value is true."
        DEFVAL{ true }
        ::= { qtechAceExtVCEntry 35 }
   
qtechAceExtIpPrecVC OBJECT-TYPE
        SYNTAX Integer32 
        MAX-ACCESS read-create
        STATUS current
        DESCRIPTION
            "Ip precedence of Ace flow definition."
        ::= { qtechAceExtVCEntry 36 }

qtechAceExtIfAnyDscpVC OBJECT-TYPE
        SYNTAX TruthValue
        MAX-ACCESS read-create
        STATUS current
        DESCRIPTION
            "Dscp will not be checked if this value is true."
        DEFVAL{ true }
        ::= { qtechAceExtVCEntry 37 }
   
qtechAceExtDscpVC OBJECT-TYPE
        SYNTAX Integer32
        MAX-ACCESS read-create
        STATUS current
        DESCRIPTION
            "Dscp of Ace flow definition."
        ::= { qtechAceExtVCEntry 38 }

qtechAceExtIfAnyTcpFlagVC OBJECT-TYPE
        SYNTAX TruthValue
        MAX-ACCESS read-create
        STATUS current
        DESCRIPTION
            "Tcp flag will not be checked if this value is true."
        DEFVAL{ true }
        ::= { qtechAceExtVCEntry 39 }
   
qtechAceExtTcpFlagVC OBJECT-TYPE
        SYNTAX Integer32
        MAX-ACCESS read-create
        STATUS current
        DESCRIPTION
            "Tcp flag of Ace flow definition."
        ::= { qtechAceExtVCEntry 40 }
        
qtechAceExtIfAnySourceMacAddrWildCardVC OBJECT-TYPE
        SYNTAX TruthValue
        MAX-ACCESS read-create
        STATUS current
        DESCRIPTION
            "Source mac address wildcard of class will not be checked if this value is true."
        DEFVAL{ true }
        ::= { qtechAceExtVCEntry 41 }
                
qtechAceExtSourceMacAddrWildCardVC OBJECT-TYPE
        SYNTAX MacAddress
        MAX-ACCESS read-create
        STATUS current
        DESCRIPTION
            "Sourece Mac address wildcard of Ace flow definition."
        ::= { qtechAceExtVCEntry 42 }                

qtechAceExtIfAnyDestMacAddrWildCardVC OBJECT-TYPE
        SYNTAX TruthValue
        MAX-ACCESS read-create
        STATUS current
        DESCRIPTION
            "Dest mac address wildcard of class will not be checked if this value is true."
        DEFVAL{ true }
        ::= { qtechAceExtVCEntry 43 }
                
qtechAceExtDestMacAddrWildCardVC OBJECT-TYPE
        SYNTAX MacAddress
        MAX-ACCESS read-create
        STATUS current
        DESCRIPTION
            "Dest Mac address wildcard of Ace flow definition."
        ::= { qtechAceExtVCEntry 44 }                

qtechAceExtIfAnySourceIp6VC OBJECT-TYPE
        SYNTAX TruthValue
        MAX-ACCESS read-create
        STATUS current
        DESCRIPTION
            "Source Ipv6 address of class will not be checked if this value is true."
        DEFVAL{ true }
        ::= { qtechAceExtVCEntry 45 }
            
qtechAceExtSourceIp6VC OBJECT-TYPE
        SYNTAX OCTET STRING (SIZE (16))
        MAX-ACCESS read-create
        STATUS current
        DESCRIPTION
            "Sourece ipv6 address of Ace flow definition."
        ::= { qtechAceExtVCEntry 46 }

qtechAceExtIfAnySourceIp6WildCardVC OBJECT-TYPE
        SYNTAX TruthValue
        MAX-ACCESS read-create
        STATUS current
        DESCRIPTION
            "Source Ipv6 address wild card of class will not be checked if this value is true."
        DEFVAL{ true }
        ::= { qtechAceExtVCEntry 47 }
                
qtechAceExtSourceIp6WildCardVC OBJECT-TYPE
        SYNTAX OCTET STRING (SIZE (16))
        MAX-ACCESS read-create
        STATUS current
        DESCRIPTION
            "Sourece ipv6 address wild card(in reverse ip address mask)of Ace flow definition."
        ::= { qtechAceExtVCEntry 48 }        

qtechAceExtIfAnyDestIp6VC OBJECT-TYPE
        SYNTAX TruthValue
        MAX-ACCESS read-create
        STATUS current
        DESCRIPTION
            "Dest Ipv6 address of class will not be checked if this value is true."
        DEFVAL{ true }
        ::= { qtechAceExtVCEntry 49 }
            
qtechAceExtDestIp6VC OBJECT-TYPE
        SYNTAX OCTET STRING (SIZE (16))
        MAX-ACCESS read-create
        STATUS current
        DESCRIPTION
            "Dest ipv6 address of Ace flow definition."
        ::= { qtechAceExtVCEntry 50 }

qtechAceExtIfAnyDestIp6WildCardVC OBJECT-TYPE
        SYNTAX TruthValue
        MAX-ACCESS read-create
        STATUS current
        DESCRIPTION
            "Dest Ipv6 address wild card of class will not be checked if this value is true."
        DEFVAL{ true }
        ::= { qtechAceExtVCEntry 51 }
                
qtechAceExtDestIp6WildCardVC OBJECT-TYPE
        SYNTAX OCTET STRING (SIZE (16))
        MAX-ACCESS read-create
        STATUS current
        DESCRIPTION
            "Dest ipv6 address wild card(in reverse ip address mask)of Ace flow definition."
        ::= { qtechAceExtVCEntry 52 }        



-- conformance information

qtechAclVCMIBConformance OBJECT IDENTIFIER ::= { qtechAclVCMIB 2 }
qtechAclVCMIBCompliances OBJECT IDENTIFIER ::= { qtechAclVCMIBConformance 1 }
qtechAclVCMIBGroups      OBJECT IDENTIFIER ::= { qtechAclVCMIBConformance 2 }


-- compliance statements

qtechAclVCMIBCompliance MODULE-COMPLIANCE
        STATUS  current
        DESCRIPTION
                "The compliance statement for entities which implement
                the Qtech Acl MIB for multiple context"
        MODULE  -- this module
                MANDATORY-GROUPS { qtechAclVCMIBGroup }
        ::= { qtechAclVCMIBCompliances 1 }
        
        
-- units of conformance

qtechAclVCMIBGroup OBJECT-GROUP
        OBJECTS {
                qtechAclContextNameVC,
                qtechAclNameVC,
                qtechAclModeVC,
                qtechAclEntryStatusVC,
                
                qtechAceExtContextNameVC,
                qtechAceExtAclNameVC,
                qtechAceExtIndexVC,
                qtechAceExtIfAnyVIDVC,
                qtechAceExtVIDVC,
                qtechAceExtIfAnySourceIpVC,
                qtechAceExtSourceIpVC,
                qtechAceExtIfAnySourceWildCardVC,
                qtechAceExtSourceWildCardVC,
                qtechAceExtIfAnySourceMacAddrVC,
                qtechAceExtSourceMacAddrVC,
                qtechAceExtIfAnyDestIpVC,
                qtechAceExtDestIpVC,
                qtechAceExtIfAnyDestWildCardVC,
                qtechAceExtDestIpWildCardVC,
                qtechAceExtIfAnyDestMacAddrVC,
                qtechAceExtDestMacAddrVC,
                qtechAceExtIfAnyEtherLikeTypeVC,
                qtechAceExtEtherLikeTypeVC,
                qtechAceExtIfAnyIpProtocolFieldVC,
                qtechAceExtIpProtocolFieldVC,
                qtechAceExtSourceProtocolPortVC,
                qtechAceExtDestProtocolPortVC,
                qtechAceExtProtocolTypeVC,
                qtechAceExtProtocolTypeVC,
                qtechAceExtFlowActionVC,
                qtechAceExtEntryStautsVC,
                qtechAceExtTimeRangeNameVC,
                qtechAceExtSourcePortOpVC,
                qtechAceExtSourceProtocolPortRangeVC,
                --qtechAceExtIfAnySourceProtocolPortVC,
                qtechAceExtDestPortOpVC,
                qtechAceExtDestProtocolPortRangeVC,
                --qtechAceExtIfAnyDestProtocolPortVC,
                qtechAceExtIfAnyCosVC,
                qtechAceExtCosVC,
                qtechAceExtIfAnyIpPrecVC,
                qtechAceExtIpPrecVC,
                qtechAceExtIfAnyDscpVC,
                qtechAceExtDscpVC,
                qtechAceExtIfAnyTcpFlagVC,
                qtechAceExtTcpFlagVC,
                qtechAceExtIfAnySourceMacAddrWildCardVC,
                qtechAceExtSourceMacAddrWildCardVC,
                qtechAceExtIfAnyDestMacAddrWildCardVC,
                qtechAceExtDestMacAddrWildCardVC,
                qtechAceExtIfAnySourceIp6VC,
                qtechAceExtSourceIp6VC,
                qtechAceExtIfAnySourceIp6WildCardVC,
                qtechAceExtSourceIp6WildCardVC,
                qtechAceExtIfAnyDestIp6VC,
                qtechAceExtDestIp6VC,
                qtechAceExtIfAnyDestIp6WildCardVC,
                qtechAceExtDestIp6WildCardVC,
                
                qtechAclIfContextNameVC,
                qtechAclIfIndexVC,
                qtechAclIfMaxEntryNumVC,
                qtechAclIfCurruntEntryNumVC,
                qtechIfInAclNameVC,
                qtechIfOutAclNameVC
        }
        STATUS  current
        DESCRIPTION
                "A collection of objects providing acl (echo) ability to a
                Qtech agent."
        ::= { qtechAclVCMIBGroups 1 }        


--
        
END

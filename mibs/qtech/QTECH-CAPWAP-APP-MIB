-- *****************************************************************
-- QTECH-CAPWAP-APP-MIB.mib:  Qtech CAPWAP APP MIB file
--
-- Jul 2010, Panshiyong
--
-- Copyright(c) 2010 by Qtech Networks Co.,Ltd.
-- All rights reserved.
-- 
-- *****************************************************************
--

QTECH-CAPWAP-APP-MIB DEFINITIONS ::= BEGIN

IMPORTS
        MODULE-IDENTITY,
        OBJECT-TYPE,
        TimeTicks,
        Unsigned32,
        Integer32,
        IpAddress
                FROM SNMPv2-SMI
        DisplayString,
        TruthValue,
        TAddress,
        RowStatus
                FROM SNMPv2-TC
        MODULE-COMPLIANCE,
        OBJECT-GROUP
                FROM SNMPv2-CONF
        InetAddressType,
        InetAddress
                FROM INET-ADDRESS-MIB
        sysObjectID
                FROM RFC1213-MIB
        qtechSystemSerialno
                FROM QTECH-SYSTEM-MIB
        qtechDeviceMacAddress
                FROM QTECH-ENTITY-MIB
        qtechMgmt
                FROM QTECH-SMI;

qtechCapwapAppMIB MODULE-IDENTITY
        LAST-UPDATED "201006040000Z"
        ORGANIZATION "Qtech Networks Co.,Ltd."
        CONTACT-INFO
                " 
                Tel: 4008-111-000 

                E-mail: service@qtech.com.cn"
        DESCRIPTION
                "This module defines qtech Capwap App mibs."
        REVISION      "201006040000Z"
        DESCRIPTION
                "Initial version of this MIB module."
        ::= { qtechMgmt 87 }

qtechCapwapAppMIBObjects   OBJECT IDENTIFIER ::= { qtechCapwapAppMIB 1 }


--**********************************************************************
-- about heartbeat info 
--**********************************************************************
qtechAppHeartbeatMIBObjects 
    OBJECT IDENTIFIER ::= { qtechCapwapAppMIBObjects 1 }

qtechAppHeartbeatOnOff OBJECT-TYPE
    SYNTAX INTEGER {
             off(0),
             on(1)
           }
    MAX-ACCESS read-write
    STATUS current
    DESCRIPTION
        "Heartbeat detect switch."
    ::= { qtechAppHeartbeatMIBObjects 1 } 
     
qtechAppHeartbeatPeriod OBJECT-TYPE
    SYNTAX INTEGER (60..3600)
    MAX-ACCESS read-write
    STATUS current
    DESCRIPTION
        "Heartbeat detect periode."
    ::= { qtechAppHeartbeatMIBObjects 2 } 

qtechAppHeartbeatIpAddr OBJECT-TYPE
    SYNTAX IpAddress
    MAX-ACCESS read-only
    STATUS current
    DESCRIPTION
        "IP address of the AP"
    ::= { qtechAppHeartbeatMIBObjects 3 }
    
qtechAppHeartbeatTimeStamp OBJECT-TYPE
    SYNTAX TimeTicks
    MAX-ACCESS read-only
    STATUS current
    DESCRIPTION
        "Time stamp of the AP"
    ::= { qtechAppHeartbeatMIBObjects 4 }
    
    
-- heartbeat traps    
qtechAppHeartbeatMIBTraps OBJECT IDENTIFIER ::= { qtechAppHeartbeatMIBObjects 0 }

qtechAppHeartbeatTrap NOTIFICATION-TYPE
    OBJECTS {
        qtechAppHeartbeatIpAddr,
        qtechAppHeartbeatTimeStamp
    }
    STATUS  current
    DESCRIPTION
            " This trap will be sent when a heartbeat periode pass."
    ::= { qtechAppHeartbeatMIBTraps 1 } 


--**********************************************************************
-- about admin info 
--**********************************************************************
qtechAppAdminInfoMIBObjects 
    OBJECT IDENTIFIER ::= { qtechCapwapAppMIBObjects 2 }

qtechAppAdminInfoTable OBJECT-TYPE
    SYNTAX SEQUENCE OF QtechAppAdminInfoEntry
    MAX-ACCESS not-accessible
    STATUS current
    DESCRIPTION
        "The table about admin info."
    ::= { qtechAppAdminInfoMIBObjects 1 }

qtechAppAdminInfoEntry OBJECT-TYPE
    SYNTAX QtechAppAdminInfoEntry
    MAX-ACCESS not-accessible
    STATUS current
    DESCRIPTION
        "The entry of qtechAdminInfoTable."
    INDEX { qtechAppAdminName }
    ::= { qtechAppAdminInfoTable 1 }

QtechAppAdminInfoEntry ::=
    SEQUENCE {
       qtechAppAdminName      DisplayString,
       qtechAppAdminPwd       DisplayString,
       qtechAppAdminPriLevel  INTEGER,
       qtechAppAdminStatus    RowStatus
    }

qtechAppAdminName OBJECT-TYPE 
    SYNTAX DisplayString(SIZE(1..64))
    MAX-ACCESS read-only
    STATUS current
    DESCRIPTION
           "The name of the administrator."
    ::= { qtechAppAdminInfoEntry 1 }
				
qtechAppAdminPwd OBJECT-TYPE
    SYNTAX DisplayString(SIZE(1..255))
    MAX-ACCESS read-create
    STATUS current
    DESCRIPTION
           "The password of the administrator."
    ::= { qtechAppAdminInfoEntry 2 }

qtechAppAdminPriLevel OBJECT-TYPE
    SYNTAX INTEGER
    MAX-ACCESS read-create
    STATUS current
    DESCRIPTION
           "The privilege level of the administrator."
    ::= { qtechAppAdminInfoEntry 3 }

qtechAppAdminStatus OBJECT-TYPE
    SYNTAX RowStatus
    MAX-ACCESS read-create
    STATUS current
    DESCRIPTION
           "The rowstatus of the adminInfoEntry."
    ::= { qtechAppAdminInfoEntry 4 }


qtechAppAdminInfoName OBJECT-TYPE
    SYNTAX DisplayString(SIZE(1..64))
    MAX-ACCESS not-accessible
    STATUS current
    DESCRIPTION
        "The administrator name info."
    ::= { qtechAppAdminInfoMIBObjects 2 }

qtechAppAdminInfoIpAddr OBJECT-TYPE
    SYNTAX IpAddress
    MAX-ACCESS not-accessible
    STATUS current
    DESCRIPTION
        "The administrator ip address info."
    ::= { qtechAppAdminInfoMIBObjects 3 }

qtechAppAdminInfoConfigContext OBJECT-TYPE
    SYNTAX OCTET STRING(SIZE(1..512))
    MAX-ACCESS not-accessible
    STATUS current
    DESCRIPTION
        "The context of configuration."
    ::= { qtechAppAdminInfoMIBObjects 4 }

qtechAppAdminInfoLoginType OBJECT-TYPE
    SYNTAX DisplayString(SIZE(1..64))
    MAX-ACCESS not-accessible
    STATUS current
    DESCRIPTION
        "The administrator login type."
    ::= { qtechAppAdminInfoMIBObjects 5 }

qtechAppAdminTerminalInfo OBJECT-TYPE
    SYNTAX DisplayString(SIZE(1..64))
    MAX-ACCESS not-accessible
    STATUS current
    DESCRIPTION
        "The administrator terminal information:
         console  -  login from console
         aux id   -  login from auxiliary
         vty id   -  login from telnet or ssh
         web      -  login from http/web "
    ::= { qtechAppAdminInfoMIBObjects 6 }

qtechAppAdminLoginFailReason OBJECT-TYPE
    SYNTAX INTEGER 
    MAX-ACCESS not-accessible
    STATUS current
    DESCRIPTION
        "The administrator login fail reason:
         1  -  username or password is error "
    ::= { qtechAppAdminInfoMIBObjects 7 }

qtechAppAdminTargetLevel OBJECT-TYPE
    SYNTAX INTEGER (0..15)
    MAX-ACCESS not-accessible
    STATUS current
    DESCRIPTION
        "The administrator target level"
    ::= { qtechAppAdminInfoMIBObjects 8 }

-- admin traps
qtechAppAdminMIBTraps
    OBJECT IDENTIFIER ::= { qtechAppAdminInfoMIBObjects 0 }

qtechAppAdminLoginTrap NOTIFICATION-TYPE
    OBJECTS {
        qtechAppAdminInfoName,
        qtechAppAdminInfoIpAddr,
        qtechAppAdminInfoLoginType
    }
    STATUS  current
    DESCRIPTION
            " This trap will be sent when the administrator rlogin the device."
    ::= { qtechAppAdminMIBTraps 1 } 

qtechAppAdminModifyConfigTrap NOTIFICATION-TYPE
    OBJECTS {
        qtechAppAdminInfoName,
        qtechAppAdminInfoIpAddr,
        qtechAppAdminInfoConfigContext
    }
    STATUS  current
    DESCRIPTION
            " This trap will be sent when the administrator modify the configuration."
    ::= { qtechAppAdminMIBTraps 2 } 

qtechAppAdminLoginFailTrap NOTIFICATION-TYPE
    OBJECTS {
        qtechAppAdminInfoName,
        qtechAppAdminInfoIpAddr,
        qtechAppAdminTerminalInfo,
        qtechAppAdminLoginFailReason
    }
    STATUS  current
    DESCRIPTION
            " This trap will be sent when the administrator login the device failed."
    ::= { qtechAppAdminMIBTraps 3 } 

qtechAppAdminEnableFailTrap NOTIFICATION-TYPE
    OBJECTS {
        qtechAppAdminInfoName,
        qtechAppAdminInfoIpAddr,
        qtechAppAdminTerminalInfo,
        qtechAppAdminTargetLevel
    }
    STATUS  current
    DESCRIPTION
            " This trap will be sent when the administrator enter target cli level failed."
    ::= { qtechAppAdminMIBTraps 4 } 

--**********************************************************************
-- about polltime info 
--**********************************************************************
qtechAppPollTimeMIBObjects 
    OBJECT IDENTIFIER ::= { qtechCapwapAppMIBObjects 3 }

qtechAppPollTimeOfLast OBJECT-TYPE
    SYNTAX TimeTicks
    MAX-ACCESS read-only
    STATUS current
    DESCRIPTION
           "The last time of administrator 
            poll the devices."
		::= { qtechAppPollTimeMIBObjects 1 }


--**********************************************************************
-- about config info 
--**********************************************************************
qtechAppConfigMIBObjects 
    OBJECT IDENTIFIER ::= { qtechCapwapAppMIBObjects 4 }
    
qtechAppRcvToDefConfig OBJECT-TYPE
    SYNTAX INTEGER{
         normal(0),
         reset(1)
    }
    MAX-ACCESS read-write
    STATUS current
    DESCRIPTION
        "0 - normal, 
         1 - recove the device to default config. then reload the device"
    ::= { qtechAppConfigMIBObjects 1 }

qtechAppConfigFileName OBJECT-TYPE
    SYNTAX DisplayString(SIZE (1..32))
    MAX-ACCESS read-only
    STATUS current
    DESCRIPTION
        "Name of configuration file."
    ::= { qtechAppConfigMIBObjects 2 }

qtechAppConfigParseErrReason OBJECT-TYPE
    SYNTAX DisplayString(SIZE (1..255))
    MAX-ACCESS read-only
    STATUS current
    DESCRIPTION
        "The reason of configuration file parse error."
    ::= { qtechAppConfigMIBObjects 3 }

-- modify config trap
qtechAppConfigMIBTraps
    OBJECT IDENTIFIER ::= { qtechAppConfigMIBObjects 0 }
    
qtechAppConfigModifyFileTrap NOTIFICATION-TYPE
    STATUS  current
    DESCRIPTION
            "The notification of discovering someone 
             modify the configuration file." 
    ::= { qtechAppConfigMIBTraps 1 } 
    
qtechAppConfigParseErrTrap NOTIFICATION-TYPE
    OBJECTS {
        qtechAppConfigFileName,
        qtechAppConfigParseErrReason
    }
    STATUS  current
    DESCRIPTION
        "The notification of discovering parser 
         configuration file error." 
    ::= { qtechAppConfigMIBTraps 2 } 


--**********************************************************************
-- about syslog info 
--**********************************************************************
qtechAppSyslogMIBObjects 
    OBJECT IDENTIFIER ::= { qtechCapwapAppMIBObjects 5 }

qtechAppSyslogSvcEnable OBJECT-TYPE
    SYNTAX TruthValue
    MAX-ACCESS read-write
    STATUS current
    DESCRIPTION
        "Whether to open syslog service or not:
         2 - no
         1 - yes.
        "
    ::= { qtechAppSyslogMIBObjects 1 }

qtechAppSyslogReportEventLevel OBJECT-TYPE
    SYNTAX INTEGER
    MAX-ACCESS read-write
    STATUS current
    DESCRIPTION
        "Report event level"
    ::= { qtechAppSyslogMIBObjects 2 }


qtechAppSyslogSvrCfgTable OBJECT-TYPE
    SYNTAX SEQUENCE OF QtechAppSyslogSvrCfgEntry
    MAX-ACCESS not-accessible
    STATUS current
    DESCRIPTION
        "The table discribe the system log configuration of the AP."
    ::= { qtechAppSyslogMIBObjects 3 }

qtechAppSyslogSvrCfgEntry OBJECT-TYPE
    SYNTAX QtechAppSyslogSvrCfgEntry
    MAX-ACCESS not-accessible
    STATUS current
    DESCRIPTION
        "The entry of apSyslogSvrCfgTable."
    INDEX { 
          qtechAppSyslogSvrNetType,
          qtechAppSyslogSvrNetAddr
      }
    ::= { qtechAppSyslogSvrCfgTable 1 }

QtechAppSyslogSvrCfgEntry ::=
    SEQUENCE {
        qtechAppSyslogSvrNetType    InetAddressType,
        qtechAppSyslogSvrNetAddr    InetAddress,
        qtechAppSyslogSvrNetPort    Unsigned32,
        qtechAppSyslogVrfName       DisplayString,
        qtechAppSyslogStatus        RowStatus
	  } 

qtechAppSyslogSvrNetType  OBJECT-TYPE
    SYNTAX InetAddressType
    MAX-ACCESS read-only           
    STATUS current               
    DESCRIPTION               
        "Address type of syslog server."               
    ::= { qtechAppSyslogSvrCfgEntry 1 }   
    
qtechAppSyslogSvrNetAddr OBJECT-TYPE
    SYNTAX InetAddress               
    MAX-ACCESS read-only             
    STATUS current               
    DESCRIPTION               
        "Address of syslog server."               
    ::= { qtechAppSyslogSvrCfgEntry 2 } 

qtechAppSyslogSvrNetPort OBJECT-TYPE
    SYNTAX Unsigned32               
    MAX-ACCESS read-create             
    STATUS current               
    DESCRIPTION               
        "NetPort of syslog server."               
    ::= { qtechAppSyslogSvrCfgEntry 3 }

qtechAppSyslogVrfName OBJECT-TYPE
    SYNTAX DisplayString               
    MAX-ACCESS read-create             
    STATUS current               
    DESCRIPTION               
        "Vrf name of syslog server."               
    ::= { qtechAppSyslogSvrCfgEntry 4 } 

qtechAppSyslogStatus OBJECT-TYPE               
    SYNTAX RowStatus               
    MAX-ACCESS read-create              
    STATUS current               
    DESCRIPTION               
        "RowStatus of syslog server."               
    ::= { qtechAppSyslogSvrCfgEntry 5 } 

--
-- about syslog Taddress info 
--
qtechSyslogServerAddrInfoTable OBJECT-TYPE
    SYNTAX SEQUENCE OF QtechSyslogServerAddrInfoEntry
    MAX-ACCESS not-accessible
    STATUS current
    DESCRIPTION
        "The table discribe the syslog server informations."
    ::= { qtechAppSyslogMIBObjects 4 }

qtechSyslogServerAddrInfoEntry OBJECT-TYPE
    SYNTAX QtechSyslogServerAddrInfoEntry
    MAX-ACCESS not-accessible
    STATUS current
    DESCRIPTION
        "The entry of qtechSyslogServerAddrInfoTable."
    INDEX { 
        qtechSyslogServerIndex
    }
    ::= { qtechSyslogServerAddrInfoTable 1 }

QtechSyslogServerAddrInfoEntry ::=
    SEQUENCE {
        qtechSyslogServerIndex      Integer32,
        qtechSyslogServerAddr       TAddress,
        qtechSyslogServerVrfName    DisplayString,
        qtechSyslogServerStatus     RowStatus
	  } 

qtechSyslogServerIndex OBJECT-TYPE
    SYNTAX Integer32
    MAX-ACCESS read-only          
    STATUS current        
    DESCRIPTION               
        "Index of syslog server information table."               
    ::= { qtechSyslogServerAddrInfoEntry 1 }

qtechSyslogServerAddr OBJECT-TYPE
    SYNTAX TAddress
    MAX-ACCESS read-create          
    STATUS current        
    DESCRIPTION               
        "Taddess of syslog server."               
    ::= { qtechSyslogServerAddrInfoEntry 2 }

qtechSyslogServerVrfName OBJECT-TYPE
    SYNTAX DisplayString               
    MAX-ACCESS read-create             
    STATUS current               
    DESCRIPTION               
        "Vrf name of syslog server."               
    ::= { qtechSyslogServerAddrInfoEntry 3 } 

qtechSyslogServerStatus OBJECT-TYPE               
    SYNTAX RowStatus               
    MAX-ACCESS read-create              
    STATUS current
    DESCRIPTION               
        "RowStatus of syslog server."               
    ::= { qtechSyslogServerAddrInfoEntry 4 } 


--**********************************************************************
-- about Trap Action info 
--**********************************************************************
qtechAppTrapActionMIBObjects 
    OBJECT IDENTIFIER ::= { qtechCapwapAppMIBObjects 6 }

qtechAppTrapActionEnable OBJECT-TYPE
    SYNTAX INTEGER {
        disableSendTrap(0),  -- disable send trap
        enableSendTrap(1)    -- enable  send trap
    }
    MAX-ACCESS read-write
    STATUS current
    DESCRIPTION
        "This value decide enable or not to send trap 
         while some notification happen."
    ::= { qtechAppTrapActionMIBObjects 1 }

qtechAppTrapActionTable OBJECT-TYPE
    SYNTAX SEQUENCE OF QtechAppTrapActionEntry
    MAX-ACCESS not-accessible
    STATUS current
    DESCRIPTION
        "This table of the trap's action."
    ::= { qtechAppTrapActionMIBObjects 2 }

qtechAppTrapActionEntry OBJECT-TYPE
    SYNTAX QtechAppTrapActionEntry
    MAX-ACCESS not-accessible
    STATUS current
    DESCRIPTION
        "List of of the trap's action."
    INDEX { qtechAppTrapType }
    ::= { qtechAppTrapActionTable 1 }
    
QtechAppTrapActionEntry ::=
    SEQUENCE {
        qtechAppTrapType   INTEGER,
        qtechAppTrapAction INTEGER,
        qtechAppTrapDescr  DisplayString
    }

qtechAppTrapType OBJECT-TYPE
    SYNTAX INTEGER { 
        gencoldstart(1),
        genwarmstart(2),
        genlinkdown(3),
        genlinkup(4),
        genauthenfail(5),
        genegpnbloss(6),
        spenewroot(7),
        spetopchange(8),
        spehardchange(9),
        speportsecuviolation(10),
        spestormviolation(11),
        spemacnotification(12),
        spevrrpnewmaster(13),
        spevrrpauthfailure(14),
        spepowerstatetrans(15),
        spefanstatetrans(16),
        speospf(17),
        speospfvifstatechange(18),
        speospfnbrstatechange(19),
        speospfvifnbrstatechange(20),
        speospfifconfigerror(21),
        speospfvifconfigerror(22),
        speospfifauthfailure(23),
        speospfvifauthfailure(24),
        speospfifrxbadpacket(25),
        speospfvifrxbadpacket(26),
        speospftxretransmit(27),
        speospfviftxretransmit(28),
        speospforiginatelsa(29),
        speospfmaxagelsa(30),
        speospflsdboverflow(31),
        speospflsdbapproachingoverflow(32),
        speospfifstatechange(33),
        spebgpestablished(34),
        spebgpbackwardtransition(35),
        speisisdatabaseoverload(36),
        speisismanualaddressdrop(37),
        speisiscorruptedlspdetected(38),
        speisisattempttoexceedmaxseq(39),
        speisisidlenmismatch(40),
        speisismaxareaaddrmismatch(41),
        speisisownlsppurge(42),
        speisisseqnumberskip(43),
        speisisauthtypefailure(44),
        speisisauthfailure(45),
        speisisversionskew(46),
        speisisareamismatch(47),
        speisisrejectedadj(48),
        speisislsptoolargetopropagate(49),
        speisisoriglspbufsizemismatch(50),
        speisisprotocolsupportedmismatch(51),
        speisisadjchange(52),
        spepim(53),
        speigmp(54),
        spedvmrp(55),
        speentitychange(56),
        specluster(57),
        spedetectipviolation(58),
        spelinestate(59),
        spesysguard(60),
        spernfpmsgtrap(61),
        sperrmclientsfailedtrap(62),
        sperrmloadfailedtrap(63),
        sperrmnoisefailedtrap(64),
        sperrminterferencefailedtrap(65),
        sperrmperformancefailedtrap(66),
        sperrmclientspasstrap(67),
        sperrmloadpasstrap(68),
        sperrmnoisepasstrap(69),
        sperrminterferencepasstrap(70),
        sperrmperformancepasstrap(71),
        sperrmchannelchangetrap(72),
        sperrmtxpowerchangetrap(73),
        sperrmleaderachangetrap(74),
        sperrmleaderbchangetrap(75),
        sperrmdfsfreecountatrap(76),
        sperrmdfsfreecountbtrap(77),
        sperrmneighborapintertrap(78),
        sperrmstationintertrap(79),
        sperrmotherdiveceintertrap(80),
        rmonalarmfallingtrap(81),
        rmonalarmrisingtrap(82),
        smpframerelaytrap(83),
        priventitytrans(84),
        privtemperaturetrans(85),
        speipv6ifstatechange(86),
        psmachashconflicttrap(87),
        privwebauthuserleave(88),
        radiusauthserverdowntrap(89),
        radiusacctserverdowntrap(90),
        configurationerrortrap(91),
        cpuusagetoohightrap(92),
        cpuusagetoohighrecovtrap(93),
        memusagetoohightrap(94),
        memusagetoohighrecovtrap(95),
        systmcoldstarttrap(96),
        ipaddrchangetrap(97),
        apmtworkmodechgtrap(98),
        apswupdatefailtrap(99),
        ssidkeyconflicttrap(100),
        fatapheartbeattrap(101),
        acconfigurationerrortrap(102),
        accpuusagetoohightrap(103),
        accpuusagetoohighrecovtrap(104),
        acmemusagetoohightrap(105),
        acmemusagetoohighrecovtrap(106),
        acofflinetrap(107),
        aconlinetrap(108),
        acapmtworkmodechgtrap(109),
        acapswupdatefailtrap(110),
        acssidkeyconflicttrap(111),
        acfatapheartbeattrap(112),
        staauthfailtrap(113),
        staassofailtrap(114),
        acstaauthfailtrap(115),
        acstaassofailtrap(116),
        invalidcertinvadetrap(117),
        repaccacktrap(118),
        tamperattacktrap(119),
        lowersafeattacktrap(120),
        addrredirectiontrap(121),
        acinvalidcertinvadetrap(122),
        acrepaccacktrap(123),
        actamperattacktrap(124),
        aclowersafeattacktrap(125),
        acaddrredirectiontrap(126),
        widsieee80211connect(127),
        widsieee80211disconnect(128),
        widsieee80211reauthentication(129),
        widsieee80211authenticationfailure(130),
        widsieee80211connectfailure(131),
        apcointerfdetectedtrap(132),
        apcointerfcleartrap(133),
        apnerborinterfdetectedtrap(134),
        apneiborinterfcleartrap(135),
        stainterfdetectedtrap(136),
        stainterfcleartrap(137),
        otherdeviceinterfdetectedtrap(138),
        otherdevinterfcleartrap(139),
        radiodowntrap(140),
        radiodownrecovtrap(141),
        apstafulltrap(142),
        apstafullrecovertrap(143),
        apmtrdochanlchgtrap(144),
        acapcointerfdetectedtrap(145),
        acapcointerfcleartrap(146),
        acapnerborinterfdetectedtrap(147),
        acapneiborinterfcleartrap(148),
        acstainterfdetectedtrap(149),
        acstainterfcleartrap(150),
        acotherdeviceinterfdetectedtrap(151),
        acotherdevinterfcleartrap(152),
        acradiodowntrap(153),
        acradiodownrecovtrap(154),
        acapstafulltrap(155),
        acapstafullrecovertrap(156),
        acapmtrdochanlchgtrap(157),
        acspeciousdevicedetecttrap(158),
        acrxpackage(159),
        accpuusage(160),
        capwapbasechanup(161),
        capwapbasechandown(162),
        capwapbasedecrypterrorreport(163),
        capwapbasejoinfail(164),
        capwapbaseimageupgradefail(165),
        capwapbaseconifgmsgerror(166),
        capwapbaseradiooperstatu(167),
        capwapbaseauthenfail(168),
        apmgmtaptimestamp(169),
        apmgmtstaoper(170),
        apmgmtmbchange(171),
        apmgmtapswupdtfail(172),
        widswarninginfo(173),
        privcmccportalunavailable(174),
        privipaddrchange(175),
        dhcppoolexhaust(176),
        dhcppoolnoexhaust(177),
        speheartbeatperiodtrap(178),
        tftpupgradefailed(179),
        syscpuhigh(180),
        syscpuhighrecov(181),
        systemperaturehigh(182),
        systemperaturehighrecov(183),
        sysmemoryhigh(184),
        sysmemoryhighrecov(185),
        speconfigmodifytrap(186),
        speconfigparseerrtrap(187),
        apmgmtstaactoverthrehold(188),
        apmgmtstadisactoverthredhold(189),
        apmgmtstaroamtotaloverthredhlod(190),
        apmgmtstaroamoerminoverthredhold(191),
        apmgmtapwritebuffero(192),
        apmgmtacheartbeat(193),
        apmgmtacpowerstatus(194),
        radiusauthserverrecovertrap(195),
        radiusacctserverrecovertrap(196),
        privcmccportalavailable(197),
        sysapcpuhigh(198),
        sysapcpuhighrecov(199),
        sysapmemoryhigh(200),
        sysapmemoryhighrecov(201),
        syssystemreset(202)
    } 
    MAX-ACCESS read-only
    STATUS current
    DESCRIPTION
        "Trap type identifier, every kind of trap which the system support
         will has one entry in this table."
    ::= { qtechAppTrapActionEntry 1 }

qtechAppTrapAction OBJECT-TYPE
    SYNTAX INTEGER {
        off(0),     -- do nothing
        on(1)       -- send trap
    }
    MAX-ACCESS read-write
    STATUS current
    DESCRIPTION
        "This value decide how to deal with when this type trap has happened."
    ::= { qtechAppTrapActionEntry 2 }

qtechAppTrapDescr OBJECT-TYPE
    SYNTAX DisplayString
    MAX-ACCESS read-write
    STATUS current
    DESCRIPTION
        "The description of the trap."
    ::= { qtechAppTrapActionEntry 3 }    

--**********************************************************************
-- about ZCM Zero-Config Management info 
--**********************************************************************
qtechZCMMIBObjects 
    OBJECT IDENTIFIER ::= { qtechCapwapAppMIBObjects 7 }

-- zcm mib
qtechAssignedIPAddress OBJECT-TYPE
    SYNTAX IpAddress
    MAX-ACCESS not-accessible
    STATUS current
    DESCRIPTION
        "The device ip address information."
    ::= { qtechZCMMIBObjects 1 }

qtechNeedConfiguration OBJECT-TYPE
    SYNTAX INTEGER {
             no(0),  -- system does not need configuration
             yes(1)  -- system need configuration
           }
    MAX-ACCESS not-accessible
    STATUS current
    DESCRIPTION
        "The device does need configuration."
    ::= { qtechZCMMIBObjects 2 }

-- zcm trap
qtechZCMMIBTraps
    OBJECT IDENTIFIER ::= { qtechZCMMIBObjects 0 }

qtechZCMNotifyTrap NOTIFICATION-TYPE
    OBJECTS {
        qtechSystemSerialno,
        qtechDeviceMacAddress,
        qtechAssignedIPAddress,
        qtechNeedConfiguration,
        sysObjectID
    }
    STATUS  current
    DESCRIPTION
            "The notification sent when the device startup." 
    ::= { qtechZCMMIBTraps 1 } 

--**********************************************************************
-- about conformance info 
--**********************************************************************
qtechCapwapAppMIBConformance OBJECT IDENTIFIER ::= { qtechCapwapAppMIB 2 }
qtechCapwapAppMIBCompliances OBJECT IDENTIFIER ::= { qtechCapwapAppMIBConformance 1 }
qtechCapwapAppMIBGroups      OBJECT IDENTIFIER ::= { qtechCapwapAppMIBConformance 2 }

-- compliance statements
qtechCapwapAppMIBCompliance MODULE-COMPLIANCE
    STATUS  current
    DESCRIPTION
        "The compliance statement for entities which implement
         the Qtech Capwap App MIB"
    MODULE  
    MANDATORY-GROUPS { 
        qtechCapwapAppMIBGroup
    }
    ::= { qtechCapwapAppMIBCompliances 1 }
                
-- units of conformance

qtechCapwapAppMIBGroup OBJECT-GROUP
        OBJECTS {
           qtechAppHeartbeatOnOff,
           qtechAppHeartbeatPeriod,
           qtechAppHeartbeatIpAddr,
           qtechAppHeartbeatTimeStamp,	
           qtechAppAdminName,
           qtechAppAdminPwd,
           qtechAppAdminPriLevel,
           qtechAppAdminStatus,
           qtechAppPollTimeOfLast,
           qtechAppRcvToDefConfig,
           qtechAppConfigFileName,
           qtechAppConfigParseErrReason,
           qtechAppSyslogSvcEnable,
           qtechAppSyslogReportEventLevel,
           qtechAppSyslogSvrNetType,
           qtechAppSyslogSvrNetAddr,
           qtechAppSyslogSvrNetPort,
           qtechAppSyslogVrfName,
           qtechAppSyslogStatus,
           qtechSyslogServerAddr,
           qtechSyslogServerVrfName,
           qtechSyslogServerStatus
        }
        STATUS  current
        DESCRIPTION
                "A collection of objects providing Capwap App configure."
        ::= { qtechCapwapAppMIBGroups 1 }
        
END

-- *******************************************************************
-- QTECH-CAPWAP-DHCP-MIB.mib : Qtech WLAN DHCP MIB 
-- 
-- Nov 2009, chenfg1
--
-- Copyright (c) 2009 by Qtech Networks Co.,Ltd.
-- All rights reserved.
-- *******************************************************************
--
QTECH-CAPWAP-DHCP-MIB DEFINITIONS ::= BEGIN

IMPORTS 
        MODULE-IDENTITY, 
        OBJECT-TYPE,
		Integer32,
	NOTIFICATION-TYPE,	
        Unsigned32,
        IpAddress
                FROM SNMPv2-SMI
        OBJECT-GROUP,
        MODULE-COMPLIANCE
                FROM SNMPv2-CONF
        TruthValue,
        RowStatus,
        DisplayString,
        MacAddress
                FROM SNMPv2-TC 
        qtechMgmt
                FROM QTECH-SMI
        qtechIfIndex 
                FROM QTECH-INTERFACE-MIB;

--********************************************************************
--*  MODULE IDENTITY
--********************************************************************

qtechCapwapDhcpMIB    MODULE-IDENTITY
       LAST-UPDATED    "200911100000Z"
       ORGANIZATION    "Qtech Networks Co.,Ltd."
       CONTACT-INFO  
                " 
                Tel: 4008-111-000 

                E-mail: service@qtech.com.cn"

        DESCRIPTION             
                "This MIB is intended to be implemented on all those
                devices operating as Central controllers, that
                terminate the Light Weight Access Point Protocol
                tunnel from Qtech Light-weight CAPWAP Access Points.

                This MIB is used to show and configure Dynamic Host
		        Configuration Protocol (DHCP) related statistics.


                The relationship between CC and the CAPWAP APs
                can be depicted as follows:

        +......+     +......+     +......+           +......+
        +      +     +      +     +      +           +      +
        +  CC  +     +  CC  +     +  CC  +           +  CC  +
        +      +     +      +     +      +           +      +
        +......+     +......+     +......+           +......+
          ..            .             .                 .
          ..            .             .                 .
         .  .            .             .                 .
        .    .            .             .                 .
       .      .            .             .                 .
      .        .            .             .                 .
   +......+ +......+     +......+      +......+          +......+
   +      + +      +     +      +      +      +          +      +
   +  AP  + +  AP  +     +  AP  +      +  AP  +          +  AP  +
   +      + +      +     +      +      +      +          +      +
   +......+ +......+     +......+      +......+          +......+
              .              .             .                 .
            .  .              .             .                 .
           .    .              .             .                 .
          .      .              .             .                 .
         .        .              .             .                 .
      +......+ +......+     +......+      +......+          +......+
      +      + +      +     +      +      +      +          +      +
      +  MN  + +  MN  +     +  MN  +      +  MN  +          +  MN  +
      +      + +      +     +      +      +      +          +      +
      +......+ +......+     +......+      +......+          +......+


                The CAPWAP tunnel exists between the controller and
                the APs.  The MNs communicate with the APs through
                the protocol defined by the 802.11 standard.

                CAPWAP APs, upon bootup, discover and join one of the
                controllers and the controller pushes the configuration,
                that includes the WLAN parameters, to the CAPWAP APs.
                The APs then encapsulate all the 802.11 frames from
                wireless clients inside CAPWAP frames and forward
                the CAPWAP frames to the controller.

                                   GLOSSARY

                Access Point ( AP )

                An entity that contains an 802.11 medium access
                control ( MAC ) and physical layer ( PHY ) interface
                and provides access to the distribution services via
                the wireless medium for associated clients.  

                CAPWAP APs encapsulate all the 802.11 frames in
                CAPWAP frames and sends them to the controller to which
                it is logically connected.

                Central Controller ( CC )

                The central entity that terminates the CAPWAP protocol
                tunnel from the CAPWAP APs.  Throughout this MIB,
                this entity also referred to as 'controller'. 

                Light Weight Access Point Protocol ( CAPWAP ) 

                This is a generic protocol that defines the 
                communication between the Access Points and the
                Central Controller.

                Mobile Node ( MN )

                A roaming 802.11 wireless device in a wireless
                network associated with an access point. Mobile Node,
                Mobile Station(Ms) and client are used interchangeably. 
                
                REFERENCE
 
                [1] Wireless LAN Medium Access Control ( MAC ) and
                Physical Layer ( PHY ) Specifications.
  
                [2] Draft-obara-capwap-capwap-00.txt, IETF Light 
                Weight Access Point Protocol "
        
        REVISION      "200911100000Z"
        DESCRIPTION
                "Initial version of this MIB module. "
        ::= { qtechMgmt 58 }

qtechCapwapDhcpMIBTrap    OBJECT IDENTIFIER 
    ::= { qtechCapwapDhcpMIB 0 }

qtechCapwapDhcpMIBObjects OBJECT IDENTIFIER 
    ::= { qtechCapwapDhcpMIB 1 }

qtechCapwapDhcpGlobalConfig OBJECT IDENTIFIER
	::= { qtechCapwapDhcpMIBObjects 1 }

qtechCapwapDhcpShowStats OBJECT IDENTIFIER
	::= { qtechCapwapDhcpMIBObjects 2 }
	
qtechCapwapDhcpServerConfig OBJECT IDENTIFIER
	::= { qtechCapwapDhcpMIBObjects 3 }
	
qtechCapwapDhcpRelayConfig OBJECT IDENTIFIER
	::= { qtechCapwapDhcpMIBObjects 4 }
	
	
--*************************************************
--DHCP Global Config
--*************************************************

qtechLDhcpClearAllStats    OBJECT-TYPE
	SYNTAX	                TruthValue
	MAX-ACCESS              read-write
	STATUS	                current
	DESCRIPTION
	"This attribute when set to true, clears
	all the statistics of the DHCP server."
	::= { qtechCapwapDhcpGlobalConfig  1 }
	
qtechLDhcpStartService    OBJECT-TYPE
	SYNTAX	                INTEGER {
                            enable(1),
                            disable(0)
                            }
	MAX-ACCESS              read-write
	STATUS	                current
	DESCRIPTION
	"this attribute when set to true, start DHCP
	service."
	::= { qtechCapwapDhcpGlobalConfig  2 }
	
qtechDhcpClientMacAddress  OBJECT-TYPE
        SYNTAX MacAddress
        MAX-ACCESS accessible-for-notify
        STATUS  current
        DESCRIPTION
            "This trap is sent when the dhcp client failed to request address"
        ::= { qtechCapwapDhcpGlobalConfig 3 }

qtechLDhcpStartTIService OBJECT-TYPE
	SYNTAX INTEGER {
                enable(1),
                disable(0)
            }
	MAX-ACCESS read-write
	STATUS current
	DESCRIPTION
	"this attribute when set to true, start DHCP
	 terminal identify service."
	::= { qtechCapwapDhcpGlobalConfig  4 }

--********************************************************
--DHCP stats group
--********************************************************
			
qtechLDhcpDiscoverPkts     OBJECT-TYPE
	SYNTAX                  Unsigned32
	UNITS                   "packets"
	MAX-ACCESS              read-only
	STATUS                  current   
	DESCRIPTION
    "This object represents the number of DHCP discover
	Packets sent by the controller."
	::= { qtechCapwapDhcpShowStats  1 }

qtechLDhcpRequestPkts      OBJECT-TYPE
	SYNTAX                  Unsigned32
	UNITS                   "packets"
	MAX-ACCESS              read-only
	STATUS                  current   
	DESCRIPTION
	"This object represents the number of DHCP request
	packets sent by the controller."
	::= { qtechCapwapDhcpShowStats  2 }

qtechLDhcpDeclinePkts      OBJECT-TYPE
	SYNTAX                  Unsigned32
	UNITS                   "packets"
	MAX-ACCESS              read-only
	STATUS                  current  
	DESCRIPTION
    "This object represents the number of DHCP decline
	Packets received by the controller."
	::= { qtechCapwapDhcpShowStats  3 }

qtechLDhcpInformPkts       OBJECT-TYPE
	SYNTAX                  Unsigned32
	UNITS                   "packets"
	MAX-ACCESS              read-only
	STATUS                  current   
	DESCRIPTION
	"This object represents the number of DHCP 
	inform packets."
	::= { qtechCapwapDhcpShowStats  4 }

qtechLDhcpReleasePkts      OBJECT-TYPE
	SYNTAX                  Unsigned32
	UNITS                   "packets"
	MAX-ACCESS              read-only
	STATUS                  current   
	DESCRIPTION
    "This object represents the number of DHCP 
	release packets."
    ::= { qtechCapwapDhcpShowStats  5 }

qtechLDhcpReplyPkts        OBJECT-TYPE
	SYNTAX                  Unsigned32
	UNITS                   "packets"
	MAX-ACCESS              read-only
	STATUS                  current   
	DESCRIPTION
	"This object represents the number of DHCP reply
	Packets received by the controller."
	::= { qtechCapwapDhcpShowStats  6 }

qtechLDhcpOfferPkts        OBJECT-TYPE
	SYNTAX                  Unsigned32
	UNITS                   "packets"
	MAX-ACCESS              read-only
	STATUS                  current   
	DESCRIPTION
    "This object represents the number of DHCP 
	offer packets."
    ::= { qtechCapwapDhcpShowStats  7 }

qtechLDhcpAckPkts          OBJECT-TYPE
    SYNTAX                  Unsigned32
  	UNITS                   "packets"
  	MAX-ACCESS              read-only
  	STATUS                  current   
  	DESCRIPTION
    "This object represents the number of Ack  packets"
    ::= { qtechCapwapDhcpShowStats  8 }

qtechLDhcpNakPkts          OBJECT-TYPE
	SYNTAX                  Unsigned32
	UNITS                   "packets"
	MAX-ACCESS              read-only
	STATUS                  current   
	DESCRIPTION
    "This object represents the number of Nak packets"
	::= { qtechCapwapDhcpShowStats  9 }


qtechLDhcpReqTimes          OBJECT-TYPE
	SYNTAX                  Unsigned32
	UNITS                     "packets"
	MAX-ACCESS              read-only
	STATUS                  current   
	DESCRIPTION
             "This object represents the number of request packets"
	::= { qtechCapwapDhcpShowStats  10 }

qtechLDhcpReqSucTimes           OBJECT-TYPE
	SYNTAX                  Unsigned32
	UNITS                   "packets"
	MAX-ACCESS              read-only
	STATUS                  current   
	DESCRIPTION
             "This object represents the number of Success Reqeust packets"
	::= { qtechCapwapDhcpShowStats  11 }	

--********************************************************
--DHCP Server config 
--********************************************************
    qtechDhcpScopeTable OBJECT-TYPE
         SYNTAX      SEQUENCE OF QtechDhcpScopeEntry
         MAX-ACCESS  not-accessible
         STATUS      current
         DESCRIPTION
                     "A table listing the Scopes defined on the
                      switch's DHCP Server."
         ::= { qtechCapwapDhcpServerConfig 1 }

    qtechDhcpScopeEntry OBJECT-TYPE
         SYNTAX      QtechDhcpScopeEntry
         MAX-ACCESS  not-accessible
         STATUS      current
         DESCRIPTION
                     "Switch's DHCP Server Scope entry."
         INDEX       { qtechDhcpScopeIndex }
         ::= { qtechDhcpScopeTable 1 }

    QtechDhcpScopeEntry ::= SEQUENCE {
             qtechDhcpScopeIndex                        Unsigned32,
             qtechDhcpScopeName                         DisplayString,
             qtechDhcpScopeLeaseTime                    Integer32,
             qtechDhcpScopeNetwork                      IpAddress,
             qtechDhcpScopeNetmask                      IpAddress,
	         qtechDhcpScopePoolStartAddress             IpAddress,
             qtechDhcpScopePoolEndAddress               IpAddress,
             qtechDhcpScopeDefaultRouterAddress1        IpAddress,
             qtechDhcpScopeDefaultRouterAddress2        IpAddress,
             qtechDhcpScopeDefaultRouterAddress3        IpAddress,
             qtechDhcpScopeDnsDomainName                DisplayString,
             qtechDhcpScopeDnsServerAddress1            IpAddress,
             qtechDhcpScopeDnsServerAddress2            IpAddress,
             qtechDhcpScopeDnsServerAddress3            IpAddress,
             qtechDhcpScopeNetbiosNameServerAddress1    IpAddress,
             qtechDhcpScopeNetbiosNameServerAddress2    IpAddress,
             qtechDhcpScopeNetbiosNameServerAddress3    IpAddress,
	         qtechDhcpScopeState                        INTEGER,
             qtechDhcpScopeRowStatus                    RowStatus,
             qtechDhcpIPPoolUsage                       Integer32,
             qtechDhcpoption43                          IpAddress,
             qtechDhcpoption138                         IpAddress,
             qtechDhcpReqtimes                          Unsigned32,
             qtechDhcpReqSuctimes                       Unsigned32,
             qtechDhcpTotalIPNum                        Integer32,		
             qtechDhcpCurrentUsedIPNum			 Integer32							
             }

    qtechDhcpScopeIndex OBJECT-TYPE
         SYNTAX      Unsigned32(1..15)
         MAX-ACCESS  not-accessible
         STATUS      current
         DESCRIPTION
                     "DHCP Scope Identifier Index."
         ::= { qtechDhcpScopeEntry 1 }

    qtechDhcpScopeName OBJECT-TYPE
         SYNTAX      DisplayString(SIZE(1..64))
         MAX-ACCESS  read-create
         STATUS      current
         DESCRIPTION
                     "DHCP Scope Name."
         ::= { qtechDhcpScopeEntry 2 }

    qtechDhcpScopeLeaseTime OBJECT-TYPE
         SYNTAX      Integer32(120..8640000)
         MAX-ACCESS  read-create
         STATUS      current
         DESCRIPTION
                     "DHCP Scope Lease time in seconds."
         ::= { qtechDhcpScopeEntry 3 }

    qtechDhcpScopeNetwork OBJECT-TYPE
         SYNTAX      IpAddress
         MAX-ACCESS  read-create
         STATUS      current
         DESCRIPTION
                     "IP Address of the DHCP Scope Network. This is
                     the address which is used to determine the DHCP
                     scope a remote Switch is attaching to."
         ::= { qtechDhcpScopeEntry 4 }

    qtechDhcpScopeNetmask OBJECT-TYPE
         SYNTAX      IpAddress
         MAX-ACCESS  read-create
         STATUS      current
         DESCRIPTION
                     "The DHCP Scope Netmask. This the subnet mask for
                      the address pool."
         ::= { qtechDhcpScopeEntry 5 }
		 
    qtechDhcpScopePoolStartAddress OBJECT-TYPE
         SYNTAX      IpAddress
         MAX-ACCESS  read-create
         STATUS      current
         DESCRIPTION
                     "The DHCP Scope address pool start IP address."
         ::= { qtechDhcpScopeEntry 6 }

    qtechDhcpScopePoolEndAddress OBJECT-TYPE
         SYNTAX      IpAddress
         MAX-ACCESS  read-create
         STATUS      current
         DESCRIPTION
                     "The DHCP Scope address pool end IP address."
         ::= { qtechDhcpScopeEntry 7 }

    qtechDhcpScopeDefaultRouterAddress1 OBJECT-TYPE
         SYNTAX      IpAddress
         MAX-ACCESS  read-create
         STATUS      current
         DESCRIPTION
                     "IP Address of the DHCP Scope's default Router
                     1."
         ::= { qtechDhcpScopeEntry 8 }

    qtechDhcpScopeDefaultRouterAddress2 OBJECT-TYPE
         SYNTAX      IpAddress
         MAX-ACCESS  read-create
         STATUS      current
         DESCRIPTION
                     "IP Address of the DHCP Scope's default Router
                     2."
         ::= { qtechDhcpScopeEntry 9 }

    qtechDhcpScopeDefaultRouterAddress3 OBJECT-TYPE
         SYNTAX      IpAddress
         MAX-ACCESS  read-create
         STATUS      current
         DESCRIPTION
                     "IP Address of the DHCP Scope's default Router
                     3."
         ::= { qtechDhcpScopeEntry 10 }

    qtechDhcpScopeDnsDomainName OBJECT-TYPE
         SYNTAX      DisplayString(SIZE(0..64))
         MAX-ACCESS  read-create
         STATUS      current
         DESCRIPTION
                     "DNS Domain name for the DHCP Scope."
         ::= { qtechDhcpScopeEntry 11 }

    qtechDhcpScopeDnsServerAddress1 OBJECT-TYPE
         SYNTAX      IpAddress
         MAX-ACCESS  read-create
         STATUS      current
         DESCRIPTION
                     "IP Address of the DHCP Scope's DNS Server 1."
         ::= { qtechDhcpScopeEntry 12 }

    qtechDhcpScopeDnsServerAddress2 OBJECT-TYPE
         SYNTAX      IpAddress
         MAX-ACCESS  read-create
         STATUS      current
         DESCRIPTION
                     "IP Address of the DHCP Scope's DNS Server 2."
         ::= { qtechDhcpScopeEntry 13 }

    qtechDhcpScopeDnsServerAddress3 OBJECT-TYPE
         SYNTAX      IpAddress
         MAX-ACCESS  read-create
         STATUS      current
         DESCRIPTION
                     "IP Address of the DHCP Scope's DNS Server 3."
         ::= { qtechDhcpScopeEntry 14 }

    qtechDhcpScopeNetbiosNameServerAddress1 OBJECT-TYPE
         SYNTAX      IpAddress
         MAX-ACCESS  read-create
         STATUS      current
         DESCRIPTION
                     "IP Address of DHCP Scope's Netbios Name Server
                     1."
         ::= { qtechDhcpScopeEntry 15 }

    qtechDhcpScopeNetbiosNameServerAddress2 OBJECT-TYPE
         SYNTAX      IpAddress
         MAX-ACCESS  read-create
         STATUS      current
         DESCRIPTION
                     "IP Address of DHCP Scope's Netbios Name Server
                     2."
         ::= { qtechDhcpScopeEntry 16 }

    qtechDhcpScopeNetbiosNameServerAddress3 OBJECT-TYPE
         SYNTAX      IpAddress
         MAX-ACCESS  read-create
         STATUS      current
         DESCRIPTION
                     "IP Address of DHCP Scope's Netbios Name Server
                     3."
         ::= { qtechDhcpScopeEntry 17 }
		
    qtechDhcpScopeState OBJECT-TYPE
         SYNTAX      INTEGER {
                     disable(0),
                     enable(1)
                     }
         MAX-ACCESS  read-create
         STATUS      current
         DESCRIPTION
                      "DHCP Scope's State."
         ::= { qtechDhcpScopeEntry 18 }

    qtechDhcpScopeRowStatus OBJECT-TYPE
         SYNTAX      RowStatus
         MAX-ACCESS  read-create
         STATUS      current
         DESCRIPTION
                     "Dhcp Scope entry row status."
         ::= { qtechDhcpScopeEntry 19 }

    qtechDhcpIPPoolUsage OBJECT-TYPE
         SYNTAX      Integer32(0..100)
         MAX-ACCESS  read-create
         STATUS      current
         DESCRIPTION
                     "DHCP pool use rate."
         ::= { qtechDhcpScopeEntry 20 }

    qtechDhcpoption43 OBJECT-TYPE
         SYNTAX      IpAddress
         MAX-ACCESS  read-create
         STATUS      current
         DESCRIPTION
                     "use DHCP option43 to set ac ipaddress."
         ::= { qtechDhcpScopeEntry 21 }

    qtechDhcpoption138 OBJECT-TYPE
         SYNTAX      IpAddress
         MAX-ACCESS  read-create
         STATUS      current
         DESCRIPTION
                     "use DHCP option138 to set ac ipaddress."
         ::= { qtechDhcpScopeEntry 22 }         
 
    qtechDhcpReqtimes OBJECT-TYPE
         SYNTAX      Unsigned32
         MAX-ACCESS  read-only
         STATUS      current
         DESCRIPTION
                     "use DHCP pool reqest times."
         ::= { qtechDhcpScopeEntry 23 }       

    qtechDhcpReqSuctimes OBJECT-TYPE
         SYNTAX      Unsigned32
         MAX-ACCESS  read-only
         STATUS      current
         DESCRIPTION
                     "use DHCP pool request successful times."
         ::= { qtechDhcpScopeEntry 24 }     
    qtechDhcpTotalIPNum	OBJECT-TYPE
    		 SYNTAX		Integer32
    		 MAX-ACCESS	read-only
    		 STATUS		current
    		 DESCRIPTION
				"total IP address amount of DHCP pool. "  	
    		 ::= { qtechDhcpScopeEntry 25 }
    qtechDhcpCurrentUsedIPNum	OBJECT-TYPE
    		 SYNTAX		Integer32
    		 MAX-ACCESS	read-only
    		 STATUS		current
    		 DESCRIPTION  
				"current used IP amount of DHCP pool."	
    		 ::= { qtechDhcpScopeEntry 26 } 

--*******************************************************************
--DHCP Relay Config :  external DHCP Server Address 
--*******************************************************************
    qtechDhcpGlobalServerAddrTable OBJECT-TYPE
         SYNTAX      SEQUENCE OF QtechDhcpGlobalServerAddrEntry
         MAX-ACCESS  not-accessible
         STATUS      current
         DESCRIPTION
                     "A table listing the global external DHCP server 
                     address configed for DHCP relay."
         ::= { qtechCapwapDhcpRelayConfig 1 }
               
    qtechDhcpGlobalServerAddrEntry OBJECT-TYPE
         SYNTAX      QtechDhcpGlobalServerAddrEntry
         MAX-ACCESS  not-accessible
         STATUS      current
         DESCRIPTION
                     "Global DHCP server address entry configed for DHCP 
                     relay. Upto 20 entries may be added."
         INDEX       { qtechDhcpGlobalServerIndex }
         ::= { qtechDhcpGlobalServerAddrTable 1 }
         
    QtechDhcpGlobalServerAddrEntry ::= SEQUENCE {
             qtechDhcpGlobalServerIndex      Integer32,
             qtechDhcpGlobalServerAddress    IpAddress,
             qtechDhcpGlobalServerRowStatus  RowStatus
             }

    qtechDhcpGlobalServerIndex OBJECT-TYPE
         SYNTAX      Integer32(1..20)
         MAX-ACCESS  not-accessible
         STATUS      current
         DESCRIPTION
                     "Global DHCP server index."
         ::= { qtechDhcpGlobalServerAddrEntry 1 }

    qtechDhcpGlobalServerAddress OBJECT-TYPE
         SYNTAX      IpAddress
         MAX-ACCESS  read-create
         STATUS      current
         DESCRIPTION
                     "IP Address of the Global DHCP server"
         ::= { qtechDhcpGlobalServerAddrEntry 2 }

    qtechDhcpGlobalServerRowStatus OBJECT-TYPE
         SYNTAX      RowStatus
         MAX-ACCESS  read-create
         STATUS      current
         DESCRIPTION
                     "This is the status column for this row and used
                      to create and delete specific instances of rows
                      in this table. "
         ::= { qtechDhcpGlobalServerAddrEntry 3 }


--*******************************************************************
--DHCP Relay Config :  external DHCP Server Address on interface
--*******************************************************************

    qtechDhcpIntfServerAddrTable OBJECT-TYPE
         SYNTAX      SEQUENCE OF QtechDhcpIntfServerAddrEntry
         MAX-ACCESS  not-accessible
         STATUS      current
         DESCRIPTION
                     "A table listing the  external DHCP server address 
                     on interface configed for DHCP relay."
         ::= { qtechCapwapDhcpRelayConfig 2 }
   
    qtechDhcpIntfServerAddrEntry OBJECT-TYPE
         SYNTAX      QtechDhcpIntfServerAddrEntry
         MAX-ACCESS  not-accessible
         STATUS      current
         DESCRIPTION
                     "Extern DHCP server address entry configed on interface 
                 for DHCP relay. Upto 20 entries may be added on a interface."
         INDEX       { qtechIfIndex, qtechDhcpIntfServerIndex}
         ::= { qtechDhcpIntfServerAddrTable 1 }
         
    QtechDhcpIntfServerAddrEntry ::= SEQUENCE {
             qtechDhcpIntfServerIndex      Integer32,
             qtechDhcpIntfServerAddress    IpAddress,
             qtechDhcpIntfServerRowStatus  RowStatus
             }

    qtechDhcpIntfServerIndex OBJECT-TYPE
         SYNTAX      Integer32 (1..20) 
         MAX-ACCESS  not-accessible
         STATUS      current
         DESCRIPTION
                     "Interface DHCP server index."
         ::= { qtechDhcpIntfServerAddrEntry 1 }

    qtechDhcpIntfServerAddress OBJECT-TYPE
         SYNTAX      IpAddress
         MAX-ACCESS  read-create
         STATUS      current
         DESCRIPTION
                     "IP Address of the Global DHCP server"
         ::= { qtechDhcpIntfServerAddrEntry 2 }

    qtechDhcpIntfServerRowStatus OBJECT-TYPE
         SYNTAX      RowStatus
         MAX-ACCESS  read-create
         STATUS      current
         DESCRIPTION
                     "This is the status column for this row and used
                      to create and delete specific instances of rows
                      in this table. "
         ::= { qtechDhcpIntfServerAddrEntry 3 }


--*******************************************************************
-- DHCP trap
--*******************************************************************
     qtechDhcpAddressExhaustTrap       NOTIFICATION-TYPE
        OBJECTS {
             qtechDhcpScopeName
        }
        STATUS  current
        DESCRIPTION
            "This trap is sent when the dhcp pool is full"
        ::= { qtechCapwapDhcpMIBTrap 1 }

     qtechDhcpAddressExhaustRecovTrap  NOTIFICATION-TYPE
        OBJECTS {
             qtechDhcpScopeName
        }
        STATUS  current
        DESCRIPTION
            "This trap is sent when the dhcp pool recover from full"
        ::= { qtechCapwapDhcpMIBTrap 2 }
        
    qtechDhcpClientFailTrap  NOTIFICATION-TYPE
        OBJECTS {
             qtechDhcpClientMacAddress
        }
        STATUS  current
        DESCRIPTION
            "This trap is sent when the dhcp client failed to request address"
        ::= { qtechCapwapDhcpMIBTrap 3 }

		
qtechCapwapDhcpMIBConformance OBJECT IDENTIFIER ::= { qtechCapwapDhcpMIB 2 }
qtechCapwapDhcpMIBCompliances OBJECT IDENTIFIER ::= { qtechCapwapDhcpMIBConformance 1 }
qtechCapwapDhcpMIBGroups      OBJECT IDENTIFIER ::= { qtechCapwapDhcpMIBConformance 2 }


-- compliance statements

qtechCapwapDhcpMIBCompliance MODULE-COMPLIANCE
        STATUS  current
        DESCRIPTION
                "The compliance statement for entities which implement
                the Qtech Capwap Dhcp MIB"
        MODULE  -- this module
                MANDATORY-GROUPS { qtechCapwapDhcpMIBGroup,
				        qtechCapwapDhcpServerConfigGroup,
				        qtechCapwapDhcpRelayGlobalConfigGroup,
				        qtechCapwapDhcpRelayIntfConfigGroup
                }
        ::= { qtechCapwapDhcpMIBCompliances 1 }
                
-- units of conformance

qtechCapwapDhcpMIBGroup OBJECT-GROUP
        OBJECTS {
              qtechLDhcpClearAllStats,
	        qtechLDhcpStartService,
              qtechLDhcpDiscoverPkts,
              qtechLDhcpRequestPkts,
              qtechLDhcpDeclinePkts,
              qtechLDhcpInformPkts,
              qtechLDhcpReleasePkts,
              qtechLDhcpReplyPkts,
              qtechLDhcpOfferPkts,
              qtechLDhcpAckPkts,
              qtechLDhcpNakPkts,
              qtechLDhcpReqTimes,
              qtechLDhcpReqSucTimes
        }
        STATUS  current
        DESCRIPTION
                "A collection of objects providing capwap dhcp information and
                opertion to a Qtech agent."
        ::= { qtechCapwapDhcpMIBGroups 1 } 
		
qtechCapwapDhcpServerConfigGroup OBJECT-GROUP
        OBJECTS {
             qtechDhcpScopeName,
             qtechDhcpScopeLeaseTime,
             qtechDhcpScopeNetwork,
             qtechDhcpScopeNetmask,
             qtechDhcpScopeDefaultRouterAddress1,
             qtechDhcpScopeDefaultRouterAddress2,
             qtechDhcpScopeDefaultRouterAddress3,
             qtechDhcpScopeDnsDomainName,
             qtechDhcpScopeDnsServerAddress1,
             qtechDhcpScopeDnsServerAddress2,
             qtechDhcpScopeDnsServerAddress3,
             qtechDhcpScopeNetbiosNameServerAddress1,
             qtechDhcpScopeNetbiosNameServerAddress2,
             qtechDhcpScopeNetbiosNameServerAddress3,
	      qtechDhcpScopeState,
             qtechDhcpScopeRowStatus,
             qtechDhcpIPPoolUsage,
             qtechDhcpoption43,
             qtechDhcpoption138
        }
        STATUS  current
        DESCRIPTION
                "A collection of objects providing capwap dhcp server config information."
        ::= { qtechCapwapDhcpMIBGroups 2 } 


qtechCapwapDhcpRelayGlobalConfigGroup OBJECT-GROUP
        OBJECTS {
             qtechDhcpGlobalServerAddress,
             qtechDhcpGlobalServerRowStatus
        }
        STATUS  current
        DESCRIPTION
                "A collection of objects providing capwap dhcp relay config information."
        ::= { qtechCapwapDhcpMIBGroups 3 } 
        
qtechCapwapDhcpRelayIntfConfigGroup OBJECT-GROUP
        OBJECTS {
             qtechDhcpIntfServerAddress,
             qtechDhcpIntfServerRowStatus
        }
        STATUS  current
        DESCRIPTION
                "A collection of objects providing capwap dhcp relay config information."
        ::= { qtechCapwapDhcpMIBGroups 4 } 

END

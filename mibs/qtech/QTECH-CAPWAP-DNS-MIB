-- *******************************************************************
-- QTECH-CAPWAP-DNS-MIB.mib : Qtech DNS MIB 
-- 
-- Jun 2010, chenfg1
--
-- Copyright (c) 2010 by Qtech Networks Co.,Ltd.
-- All rights reserved.
-- *******************************************************************
--
QTECH-CAPWAP-DNS-MIB DEFINITIONS ::= BEGIN

IMPORTS 
        MODULE-IDENTITY, 
        OBJECT-TYPE,
		    Integer32,
	      NOTIFICATION-TYPE,	
        Unsigned32,
        IpAddress
                FROM SNMPv2-SMI
        OBJECT-GROUP,
        MODULE-COMPLIANCE
                FROM SNMPv2-CONF
        TruthValue,
        RowStatus,
        DisplayString
                FROM SNMPv2-TC 
        qtechMgmt
                FROM QTECH-SMI
        qtechIfIndex 
                FROM QTECH-INTERFACE-MIB;


qtechCapwapDnsMIB   MODULE-IDENTITY
       LAST-UPDATED    "201007090000Z"
       ORGANIZATION    "Qtech Networks Co.,Ltd."
       CONTACT-INFO  
                " 
                Tel: 4008-111-000 

                E-mail: service@qtech.com.cn"

        DESCRIPTION             
                "This is DNS MIB"
        
        REVISION      "201007090000Z"
        DESCRIPTION
                "Initial version of this MIB module. "
        ::= { qtechMgmt 88 }


qtechCapwapDnsMIBObjects OBJECT IDENTIFIER 
    ::= { qtechCapwapDnsMIB 0 }

qtechCapwapDnsGlobalConfig OBJECT IDENTIFIER
	::= { qtechCapwapDnsMIBObjects 1 }


--*************************************************
--DNS Global Config
--*************************************************

qtechLDnsFirstServer     OBJECT-TYPE
	SYNTAX	                IpAddress
	MAX-ACCESS              read-write
	STATUS	                current
	DESCRIPTION
	     "The first dns server address."
	::= { qtechCapwapDnsGlobalConfig  1 }
	
qtechLDnsSecondServer    OBJECT-TYPE
	SYNTAX	                IpAddress
	MAX-ACCESS              read-write
	STATUS	                current
	DESCRIPTION
	     "The second dns server address."
	::= { qtechCapwapDnsGlobalConfig  2 }



qtechCapwapDnsMIBConformance OBJECT IDENTIFIER ::= { qtechCapwapDnsMIB 2 }
qtechCapwapDnsMIBCompliances OBJECT IDENTIFIER ::= { qtechCapwapDnsMIBConformance 1 }
qtechCapwapDnsMIBGroups      OBJECT IDENTIFIER ::= { qtechCapwapDnsMIBConformance 2 }

-- compliance statements

qtechCapwapDnsMIBCompliance MODULE-COMPLIANCE
        STATUS  current
        DESCRIPTION
                "The compliance statement for entities which implement
                the Qtech Capwap Dns MIB"
        MODULE  -- this module
        MANDATORY-GROUPS { 
              qtechCapwapDnsMIBGroup
        }
        ::= { qtechCapwapDnsMIBCompliances 1 }

-- units of conformance

qtechCapwapDnsMIBGroup OBJECT-GROUP
        OBJECTS {
              qtechLDnsFirstServer,
	      qtechLDnsSecondServer
        }
        STATUS  current
        DESCRIPTION
                "A collection of objects providing capwap dns information and
                opertion to a Qtech agent."
        ::= { qtechCapwapDnsMIBGroups 1 } 
		
END

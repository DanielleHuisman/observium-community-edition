-- *****************************************************************
-- QTECH-DHCP-RELAY-MIB.mib:  Qtech DHCP relay MIB file
--
-- Oct 2011, yangchanghua
--
-- Copyright (c) 2011 by Qtech Networks Co.,Ltd.
-- All rights reserved.
-- *****************************************************************
--

QTECH-DHCP-RELAY-MIB DEFINITIONS ::= BEGIN

IMPORTS
        MODULE-IDENTITY,
        OBJECT-TYPE,
        NOTIFICATION-TYPE,
        Integer32,
        Counter32
                FROM SNMPv2-SMI
        TruthValue,
        DisplayString,
        RowStatus,
        MacAddress
                FROM SNMPv2-TC
        MODULE-COMPLIANCE,
        OBJECT-GROUP,
        NOTIFICATION-GROUP
                FROM SNMPv2-CONF
        qtechMgmt
                FROM QTECH-SMI;
                
qtechDhcpMIB  MODULE-IDENTITY
    LAST-UPDATED "201111280000Z"
    ORGANIZATION "Qtech Networks Co.,Ltd."
    CONTACT-INFO
        				" 
                Tel: 4008-111-000 

                E-mail: service@qtech.com.cn"
    DESCRIPTION
        "This module defines qtech DHCP mibs."
    -- Revision History
    REVISION    "201111280000Z"
    DESCRIPTION
        "Initial version of this MIB module."
    ::= { qtechMgmt 104 }
    
--
-- Declare top-level DHCP relay MIB objects
--
qtechDhcpMIBObjects OBJECT-IDENTITY 
    STATUS      current
    DESCRIPTION
        "DHCP Relay MIB objects are defined in this branch."
    ::= { qtechDhcpMIB 1 }
    
--
-- DHCP Relay
--
qtechDhcpRelayMIBObjects OBJECT-IDENTITY 
    STATUS      current
    DESCRIPTION
        "DHCP Relay MIB identification objects are all defined
        in this branch."
    ::= { qtechDhcpMIBObjects 1 }

--
-- DHCP Relay Status
--
qtechDHCPRelayCycleStatus OBJECT-TYPE
    SYNTAX      INTEGER {
                             on(0), -- DHCP relay cycle mode status is on
                             off(1) -- DHCP relay cycle mode status is off
                        }
    MAX-ACCESS  read-write
    STATUS      current
    DESCRIPTION
        "Status of DHCP relay cycle mode,
         when the value is 0, cycle with the serveral DHCP servers addresses,
         when the value is 1, use one same DHCP server."
    ::= { qtechDhcpRelayMIBObjects 1 }

qtechDhcpRelayCounters OBJECT-IDENTITY
    STATUS      current
    DESCRIPTION
        "Group of objects that count various DHCP Relay events."
 ::= { qtechDhcpRelayMIBObjects 2 }
 
--
-- DHCP Relay Counters
--
qtechDHCPRRxBadPktNum OBJECT-TYPE
    SYNTAX      Integer32
    MAX-ACCESS  read-only
    STATUS      current
    DESCRIPTION
        "The total number of the bad packets received by 
            DHCP relay."
    ::= { qtechDhcpRelayCounters 1 }
    
qtechDHCPRRxServerPktNum OBJECT-TYPE
    SYNTAX      Integer32
    MAX-ACCESS  read-only
    STATUS      current
    DESCRIPTION
        "The total number of the packets received from
            DHCP servers by DHCP relay module."
    ::= { qtechDhcpRelayCounters 2 }
    
qtechDHCPRTxServerPktNum OBJECT-TYPE
    SYNTAX      Integer32
    MAX-ACCESS  read-only
    STATUS      current
    DESCRIPTION
        "The total number of the packets transmited to
            DHCP servers by DHCP relay module."
    ::= { qtechDhcpRelayCounters 3 }

qtechDHCPRRxClientPktNum OBJECT-TYPE
    SYNTAX      Integer32
    MAX-ACCESS  read-only
    STATUS      current
    DESCRIPTION
        "The total number of the packets received form DHCP
            clients by DHCP relay."
    ::= { qtechDhcpRelayCounters 4 }
    
qtechDHCPRTxClientPktNum OBJECT-TYPE
    SYNTAX      Integer32
    MAX-ACCESS  read-only
    STATUS      current
    DESCRIPTION
        "The total number of the packets transmited
            to DHCP clients by DHCP relay."
    ::= { qtechDhcpRelayCounters 5 }

qtechDHCPRRxClientUniPktNum OBJECT-TYPE
    SYNTAX      Integer32
    MAX-ACCESS  read-only
    STATUS      current
    DESCRIPTION
        "The total number of the unicast packets received form DHCP
            clients by DHCP relay."
    ::= { qtechDhcpRelayCounters 6 }

qtechDHCPRRxClientBroPktNum OBJECT-TYPE
    SYNTAX      Integer32
    MAX-ACCESS  read-only
    STATUS      current
    DESCRIPTION
        "The total number of the broadcast packets received form DHCP
            clients by DHCP relay."
    ::= { qtechDhcpRelayCounters 7 }

qtechDHCPRTxClientUniPktNum OBJECT-TYPE
    SYNTAX      Integer32
    MAX-ACCESS  read-only
    STATUS      current
    DESCRIPTION
        "The total number of the unicast packets transmited
            to DHCP clients by DHCP relay."
    ::= { qtechDhcpRelayCounters 8 }
    
qtechDHCPRTxClientBroPktNum OBJECT-TYPE
    SYNTAX      Integer32
    MAX-ACCESS  read-only
    STATUS      current
    DESCRIPTION
        "The total number of the broadcast packets transmited
            to DHCP clients by DHCP relay."
    ::= { qtechDhcpRelayCounters 9 }
    
qtechDHCPRelayDiscoverPktNum OBJECT-TYPE
    SYNTAX      Integer32
    MAX-ACCESS  read-only
    STATUS      current
    DESCRIPTION
        "The total number of the DHCP Discover packets handled
            by DHCP relay."
    ::= { qtechDhcpRelayCounters 10 }
    
qtechDHCPRelayRequestPktNum OBJECT-TYPE
    SYNTAX      Integer32
    MAX-ACCESS  read-only
    STATUS      current
    DESCRIPTION
        "The total number of the DHCP Request packets handled
            by DHCP relay."
    ::= { qtechDhcpRelayCounters 11 }
    
qtechDHCPRelayDeclinePktNum OBJECT-TYPE
    SYNTAX      Integer32
    MAX-ACCESS  read-only
    STATUS      current
    DESCRIPTION
        "The total number of the DHCP Decline packets handled
            by DHCP relay."
    ::= { qtechDhcpRelayCounters 12 }
    
qtechDHCPRelayReleasePktNum OBJECT-TYPE
    SYNTAX      Integer32
    MAX-ACCESS  read-only
    STATUS      current
    DESCRIPTION
        "The total number of the DHCP Release packets handled
            by DHCP relay."
    ::= { qtechDhcpRelayCounters 13 }
    
qtechDHCPRelayInformPktNum OBJECT-TYPE
    SYNTAX      Integer32
    MAX-ACCESS  read-only
    STATUS      current
    DESCRIPTION
        "The total number of the DHCP Inform packets handled
            by DHCP relay."
    ::= { qtechDhcpRelayCounters 14 }
    
qtechDHCPRelayOfferPktNum OBJECT-TYPE
    SYNTAX      Integer32
    MAX-ACCESS  read-only
    STATUS      current
    DESCRIPTION
        "The total number of the DHCP Offer packets handled
            by DHCP server."
    ::= { qtechDhcpRelayCounters 15 }
    
qtechDHCPRelayAckPktNum OBJECT-TYPE
    SYNTAX      Integer32
    MAX-ACCESS  read-only
    STATUS      current
    DESCRIPTION
        "The total number of the DHCP Ack packets handled
            by DHCP relay."
    ::= { qtechDhcpRelayCounters 16 }
    
qtechDHCPRelayNakPktNum OBJECT-TYPE
    SYNTAX      Integer32
    MAX-ACCESS  read-only
    STATUS      current
    DESCRIPTION
        "The total number of the DHCP Nak packets handled
            by DHCP relay."
    ::= { qtechDhcpRelayCounters 17 }
    
--
-- Conformance
--
qtechDhcpMIBConformance   OBJECT-IDENTITY 
    STATUS      current
    DESCRIPTION
        "DHCP relay conformance objects are all defined in this
        branch."
    ::= { qtechDhcpMIB 2 }
    
qtechDhcpMIBCompliances   OBJECT IDENTIFIER ::= { qtechDhcpMIBConformance 1 }
qtechDhcpMIBGroups        OBJECT IDENTIFIER ::= { qtechDhcpMIBConformance 2 }

--
-- Compliance groups
--
qtechDhcpRelayCompliance MODULE-COMPLIANCE
    STATUS      current
    DESCRIPTION
        "This group describes the requirements for conformance to the
        DHCP Relay MIB."
    MODULE  -- this module
    MANDATORY-GROUPS {
        qtechDhcpRelayCountersObjects
    }
    ::= { qtechDhcpMIBCompliances 1 } 
    
--
-- Object groups
--
qtechDhcpRelayCountersObjects  OBJECT-GROUP
    OBJECTS {
        qtechDHCPRelayCycleStatus,
        qtechDHCPRRxBadPktNum,
        qtechDHCPRRxServerPktNum,
        qtechDHCPRTxServerPktNum,
        qtechDHCPRRxClientPktNum,
        qtechDHCPRTxClientPktNum,
        qtechDHCPRRxClientUniPktNum,
        qtechDHCPRRxClientBroPktNum,
        qtechDHCPRTxClientUniPktNum,
        qtechDHCPRTxClientBroPktNum,
        qtechDHCPRelayDiscoverPktNum,
        qtechDHCPRelayRequestPktNum,
        qtechDHCPRelayDeclinePktNum,
        qtechDHCPRelayReleasePktNum,
        qtechDHCPRelayInformPktNum,
        qtechDHCPRelayOfferPktNum,
		    qtechDHCPRelayAckPktNum,
		    qtechDHCPRelayNakPktNum }
    STATUS      current
    DESCRIPTION
        "The basic collection of objects providing management of DHCP
        Relay functionality."
    ::= { qtechDhcpMIBGroups 1 }

END

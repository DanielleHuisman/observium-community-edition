-- *******************************************************************
-- QTECH-DOT11-WIDS-MIB.mib : Qtech WLAN wids MIB
--
-- Oct 2009, kangxiankun
--
-- Copyright (c) 2009 by Qtech Networks Co.,Ltd.
-- All rights reserved.
-- *******************************************************************
--
QTECH-DOT11-WIDS-MIB DEFINITIONS ::= BEGIN

IMPORTS
        TruthValue,
        MacAddress,
        DisplayString
                FROM SNMPv2-TC
        MODULE-IDENTITY,
        OBJECT-TYPE,
        TimeTicks,
        Integer32
                FROM SNMPv2-SMI
        MODULE-COMPLIANCE,
        OBJECT-GROUP
                FROM SNMPv2-CONF
        qtechMgmt
                FROM QTECH-SMI;
--********************************************************************
--*  MODULE IDENTITY
--********************************************************************
qtechDot11WIDSMIB    MODULE-IDENTITY
   LAST-UPDATED    "200904150900Z"
   ORGANIZATION    "Qtech Networks Co.,Ltd."
   CONTACT-INFO
            "
            Tel: 4008-111-000

            E-mail: service@qtech.com.cn"
    DESCRIPTION
          "This MIB provides information about WIDS feature.

          GLOSSARY

          Wireless Intrusion Detection Sensor (WIDS)
          WIDS is designed to be employed in an area that is serviced
          by an existing wireless network.
          It aids in the early detection of malicious outsider attacks
          and intrusions via wireless networks.

          Rogue AP
          A rogue access point is any Wi-Fi access point connected to
          your network without authorization.
          As it is not authorized, if there is any weakness in
          the AP, the hacker will have chance to compromise your
          network.

          Rogue Station
          It is similiar to Rogue AP, while it is a station.

          Monitor AP
          An AP will scan or listen to the air, and try to detect
          wireless attack in the network.
          Some AP products will work only in monitor role, while some
          AP products could switch between normal AP role (only
          provide wireless access service)and monitor AP role.

          Ad Hoc Mode
          Station could work under Ad hoc mode, then they
          could directly do peer-to-peer communication without
          other device support."

          REVISION "200904150900Z"
          DESCRIPTION
                  "The initial revision of this MIB module."
          ::= { qtechMgmt 62 }

qtechDot11WIDSConfigObjects OBJECT IDENTIFIER       ::= { qtechDot11WIDSMIB 1 }
qtechDot11WIDSDetectObjects OBJECT IDENTIFIER       ::= { qtechDot11WIDSMIB 2 }
--qtechDot11WIDSTraps OBJECT IDENTIFIER       ::= { qtechDot11WIDSMIB 0 }

--*****************************************************************************
--*  qtechDot11WIDSPermitVendorTable Definition
--*****************************************************************************
qtechDot11WIDSPermitVendorTable OBJECT-TYPE
    SYNTAX      SEQUENCE OF QtechDot11WIDSPermitVendorEntry
    MAX-ACCESS  not-accessible
    STATUS      current
    DESCRIPTION
        "The table provides the permitted vendor list, and each vendor
        will be identified by MAC. The legal device should be made by the permitted vendors."
    ::= { qtechDot11WIDSConfigObjects 1 }

qtechDot11WIDSPermitVendorEntry OBJECT-TYPE
    SYNTAX      QtechDot11WIDSPermitVendorEntry
    MAX-ACCESS  not-accessible
    STATUS      current
    DESCRIPTION
        "Each entry provides the information of permitted vendor."
    INDEX { qtechDot11VendorOUI }
    ::= { qtechDot11WIDSPermitVendorTable 1 }

QtechDot11WIDSPermitVendorEntry ::=
    SEQUENCE {
        qtechDot11VendorOUI                Integer32,
        qtechDot11VendorOper               Integer32,
        qtechDot11VendorName               MacAddress
    }

qtechDot11VendorOUI OBJECT-TYPE
    SYNTAX      Integer32
    MAX-ACCESS  not-accessible
    STATUS      current
    DESCRIPTION
        "Represents the vendor OUI information of the wireless device."
    ::= { qtechDot11WIDSPermitVendorEntry 1 }

qtechDot11VendorOper OBJECT-TYPE
    SYNTAX      Integer32
    MAX-ACCESS  read-write
    STATUS      current
    DESCRIPTION
        "Represents the operation of vendor list."
    ::= { qtechDot11WIDSPermitVendorEntry 2 }

qtechDot11VendorName OBJECT-TYPE
    SYNTAX      MacAddress
    MAX-ACCESS  read-write
    STATUS      current
    DESCRIPTION
        "Represents the vendor mac of the wireless device."
    ::= { qtechDot11WIDSPermitVendorEntry 3 }

--*****************************************************************************
--*  qtechDot11WIDSPermitSSIDTable Definition
--*****************************************************************************

qtechDot11WIDSPermitSSIDTable OBJECT-TYPE
    SYNTAX      SEQUENCE OF QtechDot11WIDSPermitSSIDEntry
    MAX-ACCESS  not-accessible
    STATUS      current
    DESCRIPTION
        "The table represents the list of SSID could be permitted in
        the wireless network."
    ::= { qtechDot11WIDSConfigObjects 2 }

qtechDot11WIDSPermitSSIDEntry OBJECT-TYPE
    SYNTAX      QtechDot11WIDSPermitSSIDEntry
    MAX-ACCESS  not-accessible
    STATUS      current
    DESCRIPTION
        "Each entry provides the information of permitted SSID."
    INDEX { qtechDot11PermitNum }
    ::= { qtechDot11WIDSPermitSSIDTable 1 }

QtechDot11WIDSPermitSSIDEntry ::=
    SEQUENCE {
        qtechDot11PermitNum              Integer32,
        qtechDot11PermitOper             Integer32,
        qtechDot11PermitSSID             DisplayString
    }

qtechDot11PermitNum OBJECT-TYPE
    SYNTAX      Integer32
    MAX-ACCESS  not-accessible
    STATUS      current
    DESCRIPTION
        "Represents the permitted num in the wireless network."
    ::= { qtechDot11WIDSPermitSSIDEntry 1 }

qtechDot11PermitOper OBJECT-TYPE
    SYNTAX      Integer32
    MAX-ACCESS  read-write
    STATUS      current
    DESCRIPTION
        "Represents the operation of ssid list."
    ::= { qtechDot11WIDSPermitSSIDEntry 2 }

qtechDot11PermitSSID OBJECT-TYPE
    SYNTAX      DisplayString(SIZE (0..255))
    MAX-ACCESS  read-write
    STATUS      current
    DESCRIPTION
        "Represents the permitted SSID in the wireless network."
    ::= { qtechDot11WIDSPermitSSIDEntry 3 }

--*****************************************************************************
--*  qtechDot11WIDSDeviceAttackMacaddressListTable Definition
--*****************************************************************************
qtechDot11WIDSDeviceAttackMacaddressListTable OBJECT-TYPE
    SYNTAX      SEQUENCE OF QtechDot11WIDSDeviceAttackMacaddressListEntry
    MAX-ACCESS  not-accessible
    STATUS      current
    DESCRIPTION
        "The table provides the MAC address list of legal stations"
    ::= { qtechDot11WIDSConfigObjects 3 }

qtechDot11WIDSDeviceAttackMacaddressListEntry OBJECT-TYPE
    SYNTAX      QtechDot11WIDSDeviceAttackMacaddressListEntry
    MAX-ACCESS  not-accessible
    STATUS      current
    DESCRIPTION
        "Each entry contains the MAC address of legal stations."
    INDEX { qtechDot11AttackNum }
    ::= { qtechDot11WIDSDeviceAttackMacaddressListTable 1 }

QtechDot11WIDSDeviceAttackMacaddressListEntry ::=
    SEQUENCE {
        qtechDot11AttackNum              Integer32,
        qtechDot11AttackOper             Integer32,
        qtechDot11AttackMAC              MacAddress,
        qtechDot11AttackInfo             DisplayString
    }

qtechDot11AttackNum OBJECT-TYPE
    SYNTAX      Integer32
    MAX-ACCESS  not-accessible
    STATUS      current
    DESCRIPTION
        "Represents the number of station or AP, and WIDS always
        take it as illegal station or AP."
    ::= { qtechDot11WIDSDeviceAttackMacaddressListEntry 1 }

qtechDot11AttackOper OBJECT-TYPE
    SYNTAX      Integer32
    MAX-ACCESS  read-write
    STATUS      current
    DESCRIPTION
        "Represents the operaton of attack mac address list."
    ::= { qtechDot11WIDSDeviceAttackMacaddressListEntry 2 }

qtechDot11AttackMAC OBJECT-TYPE
    SYNTAX      MacAddress
    MAX-ACCESS  read-write
    STATUS      current
    DESCRIPTION
        "Represents the MAC address of illegal stations."
    ::= { qtechDot11WIDSDeviceAttackMacaddressListEntry 3 }

qtechDot11AttackInfo OBJECT-TYPE
    SYNTAX DisplayString (SIZE (0..255))
    MAX-ACCESS read-only
    STATUS current
    DESCRIPTION
        "Represents the detail of illegal stations."
    ::= { qtechDot11WIDSDeviceAttackMacaddressListEntry 4 }

--*****************************************************************************
--*  qtechDot11WIDSDevicePermitMacaddressListTable Definition
--*****************************************************************************

qtechDot11WIDSDevicePermitMacaddressListTable OBJECT-TYPE
    SYNTAX      SEQUENCE OF QtechDot11WIDSDevicePermitMacaddressListEntry
    MAX-ACCESS  not-accessible
    STATUS      current
    DESCRIPTION
        "The table provides the MAC address list of stations or APs,
        and WIDS always take them as legal stations or APs."
    ::= { qtechDot11WIDSConfigObjects 4 }

qtechDot11WIDSDevicePermitMacaddressListEntry OBJECT-TYPE
    SYNTAX      QtechDot11WIDSDevicePermitMacaddressListEntry
    MAX-ACCESS  not-accessible
    STATUS      current
    DESCRIPTION
        "Each entry contains the MAC address of station or AP,
        and WIDS always take it as legal station or AP."
    INDEX { qtechDot11PermitMACNum }
    ::= { qtechDot11WIDSDevicePermitMacaddressListTable 1 }

QtechDot11WIDSDevicePermitMacaddressListEntry ::=
    SEQUENCE {
        qtechDot11PermitMACNum           Integer32,
        qtechDot11PermitMACOper          Integer32,
        qtechDot11PermitMACAddr          MacAddress
    }

qtechDot11PermitMACNum OBJECT-TYPE
    SYNTAX      Integer32
    MAX-ACCESS  not-accessible
    STATUS      current
    DESCRIPTION
        "Represents the number of station or AP, and WIDS always
        take it as legal station or AP."
    ::= { qtechDot11WIDSDevicePermitMacaddressListEntry 1 }

qtechDot11PermitMACOper OBJECT-TYPE
    SYNTAX      Integer32
    MAX-ACCESS  read-write
    STATUS      current
    DESCRIPTION
        "Represents the operation for mac address list."
    ::= { qtechDot11WIDSDevicePermitMacaddressListEntry 2 }

qtechDot11PermitMACAddr OBJECT-TYPE
    SYNTAX      MacAddress
    MAX-ACCESS  read-write
    STATUS      current
    DESCRIPTION
        "Represents the MAC address of station or AP, and WIDS always
        take it as legal station or AP."
    ::= { qtechDot11WIDSDevicePermitMacaddressListEntry 3 }

-- *****************************************************************************
-- *  qtechDot11WIDSDeviceagingDuration Definition
-- *****************************************************************************

qtechDot11WIDSDeviceagingDuration OBJECT-TYPE
    SYNTAX Integer32
    MAX-ACCESS  read-write
    STATUS      current
    DESCRIPTION
        "Represents the scope of device aging duration."
    ::= { qtechDot11WIDSConfigObjects 5 }


-- *****************************************************************************
-- *  qtechDot11WIDSCountermeasuresMode Definition
-- *****************************************************************************

qtechDot11WIDSCountermeasuresMode OBJECT-TYPE
    SYNTAX Integer32
    MAX-ACCESS  read-write
    STATUS      current
    DESCRIPTION
        "Represents device working countermeasures mode ."
    ::= { qtechDot11WIDSConfigObjects 6 }

-- *****************************************************************************
-- *  qtechDot11WIDSCountermeasureSet Definition
-- *****************************************************************************

qtechDot11WIDSCountermeasureSet OBJECT-TYPE
    SYNTAX Integer32
    MAX-ACCESS  read-write
    STATUS      current
    DESCRIPTION
        "Represents enable or disable device countermeasures."
    ::= { qtechDot11WIDSConfigObjects 7 }


-- *****************************************************************************
-- *  qtechDot11WIDSMode Definition
-- *****************************************************************************

qtechDot11WIDSModeTable OBJECT-TYPE
    SYNTAX SEQUENCE OF QtechDot11WIDSModeEntry
    MAX-ACCESS not-accessible
    STATUS current
    DESCRIPTION
      "Qtech AP device mode"
    ::={ qtechDot11WIDSConfigObjects 8 }

qtechDot11WIDSModeEntry OBJECT-TYPE
    SYNTAX QtechDot11WIDSModeEntry
    MAX-ACCESS not-accessible
    STATUS current
    DESCRIPTION
      "AP MAC is the index of this MIB table."
    INDEX { qtechDot11WIDSAPID }
    ::={ qtechDot11WIDSModeTable 1 }

QtechDot11WIDSModeEntry ::=
    SEQUENCE {
        qtechDot11WIDSAPID                  Integer32,
        qtechDot11WIDSDeviceMode            Integer32
    }

qtechDot11WIDSAPID OBJECT-TYPE
    SYNTAX Integer32
    MAX-ACCESS  not-accessible
    STATUS      current
    DESCRIPTION
        "AP ID."
    ::= { qtechDot11WIDSModeEntry 1 }

qtechDot11WIDSDeviceMode OBJECT-TYPE
    SYNTAX Integer32
    MAX-ACCESS  read-write
    STATUS      current
    DESCRIPTION
        "Represents WIDS device mode."
    ::= { qtechDot11WIDSModeEntry 2 }

--*****************************************************************************
--*  qtechDot11WIDSWhitelistMacaddressListTable Definition
--*****************************************************************************

qtechDot11WIDSWhitelistMacaddressListTable OBJECT-TYPE
    SYNTAX      SEQUENCE OF QtechDot11WIDSWhitelistMacaddressListEntry
    MAX-ACCESS  not-accessible
    STATUS      current
    DESCRIPTION
        "The table provides the MAC address list of stations or APs,
        and WIDS always take them as legal stations or APs."
    ::= { qtechDot11WIDSConfigObjects 9 }

qtechDot11WIDSWhitelistMacaddressListEntry OBJECT-TYPE
    SYNTAX      QtechDot11WIDSWhitelistMacaddressListEntry
    MAX-ACCESS  not-accessible
    STATUS      current
    DESCRIPTION
        "Each entry contains the MAC address of station or AP,
        and WIDS always take it as legal station or AP."
    INDEX { qtechDot11WhitelistNum }
    ::= { qtechDot11WIDSWhitelistMacaddressListTable 1 }

QtechDot11WIDSWhitelistMacaddressListEntry ::=
    SEQUENCE {
        qtechDot11WhitelistNum              Integer32,
        qtechDot11WhitelistOper             Integer32,
        qtechDot11WhitelistMAC              MacAddress
    }

qtechDot11WhitelistNum OBJECT-TYPE
    SYNTAX      Integer32
    MAX-ACCESS  not-accessible
    STATUS      current
    DESCRIPTION
        "Represents the Number of station or AP, and WIDS always
        take it as legal station or AP."
    ::= { qtechDot11WIDSWhitelistMacaddressListEntry 1 }

qtechDot11WhitelistOper OBJECT-TYPE
    SYNTAX      Integer32
    MAX-ACCESS  read-write
    STATUS      current
    DESCRIPTION
        "Represents the operation for this table."
    ::= { qtechDot11WIDSWhitelistMacaddressListEntry 2 }

qtechDot11WhitelistMAC OBJECT-TYPE
    SYNTAX      MacAddress
    MAX-ACCESS  read-write
    STATUS      current
    DESCRIPTION
        "Represents the MAC address of station or AP, and WIDS always
        take it as legal station or AP."
    ::= { qtechDot11WIDSWhitelistMacaddressListEntry 3 }

--*****************************************************************************
--*  qtechDot11WIDSStaticblacklistMacaddressListTable Definition
--*****************************************************************************

qtechDot11WIDSStaticblackListTable OBJECT-TYPE
    SYNTAX      SEQUENCE OF QtechDot11WIDSStaticblackListEntry
    MAX-ACCESS  not-accessible
    STATUS      current
    DESCRIPTION
        "The table provides the MAC address list of stations or APs,
        and WIDS always take them as illegal stations or APs."
    ::= { qtechDot11WIDSConfigObjects 10 }

qtechDot11WIDSStaticblackListEntry OBJECT-TYPE
    SYNTAX      QtechDot11WIDSStaticblackListEntry
    MAX-ACCESS  not-accessible
    STATUS      current
    DESCRIPTION
        "Each entry contains the MAC address of station or AP,
        and WIDS always take it as illegal station or AP."
    INDEX { qtechDot11StaticblacklistNum }
    ::= { qtechDot11WIDSStaticblackListTable 1 }

QtechDot11WIDSStaticblackListEntry ::=
    SEQUENCE {
        qtechDot11StaticblacklistNum              Integer32,
        qtechDot11StaticblacklistOper             Integer32,
        qtechDot11StaticblacklistMAC              MacAddress
    }

qtechDot11StaticblacklistNum OBJECT-TYPE
    SYNTAX      Integer32
    MAX-ACCESS  not-accessible
    STATUS      current
    DESCRIPTION
        "Represents the number of station or AP, and WIDS always
        take it as illegal station or AP."
    ::= { qtechDot11WIDSStaticblackListEntry 1 }

qtechDot11StaticblacklistOper OBJECT-TYPE
    SYNTAX      Integer32
    MAX-ACCESS  read-write
    STATUS      current
    DESCRIPTION
        "Represents the operation for this table."
    ::= { qtechDot11WIDSStaticblackListEntry 2 }

qtechDot11StaticblacklistMAC OBJECT-TYPE
    SYNTAX      MacAddress
    MAX-ACCESS  read-write
    STATUS      current
    DESCRIPTION
        "Represents the MAC address of station or AP, and WIDS always
        take it as illegal station or AP."
    ::= { qtechDot11WIDSStaticblackListEntry 3 }


--*****************************************************************************
--*  qtechDot11WIDSDynamicblacklistEnable Definition
--*****************************************************************************

qtechDot11WIDSDynamicblacklistEnable OBJECT-TYPE
    SYNTAX TruthValue
    MAX-ACCESS  read-write
    STATUS      current
    DESCRIPTION
        "Represents enable or disable devic dynamic blacklist."
    ::= { qtechDot11WIDSConfigObjects 11 }

-- *****************************************************************************
-- *  qtechDot11WIDSDynamicblacklistLifetime Definition
-- *****************************************************************************

qtechDot11WIDSDynamicblacklistLifetime OBJECT-TYPE
    SYNTAX Integer32
    MAX-ACCESS  read-write
    STATUS      current
    DESCRIPTION
        "Represents the scope of dynamic blacklist lifetime."
    ::= { qtechDot11WIDSConfigObjects 12 }

--*****************************************************************************
--*  qtechDot11WIDSAttackDetectionMode Definition
--*****************************************************************************

qtechDot11WIDSAttackDetectionMode OBJECT-TYPE
    SYNTAX Integer32
    MAX-ACCESS  read-write
    STATUS      current
    DESCRIPTION
        "Represents enable which mode of attack-detection to work."
    ::= { qtechDot11WIDSConfigObjects 13 }

--*****************************************************************************
--*  qtechDot11WIDSRogueInfo Definition
--*****************************************************************************
qtechDot11WIDSRogueInfoTable OBJECT-TYPE
    SYNTAX      SEQUENCE OF QtechDot11WIDSRogueInfoEntry
    MAX-ACCESS  not-accessible
    STATUS      current
    DESCRIPTION
        "The table provides Rogue information."
    ::= { qtechDot11WIDSConfigObjects 14 }

qtechDot11WIDSRogueInfoEntry OBJECT-TYPE
    SYNTAX      QtechDot11WIDSRogueInfoEntry
    MAX-ACCESS  not-accessible
    STATUS      current
    DESCRIPTION
        "Each entry contains vlan list for user-isolation."
    INDEX { qtechDot11WIDSRogueInfoNUM, qtechDot11WIDSRogueInfoTYPE}
    ::= { qtechDot11WIDSRogueInfoTable 1 }

QtechDot11WIDSRogueInfoEntry ::=
    SEQUENCE {
        qtechDot11WIDSRogueInfoNUM       Integer32,
        qtechDot11WIDSRogueInfoTYPE      Integer32,
        qtechDot11WIDSRogueInfoOper      Integer32,
        qtechDot11WIDSRogueInfoMAC       MacAddress,
        qtechDot11WIDSRogueInfoString	  DisplayString
    }

qtechDot11WIDSRogueInfoNUM OBJECT-TYPE
    SYNTAX      Integer32
    MAX-ACCESS  not-accessible
    STATUS      current
    DESCRIPTION
        "Each entry contains the number for rogue device."
    ::= { qtechDot11WIDSRogueInfoEntry 1 }

qtechDot11WIDSRogueInfoTYPE OBJECT-TYPE
    SYNTAX      Integer32
    MAX-ACCESS  not-accessible
    STATUS      current
    DESCRIPTION
        "Each entry contains the type for rogue device ."
    ::= { qtechDot11WIDSRogueInfoEntry 2 }

qtechDot11WIDSRogueInfoOper OBJECT-TYPE
    SYNTAX      Integer32
    MAX-ACCESS  read-write
    STATUS      current
    DESCRIPTION
        "Each entry contains the operation for rogue device ."
    ::= { qtechDot11WIDSRogueInfoEntry 3 }

qtechDot11WIDSRogueInfoMAC OBJECT-TYPE
    SYNTAX      MacAddress
    MAX-ACCESS  read-write
    STATUS      current
    DESCRIPTION
        "Each entry contains the mac for rogue device ."
    ::= { qtechDot11WIDSRogueInfoEntry 4 }

qtechDot11WIDSRogueInfoString OBJECT-TYPE
    SYNTAX      DisplayString
    MAX-ACCESS  read-write
    STATUS      current
    DESCRIPTION
        "Each entry contains the info for rogue device."
    ::= { qtechDot11WIDSRogueInfoEntry 5 }

--*****************************************************************************
--*  qtechDot11WIDSUserisolationPermitmaclist Definition
--*****************************************************************************

qtechDot11WIDSPermitmaclistEnableTable OBJECT-TYPE
    SYNTAX      SEQUENCE OF QtechDot11WIDSPermitmaclistEnableEntry
    MAX-ACCESS  not-accessible
    STATUS      current
    DESCRIPTION
        "The table provides vlan Permitmaclist for user-isolation."
    ::= { qtechDot11WIDSConfigObjects 15 }

qtechDot11WIDSPermitmaclistEnableEntry OBJECT-TYPE
    SYNTAX      QtechDot11WIDSPermitmaclistEnableEntry
    MAX-ACCESS  not-accessible
    STATUS      current
    DESCRIPTION
        "Each entry contains vlan Permitmaclist for user-isolation."
    INDEX { qtechDot11WIDSEnableVlanPermitmaclistNum }
    ::= { qtechDot11WIDSPermitmaclistEnableTable 1 }

QtechDot11WIDSPermitmaclistEnableEntry ::=
    SEQUENCE {
        qtechDot11WIDSEnableVlanPermitmaclistNum  Integer32,
        qtechDot11WIDSEnableVlanPermitmaclistOper Integer32,
        qtechDot11WIDSEnableVlanPermitmaclist     MacAddress
    }

qtechDot11WIDSEnableVlanPermitmaclistNum OBJECT-TYPE
    SYNTAX      Integer32
    MAX-ACCESS  not-accessible
    STATUS      current
    DESCRIPTION
        "Each entry contains vlan Permitmaclist number for user-isolation."
    ::= { qtechDot11WIDSPermitmaclistEnableEntry 1 }

qtechDot11WIDSEnableVlanPermitmaclistOper OBJECT-TYPE
    SYNTAX      Integer32
    MAX-ACCESS  read-write
    STATUS      current
    DESCRIPTION
        "Each entry contains vlan Permitmaclist operation for user-isolation."
    ::= { qtechDot11WIDSPermitmaclistEnableEntry 2 }

qtechDot11WIDSEnableVlanPermitmaclist OBJECT-TYPE
    SYNTAX      MacAddress
    MAX-ACCESS  read-write
    STATUS      current
    DESCRIPTION
        "Each entry contains vlan Permitmaclist for user-isolation."
    ::= { qtechDot11WIDSPermitmaclistEnableEntry 3 }

--*****************************************************************************
--*  qtechDot11WIDSResetStatistics Definition
--*****************************************************************************

qtechDot11WIDSResetStatistics    OBJECT-TYPE
  SYNTAX                  TruthValue
  MAX-ACCESS              read-write
  STATUS                  current
  DESCRIPTION
  "This attribute set to clears all the statistics of attack detection information."
  ::= { qtechDot11WIDSConfigObjects  18 }

--*****************************************************************************
--*  qtechDot11WIDSResetRoguehistoryStatistics Definition
--*****************************************************************************

qtechDot11WIDSResetRoguehistoryStatistics    OBJECT-TYPE
  SYNTAX                  Integer32
  MAX-ACCESS              read-write
  STATUS                  current
  DESCRIPTION
  "This attribute set to clears all the statistics of rogue information."
  ::= { qtechDot11WIDSConfigObjects  19 }

--*****************************************************************************
--*  qtechDot11WIDSResethistory Definition
--*****************************************************************************

qtechDot11WIDSResethistory    OBJECT-TYPE
  SYNTAX                  Integer32
  MAX-ACCESS              read-write
  STATUS                  current
  DESCRIPTION
  "This attribute set to clears the history."
  ::= { qtechDot11WIDSConfigObjects  20 }

--*****************************************************************************
--*  qtechDot11WIDSResetDynamicBlacklisttable Definition
--*****************************************************************************

qtechDot11WIDSResetDynamicBlacklistTable OBJECT-TYPE
    SYNTAX      SEQUENCE OF QtechDot11WIDSResetDynamicBlacklistEntry
    MAX-ACCESS  not-accessible
    STATUS      current
    DESCRIPTION
        "The table descrips information about reseting wlan dynamic-blacklist."
    ::= { qtechDot11WIDSConfigObjects 21 }

qtechDot11WIDSResetDynamicBlacklistEntry OBJECT-TYPE
    SYNTAX      QtechDot11WIDSResetDynamicBlacklistEntry
    MAX-ACCESS  not-accessible
    STATUS      current
    DESCRIPTION
        "Each entry contains information about reseting wlan dynamic-blacklist."
    INDEX { qtechDot11WIDSResetDynamicBlacklistMac }
    ::= { qtechDot11WIDSResetDynamicBlacklistTable 1 }

QtechDot11WIDSResetDynamicBlacklistEntry ::=
    SEQUENCE {
        qtechDot11WIDSResetDynamicBlacklistMac  MacAddress,
        qtechDot11WIDSResetDynamicBlacklistType Integer32
    }

qtechDot11WIDSResetDynamicBlacklistMac OBJECT-TYPE
    SYNTAX      MacAddress
    MAX-ACCESS  not-accessible
    STATUS      current
    DESCRIPTION
        "Each entry contains Macaddress."
    ::= { qtechDot11WIDSResetDynamicBlacklistEntry 1 }

qtechDot11WIDSResetDynamicBlacklistType OBJECT-TYPE
    SYNTAX      Integer32
    MAX-ACCESS  read-write
    STATUS      current
    DESCRIPTION
        "Each entry contains Macaddress."
    ::= { qtechDot11WIDSResetDynamicBlacklistEntry 2 }


--*****************************************************************************
--*  qtechDot11WIDResetUserisolationStatistics Definition
--*****************************************************************************

qtechDot11WIDResetUserisolationStatistics OBJECT-TYPE
    SYNTAX Integer32
    MAX-ACCESS  read-write
    STATUS      current
    DESCRIPTION
        "Represents information about which vlanlist to reset user-isolation statistics."
    ::= { qtechDot11WIDSConfigObjects 22 }


--*****************************************************************************
--*  qtechDot11WIDSShowDot11IdsAttacklist Definition
--*****************************************************************************

qtechDot11WIDSShowDot11IdsAttacklistTable OBJECT-TYPE
    SYNTAX      SEQUENCE OF QtechDot11WIDSShowDot11IdsAttacklistEntry
    MAX-ACCESS  not-accessible
    STATUS      current
    DESCRIPTION
        "The table descrips information about reseting wlan dynamic-blacklist."
    ::= { qtechDot11WIDSDetectObjects 1 }

qtechDot11WIDSShowDot11IdsAttacklistEntry OBJECT-TYPE
    SYNTAX      QtechDot11WIDSShowDot11IdsAttacklistEntry
    MAX-ACCESS  not-accessible
    STATUS      current
    DESCRIPTION
        "Each entry contains information about reseting wlan dynamic-blacklist."
    INDEX { qtechDot11WIDSShowDot11IdsAttacklistNum }
    ::= { qtechDot11WIDSShowDot11IdsAttacklistTable 1 }

QtechDot11WIDSShowDot11IdsAttacklistEntry ::=
    SEQUENCE {
        qtechDot11WIDSShowDot11IdsAttacklistNum  INTEGER,
        qtechDot11WIDSShowDot11IdsAttacklistOper INTEGER,
        qtechDot11WIDSShowDot11IdsAttacklistMac  MacAddress,
        qtechDot11WIDSShowDot11IdsAttacklistInfo DisplayString
    }

qtechDot11WIDSShowDot11IdsAttacklistNum OBJECT-TYPE
    SYNTAX      INTEGER
    MAX-ACCESS  not-accessible
    STATUS      current
    DESCRIPTION
        "Each entry contains Macaddress."
    ::= { qtechDot11WIDSShowDot11IdsAttacklistEntry 1 }

qtechDot11WIDSShowDot11IdsAttacklistOper OBJECT-TYPE
    SYNTAX      INTEGER
    MAX-ACCESS  read-write
    STATUS      current
    DESCRIPTION
        "Each entry contains operation."
    ::= { qtechDot11WIDSShowDot11IdsAttacklistEntry 2 }

qtechDot11WIDSShowDot11IdsAttacklistMac OBJECT-TYPE
    SYNTAX      MacAddress
    MAX-ACCESS  read-write
    STATUS      current
    DESCRIPTION
        "Each entry contains Macaddress."
    ::= { qtechDot11WIDSShowDot11IdsAttacklistEntry 3 }

qtechDot11WIDSShowDot11IdsAttacklistInfo OBJECT-TYPE
    SYNTAX      DisplayString (SIZE (0..255))
    MAX-ACCESS  read-write
    STATUS      current
    DESCRIPTION
         "Each entry contains info."
    ::= { qtechDot11WIDSShowDot11IdsAttacklistEntry 4 }

--*****************************************************************************
--*  qtechDot11WIDUserisolation Definition
--*****************************************************************************
qtechDot11WIDUserisolationAC OBJECT-TYPE
    SYNTAX Integer32
    MAX-ACCESS  read-write
    STATUS      current
    DESCRIPTION
        "Represents information about user-isolation for AC."
    ::= { qtechDot11WIDSConfigObjects 23 }

qtechDot11WIDUserisolationAP OBJECT-TYPE
    SYNTAX Integer32
    MAX-ACCESS  read-write
    STATUS      current
    DESCRIPTION
        "Represents information about user-isolation for AP."
    ::= { qtechDot11WIDSConfigObjects 24 }

--*****************************************************************************
--*  qtechDot11WIDSShowStatics Definition
--*****************************************************************************

qtechDot11WIDSShowStaticsTable OBJECT-TYPE
    SYNTAX      SEQUENCE OF QtechDot11WIDSShowStaticsEntry
    MAX-ACCESS  not-accessible
    STATUS      current
    DESCRIPTION
        "The table contains statics."
    ::= { qtechDot11WIDSConfigObjects 25 }

qtechDot11WIDSShowStaticsEntry OBJECT-TYPE
    SYNTAX      QtechDot11WIDSShowStaticsEntry
    MAX-ACCESS  not-accessible
    STATUS      current
    DESCRIPTION
        "The table contains statics."
    INDEX { qtechDot11WIDSShowStaticsNum }
    ::= { qtechDot11WIDSShowStaticsTable 1 }

QtechDot11WIDSShowStaticsEntry ::=
    SEQUENCE {
        qtechDot11WIDSShowStaticsNum  INTEGER,
        qtechDot11WIDSShowStaticsOper INTEGER,
        qtechDot11WIDSShowStaticsMac  MacAddress,
        qtechDot11WIDSShowStaticsInfo DisplayString
    }

qtechDot11WIDSShowStaticsNum OBJECT-TYPE
    SYNTAX      INTEGER
    MAX-ACCESS  not-accessible
    STATUS      current
    DESCRIPTION
        "Each entry contains Macaddress."
    ::= { qtechDot11WIDSShowStaticsEntry 1 }

qtechDot11WIDSShowStaticsOper OBJECT-TYPE
    SYNTAX      INTEGER
    MAX-ACCESS  read-write
    STATUS      current
    DESCRIPTION
        "Each entry contains operation."
    ::= { qtechDot11WIDSShowStaticsEntry 2 }

qtechDot11WIDSShowStaticsMac OBJECT-TYPE
    SYNTAX      MacAddress
    MAX-ACCESS  read-write
    STATUS      current
    DESCRIPTION
        "Each entry contains Macaddress."
    ::= { qtechDot11WIDSShowStaticsEntry 3 }

qtechDot11WIDSShowStaticsInfo OBJECT-TYPE
    SYNTAX      DisplayString (SIZE (0..255))
    MAX-ACCESS  read-write
    STATUS      current
    DESCRIPTION
        "Each entry contains info."
    ::= { qtechDot11WIDSShowStaticsEntry 4 }
--********************************************************************
--*
--********************************************************************
qtechDot11WIDSAssociationFailureTotalTimes  OBJECT-TYPE
    SYNTAX      INTEGER
    MAX-ACCESS  read-only
    STATUS      current
    DESCRIPTION
        " The total times the association fails."
    ::= { qtechDot11WIDSConfigObjects 26 }
--********************************************************************
--*
--********************************************************************


--**************************************************
--* qtechDot11WIDSSuspiciousAPInfoTable begins
--**************************************************
qtechDot11WIDSSuspiciousAPInfoTable OBJECT-TYPE
    SYNTAX SEQUENCE OF QtechDot11WIDSSuspiciousAPInfoEntry
    MAX-ACCESS not-accessible
    STATUS current
    DESCRIPTION
      "The table includes the information of the suspicious ap detected."
    ::={ qtechDot11WIDSConfigObjects 27 }

qtechDot11WIDSSuspiciousAPInfoEntry OBJECT-TYPE
    SYNTAX QtechDot11WIDSSuspiciousAPInfoEntry
    MAX-ACCESS not-accessible
    STATUS current
    DESCRIPTION
      "The entry of the qtechDot11WIDSSuspiciousAPInfoTable table."
    INDEX { qtechDot11WIDSSuspiciousAPBSS }
    ::={ qtechDot11WIDSSuspiciousAPInfoTable 1 }
    
QtechDot11WIDSSuspiciousAPInfoEntry ::=
    SEQUENCE {
        qtechDot11WIDSSuspiciousAPBSS                  MacAddress,
        qtechDot11WIDSSuspiciousAPCount                INTEGER,
        qtechDot11WIDSMomentFirstTimeDetectedSusAP     TimeTicks,
        qtechDot11WIDSMomentLastTimeDetectedSusAP      TimeTicks,
        qtechDot11WIDSSuspiciousAPSSID                 DisplayString,
        qtechDot11WIDSSuspiciousAPMaxSignalStrength    INTEGER,
        qtechDot11WIDSSuspiciousAPUsingChannel         INTEGER,
        qtechDot11WIDSSuspiciousAPFrameEncrption       INTEGER,
        qtechDot11WIDSSuspiciousAPNeedsDealingTag      TruthValue,
        qtechDot11WIDSSuspiciousAPIgnoredTag           TruthValue
    }

qtechDot11WIDSSuspiciousAPBSS OBJECT-TYPE
    SYNTAX  MacAddress
    MAX-ACCESS  read-only
    STATUS      current
    DESCRIPTION
        " The BSS MAC of the Suspicious AP."
    ::= { qtechDot11WIDSSuspiciousAPInfoEntry 1 }

qtechDot11WIDSSuspiciousAPCount OBJECT-TYPE
    SYNTAX  INTEGER
    MAX-ACCESS  read-only
    STATUS      current
    DESCRIPTION
        " The count of the Suspicious AP."
    ::= { qtechDot11WIDSSuspiciousAPInfoEntry 2 }

qtechDot11WIDSMomentFirstTimeDetectedSusAP OBJECT-TYPE
    SYNTAX  TimeTicks
    MAX-ACCESS  read-only
    STATUS      current
    DESCRIPTION
        " The moment when the AP is detected as the Suspicious AP at the first time."
    ::= { qtechDot11WIDSSuspiciousAPInfoEntry 3 }

qtechDot11WIDSMomentLastTimeDetectedSusAP OBJECT-TYPE
    SYNTAX  TimeTicks
    MAX-ACCESS  read-only
    STATUS      current
    DESCRIPTION
        " The moment when the AP is detected as the Suspicious AP at the last time."
    ::= { qtechDot11WIDSSuspiciousAPInfoEntry 4 }

qtechDot11WIDSSuspiciousAPSSID OBJECT-TYPE
    SYNTAX  DisplayString
    MAX-ACCESS  read-only
    STATUS      current
    DESCRIPTION
        " The SSID of the Suspicious AP."
    ::= { qtechDot11WIDSSuspiciousAPInfoEntry 5 }

qtechDot11WIDSSuspiciousAPMaxSignalStrength OBJECT-TYPE
    SYNTAX  INTEGER
    MAX-ACCESS  read-only
    STATUS      current
    DESCRIPTION
        " The max signal strength of the Suspicious AP."
    ::= { qtechDot11WIDSSuspiciousAPInfoEntry 6 }

qtechDot11WIDSSuspiciousAPUsingChannel OBJECT-TYPE
    SYNTAX  INTEGER
    MAX-ACCESS  read-only
    STATUS      current
    DESCRIPTION
        " The channel the Suspicious AP is in."
    ::= { qtechDot11WIDSSuspiciousAPInfoEntry 7 }

qtechDot11WIDSSuspiciousAPFrameEncrption OBJECT-TYPE
    SYNTAX  INTEGER
    MAX-ACCESS  read-only
    STATUS      current
    DESCRIPTION
        " The frame encrption of the Suspicious AP."
    ::= { qtechDot11WIDSSuspiciousAPInfoEntry 8 }

qtechDot11WIDSSuspiciousAPNeedsDealingTag OBJECT-TYPE
    SYNTAX  TruthValue
    MAX-ACCESS  read-only
    STATUS      current
    DESCRIPTION
        " The tag telling whether it needs to deal the Suspicious AP."
    ::= { qtechDot11WIDSSuspiciousAPInfoEntry 9 }

qtechDot11WIDSSuspiciousAPIgnoredTag OBJECT-TYPE
    SYNTAX  TruthValue
    MAX-ACCESS  read-only
    STATUS      current
    DESCRIPTION
        " The tag telling whether to ignore the Suspicious AP."
    ::= { qtechDot11WIDSSuspiciousAPInfoEntry 10 }

--**************************************************
--* qtechDot11WIDSSuspiciousAPInfoTable begins
--**************************************************    
    
--**************************************************
--* qtechDot11WIDSSuspiciousSTAInfoTable begins
--**************************************************

qtechDot11WIDSSuspiciousSTAInfoTable OBJECT-TYPE
    SYNTAX SEQUENCE OF QtechDot11WIDSSuspiciousSTAInfoEntry
    MAX-ACCESS not-accessible
    STATUS current
    DESCRIPTION
      "The table includes the information of the suspicious STA detected."
    ::={ qtechDot11WIDSConfigObjects 28 }

qtechDot11WIDSSuspiciousSTAInfoEntry OBJECT-TYPE
    SYNTAX QtechDot11WIDSSuspiciousSTAInfoEntry
    MAX-ACCESS not-accessible
    STATUS current
    DESCRIPTION
      "The entry of the qtechDot11WIDSSuspiciousSTAInfoTable table."
    INDEX { qtechDot11WIDSSuspiciousSTAMAC }
    ::={ qtechDot11WIDSSuspiciousSTAInfoTable 1 }
    
QtechDot11WIDSSuspiciousSTAInfoEntry ::=
    SEQUENCE {        
        qtechDot11WIDSSuspiciousSTAMAC                 MacAddress,
        qtechDot11WIDSAPCountDetectingSuspiciousSTA    INTEGER,
        qtechDot11WIDSMomentFirstTimeDetectedSusSTA    TimeTicks,
        qtechDot11WIDSMomentLastTimeDetectedSusSTA     TimeTicks,
        qtechDot11WIDSBSSIDSuspiciousSTAAccessing      MacAddress,
        qtechDot11WIDSSuspiciousSTAMaxSignalStrength   INTEGER,
        qtechDot11WIDSSuspiciousSTAUsingChannel        INTEGER,
        qtechDot11WIDSSuspiciousSTAWorksInAdhocMode    TruthValue,
        qtechDot11WIDSSuspiciousSTANeedsDealingTag     TruthValue,
        qtechDot11WIDSSuspiciousSTAIgnoredTag          TruthValue
    }

qtechDot11WIDSSuspiciousSTAMAC OBJECT-TYPE
    SYNTAX  MacAddress
    MAX-ACCESS  read-only
    STATUS      current
    DESCRIPTION
        " The MAC of the the Suspicious STA."
    ::= { qtechDot11WIDSSuspiciousSTAInfoEntry 1 }

qtechDot11WIDSAPCountDetectingSuspiciousSTA OBJECT-TYPE
    SYNTAX  INTEGER
    MAX-ACCESS  read-only
    STATUS      current
    DESCRIPTION
        " The AP count which is detecting the Suspicious STA."
    ::= { qtechDot11WIDSSuspiciousSTAInfoEntry 2 }

qtechDot11WIDSMomentFirstTimeDetectedSusSTA OBJECT-TYPE
    SYNTAX  TimeTicks
    MAX-ACCESS  read-only
    STATUS      current
    DESCRIPTION
        " The moment when the STA is detected as the Suspicious STA at the first time."
    ::= { qtechDot11WIDSSuspiciousSTAInfoEntry 3 }

qtechDot11WIDSMomentLastTimeDetectedSusSTA OBJECT-TYPE
    SYNTAX  TimeTicks
    MAX-ACCESS  read-only
    STATUS      current
    DESCRIPTION
        " The moment when the AP is detected as the Suspicious AP at the last time."
    ::= { qtechDot11WIDSSuspiciousSTAInfoEntry 4 }

qtechDot11WIDSBSSIDSuspiciousSTAAccessing OBJECT-TYPE
    SYNTAX  MacAddress
    MAX-ACCESS  read-only
    STATUS      current
    DESCRIPTION
        " The BSSID which the the Suspicious STA is trying to access."
    ::= { qtechDot11WIDSSuspiciousSTAInfoEntry 5 }

qtechDot11WIDSSuspiciousSTAMaxSignalStrength OBJECT-TYPE
    SYNTAX  INTEGER
    MAX-ACCESS  read-only
    STATUS      current
    DESCRIPTION
        " The max signal strength of the Suspicious STA."
    ::= { qtechDot11WIDSSuspiciousSTAInfoEntry 6 }

qtechDot11WIDSSuspiciousSTAUsingChannel OBJECT-TYPE
    SYNTAX  INTEGER
    MAX-ACCESS  read-only
    STATUS      current
    DESCRIPTION
        " The channel the Suspicious sta is in."
    ::= { qtechDot11WIDSSuspiciousSTAInfoEntry 7 }

qtechDot11WIDSSuspiciousSTAWorksInAdhocMode OBJECT-TYPE
    SYNTAX  TruthValue
    MAX-ACCESS  read-only
    STATUS      current
    DESCRIPTION
        " The tag whether the Suspicious STA is working in the Ad hoc mode."
    ::= { qtechDot11WIDSSuspiciousSTAInfoEntry 8 }


qtechDot11WIDSSuspiciousSTANeedsDealingTag OBJECT-TYPE
    SYNTAX  TruthValue
    MAX-ACCESS  read-only
    STATUS      current
    DESCRIPTION
        " The tag telling whether it needs to deal the Suspicious STA."
    ::= { qtechDot11WIDSSuspiciousSTAInfoEntry 9 }

qtechDot11WIDSSuspiciousSTAIgnoredTag OBJECT-TYPE
    SYNTAX  TruthValue
    MAX-ACCESS  read-write
    STATUS      current
    DESCRIPTION
        " The tag telling whether to ignore the Suspicious STA."
    ::= { qtechDot11WIDSSuspiciousSTAInfoEntry 10 }

--**************************************************
--* qtechDot11WIDSSuspiciousSTAInfoTable ends
--**************************************************

--*******************************************************************
--* traps begin here
--*******************************************************************
--*************************************************************
--*************************************************************
qtechDot11WIDSTraps OBJECT IDENTIFIER ::= { qtechDot11WIDSMIB 0}
qtechDot11WIDSTrapsObjects OBJECT IDENTIFIER ::= { qtechDot11WIDSMIB 3 }

qtechDot11WIDSWirelessUserConnect NOTIFICATION-TYPE
    OBJECTS {
        qtechDot11WIDSSTAMAC,
        qtechDot11WIDSAPBSSID,
        qtechDot11WIDSInformation,
        qtechDot11WIDSextinfo
    }
    STATUS  current
    DESCRIPTION
            "trap of 802.11 connection, tell the receiver information
             as follow: STAMAC, BSSID, Information need."
    ::= { qtechDot11WIDSTraps 1 }
    
qtechDot11WIDSWirelessUserDisconnect NOTIFICATION-TYPE
    OBJECTS {
        qtechDot11WIDSSTAMAC,
        qtechDot11WIDSAPBSSID,
        qtechDot11WIDSInformation,
        qtechDot11WIDSextinfo
    }
    STATUS  current
    DESCRIPTION
            "trap of 802.11 disconnection, tell the receiver information
             as follow: STAMAC, BSSID, Information need."
    ::= { qtechDot11WIDSTraps 2 }

qtechDot11WIDSWirelessUserReauthentication NOTIFICATION-TYPE
    OBJECTS {
        qtechDot11WIDSSTAMAC,
        qtechDot11WIDSAPBSSID,
        qtechDot11WIDSInformation,
        qtechDot11WIDSextinfo
    }
    STATUS  current
    DESCRIPTION
            "trap of 802.11 re-authentication, tell the receiver information
             as follow: STAMAC, BSSID, Information need."
    ::= { qtechDot11WIDSTraps 3 }
    
qtechDot11WIDSWirelessUserAuthenticationFailure NOTIFICATION-TYPE
    OBJECTS {
        qtechDot11WIDSSTAMAC,
        qtechDot11WIDSAPBSSID,
        qtechDot11WIDSInformation,
        qtechDot11WIDSextinfo
    }
    STATUS  current
    DESCRIPTION
            "trap of the failure of802.11 authentication, tell the receiver 
             information as follow: STAMAC, BSSID, Information need."
    ::= { qtechDot11WIDSTraps 4 }

qtechDot11WIDSWirelessUserConnectFailure NOTIFICATION-TYPE
    OBJECTS {
        qtechDot11WIDSSTAMAC,
        qtechDot11WIDSAPBSSID,
        qtechDot11WIDSInformation,
        qtechDot11WIDSextinfo
    }
    STATUS  current
    DESCRIPTION
            "trap of the failure of 802.11 connection, tell the receiver information
             as follow: STAMAC, BSSID, Information need."
    ::= { qtechDot11WIDSTraps 5 }
  
--*************************************************************************
--*************************************************************************
qtechDot11WIDSDevice NOTIFICATION-TYPE
    OBJECTS {
        qtechDot11WIDSDeviceInfoNUM,
        qtechDot11WIDSDeviceInfoTYPE,
        qtechDot11WIDSDeviceInfoOper,
        qtechDot11WIDSDeviceInfoMAC,
        qtechDot11WIDSDeviceInfoString
    }
    STATUS  current
    DESCRIPTION
            "The information of an event of a device, which can be a rogue ap,  a debious ap,
            a friendly ap, a rogue ad hoc, a debious ad hoc, a friendly ad hoc, a rogue sta,
            a debious sta, a friendly sta or an attacking device."
    ::= { qtechDot11WIDSTraps 6 } 
    
qtechDot11WIDSSuspiciousDeviceTrap NOTIFICATION-TYPE
    OBJECTS {
        qtechDot11WIDSSuspiciousDeviceMac,
        qtechDot11WIDSSuspiciousDeviceExtensionInfo
    }
    STATUS  current
    DESCRIPTION
            " This trap will be sent at once when detecting an suspicious ap or sta."
    ::= { qtechDot11WIDSTraps 7 }

qtechDot11WIDSUnauthorizedSSIDTrap NOTIFICATION-TYPE
    OBJECTS {
        qtechDot11WIDSUnauthorizedSSID,
        qtechDot11WIDSSUnauthorizedSSIDExtensionInfo
    }
    STATUS  current
    DESCRIPTION
            " This trap will be sent at once when detecting an unauthorized SSID
            which is not in the permitted ssid list."
    ::= { qtechDot11WIDSTraps 8 }

qtechDot11WIDSDetectingAttackTrap NOTIFICATION-TYPE
    OBJECTS {
        qtechDot11WIDSAttackingDeviceMac,
        qtechDot11WIDSAttackType,
        qtechDot11WIDSAttackExtensionInfo
    }
    STATUS  current
    DESCRIPTION
            " This trap will be sent at once when detecting an attack, such as flood
            attack, spoof attack, and so on."
    ::= { qtechDot11WIDSTraps 9 }

qtechDot11WIDSSTAMAC OBJECT-TYPE
    SYNTAX      MacAddress
    MAX-ACCESS  read-write
    STATUS      current
    DESCRIPTION
        "MAC address of the STA."
    ::= { qtechDot11WIDSTrapsObjects 1 }

qtechDot11WIDSAPBSSID OBJECT-TYPE
    SYNTAX      DisplayString(SIZE (0..255))
    MAX-ACCESS  read-write
    STATUS      current
    DESCRIPTION
        "BSSID of AP."
    ::= { qtechDot11WIDSTrapsObjects 2 }

qtechDot11WIDSInformation OBJECT-TYPE
    SYNTAX      DisplayString(SIZE (0..255))
    MAX-ACCESS  read-write
    STATUS      current
    DESCRIPTION
        "Information to be commited."
    ::= { qtechDot11WIDSTrapsObjects 3 }

qtechDot11WIDSextinfo OBJECT-TYPE
    SYNTAX      DisplayString(SIZE (0..255))
    MAX-ACCESS  read-write
    STATUS      current
    DESCRIPTION
        "Extensive information to be commited."
    ::= { qtechDot11WIDSTrapsObjects 4 }

qtechDot11WIDSDeviceInfoNUM OBJECT-TYPE
    SYNTAX      Integer32
    MAX-ACCESS  read-write
    STATUS      current
    DESCRIPTION
        "Each entry contains the number for rogue device."
    ::= { qtechDot11WIDSTrapsObjects 5 }

qtechDot11WIDSDeviceInfoTYPE OBJECT-TYPE
    SYNTAX      Integer32
    MAX-ACCESS  read-write
    STATUS      current
    DESCRIPTION
        "Each entry contains the type for rogue device ."
    ::= { qtechDot11WIDSTrapsObjects 6 }

qtechDot11WIDSDeviceInfoOper OBJECT-TYPE
    SYNTAX      Integer32
    MAX-ACCESS  read-write
    STATUS      current
    DESCRIPTION
        "Each entry contains the operation for rogue device ."
    ::= { qtechDot11WIDSTrapsObjects 7 }

qtechDot11WIDSDeviceInfoMAC OBJECT-TYPE
    SYNTAX      MacAddress
    MAX-ACCESS  read-write
    STATUS      current
    DESCRIPTION
        "Each entry contains the mac for rogue device ."
    ::= { qtechDot11WIDSTrapsObjects 8 }

qtechDot11WIDSDeviceInfoString OBJECT-TYPE
    SYNTAX      DisplayString (SIZE (0..255))
    MAX-ACCESS  read-write
    STATUS      current
    DESCRIPTION
        "Each entry contains the info for rogue device."
    ::= { qtechDot11WIDSTrapsObjects 9 }     
    
qtechDot11WIDSSuspiciousDeviceMac OBJECT-TYPE
    SYNTAX      MacAddress
    MAX-ACCESS  read-write
    STATUS      current
    DESCRIPTION
        " The macaddress of the suspicious device."
    ::= { qtechDot11WIDSTrapsObjects 10 }

qtechDot11WIDSSuspiciousDeviceExtensionInfo OBJECT-TYPE
    SYNTAX      DisplayString
    MAX-ACCESS  read-write
    STATUS      current
    DESCRIPTION
        " The information left for the future extension."
    ::= { qtechDot11WIDSTrapsObjects 11 }

qtechDot11WIDSUnauthorizedSSID OBJECT-TYPE
    SYNTAX      DisplayString
    MAX-ACCESS  read-write
    STATUS      current
    DESCRIPTION
        " The macaddress of the suspicious device."
    ::= { qtechDot11WIDSTrapsObjects 12 }

qtechDot11WIDSSUnauthorizedSSIDExtensionInfo OBJECT-TYPE
    SYNTAX      DisplayString
    MAX-ACCESS  read-write
    STATUS      current
    DESCRIPTION
        " The information left for the future extension."
    ::= { qtechDot11WIDSTrapsObjects 13 }

qtechDot11WIDSAttackingDeviceMac OBJECT-TYPE
    SYNTAX      MacAddress
    MAX-ACCESS  read-write
    STATUS      current
    DESCRIPTION
        " The macaddress of the suspicious device."
    ::= { qtechDot11WIDSTrapsObjects 14 }

qtechDot11WIDSAttackType OBJECT-TYPE
    SYNTAX      INTEGER
    MAX-ACCESS  read-write
    STATUS      current
    DESCRIPTION
        " The information left for the future extension."
    ::= { qtechDot11WIDSTrapsObjects 15 }
    
qtechDot11WIDSAttackExtensionInfo OBJECT-TYPE
    SYNTAX      DisplayString
    MAX-ACCESS  read-write
    STATUS      current
    DESCRIPTION
        " The information left for the future extension."
    ::= { qtechDot11WIDSTrapsObjects 16 }

--*******************************************************************
--* traps end here
--*******************************************************************

--********************************************************************
--*    Compliance statements
--********************************************************************
qtechDot11WIDSMIBConform OBJECT IDENTIFIER ::= { qtechDot11WIDSMIB 4 }

qtechDot11WIDSMIBCompliances OBJECT IDENTIFIER ::= { qtechDot11WIDSMIBConform 1 }

qtechDot11WIDSMIBGroups      OBJECT IDENTIFIER ::= { qtechDot11WIDSMIBConform 2 }

qtechDot11WIDSMIBCompliance MODULE-COMPLIANCE
    STATUS  current
    DESCRIPTION
        "The compliance statement for entities which implement
        the dot11 wids module of Qtech Ac device Manager"
    MODULE
    MANDATORY-GROUPS {
        qtechDot11WIDSMIBGroup
    }
    ::= { qtechDot11WIDSMIBCompliances 1 }

--********************************************************************
--*    Units of conformance
--********************************************************************

qtechDot11WIDSMIBGroup OBJECT-GROUP
    OBJECTS {
        qtechDot11VendorOper,
        qtechDot11VendorName,
        qtechDot11PermitOper,
        qtechDot11PermitSSID,
        qtechDot11AttackOper,
        qtechDot11AttackMAC,
        qtechDot11AttackInfo,
        qtechDot11PermitMACOper,
        qtechDot11PermitMACAddr,
        qtechDot11WIDSDeviceagingDuration,
        qtechDot11WIDSCountermeasuresMode,
        qtechDot11WIDSCountermeasureSet,
        qtechDot11WIDSDeviceMode,
        qtechDot11WhitelistOper,
        qtechDot11WhitelistMAC,
        qtechDot11StaticblacklistOper,
        qtechDot11StaticblacklistMAC,
        qtechDot11WIDSDynamicblacklistEnable,
        qtechDot11WIDSDynamicblacklistLifetime,
        qtechDot11WIDSAttackDetectionMode,
        qtechDot11WIDSRogueInfoOper,
        qtechDot11WIDSRogueInfoMAC,
        qtechDot11WIDSRogueInfoString,
        qtechDot11WIDSEnableVlanPermitmaclistOper,
        qtechDot11WIDSEnableVlanPermitmaclist,
        qtechDot11WIDSResetStatistics,
        qtechDot11WIDSResetRoguehistoryStatistics,
        qtechDot11WIDSResethistory,
        qtechDot11WIDSResetDynamicBlacklistType,
        qtechDot11WIDResetUserisolationStatistics,
        qtechDot11WIDSShowDot11IdsAttacklistOper,
        qtechDot11WIDSShowDot11IdsAttacklistMac,
        qtechDot11WIDSShowDot11IdsAttacklistInfo,
        qtechDot11WIDUserisolationAC,
        qtechDot11WIDUserisolationAP,
        qtechDot11WIDSShowStaticsOper,
        qtechDot11WIDSShowStaticsMac,
        qtechDot11WIDSShowStaticsInfo,
        qtechDot11WIDSAssociationFailureTotalTimes,
        qtechDot11WIDSSuspiciousAPCount,
        qtechDot11WIDSMomentFirstTimeDetectedSusAP,
        qtechDot11WIDSMomentLastTimeDetectedSusAP,
        qtechDot11WIDSSuspiciousAPSSID,
        qtechDot11WIDSSuspiciousAPMaxSignalStrength,
        qtechDot11WIDSSuspiciousAPUsingChannel,
        qtechDot11WIDSSuspiciousAPFrameEncrption,
        qtechDot11WIDSSuspiciousAPNeedsDealingTag,
        qtechDot11WIDSSuspiciousAPIgnoredTag,
        qtechDot11WIDSAPCountDetectingSuspiciousSTA,
        qtechDot11WIDSMomentFirstTimeDetectedSusSTA,
        qtechDot11WIDSMomentLastTimeDetectedSusSTA,
        qtechDot11WIDSBSSIDSuspiciousSTAAccessing,
        qtechDot11WIDSSuspiciousSTAMaxSignalStrength,
        qtechDot11WIDSSuspiciousSTAUsingChannel,
        qtechDot11WIDSSuspiciousSTAWorksInAdhocMode,
        qtechDot11WIDSSuspiciousSTANeedsDealingTag,
        qtechDot11WIDSSuspiciousSTAIgnoredTag,
        qtechDot11WIDSSuspiciousDeviceMac,
        qtechDot11WIDSSuspiciousDeviceExtensionInfo,
        qtechDot11WIDSUnauthorizedSSID,
        qtechDot11WIDSSUnauthorizedSSIDExtensionInfo,
        qtechDot11WIDSAttackingDeviceMac,
        qtechDot11WIDSAttackType,
        qtechDot11WIDSAttackExtensionInfo,        
        qtechDot11WIDSSTAMAC,
        qtechDot11WIDSAPBSSID,
        qtechDot11WIDSInformation,
        qtechDot11WIDSextinfo,        
        qtechDot11WIDSDeviceInfoNUM,
        qtechDot11WIDSDeviceInfoTYPE,
        qtechDot11WIDSDeviceInfoOper,
        qtechDot11WIDSDeviceInfoMAC,
        qtechDot11WIDSDeviceInfoString
    }
    STATUS     current
    DESCRIPTION
            "This collection of objects represents the
             dot11 wids private MIB "
    ::= { qtechDot11WIDSMIBGroups 1 }



END

-- *****************************************************************
-- QTECH-EEE-MIB.mib:  Qtech EEE MIB file
--
-- Feb 2012, linzhihong
--
-- Copyright (c) 2012 by Qtech Networks Co.,Ltd.
-- All rights reserved.
-- 
-- *****************************************************************
--

QTECH-EEE-MIB DEFINITIONS ::= BEGIN

IMPORTS
        MODULE-IDENTITY,
        OBJECT-TYPE,
        NOTIFICATION-TYPE,
        Integer32,
        OBJECT-TYPE
                FROM SNMPv2-SMI
        qtechMgmt
                FROM QTECH-SMI;

qtechEEEMIB MODULE-IDENTITY
        LAST-UPDATED "201210160000Z"
        ORGANIZATION "Qtech Networks Co.,Ltd."
        CONTACT-INFO
                " 
                Tel: 4008-111-000 

                E-mail: service@qtech.com.cn"
        DESCRIPTION
                "This module defines qtech EEE mibs."
        REVISION      "201210160000Z"
        DESCRIPTION
                "Add a table about EEE."
        REVISION      "201210160000Z"
        DESCRIPTION
                "Initial version of this MIB module."
        ::= { qtechMgmt 119 }

qtechEEEConfigMIBObjects OBJECT IDENTIFIER ::= { qtechEEEMIB 1 }

qtechEEETable OBJECT-TYPE
        SYNTAX 			SEQUENCE OF QtechEEEEntry
        MAX-ACCESS 	not-accessible
        STATUS 			current
        DESCRIPTION
            " "
        ::= { qtechEEEConfigMIBObjects 1 }

   
qtechEEEEntry OBJECT-TYPE
        SYNTAX 			QtechEEEEntry
        MAX-ACCESS 	not-accessible
        STATUS 			current
        DESCRIPTION
            " "
        INDEX { qtechEEEifIndex }
        ::= { qtechEEETable 1 }

QtechEEEEntry ::=
        SEQUENCE {
            qtechEEEifIndex 		 Integer32,
            qtechEEEAdminEnable INTEGER,
            qtechEEEOperEnable  INTEGER
        }
       
qtechEEEifIndex OBJECT-TYPE
        SYNTAX 			Integer32 (1..2147483647)
        MAX-ACCESS 	read-only
        STATUS 			current
        DESCRIPTION
            " "
        ::= { qtechEEEEntry 1 }
   
           
qtechEEEAdminEnable OBJECT-TYPE
        SYNTAX INTEGER {
            enabled(1),
            disabled(2)
        }
        MAX-ACCESS read-write
        STATUS current
        DESCRIPTION
            " "
        ::= { qtechEEEEntry 2 }
    
qtechEEEOperEnable OBJECT-TYPE
        SYNTAX INTEGER {
            enabled(1),
            disabled(2)
        }
        MAX-ACCESS read-only
        STATUS current
        DESCRIPTION
            " "
        ::= { qtechEEEEntry 3 }                             
        
END

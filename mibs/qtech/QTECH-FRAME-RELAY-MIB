-- *******************************************************************
-- Qtech-FRAME-RELAY-MIB.mib
--        Qtech Frame Relay MIB file, providing Frame Relay specific
--        information that are either excluded by RFC 1315 (FR DTE MIB)
--        or specific to Qtech products.
--
-- May 2009, juncheng hong
--
-- Copyright (c) 2009 by Qtech Networks Co.,Ltd.
-- All rights reserved.
--
-- *******************************************************************

-- Note:
-- Until future change, it is no intention for this MIB to cover 
-- every Frame Relay related feature, configuration statement, or
-- exec command display. The focus is to provide key information
-- that are unavailable in any of the existing MIB's, but are
-- currently available through the Frame Relay show commands and/or
-- configuration displays.


QTECH-FRAME-RELAY-MIB DEFINITIONS ::= BEGIN

IMPORTS
        MODULE-IDENTITY,
        OBJECT-TYPE,
        Counter32,
        Integer32,
        IpAddress
                FROM SNMPv2-SMI
        MODULE-COMPLIANCE,
        OBJECT-GROUP
                FROM SNMPv2-CONF
        TEXTUAL-CONVENTION,
        DisplayString,
        TruthValue
                FROM SNMPv2-TC
        qtechMgmt
                FROM QTECH-SMI
        InterfaceIndex,
        ifIndex
                FROM IF-MIB
        frDlcmiEntry,
        frCircuitEntry,
        frCircuitIfIndex,
        frCircuitDlci
                FROM FRAME-RELAY-DTE-MIB;

-- All table indicies in this MIB that involve interface index and
-- DLCI are derived from frCircuitIfIndex and frCircuitDlci 
-- respectively from RFC 1315.

qtechFrameRelayMIB     MODULE-IDENTITY
        LAST-UPDATED   "200010130000Z"
        ORGANIZATION   "Qtech Networks Co.,Ltd."
        CONTACT-INFO
                " 
                Tel: 4008-111-000 

                E-mail: service@qtech.com.cn"
        DESCRIPTION
                "Qtech Frame Relay MIB"

        REVISION        "200010130000Z"
        DESCRIPTION
                "(1) Added objects of FR Switching, FR Fragmentation 
                and FR/ATM Interworking.
                (2) Objects for per PVC I/O rate is added to 
                cfrExtCircuitTable"

        REVISION        "200005220000Z"
        DESCRIPTION
                "(1) Added  ELMI subgroup for ELMI objects."

        REVISION        "200005160000Z"
        DESCRIPTION
                "(1) Added Traffic Shaping parameter objects to
                qtechfrExtCircuitTable.
                (2) Deprecated qtechfrSvcMinThruputOut and 
                qtechfrSvcMinThruputIn. Added qtechfrExtCircuitMinThruputOut 
                and qtechfrExtCircuitMinThruputIn in qtechfrExtCircuitTable 
                inorder to make them applicable to both PVC/SVC. 
                (3) Added qtechfrExtCircuitBandwidth object to 
                qtechfrExtCircuitTable."

        REVISION        "200905180000Z"
        DESCRIPTION
                "(1) add an integer value for qtechfrMapPayloadCompressType;
                (2) reword the Description statements for 
                      { qtechfrMapPayloadCompressType,
                      qtechfrExtCircuitUncompressIns,
                      qtechfrExtCircuitUncompressOuts }
                so that they are not limited to software compression."

        REVISION        "9908210000Z"
        DESCRIPTION
                "(1) Added qtechfrExtCircuitUncompressOuts and
                qtechfrExtCircuitUncompressIns to the circuit subgroup;
                (2) Added qtechfrMapRtpHdrCompress and qtechfrMapPayloadCompressType
                to the mapping subgroup;
                (3) qtechfrMapPayloadCompress becomes deprecated, obsoleted
                by qtechfrMapPayloadCompressType;
                (4) frCircuitSentOctets and frCircuitReceivedOctets
                per RFC1315 will reflect the number of bytes in Frame Relay
                frames sent to and received from the physical layer. Same
                effect is applied to ifOutOctets and ifInOctets as well
                when ifIndex refers to a Frame Relay subinterface."

        REVISION        "9608150000Z"
        DESCRIPTION
                "Initial version of this MIB module."

        ::= { qtechMgmt 50 }


qtechFrMIBObjects OBJECT IDENTIFIER ::= { qtechFrameRelayMIB 1 }

-- Subgroups:
-- The objects include four subgroups on the topics of
--        o LMI (Local Management Interface, see ANSI T1.617 Annex D and
--          the Frame Relay Specification with Extensions by DEC,
--          NT, StrataCom, and Qtech.),
--        o Virtual circuits,
--        o Circuit mapping information, 
--        o SVC (switched virtual circuits, see CCITT/ITU Q.933 and 
--           Q.922.),
--        o ELMI (Enhanced Link Management Interface) objects,
--        o Fragmentation objects,
--        o Frame Relay/ATM Network Interworking objects,
--        o Frame Relay/ATM PVC Service Interworking objects, and
--        o Frame Relay Switching objects.

qtechfrLmiObjs        OBJECT IDENTIFIER ::= { qtechFrMIBObjects 1 }

qtechfrCircuitObjs    OBJECT IDENTIFIER ::= { qtechFrMIBObjects 2 }

qtechfrMapObjs        OBJECT IDENTIFIER ::= { qtechFrMIBObjects 3 }

qtechfrSvcObjs        OBJECT IDENTIFIER ::= { qtechFrMIBObjects 4 }

qtechfrElmiObjs       OBJECT IDENTIFIER ::= { qtechFrMIBObjects 5 }

qtechfrFragObjs       OBJECT IDENTIFIER ::= { qtechFrMIBObjects 6 }

qtechfrConnectionObjs  OBJECT IDENTIFIER ::= { qtechFrMIBObjects 7 }

DlciNumber ::= TEXTUAL-CONVENTION
        STATUS  current
        DESCRIPTION
                "Numerical format of Data Link Connection Identifier
                (DLCI) in decimal, identical to the 'DLCI' as INTEGER
                of 0..DLCINumber in RFC1315. The maximum value depends
                on Frame Relay implementation, which is currently set
                to be 1023 for 2-octet address format per UNI
                Implementation Agreement FRF.1."
        SYNTAX        INTEGER (0..1023)

QtechfrMapProtocols ::= TEXTUAL-CONVENTION
        STATUS  current
        DESCRIPTION
                "Qtech link types (network protocols) that run
                over Frame Relay. Associated values, except for
                wildcard, match assigned values of internal software
                respectively."
        SYNTAX  INTEGER
        {
                arp(1),
                serialArp(6),
                ip(7),
                xns(10),
                novell(11),
                apollo(12),
                vines(13),
                appletalk(16),
                ieeeSpanning(18),
                decnet(22),
                clns(25),
                rsrb(37),
                bridge(38),
                stun(39),
                frArp(40),
                uncompressedTcp(47),
                compressedTcp(48),
                llc2(49),
                frSwitch(53),
                dlsw(63),
                nhrp(74),
                compressedRtp(83),
                wildcard(999)        -- either means no applicable type for
                                -- the circuit or means point-to-point
        }


-- LMI sub-group {

qtechfrLmiTable OBJECT-TYPE
        SYNTAX      SEQUENCE OF QtechfrLmiEntry
        MAX-ACCESS  not-accessible
        STATUS      current
        DESCRIPTION
                "Table of Frame Relay LMI information that are
                either supplemental to the frDlcmiTable of RFC 1315
                or specific to Qtech's implementation."
        REFERENCE
                "American National Standard T1.617-1991, Annex D"
        ::= { qtechfrLmiObjs 1 }

qtechfrLmiEntry OBJECT-TYPE
        SYNTAX      QtechfrLmiEntry
        MAX-ACCESS  not-accessible
        STATUS      current
        DESCRIPTION
                "Each entry of the table contains information
                of Frame Relay LMI over one physical interface.
                They are mostly FR generic and some Qtech specific."
        AUGMENTS { frDlcmiEntry }
        ::= { qtechfrLmiTable 1 }

QtechfrLmiEntry ::=
        SEQUENCE {
            qtechfrLmiLinkstatus             INTEGER, 
            qtechfrLmiLinkType               INTEGER, 
            qtechfrLmiEnquiryIns             Counter32,
            qtechfrLmiEnquiryOuts            Counter32,
            qtechfrLmiStatusIns              Counter32, 
            qtechfrLmiStatusOuts             Counter32,
            qtechfrLmiUpdateStatusIns        Counter32, 
            qtechfrLmiUpdateStatusOuts       Counter32, 
            qtechfrLmiStatusTimeouts         Counter32,
            qtechfrLmiStatusEnqTimeouts      Counter32,
            qtechfrLmiN392Dce                INTEGER,
            qtechfrLmiN393Dce                INTEGER,
            qtechfrLmiT392Dce                INTEGER
        }

-- Note: for LMI type, i.e. ANSI or cisco, see frDlcmiState
-- of RFC 1315. Also, for LMI parameters for DTE not listed here,
-- e.g. T391, N391, N392, and N393, see RFC 1315.
--
-- Although based on the current logic the value for
-- cfrLmiDLstatus is equivalent to ifOperStatus, the object
-- remains herein for future possible development change.

qtechfrLmiLinkstatus OBJECT-TYPE
        SYNTAX  INTEGER {
                    up(1),
                    down(2)
                }
        MAX-ACCESS  read-only
        STATUS      current
        DESCRIPTION
                "Data link status via LMI."
        ::= { qtechfrLmiEntry 1 }

qtechfrLmiLinkType OBJECT-TYPE
        SYNTAX  INTEGER {
                    dte(1),
                    dce(2),
                    nni(3)
                }
        MAX-ACCESS  read-only
        STATUS      current
        DESCRIPTION
                "Frame Relay link type."
        ::= { qtechfrLmiEntry 2 }


qtechfrLmiEnquiryIns OBJECT-TYPE
        SYNTAX      Counter32
        UNITS       "messages"
        MAX-ACCESS  read-only
        STATUS      current
        DESCRIPTION
                "Number of Status Enquiry messages received."
        ::= { qtechfrLmiEntry 3 }

qtechfrLmiEnquiryOuts OBJECT-TYPE
        SYNTAX      Counter32
        UNITS       "messages"
        MAX-ACCESS  read-only
        STATUS      current
        DESCRIPTION
                "Number of Status Enquiry messages sent."
        ::= { qtechfrLmiEntry 4 }

qtechfrLmiStatusIns OBJECT-TYPE
        SYNTAX      Counter32
        UNITS       "messages"
        MAX-ACCESS  read-only
        STATUS      current
        DESCRIPTION
                "Number of Status messages received."
        ::= { qtechfrLmiEntry 5 }

qtechfrLmiStatusOuts OBJECT-TYPE
        SYNTAX      Counter32
        UNITS       "messages"
        MAX-ACCESS  read-only
        STATUS      current
        DESCRIPTION
                "Number of Status messages sent."
        ::= { qtechfrLmiEntry 6 }

qtechfrLmiUpdateStatusIns OBJECT-TYPE
        SYNTAX      Counter32
        UNITS       "messages"
        MAX-ACCESS  read-only
        STATUS      current
        DESCRIPTION
                "Number of Update Status messages received."
        ::= { qtechfrLmiEntry 7 }

qtechfrLmiUpdateStatusOuts OBJECT-TYPE
        SYNTAX      Counter32
        UNITS       "messages"
        MAX-ACCESS  read-only
        STATUS      current
        DESCRIPTION
                "Number of Update Status messages sent"
        ::= { qtechfrLmiEntry 8 }

qtechfrLmiStatusTimeouts OBJECT-TYPE
        SYNTAX      Counter32
        UNITS       "times"
        MAX-ACCESS  read-only
        STATUS      current
        DESCRIPTION
                "Number of times when timeout occurred on waiting
                for Status message"
        ::= { qtechfrLmiEntry 9 }

qtechfrLmiStatusEnqTimeouts OBJECT-TYPE
        SYNTAX      Counter32
        UNITS       "times"
        MAX-ACCESS  read-only
        STATUS      current
        DESCRIPTION
                "Number of times when timeout occurred on waiting
                for Status Enquiry message"
        ::= { qtechfrLmiEntry 10 }

qtechfrLmiN392Dce OBJECT-TYPE
        SYNTAX      INTEGER (0..10)
        MAX-ACCESS  read-only
        STATUS      current
        DESCRIPTION
                "LMI error threshold for DCE interface.
                For DTE, value becomes 0."
        ::= { qtechfrLmiEntry 11 }

qtechfrLmiN393Dce OBJECT-TYPE
        SYNTAX      INTEGER (0..10)
        MAX-ACCESS  read-only
        STATUS      current
        DESCRIPTION
                "LMI monitored event count for DCE interface.
                For DTE, value becomes zero (0)."
        ::= { qtechfrLmiEntry 12 }

qtechfrLmiT392Dce OBJECT-TYPE
        SYNTAX      INTEGER (0..30)
        UNITS       "seconds"
        MAX-ACCESS  read-only
        STATUS      current
        DESCRIPTION
                "DCE polling verification timer for DCE interface
                For DTE, the value becomes zero (0)."
        ::= { qtechfrLmiEntry 13 }

-- end LMI subgroup }

-- Circut sub-group {

qtechfrCircuitTable OBJECT-TYPE
        SYNTAX      SEQUENCE OF QtechfrCircuitEntry
        MAX-ACCESS  not-accessible
        STATUS      current
        DESCRIPTION
                "Table of descriptive and statistics information
                that are generic to Frame Relay virtual circuits."
        ::= { qtechfrCircuitObjs 1 }

qtechfrCircuitEntry OBJECT-TYPE
        SYNTAX      QtechfrCircuitEntry
        MAX-ACCESS  not-accessible
        STATUS      current
        DESCRIPTION
                "Each entry of the table contains information of a
                circuit that are not included in frCircuitTable of
                RFC1315 but are generic to Frame Relay."
        AUGMENTS { frCircuitEntry }
                -- indexed by { frCircuitIfIndex, frCircuitDlci }
        ::= { qtechfrCircuitTable 1 }

QtechfrCircuitEntry ::=
        SEQUENCE {
            qtechfrCircuitDEins              Counter32,
            qtechfrCircuitDEouts             Counter32,
            qtechfrCircuitDropPktsOuts       Counter32,
            qtechfrCircuitType               INTEGER
        }

qtechfrCircuitDEins OBJECT-TYPE
        SYNTAX      Counter32
        UNITS       "packets"
        MAX-ACCESS  read-only
        STATUS      current
        DESCRIPTION
                "Number of packets received with the Discarded
                Eligibility indictor (the DE bit) set."
        ::= { qtechfrCircuitEntry 1 }

qtechfrCircuitDEouts OBJECT-TYPE
        SYNTAX      Counter32
        UNITS       "packets"
        MAX-ACCESS  read-only
        STATUS      current
        DESCRIPTION
                "Number of packets transmitted with DE bit set."
        ::= { qtechfrCircuitEntry 2 }

qtechfrCircuitDropPktsOuts OBJECT-TYPE
        SYNTAX      Counter32
        UNITS       "packets"
        MAX-ACCESS  read-only
        STATUS      current
        DESCRIPTION
                "Number of discarded packets that were to be sent."
        ::= { qtechfrCircuitEntry 3 }

qtechfrCircuitType OBJECT-TYPE
        SYNTAX  INTEGER
                {
                    pvc(1),        -- permanent virtual circuit
                    svc(2)        -- switched virtual circuit
                }
        MAX-ACCESS  read-only
        STATUS      current
        DESCRIPTION
                "Basic circuit type"
        ::= { qtechfrCircuitEntry 4 }

-- Qtech specific circuit information:

qtechfrExtCircuitTable  OBJECT-TYPE
        SYNTAX      SEQUENCE OF QtechfrExtCircuitEntry
        MAX-ACCESS  not-accessible
        STATUS      current
        DESCRIPTION
                "Table of Qtech implementation specific FR
                circuit information. This is a Qtech extension
                for the frCircuitTable of RFC 1315."
        ::= { qtechfrCircuitObjs 2 }

qtechfrExtCircuitEntry  OBJECT-TYPE
        SYNTAX      QtechfrExtCircuitEntry
        MAX-ACCESS  not-accessible
        STATUS      current
        DESCRIPTION
                "Each entry of the table contains information
                of a Frame Relay virtual circuit that are specific
                to Qtech implementation."
        AUGMENTS { frCircuitEntry }
                -- indexed by { frCircuitIfIndex, frCircuitDlci }
        ::= { qtechfrExtCircuitTable 1 }

QtechfrExtCircuitEntry ::=
        SEQUENCE {
            qtechfrExtCircuitIfName             DisplayString,
            qtechfrExtCircuitIfType             INTEGER,
            qtechfrExtCircuitSubifIndex         InterfaceIndex,
            qtechfrExtCircuitMapStatus          INTEGER,
            qtechfrExtCircuitCreateType         INTEGER,
            qtechfrExtCircuitMulticast          TruthValue,
            qtechfrExtCircuitRoutedDlci         DlciNumber, 
            qtechfrExtCircuitRoutedIf           InterfaceIndex,
            qtechfrExtCircuitUncompressIns      Counter32,
            qtechfrExtCircuitUncompressOuts     Counter32,
            qtechfrExtCircuitFECNOuts           Counter32,  
            qtechfrExtCircuitBECNOuts           Counter32,  
            qtechfrExtCircuitMinThruputOut      Integer32,
            qtechfrExtCircuitMinThruputIn       Integer32,
            qtechfrExtCircuitBcastPktOuts       Counter32,
            qtechfrExtCircuitBcastByteOuts      Counter32,
            qtechfrExtCircuitBandwidth          Integer32,
            qtechfrExtCircuitShapeByteLimit     Integer32,
            qtechfrExtCircuitShapeInterval      Integer32,
            qtechfrExtCircuitShapeByteIncrement Integer32,
            qtechfrExtCircuitShapePkts          Counter32,
            qtechfrExtCircuitShapeBytes         Counter32,
            qtechfrExtCircuitShapePktsDelay     Counter32,
            qtechfrExtCircuitShapeBytesDelay    Counter32,
            qtechfrExtCircuitShapeActive        TruthValue,
            qtechfrExtCircuitShapeAdapting      INTEGER,
            qtechfrExtCircuitTxDataRate         INTEGER,
            qtechfrExtCircuitTxPktRate          INTEGER,
            qtechfrExtCircuitRcvDataRate        INTEGER,
            qtechfrExtCircuitRcvPktRate         INTEGER 
        }

qtechfrExtCircuitIfName  OBJECT-TYPE
        SYNTAX       DisplayString
        MAX-ACCESS   read-only
        STATUS       current
        DESCRIPTION
                "The textual name of the main interface or the 
                subinterface that this DLCI is associated with.
                This is the same name string of an interface used
                in the configuration and all console displays,
                such as 'serial 0', 'serial 3/0.3', etc."
        ::= { qtechfrExtCircuitEntry 1 }

qtechfrExtCircuitIfType  OBJECT-TYPE
        SYNTAX  INTEGER {
                  mainInterface(1),
                  pointToPoint(2),        -- subinterface
                  multipoint(3)           -- subinterface
                }
        MAX-ACCESS  read-only
        STATUS      current
        DESCRIPTION
                "Type of the subinterface this DLCI is associated
                with, if configured."
        ::= { qtechfrExtCircuitEntry 2 }

qtechfrExtCircuitSubifIndex OBJECT-TYPE
        SYNTAX      InterfaceIndex
        MAX-ACCESS  read-only
        STATUS      current
        DESCRIPTION
                "For value greater than zero (0), it indicates
                the network management interface index
                for the subinterface associated with
                this DLCI. Value 0 means the DLCI is not
                associated with any subinterface." 
        ::= { qtechfrExtCircuitEntry 3 }

qtechfrExtCircuitMapStatus OBJECT-TYPE
        SYNTAX      INTEGER (0..2047)
        MAX-ACCESS  read-only
        STATUS      current
        DESCRIPTION
                "The mapping protocols (internally considered as
                the 'link type') applied on this circuit.
                The value ranges from 0 to 2047.
                For point-to-point DLCI, the value stays zero.
                Otherwise, the value is a sum. It initially takes
                the value zero, then, for each type of Protocol,
                2 raised to a power is added to the sum.
                The following table presents respective power and
                equivalent value for each applicable type:

                        Protocol        Power    Value
                        --------        -----    -----
                        IP              0        1
                        IPX             1        2
                        Appletalk       2        4
                        XNS             3        8
                        VINES           4        16
                        DECnet          5        32
                        CLNS            6        64
                        Bridging        7        128
                        RSRB            8        256
                        STUN            9        512
                        LLC2            10       1024

                For example, value 3 means the circuit's mapping
                protocols include IP and IPX. (3 = 2**1 + 2**0,
                where 0 corresponds to IP and 1 to IPX.) Value 0
                means there is currently no mapping protocol for
                the circuit.
                See qtechfrMapTable for more mapping information."
        ::= { qtechfrExtCircuitEntry 4 }

qtechfrExtCircuitCreateType OBJECT-TYPE
        SYNTAX  INTEGER
                {
                    dynamic(1),      -- PVC established through LMI
                                     -- or an SVC established through
                                     -- SVC signalling
                    static(2)        -- circuit was configured
                }
        MAX-ACCESS  read-only
        STATUS      current
        DESCRIPTION
                "Identify the last source of the circuit's creation."
        ::= { qtechfrExtCircuitEntry 5 }

qtechfrExtCircuitMulticast  OBJECT-TYPE
        SYNTAX      TruthValue
        MAX-ACCESS  read-only
        STATUS      current
        DESCRIPTION
                "Indicate if this DLCI is a multicast DLCI."
        ::= { qtechfrExtCircuitEntry 6 }

qtechfrExtCircuitRoutedDlci OBJECT-TYPE
        SYNTAX      DlciNumber
        MAX-ACCESS  read-only
        STATUS      current
        DESCRIPTION
                "The routed DLCI to pair up with this DLCI
                for switching function. NOTE: Value zero (0)
                indicates that there is no such routed DLCI
                corresponding to this DLCI."
        ::= { qtechfrExtCircuitEntry 7 }

qtechfrExtCircuitRoutedIf OBJECT-TYPE
        SYNTAX      InterfaceIndex
        MAX-ACCESS  read-only
        STATUS      current
        DESCRIPTION
                "The interface for the routed DLCI that pairs up
                with this DLCI for switching. Value greater than 0
                is the InterfaceIndex for that interface. Value
                zero (0) indicates that there is no such routed DLCI
                corresponding to this DLCI."
        ::= { qtechfrExtCircuitEntry 8 }

qtechfrExtCircuitUncompressIns OBJECT-TYPE
        SYNTAX      Counter32
        UNITS       "octets"
        MAX-ACCESS  read-only
        STATUS      current
        DESCRIPTION
                "Number of inbound octets of the data packets,
                accounted at Frame Relay level after FRF.9
                payload decompression is applied. In the case of
                non-FRF.9, this value could be identical to
                frCircuitReceivedOctets, unless otherwise noted."
        ::= { qtechfrExtCircuitEntry 9 }

qtechfrExtCircuitUncompressOuts OBJECT-TYPE
        SYNTAX      Counter32
        UNITS       "octets"
        MAX-ACCESS  read-only
        STATUS      current
        DESCRIPTION
                "Number of outbound octets of the data packets,
                accounted at Frame Relay level before FRF.9
                payload compression is applied. In the case of
                non-FRF.9, this value could be identical to
                frCircuitSentOctets, unless otherwise noted."
        ::= { qtechfrExtCircuitEntry 10 }

qtechfrExtCircuitFECNOuts OBJECT-TYPE
        SYNTAX      Counter32
        MAX-ACCESS  read-only
        STATUS      current
        DESCRIPTION
                "Total number of frames sent out to the network 
                indicating forward congestion."
        ::= { qtechfrExtCircuitEntry 11 }

qtechfrExtCircuitBECNOuts OBJECT-TYPE
        SYNTAX      Counter32
        MAX-ACCESS  read-only
        STATUS      current
        DESCRIPTION
                "Total number of frames sent out to the network 
                indicating backward congestion."
        ::= { qtechfrExtCircuitEntry 12 }

qtechfrExtCircuitMinThruputOut OBJECT-TYPE
        SYNTAX      Integer32 (9600..1544000)
        UNITS       "bits per second"
        MAX-ACCESS  read-only
        STATUS      current
        DESCRIPTION
                "Circuit's outgoing minimal Throughput based on 
                configuration."
        ::= { qtechfrExtCircuitEntry 13 }

qtechfrExtCircuitMinThruputIn  OBJECT-TYPE
        SYNTAX      Integer32 (9600..1544000)
        UNITS       "bits per second"
        MAX-ACCESS  read-only
        STATUS      current
        DESCRIPTION
                "Circuit's incoming minimal Throughput based on
                configuration."
        ::= { qtechfrExtCircuitEntry 14 }

qtechfrExtCircuitBcastPktOuts OBJECT-TYPE
        SYNTAX      Counter32
        MAX-ACCESS  read-only
        STATUS      current
        DESCRIPTION
                "Total number of broadcast packets sent out to the 
                 network."
        ::= { qtechfrExtCircuitEntry 15 }

qtechfrExtCircuitBcastByteOuts OBJECT-TYPE
        SYNTAX      Counter32
        MAX-ACCESS  read-only
        STATUS      current
        DESCRIPTION
                "Total number of bytes sent out to the network in 
                broadcast packets."
        ::= { qtechfrExtCircuitEntry 16 }

qtechfrExtCircuitBandwidth OBJECT-TYPE
        SYNTAX      Integer32 (0..16777215)
        UNITS       "bits per second"
        MAX-ACCESS  read-only
        STATUS      current
        DESCRIPTION
                "Bandwidth of the virtual circuit, acquired from 
                Qtech typed LMI Full Status message."
        ::= { qtechfrExtCircuitEntry 17 }

qtechfrExtCircuitShapeByteLimit OBJECT-TYPE
        SYNTAX      Integer32 (125..2147483647)
        UNITS       "octets"
        MAX-ACCESS  read-only
        STATUS      current
        DESCRIPTION
                "Maximum number of tokens a token bucket can hold in any
                time interval in case of traffic shaping."
        ::= { qtechfrExtCircuitEntry 18 }

qtechfrExtCircuitShapeInterval OBJECT-TYPE
        SYNTAX      Integer32 (10..125)
        UNITS       "milliseconds"
        MAX-ACCESS  read-only
        STATUS      current
        DESCRIPTION
                "Committed rate measurement interval."
        ::= { qtechfrExtCircuitEntry 19 }

qtechfrExtCircuitShapeByteIncrement OBJECT-TYPE
        SYNTAX      Integer32 (125..2147483647)
        UNITS       "octets"
        MAX-ACCESS  read-only
        STATUS      current
        DESCRIPTION
                "Number of tokens added into the token bucket per time
                interval in case of traffic shaping."
        ::= { qtechfrExtCircuitEntry 20 }

qtechfrExtCircuitShapePkts OBJECT-TYPE
        SYNTAX      Counter32
        MAX-ACCESS  read-only
        STATUS      current
        DESCRIPTION
                "Total number of packets that went through traffic 
                shaping."
        ::= { qtechfrExtCircuitEntry 21 }

qtechfrExtCircuitShapeBytes OBJECT-TYPE
        SYNTAX      Counter32
        UNITS       "octets"
        MAX-ACCESS  read-only
        STATUS      current
        DESCRIPTION
                "Total number of bytes that went through traffic 
                shaping."
        ::= { qtechfrExtCircuitEntry 22 }

qtechfrExtCircuitShapePktsDelay OBJECT-TYPE
        SYNTAX      Counter32
        MAX-ACCESS  read-only
        STATUS      current
        DESCRIPTION
                "Total number of packets that were delayed by the 
                traffic shaper."
        ::= { qtechfrExtCircuitEntry 23 }

qtechfrExtCircuitShapeBytesDelay OBJECT-TYPE
        SYNTAX      Counter32
        UNITS       "octets"
        MAX-ACCESS  read-only
        STATUS      current
        DESCRIPTION
                "Total number of bytes that were delayed by the 
                traffic shaper."
        ::= { qtechfrExtCircuitEntry 24 }

qtechfrExtCircuitShapeActive OBJECT-TYPE
        SYNTAX      TruthValue
        MAX-ACCESS  read-only
        STATUS      current
        DESCRIPTION
                "Shows whether shaping is active or not."
        ::= { qtechfrExtCircuitEntry 25 }

qtechfrExtCircuitShapeAdapting  OBJECT-TYPE
        SYNTAX  INTEGER {
                  none(1),
                  becn(2),
                  foreSight(3)
                }
        MAX-ACCESS  read-only
        STATUS      current
        DESCRIPTION
                "Type of Adaptive Shaping configured.
                none(1)      - No adaptive shaping configured
                becn(2)      - Backward Explicit Congestion Notification
                foreSight(3) - ForeSight is the network traffic control 
                               software used in Qtech WAN switches"
        ::= { qtechfrExtCircuitEntry 26 }

qtechfrExtCircuitTxDataRate OBJECT-TYPE
        SYNTAX       INTEGER (1..45000000)
        MAX-ACCESS   read-only
        STATUS       current
        DESCRIPTION
               "The average rate (bytes/second) at which data is 
               transmitted in this circuit. "
        ::= { qtechfrExtCircuitEntry 27 }

qtechfrExtCircuitTxPktRate OBJECT-TYPE
        SYNTAX       INTEGER (1..45000000)
        MAX-ACCESS   read-only
        STATUS       current
        DESCRIPTION
              "The average number of packets sent in a second in this 
              circuit."
        ::= { qtechfrExtCircuitEntry 28 }

qtechfrExtCircuitRcvDataRate OBJECT-TYPE
        SYNTAX       INTEGER (1..45000000)
        MAX-ACCESS   read-only
        STATUS       current
        DESCRIPTION
               "The average rate (bytes/second) at which data is 
               received in this circuit. "
        ::= { qtechfrExtCircuitEntry 29 }

qtechfrExtCircuitRcvPktRate OBJECT-TYPE
        SYNTAX       INTEGER (1..45000000)
        MAX-ACCESS   read-only
        STATUS       current
        DESCRIPTION
               "The average number of packets received in a second in 
               this circuit. "
       ::= { qtechfrExtCircuitEntry 30 }

-- end circuit subgroup }

-- Mapping sub-group {

qtechfrMapTable OBJECT-TYPE
        SYNTAX      SEQUENCE OF QtechfrMapEntry
        MAX-ACCESS  not-accessible
        STATUS      current
        DESCRIPTION
                "Table of protocols and addresses mapping
                information of FR virtual circuit."
        ::= { qtechfrMapObjs 1 }

qtechfrMapEntry OBJECT-TYPE
        SYNTAX      QtechfrMapEntry
        MAX-ACCESS  not-accessible
        STATUS     current
        DESCRIPTION
                "Each entry of the table contains one mapping 
                information of a Frame Relay virtual circuit."
        INDEX { frCircuitIfIndex, frCircuitDlci, qtechfrMapIndex } 
        ::= { qtechfrMapTable 1 }

QtechfrMapEntry ::=
        SEQUENCE {
            qtechfrMapIndex                 INTEGER,
            qtechfrMapProtocol              QtechfrMapProtocols,
            qtechfrMapAddress               OCTET STRING (SIZE(0..64)),
            qtechfrMapType                  INTEGER,
            qtechfrMapEncaps                INTEGER,
            qtechfrMapBroadcast             TruthValue,
            qtechfrMapPayloadCompress       TruthValue,
            qtechfrMapTcpHdrCompress        INTEGER,
            qtechfrMapRtpHdrCompress        INTEGER,
            qtechfrMapPayloadCompressType   INTEGER
        }

qtechfrMapIndex OBJECT-TYPE
        SYNTAX      INTEGER (1..999)
        MAX-ACCESS  read-only
        STATUS      current
        DESCRIPTION
                "An arbitrary Index to the mapping information
                associated with a certain circuit. The maximum
                value is arbitrarily picked which is considered
                sufficient for usual configuration."
        ::= { qtechfrMapEntry 1 }

qtechfrMapProtocol OBJECT-TYPE
        SYNTAX      QtechfrMapProtocols
        MAX-ACCESS  read-only
        STATUS      current
        DESCRIPTION
                "Mapping protocol for this circuit."
        ::= { qtechfrMapEntry 2 }

qtechfrMapAddress OBJECT-TYPE
        SYNTAX      OCTET STRING (SIZE(0..64))
        MAX-ACCESS  read-only
        STATUS      current
        DESCRIPTION
                "Mapping protocol address at remote end for
                this DLCI.
                NOTE: For point-to-point DLCI, the string is fixed
                to be point-to-point."
        ::= { qtechfrMapEntry 3 }

qtechfrMapType OBJECT-TYPE
        SYNTAX  INTEGER
                {
                    static(1),
                    dynamic(2),
                    svc(3)
                }
        MAX-ACCESS  read-only
        STATUS      current
        DESCRIPTION
                "Type for the map creation."
        ::= { qtechfrMapEntry 4 }

qtechfrMapEncaps OBJECT-TYPE
        SYNTAX  INTEGER
                {
                    ietf(1),    -- following IETF specifications
                                -- (RFC 1490 as up to date)
                    cisco(2)
                }
        MAX-ACCESS  read-only
        STATUS      current
        DESCRIPTION
                "Indication of the encapsulation type for this
                mapping protocol."
        ::= { qtechfrMapEntry 5 }

qtechfrMapBroadcast OBJECT-TYPE
        SYNTAX      TruthValue
        MAX-ACCESS  read-only
        STATUS      current
        DESCRIPTION
                "Broadcast enabled or disabled."
        ::= { qtechfrMapEntry 6 }

qtechfrMapPayloadCompress OBJECT-TYPE
        SYNTAX      TruthValue
        MAX-ACCESS  read-only
        STATUS      deprecated
                    -- obsoleted by qtechfrMapPayloadCompressType
        DESCRIPTION
                "Indicate if payload compression is enabled."
        ::= { qtechfrMapEntry 7 }

qtechfrMapTcpHdrCompress OBJECT-TYPE
        SYNTAX  INTEGER
                {
                    inapplicable(1),
                    passive(2),
                    active(3)
                }
        MAX-ACCESS  read-only
        STATUS      current
        DESCRIPTION
                "TCP header compression type, if applicable."
        ::= { qtechfrMapEntry 8 }

qtechfrMapRtpHdrCompress OBJECT-TYPE
        SYNTAX  INTEGER
                {
                    inapplicable(1),
                    passive(2),
                    active(3)
                }
        MAX-ACCESS  read-only
        STATUS      current
        DESCRIPTION
                "RTP header compression type, if applicable.
                The value 'passive' means that the header of an
                outgoing RTP/IP packet is compressed only if an
                incoming RTP/IP packet had a compressed header.
                The value 'active' means the header of every outgoing
                RTP/IP packet is compressed."
        ::= { qtechfrMapEntry 9 }

qtechfrMapPayloadCompressType OBJECT-TYPE
        SYNTAX  INTEGER
             {
                inapplicable(1),
                cisco(2),         -- cisco proprietary FR packet-
                                  -- by-packet payload compression
                frf9Software(3),  -- FRF.9 software payload compression
                frf9Hardware(4)   -- FRF.9 hardware payload compression
             }
        MAX-ACCESS  read-only
        STATUS      current
        DESCRIPTION
                "FR payload compression type, if applicable.
                FRF.9 is the Frame Relay Forum Implementation Agreement
                on FR payload compression. The compression can be done
                by either software or hardware (when equipped with the
                supporting hardware), depending on configuration."
        REFERENCE
                "Frame Relay Forum document number FRF.9"
        ::= { qtechfrMapEntry 10 }

-- end mapping subgroup }

-- SVC sub-group {
--        containing SVC spcific information

qtechfrSvcTable OBJECT-TYPE
        SYNTAX      SEQUENCE OF QtechfrSvcEntry
        MAX-ACCESS  not-accessible
        STATUS      current
        DESCRIPTION
                "Table of FR SVC specific, descriptive
                and statistics information."
        ::= { qtechfrSvcObjs 1 }

qtechfrSvcEntry OBJECT-TYPE
        SYNTAX      QtechfrSvcEntry
        MAX-ACCESS  not-accessible
        STATUS      current
        DESCRIPTION
                "Each entry of the table contains circuit information
                specific to a Frame Relay Switched Virtual Circuit."
        INDEX { frCircuitIfIndex, frCircuitDlci } 
        ::= { qtechfrSvcTable 1 }

QtechfrSvcEntry ::=
        SEQUENCE {
            qtechfrSvcAddrLocal           OCTET STRING (SIZE(0..64)),
            qtechfrSvcAddrRemote          OCTET STRING (SIZE(0..64)),
            qtechfrSvcThroughputIn        Integer32,
            qtechfrSvcMinThruputOut       Integer32,
            qtechfrSvcMinThruputIn        Integer32,
            qtechfrSvcCommitBurstIn       Integer32,
            qtechfrSvcExcessBurstIn       Integer32,
            qtechfrSvcIdleTime            Integer32
        }

-- For circuit (DLCI) outbound throughput and outbound Committed 
-- and Excess Burst size, please refer to the following from
-- RFC1315 respectively:
--        frCircuitThroughput, 
--        frCircuitCommittedBurst, and
--        frCircuitExcessBurst


qtechfrSvcAddrLocal OBJECT-TYPE
        SYNTAX      OCTET STRING (SIZE(0..64))
        MAX-ACCESS  read-only
        STATUS      current
        DESCRIPTION
                "Local E.164/X.125 address for the circuit."
        ::= { qtechfrSvcEntry 1 }

qtechfrSvcAddrRemote OBJECT-TYPE
        SYNTAX      OCTET STRING (SIZE(0..64))
        MAX-ACCESS  read-only
        STATUS      current
        DESCRIPTION
                "Remote E.164/X.125 address for the circuit."
        ::= { qtechfrSvcEntry 2 }

qtechfrSvcThroughputIn OBJECT-TYPE
        SYNTAX      Integer32 (9600..1544000)
        UNITS       "bits per second"
        MAX-ACCESS  read-only
        STATUS      current
        DESCRIPTION
                "Circuit's incoming throughput. For outgoing 
                throughput (commonly referred to as CIR) see
                frCircuitThroughput per RFC1315."
        ::= { qtechfrSvcEntry 3 }

qtechfrSvcMinThruputOut OBJECT-TYPE
        SYNTAX      Integer32 (9600..1544000)
        UNITS       "bits per second"
        MAX-ACCESS  read-only
        STATUS      deprecated -- deprecated by 
                               -- cfrExtCircuitMinThruputOut
        DESCRIPTION
                "Circuit's outgoing minimal Throughput."
        ::= { qtechfrSvcEntry 4 }

qtechfrSvcMinThruputIn  OBJECT-TYPE
        SYNTAX      Integer32 (9600..1544000)
        UNITS       "bits per second"
        MAX-ACCESS  read-only
        STATUS      deprecated -- deprecated by 
                               -- cfrExtCircuitMinThruputIn
        DESCRIPTION
                "Circuit's incoming minimal Throughput."
        ::= { qtechfrSvcEntry 5 }

qtechfrSvcCommitBurstIn OBJECT-TYPE
        SYNTAX      Integer32 (9600..1544000)
        MAX-ACCESS  read-only
        STATUS      current
        DESCRIPTION
                "Circuit's incoming Committed Burst Rate.
                See ANSI and/or ITU specifications for
                definition and calculations. For outgoing
                CBR, see frCircuitCommittedBurst per RFC 1315."
        ::= { qtechfrSvcEntry 6 }

qtechfrSvcExcessBurstIn OBJECT-TYPE
        SYNTAX      Integer32 (9600..2440000)
        MAX-ACCESS  read-only
        STATUS      current
        DESCRIPTION
                "Circuit's incoming Excess Burst Rate.
                See ANSI and/or ITU specifications for
                definition and calculations. For outgoing
                EBR, see frCircuitExcessBurst per RFC 1315."
        ::= { qtechfrSvcEntry 7 }

qtechfrSvcIdleTime      OBJECT-TYPE
        SYNTAX      Integer32
        UNITS       "seconds"
        MAX-ACCESS  read-only
        STATUS      current
        DESCRIPTION
                "Circuit's idle time period. If expires, the
                circuit is cleared."
        ::= { qtechfrSvcEntry 8 }

-- end SVC subgroup }

-- Enhanced Link Management Interface(ELMI) sub-group {
-- ELMI is the protocol that learns QOS parameters(CIR,Bc,Be etc)
-- of a VC from the switch.
-- This sub group contains ELMI specific information.

qtechfrElmiIpAddr      OBJECT-TYPE
        SYNTAX     IpAddress
        MAX-ACCESS read-only
        STATUS     current
        DESCRIPTION
                "This object represents the Management address of the
                 device used for address registration. 
                 Network management station can send management
                 messages to this IP address. This can be 
                 user configured address or the address of one of the
                 interfaces on the device. If address registration is
                 disabled then this will have a value of 0.0.0.0. 
                 This object is accessible only if the ELMI protocol 
                 is supported on the device"
        ::= { qtechfrElmiObjs 1 }

qtechfrElmiTable       OBJECT-TYPE
        SYNTAX     SEQUENCE OF QtechfrElmiEntry
        MAX-ACCESS not-accessible
        STATUS     current
        DESCRIPTION
                "Table of QTECH Frame Relay ELMI information that is
                 specific to QTECH implementation"
        ::= { qtechfrElmiObjs 2 }

qtechfrElmiEntry       OBJECT-TYPE
        SYNTAX     QtechfrElmiEntry
        MAX-ACCESS not-accessible
        STATUS     current
        DESCRIPTION
                "Each entry of the table contains information about a
                 physical interface. The table can be accessible only
                 if the device supports ELMI protocol and if LMI is
                 enabled on the interface."
        INDEX { ifIndex }
        ::= { qtechfrElmiTable 1 }
  
QtechfrElmiEntry ::=
        SEQUENCE {
            qtechfrElmiLinkStatus
                INTEGER,
            qtechfrElmiArStatus
                INTEGER,
            qtechfrElmiRemoteStatus
                INTEGER
        }

qtechfrElmiLinkStatus  OBJECT-TYPE
        SYNTAX     INTEGER {
                       enabled(1),
                       disabled(2)
                   }
        MAX-ACCESS read-only
        STATUS     current
        DESCRIPTION
                "This variable states whether Enhanced Link Management
                 Interface(ELMI) protocol is enabled or not on a 
                 frame relay interface."
        ::= { qtechfrElmiEntry 1 }

qtechfrElmiArStatus    OBJECT-TYPE
        SYNTAX     INTEGER {
                       enabled(1),
                       disabled(2)
                   }
        MAX-ACCESS read-only
        STATUS     current
        DESCRIPTION
                "This variable states whether the Enhanced Link
                 Management Interface(ELMI) address registration(AR)
                 mechanism is enabled or not on a frame relay 
                 interface. A value of 1 indicates ELMI AR is 
                 supported on the interface. A value of 2 indicates
                 ELMI AR is supported but the user disabled the
                 exchange of IP address and ifIndex with the
                 neighboring device. This object doesn't have any
                 significance if cfrElmiLinkStatus is disabled
                 on the interface."
        ::= { qtechfrElmiEntry 2 }

qtechfrElmiRemoteStatus OBJECT-TYPE
        SYNTAX      INTEGER {
                        enabled(1),
                        disabled(2)
                    }
        MAX-ACCESS  read-only
        STATUS      current
        DESCRIPTION
                "This variable states the Enhanced Link 
                 Management(ELMI) status on the other end of the
                 interface. If cfrElmiLinkStatus is enabled on the
                 other end a value of 1 will be returned,
                 else 2 will be returned. This object doesn't have any
                 significance if cfrElmiLinkStatus is disabled on the
                 interface"
        ::= { qtechfrElmiEntry 3 }

qtechfrElmiNeighborTable    OBJECT-TYPE
        SYNTAX          SEQUENCE OF QtechfrElmiNeighborEntry
        MAX-ACCESS      not-accessible
        STATUS          current
        DESCRIPTION
                "Table of QTECH Frame Relay Neighbor ELMI information
                 that is specific to QTECH implementation."
        ::= { qtechfrElmiObjs 3 }

qtechfrElmiNeighborEntry OBJECT-TYPE
        SYNTAX       QtechfrElmiNeighborEntry
        MAX-ACCESS   not-accessible
        STATUS       current
        DESCRIPTION
                "Each entry of the table contains information of the
                 neighboring device connected to a physical interface.
                 The entry will be present only if ELMI is enabled on
                 the neighboring device interface. If the value of the
                 qtechfrElmiRemoteStatus in the qtechfrElmiEntry is 1 then a 
                 valid entry exists for the interface. If ELMI is not 
                 supported on the remote end then, the neighbor 
                 information for the interface will not be present"
        INDEX { ifIndex }
        ::= { qtechfrElmiNeighborTable 1 }

QtechfrElmiNeighborEntry ::=
        SEQUENCE {
            qtechfrElmiNeighborArStatus
                INTEGER,
            qtechfrElmiNeighborIpAddress
                IpAddress,
            qtechfrElmiNeighborIfIndex
                InterfaceIndex,
            qtechfrElmiNeighborVendorName
                DisplayString,
            qtechfrElmiNeighborPlatformName
                DisplayString,
            qtechfrElmiNeighborDeviceName
                DisplayString
        }


qtechfrElmiNeighborArStatus OBJECT-TYPE
        SYNTAX          INTEGER {
                            notsupported(1),
                            enabled(2),
                            disabled(3)
                        }
        MAX-ACCESS      read-only
        STATUS          current
        DESCRIPTION
                "This variable indicates the status of ELMI Address 
                 registration(AR) on the neighboring device. A value 
                 of 1 indicates ELMI AR is not supported on the 
                 neighboring device. A value of 2 indicates ELMI AR is
                 enabled on the interface. A value of 3 indicates AR is
                 supported, but user disabled the exchange of IP 
                 address and ifIndex with the neighbor."
        ::= { qtechfrElmiNeighborEntry 1 }

qtechfrElmiNeighborIpAddress OBJECT-TYPE
        SYNTAX           IpAddress
        MAX-ACCESS       read-only
        STATUS           current
        DESCRIPTION
                "The Management IP address of the neighboring device 
                 to which the other end of this interface is 
                 connected. Network management system can use this
                 address to send management messages to the device.
                 If address registration is not supported on the
                 remote end then the value will be 0.0.0.0.
                 NMS uses this object in the topology discovery of the
                 network."
        ::= { qtechfrElmiNeighborEntry 2 }

qtechfrElmiNeighborIfIndex   OBJECT-TYPE
        SYNTAX           InterfaceIndex
        MAX-ACCESS       read-only
        STATUS           current
        DESCRIPTION
                "The Interface index of the neighboring device to 
                 which this interface is connected. If the value of
                 qtechfrElmiNeighborArStatus is 2 then this will have a
                 valid value. If the value of qtechfrElmiNeighborArStatus
                 is 3 or 1 then value of this object will be 0. NMS
                 uses this object in the topology discovery of the
                 network."
        ::= { qtechfrElmiNeighborEntry 3 }

qtechfrElmiNeighborVendorName OBJECT-TYPE
        SYNTAX            DisplayString
        MAX-ACCESS        read-only
        STATUS            current
        DESCRIPTION
                "Vendor name of the neighboring device to which the
                 other end of this interface is connected."
        ::= { qtechfrElmiNeighborEntry 4 }

qtechfrElmiNeighborPlatformName OBJECT-TYPE
        SYNTAX              DisplayString
        MAX-ACCESS          read-only
        STATUS              current
        DESCRIPTION
                "Platform name of the neighboring device to which the
                 other end of this interface is connected."
        ::= { qtechfrElmiNeighborEntry 5 }

qtechfrElmiNeighborDeviceName   OBJECT-TYPE
        SYNTAX              DisplayString
        MAX-ACCESS          read-only
        STATUS              current
        DESCRIPTION
                "Device name of the neighboring device to which the
                 other end of this interface is connected."
        ::= { qtechfrElmiNeighborEntry 6 }

-- end ELMI sub-group }

-- Fragmentation sub-group {

qtechfrFragTable OBJECT-TYPE
        SYNTAX      SEQUENCE OF QtechfrFragEntry
        MAX-ACCESS  not-accessible
        STATUS      current
        DESCRIPTION
                "Table of Frame Relay Fragmentation information. 
                These are specific to Qtech's implementation."
        ::= { qtechfrFragObjs 1 }

qtechfrFragEntry OBJECT-TYPE
        SYNTAX      QtechfrFragEntry
        MAX-ACCESS  not-accessible
        STATUS      current
        DESCRIPTION
                "Each entry of the table contains details of 
                fragmentation configured on  this circuit. "
        INDEX { frCircuitIfIndex, frCircuitDlci}
        ::= { qtechfrFragTable 1 }

QtechfrFragEntry ::=
        SEQUENCE {
            qtechfrFragSize                       INTEGER,
            qtechfrFragType                       DisplayString,
            qtechfrFragInPkts                     Counter32,
            qtechfrFragOutPkts                    Counter32,
            qtechfrFragInOctets                   Counter32,
            qtechfrFragOutOctets                  Counter32,
            qtechfrFragNotInPkts                  Counter32,
            qtechfrFragNotOutPkts                 Counter32,
            qtechfrFragNotInOctets                Counter32,
            qtechfrFragNotOutOctets               Counter32,
            qtechfrFragAssembledInPkts            Counter32,
            qtechfrFragAssembledInOctets          Counter32,
            qtechfrFragPreOutPkts                 Counter32,
            qtechfrFragPreOutOctets               Counter32,
            qtechfrFragDroppedReAssembledInPkts   Counter32,
            qtechfrFragDroppedFragmentedOutPkts   Counter32,
            qtechfrFragTimeoutsIn                 INTEGER,
            qtechfrFragOutOfSeqFragPkts           Counter32,
            qtechfrFragUnexpectedBBitSetPkts      Counter32,
            qtechfrFragSeqMissedPkts              Counter32,
            qtechfrFragInterleavedOutPkts         Counter32
        }

qtechfrFragSize OBJECT-TYPE
        SYNTAX      INTEGER (16..1600)
        UNITS       "octets"
        MAX-ACCESS  read-only
        STATUS      current
        DESCRIPTION
                "qtechfrFragSize defines the payload size of a fragment 
                and it excludes the FR headers and any FR fragmentation
                header."

        ::= { qtechfrFragEntry 1 }
qtechfrFragType OBJECT-TYPE
        SYNTAX  DisplayString
        MAX-ACCESS  read-only
        STATUS      current
        DESCRIPTION
                "Fragmentation type configured by the user. The types
                supported are end-to-end, VoFR-qtech and VoFR."
        ::= { qtechfrFragEntry 2 }

qtechfrFragInPkts  OBJECT-TYPE
        SYNTAX      Counter32
        UNITS       "packets"
        MAX-ACCESS  read-only
        STATUS      current
        DESCRIPTION
                "Total number of frames received that have a 
                fragmentation header."
        ::= { qtechfrFragEntry 3 }

qtechfrFragOutPkts OBJECT-TYPE
        SYNTAX      Counter32
        UNITS       "packets"
        MAX-ACCESS  read-only
        STATUS      current
        DESCRIPTION
                "Total number of fragments that are transmitted with a
                fragmenation header."
        ::= { qtechfrFragEntry 4 }

qtechfrFragInOctets OBJECT-TYPE
        SYNTAX      Counter32
        UNITS       "octets"
        MAX-ACCESS  read-only
        STATUS      current
        DESCRIPTION
                "Total number of bytes received in frames that have a 
                fragmentation header. The number of bytes include the
                FR header." 
        ::= { qtechfrFragEntry 5}

qtechfrFragOutOctets OBJECT-TYPE
        SYNTAX      Counter32
        UNITS       "octets"
        MAX-ACCESS  read-only
        STATUS      current
        DESCRIPTION
                "Total number of bytes that are transmitted in frames
                with a fragmenation header. The number of bytes also
                includes the FR header." 
        ::= { qtechfrFragEntry 6}

qtechfrFragNotInPkts OBJECT-TYPE
        SYNTAX      Counter32
        UNITS       "packets"
        MAX-ACCESS  read-only
        STATUS      current
        DESCRIPTION
                "Total number of frames received that do not require 
                reassembly and therefore will not contain the 
                fragmentation header. This counter is valid only when
                end-to-end fragmentation type is set." 
        ::= { qtechfrFragEntry 7}

qtechfrFragNotOutPkts  OBJECT-TYPE
        SYNTAX      Counter32
        UNITS       "packets"
        MAX-ACCESS  read-only
        STATUS      current
        DESCRIPTION
                "Total number of frames transmitted without fragmenting
                and therefore will not contain the fragmentation header.
                This counter is valid only when end-to-end fragmentation
                type is set." 
        ::= { qtechfrFragEntry 8}

qtechfrFragNotInOctets  OBJECT-TYPE
        SYNTAX      Counter32
        UNITS       "octets"
        MAX-ACCESS  read-only
        STATUS      current
        DESCRIPTION
                "Total number of bytes received in frames that do not 
                require reassembly and therefore will not contain the 
                fragmentation header. This counter is valid only when
                end-to-end fragmentation type is set." 
        ::= { qtechfrFragEntry 9}

qtechfrFragNotOutOctets OBJECT-TYPE
        SYNTAX      Counter32
        UNITS       "octets"
        MAX-ACCESS  read-only
        STATUS      current
        DESCRIPTION
                "Total number of bytes transmitted in frames that are
                not fragmented and therefore will not contain the 
                fragmentation header. This counter is valid only when 
                end-to-end fragmentation type is set." 
        ::= { qtechfrFragEntry 10}

qtechfrFragAssembledInPkts OBJECT-TYPE
        SYNTAX      Counter32
        UNITS       "packets"
        MAX-ACCESS  read-only
        STATUS      current
        DESCRIPTION
                "Total number of fully reassembled frames. It also 
                counts the number of packets received without FR 
                fragmentation header (i.e. in un-fragmentated pkts)."
        ::= { qtechfrFragEntry 11}

qtechfrFragAssembledInOctets OBJECT-TYPE
        SYNTAX      Counter32
        UNITS       "octets"
        MAX-ACCESS  read-only
        STATUS      current
        DESCRIPTION
                "Total number of bytes received in fully reassembled 
                frames. It also counts the number of packets received
                without FR fragmentation header (i.e.in un-fragmentated
                pkts)."
        ::= { qtechfrFragEntry 12}

qtechfrFragPreOutPkts OBJECT-TYPE
        SYNTAX      Counter32
        UNITS       "packets"
        MAX-ACCESS  read-only
        STATUS      current
        DESCRIPTION
                "Total number of frames fragmented and trasmitted. It 
                also counts the number of packets trasmitted without FR
                fragmentation header (i.e. in un-fragmentated pkts)."
        ::= { qtechfrFragEntry 13}

qtechfrFragPreOutOctets OBJECT-TYPE
        SYNTAX      Counter32
        UNITS       "octets"
        MAX-ACCESS  read-only
        STATUS      current
        DESCRIPTION
                "Total number of bytes transmitted in fragmented frames.
                It also counts the number of bytes trasmitted in frames
                without FR fragmentation header (i.e. in un-fragmentated
                pkts)."
        ::= { qtechfrFragEntry 14}

qtechfrFragDroppedReAssembledInPkts OBJECT-TYPE
        SYNTAX      Counter32
        UNITS       "packets"
        MAX-ACCESS  read-only
        STATUS      current
        DESCRIPTION
                "Number of received fragments dropped for reasons such
                as : running out of memory, receiving segments out of 
                sequence, receiving an unexpected frame with a B bit 
                set, timing out on a reassembling frame." 
        ::= { qtechfrFragEntry 15}

qtechfrFragDroppedFragmentedOutPkts OBJECT-TYPE
        SYNTAX      Counter32
        UNITS       "packets"
        MAX-ACCESS  read-only
        STATUS      current
        DESCRIPTION
                "Number of fragments dropped because of running 
                out of memory." 
        ::= { qtechfrFragEntry 16}

qtechfrFragTimeoutsIn OBJECT-TYPE
        SYNTAX      INTEGER (0..1000)
        MAX-ACCESS  read-only
        STATUS      current
        DESCRIPTION
                "Number of reassemble timer timeouts for this circuit.
                A frame requiring more than two minutes to fully 
                reassemble is dropped and timeout will be incremented
                by one." 
        ::= { qtechfrFragEntry 17}

qtechfrFragOutOfSeqFragPkts OBJECT-TYPE
        SYNTAX      Counter32
        UNITS       "packets"
        MAX-ACCESS  read-only
        STATUS      current
        DESCRIPTION
                "Indicates the total number of packets received with an
                unexpected sequence number. All fragments being 
                reassembled are dropped. Start a new packet with the
                received segment only if the B bit is set on the 
                segment. Otherwise the new segment is also dropped." 
        ::= { qtechfrFragEntry 18}

qtechfrFragUnexpectedBBitSetPkts OBJECT-TYPE
        SYNTAX      Counter32
        UNITS       "packets"
        MAX-ACCESS  read-only
        STATUS      current
        DESCRIPTION
                "Number of fragments received in this circuit with 
                a B bit set. All fragments being reassembled are dropped
                and a new packet is started with this segment." 
        ::= { qtechfrFragEntry 19}

qtechfrFragSeqMissedPkts OBJECT-TYPE
        SYNTAX      Counter32
        UNITS       "packets"
        MAX-ACCESS  read-only
        STATUS      current
        DESCRIPTION
                "Number of fragments received in this circuit with 
                skipped sequence number."
        ::= { qtechfrFragEntry 20}

qtechfrFragInterleavedOutPkts OBJECT-TYPE
        SYNTAX      Counter32
        UNITS       "packets"
        MAX-ACCESS  read-only
        STATUS      current
        DESCRIPTION
                "Number of packets that have been interleaved between 
                segments." 
        ::= { qtechfrFragEntry 21}

-- end Fragmentation sub-group }


-- Connect sub-group {

qtechfrConnectionTable OBJECT-TYPE
        SYNTAX      SEQUENCE OF QtechfrConnectionEntry
        MAX-ACCESS  not-accessible
        STATUS      current
        DESCRIPTION
                "Table of Frame Relay/Frame Relay and Frame Relay/ATM
                Network/Service Interworking connection information. 
                These are specific to Qtech's implementation."
        ::= { qtechfrConnectionObjs 1 }

qtechfrConnectionEntry OBJECT-TYPE
        SYNTAX      QtechfrConnectionEntry
        MAX-ACCESS  not-accessible
        STATUS      current
        DESCRIPTION
                "Each entry of the table contains information of a
                connection that is established for Frame Relay/Frame 
                Relay and Frame Relay/ATM Network/Service Interworking."
        INDEX { frCircuitIfIndex, frCircuitDlci}
        ::= { qtechfrConnectionTable 1 }

QtechfrConnectionEntry ::=
        SEQUENCE {
            qtechfrConnName               DisplayString,
            qtechfrConnID                 INTEGER,
            qtechfrConnState              DisplayString,
            qtechfrConnSegment1Name       DisplayString,
            qtechfrConnSegment1VCGroup    DisplayString,
            qtechfrConnSegment1Dlci       DlciNumber,
            qtechfrConnSegment2Name       DisplayString, 
            qtechfrConnSegment2Vpi        INTEGER,
            qtechfrConnSegment2Vci        INTEGER,
            qtechfrConnServiceTranslation INTEGER,
            qtechfrConnFrSscsDlci         DlciNumber,
            qtechfrConnEfciBit            INTEGER,
            qtechfrConnDeBit              INTEGER,
            qtechfrConnClpBit             INTEGER
        }

qtechfrConnName OBJECT-TYPE
        SYNTAX       DisplayString
        MAX-ACCESS   read-only
        STATUS       current        
        DESCRIPTION
               "The textual name of a for FR/FR or FR/ATM  
               Network/Service Interworking connection."
        ::= { qtechfrConnectionEntry 1 }

qtechfrConnID OBJECT-TYPE
        SYNTAX       INTEGER (1..2000)
        MAX-ACCESS   read-only
        STATUS       current
        DESCRIPTION
               "The numerical identifier of a FR/FR or FR/ATM  
               Network/Service Interworking connection."
        ::= { qtechfrConnectionEntry 2 }

qtechfrConnState OBJECT-TYPE
        SYNTAX      DisplayString
        MAX-ACCESS  read-only
        STATUS      current
        DESCRIPTION
                "Status of a FR/FR or FR/ATM  Network/Service 
                Interworking connection."
        ::= { qtechfrConnectionEntry 3}

qtechfrConnSegment1Name OBJECT-TYPE
        SYNTAX       DisplayString
        MAX-ACCESS   read-only
        STATUS       current
        DESCRIPTION
               "The textual name used to identify the first segment of 
               a FR/FR or FR/ATM  Network/Service Interworking 
               connection."
        ::= { qtechfrConnectionEntry 4}

qtechfrConnSegment1VCGroup OBJECT-TYPE
        SYNTAX       DisplayString
        MAX-ACCESS   read-only
        STATUS       current
        DESCRIPTION
               "The textual name used to identify the VC-Group in the
               first segment of a Frame Relay/ATM  Network Interworking
               (FRF.5)connection. 
               This field is not applicabe in case of,
                        FRF.8 (Frame Relay/ATM  Service Interworking)
                        and
                        FR-FR connectione. "
       ::= { qtechfrConnectionEntry 5}

qtechfrConnSegment1Dlci OBJECT-TYPE
        SYNTAX       DlciNumber
        MAX-ACCESS   read-only
        STATUS       current
        DESCRIPTION
               "The DLCI used as the first segment of a FR-FR or FR-ATM
               Network/Service Interworking connection."
        ::= { qtechfrConnectionEntry 6}

qtechfrConnSegment2Name OBJECT-TYPE
        SYNTAX       DisplayString
        MAX-ACCESS   read-only
        STATUS       current
        DESCRIPTION
               "The interface on which second segment of a FR-FR or 
               FR-ATM  Network/Service Interworking connection is 
               configured."
        ::= { qtechfrConnectionEntry 7}

qtechfrConnSegment2Vpi OBJECT-TYPE
        SYNTAX       INTEGER (0..4095)
        MAX-ACCESS   read-only
        STATUS       current
        DESCRIPTION
               "The value of  VPI, in the ATM connection, used as the
               second segment of a FR-ATM  Network/Service Interworking
               connection. In case of FR-FR connection, the same will 
               be used to display the DLCI used as the second segment."
        ::= { qtechfrConnectionEntry 8}

qtechfrConnSegment2Vci OBJECT-TYPE
        SYNTAX       INTEGER (0..4095)
        MAX-ACCESS   read-only
        STATUS       current
        DESCRIPTION
               "The value of  VCI, in the ATM connection, used as the
               second segment of a FR-ATM  Network/Service Interworking
               connection. In case of FR-FR connection, this is not 
               supported."
       ::= { qtechfrConnectionEntry 9}

qtechfrConnServiceTranslation OBJECT-TYPE
        SYNTAX       INTEGER {
                        serviceTranslationEnabled(1),
                        serviceTranslationNotEnabled(2)
                     }
        MAX-ACCESS   read-only
        STATUS       current
        DESCRIPTION
               "Shows whether Service Translation Mode is supported or
               not. Translation Mode is the interworking of 
               internetworking (routed and/or bridged) protocols used 
               in FR-ATM  Service PVC Interworking(FRF.8).
               This is not supported in case of FRF.5 (FR-ATM network
               Interworking) and FR-FR connections."
       ::= { qtechfrConnectionEntry 10}

qtechfrConnFrSscsDlci OBJECT-TYPE
        SYNTAX       DlciNumber
        MAX-ACCESS   read-only
        STATUS       current        
        DESCRIPTION
               "The DLCI value used at the FR-SSCS layer. This is one of
               connection multiplexing methods used in Frame Relay/ATM  
               Network Interworking.
               Not supported in case of FRF.8 (FR-ATM Service PVC 
               Interworking) and FR-FR connections"
        ::= { qtechfrConnectionEntry 11}

qtechfrConnEfciBit OBJECT-TYPE
        SYNTAX       INTEGER  {
                         mapFecn(1),
                         notMapFecn(2)
                     }
        MAX-ACCESS   read-only
        STATUS       current
        DESCRIPTION
               "Shows whether the FECN field in the FR frame is mapped 
               to the ATM EFCI field of every cell generated out of the 
               FR frame. This is used to indicate congestion in FR to
               ATM direction in case of Frame Relay/ATM  Service PVC 
               Interworking.
               Not supported in FRF.5 (Frame Relay/ATM Network 
               Interworking and FR-FR connections."
::= { qtechfrConnectionEntry 12}

qtechfrConnDeBit OBJECT-TYPE
        SYNTAX       INTEGER {
                         noMapClp(1),
                         mapClp(2),
                         setDe0(3),
                         setDe1(4)
                     }
        MAX-ACCESS   read-only
        STATUS       current
        DESCRIPTION
               "The method of operation for loss priority mapping in the
               B-ISDN to FR direction..
               Not supported in case of FR-FR connection."
        ::= { qtechfrConnectionEntry 13}

qtechfrConnClpBit OBJECT-TYPE
        SYNTAX  INTEGER {
                  setClpTo0AndCopyDeToFrsscsDe(1),
                  setClpTo1AndCopyDeToFrsscsDe(2),
                  copyDeToFrsscsDeAndClp(3),
                  copyDeToClp(4),
                  setClp1(5),
                  setClp0(6)
                }
        MAX-ACCESS   read-only
        STATUS       current
        DESCRIPTION
               "The method of operation used to map loss priority
               mapping in the FR to ATM direction.
               Not supported in case of FR-FR connection."
        ::= { qtechfrConnectionEntry 14}

-- end Conn subgroup }

qtechFrMIBConformance OBJECT IDENTIFIER ::= { qtechFrameRelayMIB 3 }
qtechFrMIBCompliances OBJECT IDENTIFIER ::= { qtechFrMIBConformance 1 }
qtechFrMIBGroups      OBJECT IDENTIFIER ::= { qtechFrMIBConformance 2 }

qtechFrMIBCompliance MODULE-COMPLIANCE
        STATUS  obsolete  -- obsoleted by qtechFrMIBCompliancesRev2
        DESCRIPTION
                "The compliance statement for entities which implement
                this Qtech Frame Relay MIB."
        MODULE  -- this module
                MANDATORY-GROUPS { qtechFrMIBGroup }
        ::= { qtechFrMIBCompliances 1 }

qtechFrMIBCompliancesRev1 MODULE-COMPLIANCE
        STATUS  obsolete  -- obsoleted by qtechFrMIBCompliancesRev2
        DESCRIPTION
                "The compliance statement for entities which implement
                this Qtech Frame Relay MIB."
        MODULE  -- this module
                MANDATORY-GROUPS { qtechFrMIBGroupRev1 }
        ::= { qtechFrMIBCompliances 2 }

qtechFrMIBCompliancesRev2 MODULE-COMPLIANCE
        STATUS  obsolete  -- obsoleted by qtechFrMIBCompliancesRev3 
        DESCRIPTION
                "The compliance statement for entities which implement
                this Qtech Frame Relay MIB."
        MODULE  -- this module
                MANDATORY-GROUPS { qtechFrLmiMIBGroup, 
                                   qtechFrCircuitMIBGroup,
                                   qtechExtCircuitMIBGroup,
                                   qtechFrTsMIBGroup,
                                   qtechFrMapMIBGroup,
                                   qtechFrSvcMIBGroup }
        ::= { qtechFrMIBCompliances 3 }

qtechFrMIBCompliancesRev3 MODULE-COMPLIANCE
        STATUS  deprecated  -- deprecated by qtechFrMIBCompliancesRev4
        DESCRIPTION
                "The compliance statement for entities which implement
                this Qtech Frame Relay MIB."
        MODULE  -- this module
                MANDATORY-GROUPS { qtechFrLmiMIBGroup,
                                   qtechFrCircuitMIBGroup,
                                   qtechExtCircuitMIBGroup,
                                   qtechFrTsMIBGroup,
                                   qtechFrMapMIBGroup,
                                   qtechFrSvcMIBGroup,
                                   qtechFrElmiMIBGroup}
        ::= { qtechFrMIBCompliances 4 }

qtechFrMIBCompliancesRev4 MODULE-COMPLIANCE
        STATUS  current
        DESCRIPTION
                "The compliance statement for entities which implement
                this qtech Frame Relay MIB."
        MODULE  -- this module
                MANDATORY-GROUPS { qtechFrLmiMIBGroup,
                                   qtechFrCircuitMIBGroup,
                                   qtechExtCircuitMIBGroup1,
                                   qtechFrTsMIBGroup,
                                   qtechFrMapMIBGroup,
                                   qtechFrSvcMIBGroup,
                                   qtechFrElmiMIBGroup1,
                                   qtechFrFragMIBGroup,
                                   qtechFrConnMIBGroup}
        ::= { qtechFrMIBCompliances 5 }

-- units of conformance:

qtechFrMIBGroup OBJECT-GROUP
        OBJECTS {
            qtechfrLmiLinkstatus,
            qtechfrLmiLinkType,
            qtechfrLmiEnquiryIns,
            qtechfrLmiEnquiryOuts,
            qtechfrLmiStatusIns,
            qtechfrLmiStatusOuts,
            qtechfrLmiUpdateStatusIns,
            qtechfrLmiUpdateStatusOuts,
            qtechfrLmiStatusTimeouts,
            qtechfrLmiStatusEnqTimeouts,
            qtechfrLmiN392Dce,
            qtechfrLmiN393Dce,
            qtechfrLmiT392Dce,
            qtechfrCircuitDEins,
            qtechfrCircuitDEouts,
            qtechfrCircuitDropPktsOuts,
            qtechfrCircuitType,
            qtechfrExtCircuitIfName,
            qtechfrExtCircuitIfType,
            qtechfrExtCircuitSubifIndex,
            qtechfrExtCircuitMapStatus,
            qtechfrExtCircuitCreateType,
            qtechfrExtCircuitMulticast,
            qtechfrExtCircuitRoutedDlci,
            qtechfrExtCircuitRoutedIf,
            qtechfrMapIndex,
            qtechfrMapProtocol,
            qtechfrMapAddress,
            qtechfrMapType,
            qtechfrMapEncaps,
            qtechfrMapBroadcast,
            qtechfrMapPayloadCompress,
            qtechfrMapTcpHdrCompress,
            qtechfrSvcAddrLocal,
            qtechfrSvcAddrRemote,
            qtechfrSvcThroughputIn,
            qtechfrSvcMinThruputOut,
            qtechfrSvcMinThruputIn,
            qtechfrSvcCommitBurstIn,
            qtechfrSvcExcessBurstIn,
            qtechfrSvcIdleTime
        }
        STATUS  deprecated       -- obsoleted by qtechFrMIBGroupRev1
        DESCRIPTION
                "The compliance statement for entities which implement
                this Qtech Frame Relay MIB."
        ::= { qtechFrMIBGroups 1 }

qtechFrMIBGroupRev1 OBJECT-GROUP
        OBJECTS {
            qtechfrLmiLinkstatus,
            qtechfrLmiLinkType,
            qtechfrLmiEnquiryIns,
            qtechfrLmiEnquiryOuts,
            qtechfrLmiStatusIns,
            qtechfrLmiStatusOuts,
            qtechfrLmiUpdateStatusIns,
            qtechfrLmiUpdateStatusOuts,
            qtechfrLmiStatusTimeouts,
            qtechfrLmiStatusEnqTimeouts,
            qtechfrLmiN392Dce,
            qtechfrLmiN393Dce,
            qtechfrLmiT392Dce,
            qtechfrCircuitDEins,
            qtechfrCircuitDEouts,
            qtechfrCircuitDropPktsOuts,
            qtechfrCircuitType,
            qtechfrExtCircuitIfName,
            qtechfrExtCircuitIfType,
            qtechfrExtCircuitSubifIndex,
            qtechfrExtCircuitMapStatus,
            qtechfrExtCircuitCreateType,
            qtechfrExtCircuitMulticast,
            qtechfrExtCircuitRoutedDlci,
            qtechfrExtCircuitRoutedIf,
            qtechfrExtCircuitUncompressIns,  
            qtechfrExtCircuitUncompressOuts,
            qtechfrMapIndex,
            qtechfrMapProtocol,
            qtechfrMapAddress,
            qtechfrMapType,
            qtechfrMapEncaps,
            qtechfrMapBroadcast,
-- removed  qtechfrMapPayloadCompress, obsoleted by qtechfrMapPayloadCompressType
            qtechfrMapTcpHdrCompress,
            qtechfrMapRtpHdrCompress,          
            qtechfrMapPayloadCompressType,    
            qtechfrSvcAddrLocal,
            qtechfrSvcAddrRemote,
            qtechfrSvcThroughputIn,
            qtechfrSvcMinThruputOut,
            qtechfrSvcMinThruputIn,
            qtechfrSvcCommitBurstIn,
            qtechfrSvcExcessBurstIn,
            qtechfrSvcIdleTime
        }
        STATUS  deprecated       
        DESCRIPTION
                "A collection of objects providing router's
                Frame Relay configuration and statistics
                information that are additional to the IETF
                standard Frame Relay DTE MIB."
        ::= { qtechFrMIBGroups 2 }

qtechFrLmiMIBGroup    OBJECT-GROUP
        OBJECTS { 
            qtechfrLmiLinkstatus, qtechfrLmiLinkType, qtechfrLmiEnquiryIns,
            qtechfrLmiEnquiryOuts, qtechfrLmiStatusIns, qtechfrLmiStatusOuts,
            qtechfrLmiUpdateStatusIns, qtechfrLmiUpdateStatusOuts,
            qtechfrLmiStatusTimeouts, qtechfrLmiStatusEnqTimeouts,
            qtechfrLmiN392Dce, qtechfrLmiN393Dce, qtechfrLmiT392Dce
        }   
        STATUS current
        DESCRIPTION
                "A collection of objects providing router's
                 Frame Relay LMI configuration and statistics
                 information either supplemental to the 
                 frDlcmiTable of RFC 1315 or specific to qtech's 
                 implementation."
        ::= { qtechFrMIBGroups 3 }
 
qtechFrCircuitMIBGroup    OBJECT-GROUP
        OBJECTS { 
            qtechfrCircuitDEins, qtechfrCircuitDEouts,
            qtechfrCircuitDropPktsOuts, qtechfrCircuitType
        }   
        STATUS current
        DESCRIPTION
                "A collection of objects providing information of a
                circuit that are not included in frCircuitTable of
                RFC1315 but are generic to Frame Relay."
        ::= { qtechFrMIBGroups 4 }

qtechExtCircuitMIBGroup    OBJECT-GROUP
        OBJECTS { 
            qtechfrExtCircuitIfName, qtechfrExtCircuitIfType,
            qtechfrExtCircuitSubifIndex, qtechfrExtCircuitMapStatus,
            qtechfrExtCircuitCreateType, qtechfrExtCircuitMulticast,
            qtechfrExtCircuitRoutedDlci, qtechfrExtCircuitRoutedIf,
            qtechfrExtCircuitUncompressIns, qtechfrExtCircuitUncompressOuts,
            qtechfrExtCircuitFECNOuts, qtechfrExtCircuitBECNOuts,
            qtechfrExtCircuitMinThruputOut, qtechfrExtCircuitMinThruputIn,
            qtechfrExtCircuitBcastPktOuts, qtechfrExtCircuitBcastByteOuts,
            qtechfrExtCircuitBandwidth
        }   
        STATUS  deprecated       
        DESCRIPTION
                "A collection of objects that provide qtech 
                implementation specific FR circuit information. 
                This is a qtech extension for the frCircuitTable 
                of RFC 1315."
        ::= { qtechFrMIBGroups 5 }

qtechExtCircuitMIBGroup1    OBJECT-GROUP
        OBJECTS {
            qtechfrExtCircuitIfName, qtechfrExtCircuitIfType,
            qtechfrExtCircuitSubifIndex, qtechfrExtCircuitMapStatus,
            qtechfrExtCircuitCreateType, qtechfrExtCircuitMulticast,
            qtechfrExtCircuitRoutedDlci, qtechfrExtCircuitRoutedIf,
            qtechfrExtCircuitUncompressIns, qtechfrExtCircuitUncompressOuts,
            qtechfrExtCircuitFECNOuts, qtechfrExtCircuitBECNOuts,
            qtechfrExtCircuitMinThruputOut, qtechfrExtCircuitMinThruputIn,
            qtechfrExtCircuitBcastPktOuts, qtechfrExtCircuitBcastByteOuts,
            qtechfrExtCircuitBandwidth, qtechfrExtCircuitTxDataRate,
            qtechfrExtCircuitTxPktRate, qtechfrExtCircuitRcvDataRate,
            qtechfrExtCircuitRcvPktRate
        }
        STATUS current
        DESCRIPTION
                "A collection of objects that provide qtech
                implementation specific FR circuit information.
                This is a qtech extension for the frCircuitTable
                of RFC 1315."
        ::= { qtechFrMIBGroups 13 }


qtechFrTsMIBGroup    OBJECT-GROUP
        OBJECTS { 
            qtechfrExtCircuitShapeByteLimit, qtechfrExtCircuitShapeInterval,
            qtechfrExtCircuitShapeByteIncrement, qtechfrExtCircuitShapePkts,
            qtechfrExtCircuitShapeBytes, qtechfrExtCircuitShapePktsDelay,
            qtechfrExtCircuitShapeBytesDelay, qtechfrExtCircuitShapeActive,
            qtechfrExtCircuitShapeAdapting
        }   
        STATUS current
        DESCRIPTION
                "A collection of objects that provide information
                about Frame Relay Traffic Shaping. These are 
                additional to the IETF standard Frame Relay DTE MIB." 
        ::= { qtechFrMIBGroups 6 }

qtechFrMapMIBGroup    OBJECT-GROUP
        OBJECTS { 
            qtechfrMapIndex, qtechfrMapProtocol, qtechfrMapAddress,
            qtechfrMapType, qtechfrMapEncaps, qtechfrMapBroadcast,
            qtechfrMapTcpHdrCompress, qtechfrMapRtpHdrCompress,         
            qtechfrMapPayloadCompressType  
        }   
        STATUS current
        DESCRIPTION
                "A collection of objects to provide mapping 
                information of a Frame Relay virtual circuit.
                These are additional to the IETF standard 
                Frame Relay DTE MIB."
        ::= { qtechFrMIBGroups 7 }

qtechFrSvcMIBGroup    OBJECT-GROUP
        OBJECTS { 
            qtechfrSvcAddrLocal,
            qtechfrSvcAddrRemote,
            qtechfrSvcThroughputIn,
            qtechfrSvcCommitBurstIn,
            qtechfrSvcExcessBurstIn,
            qtechfrSvcIdleTime
        }   
        STATUS current
        DESCRIPTION
                "A collection of objects to provide circuit
                information specific to a Frame Relay Switched
                Virtual Circuit.This is in addition to the IETF 
                standard Frame Relay DTE MIB."        
        ::= { qtechFrMIBGroups 8 }

qtechFrElmiMIBGroup    OBJECT-GROUP
        OBJECTS {
            qtechfrElmiIpAddr, qtechfrElmiArStatus, qtechfrElmiRemoteStatus,
            qtechfrElmiNeighborArStatus, qtechfrElmiNeighborIpAddress,
            qtechfrElmiNeighborIfIndex, qtechfrElmiNeighborVendorName,
            qtechfrElmiNeighborPlatformName, qtechfrElmiNeighborDeviceName
        }
        STATUS deprecated
        DESCRIPTION
                "A collection of objects providing router's
                ELMI information."
        ::= { qtechFrMIBGroups 9 }

qtechFrElmiMIBGroup1    OBJECT-GROUP
        OBJECTS {
            qtechfrElmiIpAddr, qtechfrElmiArStatus, qtechfrElmiRemoteStatus,
            qtechfrElmiNeighborArStatus, qtechfrElmiNeighborIpAddress,
            qtechfrElmiNeighborIfIndex, qtechfrElmiNeighborVendorName,
            qtechfrElmiNeighborPlatformName, qtechfrElmiNeighborDeviceName,
            qtechfrElmiLinkStatus
        }
        STATUS current
        DESCRIPTION
                "A collection of objects providing router's
                ELMI information."
        ::= { qtechFrMIBGroups 10 }

qtechFrFragMIBGroup    OBJECT-GROUP
        OBJECTS {
            qtechfrFragSize, qtechfrFragType, qtechfrFragInPkts, qtechfrFragOutPkts,
            qtechfrFragInOctets, qtechfrFragOutOctets, qtechfrFragNotInPkts,
            qtechfrFragNotOutPkts, qtechfrFragNotInOctets, qtechfrFragNotOutOctets,
            qtechfrFragAssembledInPkts, qtechfrFragAssembledInOctets, 
            qtechfrFragPreOutPkts, qtechfrFragPreOutOctets,
            qtechfrFragDroppedReAssembledInPkts, 
            qtechfrFragDroppedFragmentedOutPkts,
            qtechfrFragTimeoutsIn, qtechfrFragOutOfSeqFragPkts,
            qtechfrFragUnexpectedBBitSetPkts, qtechfrFragSeqMissedPkts, 
            qtechfrFragInterleavedOutPkts  
        }
        STATUS current
        DESCRIPTION
                "A collection of objects providing router's
                fragmentation information."
        ::= { qtechFrMIBGroups 11 }
            
qtechFrConnMIBGroup    OBJECT-GROUP
        OBJECTS {
            qtechfrConnName, qtechfrConnID, qtechfrConnState, qtechfrConnSegment1Name,
            qtechfrConnSegment1VCGroup, qtechfrConnSegment1Dlci,  
            qtechfrConnSegment2Name, qtechfrConnSegment2Vpi,
            qtechfrConnSegment2Vci, qtechfrConnServiceTranslation, 
            qtechfrConnFrSscsDlci, qtechfrConnEfciBit,
            qtechfrConnDeBit, qtechfrConnClpBit        
        }
        STATUS current
        DESCRIPTION
                "A collection of objects providing router's
                fragmentation information."
        ::= { qtechFrMIBGroups 12 }
            

END

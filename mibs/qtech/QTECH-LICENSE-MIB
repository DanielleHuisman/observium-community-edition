-- *****************************************************************
-- QTECH-LICENSE-MIB.mib:  Qtech License MIB
--
-- Oct 2009, jiangxh
--
-- Copyright (c) 2009 by Qtech Networks Co.,Ltd.
-- All rights reserved.
-- *****************************************************************
--

QTECH-LICENSE-MIB DEFINITIONS ::= BEGIN

IMPORTS
        MODULE-IDENTITY,
        OBJECT-TYPE,
        Integer32
                FROM SNMPv2-SMI
        DisplayString
                FROM SNMPv2-TC
        MODULE-COMPLIANCE,
        OBJECT-GROUP
                FROM SNMPv2-CONF
        qtechMgmt
                FROM QTECH-SMI;

qtechLicenseMIB MODULE-IDENTITY
        LAST-UPDATED "200909180000Z"
        ORGANIZATION "Qtech Networks Co.,Ltd."
        CONTACT-INFO
            " 
        Tel: 4008-111-000

        E-mail: service@qtech.com.cn"
        DESCRIPTION
                "This module defines qtech license mibs."
        REVISION      "200909180000Z"
        DESCRIPTION
                "Initial version of this MIB module."
        ::= { qtechMgmt 57}

qtechLicenseMIBObjects OBJECT IDENTIFIER ::= { qtechLicenseMIB 1 }

qtechShowLicense OBJECT-TYPE
    SYNTAX      Integer32
    MAX-ACCESS  read-only
    STATUS      current
    DESCRIPTION
            "This object represents the support of AP nums."
    ::= { qtechLicenseMIBObjects 1 }    
    
qtechLicenseTable OBJECT-TYPE
  SYNTAX      SEQUENCE OF QtechLicenseEntry
  MAX-ACCESS  not-accessible
  STATUS      current
  DESCRIPTION
    "A table of license entries. Each of the
     objects indicate the license configured."
  ::= { qtechLicenseMIBObjects 2 }

qtechLicenseEntry OBJECT-TYPE
  SYNTAX      QtechLicenseEntry
  MAX-ACCESS  not-accessible
  STATUS      current
  DESCRIPTION
    "An entry in the license table."
  INDEX { qtechLicenseIndex }
  ::= { qtechLicenseTable 1 }

QtechLicenseEntry ::=
  SEQUENCE {
    qtechLicenseIndex  	Integer32,
    qtechLicenseString   DisplayString,
    qtechLicenseValue   	Integer32
  }
    
qtechLicenseIndex OBJECT-TYPE
    SYNTAX        Integer32
    MAX-ACCESS    not-accessible
    STATUS        current
    DESCRIPTION
        "An index that uniquely represents a license."
    ::= { qtechLicenseEntry 1 }
    
qtechLicenseString OBJECT-TYPE
    SYNTAX        DisplayString
    MAX-ACCESS    read-write
    STATUS        current
    DESCRIPTION
        "The license configured."
    ::= { qtechLicenseEntry 2 } 
   
qtechLicenseValue OBJECT-TYPE
    SYNTAX        Integer32
    MAX-ACCESS    read-only
    STATUS        current
    DESCRIPTION
        "This is the support numbers of APs for the license."
    ::= { qtechLicenseEntry 3 }

qtechLicenseMIBConformance OBJECT IDENTIFIER ::= { qtechLicenseMIB 2 }
qtechLicenseMIBCompliances OBJECT IDENTIFIER ::= { qtechLicenseMIBConformance 1 }
qtechLicenseMIBGroups      OBJECT IDENTIFIER ::= { qtechLicenseMIBConformance 2 }


-- compliance statements

qtechLicenseMIBCompliance MODULE-COMPLIANCE
        STATUS  current
        DESCRIPTION
                "The compliance statement for entities which implement
                the Qtech License MIB"
        MODULE  -- this module
                MANDATORY-GROUPS { qtechLicenseMIBGroup
                }
        ::= { qtechLicenseMIBCompliances 1 }
                
-- units of conformance

qtechLicenseMIBGroup OBJECT-GROUP
        OBJECTS {
               qtechShowLicense, 
               qtechLicenseString,
               qtechLicenseValue 
        }
        STATUS  current
        DESCRIPTION
                "A collection of objects providing license information and
                opertion to a Qtech agent."
        ::= { qtechLicenseMIBGroups 1 } 

END

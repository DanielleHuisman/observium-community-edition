QTECH-MASTER-MIB DEFINITIONS ::= BEGIN

IMPORTS
    MODULE-IDENTITY, enterprises              FROM SNMPv2-SMI;

    qtech MODULE-IDENTITY
        LAST-UPDATED    "0008290000Z"  -- August 29, 2000
        ORGANIZATION    "QTECH LLC."
        CONTACT-INFO    "Basil Budko
                         E-mail: budko@qtech.ru"

        DESCRIPTION     "QTECH Master MIB OID defines and documentation."

        REVISION        "0008290000Z"  -- August 29, 2000
        DESCRIPTION     "Initial MIB creation."

        ::= { enterprises 27514 }
    
-- QTECH Products
dataCom           OBJECT IDENTIFIER ::= {qtech 1} 


-- DataCom Products
gbn             OBJECT IDENTIFIER ::= {dataCom 2 } 
switch			OBJECT IDENTIFIER ::= {dataCom 3}

-- VDSL Products

-- GBN Major MIB Categories
    gbnPlatform     OBJECT IDENTIFIER ::= { gbn 1 }     
    gbnDevice       OBJECT IDENTIFIER ::= { gbn 2 }     
    gbnService      OBJECT IDENTIFIER ::= { gbn 3 }     
    gbnL2           OBJECT IDENTIFIER ::= { gbn 4 }     
    gbnL3           OBJECT IDENTIFIER ::= { gbn 5 }
    gbnLS           OBJECT IDENTIFIER ::= { gbn 6 } 

    gbnServiceAAA      OBJECT IDENTIFIER ::= { gbnService 1 } 
    rmonMib            OBJECT IDENTIFIER ::= { gbnService 2}--gbnServiceRMON

-- Switch Products
QSW_2724         OBJECT IDENTIFIER ::= { switch 11 }
QSW_3924         OBJECT IDENTIFIER ::= { switch 18 }


-- EZVoice Products
--
-- END of QTECH-MASTER-MIB
--

END

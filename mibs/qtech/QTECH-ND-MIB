-- *****************************************************************
-- QTECH-ND-MIB.mib:  Qtech ND MIB file
--
--  2013.12.30, huangguohua@qtech.com.cn
--
-- Copyright (c) 2013 by Qtech Networks .
-- All rights reserved.
-- 
-- *****************************************************************
--

QTECH-ND-MIB DEFINITIONS ::= BEGIN

IMPORTS
        MODULE-IDENTITY,
        OBJECT-TYPE,
        NOTIFICATION-TYPE
                FROM SNMPv2-SMI
        Integer32
                FROM SNMPv2-SMI        
        MODULE-COMPLIANCE,
        OBJECT-GROUP,
        NOTIFICATION-GROUP
                FROM SNMPv2-CONF
        qtechMgmt
                FROM QTECH-SMI;

qtechNDMIB MODULE-IDENTITY
        LAST-UPDATED "201312300000Z"
        ORGANIZATION "Qtech Networks."
        CONTACT-INFO
                " 
                Tel: 4008-111-000

                E-mail: service@qtech.com.cn"
        DESCRIPTION
                "This module defines qtech ND mibs."
        REVISION      "201312300000Z"
        DESCRIPTION
                "Initial version of this MIB module."
        ::= { qtechMgmt 125}

qtechNDMIBObjects OBJECT IDENTIFIER ::= { qtechNDMIB 1 }     
          
   qtechNDTotalActiveNeighbors OBJECT-TYPE
        SYNTAX Counter32
        MAX-ACCESS read-only
        STATUS current
        DESCRIPTION
            "Total active neighbors This system have"
        ::= { qtechNDMIBObjects 1 }  
		
  qtechNDTotalActiveDynamicNeighbors OBJECT-TYPE
          SYNTAX Counter32
          MAX-ACCESS read-only
          STATUS current
          DESCRIPTION
            "Total active dynamic neighbors This system have"
          ::= { qtechNDMIBObjects 2} 
          
   qtechNDTotalStaticNeighbors OBJECT-TYPE
        SYNTAX Counter32
        MAX-ACCESS read-only
        STATUS current
        DESCRIPTION
            "Total static neighbors This system configure"
        ::= { qtechNDMIBObjects 3 } 
		
   qtechNDTotalActiveStaticNeighbors OBJECT-TYPE
        SYNTAX Counter32
        MAX-ACCESS read-only
        STATUS current
        DESCRIPTION
            "Total active static neighbors This system have"
        ::= { qtechNDMIBObjects 4 }        
                   

qtechNDMIBConformance OBJECT IDENTIFIER ::= { qtechNDMIB 2}
qtechNDMIBCompliances OBJECT IDENTIFIER ::= { qtechNDMIBConformance 1 }
qtechNDMIBGroups      OBJECT IDENTIFIER ::= { qtechNDMIBConformance 2 }

-- compliance statements

qtechNDMIBCompliance MODULE-COMPLIANCE
        STATUS  current
        DESCRIPTION
                "The compliance statement for entities which implement
                the Qtech ND MIB"
        MODULE  -- this module
                MANDATORY-GROUPS { 
                        qtechNDObjectsGroup
                 }
         ::= { qtechNDMIBCompliances 1 }
        
-- units of conformance

qtechNDObjectsGroup OBJECT-GROUP
       OBJECTS {
	       qtechNDTotalActiveNeighbors,
           qtechNDTotalActiveDynamicNeighbors,
		   qtechNDTotalStaticNeighbors,
		   qtechNDTotalActiveStaticNeighbors
       }
       STATUS  current
       DESCRIPTION
                "A collection of objects providing ND information to a
                Qtech agent."
       ::= { qtechNDMIBGroups 1 }       

END

-- *****************************************************************
-- QTECH-SMP-MIB.mib:  Qtech SMP MIB file
--
-- Sept 2004, Chenxin
--
-- Copyright (c) 2004 by Qtech Networks Co.,Ltd.
-- All rights reserved.
-- 
-- *****************************************************************
--

QTECH-SMP-MIB DEFINITIONS ::= BEGIN

IMPORTS
        MODULE-IDENTITY,
        OBJECT-TYPE,
        NOTIFICATION-TYPE,
        Unsigned32,
        Integer32,
        Gauge32,
        IpAddress
                FROM SNMPv2-SMI
        RowStatus,
        DisplayString,
        MacAddress,
        TruthValue
                FROM SNMPv2-TC
        MODULE-COMPLIANCE,
        OBJECT-GROUP
                FROM SNMPv2-CONF
        IfIndex,
        ConfigStatus
                FROM QTECH-TC
        qtechMgmt
                FROM QTECH-SMI
        Community
        	FROM QTECH-SNMP-AGENT-MIB
        VlanId
                FROM Q-BRIDGE-MIB        				
	InetAddressType,
	InetAddress
		FROM INET-ADDRESS-MIB;

qtechSMPMIB MODULE-IDENTITY
        LAST-UPDATED "200409090000Z"
        ORGANIZATION "Qtech Networks Co.,Ltd."
        CONTACT-INFO
                " 
                Tel: 4008-111-000 

                E-mail: service@qtech.com.cn"
        DESCRIPTION
                "This module defines the MIB security case requires. At present, this MIB could only be accessed by 
                the specified SMP Server." 
        REVISION      "200409090000Z"
        DESCRIPTION
                "Initial version of this MIB module."
        ::= { qtechMgmt 39}

qtechSMPMIBObjects OBJECT IDENTIFIER ::= { qtechSMPMIB 1 }

--
--  user management
--

qtechSMPServer OBJECT-TYPE
		SYNTAX IpAddress
    MAX-ACCESS  read-write
    STATUS      current
    DESCRIPTION
            "IP addresses for the SMP Server."  
    ::= { qtechSMPMIBObjects 1 }
    
qtechSMPServerKey OBJECT-TYPE
		SYNTAX Community
    MAX-ACCESS  read-write
    STATUS      current
    DESCRIPTION
            "Keys for the SMP Server." 
    ::= { qtechSMPMIBObjects 2 }    
    
qtechSMPEventSendSlice OBJECT-TYPE
    SYNTAX      Unsigned32
    MAX-ACCESS  read-write
    STATUS      current
    DESCRIPTION
            "The minimum interval of sending SU security event. The variable value must be less 
             than the one defined by qtechSMPHICheckInterval."
    ::= { qtechSMPMIBObjects 3 }    
    
qtechSMPPolicyDelete OBJECT-TYPE
    SYNTAX Integer32
    MAX-ACCESS read-write
    STATUS      current    
    DESCRIPTION
            "This variable value:
             0: No action is required; other values:Delete all policy information."
    ::= { qtechSMPMIBObjects 4 }  
        
qtechSMPPolicyChecksum OBJECT-TYPE
    SYNTAX OCTET STRING(SIZE(16))
    MAX-ACCESS read-only
    STATUS      current    
    DESCRIPTION
            "The checksum information set on the current SMP policy table."  
    ::= { qtechSMPMIBObjects 5 }     

qtechSMPPolicyTimeout OBJECT-TYPE
    SYNTAX     Unsigned32
    MAX-ACCESS read-write
    STATUS      current    
    DESCRIPTION
            "Timeout time of SMP policy."  
    ::= { qtechSMPMIBObjects 6 }    
    
qtechSMPPolicyGroupTable OBJECT-TYPE
        SYNTAX  SEQUENCE OF QtechSMPPolicyGroupEntry
        MAX-ACCESS  not-accessible
        STATUS  current
        DESCRIPTION
              "Security policy group."  
    ::= { qtechSMPMIBObjects 9}

qtechSMPPolicyGroupEntry OBJECT-TYPE
        SYNTAX  QtechSMPPolicyGroupEntry
        MAX-ACCESS  not-accessible
        STATUS  current
        DESCRIPTION
              "SMP policy group." 
        INDEX   {qtechSMPPolicyGroupIndex}
    ::= { qtechSMPPolicyGroupTable 1 }
 
    QtechSMPPolicyGroupEntry ::=
        SEQUENCE {
                qtechSMPPolicyGroupIndex
                       Unsigned32,        
                qtechSMPPolicyGroupCount
                       Unsigned32,
                qtechSMPPolicyGroupChecksum
                       OCTET STRING(SIZE(16)),           
                qtechSMPPolicyGroupStatus
                       RowStatus
      }

qtechSMPPolicyGroupIndex OBJECT-TYPE
        SYNTAX  Unsigned32
        MAX-ACCESS  read-only
        STATUS  current
        DESCRIPTION
              "Policy group index."
    ::= { qtechSMPPolicyGroupEntry 1 }

qtechSMPPolicyGroupCount OBJECT-TYPE
        SYNTAX       Unsigned32
        MAX-ACCESS   read-create
        STATUS       current
        DESCRIPTION
            "Policy count in the policy group." 
    ::= { qtechSMPPolicyGroupEntry 2 }
    
qtechSMPPolicyGroupChecksum OBJECT-TYPE
        SYNTAX OCTET STRING(SIZE(16))
        MAX-ACCESS   read-create
        STATUS       current
        DESCRIPTION
            "The sole identification in the policy group."  
    ::= { qtechSMPPolicyGroupEntry 3 }

qtechSMPPolicyGroupStatus OBJECT-TYPE
        SYNTAX       RowStatus
        MAX-ACCESS   read-create
        STATUS       current
        DESCRIPTION
            "The status of this conceptual row."
    ::= { qtechSMPPolicyGroupEntry 4 }
    
qtechSMPPolicyTable OBJECT-TYPE
        SYNTAX  SEQUENCE OF QtechSMPPolicyEntry
        MAX-ACCESS  not-accessible
        STATUS  current
        DESCRIPTION
              "Security policy table." 
    ::= { qtechSMPMIBObjects 8}

qtechSMPPolicyEntry OBJECT-TYPE
        SYNTAX  QtechSMPPolicyEntry
        MAX-ACCESS  not-accessible
        STATUS  current
        DESCRIPTION
              "SMP policy table."  
        INDEX   {qtechSMPGroupIndex,qtechSMPPolicyIndex}
    ::= { qtechSMPPolicyTable 1 }

    QtechSMPPolicyEntry ::=
        SEQUENCE {
                qtechSMPGroupIndex
                       Unsigned32,
                qtechSMPPolicyIndex
                       Unsigned32,        
                qtechSMPPolicyStatus
                       ConfigStatus,
                qtechSMPPolicyNumber
                       Unsigned32,
                qtechSMPPolicyInstallPort
                       IfIndex,           
                qtechSMPPolicyType
                       INTEGER,  
                qtechSMPPolicyContent
                       OCTET STRING,
                qtechSMPPolicyMask
                       OCTET STRING,
                qtechSMPPolicyName
                       DisplayString
      }

qtechSMPGroupIndex OBJECT-TYPE
        SYNTAX  Unsigned32
        MAX-ACCESS  read-only
        STATUS  current
        DESCRIPTION
              "The index of the policy group which the current policy is in." 
    ::= { qtechSMPPolicyEntry 1 }

qtechSMPPolicyIndex OBJECT-TYPE
        SYNTAX  Unsigned32
        MAX-ACCESS  read-only
        STATUS  current
        DESCRIPTION
              "The policy index." 
    ::= { qtechSMPPolicyEntry 2 }

qtechSMPPolicyStatus OBJECT-TYPE
        SYNTAX       ConfigStatus
        MAX-ACCESS   read-write
        STATUS       current
        DESCRIPTION
            "Entry state fields. For the detailed information, pls refer to QTECH-TC.mib."
    ::= { qtechSMPPolicyEntry 3 }
  
qtechSMPPolicyNumber OBJECT-TYPE
        SYNTAX  Unsigned32
        MAX-ACCESS  read-write
        STATUS  current
        DESCRIPTION
              "The policy sequence number."  
    ::= { qtechSMPPolicyEntry 4 }
    
qtechSMPPolicyInstallPort OBJECT-TYPE
        SYNTAX  IfIndex
        MAX-ACCESS  read-write
        STATUS  current
        DESCRIPTION
              "The index of port installed the policy." 
    ::= { qtechSMPPolicyEntry 5 }
    
qtechSMPPolicyType OBJECT-TYPE
        SYNTAX INTEGER{
        	hi-isolate(1),
        	isolate(2),
        	blocked(3),
        	addrBind(4)
        }
        MAX-ACCESS read-write
        STATUS current
        DESCRIPTION
            "The action of policy template. Hi-isolate application failure can be detected by HI only.
            isolate: isolation action; blocked: blocking action; addrBind: address-binding action. "
        ::= { qtechSMPPolicyEntry 6 }
        
qtechSMPPolicyContent OBJECT-TYPE
        SYNTAX OCTET STRING(SIZE(80))
        MAX-ACCESS read-write
        STATUS current
        DESCRIPTION
            "Content(80 bytes) of policy template."  
        ::= { qtechSMPPolicyEntry 7 }
        
qtechSMPPolicyMask OBJECT-TYPE
        SYNTAX OCTET STRING(SIZE(80))
        MAX-ACCESS read-write
        STATUS current
        DESCRIPTION
            "Mask information(80 bytes) of policy template." 
        ::= { qtechSMPPolicyEntry 8 }    
        
qtechSMPPolicyName OBJECT-TYPE
        SYNTAX       DisplayString(SIZE (0..32))
        MAX-ACCESS   read-write
        STATUS       current
        DESCRIPTION
            "Policy name fields."  
    ::= { qtechSMPPolicyEntry 9 }
    
qtechSMPFrameRelayTable OBJECT-TYPE
        SYNTAX  SEQUENCE OF QtechSMPFrameRelayEntry
        MAX-ACCESS  not-accessible
        STATUS  current
        DESCRIPTION
              "SMP message forward table." 
    ::= { qtechSMPMIBObjects 7}

qtechSMPFrameRelayEntry OBJECT-TYPE
        SYNTAX  QtechSMPFrameRelayEntry
        MAX-ACCESS  not-accessible
        STATUS  current
        DESCRIPTION
              "SMP message forward table."  
        INDEX   {qtechSMPFrameRelayIndex}
    ::= { qtechSMPFrameRelayTable 1 }

    QtechSMPFrameRelayEntry ::=
        SEQUENCE {
                qtechSMPFrameRelayIndex
                       Unsigned32,        
                qtechSMPFrameRelayContent
                       OCTET STRING,
                qtechSMPFrameRelayLength
                       Unsigned32,           
                qtechSMPFrameRelayDestPort
                		   IfIndex,
                qtechSMPFrameRelayDestVlan
                		   VlanId                                       		   
      }

qtechSMPFrameRelayIndex OBJECT-TYPE
        SYNTAX  Unsigned32
        MAX-ACCESS  read-only
        STATUS  current
        DESCRIPTION
              "SMP message forward table index."   
    ::= { qtechSMPFrameRelayEntry 1 }
    
qtechSMPFrameRelayContent OBJECT-TYPE
        SYNTAX OCTET STRING(SIZE(0..1024))
        MAX-ACCESS read-write
        STATUS current
        DESCRIPTION
            "SMP message content with maximal 1024 bytes." 
    ::= { qtechSMPFrameRelayEntry 2 }
    
qtechSMPFrameRelayLength OBJECT-TYPE
    SYNTAX Unsigned32
    MAX-ACCESS read-write
    STATUS      current    
    DESCRIPTION
            "SMP message length."  
    ::= { qtechSMPFrameRelayEntry 3 } 

qtechSMPFrameRelayDestPort OBJECT-TYPE
        SYNTAX  IfIndex
        MAX-ACCESS  read-write
        STATUS  current
        DESCRIPTION
              "The index of destination port SMP messages are sent to." 
    ::= { qtechSMPFrameRelayEntry 4 }
    
qtechSMPFrameRelayDestVlan OBJECT-TYPE
        SYNTAX  VlanId
        MAX-ACCESS  read-write
        STATUS  current
        DESCRIPTION
              "The VLAN ID of destination port SMP messages are sent to." 
    ::= { qtechSMPFrameRelayEntry 5 }    


-- EG log
qtechEGMIBObjects OBJECT IDENTIFIER ::= { qtechSMPMIB 2 }

-- authenticated user info   
qtechEGUserTable OBJECT-TYPE
    SYNTAX  SEQUENCE OF QtechEGUserEntry
    MAX-ACCESS  not-accessible
    STATUS      current
    DESCRIPTION
            "A table that contains generic information about every user that is authenticated."
    ::= { qtechEGMIBObjects 1 }

qtechEGUserEntry OBJECT-TYPE
    SYNTAX  QtechEGUserEntry
    MAX-ACCESS  not-accessible
    STATUS  current
    DESCRIPTION
         "The entry of authenticated user table."
    INDEX   { qtechEGUserIpAddrType,qtechEGUserIpAddr }
    ::= { qtechEGUserTable 1 }

QtechEGUserEntry ::=
    SEQUENCE {
	qtechEGUserIpAddrType	InetAddressType,
	qtechEGUserIpAddr	InetAddress,
	qtechEGUserId		OCTET STRING,
	qtechEGUserName	OCTET STRING,
	qtechEGUserGroupName	OCTET STRING,
	qtechEGUserMac		MacAddress,
	qtechEGNasIp		InetAddress,
	qtechEGNasPort		Gauge32,
	qtechEGGatewayIp	InetAddress,
	qtechEGVlanId		Gauge32,
	qtechEGLoginTime	OCTET STRING,
	qtechEGLogoutTime	OCTET STRING,
	qtechEGMessageType	Gauge32,
	qtechEGUserStatus	RowStatus
    }

qtechEGUserIpAddrType OBJECT-TYPE
    SYNTAX  InetAddressType
    MAX-ACCESS  read-only
    STATUS  current
    DESCRIPTION
            "The IP address type of the user."
    ::= { qtechEGUserEntry 1 }

qtechEGUserIpAddr OBJECT-TYPE
    SYNTAX  InetAddress
    MAX-ACCESS  read-only
    STATUS  current
    DESCRIPTION
            "The IP address of the user."
    ::= { qtechEGUserEntry 2 }

qtechEGUserId OBJECT-TYPE
    SYNTAX  OCTET STRING(SIZE(0..256))
    MAX-ACCESS  read-create
    STATUS  current
    DESCRIPTION
            "The Id of User."
    ::= { qtechEGUserEntry 3 }

qtechEGUserName OBJECT-TYPE
    SYNTAX  OCTET STRING(SIZE(0..256))
    MAX-ACCESS  read-create
    STATUS  current
    DESCRIPTION
            "The Truename of User."
    ::= { qtechEGUserEntry 4 }

qtechEGUserGroupName OBJECT-TYPE
    SYNTAX  OCTET STRING(SIZE(0..256))
    MAX-ACCESS  read-create
    STATUS  current
    DESCRIPTION
            "The group name of User."
    ::= { qtechEGUserEntry 5 }
       
qtechEGUserMac OBJECT-TYPE
    SYNTAX  MacAddress
    MAX-ACCESS  read-create
    STATUS  current
    DESCRIPTION
            "The MAC Address of User."
    ::= { qtechEGUserEntry 6 }
       
qtechEGNasIp OBJECT-TYPE
    SYNTAX  InetAddress
    MAX-ACCESS  read-create
    STATUS  current
    DESCRIPTION
            "The Ip Address of 1x Nas."
    ::= { qtechEGUserEntry 7 }
       
qtechEGNasPort OBJECT-TYPE
    SYNTAX  Gauge32
    MAX-ACCESS  read-create
    STATUS  current
    DESCRIPTION
            "The user port of 1x Nas."
    ::= { qtechEGUserEntry 8 }
       
qtechEGGatewayIp OBJECT-TYPE
    SYNTAX  InetAddress
    MAX-ACCESS  read-create
    STATUS  current
    DESCRIPTION
            "The ip address of gateway."
    ::= { qtechEGUserEntry 9 }
       
qtechEGVlanId OBJECT-TYPE
    SYNTAX  Gauge32
    MAX-ACCESS  read-create
    STATUS  current
    DESCRIPTION
            "The vlan id of user."
    ::= { qtechEGUserEntry 10 }
       
qtechEGLoginTime OBJECT-TYPE
    SYNTAX  OCTET STRING
    MAX-ACCESS  read-create
    STATUS  current
    DESCRIPTION
            "The login time of user. for example: 2010-07-12 12:35:56"
    ::= { qtechEGUserEntry 11 }
       
qtechEGLogoutTime OBJECT-TYPE
    SYNTAX  OCTET STRING
    MAX-ACCESS  read-create
    STATUS  current
    DESCRIPTION
            "The logout time of user. for example: 2010-07-12 12:35:56"
    ::= { qtechEGUserEntry 12 }

qtechEGMessageType OBJECT-TYPE
    SYNTAX Gauge32
    MAX-ACCESS read-create
    STATUS current
    DESCRIPTION
            "The online(1)/offline(2) message type of the user."
   ::= { qtechEGUserEntry 13 }        

qtechEGUserStatus OBJECT-TYPE
    SYNTAX RowStatus
    MAX-ACCESS read-create
    STATUS current
    DESCRIPTION
            "The status of this row, by which new entries may be
            created, or old entries deleted from this table."
   ::= { qtechEGUserEntry 14 }        

qtechEGUserDelete OBJECT-TYPE
    SYNTAX Integer32
    MAX-ACCESS read-write
    STATUS      current    
    DESCRIPTION
            "This variable value:
             0: No action is required; other values:Delete all qtechEGUser information."
    ::= { qtechEGMIBObjects 2 }  
        

-- As the given port in SMP Server, this node will not be present in MIB. 
  qtechSMPTraps      OBJECT IDENTIFIER ::= { qtechSMPMIB 65535}
        
  qtechSMPSwitchIP OBJECT-TYPE
          SYNTAX IpAddress
          MAX-ACCESS accessible-for-notify
          STATUS current
          DESCRIPTION
            "IP addresses for the switch sending the Trap." 
          ::= { qtechSMPTraps 1 }          
        
  qtechSMPSwitchInterfaceID OBJECT-TYPE
          SYNTAX IfIndex
          MAX-ACCESS accessible-for-notify
          STATUS current
          DESCRIPTION
            "The interface receiving the messages to be forwarded." 
          ::= { qtechSMPTraps 2 }    
  
  qtechSMPSwitchInterfaceVLANID OBJECT-TYPE
          SYNTAX VlanId
          MAX-ACCESS accessible-for-notify
          STATUS current
          DESCRIPTION
            "The VLAN ID of the switch interface receiving the messages to be forwarded."
          ::= { qtechSMPTraps 3 }  

  qtechSMPFrameContentLength OBJECT-TYPE
          SYNTAX Unsigned32
          MAX-ACCESS accessible-for-notify
          STATUS current
          DESCRIPTION
            "The encapsulated message length, which can not exceed 1024." 
          ::= { qtechSMPTraps 4 }      
        
  qtechSMPFrameContent OBJECT-TYPE
          SYNTAX OCTET STRING(SIZE(0..1024))
          MAX-ACCESS accessible-for-notify
          STATUS current
          DESCRIPTION
            "The encapsulated message whose length can not exceed 1024." 
          ::= { qtechSMPTraps 5 }      
        
  qtechSMPFrameRelayTrap NOTIFICATION-TYPE
      OBJECTS  {qtechSMPSwitchIP,qtechSMPSwitchInterfaceID,qtechSMPSwitchInterfaceVLANID,
      			  qtechSMPFrameContentLength,qtechSMPFrameContent}
      STATUS  current
      DESCRIPTION
              "Trap message includes: IP address for the specified received message, 
               port receiving the message, message length and message content." 
      ::= { qtechSMPTraps 6 }


  qtechSMPArpAttackSubnetIP OBJECT-TYPE
          SYNTAX OCTET STRING(SIZE(0..40))
          MAX-ACCESS accessible-for-notify
          STATUS current
          DESCRIPTION
            "IP addresses for all subnets of SVI where the attack source locates." 
          ::= { qtechSMPTraps 7 }          
        
  qtechSMPArpAttackSubnetIPNum OBJECT-TYPE
          SYNTAX Integer32
          MAX-ACCESS accessible-for-notify
          STATUS current
          DESCRIPTION
            "Subnet IP address number." 
          ::= { qtechSMPTraps 8 }          

  qtechSMPArpAttackInterfaceSlot OBJECT-TYPE
          SYNTAX Integer32
          MAX-ACCESS accessible-for-notify
          STATUS current
          DESCRIPTION
            "The slot number for the device connecting the attack source." 
          ::= { qtechSMPTraps 9 }    
  
  qtechSMPArpAttackInterfacePort OBJECT-TYPE
          SYNTAX Integer32
          MAX-ACCESS accessible-for-notify
          STATUS current
          DESCRIPTION
            "The interface number for the device connecting the attack source." 
          ::= { qtechSMPTraps 10}  

  qtechSMPArpAttackInterfaceVlanID OBJECT-TYPE
          SYNTAX VlanId
          MAX-ACCESS accessible-for-notify
          STATUS current
          DESCRIPTION
            "The VLAN ID of VLAN where the attack source locates."
          ::= { qtechSMPTraps 11 }      
        
  qtechSMPArpAttackFrameContent OBJECT-TYPE
          SYNTAX OCTET STRING(SIZE(0..64))
          MAX-ACCESS accessible-for-notify
          STATUS current
          DESCRIPTION
            "The ARP messages sent from the attack source." 
          ::= { qtechSMPTraps 12 }      

  qtechSMPArpAttackStatus OBJECT-TYPE
          SYNTAX TruthValue
          MAX-ACCESS accessible-for-notify
          STATUS current
          DESCRIPTION
            "Show whether the device is attacked by the attack source or not.
             true: attack occurred; false: attack has been removed." 
          ::= { qtechSMPTraps 13 }

  qtechSMPArpAttackCriticalStatus OBJECT-TYPE
          SYNTAX INTEGER{
             critical(1),          -- Slight ARP attack, infulencing normal operation of the network 
                                   -- and advertising the SMP Server. 
             emergencies(2)        -- Severe ARP attack, leading to network crash. System blocks this 
                                   -- attack automatically and advertise the SMP Server. 
          }
          MAX-ACCESS accessible-for-notify
          STATUS current
          DESCRIPTION
            "The severity level of device attack by attack source: 
             critical(1),          -- Slight ARP attack, infulencing normal operation of the network
                                      and advertising the SMP Server. 
             emergencies(2)        -- Severe ARP attack, leading to network crash. System blocks this
                                      attack automatically and advertise the SMP Server. "
          ::= { qtechSMPTraps 14 }

  qtechSMPArpAttackMac OBJECT-TYPE
          SYNTAX MacAddress
          MAX-ACCESS accessible-for-notify
          STATUS current
          DESCRIPTION
            "MAC address for the device connecting the attack source." 
          ::= { qtechSMPTraps 15 }      

  qtechSMPArpAttackInterfaceIndex OBJECT-TYPE
          SYNTAX Integer32
          MAX-ACCESS accessible-for-notify
          STATUS current
          DESCRIPTION
            "The interface index for the device connecting the attack source." 
          ::= { qtechSMPTraps 16 }      
        
  qtechSMPArpAttackTrap NOTIFICATION-TYPE
      OBJECTS  {qtechSMPArpAttackSubnetIP, qtechSMPArpAttackSubnetIPNum, qtechSMPArpAttackInterfaceSlot,
               qtechSMPArpAttackInterfacePort, qtechSMPArpAttackInterfaceVlanID, qtechSMPArpAttackFrameContent,
               qtechSMPArpAttackStatus, qtechSMPArpAttackCriticalStatus, qtechSMPArpAttackMac, 
               qtechSMPArpAttackInterfaceIndex}
      STATUS  current
      DESCRIPTION
              "Trap message includes: 
                  IP addresses for all subnets of SVI where the attack source locates,
                  Subnet IP address number,
                  Slot number the attack source attacks,
                  Port number the attack source attacks,
                  VLAN ID of the VLAN the attack source belongs to,
                  ARP message(64 bytes),
                  Advertisement of attack occurrance and removal,
                  MAC address for the device connecting the attack source,
                  Interface index for the device connecting the attack source."
      ::= { qtechSMPTraps 17 }        

qtechSMPMIBConformance OBJECT IDENTIFIER ::= { qtechSMPMIB 3 }
qtechSMPMIBCompliances OBJECT IDENTIFIER ::= { qtechSMPMIBConformance 1 }
qtechSMPMIBGroups      OBJECT IDENTIFIER ::= { qtechSMPMIBConformance 2 }

-- compliance statements
qtechDeviceMIBCompliance MODULE-COMPLIANCE
        STATUS  current
        DESCRIPTION
                "The compliance statement for entities which implement
                the Qtech SMP MIB"
        MODULE  -- this module
                MANDATORY-GROUPS { qtechSMPServerMibGroup,
                                   qtechSMPClientMibGroup,
                                   qtechSMPPolicyMibGroup,
                                   qtechSMPFrameRelayMibGroup}
        ::= { qtechSMPMIBCompliances 1 }
        
qtechSMPServerMibGroup    OBJECT-GROUP
    OBJECTS {
    					qtechSMPServer,
    					qtechSMPServerKey
            }
    STATUS  current
    DESCRIPTION
            "Collection of SMP Server information." 
    ::= { qtechSMPMIBGroups 1 }
    
qtechSMPClientMibGroup    OBJECT-GROUP
    OBJECTS {
    					qtechSMPEventSendSlice
            }
    STATUS  current
    DESCRIPTION
            "Collection of restricted information of SMP Client management." 
    ::= { qtechSMPMIBGroups 2 }    
    
qtechSMPPolicyMibGroup    OBJECT-GROUP
    OBJECTS {
    					qtechSMPPolicyDelete,
    					qtechSMPPolicyChecksum,
              qtechSMPPolicyIndex,
              qtechSMPPolicyStatus,
              qtechSMPPolicyInstallPort,
              qtechSMPPolicyType,
              qtechSMPPolicyContent,
              qtechSMPPolicyMask,
              qtechSMPPolicyName
            }
    STATUS  current
    DESCRIPTION
            "Policy information collection." 
    ::= { qtechSMPMIBGroups 3 }       
    
qtechSMPFrameRelayMibGroup    OBJECT-GROUP
    OBJECTS {
              qtechSMPFrameRelayIndex,
              qtechSMPFrameRelayContent,
              qtechSMPFrameRelayLength,
              qtechSMPFrameRelayDestPort,
              qtechSMPFrameRelayDestVlan
            }
    STATUS  current
    DESCRIPTION
            "Information collection of message forward table." 
    ::= { qtechSMPMIBGroups 4 }         


END

-- *****************************************************************
-- QTECH-SOFTWARE-SMI.mib: Qtech SOFTWARE SMI File
-- 
-- Aug. 2014, panshiyong
--
-- Copyright (c) 2014 by Qtech Networks Co.,Ltd.
-- All rights reserved.
-- 
-- *****************************************************************
--

QTECH-SOFTWARE-SMI DEFINITIONS ::= BEGIN

IMPORTS
        MODULE-IDENTITY,
        OBJECT-IDENTITY
                FROM SNMPv2-SMI
        products
                FROM QTECH-SMI;
                
software OBJECT IDENTIFIER ::= { products 7 }

softwareMib MODULE-IDENTITY
        LAST-UPDATED "201408190000Z"
        ORGANIZATION "Qtech Networks Co.,Ltd."
        CONTACT-INFO
                " 
                Tel: 4008-111-000 

                E-mail: service@qtech.com.cn"
        DESCRIPTION
                "The Structure of Management Information for the
                 Qtech enterprise."
        REVISION      "201005250000Z"
        DESCRIPTION
                "Initial version of this MIB module."
        ::= { software 1 }        

qtechSoftwareProducts OBJECT-IDENTITY
        STATUS  current
        DESCRIPTION
                "qtechSoftwareProducts is the root OBJECT IDENTIFIER from
                 which sysObjectID values are assigned for software.  Actual
                 values are defined in QTECH-PRODUCTS-MIB."
        ::= { softwareMib 1 }
        
END

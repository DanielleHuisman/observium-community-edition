-- *****************************************************************
-- QTECH-SPAN-MIB.mib:  Qtech SPAN MIB file
--
-- March 2002, Wuzg
--
-- Copyright (c) 2002 by Qtech Networks Co.,Ltd.
-- All rights reserved.
-- 
-- *****************************************************************
--

QTECH-SPAN-MIB DEFINITIONS ::= BEGIN

IMPORTS
        MODULE-IDENTITY,
        OBJECT-TYPE,
        Integer32
                FROM SNMPv2-SMI
        MODULE-COMPLIANCE,
        OBJECT-GROUP
                FROM SNMPv2-CONF
        ConfigStatus,
        IfIndex
                FROM QTECH-TC
        qtechMgmt
                FROM QTECH-SMI;

qtechSPANMIB MODULE-IDENTITY
        LAST-UPDATED "200203200000Z"
        ORGANIZATION "Qtech Networks Co.,Ltd."
        CONTACT-INFO
                " 
                Tel: 4008-111-000 

                E-mail: service@qtech.com.cn"
        DESCRIPTION
                "This module defines qtech SPAN(Statistical Processing and Analysis)mibs."
        REVISION      "200203200000Z"
        DESCRIPTION
                "Initial version of this MIB module."
        ::= { qtechMgmt 23}

qtechSPANMIBObjects OBJECT IDENTIFIER ::= { qtechSPANMIB 1 }


qtechSPANSessionNum OBJECT-TYPE
        SYNTAX Integer32
        MAX-ACCESS read-only
        STATUS current
        DESCRIPTION
            "Max num of SPAN session which the system support."
        ::= { qtechSPANMIBObjects 1 }

qtechSPANTable OBJECT-TYPE
        SYNTAX SEQUENCE OF QtechSPANEntry
        MAX-ACCESS not-accessible
        STATUS current
        DESCRIPTION
            "list of  SPAN configuration objects."
        ::= { qtechSPANMIBObjects 2 }
    
qtechSPANEntry OBJECT-TYPE
        SYNTAX QtechSPANEntry
        MAX-ACCESS not-accessible
        STATUS current
        DESCRIPTION
            "Entry contains SPAN configuration objects."
        INDEX { qtechSPANSession,qtechSPANIfIndex}
        ::= { qtechSPANTable 1 }

QtechSPANEntry ::=
        SEQUENCE {
            qtechSPANSession Integer32,
            qtechSPANIfIndex IfIndex,            
            qtechSPANIfRole INTEGER,
            qtechSPANEntryStatus ConfigStatus
        }
qtechSPANSession OBJECT-TYPE
        SYNTAX Integer32
        MAX-ACCESS read-only
        STATUS current
        DESCRIPTION
            "Index of an association of a destination port with source ports or source."
        ::= { qtechSPANEntry 1 }

qtechSPANIfIndex OBJECT-TYPE
        SYNTAX IfIndex
        MAX-ACCESS read-only
        STATUS current
        DESCRIPTION
            " "
        ::= { qtechSPANEntry 2 }
                                           
qtechSPANIfRole OBJECT-TYPE
        SYNTAX INTEGER{
            span-desc(1),    -- a destination port (also called a monitoring port) that 
                             -- receives a copy of traffic from the source port.
            span-src-rx(2),  -- A source port (also called a monitored port) which 
                             -- the received packets is monitored.
            span-src-tx(3),  -- A source port (also called a monitored port) which 
                             -- the transmitted packets  is monitored.
            span-src-all(4)  -- A source port (also called a monitored port) which 
                             -- the received and transmitted packets  is all monitored.
        }
        MAX-ACCESS read-create
        STATUS current
        DESCRIPTION
            " Role of the interface in the SPAN session"
        ::= { qtechSPANEntry 3 }
                            
qtechSPANEntryStatus OBJECT-TYPE
        SYNTAX ConfigStatus
        MAX-ACCESS read-create
        STATUS current
        DESCRIPTION
            "Status of this entry, set its value to invalid will delete the interface of 
             this entry and set this object to valid will have no any effect"
        ::= { qtechSPANEntry 4 }        

qtechSPANMIBConformance OBJECT IDENTIFIER ::= { qtechSPANMIB 3 }
qtechSPANMIBCompliances OBJECT IDENTIFIER ::= { qtechSPANMIBConformance 1 }
qtechSPANMIBGroups      OBJECT IDENTIFIER ::= { qtechSPANMIBConformance 2 }


-- compliance statements

qtechSPANMIBCompliance MODULE-COMPLIANCE
        STATUS  current
        DESCRIPTION
                "The compliance statement for entities which implement
                the Qtech IfConfig MIB"
        MODULE  -- this module
                MANDATORY-GROUPS { qtechSPANMIBGroup
                 }
        ::= { qtechSPANMIBCompliances 1 }
                
-- units of conformance

qtechSPANMIBGroup OBJECT-GROUP
        OBJECTS {
            qtechSPANSession,
            qtechSPANIfIndex,            
            qtechSPANIfRole,
            qtechSPANEntryStatus
        }
        STATUS  current
        DESCRIPTION
                "A collection of objects providing port SPAN configure."
        ::= { qtechSPANMIBGroups 1 }         
                
END

-- *******************************************************************
-- QTECH-STA-ASS-RECORDS-MIB.mib : Qtech STA ASSIATION RECORDS MIB 
-- 
-- JUNE 2011, chenfg1
--
-- Copyright (c) 2011 by Qtech Networks Co.,Ltd.
-- All rights reserved.
-- *******************************************************************
--
QTECH-STA-ASS-RECORDS-MIB DEFINITIONS ::= BEGIN

IMPORTS 
        MODULE-IDENTITY, 
        OBJECT-TYPE,
		Integer32,
	    NOTIFICATION-TYPE,	
        Unsigned32,
        IpAddress
                FROM SNMPv2-SMI
        OBJECT-GROUP,
        MODULE-COMPLIANCE
                FROM SNMPv2-CONF
        TruthValue,
        RowStatus,
        DisplayString,
        MacAddress,
        DateAndTime
                FROM SNMPv2-TC 
        qtechMgmt
                FROM QTECH-SMI
        qtechIfIndex 
                FROM QTECH-INTERFACE-MIB;

--********************************************************************
--*  MODULE IDENTITY
--********************************************************************

qtechStaAssRecordsMIB    MODULE-IDENTITY
       LAST-UPDATED       "201111100000Z"
       ORGANIZATION       "Qtech Networks Co.,Ltd."
       CONTACT-INFO  
                " 
                Tel: 4008-111-000 

                E-mail: service@qtech.com.cn"

        DESCRIPTION             
                "This MIB is intended to get the sta assoiation records"
        
        REVISION      "200911100000Z"
        DESCRIPTION
                "Initial version of this MIB module. "
        ::= { qtechMgmt 101 }

qtechStaAssRecordsMIBTrap    OBJECT IDENTIFIER 
    ::= { qtechStaAssRecordsMIB 0 }

qtechStaAssRecordsMIBObjects OBJECT IDENTIFIER 
    ::= { qtechStaAssRecordsMIB 1 }

qtechStaAssRecordsGrobal OBJECT IDENTIFIER
	::= { qtechStaAssRecordsMIBObjects 1 }

qtechStaAssRecordsByMAC OBJECT IDENTIFIER
	::= { qtechStaAssRecordsMIBObjects 2 }

qtechStaAssRecordsByTime OBJECT IDENTIFIER
	::= { qtechStaAssRecordsMIBObjects 3 }

qtechStaAssRecordsByAP OBJECT IDENTIFIER
	::= { qtechStaAssRecordsMIBObjects 4 }
	
qtechStaAssSignalByMAC OBJECT IDENTIFIER
	::= { qtechStaAssRecordsMIBObjects 5 }

qtechStaAssRetryByMAC OBJECT IDENTIFIER
	::= { qtechStaAssRecordsMIBObjects 6 }	

qtechStaAssStatistic OBJECT IDENTIFIER
	::= { qtechStaAssRecordsMIBObjects 7 }		
	
--*******************************************************************
--qtechStaAssRecordsTable:  get sta association grobal static by mac
--*******************************************************************
    qtechStaAssRecordsGrobalTable  OBJECT-TYPE
         SYNTAX      SEQUENCE OF QtechStaAssRecordsGrobalEntry
         MAX-ACCESS  not-accessible
         STATUS      current
         DESCRIPTION
                     "A table listing the sta association process survey records,
                      can be search record by mac."
         ::= { qtechStaAssRecordsGrobal 1 }
   
    qtechStaAssRecordsGrobalEntry OBJECT-TYPE
         SYNTAX      QtechStaAssRecordsGrobalEntry
         MAX-ACCESS  not-accessible
         STATUS      current
         DESCRIPTION
                     "Get sta association records by mac."
         INDEX       { qtechStaMacGrobalAddress }
         ::= { qtechStaAssRecordsGrobalTable  1 }

    QtechStaAssRecordsGrobalEntry ::= SEQUENCE {             
             qtechStaMacGrobalAddress        MacAddress,       
             qtechStaMacGrobalAPName         DisplayString,    
             qtechStaMacGrobalISUP           INTEGER,          
             qtechStaMacGrobalStartime       DateAndTime,      
             qtechStaMacGrobalupdowntimes    Unsigned32,       
             qtechStaMacGrobalroamtimes      Unsigned32,      
	     qtechStaMacGrobaltotaltimes     Unsigned32,
	     qtechStaMacGrobalrealdowntimes  Unsigned32,
	     qtechStaMacGrobalSSID           DisplayString
             }

    qtechStaMacGrobalAddress OBJECT-TYPE
         SYNTAX      MacAddress
         MAX-ACCESS  not-accessible
         STATUS      current
         DESCRIPTION
                     "Sta Mac address."
         ::= { qtechStaAssRecordsGrobalEntry 1 }

    qtechStaMacGrobalAPName OBJECT-TYPE
         SYNTAX      DisplayString(SIZE(1..64))
         MAX-ACCESS  read-only
         STATUS      current
         DESCRIPTION
                     "ap name."
         ::= { qtechStaAssRecordsGrobalEntry 2 }

    qtechStaMacGrobalISUP OBJECT-TYPE
         SYNTAX      INTEGER {
                      up(0),
                      down(1)
                     }
         MAX-ACCESS  read-only
         STATUS      current
         DESCRIPTION
                     "Sta is active or not."
         ::= { qtechStaAssRecordsGrobalEntry 3 }

    qtechStaMacGrobalStartime OBJECT-TYPE
         SYNTAX      DateAndTime
         MAX-ACCESS  read-only
         STATUS      current
         DESCRIPTION
                     "Sta active time."
         ::= { qtechStaAssRecordsGrobalEntry 4 }

    qtechStaMacGrobalupdowntimes OBJECT-TYPE
         SYNTAX      Unsigned32
         MAX-ACCESS  read-only
         STATUS      current
         DESCRIPTION
                     "Sta up and down times."
         ::= { qtechStaAssRecordsGrobalEntry 5 }

    qtechStaMacGrobalroamtimes OBJECT-TYPE
         SYNTAX      Unsigned32
         MAX-ACCESS  read-only
         STATUS      current
         DESCRIPTION
                     "Sta roam times."
         ::= { qtechStaAssRecordsGrobalEntry 6 }
		 
    qtechStaMacGrobaltotaltimes OBJECT-TYPE
         SYNTAX      Unsigned32
         MAX-ACCESS  read-only
         STATUS      current
         DESCRIPTION
                     "Sta total times(join\leave\delete\roam)."
         ::= { qtechStaAssRecordsGrobalEntry 7 }
		 
    qtechStaMacGrobalrealdowntimes OBJECT-TYPE
         SYNTAX      Unsigned32
         MAX-ACCESS  read-only
         STATUS      current
         DESCRIPTION
                     "Sta real down times(sta join after leave within 5s)."
         ::= { qtechStaAssRecordsGrobalEntry 8 }		 

    qtechStaMacGrobalSSID OBJECT-TYPE
         SYNTAX      DisplayString(SIZE(1..64))
         MAX-ACCESS  read-only
         STATUS      current
         DESCRIPTION
                     "STA curent ssid."
         ::= { qtechStaAssRecordsGrobalEntry 9 }
		 
--*******************************************************************
--qtechStaAssRecordsByMACTable  :  get sta association records by mac
--*******************************************************************
    qtechStaAssRecordsByMACTable  OBJECT-TYPE
         SYNTAX      SEQUENCE OF QtechStaAssRecordsByMACEntry
         MAX-ACCESS  not-accessible
         STATUS      current
         DESCRIPTION
                     "A table listing the sta association process detail records,
                      can be search record by mac."
         ::= { qtechStaAssRecordsByMAC 1 }
   
    qtechStaAssRecordsByMACEntry OBJECT-TYPE
         SYNTAX      QtechStaAssRecordsByMACEntry
         MAX-ACCESS  not-accessible
         STATUS      current
         DESCRIPTION
                     "Get sta association records by mac."
         INDEX       { qtechStaMacAddress,
                       qtechStaMacindex}
         ::= { qtechStaAssRecordsByMACTable  1 }

    QtechStaAssRecordsByMACEntry ::= SEQUENCE {        
             qtechStaMacAddress      MacAddress,      
             qtechStaMacindex        Unsigned32,     
             qtechStaAsstime         DateAndTime,    
             qtechStaAssAction       INTEGER,
             qtechStaAssSubAction    INTEGER,			 
             qtechStaAssResult       INTEGER,       
             qtechStaAssReason       INTEGER,       
             qtechStaAssApNamePre    DisplayString,   
             qtechStaAssApNameNow    DisplayString,   
             qtechStaAssSignalQua    INTEGER,        
             qtechStaAssRoamtype     INTEGER,
             qtechStaAssjitter       INTEGER,
             qtechStaAssjointimes    Unsigned32,
             qtechStaAsslatelytime   DateAndTime,
             qtechStaAssSSID         DisplayString
             			 
             }
    qtechStaMacAddress OBJECT-TYPE
         SYNTAX      MacAddress
         MAX-ACCESS  not-accessible
         STATUS      current
         DESCRIPTION
                     "Sta Mac address."
         ::= { qtechStaAssRecordsByMACEntry 1 }

    qtechStaMacindex OBJECT-TYPE
         SYNTAX      Unsigned32
         MAX-ACCESS  not-accessible
         STATUS      current
         DESCRIPTION
                     "the index of Sta mac."
         ::= { qtechStaAssRecordsByMACEntry 2 }
		 
    qtechStaAsstime OBJECT-TYPE
         SYNTAX      DateAndTime
         MAX-ACCESS  read-only
         STATUS      current
         DESCRIPTION
                     "Sta association time."
         ::= { qtechStaAssRecordsByMACEntry 3 }
		 
    qtechStaAssAction OBJECT-TYPE
         SYNTAX      INTEGER {
                      join(1),
                      leave(2),
                      roam(3),
                      delete(4)
                     }
         MAX-ACCESS  read-only
         STATUS      current
         DESCRIPTION
                     "Sta association action."
         ::= { qtechStaAssRecordsByMACEntry 4 }		 
		 
    qtechStaAssSubAction OBJECT-TYPE
         SYNTAX      INTEGER 
         MAX-ACCESS  read-only
         STATUS      current
         DESCRIPTION
                     "Sta association sub action."
         ::= { qtechStaAssRecordsByMACEntry 5 }
		 
    qtechStaAssResult OBJECT-TYPE
         SYNTAX      INTEGER {
                      success(0),
                      failed(1)
                     }
         MAX-ACCESS  read-only
         STATUS      current
         DESCRIPTION
                     "Sta association action resoult."
         ::= { qtechStaAssRecordsByMACEntry 6 }

    qtechStaAssReason OBJECT-TYPE
         SYNTAX      INTEGER
         MAX-ACCESS  read-only
         STATUS      current
         DESCRIPTION
                     "Sta association action reason."
         ::= { qtechStaAssRecordsByMACEntry 7 }

    qtechStaAssApNamePre OBJECT-TYPE
         SYNTAX      DisplayString(SIZE(1..64))
         MAX-ACCESS  read-only
         STATUS      current
         DESCRIPTION
                     "Sta preference ap-id."
         ::= { qtechStaAssRecordsByMACEntry 8 }

    qtechStaAssApNameNow OBJECT-TYPE
         SYNTAX      DisplayString(SIZE(1..64))
         MAX-ACCESS  read-only
         STATUS      current
         DESCRIPTION
                     "Sta now ap-id."
         ::= { qtechStaAssRecordsByMACEntry 9 }

    qtechStaAssSignalQua OBJECT-TYPE
         SYNTAX      INTEGER
         MAX-ACCESS  read-only
         STATUS      current
         DESCRIPTION
                     "Sta signal quality."
         ::= { qtechStaAssRecordsByMACEntry 10 }
		 
    qtechStaAssRoamtype OBJECT-TYPE
         SYNTAX      INTEGER
         MAX-ACCESS  read-only
         STATUS      current
         DESCRIPTION
                     "Sta roam type."
         ::= { qtechStaAssRecordsByMACEntry 11 }		 

    qtechStaAssjitter OBJECT-TYPE
         SYNTAX      INTEGER
         MAX-ACCESS  read-only
         STATUS      current
         DESCRIPTION
                     "Sta association action jitter or not."
         ::= { qtechStaAssRecordsByMACEntry 12}
		 
    qtechStaAssjointimes OBJECT-TYPE
         SYNTAX      Unsigned32
         MAX-ACCESS  read-only
         STATUS      current
         DESCRIPTION
                     "Sta association join times."
         ::= { qtechStaAssRecordsByMACEntry 13 }

    qtechStaAsslatelytime OBJECT-TYPE
         SYNTAX      DateAndTime
         MAX-ACCESS  read-only
         STATUS      current
         DESCRIPTION
                     "Sta association lately join time."
         ::= { qtechStaAssRecordsByMACEntry 14 }

    qtechStaAssSSID OBJECT-TYPE
         SYNTAX      DisplayString
         MAX-ACCESS  read-only
         STATUS      current
         DESCRIPTION
                     "Sta association ssid."
         ::= { qtechStaAssRecordsByMACEntry 15 }		 
		 
		 
--*******************************************************************************
--qtechStaAssRecordsSearchByTime  :  search sta association records macs by time
--*******************************************************************************
    qtechStaAssRecordsSearchByTimeTable  OBJECT-TYPE
         SYNTAX      SEQUENCE OF QtechStaAssRecordsSearchByTimeEntry
         MAX-ACCESS  not-accessible
         STATUS      current
         DESCRIPTION
                     "A table listing the sta association process detail records,
                      can be search record by the time of sta association."
         ::= { qtechStaAssRecordsByTime 1 }
   
    qtechStaAssRecordsSearchByTimeEntry OBJECT-TYPE
         SYNTAX      QtechStaAssRecordsSearchByTimeEntry
         MAX-ACCESS  not-accessible
         STATUS      current
         DESCRIPTION
                     "Get sta association records by mac."
         INDEX       { qtechStaUptimeLow, 
                       qtechStaUptimeHigh,
                       qtechStaDowntimeLow,
                       qtechStaDowntimeHigh,
                       qtechStaTimeindex }
         ::= { qtechStaAssRecordsSearchByTimeTable  1 }


    QtechStaAssRecordsSearchByTimeEntry ::= SEQUENCE {      
             qtechStaUptimeLow        DateAndTime,           
             qtechStaUptimeHigh       DateAndTime,           
             qtechStaDowntimeLow      DateAndTime,          
             qtechStaDowntimeHigh     DateAndTime,          
             qtechStaTimeindex        Unsigned32,            
             qtechStaTimeMac          MacAddress,           
             qtechStaTimeAPName       DisplayString,      
             qtechStaTimeISUP         INTEGER,            
             qtechStaTimeStartime     DateAndTime,          
             qtechStaTimeupdowntimes  Unsigned32,         
             qtechStaTimeroamtimes    Unsigned32,           
             qtechStaTimertotaltimes  Unsigned32,
             qtechStaTimerjitter      INTEGER,
             qtechStaTimerjointimes   Unsigned32,
             qtechStaTimerlatelytime  DateAndTime,
             qtechStaTimerSSID        DisplayString			 
             }

    qtechStaUptimeLow OBJECT-TYPE
         SYNTAX      DateAndTime
         MAX-ACCESS  not-accessible
         STATUS      current
         DESCRIPTION
                     "the low time of Sta active time range."
         ::= { qtechStaAssRecordsSearchByTimeEntry 1 }

    qtechStaUptimeHigh OBJECT-TYPE
         SYNTAX      DateAndTime
         MAX-ACCESS  not-accessible
         STATUS      current
         DESCRIPTION
                     "the high time of Sta active time range."
         ::= { qtechStaAssRecordsSearchByTimeEntry 2 }

    qtechStaDowntimeLow OBJECT-TYPE
         SYNTAX      DateAndTime
         MAX-ACCESS  not-accessible
         STATUS      current
         DESCRIPTION
                     "the low time of Sta down time range."
         ::= { qtechStaAssRecordsSearchByTimeEntry 3 }

    qtechStaDowntimeHigh OBJECT-TYPE
         SYNTAX      DateAndTime
         MAX-ACCESS  not-accessible
         STATUS      current
         DESCRIPTION
                     "the high time of Sta down time range."
         ::= { qtechStaAssRecordsSearchByTimeEntry 4 }

    qtechStaTimeindex OBJECT-TYPE
         SYNTAX      Unsigned32
         MAX-ACCESS  not-accessible
         STATUS      current
         DESCRIPTION
                     "the index of Sta mac."
         ::= { qtechStaAssRecordsSearchByTimeEntry 5 }

    qtechStaTimeMac OBJECT-TYPE
         SYNTAX      MacAddress
         MAX-ACCESS  read-only
         STATUS      current
         DESCRIPTION
                     "Sta Mac address."
         ::= { qtechStaAssRecordsSearchByTimeEntry 6 }

    qtechStaTimeAPName OBJECT-TYPE
         SYNTAX      DisplayString(SIZE(1..64))
         MAX-ACCESS  read-only
         STATUS      current
         DESCRIPTION
                     "ap name."
         ::= { qtechStaAssRecordsSearchByTimeEntry 7 }

    qtechStaTimeISUP OBJECT-TYPE
         SYNTAX      INTEGER {
                      up(0),
                      down(1)
                     }
         MAX-ACCESS  read-only
         STATUS      current
         DESCRIPTION
                     "Sta is active or not."
         ::= { qtechStaAssRecordsSearchByTimeEntry 8 }

    qtechStaTimeStartime OBJECT-TYPE
         SYNTAX      DateAndTime
         MAX-ACCESS  read-only
         STATUS      current
         DESCRIPTION
                     "Sta active time."
         ::= { qtechStaAssRecordsSearchByTimeEntry 9 }

    qtechStaTimeupdowntimes OBJECT-TYPE
         SYNTAX      Unsigned32
         MAX-ACCESS  read-only
         STATUS      current
         DESCRIPTION
                     "Sta up and down times."
         ::= { qtechStaAssRecordsSearchByTimeEntry 10 }

    qtechStaTimeroamtimes OBJECT-TYPE
         SYNTAX      Unsigned32
         MAX-ACCESS  read-only
         STATUS      current
         DESCRIPTION
                     "Sta roam times."
         ::= { qtechStaAssRecordsSearchByTimeEntry 11 }
		 
    qtechStaTimertotaltimes OBJECT-TYPE
         SYNTAX      Unsigned32
         MAX-ACCESS  read-only
         STATUS      current
         DESCRIPTION
                     "Sta total times(join\leave\delete\roam)."
         ::= { qtechStaAssRecordsSearchByTimeEntry 12 }		 

    qtechStaTimerjitter OBJECT-TYPE
         SYNTAX      INTEGER
         MAX-ACCESS  read-only
         STATUS      current
         DESCRIPTION
                     "Sta association action jitter or not."
         ::= { qtechStaAssRecordsSearchByTimeEntry 13}
		 
    qtechStaTimerjointimes OBJECT-TYPE
         SYNTAX      Unsigned32
         MAX-ACCESS  read-only
         STATUS      current
         DESCRIPTION
                     "Sta association join times."
         ::= { qtechStaAssRecordsSearchByTimeEntry 14 }

    qtechStaTimerlatelytime OBJECT-TYPE
         SYNTAX      DateAndTime
         MAX-ACCESS  read-only
         STATUS      current
         DESCRIPTION
                     "Sta association lately join time."
         ::= { qtechStaAssRecordsSearchByTimeEntry 15 }

    qtechStaTimerSSID OBJECT-TYPE
         SYNTAX      DisplayString
         MAX-ACCESS  read-only
         STATUS      current
         DESCRIPTION
                     "Sta association ssid."
         ::= { qtechStaAssRecordsSearchByTimeEntry 16 }				 
		 
--*******************************************************************************
--qtechStaAssRecordsSearchByAPTable :  search sta association records macs by AP
--*******************************************************************************
    qtechStaAssRecordsSearchByAPTable  OBJECT-TYPE
         SYNTAX      SEQUENCE OF QtechStaAssRecordsSearchByAPEntry
         MAX-ACCESS  not-accessible
         STATUS      current
         DESCRIPTION
                     "A table listing the sta association process detail records,
                      can be search record by ap which sta associatied."
         ::= { qtechStaAssRecordsByAP 1 }
   
    qtechStaAssRecordsSearchByAPEntry OBJECT-TYPE
         SYNTAX      QtechStaAssRecordsSearchByAPEntry
         MAX-ACCESS  not-accessible
         STATUS      current
         DESCRIPTION
                     "Get sta association records by ap."
         INDEX       { qtechStaAPAPName,
                       qtechStaAPindex }
         ::= { qtechStaAssRecordsSearchByAPTable  1 }


    QtechStaAssRecordsSearchByAPEntry ::= SEQUENCE {    
             qtechStaAPAPName       DisplayString,    
             qtechStaAPindex        Unsigned32,      
             qtechStaAPMac          MacAddress,       
             qtechStaAPISUP         INTEGER,          
             qtechStaAPStartime     DateAndTime,      
             qtechStaAPupdowntimes  Unsigned32,       
             qtechStaAProamtimes    Unsigned32,       
             qtechStaAPtotaltimes   Unsigned32,
	     qtechStaAPjitter       INTEGER,
             qtechStaAPjointimes    Unsigned32,
             qtechStaAPlatelytime   DateAndTime,
             qtechStaAPSSID         DisplayString					 
             }

    qtechStaAPAPName OBJECT-TYPE
         SYNTAX      DisplayString(SIZE(1..64))
         MAX-ACCESS  not-accessible
         STATUS      current
         DESCRIPTION
                     "ap name."
         ::= { qtechStaAssRecordsSearchByAPEntry 1 }

    qtechStaAPindex OBJECT-TYPE
         SYNTAX      Unsigned32
         MAX-ACCESS  not-accessible
         STATUS      current
         DESCRIPTION
                     "the index of Sta mac."
         ::= { qtechStaAssRecordsSearchByAPEntry 2 }


    qtechStaAPMac OBJECT-TYPE
         SYNTAX      MacAddress
         MAX-ACCESS  read-only
         STATUS      current
         DESCRIPTION
                     "Sta Mac address."
         ::= { qtechStaAssRecordsSearchByAPEntry 3 }

    qtechStaAPISUP OBJECT-TYPE
         SYNTAX      INTEGER {
                      up(0),
                      down(1)
                     }
         MAX-ACCESS  read-only
         STATUS      current
         DESCRIPTION
                     "Sta is active or not."
         ::= { qtechStaAssRecordsSearchByAPEntry 4 }

    qtechStaAPStartime OBJECT-TYPE
         SYNTAX      DateAndTime
         MAX-ACCESS  read-only
         STATUS      current
         DESCRIPTION
                     "Sta active time."
         ::= { qtechStaAssRecordsSearchByAPEntry 5 }

    qtechStaAPupdowntimes OBJECT-TYPE
         SYNTAX      Unsigned32
         MAX-ACCESS  read-only
         STATUS      current
         DESCRIPTION
                     "Sta up and down times."
         ::= { qtechStaAssRecordsSearchByAPEntry 6 }

    qtechStaAProamtimes OBJECT-TYPE
         SYNTAX      Unsigned32
         MAX-ACCESS  read-only
         STATUS      current
         DESCRIPTION
                     "Sta roam times."
         ::= { qtechStaAssRecordsSearchByAPEntry 7 }
		 
    qtechStaAPtotaltimes OBJECT-TYPE
         SYNTAX      Unsigned32
         MAX-ACCESS  read-only
         STATUS      current
         DESCRIPTION
                     "Sta total times(join\leave\delete\roam)."
         ::= { qtechStaAssRecordsSearchByAPEntry 8 }
		 
    qtechStaAPjitter OBJECT-TYPE
         SYNTAX      INTEGER
         MAX-ACCESS  read-only
         STATUS      current
         DESCRIPTION
                     "Sta association action jitter or not."
         ::= { qtechStaAssRecordsSearchByAPEntry 9}
		 
    qtechStaAPjointimes OBJECT-TYPE
         SYNTAX      Unsigned32
         MAX-ACCESS  read-only
         STATUS      current
         DESCRIPTION
                     "Sta association join times."
         ::= { qtechStaAssRecordsSearchByAPEntry 10 }

    qtechStaAPlatelytime OBJECT-TYPE
         SYNTAX      DateAndTime
         MAX-ACCESS  read-only
         STATUS      current
         DESCRIPTION
                     "Sta association lately join time."
         ::= { qtechStaAssRecordsSearchByAPEntry 11 }

    qtechStaAPSSID OBJECT-TYPE
         SYNTAX      DisplayString
         MAX-ACCESS  read-only
         STATUS      current
         DESCRIPTION
                     "Sta association ssid."
         ::= { qtechStaAssRecordsSearchByAPEntry 12 }		

--*******************************************************************
--qtechStaAssSignalByMACTable  :  get sta association signal by mac
--*******************************************************************
    qtechStaAssSignalByMACTable  OBJECT-TYPE
         SYNTAX      SEQUENCE OF QtechStaAssSignalByMACEntry
         MAX-ACCESS  not-accessible
         STATUS      current
         DESCRIPTION
                     "A table listing the sta association process detail signal,
                      can be search by mac."
         ::= { qtechStaAssSignalByMAC 1 }
   
    qtechStaAssSignalByMACEntry OBJECT-TYPE
         SYNTAX      QtechStaAssSignalByMACEntry
         MAX-ACCESS  not-accessible
         STATUS      current
         DESCRIPTION
                     "Get sta association signal by mac."
         INDEX       { qtechStaSignalMacAddress,
                       qtechStaSignalMacindex}
         ::= { qtechStaAssSignalByMACTable  1 }

    QtechStaAssSignalByMACEntry ::= SEQUENCE {        
             qtechStaSignalMacAddress      MacAddress,      
             qtechStaSignalMacindex        Unsigned32,     
             qtechStaSignaltime            DateAndTime,    
             qtechStaSignalValue           INTEGER
             }
    qtechStaSignalMacAddress OBJECT-TYPE
         SYNTAX      MacAddress
         MAX-ACCESS  not-accessible
         STATUS      current
         DESCRIPTION
                     "Sta Mac address."
         ::= { qtechStaAssSignalByMACEntry 1 }

    qtechStaSignalMacindex OBJECT-TYPE
         SYNTAX      Unsigned32
         MAX-ACCESS  not-accessible
         STATUS      current
         DESCRIPTION
                     "the index of Sta mac."
         ::= { qtechStaAssSignalByMACEntry 2 }
		 
    qtechStaSignaltime OBJECT-TYPE
         SYNTAX      DateAndTime
         MAX-ACCESS  read-only
         STATUS      current
         DESCRIPTION
                     "Sta time of signal."
         ::= { qtechStaAssSignalByMACEntry 3 }
		 
    qtechStaSignalValue OBJECT-TYPE
         SYNTAX      INTEGER 
         MAX-ACCESS  read-only
         STATUS      current
         DESCRIPTION
                     "the signal value."
         ::= { qtechStaAssSignalByMACEntry 4 }

--*******************************************************************
--qtechStaAssRetryByMACTable  :  get sta retry packet value by mac
--*******************************************************************
    qtechStaAssRetryByMACTable  OBJECT-TYPE
         SYNTAX      SEQUENCE OF QtechStaAssRetryByMACEntry
         MAX-ACCESS  not-accessible
         STATUS      current
         DESCRIPTION
                     "A table listing the sta association process detail signal,
                      can be search by mac."
         ::= { qtechStaAssRetryByMAC 1 }
   
    qtechStaAssRetryByMACEntry OBJECT-TYPE
         SYNTAX      QtechStaAssRetryByMACEntry
         MAX-ACCESS  not-accessible
         STATUS      current
         DESCRIPTION
                     "Get sta association signal by mac."
         INDEX       { qtechStaRetryMacAddress,
                       qtechStaRetryMacindex}
         ::= { qtechStaAssRetryByMACTable  1 }

    QtechStaAssRetryByMACEntry ::= SEQUENCE {        
             qtechStaRetryMacAddress      MacAddress,      
             qtechStaRetryMacindex        Unsigned32,     
             qtechStaRetrytime            DateAndTime,    
             qtechStaRetryValue           INTEGER
             }
    qtechStaRetryMacAddress OBJECT-TYPE
         SYNTAX      MacAddress
         MAX-ACCESS  not-accessible
         STATUS      current
         DESCRIPTION
                     "Sta Mac address."
         ::= { qtechStaAssRetryByMACEntry 1 }

    qtechStaRetryMacindex OBJECT-TYPE
         SYNTAX      Unsigned32
         MAX-ACCESS  not-accessible
         STATUS      current
         DESCRIPTION
                     "the index of Sta mac."
         ::= { qtechStaAssRetryByMACEntry 2 }
		 
    qtechStaRetrytime OBJECT-TYPE
         SYNTAX      DateAndTime
         MAX-ACCESS  read-only
         STATUS      current
         DESCRIPTION
                     "Sta time of signal."
         ::= { qtechStaAssRetryByMACEntry 3 }
		 
    qtechStaRetryValue OBJECT-TYPE
         SYNTAX      INTEGER 
         MAX-ACCESS  read-only
         STATUS      current
         DESCRIPTION
                     "the retry value."
         ::= { qtechStaAssRetryByMACEntry 4 }		

--*******************************************************************
--statistics data
--*******************************************************************
    qtechAssStatisticsTotalsta OBJECT-TYPE
         SYNTAX      Unsigned32 
         MAX-ACCESS  read-only
         STATUS      current
         DESCRIPTION
                     "the total sta."
         ::= { qtechStaAssStatistic 1 }	

    qtechAssStatisticsTotalinfo OBJECT-TYPE
         SYNTAX      Unsigned32 
         MAX-ACCESS  read-only
         STATUS      current
         DESCRIPTION
                     "the total info."
         ::= { qtechStaAssStatistic 2 }	
		 
    qtechAssStatisticsdown OBJECT-TYPE
         SYNTAX      Unsigned32 
         MAX-ACCESS  read-only
         STATUS      current
         DESCRIPTION
                     "the down sta within one hour."
         ::= { qtechStaAssStatistic 3 }			 

    qtechAssStatisticsObligate1 OBJECT-TYPE
         SYNTAX      Unsigned32 
         MAX-ACCESS  read-only
         STATUS      current
         DESCRIPTION
                     "the obligate 2."
         ::= { qtechStaAssStatistic 4 }					 

    qtechAssStatisticsObligate2 OBJECT-TYPE
         SYNTAX      Unsigned32 
         MAX-ACCESS  read-only
         STATUS      current
         DESCRIPTION
                     "the obligate 2."
         ::= { qtechStaAssStatistic 5 }			 
		 
    qtechAssStatisticsObligate3 OBJECT-TYPE
         SYNTAX      Unsigned32 
         MAX-ACCESS  read-only
         STATUS      current
         DESCRIPTION
                     "the obligate 2."
         ::= { qtechStaAssStatistic 6 }					 
		 
qtechStaAssRecordsMIBConformance OBJECT IDENTIFIER ::= { qtechStaAssRecordsMIB 2 }
qtechStaAssRecordsMIBCompliances OBJECT IDENTIFIER ::= { qtechStaAssRecordsMIBConformance 1 }
qtechStaAssRecordsMIBGroups      OBJECT IDENTIFIER ::= { qtechStaAssRecordsMIBConformance 2 }


-- compliance statements

qtechStaAssRecordsMIBCompliance MODULE-COMPLIANCE
        STATUS  current
        DESCRIPTION
                "The compliance statement for entities which implement
                the Qtech Sta Association Records"
        MODULE  -- this module
                MANDATORY-GROUPS { 
                                  qtechStaAssRecordsGrobalMIBroup,
                                  qtechStaAssRecordsMIBroup,
                                  qtechStaAssRecordsSearchByTimeMIBroup,
                                  qtechStaAssRecordsSearchByAPMIBroup,
				  qtechStaAssSignalSearchByMACMIBroup,
				  qtechStaAssRetrySearchByMACMIBroup,
				  qtechStaAssStatisticsMIBroup
                }
        ::= { qtechStaAssRecordsMIBCompliances 1 }
                
-- units of conformance

qtechStaAssRecordsGrobalMIBroup OBJECT-GROUP
        OBJECTS {
             qtechStaMacGrobalAPName,  
             qtechStaMacGrobalISUP,           
             qtechStaMacGrobalStartime,       
             qtechStaMacGrobalupdowntimes,     
             qtechStaMacGrobalroamtimes,    
             qtechStaMacGrobaltotaltimes,    
             qtechStaMacGrobalrealdowntimes, 
             qtechStaMacGrobalSSID          
        }
        STATUS  current
        DESCRIPTION
                "A table listing the sta association process survey records,
                      can be search record by mac."
        ::= { qtechStaAssRecordsMIBGroups 1 } 

qtechStaAssRecordsMIBroup OBJECT-GROUP
        OBJECTS {
             qtechStaAsstime,  
             qtechStaAssAction,    
             qtechStaAssSubAction,   		 
             qtechStaAssResult,       
             qtechStaAssReason,        
             qtechStaAssApNamePre,    
             qtechStaAssApNameNow,     
             qtechStaAssSignalQua,   
             qtechStaAssRoamtype,    
             qtechStaAssjitter,       
             qtechStaAssjointimes,    
             qtechStaAsslatelytime,  
	     qtechStaAssSSID        
        }
        STATUS  current
        DESCRIPTION
                "A table listing the sta association process detail records,
                      can be search record by mac."
        ::= { qtechStaAssRecordsMIBGroups 2 } 

qtechStaAssRecordsSearchByTimeMIBroup OBJECT-GROUP
        OBJECTS {
             qtechStaTimeMac,
             qtechStaTimeAPName,
             qtechStaTimeISUP,
             qtechStaTimeStartime,
             qtechStaTimeupdowntimes,
             qtechStaTimeroamtimes,
             qtechStaTimertotaltimes,
             qtechStaTimerjitter,
             qtechStaTimerjointimes,   
             qtechStaTimerlatelytime,  
             qtechStaTimerSSID       				 
        }
        STATUS  current
        DESCRIPTION
                "A table listing the sta association process detail records,
                      can be search record by the time of sta association."
        ::= { qtechStaAssRecordsMIBGroups 3 } 

qtechStaAssRecordsSearchByAPMIBroup OBJECT-GROUP
        OBJECTS {
             qtechStaAPMac,
             qtechStaAPISUP,
             qtechStaAPStartime,
             qtechStaAPupdowntimes,
             qtechStaAProamtimes,
             qtechStaAPtotaltimes,
             qtechStaAPjitter,   
             qtechStaAPjointimes,   
             qtechStaAPlatelytime,  
             qtechStaAPSSID       
        }
        STATUS  current
        DESCRIPTION
                "A table listing the sta association process detail records,
                      can be search record by ap which sta associatied."
        ::= { qtechStaAssRecordsMIBGroups 4 } 

qtechStaAssSignalSearchByMACMIBroup OBJECT-GROUP
        OBJECTS {
             qtechStaSignaltime,    
             qtechStaSignalValue
        }
        STATUS  current
        DESCRIPTION
                "A table listing the sta association process detail signal,
                      can be search record by mac."
        ::= { qtechStaAssRecordsMIBGroups 5 } 

qtechStaAssRetrySearchByMACMIBroup OBJECT-GROUP
        OBJECTS {
             qtechStaRetrytime,    
             qtechStaRetryValue
        }
        STATUS  current
        DESCRIPTION
                "A table listing the sta association process detail retry packet,
                      can be search record by mac."
        ::= { qtechStaAssRecordsMIBGroups 6 } 		

qtechStaAssStatisticsMIBroup OBJECT-GROUP
        OBJECTS {
             qtechAssStatisticsTotalsta,    
             qtechAssStatisticsTotalinfo,
	     qtechAssStatisticsdown,
	     qtechAssStatisticsObligate1,
	     qtechAssStatisticsObligate2,
	     qtechAssStatisticsObligate3
        }
        STATUS  current
        DESCRIPTION
                "statistics of troubleshooting."
        ::= { qtechStaAssRecordsMIBGroups 7 } 				
		
END

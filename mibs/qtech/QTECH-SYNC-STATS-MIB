-- *------------------------------------------------------------------
-- * QTECH-SYNC-STATS-MIB.mib
-- *   Qtech Sync Statistics MIB.
-- * 
-- * May 2009, yingde tan
-- *
-- * Copyright (c) 2009 by Qtech Networks Co.,Ltd.
-- * All rights reserved.
-- *
-- *------------------------------------------------------------------

QTECH-SYNC-STATS-MIB DEFINITIONS ::= BEGIN

   IMPORTS
      MODULE-IDENTITY, 
      OBJECT-TYPE, 
      Integer32, 
      Counter32
         FROM SNMPv2-SMI
      RowStatus
         FROM SNMPv2-TC
      OBJECT-GROUP, 
      MODULE-COMPLIANCE
         FROM SNMPv2-CONF
      qtechMgmt
         FROM QTECH-SMI
      InterfaceIndex
         FROM IF-MIB;

   qtechSyncStatsMIB MODULE-IDENTITY
      LAST-UPDATED   "200905201456Z"
      ORGANIZATION   "Qtech Networks Co.,Ltd."
      CONTACT-INFO
                " 
                Tel: 4008-111-000 

                E-mail: service@qtech.com.cn"

      DESCRIPTION
         "Qtech Sync Statistics MIB.
         
          Acronyms
          The following acronyms are used in this document:

            CRC:        Cyclic Redundancy Check

            HDLC:       High-level Data Link Control

            MIB:        Management Information Base

            MTU:        Maximum Transmission Unit

         "

        REVISION "200905201456Z"
        DESCRIPTION
                "Added module compliance."

      ::= { qtechMgmt 51 }

-- +++++++++++++++++++++++++++++++++++++++++++++++++++++++
-- MIB Objects
-- +++++++++++++++++++++++++++++++++++++++++++++++++++++++

qtechSyncStatsMibObjects OBJECT IDENTIFIER ::= { qtechSyncStatsMIB 1 }

qtechStatsSyncGlobal OBJECT IDENTIFIER ::= { qtechSyncStatsMibObjects 1 }

qtechSyncStatsTable     OBJECT-TYPE
   SYNTAX         SEQUENCE OF QtechSyncStatsEntry
   MAX-ACCESS     not-accessible
   STATUS         current
   DESCRIPTION
      "The SYNC interface statistics MIB."
   ::= { qtechSyncStatsMibObjects 2 }

qtechSyncStatsEntry     OBJECT-TYPE
   SYNTAX         QtechSyncStatsEntry
   MAX-ACCESS     not-accessible
   STATUS         current
   DESCRIPTION
      "An entry the qtechSyncStatsTable."
   INDEX    { qtechSyncStatsSlot, qtechSyncStatsConn, qtechSyncStatsChannel }
   ::= { qtechSyncStatsTable 1 }

QtechSyncStatsEntry ::= SEQUENCE {
   qtechSyncStatsRowStatus                RowStatus,
   qtechSyncStatsSlot                     Integer32,
   qtechSyncStatsConn                     Integer32,
   qtechSyncStatsChannel                  Integer32,
   qtechSyncStatsIfIndex                  InterfaceIndex, 
   qtechSyncStatsPortState                INTEGER,
   qtechSyncStatsRxFrames                 Counter32,
   qtechSyncStatsRxOctets                 Counter32,
   qtechSyncStatsRxReplenFails            Counter32,
   qtechSyncStatsRxClockErrors            Counter32,
   qtechSyncStatsRxDpllErrors             Counter32,
   qtechSyncStatsRxFrameTooLongErrors     Counter32,
   qtechSyncStatsRxFrameOctetAlignErrors  Counter32,
   qtechSyncStatsRxAbortErrors            Counter32,
   qtechSyncStatsRxCrcErrors              Counter32,          
   qtechSyncStatsRxRcvrOverrunErrors      Counter32,
   qtechSyncStatsTxFrames                 Counter32,
   qtechSyncStatsTxOctets                 Counter32,
   qtechSyncStatsTxRingFullDropsErrors    Counter32,
   qtechSyncStatsTxClockErrors            Counter32,
   qtechSyncStatsTxFrameTooLongErrors     Counter32,
   qtechSyncStatsTxUnderrunErrors         Counter32
}

qtechSyncStatsRowStatus    OBJECT-TYPE
   SYNTAX         RowStatus
   MAX-ACCESS     read-create
   STATUS         current
   DESCRIPTION
      "The status of this row."
   ::= { qtechSyncStatsEntry 1 }

qtechSyncStatsSlot         OBJECT-TYPE
   SYNTAX         Integer32 (0..2147483647)
   MAX-ACCESS     read-only
   STATUS         current
   DESCRIPTION
      "The physical slot for this Sync port. Part of the index."
   ::= { qtechSyncStatsEntry 2 }
   
qtechSyncStatsConn         OBJECT-TYPE
   SYNTAX         Integer32 (0..2147483647)
   MAX-ACCESS     read-only
   STATUS         current
   DESCRIPTION
      "The physical connector for this Sync port. Part of the index."
   ::= { qtechSyncStatsEntry 3 }
   
qtechSyncStatsChannel      OBJECT-TYPE
   SYNTAX         Integer32 (0..2147483647)
   MAX-ACCESS     read-only
   STATUS         current
   DESCRIPTION
      "The virtual channel for this Sync port. Part of the index."
   ::= { qtechSyncStatsEntry 4 }
   
qtechSyncStatsIfIndex      OBJECT-TYPE
   SYNTAX         InterfaceIndex
   MAX-ACCESS     read-only
   STATUS         current
   DESCRIPTION
      "The IfIndex of this SYNC slot/conn/channel. This is
       configured, but configuration is not available via
       SNMP."
   ::= { qtechSyncStatsEntry 5 }

qtechSyncStatsPortState OBJECT-TYPE
   SYNTAX         INTEGER {
                     init(1),      -- port is coming up
                     running(2),   -- port has finished initialization
                                   -- and is waiting to transition to
                                   -- data state
                     up(3),        -- ready to pass packets
                     down(4)       -- port is down, unable to pass
                                   -- packets
                  }
   MAX-ACCESS     read-only
   STATUS         current
   DESCRIPTION
      "The current operational state of the interface.  
       The init(1) state indicates the port is in the state 
       of trying to come up. It will transition to running(2)
       once initialization is complete. up(3) indicates the 
       interface is capable of passing packets. down(4) indicates
       the interface is no longer capable of passing packets." 
   ::= { qtechSyncStatsEntry 6 }

qtechSyncStatsRxFrames     OBJECT-TYPE
   SYNTAX         Counter32
   MAX-ACCESS     read-only
   STATUS         current
   DESCRIPTION
      "The number of frames received on this HDLC interface." 
   ::= { qtechSyncStatsEntry 7 }
   
qtechSyncStatsRxOctets     OBJECT-TYPE
   SYNTAX         Counter32
   MAX-ACCESS     read-only
   STATUS         current
   DESCRIPTION
      "The number of octets received on this HDLC interface." 
   ::= { qtechSyncStatsEntry 8 }
   
qtechSyncStatsRxReplenFails   OBJECT-TYPE
   SYNTAX         Counter32
   MAX-ACCESS     read-only
   STATUS         current
   DESCRIPTION
      "The number of times receive buffers could not be allocated 
      on this HDLC interface." 
   ::= { qtechSyncStatsEntry 9 }
   
qtechSyncStatsRxClockErrors   OBJECT-TYPE
   SYNTAX         Counter32
   MAX-ACCESS     read-only
   STATUS         current
   DESCRIPTION
      "The number of clock errors on this HDLC interface." 
   ::= { qtechSyncStatsEntry 10 }
   
qtechSyncStatsRxDpllErrors OBJECT-TYPE
   SYNTAX         Counter32
   MAX-ACCESS     read-only
   STATUS         current
   DESCRIPTION
      "The number of DPLL errors received on this HDLC interface." 
   ::= { qtechSyncStatsEntry 11 }
   
qtechSyncStatsRxFrameTooLongErrors     OBJECT-TYPE
   SYNTAX         Counter32
   MAX-ACCESS     read-only
   STATUS         current
   DESCRIPTION
      "The number of received long frame errors received on this 
       HDLC interface." 
   ::= { qtechSyncStatsEntry 12 }
   
qtechSyncStatsRxFrameOctetAlignErrors     OBJECT-TYPE
   SYNTAX         Counter32
   MAX-ACCESS     read-only
   STATUS         current
   DESCRIPTION
      "The number of received long frame errors received on 
       this HDLC interface." 
   ::= { qtechSyncStatsEntry 13 }
   
qtechSyncStatsRxAbortErrors      OBJECT-TYPE
   SYNTAX         Counter32
   MAX-ACCESS     read-only
   STATUS         current
   DESCRIPTION
      "The number of received abort errors received on 
       this HDLC interface." 
   ::= { qtechSyncStatsEntry 14 }
   
qtechSyncStatsRxCrcErrors     OBJECT-TYPE
   SYNTAX         Counter32
   MAX-ACCESS     read-only
   STATUS         current
   DESCRIPTION
      "The number of received CRC errors received on 
       this HDLC interface." 
   ::= { qtechSyncStatsEntry 15 }
   
qtechSyncStatsRxRcvrOverrunErrors      OBJECT-TYPE
   SYNTAX         Counter32
   MAX-ACCESS     read-only
   STATUS         current
   DESCRIPTION
      "The number of received CRC errors received on 
       this HDLC interface." 
   ::= { qtechSyncStatsEntry 16 }
   
qtechSyncStatsTxFrames     OBJECT-TYPE
   SYNTAX         Counter32
   MAX-ACCESS     read-only
   STATUS         current
   DESCRIPTION
      "The number of transmitted frames on this HDLC interface." 
   ::= { qtechSyncStatsEntry 17 }
   
qtechSyncStatsTxOctets     OBJECT-TYPE
   SYNTAX         Counter32
   MAX-ACCESS     read-only
   STATUS         current
   DESCRIPTION
      "The number of transmitted frames on this HDLC interface." 
   ::= { qtechSyncStatsEntry 18 }
   
qtechSyncStatsTxRingFullDropsErrors    OBJECT-TYPE
   SYNTAX         Counter32
   MAX-ACCESS     read-only
   STATUS         current
   DESCRIPTION
      "The number of frames dropped on this HDLC interface because
       the transmit ring was full." 
   ::= { qtechSyncStatsEntry 19 }
   
qtechSyncStatsTxClockErrors      OBJECT-TYPE
   SYNTAX         Counter32
   MAX-ACCESS     read-only
   STATUS         current
   DESCRIPTION
      "The number of transmit clock errors on this HDLC interface." 
   ::= { qtechSyncStatsEntry 20 }
   
qtechSyncStatsTxFrameTooLongErrors     OBJECT-TYPE
   SYNTAX         Counter32
   MAX-ACCESS     read-only
   STATUS         current
   DESCRIPTION
      "The number of frames dropped this HDLC interface because they
       were long than the interface's MTU." 
   ::= { qtechSyncStatsEntry 21 }
   
qtechSyncStatsTxUnderrunErrors      OBJECT-TYPE
   SYNTAX         Counter32
   MAX-ACCESS     read-only
   STATUS         current
   DESCRIPTION
      "The number of transmitter underruns on this HDLC interface." 
   ::= { qtechSyncStatsEntry 22 }
   
qtechSyncStatsMibConformance OBJECT IDENTIFIER ::= { qtechSyncStatsMIB 2 }

qtechSyncStatsMibCompliances OBJECT IDENTIFIER ::= { qtechSyncStatsMibConformance 1 }
qtechSyncStatsMibGroups OBJECT IDENTIFIER ::= { qtechSyncStatsMibConformance 2 }

qtechSyncStatsMibCompliance MODULE-COMPLIANCE
   STATUS         current
   DESCRIPTION
      "The compliance statement for agents which 
       implement the Qtech Sync Statistics MIB."
   MODULE
   MANDATORY-GROUPS { 
      qtechSyncStatsGroup
   }
   ::= { qtechSyncStatsMibCompliances 1 }

qtechSyncStatsGroup OBJECT-GROUP
   OBJECTS
   {
      qtechSyncStatsRowStatus,
      qtechSyncStatsSlot,
      qtechSyncStatsConn,
      qtechSyncStatsChannel,
      qtechSyncStatsIfIndex,
      qtechSyncStatsPortState,
      qtechSyncStatsRxFrames,
      qtechSyncStatsRxOctets,
      qtechSyncStatsRxReplenFails,
      qtechSyncStatsRxClockErrors,
      qtechSyncStatsRxDpllErrors,
      qtechSyncStatsRxFrameTooLongErrors,
      qtechSyncStatsRxFrameOctetAlignErrors,
      qtechSyncStatsRxAbortErrors,
      qtechSyncStatsRxCrcErrors,          
      qtechSyncStatsRxRcvrOverrunErrors,
      qtechSyncStatsTxFrames,
      qtechSyncStatsTxOctets,
      qtechSyncStatsTxRingFullDropsErrors,
      qtechSyncStatsTxClockErrors,
      qtechSyncStatsTxFrameTooLongErrors,
      qtechSyncStatsTxUnderrunErrors
   }
   STATUS   current
   DESCRIPTION
          "The objects for SYNC configuration."
   ::= { qtechSyncStatsMibGroups 1 }

END

-- *****************************************************************
-- QTECH-TUNNEL-MIB.mib:  Qtech Time MIB file
--
-- June 2012, zhangtao
--
-- Copyright (c) 2012 by Qtech Networks Co.,Ltd.
-- All rights reserved.
-- 
-- *****************************************************************
--

QTECH-TUNNEL-MIB DEFINITIONS ::= BEGIN

    IMPORTS
        qtechMgmt			
            FROM QTECH-SMI			
        IpAddress, Integer32, OBJECT-TYPE, MODULE-IDENTITY			
            FROM SNMPv2-SMI;

		-- 1.3.6.1.4.1.27514.1.1.10.2.1
    qtechTunnelMib MODULE-IDENTITY 
        LAST-UPDATED "201206201634Z"		-- June 20, 2012 at 16:34 GMT
        ORGANIZATION 
            "Qtech Networks Co.,Ltd."
        CONTACT-INFO 
            "
             Tel: 4008-111-000 
					
             E-mail: service@qtech.com.cn"
        DESCRIPTION 
             "This module defines qtech tunnel mibs."
        REVISION      
             "201206200000Z"
        DESCRIPTION
            "Initial version of this MIB module."
			::= { qtechMgmt 114 }
			
--
-- Node definitions
--
	
		-- 1.3.6.1.4.1.27514.1.1.10.2.1.1
		qtechTunnelObjects OBJECT IDENTIFIER ::= { qtechTunnelMib 1 }
		
		-- 1.3.6.1.4.1.27514.1.1.10.2.1.1.1
		qtechTunnelTable OBJECT-TYPE
			SYNTAX SEQUENCE OF QtechTunnelEntry
			MAX-ACCESS not-accessible
			STATUS current
			DESCRIPTION
				"Description."
			::= { qtechTunnelObjects 1 }
		
		-- 1.3.6.1.4.1.27514.1.1.10.2.1.1.1.1
		qtechTunnelEntry OBJECT-TYPE
			SYNTAX QtechTunnelEntry
			MAX-ACCESS not-accessible
			STATUS current
			DESCRIPTION
				"Description."
			INDEX { qtechTunnelIp }
			::= { qtechTunnelTable 1 }
		
		QtechTunnelEntry ::=
			SEQUENCE { 
				qtechTunnelIp
					IpAddress,
				qtechTunnelOutIfindex
					Integer32
			 }

		-- 1.3.6.1.4.1.27514.1.1.10.2.1.1.1.1.1
		qtechTunnelIp OBJECT-TYPE
			SYNTAX IpAddress
			MAX-ACCESS read-only
			STATUS current
			DESCRIPTION
				"Description."
			::= { qtechTunnelEntry 1 }
		
		-- 1.3.6.1.4.1.27514.1.1.10.2.1.1.1.1.2
		qtechTunnelOutIfindex OBJECT-TYPE
			SYNTAX Integer32
			MAX-ACCESS read-only
			STATUS current
			DESCRIPTION
				"Description."
			::= { qtechTunnelEntry 2 }
	
	END

--
-- QTECH-TUNNEL-MIB.my
--

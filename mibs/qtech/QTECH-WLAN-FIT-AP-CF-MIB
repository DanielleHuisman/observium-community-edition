-- *******************************************************************
-- QTECH-WLAN-FIT-AP-CF-MIB.mib : Qtech MIB
-- May 2010, ruanyucheng	
--
-- Copyright (c) 2010 by Qtech Networks Co.,Ltd.
-- All rights reserved.
-- *******************************************************************
QTECH-WLAN-FIT-AP-CF-MIB DEFINITIONS ::= BEGIN
    IMPORTS
        MODULE-IDENTITY,
        OBJECT-TYPE,
        Integer32,
        Counter32,
        Counter64,
        IpAddress,
        Unsigned32
            FROM SNMPv2-SMI
        TruthValue,
        DisplayString,
        MacAddress,
        RowStatus
            FROM SNMPv2-TC
        Gauge
            FROM RFC1155-SMI
        MODULE-COMPLIANCE,
        NOTIFICATION-GROUP,
        OBJECT-GROUP
            FROM SNMPv2-CONF
        qtechStaMacAddr,    
        qtechApApName,
        qtechApCfgRadioId,    
        qtechApMacAddr,
        qtechApgWlanId
            FROM QTECH-AC-MGMT-MIB
        IANAifType
            FROM IANAifType-MIB     
        ifIndex
            FROM RFC1213-MIB
        TimeTicks
            FROM SNMPv2-SMI    
        qtechMgmt
            FROM QTECH-SMI;
--*******************************************
--* module definition
--*******************************************
qtechFitApMibModule MODULE-IDENTITY
    LAST-UPDATED    "201002260000Z"
    ORGANIZATION
        "Qtech Networks Co.,Ltd."
    CONTACT-INFO
        "Tel: 4008-111-000
           E-mail: service@qtech.com.cn "

    DESCRIPTION
       "
       Wlan software private MIB for Qtech SNC according to the China
       Mobile standard. This is device manage MIB.
       "
    REVISION      "201002280000Z"
    DESCRIPTION
       "Initial version of this MIB module."

    ::= { qtechMgmt  81 }
    
--**************************************************
--* apQtechTrapObjects begins * 
--**************************************************    
apQtechAlarmTraps            OBJECT IDENTIFIER  ::= { qtechFitApMibModule 0 }  
apQtechAlarmTrapObjects      OBJECT IDENTIFIER  ::= { qtechFitApMibModule 11 }  
apSystemAlarmTraps            OBJECT IDENTIFIER  ::= { apQtechAlarmTraps 1 }
apWirelessAlarmTraps          OBJECT IDENTIFIER  ::= { apQtechAlarmTraps 2 }
apStaAnnounceTraps            OBJECT IDENTIFIER  ::= { apQtechAlarmTraps 3 }
apWAPISecurityAlarmTraps      OBJECT IDENTIFIER  ::= { apQtechAlarmTraps 4 }
--**************apSystemAlarmTraps start ************************************
apCPUusageTooHighTrap NOTIFICATION-TYPE
    STATUS  current
    DESCRIPTION
            " This trap will be sent when the ap cpu usage too High."
    ::= { apSystemAlarmTraps 1 }
    
apCPUusageTooHighRecovTrap  NOTIFICATION-TYPE
    STATUS  current
    DESCRIPTION
            " This trap will be sent when the ap cpu usage too High state disappeared."
    ::= { apSystemAlarmTraps 2 }  
    
apMemUsageTooHighTrap  NOTIFICATION-TYPE
    STATUS  current
    DESCRIPTION
            " This trap will be sent when the ap Memory usage too High."
    ::= { apSystemAlarmTraps 3 }
    
apMemUsageTooHighRecovTrap  NOTIFICATION-TYPE
    STATUS  current
    DESCRIPTION
            " This trap will be sent when the ap Memory usage too High state disappeared."
    ::= { apSystemAlarmTraps 4 }  
    
aPOfflineTrap    NOTIFICATION-TYPE
    STATUS  current
    DESCRIPTION
            " This trap will be sent when the ap offline."
    ::= { apSystemAlarmTraps 5 }  
    
aPOnlineTrap    NOTIFICATION-TYPE
    STATUS  current
    DESCRIPTION
            " This trap will be sent when the ap Online."
    ::= { apSystemAlarmTraps 6 }  

aPMtWorkModeChgTrap    NOTIFICATION-TYPE
    OBJECTS {
        apAPMac,
        apWorkModeBeforeChange,
        apWorkModeAfterChange
    } 
    STATUS  current
    DESCRIPTION
            " This trap will be sent when the ap monitor workMode Change."
    ::= { apSystemAlarmTraps 7 }
    
apSoftwareUpdateFailTrap    NOTIFICATION-TYPE
    OBJECTS {
        updateFailReason,
        apSWVersionBeforeUpdate
    }    
    STATUS  current
    DESCRIPTION
            " This trap will be sent when software update fail."
    ::= { apSystemAlarmTraps 8 }   

apSSIDCyperConflictTrap    NOTIFICATION-TYPE
    OBJECTS {
				qtechApMacAddr,
				apWorkingAPRadioIfInfo,
				apSSIDKey,
				apSSIDKeyConflict,
				apCyperIndex
    }    
    STATUS  current
    DESCRIPTION
            " This trap will be sent when SSID cyper conflict."
    ::= { apSystemAlarmTraps 9 }      

--***************apWirelessAlarmTraps************************
aPCoInterfDetectedTrap     NOTIFICATION-TYPE
    OBJECTS {
        qtechApMacAddr,
        apWorkingAPRadioIfInfo,
        apWorkingAPChannel,
        apInterfAPBSSID
    }
    STATUS  current
    DESCRIPTION
            " This trap will be sent when detecting an same channel AP interfere Detected"
    ::= { apWirelessAlarmTraps 1 }
   
aPCoInterfClearTrap   NOTIFICATION-TYPE
    OBJECTS {
    		qtechApMacAddr,
        apWorkingAPRadioIfInfo,
        apWorkingAPChannel,
        apInterfAPBSSID
    }
    STATUS  current
    DESCRIPTION
            " This trap will be sent when the an same channel AP interfere Disappear."
    ::= { apWirelessAlarmTraps 2 }   
    
aPNerborInterfDetectedTrap NOTIFICATION-TYPE
    OBJECTS {
    		qtechApMacAddr,
        apWorkingAPRadioIfInfo,
        apWorkingAPChannel,
        apInterfAPBSSID,
        apInterfAPChannel
    }
    STATUS  current
    DESCRIPTION
            " This trap will be sent when detecting an same channel Nerbor AP interfere Detected"
    ::= { apWirelessAlarmTraps 3 }
    
aPNeiborInterfClearTrap   NOTIFICATION-TYPE
    OBJECTS {
    		qtechApMacAddr,
        apWorkingAPRadioIfInfo,
        apWorkingAPChannel,
        apInterfAPBSSID,
        apInterfAPChannel
    }
    STATUS  current
    DESCRIPTION
            " This trap will be sent when the Neibor interfere AP Disappear."
    ::= { apWirelessAlarmTraps 4 }   
    
staInterfDetectedTrap   NOTIFICATION-TYPE
    OBJECTS {
    		qtechApMacAddr,
        apWorkingAPRadioIfInfo,
        apWorkingAPChannel,
				apInterfStaMac
    }
    STATUS  current
    DESCRIPTION
            " This trap will be sent when the Station interfere Detected."
    ::= { apWirelessAlarmTraps 5 } 

staInterfClearTrap NOTIFICATION-TYPE
    OBJECTS {
     		qtechApMacAddr,
        apWorkingAPRadioIfInfo,
        apWorkingAPChannel,
				apInterfStaMac
    }
    STATUS  current
    DESCRIPTION
            " This trap will be sent when the Station interfere Disappear."
    ::= { apWirelessAlarmTraps 6 }
    
otherDeviceInterfDetectedTrap    NOTIFICATION-TYPE
    OBJECTS {
    		qtechApMacAddr,
        apWorkingAPRadioIfInfo,
        apWorkingAPChannel
    }
    STATUS  current
    DESCRIPTION
            " This trap will be sent when the other interfere Device Detected."
    ::= { apWirelessAlarmTraps 7 } 
    
otherDevInterfClearTrap    NOTIFICATION-TYPE
    OBJECTS {
    		qtechApMacAddr,
        apWorkingAPRadioIfInfo,
        apWorkingAPChannel
    }
    STATUS  current
    DESCRIPTION
            " This trap will be sent when the other interfere Device Disappear."
    ::= { apWirelessAlarmTraps 8 } 
    
apRadioDownTrap    NOTIFICATION-TYPE
    OBJECTS {
    		qtechApMacAddr,
        apWorkingAPRadioIfInfo,
        apInterruptReason 
    }
    STATUS  current
    DESCRIPTION
            " This trap will be sent when AP Radio has been down"
    ::= { apWirelessAlarmTraps 9 }
    
apRadioDownRecovTrap  NOTIFICATION-TYPE
    OBJECTS {
    		qtechApMacAddr,
        apWorkingAPRadioIfInfo,
        apInterruptReason 
    }
    STATUS  current
    DESCRIPTION
            " This trap will be sent when AP Radio down State Disappear."
    ::= { apWirelessAlarmTraps 10 }   
    
aPStaFullTrap    NOTIFICATION-TYPE
    OBJECTS {
    		qtechApMacAddr,
				apPermitAssoUser,
				apAssoFailReason    
		}
    STATUS  current
    DESCRIPTION
            " This trap will be sent when AP Station Num has reach to MAX , 
              AP can not add another Station."
    ::= { apWirelessAlarmTraps 11 }
    
aPStaFullRecoverTrap NOTIFICATION-TYPE
    OBJECTS {
    		qtechApMacAddr,
				apPermitAssoUser,
				apAssoFailReason    
		}
    STATUS  current
    DESCRIPTION
            " This trap will be sent when AP Station Num reach to MAX state disapper, 
              AP can  add other Stations."
    ::= { apWirelessAlarmTraps 12 }   
    
aPMtRdoChanlChgTrap NOTIFICATION-TYPE
		OBJECTS {
        qtechApMacAddr,
				apChannelBeforeChange,
				apChannelAfterChange,
				apChanChangeMode    
    }
    STATUS  current
    DESCRIPTION
            " This trap will be sent when AP Channel has been changed ."
    ::= { apWirelessAlarmTraps 13 } 

apSpeciusDeviceDetectTrap NOTIFICATION-TYPE
		OBJECTS {
    		qtechApMacAddr,
        apSpeciousDeviceMac
    }
    STATUS  current
    DESCRIPTION
            " This trap will be sent when specious device is found ."
    ::= { apWirelessAlarmTraps 14 }     
   
apRadioRxPackagesTrap  NOTIFICATION-TYPE
		OBJECTS {
			  qtechApMacAddr,
	      apAPRadioId,
	      apRevPackages		  
    }
    STATUS  current
    DESCRIPTION
            " This trap will be sent when AP receive packages update."
    ::= { apWirelessAlarmTraps 15 }  
    
apCPUUsageTrap  NOTIFICATION-TYPE
		OBJECTS {
			  qtechApMacAddr,
	      apCPUUsage		  
    }
    STATUS  current
    DESCRIPTION
            " This trap will be sent when cpu usage rate update."
    ::= { apWirelessAlarmTraps 16 }    
    
apSTARefusedRSSITrap  NOTIFICATION-TYPE
		OBJECTS {
    		qtechApMacAddr,
			  apStaMacAddr,
	      apRSSI		  
    }
    STATUS  current
    DESCRIPTION
            " This trap will be sent when sta rssi is lower than rssi thrreshold."
    ::= { apWirelessAlarmTraps 17 }        

apSTARefusedRatesetTrap  NOTIFICATION-TYPE
		OBJECTS {
    		qtechApMacAddr,
			  apStaMacAddr
    }
    STATUS  current
    DESCRIPTION
            " This trap will be sent when rate set is not satisified."
    ::= { apWirelessAlarmTraps 18 }   
    
apFindAttackTrap  NOTIFICATION-TYPE
		OBJECTS {
    		qtechApMacAddr,
			  apAttackReason
    }
    STATUS  current
    DESCRIPTION
            " This trap will be sent when rate set is not satisified."
    ::= { apWirelessAlarmTraps 19 }         
    
wlanSecurityChgTrap NOTIFICATION-TYPE
    	OBJECTS {
    	 	apWlanId,
    	 	apWlanSSID,
        	apWlanSecurityModeBeforeChg,
        	apWlanSecurityModeAfterChg
    }
    STATUS  current
    DESCRIPTION
            " This trap will be sent when wlan security mode has been changed "
    ::= { apWirelessAlarmTraps 20 }

apRadioFailureTrap    NOTIFICATION-TYPE
    OBJECTS {
    	qtechApMacAddr,
        apWorkingAPRadioIfInfo,
        apInterruptReason
    }
    STATUS  current
    DESCRIPTION
            " This trap will be sent when AP Radio failure"
    ::= { apWirelessAlarmTraps 21 }
	
apIllegalApTrap    NOTIFICATION-TYPE
    OBJECTS {
    	apTrapIllegalApMac,
        apTrapIllegalApChannel,
        apTrapIllegalApRSSI,
        apTrapWorkingApMac,
        apTrapWorkingApBSSID,
        apTrapIllegalApType,
        apTrapIllegalApSSID		
    }
    STATUS  current
    DESCRIPTION
            " This trap will be sent when AP detect illegal ap"
    ::= { apWirelessAlarmTraps 22 }
	
apIllegalApRecoverTrap    NOTIFICATION-TYPE
    OBJECTS {
    	apTrapIllegalApMac,
        apTrapIllegalApChannel,
        apTrapIllegalApRSSI,
        apTrapWorkingApMac,
        apTrapWorkingApBSSID,
        apTrapIllegalApType,
        apTrapIllegalApSSID
    }
    STATUS  current
    DESCRIPTION
            " This trap will be sent when illegal ap disappears"
    ::= { apWirelessAlarmTraps 23 }
	
apStaAssocFailTrap    NOTIFICATION-TYPE
    OBJECTS {
        qtechApMacAddr,
        apStaMacAddr,
        apAPRadioId,
        apAPRadioType,
        apAssocAuthMode,
        apStaRSSI,
        apWorkingAPSSID,
        apAssocFailReason,
        apWorkingAPChannel
    }
    STATUS  current
    DESCRIPTION
            " This trap will be sent when sta assoc fail"
    ::= { apWirelessAlarmTraps 24 }
	
apSpectralInfoTrap    NOTIFICATION-TYPE
    OBJECTS {
        apSpectralInfoApMac,
        apSpectralInfoType,
        apSpectralInfoFreq,
        apSpectralInfoRssi
    }
    STATUS  current
    DESCRIPTION
            " This trap will be sent when AC receive spectral info from AP"
    ::= { apWirelessAlarmTraps 25 }

apCounterMeasureTrap    NOTIFICATION-TYPE
    OBJECTS {
        apCounterMeasureApMac,
        apCounterMeasureBssid
    }
    STATUS  current
    DESCRIPTION
            " This trap will be sent when AC receive counter measure info from AP"
    ::= { apWirelessAlarmTraps 26 }
	
--*****************apStaAnnounceTraps*****************
apStaAuthErrorTrap  NOTIFICATION-TYPE
		OBJECTS {
    		qtechApMacAddr,
        apWorkingAPRadioIfInfo,        
        apWorkingAPBSSID,
        apWorkingAPSSID,
        apStaMacAddr,
        apAuthMode,
        apAuthFailReason     
    }
    STATUS  current
    DESCRIPTION
            " This trap will be sent when station connect ap,then Auth Fail appeared."
    ::= { apStaAnnounceTraps 1 } 

apStAssociationFailTrap    NOTIFICATION-TYPE
		OBJECTS {
    		qtechApMacAddr,
        apWorkingAPRadioIfInfo,        
        apWorkingAPBSSID,
        apWorkingAPSSID,
        apStaMacAddr,
        apAssoFailReason  
    }
    STATUS  current
    DESCRIPTION
            " This trap will be sent when station Associa  Fail appeared."
    ::= { apStaAnnounceTraps 2 } 
--****************apWAPISecurityAlarmTraps************
userwithInvalidCerficationInbreakNetwork NOTIFICATION-TYPE
    OBJECTS {
    		qtechApMacAddr,
        apWorkingAPRadioIfInfo,        
        apWorkingAPBSSID,
        apWorkingAPSSID,
        apStaMacAddr
    }
    STATUS  current
    DESCRIPTION
            " This trap will be sent when detecting an user accesses the network
            with invlid certification."
    ::= { apWAPISecurityAlarmTraps 1 }   
    
stationRepititiveAttack NOTIFICATION-TYPE
    OBJECTS {
    		qtechApMacAddr,
        apWorkingAPRadioIfInfo,        
        apWorkingAPBSSID,
        apWorkingAPSSID,
        apStaMacAddr
    }
    STATUS  current
    DESCRIPTION
            " This trap will be sent when detecting an illegal client catches the
            packets of the WAPI authentication process of legal client and pretend
            to be legal client to authenticate."
    ::= { apWAPISecurityAlarmTraps 2 }  
    
tamperAttack NOTIFICATION-TYPE
    OBJECTS {
    		qtechApMacAddr,
        apWorkingAPRadioIfInfo,        
        apWorkingAPBSSID,
        apWorkingAPSSID,
        apStaMacAddr
    }
    STATUS  current
    DESCRIPTION
            " This trap will be sent when detecting an illegal client catches the
            packets of the WAPI authentication process of legal client, modifies
            the bytes of the authentication code of the packets and uses the packets
            to pass the WAPI authentication."
    ::= { apWAPISecurityAlarmTraps 3 }  
    
lowSafeLevelAttack NOTIFICATION-TYPE
    OBJECTS {
     		qtechApMacAddr,
        apWorkingAPRadioIfInfo,        
        apWorkingAPBSSID,
        apWorkingAPSSID,
        apStaMacAddr
    }
    STATUS  current
    DESCRIPTION
            " This trap will be sent when detecting an illegal client catches the
            packets of the WAPI authentication process of legal client, modifies
            the bytes of the authentication code of the packets to lower the safe
            level and uses the packets to pass the WAPI authentication."
    ::= { apWAPISecurityAlarmTraps 4 }     
    
addressRedirectionAttack NOTIFICATION-TYPE
    OBJECTS {
    		qtechApMacAddr,
        apWorkingAPRadioIfInfo,        
        apWorkingAPBSSID,
        apWorkingAPSSID,
        apStaMacAddr
    }
    STATUS  current
    DESCRIPTION
            " This trap will be sent when detecting an client passes the authentication
            process, but the destination address of the 802.11 head of the WPI frame."
    ::= { apWAPISecurityAlarmTraps 5 }     
       
--***************apQtechAlarmTrapObjects*************
apAPMac OBJECT-TYPE
    SYNTAX MacAddress
    MAX-ACCESS read-only
    STATUS current
    DESCRIPTION
        "AP mac address"
    ::= { apQtechAlarmTrapObjects 1 }
    
apWorkModeBeforeChange    OBJECT-TYPE
    SYNTAX      INTEGER
    MAX-ACCESS  read-only
    STATUS      current
    DESCRIPTION
        " ap work mode before change"
    ::= { apQtechAlarmTrapObjects 2 }  

apWorkModeAfterChange    OBJECT-TYPE
    SYNTAX      INTEGER
    MAX-ACCESS  read-only
    STATUS      current
    DESCRIPTION
        " ap work mode after change"
    ::= { apQtechAlarmTrapObjects 3 } 
    
apSSIDKey OBJECT-TYPE
    SYNTAX DisplayString
    MAX-ACCESS read-only
    STATUS current
    DESCRIPTION
        "Key SSID"
    ::= { apQtechAlarmTrapObjects 4 }
    
apSSIDKeyConflict OBJECT-TYPE
    SYNTAX DisplayString
    MAX-ACCESS read-only
    STATUS current
    DESCRIPTION
        "Key SSID"
    ::= { apQtechAlarmTrapObjects 5 }
 
apCyperIndex OBJECT-TYPE
    SYNTAX INTEGER
    MAX-ACCESS read-only
    STATUS current
    DESCRIPTION
        "Key SSID"
    ::= { apQtechAlarmTrapObjects 6 } 
    
apInterruptReason OBJECT-TYPE
    SYNTAX DisplayString
    MAX-ACCESS read-only
    STATUS current
    DESCRIPTION
        "The interrupt reason of the wireless link"
    ::= { apQtechAlarmTrapObjects 7} 
    
apWorkingAPRadioIfInfo OBJECT-TYPE
    SYNTAX MacAddress
    MAX-ACCESS read-only
    STATUS current
    DESCRIPTION
        "radio interface infomation."
    ::= { apQtechAlarmTrapObjects 8} 
 
apWorkingAPChannel OBJECT-TYPE
    SYNTAX INTEGER
    MAX-ACCESS read-only
    STATUS current
    DESCRIPTION
        "Channel of working AP"
    ::= { apQtechAlarmTrapObjects 9}  
    
apInterfAPChannel OBJECT-TYPE
    SYNTAX INTEGER
    MAX-ACCESS read-only
    STATUS current
    DESCRIPTION
        "Channel of inteference AP"
    ::= { apQtechAlarmTrapObjects 10}  
    
apInterfAPBSSID OBJECT-TYPE
    SYNTAX MacAddress
    MAX-ACCESS read-only
    STATUS current
    DESCRIPTION
        "BSSID of inteference AP"
    ::= { apQtechAlarmTrapObjects 11}
    
apInterfStaMac OBJECT-TYPE
    SYNTAX MacAddress
    MAX-ACCESS read-only
    STATUS current
    DESCRIPTION
        "mac of inteference STA"
    ::= { apQtechAlarmTrapObjects 12}   

  
apPermitAssoUser OBJECT-TYPE
    SYNTAX INTEGER
    MAX-ACCESS read-only
    STATUS current
    DESCRIPTION
        "mac of inteference STA"
    ::= { apQtechAlarmTrapObjects 13}   
    
apAssoFailReason OBJECT-TYPE
    SYNTAX DisplayString
    MAX-ACCESS read-only
    STATUS current
    DESCRIPTION
        "Association fail reason."
    ::= { apQtechAlarmTrapObjects 14} 
    
apChannelBeforeChange OBJECT-TYPE
    SYNTAX INTEGER
    MAX-ACCESS read-only
    STATUS current
    DESCRIPTION
        "radio channel before channel change."
    ::= { apQtechAlarmTrapObjects 15} 

apChannelAfterChange OBJECT-TYPE
    SYNTAX INTEGER
    MAX-ACCESS read-only
    STATUS current
    DESCRIPTION
        "radio channel after channel change."
    ::= { apQtechAlarmTrapObjects 16}  
    
apChanChangeMode OBJECT-TYPE
    SYNTAX INTEGER
    MAX-ACCESS read-only
    STATUS current
    DESCRIPTION
        "radio channel change mode."
    ::= { apQtechAlarmTrapObjects 17} 
    
apWorkingAPBSSID OBJECT-TYPE
    SYNTAX MacAddress
    MAX-ACCESS read-only
    STATUS current
    DESCRIPTION
        "AP BSSID"
    ::= { apQtechAlarmTrapObjects 18} 

apWorkingAPSSID OBJECT-TYPE
    SYNTAX DisplayString
    MAX-ACCESS read-only
    STATUS current
    DESCRIPTION
        "AP SSID"
    ::= { apQtechAlarmTrapObjects 19}        
    
apStaMacAddr OBJECT-TYPE
    SYNTAX MacAddress
    MAX-ACCESS read-only
    STATUS current
    DESCRIPTION
        "MAC address of the STA"
    ::= { apQtechAlarmTrapObjects 20}     

apAuthMode OBJECT-TYPE
    SYNTAX INTEGER
    MAX-ACCESS read-only
    STATUS current
    DESCRIPTION
        "auth mode"
    ::= { apQtechAlarmTrapObjects 21}   
    
apAuthFailReason OBJECT-TYPE
    SYNTAX DisplayString
    MAX-ACCESS read-only
    STATUS current
    DESCRIPTION
        "Reason of the 	 failure"
    ::= { apQtechAlarmTrapObjects 22}  
     
 
updateFailReason   OBJECT-TYPE
    SYNTAX      DisplayString
    MAX-ACCESS  read-only
    STATUS      current
    DESCRIPTION
        "software update fail reason"
    ::= { apQtechAlarmTrapObjects 23 } 
    
apSWVersionBeforeUpdate   OBJECT-TYPE
    SYNTAX      DisplayString
    MAX-ACCESS  read-only
    STATUS      current
    DESCRIPTION
        "software version before update"
    ::= { apQtechAlarmTrapObjects 24 } 
        
apAPRadioId   OBJECT-TYPE
    SYNTAX      INTEGER
    MAX-ACCESS  read-only
    STATUS      current
    DESCRIPTION
        "AP radio id"
    ::= { apQtechAlarmTrapObjects 25 }    

apRevPackages   OBJECT-TYPE
    SYNTAX      INTEGER
    MAX-ACCESS  read-only
    STATUS      current
    DESCRIPTION
        "AP received packages"
    ::= { apQtechAlarmTrapObjects 26 } 
    
apCPUUsage   OBJECT-TYPE
    SYNTAX      INTEGER
    MAX-ACCESS  read-only
    STATUS      current
    DESCRIPTION
        "AP CPU usage"
    ::= { apQtechAlarmTrapObjects 27 }  
    
apSpeciousDeviceMac   OBJECT-TYPE
    SYNTAX      MacAddress
    MAX-ACCESS  read-only
    STATUS      current
    DESCRIPTION
        "specious device mac address"
    ::= { apQtechAlarmTrapObjects 28 } 
    
apRSSI   OBJECT-TYPE
    SYNTAX      INTEGER
    MAX-ACCESS  read-only
    STATUS      current
    DESCRIPTION
        "STA RSSI value"
    ::= { apQtechAlarmTrapObjects 29 }   
    
apAttackReason   OBJECT-TYPE
    SYNTAX      DisplayString
    MAX-ACCESS  read-only
    STATUS      current
    DESCRIPTION
        "attack reason"
    ::= { apQtechAlarmTrapObjects 30 }    
    
apWlanId   OBJECT-TYPE
    SYNTAX      INTEGER
    MAX-ACCESS  read-only
    STATUS      current
    DESCRIPTION
        "wlan id"
    ::= { apQtechAlarmTrapObjects 31 }  
    
apWlanSSID   OBJECT-TYPE
    SYNTAX      DisplayString
    MAX-ACCESS  read-only
    STATUS      current
    DESCRIPTION
        "wlan ssid"
    ::= { apQtechAlarmTrapObjects 32 }     
    
apWlanSecurityModeBeforeChg   OBJECT-TYPE
    SYNTAX      DisplayString
    MAX-ACCESS  read-only
    STATUS      current
    DESCRIPTION
        "wlan Security Mode Before Change."
    ::= { apQtechAlarmTrapObjects 33 }  

apWlanSecurityModeAfterChg   OBJECT-TYPE
    SYNTAX      DisplayString
    MAX-ACCESS  read-only
    STATUS      current
    DESCRIPTION
        "wlan Security Mode After Change."
    ::= { apQtechAlarmTrapObjects 34 }    
	
apTrapIllegalApMac   OBJECT-TYPE
    SYNTAX      MacAddress
    MAX-ACCESS  read-only
    STATUS      current
    DESCRIPTION
        "illegal ap mac, trap bind var."
    ::= { apQtechAlarmTrapObjects 35 }    
	
apTrapIllegalApChannel   OBJECT-TYPE
    SYNTAX      INTEGER
    MAX-ACCESS  read-only
    STATUS      current
    DESCRIPTION
        "illegal ap channel, trap bind var."
    ::= { apQtechAlarmTrapObjects 36 }   
	
apTrapIllegalApRSSI   OBJECT-TYPE
    SYNTAX      INTEGER
    MAX-ACCESS  read-only
    STATUS      current
    DESCRIPTION
        "illegal ap RSSI, trap bind var."
    ::= { apQtechAlarmTrapObjects 37 }   
    
apTrapWorkingApMac   OBJECT-TYPE
    SYNTAX      MacAddress
    MAX-ACCESS  read-only
    STATUS      current
    DESCRIPTION
        "working ap mac, trap bind var."
    ::= { apQtechAlarmTrapObjects 38 }    	
    
apTrapWorkingApBSSID   OBJECT-TYPE
    SYNTAX      MacAddress
    MAX-ACCESS  read-only
    STATUS      current
    DESCRIPTION
        "working ap bssid, trap bind var."
    ::= { apQtechAlarmTrapObjects 39 }    	
    
apTrapIllegalApType   OBJECT-TYPE
    SYNTAX      INTEGER
    MAX-ACCESS  read-only
    STATUS      current
    DESCRIPTION
        "illegal ap type, trap bind var."
    ::= { apQtechAlarmTrapObjects 40 }   
	
apTrapIllegalApSSID   OBJECT-TYPE
    SYNTAX      DisplayString
    MAX-ACCESS  read-only
    STATUS      current
    DESCRIPTION
        "illegal ap SSID, trap bind var."
    ::= { apQtechAlarmTrapObjects 41 }
	
apAPRadioType   OBJECT-TYPE
    SYNTAX      INTEGER{
        dot11a(0),
        dot11b(1) 	
	}
    MAX-ACCESS  read-only
    STATUS      current
    DESCRIPTION
        "ap radio type 0:80211a  1:80211b, trap bind var."
    ::= { apQtechAlarmTrapObjects 42 }
	
apAssocAuthMode   OBJECT-TYPE
    SYNTAX      INTEGER
    MAX-ACCESS  read-only
    STATUS      current
    DESCRIPTION
        "assoc auth mode, trap bind var."
    ::= { apQtechAlarmTrapObjects 43 }
	
apStaRSSI   OBJECT-TYPE
    SYNTAX      DisplayString
    MAX-ACCESS  read-only
    STATUS      current
    DESCRIPTION
        "sta RSSI, trap bind var."
    ::= { apQtechAlarmTrapObjects 44 }
	
apAssocFailReason   OBJECT-TYPE
    SYNTAX      INTEGER 
    MAX-ACCESS  read-only
    STATUS      current
    DESCRIPTION
        "assoc fail reason, trap bind var."
    ::= { apQtechAlarmTrapObjects 45 }
	
apSpectralInfoApMac   OBJECT-TYPE
    SYNTAX      MacAddress
    MAX-ACCESS  read-only
    STATUS      current
    DESCRIPTION
        "spectral ap mac, trap bind var."
    ::= { apQtechAlarmTrapObjects 46 }
	
apSpectralInfoType   OBJECT-TYPE
    SYNTAX      INTEGER
    MAX-ACCESS  read-only
    STATUS      current
    DESCRIPTION
        "spectral type, trap bind var."
    ::= { apQtechAlarmTrapObjects 47 }
	
apSpectralInfoFreq   OBJECT-TYPE
    SYNTAX      INTEGER
    MAX-ACCESS  read-only
    STATUS      current
    DESCRIPTION
        "spectral freq, trap bind var."
    ::= { apQtechAlarmTrapObjects 48 }
	
apSpectralInfoRssi   OBJECT-TYPE
    SYNTAX      INTEGER
    MAX-ACCESS  read-only
    STATUS      current
    DESCRIPTION
        "spectral rssi, trap bind var."
    ::= { apQtechAlarmTrapObjects 49 }

apCounterMeasureApMac   OBJECT-TYPE
    SYNTAX      MacAddress
    MAX-ACCESS  read-only
    STATUS      current
    DESCRIPTION
        "the mac of ap which counters the wlan, trap bind var."
    ::= { apQtechAlarmTrapObjects 50 }

apCounterMeasureBssid   OBJECT-TYPE
    SYNTAX      MacAddress
    MAX-ACCESS  read-only
    STATUS      current
    DESCRIPTION
        "the bssid which is countered, trap bind var."
    ::= { apQtechAlarmTrapObjects 51 }

--**************************************************
--* apQtechTrapObjects ends * 
--************************************************** 
apSystemInfoConfigObjects OBJECT IDENTIFIER  ::= { qtechFitApMibModule 1 }
apGeneralInfoConfigObjects OBJECT IDENTIFIER  ::= { apSystemInfoConfigObjects 1 }
apGeneralInfoReadObjects   OBJECT IDENTIFIER  ::= { apSystemInfoConfigObjects 2 }
apGeneralStatusCFGObjects OBJECT IDENTIFIER  ::= { apSystemInfoConfigObjects 3 }
--**************************************************
--* apGeneralInfoConfigObjects begins * 
--**************************************************
apGeneralInfoConfigTable  OBJECT-TYPE
    SYNTAX SEQUENCE OF ApGeneralInfoConfigTableEntry
    MAX-ACCESS not-accessible
    STATUS current
    DESCRIPTION
      "The general information configure table."
    ::={ apGeneralInfoConfigObjects 1 }

apGeneralInfoConfigTableEntry OBJECT-TYPE
    SYNTAX  ApGeneralInfoConfigTableEntry
    MAX-ACCESS  not-accessible
    STATUS  current
    DESCRIPTION
        "The general information configure table."
    INDEX   { qtechApMacAddr }
    ::= { apGeneralInfoConfigTable 1 }

ApGeneralInfoConfigTableEntry ::=
    SEQUENCE {
        apSysNEId                   DisplayString,
        apSysName                   DisplayString,
        apStatWindowTime            TimeTicks,
        apSampleTime                Counter32,
        apRtCollectOnoff            INTEGER,
        apSysRestart                INTEGER,
        apSysReset                  INTEGER
    }
    
apSysNEId OBJECT-TYPE
    SYNTAX DisplayString (SIZE(1..16))
    MAX-ACCESS read-write
    STATUS current
    DESCRIPTION
        "Network elements encoding of AP, unifiedly defined by
        China Mobile. It's length is not less than 16."
    ::= { apGeneralInfoConfigTableEntry 1 }
    
apSysName OBJECT-TYPE
    SYNTAX DisplayString (SIZE(1..40))
    MAX-ACCESS read-write
    STATUS current
    DESCRIPTION
        "The AP device name, in line with the naming
        convention of China Mobile. It's length will not be
        longer than 40."
    ::= { apGeneralInfoConfigTableEntry 2 }    

apStatWindowTime OBJECT-TYPE
    SYNTAX TimeTicks 
    MAX-ACCESS read-write
    STATUS current
    DESCRIPTION
        "cpu statistics time set,the units is second,max is 15  minute."
    ::= { apGeneralInfoConfigTableEntry 3 }

apSampleTime  OBJECT-TYPE
    SYNTAX Counter32
    MAX-ACCESS read-write
    STATUS current
    DESCRIPTION
        "ap sample time set,mini is 2 Second."
    ::= { apGeneralInfoConfigTableEntry 4 }
	  
apRtCollectOnoff OBJECT-TYPE
    SYNTAX INTEGER {
        off(0),
        on(1)       
    }
    MAX-ACCESS read-write
    STATUS current
    DESCRIPTION
        "Real-time collection of ap is enabled, 1:on  0:off."
    ::= { apGeneralInfoConfigTableEntry 5 }   
    
apSysRestart  OBJECT-TYPE
    SYNTAX INTEGER {
        normal(0),
        restart(1)       
    }
    MAX-ACCESS read-write
    STATUS current
    DESCRIPTION
        "restaet system config,0: normal 1:restart."
    ::= { apGeneralInfoConfigTableEntry 6 } 
         
apSysReset  OBJECT-TYPE
    SYNTAX INTEGER {
        normal(0),
        reset(1)       
    }
    MAX-ACCESS read-write
    STATUS current
    DESCRIPTION
        "rest system config to default config, 0:normal 1:reset ."
    ::= { apGeneralInfoConfigTableEntry 7 } 
--**************************************************
--* apGeneralInfoConfigObjects ends * 
--**************************************************    
--**************************************************
--* apGeneralInfoReadObjects starts * 
--**************************************************
apGeneralCfgInfoReadTable   OBJECT-TYPE
    SYNTAX SEQUENCE OF ApGeneralCfgInfoReadTableEntry
    MAX-ACCESS not-accessible
    STATUS current
    DESCRIPTION
      "The general information read."
    ::={ apGeneralInfoReadObjects 1 }
    
apGeneralCfgInfoReadTableEntry    OBJECT-TYPE
    SYNTAX  ApGeneralCfgInfoReadTableEntry
    MAX-ACCESS  not-accessible
    STATUS  current
    DESCRIPTION
        "The general information configure table."
    INDEX   { qtechApMacAddr }
    ::= { apGeneralCfgInfoReadTable 1 }

ApGeneralCfgInfoReadTableEntry ::=
    SEQUENCE {
        apSysDescr                   DisplayString,
        apSysManufacture             DisplayString,
        apSerialNumber               DisplayString,
        apSysModel                   DisplayString,
        apSysUpTime                  Counter32,
        apSysOnlineTime              Counter32,
        apSysIPAddress               IpAddress,
        apSysIPNetMask               IpAddress,
        apSysGateWayAddr             IpAddress,
        apSysMacAddrConnectToAC      MacAddress,
        apSoftwareName               DisplayString,
        apSoftwareVersion            DisplayString, 
        apSoftwareVendor             DisplayString,
        apCPUType                    DisplayString,
        apMemoryType                 DisplayString,
        apMemorySize                 OCTET STRING,
        apFlashSize                  OCTET STRING
    }

apSysDescr OBJECT-TYPE
    SYNTAX DisplayString (SIZE(1..255))
    MAX-ACCESS read-only
    STATUS current
    DESCRIPTION
        "ap systerm description detail"
    ::= { apGeneralCfgInfoReadTableEntry 1 }    
    
apSysManufacture  OBJECT-TYPE
    SYNTAX DisplayString (SIZE(1..255))
    MAX-ACCESS read-only
    STATUS current
    DESCRIPTION
        "ap systerm Manufacture "
    ::= { apGeneralCfgInfoReadTableEntry 2 }      
    
apSerialNumber  OBJECT-TYPE
    SYNTAX DisplayString (SIZE(1..255))
    MAX-ACCESS read-only
    STATUS current
    DESCRIPTION
        "ap product serial Number"
    ::= { apGeneralCfgInfoReadTableEntry 3 }      
    
apSysModel    OBJECT-TYPE
    SYNTAX DisplayString (SIZE(1..255))
    MAX-ACCESS read-only
    STATUS current
    DESCRIPTION
        "ap product type Model detail"
    ::= { apGeneralCfgInfoReadTableEntry 4 }    

apSysUpTime   OBJECT-TYPE
    SYNTAX Counter32
    MAX-ACCESS read-only
    STATUS current
    DESCRIPTION
        "The run time of the AP."
    ::= { apGeneralCfgInfoReadTableEntry 5 }
    
apSysOnlineTime   OBJECT-TYPE
    SYNTAX Counter32
    MAX-ACCESS read-only
    STATUS current
    DESCRIPTION
        "The time of the AP connect to AC."
    ::= { apGeneralCfgInfoReadTableEntry 6 }  
    
apSysIPAddress  OBJECT-TYPE
    SYNTAX IpAddress
    MAX-ACCESS read-only
    STATUS current
    DESCRIPTION
        "The ip of AP."
    ::= { apGeneralCfgInfoReadTableEntry 7 }    
    
apSysIPNetMask   OBJECT-TYPE
    SYNTAX IpAddress
    MAX-ACCESS read-only
    STATUS current
    DESCRIPTION
        "The netmask of the AP ip"
    ::= { apGeneralCfgInfoReadTableEntry 8 }      
    
apSysGateWayAddr OBJECT-TYPE
    SYNTAX IpAddress
    MAX-ACCESS read-only
    STATUS current
    DESCRIPTION
        "The gate way of the AP "
    ::= { apGeneralCfgInfoReadTableEntry 9 }   
    
apSysMacAddrConnectToAC  OBJECT-TYPE
    SYNTAX MacAddress
    MAX-ACCESS read-only
    STATUS current
    DESCRIPTION
        "The MAC interface of AP which connects with AC."
    ::= { apGeneralCfgInfoReadTableEntry 10 }      
    
apSoftwareName    OBJECT-TYPE
    SYNTAX DisplayString
    MAX-ACCESS read-only
    STATUS current
    DESCRIPTION
        "The software name of the ap system."
    ::= { apGeneralCfgInfoReadTableEntry 11 }   
    
apSoftwareVersion  OBJECT-TYPE
    SYNTAX DisplayString
    MAX-ACCESS read-only
    STATUS current
    DESCRIPTION
        "The software version of the ap system."
    ::= { apGeneralCfgInfoReadTableEntry 12 }    
    
apSoftwareVendor   OBJECT-TYPE
    SYNTAX DisplayString
    MAX-ACCESS read-only
    STATUS current
    DESCRIPTION
        "The software vendor of the ap system."
    ::= { apGeneralCfgInfoReadTableEntry 13 } 
    
apCPUType    OBJECT-TYPE
    SYNTAX DisplayString
    MAX-ACCESS read-only
    STATUS current
    DESCRIPTION
        "The cpu info of ap system."
    ::= { apGeneralCfgInfoReadTableEntry 14 }  
    
apMemoryType    OBJECT-TYPE
    SYNTAX DisplayString
    MAX-ACCESS read-only
    STATUS current
    DESCRIPTION
        "The memory and flash type of ap system."
    ::= { apGeneralCfgInfoReadTableEntry 15 }    
    
apMemorySize OBJECT-TYPE
    SYNTAX OCTET STRING
    MAX-ACCESS read-only
    STATUS current
    DESCRIPTION
        "The capability of the memory size."
    ::= { apGeneralCfgInfoReadTableEntry 17 }          
    
apFlashSize  OBJECT-TYPE
    SYNTAX OCTET STRING
    MAX-ACCESS read-only
    STATUS current
    DESCRIPTION
        "The capability of the flash size."
    ::= { apGeneralCfgInfoReadTableEntry 18 }        
--**************************************************
--* apGeneralInfoReadObjects ends * 
--**************************************************
--**************************************************
--* apGeneralStatusCFGObjects starts * 
--**************************************************    
apGeneralStatusCFGTable   OBJECT-TYPE
    SYNTAX SEQUENCE OF ApGeneralStatusCFGTableEntry
    MAX-ACCESS not-accessible
    STATUS current
    DESCRIPTION
      "The status of general information read."
    ::={ apGeneralStatusCFGObjects 1 }
    
apGeneralStatusCFGTableEntry    OBJECT-TYPE
    SYNTAX  ApGeneralStatusCFGTableEntry
    MAX-ACCESS  not-accessible
    STATUS  current
    DESCRIPTION
        "The general information configure table."
    INDEX   { apAssoStatusAPMac }
    ::= { apGeneralStatusCFGTable 1 }

ApGeneralStatusCFGTableEntry ::=
    SEQUENCE {
    		apAPName										 DisplayString,    		
        apACAssociateStatus          INTEGER,
        apMonitorMode                INTEGER,
        apAssoStatusAPMac						 MacAddress,
        apACHbAssocStatus			  INTEGER,
        apScanType						INTEGER
    }
    
apAPName OBJECT-TYPE
    SYNTAX DisplayString
    MAX-ACCESS read-only
    STATUS current
    DESCRIPTION
        "AP name"
    ::= { apGeneralStatusCFGTableEntry 1 }   
             
apACAssociateStatus OBJECT-TYPE
    SYNTAX  INTEGER {
         associate(1),
         deassociate(0)
    }
    MAX-ACCESS read-only
    STATUS current
    DESCRIPTION
        "AP associate AC states string 
        1:associated 0:deassociated "
    ::= { apGeneralStatusCFGTableEntry 2 }    
    
apMonitorMode  OBJECT-TYPE
    SYNTAX  INTEGER {
         normal(0),
         monitor(1),
         semiMonitor(2)
    }
    MAX-ACCESS  read-write
    STATUS  current
    DESCRIPTION
            "ap monitor mode 0:normal 1:monitor  2:SemiMonitor."
    ::= { apGeneralStatusCFGTableEntry 3 }  
    
apAssoStatusAPMac OBJECT-TYPE
    SYNTAX MacAddress
    MAX-ACCESS read-only
    STATUS current
    DESCRIPTION
        "AP MAC"
    ::= { apGeneralStatusCFGTableEntry 4 }  
    
apACHbAssocStatus OBJECT-TYPE
    SYNTAX  INTEGER {
         associate(1),
         deassociate(0)
    }
    MAX-ACCESS read-only
    STATUS current
    DESCRIPTION
        "AP associate back-up AC states string 
        1:associated 0:deassociated "
    ::= { apGeneralStatusCFGTableEntry 5 }    
    
apScanType	OBJECT-TYPE
    SYNTAX  INTEGER 
    MAX-ACCESS read-write
    STATUS current
    DESCRIPTION
        "AP scan type 
        1:scan working channel 0:scan_all "
    ::= { apGeneralStatusCFGTableEntry 6 }    
    
--**************************************************
--* apGeneralStatusCFGObjects ends * 
--**************************************************     
    
apInterfaceConfigObjects        OBJECT IDENTIFIER  ::= { qtechFitApMibModule 2 }  
apInterfaceNumberObjects        OBJECT IDENTIFIER  ::= { apInterfaceConfigObjects 1 }
apInterfaceRGMIIcfgObjects      OBJECT IDENTIFIER  ::= { apInterfaceConfigObjects 2 }
apInterfaceWirelesscfgObjects   OBJECT IDENTIFIER  ::= { apInterfaceConfigObjects 3 }
--**************************************************
--* apInterfaceConfig starts * 
--************************************************** 
apInterfaceNumberTable  OBJECT-TYPE
    SYNTAX SEQUENCE OF ApInterfaceNumberTableEntry
    MAX-ACCESS not-accessible
    STATUS current
    DESCRIPTION
      "The interface number of ap."
    ::={ apInterfaceNumberObjects 1 }

apInterfaceNumberTableEntry OBJECT-TYPE
    SYNTAX  ApInterfaceNumberTableEntry
    MAX-ACCESS  not-accessible
    STATUS  current
    DESCRIPTION
        "The interface number of ap."
    INDEX   { qtechApMacAddr }
    ::= { apInterfaceNumberTable 1 }

ApInterfaceNumberTableEntry ::=
    SEQUENCE {
        apIfNumber                   INTEGER,
        apBSSIDNum									 INTEGER
    }

apIfNumber OBJECT-TYPE
    SYNTAX INTEGER (0..255)
    MAX-ACCESS read-only
    STATUS current
    DESCRIPTION
        "The count of the physical interfaces of ap."
    ::= { apInterfaceNumberTableEntry 1 } 
    
apBSSIDNum OBJECT-TYPE
    SYNTAX INTEGER (0..255)
    MAX-ACCESS read-only
    STATUS current
    DESCRIPTION
        "bssid number of ap."
    ::= { apInterfaceNumberTableEntry 2 }       
--**************************************************
--* apInterfaceRGMIIConfig starts * 
--************************************************** 
apInterfaceRGMIIconfigTable  OBJECT-TYPE
    SYNTAX SEQUENCE OF ApInterfaceRGMIIconfigTableEntry
    MAX-ACCESS not-accessible
    STATUS current
    DESCRIPTION
      "The interface RGMII config of ap."
    ::={ apInterfaceRGMIIcfgObjects 1 }

apInterfaceRGMIIconfigTableEntry OBJECT-TYPE
    SYNTAX  ApInterfaceRGMIIconfigTableEntry
    MAX-ACCESS  not-accessible
    STATUS  current
    DESCRIPTION
        "The interface RGMII config of ap"
    INDEX   { qtechApMacAddr,apIfLocalRGMIINum }
    ::= { apInterfaceRGMIIconfigTable 1 }
    
ApInterfaceRGMIIconfigTableEntry ::=
    SEQUENCE {
        apIfLocalRGMIINum                      INTEGER,
        apIfRGMIIDescr                         DisplayString,
        apIfRGMIIType                          IANAifType,
        apIfRGMIIMtu                           INTEGER,
        apIfRGMIISpeed                         Integer32,
        apIfRGMIIPhysAddress                   MacAddress,
        apIfRGMIIAdminStatusEnable             INTEGER,
        apIfRGMIIOperStatus                    INTEGER,
        apIfRGMIILastChange                    TimeTicks
    }    

apIfLocalRGMIINum  OBJECT-TYPE
    SYNTAX  INTEGER
    MAX-ACCESS  not-accessible
    STATUS  current
    DESCRIPTION
            "rgmii interface number."
    ::= { apInterfaceRGMIIconfigTableEntry 1}
    
apIfRGMIIDescr OBJECT-TYPE
    SYNTAX DisplayString (SIZE (0..255))
    MAX-ACCESS read-only
    STATUS current
    DESCRIPTION
        "The description of the ap interfaces."
    ::= { apInterfaceRGMIIconfigTableEntry 2 }   
    
apIfRGMIIType OBJECT-TYPE
    SYNTAX IANAifType
    MAX-ACCESS read-write
    STATUS current
    DESCRIPTION
        "The style of the ap interfaces."
    ::= { apInterfaceRGMIIconfigTableEntry 3 }   
    
apIfRGMIIMtu OBJECT-TYPE
    SYNTAX INTEGER
    MAX-ACCESS read-write
    STATUS current
    DESCRIPTION
        "The max mtu of the ap interfaces."
    ::= { apInterfaceRGMIIconfigTableEntry 4 }     
    
apIfRGMIISpeed OBJECT-TYPE
    SYNTAX Integer32
    MAX-ACCESS read-only
    STATUS current
    DESCRIPTION
        "The speed of the ap interfaces."
    ::= { apInterfaceRGMIIconfigTableEntry 5 }     

apIfRGMIIPhysAddress OBJECT-TYPE
    SYNTAX MacAddress
    MAX-ACCESS read-only
    STATUS current
    DESCRIPTION
        "The physical address of the ap interfaces."
    ::= { apInterfaceRGMIIconfigTableEntry 6 }    
    
apIfRGMIIAdminStatusEnable  OBJECT-TYPE
    SYNTAX  INTEGER {
          admindown(0),
          up(1)
    }
    MAX-ACCESS read-write
    STATUS current
    DESCRIPTION
        "The  RGMII  manage enable ,0 admindown 1 up."
    ::= { apInterfaceRGMIIconfigTableEntry 7 }     
    
apIfRGMIIOperStatus OBJECT-TYPE
    SYNTAX  INTEGER {
          down(0),
          up(1),
          admindown(2)
    }
    MAX-ACCESS read-only
    STATUS current
    DESCRIPTION
        "The  status of RGMII manage 0:down 1:up 2:admindown"
    ::= { apInterfaceRGMIIconfigTableEntry 8 }  
    
apIfRGMIILastChange   OBJECT-TYPE
    SYNTAX TimeTicks
    MAX-ACCESS read-only
    STATUS current
    DESCRIPTION
        "The time ap status in now status."
    ::= { apInterfaceRGMIIconfigTableEntry 9 }    
      
--**************************************************
--* apInterfaceRGMIIConfig ends * 
--************************************************** 
--**************************************************
--* apInterfaceWirelsessConfig starts * 
--************************************************** 

apInterfaceWirelessconfigTable  OBJECT-TYPE
    SYNTAX SEQUENCE OF ApInterfaceWirelessconfigTableEntry
    MAX-ACCESS not-accessible
    STATUS current
    DESCRIPTION
      "The interface of Wireless config of ap."
    ::={ apInterfaceWirelesscfgObjects 1 }

apInterfaceWirelessconfigTableEntry OBJECT-TYPE
    SYNTAX  ApInterfaceWirelessconfigTableEntry
    MAX-ACCESS  not-accessible
    STATUS  current
    DESCRIPTION
        "The interface RGMII config of ap"
    INDEX   { qtechApMacAddr,qtechApCfgRadioId }
    ::= { apInterfaceWirelessconfigTable 1 }
    
ApInterfaceWirelessconfigTableEntry ::=
    SEQUENCE {
        apIfWireDescr                     DisplayString,
        apIfWireType                      IANAifType,
        apIfWireMtu                       Integer32,
        apIfWireSpeed                     Integer32,
        apIfWirePhysAddress               MacAddress,
        apIfWireAdminStatusEnable         INTEGER,
        apIfWireOperStatus                INTEGER,
        apIfWireLastChange                TimeTicks,
        apIfWireChannelAutoSelectEnable   INTEGER,
        apIfWireRadioChannelConfig        INTEGER,
        apIfWireRadioChannelUsing         INTEGER,
        apIfWireCurrRadioModeSupport      Counter32,
        apIfWireRadioModeConfig           Counter32,
        apIfWireTransmitSpeedConfig       DisplayString,
        apIfWireMaxTxPwrLvl               DisplayString,
        apIfWirePwrAttRange               INTEGER,
        apIfWirePwrAttValue               INTEGER,
        apIfWireAntennaGain               INTEGER,
        apIfWirePowerMgmtEnable           TruthValue,
        apTxPwr	                          INTEGER,
        apIfWireMaxStationNumPermitted    Counter32,
        apIfWireAMPDUEnabled              INTEGER,
        apIfWireBWMode                    INTEGER,
        apIfWireShortGIEnabled            INTEGER,
        apIfWireIs11nOnly                 TruthValue,
        apIfWireBeaconIntvl               Integer32,
        apIfWireDtimIntvl                 Integer32,
        apIfWireRtsThreshold              Integer32,
        apIfWireFragThreshlod             Integer32,
        apIfWirePreambleLen               INTEGER,
        apAntennaReceiveMask	          INTEGER,
        apAntennaTransmitMask             INTEGER, 
        apIfWireAMSDUEnabled              INTEGER,
        apIfwireMcsSuppIndex              INTEGER,
        apIfwireMcsMandIndex              INTEGER,
        apIfwire11nSuppEnable	          INTEGER,
        apShtRetryThld	                  INTEGER,
        apLongRetryThld                   INTEGER,
        apIfWireResponseRssi	          INTEGER,
        apIfWireMaxStationLimit           INTEGER,
        apIfWireLinkscan                  INTEGER
    }    
    
apIfWireDescr OBJECT-TYPE
    SYNTAX DisplayString (SIZE (0..255))
    MAX-ACCESS read-only
    STATUS current
    DESCRIPTION
        "The description of the ap interfaces."
    ::= { apInterfaceWirelessconfigTableEntry 1 }   
    
apIfWireType OBJECT-TYPE
    SYNTAX IANAifType
    MAX-ACCESS read-only
    STATUS current
    DESCRIPTION
        "The style of the ap interfaces."
    ::= { apInterfaceWirelessconfigTableEntry 2 }   
    
apIfWireMtu OBJECT-TYPE
    SYNTAX Integer32
    MAX-ACCESS read-only
    STATUS current
    DESCRIPTION
        "The max mtu of the ap interfaces."
    ::= { apInterfaceWirelessconfigTableEntry 3 }     
    
apIfWireSpeed OBJECT-TYPE
    SYNTAX Integer32
    MAX-ACCESS read-only
    STATUS current
    DESCRIPTION
        "The speed of the ap interfaces."
    ::= { apInterfaceWirelessconfigTableEntry 4 }     

apIfWirePhysAddress OBJECT-TYPE
    SYNTAX MacAddress
    MAX-ACCESS read-only
    STATUS current
    DESCRIPTION
        "The physical address of the ap interfaces."
    ::= { apInterfaceWirelessconfigTableEntry 5 }    
    
apIfWireAdminStatusEnable  OBJECT-TYPE
    SYNTAX  INTEGER {
          up(0),
          admindown(1)
    }
    MAX-ACCESS read-write
    STATUS current
    DESCRIPTION
        "The  RGMII  manage enable ,0 up 2 admindown."
    ::= { apInterfaceWirelessconfigTableEntry 6 }     
    
apIfWireOperStatus OBJECT-TYPE
    SYNTAX  INTEGER {
        up(0),
        down(1),
        admindown(2)
    }
    MAX-ACCESS read-only
    STATUS current
    DESCRIPTION
        "The  status of RGMII manage 0:up 1:exception down 2:admindown"
    ::= { apInterfaceWirelessconfigTableEntry 7 }  
    
apIfWireLastChange   OBJECT-TYPE
    SYNTAX TimeTicks
    MAX-ACCESS read-only
    STATUS current
    DESCRIPTION
        "The time ap status in now status."
    ::= { apInterfaceWirelessconfigTableEntry 8 }  

apIfWireChannelAutoSelectEnable   OBJECT-TYPE
    SYNTAX  INTEGER {
          off(0),
          on(1)
    }
    MAX-ACCESS read-write
    STATUS current
    DESCRIPTION
        "Radio Channel Auto Select Enable 1:on 0:off"
    ::= { apInterfaceWirelessconfigTableEntry 9 }    

apIfWireRadioChannelConfig  OBJECT-TYPE
    SYNTAX  INTEGER 
    MAX-ACCESS read-write
    STATUS current
    DESCRIPTION
        "Radio Channel Manual config"
    ::= { apInterfaceWirelessconfigTableEntry 10 } 

apIfWireRadioChannelUsing   OBJECT-TYPE
    SYNTAX  INTEGER
    MAX-ACCESS read-only
    STATUS current
    DESCRIPTION
        "Radio Channel current used"
    ::= { apInterfaceWirelessconfigTableEntry 11 } 
    
apIfWireCurrRadioModeSupport  OBJECT-TYPE
    SYNTAX Counter32
    MAX-ACCESS read-only
    STATUS current
    DESCRIPTION
        "The  ap support radio mode."
    ::= { apInterfaceWirelessconfigTableEntry 12 } 
     
apIfWireRadioModeConfig  OBJECT-TYPE
    SYNTAX Counter32
    MAX-ACCESS read-write
    STATUS current
    DESCRIPTION
        "The  ap radio mode configure."
    ::= { apInterfaceWirelessconfigTableEntry 13 } 
    
apIfWireTransmitSpeedConfig   OBJECT-TYPE
    SYNTAX DisplayString (SIZE (0..255))
    MAX-ACCESS read-write
    STATUS current
    DESCRIPTION
        "The transmit speed of the ap config."
    ::= { apInterfaceWirelessconfigTableEntry 14 }    

apIfWireMaxTxPwrLvl OBJECT-TYPE
    SYNTAX DisplayString (SIZE (0..255))
    MAX-ACCESS read-only
    STATUS current
    DESCRIPTION
        "The max Tx power Level config."
    ::= { apInterfaceWirelessconfigTableEntry 15 }    
    
apIfWirePwrAttRange  OBJECT-TYPE
    SYNTAX  INTEGER
    MAX-ACCESS read-only
    STATUS current
    DESCRIPTION
        "The Tx Power attenuation range of ap radio "
    ::= { apInterfaceWirelessconfigTableEntry 16 }    
                   
apIfWirePwrAttValue  OBJECT-TYPE
    SYNTAX  INTEGER
    MAX-ACCESS read-write
    STATUS current
    DESCRIPTION
        "The Radio Tx Power attenuation value config"
    ::= { apInterfaceWirelessconfigTableEntry 17 }   
    
apIfWireAntennaGain   OBJECT-TYPE
    SYNTAX  INTEGER
    MAX-ACCESS read-only
    STATUS current
    DESCRIPTION
        "The Radio Antenna  Gain"
    ::= { apInterfaceWirelessconfigTableEntry 18 }    
       
apIfWirePowerMgmtEnable   OBJECT-TYPE
    SYNTAX TruthValue
    MAX-ACCESS read-write
    STATUS current
    DESCRIPTION
        "The Tx Power Auto mangement config "
    ::= { apInterfaceWirelessconfigTableEntry 19 }  
    
apTxPwr   OBJECT-TYPE
    SYNTAX  INTEGER
    MAX-ACCESS read-write
    STATUS current
    DESCRIPTION
        "The Tx power"
    ::= { apInterfaceWirelessconfigTableEntry 20 }   
    
apIfWireMaxStationNumPermitted  OBJECT-TYPE
    SYNTAX Counter32
    MAX-ACCESS read-write
    STATUS current
    DESCRIPTION
        "The  max permit station  Num configure."
    ::= { apInterfaceWirelessconfigTableEntry 21 }    
    
apIfWireAMPDUEnabled  OBJECT-TYPE
    SYNTAX  INTEGER {
          off(0),
          on(1)
    }
    MAX-ACCESS read-write
    STATUS current
    DESCRIPTION
        "The A-MPDU enable ,used for 11n, 0:off 1:on"
    ::= { apInterfaceWirelessconfigTableEntry 22 }     
    
apIfWireBWMode   OBJECT-TYPE
    SYNTAX  INTEGER {
          off(0),
          on(1)
    }
    MAX-ACCESS read-write
    STATUS current
    DESCRIPTION
        "The radio bandwith mode set 20M/40M ,1:on 0:off"
    ::= { apInterfaceWirelessconfigTableEntry 23 }    
    
apIfWireShortGIEnabled  OBJECT-TYPE
    SYNTAX  INTEGER {
          off(0),
          on(1)
    }
    MAX-ACCESS read-write
    STATUS current
    DESCRIPTION
        "The short GI enable ,used for 11n. 1:on 0:off"
    ::= { apInterfaceWirelessconfigTableEntry 24 }   
    
apIfWireIs11nOnly  OBJECT-TYPE
    SYNTAX TruthValue
    MAX-ACCESS read-write
    STATUS current
    DESCRIPTION
        "The only used for 11n config ."
    ::= { apInterfaceWirelessconfigTableEntry 25 }      
    
apIfWireBeaconIntvl  OBJECT-TYPE
    SYNTAX Integer32
    MAX-ACCESS read-write
    STATUS current
    DESCRIPTION
        "AP beacon interval time  config ,default 100 microsecond."
    ::= { apInterfaceWirelessconfigTableEntry 26 }  
    
apIfWireDtimIntvl    OBJECT-TYPE
    SYNTAX Integer32
    MAX-ACCESS read-write
    STATUS current
    DESCRIPTION
        "AP Dtim information interval time  config."
    ::= { apInterfaceWirelessconfigTableEntry 27 }    
    
apIfWireRtsThreshold   OBJECT-TYPE
    SYNTAX Integer32
    MAX-ACCESS read-write
    STATUS current
    DESCRIPTION
        "AP RTX threshold  config."
    ::= { apInterfaceWirelessconfigTableEntry 28 }    
    
apIfWireFragThreshlod  OBJECT-TYPE
    SYNTAX Integer32
    MAX-ACCESS read-write
    STATUS current
    DESCRIPTION
        "MSDU Frag Threshlod config."
    ::= { apInterfaceWirelessconfigTableEntry 29 }   
    
apIfWirePreambleLen  OBJECT-TYPE
    SYNTAX  INTEGER {
          long(0),
          short(1)
    }
    MAX-ACCESS read-write
    STATUS current
    DESCRIPTION
        "AP preamble mode config, 0:long 1:short"
    ::= { apInterfaceWirelessconfigTableEntry 30 } 

apAntennaReceiveMask  OBJECT-TYPE
    SYNTAX  INTEGER 
    MAX-ACCESS read-write
    STATUS current
    DESCRIPTION
        "Antenna receive mask."
    ::= { apInterfaceWirelessconfigTableEntry 31 } 

apAntennaTransmitMask  OBJECT-TYPE
    SYNTAX  INTEGER 
    MAX-ACCESS read-write
    STATUS current
    DESCRIPTION
        "Antenna transmit mask."
    ::= { apInterfaceWirelessconfigTableEntry 32 } 	 
    
apIfWireAMSDUEnabled	OBJECT-TYPE
    SYNTAX  INTEGER 
    MAX-ACCESS read-write
    STATUS current
    DESCRIPTION
        "ap wireless AMSDU Enable."
    ::= { apInterfaceWirelessconfigTableEntry 33 }

apIfwireMcsSuppIndex	OBJECT-TYPE
    SYNTAX  INTEGER 
    MAX-ACCESS read-write
    STATUS current
    DESCRIPTION
        "ap wireless Support Mcs Index."
    ::= { apInterfaceWirelessconfigTableEntry 34 }

apIfwireMcsMandIndex	OBJECT-TYPE
    SYNTAX  INTEGER 
    MAX-ACCESS read-write
    STATUS current
    DESCRIPTION
        "ap wireless Mandory Mcs Index."
    ::= { apInterfaceWirelessconfigTableEntry 35 }  
    
apIfwire11nSuppEnable	OBJECT-TYPE
    SYNTAX  INTEGER 
    MAX-ACCESS read-write
    STATUS current
    DESCRIPTION
        "ap wireless 11nsupport enable."
    ::= { apInterfaceWirelessconfigTableEntry 36 }  

apShtRetryThld			OBJECT-TYPE
    SYNTAX  INTEGER 
    MAX-ACCESS read-write
    STATUS current
    DESCRIPTION
        "ap wireless short retry times."
    ::= { apInterfaceWirelessconfigTableEntry 37 }         

apLongRetryThld			OBJECT-TYPE
    SYNTAX  INTEGER 
    MAX-ACCESS read-write
    STATUS current
    DESCRIPTION
        "ap wireless long retry times."
    ::= { apInterfaceWirelessconfigTableEntry 38 }

apIfWireResponseRssi		 OBJECT-TYPE
    SYNTAX  INTEGER 
    MAX-ACCESS read-write
    STATUS current
    DESCRIPTION
        "ap radio response rssi."
    ::= { apInterfaceWirelessconfigTableEntry 39 }   
    
apIfWireMaxStationLimit 	 OBJECT-TYPE
    SYNTAX  INTEGER 
    MAX-ACCESS read-write
    STATUS current
    DESCRIPTION
        "ap radio limit the num of associated stations."
    ::= { apInterfaceWirelessconfigTableEntry 40 }   
    
apIfWireLinkscan   OBJECT-TYPE
    SYNTAX  INTEGER 
    MAX-ACCESS read-only
    STATUS current
    DESCRIPTION
        "ap radio link scan."
    ::= { apInterfaceWirelessconfigTableEntry 41 } 

--**************************************************
--* apInterfaceWirelsessConfig ends * 
--**************************************************
--**************************************************
--* apSSIDConfig starts * 
--**************************************************
apSSIDConfigObjects        OBJECT IDENTIFIER  ::= { qtechFitApMibModule 3 }  
--**********************************************
--*  apSSIDListCreateTable starts
--**********************************************
apSSIDListCreateTable OBJECT-TYPE
    SYNTAX SEQUENCE OF ApSSIDListCreateTableEntry
    MAX-ACCESS not-accessible
    STATUS current
    DESCRIPTION
      "The SSID list manegment for ap."
    ::={ apSSIDConfigObjects 1 }

apSSIDListCreateTableEntry OBJECT-TYPE
    SYNTAX  ApSSIDListCreateTableEntry
    MAX-ACCESS  not-accessible
    STATUS  current
    DESCRIPTION
        "The SSID list manegment for ap"
    INDEX   {apSSIDAPMac, apSSIDRadioId, qtechApgWlanId} 
    ::= { apSSIDListCreateTable 1 }
    
ApSSIDListCreateTableEntry ::=
    SEQUENCE {
    		 apSSIDAPMac			 MacAddress,         
         apSSIDRadioId     INTEGER,
         apSSIDListName		 DisplayString,
         apListBSSIDAddr   MacAddress,
         apSSIDListStatus	 RowStatus
    }
    
apSSIDAPMac    OBJECT-TYPE
  	SYNTAX MacAddress 
    MAX-ACCESS read-only
    STATUS current
    DESCRIPTION
        "AP mac address"
    ::= { apSSIDListCreateTableEntry 1 } 
    
apSSIDRadioId  OBJECT-TYPE
    SYNTAX  INTEGER
    MAX-ACCESS  read-only
    STATUS  current
    DESCRIPTION
            "ssid connect radio index num."
    ::= { apSSIDListCreateTableEntry 2}   
    
apSSIDListName  OBJECT-TYPE
    SYNTAX  DisplayString
    MAX-ACCESS  read-create
    STATUS  current
    DESCRIPTION
            "SSID name."
    ::= { apSSIDListCreateTableEntry 3}       
    
    
apListBSSIDAddr    OBJECT-TYPE
  	SYNTAX MacAddress 
    MAX-ACCESS read-create
    STATUS current
    DESCRIPTION
        "config bssid virtual mac address"
    ::= { apSSIDListCreateTableEntry 4 } 
    
    
apSSIDListStatus    OBJECT-TYPE
    SYNTAX  RowStatus
    MAX-ACCESS  read-create
    STATUS  current
    DESCRIPTION
            "The status column used for creating and
         deleting instances of the columnar objects in the table."
    ::= { apSSIDListCreateTableEntry 5}   
--**********************************************
--*apSSIDListCreateTable ends
--**********************************************

apSSIDConfigTable  OBJECT-TYPE
    SYNTAX SEQUENCE OF ApSSIDConfigTableEntry
    MAX-ACCESS not-accessible
    STATUS current
    DESCRIPTION
      "The SSID config of ap."
    ::={ apSSIDConfigObjects 2 }

apSSIDConfigTableEntry OBJECT-TYPE
    SYNTAX  ApSSIDConfigTableEntry
    MAX-ACCESS  not-accessible
    STATUS  current
    DESCRIPTION
        "The SSID config of ap"
    INDEX   { qtechApgWlanId }
    ::= { apSSIDConfigTable 1 }  
ApSSIDConfigTableEntry ::=
    SEQUENCE {
        apSSIDName                          DisplayString,     
        apSSIDEnabled                       TruthValue,
        apSSIDHidden                        TruthValue,
        apStaIsolate                        TruthValue,
        apDot11Auth                         INTEGER,
        apsecurityMode                      INTEGER,
        apAuthenMode                        INTEGER,
        apSecurityCiphers                   INTEGER,
        apVlanId                            INTEGER,
        apVlanIpAddr												IpAddress,
        apMaxSimultUsers                    Counter32,
        apStaUplinkMaxRate                  Counter32,
        apStaDwlinkMaxRate                  Counter32,
        apSSIDCfgStatus											RowStatus
    }    

apSSIDName   OBJECT-TYPE
  	SYNTAX DisplayString (SIZE(1..255))
    MAX-ACCESS read-create
    STATUS current
    DESCRIPTION
        "config ssid name"
    ::= { apSSIDConfigTableEntry 1 }
    
apSSIDEnabled     OBJECT-TYPE
    SYNTAX TruthValue
    MAX-ACCESS read-create
    STATUS current
    DESCRIPTION
        "ssid enable config "
    ::= { apSSIDConfigTableEntry 2 }    
    
apSSIDHidden     OBJECT-TYPE
    SYNTAX TruthValue
    MAX-ACCESS read-create
    STATUS current
    DESCRIPTION
        "ssid hidden config "
    ::= { apSSIDConfigTableEntry 3 }   
    
apStaIsolate    OBJECT-TYPE
    SYNTAX TruthValue
    MAX-ACCESS read-create
    STATUS current
    DESCRIPTION
        "station isolate config "
    ::= { apSSIDConfigTableEntry 4 } 
    
apDot11Auth   OBJECT-TYPE
    SYNTAX  INTEGER {
          opensystem(0),
          sharedkey(1)
    }
    MAX-ACCESS  read-create
    STATUS  current
    DESCRIPTION
            "dot11 authenticate mode 0:opensystem 1:sharedkey."
    ::= { apSSIDConfigTableEntry 5} 
    
apsecurityMode  OBJECT-TYPE
    SYNTAX  INTEGER {
          none(0),
          wpa(1),
          wpa2(2),
          wapi(3)
    }
    MAX-ACCESS  read-create
    STATUS  current
    DESCRIPTION
            "security mode config 0:none 1:wpa
             2:wpa2   3:wapi."
    ::= { apSSIDConfigTableEntry 6}    
    
apAuthenMode   OBJECT-TYPE
    SYNTAX  INTEGER {
          none(0),
          psk(1),
          radius(2),
          wapicer(3),
          web(4),
          psk-web(5),
          wapicer-web(6),
          wapipsk(7)
    }
    MAX-ACCESS  read-create
    STATUS  current
    DESCRIPTION
            "dot11 authen mode 0:none 1:PSK 2:Radius 3:WAPICER 4:Web 5:PSK-Web 6:WAPICER-Web 7:WAPIPSK."
    ::= { apSSIDConfigTableEntry 7}   
    
apSecurityCiphers OBJECT-TYPE
    SYNTAX  INTEGER {
          none(0),
          wep40(1),
          wep104(2),
          tkip(3),
          aesccmp(4),
          wapisms4(5)
    }
    MAX-ACCESS  read-create
    STATUS  current
    DESCRIPTION
            "SecurityCiphers config 0:none 1:wep40
             2:wep104   3:aesccmp  4:wpi-SMS4."
    ::= { apSSIDConfigTableEntry 8}  

apVlanId   OBJECT-TYPE
    SYNTAX  INTEGER
    MAX-ACCESS  read-create
    STATUS  current
    DESCRIPTION
            "vlan id config"
    ::= { apSSIDConfigTableEntry 9}   
   												 
apVlanIpAddr   OBJECT-TYPE
    SYNTAX  IpAddress
    MAX-ACCESS  read-create
    STATUS  current
    DESCRIPTION
            "vlan ip address"
    ::= { apSSIDConfigTableEntry 10}   
         
apMaxSimultUsers  OBJECT-TYPE
    SYNTAX Counter32
    MAX-ACCESS read-create
    STATUS current
    DESCRIPTION
        "AP max station support config."
    ::= { apSSIDConfigTableEntry 11 }   
    
apStaUplinkMaxRate  OBJECT-TYPE
    SYNTAX Counter32
    MAX-ACCESS read-create
    STATUS current
    DESCRIPTION
        "AP station Uplink MaxRate."
    ::= { apSSIDConfigTableEntry 12 }   
    
apStaDwlinkMaxRate  OBJECT-TYPE
    SYNTAX Counter32
    MAX-ACCESS read-create
    STATUS current
    DESCRIPTION
        "AP station Dwlink MaxRate."
    ::= { apSSIDConfigTableEntry 13 } 
    
apSSIDCfgStatus  OBJECT-TYPE
    SYNTAX RowStatus
    MAX-ACCESS read-create
    STATUS current
    DESCRIPTION
        "The status column used for creating and
         deleting instances of the columnar objects in the table."
    ::= { apSSIDConfigTableEntry 14 } 
    
              
--**************************************************
--* apSSIDConfig ends * 
--**************************************************
--**************************************************
--* apSecurityConfig starts * 
--**************************************************
apSecurityConfigObjects        OBJECT IDENTIFIER  ::= { qtechFitApMibModule 4 }  
apSecurityConfigTable  OBJECT-TYPE
    SYNTAX SEQUENCE OF ApSecurityConfigTableEntry
    MAX-ACCESS not-accessible
    STATUS current
    DESCRIPTION
      "The SSID config of ap."
    ::={ apSecurityConfigObjects 1 }

apSecurityConfigTableEntry OBJECT-TYPE
    SYNTAX  ApSecurityConfigTableEntry
    MAX-ACCESS  not-accessible
    STATUS  current
    DESCRIPTION
        "The SSID config of ap"
    INDEX   { qtechApgWlanId }
    ::= { apSecurityConfigTable 1 }
    
ApSecurityConfigTableEntry ::=
    SEQUENCE {
        apWEPCipherKeyIndex                 INTEGER,
        apWEPCipherKeyValue                 DisplayString,
        apWEPCipherKeyCharType              INTEGER,  
        apPSKCipherKeyValue                 DisplayString,
        apPSKCipherKeyCharType              INTEGER, 
        apWAPIAuthModeEnable									TruthValue,
        apWAPIASIPAddress                   IpAddress,
        apWAPIIsInstalledCer                TruthValue    		
    }    

apWEPCipherKeyIndex   OBJECT-TYPE
    SYNTAX  INTEGER
    MAX-ACCESS  read-write
    STATUS  current
    DESCRIPTION
            "WEP CipherKey  Index"
    ::= { apSecurityConfigTableEntry 1}  
   
apWEPCipherKeyValue   OBJECT-TYPE
  	SYNTAX DisplayString 
    MAX-ACCESS read-write
    STATUS current
    DESCRIPTION
        "WEP cipherKey value ."
    ::= { apSecurityConfigTableEntry 2 }  
    
apWEPCipherKeyCharType  OBJECT-TYPE
    SYNTAX  INTEGER {
          char(1),
          hex(0)
    }
    MAX-ACCESS  read-write
    STATUS  current
    DESCRIPTION
            "WEP CipherKey  type 0:char 1:hex ."
    ::= { apSecurityConfigTableEntry 3}  
    
apPSKCipherKeyValue  OBJECT-TYPE
  	SYNTAX DisplayString 
    MAX-ACCESS read-write
    STATUS current
    DESCRIPTION
        "PSK cipherKey value ."
    ::= { apSecurityConfigTableEntry 4 }   
    
apPSKCipherKeyCharType   OBJECT-TYPE
    SYNTAX  INTEGER {
          char(1),
          hex(0)
    }
    MAX-ACCESS  read-write
    STATUS  current
    DESCRIPTION
            "PSK CipherKey  type 0:char 1:hex ."
    ::= { apSecurityConfigTableEntry 5}
    
apWAPIAuthModeEnable    OBJECT-TYPE
    SYNTAX TruthValue
    MAX-ACCESS read-write
    STATUS current
    DESCRIPTION
        "WAPI auth mode switch. "
    ::= { apSecurityConfigTableEntry 6 }       
    
apWAPIASIPAddress    OBJECT-TYPE
    SYNTAX IpAddress
    MAX-ACCESS read-write
    STATUS current
    DESCRIPTION
        "The WAPI AS ip address "
    ::= { apSecurityConfigTableEntry 7 }      
       
apWAPIIsInstalledCer  OBJECT-TYPE
    SYNTAX TruthValue
    MAX-ACCESS read-only
    STATUS current
    DESCRIPTION
        "WAPI has installed Cet ?"
    ::= { apSecurityConfigTableEntry 8 }       
--**************************************************
--* apSecurityConfig ends * 
--**************************************************
--**************************************************
--* apWAPIExternInfoConfig starts * 
--**************************************************
apWAPIExternInfoConfigObjects        OBJECT IDENTIFIER  ::= { qtechFitApMibModule 5 }
apWAPIExternInfoConfigTable OBJECT-TYPE
    SYNTAX SEQUENCE OF ApWAPIExternInfoConfigTableEntry
    MAX-ACCESS not-accessible
    STATUS current
    DESCRIPTION
      "The WAPI extern config ."
    ::={ apWAPIExternInfoConfigObjects 1 }

apWAPIExternInfoConfigTableEntry OBJECT-TYPE
    SYNTAX  ApWAPIExternInfoConfigTableEntry
    MAX-ACCESS  not-accessible
    STATUS  current
    DESCRIPTION
        "The WAPI extern config ."
    INDEX   { qtechApgWlanId }
    ::= { apWAPIExternInfoConfigTable 1 }
    
ApWAPIExternInfoConfigTableEntry ::=
    SEQUENCE {
        apWAPIConfigVersion                   Integer32,
        apWAPIControlledAuthControl           TruthValue,
        apWAPIControlledPortControl           INTEGER,
        apWAPIOptionImplemented               TruthValue,
        apWAPIPreauthenticationImplemented    TruthValue,
        apWAPIEnabled                         TruthValue,
        apWAPIPreauthEnabled                  TruthValue,
        apWAPIUnicastKeysSupported            Unsigned32,
        apWAPIUnicastRekeyMethod              INTEGER,
        apWAPIUnicastRekeyTime                Unsigned32,
        apWAPIUnicastRekeyPackets             Unsigned32,
        apWAPIMulticastCipher                 OCTET STRING,
        apWAPIMulticastRekeyMethod            INTEGER,
        apWAPIMulticastRekeyTime              Unsigned32,
        apWAPIMulticastRekeyPackets  	        Unsigned32,
        apWAPIMulticastRekeyStrict  	        TruthValue,
        apWAPIPSKValue 	                      OCTET STRING,
        apWAPIPSKPassPhrase 	                DisplayString,
        apWAPICertificateUpdateCount 	        Unsigned32,
        apWAPIMulticastUpdateCount 	          Unsigned32,
        apWAPIUnicastUpdateCount  	          Unsigned32,
        apWAPIMulticastCipherSize 	          Unsigned32,
        apWAPIBKLifetime  	                  Unsigned32,
        apWAPIBKReauthThreshold 	            Unsigned32,
        apWAPISATimeout 	                    Unsigned32,
        apWAPIAuthSuiteSelected 	            OCTET STRING,
        apWAPIUnicastCipherSelected 	        OCTET STRING,
        apWAPIMulticastCipherSelected 	      OCTET STRING,
        apWAPIBKIDUsed 	                      OCTET STRING,
        apWAPIAuthSuiteRequested 	            OCTET STRING,
        apWAPIUnicastCipherRequested 	        OCTET STRING,
        apWAPIMulticastCipherRequested 	      OCTET STRING,
        apWAPIUnicastCipher                   OCTET STRING,
        apWAPIUnicastCipherEnabled            TruthValue,
        apWAPIUnicastCipherSize               Unsigned32,
        apWAPIAuthenticationSuite             OCTET STRING,
        apWAPIAuthenticationSuiteEnabled      TruthValue,
        apWAPIAECertFile                      DisplayString,
        apWAPICACertFile											DisplayString,
        apWAPIASUCertFile                     DisplayString
    }    
apWAPIConfigVersion OBJECT-TYPE
    SYNTAX Integer32
    MAX-ACCESS read-only
    STATUS current
    DESCRIPTION

        " the newest wapi version the entity support. "
    ::= { apWAPIExternInfoConfigTableEntry 1 }    
    
apWAPIControlledAuthControl OBJECT-TYPE
    SYNTAX TruthValue
    MAX-ACCESS read-write
    STATUS current
    DESCRIPTION

        " This attribute means whether the entity enbales identification. If its value is false, it
        means it disables identification, the status of the controlled port is 'identified'. If
        true, it means it enables identification, the status of the controlled port is decided by
        the gb15629dot11wapiControlledPortControl. "
    ::= { apWAPIExternInfoConfigTableEntry 2 }    
    
apWAPIControlledPortControl OBJECT-TYPE
    SYNTAX INTEGER
    MAX-ACCESS read-only
    STATUS current
    DESCRIPTION

        " This attribute used as the control type of the entity port, valid when gb15629dot11wapiControlledAuthControl
        is true. It mean 'auto' when 0 and  the status of control port is decided by the result of
        identification. 'force to unidentified' when 1 and the status of control port is 'unidentified'。"
    ::= { apWAPIExternInfoConfigTableEntry 3 }    
    
apWAPIOptionImplemented OBJECT-TYPE
    SYNTAX TruthValue
    MAX-ACCESS read-only
    STATUS current
    DESCRIPTION

        " This attribute instruts whether the entity supports the WAPI funtion. It supports the WAPI
        funtion when value is true. Or not support. "
    ::= { apWAPIExternInfoConfigTableEntry 4 }   
    
apWAPIPreauthenticationImplemented OBJECT-TYPE
    SYNTAX TruthValue
    MAX-ACCESS read-only
    STATUS current
    DESCRIPTION

        " This attribute instruts whether the entity supports the WAPI pre-identification. It can't
        be valued true except that gb15629dot11wapiOptionImplemented is valued true. "
    ::= { apWAPIExternInfoConfigTableEntry 5 }     
    
apWAPIEnabled OBJECT-TYPE
    SYNTAX TruthValue
    MAX-ACCESS read-write
    STATUS current
    DESCRIPTION

        " When it is valued true, the object instruts that the WAPI of the entity has been activated.
        The entity will broadcast the WAPI info elemnetds by beacon frames and probe response frames. "
    ::= { apWAPIExternInfoConfigTableEntry 6 }    
    
apWAPIPreauthEnabled OBJECT-TYPE
    SYNTAX TruthValue
    MAX-ACCESS read-write
    STATUS current
    DESCRIPTION

        "When it is valued true, the object instruts that the WAPI of the entity has been activated.
        The object requires thar the dot11WAPI Enabled is also set to true. "
    ::= { apWAPIExternInfoConfigTableEntry 7 } 
    
apWAPIUnicastKeysSupported OBJECT-TYPE
    SYNTAX Unsigned32
    MAX-ACCESS read-only
    STATUS current

    DESCRIPTION

        " The object instruts the count of the unicast keys  supported by the WAPI entity. "
    ::= { apWAPIExternInfoConfigTableEntry 8 }    
    
apWAPIUnicastRekeyMethod OBJECT-TYPE
    SYNTAX INTEGER {
        disabled(0),
        timeBased(1),
        packetBased(2),
        timepacket-Based(3)
    }
    MAX-ACCESS read-write
    STATUS current
    DESCRIPTION

        " The object choosee a mechanism to rebuild USK of WAPI. It is defaultly based on time,
        once per day. The update of USK is initialized by the entities which play as the role of AE
        or ASUE. "
    DEFVAL { timeBased }
    ::= { apWAPIExternInfoConfigTableEntry 9 }    
    
apWAPIUnicastRekeyTime OBJECT-TYPE
    SYNTAX Unsigned32 (1..4294967295)
    UNITS "second"
    MAX-ACCESS read-write
    STATUS current
    DESCRIPTION

        "The timing-Second of the update of WAPI USK. The timer BEGINS working when the USK is
        set by the primitive MLME-SETWPIKEYS.request. "
    DEFVAL { 86400 }
    ::= { apWAPIExternInfoConfigTableEntry 10 }    
    
apWAPIUnicastRekeyPackets OBJECT-TYPE
    SYNTAX Unsigned32 (1..4294967295)
    UNITS "1000 packets"
    MAX-ACCESS read-write
    STATUS current
    DESCRIPTION

        " The packet count of the update of WAPI USK(unit in 1000 packets). Thr counter BEGINS
        working to account the count of the packets which used the current USK, when the USK is set 
        by the primitive MLME-SETWPIKEYS.request. "
    ::= { apWAPIExternInfoConfigTableEntry 11 }     
    
apWAPIMulticastCipher OBJECT-TYPE
    SYNTAX OCTET STRING (SIZE(4))
    MAX-ACCESS read-write
    STATUS current
    DESCRIPTION

        "The object instruts the muticast cipher suites which entities should adopt. The unicast
        cipher suites of WAPI info-elements should adopt the value of this variable, which includes
        three OCTET OUI and an identification of the muticast cipher suites. "
    ::= { apWAPIExternInfoConfigTableEntry 12 }    
    
apWAPIMulticastRekeyMethod OBJECT-TYPE
    SYNTAX INTEGER {
        disabled(0),
        timeBased(1),
        packetBased(2),
        timepacket-Based(3)
    }
    MAX-ACCESS read-write
    STATUS current
    DESCRIPTION

        "The object choosee a mechanism to rebuild MSK of WAPI. It is defaultly timebased, once per
        day. The update of MSK is initialized by the entity which play the role of AE. "
    DEFVAL { timeBased }
    ::= { apWAPIExternInfoConfigTableEntry 13 }      
    
apWAPIMulticastRekeyTime OBJECT-TYPE
    SYNTAX Unsigned32 (1..4294967295)
    UNITS "second"
    MAX-ACCESS read-write
    STATUS current
    DESCRIPTION

        " The timing-Second of the update of WAPI MSK. The timer BEGINS working when the MSK is
        set by the primitive MLME-SETWPIKEYS.request. "
    DEFVAL { 86400 }
    ::= { apWAPIExternInfoConfigTableEntry 14 }   
    
apWAPIMulticastRekeyPackets OBJECT-TYPE
    SYNTAX Unsigned32 (1..4294967295)
    UNITS "1000 packets"
    MAX-ACCESS read-write
    STATUS current
    DESCRIPTION

        " The packet count of the update of WAPI MSK(unit in 1000 packets). Thr counter BEGINS
        working to account the count of the packets which used the current MSK, when the MSK is set 
        by the primitive MLME-SETWPIKEYS.request. "
    ::= { apWAPIExternInfoConfigTableEntry 15}    
    
apWAPIMulticastRekeyStrict OBJECT-TYPE
    SYNTAX TruthValue
    MAX-ACCESS read-write
    STATUS current
    DESCRIPTION

        " The object will send signal to notify that the MSK need update, whenever the STA leave the 
        BSS which owns MSK. "
    ::= { apWAPIExternInfoConfigTableEntry 16 }   
    
apWAPIPSKValue OBJECT-TYPE
    SYNTAX OCTET STRING (SIZE(32))
    MAX-ACCESS read-write
    STATUS current
    DESCRIPTION
    
        " Choose the PSK of the AKM suite of WAPI as the module of PSK. BK will be derivated by this
        object. This object is logically write-only. Reading the variable will return the status of 
        unsuccessfull, meaningless or 0. "
    ::= { apWAPIExternInfoConfigTableEntry 17 }     
    
apWAPIPSKPassPhrase OBJECT-TYPE
    SYNTAX DisplayString
    MAX-ACCESS read-write
    STATUS current
    DESCRIPTION
    
        " Choose the PSK of the AKM suite of WAPI as the module of PSK. BK is set by
        gb15629dot11wapiConfigPSKValue. Another alternative method is that using password-key 
        algorithm to set PSK. This variable provides a way to enter a password. When the object is 
        being writen, WAPI entity will use the password - key algorithm to export a pre-shared key,
        at the same time, it fill the gb15629dot11wapiConfigPSKValue with the pre-shared key. This 
        object is logically write-only. Reading the variable will return the status of unsuccessfull,
        meaningless or 0. "
    ::= { apWAPIExternInfoConfigTableEntry 18 }    
    
apWAPICertificateUpdateCount OBJECT-TYPE
    SYNTAX Unsigned32 (1..4294967295)
    MAX-ACCESS read-write
    STATUS current
    DESCRIPTION

        " In each handshake of the identification of each certificate,  retrans of WAPI certificate 
        identification handshake protocol messages. "
    DEFVAL { 3 }
    ::= { apWAPIExternInfoConfigTableEntry 19 }
    
apWAPIMulticastUpdateCount OBJECT-TYPE
    SYNTAX Unsigned32 (1..4294967295)
    MAX-ACCESS read-write
    STATUS current
    DESCRIPTION
    
        " In each handshake of MSK, retrans of WAPI muticast key handshake protocol messages. "
    DEFVAL { 3 }
    ::= { apWAPIExternInfoConfigTableEntry 20 }    
    
apWAPIUnicastUpdateCount OBJECT-TYPE
    SYNTAX Unsigned32 (1..4294967295)
    MAX-ACCESS read-write
    STATUS current
    DESCRIPTION

        " The retrans of the WAPI unicast key handshake protocol messages in the three times
        handshakes. "
    DEFVAL { 3 }
    ::= { apWAPIExternInfoConfigTableEntry 21 }    
    
apWAPIMulticastCipherSize OBJECT-TYPE
    SYNTAX Unsigned32 (0..4294967295)
    MAX-ACCESS read-only
    STATUS current
    DESCRIPTION

        " The object instruts the bits of the muticast key. For example SMS4, the length should be
        256. A 128-bit encryption keys for the front, followed by 128-bit key for the integrity
        check. "
    ::= { apWAPIExternInfoConfigTableEntry 22 }    
    
apWAPIBKLifetime OBJECT-TYPE
    SYNTAX Unsigned32 (1..4294967295)
    UNITS "second"
    MAX-ACCESS read-write
    STATUS current
    DESCRIPTION

        " At the buffering of BK, the maximum lifetime of a BK. "
    DEFVAL { 43200 }
    ::= { apWAPIExternInfoConfigTableEntry 23 }    
    
apWAPIBKReauthThreshold OBJECT-TYPE
    SYNTAX Unsigned32 (1..100)
    UNITS "percentage"
    MAX-ACCESS read-write
    STATUS current
    DESCRIPTION

        " Before the re-certification identification, the percentage of survival of the BK 
        should be preceded." 
    ::= { apWAPIExternInfoConfigTableEntry 24 }    
    
apWAPISATimeout OBJECT-TYPE
    SYNTAX Unsigned32 (1..4294967295)
    UNITS "second"
    MAX-ACCESS read-write
    STATUS current
    DESCRIPTION

        " The maximum time neededto establish Security association. "
    DEFVAL { 60 }
    ::= { apWAPIExternInfoConfigTableEntry 25 }    
    
apWAPIAuthSuiteSelected OBJECT-TYPE
    SYNTAX OCTET STRING (SIZE(4))
    MAX-ACCESS read-only
    STATUS current
    DESCRIPTION
    
        " AKM suite of the last consultation. "
    ::= { apWAPIExternInfoConfigTableEntry 26 }    
    
apWAPIUnicastCipherSelected OBJECT-TYPE
    SYNTAX OCTET STRING (SIZE(4))
    MAX-ACCESS read-only
    STATUS current
    DESCRIPTION
        
        " Unicast cipher suites of the last consultation. "
    ::= { apWAPIExternInfoConfigTableEntry 27 }    
        
apWAPIMulticastCipherSelected OBJECT-TYPE
    SYNTAX OCTET STRING (SIZE(4))
    MAX-ACCESS read-only
    STATUS current
    DESCRIPTION
    
        " Muticast cipher suites of the last consultation."
    ::= { apWAPIExternInfoConfigTableEntry 28 }     
    
apWAPIBKIDUsed OBJECT-TYPE
    SYNTAX OCTET STRING (SIZE(16))
    MAX-ACCESS read-only
    STATUS current
    DESCRIPTION
    
        " The BKID used in the process of last unicast key handshake. "
    ::= { apWAPIExternInfoConfigTableEntry 29 } 
    
apWAPIAuthSuiteRequested OBJECT-TYPE
    SYNTAX OCTET STRING (SIZE(4))
    MAX-ACCESS read-only
    STATUS current
    DESCRIPTION
        
        " AKM suite of the last requirements. "
    ::= { apWAPIExternInfoConfigTableEntry 30 }    
    
apWAPIUnicastCipherRequested OBJECT-TYPE
    SYNTAX OCTET STRING (SIZE(4))
    MAX-ACCESS read-only
    STATUS current
    DESCRIPTION
        
        " Unicast cipher suites of the last requirements. "
    ::= { apWAPIExternInfoConfigTableEntry 31 }     
    
apWAPIMulticastCipherRequested OBJECT-TYPE
    SYNTAX OCTET STRING (SIZE(4))
    MAX-ACCESS read-only
    STATUS current
    DESCRIPTION         
        " Muticast cipher suites of the last requirements. "
    ::= { apWAPIExternInfoConfigTableEntry 32 }         

apWAPIUnicastCipher OBJECT-TYPE
    SYNTAX OCTET STRING 
    MAX-ACCESS read-only
    STATUS current
    DESCRIPTION         
        " wapi select Unicast encrypt. "
    ::= { apWAPIExternInfoConfigTableEntry 33 }    

apWAPIUnicastCipherEnabled   OBJECT-TYPE
    SYNTAX TruthValue 
    MAX-ACCESS read-write
    STATUS current
    DESCRIPTION         
        " wapi Unicast encrypt enable. "
    ::= { apWAPIExternInfoConfigTableEntry 34 }   
    
apWAPIUnicastCipherSize    OBJECT-TYPE
    SYNTAX Unsigned32 
    MAX-ACCESS read-only
    STATUS current
    DESCRIPTION         
        " wapi Unicast encrypt bit len. "
    ::= { apWAPIExternInfoConfigTableEntry 35 }      
    
apWAPIAuthenticationSuite  OBJECT-TYPE
    SYNTAX OCTET STRING 
    MAX-ACCESS read-only
    STATUS current
    DESCRIPTION         
        " wapi select AKM . "
    ::= { apWAPIExternInfoConfigTableEntry 36 }   
    
apWAPIAuthenticationSuiteEnabled  OBJECT-TYPE
    SYNTAX TruthValue 
    MAX-ACCESS read-write
    STATUS current
    DESCRIPTION         
        " wapi AKM encrypt enable. "
    ::= { apWAPIExternInfoConfigTableEntry 37 } 

apWAPIAECertFile  OBJECT-TYPE
    SYNTAX DisplayString 
    MAX-ACCESS read-write
    STATUS current
    DESCRIPTION         
        " the file name of AE cert in WAPI. "
    ::= { apWAPIExternInfoConfigTableEntry 38 }
    
apWAPICACertFile  OBJECT-TYPE
    SYNTAX DisplayString 
    MAX-ACCESS read-write
    STATUS current
    DESCRIPTION         
        " the file name of CA cert in WAPI."
    ::= { apWAPIExternInfoConfigTableEntry 39 }   
    
apWAPIASUCertFile  OBJECT-TYPE
    SYNTAX DisplayString 
    MAX-ACCESS read-write
    STATUS current
    DESCRIPTION         
        " the file name of ASU cert in WAPI. "
    ::= { apWAPIExternInfoConfigTableEntry 40 }   
    
 
            
--**************************************************
--* apWAPIExternInfoConfig ends * 
--**************************************************
--**************************************************
--* apStationInfoGet starts * 
--**************************************************
apStationInfoGetObjects        OBJECT IDENTIFIER  ::= { qtechFitApMibModule 6 }  
apStationInfoGetTable  OBJECT-TYPE
    SYNTAX SEQUENCE OF ApStationInfoGetTableEntry
    MAX-ACCESS not-accessible
    STATUS current
    DESCRIPTION
      "The SSID config of ap."
    ::={ apStationInfoGetObjects 1 }

apStationInfoGetTableEntry OBJECT-TYPE
    SYNTAX  ApStationInfoGetTableEntry
    MAX-ACCESS  not-accessible
    STATUS  current
    DESCRIPTION
        "The SSID config of ap"
    INDEX   { qtechStaMacAddr }
    ::= { apStationInfoGetTable 1 }
    
ApStationInfoGetTableEntry ::=
    SEQUENCE {
        apStaMAC                       MacAddress,
        apStaWMMAttr                   INTEGER,
        apStaIPAddress                 IpAddress,
        apStaRadioMode                 INTEGER,  
        apStaRadioChannel              INTEGER,
        apAPTxRates                    INTEGER,
        apStaPowerSaveMode             INTEGER,
        apStaVlanId                    Counter32,
        apStaSSIDName                  DisplayString,
        apAPId                         INTEGER,
        apStaDot11Auth                 INTEGER,
        apsecurity                     INTEGER,
        apStaAuthenMode                INTEGER,
        apStaSecurityCiphers           INTEGER, 
        apAPIdMac                      MacAddress,
        apStaMode                      INTEGER,
        apStaBand                      INTEGER
    }  

apStaMAC  OBJECT-TYPE
    SYNTAX  MacAddress
    MAX-ACCESS  read-only
    STATUS  current
    DESCRIPTION
            "station mac addr number."
    ::= { apStationInfoGetTableEntry 1}    
    
apStaWMMAttr   OBJECT-TYPE
    SYNTAX  INTEGER {
          wmmsta(1),
          nonwmmsta(0)
    }
    MAX-ACCESS  read-only
    STATUS  current
    DESCRIPTION
            "QOS config support 0:WMMSta 1:NonWMMSta Index number."
    ::= { apStationInfoGetTableEntry 2}   
    
apStaIPAddress  OBJECT-TYPE
    SYNTAX  IpAddress
    MAX-ACCESS  read-only
    STATUS  current
    DESCRIPTION
            "station ip address."
    ::= { apStationInfoGetTableEntry 3}   
    
apStaRadioMode   OBJECT-TYPE
    SYNTAX  INTEGER {
        dot11a(0),
        dot11b(1),
        dot11g(2),
        dot11n(3)    
    }
    MAX-ACCESS  read-only
    STATUS  current
    DESCRIPTION
            "station radio mode 0:dot11a 1:dot11b
            2:dot11g 3:dot11n"
    ::= { apStationInfoGetTableEntry 4}     
    
apStaRadioChannel   OBJECT-TYPE
    SYNTAX  INTEGER
    MAX-ACCESS  read-only
    STATUS  current
    DESCRIPTION
            "station radio channel  "
    ::= { apStationInfoGetTableEntry 5}    
    
apAPTxRates   OBJECT-TYPE
    SYNTAX  INTEGER
    MAX-ACCESS  read-only
    STATUS  current
    DESCRIPTION
            "station current rate  "
    ::= { apStationInfoGetTableEntry 6}    
    
apStaPowerSaveMode  OBJECT-TYPE
    SYNTAX  INTEGER {
          active(0),
          powersave(1)
    }
    MAX-ACCESS  read-only
    STATUS  current
    DESCRIPTION
            "station power States 0:Active 1:Powersave ."
    ::= { apStationInfoGetTableEntry 7}        
    
apStaVlanId      OBJECT-TYPE
    SYNTAX  Counter32
    MAX-ACCESS  read-only
    STATUS  current
    DESCRIPTION
            "station vlan id ."
    ::= { apStationInfoGetTableEntry 8}
    
apStaSSIDName      OBJECT-TYPE
    SYNTAX  DisplayString
    MAX-ACCESS  read-only
    STATUS  current
    DESCRIPTION
            "station name ."
    ::= { apStationInfoGetTableEntry 9}
    
apAPId      OBJECT-TYPE
    SYNTAX  INTEGER
    MAX-ACCESS  read-only
    STATUS  current
    DESCRIPTION
            "ap id which station connectted ."
    ::= { apStationInfoGetTableEntry 10} 

apStaDot11Auth    OBJECT-TYPE
    SYNTAX  INTEGER {
          opensystem(0),
          sharedkey(1)
    }
    MAX-ACCESS  read-only
    STATUS  current
    DESCRIPTION
            "station dot11 auth 0:opensystem  1:sharedkey."
    ::= { apStationInfoGetTableEntry 11} 
   
apsecurity   OBJECT-TYPE
    SYNTAX  INTEGER {
          none(0),
          wpa(1),
          wpa2(2),
          wapi(3)
    }
    MAX-ACCESS  read-only
    STATUS  current
    DESCRIPTION
            "station dot11 apsecurity 0:none 1:wpa 2:wpa2 3:wapi."
    ::= { apStationInfoGetTableEntry 12}    
    
apStaAuthenMode  OBJECT-TYPE
    SYNTAX  INTEGER {
          none(0),
          psk(1),
          radius(2),
          wapicer(3),
          web(4),
          psk-web(5),
          wapicer-web(6),
	  wapipsk(7)
    }
    MAX-ACCESS  read-only
    STATUS  current
    DESCRIPTION
            "station AuthenMode 0:none 1:PSK 2:Radius 3:WAPICER 4:Web 5:PSK-Web 6:WAPICER-Web 7:WAPIPSK."
    ::= { apStationInfoGetTableEntry 13}   
    
apStaSecurityCiphers   OBJECT-TYPE
    SYNTAX  INTEGER {
          none(0),
          wep40(1),
          wep104(2),
          tkip(3),
          aesccmp(4),
          wpisms4(5)
    }
    MAX-ACCESS  read-only
    STATUS  current
    DESCRIPTION
            "station SecurityCiphers  0:none 1:wep40 
            2:wep104 3:tkip 4:aesccmp 5:wpi-SMS4"
    ::= { apStationInfoGetTableEntry 14}  
    
apAPIdMac	OBJECT-TYPE
    SYNTAX  MacAddress
    MAX-ACCESS  read-only
    STATUS  current
    DESCRIPTION
            "ap Mac which station connectted ."
    ::= { apStationInfoGetTableEntry 15}    
apStaMode  OBJECT-TYPE
    SYNTAX  INTEGER {
          dot11a(1),
          dot11b(2),
          dot11g(4),
          dot11an(8),
          dot11gn(16)
    }
    MAX-ACCESS  read-only
    STATUS  current
    DESCRIPTION
            "1:dot11a 2:dot11b 4:dot11g 8:dot11an 16:dot11gn"
    ::= { apStationInfoGetTableEntry 16}  
    
apStaBand  OBJECT-TYPE
    SYNTAX  INTEGER
    MAX-ACCESS  read-only
    STATUS  current
    DESCRIPTION
            "sta band  0:2.4G 1:5G"
    ::= { apStationInfoGetTableEntry 17} 
--**************************************************
--* apStationInfoGet ends * 
--**************************************************

--**************************************************
--* apStationRefusedAccess starts * 
--**************************************************

apStationRefusedAccessTable  OBJECT-TYPE
    SYNTAX SEQUENCE OF ApStationRefusedAccessTableEntry
    MAX-ACCESS not-accessible
    STATUS current
    DESCRIPTION
      "The refused accessed STA infomation."
    ::={ apStationInfoGetObjects 2 }

apStationRefusedAccessTableEntry OBJECT-TYPE
    SYNTAX  ApStationRefusedAccessTableEntry
    MAX-ACCESS  not-accessible
    STATUS  current
    DESCRIPTION
        "The refused accessed STA infomation."
    INDEX   { apRefusedStaMAC }
    ::= { apStationRefusedAccessTable 1 }
    
ApStationRefusedAccessTableEntry ::=
    SEQUENCE {
        apRefusedStaMAC                MacAddress,
        apFailReason									 INTEGER,
        apRefusedTime                  DisplayString,
        apRefusedAPMac								 MacAddress					
    }  

apRefusedStaMAC   OBJECT-TYPE
    SYNTAX  MacAddress
    MAX-ACCESS  read-only
    STATUS  current
    DESCRIPTION
            "Refused station MAC."
    ::= { apStationRefusedAccessTableEntry 1}   

apFailReason   OBJECT-TYPE
    SYNTAX  INTEGER
    MAX-ACCESS  read-only
    STATUS  current
    DESCRIPTION
            "Sation refused reason."
    ::= { apStationRefusedAccessTableEntry 2}   
    
apRefusedTime   OBJECT-TYPE
    SYNTAX  DisplayString
    MAX-ACCESS  read-only
    STATUS  current
    DESCRIPTION
            "Sation refused time"
    ::= { apStationRefusedAccessTableEntry 3} 
    
apRefusedAPMac   OBJECT-TYPE
    SYNTAX  MacAddress
    MAX-ACCESS  read-only
    STATUS  current
    DESCRIPTION
            "Sation refused AP MAC"
    ::= { apStationRefusedAccessTableEntry 4} 

--**************************************************
--* apStationRefusedAccess ends * 
--**************************************************    

--**************************************************
--* apStationRadiusInfoTable starts * 
--**************************************************

apStationRadiusInfoTable  OBJECT-TYPE
    SYNTAX SEQUENCE OF ApStationRadiusInfoTableEntry
    MAX-ACCESS not-accessible
    STATUS current
    DESCRIPTION
      "The Stations Radius Auth infomation."
    ::={ apStationInfoGetObjects 3 }

apStationRadiusInfoTableEntry OBJECT-TYPE
    SYNTAX  ApStationRadiusInfoTableEntry
    MAX-ACCESS  not-accessible
    STATUS  current
    DESCRIPTION
        "The refused accessed STA infomation."
    INDEX   {  qtechApMacAddr, apUserMacAddress }
    ::= { apStationRadiusInfoTable 1 }
    
ApStationRadiusInfoTableEntry ::=
    SEQUENCE {
        apUserMacAddress                	MacAddress,
        apUserIpAddress					IpAddress,
        apUserLoginName              		OCTET STRING,
        apUserLoginTime					OCTET STRING,
        apUserOnlineTime				    TimeTicks
    }  

apUserMacAddress   OBJECT-TYPE
    SYNTAX  MacAddress
    MAX-ACCESS  read-only
    STATUS  current
    DESCRIPTION
            "User MAC Address."
    ::= { apStationRadiusInfoTableEntry 1}   

apUserIpAddress   OBJECT-TYPE
    SYNTAX  IpAddress
    MAX-ACCESS  read-only
    STATUS  current
    DESCRIPTION
            "User Ip Address."
    ::= { apStationRadiusInfoTableEntry 2}   
    
apUserLoginName   OBJECT-TYPE
    SYNTAX  OCTET STRING
    MAX-ACCESS  read-only
    STATUS  current
    DESCRIPTION
            "User Login Name"
    ::= { apStationRadiusInfoTableEntry 3} 
    
apUserLoginTime   OBJECT-TYPE
    SYNTAX  OCTET STRING
    MAX-ACCESS  read-only
    STATUS  current
    DESCRIPTION
            "User Login Time"
    ::= { apStationRadiusInfoTableEntry 4}      
    
apUserOnlineTime   OBJECT-TYPE
    SYNTAX  TimeTicks
    MAX-ACCESS  read-only
    STATUS  current
    DESCRIPTION
            "User Online Time"
    ::= { apStationRadiusInfoTableEntry 5} 


--**************************************************
--* apStationRadiusInfoTable ends * 
--**************************************************

--**************************************************
--* apQOSinfoConfig starts * 
--**************************************************
apQOSInfoConfigObjects        OBJECT IDENTIFIER  ::= { qtechFitApMibModule 7 }  
apQOSWirelessConfigObjects    OBJECT IDENTIFIER  ::= { apQOSInfoConfigObjects 1 } 
apQOSBaseInfoConfigObjects    OBJECT IDENTIFIER  ::= { apQOSInfoConfigObjects 2 } 
apQOSBackgroundCfgObjects     OBJECT IDENTIFIER  ::= { apQOSInfoConfigObjects 3 } 
apQOSBestEffortCfgObjects     OBJECT IDENTIFIER  ::= { apQOSInfoConfigObjects 4 } 
apQOSVoiceInfoCfgObjects      OBJECT IDENTIFIER  ::= { apQOSInfoConfigObjects 5 } 
apQOSVideoInfoCfgObjects      OBJECT IDENTIFIER  ::= { apQOSInfoConfigObjects 6 } 
apQOSWMMConfigObjects	      OBJECT IDENTIFIER  ::= { apQOSInfoConfigObjects 7 }
--********apQOSWirelessConfig starts****************
apQOSWirelessConfigTable OBJECT-TYPE
    SYNTAX SEQUENCE OF ApQOSWirelessConfigTableEntry
    MAX-ACCESS not-accessible
    STATUS current
    DESCRIPTION
      "ap wireless QOS parameter config table."
    ::={ apQOSWirelessConfigObjects 1 }

apQOSWirelessConfigTableEntry    OBJECT-TYPE
    SYNTAX  ApQOSWirelessConfigTableEntry
    MAX-ACCESS  not-accessible
    STATUS  current
    DESCRIPTION
        "ap wireless QOS parameter config table."
    INDEX   { qtechApMacAddr,qtechApCfgRadioId,apWireQoSTrafficClassId }
    ::= { apQOSWirelessConfigTable 1 }

ApQOSWirelessConfigTableEntry ::=
    SEQUENCE {
        apWireQoSTrafficClassId            INTEGER,
        apWireQosAIFS                      INTEGER,
        apWireQoSCWmin                     INTEGER,
        apWireQoSCWmax                     INTEGER,
        apWireQoSTXOPLim                   INTEGER
    }
    
apWireQoSTrafficClassId  OBJECT-TYPE
    SYNTAX INTEGER {
        bestEffort(0),
        background(1),
        video(2),
        voice(3)
    }
    MAX-ACCESS read-only
    STATUS current
    DESCRIPTION
        "ap QOS Service type 0:bestEffort  1:background  2:video  3:voice."
    ::= { apQOSWirelessConfigTableEntry 1 } 
    
apWireQosAIFS   OBJECT-TYPE
    SYNTAX INTEGER 
    MAX-ACCESS read-write
    STATUS current
    DESCRIPTION
        "ap QOS AIFS ."
    ::= { apQOSWirelessConfigTableEntry 2 }  
    
apWireQoSCWmin  OBJECT-TYPE
    SYNTAX INTEGER 
    MAX-ACCESS read-write
    STATUS current
    DESCRIPTION
        "ap QOS WM min ."
    ::= { apQOSWirelessConfigTableEntry 3 }   
    
apWireQoSCWmax   OBJECT-TYPE
    SYNTAX INTEGER 
    MAX-ACCESS read-write
    STATUS current
    DESCRIPTION
        "ap QOS WM max ."
    ::= { apQOSWirelessConfigTableEntry 4 }    
    
apWireQoSTXOPLim  OBJECT-TYPE
    SYNTAX INTEGER 
    MAX-ACCESS read-write
    STATUS current
    DESCRIPTION
        "ap QOS TXOP limit ."
    ::= { apQOSWirelessConfigTableEntry 5 }       
--*************** apQOSWirelessConfig ends **********  
--*************** apQOSBaseInfoConfig starts **********  
     
apQOSBaseInfoConfigTable OBJECT-TYPE
    SYNTAX SEQUENCE OF ApQOSBaseInfoConfigTableEntry
    MAX-ACCESS not-accessible
    STATUS current
    DESCRIPTION
      "ap wireless QOS parameter config table."
    ::={ apQOSBaseInfoConfigObjects 1 }

apQOSBaseInfoConfigTableEntry    OBJECT-TYPE
    SYNTAX  ApQOSBaseInfoConfigTableEntry
    MAX-ACCESS  not-accessible
    STATUS  current
    DESCRIPTION
        "ap base QOS parameter config table."
    INDEX   { qtechApMacAddr, qtechApCfgRadioId }
    ::= { apQOSBaseInfoConfigTable 1 }

ApQOSBaseInfoConfigTableEntry ::=
    SEQUENCE {
        apBaseQoSTrafficClass              INTEGER,
        apBaseQoSEnabled                   TruthValue,
        apBaseQoSBW                        Integer32,
        apBaseQoSResPercent                Integer32,
        apBaseQoSsharedBW                  Integer32,
        apBaseQoSsharedBWPercent           Integer32,
        apBaseQoSSchedAlgName              DisplayString,
        apBaseQoSResPolicyEnabled          TruthValue,
        apBaseQoSResPolicyName             DisplayString,
        apBaseQoSBackgroundSvcAvgSpeed     Integer32,
        apBaseQoSBackgroundSvcMaxBurst     Integer32,
        apBaseQoSBackgroundSvcPriority     Integer32,
        apBaseQoSBackgroundSvcResPriority  Integer32,
        apBaseQoSBestEffortSvcAvgSpeed     Integer32,
        apBaseQoSBestEffortSvcMaxBurst     Integer32,
        apBaseQoSBestEffortSvcPriority     Integer32,
        apBaseQoSBestEffortSvcResPriority  Integer32,
        apBaseQoSVoiceSvcAvgSpeed          Integer32,
        apBaseQoSVoiceSvcMaxBurst          Integer32,
        apBaseQoSVoiceSvcPriority          Integer32,
        apBaseQoSVoiceSvcResPriority       Integer32,
        apBaseQoSVideoSvcAvgSpeed          Integer32,
        apBaseQoSVideoSvcMaxBurst          Integer32,
        apBaseQoSVideoSvcPriority          Integer32,
        apBaseQoSVideoSvcResPriority       Integer32
    }   
    
apBaseQoSTrafficClass   OBJECT-TYPE
    SYNTAX INTEGER {
        background(0),
        bestEffort(1),
        video(2),
        voice(3)
    }
    MAX-ACCESS read-write
    STATUS current
    DESCRIPTION
        "ap QOS Base Traffic type 0:background  1:bestEffort  2:video  3:voice."
    ::= { apQOSBaseInfoConfigTableEntry 1 }   
    
apBaseQoSEnabled   OBJECT-TYPE
    SYNTAX TruthValue
    MAX-ACCESS read-write
    STATUS current
    DESCRIPTION
        "ap Base QOS  enable or disable."
    ::= { apQOSBaseInfoConfigTableEntry 2 }     
    
apBaseQoSBW   OBJECT-TYPE
    SYNTAX Integer32
    MAX-ACCESS read-write
    STATUS current
    DESCRIPTION
        "ap Base QOS base service bandwidth."
    ::= { apQOSBaseInfoConfigTableEntry 3 }    
    
apBaseQoSResPercent  OBJECT-TYPE
    SYNTAX Integer32
    MAX-ACCESS read-write
    STATUS current
    DESCRIPTION
        "ap Base QOS base service Resource percent."
    ::= { apQOSBaseInfoConfigTableEntry 4 }  
    
apBaseQoSsharedBW  OBJECT-TYPE
    SYNTAX Integer32
    MAX-ACCESS read-write
    STATUS current
    DESCRIPTION
        "ap Base QOS share service bandwidth."
    ::= { apQOSBaseInfoConfigTableEntry 5 }  
    
apBaseQoSsharedBWPercent OBJECT-TYPE
    SYNTAX Integer32
    MAX-ACCESS read-write
    STATUS current
    DESCRIPTION
        "ap Base QOS share service Resource percent."
    ::= { apQOSBaseInfoConfigTableEntry 6 }    
    
apBaseQoSSchedAlgName    OBJECT-TYPE
    SYNTAX DisplayString
    MAX-ACCESS read-write
    STATUS current
    DESCRIPTION
        "ap Base QOS service schedule name."
    ::= { apQOSBaseInfoConfigTableEntry 7 }   
    
apBaseQoSResPolicyEnabled   OBJECT-TYPE
    SYNTAX TruthValue
    MAX-ACCESS read-write
    STATUS current
    DESCRIPTION
        "ap Base QOS Resource Policy enable."
    ::= { apQOSBaseInfoConfigTableEntry 8 }    
    
apBaseQoSResPolicyName   OBJECT-TYPE
    SYNTAX DisplayString
    MAX-ACCESS read-write
    STATUS current
    DESCRIPTION
        "ap Base QOS Resource Policy name."
    ::= { apQOSBaseInfoConfigTableEntry 9 }    
    
apBaseQoSBackgroundSvcAvgSpeed OBJECT-TYPE
    SYNTAX Integer32
    MAX-ACCESS read-write
    STATUS current
    DESCRIPTION
        "ap Base QOS background service average speed."
    ::= { apQOSBaseInfoConfigTableEntry 10 }     
    
apBaseQoSBackgroundSvcMaxBurst OBJECT-TYPE
    SYNTAX Integer32
    MAX-ACCESS read-write
    STATUS current
    DESCRIPTION
        "ap Base QOS background service busrt max speed."
    ::= { apQOSBaseInfoConfigTableEntry 11 }  
    
apBaseQoSBackgroundSvcPriority OBJECT-TYPE
    SYNTAX Integer32
    MAX-ACCESS read-write
    STATUS current
    DESCRIPTION
        "ap Base QOS background service schedule Priority."
    ::= { apQOSBaseInfoConfigTableEntry 12 }   
    
apBaseQoSBackgroundSvcResPriority OBJECT-TYPE
    SYNTAX Integer32
    MAX-ACCESS read-write
    STATUS current
    DESCRIPTION
        "ap Base QOS background despoil  Priority."
    ::= { apQOSBaseInfoConfigTableEntry 13 }  
    
apBaseQoSBestEffortSvcAvgSpeed OBJECT-TYPE
    SYNTAX Integer32
    MAX-ACCESS read-write
    STATUS current
    DESCRIPTION
        "ap Base QOS BestEffort service average speed."
    ::= { apQOSBaseInfoConfigTableEntry 14 }      
    
apBaseQoSBestEffortSvcMaxBurst OBJECT-TYPE
    SYNTAX Integer32
    MAX-ACCESS read-write
    STATUS current
    DESCRIPTION
        "ap Base QOS BestEffort service  MAX burst speed."
    ::= { apQOSBaseInfoConfigTableEntry 15 }   
    
apBaseQoSBestEffortSvcPriority OBJECT-TYPE
    SYNTAX Integer32
    MAX-ACCESS read-write
    STATUS current
    DESCRIPTION
        "ap Base QOS BestEffort service schedule Priority."
    ::= { apQOSBaseInfoConfigTableEntry 16 }   
    
apBaseQoSBestEffortSvcResPriority OBJECT-TYPE
    SYNTAX Integer32
    MAX-ACCESS read-write
    STATUS current
    DESCRIPTION
        "ap Base QOS BestEffort despoil  Priority."
    ::= { apQOSBaseInfoConfigTableEntry 17 }     
    
apBaseQoSVoiceSvcAvgSpeed OBJECT-TYPE
    SYNTAX Integer32
    MAX-ACCESS read-write
    STATUS current
    DESCRIPTION
        "ap Base QOS voice service average speed."
    ::= { apQOSBaseInfoConfigTableEntry 18 }      
    
apBaseQoSVoiceSvcMaxBurst OBJECT-TYPE
    SYNTAX Integer32
    MAX-ACCESS read-write
    STATUS current
    DESCRIPTION
        "ap Base QOS voice service  MAX burst speed."
    ::= { apQOSBaseInfoConfigTableEntry 19 }   
    
apBaseQoSVoiceSvcPriority OBJECT-TYPE
    SYNTAX Integer32
    MAX-ACCESS read-write
    STATUS current
    DESCRIPTION
        "ap Base QOS voice service schedule Priority."
    ::= { apQOSBaseInfoConfigTableEntry 20 }   
    
apBaseQoSVoiceSvcResPriority OBJECT-TYPE
    SYNTAX Integer32
    MAX-ACCESS read-write
    STATUS current
    DESCRIPTION
        "ap Base QOS voice service despoil  Priority."
    ::= { apQOSBaseInfoConfigTableEntry 21 }     
     
apBaseQoSVideoSvcAvgSpeed OBJECT-TYPE
    SYNTAX Integer32
    MAX-ACCESS read-write
    STATUS current
    DESCRIPTION
        "ap Base QOS video service average speed."
    ::= { apQOSBaseInfoConfigTableEntry 22 }      
    
apBaseQoSVideoSvcMaxBurst OBJECT-TYPE
    SYNTAX Integer32
    MAX-ACCESS read-write
    STATUS current
    DESCRIPTION
        "ap Base QOS video service  MAX burst speed."
    ::= { apQOSBaseInfoConfigTableEntry 23 }   
    
apBaseQoSVideoSvcPriority OBJECT-TYPE
    SYNTAX Integer32
    MAX-ACCESS read-write
    STATUS current
    DESCRIPTION
        "ap Base QOS video service schedule Priority."
    ::= { apQOSBaseInfoConfigTableEntry 24 }   
    
apBaseQoSVideoSvcResPriority OBJECT-TYPE
    SYNTAX Integer32
    MAX-ACCESS read-write
    STATUS current
    DESCRIPTION
        "ap Base QOS video service despoil  Priority."
    ::= { apQOSBaseInfoConfigTableEntry 25 }                                      
--*************** apQOSBaseInfoConfig ends **********    
--*************** apQOSBackgroundCfg starts **********  

apQOSBackgroundCfgTable OBJECT-TYPE
    SYNTAX SEQUENCE OF ApQOSBackgroundCfgTableEntry
    MAX-ACCESS not-accessible
    STATUS current
    DESCRIPTION
      "ap  QOS Background service parameter config table."
    ::={ apQOSBackgroundCfgObjects 1 }

apQOSBackgroundCfgTableEntry    OBJECT-TYPE
    SYNTAX  ApQOSBackgroundCfgTableEntry
    MAX-ACCESS  not-accessible
    STATUS  current
    DESCRIPTION
        "ap  QOS Background service parameter config table."
    INDEX   { qtechApMacAddr, qtechApCfgRadioId }
    ::= { apQOSBackgroundCfgTable 1 }

ApQOSBackgroundCfgTableEntry ::=
    SEQUENCE {
        apQOSBgMaxSvcCnt              Integer32,
        apQOSBgSvcBW                  Integer32,
        apQOSBgSvcBWPercent           Integer32,
        apQOSBgIsUseWREDAlg           TruthValue,
        apQOSBgIsUseTrafficShaping    TruthValue
    }
    
apQOSBgMaxSvcCnt  OBJECT-TYPE
    SYNTAX Integer32
    MAX-ACCESS read-write
    STATUS current
    DESCRIPTION
        "ap QOS BackGroud service apposition max count."
    ::= { apQOSBackgroundCfgTableEntry 1 }    

apQOSBgSvcBW    OBJECT-TYPE
    SYNTAX Integer32
    MAX-ACCESS read-write
    STATUS current
    DESCRIPTION
        "ap QOS BackGroud service bandwidth limit."
    ::= { apQOSBackgroundCfgTableEntry 2 }   
    
apQOSBgSvcBWPercent  OBJECT-TYPE
    SYNTAX Integer32
    MAX-ACCESS read-write
    STATUS current
    DESCRIPTION
        "ap QOS BackGroud service bandwidth percent."
    ::= { apQOSBackgroundCfgTableEntry 3 }   
    
apQOSBgIsUseWREDAlg  OBJECT-TYPE
    SYNTAX TruthValue
    MAX-ACCESS read-write
    STATUS current
    DESCRIPTION
        "ap QOS BackGroud service used WRED  arithmetic."
    ::= { apQOSBackgroundCfgTableEntry 4 }   
    
apQOSBgIsUseTrafficShaping   OBJECT-TYPE
    SYNTAX TruthValue
    MAX-ACCESS read-write
    STATUS current
    DESCRIPTION
        "ap QOS BackGroud service used Traffic Shaping."
    ::= { apQOSBackgroundCfgTableEntry 5 }      
--*************** apQOSBackgroundCfg ends **********    
--*************** apQOSBestEffortCfg starts ********** 

apQOSBestEffortCfgTable OBJECT-TYPE
    SYNTAX SEQUENCE OF ApQOSBestEffortCfgTableEntry
    MAX-ACCESS not-accessible
    STATUS current
    DESCRIPTION
      "ap  QOS BestEffort service parameter config table."
    ::={ apQOSBestEffortCfgObjects 1 }

apQOSBestEffortCfgTableEntry    OBJECT-TYPE
    SYNTAX  ApQOSBestEffortCfgTableEntry
    MAX-ACCESS  not-accessible
    STATUS  current
    DESCRIPTION
        "ap  QOS BestEffort service parameter config table."
    INDEX   { qtechApMacAddr, qtechApCfgRadioId }
    ::= { apQOSBestEffortCfgTable 1 }

ApQOSBestEffortCfgTableEntry ::=
    SEQUENCE {
        apQOSBeMaxSvcCnt              Integer32,
        apQOSBeSvcBW                  Integer32,
        apQOSBeSvcBWPercent           Integer32,
        apQOSBeIsUseWREDAlg           TruthValue,
        apQOSBeIsUseTrafficShaping    TruthValue
    }
apQOSBeMaxSvcCnt  OBJECT-TYPE
    SYNTAX Integer32
    MAX-ACCESS read-write
    STATUS current
    DESCRIPTION
        "ap QOS BestEffort service apposition max count."
    ::= { apQOSBestEffortCfgTableEntry 1 }    

apQOSBeSvcBW    OBJECT-TYPE
    SYNTAX Integer32
    MAX-ACCESS read-write
    STATUS current
    DESCRIPTION
        "ap QOS BestEffort service bandwidth limit."
    ::= { apQOSBestEffortCfgTableEntry 2 }   
    
apQOSBeSvcBWPercent  OBJECT-TYPE
    SYNTAX Integer32
    MAX-ACCESS read-write
    STATUS current
    DESCRIPTION
        "ap QOS BestEffort service bandwidth percent."
    ::= { apQOSBestEffortCfgTableEntry 3 }   
    
apQOSBeIsUseWREDAlg  OBJECT-TYPE
    SYNTAX TruthValue
    MAX-ACCESS read-write
    STATUS current
    DESCRIPTION
        "ap QOS BestEffort service used WRED  arithmetic."
    ::= { apQOSBestEffortCfgTableEntry 4 }   
    
apQOSBeIsUseTrafficShaping   OBJECT-TYPE
    SYNTAX TruthValue
    MAX-ACCESS read-write
    STATUS current
    DESCRIPTION
        "ap QOS BestEffort service used Traffic Shaping."
    ::= { apQOSBestEffortCfgTableEntry 5 }       
--*************** apQOSBestEffortCfg ends ********** 
--*************** apQOSVoiceInfoCfg starts ********** 

apQOSVoiceInfoCfgTable OBJECT-TYPE
    SYNTAX SEQUENCE OF ApQOSVoiceInfoCfgTableEntry
    MAX-ACCESS not-accessible
    STATUS current
    DESCRIPTION
      "ap  QOS voice service parameter config table."
    ::={ apQOSVoiceInfoCfgObjects 1 }

apQOSVoiceInfoCfgTableEntry    OBJECT-TYPE
    SYNTAX  ApQOSVoiceInfoCfgTableEntry
    MAX-ACCESS  not-accessible
    STATUS  current
    DESCRIPTION
        "ap  QOS voice service parameter config table."
    INDEX   { qtechApMacAddr, qtechApCfgRadioId }
    ::= { apQOSVoiceInfoCfgTable 1 }

ApQOSVoiceInfoCfgTableEntry ::=
    SEQUENCE {
        apQOSVoiceMaxSvcCnt               Integer32,
        apQOSVoiceSvcBW                   Integer32,
        apQOSVoiceSvcBWPercent            Integer32,
        apQOSVoiceIsUseStreamBasedQueue   TruthValue,
        apQOSVoiceStreamMaxQueueLen       Integer32,
        apQOSVoiceStreamAvgSpeed          Integer32,
        apQOSVoiceStreamMaxBurst          Integer32,
        apQOSVoiceIsUseWREDAlg            TruthValue,
        apQOSVoiceIsUseTrafficShaping     TruthValue
    }
    
apQOSVoiceMaxSvcCnt  OBJECT-TYPE
    SYNTAX Integer32
    MAX-ACCESS read-write
    STATUS current
    DESCRIPTION
        "ap QOS Voice service apposition max count."
    ::= { apQOSVoiceInfoCfgTableEntry 1 } 
    
apQOSVoiceSvcBW   OBJECT-TYPE
    SYNTAX Integer32
    MAX-ACCESS read-write
    STATUS current
    DESCRIPTION
        "ap QOS Voice service bandwidth limit."
    ::= { apQOSVoiceInfoCfgTableEntry 2 } 
    
apQOSVoiceSvcBWPercent   OBJECT-TYPE
    SYNTAX Integer32
    MAX-ACCESS read-write
    STATUS current
    DESCRIPTION
        "ap QOS Voice service bandwidth percent."
    ::= { apQOSVoiceInfoCfgTableEntry 3 }         

apQOSVoiceIsUseStreamBasedQueue    OBJECT-TYPE
    SYNTAX TruthValue
    MAX-ACCESS read-write
    STATUS current
    DESCRIPTION
        "ap QOS Voice Stream Based Queue enable."
    ::= { apQOSVoiceInfoCfgTableEntry 4 }   
    
apQOSVoiceStreamMaxQueueLen  OBJECT-TYPE
    SYNTAX Integer32
    MAX-ACCESS read-write
    STATUS current
    DESCRIPTION
        "ap QOS Voice Stream Max Queue lenth."
    ::= { apQOSVoiceInfoCfgTableEntry 5 }  
    
apQOSVoiceStreamAvgSpeed    OBJECT-TYPE
    SYNTAX Integer32
    MAX-ACCESS read-write
    STATUS current
    DESCRIPTION
        "ap QOS Voice Stream average speed."
    ::= { apQOSVoiceInfoCfgTableEntry 6 } 
    
apQOSVoiceStreamMaxBurst OBJECT-TYPE
    SYNTAX Integer32
    MAX-ACCESS read-write
    STATUS current
    DESCRIPTION
        "ap QOS Voice Stream Max Burst speed."
    ::= { apQOSVoiceInfoCfgTableEntry 7 }
    
apQOSVoiceIsUseWREDAlg    OBJECT-TYPE
    SYNTAX TruthValue
    MAX-ACCESS read-write
    STATUS current
    DESCRIPTION
        "ap QOS Voice service used WRED  arithmetic."
    ::= { apQOSVoiceInfoCfgTableEntry 8 }   
    
apQOSVoiceIsUseTrafficShaping   OBJECT-TYPE
    SYNTAX TruthValue
    MAX-ACCESS read-write
    STATUS current
    DESCRIPTION
        "ap QOS Voice service used Traffic Shaping."
    ::= { apQOSVoiceInfoCfgTableEntry 9 }           
      
--*************** apQOSVoiceInfoCfg ends ********** 
--*************** apQOSVideoInfoCfg starts ********** 

apQOSVideoInfoCfgTable OBJECT-TYPE
    SYNTAX SEQUENCE OF ApQOSVideoInfoCfgTableEntry
    MAX-ACCESS not-accessible
    STATUS current
    DESCRIPTION
      "ap  QOS Video service parameter config table."
    ::={ apQOSVideoInfoCfgObjects 1 }

apQOSVideoInfoCfgTableEntry    OBJECT-TYPE
    SYNTAX  ApQOSVideoInfoCfgTableEntry
    MAX-ACCESS  not-accessible
    STATUS  current
    DESCRIPTION
        "ap  QOS Video service parameter config table."
    INDEX   { qtechApMacAddr, qtechApCfgRadioId }
    ::= { apQOSVideoInfoCfgTable 1 }

ApQOSVideoInfoCfgTableEntry ::=
    SEQUENCE {
        apQOSVideoMaxSvcCnt               Integer32,
        apQOSVideoSvcBW                   Integer32,
        apQOSVideoSvcBWPercent            Integer32,
        apQOSVideoIsUseStreamBasedQueue   TruthValue,
        apQOSVideoStreamMaxQueueLen       Integer32,
        apQOSVideoStreamAvgSpeed          Integer32,
        apQOSVideoStreamMaxBurst          Integer32,
        apQOSVideoIsUseWREDAlg            TruthValue,
        apQOSVideoIsUseTrafficShaping     TruthValue
    }
    
apQOSVideoMaxSvcCnt  OBJECT-TYPE
    SYNTAX Integer32
    MAX-ACCESS read-write
    STATUS current
    DESCRIPTION
        "ap QOS Video service apposition max count."
    ::= { apQOSVideoInfoCfgTableEntry 1 } 
    
apQOSVideoSvcBW   OBJECT-TYPE
    SYNTAX Integer32
    MAX-ACCESS read-write
    STATUS current
    DESCRIPTION
        "ap QOS Video service bandwidth limit."
    ::= { apQOSVideoInfoCfgTableEntry 2 } 
    
apQOSVideoSvcBWPercent   OBJECT-TYPE
    SYNTAX Integer32
    MAX-ACCESS read-write
    STATUS current
    DESCRIPTION
        "ap QOS Video service bandwidth percent."
    ::= { apQOSVideoInfoCfgTableEntry 3 }         

apQOSVideoIsUseStreamBasedQueue    OBJECT-TYPE
    SYNTAX TruthValue
    MAX-ACCESS read-write
    STATUS current
    DESCRIPTION
        "ap QOS Video Stream Based Queue enable."
    ::= { apQOSVideoInfoCfgTableEntry 4 }   
    
apQOSVideoStreamMaxQueueLen  OBJECT-TYPE
    SYNTAX Integer32
    MAX-ACCESS read-write
    STATUS current
    DESCRIPTION
        "ap QOS Video Stream Max Queue lenth."
    ::= { apQOSVideoInfoCfgTableEntry 5 }  
    
apQOSVideoStreamAvgSpeed    OBJECT-TYPE
    SYNTAX Integer32
    MAX-ACCESS read-write
    STATUS current
    DESCRIPTION
        "ap QOS Video Stream average speed."
    ::= { apQOSVideoInfoCfgTableEntry 6 } 
    
apQOSVideoStreamMaxBurst OBJECT-TYPE
    SYNTAX Integer32
    MAX-ACCESS read-write
    STATUS current
    DESCRIPTION
        "ap QOS Video Stream Max Burst speed."
    ::= { apQOSVideoInfoCfgTableEntry 7 }
    
apQOSVideoIsUseWREDAlg    OBJECT-TYPE
    SYNTAX TruthValue
    MAX-ACCESS read-write
    STATUS current
    DESCRIPTION
        "ap QOS Video service used WRED  arithmetic."
    ::= { apQOSVideoInfoCfgTableEntry 8 }   
    
apQOSVideoIsUseTrafficShaping   OBJECT-TYPE
    SYNTAX TruthValue
    MAX-ACCESS read-write
    STATUS current
    DESCRIPTION
        "ap QOS Video service used Traffic Shaping."
    ::= { apQOSVideoInfoCfgTableEntry 9 }           
      
--*************** apQOSVideoInfoCfg ends ********** 
--*************** apQOSWMMConifg starts ********** 
apQOSWMMConfigTable OBJECT-TYPE
    SYNTAX SEQUENCE OF ApQOSWMMConfigTableEntry
    MAX-ACCESS not-accessible
    STATUS current
    DESCRIPTION
      "ap  QOS Video service parameter config table."
    ::={ apQOSWMMConfigObjects 1 }

apQOSWMMConfigTableEntry    OBJECT-TYPE
    SYNTAX  ApQOSWMMConfigTableEntry
    MAX-ACCESS  not-accessible
    STATUS  current
    DESCRIPTION
        "ap Radio WMM parameter config table."
    INDEX   { qtechApMacAddr, qtechApCfgRadioId }
    ::= { apQOSWMMConfigTable 1 }

ApQOSWMMConfigTableEntry ::=   
    SEQUENCE {
        apQOSMode			              	INTEGER,
        apQOSUpdateSeq                   	INTEGER,
        apQOSSvpAcIndex            			INTEGER,
        apQOSUapsd   						INTEGER, 
        apQOSAcIndx1						INTEGER,
        apQOSAcIndx2						INTEGER, 
        apQOSAcIndx3						INTEGER,
        apQOSAcIndx4						INTEGER,
        apQOSAifsn1							INTEGER, 
        apQOSAifsn2							INTEGER,
        apQOSAifsn3							INTEGER,
        apQOSAifsn4							INTEGER,
        apQOSEcwMin1						INTEGER,
        apQOSEcwMin2						INTEGER,
        apQOSEcwMin3						INTEGER,
        apQOSEcwMin4						INTEGER,
        apQOSEcwMax1						INTEGER, 
        apQOSEcwMax2						INTEGER,
        apQOSEcwMax3						INTEGER,
        apQOSEcwMax4						INTEGER,
        apQOSTxopLmt1						INTEGER, 
        apQOSTxopLmt2						INTEGER,
        apQOSTxopLmt3						INTEGER,
        apQOSTxopLmt4						INTEGER,
        apQOSAcmAndAck1						INTEGER, 
        apQOSAcmAndAck2						INTEGER,
        apQOSAcmAndAck3						INTEGER,
        apQOSAcmAndAck4						INTEGER
	}	          
	
	apQOSMode   OBJECT-TYPE
    SYNTAX  INTEGER {
          none(0),
          wmm(1),
          dot8011e(2),
          wmm80211e(3)
    }
    MAX-ACCESS  read-only
    STATUS  current
    DESCRIPTION
            "QOS Mode  0:none 1:wmm 2:80211.e 3:wmm & 80211.e ."
    ::= { apQOSWMMConfigTableEntry 1 }  
    
    apQOSUpdateSeq OBJECT-TYPE
    SYNTAX INTEGER
    MAX-ACCESS read-write
    STATUS current
    DESCRIPTION
        "apQOSUpdateSeq."
    ::= { apQOSWMMConfigTableEntry 2}
          
    apQOSSvpAcIndex OBJECT-TYPE
    SYNTAX INTEGER
    MAX-ACCESS read-write
    STATUS current
    DESCRIPTION
        "apQOSSvpAcIndex."
    ::= { apQOSWMMConfigTableEntry 3}  
    
    apQOSUapsd OBJECT-TYPE
    SYNTAX INTEGER
    MAX-ACCESS read-write
    STATUS current
    DESCRIPTION
        "apQOSUapsd."
    ::= { apQOSWMMConfigTableEntry 4} 
        
	apQOSAcIndx1  OBJECT-TYPE
    SYNTAX INTEGER
    MAX-ACCESS read-write
    STATUS current
    DESCRIPTION
        "apQOSAifsn1."
    ::= {apQOSWMMConfigTableEntry 5}

	apQOSAcIndx2  OBJECT-TYPE
    SYNTAX INTEGER
    MAX-ACCESS read-write
    STATUS current
    DESCRIPTION
        "apQOSAifsn2."
    ::= {apQOSWMMConfigTableEntry 6}

	apQOSAcIndx3  OBJECT-TYPE
    SYNTAX INTEGER
    MAX-ACCESS read-write
    STATUS current
    DESCRIPTION
        "apQOSAifsn3."
    ::= {apQOSWMMConfigTableEntry 7}

	apQOSAcIndx4  OBJECT-TYPE
    SYNTAX INTEGER
    MAX-ACCESS read-write
    STATUS current
    DESCRIPTION
        "apQOSAcIndx4."
    ::= {apQOSWMMConfigTableEntry 8}
 
	apQOSAifsn1  OBJECT-TYPE
    SYNTAX INTEGER
    MAX-ACCESS read-write
    STATUS current
    DESCRIPTION
        "apQOSAifsn1."
    ::= {apQOSWMMConfigTableEntry 9}

	apQOSAifsn2  OBJECT-TYPE
    SYNTAX INTEGER
    MAX-ACCESS read-write
    STATUS current
    DESCRIPTION
        "apQOSAifsn2."
    ::= {apQOSWMMConfigTableEntry 10}

	apQOSAifsn3  OBJECT-TYPE
    SYNTAX INTEGER
    MAX-ACCESS read-write
    STATUS current
    DESCRIPTION
        "apQOSAifsn3."
    ::= {apQOSWMMConfigTableEntry 11}

	apQOSAifsn4  OBJECT-TYPE
    SYNTAX INTEGER
    MAX-ACCESS read-write
    STATUS current
    DESCRIPTION
        "apQOSAifsn4."
    ::= {apQOSWMMConfigTableEntry 12}

	apQOSEcwMin1  OBJECT-TYPE
    SYNTAX INTEGER
    MAX-ACCESS read-write
    STATUS current
    DESCRIPTION
        "apQOSEcwMin1."
    ::= {apQOSWMMConfigTableEntry 13}

	apQOSEcwMin2  OBJECT-TYPE
    SYNTAX INTEGER
    MAX-ACCESS read-write
    STATUS current
    DESCRIPTION
        "apQOSEcwMin2."
    ::= {apQOSWMMConfigTableEntry 14}

	apQOSEcwMin3  OBJECT-TYPE
    SYNTAX INTEGER
    MAX-ACCESS read-write
    STATUS current
    DESCRIPTION
        "apQOSEcwMax1."
    ::= {apQOSWMMConfigTableEntry 15}

	apQOSEcwMin4  OBJECT-TYPE
    SYNTAX INTEGER
    MAX-ACCESS read-write
    STATUS current
    DESCRIPTION
        "apQOSEcwMax1."
    ::= {apQOSWMMConfigTableEntry 16}
  
	apQOSEcwMax1  OBJECT-TYPE
    SYNTAX INTEGER
    MAX-ACCESS read-write
    STATUS current
    DESCRIPTION
        "apQOSEcwMax1."
    ::= {apQOSWMMConfigTableEntry 17}
 
	apQOSEcwMax2  OBJECT-TYPE
    SYNTAX INTEGER
    MAX-ACCESS read-write
    STATUS current
    DESCRIPTION
        "apQOSEcwMax2."
    ::= {apQOSWMMConfigTableEntry 18}

	apQOSEcwMax3  OBJECT-TYPE
    SYNTAX INTEGER
    MAX-ACCESS read-write
    STATUS current
    DESCRIPTION
        "apQOSEcwMax3."
    ::= {apQOSWMMConfigTableEntry 19}
	
	apQOSEcwMax4  OBJECT-TYPE
    SYNTAX INTEGER
    MAX-ACCESS read-write
    STATUS current
    DESCRIPTION
        "apQOSEcwMax4."
    ::= {apQOSWMMConfigTableEntry 20}

	apQOSTxopLmt1  OBJECT-TYPE
    SYNTAX INTEGER
    MAX-ACCESS read-write
    STATUS current
    DESCRIPTION
        "apQOSTxopLmt3."
    ::= {apQOSWMMConfigTableEntry 21}

	apQOSTxopLmt2  OBJECT-TYPE
    SYNTAX INTEGER
    MAX-ACCESS read-write
    STATUS current
    DESCRIPTION
        "apQOSTxopLmt3."
    ::= {apQOSWMMConfigTableEntry 22}

	apQOSTxopLmt3  OBJECT-TYPE
    SYNTAX INTEGER
    MAX-ACCESS read-write
    STATUS current
    DESCRIPTION
        "apQOSTxopLmt3."
    ::= {apQOSWMMConfigTableEntry 23}
 
	apQOSTxopLmt4  OBJECT-TYPE
    SYNTAX INTEGER
    MAX-ACCESS read-write
    STATUS current
    DESCRIPTION
        "apQOSTxopLmt4."
    ::= {apQOSWMMConfigTableEntry 24}
   	
	apQOSAcmAndAck1  OBJECT-TYPE
    SYNTAX INTEGER
    MAX-ACCESS read-write
    STATUS current
    DESCRIPTION
        "apQOSAcmAndAck1."
    ::= { apQOSWMMConfigTableEntry 25}

	apQOSAcmAndAck2  OBJECT-TYPE
    SYNTAX INTEGER
    MAX-ACCESS read-write
    STATUS current
    DESCRIPTION
        "apQOSAcmAndAck2."
    ::= { apQOSWMMConfigTableEntry 26}
        
    apQOSAcmAndAck3  OBJECT-TYPE
    SYNTAX INTEGER
    MAX-ACCESS read-write
    STATUS current
    DESCRIPTION
        "apQOSAcmAndAck3."
    ::= { apQOSWMMConfigTableEntry 27}
        
    apQOSAcmAndAck4  OBJECT-TYPE
    SYNTAX INTEGER
    MAX-ACCESS read-write
    STATUS current
    DESCRIPTION
        "apQOSAcmAndAck2."
    ::= { apQOSWMMConfigTableEntry 28}

        
--*************** apQOSWMMConifg ends **********
--**************************************************
--* apQOSinfoConfig ends * 
--**************************************************
--**************************************************
--* apAlarmParamConfig starts * 
--**************************************************
--apAlarmParamConfigObjects        OBJECT IDENTIFIER  ::= { qtechFitApMibModule 8 } 
--apAlarmParamConfigTable  OBJECT-TYPE
--    SYNTAX SEQUENCE OF ApAlarmParamConfigTableEntry
--    MAX-ACCESS not-accessible
--    STATUS current
--    DESCRIPTION
--      "ap alarm parameter config table."
--    ::={ apAlarmParamConfigObjects 1 }
--
--apAlarmParamConfigTableEntry OBJECT-TYPE
--    SYNTAX  ApAlarmParamConfigTableEntry
--    MAX-ACCESS  not-accessible
--    STATUS  current
--    DESCRIPTION
--        "ap alarm parameter config table."
--    INDEX   { ifIndex }
--   ::= { apAlarmParamConfigTable 1 }
--
--ApAlarmParamConfigTableEntry ::=
--    SEQUENCE {
--        apStaInterfNumThreshhd              INTEGER,
--        apAPCoInterfThreshhd                INTEGER,
--        apAPNeiborInterfThreshhd            INTEGER,
--        apCPUusageThreshhd                  INTEGER,
--        apMemUsageThreshhd                  INTEGER
--    }
apAlarmParamConfigEntry        OBJECT IDENTIFIER  ::= { qtechFitApMibModule 8 }     
apStaInterfNumThreshhd OBJECT-TYPE
    SYNTAX INTEGER 
    MAX-ACCESS read-write
    STATUS current
    DESCRIPTION
        "if Sta InterfNum bigger this param,them send trap."
    ::= { apAlarmParamConfigEntry 1 }
    
apAPCoInterfThreshhd    OBJECT-TYPE
    SYNTAX INTEGER 
    MAX-ACCESS read-write
    STATUS current
    DESCRIPTION
        "ap detect CoInterfThreshhderfNum bigger this param,them send trap."
    ::= { apAlarmParamConfigEntry 2 }
    
apAPNeiborInterfThreshhd   OBJECT-TYPE
    SYNTAX INTEGER 
    MAX-ACCESS read-write
    STATUS current
    DESCRIPTION
        "ap detect APNeiborInterf bigger this param,them send trap."
    ::= { apAlarmParamConfigEntry 3 }
 
 apCPUusageThreshhd   OBJECT-TYPE
    SYNTAX INTEGER 
    MAX-ACCESS read-write
    STATUS current
    DESCRIPTION
        "ap CPUusage bigger this param,them send trap."
    ::= { apAlarmParamConfigEntry 4 } 
  
apMemUsageThreshhd    OBJECT-TYPE
    SYNTAX INTEGER 
    MAX-ACCESS read-write
    STATUS current
    DESCRIPTION
        "ap Memory usage bigger this param,them send trap."
    ::= { apAlarmParamConfigEntry 5 } 
    
acUserExcepOfflineTimes    OBJECT-TYPE
    SYNTAX Counter32 
    MAX-ACCESS read-only
    STATUS current
    DESCRIPTION
        "user exception offline times."
    ::= { apAlarmParamConfigEntry 6 } 
    
acAuthReqTimes    OBJECT-TYPE
    SYNTAX Counter32 
    MAX-ACCESS read-only
    STATUS current
    DESCRIPTION
        "user auth request total times."
    ::= { apAlarmParamConfigEntry 7 } 
    
acAuthSuccessTimes    OBJECT-TYPE
    SYNTAX Counter32 
    MAX-ACCESS read-only
    STATUS current
    DESCRIPTION
        "user auth success times."
    ::= { apAlarmParamConfigEntry 8 } 
    
acAuthReqFailTimes    OBJECT-TYPE
    SYNTAX Counter32 
    MAX-ACCESS read-only
    STATUS current
    DESCRIPTION
        "user auth request fail times."
    ::= { apAlarmParamConfigEntry 9 }     
    
acDisconnectOnlineUsersCount    OBJECT-TYPE
    SYNTAX Counter32 
    MAX-ACCESS read-only
    STATUS current
    DESCRIPTION
        "user offline times."
    ::= { apAlarmParamConfigEntry 10 }  
    
acOnlineUserNum    OBJECT-TYPE
    SYNTAX Counter32 
    MAX-ACCESS read-only
    STATUS current
    DESCRIPTION
        "on-line user number."
    ::= { apAlarmParamConfigEntry 11 }  
    

--**************************************************
--* apAlarmParameterConfig ends * 
--**************************************************
--**************************************************
--* apVLANConfig starts * 
--**************************************************
apVLANConfigObjects        OBJECT IDENTIFIER  ::= { qtechFitApMibModule 9 } 
apVLANConfigTable  OBJECT-TYPE
    SYNTAX SEQUENCE OF ApVLANConfigTableEntry
    MAX-ACCESS not-accessible
    STATUS current
    DESCRIPTION
      "ap vlan config table."
    ::={ apVLANConfigObjects 1 }

apVLANConfigTableEntry OBJECT-TYPE
    SYNTAX  ApVLANConfigTableEntry
    MAX-ACCESS  not-accessible
    STATUS  current
    DESCRIPTION
        "ap vlan config table."
    INDEX   { ifIndex,qtechApgWlanId }
    ::= { apVLANConfigTable 1 }

ApVLANConfigTableEntry ::=
    SEQUENCE {
        apVLANID              INTEGER,
        apVlanCfgStatus				RowStatus
    }
    
apVLANID   OBJECT-TYPE
    SYNTAX INTEGER 
    MAX-ACCESS read-create
    STATUS current
    DESCRIPTION
        "ap Memory usage bigger this param,them send trap."
    ::= { apVLANConfigTableEntry 1 }   
    
apVlanCfgStatus   OBJECT-TYPE
    SYNTAX RowStatus 
    MAX-ACCESS read-create
    STATUS current
    DESCRIPTION
        "The status column used for creating and
         deleting instances of the columnar objects in the table."
    ::= { apVLANConfigTableEntry 2 }  
--**************************************************
--* apVLANConfig ends * 
--**************************************************  

--**************************************************
--* apAccessControl starts * 
--**************************************************
apAccessControl        OBJECT IDENTIFIER  ::= { qtechFitApMibModule 12 } 

--**************************************************
--* apTerminalPermitTable begins
--**************************************************
apTerminalPermitTable OBJECT-TYPE
    SYNTAX SEQUENCE OF ApTerminalPermitEntry
    MAX-ACCESS not-accessible
    STATUS current
    DESCRIPTION
        "Terminal white list"
    ::= { apAccessControl 1 }

apTerminalPermitEntry OBJECT-TYPE
    SYNTAX ApTerminalPermitEntry
    MAX-ACCESS not-accessible
    STATUS current
    DESCRIPTION
        "The entry of apTerminalPermitTable."
    INDEX
    { apWhiteListIndex }
    ::= { apTerminalPermitTable 1 }

ApTerminalPermitEntry ::=
    SEQUENCE {
        apWhiteListIndex	INTEGER,
        apPermitMAC             MacAddress,
        apWhiteListStatus	RowStatus
        } 
apWhiteListIndex OBJECT-TYPE               
    SYNTAX INTEGER               
    MAX-ACCESS read-only              
    STATUS current               
    DESCRIPTION               
        "The index of the table."               
    ::= { apTerminalPermitEntry 1 }   
apPermitMAC OBJECT-TYPE               
    SYNTAX MacAddress               
    MAX-ACCESS read-create              
    STATUS current               
    DESCRIPTION               
        "The permited MAC address."               
    ::= { apTerminalPermitEntry 2 } 
    
apWhiteListStatus OBJECT-TYPE               
    SYNTAX RowStatus               
    MAX-ACCESS read-create              
    STATUS current               
    DESCRIPTION               
        "The status column used for creating and
         deleting instances of the columnar objects in the table."               
    ::= { apTerminalPermitEntry 3 } 
    
    


--**************************************************
--* apTerminalPermitTable ends
--**************************************************


--**************************************************
--* apTerminalDeniedTable begins
--**************************************************
apTerminalDeniedTable OBJECT-TYPE
    SYNTAX SEQUENCE OF ApTerminalDeniedEntry
    MAX-ACCESS not-accessible
    STATUS current
    DESCRIPTION
        "Terminal black list"
    ::= { apAccessControl 2 }

apTerminalDeniedEntry OBJECT-TYPE
    SYNTAX ApTerminalDeniedEntry
    MAX-ACCESS not-accessible
    STATUS current
    DESCRIPTION
        "The entry of apTerminalDeniedTable."
    INDEX
    { apBlackListIndex }
    ::= { apTerminalDeniedTable 1 }

ApTerminalDeniedEntry ::=
    SEQUENCE {
        apBlackListIndex								INTEGER,
        apAttackDeviceMAC               MacAddress,
        apBlackListStatus		RowStatus
        } 
apBlackListIndex OBJECT-TYPE               
    SYNTAX INTEGER               
    MAX-ACCESS read-only              
    STATUS current               
    DESCRIPTION               
        "The index of the table."               
    ::= { apTerminalDeniedEntry 1 } 
      
apAttackDeviceMAC OBJECT-TYPE               
    SYNTAX MacAddress               
    MAX-ACCESS read-create              
    STATUS current               
    DESCRIPTION               
        "The Denied MAC address."               
    ::= { apTerminalDeniedEntry 2 } 
    
apBlackListStatus OBJECT-TYPE               
    SYNTAX RowStatus               
    MAX-ACCESS read-create              
    STATUS current               
    DESCRIPTION               
        "The status column used for creating and
         deleting instances of the columnar objects in the table."               
    ::= { apTerminalDeniedEntry 3 } 


--**************************************************
--* apTerminalDeniedTable ends
--**************************************************
--**************************************************
--* apTerminalBlackListTable begins
--**************************************************
apTerminalBlackListTable OBJECT-TYPE
    SYNTAX SEQUENCE OF ApTerminalBlackListEntry
    MAX-ACCESS not-accessible
    STATUS current
    DESCRIPTION
        "Terminal Black List Table"
    ::= { apAccessControl 3 }

apTerminalBlackListEntry OBJECT-TYPE
    SYNTAX ApTerminalBlackListEntry
    MAX-ACCESS not-accessible
    STATUS current
    DESCRIPTION
        "The entry of apTerminalBlackListTable."
    INDEX
    { apBlackListDeviceMAC }
    ::= { apTerminalBlackListTable 1 }

ApTerminalBlackListEntry ::=
    SEQUENCE {
        apBlackListDeviceMAC				MacAddress,
        apBlackListAddReason               	OCTET STRING,
        apBlackListDuration					TimeTicks
        } 
apBlackListDeviceMAC OBJECT-TYPE               
    SYNTAX MacAddress               
    MAX-ACCESS read-create              
    STATUS current               
    DESCRIPTION               
        "the Station Mac Address."               
    ::= { apTerminalBlackListEntry 1 } 
      
apBlackListAddReason OBJECT-TYPE               
    SYNTAX OCTET STRING            
    MAX-ACCESS read-only              
    STATUS current               
    DESCRIPTION               
        "the reason of adding, included static and dynamic."               
    ::= { apTerminalBlackListEntry 2 } 
    
apBlackListDuration OBJECT-TYPE               
    SYNTAX TimeTicks               
    MAX-ACCESS read-only              
    STATUS current               
    DESCRIPTION               
        "adding type: dynamic, the rest of time the record in list
         adding type: static, 0."               
    ::= { apTerminalBlackListEntry 3 } 


--**************************************************
--* apTerminalBlackListTable ends
--**************************************************

--**************************************************
--* apAccessControl ends * 
--**************************************************  

--**************************************************
--* acCapabilityStatistics begins * 
--**************************************************  

acCapabilityStatistics        OBJECT IDENTIFIER  ::= { qtechFitApMibModule 13 } 

acWirelessDownDropFrame OBJECT-TYPE
    SYNTAX Counter64 
    MAX-ACCESS read-only
    STATUS current
    DESCRIPTION
        "Total downlink droped frames of ac"
    ::= { acCapabilityStatistics 1 }
	
acWirelessDownRetryFrame OBJECT-TYPE
    SYNTAX Counter64 
    MAX-ACCESS read-only
    STATUS current
    DESCRIPTION
        "Total downlink retry frames of ac"
    ::= { acCapabilityStatistics 2 }

acWirelessDownFrame OBJECT-TYPE
    SYNTAX Counter64 
    MAX-ACCESS read-only
    STATUS current
    DESCRIPTION
        "Total downlink frames of ac"
    ::= { acCapabilityStatistics 3 }
	
acWirelessDownErrorFrame OBJECT-TYPE
    SYNTAX Counter64 
    MAX-ACCESS read-only
    STATUS current
    DESCRIPTION
        "Total downlink error frames of ac"
    ::= { acCapabilityStatistics 4 }
	
acWirelessUpFrame OBJECT-TYPE
    SYNTAX Counter64 
    MAX-ACCESS read-only
    STATUS current
    DESCRIPTION
        "Total uplink frames of ac"
    ::= { acCapabilityStatistics 5 }
	
acWirelessUpDropFrame OBJECT-TYPE
    SYNTAX Counter64 
    MAX-ACCESS read-only
    STATUS current
    DESCRIPTION
        "Total uplink droped frames of ac"
    ::= { acCapabilityStatistics 6 }
	
acWirelessUpRetryFrame OBJECT-TYPE
    SYNTAX Counter64 
    MAX-ACCESS read-only
    STATUS current
    DESCRIPTION
        "Total uplink retry frames of ac"
    ::= { acCapabilityStatistics 7 }
	
acWirelessUpRate OBJECT-TYPE
    SYNTAX Counter64 
    MAX-ACCESS read-only
    STATUS current
    DESCRIPTION
        "Total bit uplink rate of ac, unit: kbyte/s."
    ::= { acCapabilityStatistics 8 }
	
acWirelessDownRate OBJECT-TYPE
    SYNTAX Counter64 
    MAX-ACCESS read-only
    STATUS current
    DESCRIPTION
        "Total bit downlink rate of ac, unit: kbyte/s."
    ::= { acCapabilityStatistics 9 }


--**************************************************
--* acCapabilityStatistics ends * 
--**************************************************  

--**************************************************
--* apWidsInfoObjects begins * 
--**************************************************  
apWidsInfoObjects        OBJECT IDENTIFIER  ::= { qtechFitApMibModule 14 }

--**************************************************
--* apWidsIllegalApTable begins
--**************************************************

apWidsIllegalApTable OBJECT-TYPE
    SYNTAX SEQUENCE OF ApWidsIllegalApEntry
    MAX-ACCESS not-accessible
    STATUS current
    DESCRIPTION
        "Illegal ap table"
    ::= { apWidsInfoObjects 1 }

apWidsIllegalApEntry OBJECT-TYPE
    SYNTAX ApWidsIllegalApEntry
    MAX-ACCESS not-accessible
    STATUS current
    DESCRIPTION
        "The entry of apWidsIllegalApTable."
    INDEX
    { apIllegalApMac }
    ::= { apWidsIllegalApTable 1 }

ApWidsIllegalApEntry ::=
    SEQUENCE {
        apIllegalApMac					MacAddress,
        apIllegalApChannel              INTEGER,
        apIllegalApRSSI   		        INTEGER,
        apWorkingApMac                  MacAddress,
        apDetectAPBSSID                 MacAddress,
		apIllegalApType   		        INTEGER,
        apIllegalApSSID                 DisplayString
        } 
		
apIllegalApMac   OBJECT-TYPE
    SYNTAX      MacAddress
    MAX-ACCESS  read-only
    STATUS      current
    DESCRIPTION
        "illegal ap mac."
    ::= { apWidsIllegalApEntry 1 }   

apIllegalApChannel   OBJECT-TYPE
    SYNTAX      INTEGER
    MAX-ACCESS  read-only
    STATUS      current
    DESCRIPTION
        "illegal ap channel."
    ::= { apWidsIllegalApEntry 2 }  	
		
apIllegalApRSSI   OBJECT-TYPE
    SYNTAX      INTEGER
    MAX-ACCESS  read-only
    STATUS      current
    DESCRIPTION
        "illegal ap RSSI."
    ::= { apWidsIllegalApEntry 3 }  
	
apWorkingApMac   OBJECT-TYPE
    SYNTAX      MacAddress
    MAX-ACCESS  read-only
    STATUS      current
    DESCRIPTION
        "Working ap mac."
    ::= { apWidsIllegalApEntry 4 }  
	
apDetectAPBSSID   OBJECT-TYPE
    SYNTAX      MacAddress
    MAX-ACCESS  read-only
    STATUS      current
    DESCRIPTION
        "Working ap BSSID."
    ::= { apWidsIllegalApEntry 5 }  	
	
apIllegalApType   OBJECT-TYPE
    SYNTAX  INTEGER 
    MAX-ACCESS  read-only
    STATUS      current
    DESCRIPTION
        "illegal ap type  0:AP 1:adhoc."
    ::= { apWidsIllegalApEntry 6 } 
	
apIllegalApSSID   OBJECT-TYPE
    SYNTAX      DisplayString
    MAX-ACCESS  read-only
    STATUS      current
    DESCRIPTION
        "illegal ap SSID."
    ::= { apWidsIllegalApEntry 7 } 
	
--**************************************************
--* apWidsIllegalApTable ends
--**************************************************

--**************************************************
--* apWidsApCounterTable begins
--**************************************************
 
apWidsApCounterTable OBJECT-TYPE
    SYNTAX SEQUENCE OF ApWidsApCounterEntry
    MAX-ACCESS not-accessible
    STATUS current
    DESCRIPTION
        "Illegal ap table"
    ::= { apWidsInfoObjects 2 }

apWidsApCounterEntry OBJECT-TYPE
    SYNTAX ApWidsApCounterEntry
    MAX-ACCESS not-accessible
    STATUS current
    DESCRIPTION
        "The entry of apWidsApCounterTable."
    INDEX
    { apCounterMac }
    ::= { apWidsApCounterTable 1 }

ApWidsApCounterEntry ::=
    SEQUENCE {
        apCounterMac            MacAddress,
        apCounter               INTEGER,
        apCounterMode           INTEGER,
        apCounterRssiThreshold  INTEGER
    } 
		
apCounterMac   OBJECT-TYPE
    SYNTAX      MacAddress
    MAX-ACCESS  read-only
    STATUS      current
    DESCRIPTION
        "ap mac."
    ::= { apWidsApCounterEntry 1 } 

apCounter   OBJECT-TYPE
    SYNTAX      INTEGER
    MAX-ACCESS  read-write
    STATUS      current
    DESCRIPTION
        "ap counter."
    ::= { apWidsApCounterEntry 2}   

apCounterMode   OBJECT-TYPE
    SYNTAX  INTEGER   
    MAX-ACCESS  read-write
    STATUS      current
    DESCRIPTION
        "ap counter mdoe, supports a variety of combinations, 0x1:config  0x2:rouge  0x4:ssid  0x8:adhoc."
    ::= { apWidsApCounterEntry 3}  	
 
apCounterRssiThreshold   OBJECT-TYPE
    SYNTAX      INTEGER
    MAX-ACCESS  read-write
    STATUS      current
    DESCRIPTION
        "ap counter rssi."
    ::= { apWidsApCounterEntry 4} 
--**************************************************
--* apWidsIllegalApCounterTable ends
--**************************************************

apWidsDeviceMode OBJECT-TYPE
    SYNTAX INTEGER 
    MAX-ACCESS read-write
    STATUS current
    DESCRIPTION
        "set device mode for all ap, 0: normal, 1:mornitor, 2: hybrid"
    ::= { apWidsInfoObjects 3 }
	
apWidsCounterIllegalAp OBJECT-TYPE
    SYNTAX INTEGER 
    MAX-ACCESS read-write
    STATUS current
    DESCRIPTION
        "set device mode for all ap, 0: not counter, non-zero: counter"
    ::= { apWidsInfoObjects 4 }

apWidsCounterModeIllegalAp OBJECT-TYPE
    SYNTAX  INTEGER  
    MAX-ACCESS read-write
    STATUS current
    DESCRIPTION
        "ap counter mdoe, supports a variety of combinations, 0x1:config  0x2:rouge  0x4:ssid  0x8:adhoc."
    ::= { apWidsInfoObjects 5 }

apWidsDeviceModeFlag OBJECT-TYPE
    SYNTAX INTEGER 
    MAX-ACCESS read-only
    STATUS current
    DESCRIPTION
        "device mode flag, 0 for single ap config, 1 for all ap config. "
    ::= { apWidsInfoObjects 6 }

apWidsCounterIllegalApFlag OBJECT-TYPE
    SYNTAX INTEGER 
    MAX-ACCESS read-only
    STATUS current
    DESCRIPTION
        "device mode flag, 0 for single ap config, 1 for all ap config."
    ::= { apWidsInfoObjects 7 }
	
apWidsCounterModeIllegalApFlag OBJECT-TYPE
    SYNTAX  INTEGER 
    MAX-ACCESS read-only
    STATUS current
    DESCRIPTION
        "device mode flag, 0 for single ap config, 1 for all ap config."
    ::= { apWidsInfoObjects 8 }     

--**************************************************
--* apWidsPermitMacTable begins
--**************************************************	
apWidsPermitMacTable OBJECT-TYPE
    SYNTAX SEQUENCE OF ApWidsPermitMacEntry
    MAX-ACCESS not-accessible
    STATUS current
    DESCRIPTION
        "wids permit mac table"
    ::= { apWidsInfoObjects 9 }

apWidsPermitMacEntry OBJECT-TYPE
    SYNTAX ApWidsPermitMacEntry
    MAX-ACCESS not-accessible
    STATUS current
    DESCRIPTION
        "The entry of apWidsPermitMacTable."
    INDEX
    { apWidsPermitMac }
    ::= { apWidsPermitMacTable 1 }

ApWidsPermitMacEntry ::=
    SEQUENCE {
        apWidsPermitMac           MacAddress,
	    apPermitMacrowstatus      RowStatus
        } 

apWidsPermitMac   OBJECT-TYPE
    SYNTAX      MacAddress
    MAX-ACCESS  read-only
    STATUS      current
    DESCRIPTION
        "wids permit mac."
    ::= { apWidsPermitMacEntry 1 } 

apPermitMacrowstatus   OBJECT-TYPE
    SYNTAX      RowStatus
    MAX-ACCESS  read-create
    STATUS      current
    DESCRIPTION
        "wids permit mac table row status."
    ::= { apWidsPermitMacEntry 2 } 

--**************************************************
--* apWidsPermitMacTable ends
--**************************************************

--**************************************************
--* apWidsPermitSSIDTable begins
--**************************************************	
apWidsPermitSSIDTable OBJECT-TYPE
    SYNTAX SEQUENCE OF ApWidsPermitSSIDEntry
    MAX-ACCESS not-accessible
    STATUS current
    DESCRIPTION
        "wids permit ssid table"
    ::= { apWidsInfoObjects 10 }

apWidsPermitSSIDEntry OBJECT-TYPE
    SYNTAX ApWidsPermitSSIDEntry
    MAX-ACCESS not-accessible
    STATUS current
    DESCRIPTION
        "The entry of apWidsPermitSSIDTable."
    INDEX
    { apCounterSSID }
    ::= { apWidsPermitSSIDTable 1 }

ApWidsPermitSSIDEntry ::=
    SEQUENCE {
        apCounterSSID              DisplayString,
	    apPermitSSIDrowstatus      RowStatus
	} 

apCounterSSID   OBJECT-TYPE
    SYNTAX      DisplayString
    MAX-ACCESS  read-only
    STATUS      current
    DESCRIPTION
        "wids permit ssid."
    ::= { apWidsPermitSSIDEntry 1 } 

apPermitSSIDrowstatus   OBJECT-TYPE
    SYNTAX      RowStatus
    MAX-ACCESS  read-create
    STATUS      current
    DESCRIPTION
        "wids permit ssid table row status."
    ::= { apWidsPermitSSIDEntry 2 } 
--**************************************************
--* apWidsPermitSSIDTable ends
--**************************************************

--**************************************************
--* apWidsPermitVendorTable begins
--**************************************************	
apWidsPermitVendorTable OBJECT-TYPE
    SYNTAX SEQUENCE OF ApWidsPermitVendorEntry
    MAX-ACCESS not-accessible
    STATUS current
    DESCRIPTION
        "wids permit Vendor table"
    ::= { apWidsInfoObjects 11 }

apWidsPermitVendorEntry OBJECT-TYPE
    SYNTAX ApWidsPermitVendorEntry
    MAX-ACCESS not-accessible
    STATUS current
    DESCRIPTION
        "The entry of apWidsPermitVendorTable."
    INDEX
    { apCounterVendor }
    ::= { apWidsPermitVendorTable 1 }

ApWidsPermitVendorEntry ::=
    SEQUENCE {
        apCounterVendor              MacAddress,
	    apPermitVendorrowstatus      RowStatus
	} 

apCounterVendor   OBJECT-TYPE
    SYNTAX      MacAddress
    MAX-ACCESS  read-only
    STATUS      current
    DESCRIPTION
        "wids permit Vendor."
    ::= { apWidsPermitVendorEntry 1 } 

apPermitVendorrowstatus   OBJECT-TYPE
    SYNTAX      RowStatus
    MAX-ACCESS  read-create
    STATUS      current
    DESCRIPTION
        "wids permit vendor table row status."
    ::= { apWidsPermitVendorEntry 2 } 
--**************************************************
--* apWidsPermitVendorTable ends
--**************************************************



--**************************************************
--* apWidsStaticAttackTable begins
--**************************************************	
apWidsStaticAttackTable OBJECT-TYPE
    SYNTAX SEQUENCE OF ApWidsStaticAttackEntry
    MAX-ACCESS not-accessible
    STATUS current
    DESCRIPTION
        "wids static attack mac table"
    ::= { apWidsInfoObjects 12}

apWidsStaticAttackEntry OBJECT-TYPE
    SYNTAX ApWidsStaticAttackEntry
    MAX-ACCESS not-accessible
    STATUS current
    DESCRIPTION
        "The entry of apWidsStaticAttackTable."
    INDEX
    { apStaticAttackMac }
    ::= { apWidsStaticAttackTable 1 }

ApWidsStaticAttackEntry ::=
    SEQUENCE {
        apStaticAttackMac            MacAddress,
	    apStaticAttackrowstatus      RowStatus
        } 

apStaticAttackMac   OBJECT-TYPE
    SYNTAX      MacAddress
    MAX-ACCESS  read-only
    STATUS      current
    DESCRIPTION
        "wids static attack mac."
    ::= { apWidsStaticAttackEntry 1 } 

apStaticAttackrowstatus   OBJECT-TYPE
    SYNTAX      RowStatus
    MAX-ACCESS  read-create
    STATUS      current
    DESCRIPTION
        "wids static attack mac table row status."
    ::= { apWidsStaticAttackEntry 2 } 

--**************************************************
--* apWidsStaticAttackTable ends
--**************************************************	
 --**************************************************
--* apWidsNeighborApTable begins
--**************************************************	
apWidsNeighborApInfoTable OBJECT-TYPE
    SYNTAX SEQUENCE OF ApWidsNeighborApInfoEntry
    MAX-ACCESS not-accessible
    STATUS current
    DESCRIPTION
        "wids neighbor Aps' Infomation table"
    ::= { apWidsInfoObjects 13 }

apWidsNeighborApInfoEntry OBJECT-TYPE
    SYNTAX ApWidsNeighborApInfoEntry
    MAX-ACCESS not-accessible
    STATUS current
    DESCRIPTION
        "The entry of apWidsNeighborApInfoTable."
    INDEX { neighborApMac }
    ::= { apWidsNeighborApInfoTable 1 }

ApWidsNeighborApInfoEntry ::=
    SEQUENCE {
        neighborApMac           MacAddress,
	neighborApSSID          DisplayString,	
	neighborApRSSI      	INTEGER,
	neighborApChannel      	INTEGER,
	neighborApInControl	INTEGER
    }

    neighborApMac   OBJECT-TYPE
    SYNTAX MacAddress
    MAX-ACCESS read-only
    STATUS current
    DESCRIPTION
        "Neighbor Ap Mac Address ."
    ::= { apWidsNeighborApInfoEntry 1 }

    neighborApSSID   OBJECT-TYPE
    SYNTAX DisplayString
    MAX-ACCESS read-only
    STATUS current
    DESCRIPTION
        "Neighbor Ap Mac SSID ."
    ::= { apWidsNeighborApInfoEntry 2 }

    neighborApRSSI  OBJECT-TYPE
    SYNTAX INTEGER
    MAX-ACCESS read-only
    STATUS current
    DESCRIPTION
        "Neighbor Ap Mac  RSSI ."
    ::= { apWidsNeighborApInfoEntry 3 }

	neighborApChannel  OBJECT-TYPE
    SYNTAX INTEGER
    MAX-ACCESS read-only
    STATUS current
    DESCRIPTION
        "Neighbor Ap  Channel ."
    ::= { apWidsNeighborApInfoEntry 4 }

    neighborApInControl  OBJECT-TYPE
    SYNTAX INTEGER
    MAX-ACCESS read-only
    STATUS current
    DESCRIPTION
        "Is this Neighbor Ap under this Ac's control."
    ::= { apWidsNeighborApInfoEntry 5 }

    
apWidsClearIlleglApListFlag OBJECT-TYPE
    SYNTAX  TruthValue 
    MAX-ACCESS read-write
    STATUS current
    DESCRIPTION
        "set 1(TRUE) to clear Wids illagle."
    ::= { apWidsInfoObjects 14 }
    
apWidsFloodInterval OBJECT-TYPE
    SYNTAX  Unsigned32 
    MAX-ACCESS read-write
    STATUS current
    DESCRIPTION
        "WIDS flood detech Interval."
    ::= { apWidsInfoObjects 15 } 

apWidsBlackListThreshold OBJECT-TYPE
    SYNTAX  Unsigned32 
    MAX-ACCESS read-write
    STATUS current
    DESCRIPTION
        "WIDS Black List Threshold."
    ::= { apWidsInfoObjects 16 }
    
apWidsBlackListDuration 	OBJECT-TYPE
    SYNTAX  Unsigned32 
    MAX-ACCESS read-write
    STATUS current
    DESCRIPTION
        "WIDS Black List Duration."
    ::= { apWidsInfoObjects 17 }

apWidsFloodDetectOnOff 	OBJECT-TYPE
    SYNTAX  INTEGER  
    MAX-ACCESS read-write
    STATUS current
    DESCRIPTION
        "WIDS Flood Detect On or Off
        1: on
    	0: off."
    ::= { apWidsInfoObjects 18 } 

apWidsCounterRssiThreshold 	OBJECT-TYPE
    SYNTAX  INTEGER  
    MAX-ACCESS read-write
    STATUS current
    DESCRIPTION
        "Global wids counter rssi."
    ::= { apWidsInfoObjects 19 } 

--**************************************************
--* apWidsBlackSSIDTable begins
--**************************************************	
apWidsBlackSSIDTable OBJECT-TYPE
    SYNTAX SEQUENCE OF ApWidsBlackSSIDEntry
    MAX-ACCESS not-accessible
    STATUS current
    DESCRIPTION
        "wids black ssid table"
    ::= { apWidsInfoObjects 20 }

apWidsBlackSSIDEntry OBJECT-TYPE
    SYNTAX ApWidsBlackSSIDEntry
    MAX-ACCESS not-accessible
    STATUS current
    DESCRIPTION
        "The entry of apWidsBlackSSIDTable."
    INDEX
    { apBlackSSID }
    ::= { apWidsBlackSSIDTable 1 }

ApWidsBlackSSIDEntry ::=
    SEQUENCE {
        apBlackSSID              DisplayString,
        apBlackSSIDrowstatus     RowStatus
    } 

apBlackSSID   OBJECT-TYPE
    SYNTAX      DisplayString
    MAX-ACCESS  read-only
    STATUS      current
    DESCRIPTION
        "wids black ssid."
    ::= { apWidsBlackSSIDEntry 1 } 

apBlackSSIDrowstatus   OBJECT-TYPE
    SYNTAX      RowStatus
    MAX-ACCESS  read-create
    STATUS      current
    DESCRIPTION
        "wids black ssid table row status."
    ::= { apWidsBlackSSIDEntry 2 } 
--**************************************************
--* apWidsBlackSSIDTable ends
--**************************************************

--**************************************************
--* apWidsInfoObjects ends * 
--**************************************************  

  
--**************************************************
--* apConfigInfoObjects begins * 
--**************************************************  
apConfigInfoObjects        OBJECT IDENTIFIER  ::= { qtechFitApMibModule 15 }

--**************************************************
--* apConfigInfoTable begins
--**************************************************

apConfigInfoTable OBJECT-TYPE
    SYNTAX SEQUENCE OF ApConfigInfoEntry
    MAX-ACCESS not-accessible
    STATUS current
    DESCRIPTION
        "Ap config table"
    ::= { apConfigInfoObjects 1 }

apConfigInfoEntry OBJECT-TYPE
    SYNTAX ApConfigInfoEntry
    MAX-ACCESS not-accessible
    STATUS current
    DESCRIPTION
        "The entry of apConfigInfoTable."
    INDEX
    { apConfigInfoMac }
    ::= { apConfigInfoTable 1 }

ApConfigInfoEntry ::=
    SEQUENCE {
        apConfigInfoMac         MacAddress,
        apSpectralSwitch        INTEGER,
        apSpectralSupport       INTEGER,
        apSmartAntSupport       INTEGER,
        apSmartDisSupport       INTEGER,
        apAntdetectSupport      INTEGER,
        apAntdetectEnable       INTEGER,
        apAntdetectInterval     INTEGER,
        apAntdetectState        INTEGER
    } 
		
apConfigInfoMac   OBJECT-TYPE
    SYNTAX      MacAddress
    MAX-ACCESS  read-only
    STATUS      current
    DESCRIPTION
        "Ap mac."
    ::= { apConfigInfoEntry 1 }   

apSpectralSwitch   OBJECT-TYPE
    SYNTAX      INTEGER
    MAX-ACCESS  read-write
    STATUS      current
    DESCRIPTION
        "spectral switch, 0:closed 1:open."
    ::= { apConfigInfoEntry 2 }  	

apSpectralSupport   OBJECT-TYPE
    SYNTAX      INTEGER
    MAX-ACCESS  read-only
    STATUS      current
    DESCRIPTION
        "spectral support  0:not support  1:only support 2.4G  2:only support 5G  3:both support 2.4G/5G."
    ::= { apConfigInfoEntry 3 }

apSmartAntSupport   OBJECT-TYPE
    SYNTAX      INTEGER
    MAX-ACCESS  read-only
    STATUS      current
    DESCRIPTION
        "smartant support  0:not support  1:support."
    ::= { apConfigInfoEntry 4 }

apSmartDisSupport   OBJECT-TYPE
    SYNTAX      INTEGER
    MAX-ACCESS  read-only
    STATUS      current
    DESCRIPTION
        "smartdis support  0:not support  1:support."
    ::= { apConfigInfoEntry 5 }

apAntdetectSupport   OBJECT-TYPE
    SYNTAX      INTEGER
    MAX-ACCESS  read-only
    STATUS      current
    DESCRIPTION
        "Antenna detect support  0:not support  1:support."
    ::= { apConfigInfoEntry 6 }

apAntdetectEnable   OBJECT-TYPE
    SYNTAX      INTEGER
    MAX-ACCESS  read-write
    STATUS      current
    DESCRIPTION
        "antenna detect switch, 0:closed 1:open."
    ::= { apConfigInfoEntry 7 }

apAntdetectInterval   OBJECT-TYPE
    SYNTAX      INTEGER
    MAX-ACCESS  read-write
    STATUS      current
    DESCRIPTION
        "antenna detect interval, (1 - 10000) minutes "
    ::= { apConfigInfoEntry 8 }

apAntdetectState   OBJECT-TYPE
    SYNTAX      INTEGER
    MAX-ACCESS  read-only
    STATUS      current
    DESCRIPTION
        "antenna state, result of antenna detect, bitmask, 0:ok, 1:not"
    ::= { apConfigInfoEntry 9 }	

--**************************************************
--* apConfigInfoTable ends
--**************************************************

--**************************************************
--* apConfigInfoObjects ends * 
--**************************************************  


--**************************************************
--* apAntDetectObjects begins * 
--**************************************************  
apAntDetectObjects        OBJECT IDENTIFIER  ::= { qtechFitApMibModule 16 }


--**************************************************
--* apAntDetectTable begins
--**************************************************

apAntDetectTable OBJECT-TYPE
    SYNTAX SEQUENCE OF ApAntDetectEntry
    MAX-ACCESS not-accessible
    STATUS current
    DESCRIPTION
        "Ap ant detect table"
    ::= { apAntDetectObjects 1 }

apAntDetectEntry OBJECT-TYPE
    SYNTAX ApAntDetectEntry
    MAX-ACCESS not-accessible
    STATUS current
    DESCRIPTION
        "The entry of apAntDetectTable."
    INDEX
    { apAntDetectAPMac, apAntDetectAntIndex }
    ::= { apAntDetectTable 1 }

ApAntDetectEntry ::=
    SEQUENCE {
        apAntDetectAPMac        MacAddress,
        apAntDetectAntIndex     INTEGER,
        apAntDetectDesc         DisplayString,
        apAntDetectRadioId      DisplayString,
        apAntDetectStatus       INTEGER
    } 
		
apAntDetectAPMac   OBJECT-TYPE
    SYNTAX      MacAddress
    MAX-ACCESS  read-only
    STATUS      current
    DESCRIPTION
        "Ap mac."
    ::= { apAntDetectEntry 1 }   

apAntDetectAntIndex   OBJECT-TYPE
    SYNTAX      INTEGER
    MAX-ACCESS  read-only
    STATUS      current
    DESCRIPTION
        "ant index."
    ::= { apAntDetectEntry 2 }  	

apAntDetectDesc   OBJECT-TYPE
    SYNTAX      DisplayString
    MAX-ACCESS  read-only
    STATUS      current
    DESCRIPTION
        "ant description."
    ::= { apAntDetectEntry 3 }

apAntDetectRadioId   OBJECT-TYPE
    SYNTAX      DisplayString
    MAX-ACCESS  read-only
    STATUS      current
    DESCRIPTION
        "ant radioid."
    ::= { apAntDetectEntry 4 }

apAntDetectStatus   OBJECT-TYPE
    SYNTAX      INTEGER
    MAX-ACCESS  read-only
    STATUS      current
    DESCRIPTION
        "ant status."
    ::= { apAntDetectEntry 5 }

--**************************************************
--* apAntDetectTable ends
--**************************************************

--**************************************************
--* apAntDetectCfgTable begins
--**************************************************

apAntDetectCfgTable OBJECT-TYPE
    SYNTAX SEQUENCE OF ApAntDetectCfgEntry
    MAX-ACCESS not-accessible
    STATUS current
    DESCRIPTION
        "Ap ant detect cfg table"
    ::= { apAntDetectObjects 2 }

apAntDetectCfgEntry OBJECT-TYPE
    SYNTAX ApAntDetectCfgEntry
    MAX-ACCESS not-accessible
    STATUS current
    DESCRIPTION
        "The entry of apAntDetectCfgTable."
    INDEX
    { apAntDetectCfgAPMac }
    ::= { apAntDetectCfgTable 1 }

ApAntDetectCfgEntry ::=
    SEQUENCE {
        apAntDetectCfgAPMac     MacAddress,
        apAntDetectCfgSupport   INTEGER,
        apAntDetectCfgSwitch    INTEGER
    } 

apAntDetectCfgAPMac   OBJECT-TYPE
    SYNTAX      MacAddress
    MAX-ACCESS  read-only
    STATUS      current
    DESCRIPTION
        "Ap mac."
    ::= { apAntDetectCfgEntry 1 }   

apAntDetectCfgSupport   OBJECT-TYPE
    SYNTAX      INTEGER
    MAX-ACCESS  read-only
    STATUS      current
    DESCRIPTION
        "ant detect support."
    ::= { apAntDetectCfgEntry 2 }

apAntDetectCfgSwitch   OBJECT-TYPE
    SYNTAX      INTEGER
    MAX-ACCESS  read-write
    STATUS      current
    DESCRIPTION
        "ant detect switch."
    ::= { apAntDetectCfgEntry 3 }

--**************************************************
--* apAntDetectCfgTable ends
--**************************************************

--**************************************************
--* apAntDetectObjects ends * 
--**************************************************  


--**************************************************
--* apStatisticsInfoRead starts * 
--**************************************************
apStatisticsInfoReadObjects             OBJECT IDENTIFIER  ::= { qtechFitApMibModule 10 } 
apSysCapabilityStatisticsObjects        OBJECT IDENTIFIER  ::= { apStatisticsInfoReadObjects 1 } 
apLinkStatisticsObjects                 OBJECT IDENTIFIER  ::= { apStatisticsInfoReadObjects 2 }
apInterfaceRGMIIStatisticsObjects       OBJECT IDENTIFIER  ::= { apStatisticsInfoReadObjects 3 }
apInterfaceWireStatisticsObjects        OBJECT IDENTIFIER  ::= { apStatisticsInfoReadObjects 4 }
apSSIDStatisticsObjects                 OBJECT IDENTIFIER  ::= { apStatisticsInfoReadObjects 5 }
apWAPIStatisticsObjects                 OBJECT IDENTIFIER  ::= { apStatisticsInfoReadObjects 6 }
apStationStatisticsObjects              OBJECT IDENTIFIER  ::= { apStatisticsInfoReadObjects 7 }
apQOSStatisticsObjects                  OBJECT IDENTIFIER  ::= { apStatisticsInfoReadObjects 8 }
apQOSBaseStatisticsObjects              OBJECT IDENTIFIER  ::= { apQOSStatisticsObjects 1 }
apQOSBackgroundStatisticsObjects        OBJECT IDENTIFIER  ::= { apQOSStatisticsObjects 2 }
apQOSBestEffortStatisticsObjects        OBJECT IDENTIFIER  ::= { apQOSStatisticsObjects 3 }
apQOSVoiceStatisticsObjects             OBJECT IDENTIFIER  ::= { apQOSStatisticsObjects 4 }
apQOSVideoStatisticsObjects             OBJECT IDENTIFIER  ::= { apQOSStatisticsObjects 5 }
apWIDSRogueApInfoObjects                OBJECT IDENTIFIER  ::= { apStatisticsInfoReadObjects 9 } 


apSysCapabilityStatisticsTable OBJECT-TYPE
    SYNTAX SEQUENCE OF ApSysCapabilityStatisticsTableEntry
    MAX-ACCESS not-accessible
    STATUS current
    DESCRIPTION
      "ap system Capability Statistics info table."
    ::={ apSysCapabilityStatisticsObjects 1 }

apSysCapabilityStatisticsTableEntry OBJECT-TYPE
    SYNTAX  ApSysCapabilityStatisticsTableEntry
    MAX-ACCESS  not-accessible
    STATUS  current
    DESCRIPTION
        "ap system Capability Statistics info table."
    INDEX   { qtechApMacAddr }
    ::= { apSysCapabilityStatisticsTable 1 }

ApSysCapabilityStatisticsTableEntry ::=
    SEQUENCE {
        apCPURTUsage              INTEGER,
        apCPUAvgUsage             INTEGER,
        apMemRTUsage              INTEGER,
        apMemAvgUsage             INTEGER
    }
apCPURTUsage   OBJECT-TYPE
    SYNTAX INTEGER 
    MAX-ACCESS read-only
    STATUS current
    DESCRIPTION
        "ap CPU real time usage ."
    ::= { apSysCapabilityStatisticsTableEntry 1 }   
    
apCPUAvgUsage   OBJECT-TYPE
    SYNTAX INTEGER 
    MAX-ACCESS read-only
    STATUS current
    DESCRIPTION
        "ap CPU average usage ."
    ::= { apSysCapabilityStatisticsTableEntry 2 }  
    
apMemRTUsage   OBJECT-TYPE
    SYNTAX INTEGER 
    MAX-ACCESS read-only
    STATUS current
    DESCRIPTION
        "ap Memory real time usage ."
    ::= { apSysCapabilityStatisticsTableEntry 3 }   
    
apMemAvgUsage   OBJECT-TYPE
    SYNTAX INTEGER 
    MAX-ACCESS read-only
    STATUS current
    DESCRIPTION
        "ap Memory average usage ."
    ::= { apSysCapabilityStatisticsTableEntry 4 }    
    
--**************************************************
apLinkStatisticsTable OBJECT-TYPE
    SYNTAX SEQUENCE OF ApLinkStatisticsTableEntry
    MAX-ACCESS not-accessible
    STATUS current
    DESCRIPTION
      "ap Links Statistics info table."
    ::={ apLinkStatisticsObjects 1 }

apLinkStatisticsTableEntry OBJECT-TYPE
    SYNTAX  ApLinkStatisticsTableEntry
    MAX-ACCESS  not-accessible
    STATUS  current
    DESCRIPTION
        "ap Links Statistics info table."
    INDEX   { qtechApMacAddr }
    ::= { apLinkStatisticsTable 1 }

ApLinkStatisticsTableEntry ::=
    SEQUENCE {
        apStationAssocSum              							INTEGER,
        apStationOnlineSum             							INTEGER,
        apAssocTimes              		 							Counter32,
        apAssocFailTimes              						 	Counter32,
        apReassocTimes                 							Counter32,
        apPreAssCannotShiftDeassocFailSum						Counter32,		
        apApStatsDisassociated											Counter32,
        apAssocRejectSum														Counter32,
        apBSSNotSupportAssocFailSum									Counter32,
        apApAuthReqTimes                            Counter32,
        apApAuthSuccessTimes                        Counter32,
        acApAuthReqFailTimes                        Counter32,
        apReassocFailTimes													Counter32,
        apRSSILowAssocFailSum												Counter32,
		apUnknowReasonAssoFailSum						Counter32,
		apOut80211StandardAssocFailSum					Counter32,
		apAllStationsTotalUpTime			            INTEGER,
		apAssocRespTimes								Counter32,
		apAssocSuccTimes  								Counter32,
		apUserRadiusOnlineSum                        INTEGER,
		apAllUserOnlineTime			            	TimeTicks,
		apRadiusAuthTimes								Counter32,
		apRadiusAuthSuccTimes                           Counter32,
		apRadiusAuthFailTimes 					        Counter32
   }
apStationAssocSum   OBJECT-TYPE
    SYNTAX INTEGER 
    MAX-ACCESS read-only
    STATUS current
    DESCRIPTION
        "Station Assocate Sum."
    ::= { apLinkStatisticsTableEntry 1 }    

apStationOnlineSum   OBJECT-TYPE
    SYNTAX INTEGER 
    MAX-ACCESS read-only
    STATUS current
    DESCRIPTION
        "Station Online Sum."
    ::= { apLinkStatisticsTableEntry 2 }   
    
apAssocTimes     OBJECT-TYPE
    SYNTAX Counter32 
    MAX-ACCESS read-only
    STATUS current
    DESCRIPTION
        "Station Assocate times."
    ::= { apLinkStatisticsTableEntry 3 }   

apAssocFailTimes  OBJECT-TYPE
    SYNTAX Counter32 
    MAX-ACCESS read-only
    STATUS current
    DESCRIPTION
        "Station Assocate fail times."
    ::= { apLinkStatisticsTableEntry 4 }   

apReassocTimes    OBJECT-TYPE
    SYNTAX Counter32 
    MAX-ACCESS read-only
    STATUS current
    DESCRIPTION
        "Station reAssocate times."
    ::= { apLinkStatisticsTableEntry 5 }  
    
apPreAssCannotShiftDeassocFailSum    OBJECT-TYPE
    SYNTAX Counter32 
    MAX-ACCESS read-only
    STATUS current
    DESCRIPTION
        "."
    ::= { apLinkStatisticsTableEntry 6 }      
    
apApStatsDisassociated    OBJECT-TYPE
    SYNTAX Counter32 
    MAX-ACCESS read-only
    STATUS current
    DESCRIPTION
        "STA deassociation times"
    ::= { apLinkStatisticsTableEntry 7 }   
    
apAssocRejectSum    OBJECT-TYPE
    SYNTAX Counter32 
    MAX-ACCESS read-only
    STATUS current
    DESCRIPTION
        "Total association reject times."
    ::= { apLinkStatisticsTableEntry 8 } 
    
apBSSNotSupportAssocFailSum    OBJECT-TYPE
    SYNTAX Counter32 
    MAX-ACCESS read-only
    STATUS current
    DESCRIPTION
        "Total association fail times due to sta not support."
    ::= { apLinkStatisticsTableEntry 9 }     
    
apApAuthReqTimes OBJECT-TYPE                                                  
    SYNTAX Counter32                                                  
    MAX-ACCESS read-only                                                
    STATUS current                                                  
    DESCRIPTION                                                  
        "receive error packages."                                                  
    ::= { apLinkStatisticsTableEntry 10 }                                    
                                       
apApAuthSuccessTimes OBJECT-TYPE                                                  
    SYNTAX Counter32                                                  
    MAX-ACCESS read-only                                                
    STATUS current                                                  
    DESCRIPTION                                                  
        "receive error packages."                                                  
    ::= { apLinkStatisticsTableEntry 11 }                                    
                                       
acApAuthReqFailTimes    OBJECT-TYPE
    SYNTAX Counter32 
    MAX-ACCESS read-only
    STATUS current
    DESCRIPTION
        "user auth request fail times."
    ::= { apLinkStatisticsTableEntry 12 }     
    
apReassocFailTimes    OBJECT-TYPE
    SYNTAX Counter32 
    MAX-ACCESS read-only
    STATUS current
    DESCRIPTION
        "user reassociation fail times."
    ::= { apLinkStatisticsTableEntry 13 }  
    
apRSSILowAssocFailSum    OBJECT-TYPE
    SYNTAX Counter32 
    MAX-ACCESS read-only
    STATUS current
    DESCRIPTION
        "association fail times due to low rssi."
    ::= { apLinkStatisticsTableEntry 14 }    

apUnknowReasonAssoFailSum     OBJECT-TYPE
    SYNTAX Counter32 
    MAX-ACCESS read-only
    STATUS current
    DESCRIPTION
        "association fail times unkonw reason."
    ::= { apLinkStatisticsTableEntry 15 }    

apOut80211StandardAssocFailSum     OBJECT-TYPE
    SYNTAX Counter32 
    MAX-ACCESS read-only
    STATUS current
    DESCRIPTION
        "association fail times reason out of the 80211 standard defined."
    ::= { apLinkStatisticsTableEntry 16 }    

apAllStationsTotalUpTime	 OBJECT-TYPE
    SYNTAX INTEGER 
    MAX-ACCESS read-only
    STATUS current
    DESCRIPTION
        "all stations in ap total up time."
    ::= { apLinkStatisticsTableEntry 17 }    

apAssocRespTimes    OBJECT-TYPE
    SYNTAX Counter32 
    MAX-ACCESS read-only
    STATUS current
    DESCRIPTION
        "association response times."
    ::= { apLinkStatisticsTableEntry 18 }  
    
apAssocSuccTimes    OBJECT-TYPE
    SYNTAX Counter32 
    MAX-ACCESS read-only
    STATUS current
    DESCRIPTION
        "association success times."
    ::= { apLinkStatisticsTableEntry 19 }
    
apUserRadiusOnlineSum     OBJECT-TYPE
    SYNTAX INTEGER 
    MAX-ACCESS read-only
    STATUS current
    DESCRIPTION
        "Radius User Online Sum."
    ::= { apLinkStatisticsTableEntry 20 }

apAllUserOnlineTime     OBJECT-TYPE
    SYNTAX TimeTicks 
    MAX-ACCESS read-only
    STATUS current
    DESCRIPTION
        "Radius User Total Up Times."
    ::= { apLinkStatisticsTableEntry 21 }

apRadiusAuthTimes    OBJECT-TYPE
    SYNTAX Counter32 
    MAX-ACCESS read-only
    STATUS current
    DESCRIPTION
        "Radius Auth Times."
    ::= { apLinkStatisticsTableEntry 22 }
   
apRadiusAuthSuccTimes    OBJECT-TYPE
    SYNTAX Counter32 
    MAX-ACCESS read-only
    STATUS current
    DESCRIPTION
        "Radius Auth Success Times."
    ::= { apLinkStatisticsTableEntry 23 }
 
apRadiusAuthFailTimes    OBJECT-TYPE
    SYNTAX Counter32 
    MAX-ACCESS read-only
    STATUS current
    DESCRIPTION
        "Radius Auth Fail Times."
    ::= { apLinkStatisticsTableEntry 24 }	 
         
--****************************************    
apInterfaceRGMIIStatisticsTable OBJECT-TYPE
    SYNTAX SEQUENCE OF ApInterfaceRGMIIStatisticsTableEntry
    MAX-ACCESS not-accessible
    STATUS current
    DESCRIPTION
      "ap RGMII interface Statistics info table."
    ::={ apInterfaceRGMIIStatisticsObjects 1 }

apInterfaceRGMIIStatisticsTableEntry OBJECT-TYPE
    SYNTAX  ApInterfaceRGMIIStatisticsTableEntry
    MAX-ACCESS  not-accessible
    STATUS  current
    DESCRIPTION
        "ap RGMII interface Statistics info table."
    INDEX   { qtechApMacAddr ,apRGMIIIndex}
    ::= { apInterfaceRGMIIStatisticsTable 1 }

ApInterfaceRGMIIStatisticsTableEntry ::=
    SEQUENCE {
        apRGMIIIndex              INTEGER,
        apifInUcastPkts           Counter32,
        apifInNUcastPkts          Counter32,
        apifInOctets              Counter32,
        apifInDiscardPkts         Counter32,
        apifInErrors              Counter32,
        apifOutUcastPkts          Counter32,
        apifOutNUcastPkts         Counter32,
        apifOutOctets             Counter32,
        apifOutDiscardPkts        Counter32,
        apifOutErrors             Counter32,
        apifUpDwnTimes            Counter32
    } 
apRGMIIIndex  OBJECT-TYPE
    SYNTAX INTEGER 
    MAX-ACCESS not-accessible
    STATUS current
    DESCRIPTION
        "local RGMII index ."
    ::= { apInterfaceRGMIIStatisticsTableEntry 1 }   
    
apifInUcastPkts   OBJECT-TYPE
    SYNTAX Counter32 
    MAX-ACCESS read-only
    STATUS current
    DESCRIPTION
        " RGMII Receive Ucast packets ."
    ::= { apInterfaceRGMIIStatisticsTableEntry 2 } 
    
apifInNUcastPkts    OBJECT-TYPE
    SYNTAX Counter32 
    MAX-ACCESS read-only
    STATUS current
    DESCRIPTION
        " RGMII Receive broadcast packets ."
    ::= { apInterfaceRGMIIStatisticsTableEntry 3 }  
    
apifInOctets    OBJECT-TYPE
    SYNTAX Counter32 
    MAX-ACCESS read-only
    STATUS current
    DESCRIPTION
        " RGMII Receive  bytes ."
    ::= { apInterfaceRGMIIStatisticsTableEntry 4 } 
    
apifInDiscardPkts   OBJECT-TYPE
    SYNTAX Counter32 
    MAX-ACCESS read-only
    STATUS current
    DESCRIPTION
        " RGMII drop Receive  packets ."
    ::= { apInterfaceRGMIIStatisticsTableEntry 5 }   
    
apifInErrors      OBJECT-TYPE
    SYNTAX Counter32 
    MAX-ACCESS read-only
    STATUS current
    DESCRIPTION
        " RGMII error Receive packets ."
    ::= { apInterfaceRGMIIStatisticsTableEntry 6 }  
 
apifOutUcastPkts  OBJECT-TYPE
    SYNTAX Counter32 
    MAX-ACCESS read-only
    STATUS current
    DESCRIPTION
        " RGMII Send Ucast packets ."
    ::= { apInterfaceRGMIIStatisticsTableEntry 7 } 

apifOutNUcastPkts  OBJECT-TYPE
    SYNTAX Counter32 
    MAX-ACCESS read-only
    STATUS current
    DESCRIPTION
        " RGMII Send broadcast packets ."
    ::= { apInterfaceRGMIIStatisticsTableEntry 8 }    
    
apifOutOctets     OBJECT-TYPE
    SYNTAX Counter32 
    MAX-ACCESS read-only
    STATUS current
    DESCRIPTION
        " RGMII Send  bytes ."
    ::= { apInterfaceRGMIIStatisticsTableEntry 9 }   
    
apifOutDiscardPkts OBJECT-TYPE
    SYNTAX Counter32 
    MAX-ACCESS read-only
    STATUS current
    DESCRIPTION
        " RGMII drop Send  packets ."
    ::= { apInterfaceRGMIIStatisticsTableEntry 10 }  
    
apifOutErrors   OBJECT-TYPE
    SYNTAX Counter32 
    MAX-ACCESS read-only
    STATUS current
    DESCRIPTION
        " RGMII error Send packets ."
    ::= { apInterfaceRGMIIStatisticsTableEntry 11 }  
    
apifUpDwnTimes  OBJECT-TYPE
    SYNTAX Counter32 
    MAX-ACCESS read-only
    STATUS current
    DESCRIPTION
        " RGMII upDown Times ."
    ::= { apInterfaceRGMIIStatisticsTableEntry 12 }    
--*************************************************    
apInterfaceWireStatisticsTable OBJECT-TYPE
    SYNTAX SEQUENCE OF ApInterfaceWireStatisticsTableEntry
    MAX-ACCESS not-accessible
    STATUS current
    DESCRIPTION
      "ap wireless interface Statistics info table."
    ::={ apInterfaceWireStatisticsObjects 1 }

apInterfaceWireStatisticsTableEntry OBJECT-TYPE
    SYNTAX  ApInterfaceWireStatisticsTableEntry
    MAX-ACCESS  not-accessible
    STATUS  current
    DESCRIPTION
        "ap wireless interface Statistics info table."
    INDEX   { qtechApMacAddr ,qtechApCfgRadioId}
    ::= { apInterfaceWireStatisticsTable 1 }

ApInterfaceWireStatisticsTableEntry ::=
    SEQUENCE {
        apAvgRxSignalStrength          DisplayString,
        apHighestRxSignalStrength      DisplayString,
        apLowestRxSignalStrength       DisplayString,
        apWirelessUpdownTimes          Counter32,
        apChStatsNumStations           Counter32,
        apTxDataPkts                   Counter32,
        apRxDataPkts                   Counter32,
        apUplinkDataOctets             Counter64,
        apDwlinkDataOctets             Counter64,
        apChStatsDwlinkTotRetryPkts    Counter32,
        apChStatsPhyErrPkts            Counter32,
        apChStatsMacFcsErrPkts         Counter32,
        apChStatsMacMicErrPkts         Counter32,
        apChStatsMacDecryptErrPkts     Counter32,
        apChStatsTotalErrPkts          Counter32,
        apRxMgmtFrameCnt               Counter32,
        apRxCtrlFrameCnt               Counter32,
        apRxDataFrameCnt               Counter32,
        apTxMgmtFrameCnt               Counter32,
        apTxCtrlFrameCnt               Counter32,
        apTxDataFrameCnt               Counter32,
        apChStatsFrameErrorCnt	       Counter32,
        apRetryCnt                     Counter32,
        apCurTxPwr                     Integer32,
        apAPNeighborSSIDList           DisplayString,
        apChDownUnicastFrame           Counter32,
        apChDownNonUnicastFrame        Counter32,
        apChTxThroughput               Counter32,
        apChRxThroughput               Counter32,	
        apChTxDropPkts                 Counter32,
        apChRxDropPkts                 Counter32,
        apChTxErrorPkts                Counter32,
        apChRxErrorPkts                Counter32,
        apRxBytes                      Counter32,
        apRxPkts                       Counter32,
        apTxBytes                      Counter32,
        apTxPkts                       Counter32,
        apDownNonUnicastPkts           Counter32,
        apDownUnicastPkts              Counter32,
        apUpNonUnicastPkts             Counter32,
        apUpUnicastPkts	               Counter32,    
        apAssoFailUnknowReason         Counter32,
        apAssoFailOutofDot11           Counter32,
        apAssoTotalTime                Counter32,
        apAuthReqFailTimes             Counter32,
        apAuthReqTimes                 Counter32,
        apAuthSuccessTimes             Counter32,
        apReAssoFailTimes              Counter32,
        apMacTxCorrectFrameCnt	       Counter32,
        apMacRxCorrectFrameCnt 	       Counter32,
        apPktErrRate	               INTEGER,
        apTotalRxBytes                 Counter64,
        apTotalTxBytes                 Counter64,
        apTxErrorPkts                  Counter32,
        apTxDropPkts                   Counter32,
        apIfRadiusOnlineUserNum	       Counter32
    }   
       
apAvgRxSignalStrength  OBJECT-TYPE
    SYNTAX DisplayString 
    MAX-ACCESS read-only
    STATUS current
    DESCRIPTION
        "average Rx Signal Strength."
    ::= { apInterfaceWireStatisticsTableEntry 1 }  
    
apHighestRxSignalStrength   OBJECT-TYPE
    SYNTAX DisplayString 
    MAX-ACCESS read-only
    STATUS current
    DESCRIPTION
        "Highest Rx Signal Strength ."
    ::= { apInterfaceWireStatisticsTableEntry 2 }  

apLowestRxSignalStrength OBJECT-TYPE
    SYNTAX DisplayString 
    MAX-ACCESS read-only
    STATUS current
    DESCRIPTION
        "Lowest Rx Signal Strength ."
    ::= { apInterfaceWireStatisticsTableEntry 3 }   

apWirelessUpdownTimes    OBJECT-TYPE
    SYNTAX Counter32 
    MAX-ACCESS read-only
    STATUS current
    DESCRIPTION
        "Wireless  Updown Times ."
    ::= { apInterfaceWireStatisticsTableEntry 4 }  
    
apChStatsNumStations    OBJECT-TYPE
    SYNTAX Counter32 
    MAX-ACCESS read-only
    STATUS current
    DESCRIPTION
        "the number of statons used this channel."
    ::= { apInterfaceWireStatisticsTableEntry 5 }  
    
apTxDataPkts  OBJECT-TYPE
    SYNTAX Counter32 
    MAX-ACCESS read-only
    STATUS current
    DESCRIPTION
        "ap send Data Packets ."
    ::= { apInterfaceWireStatisticsTableEntry 6 }  
    
apRxDataPkts OBJECT-TYPE
    SYNTAX Counter32 
    MAX-ACCESS read-only
    STATUS current
    DESCRIPTION
        "ap Receive Data Packets ."
    ::= { apInterfaceWireStatisticsTableEntry 7 }   
    
apUplinkDataOctets   OBJECT-TYPE
    SYNTAX Counter64 
    MAX-ACCESS read-only
    STATUS current
    DESCRIPTION
        "ap Receive Data Bytes ."
    ::= { apInterfaceWireStatisticsTableEntry 8 }  
    
apDwlinkDataOctets    OBJECT-TYPE
    SYNTAX Counter64 
    MAX-ACCESS read-only
    STATUS current
    DESCRIPTION
        "ap Send Data Bytes ."
    ::= { apInterfaceWireStatisticsTableEntry 9 }     
    
apChStatsDwlinkTotRetryPkts   OBJECT-TYPE
    SYNTAX Counter32 
    MAX-ACCESS read-only
    STATUS current
    DESCRIPTION
        "ap Send  retry packets."
    ::= { apInterfaceWireStatisticsTableEntry 10 }  
    
apChStatsPhyErrPkts    OBJECT-TYPE
    SYNTAX Counter32 
    MAX-ACCESS read-only
    STATUS current
    DESCRIPTION
        "ap Receive phy error packets."
    ::= { apInterfaceWireStatisticsTableEntry 11 }  
    
apChStatsMacFcsErrPkts     OBJECT-TYPE
    SYNTAX Counter32 
    MAX-ACCESS read-only
    STATUS current
    DESCRIPTION
        "ap Receive MCS FCS error packets."
    ::= { apInterfaceWireStatisticsTableEntry 12 }  
    
apChStatsMacMicErrPkts    OBJECT-TYPE
    SYNTAX Counter32 
    MAX-ACCESS read-only
    STATUS current
    DESCRIPTION
        "ap Receive MCS MIC error packets."
    ::= { apInterfaceWireStatisticsTableEntry 13 } 

apChStatsMacDecryptErrPkts   OBJECT-TYPE
    SYNTAX Counter32 
    MAX-ACCESS read-only
    STATUS current
    DESCRIPTION
        "ap Receive MCS Decrypt error packets."
    ::= { apInterfaceWireStatisticsTableEntry 14 }  
    
apChStatsTotalErrPkts     OBJECT-TYPE
    SYNTAX Counter32 
    MAX-ACCESS read-only
    STATUS current
    DESCRIPTION
        "ap channel Receive all errort packets."
    ::= { apInterfaceWireStatisticsTableEntry 15 }  
    
apRxMgmtFrameCnt OBJECT-TYPE               
    SYNTAX Counter32               
    MAX-ACCESS read-only             
    STATUS current               
    DESCRIPTION               
        "Number of RX management frames."               
    ::= { apInterfaceWireStatisticsTableEntry 16 } 
    
apRxCtrlFrameCnt OBJECT-TYPE               
    SYNTAX Counter32               
    MAX-ACCESS read-only             
    STATUS current               
    DESCRIPTION               
        "Number of RX control frames."               
    ::= { apInterfaceWireStatisticsTableEntry 17 } 
    
apRxDataFrameCnt OBJECT-TYPE               
    SYNTAX Counter32               
    MAX-ACCESS read-only             
    STATUS current               
    DESCRIPTION               
        "Number of RX data frames."               
    ::= { apInterfaceWireStatisticsTableEntry 18 }     
    
apTxMgmtFrameCnt OBJECT-TYPE               
    SYNTAX Counter32               
    MAX-ACCESS read-only             
    STATUS current               
    DESCRIPTION               
        "Number of TX management frames."               
    ::= { apInterfaceWireStatisticsTableEntry 19 }     
        
apTxCtrlFrameCnt OBJECT-TYPE               
    SYNTAX Counter32               
    MAX-ACCESS read-only             
    STATUS current               
    DESCRIPTION               
        "Number of TX control frames."               
    ::= { apInterfaceWireStatisticsTableEntry 20 } 
    
apTxDataFrameCnt OBJECT-TYPE               
    SYNTAX Counter32               
    MAX-ACCESS read-only             
    STATUS current               
    DESCRIPTION               
        "Number of TX data frames."               
    ::= { apInterfaceWireStatisticsTableEntry 21 }     
   
 
apChStatsFrameErrorCnt OBJECT-TYPE               
    SYNTAX Counter32               
    MAX-ACCESS read-only             
    STATUS current               
    DESCRIPTION               
        "error frames."               
    ::= { apInterfaceWireStatisticsTableEntry 22 }  
    
apRetryCnt OBJECT-TYPE               
    SYNTAX Counter32               
    MAX-ACCESS read-only             
    STATUS current               
    DESCRIPTION               
        "retry count."               
    ::= { apInterfaceWireStatisticsTableEntry 23 }
    
apCurTxPwr OBJECT-TYPE               
    SYNTAX Integer32               
    MAX-ACCESS read-only             
    STATUS current               
    DESCRIPTION               
        "TX power of AP."               
    ::= { apInterfaceWireStatisticsTableEntry 24 }    
    
apAPNeighborSSIDList OBJECT-TYPE               
    SYNTAX DisplayString               
    MAX-ACCESS read-only             
    STATUS current               
    DESCRIPTION               
        "SSID list around AP."               
    ::= { apInterfaceWireStatisticsTableEntry 25 } 
    
apChDownUnicastFrame OBJECT-TYPE               
    SYNTAX Counter32               
    MAX-ACCESS read-only             
    STATUS current               
    DESCRIPTION               
        "down link uincast frame."               
    ::= { apInterfaceWireStatisticsTableEntry 26 }   
    
apChDownNonUnicastFrame OBJECT-TYPE               
    SYNTAX Counter32               
    MAX-ACCESS read-only             
    STATUS current               
    DESCRIPTION               
        "down link non-uincast frame."               
    ::= { apInterfaceWireStatisticsTableEntry 27 }  
    
apChTxThroughput OBJECT-TYPE               
    SYNTAX Counter32               
    MAX-ACCESS read-only             
    STATUS current               
    DESCRIPTION               
        "transmit throughput."               
    ::= { apInterfaceWireStatisticsTableEntry 28 }     
    
apChRxThroughput OBJECT-TYPE               
    SYNTAX Counter32               
    MAX-ACCESS read-only             
    STATUS current               
    DESCRIPTION               
        "receive throughput."               
    ::= { apInterfaceWireStatisticsTableEntry 29 }   
    
apChTxDropPkts OBJECT-TYPE               
    SYNTAX Counter32               
    MAX-ACCESS read-only             
    STATUS current               
    DESCRIPTION               
        "transmit drop packages."               
    ::= { apInterfaceWireStatisticsTableEntry 30 } 
    
apChRxDropPkts OBJECT-TYPE               
    SYNTAX Counter32               
    MAX-ACCESS read-only             
    STATUS current               
    DESCRIPTION               
        "receive drop packages."               
    ::= { apInterfaceWireStatisticsTableEntry 31 }
    
apChTxErrorPkts OBJECT-TYPE               
    SYNTAX Counter32               
    MAX-ACCESS read-only             
    STATUS current               
    DESCRIPTION               
        "transmit error packages."               
    ::= { apInterfaceWireStatisticsTableEntry 32 } 
    
apChRxErrorPkts OBJECT-TYPE               
    SYNTAX Counter32               
    MAX-ACCESS read-only             
    STATUS current               
    DESCRIPTION               
        "receive error packages."               
    ::= { apInterfaceWireStatisticsTableEntry 33 } 
    
apRxBytes OBJECT-TYPE               
    SYNTAX Counter32               
    MAX-ACCESS read-only             
    STATUS current               
    DESCRIPTION               
        "receive error packages."               
    ::= { apInterfaceWireStatisticsTableEntry 34 }    
    
apRxPkts OBJECT-TYPE               
    SYNTAX Counter32               
    MAX-ACCESS read-only             
    STATUS current               
    DESCRIPTION               
        "receive error packages."               
    ::= { apInterfaceWireStatisticsTableEntry 35 }    
    
apTxBytes OBJECT-TYPE               
    SYNTAX Counter32               
    MAX-ACCESS read-only             
    STATUS current               
    DESCRIPTION               
        "receive error packages."               
    ::= { apInterfaceWireStatisticsTableEntry 36 } 
    
apTxPkts OBJECT-TYPE               
    SYNTAX Counter32               
    MAX-ACCESS read-only             
    STATUS current               
    DESCRIPTION               
        "receive error packages."               
    ::= { apInterfaceWireStatisticsTableEntry 37 }     
    
apDownNonUnicastPkts OBJECT-TYPE               
    SYNTAX Counter32               
    MAX-ACCESS read-only             
    STATUS current               
    DESCRIPTION               
        "receive error packages."               
    ::= { apInterfaceWireStatisticsTableEntry 38 }  
    
apDownUnicastPkts OBJECT-TYPE               
    SYNTAX Counter32               
    MAX-ACCESS read-only             
    STATUS current               
    DESCRIPTION               
        "receive error packages."               
    ::= { apInterfaceWireStatisticsTableEntry 39 } 
    
apUpNonUnicastPkts OBJECT-TYPE               
    SYNTAX Counter32               
    MAX-ACCESS read-only             
    STATUS current               
    DESCRIPTION               
        "receive error packages."               
    ::= { apInterfaceWireStatisticsTableEntry 40 }   
    
apUpUnicastPkts OBJECT-TYPE               
    SYNTAX Counter32               
    MAX-ACCESS read-only             
    STATUS current               
    DESCRIPTION               
        "receive error packages."               
    ::= { apInterfaceWireStatisticsTableEntry 41 }  
    
apAssoFailUnknowReason OBJECT-TYPE               
    SYNTAX Counter32               
    MAX-ACCESS read-only             
    STATUS current               
    DESCRIPTION               
        "receive error packages."               
    ::= { apInterfaceWireStatisticsTableEntry 42 }  
    
apAssoFailOutofDot11 OBJECT-TYPE               
    SYNTAX Counter32               
    MAX-ACCESS read-only             
    STATUS current               
    DESCRIPTION               
        "receive error packages."               
    ::= { apInterfaceWireStatisticsTableEntry 43 }  
    
apAssoTotalTime OBJECT-TYPE               
    SYNTAX Counter32               
    MAX-ACCESS read-only             
    STATUS current               
    DESCRIPTION               
        "receive error packages."               
    ::= { apInterfaceWireStatisticsTableEntry 44 } 
    
apAuthReqFailTimes OBJECT-TYPE               
    SYNTAX Counter32               
    MAX-ACCESS read-only             
    STATUS current               
    DESCRIPTION               
        "receive error packages."               
    ::= { apInterfaceWireStatisticsTableEntry 45 } 
    
apAuthReqTimes OBJECT-TYPE               
    SYNTAX Counter32               
    MAX-ACCESS read-only             
    STATUS current               
    DESCRIPTION               
        "receive error packages."               
    ::= { apInterfaceWireStatisticsTableEntry 46 } 
    
apAuthSuccessTimes OBJECT-TYPE               
    SYNTAX Counter32               
    MAX-ACCESS read-only             
    STATUS current               
    DESCRIPTION               
        "receive error packages."               
    ::= { apInterfaceWireStatisticsTableEntry 47 } 
    
apReAssoFailTimes OBJECT-TYPE               
    SYNTAX Counter32               
    MAX-ACCESS read-only             
    STATUS current               
    DESCRIPTION               
        "receive error packages."               
    ::= { apInterfaceWireStatisticsTableEntry 48 }

apMacTxCorrectFrameCnt OBJECT-TYPE 
    SYNTAX Counter32 
    MAX-ACCESS read-only
    STATUS current
    DESCRIPTION
        "ap Send Correct Frame Count ."
    ::= { apInterfaceWireStatisticsTableEntry 49 }   

apMacRxCorrectFrameCnt OBJECT-TYPE 
    SYNTAX Counter32 
    MAX-ACCESS read-only
    STATUS current
    DESCRIPTION
        "ap Receive Correct Frame Count ."
    ::= { apInterfaceWireStatisticsTableEntry 50 } 

    
apPktErrRate OBJECT-TYPE               
    SYNTAX INTEGER               
    MAX-ACCESS read-only             
    STATUS current               
    DESCRIPTION               
        "ap Pkt err rate = pkt error rate."               
    ::= { apInterfaceWireStatisticsTableEntry 51 }  

apTotalRxBytes OBJECT-TYPE               
    SYNTAX Counter64               
    MAX-ACCESS read-only             
    STATUS current               
    DESCRIPTION               
        "ap rx bytes count64."               
    ::= { apInterfaceWireStatisticsTableEntry 52 }   
 
apTotalTxBytes OBJECT-TYPE               
    SYNTAX Counter64               
    MAX-ACCESS read-only             
    STATUS current               
    DESCRIPTION               
        "ap tx bytes count64."               
    ::= { apInterfaceWireStatisticsTableEntry 53 }

apTxErrorPkts OBJECT-TYPE               
    SYNTAX Counter32               
    MAX-ACCESS read-only             
    STATUS current               
    DESCRIPTION               
        "TX error packet for ap radio."               
    ::= { apInterfaceWireStatisticsTableEntry 54 }	
	
apTxDropPkts OBJECT-TYPE               
    SYNTAX Counter32               
    MAX-ACCESS read-only             
    STATUS current               
    DESCRIPTION               
        "TX drop packet for ap radio."               
    ::= { apInterfaceWireStatisticsTableEntry 55 } 
    
apIfRadiusOnlineUserNum OBJECT-TYPE               
    SYNTAX Counter32               
    MAX-ACCESS read-only             
    STATUS current               
    DESCRIPTION               
        "ap Interface Radius Online User Number."               
    ::= { apInterfaceWireStatisticsTableEntry 56 }
 	    
      				    
--*************************************************   
apSSIDStatisticsTable OBJECT-TYPE
    SYNTAX SEQUENCE OF ApSSIDStatisticsTableEntry
    MAX-ACCESS not-accessible
    STATUS current
    DESCRIPTION
      "ap SSID Statistics info table."
    ::={ apSSIDStatisticsObjects 1 }

apSSIDStatisticsTableEntry OBJECT-TYPE
    SYNTAX  ApSSIDStatisticsTableEntry
    MAX-ACCESS  not-accessible
    STATUS  current
    DESCRIPTION
        "ap SSID Statistics info table."
    INDEX   { apSSIDStatisticsAPMac, apSSIDStatisticsRadioId, apSSIDStatisticsWlanId }
    ::= { apSSIDStatisticsTable 1 }

ApSSIDStatisticsTableEntry ::=
    SEQUENCE {
        apSSIDStatisticsAPMac            MacAddress,
        apSSIDStatisticsRadioId          INTEGER,
        apSSIDStatisticsWlanId           INTEGER,
        apSSIDTxDataPkts                 Counter32,
        apSSIDRxDataPkts                 Counter32,
        apSSIDUplinkDataOctets           Counter64,
        apSSIDDwlinkDataOctets           Counter64,
        apSSIDChStatsDwlinkTotRetryPkts  Counter32,
        apSSIDApChStatsNumStations       Integer32,     
        apApChStatsOnlineSum		 	 INTEGER,
        apSSIDStatisticsName             DisplayString,   
        apSSIDMacTxPkts			 		Counter32,      
        apSSIDMacRxPkts			 		Counter32
}  
apSSIDStatisticsAPMac  OBJECT-TYPE
    SYNTAX MacAddress 
    MAX-ACCESS read-only
    STATUS current
    DESCRIPTION
        "ap mac."
    ::= { apSSIDStatisticsTableEntry 1 }   
    
apSSIDStatisticsRadioId   OBJECT-TYPE
    SYNTAX INTEGER 
    MAX-ACCESS read-only
    STATUS current
    DESCRIPTION
        "radio id ."
    ::= { apSSIDStatisticsTableEntry 2 } 
    
apSSIDStatisticsWlanId   OBJECT-TYPE
    SYNTAX INTEGER 
    MAX-ACCESS read-only
    STATUS current
    DESCRIPTION
        "wlan id ."
    ::= { apSSIDStatisticsTableEntry 3 }  
    
apSSIDTxDataPkts  OBJECT-TYPE
    SYNTAX Counter32 
    MAX-ACCESS read-only
    STATUS current
    DESCRIPTION
        "ap ssid Tx Data packets."
    ::= { apSSIDStatisticsTableEntry 4 }   
    
apSSIDRxDataPkts  OBJECT-TYPE
    SYNTAX Counter32 
    MAX-ACCESS read-only
    STATUS current
    DESCRIPTION
        "ap ssid Rx Data packets."
    ::= { apSSIDStatisticsTableEntry 5 } 
    
apSSIDUplinkDataOctets   OBJECT-TYPE
    SYNTAX Counter64 
    MAX-ACCESS read-only
    STATUS current
    DESCRIPTION
        "ap ssid Rx Link Data Bytes."
    ::= { apSSIDStatisticsTableEntry 6 }  
    
apSSIDDwlinkDataOctets  OBJECT-TYPE
    SYNTAX Counter64 
    MAX-ACCESS read-only
    STATUS current
    DESCRIPTION
        "ap ssid Tx Link Data Bytes."
    ::= { apSSIDStatisticsTableEntry 7 }    
    
apSSIDChStatsDwlinkTotRetryPkts  OBJECT-TYPE
    SYNTAX Counter32 
    MAX-ACCESS read-only
    STATUS current
    DESCRIPTION
        "ap downLink retry packets."
    ::= { apSSIDStatisticsTableEntry 8 }  
    
apSSIDApChStatsNumStations   OBJECT-TYPE
    SYNTAX Integer32 
    MAX-ACCESS read-only
    STATUS current
    DESCRIPTION
        "stations number current connet to this ssid ."
    ::= { apSSIDStatisticsTableEntry 9 }  
    
apApChStatsOnlineSum   OBJECT-TYPE
    SYNTAX INTEGER 
    MAX-ACCESS read-only
    STATUS current
    DESCRIPTION
        "stations number on line ."
    ::= { apSSIDStatisticsTableEntry 10 }  
apSSIDStatisticsName   OBJECT-TYPE
    SYNTAX DisplayString 
    MAX-ACCESS read-only
    STATUS current
    DESCRIPTION
        "SSID name ."
    ::= { apSSIDStatisticsTableEntry 11 }   
        
apSSIDMacTxPkts   OBJECT-TYPE
    SYNTAX Counter32 
    MAX-ACCESS read-only
    STATUS current
    DESCRIPTION
        "ssid mac transmit correct packet counte."
    ::= { apSSIDStatisticsTableEntry 12 }     
            
apSSIDMacRxPkts   OBJECT-TYPE
    SYNTAX Counter32 
    MAX-ACCESS read-only
    STATUS current
    DESCRIPTION
        "ssid mac receive correct packets counte."
    ::= { apSSIDStatisticsTableEntry 13 }  
         
--**************************************************    

--*************************************************   
apSSIDStatisticsNewTable OBJECT-TYPE
    SYNTAX SEQUENCE OF ApSSIDStatisticsNewTableEntry
    MAX-ACCESS not-accessible
    STATUS current
    DESCRIPTION
      "ap SSID Statistics info table."
    ::={ apSSIDStatisticsObjects 2 }

apSSIDStatisticsNewTableEntry OBJECT-TYPE
    SYNTAX  ApSSIDStatisticsNewTableEntry
    MAX-ACCESS  not-accessible
    STATUS  current
    DESCRIPTION
        "ap SSID Statistics info table."
    INDEX   { apSSIDStatisticsNewAPMac, apSSIDStatisticsNewRadioId, apSSIDStatisticsNewSSID }
    ::= { apSSIDStatisticsNewTable 1 }

ApSSIDStatisticsNewTableEntry ::=
    SEQUENCE {
        apSSIDStatisticsNewAPMac            MacAddress,
        apSSIDStatisticsNewRadioId          INTEGER,
        apSSIDStatisticsNewSSID             DisplayString,
        apSSIDNewTxDataPkts                 Counter32,
        apSSIDNewRxDataPkts                 Counter32,
        apSSIDNewUplinkDataOctets           Counter64,
        apSSIDNewDwlinkDataOctets           Counter64,
        apSSIDNewChStatsDwlinkTotRetryPkts  Counter32,
        apSSIDNewApChStatsNumStations       Integer32,     
        apApNewChStatsOnlineSum             INTEGER,
        apSSIDNewMacTxPkts                  Counter32,      
        apSSIDNewMacRxPkts                  Counter32
}  
apSSIDStatisticsNewAPMac  OBJECT-TYPE
    SYNTAX MacAddress 
    MAX-ACCESS read-only
    STATUS current
    DESCRIPTION
        "ap mac."
    ::= { apSSIDStatisticsNewTableEntry 1 }   
    
apSSIDStatisticsNewRadioId   OBJECT-TYPE
    SYNTAX INTEGER 
    MAX-ACCESS read-only
    STATUS current
    DESCRIPTION
        "radio id ."
    ::= { apSSIDStatisticsNewTableEntry 2 } 
    
apSSIDStatisticsNewSSID   OBJECT-TYPE
    SYNTAX DisplayString 
    MAX-ACCESS read-only
    STATUS current
    DESCRIPTION
        "wlan id ."
    ::= { apSSIDStatisticsNewTableEntry 3 }  
    
apSSIDNewTxDataPkts  OBJECT-TYPE
    SYNTAX Counter32 
    MAX-ACCESS read-only
    STATUS current
    DESCRIPTION
        "ap ssid Tx Data packets."
    ::= { apSSIDStatisticsNewTableEntry 4 }   
    
apSSIDNewRxDataPkts  OBJECT-TYPE
    SYNTAX Counter32 
    MAX-ACCESS read-only
    STATUS current
    DESCRIPTION
        "ap ssid Rx Data packets."
    ::= { apSSIDStatisticsNewTableEntry 5 } 
    
apSSIDNewUplinkDataOctets   OBJECT-TYPE
    SYNTAX Counter64 
    MAX-ACCESS read-only
    STATUS current
    DESCRIPTION
        "ap ssid Rx Link Data Bytes."
    ::= { apSSIDStatisticsNewTableEntry 6 }  
    
apSSIDNewDwlinkDataOctets  OBJECT-TYPE
    SYNTAX Counter64 
    MAX-ACCESS read-only
    STATUS current
    DESCRIPTION
        "ap ssid Tx Link Data Bytes."
    ::= { apSSIDStatisticsNewTableEntry 7 }    
    
apSSIDNewChStatsDwlinkTotRetryPkts  OBJECT-TYPE
    SYNTAX Counter32 
    MAX-ACCESS read-only
    STATUS current
    DESCRIPTION
        "ap downLink retry packets."
    ::= { apSSIDStatisticsNewTableEntry 8 }  
    
apSSIDNewApChStatsNumStations   OBJECT-TYPE
    SYNTAX Integer32 
    MAX-ACCESS read-only
    STATUS current
    DESCRIPTION
        "stations number current connet to this ssid ."
    ::= { apSSIDStatisticsNewTableEntry 9 }  
    
apApNewChStatsOnlineSum   OBJECT-TYPE
    SYNTAX INTEGER 
    MAX-ACCESS read-only
    STATUS current
    DESCRIPTION
        "stations number on line ."
    ::= { apSSIDStatisticsNewTableEntry 10 }  
        
apSSIDNewMacTxPkts   OBJECT-TYPE
    SYNTAX Counter32 
    MAX-ACCESS read-only
    STATUS current
    DESCRIPTION
        "ssid mac transmit correct packet counte."
    ::= { apSSIDStatisticsNewTableEntry 11 }     
            
apSSIDNewMacRxPkts   OBJECT-TYPE
    SYNTAX Counter32 
    MAX-ACCESS read-only
    STATUS current
    DESCRIPTION
        "ssid mac receive correct packets counte."
    ::= { apSSIDStatisticsNewTableEntry 12 }  
         
--**************************************************    

apStationStatisticsTable OBJECT-TYPE
    SYNTAX SEQUENCE OF ApStationStatisticsTableEntry
    MAX-ACCESS not-accessible
    STATUS current
    DESCRIPTION
      "ap Stations Statistics info table."
    ::={ apStationStatisticsObjects 1 }

apStationStatisticsTableEntry OBJECT-TYPE
    SYNTAX  ApStationStatisticsTableEntry
    MAX-ACCESS  not-accessible
    STATUS  current
    DESCRIPTION
        "ap Stations Statistics info table."
    INDEX   { qtechStaMacAddr }
    ::= { apStationStatisticsTable 1 }

ApStationStatisticsTableEntry ::=
    SEQUENCE {
        apStaAddress                   MacAddress,
        apStaUpTime                    TimeTicks,
        apReceivedStaSignalStrength    DisplayString,
        apAPReceiveStaSNR              DisplayString,
        apStaTxPkts                    Counter32,
        apStaTxBytes                   Counter64,
        apStaRxPkts                    Counter32,
        apStaRxBytes                   Counter64,
        apWAPISTAAddress               MacAddress,
        apWAPIVersion                  Integer32,
        apStaLinkSpeed                 Integer32,
        apStaUpRate                    Integer32,
        apStaDownRate                  Integer32,
        apStaTxThroughput              Counter32,  
        apStaRxThroughput              Counter32,
        apStaRxRetryBytes              Counter64
 }  
    
apStaAddress   OBJECT-TYPE
    SYNTAX MacAddress 
    MAX-ACCESS read-only
    STATUS current
    DESCRIPTION
        "station Mac addr."
    ::= { apStationStatisticsTableEntry 1 }   
    
apStaUpTime    OBJECT-TYPE
    SYNTAX TimeTicks 
    MAX-ACCESS read-only
    STATUS current
    DESCRIPTION
        "station connect to AP seconds."
    ::= { apStationStatisticsTableEntry 2 }  
    
apReceivedStaSignalStrength  OBJECT-TYPE
    SYNTAX DisplayString
    MAX-ACCESS read-only
    STATUS current
    DESCRIPTION
        "station current single strength."
    ::= { apStationStatisticsTableEntry 3 }  

apAPReceiveStaSNR  OBJECT-TYPE
    SYNTAX DisplayString
    MAX-ACCESS read-only
    STATUS current
    DESCRIPTION
        "SNR"
    ::= { apStationStatisticsTableEntry 4 }     
    
    
apStaTxPkts  OBJECT-TYPE
    SYNTAX Counter32 
    MAX-ACCESS read-only
    STATUS current
    DESCRIPTION
        "station Tx Packets."
    ::= { apStationStatisticsTableEntry 5 }  
    
apStaTxBytes   OBJECT-TYPE
    SYNTAX Counter64 
    MAX-ACCESS read-only
    STATUS current
    DESCRIPTION
        "station Tx Bytess."
    ::= { apStationStatisticsTableEntry 6 }  
    
apStaRxPkts  OBJECT-TYPE
    SYNTAX Counter32 
    MAX-ACCESS read-only
    STATUS current
    DESCRIPTION
        "station Rx Packets."
    ::= { apStationStatisticsTableEntry 7 }  
    
apStaRxBytes   OBJECT-TYPE
    SYNTAX Counter64 
    MAX-ACCESS read-only
    STATUS current
    DESCRIPTION
        "station Rx Bytess."
    ::= { apStationStatisticsTableEntry 8 }   
    
apWAPISTAAddress OBJECT-TYPE
    SYNTAX MacAddress 
    MAX-ACCESS read-only
    STATUS current
    DESCRIPTION
        "wapi station mac address."
    ::= { apStationStatisticsTableEntry 9 }   
    
apWAPIVersion  OBJECT-TYPE
    SYNTAX Integer32 
    MAX-ACCESS read-only
    STATUS current
    DESCRIPTION
        "wapi version."
    ::= { apStationStatisticsTableEntry 10 }   
    
apStaLinkSpeed  OBJECT-TYPE
    SYNTAX Integer32 
    MAX-ACCESS read-only
    STATUS current
    DESCRIPTION
        "STA link speed."
    ::= { apStationStatisticsTableEntry 11 }     

apStaUpRate  OBJECT-TYPE
    SYNTAX Integer32 
    MAX-ACCESS read-only
    STATUS current
    DESCRIPTION
        "STA uplink rate."
    ::= { apStationStatisticsTableEntry 12 }    
    
apStaDownRate  OBJECT-TYPE
    SYNTAX Integer32 
    MAX-ACCESS read-only
    STATUS current
    DESCRIPTION
        "STA downlink rate."
    ::= { apStationStatisticsTableEntry 13 }    
    
apStaTxThroughput   OBJECT-TYPE
    SYNTAX Counter32 
    MAX-ACCESS read-only
    STATUS current
    DESCRIPTION
        "station transmit throughput during associated time."
    ::= { apStationStatisticsTableEntry 14 }
    
apStaRxThroughput   OBJECT-TYPE
    SYNTAX Counter32 
    MAX-ACCESS read-only
    STATUS current
    DESCRIPTION
        "station receive throughput during associated time."
    ::= { apStationStatisticsTableEntry 15 }       
       
apStaRxRetryBytes   OBJECT-TYPE
    SYNTAX Counter64 
    MAX-ACCESS read-only
    STATUS current
    DESCRIPTION
        "station Rx retry Bytes."
    ::= { apStationStatisticsTableEntry 16 } 

--**************************************************      
apWAPIStatisticsTable OBJECT-TYPE
    SYNTAX SEQUENCE OF ApWAPIStatisticsTableEntry
    MAX-ACCESS not-accessible
    STATUS current
    DESCRIPTION
      "ap Stations Statistics info table."
    ::={ apWAPIStatisticsObjects 1 }

apWAPIStatisticsTableEntry OBJECT-TYPE
    SYNTAX  ApWAPIStatisticsTableEntry
    MAX-ACCESS  not-accessible
    STATUS  current
    DESCRIPTION
        "ap Stations Statistics info table."
    INDEX   { qtechApgWlanId }
    ::= { apWAPIStatisticsTable 1 }

ApWAPIStatisticsTableEntry ::=
    SEQUENCE {
        apWAPIControlledPortStatus         TruthValue,
        apWAPISelectedUnicastCipher        OCTET STRING,
        apWPIReplayCounters                Counter32,
        apWPIDecryptableErrors             Counter32,
        apWPIMICErrors                     Counter32,
        apWAISignatureErrors               Counter32,
        apWAIHMACErrors                    Counter32,
        apWAIAuthResultFailures            Counter32,
        apWAIDiscardCounters               Counter32,
        apWAITimeoutCounters               Counter32,
        apWAIFormatErrors                  Counter32,
        apWAICertificateHandshakeFailures  Counter32,
        apWAIUnicastHandshakeFailures      Counter32,
        apWAIMulticastHandshakeFailures    Counter32
    }   
    
    
apWAPIControlledPortStatus OBJECT-TYPE
    SYNTAX TruthValue 
    MAX-ACCESS read-only
    STATUS current
    DESCRIPTION
        "wapi Controlled Port Status."
    ::= { apWAPIStatisticsTableEntry 1 }     
    
apWAPISelectedUnicastCipher  OBJECT-TYPE
    SYNTAX OCTET STRING 
    MAX-ACCESS read-only
    STATUS current
    DESCRIPTION
        "wapi Selected Unicast Cipher."
    ::= { apWAPIStatisticsTableEntry 2 }   
    
apWPIReplayCounters   OBJECT-TYPE
    SYNTAX Counter32 
    MAX-ACCESS read-only
    STATUS current
    DESCRIPTION
        "wapi Replay drop MPDU packets."
    ::= { apWAPIStatisticsTableEntry 3 }  
    
apWPIDecryptableErrors  OBJECT-TYPE
    SYNTAX Counter32 
    MAX-ACCESS read-only
    STATUS current
    DESCRIPTION
        "wapi Decryptable Errors drop MPDU packets."
    ::= { apWAPIStatisticsTableEntry 4 } 
    
apWPIMICErrors   OBJECT-TYPE
    SYNTAX Counter32 
    MAX-ACCESS read-only
    STATUS current
    DESCRIPTION
        "wapi MIC Check Errors drop MPDU packets."
    ::= { apWAPIStatisticsTableEntry 5 }  
    
apWAISignatureErrors   OBJECT-TYPE
    SYNTAX Counter32 
    MAX-ACCESS read-only
    STATUS current
    DESCRIPTION
        "wai Signature errors packets."
    ::= { apWAPIStatisticsTableEntry 6 } 
 
apWAIHMACErrors   OBJECT-TYPE
    SYNTAX Counter32 
    MAX-ACCESS read-only
    STATUS current
    DESCRIPTION
        "WAIHMAC errors packets."
    ::= { apWAPIStatisticsTableEntry 7 }   
    
apWAIAuthResultFailures   OBJECT-TYPE
    SYNTAX Counter32 
    MAX-ACCESS read-only
    STATUS current
    DESCRIPTION
        "WAPI AuthResultFailures packets."
    ::= { apWAPIStatisticsTableEntry 8 }  
    
apWAIDiscardCounters    OBJECT-TYPE
    SYNTAX Counter32 
    MAX-ACCESS read-only
    STATUS current
    DESCRIPTION
        "WAPI Discard packets."
    ::= { apWAPIStatisticsTableEntry 9 }   
    
apWAITimeoutCounters   OBJECT-TYPE
    SYNTAX Counter32 
    MAX-ACCESS read-only
    STATUS current
    DESCRIPTION
        "WAPI Timeout drop packets."
    ::= { apWAPIStatisticsTableEntry 10 }   
    
apWAIFormatErrors   OBJECT-TYPE
    SYNTAX Counter32
    MAX-ACCESS read-only
    STATUS current
    DESCRIPTION
        "WAPI Format Errors drop packets."
    ::= { apWAPIStatisticsTableEntry 11 } 
    
apWAICertificateHandshakeFailures  OBJECT-TYPE
    SYNTAX Counter32
    MAX-ACCESS read-only
    STATUS current
    DESCRIPTION
        "WAPI Certificate Handshake Failures counts."
    ::= { apWAPIStatisticsTableEntry 12 } 
    
apWAIUnicastHandshakeFailures  OBJECT-TYPE
    SYNTAX Counter32
    MAX-ACCESS read-only
    STATUS current
    DESCRIPTION
        "WAPI Unicast Handshake Failures counts."
    ::= { apWAPIStatisticsTableEntry 13 }  
    
apWAIMulticastHandshakeFailures OBJECT-TYPE
    SYNTAX Counter32
    MAX-ACCESS read-only
    STATUS current
    DESCRIPTION
        "WAPI Multicast Handshake Failures counts."
    ::= { apWAPIStatisticsTableEntry 14 }   
--**************************************************
--* ap  QOS Statistics Info get Starts * 
--**************************************************    
apQOSBaseStatisticsTable OBJECT-TYPE
    SYNTAX SEQUENCE OF ApQOSBaseStatisticsTableEntry
    MAX-ACCESS not-accessible
    STATUS current
    DESCRIPTION
      "ap Base QOS Statistics info table."
    ::={ apQOSBaseStatisticsObjects 1 }

apQOSBaseStatisticsTableEntry OBJECT-TYPE
    SYNTAX  ApQOSBaseStatisticsTableEntry
    MAX-ACCESS  not-accessible
    STATUS  current
    DESCRIPTION
        "ap Base QOS Statistics info table."
    INDEX   { qtechApMacAddr, qtechApCfgRadioId }
    ::= { apQOSBaseStatisticsTable 1 }

ApQOSBaseStatisticsTableEntry ::=
    SEQUENCE {
        apBaseQoSSvcQueAvgLen         INTEGER,
        apBaseQoSSvcPktLossRatio      INTEGER,
        apBaseAvgTransSpeed           INTEGER
    }
    
apBaseQoSSvcQueAvgLen   OBJECT-TYPE
    SYNTAX INTEGER 
    MAX-ACCESS read-only
    STATUS current
    DESCRIPTION
        "AP QOS Queue average len."
    ::= { apQOSBaseStatisticsTableEntry 1 }  
    
apBaseQoSSvcPktLossRatio   OBJECT-TYPE
    SYNTAX INTEGER 
    MAX-ACCESS read-only
    STATUS current
    DESCRIPTION
        "AP QOS packets loss Ratio."
    ::= { apQOSBaseStatisticsTableEntry 2 }   
    
apBaseAvgTransSpeed   OBJECT-TYPE
    SYNTAX INTEGER 
    MAX-ACCESS read-only
    STATUS current
    DESCRIPTION
        "AP QOS average TX speed."
    ::= { apQOSBaseStatisticsTableEntry 3 }    
---------------------------------------------------
---------------------------------------------------
apQOSBackgroundStatisticsTable OBJECT-TYPE
    SYNTAX SEQUENCE OF ApQOSBackgroundStatisticsTableEntry
    MAX-ACCESS not-accessible
    STATUS current
    DESCRIPTION
      "ap Background QOS Statistics info table."
    ::={ apQOSBackgroundStatisticsObjects 1 }

apQOSBackgroundStatisticsTableEntry OBJECT-TYPE
    SYNTAX  ApQOSBackgroundStatisticsTableEntry
    MAX-ACCESS  not-accessible
    STATUS  current
    DESCRIPTION
        "ap Background QOS Statistics info table."
    INDEX   { qtechApMacAddr, qtechApCfgRadioId }
    ::= { apQOSBackgroundStatisticsTable 1 }

ApQOSBackgroundStatisticsTableEntry ::=
    SEQUENCE {
        apQOSBgQueAvgLen         INTEGER,
        apQOSBgAvgBurst          INTEGER,
        apQOSBgPktLossRatio      INTEGER,
        apQOSBgAvgTransSpeed     INTEGER,
        apQOSBgSvcLoss           INTEGER
    }
    
apQOSBgQueAvgLen   OBJECT-TYPE
    SYNTAX INTEGER 
    MAX-ACCESS read-only
    STATUS current
    DESCRIPTION
        "AP QOS Background  Queue average len."
    ::= { apQOSBackgroundStatisticsTableEntry 1 }  
    
apQOSBgAvgBurst    OBJECT-TYPE
    SYNTAX INTEGER 
    MAX-ACCESS read-only
    STATUS current
    DESCRIPTION
        "AP QOS Background  average burst ratio."
    ::= { apQOSBackgroundStatisticsTableEntry 2 }  
    
apQOSBgPktLossRatio OBJECT-TYPE
    SYNTAX INTEGER 
    MAX-ACCESS read-only
    STATUS current
    DESCRIPTION
        "AP QOS Background  packet loss ratio."
    ::= { apQOSBackgroundStatisticsTableEntry 3 }     
    
apQOSBgAvgTransSpeed    OBJECT-TYPE
    SYNTAX INTEGER 
    MAX-ACCESS read-only
    STATUS current
    DESCRIPTION
        "AP QOS Background  average TX speed."
    ::= { apQOSBackgroundStatisticsTableEntry 4 }     
    
apQOSBgSvcLoss    OBJECT-TYPE
    SYNTAX INTEGER 
    MAX-ACCESS read-only
    STATUS current
    DESCRIPTION
        "AP QOS Background  rob loss ratio.s"
    ::= { apQOSBackgroundStatisticsTableEntry 5 }            
-------------------------------------------------
-------------------------------------------------
apQOSBestEffortStatisticsTable OBJECT-TYPE
    SYNTAX SEQUENCE OF ApQOSBestEffortStatisticsTableEntry
    MAX-ACCESS not-accessible
    STATUS current
    DESCRIPTION
      "ap BestEffort QOS Statistics info table."
    ::={ apQOSBestEffortStatisticsObjects 1 }

apQOSBestEffortStatisticsTableEntry OBJECT-TYPE
    SYNTAX  ApQOSBestEffortStatisticsTableEntry
    MAX-ACCESS  not-accessible
    STATUS  current
    DESCRIPTION
        "ap BestEffort QOS Statistics info table."
    INDEX   { qtechApMacAddr, qtechApCfgRadioId }
    ::= { apQOSBestEffortStatisticsTable 1 }

ApQOSBestEffortStatisticsTableEntry ::=
    SEQUENCE {
        apQOSBeQueAvgLen         INTEGER,
        apQOSBeAvgBurst          INTEGER,
        apQOSBePktLossRatio      INTEGER,
        apQOSBeAvgTransSpeed     INTEGER,
        apQOSBeSvcLoss           INTEGER
    }
    
apQOSBeQueAvgLen   OBJECT-TYPE
    SYNTAX INTEGER 
    MAX-ACCESS read-only
    STATUS current
    DESCRIPTION
        "AP QOS BestEffort  Queue average len."
    ::= { apQOSBestEffortStatisticsTableEntry 1 }  
    
apQOSBeAvgBurst    OBJECT-TYPE
    SYNTAX INTEGER 
    MAX-ACCESS read-only
    STATUS current
    DESCRIPTION
        "AP QOS BestEffort  average burst ratio."
    ::= { apQOSBestEffortStatisticsTableEntry 2 }  
    
apQOSBePktLossRatio OBJECT-TYPE
    SYNTAX INTEGER 
    MAX-ACCESS read-only
    STATUS current
    DESCRIPTION
        "AP QOS BestEffort  packet loss ratio."
    ::= { apQOSBestEffortStatisticsTableEntry 3 }     
    
apQOSBeAvgTransSpeed    OBJECT-TYPE
    SYNTAX INTEGER 
    MAX-ACCESS read-only
    STATUS current
    DESCRIPTION
        "AP QOS BestEffort  average TX speed."
    ::= { apQOSBestEffortStatisticsTableEntry 4 }     
    
apQOSBeSvcLoss    OBJECT-TYPE
    SYNTAX INTEGER 
    MAX-ACCESS read-only
    STATUS current
    DESCRIPTION
        "AP QOS BestEffort  rob loss ratio."
    ::= { apQOSBestEffortStatisticsTableEntry 5 }            
-------------------------------------------------
-------------------------------------------------         
apQOSVoiceStatisticsTable OBJECT-TYPE
    SYNTAX SEQUENCE OF ApQOSVoiceStatisticsTableEntry
    MAX-ACCESS not-accessible
    STATUS current
    DESCRIPTION
      "ap voice QOS Statistics info table."
    ::={ apQOSVoiceStatisticsObjects 1 }

apQOSVoiceStatisticsTableEntry OBJECT-TYPE
    SYNTAX  ApQOSVoiceStatisticsTableEntry
    MAX-ACCESS  not-accessible
    STATUS  current
    DESCRIPTION
        "ap vioce QOS Statistics info table."
    INDEX   { qtechApMacAddr, qtechApCfgRadioId }
    ::= { apQOSVoiceStatisticsTable 1 }

ApQOSVoiceStatisticsTableEntry ::=
    SEQUENCE {
        apQOSVoiceQueAvgLen             INTEGER,
        apQOSVoiceAvgBurst              INTEGER,
        apQOSVoicePktLossRatio          INTEGER,
        apQOSVoiceAvgTransSpeed         INTEGER,
        apQOSVoicePutThroughRatio       INTEGER,
        apQOSVoiceDropRatio             INTEGER,
        apQOSVoiceSvcLoss               INTEGER,
        apQOSVoiceExceedMaxUsersRequest Counter32
    }   

apQOSVoiceQueAvgLen OBJECT-TYPE
    SYNTAX INTEGER 
    MAX-ACCESS read-only
    STATUS current
    DESCRIPTION
        "AP QOS voice queue average length"
    ::= { apQOSVoiceStatisticsTableEntry 1 }  
    
apQOSVoiceAvgBurst  OBJECT-TYPE
    SYNTAX INTEGER 
    MAX-ACCESS read-only
    STATUS current
    DESCRIPTION
        "AP QOS voice average burst ratio"
    ::= { apQOSVoiceStatisticsTableEntry 2 }   
    
apQOSVoicePktLossRatio OBJECT-TYPE
    SYNTAX INTEGER 
    MAX-ACCESS read-only
    STATUS current
    DESCRIPTION
        "AP QOS voice packets loss ratio"
    ::= { apQOSVoiceStatisticsTableEntry 3 } 
    
apQOSVoiceAvgTransSpeed  OBJECT-TYPE
    SYNTAX INTEGER 
    MAX-ACCESS read-only
    STATUS current
    DESCRIPTION
        "AP QOS voice average TX speed"
    ::= { apQOSVoiceStatisticsTableEntry 4 }    
    
apQOSVoicePutThroughRatio OBJECT-TYPE
    SYNTAX INTEGER 
    MAX-ACCESS read-only
    STATUS current
    DESCRIPTION
        "AP QOS voice PutThrough Ratio"
    ::= { apQOSVoiceStatisticsTableEntry 5 }      
    
apQOSVoiceDropRatio     OBJECT-TYPE
    SYNTAX INTEGER 
    MAX-ACCESS read-only
    STATUS current
    DESCRIPTION
        "AP QOS voice Drop Ratio"
    ::= { apQOSVoiceStatisticsTableEntry 6 }   
    
apQOSVoiceSvcLoss    OBJECT-TYPE
    SYNTAX INTEGER 
    MAX-ACCESS read-only
    STATUS current
    DESCRIPTION
        "AP QOS voice rob loss ratio"
    ::= { apQOSVoiceStatisticsTableEntry 7 }  
    
apQOSVoiceExceedMaxUsersRequest   OBJECT-TYPE
    SYNTAX Counter32 
    MAX-ACCESS read-only
    STATUS current
    DESCRIPTION
        "AP QOS decline counts of Voice user Exceed Max Users"
    ::= { apQOSVoiceStatisticsTableEntry 8 }               
--------------------------------------------------
--------------------------------------------------             
apQOSVideoStatisticsTable OBJECT-TYPE
    SYNTAX SEQUENCE OF ApQOSVideoStatisticsTableEntry
    MAX-ACCESS not-accessible
    STATUS current
    DESCRIPTION
      "ap Video QOS Statistics info table."
    ::={ apQOSVideoStatisticsObjects 1 }

apQOSVideoStatisticsTableEntry OBJECT-TYPE
    SYNTAX  ApQOSVideoStatisticsTableEntry
    MAX-ACCESS  not-accessible
    STATUS  current
    DESCRIPTION
        "ap Video QOS Statistics info table."
    INDEX   { qtechApMacAddr, qtechApCfgRadioId }
    ::= { apQOSVideoStatisticsTable 1 }

ApQOSVideoStatisticsTableEntry ::=
    SEQUENCE {
        apQOSVideoQueAvgLen             INTEGER,
        apQOSVideoAvgBurst              INTEGER,
        apQOSVideoPktLossRatio          INTEGER,
        apQOSVideoAvgTransSpeed         INTEGER,
        apQOSVideoPutThroughRatio       INTEGER,
        apQOSVideoDropRatio             INTEGER,
        apQOSVideoSvcLoss               INTEGER,
        apQOSVideoExceedMaxUsersRequest Counter32
    }   

apQOSVideoQueAvgLen OBJECT-TYPE
    SYNTAX INTEGER 
    MAX-ACCESS read-only
    STATUS current
    DESCRIPTION
        "AP QOS Video queue average length"
    ::= { apQOSVideoStatisticsTableEntry 1 }  
    
apQOSVideoAvgBurst  OBJECT-TYPE
    SYNTAX INTEGER 
    MAX-ACCESS read-only
    STATUS current
    DESCRIPTION
        "AP QOS Video average burst ratio"
    ::= { apQOSVideoStatisticsTableEntry 2 }   
    
apQOSVideoPktLossRatio OBJECT-TYPE
    SYNTAX INTEGER 
    MAX-ACCESS read-only
    STATUS current
    DESCRIPTION
        "AP QOS Video packets loss ratio"
    ::= { apQOSVideoStatisticsTableEntry 3 } 
    
apQOSVideoAvgTransSpeed  OBJECT-TYPE
    SYNTAX INTEGER 
    MAX-ACCESS read-only
    STATUS current
    DESCRIPTION
        "AP QOS Video average TX speed"
    ::= { apQOSVideoStatisticsTableEntry 4 }    
    
apQOSVideoPutThroughRatio OBJECT-TYPE
    SYNTAX INTEGER 
    MAX-ACCESS read-only
    STATUS current
    DESCRIPTION
        "AP QOS Video PutThrough Ratio"
    ::= { apQOSVideoStatisticsTableEntry 5 } 
    
apQOSVideoDropRatio     OBJECT-TYPE
    SYNTAX INTEGER 
    MAX-ACCESS read-only
    STATUS current
    DESCRIPTION
        "AP QOS Video Drop Ratio"
    ::= { apQOSVideoStatisticsTableEntry 6 }   
    
apQOSVideoSvcLoss    OBJECT-TYPE
    SYNTAX INTEGER 
    MAX-ACCESS read-only
    STATUS current
    DESCRIPTION
        "AP QOS Video rob loss ratio"
    ::= { apQOSVideoStatisticsTableEntry 7 }  
    
apQOSVideoExceedMaxUsersRequest   OBJECT-TYPE
    SYNTAX Counter32 
    MAX-ACCESS read-only
    STATUS current
    DESCRIPTION
        "AP QOS decline counts of Voice user Exceed Max Users"
    ::= { apQOSVideoStatisticsTableEntry 8 }                
--**************************************************
--* ap  QOS Statistics Info get ends * 
--************************************************** 

apWIDSRogueApInfoTable OBJECT-TYPE
    SYNTAX SEQUENCE OF ApWIDSRogueApInfoTableEntry
    MAX-ACCESS not-accessible
    STATUS current
    DESCRIPTION
      "Rogue ap info."              
    ::={ apWIDSRogueApInfoObjects 1 }   
    
apWIDSRogueApInfoTableEntry OBJECT-TYPE
    SYNTAX  ApWIDSRogueApInfoTableEntry
    MAX-ACCESS  not-accessible
    STATUS  current
    DESCRIPTION
        "ap WIDS Rogue Ap info table."
    INDEX   { qtechRogueApMacAddr }
    ::= { apWIDSRogueApInfoTable 1 }


ApWIDSRogueApInfoTableEntry ::=
    SEQUENCE {
        qtechRogueApMacAddr            MacAddress,
        qtechRogueApRSSI               INTEGER           
    }
    
qtechRogueApMacAddr OBJECT-TYPE    
SYNTAX MacAddress 
    MAX-ACCESS read-only
    STATUS current
    DESCRIPTION
        " Rogue Ap mac"
    ::= { apWIDSRogueApInfoTableEntry 1 }
    
qtechRogueApRSSI OBJECT-TYPE    
SYNTAX INTEGER 
    MAX-ACCESS read-only
    STATUS current
    DESCRIPTION
        " Rogue Ap RSSI"
    ::= { apWIDSRogueApInfoTableEntry 2 }
------------------------------------------------- 
-------------------------------------------------                                           
END

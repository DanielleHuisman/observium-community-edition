-- *****************************************************************
-- QTECH-WLAN-WLOG-MIB.mib:  Qtech WLAN WLOG MIB file
--
-- October 2012, jiangweifeng
-- 
-- Copyright (c) 2012 by Qtech Networks Co.,Ltd.
-- All rights reserved.
-- *****************************************************************


QTECH-WLAN-WLOG-MIB DEFINITIONS ::= BEGIN

IMPORTS
    MODULE-IDENTITY, 
    OBJECT-TYPE,
    Integer32,
    IpAddress
        FROM SNMPv2-SMI
    MacAddress,
    DisplayString
        FROM SNMPv2-TC
    InetAddress,
    InetAddressType
        FROM INET-ADDRESS-MIB
    qtechMgmt
        FROM QTECH-SMI;

qtechWlanWlogMIB MODULE-IDENTITY
    LAST-UPDATED "201210100000Z"
    ORGANIZATION "Qtech Networks Co.,Ltd."
    CONTACT-INFO
            " 
            Tel: 4008-111-000 
                
            E-mail: service@qtech.com.cn"
    DESCRIPTION
            "This module defines wlan wlog mibs."
    REVISION  "201210100000Z"
    DESCRIPTION
            "Initial version of this mib."
    ::= { qtechMgmt 118 }

-- ******** define the notify nodes ***************
qtechWlanWlogNotificationsMIBObjects OBJECT IDENTIFIER      ::= { qtechWlanWlogMIB 1 }
qtechWlanWlogNtfObjects       OBJECT IDENTIFIER ::= { qtechWlanWlogNotificationsMIBObjects 1 }
qtechWlanWlogNotifications     OBJECT IDENTIFIER ::= { qtechWlanWlogNotificationsMIBObjects 2 }

-- ****************************************
--
--               Notifications Objects
--
-- ****************************************
qtechWlogNotifyApName OBJECT-TYPE
    SYNTAX      DisplayString
    MAX-ACCESS  accessible-for-notify
    STATUS      current
    DESCRIPTION
        "Represents the name of a WTP."
    ::= { qtechWlanWlogNtfObjects 1 }

qtechWlogNotifyApMac OBJECT-TYPE
    SYNTAX      MacAddress
    MAX-ACCESS  accessible-for-notify
    STATUS      current
    DESCRIPTION
        "Represents the unique identifier of a WTP."
    ::= { qtechWlanWlogNtfObjects 2 }

qtechWlogNotifyApIp OBJECT-TYPE
    SYNTAX      InetAddress
    MAX-ACCESS  accessible-for-notify
    STATUS      current
    DESCRIPTION
        "Represents the Ip address of a WTP."
    ::= { qtechWlanWlogNtfObjects 3 }

qtechWlogNotifyApCwDownId OBJECT-TYPE
    SYNTAX      INTEGER
    MAX-ACCESS  accessible-for-notify
    STATUS      current
    DESCRIPTION
        "Represents the identification for a WTP's capwap down incident."
    ::= { qtechWlanWlogNtfObjects 4 }

qtechWlogNotifyApCwDownReason OBJECT-TYPE
    SYNTAX      DisplayString
    MAX-ACCESS  accessible-for-notify
    STATUS      current
    DESCRIPTION
        "Represents the reason for a WTP's capwap down."
    ::= { qtechWlanWlogNtfObjects 5 }

-- **** define AP ethernet interface statistics table ****
qtechWlogNotifyApIntfStatTable OBJECT-TYPE
    SYNTAX      SEQUENCE OF QtechWlogNotifyApIntfStatEntry
    MAX-ACCESS  accessible-for-notify
    STATUS      current
    DESCRIPTION
        "Represents the ethernet interface statistics table of a WTP."
    ::= { qtechWlanWlogNtfObjects 6 }

qtechWlogNotifyApIntfStatEntry OBJECT-TYPE
    SYNTAX      QtechWlogNotifyApIntfStatEntry
    MAX-ACCESS  accessible-for-notify
    STATUS      current
    DESCRIPTION
        "Represents the WTP ethernet interface statistics table Entry."
    INDEX   { qtechWlogNotifyApIntfName}
    ::= { qtechWlogNotifyApIntfStatTable 1 }

QtechWlogNotifyApIntfStatEntry ::=
    SEQUENCE {
        qtechWlogNotifyApIntfName                    DisplayString,
        qtechWlogNotifyApIntfInputRate               INTEGER,
        qtechWlogNotifyApIntfOutputRate              INTEGER,
        qtechWlogNotifyApIntfUnicastInputPkts        INTEGER,
        qtechWlogNotifyApIntfUnicastOutputPkts       INTEGER,
        qtechWlogNotifyApIntfMulticastInputPkts      INTEGER,
        qtechWlogNotifyApIntfMulticastOutputPkts     INTEGER,
        qtechWlogNotifyApIntfBroadcastInputPkts      INTEGER,
        qtechWlogNotifyApIntfBroadcastOutputPkts     INTEGER,
        qtechWlogNotifyApIntfErrorInputPkts          INTEGER,
        qtechWlogNotifyApIntfErrorOutputPkts         INTEGER
     }

qtechWlogNotifyApIntfName OBJECT-TYPE
    SYNTAX      DisplayString
    MAX-ACCESS  accessible-for-notify
    STATUS      current
    DESCRIPTION
        "Represents the name of a interface of a WTP."
    ::= { qtechWlogNotifyApIntfStatEntry 1 }

qtechWlogNotifyApIntfInputRate OBJECT-TYPE
    SYNTAX      INTEGER
    MAX-ACCESS  accessible-for-notify
    STATUS      current
    DESCRIPTION
        "AP's ethernet interface's input rate(Kbps) in 5 mins."
    ::= { qtechWlogNotifyApIntfStatEntry 2 }

qtechWlogNotifyApIntfOutputRate OBJECT-TYPE
    SYNTAX      INTEGER
    MAX-ACCESS  accessible-for-notify
    STATUS      current
    DESCRIPTION
        "AP's ethernet interface's output rate(Kbps) in 5 mins."
    ::= { qtechWlogNotifyApIntfStatEntry 3 }

qtechWlogNotifyApIntfUnicastInputPkts OBJECT-TYPE
    SYNTAX      INTEGER
    MAX-ACCESS  accessible-for-notify
    STATUS      current
    DESCRIPTION
        "AP's ethernet interface's unicast input packets."
    ::= { qtechWlogNotifyApIntfStatEntry 4 }

qtechWlogNotifyApIntfUnicastOutputPkts OBJECT-TYPE
    SYNTAX      INTEGER
    MAX-ACCESS  accessible-for-notify
    STATUS      current
    DESCRIPTION
        "AP's ethernet interface's unicast output packets."
    ::= { qtechWlogNotifyApIntfStatEntry 5 }

qtechWlogNotifyApIntfMulticastInputPkts OBJECT-TYPE
    SYNTAX      INTEGER
    MAX-ACCESS  accessible-for-notify
    STATUS      current
    DESCRIPTION
        "AP's ethernet interface's multicast input packets."
    ::= { qtechWlogNotifyApIntfStatEntry 6 }

qtechWlogNotifyApIntfMulticastOutputPkts OBJECT-TYPE
    SYNTAX      INTEGER
    MAX-ACCESS  accessible-for-notify
    STATUS      current
    DESCRIPTION
        "AP's ethernet interface's multicast output packets."
    ::= { qtechWlogNotifyApIntfStatEntry 7 }

qtechWlogNotifyApIntfBroadcastInputPkts OBJECT-TYPE
    SYNTAX      INTEGER
    MAX-ACCESS  accessible-for-notify
    STATUS      current
    DESCRIPTION
        "AP's ethernet interface's broadcast input packets."
    ::= { qtechWlogNotifyApIntfStatEntry 8 }

qtechWlogNotifyApIntfBroadcastOutputPkts OBJECT-TYPE
    SYNTAX      INTEGER
    MAX-ACCESS  accessible-for-notify
    STATUS      current
    DESCRIPTION
        "AP's ethernet interface's broadcast output packets."
    ::= { qtechWlogNotifyApIntfStatEntry 9 }

qtechWlogNotifyApIntfErrorInputPkts OBJECT-TYPE
    SYNTAX      INTEGER
    MAX-ACCESS  accessible-for-notify
    STATUS      current
    DESCRIPTION
        "AP's ethernet interface's error input packets."
    ::= { qtechWlogNotifyApIntfStatEntry 10 }

qtechWlogNotifyApIntfErrorOutputPkts OBJECT-TYPE
    SYNTAX      INTEGER
    MAX-ACCESS  accessible-for-notify
    STATUS      current
    DESCRIPTION
        "AP's ethernet interface's error output packets."
    ::= { qtechWlogNotifyApIntfStatEntry 11 }

-- **** define AP's radio statistics table ****
qtechWlogNotifyApRadioStatTable OBJECT-TYPE
    SYNTAX      SEQUENCE OF QtechWlogNotifyApRadioStatEntry
    MAX-ACCESS  accessible-for-notify
    STATUS      current
    DESCRIPTION
        "Represents the radio statistics table of a WTP."
    ::= { qtechWlanWlogNtfObjects 7 }

qtechWlogNotifyApRadioStatEntry OBJECT-TYPE
    SYNTAX      QtechWlogNotifyApRadioStatEntry
    MAX-ACCESS  accessible-for-notify
    STATUS      current
    DESCRIPTION
        "Represents the WTP radio statistics table Entry."
    INDEX   { qtechWlogNotifyApRadioId}
    ::= { qtechWlogNotifyApRadioStatTable 1 }

QtechWlogNotifyApRadioStatEntry ::=
    SEQUENCE {
        qtechWlogNotifyApRadioId             INTEGER,
        qtechWlogNotifyApRadioWorkChnl       INTEGER,
        qtechWlogNotifyApRadioPower          INTEGER,
        qtechWlogNotifyApRadioRssi           INTEGER,
        qtechWlogNotifyApRadioErrFrame       INTEGER,
        qtechWlogNotifyApRadioRetrsmit       INTEGER,
        qtechWlogNotifyApRadioTotalStaNum    INTEGER,
        qtechWlogNotifyApRadioWebStaNum      INTEGER,
        qtechWlogNotifyApRadioD1xStaNum      INTEGER
     }

qtechWlogNotifyApRadioId OBJECT-TYPE
    SYNTAX      INTEGER
    MAX-ACCESS  accessible-for-notify
    STATUS      current
    DESCRIPTION
        "AP's radio id."
    ::= { qtechWlogNotifyApRadioStatEntry 1 }

qtechWlogNotifyApRadioWorkChnl OBJECT-TYPE
    SYNTAX      INTEGER
    MAX-ACCESS  accessible-for-notify
    STATUS      current
    DESCRIPTION
        "AP's radio work channel."
    ::= { qtechWlogNotifyApRadioStatEntry 2 }

qtechWlogNotifyApRadioPower OBJECT-TYPE
    SYNTAX      INTEGER
    MAX-ACCESS  accessible-for-notify
    STATUS      current
    DESCRIPTION
        "AP's radio work power."
    ::= { qtechWlogNotifyApRadioStatEntry 3 }

qtechWlogNotifyApRadioRssi OBJECT-TYPE
    SYNTAX      INTEGER
    MAX-ACCESS  accessible-for-notify
    STATUS      current
    DESCRIPTION
        "AP's radio 's RSSI(received signal strength indicator)."
    ::= { qtechWlogNotifyApRadioStatEntry 4 }

qtechWlogNotifyApRadioErrFrame OBJECT-TYPE
    SYNTAX      INTEGER
    MAX-ACCESS  accessible-for-notify
    STATUS      current
    DESCRIPTION
        "AP's radio's total error frame number."
    ::= { qtechWlogNotifyApRadioStatEntry 5 }

qtechWlogNotifyApRadioRetrsmit OBJECT-TYPE
    SYNTAX      INTEGER
    MAX-ACCESS  accessible-for-notify
    STATUS      current
    DESCRIPTION
        "AP's radio's total Retransmitted frame number."
    ::= { qtechWlogNotifyApRadioStatEntry 6 }

qtechWlogNotifyApRadioTotalStaNum OBJECT-TYPE
    SYNTAX      INTEGER
    MAX-ACCESS  accessible-for-notify
    STATUS      current
    DESCRIPTION
        "AP's radio's total online sta number."
    ::= { qtechWlogNotifyApRadioStatEntry 7 }

qtechWlogNotifyApRadioWebStaNum OBJECT-TYPE
    SYNTAX      INTEGER
    MAX-ACCESS  accessible-for-notify
    STATUS      current
    DESCRIPTION
        "AP's radio's web authenticated sta number."
    ::= { qtechWlogNotifyApRadioStatEntry 8 }

qtechWlogNotifyApRadioD1xStaNum OBJECT-TYPE
    SYNTAX      INTEGER
    MAX-ACCESS  accessible-for-notify
    STATUS      current
    DESCRIPTION
        "AP's radio's dot1x authenticated sta number."
    ::= { qtechWlogNotifyApRadioStatEntry 9 }

-- **** define STA Operation notification objects ****
qtechWlogNotifyStaMac OBJECT-TYPE
    SYNTAX      MacAddress
    MAX-ACCESS  accessible-for-notify
    STATUS      current
    DESCRIPTION
        "Represents the unique identifier of a STA."
    ::= { qtechWlanWlogNtfObjects 8 }

qtechWlogNotifyStaIp OBJECT-TYPE
    SYNTAX      IpAddress
    MAX-ACCESS  accessible-for-notify
    STATUS      current
    DESCRIPTION
        "Represents Ipv4 address of a STA."
    ::= { qtechWlanWlogNtfObjects 9 }

qtechWlogNotifyStaIpv6 OBJECT-TYPE
    SYNTAX      InetAddress
    MAX-ACCESS  accessible-for-notify
    STATUS      current
    DESCRIPTION
        "Represents Ipv6 address of a STA."
    ::= { qtechWlanWlogNtfObjects 10 }

qtechWlogNotifySsid OBJECT-TYPE
    SYNTAX      DisplayString
    MAX-ACCESS  accessible-for-notify
    STATUS      current
    DESCRIPTION
        "Represents the Wlan Ssid."
    ::= { qtechWlanWlogNtfObjects 11 }

qtechWlogNotifyStaRssi OBJECT-TYPE
    SYNTAX      INTEGER
    MAX-ACCESS  accessible-for-notify
    STATUS      current
    DESCRIPTION
        "Represents STA's RSSI(received signal strength indicator)."
    ::= { qtechWlanWlogNtfObjects 12 }

qtechWlogNotifyStaLinkrate OBJECT-TYPE
    SYNTAX      INTEGER
    MAX-ACCESS  accessible-for-notify
    STATUS      current
    DESCRIPTION
        "Represents STA's link rate(Kbps)."
    ::= { qtechWlanWlogNtfObjects 13 }

qtechWlogNotifyStaOperType OBJECT-TYPE
    SYNTAX      INTEGER
    MAX-ACCESS  accessible-for-notify
    STATUS      current
    DESCRIPTION
        "Represents the STA's normal operation, 
        1-associate,
        2-disassociate,
        3-roam in,
        4-roam out,
        5-ip update,
        6-ipv6 update."
    ::= { qtechWlanWlogNtfObjects 14 }

qtechWlogNotifyStaAbnormalOperType OBJECT-TYPE
    SYNTAX      INTEGER
    MAX-ACCESS  accessible-for-notify
    STATUS      current
    DESCRIPTION
        "Represents the STA's abnormal operation, 
        1-associate fail,
        2-offline,
        3-roam fail,
        4-dot1x authenticate fail,
        5-web authenticate fail."
    ::= { qtechWlanWlogNtfObjects 15 }

qtechWlogNotifyStaOperReason OBJECT-TYPE
    SYNTAX      DisplayString
    MAX-ACCESS  accessible-for-notify
    STATUS      current
    DESCRIPTION
        "Represents the reason of STA's abnormal operation"
    ::= { qtechWlanWlogNtfObjects 16 }

-- ****************************************
--
--               Notify nodes
--
-- ****************************************
qtechNotifyApCapwapDownReason NOTIFICATION-TYPE
    OBJECTS     {
                  qtechWlogNotifyApName,
                  qtechWlogNotifyApMac,
                  qtechWlogNotifyApIp,
                  qtechWlogNotifyApCwDownId,
                  qtechWlogNotifyApCwDownReason
                }
    STATUS      current
    DESCRIPTION
        "This notification is sent by the AC when an AP's capwap down."
    ::= { qtechWlanWlogNotifications 1 }

qtechNotifyApCapwapDownIntf NOTIFICATION-TYPE
    OBJECTS     {
                  qtechWlogNotifyApName,
                  qtechWlogNotifyApMac,
                  qtechWlogNotifyApIp,
                  qtechWlogNotifyApCwDownId,
                  qtechWlogNotifyApIntfName,
                  qtechWlogNotifyApIntfInputRate,
                  qtechWlogNotifyApIntfOutputRate,
                  qtechWlogNotifyApIntfUnicastInputPkts,
                  qtechWlogNotifyApIntfUnicastOutputPkts,
                  qtechWlogNotifyApIntfMulticastInputPkts,
                  qtechWlogNotifyApIntfMulticastOutputPkts,
                  qtechWlogNotifyApIntfBroadcastInputPkts,
                  qtechWlogNotifyApIntfBroadcastOutputPkts,
                  qtechWlogNotifyApIntfErrorInputPkts,
                  qtechWlogNotifyApIntfErrorOutputPkts
                }
    STATUS      current
    DESCRIPTION
        "This notification is sent by the AC when an AP's capwap down."
    ::= { qtechWlanWlogNotifications 2 }

qtechNotifyApCapwapDownRadio NOTIFICATION-TYPE
    OBJECTS     {
                  qtechWlogNotifyApName,
                  qtechWlogNotifyApMac,
                  qtechWlogNotifyApIp,
                  qtechWlogNotifyApCwDownId,
                  qtechWlogNotifyApRadioId,
                  qtechWlogNotifyApRadioWorkChnl,
                  qtechWlogNotifyApRadioPower,
                  qtechWlogNotifyApRadioRssi,
                  qtechWlogNotifyApRadioErrFrame,
                  qtechWlogNotifyApRadioRetrsmit,
                  qtechWlogNotifyApRadioTotalStaNum,
                  qtechWlogNotifyApRadioWebStaNum,
                  qtechWlogNotifyApRadioD1xStaNum
                }
    STATUS      current
    DESCRIPTION
        "This notification is sent by the AC when an AP's capwap down."
    ::= { qtechWlanWlogNotifications 3 }

qtechNotifyStaOper NOTIFICATION-TYPE
    OBJECTS     {
                  qtechWlogNotifyStaMac,
                  qtechWlogNotifyStaIp,
                  qtechWlogNotifyStaIpv6,
                  qtechWlogNotifyStaRssi,
                  qtechWlogNotifyStaLinkrate,
                  qtechWlogNotifyApName,
                  qtechWlogNotifySsid,
                  qtechWlogNotifyStaOperType
                }
    STATUS      current
    DESCRIPTION
        "This notification is sent by the AC when an STA 
        associate/disassociate or roam in/out or ip address update."
    ::= { qtechWlanWlogNotifications 4 }

qtechNotifyStaAbnormalOper NOTIFICATION-TYPE
    OBJECTS     {
                  qtechWlogNotifyStaMac,
                  qtechWlogNotifyStaIp,
                  qtechWlogNotifyStaIpv6,
                  qtechWlogNotifyStaAbnormalOperType,
                  qtechWlogNotifyStaOperReason
                }
    STATUS      current
    DESCRIPTION
        "This notification is sent by the AC when an STA 
        associate fail or abnormal offline or roam fail 
        or dot1x/web authenticate failed."
    ::= { qtechWlanWlogNotifications 5 }

END

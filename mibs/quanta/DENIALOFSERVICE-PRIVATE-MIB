-- Denial of Service MIB overview:
-- Denial of Service MIB falls under MIB node of the private subtree.

DENIALOFSERVICE-PRIVATE-MIB DEFINITIONS ::= BEGIN

-- Quanta Denial of Service MIB
-- Copyright 2004- Quanta Computer, Inc.  All rights reserved.

-- This Specification is supplied "AS IS", Quanta Computer Inc.
-- makes no warranty, either expressed or implied,
-- as to the use, operation, condition, or performance of the
-- Specification.



IMPORTS
    MODULE-IDENTITY, OBJECT-TYPE, NOTIFICATION-TYPE,
    Unsigned32, Integer32               FROM SNMPv2-SMI
    TEXTUAL-CONVENTION, RowStatus,
    RowStatus, MacAddress               FROM SNMPv2-TC
    ifIndex                             FROM IF-MIB

    DisplayString		        FROM RFC1213-MIB
    switch                      FROM QUANTA-SWITCH-MIB;

    denialOfService MODULE-IDENTITY
           LAST-UPDATED "201108310000Z"
           ORGANIZATION "QCI"
           CONTACT-INFO
           "                      Customer Support
           Postal:                Quanta Computer Inc.
                                 4, Wen Ming 1 St., Kuei Shan Hsiang,
                                 Tao Yuan Shien, Taiwan, R.O.C.
           Tel:                   +886 3 328 0050
           E-Mail:                strong.chen@quantatw.com"
 
     DESCRIPTION
          "The Quanta Private MIB for Denial of Service."
      ::= { switch 31 }


    --**************************************************************************************
    -- agentSwitchDenialOfServiceGroup
    --
    --**************************************************************************************
    
    agentSwitchDenialOfServiceGroup          OBJECT IDENTIFIER ::= { denialOfService 1 }


    agentSwitchDenialOfServiceSIPDIPMode OBJECT-TYPE
         SYNTAX      INTEGER {
                     enable(1),
                     disable(2)
                  }
         MAX-ACCESS  read-write
         STATUS      current
         DESCRIPTION
                     "Enables or Disables the SIP=DIP Denial of Service 
                     protection feature."                
         DEFVAL { disable }
         ::= { agentSwitchDenialOfServiceGroup 1 }

    agentSwitchDenialOfServiceSMACDMACMode OBJECT-TYPE
         SYNTAX      INTEGER {
                     enable(1),
                     disable(2)
                  }
         MAX-ACCESS  read-write
         STATUS      current
         DESCRIPTION
                     "Enables or Disables the SMAC=DMAC Denial of Service 
                     protection feature."                
         DEFVAL { disable }
         ::= { agentSwitchDenialOfServiceGroup 9 }
         
    agentSwitchDenialOfServiceFirstFragMode OBJECT-TYPE
         SYNTAX      INTEGER {
                     enable(1),
                     disable(2)
                  }
         MAX-ACCESS  read-write
         STATUS      current
         DESCRIPTION
                     "Enables or Disables the First Fragment Denial of Service 
                     protection feature."
         DEFVAL { disable }
         ::= { agentSwitchDenialOfServiceGroup 2 }
         
    agentSwitchDenialOfServiceTCPHdrSize OBJECT-TYPE
         SYNTAX      Integer32 (0..255) 
         MAX-ACCESS  read-write
         STATUS      current
         DESCRIPTION
                     "Configures the Minimum allowed TCP Header size.
                     This is active if the First Fragment Denial of Service
                     protection feature is enabled."                    
         DEFVAL { 20 }
         ::= { agentSwitchDenialOfServiceGroup 3 }

    agentSwitchDenialOfServiceTCPFragMode OBJECT-TYPE
         SYNTAX      INTEGER {
                     enable(1),
                     disable(2)
                  }
         MAX-ACCESS  read-write
         STATUS      current
         DESCRIPTION
                     "Enables or Disables the TCP Fragment Denial of Service 
                     protection feature."
         DEFVAL { disable }
         ::= { agentSwitchDenialOfServiceGroup 4 }

    agentSwitchDenialOfServiceTCPOffsetMode OBJECT-TYPE
         SYNTAX      INTEGER {
                     enable(1),
                     disable(2)
                  }
         MAX-ACCESS  read-write
         STATUS      current
         DESCRIPTION
                     "Enables or Disables the TCP Offset Denial of Service 
                     protection feature."
         DEFVAL { disable }
         ::= { agentSwitchDenialOfServiceGroup 10 }
         
    agentSwitchDenialOfServiceTCPFlagMode OBJECT-TYPE
         SYNTAX      INTEGER {
                     enable(1),
                     disable(2)
                  }
         MAX-ACCESS  read-write
         STATUS      current
         DESCRIPTION
                     "Enables or Disables the TCP Flag Denial of Service 
                     protection feature."
         DEFVAL { disable }
         ::= { agentSwitchDenialOfServiceGroup 5 }

    agentSwitchDenialOfServiceTCPFlagSeqMode OBJECT-TYPE
         SYNTAX      INTEGER {
                     enable(1),
                     disable(2)
                  }
         MAX-ACCESS  read-write
         STATUS      current
         DESCRIPTION
                     "Enables or Disables the TCP Flag and Sequence Denial of Service 
                     protection feature."
         DEFVAL { disable }
         ::= { agentSwitchDenialOfServiceGroup 11 }

    agentSwitchDenialOfServiceTCPSynMode OBJECT-TYPE
         SYNTAX      INTEGER {
                     enable(1),
                     disable(2)
                  }
         MAX-ACCESS  read-write
         STATUS      current
         DESCRIPTION
                     "Enables or Disables the TCP Syn Denial of Service 
                     protection feature."
         DEFVAL { disable }
         ::= { agentSwitchDenialOfServiceGroup 14 }

    agentSwitchDenialOfServiceTCPSynFinMode OBJECT-TYPE
         SYNTAX      INTEGER {
                     enable(1),
                     disable(2)
                  }
         MAX-ACCESS  read-write
         STATUS      current
         DESCRIPTION
                     "Enables or Disables the TCP Syn and Fin Denial of Service 
                     protection feature."
         DEFVAL { disable }
         ::= { agentSwitchDenialOfServiceGroup 15 }

    agentSwitchDenialOfServiceTCPFinUrgPshMode OBJECT-TYPE
         SYNTAX      INTEGER {
                     enable(1),
                     disable(2)
                  }
         MAX-ACCESS  read-write
         STATUS      current
         DESCRIPTION
                     "Enables or Disables the TCP Fin and Urg and Psh Denial of Service 
                     protection feature."
         DEFVAL { disable }
         ::= { agentSwitchDenialOfServiceGroup 16 }
         
    agentSwitchDenialOfServiceL4PortMode OBJECT-TYPE
         SYNTAX      INTEGER {
                     enable(1),
                     disable(2)
                  }
         MAX-ACCESS  read-write
         STATUS      current
         DESCRIPTION
                     "Enables or Disables the L4 Port Denial of Service 
                     protection feature."
         DEFVAL { disable }
         ::= { agentSwitchDenialOfServiceGroup 6 }

    agentSwitchDenialOfServiceTCPPortMode OBJECT-TYPE
         SYNTAX      INTEGER {
                     enable(1),
                     disable(2)
                  }
         MAX-ACCESS  read-write
         STATUS      current
         DESCRIPTION
                     "Enables or Disables the TCP Port Denial of Service 
                     protection feature."
         DEFVAL { disable }
         ::= { agentSwitchDenialOfServiceGroup 12 }

    agentSwitchDenialOfServiceUDPPortMode OBJECT-TYPE
         SYNTAX      INTEGER {
                     enable(1),
                     disable(2)
                  }
         MAX-ACCESS  read-write
         STATUS      current
         DESCRIPTION
                     "Enables or Disables the UDP Port Denial of Service 
                     protection feature."
         DEFVAL { disable }
         ::= { agentSwitchDenialOfServiceGroup 13 }
         
    agentSwitchDenialOfServiceICMPMode OBJECT-TYPE
         SYNTAX      INTEGER {
                     enable(1),
                     disable(2)
                  }
         MAX-ACCESS  read-write
         STATUS      current
         DESCRIPTION
                     "Enables or Disables the ICMP Denial of Service 
                     protection feature."
         DEFVAL { disable }
         ::= { agentSwitchDenialOfServiceGroup 7 }

    agentSwitchDenialOfServiceICMPv6Mode OBJECT-TYPE
         SYNTAX      INTEGER {
                     enable(1),
                     disable(2)
                  }
         MAX-ACCESS  read-write
         STATUS      current
         DESCRIPTION
                     "Enables or Disables the ICMPv6 Denial of Service 
                     protection feature."
         DEFVAL { disable }
         ::= { agentSwitchDenialOfServiceGroup 20 }

    agentSwitchDenialOfServiceICMPSize OBJECT-TYPE
         SYNTAX      Integer32 (0..16376) 
         MAX-ACCESS  read-write
         STATUS      current
         DESCRIPTION
                     "Configures the Maximum allowed ICMP data size.
                     This is active if the ICMP Denial of Service
                     protection feature is enabled."
         DEFVAL { 512 }
         ::= { agentSwitchDenialOfServiceGroup 8 }

    agentSwitchDenialOfServiceICMPv6Size OBJECT-TYPE
         SYNTAX      Integer32 (0..16376) 
         MAX-ACCESS  read-write
         STATUS      current
         DESCRIPTION
                     "Configures the Maximum allowed ICMPv6 data size.
                     This is active if the ICMPv6 Denial of Service
                     protection feature is enabled."
         DEFVAL { 512 }
         ::= { agentSwitchDenialOfServiceGroup 18 }

    agentSwitchDenialOfServiceICMPFragMode OBJECT-TYPE
         SYNTAX      INTEGER {
                     enable(1),
                     disable(2)
                  }
         MAX-ACCESS  read-write
         STATUS      current
         DESCRIPTION
                     "Enables or Disables the ICMP Fragment Denial of Service 
                     protection feature."
         DEFVAL { disable }
         ::= { agentSwitchDenialOfServiceGroup 19 }
                                                  

END

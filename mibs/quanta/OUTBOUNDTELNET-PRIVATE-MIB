-- OUTBOUND TELNET MIB overview:
-- OUTBOUND TELNET MIB falls under MIB node of the private subtree.



OUTBOUNDTELNET-PRIVATE-MIB DEFINITIONS ::= BEGIN

-- Quanta OUTBOUND TELNET MIB
-- Copyright 2004- Quanta Computer, Inc.  All rights reserved.

-- This Specification is supplied "AS IS", Quanta Computer Inc.
-- makes no warranty, either expressed or implied,
-- as to the use, operation, condition, or performance of the
-- Specification.



IMPORTS
    MODULE-IDENTITY, OBJECT-TYPE, Integer32               FROM SNMPv2-SMI
    switch                                                FROM QUANTA-SWITCH-MIB;

    outboundTelnetPrivate MODULE-IDENTITY
           LAST-UPDATED "201108310000Z" -- 26 January 2011 12:00:00 GMT
           ORGANIZATION "QCI"
           CONTACT-INFO
           "                      Customer Support
           Postal:                Quanta Computer Inc.
                                 4, Wen Ming 1 St., Kuei Shan Hsiang,
                                 Tao Yuan Shien, Taiwan, R.O.C.
          Tel:                   +886 3 328 0050
          E-Mail:                strong.chen@quantatw.com"
      DESCRIPTION
          "The QCI Private MIB for Outbound Telnet"
      ::= { switch 19 }


     --**************************************************************************************
    -- agentOutboundTelnetGroup -> contains MIB objects displaying various properties of a Outbound Telnet
    --
    --**************************************************************************************

    agentOutboundTelnetGroup       OBJECT IDENTIFIER ::= { outboundTelnetPrivate 1 }

    agentOutboundTelnetAdminMode OBJECT-TYPE
      SYNTAX      INTEGER {
                  enable(1),
                  disable(2)
                  }
      MAX-ACCESS read-write
      STATUS     current
      DESCRIPTION
       " Admin-mode of the Outbound Telnet."
      DEFVAL { enable }
    ::= { agentOutboundTelnetGroup 1 }


    agentOutboundTelnetMaxNoOfSessions OBJECT-TYPE
      SYNTAX     INTEGER (0..5)
      MAX-ACCESS read-write
      STATUS     current
      DESCRIPTION
       " The maximum no. of Outbound Telnet sessions allowed."
      DEFVAL { 5 }
    ::= { agentOutboundTelnetGroup 2 }

    agentOutboundTelnetTimeout OBJECT-TYPE
      SYNTAX     INTEGER (1..160)
      MAX-ACCESS read-write
      STATUS     current
      DESCRIPTION
       " The login inactivity timeout value for Outbound Telnet."
      DEFVAL { 5 }
    ::= { agentOutboundTelnetGroup 3 }
END

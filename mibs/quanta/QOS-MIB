QOS-MIB DEFINITIONS ::= BEGIN

-- Quanta Computer Inc. Quality of Service Package MIB
-- Copyright Quanta Computer, Inc. (2004-2008) All rights reserved.

-- This SNMP Management Information Specification
-- embodies  Quanta Computer Inc. confidential and proprietary
-- intellectual property. Quanta Computer Inc. retains all title
-- and ownership in the Specification including any revisions.

-- This Specification is supplied "AS IS", Quanta Computer Inc.
-- makes no warranty, either expressed or implied,
-- as to the use, operation, condition, or performance of the
-- Specification.


IMPORTS
    MODULE-IDENTITY, OBJECT-TYPE, NOTIFICATION-TYPE, Integer32, Gauge32        
                                        FROM SNMPv2-SMI
    RowStatus                           FROM SNMPv2-TC
    switch                              FROM QUANTA-SWITCH-MIB
    DisplayString                       FROM RFC1213-MIB;
                
    qos MODULE-IDENTITY
        LAST-UPDATED "201108310000Z" -- 26 Jan 2011 12:00:00 GMT
        ORGANIZATION "Quanta Computer Inc."
        CONTACT-INFO
          "                      Customer Support
          Postal:                Quanta Computer Inc.
                                 4, Wen Ming 1 St., Kuei Shan Hsiang,
                                 Tao Yuan Shien, Taiwan, R.O.C.
          Tel:                   +886 3 328 0050
          E-Mail:                strong.chen@quantatw.com"
        DESCRIPTION
          "The MIB definitaions for Quality of Service Flex package."
    ::= { switch 3 }
      
END

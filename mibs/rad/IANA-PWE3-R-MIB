IANA-PWE3-R-MIB DEFINITIONS ::= BEGIN
                 
IMPORTS
    MODULE-IDENTITY, transmission
       FROM SNMPv2-SMI -- [RFC2578]

    TEXTUAL-CONVENTION
       FROM SNMPv2-TC; -- [RFC2579]

ianaPwe3MIBR  MODULE-IDENTITY
    LAST-UPDATED "200702041200Z"  -- 4 February 2006 12:00:00 GMT
    ORGANIZATION "IANA"
    CONTACT-INFO
         "Internet Assigned Numbers Authority
         Internet Corporation for Assigned Names and Numbers
         4676 Admiralty Way, Suite 330
         Marina del Rey, CA 90292-6601

         Phone: +1 310 823 9358
         EMail: iana@iana.org"
    DESCRIPTION
        "This MIB module defines the IANAPwTypeTC and
        IANAPwPsnTypeTC textual conventions for use in PWE3
        MIB modules.

        Any additions or changes to the contents of this MIB
        module require either publication of an RFC, Designated 
        Expert Review as defined in RFC 2434, Guidelines for 
        Writing an IANA Considerations Section in RFCs, and should 
        be based on the procedures defined in [RFC4446]. The 
        Designated Expert will be selected by the IESG Area 
        Director(s) of the internet Area.
        
        Copyright (C) The IETF Trust (2007).  The initial
        version of this MIB module was published in RFC yyyy;
        for full legal notices see the RFC itself.  Supplementary
        information may be available at:
        http://www.ietf.org/copyrights/ianamib.html."
   -- RFC Ed.: replace yyyy with actual RFC number & remove this note

    REVISION     "200702041200Z"  -- 4 February 2006 12:00:00 GMT 
    DESCRIPTION  "Original version, published as part of RFC yyyy."
-- RFC Editor: please fill the yyyy and remove this note.

	::= { radExperimental 9 }

radExperimental	OBJECT IDENTIFIER ::= { iso (1) org (3) dod (6) internet (1) private (4) enterprises (1) rad (164) 20 }

--    ::= { transmission XXXX }
-- RFC Editor: please fill the XXXX based on the IANA allocation
-- and remove this note.

IANAPwTypeTC ::= TEXTUAL-CONVENTION 
   STATUS     current 
   DESCRIPTION 
      "Indicates the PW type (i.e. the carried service). "
 SYNTAX   INTEGER { 
    other(0), 
    frameRelayDlciMartiniMode(1), 
    atmAal5SduVcc(2), 
    atmTransparent(3), 
    ethernetTagged(4), 
    ethernet(5), 
    hdlc(6), 
    ppp(7), 
    cem(8),  -- Malis mode 
    atmCellNto1Vcc(9), 
    atmCellNto1Vpc(10), 
    ipLayer2Transport(11), 
    atmCell1to1Vcc(12), 
    atmCell1to1Vpc(13), 
    atmAal5PduVcc(14), 
    frameRelayPortMode(15), 
    cep(16), 
    e1Satop(17), 
    t1Satop(18), 
    e3Satop(19), 
    t3Satop(20), 
    basicCesPsn(21), 
    basicTdmIp(22), 
    tdmCasCesPsn(23), 
    tdmCasTdmIp(24),
    frDlci(25),
    wildcard (32767) 
     }       

IANAPwPsnTypeTC ::= TEXTUAL-CONVENTION 
   STATUS      current 
   DESCRIPTION
      "Identifies the PSN type which the PW will use over the 
       network."
   SYNTAX   INTEGER { 
      mpls        (1),  
      l2tp        (2), 
      udpOverIp   (3),
      mplsOverIp  (4),  
      mplsOverGre (5), 
      other       (6) 
      }

IANAPwCapabilities ::= TEXTUAL-CONVENTION 
   STATUS      current 
   DESCRIPTION 
      "This TC describes a collection of cabailities related to
       a specific PW.  
       Values may be added in the future based on new capabilities  
       introduced in IETF documents. 
      " 
  SYNTAX   BITS { 
    pwStatusIndication (0), -- Applicable only if maintenence 
                            -- protocol is in use.
    pwVCCV             (1)
  }       

END

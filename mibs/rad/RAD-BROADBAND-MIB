RAD-BROADBAND-MIB DEFINITIONS ::= BEGIN

-- Title:     All RadGen MIB
-- *** This file is for the modified newmasking MIB. ***
-- Copyright 2000 RAD Data Communications, Ltd.
-- All Rights Reserved.

-- It is RAD's intent to encourage the widespread use of
-- this Specification in connection with the management of
-- RAD products. RAD grants vendors, end-users,
-- and other interested parties a non-exclusive license to
-- use this Specification in connection with the management
-- of RAD products.

-- This Specification is supplied "as is," and RAD makes
-- no warranty, either express or implied, as to the use,
-- operation, condition, or performance of the Specification.


IMPORTS

       ifIndex     FROM  IF-MIB
       Integer32, Gauge32, OBJECT-TYPE, 
       MODULE-IDENTITY     FROM  SNMPv2-SMI
       RowStatus     FROM  SNMPv2-TC
       diverseIfWanGen     FROM  RAD-SMI-MIB; 


	broadbandIf  MODULE-IDENTITY
		LAST-UPDATED "201502191759Z"  -- February 19, 2015
        ORGANIZATION "RAD Data Communications Ltd."
        CONTACT-INFO
        "System Department

         Email:  mibs@rad.com
         Postal: RAD Data Communications Ltd.
                 24 Raoul Wallenberg St.
                 Tel-Aviv 6971920
                 Israel

         Phone:  +972-3-645-5421
         Fax:    +972-3-760-7844"
         DESCRIPTION
            "Broadband Interface MIB."
	::= { diverseIfWanGen 8 }


-- broadbandIf  OBJECT IDENTIFIER  ::=  {diverseIfWanGen 8}

bdbandConfig       OBJECT IDENTIFIER  ::=  {broadbandIf 1}
prtPhyPerfHistory  OBJECT IDENTIFIER  ::=  {broadbandIf 2}


-- Indication Signal Table

prtBdbandIndTable OBJECT-TYPE
    SYNTAX  SEQUENCE OF PrtBdbandIndEntry
    MAX-ACCESS  not-accessible
    STATUS  current
    DESCRIPTION
    "The Indication Signal table."
    ::= { bdbandConfig 1 }

prtBdbandIndEntry OBJECT-TYPE
    SYNTAX  PrtBdbandIndEntry
    MAX-ACCESS  not-accessible
    STATUS  current
    DESCRIPTION
    "An entry in the Indication Signal table."
    INDEX {prtBdbandCnfgIdx, prtBdbandIdx, prtBdbandIndSig, prtBdbandIndEvent}
    ::= { prtBdbandIndTable 1 }

PrtBdbandIndEntry ::= SEQUENCE {
    prtBdbandCnfgIdx     Integer32,
    prtBdbandIdx     Integer32,
    prtBdbandIndSig  INTEGER,
    prtBdbandIndEvent  INTEGER,
    prtBdbandIndSigEnable  INTEGER,
    prtBdbandRowStatus  RowStatus 
 }

prtBdbandCnfgIdx OBJECT-TYPE
    SYNTAX  Integer32 (1..255)
    MAX-ACCESS  read-only
    STATUS  current
    DESCRIPTION
    "This object indicates the Idx of the Agent Cnfg the following
     objects refer.
     255=Temporary Cnfg (when relevant, Set is done only to this configuration).
     For Agents that support only one configuration, this object will be
     constant=1. "
    ::= { prtBdbandIndEntry 1 }

prtBdbandIdx OBJECT-TYPE
    SYNTAX  Integer32
    MAX-ACCESS  read-only
    STATUS  current
    DESCRIPTION
    "This object indicates a unique  port or interface number.
	 For numbering, see product's spec.
     For some products, the numbering can equal ifIndex."
    ::= { prtBdbandIndEntry 2 }

prtBdbandIndSig OBJECT-TYPE
    SYNTAX  INTEGER
    {
     ais       (1),
	 rdi       (2),
	 aisAndRdi (3)
    }
    MAX-ACCESS  read-only
    STATUS  current
    DESCRIPTION
    "This object indicates a unique Indication Signal.
     ais(1) = AIS = Alarm Indication Signal.
     rdi(2) = RDI = Remote Defect Indication."
    ::= { prtBdbandIndEntry 3 }

prtBdbandIndEvent OBJECT-TYPE
    SYNTAX  INTEGER
    {
     notApplicable(1),
     slm          (2),
	 fail         (3),
	 eed          (4),
	 pathTrace    (5),
	 lom		  (6),
	 lop		  (7),
	 slu		  (8)
    }
    MAX-ACCESS  read-only
    STATUS  current
    DESCRIPTION
    "This object indicates a unique Event that can cause the Indication Signal.
     slm(2) = SLM = Signal Label Mismatch
	 fail (3) = other failures
     eed(4) = EED = Excessive Error Defect
     pathTrace(5) = the end-to-end source/destination of information is wrong.
     lom(6) = LOM = Loss of Multiframe.
     lop(7) = LOP = Loss of Pointer.
	 slu(8) = SLU = Signal Label Unequipped."
    ::= { prtBdbandIndEntry 4 }

prtBdbandIndSigEnable OBJECT-TYPE
    SYNTAX  INTEGER
    {
     notApplicable(1),
     disable      (2),
	 enable       (3)
    }
    MAX-ACCESS  read-create
    STATUS  current
    DESCRIPTION
    "This object allows user to define if the event specified by prtBdbandIndEvent
     will cause creation of the Indication Signal specified by prtBdbandIndSig or not.
     disable - will not enable causing the signal
     enable  - will enable causing the signal. "
    ::= { prtBdbandIndEntry 5 }

prtBdbandRowStatus OBJECT-TYPE
    SYNTAX RowStatus
    MAX-ACCESS read-create
    STATUS current
    DESCRIPTION
    "Creation/Deletion of rows in the table."
    ::= { prtBdbandIndEntry 6 }

-- Port Phy Config Table

prtPhyConfigTable OBJECT-TYPE
    SYNTAX  SEQUENCE OF PrtPhyConfigEntry
    MAX-ACCESS  not-accessible
    STATUS  current
    DESCRIPTION
    "The Phy Config table. Used now for Phy25.6 Mbps."
    ::= { bdbandConfig 2 }

prtPhyConfigEntry OBJECT-TYPE
    SYNTAX  PrtPhyConfigEntry
    MAX-ACCESS  not-accessible
    STATUS  current
    DESCRIPTION
    "An entry in the Phy Config table. "
    INDEX   { ifIndex }
    ::= { prtPhyConfigTable 1 }

PrtPhyConfigEntry ::=
    SEQUENCE {
    prtPhyTimeElapsed
        Integer32,
    prtPhyValidIntervals
        Integer32
       }

prtPhyTimeElapsed OBJECT-TYPE
    SYNTAX  Integer32 (0..899)
    MAX-ACCESS  read-only
    STATUS  current
    DESCRIPTION
    "The number of seconds that have elapsed since
     the beginning of the current error-measurement period."
   ::= { prtPhyConfigEntry 1 }

prtPhyValidIntervals OBJECT-TYPE
     SYNTAX  Integer32 (0..96)
     MAX-ACCESS  read-only
     STATUS  current
     DESCRIPTION
     "The number of previous intervals for which valid data was collected.  
      The value will be	96 unless the interface was brought online within
      the last 24 hours, in which case the value will be the number of complete 
      15 minute since the interface has been online."
     ::= { prtPhyConfigEntry 2 }


--Phy Performance History Tables

-- The PHY Current table contains various statistics being
-- collected for the current 15 minute interval.

prtPhyCurrentTable OBJECT-TYPE
    SYNTAX  SEQUENCE OF PrtPhyCurrentEntry
    MAX-ACCESS  not-accessible
    STATUS  current
    DESCRIPTION
    "The 25.6 Mbps Section/Line Current table."
    ::= { prtPhyPerfHistory 1 }

prtPhyCurrentEntry OBJECT-TYPE
    SYNTAX  PrtPhyCurrentEntry
    MAX-ACCESS  not-accessible
    STATUS  current
    DESCRIPTION
    "An entry in the 25.6 Mbps Line Current table.
     ifIndex of the line 25.6 Mbps layer of type 
     25.6 Mbps."
    INDEX   { ifIndex }
    ::= { prtPhyCurrentTable 1 }

PrtPhyCurrentEntry ::=
    SEQUENCE {
        prtPhyCurrentLOS
            Gauge32,
        prtPhyCurrentLSV
            Gauge32,
        prtPhyCurrentUAS
            Gauge32,
        prtPhyCurrentSES
            Gauge32,
        prtPhyCurrentES 
            Gauge32,
        prtPhyCurrentStatus 
            OCTET STRING,
        prtPhyCurrentLOF 
            Gauge32
    }

prtPhyCurrentLOS OBJECT-TYPE
    SYNTAX  Gauge32
    MAX-ACCESS  read-only
    STATUS  current
    DESCRIPTION
    "The counter associated with the number of Loss Of Sync
     seconds, encountered by a 25.6 Mbps interface in
     the current 15 minute interval."
    ::= { prtPhyCurrentEntry 1 }

prtPhyCurrentLSV OBJECT-TYPE
    SYNTAX  Gauge32
    MAX-ACCESS  read-only
    STATUS  current
    DESCRIPTION
    "The counter associated with the number of Line symbol violation
     seconds, encountered by a 25.6 Mbps
     interface in the current 15 minute interval."
    ::= { prtPhyCurrentEntry 2 }

prtPhyCurrentUAS OBJECT-TYPE
    SYNTAX  Gauge32
    MAX-ACCESS  read-only
    STATUS  current
    DESCRIPTION
    "The counter associated with the number of UAS
     encountered by a 25.6 Mbps
     interface in the current 15 minute interval."
    ::= { prtPhyCurrentEntry 3 }

prtPhyCurrentSES OBJECT-TYPE
     SYNTAX  Gauge32
     MAX-ACCESS  read-only
     STATUS  current
     DESCRIPTION
     "The counter associated with the number of SES
      encountered by a 25.6 Mbps
      interface in the current 15 minute interval."
     ::= { prtPhyCurrentEntry 4 }

prtPhyCurrentES OBJECT-TYPE
     SYNTAX Gauge32 
     MAX-ACCESS  read-only
     STATUS  current
     DESCRIPTION
     "The number of Errored Seconds, encountered  by a
      25.6 Mbps interface in the current 15 minute interval."
     ::= { prtPhyCurrentEntry 5 }
 
prtPhyCurrentStatus OBJECT-TYPE
     SYNTAX OCTET STRING  (SIZE (4))
     MAX-ACCESS  read-only
     STATUS  current
     DESCRIPTION
     "The statuses of the current interval:
       0 - O.K.
       1 - The link has been switched by a redundancy mechanism.
       2 - Module is in/out.
       4 - Empty - card is out."
     ::= { prtPhyCurrentEntry 6 }

prtPhyCurrentLOF OBJECT-TYPE
     SYNTAX Gauge32 
     MAX-ACCESS  read-only
     STATUS  current
     DESCRIPTION
     "The number of Loss of Frames, encountered by an
      interface in the current 15 minute interval."
     ::= { prtPhyCurrentEntry 7 }
 
 
-- The PHY interface Interval

-- The PHY Interval Table contains various statistics
-- collected by the Interface over the previous 24
-- hours of operation.  The past 24 hours are broken into 96
-- completed 15 minute intervals.

prtPhyIntervalTable OBJECT-TYPE
     SYNTAX  SEQUENCE OF PrtPhyIntervalEntry
     MAX-ACCESS  not-accessible
     STATUS  current
     DESCRIPTION
     "The Line Interval table."
     ::= { prtPhyPerfHistory 2 }

prtPhyIntervalEntry OBJECT-TYPE
     SYNTAX  PrtPhyIntervalEntry
     MAX-ACCESS  not-accessible
     STATUS  current
     DESCRIPTION
     "An entry in the 25.6 Mbps Line Interval table.
      ifIndex of the line 25.6 Mbps layer of type 25.6 Mbps."
     INDEX   { ifIndex, prtPhyIntervalNumber }
     ::= { prtPhyIntervalTable 1 }

PrtPhyIntervalEntry ::=
     SEQUENCE {
        prtPhyIntervalNumber
            Integer32,
        prtPhyIntervalLOS
            Gauge32,
        prtPhyIntervalLSV
            Gauge32,
        prtPhyIntervalUAS
            Gauge32,
        prtPhyIntervalSES
            Gauge32,
        prtPhyIntervalES
            Gauge32,
        prtPhyIntervalStatus
            OCTET STRING,
        prtPhyIntervalLOF
            Gauge32
      }

prtPhyIntervalNumber OBJECT-TYPE
     SYNTAX  Integer32 (1..96)
     MAX-ACCESS  read-only
     STATUS  current
     DESCRIPTION
     "A number between 1 and 96, where 1 is the most
      recently completed 15 minute interval and 96 is
      the least recently completed 15 minutes interval
      (assuming that all 96 intervals are valid)."
     ::= { prtPhyIntervalEntry 1 }

prtPhyIntervalLOS OBJECT-TYPE
     SYNTAX  Gauge32
     MAX-ACCESS  read-only
     STATUS  current
     DESCRIPTION
     "The counter associated with the number of Loss Of Sync
      seconds , encountered by a 25.6 Mbps interface in
      one of the previous 96, individual 15 minute intervals."
     ::= { prtPhyIntervalEntry 2 }

prtPhyIntervalLSV OBJECT-TYPE
     SYNTAX  Gauge32
     MAX-ACCESS  read-only
     STATUS  current
     DESCRIPTION
     "The counter associated with the number of line symbol violation
      seconds , encountered by a 25.6 Mbps interface in
      one of the previous 96, individual 15 minute intervals."
     ::= { prtPhyIntervalEntry 3 }

prtPhyIntervalUAS OBJECT-TYPE
     SYNTAX  Gauge32
     MAX-ACCESS  read-only
     STATUS  current
     DESCRIPTION
     "The counter associated with the number of UAS
      encountered by a 25.6 Mbps interface in one of the previous 96, 
      individual 15	minute intervals."
     ::= { prtPhyIntervalEntry 4 }

prtPhyIntervalSES OBJECT-TYPE
     SYNTAX  Gauge32
     MAX-ACCESS  read-only
     STATUS  current
     DESCRIPTION
     "The counter associated with the number of SES
      encountered by a 25.6 Mbps interface in one of the previous 96, 
      individual 15	minute intervals."
    ::= { prtPhyIntervalEntry 5 }

prtPhyIntervalES OBJECT-TYPE
     SYNTAX Gauge32 
     MAX-ACCESS  read-only
     STATUS current 
     DESCRIPTION
     "The number of Errored Seconds, encountered  by a
      25.6 Mbps interface in one of the previous 96, individual 15
      minute intervals."
     ::= { prtPhyIntervalEntry 6 }

prtPhyIntervalStatus OBJECT-TYPE
     SYNTAX OCTET STRING  (SIZE (4))
     MAX-ACCESS  read-only
     STATUS  current
     DESCRIPTION
     " The statuses of the current interval:
       0 - O.K.
       1 - The link has been switched by a redundancy mechanism.
       2 - Module is in/out.
       4 - Empty - card is out."
     ::= { prtPhyIntervalEntry 7 }

prtPhyIntervalLOF OBJECT-TYPE
     SYNTAX Gauge32 
     MAX-ACCESS  read-only
     STATUS current 
     DESCRIPTION
     "The number of Loss of Frames, encountered  by an
      interface in one of the previous 96, individual 15
      minute intervals."
     ::= { prtPhyIntervalEntry 8 }


END

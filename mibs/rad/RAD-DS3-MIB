RAD-DS3-MIB DEFINITIONS ::= BEGIN

-- It is RAD's intent to encourage the widespread use of
-- this Specification in connection with the management of
-- RAD products. RAD grants vendors, end-users,
-- and other interested parties a non-exclusive license to
-- use this Specification in connection with the management
-- of RAD products.

-- This Specification is supplied "as is," and RAD makes
-- no warranty, either express or implied, as to the use,
-- operation, condition, or performance of the Specification.


IMPORTS

       dsx3LineStatus, dsx3ConfigEntry, dsx3LoopbackConfig     FROM  DS3-MIB
       InterfaceIndex, ifAlias, ifIndex     FROM  IF-MIB
       Integer32, Gauge32, Unsigned32, 
       OBJECT-TYPE, MODULE-IDENTITY, NOTIFICATION-TYPE     FROM  SNMPv2-SMI
       diverseIfWanGen     FROM  RAD-SMI-MIB
       alarmEventLogSourceName, alarmEventLogAlarmOrEventId, alarmEventLogDescription, 
       alarmEventLogSeverity, alarmEventLogDateAndTime, alarmEventReason     FROM  RAD-GEN-MIB; 


    ds3Interface MODULE-IDENTITY
        LAST-UPDATED "201604211806Z"  -- April 21, 2016
        ORGANIZATION "RAD Data Communications Ltd."
        CONTACT-INFO
        "System Department

         Email:  mibs@rad.com
         Postal: RAD Data Communications Ltd.
                 24 Raoul Wallenberg St.
                 Tel-Aviv 6971920
                 Israel

         Phone:  +972-3-645-5421
         Fax:    +972-3-760-7844"
         DESCRIPTION
            "DS3 MIB."
    ::= { diverseIfWanGen 3 }

--Title:    RAD-DS3   MIB
-- ds3Interface  OBJECT IDENTIFIER  ::=  {diverseIfWanGen 3}

prtDS3Events OBJECT IDENTIFIER       ::= {ds3Interface 0}

prtDs3PerfHistory  OBJECT IDENTIFIER  ::=  {ds3Interface 1}


          -- The DS3 Interface Table

          prtSDs3IfTable OBJECT-TYPE
              SYNTAX  SEQUENCE OF PrtDs3IfEntry
              MAX-ACCESS  not-accessible
              STATUS  current
              DESCRIPTION
                      "The DS3 interface table."
              ::= { prtDs3PerfHistory 1 }

          prtDs3IfEntry OBJECT-TYPE
              SYNTAX  PrtDs3IfEntry
              MAX-ACCESS  not-accessible
              STATUS  current
              DESCRIPTION
                      "An entry in the DS3 interface table."
              INDEX   { ifIndex }
              ::= { prtSDs3IfTable 1 }

          PrtDs3IfEntry ::=
              SEQUENCE {
                  prtDs3IfTimeElapsed
                      Integer32,
                  prtDs3IfValidIntervals
                      Integer32
                                           }

           prtDs3IfTimeElapsed OBJECT-TYPE
               SYNTAX  Integer32 (0..899)
               MAX-ACCESS  read-only
               STATUS  current
               DESCRIPTION
                       "The number of seconds that have elapsed since
                       the beginning of the near end current error-
                       measurement period."
              ::= { prtDs3IfEntry 1 }

          prtDs3IfValidIntervals OBJECT-TYPE
              SYNTAX  Integer32 (0..96)
              MAX-ACCESS  read-only
              STATUS  current
              DESCRIPTION
                      "The number of previous near end intervals for
                      which valid data was collected.  The value will be
                      96 unless the interface was brought online within
                      the last 24 hours, in which case the value will be
                      the number of complete 15 minute near end
                      intervals since the interface has been online."
              ::= { prtDs3IfEntry 2 }

        

          -- The DS3 Current Table

          -- The DS3 Current table contains various statistics being
          -- collected for the current 15 minute interval.

          prtDs3CurrentTable OBJECT-TYPE
              SYNTAX  SEQUENCE OF PrtDs3CurrentEntry
              MAX-ACCESS  not-accessible
              STATUS  current
              DESCRIPTION
                      "The DS3 Current table."
              ::= { prtDs3PerfHistory 2 }

          prtDs3CurrentEntry OBJECT-TYPE
              SYNTAX  PrtDs3CurrentEntry
              MAX-ACCESS  not-accessible
              STATUS  current
              DESCRIPTION
                      "An entry in the DS3 Current table."
              INDEX   { ifIndex }
              ::= { prtDs3CurrentTable 1 }

          PrtDs3CurrentEntry ::=
              SEQUENCE {
                  prtDs3CurrentLOS
                      Gauge32,
                  prtDs3CurrentOOF
                      Gauge32,
                  prtDs3CurrentLOC
                      Gauge32,
                  prtDs3CurrentAIS
                      Gauge32,
                  prtDs3CurrentRDI
                      Gauge32,
                  prtDs3CurrentUAS
                      Gauge32,
	              prtDs3CurrentBIP
                      Gauge32,
                  prtDs3CurrentFEBE
	                  Gauge32,
	              prtDs3CurrentSLM
	                  Gauge32,
                  prtDs3CurrentSES
                      Gauge32,
                  prtDs3CurrentES 
                      Gauge32,
                  prtDs3CurrentBitParity
                      Gauge32,
                  prtDs3CurrentPlcpLOF
                      Gauge32,
                  prtDs3CurrentPlcpRAI
                       Gauge32,
	              prtDs3CurrentPlcpBIP
                       Gauge32,
                  prtDs3CurrentPlcpFEBE
	                   Gauge32,
				 prtDs3CurrentBPV
				       Gauge32,
				 prtDs3CurrentLCE
				       Gauge32,
				  prtDs3CurrentStatus
				       OCTET STRING
}

          prtDs3CurrentLOS OBJECT-TYPE
              SYNTAX  Gauge32
              MAX-ACCESS  read-only
              STATUS  current
              DESCRIPTION
                      "The counter associated with the number of LOS
                       seconds, encountered by a DS3 interface in
                      the current 15 minute interval."
              ::= { prtDs3CurrentEntry 1 }

          prtDs3CurrentOOF OBJECT-TYPE
              SYNTAX  Gauge32
              MAX-ACCESS  read-only
              STATUS  current
              DESCRIPTION
                      "The counter associated with the number of OOF
                       seconds, encountered by a DS3
                       interface in the current 15 minute interval."
              ::= { prtDs3CurrentEntry 2 }

          prtDs3CurrentLOC OBJECT-TYPE
              SYNTAX  Gauge32
              MAX-ACCESS  read-only
              STATUS  current
              DESCRIPTION
                      "The counter associated with the number of LOC
                      seconds, encountered by a DS3
                      interface in the current 15 minute interval."
              ::= { prtDs3CurrentEntry 3 }

          prtDs3CurrentAIS OBJECT-TYPE
              SYNTAX  Gauge32
              MAX-ACCESS  read-only
              STATUS  current
              DESCRIPTION
                      "The counter associated with the number of AIS
                      seconds, encountered by a DS3
                      interface in the current 15 minute interval."
              ::= { prtDs3CurrentEntry 4 }

          prtDs3CurrentRDI OBJECT-TYPE
              SYNTAX  Gauge32
              MAX-ACCESS  read-only
              STATUS  current
              DESCRIPTION
                      "The counter associated with the number of RDI
                      seconds, encountered by a DS3
                      interface."
              ::= { prtDs3CurrentEntry 5 }

          prtDs3CurrentUAS OBJECT-TYPE
              SYNTAX  Gauge32
              MAX-ACCESS  read-only
              STATUS  current
              DESCRIPTION
                      "The counter associated with the number of UAS, 
                      encountered by a SONET interface."
              ::= { prtDs3CurrentEntry 6 }

        prtDs3CurrentBIP OBJECT-TYPE
              SYNTAX  Gauge32
              MAX-ACCESS  read-only
              STATUS  current
              DESCRIPTION
                      "The counter associated with the number of 
                      BIP errors, encountered by a DS3
                      interface in the current 15 minute interval."
              ::= { prtDs3CurrentEntry 7 }

          prtDs3CurrentFEBE OBJECT-TYPE
              SYNTAX  Gauge32
              MAX-ACCESS  read-only
              STATUS  current
              DESCRIPTION
                      "The counter associated with the number of 
                      FEBE errors, encountered by a DS3
                      interface in the current 15 minute interval."
              ::= { prtDs3CurrentEntry 8 }

          prtDs3CurrentSLM OBJECT-TYPE
              SYNTAX  Gauge32
              MAX-ACCESS  read-only
              STATUS  current
              DESCRIPTION
                      "The counter associated with the number of SLM
                       seconds, encountered by an E3 (only )
                       interface in the current 15 minute interval."
              ::= { prtDs3CurrentEntry 9 }

        prtDs3CurrentSES OBJECT-TYPE
              SYNTAX  Gauge32
              MAX-ACCESS  read-only
              STATUS  current
              DESCRIPTION
                      "The counter associated with the number of SES
                       encountered by a E3
                       interface in the current 15 minute interval."
	     ::= { prtDs3CurrentEntry 10 }

	  prtDs3CurrentES OBJECT-TYPE
	SYNTAX Gauge32 
              MAX-ACCESS  read-only
              STATUS  current
              DESCRIPTION
                      " The number of Errored Seconds, encountered  by a
                      DS3 interface in the current 15 minute interval."
	::= { prtDs3CurrentEntry 11 }

     prtDs3CurrentBitParity OBJECT-TYPE
              SYNTAX  Gauge32
              MAX-ACCESS  read-only
              STATUS  current
              DESCRIPTION
                      "Bit Parity Error counter. Relevant to T3 only."
              ::= { prtDs3CurrentEntry 12 }

        prtDs3CurrentPlcpLOF OBJECT-TYPE
              SYNTAX  Gauge32
              MAX-ACCESS  read-only
              STATUS  current
              DESCRIPTION
                      "The counter associated with the number of LOF
                      seconds, encountered by a DS3
                      interface in one of the previous 96, individual 15
                      minute, intervals. This counter is relevant for plcpInternal(5)
                       or plcpExternal(6) configuration If frame types only."
              ::= { prtDs3CurrentEntry 13 }

prtDs3CurrentPlcpRAI OBJECT-TYPE
              SYNTAX  Gauge32
              MAX-ACCESS  read-only
              STATUS  current
              DESCRIPTION
                    "Receiving Yellow/Remote Alarm Indication. This counter is 
                      relevant for PLCP (external/internal) frame types only."
              ::= { prtDs3CurrentEntry 14 }

      prtDs3CurrentPlcpBIP OBJECT-TYPE
              SYNTAX  Gauge32
              MAX-ACCESS  read-only
              STATUS  current
              DESCRIPTION
                    " The counter associated with the number of BIP errors, 
                      encountered by a DS3 interface in the current 15 minute 
                      interval. This counter is relevant for PLCP (external/internal) 
                      frame types only."
              ::= { prtDs3CurrentEntry 15 }

      prtDs3CurrentPlcpFEBE OBJECT-TYPE
              SYNTAX  Gauge32
              MAX-ACCESS  read-only
              STATUS  current
              DESCRIPTION
                    " The counter associated with the number of FEBE
                      errors, encountered by a DS3 interface in the current
                      15 minute interval. This counter is relevant for PLCP
                      (external/internal) frame types only."
              ::= { prtDs3CurrentEntry 16 }

      prtDs3CurrentBPV OBJECT-TYPE
              SYNTAX  Gauge32
              MAX-ACCESS  read-only
              STATUS  current
              DESCRIPTION
                    " Number of BPVs (Bi-Polar Violations) , encountered by a 
                      DS3 interface in the current 15 minute interval. 
                      This object is relevant only for Electrical Line
                      of Fomi-E3/T3."
              ::= { prtDs3CurrentEntry 17 }

      prtDs3CurrentLCE OBJECT-TYPE
              SYNTAX  Gauge32
              MAX-ACCESS  read-only
              STATUS  current
              DESCRIPTION
                    " Number of LCE (Link Code Errors)  encountered 
                      by a DS3 interface in the current 15 minute interval. 
                      This object is relevant only for Optical Links
                      of Fomi-E3/T3."
              ::= { prtDs3CurrentEntry 18 }

     prtDs3CurrentStatus OBJECT-TYPE
	          SYNTAX OCTET STRING  (SIZE (4))
              MAX-ACCESS  read-only
              STATUS  current
              DESCRIPTION
                      "The statuses of the current interval:
                        0 - Valid.
                        1 - redundantLinkSwitch - the link has been switched 
                            by a redundancy mechanism.
                        2 - discontinuity - module was partialy out.
                        4 - notValid - module is out."
              ::= { prtDs3CurrentEntry 19 }

         -- The DS3 interface Interval

          -- The DS3 Interval Table contains various statistics
          -- collected by the Interface over the previous 24
          -- hours of operation.  The past 24 hours are broken into 96
          -- completed 15 minute intervals.

          prtDs3IntervalTable OBJECT-TYPE
              SYNTAX  SEQUENCE OF PrtDs3IntervalEntry
              MAX-ACCESS  not-accessible
              STATUS  current
              DESCRIPTION
                      "The DS3 Interval table."
              ::= { prtDs3PerfHistory 3 }

          prtDs3IntervalEntry OBJECT-TYPE
              SYNTAX  PrtDs3IntervalEntry
              MAX-ACCESS  not-accessible
              STATUS  current
              DESCRIPTION
                      "An entry in the DS3 Interval table."
              INDEX   { ifIndex, prtDs3IntervalNumber }
              ::= { prtDs3IntervalTable 1 }

          PrtDs3IntervalEntry ::=
              SEQUENCE {
                  prtDs3IntervalNumber
                      Integer32,
                  prtDs3IntervalLOS
                      Gauge32,
                  prtDs3IntervalOOF
                      Gauge32,
                  prtDs3IntervalLOC
                      Gauge32,
                  prtDs3IntervalAIS
                      Gauge32,
                  prtDs3IntervalRDI
                      Gauge32,
                  prtDs3IntervalUAS
                      Gauge32,
	              prtDs3IntervalBIP
                      Gauge32,
                  prtDs3IntervalFEBE
                      Gauge32,
	              prtDs3IntervalSLM
                      Gauge32,
                  prtDs3IntervalSES 
                      Gauge32,
	              prtDs3IntervalES
                      Gauge32,
                  prtDs3IntervalBitParity
                      Gauge32,
                  prtDs3IntervalPlcpLOF
                      Gauge32,
                  prtDs3IntervalPlcpRAI
                      Gauge32,
	              prtDs3IntervalPlcpBIP
                      Gauge32,
                  prtDs3IntervalPlcpFEBE
	                  Gauge32,
				  prtDs3IntervalBPV
				       Gauge32,
				  prtDs3IntervalLCE
				       Gauge32,
				  prtDs3IntervalStatus 
	                  OCTET STRING
}

          prtDs3IntervalNumber OBJECT-TYPE
              SYNTAX  Integer32 (1..96)
              MAX-ACCESS  read-only
              STATUS  current
              DESCRIPTION
                      "A number between 1 and 96, where 1 is the most
                      recently completed 15 minute interval and 96 is
                      the least recently completed 15 minutes interval
                      (assuming that all 96 intervals are valid)."
              ::= { prtDs3IntervalEntry 1 }

          prtDs3IntervalLOS OBJECT-TYPE
              SYNTAX  Gauge32
              MAX-ACCESS  read-only
              STATUS  current
              DESCRIPTION
                      "The counter associated with the number of LOS
                      seconds , encountered by a DS3 interface in
                      one of the previous 96, individual 15 minute,
                      intervals."
              ::= { prtDs3IntervalEntry 2 }

          prtDs3IntervalOOF OBJECT-TYPE
              SYNTAX  Gauge32
              MAX-ACCESS  read-only
              STATUS  current
              DESCRIPTION
                      "The counter associated with the number of OOF
                      seconds, encountered by a DS3
                      interface in one of the previous 96, individual 15
                      minute, intervals."
              ::= { prtDs3IntervalEntry 3 }

          prtDs3IntervalLOC OBJECT-TYPE
              SYNTAX  Gauge32
              MAX-ACCESS  read-only
              STATUS  current
              DESCRIPTION
                      "The counter associated with the number of LOC
                      seconds, encountered by a DS3
                      interface in one of the previous 96,
                      individual 15 minute, intervals."
              ::= { prtDs3IntervalEntry 4 }

          prtDs3IntervalAIS OBJECT-TYPE
              SYNTAX  Gauge32
              MAX-ACCESS  read-only
              STATUS  current
              DESCRIPTION
                      "The counter associated with the number of AIS
                      seconds, encountered by a SONET
                      interface in one of the previous 96, individual 15
                      minute, intervals."
              ::= { prtDs3IntervalEntry 5 }

          prtDs3IntervalRDI OBJECT-TYPE
              SYNTAX  Gauge32
              MAX-ACCESS  read-only
              STATUS  current
              DESCRIPTION
                      "The counter associated with the number of RDI
                      seconds, encountered by a DS3
                      interface in one of the previous 96, individual 15
                      minute, intervals."
              ::= { prtDs3IntervalEntry 6 }

          prtDs3IntervalUAS OBJECT-TYPE
              SYNTAX  Gauge32
              MAX-ACCESS  read-only
              STATUS  current
              DESCRIPTION
                      "The counter associated with the number of UAS,
                      encountered by a DS3
                      interface in one of the previous 96, individual 15
                      minute, intervals."
              ::= { prtDs3IntervalEntry 7 }

          prtDs3IntervalBIP OBJECT-TYPE
              SYNTAX  Gauge32
              MAX-ACCESS  read-only
              STATUS  current
              DESCRIPTION
                      "The counter associated with the number of 
                      BIP errors, encountered by a DS3 
                      interface in one of the previous 96, individual 15
                      minute, intervals."
              ::= { prtDs3IntervalEntry 8 }

          prtDs3IntervalFEBE OBJECT-TYPE
              SYNTAX  Gauge32
              MAX-ACCESS  read-only
              STATUS  current
              DESCRIPTION
                      "The counter associated with the number of 
                      FEBE errors, encountered by a DS3
                      interface in one of the previous 96, individual 15
                      minute, intervals."
              ::= { prtDs3IntervalEntry 9 }

          prtDs3IntervalSLM OBJECT-TYPE
              SYNTAX  Gauge32
              MAX-ACCESS  read-only
              STATUS  current
              DESCRIPTION
                      "The counter associated with the number of SLM
                      seconds, encountered by an E3
                      interface in one of the previous 96, individual 15
                      minute, intervals."
              ::= { prtDs3IntervalEntry 10 }

	 prtDs3IntervalSES OBJECT-TYPE
              SYNTAX  Gauge32
              MAX-ACCESS  read-only
              STATUS  current
              DESCRIPTION
                      "The counter associated with the number of SES
                      encountered by a E3
                      interface in one of the previous 96, individual 15
                      minute, intervals."
	      ::= { prtDs3IntervalEntry 11 }

	 prtDs3IntervalES OBJECT-TYPE
	SYNTAX Gauge32
              MAX-ACCESS  read-only
              STATUS  current
              DESCRIPTION
                      " The number of Errored Seconds, encountered  by a
                      DS3 interface in one of the previous 96, individual 15
                      minute, intervals."
	::= { prtDs3IntervalEntry 12 }

prtDs3IntervalBitParity OBJECT-TYPE
              SYNTAX  Gauge32
              MAX-ACCESS  read-only
              STATUS  current
              DESCRIPTION
                      "Bit Parity Error counter. Relevant to T3 only."
              ::= { prtDs3IntervalEntry 13 }

        prtDs3IntervalPlcpLOF OBJECT-TYPE
              SYNTAX  Gauge32
              MAX-ACCESS  read-only
              STATUS  current
              DESCRIPTION
                      "The counter associated with the number of LOF
                      seconds, encountered by a DS3
                      interface in one of the previous 96, individual 15
                      minute, intervals. This counter is relevant for plcpInternal(5)
                       or plcpExternal(6) configuration If frame types only."
              ::= { prtDs3IntervalEntry 14 }

prtDs3IntervalPlcpRAI OBJECT-TYPE
              SYNTAX  Gauge32
              MAX-ACCESS  read-only
              STATUS  current
              DESCRIPTION
                    "Receiving Yellow/Remote Alarm Indication. This counter is 
                      relevant for PLCP (external/internal) frame types only."
              ::= { prtDs3IntervalEntry 15 }

      prtDs3IntervalPlcpBIP OBJECT-TYPE
              SYNTAX  Gauge32
              MAX-ACCESS  read-only
              STATUS  current
              DESCRIPTION
                    " The counter associated with the number of BIP errors, 
                      encountered by a DS3 interface in the current 15 minute 
                      interval. This counter is relevant for PLCP (external/internal) 
                      frame types only."
              ::= { prtDs3IntervalEntry 16 }

      prtDs3IntervalPlcpFEBE OBJECT-TYPE
              SYNTAX  Gauge32
              MAX-ACCESS  read-only
              STATUS  current
              DESCRIPTION
                    " The counter associated with the number of FEBE
                      errors, encountered by a DS3 interface in the current
                      15 minute interval. This counter is relevant for PLCP
                      (external/internal) frame types only."
              ::= { prtDs3IntervalEntry 17 }

      prtDs3IntervalBPV OBJECT-TYPE
              SYNTAX  Gauge32
              MAX-ACCESS  read-only
              STATUS  current
              DESCRIPTION
                    " Number of BPVs (Bi-Polar Violations) , encountered by a 
                      DS3 interface in the specified 15 minute interval. 
                      This object is relevant only for Electrical Line
                      of Fomi-E3/T3."
              ::= { prtDs3IntervalEntry 18 }

      prtDs3IntervalLCE OBJECT-TYPE
              SYNTAX  Gauge32
              MAX-ACCESS  read-only
              STATUS  current
              DESCRIPTION
                    " Number of LCE (Link Code Errors) encountered 
                      by a DS3 interface in the specified 15 minute interval. 
                      This object is relevant only for Optical Links
                      of Fomi-E3/T3."
              ::= { prtDs3IntervalEntry 19 }


     prtDs3IntervalStatus OBJECT-TYPE
	          SYNTAX OCTET STRING  (SIZE (4))
              MAX-ACCESS  read-only
              STATUS  current
              DESCRIPTION
                      "The statuses of the current interval:
                        0 - Valid.
                        1 - redundantLinkSwitch - the link has been switched 
                            by a redundancy mechanism.
                        2 - discontinuity - module was partialy out.
                        4 - notValid - module is out."
              ::= { prtDs3IntervalEntry 20 }

-- the DS3 Total table

prtDs3TotalTable OBJECT-TYPE
              SYNTAX  SEQUENCE OF PrtDs3TotalEntry
              MAX-ACCESS  not-accessible
              STATUS  current
              DESCRIPTION
              " A list of Total entries."
              ::= { prtDs3PerfHistory 4 }

prtDs3TotalEntry OBJECT-TYPE
              SYNTAX  PrtDs3TotalEntry
              MAX-ACCESS  not-accessible
              STATUS  current
              DESCRIPTION
              "An entry of Total table."
              INDEX   { ifIndex }
              ::= { prtDs3TotalTable 1 }

PrtDs3TotalEntry     ::=
          SEQUENCE {
       	    prtDs3TotalUAS	Gauge32,
        	prtDs3TotalBPV	Gauge32,
            prtDs3TotalLCE  Gauge32,
			prtDs3TotalSES  Gauge32
            }

prtDs3TotalUAS OBJECT-TYPE
              SYNTAX  Gauge32
              MAX-ACCESS  read-only
              STATUS  current
              DESCRIPTION
              "Number of UASs (Unavailable Seconds) , encountered by a 
               DS3 interface in the previous 96 intervals.
               Invalid 15 minute intervals count as 0."
              ::= { prtDs3TotalEntry 6 }

prtDs3TotalBPV OBJECT-TYPE
              SYNTAX  Gauge32
              MAX-ACCESS  read-only
              STATUS  current
              DESCRIPTION
              "Number of BPVs (Bi-Polar Violations) , encountered by a 
               DS3 interface in the previous 96 intervals.
               Invalid 15 minute intervals count as 0."
              ::= { prtDs3TotalEntry 17 }

prtDs3TotalLCE OBJECT-TYPE
              SYNTAX  Gauge32
              MAX-ACCESS  read-only
              STATUS  current
              DESCRIPTION
              "Number of LCE (Link Code Errors) encountered 
               by a DS3 interface in the previous 96 intervals.
               Invalid 15 minute intervals count as 0."
              ::= { prtDs3TotalEntry 18 }
   
prtDs3TotalSES OBJECT-TYPE
              SYNTAX  Gauge32
              MAX-ACCESS  read-only
              STATUS  current
              DESCRIPTION
              "Number of SES (Severely Errored Seconds) encountered 
               by a DS3 interface in the previous 96 intervals.
               Invalid 15 minute intervals count as 0."
              ::= { prtDs3TotalEntry 19 } 


dsx3XConfigTable  OBJECT-TYPE
       SYNTAX      SEQUENCE OF Dsx3XConfigEntry
       MAX-ACCESS  not-accessible
       STATUS      current
       DESCRIPTION
       "An extension to the DS3 Configuration table."
       ::= { ds3Interface 2 }

dsx3XConfigEntry OBJECT-TYPE
       SYNTAX  Dsx3XConfigEntry
       MAX-ACCESS  not-accessible
       STATUS      current
       DESCRIPTION
       "An entry containing additional configuration
        parameters."
       AUGMENTS    { dsx3ConfigEntry }
      --  INDEX   {dsx3LineIndex }
       ::= { dsx3XConfigTable 1 }

Dsx3XConfigEntry ::= SEQUENCE {
         dsx3AisEnable				INTEGER,
    dsx3TxClockSource          INTEGER,
    dsx3TxPortQuality          INTEGER,
    dsx3TxClockInstance        Unsigned32 
 }

dsx3AisEnable  OBJECT-TYPE
       SYNTAX  INTEGER {
	   notApplicable(1),
       disable(2),
	   enable(3)
       }
	   MAX-ACCESS  read-write
	   STATUS  current
	   DESCRIPTION
	   "Enable/ disable AIS transmit when Ethernet (for TDMoIP) line is disconnected."
	   ::= { dsx3XConfigEntry 1 }

dsx3TxClockSource OBJECT-TYPE
     SYNTAX  INTEGER {
                loopTiming(1),
                localTiming(2),
                throughTiming(3),
                system (4),
                adaptive(5)
            }
     MAX-ACCESS  read-write
     STATUS  current
     DESCRIPTION
            "The source of Transmit Clock.

            loopTiming indicates that the recovered receive
            clock is used as the transmit clock.

            localTiming indicates that a local clock source is
            used or that an external clock is attached to the
            box containing the interface.

            throughTiming indicates that transmit clock is
            derived from the recovered receive clock of
            another DS3 interface.

            'system' indicates that the system clock
            is used as the transmit clock.

            'adaptive' indicates clock is recovered from PW using
            adaptive clock recovery mechanism."

     ::= { dsx3XConfigEntry 2}

dsx3TxPortQuality       OBJECT-TYPE
      SYNTAX  INTEGER
      {
        notApplicable       (1),
        stratum1            (2),
        stratum2            (3),
        stratum3            (4),
        stratum3e           (5),
        stratum4            (6)
      }
      MAX-ACCESS  read-write
      STATUS  current
      DESCRIPTION
      "This object indicates the DS3 port clock quality."
     ::= { dsx3XConfigEntry 3}

dsx3TxClockInstance OBJECT-TYPE
     SYNTAX  Unsigned32
     MAX-ACCESS  read-write
     STATUS  current
     DESCRIPTION
            "When dsx3TxClockSource is set to throughTiming(3) or
            adaptive(4), this parameter specifies the instanse of
            the clock domain or recovered clock, respectively, that
            shall be used for transmission "

     ::= { dsx3XConfigEntry 4}


-- The DS3/E3 Mapping Table

dsx3MappingTable OBJECT-TYPE
    SYNTAX  SEQUENCE OF Dsx3MappingEntry
    MAX-ACCESS  not-accessible
    STATUS  current
    DESCRIPTION
            "The DS3/E3 mapping table associates DS3/E3 channels
             with logical or physical interfaces.

            For example, consider a DS3 device with 16 T1's and 1 VCG.
			There are 28 logical/internal channels, numbered 1 through 28
			but only 17 are actually connected.

			We might describe the allocation of channels, in the dsx3MappingTable, as
            follows:
            dsx3MappingIfIndex.1. 1 = 1001  dsx3MappingIfIndex.1.15 = 1015
            dsx3MappingIfIndex.1. 2 = 1002  dsx3MappingIfIndex.1.16 = 1016
            dsx3MappingIfIndex.1. 3 = 1003  dsx3MappingIfIndex.1.17 = 1017
            dsx3MappingIfIndex.1. 4 = 1004  dsx3MappingIfIndex.1.18 =  0
            dsx3MappingIfIndex.1. 5 = 1005  dsx3MappingIfIndex.1.19 =  0
            dsx3MappingIfIndex.1. 6 = 1006  dsx3MappingIfIndex.1.20 =  0
            dsx3MappingIfIndex.1. 7 = 1007  dsx3MappingIfIndex.1.21 =  0
            dsx3MappingIfIndex.1. 8 = 1008  dsx3MappingIfIndex.1.22 =  0
            dsx3MappingIfIndex.1. 9 = 1009  dsx3MappingIfIndex.1.23 =  0
            dsx3MappingIfIndex.1.10 = 1010  dsx3MappingIfIndex.1.24 =  0
            dsx3MappingIfIndex.1.11 = 1011  dsx3MappingIfIndex.1.25 =  0
            dsx3MappingIfIndex.1.12 = 1012  dsx3MappingIfIndex.1.26 =  0
            dsx3MappingIfIndex.1.13 = 1013  dsx3MappingIfIndex.1.27 =  0
            dsx3MappingIfIndex.1.14 = 1014  dsx3MappingIfIndex.1.28 =  0
            
			Note that in the case above all channels are mapped to one T3 port with ifIndex = 1.
			The Channels 1...28 are represented via the 2nd index.
			The values of 1001...1016 are the T1 interface ifIndexes.
			The value of 1017 is the ifIndex of the VCG.
		    Unconnected channels have a value of 0.			
            "
     ::= { ds3Interface 3 }

dsx3MappingEntry OBJECT-TYPE
     SYNTAX  Dsx3MappingEntry
     MAX-ACCESS  not-accessible
     STATUS  deprecated
     DESCRIPTION
                    "An entry in the DS3 mapping table."
    INDEX   { dsx3MappingDs3Index, dsx3MappingNumber }
    ::= { dsx3MappingTable 1 }

Dsx3MappingEntry ::=
     SEQUENCE {
         dsx3MappingDs3Index     InterfaceIndex,
         dsx3MappingNumber       Unsigned32,
         dsx3MappingIfIndex      InterfaceIndex
    }

dsx3MappingDs3Index OBJECT-TYPE
    SYNTAX  InterfaceIndex
    MAX-ACCESS  not-accessible
    STATUS  current
    DESCRIPTION
            "The index value which uniquely identifies  the
            DS3/E3 interface to which this entry is applicable.
			This value is also equal to dsx3LineIndex used in dsx3ConfigEntry.
                        
            For RICi-16 this is the ifIndex of the T3 interface."
    ::= { dsx3MappingEntry 1 }

dsx3MappingNumber OBJECT-TYPE
    SYNTAX  Unsigned32
    MAX-ACCESS  not-accessible
    STATUS  current
    DESCRIPTION
            "The channel number for this entry.
            
            For RICi-16 this is the channel number 1...28."
   ::= { dsx3MappingEntry 2 }

dsx3MappingIfIndex OBJECT-TYPE
   SYNTAX  InterfaceIndex
   MAX-ACCESS  read-write
   STATUS  current
   DESCRIPTION
           "An index value that uniquely identifies a logical or physical
           interface mapped to a DS3/E3 channel.
           If no interface is currently using a channel, the value should be zero.
           If a single interface occupies more  than one channel,
           that ifIndex value will be found in multiple channels.
           
           For RICi-16 this is the ifIndex of the T1 or VCG interface."
   ::= { dsx3MappingEntry 3 }

-- E3/T3/DS3 Common Trap Definitions

--NOTIFICATIONs

-- Alarm and Events TRAPS


-- REMOTE ALARM INDICATION (RAI)
e3t3Rai  NOTIFICATION-TYPE
	OBJECTS { alarmEventLogSourceName, alarmEventLogAlarmOrEventId, alarmEventLogDescription, 
     alarmEventLogSeverity, alarmEventLogDateAndTime, alarmEventReason, 
     ifAlias, dsx3LineStatus } 
      STATUS  current
      DESCRIPTION
      "This trap shows that a Remote Alarm Indication (RAI) was detected by an E3/T3 interface.
      "
      ::= { prtDS3Events  1 }


-- ALARM INDICATION SIGNAL (AIS)
e3t3Ais  NOTIFICATION-TYPE
	OBJECTS { alarmEventLogSourceName, alarmEventLogAlarmOrEventId, alarmEventLogDescription, 
     alarmEventLogSeverity, alarmEventLogDateAndTime, alarmEventReason, 
     ifAlias, dsx3LineStatus } 
      STATUS  current
      DESCRIPTION
      "This trap indicates that an Alarm Indication Signal (AIS) was detected
       on an E3/T3 interface.
      "
      ::= { prtDS3Events  2 }


      -- LOSS OF FRAME (LOF)
e3t3Lof  NOTIFICATION-TYPE
	OBJECTS { alarmEventLogSourceName, alarmEventLogAlarmOrEventId, alarmEventLogDescription, 
     alarmEventLogSeverity, alarmEventLogDateAndTime, alarmEventReason, 
     ifAlias, dsx3LineStatus } 
      STATUS  current
      DESCRIPTION
      "This trap indicates that a Loss of Frame (LOF) was detected on an E3/T3 interface.
      "
      ::= { prtDS3Events  3 }


-- LOSS OF SIGNAL (LOS)
e3t3Los  NOTIFICATION-TYPE
	OBJECTS { alarmEventLogSourceName, alarmEventLogAlarmOrEventId, alarmEventLogDescription, 
     alarmEventLogSeverity, alarmEventLogDateAndTime, alarmEventReason, 
     ifAlias, dsx3LineStatus } 
      STATUS  current
      DESCRIPTION
      "This trap indicates that a Loss of signal was detected on an E3/T3 interface.
      "
      ::= { prtDS3Events  4}

END

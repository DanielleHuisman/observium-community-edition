RAD-Dacs-MIB DEFINITIONS ::= BEGIN

-- Title:     Dacs MIB
-- *** This file is for the modified newmasking MIB. ***
-- Copyright 2000 RAD Data Communications, Ltd.
-- All Rights Reserved.  

-- It is RAD's intent to encourage the widespread use of
-- this Specification in connection with the management of
-- RAD products. RAD grants vendors, end-users,
-- and other interested parties a non-exclusive license to
-- use this Specification in connection with the management
-- of RAD products.

-- This Specification is supplied "as is," and RAD makes
-- no warranty, either express or implied, as to the use,
-- operation, condition, or performance of the Specification.


IMPORTS

       entPhysicalEntry, PhysicalIndexOrZero, entPhysicalSoftwareRev, 
       entPhysicalAlias, entPhysicalHardwareRev, entPhysicalDescr     FROM  ENTITY-MIB
       InetAddressType, InetAddress     FROM  INET-ADDRESS-MIB
       SnmpAdminString     FROM  SNMP-FRAMEWORK-MIB
       sysName     FROM  SNMPv2-MIB
       Integer32, TimeTicks, Gauge32, 
       Unsigned32, OBJECT-TYPE, MODULE-IDENTITY, 
       NOTIFICATION-TYPE, OBJECT-IDENTITY     FROM  SNMPv2-SMI
       DisplayString, RowStatus, MacAddress, 
       TruthValue     FROM  SNMPv2-TC
       radWan     FROM  RAD-SMI-MIB
       alarmEventLogSourceName, alarmEventLogAlarmOrEventId, alarmEventLogDescription, 
       alarmEventLogSeverity, alarmEventLogDateAndTime, systemsEvents, 
       agnLed, alarmEventReason, agnThresholdMin, 
       agnThresholdMax, agnThresholdUom     FROM  RAD-GEN-MIB
       protectGroupLastSwitchReason, protectGroupLastCmd     FROM  RAD-Protection-MIB
       SlotType, CardType, ProtectGroupCmdType, 
       ProtectLastSwitchReasonType     FROM  RAD-TC; 


    dacsMux MODULE-IDENTITY
        LAST-UPDATED "201604211736Z"  -- April 21, 2016
        ORGANIZATION "RAD Data Communications Ltd."
        CONTACT-INFO
        "System Department
     
         Email:  mibs@rad.com    
         Postal: RAD Data Communications Ltd.
                 24 Raoul Wallenberg St.
                 Tel-Aviv 6971920
                 Israel

         Phone:  +972-3-645-5421
         Fax:    +972-3-760-7844"
         DESCRIPTION
            "Digital Access and Cross Connect System device MIB." 
    ::= { radWan 3 }


systemDacsMux OBJECT IDENTIFIER ::= {dacsMux 1}
mdlDacsMux    OBJECT IDENTIFIER ::= {dacsMux 2}
prtDacsMux    OBJECT IDENTIFIER ::= {dacsMux 3}
genDacsMux    OBJECT IDENTIFIER ::= {dacsMux 4}
    

--System level of DACS MIB
--
--Sa  - data specific to a stand-alone unit
--Hub - data specific to a Hub unit
--Rest of the branches are common to both types of units.

sysSa         OBJECT IDENTIFIER ::= {systemDacsMux 1}
sysHub        OBJECT IDENTIFIER ::= {systemDacsMux 2}
sysStatus     OBJECT IDENTIFIER ::= {systemDacsMux 3}
sysCurrentAlr OBJECT IDENTIFIER ::= {systemDacsMux 4}
sysBufferAlr  OBJECT IDENTIFIER ::= {systemDacsMux 5}
sysConfig     OBJECT IDENTIFIER ::= {systemDacsMux 6}
sysDbase      OBJECT IDENTIFIER ::= {systemDacsMux 7}


--Stand-alone specific parameters

sysSaSwchStatus OBJECT-TYPE
      SYNTAX  Integer32
      MAX-ACCESS  read-only
      STATUS  current
      DESCRIPTION
      "This object indicates the status of the switches on 
       the SA unit.
       Each switch is represented by a bit. The status is a sum
       of 2**n, according to the bits.
       
	   For SMODs products see modem's specification.
	   
	   For DXC product see the following:
       There are 4 switches:
       bit 0  SP-PAR (LSB)  '1' - Default parameters    
       bit 1  PSWRD         '1' - Password=default
                            '0' - Password=user selected
       bit 2  DB-INIT       '1' - DB initiated with default
                            '0' - DB initiated with NVRAM contents 
       bit 3  PC-SP  (MSB)  '1' - Management by terminal only
                            '0' - Management by NMS
       Example: If SP-PAR  and PSWRD bits are set ('1'), the value
             will be 3 (2**1 + 2**0).
       When the status of the switches is unknown, the value of
       this object will be 255."
      ::= { sysSa 1}

sysSaSwRevision OBJECT-TYPE
      SYNTAX  DisplayString (SIZE (0..255))
      MAX-ACCESS  read-only
      STATUS  current
      DESCRIPTION
      "This object indicates the Software revision of the 
       system."
      ::= {sysSa 2}

sysSaHwVersion OBJECT-TYPE
      SYNTAX  DisplayString (SIZE (0..255))
      MAX-ACCESS  read-only
      STATUS  current
      DESCRIPTION
      "This object indicates the Hardware version of the 
       system."
      ::= {sysSa 3}

sysSaPorts OBJECT-TYPE
      SYNTAX  Integer32
      MAX-ACCESS  read-only
      STATUS  current
      DESCRIPTION
   "This object indicates the ports that are present in the 
    system.
    Each possible port is represented by a bit.
    The value of this object is a sum of 2**n, n=number of bits.
    '1' - means that the port exists
    '0' - means that the port does not exist
    For detailed bit assignment, see product's spec.
    Bit 0 = LSB
    When this object is not relevant, the value will be 0.
    In some cases, this object may represent ports configuration
    of the system AND its far-end unit."
   ::= {sysSa 4}

sysSaReadSwch OBJECT-TYPE
      SYNTAX  Integer32
      MAX-ACCESS  read-write
      STATUS  current
      DESCRIPTION
      "This object indicates wether the configuration will be read from the DIP switches
       on the SA (stand alone) unit.
       Each switch is represented by a bit.
       If the bit is 1: the configuration will be read from the HW switch position.
       If the bit is 0: the configuration will be read from the SW user configuration.
       
       The DIP switches are different in each of the RAD devices.
       In the Tiny Router (starting from the LSB) the following switches exist:
       Bit 0: WAN Loop
       Bit 1: LAN Full Duplex (When LAN AUI connector, it is SQE)
       Bit 2: PPP (When WAN 4 Wire connector, it is LONG)
       Bit 3: IP Learn"
   ::= {sysSa 5}

sysSaBuActivePort OBJECT-TYPE
      SYNTAX  INTEGER
	  {
	  notApplicable (1),
	  e1T1orSerial  (2),
	  eth           (3),
	  primary       (4),
	  secondary     (5),
	  third         (6),
	  fourth		(7)
	  }
      MAX-ACCESS  read-only
      STATUS  current
      DESCRIPTION
      "This object shows through which port the traffic is flowing
      (the current Active Port) when the Backup mechanism exists.
      When No Backup exists in the device, the value should be: notApplicable(1)."      
      ::= {sysSa 6}


--Hub specific parameters

--Hub Cassis data

sysChas  OBJECT IDENTIFIER ::= {sysHub 1}

chassTotalNoOfSlt  OBJECT-TYPE
      SYNTAX  Integer32
      MAX-ACCESS  read-only
      STATUS  current
      DESCRIPTION
      "This object indicates the number of physical slots in 
       the Hub chassis."
      ::= { sysChas 1 }

chassTotalNoOfIoSlt  OBJECT-TYPE
      SYNTAX  Integer32
      MAX-ACCESS  read-only
      STATUS  current
      DESCRIPTION
      "This object indicates the total number of physical IO slots 
       in the chassis, (not all slots must be occupied and active)."
      ::= { sysChas 2 }

chassTotalNoOfPsSlt  OBJECT-TYPE
      SYNTAX  Integer32
      MAX-ACCESS  read-only
      STATUS  current
      DESCRIPTION
      "This object indicates the number of physical Power Supply 
       slots in the chassis."
      ::= { sysChas 3 }

chassTotalNoOfClSlt  OBJECT-TYPE
      SYNTAX  Integer32
      MAX-ACCESS  read-only
      STATUS  current
      DESCRIPTION
      "This object indicates the number of physical Common Logic 
       slots in the chassis."
      ::= { sysChas 4 }

chassTotalNoOfMlSlt  OBJECT-TYPE
      SYNTAX  Integer32
      MAX-ACCESS  read-only
      STATUS  current
      DESCRIPTION
      "This object indicates the number of physical Main Link 
       slots in the chassis (Kmux)."
      ::= { sysChas 5 }


--Hub DCL parameters

sysDcl  OBJECT IDENTIFIER ::= {sysHub 2}


sysDclTable  OBJECT-TYPE
      SYNTAX SEQUENCE OF SysDclEntry
      MAX-ACCESS not-accessible
      STATUS  current
      DESCRIPTION
      "All the entries of this table are identical (have the 
       same value) for all the configurations (1..255) except 
       the TmpCnfg.
       The write operation into the Table Objects is valid only
       for the TmpCnfg entry."
       ::= { sysDcl 1}

sysDclEntry OBJECT-TYPE
      SYNTAX SysDclEntry
      MAX-ACCESS not-accessible
      STATUS current
	DESCRIPTION  "An entry in table."
	INDEX {sysDclCnfgIdx}
      ::= { sysDclTable 1}

SysDclEntry ::=
      SEQUENCE {
   		sysDclCnfgIdx        		Integer32,
   		sysDclRedundancy     		INTEGER,
   		sysDclActiveCl       		INTEGER,
   		sysDclFlipDelay      		Integer32,
		sysDclFlipUponStnClk 		INTEGER,
		sysDclChFailThreshold 		Integer32,
		sysDclChPriority 	 		OCTET STRING,
		sysDclConfigDownloadSrc  	INTEGER,
		sysDclSwDownloadSrc    	 	INTEGER,
		sysDclRedundancyStatus		BITS
      }

sysDclCnfgIdx OBJECT-TYPE
      SYNTAX Integer32 (1..255)
      MAX-ACCESS read-only
      STATUS current
      DESCRIPTION
      "This object indicates the Idx of the Cnfg(1..255) 
       being accessed ; Idx of 255 relates to the TmpCnfg.
       This object is identical for all the configurations (1..255).
       Only the TmpCnf(255) might have a  different value.
       For devices that work on line with NMS (no Temp configuration in NMS),
       Get and Set will be performed with index value of sysDclCnfgIdx = 1."
      ::= { sysDclEntry 1}
-- In phase I only the values 1 (Cnfg1) and 255 (temp) are valid.

sysDclRedundancy  OBJECT-TYPE
      SYNTAX  INTEGER
   {
   off (2),
   on  (3)
   }
      MAX-ACCESS  read-write
      STATUS  current
      DESCRIPTION
   " DCL redundancy desired state."
   ::= {sysDclEntry 2}

sysDclActiveCl  OBJECT-TYPE
      SYNTAX  INTEGER
   {
   auto (1),
   dclA (2),
   dclB (3)
   }
      MAX-ACCESS  read-write
      STATUS  current
      DESCRIPTION
   "Active desired DCL.
    When 'auto' is selected, the system automatically selects
    the active DCL."
   ::= {sysDclEntry 3}

sysDclFlipDelay  OBJECT-TYPE
      SYNTAX  Integer32
--   {
--   t1min (1),
--   t2min (2),
--   t3min (3),
--   t4min (4)
--   }    
      MAX-ACCESS  read-write
      STATUS  current
      DESCRIPTION
   "If one DCL flip occurred and a second one should be
    performed, the time from the previous flip is checked.
    If the time is shorter than the delay specified here,
    the system should delay the flip operation until time reaches the specified delay.
    For DXC the values are 1 minute to 4 minutes (1..4).
    For Optimux-155-1 and Optimux-155-3 the values are: 0...60 Sec.
	0 means No Delay."
   ::= {sysDclEntry 4}

sysDclFlipUponStnClk  OBJECT-TYPE
      SYNTAX  INTEGER
   {
   notApplicable (1),
   no            (2),
   yes           (3)
   }    
      MAX-ACCESS  read-write
      STATUS  current
      DESCRIPTION
   "This object allows user to decide (yes/no) if Agent should Flip from 
    one DCL card to another, when there is Station Clock Fail in 
    the Online DCL card."
   ::= {sysDclEntry 5}

sysDclChFailThreshold  OBJECT-TYPE
      SYNTAX  Integer32
      MAX-ACCESS  read-write
      STATUS  current
      DESCRIPTION
   "This object indicates the number of failed channels that will trigger the
    redundancy procedure."
   ::= {sysDclEntry 6}

sysDclChPriority  OBJECT-TYPE
      SYNTAX  OCTET STRING
      MAX-ACCESS  read-write
      STATUS  current
      DESCRIPTION
   "This object indicates the Priority for all the channels in the Main Access
    (Common Logic) card. Each channel is represented by 1 bit.
	The order of the bits in each byte is from Right to Left (LSB Bit to MSB)
	starting from BIT 0:    7  6  5  4  3  2  1  0 

    Channel no. 1 is represented by bit 0.
    Channel no. 2 is represented by bit 1.
    Channel no. n is represented by bit n-1.

    The value of the bit shows the priority.
    For bit value = 1, Priority = High.
    For bit value = 0, Priority = Low." 
    ::= {sysDclEntry 7}

sysDclConfigDownloadSrc  OBJECT-TYPE
      SYNTAX  INTEGER
   {
   off	(1),
   dclA (2),
   dclB (3)
   }
      MAX-ACCESS  read-write
      STATUS  current
      DESCRIPTION
      "In case of mismatch between the 2 CL card's configuration, the user can decide 
       which card has the suitable configuration.
       The selected configuration will be downloaded from card A to card B
       if the value is dclA(2) or from card B to card A if the value is dclB(3).
       off(1) is used by part of the devices. In this case, after operation ends -
        value should be automatically set to off(1), which is the default state."  
   ::= {sysDclEntry 8}


sysDclSwDownloadSrc    OBJECT-TYPE
      SYNTAX  INTEGER
   {
   off	(1),
   dclA (2),
   dclB (3)
   }
      MAX-ACCESS  read-write
      STATUS  current
      DESCRIPTION
      "In case of mismatch between the 2 CL card's software, the user can decide 
       which card has the suitable SW.
       The selected SW will be downloaded from card A to card B if the value is dclA(2)
       or from card B to card A if the value is dclB(3).
       off(1) is used by part of the devices. In this case, after operation ends -
       value should be automatically set to off(1), which is the default state."  
   ::= {sysDclEntry 9}

sysDclRedundancyStatus 	 OBJECT-TYPE
      SYNTAX      BITS
           {
			cnfgMismatch		(0),
			swMismatch			(1),
			cardAAbsent			(2),
			cardBAbsent			(3),
			lossOfCommunication	(4),
			hwMismatch			(5),
			cnfgUpdate			(6),
			swUpdate			(7)
           }
	  MAX-ACCESS  read-only
      STATUS  current
      DESCRIPTION
         "Bit map representing current Redundancy Status.
          bit 0 - Indicates mismatch between the 2 CL cards' Configuration
          bit 1 - Indicates mismatch between the 2 CL cards' Software.
		  bit 2 - Indicates CL card A Absence.
		  bit 3 - Indicates CL card B Absence.
          bit 4 - Indicates Loss of Communication between the 2 CL cards.
          bit 5 - Indicates mismatch between the 2 CL cards' Hardware.
          bit 6 - Indicates Configuraton update is in process.
          bit 7 - Indicates Software update is in process.
          "
   ::= {sysDclEntry 10}


sysDclOnline  OBJECT-TYPE
      SYNTAX  INTEGER
   {
   dclA (1),
   dclB (2)
   }
      MAX-ACCESS  read-only
      STATUS  current
      DESCRIPTION
   "The active Dcl card of the agent."
   ::= {sysDcl 2}

sysDclCopyDbTable  OBJECT-TYPE
      SYNTAX SEQUENCE OF SysDclCopyDbEntry
      MAX-ACCESS not-accessible
      STATUS  current
      DESCRIPTION
      "This table enables to copy a cofiguration from the Offline
       Dcl to the Online Dcl."
       ::= { sysDcl 3}

sysDclCopyDbEntry OBJECT-TYPE
      SYNTAX SysDclCopyDbEntry
      MAX-ACCESS not-accessible
      STATUS current
	DESCRIPTION  "An entry in table."
	INDEX {sysDclCopyDbIdx}
      ::= { sysDclCopyDbTable 1}

SysDclCopyDbEntry ::=
      SEQUENCE {
   		sysDclCopyDbIdx       Integer32,
   		sysDclCopyDbCmd       INTEGER
      }

sysDclCopyDbIdx OBJECT-TYPE
      SYNTAX Integer32 (1..255)
      MAX-ACCESS read-only
      STATUS current
      DESCRIPTION
      "This object indicates the Idx of the Cnfg(1..255) 
       being accessed. "
      ::= { sysDclCopyDbEntry 1}

sysDclCopyDbCmd OBJECT-TYPE
      SYNTAX INTEGER {
   off(2),
   on (3)
   }
      MAX-ACCESS read-write
      STATUS current
      DESCRIPTION
      "When this command is sent to the agent, on(3), the Database
       specified (Db Idx), will be copied from the Offline Dcl 
       to the Online Dcl. Afterwards the value of this object will 
       automatically change to off(2). "
      ::= { sysDclCopyDbEntry 2}

sysDclFlipCmd OBJECT-TYPE
      SYNTAX INTEGER {
      off  (2),
      flip (3)
      }
      MAX-ACCESS read-write
      STATUS current
      DESCRIPTION
      "When the 'flip(3)' command is received by Agent, it will flip (switch) 
       between Offline Dcl and Online Dcl cards. Afterwards the value of 
       this object will automatically change to off(2)."
      ::= { sysDcl 4}


--General System - General Status parameters 

sysSDateFormat  OBJECT-TYPE
      SYNTAX  INTEGER
       {
          ddMMYYYY (1),
          mmDDYYYY (2),
      yyyyDDMM (3),
          yyyyMMDD (4)
       }
      MAX-ACCESS  read-write
      STATUS  current
      DESCRIPTION
      "This object indicates the date and time format used for the
       sysSDateAndTimeCmd and for the alarm buffer report."
      ::= { sysStatus 1 }

sysSDateCmd  OBJECT-TYPE
      SYNTAX  DisplayString (SIZE (0..255))
      MAX-ACCESS  read-write
      STATUS  current
      DESCRIPTION
      "This object indicates the current date as it is known by the
       agent using its own real-time clock. The format would be as
       specified by the sysSDateFormat.
       This  parameter can be set for time synchronization between
       the NMS and the Agent.
       * For KM-2100 V1 and FCD-T1/E1 - the string should contain 
         '/' signs between day, month and year. Example: 12/08/1998.
       * For DXC and rest of the products - the string should contain 
         '-' signs between day, month and year. Example: 12-08-1998.
       The day value will be in the range: 1..31.
       The month value will be in the range: 1..12.
       The year value will be in the range: 1996..2050 for products
       supporting the '-' format."
      ::= { sysStatus 2 }

sysSTimeCmd  OBJECT-TYPE
      SYNTAX  DisplayString (SIZE (0..255))
      MAX-ACCESS  read-write
      STATUS  current
      DESCRIPTION
      "This object indicates the current time as it is known by the
       agent using its own real-time clock.
       This  parameter can be set for time synchronization between
       the NMS and the Agent.
       The string should contain ':' signs between hour, minute 
       and second. Example: 11:05:58."
      ::= { sysStatus 3 }

sysSActiveCnfg  OBJECT-TYPE
      SYNTAX  Integer32
      MAX-ACCESS  read-only
      STATUS  current
      DESCRIPTION
      "This object specifies the configuration number,
       that is currently  active and running."
      ::= { sysStatus 4 }
-- return 1 (db1) in phase I

sysSEditCnfg OBJECT-TYPE
      SYNTAX  Integer32
      MAX-ACCESS  read-only
      STATUS  current
      DESCRIPTION
      "This object indicates the  unique configuration number that
       is currently loaded into the tmp working space  for 
       manipulation and update operations. Value of 255 means no 
       config. is under editing process."
      ::= { sysStatus 5 }
-- return 1 (db1) in phase I


sysSEditBy OBJECT-TYPE
      SYNTAX  INTEGER
       {
           none            (1),
           snmp            (2),
           terCon1         (3),
           terCon2         (4),
           terInbandCon1   (5),
           terInbandCon2   (6),
           lcd             (7)
       }
      MAX-ACCESS  read-only
      STATUS  current
      DESCRIPTION
      "This entry indicates which MMI application is working on  
       the edited config.
       The editing phase starts at the first modify operation and 
       ends after a load operation."
      ::= { sysStatus 6 }

sysSClkSrc  OBJECT-TYPE
      SYNTAX  INTEGER
    {
        master  (1),
        fallback(2),
        internal(3),
        ml      (4) 
    }
      MAX-ACCESS  read-only
      STATUS  current
      DESCRIPTION
     "This entry indicates the source of the system clock."
      ::= { sysStatus 7 }

sysSAlrStatus OBJECT-TYPE
      SYNTAX  INTEGER
       {
  off      (2),
  major    (3),
  minor    (4),
  event    (5),
  warning  (6),
  critical (7)
       }
      MAX-ACCESS  read-only
      STATUS  current
      DESCRIPTION
      "Indicates the current alarm state only for system level.
       This object will be : 
       - critical(7): when there is at least one active (ON) critical 
                    alarm .
       - major (3): when there is no active critical alarm, but there is
                    at least one active (ON) major alarm .
       - minor (4): when there is no active major or critical alarm, but 
                    there is at least one active minor alarm.
       - warning (6): when there is no active major, critical or minor alarm, but 
                    there is at least one active warning alarm.
       - event (5): when there is no active alarm of another type, but 
                    there is at least one active event alarm.
       - off(2): when there is no active (ON) alarm (since last clear operation)."
      ::= { sysStatus 8 }

sysSAlrStatusAll OBJECT-TYPE
      SYNTAX  INTEGER
       {
  off      (2),
  major    (3),
  minor    (4),
  event    (5),
  warning  (6),
  critical (7)
       }
      MAX-ACCESS  read-only
      STATUS  current
      DESCRIPTION
      "Indicates the current alarm state including all levels: 
       system, card, port.
       - critical(7): when there is at least one active (ON) critical 
                    alarm .
       - major (3): when there is no active critical alarm, but there is
                    at least one active (ON) major alarm .
       - minor (4): when there is no active major or critical alarm, but 
                    there is at least one active minor alarm.
       - warning (6): when there is no active major, critical or minor alarm, but 
                    there is at least one active warning alarm.
       - event (5): when there is no active alarm of another type, but 
                    there is at least one active event alarm.
       - off(2): when there is no active (ON) alarm (since last clear operation)."
      ::= { sysStatus 9 }

sysSTestStatus OBJECT-TYPE
      SYNTAX  INTEGER
       {
  off(2),
  on (3)
       }
      MAX-ACCESS  read-only
      STATUS  current
      DESCRIPTION
      "Indicates the current test status (for all levels: system,
       card, port).
       This attribute will be set to: 
       - on(3): when there is at least one test in progress on the
                system/card/port
         otherwise the value will be off(2)."
      ::= { sysStatus 10 }


sysSSanityCheckStatus OBJECT-TYPE
      SYNTAX  INTEGER
       {
  unknown (1),
  fail    (2),
  warning (3),
  ok      (4)
       }
      MAX-ACCESS  read-only
      STATUS  current
      DESCRIPTION
      "Upon completion of the Sanity Check process on the TmpCnfg 
       this object will be set to:
       - fail(2): when there is at least one error (which is 
                  not just a warning) encountered
                  otherwise,
       - warning(3): when there are only warnings
                  otherwise,
       - ok(4).
       The value should be unknown(1), if the TmpCnfg was changed 
       after the last Sanity check."
      ::= { sysStatus 11 }

sysSNoOfSanityCheckErr OBJECT-TYPE
      SYNTAX  Integer32
      MAX-ACCESS  read-only
      STATUS  current
      DESCRIPTION
      "This object indicates the number of errors/warnings 
       discovered by the last Sanity Check process."
      ::= { sysStatus 12 }

sysSErrListTable OBJECT-TYPE
      SYNTAX SEQUENCE OF SysSErrListEntry
      MAX-ACCESS not-accessible
      STATUS current
	DESCRIPTION  "A table."
	::=  { sysStatus 13 }

sysSErrListEntry OBJECT-TYPE
      SYNTAX SysSErrListEntry
      MAX-ACCESS not-accessible
      STATUS current
	DESCRIPTION  "An entry in table."
	INDEX { sysSErrType, sysSErrIdx}
      ::= { sysSErrListTable 1}

SysSErrListEntry ::=
      SEQUENCE {
  sysSErrType         INTEGER,
  sysSErrIdx          Integer32,
  sysSErrDescription  DisplayString 
      }

sysSErrType OBJECT-TYPE
      SYNTAX  INTEGER
   {
   error    (1),
   warning  (2)
   }
      MAX-ACCESS  read-only
      STATUS  current
      DESCRIPTION
      "The errors are recorded in the agent, in two separate lists, 
       according to their type:  error or warning."
    ::= { sysSErrListEntry 1}

sysSErrIdx OBJECT-TYPE
      SYNTAX  Integer32
      MAX-ACCESS  read-only
      STATUS  current
      DESCRIPTION
      "Unique index number to identify an entry in the error 
       or warning list .
       The maximum value  cannot exceed the value of
       'sysSNoOfSanityCheckErr' (actually, the sum of the Errors
       list max. index and the Warning list max. index should
       equal the value of'sysSNoOfSanityCheckErr')."
    ::= { sysSErrListEntry 2}

sysSErrDescription OBJECT-TYPE
      SYNTAX  DisplayString (SIZE (0..255))
      MAX-ACCESS  read-only
      STATUS  current
      DESCRIPTION
      "This object is a full text description of the sanity check
       error including error code, IO slot and port numbers related to
       the code ."
  ::= { sysSErrListEntry 3}

sysSMaxNoOfCnfg OBJECT-TYPE
      SYNTAX  Integer32
      MAX-ACCESS  read-only
      STATUS  current
      DESCRIPTION
      "Maximum number of configurations that can be defined and 
       stored in the DACS agent.
       If the DACS agent has a large capacity, the maximum will be 
       limited to 254."
      ::= { sysStatus 14 }
-- return 1 (db1) in phase I

sysSSelfTestResult OBJECT-TYPE
      SYNTAX  Integer32
      MAX-ACCESS  read-only
      STATUS  current
      DESCRIPTION
      "The test is performed by the active Common Logic card.
       The result will be a sum of 2**n according to the following
       bit convention:
    For DXC:
    bit 0   Database 1 Checksum Error (LSB)
    bit 1   Database 2 Checksum Error
    bit 2   I/O Expander Error
    bit 3   Counter Error
    bit 4   Matrix DPR Error
    bit 5   PS-A  5 Volt Error
    bit 6   PS-A 12 Volt Error
    bit 7   PS-B  5 Volt Error
    bit 8   PS-B 12 Volt Error
    bit 9   EPROM Failure

    For FCD:
    bit 0   I/O Expander Error (LSB)
    bit 1   Counter Error
    bit 2   EPROM Failure
    bit 3   Illegal Sys Config
    bit 4   SFIFO
    bit 5   EPIC Failure (ISDN)
    bit 6   XL Flash Fail  -- for MSDSL interface
    bit 7   XL MITEL Fail  -- for MSDSL interface 
    bit 8   XL Framer Fail -- for MSDSL interface
    bit 9   XL DSP Fail    -- for MSDSL interface 

	For LRS52  - refer to product's spec
     
    When a bit is ('1'), the error exists.
    When NO ERROR is encountered, this object's value will be 0."
      ::= { sysStatus 15 }

sysSRelayState OBJECT-TYPE
      SYNTAX  INTEGER
       {
  notApplicable (1),
  off(2),
  on (3)
       }
      MAX-ACCESS  read-only
      STATUS  current
      DESCRIPTION
      "Indicates the current state of the alarm relay.
       notApplicable - for agents that do not support this object."
      ::= { sysStatus 16 }

sysSInvertedAlr OBJECT-TYPE
      SYNTAX  INTEGER
       {
  notApplicable (1),
  no  (2),
  yes (3)
       }
      MAX-ACCESS  read-only
      STATUS  current
      DESCRIPTION
      "Indicates if there is any Inverted alarm at any level of the 
       system (sys, card, port).
       notApplicable - for agents that do not support this object."
      ::= { sysStatus 17 }

--The following table reports all the Flip events due to I/O Redundancy
--since last Clear command of the table. 

sysSRdnFlipTable OBJECT-TYPE
      SYNTAX SEQUENCE OF SysSRdnFlipEntry
      MAX-ACCESS not-accessible
      STATUS current
      DESCRIPTION
      "This table includes all the Flip events due to I/O Redundancy since
       last Clear command of this table."
      ::= { sysStatus 18 }

sysSRdnFlipEntry OBJECT-TYPE
      SYNTAX SysSRdnFlipEntry
      MAX-ACCESS not-accessible
      STATUS current
	DESCRIPTION  "An entry in table."
	INDEX { sysSRdnFlipIdx}
      ::= { sysSRdnFlipTable 1}

SysSRdnFlipEntry ::=
      SEQUENCE {
     sysSRdnFlipIdx   Integer32,
     sysSRdnFlipSlot  INTEGER,
     sysSRdnFlipPort  Integer32,
     sysSRdnFlipCause DisplayString,
     sysSRdnFlipDate  DisplayString,
     sysSRdnFlipTime  DisplayString
      }

sysSRdnFlipIdx OBJECT-TYPE
      SYNTAX  Integer32
      MAX-ACCESS  read-only
      STATUS  current
      DESCRIPTION
      "Unique index number to identify an entry in the Redundancy Flip list."
      ::= { sysSRdnFlipEntry 1}

sysSRdnFlipSlot OBJECT-TYPE
      SYNTAX  INTEGER
       {
       io1   (5),
       io2   (6),
       io3   (7),
       io4   (8),
       io5   (9),
       io6  (10),
       io7  (11),
       io8  (12),
       io9  (13),
       io10 (14),
       io11 (15),
       io12 (16),
       io13 (17),
       io14 (18),
       io15 (19),
       notApplicable (255)
       }
      MAX-ACCESS  read-only
      STATUS  current
      DESCRIPTION
      "The slot number from which Flip was performed."      
      ::= { sysSRdnFlipEntry 2}

sysSRdnFlipPort OBJECT-TYPE
      SYNTAX  Integer32 
      MAX-ACCESS  read-only
      STATUS  current
      DESCRIPTION
      "The port number from which Flip was performed.
	   For DXC:
	   For external ports the convention used will be:
         - first two digits will be: (IO slot number+10)
         - last one/two digits will be the port number within the 
           card, in odd numbers:
           port1 = 1
           port2 = 3
           port3 = 5 
           etc...
           Example: port2 of IO slot 11 will be: 213 .
       For internal ports the convention used will be:
         - first two digits will be: (IO slot number+10)
         - last one/two digits will be the port number within the 
           card, in even numbers:
           port1 = 2
           port2 = 4
           port3 = 6 
           etc...
           Example: port2 of IO slot 11 will be: 214 .

       For MP:
	   For external ports, the value will be as that of the port in the
	       card. Example: external-3 -> 3
                          external-4 -> 4
	   For internal ports, the value will be 100 + the port in the
	       card. Example: internal-1 -> 101
                          internal-4 -> 104	       
    
       100=notApplicable (when Redundancy is at card level)."      
      ::= { sysSRdnFlipEntry 3 }

sysSRdnFlipCause OBJECT-TYPE
      SYNTAX  DisplayString 
      MAX-ACCESS  read-only
      STATUS  current
      DESCRIPTION
      "The last cause that caused the Flip from the Slot (Port)
       of sysSRdnSlot, sysSRdnPort."
      ::= { sysSRdnFlipEntry 4}

sysSRdnFlipDate OBJECT-TYPE
      SYNTAX  DisplayString 
      MAX-ACCESS  read-only
      STATUS  current
      DESCRIPTION
      "Flip event Date. The format will be the one selected by user for 
       sysSDateFormat."
      ::= { sysSRdnFlipEntry 5}

sysSRdnFlipTime OBJECT-TYPE
      SYNTAX  DisplayString 
      MAX-ACCESS  read-only
      STATUS  current
      DESCRIPTION
      "Flip event Time. The format will be hh:mm:ss."
      ::= { sysSRdnFlipEntry 6}

sysSRdnFlipTableClearCmd OBJECT-TYPE
      SYNTAX  INTEGER
       {
         off  (2),
         on   (3)
       }
      MAX-ACCESS  read-write
      STATUS  current
      DESCRIPTION
      "This command, when Set to 'on', clears the Redundancy  Flip 
       table (sysSRdnFlipTable).
       After clear is performed, the agent will turn the value to 'off'
       automatically."
      ::= { sysStatus 19 }

sysSRdnFlipCmd OBJECT-TYPE
      SYNTAX  OBJECT IDENTIFIER
      MAX-ACCESS  read-write
      STATUS  current
      DESCRIPTION
      "This object enables the user to send a command to the Agent, to Flip
       from a current Online IO card to its Redundant card.  
       The value sent will be an Object Identifier of an entry in the sysCRdnTable.
       This entry defines the Redundant couple of Slots on which the Flip
       is applied.
       Setting this object, will cause the Agent to Flip from current Online
       card to its Redundant card.
       This manual flip command is applicable only for entries having 
       Redundancy Mode=Y Cable.        
       
       For Vmux: This command will cause flipping from Secondary or Third Link to the
       Primary Link. If the active link is the primary link, the agent will flip to the
       secondary link. The value sent will be the Object Identifier of the following
       Table: agnCBuMlTable.
       
       Agent will send the value 0 for Get."
      ::= { sysStatus 20}

sysSBusTable OBJECT-TYPE
      SYNTAX SEQUENCE OF SysSBusEntry
      MAX-ACCESS not-accessible
      STATUS current
      DESCRIPTION
      "This table includes data and status about the internal DXC BUS."
      ::= { sysStatus 21 }

sysSBusEntry OBJECT-TYPE
      SYNTAX SysSBusEntry
      MAX-ACCESS not-accessible
      STATUS current
	DESCRIPTION  "An entry in table."
	INDEX { sysSBusPortIdx}
      ::= { sysSBusTable 1}

SysSBusEntry ::=
      SEQUENCE {
     sysSBusPortIdx     Integer32,
     sysSBusStatus      INTEGER,
     sysSBusCapturePort Integer32,
	 sysSBusUtilization Integer32 
	}

sysSBusPortIdx OBJECT-TYPE
      SYNTAX  Integer32 
      MAX-ACCESS  read-only
      STATUS  current
      DESCRIPTION
      "The DXC BUS port number:
         - first two digits will be: (IO slot number+10)
         - last one/two digits will be the Bus port number, in odd numbers:
           port1 = 1
           port2 = 3
           Example: port2 of IO slot 11 will be: 213."
      ::= { sysSBusEntry 1 }

sysSBusStatus OBJECT-TYPE
      SYNTAX  INTEGER 
       {
		 free    (1),
         physical(2),
         virtual (3)
       }
      MAX-ACCESS  read-only
      STATUS  current
      DESCRIPTION
      "The Status of sysSBusPortIdx.
       free    - not used
       physical - captured by the port of the card physically installed
       virtual  - captured virtually by another port. Example: DIM port 
                 (by Destination) or by Transparent T3/E3  port."
      ::= { sysSBusEntry 2}

sysSBusCapturePort OBJECT-TYPE
      SYNTAX  Integer32 
      MAX-ACCESS  read-only
      STATUS  current
      DESCRIPTION
      "The Port that Captured the sysSBusPortIdx.
       - if sysSBusStatus=free, the value will be 'none'=0
	   - else, if sysSBusStatus=fixed, the value will be: sysSBusPortIdx
       - else, the value will be according to the port index that captured
         this Bus Port (according to DXC port index convention):
         - xx1, xx3, xx11, xx13, xx31, xx33, xx2..xx56(even numbers)
         - xx = (IO slot number+10) "
      ::= { sysSBusEntry 3}

sysSBusUtilization OBJECT-TYPE
      SYNTAX  Integer32 
      MAX-ACCESS  read-only
      STATUS  current
      DESCRIPTION
      "Utilization of sysSBusPortIdx resources, in percent [%]."
      ::= { sysSBusEntry 4}

--IO Redundancy - Commands
--sysSRdnCmdTable was moved to be after sysCRdnTable, in order to solve
--an SNMPc limitation regarding forward reference of the indexes.

sysSAlrAttrIndication OBJECT-TYPE
      SYNTAX Integer32
      MAX-ACCESS read-only
      STATUS current
      DESCRIPTION
      "This object indicates the status of the Alarm Attributes 
       for the whole device.
       It is a sum of 2**(Bit-1). A Bit will be '1', when any alarm in the
	   device is Filtered/Masked/Inverted (respectively).
       The Bit assignment is:
       Bit 1: Filter (LSB)
       Bit 2: Mask
       Bit 3: Invert  (MSB).
       Examples:
       - Alarms are filtered and masked but not inverted: value=3
       - Alarm is Inverted (not filtered or masked): value=4
       - Alarm is masked (not inverted or filtered): value=2 "
      ::= { sysStatus 23 }


--System Current Alarm Table
--
--This table contains all Events and only the major/minor alarms
--whose status is ON.

sysSAlrTable OBJECT-TYPE
      SYNTAX SEQUENCE OF SysSAlrEntry
      MAX-ACCESS not-accessible
      STATUS current
      DESCRIPTION
      "List of system level current existing alarms ."
      ::= { sysCurrentAlr 1 }

sysSAlrEntry OBJECT-TYPE
      SYNTAX SysSAlrEntry
      MAX-ACCESS not-accessible
      STATUS current
	DESCRIPTION  "An entry in table."
	INDEX { sysSAlrIdx}
      ::= { sysSAlrTable 1}

SysSAlrEntry ::=
      SEQUENCE {
     	sysSAlrIdx       Integer32,
     	sysSAlrCode      Integer32,
     	sysSAlrState     INTEGER, --Severity
     	sysSAlarmMask    INTEGER,
     	sysSAlarmInvert  INTEGER,
		sysSAlarmOnOff   INTEGER,
		sysSAlarmCounter Integer32 
	}

sysSAlrIdx OBJECT-TYPE
      SYNTAX  Integer32
      MAX-ACCESS  read-only
      STATUS  current
      DESCRIPTION
      "An index number of the current system alarms."
      ::= { sysSAlrEntry 1 }

sysSAlrCode OBJECT-TYPE
      SYNTAX  Integer32
      MAX-ACCESS  read-only
      STATUS  current
      DESCRIPTION
      "This object indicates a code related to a specific
       alarm description. The list of codes and their related
       descriptions will be sent to NMS request (for display purpose)
       by alrGenTable."
      ::= { sysSAlrEntry 2 }

sysSAlrState OBJECT-TYPE
      SYNTAX  INTEGER {
   event    (3),
   minor    (4),
   major    (5),
   warning  (6),
   critical (7)
       }
      MAX-ACCESS  read-only
      STATUS  current
      DESCRIPTION
      "This object indicates the alarm Severity."      
      ::= { sysSAlrEntry 3 }

sysSAlarmMask OBJECT-TYPE
      SYNTAX  INTEGER {
  off(2),
  on (3)
       }
      MAX-ACCESS  read-only
      STATUS  current
      DESCRIPTION
      "Alarm Mask is : on/off."
      ::= { sysSAlrEntry 4 }

sysSAlarmInvert OBJECT-TYPE
      SYNTAX  INTEGER {
  off(2),
  on (3)
       }
      MAX-ACCESS  read-only
      STATUS  current
      DESCRIPTION
      "Alarm Invert is : on/off."
      ::= { sysSAlrEntry 5 }

sysSAlarmOnOff OBJECT-TYPE
      SYNTAX  INTEGER {
  off(2),
  on (3)
       }
      MAX-ACCESS  read-only
      STATUS  current
      DESCRIPTION
      "Alarm state is : on/off."
      ::= { sysSAlrEntry 6 }

sysSAlarmCounter OBJECT-TYPE
      SYNTAX  Integer32
      MAX-ACCESS  read-only
      STATUS  current
      DESCRIPTION
      "A counter - how many times the alarm occured (ON) since last
       clear operation or since last Reset."
      ::= { sysSAlrEntry 7 }

sysSAlrClearCmd  OBJECT-TYPE
      SYNTAX  INTEGER
       {
  off(2),
  on (3)
       }
      MAX-ACCESS  read-write
      STATUS  current
      DESCRIPTION
      "Setting this attribute to ON, will enforce a  clear 
       operation on the system level alarms . Upon completion, 
       the value will automatically change to off(2)."
      ::= { sysCurrentAlr 2 }


sysSAlrClearAllCmd  OBJECT-TYPE
      SYNTAX  INTEGER
       {
  off(2),
  on (3)
       }
      MAX-ACCESS  read-write
      STATUS  current
      DESCRIPTION
      "Setting this attribute to ON, will enforce a  clear 
       operation on all levels alarms . Upon completion, 
       the value will automatically change to off(2)."
      ::= { sysCurrentAlr 3 }

sysSAlrMaskAll  OBJECT-TYPE
      SYNTAX  INTEGER
       {
  off(2),
  on (3)
       }
      MAX-ACCESS  read-write
      STATUS  current
      DESCRIPTION
      "on(3)  - will cause masking of all the system level alarms.
                These alarms will not be sent to NMS and will not 
                be taken into account for Alarms Status.
       off(2) - will unmask all system level alarms except those 
                masked via the sysSAlrMask. "
      ::= { sysCurrentAlr 4 }

sysSAlrMask OBJECT-TYPE
      SYNTAX OCTET STRING  (SIZE (8))
      MAX-ACCESS read-write
      STATUS current
   DESCRIPTION
   "This object is a mask that indicates which system level 
    alarms are masked. The masked alarms (their bit is set to 
    '1') are neither sent to the manager, nor taken into account
    for alarm status and LEDs.
    Bit no. = Alarm code
    The bits that do not belong to the system level will be 0.
    This object is applicable only when sysSAlrMaskAll=off 
    (otherwise all system alarms are masked).
    Example: When Alarms having the codes 6 and 11 are masked,
             the value of this object will be 840 (hex)."
      ::= { sysCurrentAlr 5 }

sysSAlrDataUpdateCmd  OBJECT-TYPE
      SYNTAX  INTEGER
       {
        off(2),
        on (3)
       }
      MAX-ACCESS  read-write
      STATUS  current
      DESCRIPTION
      "on(3)  - will cause Update of the Alarms Severity, Attributes and Report
                tables.
       off(2) - Upon completion, the value will automatically change to off(2)."
      ::= { sysCurrentAlr 6 }


--System Buffer Alarm Table
--
--This table contains all Events and all the major/minor alarms
--The buffer is cyclic and contains the most recent alarms.
--Since this table contains also the alarms occurence time,
--(appearance/disappearance for major/minor alarms), an alarm may 
--appear several times in this table, with alternate state: major, 
--off, major, etc.. 

sysBufferAlrTable OBJECT-TYPE
      SYNTAX SEQUENCE OF SysBufferAlrEntry
      MAX-ACCESS not-accessible
      STATUS current
      DESCRIPTION
      "List of current existing alarms (of all levels)."
      ::= { sysBufferAlr 1 }

sysBufferAlrEntry OBJECT-TYPE
      SYNTAX SysBufferAlrEntry
      MAX-ACCESS not-accessible
      STATUS current
	DESCRIPTION  "An entry in table."
	INDEX { sysBufferAlrIdx}
      ::= { sysBufferAlrTable 1}

SysBufferAlrEntry ::=
      SEQUENCE {
     	sysBufferAlrIdx   Integer32,
     	sysBufferAlrCode  Integer32,
     	sysBufferAlrState INTEGER,
     	sysBufferAlrSlot  INTEGER,
     	sysBufferAlrPort  Integer32,
     	sysBufferAlrDate  DisplayString,
     	sysBufferAlrTime  DisplayString,
		sysBufferAlrUpTime  TimeTicks,
		sysBufferAlrInfo  SnmpAdminString
				      }

sysBufferAlrIdx OBJECT-TYPE
      SYNTAX  Integer32
      MAX-ACCESS  read-only
      STATUS  current
      DESCRIPTION
      "An index number of the current alarms."
      ::= { sysBufferAlrEntry 1 }

sysBufferAlrCode OBJECT-TYPE
      SYNTAX  Integer32
      MAX-ACCESS  read-only
      STATUS  current
      DESCRIPTION
      "This object indicates a code related to a specific
       alarm description. The list of codes and thir related
       descriptions will be known by the NMS (for display purpose)
       and will appear in the unit's user manual."
      ::= { sysBufferAlrEntry 2 }

sysBufferAlrState OBJECT-TYPE
      SYNTAX  INTEGER {
     off      (2),
     event    (3),
     minor    (4),
     major    (5),
	 warning  (6),
     critical (7)
       }
      MAX-ACCESS  read-only
      STATUS  current
      DESCRIPTION
      "This object indicates the alarm type.
       minor/major/warning/critical - indicates appearance of the problem 
                     and the type.
       event       - indicates occurence of an event.
       off         - indicates disappearance of an alarm. "      
      ::= { sysBufferAlrEntry 3 }


sysBufferAlrSlot OBJECT-TYPE
      SYNTAX  INTEGER 
       {
       psA   (1),
       psB   (2),
       clA   (3),
       clB   (4),
       io1   (5),
       io2   (6),
       io3   (7),
       io4   (8),
       io5   (9),
       io6  (10),
       io7  (11),
       io8  (12),
       io9  (13),
       io10 (14),
       io11 (15),
       io12 (16),
       io13 (17),
       io14 (18),
       io15 (19),
	  local (20),
	   psC  (21),
    kmxPsA (101),
    kmxPsB (102),
    kmxMlA (103),
    kmxMlB (104),
    kmxCl  (105),
    kmxOpt (106),
    kmxIO1 (107),
    kmxIO2 (108),
    kmxIO3 (109),
    kmxIO4 (110),
    kmxIO5 (111),
    kmxIO6 (112),
    kmxIO7 (113),
    kmxIO8 (114),
    kmxIO9 (115),
    kmxIO10(116),
    kmxIO11(117),
    kmxIO12(118),
	remote (120),
    notApplicable (255)
       }
      MAX-ACCESS  read-only
      STATUS  current
      DESCRIPTION
      "The slot number this alarm refers to.
       When the alarm refers to a system function OR the DACS agent 
       is a stand-alone unit, the value will be 'notApplicable(255)'.
       local/remote - for OP-4 device."      
      ::= { sysBufferAlrEntry 4 }

sysBufferAlrPort OBJECT-TYPE
      SYNTAX  Integer32 
      MAX-ACCESS  read-only
      STATUS  current
      DESCRIPTION
      "The port number this alarm refers to.
       If the port number is irrelevant to this alarm (if it is
       a system/card level alarm) the value will be 9999."     
      ::= { sysBufferAlrEntry 5 }

sysBufferAlrDate OBJECT-TYPE
      SYNTAX  DisplayString (SIZE (0..255))
      MAX-ACCESS  read-only
      STATUS  current
      DESCRIPTION
      "The date when the alarm occured. The format will be according
       to sysSDateFormat."     
      ::= { sysBufferAlrEntry 6 }


sysBufferAlrTime OBJECT-TYPE
      SYNTAX  DisplayString (SIZE (0..255))
      MAX-ACCESS  read-only
      STATUS  current
      DESCRIPTION
      "The time when the alarm occured." 
      ::= { sysBufferAlrEntry 7 }

sysBufferAlrUpTime OBJECT-TYPE
    SYNTAX  TimeTicks
    MAX-ACCESS  read-only
    STATUS  current
    DESCRIPTION
       "The time when the alarm occured.
       This parameter holds the sysUpTime value when the alarm occured."
    ::= { sysBufferAlrEntry 8 }

sysBufferAlrInfo OBJECT-TYPE
	SYNTAX      SnmpAdminString
	MAX-ACCESS  read-only
    STATUS      current
	DESCRIPTION
      "This parameter includes information about the alarm (additional to the Description)."
	::= { sysBufferAlrEntry 9}        


sysBufferAlrClearCmd OBJECT-TYPE
      SYNTAX  INTEGER
       {
  off(2),
  on (3)
       }
      MAX-ACCESS  read-write
      STATUS  current
      DESCRIPTION
      "Setting this attribute to ON, will enforce a  clear 
       operation on the Alarms Buffer. Upon completion, 
       the value will automatically change to off(2)."
      ::= { sysBufferAlr 2 }


--System Configuration Parameters

sysCClkSrcTable  OBJECT-TYPE
      SYNTAX SEQUENCE OF SysCClkSrcEntry
      MAX-ACCESS not-accessible
      STATUS  current
      DESCRIPTION
      "All the entries of this table are identical (have the 
       same value) for all the configurations (1..255) except 
       the TmpCnfg.
       For devices with more than one configuration:
       The write operation into the Table Objects is valid only
       for the TmpCnfg entry."
       ::= { sysConfig 1}

sysCClkSrcEntry OBJECT-TYPE
      SYNTAX SysCClkSrcEntry
      MAX-ACCESS not-accessible
      STATUS current
    DESCRIPTION  "An entry in table."
    INDEX {sysCClkCnfgIdx, sysCClkSrcIdx}
      ::= { sysCClkSrcTable 1}

SysCClkSrcEntry ::= SEQUENCE {
    sysCClkCnfgIdx              Integer32,
    sysCClkSrcIdx               INTEGER,
   sysCClkSrcMode              INTEGER,
   sysCClkSrcPrt               Integer32,
   sysCClkStationFreq          INTEGER,
   sysCClkRevertiveTimeout     Integer32,
   sysCClkStationIf            INTEGER,
   sysCClkStationCableMode 	   INTEGER,
   sysCClkStationOutState 	   INTEGER,
   sysCClkSsmBased 		       INTEGER,
   sysCClkSSubsystemSlot       INTEGER, 
   sysCClkRecoveredID     	   Unsigned32 
 }

sysCClkCnfgIdx OBJECT-TYPE
      SYNTAX Integer32 (1..2147483647)
      MAX-ACCESS read-only
      STATUS current
      DESCRIPTION
      "This attribute indicates the Idx of the Cnfg being 
       accessed ; Idx of 255 relates to the TmpCnfg.
       It can be also a combination of the configuration number and the 
       Card/Port/Other System index."
      ::= { sysCClkSrcEntry 1}

sysCClkSrcIdx OBJECT-TYPE
      SYNTAX  INTEGER 
       {
     master    (1),
     fallback  (2)
    }
      MAX-ACCESS  read-only
      STATUS  current
      DESCRIPTION
      "An index in the table. There are only two entries in the 
       table. 
       master   - refers Master clock parameters 
       fallback - refers Fallback clock parameters"
      ::= { sysCClkSrcEntry 2}

sysCClkSrcMode OBJECT-TYPE
      SYNTAX  INTEGER
       {
     none            (1),
     internal        (2),
     rxClk           (3),
     station         (4),  -- station A (for IPmux1000)
     lbt             (5),
	 ntr             (6),
	 adaptive        (7),  
	 stationB        (8),
	 automatic		 (9),
	 system         (10),
	 sSubSystem     (11),
	 recovered		(12),  
     notApplicable (255)
       }
      MAX-ACCESS  read-write
      STATUS  current
      DESCRIPTION
      "This entry indicates the source the nodal timing is 
       locked to.
       none     - is an invalid option for Master clock.
       internal - is an invalid option for Fallback clock .
       station  - is an invalid option for a stand-alone unit. 
       lbt      - loop-back timing
	   ntr      - Network Time Reference 
	   adaptive - clock locking is achieved by altering the clock 
	              according to the data load
	   system   - irrelevant when sysCClkCnfgIdx refers to System Clock.
	   sSubSystem - SONET/SDH Sub System.   
	   recovered  - clock recovery.   
       notApplicable - for ML source of Kmux or ML Timing 
                       combinations when Master/Fallback clock are
                       not applicable."
      ::= { sysCClkSrcEntry 3}


sysCClkSrcPrt OBJECT-TYPE
      SYNTAX  Integer32
      MAX-ACCESS  read-write
      STATUS  current
      DESCRIPTION
      "This entry is valid only when working in rxClk mode
       (for IPmux1000 this entry will be valid whe working in LBT mode).
       
       For ACE2002 in case of invalid entry the return value 
       will be 0. 
       For other products in case of invalid entry the return 
       value will be 9999.

       The valid port number depends on the IO slot no.,  the 
       installed card type and the port type: outside, inside, 
       SP.
    * The SP ports will be numbered as follows:
     - SP port 1 :  1
     - SP port 2 :  2
	   For external ports the convention used will be (for DXC):
         - first two digits will be: (IO slot number+10)
         - last one/two digits will be the port number within the 
           card, in odd numbers:
           port1 = 1
           port2 = 3
           port3 = 5 
           etc...
           Example: port2 of IO slot 11 will be: 213 .
       For internal ports the convention used will be (for DXC):
         - first two digits will be: (IO slot number+10)
         - last one/two digits will be the port number within the 
           card, in even numbers:
           port1 = 2
           port2 = 4
           port3 = 6 
           etc...
           Example: port2 of IO slot 11 will be: 214 .

      For Kmux, the port will be according to : Slot*100+Ch.
      
      For ACE2002,  LA140 and IPmux1000 (GMUX), the port will be ifIndex."
      ::= { sysCClkSrcEntry 4}

sysCClkStationFreq OBJECT-TYPE
      SYNTAX  INTEGER
       {
     notApplicable   (1),
     f1544Khz        (2), -- DS1
     f2048Khz        (3)  -- E1
       }
      MAX-ACCESS  read-write
      STATUS  current
      DESCRIPTION
      "This entry indicates the frequency of the station clock 
       when the source is 'station'.  
       The value will be applicable only when the sysCClkSrcMode is 
       'station'. "
      ::= { sysCClkSrcEntry 5}

sysCClkRevertiveTimeout OBJECT-TYPE
      SYNTAX  Integer32
      MAX-ACCESS  read-write
      STATUS  current
      DESCRIPTION
      "The time in seconds in which the system will monitor the higher
       level clock source, before decision to revert to that clock.
       In case the time is zero, revertive mode will be disabled."
      ::= { sysCClkSrcEntry 6}

sysCClkStationIf OBJECT-TYPE
      SYNTAX  INTEGER
       {
       notApplicable (1),
       g703          (2), --E1 balanced
       rs422         (3), --E1
       g703E1Unbalanced (4),
       g703T1        (5),
       rs422T1       (6)
       }
      MAX-ACCESS  read-write
      STATUS  current
      DESCRIPTION
      "This entry indicates the electrical interface connected to the
       station clock, when the source is 'station'.  
       The value will be applicable only when the sysCClkSrcMode is 
       'station'. "
      ::= { sysCClkSrcEntry 7}

sysCClkStationCableMode OBJECT-TYPE
      SYNTAX  INTEGER
       {
       notApplicable (1),
       normal        (2),
       yCable        (3)
       }
      MAX-ACCESS  read-write
      STATUS  current
      DESCRIPTION
      "This parameter indicates whether both Station clocks get their 
      clock from the same source (Y Cable)or each one get its clock independently.
       The value will be applicable only when the sysCClkSrcMode is 'station'. "
      ::= { sysCClkSrcEntry 8}

sysCClkStationOutState OBJECT-TYPE
      SYNTAX  INTEGER
       {
       notApplicable (1),
       disabled      (2),
       enabled       (3)
       }
      MAX-ACCESS  read-write
      STATUS  current
      DESCRIPTION
      "This parameter indicates whether station clock can 
      send its clock to another device.
	  The value will be applicable only when the sysCClkSrcMode is 'station'. "
      ::= { sysCClkSrcEntry 9}

sysCClkSsmBased    OBJECT-TYPE
      SYNTAX  INTEGER
       {
       notApplicable (1),
       no            (2),
       yes           (3)
       }
      MAX-ACCESS  read-write
      STATUS  current
      DESCRIPTION
      "This parameter indicates whether clock source 
       will be selected based on receive clock quality, 
       indicated in S1 byte inside SONET/SDH overhead, 
       (encoded as SSM - Synchronization Status Messaging).
       It is relevant only for sysCClkSrcIdx=master.
       When the value is Yes, sysCClkSrcMode must be notApplicable."
      ::= { sysCClkSrcEntry 10}
      
sysCClkSSubsystemSlot OBJECT-TYPE
      SYNTAX  INTEGER
       {
       notApplicable (1),
       clA           (3),
       clB           (4)
       }
      MAX-ACCESS  read-write
      STATUS  current
      DESCRIPTION
      "This entry indicates the Slot from which the S Subsytem Source
       will be taken.  
       The value will be applicable only when the sysCClkSrcMode is 
       'sSubsystem'. "
      ::= { sysCClkSrcEntry 11}	

sysCClkRecoveredID OBJECT-TYPE
      SYNTAX  Unsigned32
      MAX-ACCESS  read-write
      STATUS  current
      DESCRIPTION
      "This entry indicates the Recovered Clock ID.
       The value will be applicable only when sysCClkSrcMode is 'recovered'."
      ::= { sysCClkSrcEntry 12}


sysCnfgTable  OBJECT-TYPE
      SYNTAX SEQUENCE OF SysCnfgEntry
      MAX-ACCESS not-accessible
      STATUS  current
      DESCRIPTION
      "All the entries of this table are identical (have the 
       same value) for all the configurations (1..255) except 
       the TmpCnfg.
       The write operation into the Table Objects is valid only
       for the TmpCnfg entry."
       ::= { sysConfig 2}

sysCnfgEntry OBJECT-TYPE
      SYNTAX SysCnfgEntry
      MAX-ACCESS not-accessible
      STATUS current
	DESCRIPTION  "An entry in table."
	INDEX {sysCnfgIdx}
      ::= { sysCnfgTable 1}

SysCnfgEntry ::=
      SEQUENCE {
   sysCnfgIdx             Integer32,
   sysCMatrixMode         INTEGER,
   sysCIsdnFormat         INTEGER,
   sysCRoutingOnEth       INTEGER,
   sysCAutoConfigEnable   INTEGER,
   sysCIntTsAllocMode     INTEGER,
   sysCBuPrimaryPort	  INTEGER,
   sysCEnableLanOverTdm   INTEGER,
   sysCSs7FisuSuppression Integer32,
   sysCBuRecMode          INTEGER
      }

sysCnfgIdx OBJECT-TYPE
      SYNTAX Integer32 
      MAX-ACCESS read-only
      STATUS current
      DESCRIPTION
      "This attribute indicates the Idx of the Cnfg(1..255) being 
       accessed ; Idx of 255 relates to the TmpCnfg.
	   For Gmux2000 the range limitation (1..255) was discarded
       since the Idx is computed as: <IO Card No.> x 1000 + 255."
      ::= { sysCnfgEntry 1}

sysCMatrixMode OBJECT-TYPE
      SYNTAX  INTEGER
       {
  notApplicable  (1),
  bidirectional  (2),
  unidirectional (3)
       }
      MAX-ACCESS  read-write
      STATUS  current
      DESCRIPTION
      "Indicates the TS Matrix Mode:
    bidirectional  - TS Assignment Matrix is symmetric.
    unidirectional - TS Assignment Matrix can be asymmetric.
       notApplicable - for agents that do not support this feature."
      ::= { sysCnfgEntry 2}

sysCIsdnFormat OBJECT-TYPE
      SYNTAX  INTEGER
       {
  notApplicable (1),
  te  (2),
  nt  (3)
       }
      MAX-ACCESS  read-write
      STATUS  current
      DESCRIPTION
      "ISDN format. This parameter controls the operation mode of
    the ISDN ports.
    te - ISDN timing is derived from the signal received
         from the equipment it is connected to.
    nt - timing of the transmit path is locked to the nodal 
         timing source.
       notApplicable - for agents that do not support this feature."
      ::= { sysCnfgEntry 3}

sysCRoutingOnEth OBJECT-TYPE
      SYNTAX  INTEGER
       {
      notApplicable (1),
      none          (2),  
      proprietary   (3),
      rip2          (4),
	  rip1          (5),
	  rip1and2      (6)
       }
      MAX-ACCESS  read-write
      STATUS  current
      DESCRIPTION
      "Mng Routing Protocol on the online CL Ethernet port,
       or on device Ethernet  port dedicated for mangement."
      ::= { sysCnfgEntry 4}

sysCAutoConfigEnable OBJECT-TYPE
      SYNTAX  INTEGER
       {
      notApplicable (1),
      disable       (2),  
      enable        (3)
       }
      MAX-ACCESS  read-write
      STATUS  current
      DESCRIPTION
      "This object enables user to enable/disable activating
       the Auto Configuration. When Auto Configuration is activated,
       the device learns its configuration Automatically from the Net 
       it is connected to."
      ::= { sysCnfgEntry 5}

sysCIntTsAllocMode OBJECT-TYPE
      SYNTAX  INTEGER
       {
      notApplicable (1),
      static        (2),  
      dynamic       (3),
	  staticOneToOne(4)
       }
      MAX-ACCESS  read-write
      STATUS  current
      DESCRIPTION
      "This object enables user to select the mode of Internal TS 
       Allocation.
       static - user has to select for each Dynamic card port, the 
                Maximum TSs expected to be connected (including future
                growth). This number will be allocated to the ports,
                so that if number of connected TSs will grow within
                the limits of this Maximum TS limit, no disruption
                of data flow will occur for other ports.
       dynamic- TS allocation is done dynamically according to the 
                connected TSs. No future reservations are done. This mode
                may cause data disruption on other ports/slots if user
                will want to change the number of connected TSs for a
                Dynamic card port.
	   staticOneToOne - user has to select for each Dynamic card port, the 
                Maximum TSs expected to be connected (including future
                growth). In addition, the TSs themselves cannot be higher
                than this defined Maximum (e.g if Maximum TSs=5 user cannot 
                selects TSs higher than 5). This mode ensures that if number 
                of TSs grow within the limits of this Maximum TS limit, no 
                disruption of data flow will occur for other ports AND for 
                the selected port itself. 
       Default=static(2).         "
      ::= { sysCnfgEntry 6}

sysCBuPrimaryPort OBJECT-TYPE
      SYNTAX  INTEGER
       {
      noBackup     (2),
      e1T1orSerial (3),  
      eth          (4)
	   }
      MAX-ACCESS  read-write
      STATUS  current
      DESCRIPTION
      "This object enables the user to configure a Backup mechanism.
       If a backup mechanism exists, it is possible to configure the primary port.
       The traffic will flow via the primary port when the port functionality is OK.

       In Vmux-2100 device the backup mechanism is relevant for the Main Board only.
       The primary port can be the E1/T1/Serial port or the ETH port. "
      ::= { sysCnfgEntry 7}

  sysCEnableLanOverTdm  OBJECT-TYPE
      SYNTAX  INTEGER
       {
      enableAll         (2),
      enableVoiceOnly   (3),  
      enableVoiceAndMng (4)
	   }
      MAX-ACCESS  read-write
      STATUS  current
      DESCRIPTION
      "This object enables/disables transferring traffic from the LAN port
       to the TDM port. It is possible to enable only part of the traffic on the
       TDM port for security reasons or in order to minimize the bandwidth ."
       ::= { sysCnfgEntry 8}

  sysCSs7FisuSuppression  OBJECT-TYPE
      SYNTAX  Integer32
      MAX-ACCESS  read-write
      STATUS  current
      DESCRIPTION
      "SS7 Suppresion is used for SS7 Spoofing.
       The SS7 spoofing terminates the keep alive messages from the local VMUX
       without sending them over the network, thus improving the bandwidth utilization.
	   FISU means Fill in Service Unit - Keep alive that is sent when no one is talking
	   on the line.

       This object enables the configuration of the SS7 Keep Alive packet % that will
       be discarded.
       
       Legal Values: 0 - No Suppression, 10%, 20%, 30% .. 90%
       
       Example: For a value of 10, 1 keep alive packet will be discarded out of
                10 keep alive packets that were supposed to be sent over the network."
       ::= { sysCnfgEntry 9}

  sysCBuRecMode OBJECT-TYPE
      SYNTAX  INTEGER
       {
          auto        (2),
          manual      (3)
       }          
      MAX-ACCESS  read-write
      STATUS  current
      DESCRIPTION
      "Recovery Mode. This object determines if after recovery
       of the Primary Link (used in Vmux) it will become on-line again or not:
       auto - automatic. In this case, the failed Link will become
           on-line again after recovery, automatically.
       manual - In this case, the failed Link will not become
             on-line again after recovery but user can manually flip
             to this Link."
       ::= { sysCnfgEntry 10}


--System I/O Redundacy Table
--
--This table contains all I/O cards/ports that have redundancy,
--data about the redundant card/port and parameters regarding the
--redundancy operation.
--The table indexes are Cnfg and the Primary card&port 


sysCRdnTable    OBJECT-TYPE
    SYNTAX      SEQUENCE OF SysCRdnEntry
    MAX-ACCESS  not-accessible
    STATUS      current
    DESCRIPTION
            "Configuration of all Redundant I/O cards and ports.
            The write operation into the table objects is valid only
            for the TmpCnfg.
            A Slot/Port that have no Redundancy, will not exist in this
            table."
    ::= { sysConfig 3 }

sysCRdnEntry    OBJECT-TYPE
    SYNTAX      SysCRdnEntry
    MAX-ACCESS  not-accessible
    STATUS      current
    DESCRIPTION
            "An entry in table."
    INDEX { sysCRdnCnfgIdx, sysCRdnPrimeSlot, sysCRdnPrimePort}
    ::= { sysCRdnTable 1}

SysCRdnEntry ::= SEQUENCE {
    sysCRdnCnfgIdx                      Integer32,
    sysCRdnPrimeSlot                    INTEGER,
    sysCRdnPrimePort                    Integer32,
    sysCRdnSecSlot                      INTEGER,
    sysCRdnSecPort                      Integer32,
    sysCRdnMode                         INTEGER,
    sysCRdnRecMode                      INTEGER,
    sysCRdnRecTime                      Integer32,
    sysCRdnHwSwFlip                     INTEGER,
    sysCRdnRowStatus                    RowStatus,
    sysCRdnOnline                       INTEGER,
    sysCRdnSwitchingMode                INTEGER,
    sysCRdnFlipUponEvent                Integer32,
    sysCRdnLosOrLofTime                 Integer32,
    sysCRdnEventsTimeWindow             Integer32,
    sysCRdnSequenceNumberThreshold      Integer32,
    sysCRdnBufferErrorsThreshold        Integer32,
    sysCRdnBuffUnderrunTime             Integer32,
    sysCRdnPrimePriority                INTEGER,
    sysCRdnSecPriority                  INTEGER,
    sysCRdnWTR                          Unsigned32,
    sysCRdnName                         SnmpAdminString,
    sysCRdnTxDownDurationUponFlip       Unsigned32 
 }

sysCRdnCnfgIdx OBJECT-TYPE
      SYNTAX  Integer32
      MAX-ACCESS  read-only
      STATUS  current
      DESCRIPTION
      "This object indicates the Idx of the Cnfg(1..255) being 
       accessed ; Idx of 255 relates to the TmpCnfg."
      ::= { sysCRdnEntry 1 }

sysCRdnPrimeSlot OBJECT-TYPE
      SYNTAX  INTEGER 
       {
       io1   (5),
       io2   (6),
       io3   (7),
       io4   (8),
       io5   (9),
       io6  (10),
       io7  (11),
       io8  (12),
       io9  (13),
       io10 (14),
       io11 (15),
       io12 (16),
       io13 (17),
       io14 (18),
       io15 (19),
       notApplicable (255)
       }
      MAX-ACCESS  read-only
      STATUS  current
      DESCRIPTION
      "The slot number of the Primary card of Redundancy.
       The Primary card should be the card that user wishes to be
       the online card (usually the more important one).
       For some Redundancy modes the importance of the redundant 
       cards/ports is the same. "      
      ::= { sysCRdnEntry 2 }

sysCRdnPrimePort OBJECT-TYPE
      SYNTAX  Integer32 
      MAX-ACCESS  read-only
      STATUS  current
      DESCRIPTION
      "The port number.
       For DXC:
       For external ports the convention used will be:
         - first two digits will be: (IO slot number+10)
         - last one/two digits will be the port number within the 
           card, in odd numbers:
           port1 = 1
           port2 = 3
           port3 = 5 
           etc...
           Example: port2 of IO slot 11 will be: 213 .
       For internal ports the convention used will be:
         - first two digits will be: (IO slot number+10)
         - last one/two digits will be the port number within the 
           card, in even numbers:
           port1 = 2
           port2 = 4
           port3 = 6 
           etc...
           Example: port2 of IO slot 11 will be: 214 .

       For MP:
       For external ports, the value will be as that of the port in the
           card. Example: external-3 -> 3
                          external-4 -> 4
       For internal ports, the value will be 100 + the port in the
           card. Example: internal-1 -> 101
                          internal-4 -> 104
       For IP Bundles, the value will be the Bundle ifIndex. For an IP Bundle 
       that is in an External Device (not in this MP), the value will be:
       70,000 + ifIndex of Secondary Bundle.                               

       For other products - refer to product specification.

       100=notApplicable (when Redundancy is at card level)."      
      ::= { sysCRdnEntry 3 }

sysCRdnSecSlot OBJECT-TYPE
      SYNTAX  INTEGER 
       {
       io1   (5),
       io2   (6),
       io3   (7),
       io4   (8),
       io5   (9),
       io6  (10),
       io7  (11),
       io8  (12),
       io9  (13),
       io10 (14),
       io11 (15),
       io12 (16),
       io13 (17),
       io14 (18),
       io15 (19),
       notApplicable (255)
       }
      MAX-ACCESS  read-create
      STATUS  current
      DESCRIPTION
      "The slot number of the Secondary card of Redundancy matching
       the Primary slot."      
      ::= { sysCRdnEntry 4 }

sysCRdnSecPort OBJECT-TYPE
      SYNTAX  Integer32 
      MAX-ACCESS  read-create
      STATUS  current
      DESCRIPTION
      "The port number.
       For DXC:
       For external ports the convention used will be:
         - first two digits will be: (IO slot number+10)
         - last one/two digits will be the port number within the 
           card, in odd numbers:
           port1 = 1
           port2 = 3
           port3 = 5 
           etc...
           Example: port2 of IO slot 11 will be: 213 .
       For internal ports the convention used will be:
         - first two digits will be: (IO slot number+10)
         - last one/two digits will be the port number within the 
           card, in even numbers:
           port1 = 2
           port2 = 4
           port3 = 6 
           etc...
           Example: port2 of IO slot 11 will be: 214 .

       For MP:
       For external ports, the value will be as that of the port in the
           card. Example: external-3 -> 3
                          external-4 -> 4
       For internal ports, the value will be 100 + the port in the
           card. Example: internal-1 -> 101
                          internal-4 -> 104        
       For IP Bundles, the value will be the Bundle ifIndex. For an IP Bundle 
       that is in an External Device (not in this MP), the value will be: 0.                           

       For other products - refer to product specification.

       100=notApplicable (when Redundancy is at card level)."      
      ::= { sysCRdnEntry 5 }

sysCRdnMode OBJECT-TYPE
    SYNTAX      INTEGER {
        dualCableAIS            (2),
        yCable                  (3),
        dualCableParallelTx     (4),
        backup                  (5),
        singleSlotProtection    (6),
        onePlusOne              (7),
        oneToOne                (8),
        linkAggregation         (9),  --802.3ad
        manual                  (10),
        onePlusOneBid           (11),
        onePlusOneOpt           (12),
        ds0SncProtection        (13)
        }
    MAX-ACCESS  read-create
    STATUS      current
    DESCRIPTION
            "Redundancy Mode.
            DXC supports yCable(3), singleSlotProtection(6) and
            dualCableParallelTx(4)
            MP supports yCable(3), dualCableParallelTx(4), onePlusOne(7)
            and oneToOne(8).(dualCableAIS and backup were planned for MP
            but were not implemented).
            backup - will be used when a port is backup of more than one
            port.
            IPmux: onePlusOne(7) and oneToOne(8) are used for Bundle
            redundancy.
            onePlusOneBid (11) defines 'Bidirectional 1+1 protection'
            onePlusOneOpt (12) defines 'Optimized 1+1 protection'
            ds0SncProtection (13) defines DS0 protection using
            symmetrical DS1 ring configuration"
    ::= { sysCRdnEntry 6 }

sysCRdnRecMode OBJECT-TYPE
      SYNTAX  INTEGER
       {
          auto        (2),
          manual      (3),
          nonRevertive(4)
       }
      MAX-ACCESS  read-create
      STATUS  current
      DESCRIPTION
      "Recovery Mode. This object determines if after recovery
       of the failed Primary card/port it will become on-line again or not:
       auto - automatic . In this case, the failed card/port will become
           on-line again after recovery, automatically.
       manual - In this case, the failed card/port will not become
             on-line again after recovery. But, user can manually flip
             to this card/port.
       nonRevertive - same as manual, but here user CANNOT manually flip
             to this card/port. It will become on-line again, only if the
             Secondary/Backup card/port will fail."
      ::= { sysCRdnEntry 7 }

sysCRdnRecTime OBJECT-TYPE
      SYNTAX  Integer32 
      MAX-ACCESS  read-create
      STATUS  current
      DESCRIPTION
      "Redundancy Recovery Time (sec). After switching to the current 
       online card, the next switch can be performed only after a 
       minimum time, indicated by this object.
       Valid Values: 0..300, 65535.
       65535=NA.
       This object is applicable only when sysCRdnRecMode=auto."
      ::= { sysCRdnEntry 8 }

sysCRdnHwSwFlip OBJECT-TYPE
      SYNTAX  INTEGER
       {
          notApplicable(1),
          hw           (2),
          sw           (3)
       }
      MAX-ACCESS  read-create
      STATUS  current
      DESCRIPTION
      "HW or SW decision for Redundancy Flip. 
       This object is applicable only for sysCRdnMode=singleSlotProtection.
       HW - decision is by I/O card
       SW - decision is by CL SW."
      ::= { sysCRdnEntry 9 }

sysCRdnRowStatus  OBJECT-TYPE
     SYNTAX  RowStatus
     MAX-ACCESS   read-create
     STATUS   current
     DESCRIPTION
     "This parameter allows NMS to create/delete entries of this table.
      The possible supported RowStatus values are
      active (1) and destroy (6).
      
      For Vmux-2100 the supported values are:
      active (1), createAndGo (4) and destroy (6)." 
     ::= { sysCRdnEntry 10 }

sysCRdnOnline OBJECT-TYPE
      SYNTAX  INTEGER
       {
          notApplicable (1),
          primary       (2),
          secondary     (3)
       }
      MAX-ACCESS  read-only
      STATUS  current
      DESCRIPTION
      "Status - who is the Online (current) Redundancy Slot/Port. 
       This object shows only the Online Slot/Port regarding the Redundancy. 
       mdlSActivity or prtGenActiveStatus of the same Slot/Port may be Offline."
      ::= { sysCRdnEntry 11 }

sysCRdnSwitchingMode  OBJECT-TYPE
      SYNTAX  INTEGER
       {
          notApplicable    (1),
          biDirectional    (2), --1+1
          uniDirectional   (3), --1:1
          linkAggregation  (4)  --802.3ad
       }
      MAX-ACCESS  read-create
      STATUS  current
      DESCRIPTION
      "This object defines which Self Healing Ring (SHR) SDH ring is used: 
       Uni Directional or BiDirectional. The type of the ring
       is defined according to the direction of traffic flow under 
       normal working conditions. 

       In Bi Directional ring, the duplex traffic is on the same path 
       and transverses the same set of nodes for both directions of transmission. 
       In Uni Directional ring, the duplex traffic travels over opposite path 
       (per direction) and all the node of the ring are involved.

       For Uni Directional  SHR Protection Switching (Single Ended Switching) 
       is controlled by one node of the SDH ring, and does not require a protocol.
       For Bi Directional SHR Protection Switching (Dual Ended switching) 
       is controlled by some nodes of  the ring and requires a protocol"
      ::= { sysCRdnEntry 12 }

sysCRdnFlipUponEvent  OBJECT-TYPE
     SYNTAX  Integer32
     MAX-ACCESS   read-create
     STATUS   current
     DESCRIPTION
     "This object allows user to define if Flip to the other port will
      be performed (or not), for certain possible events.
      Each event is represented by a bit. The value of the object is a sum
      of 2**n, according to the bits having '1' value.
      '1' - means that Flip should occur due to this event.
      Bit 0 (LSB) = SD (Signal Degraded).
      For IPmux:
      Bit 0 (LSB) = TDM Line LOS/LOF.
      Bit 1       = Sequence Number.
      Bit 2       = Jitter Buffer errors."
     ::= { sysCRdnEntry 13 }

sysCRdnLosOrLofTime OBJECT-TYPE
    SYNTAX      Integer32 
    MAX-ACCESS  read-create
    STATUS      current
    DESCRIPTION
            "This parameter determines the time to wait before switching,
            e.g. after failure (as LOF or LOS) is detected on the TDM
            Line.
            For Ipmux time is counted in msec.
            MP uses second units."
    ::= { sysCRdnEntry 14 }

sysCRdnEventsTimeWindow OBJECT-TYPE
    SYNTAX  Integer32 
    MAX-ACCESS  read-create
    STATUS  current
    DESCRIPTION
    "This parameter determines the time window in which 
    to count events to trigger protection switching.
     For Ipmux time is counted in seconds."
    ::= { sysCRdnEntry 15 }

sysCRdnSequenceNumberThreshold OBJECT-TYPE
    SYNTAX  Integer32 
    MAX-ACCESS  read-create
    STATUS  current
    DESCRIPTION
    "This parameter determines the number of Sequence Number errors
     that should occur in the time window in order to cause switching."
    ::= { sysCRdnEntry 16 }

sysCRdnBufferErrorsThreshold OBJECT-TYPE
    SYNTAX  Integer32 
    MAX-ACCESS  read-create
    STATUS  current
    DESCRIPTION
    "This parameter determines the number of Buffer undeflow/ overflow events
     occured in the time window that cause switching."
    ::= { sysCRdnEntry 17 }

sysCRdnBuffUnderrunTime OBJECT-TYPE
    SYNTAX  Integer32 
    MAX-ACCESS  read-create
    STATUS  current
    DESCRIPTION
    "This parameter determines how much time to wait before switching,
     after jitter buffer underrun.
     Switching occurs if no frame arrives within that time.
     For Ipmux time is counted in msec."
    ::= { sysCRdnEntry 18 }

sysCRdnPrimePriority OBJECT-TYPE
      SYNTAX  INTEGER
       {
          notApplicable (1),
          low       (2),
          high      (3)
       }
      MAX-ACCESS  read-create
      STATUS  current
      DESCRIPTION
      "The Primary port priority.
      
      In ETX2xx/2xxA: 
      When selecting sysCRdnMode = manual (10), 
      this parameter determines the forced active port:
      low - means that the secondary port is selected to be active
      high - means that the primary port is selected to be active. "
      ::= { sysCRdnEntry 19 }

sysCRdnSecPriority OBJECT-TYPE
      SYNTAX  INTEGER
       {
          notApplicable (1),
          low       (2),
          high      (3)
       }
      MAX-ACCESS  read-create
      STATUS  current
      DESCRIPTION
      "The Secondary port priority."
      ::= { sysCRdnEntry 20 }

sysCRdnWTR OBJECT-TYPE
      SYNTAX  Unsigned32 
      MAX-ACCESS  read-create
      STATUS  current
      DESCRIPTION
      "Redundancy Wait to Restore (sec).
       Valid Values: 0..999, 65535.
       65535=NA.
       When the value <> 65535, the value of sysCRdnRecTime must be 65535."
      ::= { sysCRdnEntry 21 }

sysCRdnName OBJECT-TYPE
    SYNTAX      SnmpAdminString
    MAX-ACCESS  read-create
    STATUS      current
    DESCRIPTION
        "A textual name for the redundancy group."
    ::= { sysCRdnEntry 22 }

sysCRdnTxDownDurationUponFlip    OBJECT-TYPE
    SYNTAX      Unsigned32  (0..30)
    MAX-ACCESS  read-create
    STATUS      current
    DESCRIPTION
    "This object defines the duration (in seconds) the active 
     port transmission is shut down after flip occurs.
     The transmission is shut down and then opened again (after the duration
     defined by this object), in order to cause the other side to flip 
     to the new active port.
     0 = no shut-down.
     This object is applicable only when sysCRdnMode = oneToOne(8)
     and mainly when each of the links of our device is connected to a different device."
     ::= { sysCRdnEntry 23 }



--IO Redundancy - Commands
--This table was moved here, so that its indexes will be defined before, 
--for SNMPc

sysSRdnCmdTable OBJECT-TYPE
      SYNTAX SEQUENCE OF SysSRdnCmdEntry
      MAX-ACCESS not-accessible
      STATUS current
      DESCRIPTION
      "This table includes commands used for IO Redundancy."
      ::= { sysStatus 22 }

sysSRdnCmdEntry OBJECT-TYPE
      SYNTAX SysSRdnCmdEntry
      MAX-ACCESS not-accessible
      STATUS current
	  DESCRIPTION  "An entry in table."
	  INDEX {sysCRdnPrimeSlot, sysCRdnPrimePort }
      ::= { sysSRdnCmdTable 1}

SysSRdnCmdEntry ::=
     SEQUENCE {
     sysSRdnEnforcedChannel      INTEGER,
	 sysSRdnLockFlip      		 INTEGER,
	 sysSRdnManualFlip      	 INTEGER
	}

sysSRdnEnforcedChannel OBJECT-TYPE
     SYNTAX       INTEGER {
     notApplicable 	(1),
     noEnforcement 	(2),
     primary	    (3),
	 secondary		(4)
        }
     MAX-ACCESS    read-write
     STATUS        current
     DESCRIPTION
     "This is a command to override all switching considerations
      and enforce use of primary/ secondary connection only.
	  noEnforcement - cancels the state of override and goes back to
	                  usual switching considerations.
      Default = noEnforcement(2)."
     ::= {sysSRdnCmdEntry 1 }

 sysSRdnLockFlip 	OBJECT-TYPE
     SYNTAX       INTEGER {
     notApplicable 	(1),
     off 			(2),
     on	    		(3)	 
        }
     MAX-ACCESS    read-write
     STATUS        current
     DESCRIPTION
     "This is a command to lock the Redundancy flip for this redundancy couple.
      Default = off(2)."
     ::= {sysSRdnCmdEntry 2 }

sysSRdnManualFlip 	OBJECT-TYPE
     SYNTAX       INTEGER {
     notApplicable 	(1),
     off 			(2),
     on	    		(3)	 
        }
     MAX-ACCESS    read-write
     STATUS        current
     DESCRIPTION
     "This is a command to move to manual Redundancy flip mode for this redundancy couple.
      Default = off(2)."
     ::= {sysSRdnCmdEntry 3 }

--System Database operations

sysDbaseSanityCheckCmd OBJECT-TYPE
      SYNTAX  INTEGER
       {
       off(2),
       on (3)
       }
      MAX-ACCESS  read-write
      STATUS  current
      DESCRIPTION
      "Setting this attribute to on(3) will initiate the process 
       of Sanity check on the TmpCnfg. Upon completion, the value 
       will automatically change to off(2)."
      ::= { sysDbase 1 }

sysDbaseDownloadCnfgIdxCmd OBJECT-TYPE
      SYNTAX  Integer32   (1..255)
      MAX-ACCESS  read-write
      STATUS  current
      DESCRIPTION
      "This attribute specifies the Id of the target RealCnfg to 
       which the TmpCnfg should be transferred. Upon set command, 
       the DACS agent will initiate the Sanity-Check  process.  
       If successful, the actual transfer will be performed. 
       If there will be errors, the user will have to perform
       the command again after errors correction.       
       The operation is valid only on configuration numbers
       that do not exceed sysSMaxNoOfCnfg."
      ::= { sysDbase 2 }
-- In phase I of DXC and FCD only the value 1 (Cnfg1) is valid.

sysDbaseUploadCnfgIdxCmd OBJECT-TYPE
      SYNTAX  Integer32  (1..255)
      MAX-ACCESS  read-write
      STATUS  current
      DESCRIPTION
      "This attribute specifies the Id of the source Cnfg to be 
       loaded into the TmpCnfg. Upon set operation the actual 
       transfer will be initiated.
       The operation is valid only on configuration numbers
       that do not exceed sysSMaxNoOfCnfg."
      ::= { sysDbase 3 }
-- In phase I of DXC and FCD only the value 1 (Cnfg1) is valid.

sysDbaseFlipTable  OBJECT-TYPE
      SYNTAX SEQUENCE OF SysDbaseFlipEntry
      MAX-ACCESS not-accessible
      STATUS  current
      DESCRIPTION
      "Dbase Flip time and activation for every configuration."
       ::= { sysDbase 4 }

sysDbaseFlipEntry OBJECT-TYPE
      SYNTAX SysDbaseFlipEntry
      MAX-ACCESS not-accessible
      STATUS current
	DESCRIPTION  "An entry in table."
	INDEX {sysDbaseFlipIdx}
      ::= { sysDbaseFlipTable 1}

SysDbaseFlipEntry ::=
      SEQUENCE {
   sysDbaseFlipIdx        Integer32,
   sysDbaseFlipTime       DisplayString,
   sysDbaseFlipActivation INTEGER      }

sysDbaseFlipIdx OBJECT-TYPE
      SYNTAX Integer32 (1..255)
      MAX-ACCESS read-only
      STATUS current
      DESCRIPTION
      "This attribute indicates the Idx of the Cnfg being 
       the target Configuration."
      ::= { sysDbaseFlipEntry 1}

sysDbaseFlipTime OBJECT-TYPE
      SYNTAX DisplayString (SIZE(0..255))
      MAX-ACCESS read-write
      STATUS current
      DESCRIPTION
      "This attribute indicates the time (HH:MM) when this data 
       base will start being used by the Tmp config."
      ::= { sysDbaseFlipEntry 2}

sysDbaseFlipActivation OBJECT-TYPE
      SYNTAX INTEGER {
      disable (1),
      enable  (2)
   }
      MAX-ACCESS read-write
      STATUS current
      DESCRIPTION
      "This attribute indicates if the Dbase flip will be 
       activated at the time specified for this configuration 
       (enable) or not (disable). 
       No more than one flip should be enabled for the same time."
      ::= { sysDbaseFlipEntry 3}


--Module (card) level of DACS MIB

mdlGen   OBJECT IDENTIFIER ::= {mdlDacsMux 1}
mdlCl   OBJECT IDENTIFIER ::=  {mdlDacsMux 2}
mdlPs   OBJECT IDENTIFIER ::=  {mdlDacsMux 3}

--DACS module (card) general parameters (common to all cards 
--type)

--General Card - Status information table 
--This table is NOT-APPLICABLE for a stand-alone unit  

mdlSTable  OBJECT-TYPE
      SYNTAX SEQUENCE OF MdlSEntry
      MAX-ACCESS not-accessible
      STATUS current
	DESCRIPTION  "A table."
	::=  { mdlGen 1 }

mdlSEntry OBJECT-TYPE
      SYNTAX MdlSEntry
      MAX-ACCESS not-accessible
      STATUS current
	DESCRIPTION  "An entry in table."
	INDEX { mdlSSltIdx }
      ::= { mdlSTable 1}

MdlSEntry ::=
      SEQUENCE {
  mdlSSltIdx            SlotType,
  mdlSCardType          CardType,
  mdlSHwVer             DisplayString,
  mdlSSwVer             DisplayString,
  mdlSAlarmStatus       INTEGER,
  mdlSAlarmStatusAll    INTEGER,
  mdlSTestStatus        INTEGER,
  mdlSHwStatus          INTEGER,
  mdlSActivity          INTEGER,
  mdlSAlrClearCmd       INTEGER,
  mdlSAlrClearAllCmd    INTEGER,
  mdlSAlrMaskAll        INTEGER,
  mdlSCmd               Integer32,
  mdlSReset             INTEGER,
  mdlSRebuildFrame      INTEGER,
  mdlSBackupSwVer		DisplayString,
  mdlSSecondaryBackupSwVer		DisplayString,
  mdlSPiggybackVer      SnmpAdminString
        }

mdlSSltIdx OBJECT-TYPE
      SYNTAX  SlotType
      MAX-ACCESS  read-only
      STATUS  current
      DESCRIPTION
      "A unique number to identify a slot position in the DACS.
       The Kilomux should use enumerated values starting with kmx.
       For IPmux100 use values 1-13, 20."
      ::= { mdlSEntry 1}


mdlSCardType OBJECT-TYPE
      SYNTAX  CardType
      MAX-ACCESS  read-only
      STATUS  current
      DESCRIPTION
      "This attribute indicates the type of  the card installed
       in the specific slot position.
       Only PS's are possible in the PS slots.
       Only CL's are possible in the CL slots.
       Only IO modules are possible in the IO slots.
       Kmux card type start with the letter k.
       LA card type start with the letters la."
      ::= { mdlSEntry 2}

mdlSHwVer OBJECT-TYPE
      SYNTAX  DisplayString (SIZE (0..255))
      MAX-ACCESS  read-only
      STATUS  current
      DESCRIPTION
      "This attribute indicates the Hardware version of the 
       card installed in the specific slot position."
      ::= { mdlSEntry 3 }

mdlSSwVer OBJECT-TYPE
      SYNTAX  DisplayString (SIZE (0..255))
      MAX-ACCESS  read-only
      STATUS  current
      DESCRIPTION
      "This attribute indicates the Software version of the 
       card installed in the specific slot position."
      ::= {mdlSEntry 4}


mdlSAlarmStatus OBJECT-TYPE
      SYNTAX  INTEGER
       {
  off      (2),
  major    (3),
  minor    (4),
  event    (5),
  warning  (6),
  critical (7)
       }
      MAX-ACCESS  read-only
      STATUS  current
      DESCRIPTION
      "Indicates the current alarm state only for card level.
       This object will be set to: 
       - critical(7): when there is at least one active (ON) critical 
                    alarm .
       - major (3): when there is no active critical alarm, but there is
                    at least one active (ON) major alarm .
       - minor (4): when there is no active major or critical alarm, but 
                    there is at least one active minor alarm.
       - warning (6): when there is no active major, critical or minor alarm, but 
                    there is at least one active warning alarm.
       - event (5): when there is no active alarm of another type, but 
                    there is at least one active event alarm.
       - off(2): when there is no active (ON) alarm (since last clear operation)."
      ::= { mdlSEntry 5 }

mdlSAlarmStatusAll OBJECT-TYPE
      SYNTAX  INTEGER
       {
  off      (2),
  major    (3),
  minor    (4),
  event    (5),
  warning  (6),
  critical (7)
       }
      MAX-ACCESS  read-only
      STATUS  current
      DESCRIPTION
      "Indicates the current card alarm state including the 
       lower level:  card, port.
       This object will be set to: 
       - critical(7): when there is at least one active (ON) critical 
                    alarm .
       - major (3): when there is no active critical alarm, but there is
                    at least one active (ON) major alarm .
       - minor (4): when there is no active major or critical alarm, but 
                    there is at least one active minor alarm.
       - warning (6): when there is no active major, critical or minor alarm, but 
                    there is at least one active warning alarm.
       - event (5): when there is no active alarm of another type, but 
                    there is at least one active event alarm.
       - off(2): when there is no active (ON) alarm (since last clear operation)."
      ::= { mdlSEntry 6 }

mdlSTestStatus OBJECT-TYPE
      SYNTAX  INTEGER
       {
  off(2),
  on (3)
       }
      MAX-ACCESS  read-only
      STATUS  current
      DESCRIPTION
      "This attribute will be on(3) when there is at least 
       one test running on a port of the module; otherwise the value 
       will be off(2)."
      ::= { mdlSEntry 7 }

mdlSHwStatus OBJECT-TYPE
      SYNTAX  INTEGER
       {
  fail(2),
  ok  (3)
       }
      MAX-ACCESS  read-only
      STATUS  current
      DESCRIPTION
      "This attribute will be fail(2) when a HW FAIL exists
       on this module (discovered by periodic self test); 
       otherwise the value will be ok(3)."
      ::= { mdlSEntry 8 }

mdlSActivity OBJECT-TYPE
      SYNTAX  INTEGER
       {
  notApplicable (1),
  offline       (2),
  online        (3)
       }
      MAX-ACCESS  read-only
      STATUS  current
      DESCRIPTION
      "notApplicable - when the slot is empty (no module)
       offline(1) - when the module is not active (redundant) 
       online (2) - when the module is active ."
      ::= { mdlSEntry 9 }

mdlSAlrClearCmd  OBJECT-TYPE
      SYNTAX  INTEGER
       {
  off(2),
  on (3)
       }
      MAX-ACCESS  read-write
      STATUS  current
      DESCRIPTION
      "Setting this attribute to ON, will enforce a  clear 
       operation on the card level alarms . Upon completion, 
       the value will automatically change to off(2)."
      ::= { mdlSEntry 10 }


mdlSAlrClearAllCmd  OBJECT-TYPE
      SYNTAX  INTEGER
       {
  off(2),
  on (3)
       }
      MAX-ACCESS  read-write
      STATUS  current
      DESCRIPTION
      "Setting this attribute to ON, will enforce a  clear 
       operation on card and port level alarms . Upon completion, 
       the value will automatically change to off(2)."
      ::= { mdlSEntry 11 }

mdlSAlrMaskAll  OBJECT-TYPE
      SYNTAX  INTEGER
       {
  off(2),
  on (3)
       }
      MAX-ACCESS  read-write
      STATUS  current
      DESCRIPTION
      "on(3)  - will cause masking of all the card level alarms.
                These alarms will not be sent to NMS and will not 
                be taken into account for Alarms Status.
       off(2) - will unmask all card level alarms except those 
                masked via the mdlAlrMaskTable. "
      ::= { mdlSEntry 12 }

mdlSCmd  OBJECT-TYPE
      SYNTAX  Integer32
      MAX-ACCESS  read-write
      STATUS  current
      DESCRIPTION
      "General object for any special command at card level.
       0=NotApplicable, for cards that don't support this object.

       For KML.10(ISDN) card of KM-2100,  the object will indicate 
       Manual Call Command in Switch mode. It is applicable only when
       for KML.10, prtIsdnSwitchMode=manual.
       KML.10 valid values:
       '1' =  noOp, will be used by agents that do not support this 
              feature or object (old KM agents)
       '2' = off, Set call command mode to disconnect state. Disconnects the call.
       '3' = on,  Set call command mode to connect state. Connects the call.
       
       For DXC IO cards, the object will be used for IO Card Reset HW command:
       '2' = off, this will be always the Get value for these cards.
       '3' = on,  this is the Set command used to Reset the IO card. Upon 
             completing the operation, the value will automatically change to off(2),
             by Agent.
       For Slots that are NOT IO Slots and for empty IO Slots, the Get value will
       be always '0' (NotApplicable). "
      ::= { mdlSEntry 13 } 
      

mdlSReset  OBJECT-TYPE
      SYNTAX  INTEGER {
	                   off (2),
					   on  (3)   --HW
					  }
      MAX-ACCESS  read-write
      STATUS  current
      DESCRIPTION
            	"Reset action to be performed on the module."
      ::= { mdlSEntry 14 } 

mdlSRebuildFrame OBJECT-TYPE
      SYNTAX  INTEGER {notApplicable(1),
                       off          (2),
                       on           (3)
                              } 
      MAX-ACCESS  read-write
      STATUS  current
      DESCRIPTION
      "Applicable only for KiloMux Main Link cards only.
	   '2' = off, this will be always the Get value.
       '3' = on,  this is the Set command used to Rebuild the Frame. 
       Upon completing the operation, the value will automatically change 
       to off(2), by Agent."
      ::= { mdlSEntry 15}

mdlSBackupSwVer OBJECT-TYPE
      SYNTAX  DisplayString (SIZE (0..255))
      MAX-ACCESS  read-only
      STATUS  current
      DESCRIPTION
      "This attribute indicates the Backup Software version of the 
       card installed in the specific slot position."
      ::= {mdlSEntry 16}

mdlSSecondaryBackupSwVer OBJECT-TYPE
      SYNTAX  DisplayString (SIZE (0..255))
      MAX-ACCESS  read-only
      STATUS  current
      DESCRIPTION
      "This attribute indicates the Secondary Backup Software version of the 
       card installed in the specific slot position."
      ::= {mdlSEntry 17}

mdlSPiggybackVer OBJECT-TYPE
      SYNTAX  SnmpAdminString (SIZE (0..255))
      MAX-ACCESS  read-only
      STATUS  current
      DESCRIPTION
      "This attribute indicates the Piggyback version of the 
       card installed in the specific slot position."
      ::= { mdlSEntry 18 }


--General Card - Configuration table 
--This table is NOT-APPLICABLE for a stand-alone unit  

mdlCTable  OBJECT-TYPE
      SYNTAX SEQUENCE OF MdlCEntry
      MAX-ACCESS not-accessible
      STATUS current
    DESCRIPTION  "A table."
    ::=  { mdlGen 2 }

mdlCEntry OBJECT-TYPE
      SYNTAX MdlCEntry
      MAX-ACCESS not-accessible
      STATUS current
    DESCRIPTION  "An entry in table."
    INDEX { mdlCConfigIdx, mdlCSlotIdx  }
      ::= { mdlCTable 1}

MdlCEntry ::= SEQUENCE {
    mdlCConfigIdx           Integer32,
    mdlCSlotIdx             SlotType,
    mdlCProgCardType        CardType,
    mdlCNoOfExtPrt          Integer32,
    mdlCNoOfIntPrt          Integer32,
    mdlCParam               Integer32,
    mdlCAdminStatus         INTEGER,
    mdlCActualCardType      CardType,
    mdlCOperStatus          INTEGER,
    mdlCDetailedStatus      BITS,
    mdlCEntPhysicalIndex    PhysicalIndexOrZero,
    mdlCReset               INTEGER,
    mdlCConfigMismatchReason   INTEGER,
    mdlCIpAddressType           InetAddressType,
    mdlCIpAddress               InetAddress,
    mdlCHardwareFailureReason   INTEGER,
    mdlCFanControl               INTEGER,
    mdlCFanOperStatus            INTEGER 
 }

mdlCConfigIdx OBJECT-TYPE
      SYNTAX  Integer32 (1..255)
      MAX-ACCESS  read-only
      STATUS  current
      DESCRIPTION
      "This object indicates the Configuration number (1..255) 
       referred.
       Value of  255 specifies the TmpCnfg (Scratch)."
      ::= { mdlCEntry 1}
-- In phase 1 only the values 1 (Cnfg1) and 255 (temp) are valid.

mdlCSlotIdx OBJECT-TYPE
      SYNTAX  SlotType
      MAX-ACCESS  read-only
      STATUS  current
      DESCRIPTION
      "This object indicates a unique number of the slot position 
       in which the module is inserted.
       The Kilomux should use enumerated values starting with kmx."
      ::= { mdlCEntry 2}


mdlCProgCardType OBJECT-TYPE
      SYNTAX    CardType
      MAX-ACCESS  read-write
      STATUS  current
      DESCRIPTION
      "This object indicates the card type assigned to the specific 
       slot in the common configuration.
       This object is identical for all the configurations (1..255).
       Only the TmpCnf(255) might have a  different value.
       The write operation is valid only for the TmpCnfg entry."
      ::= { mdlCEntry 3}

mdlCNoOfExtPrt OBJECT-TYPE
      SYNTAX  Integer32
      MAX-ACCESS  read-only
      STATUS  current
      DESCRIPTION
      "Number of external ports in the programmed module of 
       the specific slot position"
      ::= { mdlCEntry 4}

mdlCNoOfIntPrt OBJECT-TYPE
      SYNTAX  Integer32
      MAX-ACCESS  read-only
      STATUS  current
      DESCRIPTION
      "Number of internal ports in the programmed module of 
       the specific slot position."
      ::= { mdlCEntry 5}

mdlCParam  OBJECT-TYPE
      SYNTAX  Integer32
      MAX-ACCESS  read-write
      STATUS  current
      DESCRIPTION
      "General configuration object at card level (per configuration).
       NotApplicable=0, for cards that don't support this object.

       For D8U and D16U cards of DXC,  the object will indicate 
       the port on which BERT will be performed. The port can be
       one of the external ports, any of its associated B1, B2, D ports
       or no port of the card (None=0).
       For port indexes see DXC R6 spec.
       
       For Gmux-2000, this parameter used for determining the Gigabit ETH exit port"
      ::= {mdlCEntry 6 } 


mdlCAdminStatus OBJECT-TYPE
    SYNTAX  INTEGER {
            up(1),       
            down(2)
            }
    MAX-ACCESS  read-write
    STATUS      current
    DESCRIPTION
        "The desired state of the module.

         Module adminStatus should be managed for all modules in the shelf.
         When adminStatus is 'down', this module is not operational i.e.
         this module doesn't handle traffic and doesn't generate traps.

         Setting module adminStatus to up should always succeed (the
         operStatus might remain 'down' as a result of a failure).

         up
         The desired state for this module is operational.

         down
         The desired state for this module is disabled.When a managed
         system initializes, all instances start with
         mdlCAdminStatus in the up(1) state. As a result of either
         explicit management action or per configuration information
         retained by the managed system, mdlCAdminStatus is then
         changed to either the 'down' or remains in the 'up' state."
    DEFVAL  { up }
    ::= { mdlCEntry 7 }

mdlCActualCardType OBJECT-TYPE
    SYNTAX      CardType
    MAX-ACCESS  read-only
    STATUS      current
    DESCRIPTION
    "This object defines actual card type."
    ::= { mdlCEntry 8 }

mdlCOperStatus OBJECT-TYPE
    SYNTAX  INTEGER {
            up(1),
            down(2),
            notPresent (3)
            }
    MAX-ACCESS  read-only
    STATUS      current
    DESCRIPTION
        "The current operational state of the module.
                                                                                
         up
         The physical module agrees with the pre-provisioned card type,
         and the configuration of the module succeeded.

         down
         There are one or more problems/failures with the module.
         Detailed information is contained in the object mdlCDetailedStatus.

         notPresent
         The module is not detected in the shelf at the moment."
    ::= { mdlCEntry 9 }

mdlCDetailedStatus OBJECT-TYPE
    SYNTAX  BITS {
        initializing          (0),
        cardMismatch          (1),
        initFailed            (2),
        provisionFailed       (3),
        selfTestFailed        (4),
        commFailure           (5),
        bpInterfaceFailure    (6),
        configurationMismatch (7),
        noInputPower          (8)
        }
        MAX-ACCESS  read-only
        STATUS  current
        DESCRIPTION
        " The module current status.

          When moduleOperStatus is down(2), but not as a result of
          setting the moduleAdminStatus to down(2), this object contains
          the failure reason or reasons.

          The moduleOperStatus value can be up(1) only when all bits of
          this object are cleared.

          The following failure reasons can be indicated:

          initializing (0)
          The module initialization procedure is in progress.
          For a MC the start-up time may take a few minutes and the bit
          should be set during this time.

          cardMismatch (1)
          There is a type mismatch between the pre-provisioned module and
          the actual installed module.

          initFailed (2)
          A SW download problem from the Main Card to an I/O card.

          provisionFailed (3)
          Provisioning failure or any other initialization problem of an I/O card.

          selfTestFailed (4)
          Power-up or periodic diagnostics has detected a H/W malfunction of the card.

          commFailure (5)
          The MC detects loss of management communication with an I/O card that 
          it was previously talking to. In other words, the I/O card completed
          its initialization and already established communication with the MC
          and at some time later the management communication failed.

          bpInterfaceFailure (6)
          One or more of the module's backplane interfaces has detected bit errors
          or loss of packets.
          
          configurationMismatch(7)
          Indication that a configuration mismatch was detected while 
          the card has been configured 

          noInputPower(8)
          Indication that module (usually a power inlet) is plugged-in  but no power
          cable is attached to it.          
          "
    ::= { mdlCEntry 10 }

mdlCEntPhysicalIndex    OBJECT-TYPE
    SYNTAX      PhysicalIndexOrZero
    MAX-ACCESS  read-only
    STATUS      current
    DESCRIPTION
    "The object contains index of the related entPhysicalEntry of the
    ENTITY-MIB, see RFC4133. It points the relevant card and not the
    card slot. The agent should build this index accordign to the rules
    that are defined by the inventory.doc document.
    Zero value means 'no entry defined', i.e. the card is not detected
    in its slot."
    ::= { mdlCEntry 11 }

mdlCReset  OBJECT-TYPE
    SYNTAX  INTEGER {
        off (2),
        on  (3)
        }
    MAX-ACCESS  read-write
    STATUS  current
    DESCRIPTION
    "Reset action to be performed on the module. 
    Agent should set mdlCReset to off (2) during initialization."
    DEFVAL  { off }
    ::= { mdlCEntry 12 }
    
    
mdlCConfigMismatchReason        OBJECT-TYPE
    SYNTAX  INTEGER {
       s128KbpsInSynchronousMode             (1), -- 128 kbps in synchronous mode
       s14k4KbpsConfiguration                (2), -- 14.4 kbps configuration
       s28k8KbpsConfiguration                (3), -- 28.8 kbps configuration
       s48KbpsConfiguration                  (4), -- 48 kbps configuration
       s56KbpsInSynchronousMode              (5), -- 56 kbps in synchronous mode
       s7k2KbpsConfiguration                 (6), -- 7.2 kbps configuration
       adpcmConfiguration                    (7),  -- ADPCM configuration
       dceOnDteHwInSynchronousMode           (8),  -- DCE on DTE HW in synchronous mode
       dteOnDceHwInSynchronousMode           (9),  -- DTE on DCE HW in synchronous mode
       rlbLlbInV110RateAdaptation           (10), -- RLB/LLB in V.110 rate adaptation
       swNotSupportingAdvancedSignaling (11), -- SW not supporting advanced signaling
       signalingConfiguration               (12), -- signaling configuration
       stratum1WithoutOcxo                  (13), -- stratum 1 without OCXO
       stratum2WithoutOcxo                  (14), -- stratum 2 without OCXO
       useOf4TdmBusesInChassis              (15), -- use of 4 TDM buses in chassis
       winkStartModeConfiguration           (16),  -- wink start mode configuration
       other                        (2147483647)
        }
    MAX-ACCESS  read-only
    STATUS  current
    DESCRIPTION
    "This object details the card configuration mismatch 
    in case the object mdlCDetailedStatus is equal to configurationMismatch(7)" 
::= { mdlCEntry 13 }

mdlCIpAddressType OBJECT-TYPE
    SYNTAX      InetAddressType
    MAX-ACCESS  read-write
    STATUS      current
    DESCRIPTION
            "The object defines type of the mdlCIpAddress as defined
            in the InetAddress MIB: IPv4 or IPv6."
    ::= { mdlCEntry 14 }

mdlCIpAddress OBJECT-TYPE
    SYNTAX      InetAddress
    MAX-ACCESS  read-write
    STATUS      current
    DESCRIPTION
            "The object defines card IP address that will be associated
            with the card loopback IP interface."
    ::= { mdlCEntry 15 }

mdlCHardwareFailureReason          OBJECT-TYPE
    SYNTAX  INTEGER {
    other                   (1),
    ringerVoltageFailure    (2),
    fanFailure              (3)
    }
    MAX-ACCESS  read-only
    STATUS  current
    DESCRIPTION
    ""  
::= { mdlCEntry 16 }

mdlCFanControl     OBJECT-TYPE
    SYNTAX      INTEGER
    {
    up          (1),
    down    (2)
    }
    MAX-ACCESS  read-write
    STATUS      current
    DESCRIPTION
    "The desired state of the fan.

     Module fan control shall manage all fans on the module, if there are more than one.
     When mdlCFanControl is 'up', all module's fans must be in on state.
     When mdlCFanControl is 'down', all module's fans must be in off state.

     Setting module mdlCFanControl to 'up' should always succeed (if HW enables detection of
     current fan status, the mdlCFanStatus might remain 'down' as a result of a fan failure).

     up
     The desired state for all module's fans is operational.

     down
     The desired state for all module's fans is disabled."
    DEFVAL      { up }
    ::= { mdlCEntry 22 }

mdlCFanOperStatus     OBJECT-TYPE
    SYNTAX      INTEGER
    {
    up                  (1),
    down            (2),
    notPresent  (3)
    }
    MAX-ACCESS  read-only
    STATUS      current
    DESCRIPTION
    "The current operational state of the module's fans. Provides the
     aggregated state of all fans, if there are more than one on the module.
                                                                                
     up
     All the fans on the module are in operational state and running.

     down
     All fans on the module are at disabled state, or, if HW enables actual status detection,
     at least one of the fans on the module does not operate as a result of failure.

     notPresent
     There are no fans on the module - the default value for modules without fans."
    ::= { mdlCEntry 23 }

--Module level current alarms

mdlAlr OBJECT IDENTIFIER ::= {mdlGen 3}

mdlAlrTable OBJECT-TYPE
      SYNTAX SEQUENCE OF MdlAlrEntry
      MAX-ACCESS not-accessible
      STATUS current
      DESCRIPTION
      "The list of card alarms. "
      ::= { mdlAlr 1 }

mdlAlrEntry OBJECT-TYPE
      SYNTAX MdlAlrEntry
      MAX-ACCESS not-accessible
      STATUS current
	DESCRIPTION  "An entry in table."
	INDEX {mdlAlrSltIdx , mdlAlrIdx}
      ::= { mdlAlrTable 1}

MdlAlrEntry ::=
      SEQUENCE {
  mdlAlrSltIdx           SlotType,
  mdlAlrIdx              Integer32,
  mdlAlrCode             Integer32,
  mdlAlrState            INTEGER,  --severity
  mdlAlarmMask           INTEGER,
  mdlAlarmInvert         INTEGER,
  mdlAlarmOnOff          INTEGER,
  mdlAlarmCounter        Integer32 
	}

mdlAlrIdx OBJECT-TYPE
      SYNTAX  Integer32
      MAX-ACCESS  read-only
      STATUS  current
      DESCRIPTION
      "A unique number to identify an entry in the alarm status 
       table.
       Users should use the get next function to read this table 
       because the indexes are not consecutive"
      ::= { mdlAlrEntry 1}

mdlAlrSltIdx OBJECT-TYPE
      SYNTAX  SlotType
      MAX-ACCESS  read-only
      STATUS  current
      DESCRIPTION
      "This attribute indicates the  desired slot position. 
       The Kilomux should use enumerated values starting with kmx."
      ::= { mdlAlrEntry 2}

mdlAlrCode OBJECT-TYPE
      SYNTAX  Integer32
      MAX-ACCESS  read-only
      STATUS  current
      DESCRIPTION
      "This object indicates a code related to a specific
       alarm description. The list of codes and their related
       descriptions will be sent to NMS request (for display purpose)
       by alrGenTable."
      ::= { mdlAlrEntry 3 }

mdlAlrState OBJECT-TYPE
      SYNTAX  INTEGER {
   event    (3),
   minor    (4),
   major    (5),
   warning  (6),
   critical (7)
       }
      MAX-ACCESS  read-only
      STATUS  current
      DESCRIPTION
      "This object indicates the card alarm severity."      
      ::= { mdlAlrEntry 4 }

mdlAlarmMask OBJECT-TYPE
      SYNTAX  INTEGER {
  off(2),
  on (3)
       }
      MAX-ACCESS  read-only
      STATUS  current
      DESCRIPTION
      "Alarm Mask is : on/off."
      ::= { mdlAlrEntry 5 }

mdlAlarmInvert OBJECT-TYPE
      SYNTAX  INTEGER {
  off(2),
  on (3)
       }
      MAX-ACCESS  read-only
      STATUS  current
      DESCRIPTION
      "Alarm Invert is : on/off."
      ::= { mdlAlrEntry 6 }

mdlAlarmOnOff OBJECT-TYPE
      SYNTAX  INTEGER {
  off(2),
  on (3)
       }
      MAX-ACCESS  read-only
      STATUS  current
      DESCRIPTION
      "Alarm state is : on/off."
      ::= { mdlAlrEntry 7}

mdlAlarmCounter OBJECT-TYPE
      SYNTAX  Integer32
      MAX-ACCESS  read-only
      STATUS  current
      DESCRIPTION
      "A counter - how many times the alarm occured (ON) since last
       clear operation or since last Reset."
      ::= { mdlAlrEntry 8 }

mdlAlrMaskTable OBJECT-TYPE
      SYNTAX SEQUENCE OF MdlAlrMaskEntry
      MAX-ACCESS not-accessible
      STATUS current
      DESCRIPTION
      "The list of card masked alarms. "
      ::= { mdlAlr 2 }

mdlAlrMaskEntry OBJECT-TYPE
      SYNTAX MdlAlrMaskEntry
      MAX-ACCESS not-accessible
      STATUS current
	DESCRIPTION  "An entry in table."
	INDEX {mdlAlrMaskSltIdx}
      ::= { mdlAlrMaskTable 1}

MdlAlrMaskEntry ::=
      SEQUENCE {
     mdlAlrMaskSltIdx           SlotType,
     mdlAlrMask            OCTET STRING    
      }

mdlAlrMaskSltIdx OBJECT-TYPE
      SYNTAX  SlotType
      MAX-ACCESS  read-only
      STATUS  current
      DESCRIPTION
      "This attribute indicates the  desired slot position.
       The Kilomux should use enumerated values starting with kmx."
      ::= { mdlAlrMaskEntry 1}

mdlAlrMask OBJECT-TYPE
      SYNTAX OCTET STRING  (SIZE (8..10))
      MAX-ACCESS read-write
      STATUS current
   DESCRIPTION
   "This object is a mask that indicates which card level 
    alarms are masked. The masked alarms (their bit is set to 
    '1') are neither sent to the manager, nor taken into account
    for alarm status and LEDs.
    Bit no. = Alarm code
    The bits that do not belong to the card level will be 0.
    This object is applicable only when mdlSAlrMaskAll=off 
    (otherwise all card alarms are masked).
    Example: When Alarm having the code 8 is masked,
             the value of this object will be 100 (hex)."
     ::= { mdlAlrMaskEntry 2 } 


--DACS dcl (Common Logic) card specific parameters  

mdlClTable  OBJECT-TYPE
      SYNTAX SEQUENCE OF MdlClEntry
      MAX-ACCESS not-accessible
      STATUS current
	DESCRIPTION  "A table."
	::=  { mdlCl 1 }

mdlClEntry OBJECT-TYPE
      SYNTAX MdlClEntry
      MAX-ACCESS not-accessible
      STATUS current
	DESCRIPTION  "An entry in table."
	INDEX { mdlClIdx }
      ::= { mdlClTable 1}

MdlClEntry ::=
      SEQUENCE {
   mdlClIdx           INTEGER,
   mdlClSwchStatus    Integer32,
   mdlClLastFlipDate  DisplayString,
   mdlClLastFlipTime  DisplayString,
   mdlClLastFlipCause DisplayString
     }

mdlClIdx OBJECT-TYPE
      SYNTAX  INTEGER {
   clA   (3),
   clB   (4)
   }
      MAX-ACCESS  read-only
      STATUS  current
      DESCRIPTION
      "This object indicates the Cl slot referred."
      ::= { mdlClEntry 1}

mdlClSwchStatus OBJECT-TYPE
      SYNTAX  Integer32
      MAX-ACCESS  read-only
      STATUS  current
      DESCRIPTION
      "This object indicates the status of the switches on 
       the referred DCL card.
       Each switch is represented by a bit. The status is a sum
       of 2**n, according to the bits. There are 4 switches:
       bit 0  SP-PAR (LSB)  '1' - Default parameters    
       bit 1  PSWRD         '1' - Password=default
                         '0' - Password=user selected
       bit 2  DB-INIT       '1' - DB initiated with default
                         '0' - DB initiated with NVRAM contents 
       bit 3  PC-SP  (MSB)  '1' - Management by terminal only
                         '0' - Management by NMS
       Example: If SP-PAR  and PSWRD bits are set ('1'), the value
                will be 3 (2**1 + 2**0).
       When the status of the switches is unknown, the value of
       this object will be 255."
      ::= { mdlClEntry 2}

mdlClLastFlipDate  OBJECT-TYPE
      SYNTAX  DisplayString (SIZE (0..255))
      MAX-ACCESS  read-only
      STATUS  current
      DESCRIPTION
      "Date when last flip occured.
       The format would be as specified by the sysSDateFormat."
   ::= {mdlClEntry 3}

mdlClLastFlipTime  OBJECT-TYPE
      SYNTAX  DisplayString (SIZE (0..255))
      MAX-ACCESS  read-only
      STATUS  current
      DESCRIPTION
      "Time when last flip occured."
   ::= {mdlClEntry 4}

mdlClLastFlipCause  OBJECT-TYPE
      SYNTAX  DisplayString (SIZE (0..255))
      MAX-ACCESS  read-only
      STATUS  current
      DESCRIPTION
      "The cause of last flip."
   ::= {mdlClEntry 5}



--DACS Ps (Power Supply) card specific parameters  

mdlPsTable  OBJECT-TYPE
      SYNTAX SEQUENCE OF MdlPsEntry
      MAX-ACCESS not-accessible
      STATUS current
    DESCRIPTION  "A table."
    ::=  { mdlPs 1 }

mdlPsEntry OBJECT-TYPE
      SYNTAX MdlPsEntry
      MAX-ACCESS not-accessible
      STATUS current
    DESCRIPTION  "An entry in table."
    INDEX { mdlPsIdx }
      ::= { mdlPsTable 1}

MdlPsEntry ::= SEQUENCE {
    mdlPsIdx              SlotType,
    mdlPsStatus           INTEGER,
    mdlPsTestResult       INTEGER,
    mdlPsVoltageCurrent   Integer32,
    mdlPsVoltageMin       Integer32,
    mdlPsVoltageMax       Integer32 
 }

mdlPsIdx OBJECT-TYPE
      SYNTAX  SlotType
      MAX-ACCESS  read-only
      STATUS  current
      DESCRIPTION
      "This object indicates the PS card referred."
      ::= { mdlPsEntry 1}

mdlPsStatus OBJECT-TYPE
      SYNTAX  INTEGER {
   notActive  (1),
   active     (2)
   }
      MAX-ACCESS  read-only
      STATUS  current
      DESCRIPTION
      "This object indicates the status of the PS card."
      ::= { mdlPsEntry 2}

mdlPsTestResult OBJECT-TYPE
      SYNTAX  INTEGER {
   ok           (1),
   f12V         (2),
   f5V          (3),
   fMinus5V     (4),
   fFanVoltage  (5),
   fMainVoltage (6)
   }
      MAX-ACCESS  read-only
      STATUS  current
      DESCRIPTION
      "This object indicates the result of the PS test.
       ok          (1) - the test passed successfully.
       f12V        (2) - 12V FAIL was detected.
       f5V         (3) -  5V FAIL was detected.
       fMinus5V    (4) - Minus 5V FAIL was detected.
       fFanVoltage (5) - Fan Voltage FAIL was detected.
       fMainVoltage(6) - Main Voltage FAIL was detected      
       "
      ::= { mdlPsEntry 3}

    mdlPsVoltageCurrent  OBJECT-TYPE
    SYNTAX      Integer32
    MAX-ACCESS  read-only
    STATUS      current
    DESCRIPTION
    "Current PS voltage is in Millivolt."
      ::= { mdlPsEntry 4 }

    mdlPsVoltageMin  OBJECT-TYPE
    SYNTAX      Integer32
    MAX-ACCESS  read-only
    STATUS      current
    DESCRIPTION
    "Minumum PS voltage in Millivolt."
      ::= { mdlPsEntry 5 }

    mdlPsVoltageMax  OBJECT-TYPE
    SYNTAX      Integer32
    MAX-ACCESS  read-only
    STATUS      current
    DESCRIPTION
    "Maximum PS voltage in Millivolt."
      ::= { mdlPsEntry 6 }


--Port level of DACS MIB

prtGen    OBJECT IDENTIFIER ::= {prtDacsMux 1}
prtT1E1   OBJECT IDENTIFIER ::= {prtDacsMux 2}
prtHS     OBJECT IDENTIFIER ::= {prtDacsMux 3}
prtSP     OBJECT IDENTIFIER ::= {prtDacsMux 4}
prtDim    OBJECT IDENTIFIER ::= {prtDacsMux 5}
prtI      OBJECT IDENTIFIER ::= {prtDacsMux 6} --ISDN port
prtHdsl   OBJECT IDENTIFIER ::= {prtDacsMux 7} --HDSL Line
prtT3E3   OBJECT IDENTIFIER ::= {prtDacsMux 8} --T3/E3 interface

--DACS port general parameters (common to all ports type except SP)
--The table contains both status and configuration information 

prtGenParamTable  OBJECT-TYPE
      SYNTAX SEQUENCE OF PrtGenEntry
      MAX-ACCESS not-accessible
      STATUS current
    DESCRIPTION  "A table."
    ::=  { prtGen 1 }

prtGenEntry OBJECT-TYPE
      SYNTAX PrtGenEntry
      MAX-ACCESS not-accessible
      STATUS current
    DESCRIPTION  "An entry in table."
    INDEX { prtGenPrtIdx }
      ::= { prtGenParamTable 1}

PrtGenEntry ::= SEQUENCE {
    prtGenPrtIdx        Integer32,
  prtGenSlt           INTEGER,
  prtGenExtInt        INTEGER,
  prtGenIfIndex       Integer32,
  prtGenActiveStatus  INTEGER,
  prtGenAlrStatus     INTEGER,
  prtGenTestStatus    INTEGER,
  prtGenTestMask      Integer32,
  prtGenTestCmd       Integer32,
  prtGenTestRunning   Integer32,
  prtGenType          INTEGER,
  prtGenInterfaceType DisplayString,
  prtGenAlrClearCmd   INTEGER,
  prtGenAlrMaskAll    INTEGER,
  prtGenParamStatus   OCTET STRING,
  prtGenRdnStatus     INTEGER,
  prtGenTestMaskXP    OCTET STRING,
  prtGenTestCmdXP     OCTET STRING,
  prtGenTestRunningXP OCTET STRING
 }

 prtGenPrtIdx OBJECT-TYPE
      SYNTAX  Integer32
      MAX-ACCESS  read-only
      STATUS  current
      DESCRIPTION
      "This attribute indicates a unique number to identify a port. 
       The valid port number depends on the IO slot no.,  the 
       installed card type and the port type: outside/external, inside/internal. 

    In the Kilomux, the port index is calculated as follows:
    100*Slot+Ch. The external Ch numbers are 1..10, and the
    internal Ch numbers are 11..20.
       
    In the DXC :
      - first two digits will be: (IO slot number+10)
      - last one/two digits will be the port number within the 
        card in odd or even numbers, as follows:
      * For the outside/external ports, in odd numbers:
        port1 = 1
        port2 = 3
        port3 = 5 
        etc...
        Example: port2 of IO slot 11 will be: 213 .
      * The inside/internal ports, in even numbers:
        port1 = 2
        port2 = 4
        port3 = 6 
        etc...
        Example: port2 of IO slot 11 will be: 214 ."
      ::= { prtGenEntry 1}

prtGenSlt     OBJECT-TYPE
      SYNTAX  INTEGER
       {
       io1   (5),
       io2   (6),
       io3   (7),
       io4   (8),
       io5   (9),
       io6  (10),
       io7  (11),
       io8  (12),
       io9  (13),
       io10 (14),
       io11 (15),
       io12 (16),
       io13 (17),
       io14 (18),
       io15 (19),
    kmxMlA (103),
    kmxMlB (104),
    kmxCl  (105),
    kmxOpt (106),
    kmxIO1 (107),
    kmxIO2 (108),
    kmxIO3 (109),
    kmxIO4 (110),
    kmxIO5 (111),
    kmxIO6 (112),
    kmxIO7 (113),
    kmxIO8 (114),
    kmxIO9 (115),
    kmxIO10(116),
    kmxIO11(117),
    kmxIO12(118),
    standAlone (255)
       }
      MAX-ACCESS  read-only
      STATUS  current
      DESCRIPTION
      "This attribute indicates a unique number to identify the slot where
       the card is inserted in.
       When the unit is stand-alone, this object is not applicable
       and 255 will be used.
       The Kilomux should use the enumerated starting with kmx."
      ::= { prtGenEntry 2}

prtGenExtInt  OBJECT-TYPE
      SYNTAX  INTEGER
       {
  external (2),
  internal (3)
       }
      MAX-ACCESS  read-only
      STATUS  current
      DESCRIPTION
      "This attribute describes the type of the designated port. 
       Exteral  port is a port with  a physical connector. Internal 
       port might be of two types, one is a composite port which 
       collects data of a few external ports into a common 
       bandwidth (usually routed trough DS1 link); the other type is
       internal ports which get only part of external port data 
       (usually a few DS0's).
       In the Kilomux-2100, the internal(3) value is used for 
       composite channels or sub-channels of an ISDN Ch."
      ::= { prtGenEntry 3}

prtGenIfIndex  OBJECT-TYPE
      SYNTAX  Integer32
      MAX-ACCESS  read-only
      STATUS  current
      DESCRIPTION
      "This attribute indicates the  unique  interface number 
       assigned to the port. The specific interface of this 
       attribute is the same as the interface identified by the  
       value of ifindex in MIB-II.If there is no interface for the 
       specific prtIdx, the value will be '7fffffff'h."
      ::= { prtGenEntry 4}

prtGenActiveStatus   OBJECT-TYPE
      SYNTAX  INTEGER
       {
         unknown           (1),
         notUsed           (2),
         offLine           (3),
         onLine            (4),
         offLineRedundancy (5),
         onLineRedundancy  (6)
       }
      MAX-ACCESS  read-only
      STATUS  current
      DESCRIPTION
      "This attribute describes the activity status of the port.
       unknown(1) indicates that the information is not supported.
       notUsed(2) indicates that the port is not connected according
                  to the active config.
       offLine(3) indicates that the port is down (not working) 
                  due to any problem.
       onLine (4) indicates that the port is up (working)
       offLineRedundancy(5) indicates that the port is down because
                            it is a redundant port.
       onLineRedundancy (6) indicates that this is a redundant port 
                            which is up and works as the active link."
      ::= { prtGenEntry 5}

prtGenAlrStatus OBJECT-TYPE
      SYNTAX  INTEGER
       {
  off      (2),
  major    (3),
  minor    (4),
  event    (5),
  warning  (6),
  critical (7)
       }
      MAX-ACCESS  read-only
      STATUS  current
      DESCRIPTION
      "Indicates the alarm state at port (ch) agent level.
       This object will be: 
       - critical(7): when there is at least one active (ON) critical 
                    alarm .
       - major (3): when there is no active critical alarm, but there is
                    at least one active (ON) major alarm .
       - minor (4): when there is no active major or critical alarm, but 
                    there is at least one active minor alarm.
       - warning (6): when there is no active major, critical or minor alarm, but 
                    there is at least one active warning alarm.
       - event (5): when there is no active alarm of another type, but 
                    there is at least one active event alarm.
       - off(2): when there is no active (ON) alarm (since last clear operation)."
      ::= { prtGenEntry 6}

prtGenTestStatus OBJECT-TYPE
     SYNTAX  INTEGER
         {
       off(2),
       on (3)
         }
     MAX-ACCESS  read-only
     STATUS  current
     DESCRIPTION
     "This attribute will be on(3) when there is at least one test 
      in progress (running) on the port; otherwise the value will 
      be off(2)."
     ::= { prtGenEntry 7}

prtGenTestMask OBJECT-TYPE
      SYNTAX  Integer32
      MAX-ACCESS  read-only
      STATUS  current
      DESCRIPTION
      "This is a mask which indicates which tests from the
       'prtGenTestCmd' list are allowed for the selected port.
       If a specific test is allowed, its respective bit will be SET 
       in the mask :

         TEST                  BIT
        -----------            ---
        localLoop               1
        remoteLoop              2
        bert                    3
        plb                     4
        inband                  5

        prbs                    8
        loop2-v54  (RLB)        9
        loop3-v54  (LLB)       10

        Tone injection         13
        Tx-plb                 14
        Tx-llb                 15
        DTE loop (HSSI)        16

        HDSL-Tx-Inband         20
        HDSL-Rx-Inband         21
		Monitor                22  (test port)
		User Line Loopback	   23

        Rem-Loop-on-Rem-Unit   25
		LBBD                   26
		LB1                    27
		LB2                    28
        BERT-on-Rem-Unit       29
		TS Remote Loop         30
		LLB-on-Rem-Unit        31

        e.g : If the return value is 3 -> 0000000000000011  ->
              Bits 1 & 2 are set -> the allowed tests are :
                                           local-loop
                                           remote-loop  "
      ::= { prtGenEntry 8}


prtGenTestCmd OBJECT-TYPE
      SYNTAX  Integer32
      MAX-ACCESS  read-write
      STATUS  current
      DESCRIPTION
      "Setting this object to a value as detailed furter on 
       (except 0) will initiate a test on the specific port, 
       if the operation is allowed (according to TestMask). 
       If the operation is not allowed, the mux will ignore the 
       operation.
       The test/s requested will be set according to the respective
       bit:
         TEST                  BIT
        -----------            ---
        localLoop               1
        remoteLoop              2
        bert                    3
        plb                     4
        inband                  5

        prbs                    8
        loop2-v54  (RLB)        9
        loop3-v54  (LLB)       10

        Tone injection         13
        Tx-plb                 14
        Tx-llb                 15
        DTE loop (HSSI)        16

        HDSL-Tx-Inband         20
        HDSL-Rx-Inband         21
        Monitor                22  (test port)
        User Line Loopback     23

        Rem-Loop-on-Rem-Unit   25
        LBBD                   26
        LB1                    27
        LB2                    28
        BERT-on-Rem-Unit       29
        TS Remote Loop         30
        LLB-on-Rem-Unit        31

        e.g : If the requested value is 3 -> 0000000000000011  ->
              Bits 1 & 2 are set -> the requested tests are :
                                           local-loop
                                           remote-loop  

       Setting this object to stop (value=0 ; all bits are 0), 
       will stop all the user requested tests running on the 
       selected port; it will NOT stop the tests initiated by 
       the system."
      ::= { prtGenEntry 9}

prtGenTestRunning OBJECT-TYPE
      SYNTAX  Integer32
      MAX-ACCESS  read-only
      STATUS  current
      DESCRIPTION
      "This object indicates which tests are running currently on 
       the selected port (initiated by user and/or by the system).
       If a specific test is currently running on the port, its 
       respective bit will be SET: 

         TEST                  BIT
        -----------            ---
        localLoop               1
        remoteLoop              2
        bert                    3
        plb                     4
        llb                     5
        txInband                6
        rxInband                7
        prbs                    8
        loop2-v54  (RLB)        9
        loop3-v54  (LLB)       10
        DDS DSU loop           11
        DDS CSU loop           12
        Tone injection         13
        Tx-plb                 14
        Tx-llb                 15
        DTE loop (HSSI)        16
        Local  DTE  loop (HSSI)17
        Local  Line loop (HSSI)18
        Remote Line loop (HSSI)19
        HDSL-Tx-Inband         20
        HDSL-Rx-Inband         21
		Monitor                22  (test port)
		User Line Loopback	   23
		Network Line Loopback  24
        Rem-Loop-on-Rem-Unit   25
		LBBD                   26
		LB1                    27
		LB2                    28
        BERT-on-Rem-Unit       29
		TS Remote Loop         30
		LLB-on-Rem-Unit        31

        e.g : If the return value is 3 -> 0000000000000011  ->
              Bits 1 & 2 are set -> the running tests are :
                                           local-loop
                                           remote-loop  
        llb (Bit 5) - can be initiated by system only!            "
      ::= { prtGenEntry 10}


prtGenType OBJECT-TYPE
      SYNTAX  INTEGER {
   unknown (1),
   t1      (2),
   e1      (3),
   hs      (4),
   t1Csu   (5),
   t1Dsu   (6),
   e1Ltu   (7),
   e1Dsu   (8),
   hdsl    (9),
   sp      (10),
   t1F     (11),  --T1 Fiber-optic
   e1F     (12),  --E1 Fiber-optic
   dim     (13),
   isdn    (14),
   t3      (15),
   e3      (16),
   t3f     (17),
   e3f     (18),
   idsl    (19),
   stm1    (20),
   vc4     (21),
   vc12    (22),
   msdsl   (23),
   vc11    (24), 
   vc3     (25),
   soh     (26), 
   eth     (27),
   shdsl   (28),
   other   (255)
   }
      MAX-ACCESS  read-only
      STATUS  current
      DESCRIPTION
      "This object describes the type of the selected port.
       idsl - applicable for external ports of HS-U cards (of DXC) when 
              interface is LT-1."
      ::= { prtGenEntry 11}

prtGenInterfaceType OBJECT-TYPE
      SYNTAX  DisplayString (SIZE (0..255))
      MAX-ACCESS  read-only
      STATUS  current
      DESCRIPTION
      "This attribute indicates a unique HW interface type of the
       selected port.
       Examples: 
       - for T1 cards: DSU, CSU
       - for E1 cards: DSU, LTU
       - for HS cards: v35, rs422, x21
       etc..."
      ::= { prtGenEntry 12}

prtGenAlrClearCmd  OBJECT-TYPE
      SYNTAX  INTEGER
       {
  noOp (1),
  off  (2),
  on   (3)
       }
      MAX-ACCESS  read-write
      STATUS  current
      DESCRIPTION
      "Setting this attribute to ON, will enforce a  clear 
       operation on the port level alarms . Upon completion, 
       the value will automatically change to off(2).
       noOp - will be used by agents that do not support this 
              feature or object."
      ::= { prtGenEntry 13 }

prtGenAlrMaskAll  OBJECT-TYPE
      SYNTAX  INTEGER
       {
  noOp (1),
  off  (2),
  on   (3)
       }
      MAX-ACCESS  read-write
      STATUS  current
      DESCRIPTION
      "on(3) - will mask all the alarms of the selected port
       off(2)- will unmask all alarms of the selected port except
               the ones selected by the prtAlrMaskTable.
       noOp - will be used by agents that do not support this 
              feature or object."
      ::= { prtGenEntry 14 }

prtGenParamStatus OBJECT-TYPE
      SYNTAX  OCTET STRING
      MAX-ACCESS  read-only
      STATUS  current
      DESCRIPTION
      "This object indicates Status of parameters specific to the 
       selected port.
       - For a port that has no special status or is supported
         by prtSExHsfStatTable - 1 Octet: 00hex

       - For HS cards (Dxc cards) - 1 octet:
         Bit 7 (MSB)..Bit 2 = 0 (NA)
		 Bit 0 and 1 indicates RTS control signal state:
		 Bit 1:       '1'=active  ; '0'=notActive
         Bit 0 (LSB): '1'=unknown ; '0'=NA

       - For HS-U/1 external port (MP card, used in FCD-M) - 1 Octet:
	     Bit 7  6  5  4  3  2  1  0 LSB
             |________|  |__|  |__|
               spare     modem  sync  
               
         modem: 00 = other         sync:  00 = not sync
                01 = unknown              01 = sync
                10 = ASMi-31/2            10 = reserved
                11 = reserved             11 = reserved 

       - For VC-6, VC-12, VC-12/6 external ports - 1 Octet :
         Bit 7 (MSB)..Bit 2 = 0 (NA)
         Bit 1:       Tx Signaling '1'=On ; '0'=Off
         Bit 0 (LSB): Rx Signaling '1'=On ; '0'=Off

       - For VC-2/R2(FXS) external ports - 1 Octet : 
         Bit  -   7 6 5 4 3 2 1 0
                  |_| |_________|
                  Call  Call State
             Direction     

         Bit 7 (MSB) and Bit 6  : Call Direction
         00 - Incoming
         01 - Outgoing
         Bit 5..Bit 0: Call State
         000000 - Idle
         000001 - Seized
         000010 - Both-Way Conflict
         000011 - Seizure Ack
         000100 - Answered
         000101 - Clear Backward
         000110 - Clear Forward
         000111 - Blocked
         001000 - Fault
         001001 - Fault 3
         001010 - Fault 4
         001011 - Fault 5
         001100 - Fault 6
         001101 - Fault 7 
   
       - For ML-20 external port - 3 Octets :
         - 1 MS Octet will represent the Real Rate used:
           Bit    - 7 6 5 4 3 2 1 0
                    |___| |_______|
                     spare  Rate
             
          Valid values: 0..31, meaning 0..31x64Kbps
          Invalid values: 32..255.
           - 2 LS Octets will represent the Status of 7 Control 
             Signals:
             Signal - ---  CTS  DSR  DCD   RJ   TM   DTR  RTS
             Bit   - 7 6  5 4  3 2  1 0    7 6  5 4  3 2  1 0
             Octet  -          2                     3 (LS)
             '---' will always have the value 00
             Rest of the Signals (2 bits each) can have the following
             values:
             00=NA   ;  01=Unused ; 10=Off  ; 11=On 
         
       - For ML-H/E1, ML-H/1/E1, ML-H/S/E1 internal port - 1 Octet
         Bit    - 7 6 5 4 3 2 1 0
                  |___________|
                        spare   Mode of Operation

         Mode of Operation: '1'=Central  ; '0'=Remote 

       - For KM2100, KVF.5 cards - indicates the status of A and B signaling
	                               for each internal channel.
	     1 Octet:

		 Bit  -   7 6 5 4 3 2 1 0
                  |_____| |_| |_| 
                   spare   B   A

		 Bit 0 (LSB) and Bit 1 : A status
		 Bit 2 and Bit 3       : B status

		 00 - Off
		 01 - On
		 11 - Unknown
		  
	   - For FCD-W, NETWORK and USER ports - 1 Octet
         Status of Control Signals: '1'=On  ; '0'=Off or when not applicable

         Bit    - 7 6 5 4 3 2 1 0

         Bit 7 (MSB) - Signal Loss (applicable only for G.703 interface)
         Bit 6       - CONTROL     (applicable only for X.21 interface)
         Bit 5       - INDICATION  (applicable only for X.21 interface)
         Bit 4       - DSR         (applicable only for V.35 interface)
         Bit 3       - RTS         (applicable only for V.35 interface)
         Bit 2       - CTS         (applicable only for V.35 interface)
         Bit 1       - DTR         (applicable only for V.35 interface)
         Bit 0       - DCD         (applicable only for V.35 interface)

       - For DXC R6 , D8U, D16U External ports - 1 Octet
	     Bit 7  6  5  4  3  2  1  0 LSB
             |________|  |__|  |__|
               spare     modem  sync  
               
         modem: 00 = other         sync:  00 = not sync
                01 = unknown              01 = sync
                10 = ASMi-31/2            10 = reserved
                11 = reserved             11 = reserved
         
       - For DXC DE1-HDSL, DT1-HDSL, D16GSDSL, D8SL External ports - 2 Octets

         MSB octet: far-end modem channel interface
		 LSB octet: Sub Link existence (Y/N), far-end modem type,   
		            synchronization with far-end modem

         MSB octet:  0000 0000 = no interface
					 0000 0001 = db15 (X21)
					 0000 0010 = IR-IP
					 0000 0011 = IR-ETH-Q
					 0000 0100 = V35
					 0000 0101 = ETH-RJ45
					 0000 0110 = G703
					 0000 0111 = db25 (RS530)
					 0000 1000 = ETH-BNC
					 0000 1001 = E1(Balanced)
					 0000 1010 = E1(Unbalanced) 
					 0000 1011 = IR-ETH-QN 
					 Rest of the combinations: reserved

         LSB octet:
		             
	     Bit 7  6  5  4  3  2  1  0 LSB
             |  |___________|  |__|
            SL       modem     sync
    or Box material     
               
         SL:          modem: 00000 = other      sync:  00 = not sync
         0=not exist         00001 = unknown           01 = sync
         1=exists            00010 = ASMi-31/2         10 = reserved
                             00011 = HCD-E1            11 = reserved
         Box material        00100 = HTU-E1             
         (for D8SL card):    00101 = HTU-2
		 0=metal			 00110 = ASMi-52 SA/2W/Slave
		 1=plastic			 00111 = ASMi-52 SA/2W/Master     
							 01000 = ASMi-52/CQ card of LRS-24
							 01001 = ASMi-52/CD card of LRS-24
							 01010 = D16GSDSL card of DXC-3000
							 01011 = LRS-52
							 01100 = FCD  
                             01110 = D8GSDSL card of DXC-3000 
                             01111 = ASMi-52A 
							 Rest  = reserved "
      ::= { prtGenEntry 15}

prtGenRdnStatus  OBJECT-TYPE
      SYNTAX  INTEGER
       {
       none (1),
       off  (2),
       on   (3)
       }
      MAX-ACCESS  read-only
      STATUS  current
      DESCRIPTION
      "This object indicates if this port is part of a redundant pair and in
       this case, if it is On or Off.
	   
       none(1) - No redundancy or Not Applicable
       off (2) - the port is part of a redundant pair and it is Off from 
                 Redundancy point of view (not the port used).
       on  (3) - the port is part of a redundant pair and it is On from 
                 Redundancy point of view (it is the port used)."
      ::= { prtGenEntry 16 }

prtGenTestMaskXP OBJECT-TYPE
      SYNTAX  OCTET STRING
      MAX-ACCESS  read-only
      STATUS  current
      DESCRIPTION
      "This is an Expanded test mask of the prtGenTestMask object.
       The prtGenTestMask object reached its maximum, being an Integer with 31 bits.
       This object indicates which tests from the  'prtGenTestCmdXP' list are 
       allowed for the selected port.
       If a specific test is allowed, its respective bit will be SET 
       in the mask :

         TEST                  BIT
        -----------            ---
        localLoop               1	  =LSB
        remoteLoop              2
        bert                    3
        plb                     4
        inband                  5

        prbs                    8
        loop2-v54  (RLB)        9
        loop3-v54  (LLB)       10

        Tone injection         13
        Tx-plb                 14
        Tx-llb                 15
        DTE loop (HSSI)        16

        HDSL-Tx-Inband         20
        HDSL-Rx-Inband         21
		Monitor                22  (test port)
		User Line Loopback	   23

        Rem-Loop-on-Rem-Unit   25
		LBBD                   26
		LB1                    27
		LB2                    28
        BERT-on-Rem-Unit       29
		TS Remote Loop         30
		LLB-on-Rem-Unit        31
		Downstream-AIS         32
		Upstream-AIS           33
		Send-RDI               34
		Test Per TS            35 

        e.g : If the return value is  00000003 hex  ->
              Bits 1 & 2 are set -> the allowed tests are :
                                           local-loop
                                           remote-loop  "
      ::= { prtGenEntry 17}


prtGenTestCmdXP OBJECT-TYPE
      SYNTAX  OCTET STRING
      MAX-ACCESS  read-write
      STATUS  current
      DESCRIPTION
	  "This is an Expanded test command of the prtGenTestCmd object.
       The prtGenTestCmd object reached its maximum, being an Integer with 31 bits.
       Setting this object to a value as detailed furter on 
       (except 0) will initiate a test on the specific port, 
       if the operation is allowed (according to TestMaskXP). 
       If the operation is not allowed, the mux will ignore the 
       operation.
       The test/s requested will be set according to the respective
       bit:
         TEST                  BIT
        -----------            ---
        localLoop               1	=LSB
        remoteLoop              2
        bert                    3
        plb                     4
        inband                  5

        prbs                    8
        loop2-v54  (RLB)        9
        loop3-v54  (LLB)       10

        Tone injection         13
        Tx-plb                 14
        Tx-llb                 15
        DTE loop (HSSI)        16

        HDSL-Tx-Inband         20
        HDSL-Rx-Inband         21
		Monitor                22  (test port)
		User Line Loopback	   23

        Rem-Loop-on-Rem-Unit   25
		LBBD                   26
		LB1                    27
		LB2                    28
        BERT-on-Rem-Unit       29
		TS Remote Loop         30
		LLB-on-Rem-Unit        31
		Downstream-AIS         32
		Upstream-AIS           33
		Send-RDI               34 
		Test Per TS            35

        e.g : If the requested value is 00000003 hex  ->
              Bits 1 & 2 are set -> the requested tests are :
                                           local-loop
                                           remote-loop  

       Setting this object to stop (value=0 ; all bits are 0), 
       will stop all the user requested tests running on the 
       selected port; it will NOT stop the tests initiated by 
       the system."
      ::= { prtGenEntry 18}

prtGenTestRunningXP OBJECT-TYPE
      SYNTAX  OCTET STRING
      MAX-ACCESS  read-only
      STATUS  current
      DESCRIPTION
	  "This is an Expanded object of the prtGenTestRunning object.
       The prtGenTestRunning object reached its maximum, being an Integer with 31 bits.
       This object indicates which tests are running currently on 
       the selected port (initiated by user and/or by the system).
       If a specific test is currently running on the port, its 
       respective bit will be SET: 

         TEST                  BIT
        -----------            ---
        localLoop               1	 =LSB
        remoteLoop              2
        bert                    3
        plb                     4
        llb                     5
        txInband                6
        rxInband                7
        prbs                    8
        loop2-v54  (RLB)        9
        loop3-v54  (LLB)       10
        DDS DSU loop           11
        DDS CSU loop           12
        Tone injection         13
        Tx-plb                 14
        Tx-llb                 15
        DTE loop (HSSI)        16
        Local  DTE  loop (HSSI)17
        Local  Line loop (HSSI)18
        Remote Line loop (HSSI)19
        HDSL-Tx-Inband         20
        HDSL-Rx-Inband         21
		Monitor                22  (test port)
		User Line Loopback	   23
		Network Line Loopback  24
        Rem-Loop-on-Rem-Unit   25
		LBBD                   26
		LB1                    27
		LB2                    28
        BERT-on-Rem-Unit       29
		TS Remote Loop         30
		LLB-on-Rem-Unit        31
		Downstream-AIS         32
		Upstream-AIS           33
		Send-RDI               34 
		Test Per TS            35

        e.g : If the return value is 00000003 hex  ->
              Bits 1 & 2 are set -> the running tests are :
                                           local-loop
                                           remote-loop  
        llb (Bit 5) - can be initiated by system only!            "
      ::= { prtGenEntry 19}


--prtGenTestDuration - Setting Duration of tests

prtGenTestDurationTable  OBJECT-TYPE
      SYNTAX SEQUENCE OF PrtGenTestDurationEntry
      MAX-ACCESS not-accessible
      STATUS current
	DESCRIPTION  "A table."
	::=  { prtGen 2 }

prtGenTestDurationEntry OBJECT-TYPE
      SYNTAX PrtGenTestDurationEntry
      MAX-ACCESS not-accessible
      STATUS current
	DESCRIPTION  "An entry in table."
	INDEX { prtGenTestPrtIdx, prtGenTestIdx }
      ::= { prtGenTestDurationTable 1}

PrtGenTestDurationEntry ::=
     SEQUENCE {
  prtGenTestPrtIdx     Integer32,
  prtGenTestIdx        INTEGER,
  prtGenTestDuration   Integer32 
	}

prtGenTestPrtIdx OBJECT-TYPE
      SYNTAX  Integer32
      MAX-ACCESS  read-only
      STATUS  current
      DESCRIPTION
      "This attribute indicates a unique number to identify a port. 
       The valid port number depends on the IO slot no.,  the 
       installed card type and the port type: outside/external, inside/internal. 

    In the Kilomux, the port index is calculated as follows:
    100*Slot+Ch. The external Ch numbers are 1..10, and the
    internal Ch numbers are 11..20.
       
    In the DXC :
      - first two digits will be: (IO slot number+10)
      - last one/two digits will be the port number within the 
        card in odd or even numbers, as follows:
      * For the outside/external ports, in odd numbers:
        port1 = 1
        port2 = 3
        port3 = 5 
        etc...
        Example: port2 of IO slot 11 will be: 213 .
      * The inside/internal ports, in even numbers:
        port1 = 2
        port2 = 4
        port3 = 6 
        etc...
        Example: port2 of IO slot 11 will be: 214 ."
      ::= { prtGenTestDurationEntry 1}

prtGenTestIdx OBJECT-TYPE
   SYNTAX  INTEGER  
   {
   localLoop  (1),
   remoteLoop (2),
   bert       (3),
   plb        (4),
   rlb        (5),
   llb        (6),
   toneInjection (7),
   txInband (8),
   rxInband (9),
   remLoopOnRemUnit (10), 
   bertOnRemUnit (11),
   llbOnRemUnit (12),

   txPlb        (14),
   txLlb        (15),
   dteLoop      (16), --HSSI

   hdslTxInband (20),
   hdslRxInband (21),
   monitor      (22),
   userLineLoopback(23),

   lbbd         (26),
   lb1          (27),
   lb2          (28),

   tsRemoteLoop (30),

   downstreamAis(32),
   upstreamAis  (33),
   sendRdi      (34)
   }
   MAX-ACCESS  read-only
   STATUS  current
   DESCRIPTION
   "This attribute indicates the test, the duration refers. "
   ::= { prtGenTestDurationEntry 2}

prtGenTestDuration OBJECT-TYPE
      SYNTAX  Integer32
      MAX-ACCESS  read-write
      STATUS  current
      DESCRIPTION
      "This attribute indicates the maximum duration of executing
       a test on the specific port. This entry applies to the
       specified test . The resolution will be a minute, and the
       maximum duration is limited to 30 minutes .
       A zero  value specifies no time limitation.
       When the test isn't active the agent initiates this object to
       2 min. when the duration is needed and to 0 if it's not 
       required."
      ::= { prtGenTestDurationEntry 3}
       

--prtGen TS (TimeSlot) Assignment Table - for all ports of IO cards

prtGenTsTable  OBJECT-TYPE
     SYNTAX SEQUENCE OF PrtGenTsEntry
     MAX-ACCESS not-accessible
     STATUS  current
     DESCRIPTION
      "The write operation into the Table's Objects is valid only
       for the TmpCnfg entry (Scratch),exept some products 
       which enable direct writing to the ActiveCnfg. 
       This is written in the respective product's spec. "
  ::= { prtGen 3}

prtGenTsEntry OBJECT-TYPE
      SYNTAX PrtGenTsEntry
      MAX-ACCESS not-accessible
      STATUS current
	DESCRIPTION  "An entry in table."
	INDEX {prtGenTsCnfgIdx, prtGenTsPrtIdx, prtGenTsIdx }
      ::= { prtGenTsTable 1}

PrtGenTsEntry ::=
      SEQUENCE {
      prtGenTsCnfgIdx        Integer32,
      prtGenTsPrtIdx         Integer32,
      prtGenTsIdx            Integer32,
      prtGenTsType           INTEGER,
      prtGenTsIConPrt        Integer32,
      prtGenTsIConTs         Integer32 
	}

prtGenTsCnfgIdx OBJECT-TYPE
      SYNTAX  Integer32  (1..255)
      MAX-ACCESS  read-only
      STATUS  current
      DESCRIPTION
      "This attribute indicates the Idx of the Cnfg(1..255) being 
       accessed.
       Idx of 255 relates to the TmpCnfg. "
      ::= { prtGenTsEntry 1}


prtGenTsPrtIdx OBJECT-TYPE
      SYNTAX  Integer32
     MAX-ACCESS  read-only
      STATUS  current
      DESCRIPTION
      "This attribute indicates a unique  port number.
       The valid port number depends on the IO slot no.,  the 
       installed card type and the port type: outside, inside, 
       SP.
      In the DXC :
      - first two digits will be: (IO slot number+10)
      - last one/two digits will be the port number within the 
        card in odd or even numbers, as follows:
      * For the outside/external ports, in odd numbers:
        port1 = 1
        port2 = 3
        port3 = 5 
        etc...
        Example: port2 of IO slot 11 will be: 213 .
      * The inside/internal ports, in even numbers:
        port1 = 2
        port2 = 4
        port3 = 6 
        etc...
        Example: port2 of IO slot 11 will be: 214 ."
      ::= { prtGenTsEntry 2}

prtGenTsIdx OBJECT-TYPE
      SYNTAX  Integer32
      MAX-ACCESS  read-only
      STATUS  current
      DESCRIPTION
      "This attribute indicates a unique time slot  position.
       The valid time slots are 
       1..25 for T1 Card (25=Fbit)
       0..31 for E1 or HS Card . 
       In G732S-E1 lines time slot 16 is not valid for data, 
       it is dedicated for multiframe synchronization bits
       and voice signaling."
      ::= { prtGenTsEntry 3}

prtGenTsType  OBJECT-TYPE
      SYNTAX  INTEGER
   {
   unknown       (1),
   voice         (2),
   data          (3),
   vcMP          (4),
   nc            (5),
   mng           (6)
   }
      MAX-ACCESS  read-write
      STATUS  current
      DESCRIPTION
   "The type of Timeslot. 
    If the source or destination port is an HS port,'TS Type'    
    must be 'data'.
    nc - means that this TimeSlot is not connected.
    voice, data, vcMP - also mean that this TS is connected.
    mng - means that this TS is dedicated to Management (not 
          connected to another port."
          
   ::= { prtGenTsEntry 4}

prtGenTsIConPrt OBJECT-TYPE
      SYNTAX  Integer32
      MAX-ACCESS  read-write
      STATUS  current
      DESCRIPTION
      "This attribute indicates the internally (In Mux) 
       connected port.
       The valid port number depends on the IO slot no.,  the 
       installed card type and the port type: outside, inside, 
       SP.
       * The outside ports will be the T1/E1 cards ports. 
         The convention used will be (for DXC):
         - first two digits will be: (IO slot number+10)
           for a stand-alone unit, the IO slot will be considered 1.
         - last one/two digits will be the port number within the 
           card, in odd numbers:
        port1 = 1
        port2 = 3
        port3 = 5 
        etc...
        Example: port2 of IO slot 11 will be: 213 .
       * The inside ports will be for example, the HS cards ports. 
         The convention used will be (for DXC):
         - first two digits will be: (IO slot number+10)
           for a stand-alone unit, the IO slot will be considered 1.
         - last one/two digits will be the port number within the 
           card, in even numbers:
           port1 = 2
           port2 = 4
           port3 = 6 
           etc...
           Example: port2 of IO slot 11 will be: 214 .
       * noConnection - will be indicated as 10 for DXC and FCD-E1/T1.
                      - will be indicated as 100 for FCD-E1/I and SMODs.   
       * Split TS (same TS is Split to several ports) - 11. 
	   * notApplicable- will be indicated as 100 for LRS IMODs.
       
       All HS port's timeslots must have the same destination
       port."
      ::= {prtGenTsEntry 5}

prtGenTsIConTs OBJECT-TYPE
      SYNTAX  Integer32
      MAX-ACCESS  read-write
      STATUS  current
      DESCRIPTION
      "This attribute indicates a unique time slot  position.
       The valid time slots are 
       1..25 for T1 Card (25=Fbit)
       0..31 for E1 (or HS) Card. 
       In G732S-E1 lines time slot 16 is not valid for data, it is 
       dedicated for multiframe synchronization bits and voice 
       signaling.
       * For DXC: All HS port's timeslots must start with Timeslot 
         no.1 "
      ::= {prtGenTsEntry 6}

--Port current alarms table

prtAlr  OBJECT IDENTIFIER ::= {prtGen 4}

prtSAlarmTable OBJECT-TYPE
      SYNTAX SEQUENCE OF PrtSAlarmEntry
      MAX-ACCESS not-accessible
      STATUS current
    DESCRIPTION  "A table."
    ::=  { prtAlr 1 }

prtSAlarmEntry OBJECT-TYPE
      SYNTAX PrtSAlarmEntry
      MAX-ACCESS not-accessible
      STATUS current
    DESCRIPTION  "An entry in table."
    INDEX { prtSAlarmPrtIdx, prtSAlarmIdx}
      ::= { prtSAlarmTable 1}

PrtSAlarmEntry ::= SEQUENCE {
    prtSAlarmPrtIdx            Integer32,
    prtSAlarmIdx               Integer32,
    prtSAlarmCode              Integer32,
    prtSAlarmState             INTEGER,
    prtSAlarmMask              INTEGER,
  prtSAlarmInvert            INTEGER,
  prtSAlarmOnOff             INTEGER,
  prtSAlarmCounter           Integer32 
 }

prtSAlarmIdx OBJECT-TYPE
      SYNTAX  Integer32
      MAX-ACCESS  read-only
      STATUS  current
      DESCRIPTION
      "A unique number to identify an entry in the alarm status 
       table.
       Users should use the get next function to read this table 
       because the indexes are not consecutive."
      ::= { prtSAlarmEntry 1}

prtSAlarmPrtIdx OBJECT-TYPE
      SYNTAX  Integer32
      MAX-ACCESS  read-only
      STATUS  current
      DESCRIPTION
      "This attribute indicates a unique number to identify a port. 
       The valid port number depends on the IO slot no.,  the 
       installed card type and the port type: outside/external, inside/internal. 

    In the Kilomux, the port index is calculated as follows:
    100*Slot+Ch. The external Ch numbers are 1..10, and the
    internal Ch numbers are 11..20.
       
    In the DXC :
      - first two digits will be: (IO slot number+10)
      - last one/two digits will be the port number within the 
        card in odd or even numbers, as follows:
      * For the outside/external ports, in odd numbers:
        port1 = 1
        port2 = 3
        port3 = 5 
        etc...
        Example: port2 of IO slot 11 will be: 213 .
      * The inside/internal ports, in even numbers:
        port1 = 2
        port2 = 4
        port3 = 6 
        etc...
        Example: port2 of IO slot 11 will be: 214 ."
    ::= { prtSAlarmEntry 2}

prtSAlarmCode OBJECT-TYPE
      SYNTAX  Integer32
      MAX-ACCESS  read-only
      STATUS  current
      DESCRIPTION
      "This object indicates a code related to a specific
       alarm description. The list of codes and their related
       descriptions will be sent to NMS request (for display purpose)
       by alrGenTable."
      ::= { prtSAlarmEntry 3 }

prtSAlarmState OBJECT-TYPE
      SYNTAX  INTEGER {
   event    (3),
   minor    (4),
   major    (5),
   warning  (6),
   critical (7)
       }
      MAX-ACCESS  read-only
      STATUS  current
      DESCRIPTION
      "This object indicates the port alarm severity."      
      ::= { prtSAlarmEntry 4 }

prtSAlarmMask OBJECT-TYPE
      SYNTAX  INTEGER {
  off(2),
  on (3)
       }
      MAX-ACCESS  read-only
      STATUS  current
      DESCRIPTION
      "Alarm Mask is : on/off."
      ::= { prtSAlarmEntry 5 }

prtSAlarmInvert OBJECT-TYPE
      SYNTAX  INTEGER {
  off(2),
  on (3)
       }
      MAX-ACCESS  read-only
      STATUS  current
      DESCRIPTION
      "Alarm Invert is : on/off."
      ::= { prtSAlarmEntry 6 }

prtSAlarmOnOff OBJECT-TYPE
      SYNTAX  INTEGER {
  off(2),
  on (3)
       }
      MAX-ACCESS  read-only
      STATUS  current
      DESCRIPTION
      "Alarm state is : on/off."
      ::= { prtSAlarmEntry 7 }

prtSAlarmCounter OBJECT-TYPE
      SYNTAX  Integer32
      MAX-ACCESS  read-only
      STATUS  current
      DESCRIPTION
      "A counter - how many times the alarm occured (ON) since last
       clear operation or since last Reset."
      ::= { prtSAlarmEntry 8 }

prtAlrMaskTable OBJECT-TYPE
      SYNTAX SEQUENCE OF PrtAlrMaskEntry
      MAX-ACCESS not-accessible
      STATUS current
	DESCRIPTION  "A table."
	::=  { prtAlr 2 }

prtAlrMaskEntry OBJECT-TYPE
      SYNTAX PrtAlrMaskEntry
      MAX-ACCESS not-accessible
      STATUS current
	DESCRIPTION  "An entry in table."
	INDEX { prtAlrMaskPrtIdx}
      ::= { prtAlrMaskTable 1}

PrtAlrMaskEntry ::=
      SEQUENCE {
  prtAlrMaskPrtIdx         Integer32,
  prtAlrMask               OCTET STRING
      }        


prtAlrMaskPrtIdx OBJECT-TYPE
      SYNTAX  Integer32
      MAX-ACCESS  read-only
      STATUS  current
      DESCRIPTION
      "This attribute indicates a unique number to identify a port. 
       The valid port number depends on the IO slot no.,  the 
       installed card type and the port type: outside/external, inside/internal. 

    In the Kilomux, the port index is calculated as follows:
    100*Slot+Ch. The external Ch numbers are 1..10, and the
    internal Ch numbers are 11..20.
       
    In the DXC :
      - first two digits will be: (IO slot number+10)
      - last one/two digits will be the port number within the 
        card in odd or even numbers, as follows:
      * For the outside/external ports, in odd numbers:
        port1 = 1
        port2 = 3
        port3 = 5 
        etc...
        Example: port2 of IO slot 11 will be: 213 .
      * The inside/internal ports, in even numbers:
        port1 = 2
        port2 = 4
        port3 = 6 
        etc...
        Example: port2 of IO slot 11 will be: 214 ."
    ::= { prtAlrMaskEntry 1}

prtAlrMask OBJECT-TYPE
      SYNTAX OCTET STRING  (SIZE (8))
      MAX-ACCESS read-write
      STATUS current
   DESCRIPTION
   "This object is a mask that indicates which port level 
    alarms are masked. The masked alarms (their bit is set to 
    '1') are neither sent to the manager, nor taken into account
    for alarm status and LEDs.
    Bit no. = Alarm code
    The bits that do not belong to the port level will be 0.
    This object is applicable only when prtGenAlrMaskAll=off 
    (otherwise all port alarms are masked).
    Example: When Alarms having the codes 31 and 40 are masked,
             the value of this object will be 10080000000 (hex)."
      ::= { prtAlrMaskEntry 2 }
      
      
--Port BERT table


prtBertTable OBJECT-TYPE
      SYNTAX SEQUENCE OF PrtBertEntry
      MAX-ACCESS not-accessible
      STATUS current
   DESCRIPTION   
      "This table includes the BERT parameters, counters and 
       commands.
    The configurable parameters:
    - prtBertPattern
    - prtBertInjectRate
    - prtBertTs
    - prtBertDirection
    are not Set per configuration (same for all Configurations)
    but start being applied by the Agent only upon successful
    Update/Download operation. Therefore, Set will enter the 
    values to the Temporary Configuration of the agent, while
    Get will get the values of the Active Configuration."
    ::= { prtGen 5 }

prtBertEntry OBJECT-TYPE
      SYNTAX PrtBertEntry
      MAX-ACCESS not-accessible
      STATUS current
    DESCRIPTION  "An entry in table."
    INDEX { prtBertPrtIdx}
      ::= { prtBertTable 1}

PrtBertEntry ::= SEQUENCE {
    prtBertPrtIdx             Integer32,
    prtBertPattern            INTEGER,
    prtBertInjectRate         INTEGER,
  prtBertInjectErrRateCmd   INTEGER,
  prtBertInjectSingleErrCmd INTEGER,
    prtBertRunTime            Integer32,
    prtBertESs                Integer32,
    prtBertSyncLoss           Integer32,
    prtBertErrorBits          Integer32,
    prtBertClearCounters      INTEGER,
    prtBertSyncStatus         INTEGER,
    prtBertTs                 OCTET STRING,
  prtBertResult 		    DisplayString,
  prtBertTxBits		        Integer32,
  prtBertRxBits			    Integer32,
  prtBertTxErrorBits		Integer32
 }

prtBertPrtIdx OBJECT-TYPE
      SYNTAX  Integer32
      MAX-ACCESS  read-only
      STATUS  current
      DESCRIPTION
      "This attribute indicates a unique number to identify a port. 
       The valid port number depends on the IO slot no.,  the 
       installed card type and the port type: outside/external, inside/internal. 

    In the Kilomux, the port index is calculated as follows:
    100*Slot+Ch. The external Ch numbers are 1..10, and the
    internal Ch numbers are 11..20.
       
    In the DXC :
      - first two digits will be: (IO slot number+10)
      - last one/two digits will be the port number within the 
        card in odd or even numbers, as follows:
      * For the outside/external ports, in odd numbers:
        port1 = 1
        port2 = 3
        port3 = 5 
        etc...
        Example: port2 of IO slot 11 will be: 213 .
      * The inside/internal ports, in even numbers:
        port1 = 2
        port2 = 4
        port3 = 6 
        etc...
        Example: port2 of IO slot 11 will be: 214 .

    In the MP :   
      - first two digits will be: (IO slot number+10)
      - last one/two digits will be according to the external port 
        number within the card:
        exPrt1 -> 1
        exPrt2 -> 3
        exPrt3 -> 5
        exPrt4 -> 7 . "
    ::= { prtBertEntry 1}

prtBertPattern OBJECT-TYPE
      SYNTAX  INTEGER
    {
     p2E3m1   (1),
     p2E4m1   (2),
     p2E5m1   (3),
     p2E6m1   (4),
     p2E7m1   (5),
     p511     (6),
     p2E10m1  (7),
     p2047    (8),
     p2E15m1  (9),
     p2E17m1 (10),
     p2E18m1 (11),
     p2E20m1 (12),
     qrss    (13),
     p2E21m1 (14),
     p2E22m1 (15),
     p2E23m1 (16),
     p2E25m1 (17),
     p2E28m1 (18),
     p2E29m1 (19),
     p2E31m1 (20),
     p2E32m1 (21),
     rj011   (22),  
     p63     (23),  
     p1M7S   (24),  
     p1S7M   (25),  
     alternate(26), 
     mark    (27),  
     space   (28),
     p2E11m1 (29),
     notApplicable (255)
    }    
      MAX-ACCESS  read-write
      STATUS  current
      DESCRIPTION
      "This object indicates the pattern of the BERT.
       p2Exxm1 = 2Exx-1.
       pxx     = pattern xx.
       This object is the same for all configurations.
       notApplicable - when this object is not supported."
      ::= { prtBertEntry 2}

prtBertInjectRate OBJECT-TYPE
      SYNTAX  INTEGER
    {
     noError  (1),
     r10Em1   (2),
     r10Em2   (3),
     r10Em3   (4),
     r10Em4   (5),
     r10Em5   (6),
     r10Em6   (7),
     r10Em7   (8),
     single   (9),
     notApplicable (255)
    }    
      MAX-ACCESS  read-write
      STATUS  current
      DESCRIPTION
      "This object indicates the error rate injection of the BERT.
       r10Emx = 10E-x
       This object is the same for all configurations.
       single - single error injection.
       notApplicable - when this object is not supported."
      ::= { prtBertEntry 3}

prtBertInjectErrRateCmd OBJECT-TYPE
      SYNTAX  INTEGER
    {
     off  (2),
     on   (3)
    }    
      MAX-ACCESS  read-write
      STATUS  current
      DESCRIPTION
      "This object controls activation/deactivation of the Error 
       Rate Injection during BERT."   
      ::= { prtBertEntry 4}

prtBertInjectSingleErrCmd OBJECT-TYPE
      SYNTAX  INTEGER
    {
     off  (2),
     on   (3)
    }    
      MAX-ACCESS  read-write
      STATUS  current
      DESCRIPTION
      "This object enables to initiate a Single Error Injection 
       during BERT (on). Upon completion, the value will 
       automatically change to off(2)."   
      ::= { prtBertEntry 5}

prtBertRunTime OBJECT-TYPE
      SYNTAX  Integer32
      MAX-ACCESS  read-only
      STATUS  current
      DESCRIPTION
      "This object indicates how much time (seconds) passed since
       BERT started to run."   
      ::= { prtBertEntry 6}

prtBertESs OBJECT-TYPE
      SYNTAX  Integer32
      MAX-ACCESS  read-only
      STATUS  current
      DESCRIPTION
      "How many Errored Seconds were detected since BERT started
       to run.
       Counter for Kmux and MP."  
      ::= { prtBertEntry 7}
       
prtBertSyncLoss OBJECT-TYPE
      SYNTAX  Integer32
      MAX-ACCESS  read-only
      STATUS  current
      DESCRIPTION
      "How many times Sync Loss was detected since BERT started
       to run.
       For some products: number of seconds in which Sync Loss occured 
       since BERT started to run. See product specification."   
      ::= { prtBertEntry 8}
         
prtBertErrorBits OBJECT-TYPE
      SYNTAX  Integer32
      MAX-ACCESS  read-only
      STATUS  current
      DESCRIPTION
      "How many Error Bits were detected since BERT started
       to run."   
      ::= { prtBertEntry 9}

prtBertClearCounters  OBJECT-TYPE
      SYNTAX  INTEGER
       {
       off(2),
       on (3)
       }
      MAX-ACCESS  read-write
      STATUS  current
      DESCRIPTION
      "Setting this object to ON, will enforce a  clear 
       operation of some BERT Counters. Upon completion, 
       the value will automatically change to off(2)."
      ::= { prtBertEntry 10}

prtBertSyncStatus  OBJECT-TYPE
      SYNTAX  INTEGER
       {
  notApplicable(1),
  syncLoss     (2),
  sync         (3)
       }
      MAX-ACCESS  read-only
      STATUS  current
      DESCRIPTION
      "Sync Status while BERT runs."
      ::= { prtBertEntry 11}

prtBertTs  OBJECT-TYPE
      SYNTAX  OCTET STRING (SIZE(0..4))
      MAX-ACCESS  read-write
      STATUS  current
      DESCRIPTION
     "This object indicates on which TSs of the selected port, BERT 
      should be applied. 
      Each Bit of the Octet represents a TS:
      31 ......0
      MSB     LSB

      Bit 0 will not be used.
      If the bit value is '1' - BERT should be applied on this TS.
      For a  T1 port, the valid raised bits ('1') are: 1..25.
      For an E1 port, the valid raised bits ('1') are: 1..31.
      
      Agents that do not support this feature will send SIZE 0."
      ::= { prtBertEntry 12}

prtBertResult     OBJECT-TYPE
      SYNTAX      DisplayString (SIZE (0..255)) 
      MAX-ACCESS  read-only
      STATUS      current
      DESCRIPTION
     "This object indicates Result of BERT 
      for the selected port
      (number of error bits divided to the total
      number of data bits.)
      Applicable only if BERT is running on this port

      Agents that do not support this feature will send SIZE 0."
      ::= { prtBertEntry 13}


prtBertTxBits  OBJECT-TYPE
      SYNTAX      Integer32
      MAX-ACCESS  read-only
      STATUS       current
      DESCRIPTION
      "How many data bits were transmitted since BERT started
       to run, or since last counter clear 
       (prtBertClearCounters set to on)."
      ::= { prtBertEntry 14}

prtBertRxBits  OBJECT-TYPE
      SYNTAX      Integer32
      MAX-ACCESS  read-only
      STATUS       current
      DESCRIPTION
      "How many data bits were Received since BERT started
       to run, or since last counter clear 
       (prtBertClearCounters set to on)."
      ::= { prtBertEntry 15}


prtBertTxErrorBits  OBJECT-TYPE
      SYNTAX      Integer32
      MAX-ACCESS  read-only
      STATUS       current
      DESCRIPTION
      "Number of injected error bits since BERT started
       to run, or since last counter clear 
       (prtBertClearCounters set to on)."
      ::= { prtBertEntry 16}



--Port Monitoring Table - for Monitoring ports
--The table is applicable only for DXC T1/E1/HS ports and Optimux-T3

prtMonTable  OBJECT-TYPE
     SYNTAX SEQUENCE OF PrtMonEntry
     MAX-ACCESS not-accessible
     STATUS  current
     DESCRIPTION
      "For DXC, the write operation into the Table's Objects is valid only
       for the TmpCnfg entry (Scratch)."
  ::= { prtGen 6}

prtMonEntry OBJECT-TYPE
      SYNTAX PrtMonEntry
      MAX-ACCESS not-accessible
      STATUS current
	DESCRIPTION  "An entry in table."
	INDEX {prtMonCnfgIdx, prtMonitoringIdx }
      ::= { prtMonTable 1}

PrtMonEntry ::=
      SEQUENCE {
      prtMonCnfgIdx        Integer32,
      prtMonitoringIdx     Integer32,
	  prtMonitoringEnable  INTEGER,
      prtMonitoringTSs     OCTET STRING,
      prtMonitoredPort     Integer32,
      prtMonitoredTSs      OCTET STRING
      }

prtMonCnfgIdx OBJECT-TYPE
      SYNTAX  Integer32  (1..255)
      MAX-ACCESS  read-only
      STATUS  current
      DESCRIPTION
      "This object indicates the Idx of the Cnfg(1..255) being 
       accessed.
       Idx of 255 relates to the TmpCnfg.
       For products that do not support configurations, 1 will be always used."
      ::= { prtMonEntry 1}

prtMonitoringIdx OBJECT-TYPE
      SYNTAX  Integer32
      MAX-ACCESS  read-only
      STATUS  current
      DESCRIPTION
      "This object indicates the Monitoring Port Index.
	   For DXC:
         The valid port number depends on the IO slot no.,  the 
         installed card type and the port type: external, internal.
         * The external ports will according to the convention (for DXC):
         - first two digits will be: (IO slot number+10)
         - last one/two digits will be the port number within the 
           card, in odd numbers:
           port1 = 1
           port2 = 3
           port3 = 5 
           etc...
           Example: port2 of IO slot 11 will be: 213 .
         * The internal ports will be according to the convention (for DXC):
           - first two digits will be: (IO slot number+10)
           - last one/two digits will be the port number within the 
             card, in even numbers:
             port1 = 2
             port2 = 4
             port3 = 6 
             etc...
           Example: port2 of IO slot 11 will be: 214 .
        For Optimux-T3: 
          255 (Not Applicable) will be always used. The Monitoring port is always 
		  the Station Clock (not considered an interface)."
      ::= { prtMonEntry 2}

prtMonitoringEnable  OBJECT-TYPE
      SYNTAX  INTEGER
       {
      notApplicable(1),
      disabled     (2),
      enabled      (3)
       }
      MAX-ACCESS  read-write
      STATUS  current
      DESCRIPTION
      "This object indicates if the prtMonitoringIdx is configured as 
       a monitoring port or not.
       disabled = the port is NOT configured to monitor. Setting this object
	              to this value will cause reset (to 0) of the prtMonitoringTSs
				  and prtMonitoredTSs objects.
       enabled  = the port IS configured to monitor.
       For Optimux-T3: always enabled (RO supported)."
      ::= {prtMonEntry 3}

prtMonitoringTSs OBJECT-TYPE
      SYNTAX  OCTET STRING (SIZE(0..4))
      MAX-ACCESS  read-write
      STATUS  current
      DESCRIPTION
     "This object indicates which TSs of the Monitoring port, 
      the test equipment should monitor. 
      Each Bit of the Octet represents a TS:
      31 ......0
      MSB     LSB

      Bit 0 will not be used.
      If the bit value is '1' - this TS should be monitored.
      For a  T1 port, the valid raised bits ('1') are: 1..24.
      For an E1 port, the valid raised bits ('1') are: 1..31.
      Default: all bits='0'
      Agents that do not support this feature will send SIZE 0.
      This object can be Set as described only if prtMonitoringEnable=enabled. "
      ::= {prtMonEntry 4}

prtMonitoredPort  OBJECT-TYPE
      SYNTAX  Integer32
      MAX-ACCESS  read-write
      STATUS  current
      DESCRIPTION
      "This object indicates the MONITORED Port Index that the Monitoring
       port monitors.
	   For DXC:
         The valid port number depends on the IO slot no.,  the 
         installed card type and the port type: external, internal.
         * The external ports will according to the convention (for DXC):
           - first two digits will be: (IO slot number+10)
           - last one/two digits will be the port number within the 
             card, in odd numbers:
             port1 = 1
             port2 = 3
             port3 = 5 
             etc...
           Example: port2 of IO slot 11 will be: 213 .
         * The internal ports will be according to the convention (for DXC):
           - first two digits will be: (IO slot number+10)
           - last one/two digits will be the port number within the 
             card, in even numbers:
             port1 = 2
             port2 = 4
             port3 = 6 
             etc...
           Example: port2 of IO slot 11 will be: 214 .
         * 100 - no port monitored
       For Optimux-T3:
	     The valid channels are:
         0 =  no Ch monitored
         1..21 or 1..28 (=CH1..CH21 or CH1..CH28) according to product's 
         configuration."
   ::= { prtMonEntry 5}

prtMonitoredTSs OBJECT-TYPE
      SYNTAX  OCTET STRING (SIZE(0..4))
      MAX-ACCESS  read-write
      STATUS  current
      DESCRIPTION
     "This object indicates which TSs of the Monitored port, should be monitored. 
      Each Bit of the Octet represents a TS:
      31 ......0
      MSB     LSB

      Bit 0 will not be used.
      If the bit value is '1' - this TS should be monitored.
      For a  T1 port, the valid raised bits ('1') are: 1..24.
      For an E1 port, the valid raised bits ('1') are: 1..31.
      Default: all bits='0'
      Agents that do not support this feature will send SIZE 0.
      This object can be Set as described only if prtMonitoringEnable=enabled."
      ::= {prtMonEntry 6}


-- Port Configuration Table
-- This table is applicable  for KMUX, FCD-T1/E1 , FCD-T1L/E1L and FCD-U ports 

prtCfgParam  OBJECT IDENTIFIER  ::=  {prtGen 7}

prtCfgParamTable OBJECT-TYPE
      SYNTAX SEQUENCE OF PrtCfgParamEntry
      MAX-ACCESS not-accessible
      STATUS  current
      DESCRIPTION
       "The write operation into the Table Objects is valid only
        to the TmpCnfg entry.
        KMUX parameters are for the cards: KMBE/New, KVF.6 family."
      ::= { prtCfgParam 1}

prtCfgParamEntry OBJECT-TYPE
      SYNTAX PrtCfgParamEntry
      MAX-ACCESS not-accessible
      STATUS current
	DESCRIPTION  "An entry in table."
	INDEX {prtCfgParamCnfgIdx, prtCfgParamIdx }
      ::= { prtCfgParamTable 1}

PrtCfgParamEntry ::=
      SEQUENCE {
        prtCfgParamCnfgIdx        Integer32,
        prtCfgParamIdx            Integer32,
        prtCfgParamSlt            INTEGER,
        prtCfgParamOperatedMl     INTEGER,
        prtCfgParamMlAtoMlBPrio   INTEGER,
        prtCfgParamMlBtoMlAPrio   INTEGER,
		prtCfgParamInbandLoopDetection    INTEGER,
		prtCfgParamInbandLoopPatternCfg	  INTEGER,
		prtCfgParamInbandLoopActPattern   DisplayString,
		prtCfgParamInbandLoopDeactPattern DisplayString
        }

prtCfgParamCnfgIdx OBJECT-TYPE
      SYNTAX  Integer32  (1..255)
      MAX-ACCESS  read-only
      STATUS  current
      DESCRIPTION
      "This attribute indicates the Idx of the Cnfg (1..100) being 
       accessed.
       Idx  255 relates to the TmpCnfg."
      ::= {prtCfgParamEntry 1}

prtCfgParamIdx OBJECT-TYPE
      SYNTAX  Integer32
      MAX-ACCESS  read-only
      STATUS  current
      DESCRIPTION
      "A unique identifier of the port (within the card when applicable).
       - For KM-2100:  Slot*100+Ch
         external ports:  Ch=1..10
         internal ports (sub-channels): Ch=11..20.
       - For FCD-T1/E1(L): MAIN=111, SUB=113, CH1=122, CH2=124.
       - For other devices, see specific device's spec. "
      ::= {prtCfgParamEntry 2}

prtCfgParamSlt OBJECT-TYPE
      SYNTAX  INTEGER
 {
       io1   (5),
       io2   (6),
       io3   (7),
       io4   (8),
       io5   (9),
       io6  (10),
       io7  (11),
       io8  (12),
       io9  (13),
    kmxIO1 (107),
    kmxIO2 (108),
    kmxIO3 (109),
    kmxIO4 (110),
    kmxIO5 (111),
    kmxIO6 (112),
    kmxIO7 (113),
    kmxIO8 (114),
    kmxIO9 (115),
    kmxIO10(116),
    kmxIO11(117),
    kmxIO12(118),
	notApplicable(255)
       }
      MAX-ACCESS  read-only
      STATUS  current
      DESCRIPTION
      "This attribute indicates a unique number to identify the slot where
       the card is inserted in.
       In the 2104 Unit the entries kmxIO5(111)..kmxIO12(118) are not valid.
       notApplicable(255) - for products that do not have Slots."
      ::= {prtCfgParamEntry 3}

 prtCfgParamOperatedMl OBJECT-TYPE
      SYNTAX  INTEGER {
                  notApplicable(1),
                  kmxMlA     (103),
                  kmxMlB     (104)				  
        }
      MAX-ACCESS  read-write
      STATUS  current
      DESCRIPTION
      "The main link for this channel.
       The field is relevant only for ML modes of Dual, Priority 
       Bumping and Switched Backup."
      ::= {prtCfgParamEntry 4}

prtCfgParamMlAtoMlBPrio OBJECT-TYPE
      SYNTAX  INTEGER {
                       notApplicable(1),
                       low          (2),
                       high         (3)
        }
      MAX-ACCESS  read-write
      STATUS  current
      DESCRIPTION
      "ML-A to ML-B Priority.
       The field is relevant only for ML modes of Priority Bumping
       and Switched Backup."
      ::= {prtCfgParamEntry 5}

prtCfgParamMlBtoMlAPrio OBJECT-TYPE
      SYNTAX  INTEGER {
                     notApplicable(1),
                     low          (2),
                     high         (3)
        }
      MAX-ACCESS  read-write
      STATUS  current
      DESCRIPTION
      "ML-B to ML-A Priority.
       The field is relevant only for ML modes of Priority Bumping."
      ::= {prtCfgParamEntry 6}

prtCfgParamInbandLoopDetection OBJECT-TYPE
      SYNTAX  INTEGER {
                     notApplicable(1),
                     disabled     (2),
                     enabled      (3)
        }
      MAX-ACCESS  read-write
      STATUS  current
      DESCRIPTION
      "Inband Loop Detection.
       The field is relevant for FCD-T1/E1(L) ports."
      ::= {prtCfgParamEntry 7}

prtCfgParamInbandLoopPatternCfg OBJECT-TYPE
      SYNTAX  INTEGER
       {
       notApplicable   (1),
       rdlLoop         (2),
       userConfig      (3)
       }
      MAX-ACCESS  read-write
      STATUS  current
      DESCRIPTION
      "This object indicates if Inband Loop polynomial pattern
       will be according to RDL Loop (the standard) or User Configurated
       according to prtCfgParamInbandLoopActPattern and 
       prtCfgParamInbandLoopDeactPattern."
      ::= {prtCfgParamEntry 8}

prtCfgParamInbandLoopActPattern OBJECT-TYPE
      SYNTAX DisplayString
      MAX-ACCESS read-write
      STATUS current
      DESCRIPTION
      "This object is a binary string of up to 8 bits.
	   Though the syntax allows for any ASCII characters, for this object
	   only '0' or '1' characters are valid.
       The string determines coefficients of the polynomial pattern
       sent to the port in order to Activate the Inband Loop.
       This object is relevant only when prtCfgParamInbandLoopPatternCfg=userConfig."
      ::= {prtCfgParamEntry 9}

prtCfgParamInbandLoopDeactPattern OBJECT-TYPE
      SYNTAX DisplayString
      MAX-ACCESS read-write
      STATUS current
      DESCRIPTION
      "This object is a binary string of up to 8 bits.
	   Though the syntax allows for any ASCII characters, for this object
	   only '0' or '1' characters are valid.
       The string determines coefficients of the polynomial pattern
       sent to the port in order to Deactivate the Inband Loop.
       This object is relevant only when prtCfgParamInbandLoopPatternCfg=userConfig."
      ::= {prtCfgParamEntry 10}


--DACS T1/E1 port specific parameters  

--DACS T1/E1 port statistics parameters.
--These parameters are in addition to those of RFC-1406 MIB. 

prtT1E1StatTable OBJECT-TYPE
  SYNTAX  SEQUENCE OF PrtT1E1StatEntry
  MAX-ACCESS  not-accessible
  STATUS  current
  DESCRIPTION
  "T1/E1 port statistics table."
  ::= { prtT1E1 1}

prtT1E1StatEntry   OBJECT-TYPE
  SYNTAX  PrtT1E1StatEntry
  MAX-ACCESS  not-accessible
  STATUS  current
  DESCRIPTION
  " An entry in the T1/E1 port statistics table."
  INDEX { prtT1E1SPrtIdx }
  ::= { prtT1E1StatTable 1}

PrtT1E1StatEntry ::=
     SEQUENCE {
  prtT1E1SPrtIdx    Integer32,
  prtT1E1SSlt	    INTEGER,
  prtT1E1OosCount   Gauge32,
  prtT1E1BpvLastMin	Gauge32,
  prtT1E1BpvMax	    Gauge32
  }

prtT1E1SPrtIdx OBJECT-TYPE
      SYNTAX  Integer32
      MAX-ACCESS  read-only
      STATUS  current
      DESCRIPTION
      "This attribute indicates a unique  port number.
       The same numbering as for prtGenPrtIdx.
       The valid port number depends on the IO slot no.,  the 
       installed card type and the port type: outside, inside. 
      * The outside ports will be the T1/E1 cards ports. 
        The convention used will be (for DXC):
        - first two digits will be: (IO slot number+10)
        - last one/two digits will be the port number within the 
          card, in odd numbers:
          port1 = 1
          port2 = 3
          port3 = 5 
          etc...
        Example: port2 of IO slot 11 will be: 213 ."
      ::= { prtT1E1StatEntry 1}

prtT1E1SSlt     OBJECT-TYPE
      SYNTAX  INTEGER
       {
       clA   (3),
       clB   (4),
       io1   (5),
       io2   (6),
       io3   (7),
       io4   (8),
       io5   (9),
       io6  (10),
       io7  (11),
       io8  (12),
       io9  (13),
       io10 (14),
       io11 (15),
       io12 (16),
    io13 (17),
    io14 (18),
    io15 (19),
    standAlone (255)
       }
      MAX-ACCESS  read-only
      STATUS  current
      DESCRIPTION
      "This attribute indicates a unique number to identify the slot where
       the card is inserted in.
       When the unit is stand-alone, this object is not applicable
       and 255 will be used."
      ::= { prtT1E1StatEntry 2}

prtT1E1OosCount  OBJECT-TYPE
   SYNTAX  Gauge32
      MAX-ACCESS  read-only
      STATUS  current
      DESCRIPTION
   "This object is applicable only for an E1 active port.
    It provides the number of red alarm events since the last
    count clearing."
   ::= { prtT1E1StatEntry 3 }

prtT1E1BpvLastMin  OBJECT-TYPE
   SYNTAX  Gauge32
      MAX-ACCESS  read-only
      STATUS  current
      DESCRIPTION
   "This object is applicable only for an E1 active port.
    It provides the number of BPV (BiPolar Violation) events 
    detected during the last minute."
   ::= { prtT1E1StatEntry 4 }

prtT1E1BpvMax  OBJECT-TYPE
   SYNTAX  Gauge32
      MAX-ACCESS  read-only
      STATUS  current
      DESCRIPTION
   "This object is applicable only for an E1 active port.
    It provides the maximal number of BPV (BiPolar Violation) 
    events (per minute), detected during the worst minute."
   ::= { prtT1E1StatEntry 5 }


--DACS T1/E1 port configuration parameters.
--
--Objects 2..9 appear in RFC-1406 MIB (dsx1ConfigTable) as RW
--objects. They were entered in this private MIB, because in
--RFC-1406 MIB there is no reference to configuration number.


prtT1E1CnfgTable OBJECT-TYPE
  SYNTAX  SEQUENCE OF PrtT1E1CnfgEntry
  MAX-ACCESS  not-accessible
  STATUS  current
  DESCRIPTION
  "T1/E1 port configuration table."
  ::= { prtT1E1 2}

prtT1E1CnfgEntry   OBJECT-TYPE
  SYNTAX  PrtT1E1CnfgEntry
  MAX-ACCESS  not-accessible
  STATUS  current
  DESCRIPTION
  " An entry in the T1/E1 port configuration table."
  INDEX { prtT1E1CnfgIdx, prtT1E1PrtIdx }
  ::= { prtT1E1CnfgTable 1}

PrtT1E1CnfgEntry ::= SEQUENCE {
    prtT1E1CnfgIdx    Integer32,
    prtT1E1PrtIdx     Integer32,
  prtT1E1Slt	    INTEGER,
  prtT1E1LineType   INTEGER,
  prtT1E1LineCode   INTEGER,
  prtT1E1SignalMode INTEGER,
  prtT1E1Fdl	    INTEGER,
  prtT1E1FdlMode    INTEGER,
  prtT1E1Sync	    INTEGER,
  prtT1E1CGA	    INTEGER,
  prtT1E1IdleCode   OCTET STRING,
  prtT1E1OosSignal  INTEGER,
  prtT1E1VoiceOos   OCTET STRING,
  prtT1E1DataOos    OCTET STRING,
  prtT1E1LineLengthMask	INTEGER,
  prtT1E1TxGainMask	INTEGER,
  prtT1E1InbandMng  INTEGER,
  prtT1E1InbandMngRate  INTEGER,
  prtT1E1DedicatedTs  Integer32,
  prtT1E1InbandMngRoutProt INTEGER,
  prtT1E1LinkMode   INTEGER,
  prtT1E1Multiplier INTEGER,
  prtT1E1RxGain     INTEGER,
  prtT1E1RAI        INTEGER, 
    prtT1E1LineMode   INTEGER,
  prtT1E1TS0SaBits  OCTET STRING,
  prtT1E1ConnectedTS INTEGER,
  prtT1E1Ts0SaBit    INTEGER,
  prtT1E1SameFeCnfg	 INTEGER,
  prtT1E1RemCrc4     INTEGER,
  prtT1E1MaxTSs	     Integer32,
  prtT1E1EocTsConfig INTEGER,
  prtT1E1Role	     INTEGER,
  prtT1E1PppEchoFailDetection INTEGER,
    prtT1E1CasOosPattern        INTEGER,
    prtT1E1CasOosSpaceCode      Unsigned32,
    prtT1E1CasOosMarkCode       Unsigned32 
 }

prtT1E1CnfgIdx OBJECT-TYPE
      SYNTAX  Integer32 (1..255)
      MAX-ACCESS  read-only
      STATUS  current
      DESCRIPTION
      "This attribute indicates the Idx of the Config being accessed.
       Idx of 255 relates to the Temporary (Scratch) Config. "
      ::= { prtT1E1CnfgEntry 1}

prtT1E1PrtIdx OBJECT-TYPE
      SYNTAX  Integer32
      MAX-ACCESS  read-only
      STATUS  current
      DESCRIPTION
      "This attribute indicates a unique  port number.
    The same numbering as for prtGenPrtIdx.
       The valid port number depends on the IO slot no.,  the 
       installed card type and the port type: outside, inside. 
       In the DXC :
      - first two digits will be: (IO slot number+10)
      - last one/two digits will be the port number within the 
        card in odd or even numbers, as follows:
      * For the outside/external ports, in odd numbers:
        port1 = 1
        port2 = 3
        port3 = 5 
        etc...
        Example: port2 of IO slot 11 will be: 213 .
      * The inside/internal ports, in even numbers:
        port1 = 2
        port2 = 4
        port3 = 6 
        etc...
        Example: port2 of IO slot 11 will be: 214 .
   
       In the Kilomux, the port index is calculated as follows:
       100*Slot+Ch. The external Ch numbers are 1..10, and the
       internal Ch numbers are 11..20."
      ::= { prtT1E1CnfgEntry 2}

prtT1E1Slt     OBJECT-TYPE
      SYNTAX  INTEGER
       {
       clA   (3),
       clB   (4),
       io1   (5),
       io2   (6),
       io3   (7),
       io4   (8),
       io5   (9),
       io6  (10),
       io7  (11),
       io8  (12),
       io9  (13),
       io10 (14),
       io11 (15),
       io12 (16),
       io13 (17),
       io14 (18),
       io15 (19),
   
    kmxMlA (103),
    kmxMlB (104),

    kmxOpt (106),
    kmxIO1 (107),
    kmxIO2 (108),
    kmxIO3 (109),
    kmxIO4 (110),
    kmxIO5 (111),
    kmxIO6 (112),
    kmxIO7 (113),
    kmxIO8 (114),
    kmxIO9 (115),
    kmxIO10(116),
    kmxIO11(117),
    kmxIO12(118),
    standAlone (255)
       }
      MAX-ACCESS  read-only
      STATUS  current
      DESCRIPTION
      "This attribute indicates a unique number to identify the slot where
       the card is inserted in.
       When the unit is stand-alone, this object is not applicable
       and 255 will be used."
      ::= { prtT1E1CnfgEntry 3}

prtT1E1LineType OBJECT-TYPE
    SYNTAX  INTEGER {
                other    (1),
                esf      (2),
                d4       (3), --sf
                e1       (4),
                e1Crc    (5),
                e1MF     (6),
                e1CrcMF  (7),
                unframed (8)
            }
    MAX-ACCESS  read-write
    STATUS  current
    DESCRIPTION
       "This variable indicates  the  variety  of T1/E1
        Line  implementing  this  circuit.  The type of
        circuit affects the number of bits  per  second
        that  the circuit can reasonably carry, as well
        as the interpretation of the  usage  and  error
        statistics.  The values, in sequence, describe:

       TITLE:        SPECIFICATION:
       esf       Extended SuperFrame DS1
       d4        AT&T D4 format DS1  - SF
       e1        CCITT Recommendation G.704
                 (Table 4a) - G732N
       e1Crc     CCITT Recommendation G.704
                 (Table 4b) - G732N with CRC
       e1MF      G.704 (Table 4a) with TS16
                 multiframing enabled - G732S
       e1CrcMF   G.704 (Table 4b) with TS16
                 multiframing enabled - G732S with CRC
       unframed  
     
       T1 - applicable values: (1),(2),(3),(8)
       E1 - applicable values: (1),(4),(5),(6),(7),(8) "
    ::= { prtT1E1CnfgEntry 4 }

prtT1E1LineCode OBJECT-TYPE
    SYNTAX  INTEGER {
                jbzs (1),
                b8zs (2),
                hdb3 (3),
                zbtsi(4),
                ami  (5),
                other(6)
            }
    MAX-ACCESS  read-write
    STATUS  current
    DESCRIPTION
       "This variable describes the  variety  of  Zero
       Code  Suppression  used  on  the link, which in
       turn affects a number of its characteristics.

       jbzs=b7zs refers the Jammed  Bit  Zero  Suppres-
       sion,  in  which  the  AT&T specification of at
       least one pulse every 8 bit periods is literal-
       ly  implemented  by forcing a pulse in bit 8 of
       each channel.  Thus, only seven bits per  chan-
       nel, or 1.344 Mbps, is available for data (used for T1).

       b8zs refers to the use of a specified pattern
       of  normal  bits  and  bipolar violations
       which are used to replace a sequence  of  eight
       zero bits (used for T1).

       ANSI Clear Channels may use zbtsi, or  Zero
       Byte Time Slot Interchange.

       E1 links, with or without CRC, use hdb3  or
       ami (= TRAN).

       amI (=TRAN) refers to a mode wherein no zero code
       suppression  is  present  and the line encoding
       does not solve the problem directly. In this
       application, the higher layer must provide data
       which meets or exceeds the  pulse  density  re-
       quirements, such as inverting HDLC data."
   ::= { prtT1E1CnfgEntry 5 }

prtT1E1SignalMode OBJECT-TYPE
    SYNTAX  INTEGER {
                none            (1),
                robbedBit       (2),
                bitOriented     (3),  --CAS
                messageOriented (4)   --CCS
            }
    MAX-ACCESS  read-write
    STATUS  current
    DESCRIPTION
       "'none' indicates that no bits are reserved for
               signaling on this channel.

        'robbedBit' indicates that T1 Robbed Bit Signaling is in use.

        'bitOriented' indicates that E1 Channel  Associated 
               Signaling (CAS) is in use.

        'messageOriented' indicates that Common  Channel Signaling 
               (CCS) is in use either on channel 16 of an E1 link or 
               channel 24 of a T1."
   ::= { prtT1E1CnfgEntry 6 }

prtT1E1Fdl OBJECT-TYPE
    SYNTAX  INTEGER {
                  other      (1),
                  ansi-T1-403(2),
                  att-54016  (4),
                  fdl-none   (8),
                  transFdl   (16)
            }
    MAX-ACCESS  read-write
    STATUS  current
    DESCRIPTION
       "This bitmap describes the use of  the  facili-
        ties data link, and is the sum of the capabili-
        ties:

        'other' indicates that a protocol  other  than
         one following is used.

        'ansi-T1-403' refers to the  FDL  exchange
         recommended by ANSI.

        'att-54016' refers to ESF FDL exchanges.

        'fdl-none' indicates that the device  does
         not use the FDL.
        'transFdl' indicates transition between two ports of 
         the same card. "
   ::= { prtT1E1CnfgEntry 7 }

prtT1E1FdlMode OBJECT-TYPE
    SYNTAX  INTEGER {
      other     (1),
      user      (2),
      carrier   (3),
      notApplicable (255)
            }
    MAX-ACCESS  read-write
    STATUS  current
    DESCRIPTION
    " Fdl Mode of the T1 selected port.
      notApplicable - will be used for an E1 port."
   ::= { prtT1E1CnfgEntry 8 }


prtT1E1Sync OBJECT-TYPE
    SYNTAX  INTEGER {
    other  (1),
    tr62411(2),
    ccitt  (3),
    fast   (4)                 
            }
    MAX-ACCESS  read-write
    STATUS  current
    DESCRIPTION
    "This object enables returning to normal operation, after 
     the end of a main/sub link red alarm event, in reduced time.
        'tr62411' - complies with AT&T TR-62411 (after 10 seconds).
              Applicable for both T1 and E1 interfaces.
    'ccitt'   - complies with CCITT standard. Applicable only
              for E1 interfaces.
    'fast'    - after 1 second."
    ::= { prtT1E1CnfgEntry 9 }

prtT1E1CGA OBJECT-TYPE
    SYNTAX  INTEGER {
      none (1),
      trans(2),
      full (3)                                   
            }
    MAX-ACCESS  read-write
    STATUS  current
    DESCRIPTION
    "This object selects the method used to signal the CGA state
     to the other end, through the main/sub link. 
     'none'  - non-transparent mode. When one of the links 
               (main/sub) will be in Out Of Service state, both 
               'Data/Voice Oos' and 'Oos Signal' will be 
               transmitted to the other end.
     'trans' - when one of the links (main/sub) will be in Out
               Of Service state, 'Data/Voice Oos' will be 
               transmitted to the other end.
     'full'  - fully-transparent mode. When one of the links 
                  (main/sub) will be in Out Of Service state, 
                  neither 'Data/Voice Oos' nor 'Oos Signal' will 
                  be transmitted to the other end."
    ::= { prtT1E1CnfgEntry 10 }

prtT1E1IdleCode OBJECT-TYPE
    SYNTAX  OCTET STRING (SIZE (0..4))
    MAX-ACCESS  read-write
    STATUS  current
    DESCRIPTION
    "This object selects the code transmitted to fill idle 
     (unused) time slots in the main link frame. 
     Valid range: (0 - FF HEX) ."
    ::= { prtT1E1CnfgEntry 11 }

prtT1E1OosSignal  OBJECT-TYPE
      SYNTAX  INTEGER
       {
        notsupported  (2),
        forcedIdle    (3),
        forcedBusy    (4),
        busyIdle      (5),
        idleBusy      (6)
       }
      MAX-ACCESS  read-write
      STATUS  current
      DESCRIPTION
      "'idle' = '0' = on-hook, idle state
       'busy' = '1' = off-hook, busy state
       'forcedIdle' = SP = both A and B signaling bits are forced
                      to '0' during out-of-service periods.
       'forcedBusy' = MK = both A and B signaling bits are forced
                      to '1' during out-of-service periods.
       'busyIdle'   = MK_SP = A and B bits are forced to '1' for
                      2.5 seconds; then they are switched to '0'
                      until out-of-service condition disappears.
       'idleBusy'   = SP_MK = A and B bits are forced to '0' for
                      2.5 seconds; then they are switched to '1'
                      until out-of-service condition disappears.
       - for T1:    '0'=0   ;  '1'=1                         
       - for E1:    '0'=1   ;  '1'=0   "
   ::= { prtT1E1CnfgEntry 12 }

prtT1E1VoiceOos  OBJECT-TYPE
    SYNTAX  OCTET STRING (SIZE (0..4))
    MAX-ACCESS  read-write
    STATUS  current
    DESCRIPTION
    "Voice Out-Of-Service code. Valid range: (0 - FF HEX).
     For agents that do not support this feature, the value will
     always be 0."
   ::= { prtT1E1CnfgEntry 13 }

prtT1E1DataOos  OBJECT-TYPE
    SYNTAX  OCTET STRING (SIZE (0..4))
    MAX-ACCESS  read-write
    STATUS  current
    DESCRIPTION
    "Data Out-Of-Service code. Valid range: (0 - FF HEX).
     For agents that do not support this feature, the value will
     always be 0."
   ::= { prtT1E1CnfgEntry 14 }

prtT1E1LineLengthMask  OBJECT-TYPE
      SYNTAX  INTEGER
       {
        unknown      (1),
        len0p133ft   (2),
        len134p266ft (3),
        len267p399ft (4),
        len400p533ft (5),
        len534p655ft (6),
        fcc68        (7)
       }
      MAX-ACCESS  read-write
      STATUS  current
      DESCRIPTION
      "This attribute is the line length mask parameter used only 
       for T1/DSU interfaces.
       len400p533ft=length range: 400ft to 533ft 
       'fcc68' - provides compliance with the FCC 68.308 Option A
                 output pulse mask. "
      ::= { prtT1E1CnfgEntry 15 }

prtT1E1TxGainMask  OBJECT-TYPE
      SYNTAX  INTEGER
       {
          notApplicable     (1),
          txGain0db         (2),
          txGain7dot5db     (3),
          txGain15db        (4),
          txGain22dot5db    (5)
       }
      MAX-ACCESS  read-write
      STATUS  current
      DESCRIPTION
      "This attribute is the tx gain mask parameter (dB), used 
       only for T1/CSU interfaces."
   ::= { prtT1E1CnfgEntry 16 }

prtT1E1InbandMng  OBJECT-TYPE
      SYNTAX  INTEGER
       {
          off         (2),
          fdlOrTs0    (3),
          dedicatedTs (4),
          dedicatedPpp(5),
          dedicatedFr (6),
          internal    (7)		  
       }
      MAX-ACCESS  read-write
      STATUS  current
      DESCRIPTION
      "A unique number to identify an Inband management over the 
       link.
       internal - supported by KM-2100 only. It means that the management is internal
                  to the frame. It takes part of the ML Frame bits (instead of data)."
      ::= {prtT1E1CnfgEntry 17}

prtT1E1InbandMngRate  OBJECT-TYPE
      SYNTAX  INTEGER
       {
          notApplicable(1),
          r4k   (2),
          r8k   (3),
          r12k  (4),
          r16k  (5),
          r32k  (6),
          r64k  (7),
          r20k  (8)
       }
      MAX-ACCESS  read-write
      STATUS  current
      DESCRIPTION
      "A unique number to identify the rate of the Inband management.
       It is required only for E1 links and is applicable only when 
       prtExT1E1InbandMng selected is FdlOrTs0 or dedicatedTs."
      ::= {prtT1E1CnfgEntry 18}

prtT1E1DedicatedTs  OBJECT-TYPE
      SYNTAX  Integer32
      MAX-ACCESS  read-write
      STATUS  current
      DESCRIPTION

      "The value is differently determined for different products.
       There are two methods:

       1) A unique number to identify Dedicated TS of the T1/E1 port.
          It is applicable only when prtExT1E1InbandMng selected is 
          dedicatedTs.
          1..24 - Dedicated TS of T1
          1..31 - Dedicated TS of E1
          255   - notApplicable (for agents that do not support this 
                  feature)
          Other values are invalid.

       2) For FCD-STM,  up to five TSs may be dedicated to management.
          This object value is the Sum (sigma) of 2**n, where n =TS-1
          e.g. 	  Time slots 3,5,7,9,11 are dedicated to management:
            	   2** 2
          		  +2** 4
          		  +2** 6 
          		  +2** 8
          		  +2**10  = 4+16+64+256+1024=1364 
       
       User should consult the product specification, to find out 
       the method employed."
	   ::= {prtT1E1CnfgEntry 19}

prtT1E1InbandMngRoutProt  OBJECT-TYPE
      SYNTAX  INTEGER
       {
       notApplicable (1),
       none          (2),  
       proprietary   (3),
       rip2          (4)
       }
      MAX-ACCESS  read-write
      STATUS  current
      DESCRIPTION
      "Inband Mng Routing Protocol of the port.
       When prtT1E1InbandMng is 'dedicatedPpp'-'proprietary' and
                                               'rip2' are applicable.
       For other values  - only 'proprietary' is applicable.
       
       For FCD-M and FCD-A:
       When prtT1E1InbandMng is 'dedicatedPpp' or 'dedicatedFr':
                             'None', 'proprietary' and 'rip2' are applicable.
       When prtT1E1InbandMng is 'fdlOrTS0' or 'dedicatedTs':
                             'None' and 'proprietary' are applicable.
       When prtT1E1InbandMng is 'off':
                             'None' is applicable."             
      ::= {prtT1E1CnfgEntry 20}

prtT1E1LinkMode  OBJECT-TYPE
      SYNTAX  INTEGER
       {
       notApplicable (1),
       regular       (2),  
       transparent   (3)
       }
      MAX-ACCESS  read-write
      STATUS  current
      DESCRIPTION
      "regular - TSs are connected by user via TS Assignment only
       transparent - when a port with this Link Mode is connected to an 
                     internal T1/E1 port of a T3/E3 card, TS0, TS16 and Fbit
                     are transparently transferred to the E3/T3 stream."             
      ::= {prtT1E1CnfgEntry 21}

prtT1E1Multiplier OBJECT-TYPE
      SYNTAX  INTEGER { 
      notApplicable (1), 
      br56 (2),
      br64 (3)
      }
      MAX-ACCESS  read-write
      STATUS  current
      DESCRIPTION
      "The data rate of each TS. The multiplier values
       can be 56 kbps or 64 kbps. For T1 only."
      ::= { prtT1E1CnfgEntry 22 }

prtT1E1RxGain OBJECT-TYPE
      SYNTAX  INTEGER
       {
       notApplicable  (1),
       rxGain12dB     (2),
       rxGain30dB     (3),
       rxGain36dB     (4),
	   shortHaul      (5),
	   longHaul       (6),
	   rxGain20dB     (7)
       }
      MAX-ACCESS  read-write
      STATUS  current
      DESCRIPTION
      "This attribute is the rx volume (dB)."
   ::= { prtT1E1CnfgEntry 23 }

 prtT1E1RAI  OBJECT-TYPE
      SYNTAX  INTEGER
       {
        notApplicable  (1),
        off (2),
        on  (3)
       }
      MAX-ACCESS  read-write
      STATUS  current
      DESCRIPTION
      "Remote Alarm Signal"
   ::= { prtT1E1CnfgEntry 24 }

prtT1E1LineMode OBJECT-TYPE
      SYNTAX  INTEGER 
       {
        notApplicable   (1), 
        csu             (2),
        dsu             (3),
        ltu             (4)
       }
        MAX-ACCESS  read-write
        STATUS  current
        DESCRIPTION
      "Interface type of the port.
       For T1 - csu, dsu are the valid values
       For E1 - dsu, ltu are the valid values"
   ::= { prtT1E1CnfgEntry 25 }

prtT1E1TS0SaBits OBJECT-TYPE
    SYNTAX  OCTET STRING 
    MAX-ACCESS  read-write
    STATUS  current
    DESCRIPTION
    "This object is applicable only for E1 ports. For T1, string size will be 0.
     For E1, it enables user to select the use of TS0 Sa Bits 4..8, by 3 octets:
	 The order (in hexa display):
	 free Sa-Bit-4  Sa-Bit-5  Sa-Bit-6  Sa-Bit-7  Sa-Bit-8
	 |___________|  |________________|  |________________|
	     MSByte                                 LSByte
	     
	 Each Sa Bit will be represented by a nibble, having the following meaning:
	 0000 = zero
	 0001 = one
	 0010 = management
	 0011 = transparent
	 the rest are reserved for future use."      
   ::= { prtT1E1CnfgEntry 26 }

prtT1E1ConnectedTS OBJECT-TYPE
      SYNTAX  INTEGER 
       {
        notApplicable	(1), 
        no				(2),
        yes				(3)
       }
        MAX-ACCESS  read-only
        STATUS  current
        DESCRIPTION
      "This parameter indicates if there is any connected TS for this interface."
   ::= { prtT1E1CnfgEntry 27 }

prtT1E1Ts0SaBit OBJECT-TYPE
      SYNTAX  INTEGER 
       {
        notApplicable	(1), 
        noMng	(2),
        mng		(3)
       }
        MAX-ACCESS  read-write
        STATUS  current
        DESCRIPTION
      "This parameter indicates whether to send TS 0, or not.
       noMng= TS 0 is looped, therefore not sent.
       mng= TS 0 isn't looped, therefore it is sent."
   ::= { prtT1E1CnfgEntry 28 }
	   
prtT1E1SameFeCnfg OBJECT-TYPE
      SYNTAX  INTEGER 
       {
        notApplicable	(1), 
        no              (2),
        yes             (3)
       }
      MAX-ACCESS  read-write
      STATUS  current
      DESCRIPTION
      "This parameter indicates whether the same E1 configuration 
       parameters and TS assignment are set both to the local
       and remote device.
       Read-Write access is applicable only in G732N framed mode.
       For G732S and UNFRAMED this parameter is set by 
       agent to YES and is Read Only.
       In Case of conflict during power-up between the central 
       and remote, the value set by the central unit is the valid one."
      ::= { prtT1E1CnfgEntry 29 }

prtT1E1RemCrc4 OBJECT-TYPE
      SYNTAX  INTEGER 
       {
        notApplicable	(1), 
        no              (2),
        yes             (3)
       }
      MAX-ACCESS  read-write
      STATUS  current
      DESCRIPTION
      "This object indicates whether the E1 of the Remote device
       connected to this E1 port, will have CRC-4 or not."
      ::= { prtT1E1CnfgEntry 30 }

prtT1E1MaxTSs OBJECT-TYPE
      SYNTAX  Integer32 
      MAX-ACCESS  read-write
      STATUS  current
      DESCRIPTION
      "This object is applicable only for DXC D4T1, D4E1, D8T1, D8E1 
       external ports and D8GSL internal E1 ports.
	   It is relevant only when sysCIntTsAllocMode=static(2).
       255=not applicable
       If prtT1E1LineType=unframed(8), the value of this object must be 32.
       Else, the valid values are 0..31."
      ::= { prtT1E1CnfgEntry 31}

prtT1E1EocTsConfig OBJECT-TYPE
      SYNTAX  INTEGER 
       {
        notApplicable (1), 
        disabled      (2),
        enabled       (3)
       }
      MAX-ACCESS  read-write
      STATUS  current
      DESCRIPTION
      "This object indicates whether the use of EOC for TS Configuration
       is enabled or not."
      ::= { prtT1E1CnfgEntry 32 }

prtT1E1Role OBJECT-TYPE
      SYNTAX  INTEGER 
       {
        notApplicable 	(1), 
        sub      		(2),
        main       		(3)
       }
      MAX-ACCESS  read-write
      STATUS  current
      DESCRIPTION
      "This object indicates whether this port behaves as SUB or Main link."
      ::= { prtT1E1CnfgEntry 33 }

prtT1E1PppEchoFailDetection OBJECT-TYPE
      SYNTAX  INTEGER 
       {
        notApplicable	(1), 
        disable         (2),
        enable          (3)
       }
      MAX-ACCESS  read-write
      STATUS  current
      DESCRIPTION
      "This object indicates whether the PPP Echo is taken into account
       for its Fail Detection.  
       This object is relevant when Inband Mng between devices is Dedicated TS PPP.
       Default=Disable.
	   Enable - will be selected mainly when a T1/E1 Ring exists and between 2 adjacent 
	            Ring devices there is another device or Net, that causes these Ring devices
	            not to sense that the PPP connection between them is lost. In this case,
	            Echo Request should be initiated by the port."
      ::= { prtT1E1CnfgEntry 34 }

prtT1E1CasOosPattern  OBJECT-TYPE
    SYNTAX  INTEGER 
       {
       space            (1), 
       mark             (2),
       spaceMark        (3)
       }
    MAX-ACCESS  read-write
    STATUS      current
    DESCRIPTION
    "This objects defines the Cas Out-Of-Service code
    space (1) - see prtT1E1CasOosSpaceCode below
    mark  (2) - see prtT1E1CasOosMarkCode below
    spaceMark (3) - transmit 'space' for 2 sec and 
                    'mark' for 2 sec repeatedly."
      ::= { prtT1E1CnfgEntry 36 }
   
prtT1E1CasOosSpaceCode  OBJECT-TYPE
    SYNTAX      Unsigned32 (0..15)
    MAX-ACCESS  read-write
    STATUS      current
    DESCRIPTION
    "This objects defines the Cas Out-Of-Service code
    The value that will be transmitted when 
    prtT1E1CasOosPattern = space (1).
    default = 14."
      ::= { prtT1E1CnfgEntry 37 }

prtT1E1CasOosMarkCode  OBJECT-TYPE
    SYNTAX      Unsigned32 (0..15)
    MAX-ACCESS  read-write
    STATUS      current
    DESCRIPTION
    "This objects defines the Cas Out-Of-Service code
    The value that will be transmitted when 
    prtT1E1CasOosPattern = mark (2). 
    default = 1."
      ::= { prtT1E1CnfgEntry 38 }



--prtT1E1 Last FDL Message Table - Statistics

prtT1E1FdlMsgTable  OBJECT-TYPE
     SYNTAX SEQUENCE OF PrtT1E1FdlMsgEntry
     MAX-ACCESS not-accessible
     STATUS  current
     DESCRIPTION
      "This table is applicable for a T1 interface with 'esf'
       LineType or E1 interface, when CRC is enabled (LineType)."
  ::= { prtT1E1 3}

prtT1E1FdlMsgEntry OBJECT-TYPE
      SYNTAX PrtT1E1FdlMsgEntry
      MAX-ACCESS not-accessible
      STATUS current
	DESCRIPTION  "An entry in table."
	INDEX {prtT1E1FdlMsgPrtIdx, prtT1E1FdlMsgFdlType}
      ::= { prtT1E1FdlMsgTable 1}

PrtT1E1FdlMsgEntry ::=
      SEQUENCE {
      prtT1E1FdlMsgPrtIdx    Integer32,
      prtT1E1FdlMsgFdlType   INTEGER,
      prtT1E1FdlMsgSlt       INTEGER,
      prtT1E1FdlMsg          OCTET STRING   
      }

prtT1E1FdlMsgPrtIdx OBJECT-TYPE
      SYNTAX  Integer32
      MAX-ACCESS  read-only
      STATUS  current
      DESCRIPTION
      "This attribute indicates a unique  port number.
    The same numbering as for prtGenPrtIdx.
       The valid port number depends on the IO slot no.,  the 
       installed card type and the port type: outside, inside. 
      * The outside ports will be the T1/E1 cards ports. 
        The convention used will be (for DXC):
      - first two digits will be: (IO slot number+10)
         - last one/two digits will be the port number within the 
           card, in odd numbers:
     port1 = 1
     port2 = 3
     port3 = 5 
     etc...
   Example: port2 of IO slot 11 will be: 213 ."
      ::= { prtT1E1FdlMsgEntry 1}

prtT1E1FdlMsgFdlType OBJECT-TYPE
      SYNTAX  INTEGER
       {
          send    (1),
    receive (2)
    }
      MAX-ACCESS  read-only
      STATUS  current
      DESCRIPTION
   "The Fdl type reference of the Fdl message."
      ::= { prtT1E1FdlMsgEntry 2}

prtT1E1FdlMsgSlt    OBJECT-TYPE
      SYNTAX  INTEGER
       {
       io1   (5),
       io2   (6),
       io3   (7),
       io4   (8),
       io5   (9),
       io6  (10),
       io7  (11),
       io8  (12),
       io9  (13),
       io10 (14),
       io11 (15),
       io12 (16),
       io13 (17),
       io14 (18),
       io15 (19),
       standAlone (255)
      }
      MAX-ACCESS  read-only
      STATUS  current
      DESCRIPTION
      "This attribute indicates a unique number to identify the slot where
       the card is inserted in.
       When the unit is stand-alone, this object is not applicable
       and 255 will be used."
      ::= { prtT1E1FdlMsgEntry 3}

prtT1E1FdlMsg  OBJECT-TYPE
   SYNTAX  OCTET STRING
      MAX-ACCESS  read-only
      STATUS  current
      DESCRIPTION
      "FDL message."
      ::= { prtT1E1FdlMsgEntry 4}


--prtHS specific parameters (configuration & status) table

prtHSParamTable  OBJECT-TYPE
      SYNTAX SEQUENCE OF PrtHSParamEntry
      MAX-ACCESS not-accessible
      STATUS current
	DESCRIPTION  "A table."
	::=  { prtHS 1 }

prtHSParamEntry OBJECT-TYPE
      SYNTAX PrtHSParamEntry
      MAX-ACCESS not-accessible
      STATUS current
	DESCRIPTION  "An entry in table."
	INDEX { prtHSCnfgIdx, prtHSPrtIdx }
      ::= { prtHSParamTable 1}

PrtHSParamEntry ::=
      SEQUENCE {
      prtHSCnfgIdx               Integer32,
      prtHSPrtIdx                Integer32,
      prtHSSlt                   INTEGER,
      prtHSRate                  INTEGER,
      prtHSFifoSize              INTEGER,
      prtHSClkMode               INTEGER,
      prtHSCTS                   INTEGER,
      prtHSRtsState              INTEGER,
      prtHSInbandLoopback        INTEGER,
	  prtHSInbandLoopPatternCfg	 INTEGER,
	  prtHSInbandLoopActPattern  DisplayString,
	  prtHSInbandLoopDeactPattern DisplayString,
	  prtHSDCD		         	 INTEGER,
	  prtHSClkPolarity           INTEGER,
	  prtHSInterfaceType         INTEGER,
   	  prtHSUnframed              INTEGER  
   }    
   
prtHSCnfgIdx OBJECT-TYPE
      SYNTAX  Integer32 (1..255)
      MAX-ACCESS  read-only
      STATUS  current
      DESCRIPTION
      "This attribute indicates the Idx of the Config being accessed.
       Idx of 255 relates to the Temporary (Scratch) Config. "
      ::= { prtHSParamEntry 1}

prtHSPrtIdx OBJECT-TYPE
      SYNTAX  Integer32
      MAX-ACCESS  read-only
      STATUS  current
      DESCRIPTION
      "This attribute indicates a unique number to identify a port. 
       The valid port number depends on the IO slot no.,  the 
       installed card type and the port type: outside, inside, 
       SP.
    * The inside ports will be the HS cards ports. The 
      convention used will be (for DXC):
      - first two digits will be: (IO slot number+10)
         - last one/two digits will be the port number within the 
           card, in even numbers:
     port1 = 2
     port2 = 4
     port3 = 6 
     etc...
   Example: port2 of IO slot 11 will be: 214 ."
      ::= { prtHSParamEntry 2}

prtHSSlt      OBJECT-TYPE
      SYNTAX  INTEGER
       {
       io1   (5),
       io2   (6),
       io3   (7),
       io4   (8),
       io5   (9),
       io6  (10),
       io7  (11),
       io8  (12),
       io9  (13),
       io10 (14),
       io11 (15),
       io12 (16),
       io13 (17),
       io14 (18),
       io15 (19),
       standAlone (255)
       }
      MAX-ACCESS  read-only
      STATUS  current
      DESCRIPTION
      "This attribute indicates a unique number to identify the slot where
       the card is inserted in.
       When the unit is stand-alone, this object is not applicable
       and 255 will be used."
      ::= { prtHSParamEntry 3}

prtHSRate     OBJECT-TYPE
      SYNTAX  INTEGER {
        r0x56eq0Kbps     (1),
        r1x56eq56Kbps    (2),
        r2x56eq112Kbps   (3),
        r3x56eq168Kbps   (4),
        r4x56eq224Kbps   (5),
        r5x56eq280Kbps   (6),
        r6x56eq336Kbps   (7),
        r7x56eq392Kbps   (8),
        r8x56eq448Kbps   (9),
        r9x56eq504Kbps  (10),
        r10x56eq560Kbps (11),
        r11x56eq616Kbps (12),
        r12x56eq672Kbps (13),
        r13x56eq728Kbps (14),
        r14x56eq784Kbps (15),
        r15x56eq840Kbps (16),
        r16x56eq896Kbps (17),
        r17x56eq952Kbps (18),
        r18x56eq1008Kbps(19),
        r19x56eq1064Kbps(20),
        r20x56eq1120Kbps(21),
        r21x56eq1176Kbps(22),
        r22x56eq1232Kbps(23),
        r23x56eq1288Kbps(24),
        r24x56eq1344Kbps(25),
        r25x56eq1400Kbps(26),
        r26x56eq1456Kbps(27),
        r27x56eq1512Kbps(28),
        r28x56eq1568Kbps(29),
        r29x56eq1624Kbps(30),
        r30x56eq1680Kbps(31),
        r31x56eq1736Kbps(32),
        r0x64eq0Kbps    (33),
        r1x64eq64Kbps   (34),
        r2x64eq128Kbps  (35),
        r3x64eq192Kbps  (36),
        r4x64eq256Kbps  (37),
        r5x64eq320Kbps  (38),
        r6x64eq384Kbps  (39),
        r7x64eq448Kbps  (40),
        r8x64eq512Kbps  (41),
        r9x64eq576Kbps  (42),
        r10x64eq640Kbps (43),
        r11x64eq704Kbps (44),
        r12x64eq768Kbps (45),
        r13x64eq832Kbps (46),
        r14x64eq896Kbps (47),
        r15x64eq960Kbps (48),
        r16x64eq1024Kbps(49),
        r17x64eq1088Kbps(50),
        r18x64eq1152Kbps(51),
        r19x64eq1216Kbps(52),
        r20x64eq1280Kbps(53),
        r21x64eq1344Kbps(54),
        r22x64eq1408Kbps(55),
        r23x64eq1472Kbps(56),
        r24x64eq1536Kbps(57),
        r25x64eq1600Kbps(58),
        r26x64eq1664Kbps(59),
        r27x64eq1728Kbps(60),
        r28x64eq1792Kbps(61),
        r29x64eq1856Kbps(62),
        r30x64eq1920Kbps(63),
        r31x64eq1984Kbps(64),
        r32x64eq2048Kbps(65),

        r32x56eq1792Kbps(66),
        r64x64eq4096Kbps(67),

        auto           (200)
     }
      MAX-ACCESS  read-write
      STATUS  current
      DESCRIPTION
      "This object indicates the port rate (speed).
       auto - rate is selected automatically by system."
      ::= { prtHSParamEntry 4}

prtHSFifoSize OBJECT-TYPE
      SYNTAX  INTEGER {
   auto    (1),
   b32bit  (2),
   b60bit  (3),
   b104bit (4),
   b144bit (5),
   notApplicable (255)
   }
      MAX-ACCESS  read-write
      STATUS  current
      DESCRIPTION
   "This object selects the size of the user data channel buffer
    FIFO used in the DTE2 mode. In the other modes, buffer 
    size is automatically set by the DACS agent. 
    Buffer FIFO size in bits, corresponds to FIFO lengths of 
    +/-16, +/-30, +/-52, +/-72 bits."
      ::= { prtHSParamEntry 5}

prtHSClkMode OBJECT-TYPE
      SYNTAX  INTEGER {
   dce   (1),
   dte1  (2),
   dte2  (3),
   notApplicable (255)
   }
      MAX-ACCESS  read-write
      STATUS  current
      DESCRIPTION
   "Clock Mode of the user data channel. 
    dce - DACS operates as a DCE and provides transmit 
          and receive clocks to the synchronous user DTE.
    dte1- DACS supplies the receive clock to the user 
          equipment and accepts the user transmit clock.
    dte2- DACS requires transmit and receive clocks from 
          the user equipment."
      ::= { prtHSParamEntry 6}

prtHSCTS OBJECT-TYPE
      SYNTAX  INTEGER {
   on   (1),
   rts  (2),
   notApplicable (255)
   }
      MAX-ACCESS  read-write
      STATUS  current
      DESCRIPTION
    "Selection of CTS line state in the user data channel.
     on  - CTS continuously ON.
     rts - CTS line follows the RTS line."
      ::= { prtHSParamEntry 7}

prtHSRtsState OBJECT-TYPE
      SYNTAX  INTEGER {
   off   (2),
   on    (3),
   notApplicable (255)
   }
      MAX-ACCESS  read-only
      STATUS  current
      DESCRIPTION
      "RTS state of the port." 
      ::= { prtHSParamEntry 8}

prtHSInbandLoopback OBJECT-TYPE
      SYNTAX  INTEGER
       {
       notApplicable   (1),
       disabled        (2),
       enabled         (3)
       }
      MAX-ACCESS  read-write
      STATUS  current
      DESCRIPTION
      "This object indicates if Inband Loopback from the Network
       should be enabled or disabled."
      ::= {prtHSParamEntry 9}

prtHSInbandLoopPatternCfg OBJECT-TYPE
      SYNTAX  INTEGER
       {
       notApplicable   (1),
       rdlLoop         (2),
       userConfig      (3)
       }
      MAX-ACCESS  read-write
      STATUS  current
      DESCRIPTION
      "This object indicates if Inband Loop polynomial pattern
       will be according to RDL Loop (the standard) or User Configurated
       according to prtHSActivatePolyPattern and prtHSDeactivatePolyPattern."
      ::= {prtHSParamEntry 10}

prtHSInbandLoopActPattern OBJECT-TYPE
      SYNTAX DisplayString
      MAX-ACCESS read-write
      STATUS current
      DESCRIPTION
      "This object is a binary string of up to 8 bits.
	   Though the syntax allows for any ASCII characters, for this object
	   only '0' or '1' characters are valid.
       The string determines coefficients of the polynomial pattern
       sent to the port in order to Activate the Inband Loop.
       This object is relevant only when prtHSInbandLoopPatternCfg=userConfig."
      ::= {prtHSParamEntry 11}

prtHSInbandLoopDeactPattern OBJECT-TYPE
      SYNTAX DisplayString
      MAX-ACCESS read-write
      STATUS current
      DESCRIPTION
      "This object is a binary string of up to 8 bits.
	   Though the syntax allows for any ASCII characters, for this object
	   only '0' or '1' characters are valid.
       The string determines coefficients of the polynomial pattern
       sent to the port in order to Deactivate the Inband Loop.
       This object is relevant only when prtHSInbandLoopPatternCfg=userConfig."
      ::= {prtHSParamEntry 12}

prtHSDCD OBJECT-TYPE
      SYNTAX  INTEGER {
      notApplicable (1),
      linkOK  (2),
      on   (3)
      }
      MAX-ACCESS  read-write
      STATUS  current
      DESCRIPTION
      "Selection of DCD line state in the user data channel.
       linkOK - DCD line is ON only when active link is OK.
       on  - DCD continuously ON."
      ::= { prtHSParamEntry 13}

prtHSClkPolarity OBJECT-TYPE
      SYNTAX  INTEGER
       {
       notApplicable   (1),
       normal          (2),
       invert          (3)
       }
      MAX-ACCESS  read-write
      STATUS  current
      DESCRIPTION
      "This object indicates the clock polarity."
      ::= {prtHSParamEntry 14}

prtHSInterfaceType OBJECT-TYPE
      SYNTAX  INTEGER
       {
       notApplicable (1),
       rs530         (2), --EIA 530
       v35           (3),
	   rs422         (4),
	   x21           (5),
	   v24           (6),
	   rs530a        (7), --EIA 530A 
	   rs232		 (8),
	   rs449		 (9)
       }
      MAX-ACCESS  read-write
      STATUS  current
      DESCRIPTION
      "This object indicates the selected electrical interface type."
      ::= {prtHSParamEntry 15}

prtHSUnframed OBJECT-TYPE
      SYNTAX  INTEGER {
      notApplicable (1),
      no  (2),
      yes (3)
      }
      MAX-ACCESS  read-write
      STATUS  current
      DESCRIPTION
      "Unframed line for HS ports.
       yes - means that all TSs must be transferred, including TS0.
             In this case, prtHSRate must be r31x56eq1736Kbps OR 
             r31x64eq1984Kbps."
      ::= { prtHSParamEntry 16}



prtHSBertTable  OBJECT-TYPE
      SYNTAX SEQUENCE OF PrtHSBertEntry
      MAX-ACCESS not-accessible
      STATUS current
	DESCRIPTION  "A table."
	::=  { prtHS 2 }

prtHSBertEntry OBJECT-TYPE
      SYNTAX PrtHSBertEntry
      MAX-ACCESS not-accessible
      STATUS current
	DESCRIPTION  "An entry in table."
	INDEX { prtHSBertPrtIdx }
      ::= { prtHSBertTable 1}

PrtHSBertEntry ::=
     SEQUENCE {
  prtHSBertPrtIdx        Integer32,
  prtHSBertSlt           INTEGER,
  prtHSBertCountClr      INTEGER,
  prtHSBertTestResult    Integer32 
	}

prtHSBertPrtIdx OBJECT-TYPE
      SYNTAX  Integer32
      MAX-ACCESS  read-only
      STATUS  current
      DESCRIPTION
      "This attribute indicates a unique number to identify a port. 
       The valid port number depends on the IO slot no.,  the 
       installed card type and the port type: outside, inside, 
       SP.
    * The inside ports will be the HS cards ports. The 
      convention used will be (for DXC):
      - first two digits will be: (IO slot number+10)
         - last one/two digits will be the port number within the 
           card, in even numbers:
     port1 = 2
     port2 = 4
     port3 = 6 
     etc...
   Example: port2 of IO slot 11 will be: 214 ."
      ::= { prtHSBertEntry 1}

prtHSBertSlt  OBJECT-TYPE
      SYNTAX  INTEGER
       {
       io1   (5),
       io2   (6),
       io3   (7),
       io4   (8),
       io5   (9),
       io6  (10),
       io7  (11),
       io8  (12),
       io9  (13),
       io10 (14),
       io11 (15),
       io12 (16),
       io13 (17),
       io14 (18),
       io15 (19),
       standAlone (255)
       }
      MAX-ACCESS  read-only
      STATUS  current
      DESCRIPTION
      "This attribute indicates a unique number to identify the slot where
       the card is inserted in.
       When the unit is stand-alone, this object is not applicable
       and 255 will be used."
      ::= { prtHSBertEntry 2}


prtHSBertCountClr OBJECT-TYPE
      SYNTAX  INTEGER {
     off(2),
     on (3)
      }
      MAX-ACCESS  read-write
      STATUS  current
      DESCRIPTION
      "Setting this object (to on) initiate bert counter clear 
       operation.
       Valid only when bert test is active on the specific port.
       (Every time a new bert test starts, the counter is 
       automatically cleared; this command enables clearing 
       the counter while the test is running)."
      ::= { prtHSBertEntry 3}

prtHSBertTestResult   OBJECT-TYPE
      SYNTAX  Integer32
      MAX-ACCESS  read-only
      STATUS  current
      DESCRIPTION
      "This object indicates the number of Bit Error Rate indicated 
       during the BERT test.
       Active only when bert test is running on the selected port."
      ::= { prtHSBertEntry 4}



--prt SP specific configuration parameters

prtSpCnfgTable OBJECT-TYPE
      SYNTAX SEQUENCE OF PrtSpCnfgEntry
      MAX-ACCESS not-accessible
      STATUS current
    DESCRIPTION  "A table."
    ::=  {prtSP 1}

prtSpCnfgEntry OBJECT-TYPE
      SYNTAX PrtSpCnfgEntry
      MAX-ACCESS not-accessible
      STATUS current
      DESCRIPTION
      "All the entries at this table are identical(have the same value)
       at all the configurations(1..255) except at the TmpCnfg.
       - For products supporting more than one configuration, the write operation 
         into the Table Objects is valid only at the TmpCnfg entry.
       - For products that do not support configurations, the write operation 
         into the Table Objects will be to prtSpCnfgIdx=1."
      INDEX {prtSpCnfgIdx, prtSpPrtIdx }
      ::= { prtSpCnfgTable 1}

PrtSpCnfgEntry ::= SEQUENCE {
    prtSpCnfgIdx     Integer32,
    prtSpPrtIdx      Integer32,
   prtSpUsage       INTEGER,
   prtSpRate        INTEGER,
   prtSpDataBits    INTEGER,
   prtSpParity      INTEGER,
   prtSpCallOutMode INTEGER,
   prtSpInterface   INTEGER,
   prtSpCTS         INTEGER,
   prtSpDcdDelay    INTEGER,
   prtSpDsr         INTEGER,
   prtSpNoOfRetries Integer32,
   prtSpWaitForConnect INTEGER,
   prtSpDialMode    INTEGER,
   prtSpAltNumMode  INTEGER,
   prtSpPrimaryNum  DisplayString,
   prtSpAltNum      DisplayString,
   prtSpRoutProtocol INTEGER,
   prtSpCmd          OCTET STRING,
   prtSpActCallOut   INTEGER,
   prtSpAlrRelayMode INTEGER,
   prtSpStopBits     INTEGER
 }
       

prtSpCnfgIdx OBJECT-TYPE
      SYNTAX  Integer32 (1..255)
      MAX-ACCESS  read-only
      STATUS  current
      DESCRIPTION
      "This attribute indicates the Idx of the Cnfg(1..255) being 
       accessed.
       Idx of 255 relates to the TmpCnfg."
      ::= { prtSpCnfgEntry 1}

prtSpPrtIdx OBJECT-TYPE
      SYNTAX  Integer32
      MAX-ACCESS  read-only
      STATUS  current
      DESCRIPTION
      "This attribute indicates a unique port number of the SPor DP port.
       For DXC, it is the port in the active DCL card: 
       - SP = 1
       - NP ; DP = 2 
                
       For Kilomux, the port index is calculated as follows:
       100*Slot+Ch.
       
       For FCD, PRBi,  the SP port index=1.
       For Optimux-T3, the SP port index=71."
      ::= { prtSpCnfgEntry 2}

prtSpUsage OBJECT-TYPE
      SYNTAX  INTEGER
       {
  unknown (1),
  noUse   (2),
  nmsSlip (3),
  nmsPpp  (4),
  muxSlip (5),
  muxPpp  (6),
  terminal(7),
  dialOut (8)
       }
      MAX-ACCESS  read-write
      STATUS  current
      DESCRIPTION
      "This attribute indicates what is the usage of the port."
      ::= { prtSpCnfgEntry 3}

prtSpRate     OBJECT-TYPE
      SYNTAX  INTEGER
       {
        auto      (1),
        s300bps   (2),
        s1200bps  (3),
        s2400bps  (4),
        s4800bps  (5),
        s9600bps  (6),
        s19200bps (7),
        s38400bps (8),
        s57600bps (9),
        s115200bps(10)
       }
      MAX-ACCESS  read-write
      STATUS  current
      DESCRIPTION
      "This attribute indicates the operation rate (speed) of the port.
       auto - automatic rate selection, by the agent."
      ::= { prtSpCnfgEntry 4}

prtSpDataBits OBJECT-TYPE
      SYNTAX  INTEGER
       {
        dataBits7 (1),
        dataBits8 (2)
       }
      MAX-ACCESS  read-write
      STATUS  current
      DESCRIPTION
      "This attribute indicates the number of data bits in async 
       frame"
      ::= { prtSpCnfgEntry 5}

prtSpParity OBJECT-TYPE
      SYNTAX  INTEGER
       {
        none  (1),
        odd   (2),
        even  (3)
       }
      MAX-ACCESS  read-write
      STATUS  current
      DESCRIPTION
      "This attribute indicates the parity mode in async frame"
      ::= { prtSpCnfgEntry 6}

prtSpCallOutMode OBJECT-TYPE
      SYNTAX  INTEGER
       {
        notApplicable  (1),
        none           (2),
        all            (3),
        major          (4)
       }
      MAX-ACCESS  read-write
      STATUS  current
      DESCRIPTION
      "This attribute indicates the call-out mode.
       For DXC - this object is applicable only for the DP port (2)."
      ::= { prtSpCnfgEntry 7}


prtSpInterface OBJECT-TYPE
      SYNTAX  INTEGER
       {
          dce  (1),
          dte  (2)
       }
      MAX-ACCESS  read-write
      STATUS  current
      DESCRIPTION
      "This attribute indicates the supervisory port interface.
       dce - the DACS appears as a DCE for the port.
       dte - the DACS operates as a DTE, for connection via modem,
             for the port."
      ::= { prtSpCnfgEntry 8}

prtSpCTS OBJECT-TYPE
      SYNTAX  INTEGER
       {
          notApplicable (1),
          on            (2),
          rts           (3)
       }
      MAX-ACCESS  read-write
      STATUS  current
      DESCRIPTION
   "CTS line state. This object is applicable only for 
    port (1) = SP"
      ::= { prtSpCnfgEntry 9}

prtSpDcdDelay OBJECT-TYPE
      SYNTAX  INTEGER
       {
          notApplicable (1),
          d0   (2),
          d10  (3),
          d50  (4),
          d100 (5),
          d200 (6),
          d300 (7)
       }
      MAX-ACCESS  read-write
      STATUS  current
      DESCRIPTION
   "DCD delay in msec. 
    d10 = delay of 10msec.
    This object is applicable only for  port (1) = SP"
      ::= { prtSpCnfgEntry 10}

prtSpDsr OBJECT-TYPE
      SYNTAX  INTEGER
       {
          notApplicable (1),
          on   (2),
          dtr  (3)
       }
      MAX-ACCESS  read-write
      STATUS  current
      DESCRIPTION
   "DSR line state. This object is applicable only for 
    port (1) = SP"
      ::= { prtSpCnfgEntry 11}

prtSpNoOfRetries OBJECT-TYPE
      SYNTAX  Integer32  (0..8)
      MAX-ACCESS  read-write
      STATUS  current
      DESCRIPTION
   "For DXC - this object is applicable only for port (2) = DP.
    The number of dialing retries requested.
    Default = 0"
      ::= { prtSpCnfgEntry 12}

prtSpWaitForConnect OBJECT-TYPE
      SYNTAX  INTEGER
       {
          notApplicable (1),
          t30sec        (2),
          t45sec        (3), 
          t60sec        (4)
       }
      MAX-ACCESS  read-write
      STATUS  current
      DESCRIPTION
   "For DXC - this object is applicable only for port (2) = DP.
    Waiting time for connect, in seconds.
    Default = 30 sec."
      ::= { prtSpCnfgEntry 13}

prtSpDialMode OBJECT-TYPE
      SYNTAX  INTEGER
       {
          notApplicable (1),
          tone          (2),
          pulse         (3)
    }
      MAX-ACCESS  read-write
      STATUS  current
      DESCRIPTION
   "For DXC - this object is applicable only for port (2) = DP.
    Dialing mode.
    Default=tone"
      ::= { prtSpCnfgEntry 14}

prtSpAltNumMode OBJECT-TYPE
      SYNTAX  INTEGER
       {
          no  (2),
          yes (3)
       }
      MAX-ACCESS  read-write
      STATUS  current
      DESCRIPTION
   "For DXC - this object is applicable only for port (2) = DP.
    It determines wether to use the alternate number or not.
    Default = no."
      ::= { prtSpCnfgEntry 15}

prtSpPrimaryNum OBJECT-TYPE
      SYNTAX  DisplayString (SIZE(0..20))
      MAX-ACCESS  read-write
      STATUS  current
      DESCRIPTION
   "For DXC - this object is applicable only for port (2) = DP.
    It is the Primary dialing number. "
      ::= { prtSpCnfgEntry 16}

prtSpAltNum OBJECT-TYPE
      SYNTAX  DisplayString (SIZE(0..20))
      MAX-ACCESS  read-write
      STATUS  current
      DESCRIPTION
   "For DXC - this object is applicable only for port (2) = DP.
    It is the Alternate dialing number. This number 
    is applicable only if prtSpAltNumMode is 'yes'."
      ::= { prtSpCnfgEntry 17}

prtSpRoutProtocol     OBJECT-TYPE
      SYNTAX  INTEGER
       {
        notApplicable (1),
        none          (2),
        proprietary   (3),
        rip2          (4)
       }
      MAX-ACCESS  read-write
      STATUS  current
      DESCRIPTION
      "This attribute indicates the routing protocol of the port.
       notApplicable - for DP."
      ::= { prtSpCnfgEntry 18}

prtSpCmd     OBJECT-TYPE
      SYNTAX OCTET STRING  (SIZE (20))
      MAX-ACCESS  read-write
      STATUS  current
      DESCRIPTION
      "SP Command.
      For LRS this parameter will be used for a Modem Command. 
      Upon NMS's Get operation for devices that this parameter 
      is notApplicable, agent will send NULL string."
      ::= { prtSpCnfgEntry 19}

prtSpActCallOut     OBJECT-TYPE
      SYNTAX  INTEGER
       {
        notApplicable (1),
        always        (2),
        linkFail      (3)
       }
      MAX-ACCESS  read-write
      STATUS  current
      DESCRIPTION
      "This object indicates when to Activate Call-Out.
	   It is used by FCD-T1/E1.
       always - to activate call-out always.
       linkFail - to activate call-out only when Link of Inband Management fails."
      ::= { prtSpCnfgEntry 20}


prtSpAlrRelayMode OBJECT-TYPE
      SYNTAX  INTEGER
       {
  	    notApplicable (1),	
  		normal        (2),
        invert        (3)
       }
      MAX-ACCESS  read-write
      STATUS  current
      DESCRIPTION
      "This attribute indicates the Alarm Relay Mode.
       notApplicable - for DP."
      ::= { prtSpCnfgEntry 21}


prtSpStopBits OBJECT-TYPE
      SYNTAX  INTEGER
	      {
		notApplicable  (1),
        stopBits1      (2),
        stopBits1dot5  (3),
        stopBits2      (4)
	      }
      MAX-ACCESS  read-write
      STATUS  current
      DESCRIPTION
      "This attribute indicates number of stop bits in an async frame."
      ::= { prtSpCnfgEntry 22}





--prt DIM (DXC Inverse Multiplexer) specific parameters

prtDimCnfgTable OBJECT-TYPE
      SYNTAX SEQUENCE OF PrtDimCnfgEntry
      MAX-ACCESS not-accessible
      STATUS current
	DESCRIPTION  "A table."
	::=  {prtDim 1}

prtDimCnfgEntry OBJECT-TYPE
      SYNTAX PrtDimCnfgEntry
      MAX-ACCESS not-accessible
      STATUS current
      DESCRIPTION
      "The write operation into the Table Objects is valid only
       for the TmpCnfg entry (prtDimCnfgIdx=255)."
      INDEX {prtDimCnfgIdx, prtDimIdx }
      ::= { prtDimCnfgTable 1}

PrtDimCnfgEntry ::=
      SEQUENCE {
   prtDimCnfgIdx  Integer32,
   prtDimIdx      Integer32,
   prtDimTxMode   INTEGER,
   prtDimPolarity INTEGER,
   prtDimClkMode  INTEGER,
   prtDimMaxDelay INTEGER,
   prtDimMng      INTEGER,
   prtDimMngRoutProt INTEGER
   }      
       

prtDimCnfgIdx OBJECT-TYPE
      SYNTAX  Integer32 (1..255)
      MAX-ACCESS  read-only
      STATUS  current
      DESCRIPTION
      "This attribute indicates the Idx of the Cnfg(1..255) being 
       accessed.
       Idx of 255 relates to the TmpCnfg."
      ::= { prtDimCnfgEntry 1}

prtDimIdx OBJECT-TYPE
      SYNTAX  Integer32
      MAX-ACCESS  read-only
      STATUS  current
      DESCRIPTION
      "This attribute indicates a unique  port number of the
       DIM card. 
       The convention used for DXC:
       (IO slot number+10)*10 + 1
       Example: port1 of IO slot 11 will be: 211 ."
      ::= { prtDimCnfgEntry 2}


prtDimTxMode OBJECT-TYPE
      SYNTAX  INTEGER
       {
       regularTx   (2),
       broadcast   (3)
       }
      MAX-ACCESS  read-write
      STATUS  current
      DESCRIPTION
      "Tx mode.
       regularTx - the links are connected to a similar outfit on 
                   the other side. In this mode, if a link fails, 
                   the transmitted bandwidth is decreased 
                   accordingly.
       broadcast - the links are connected to MORE than one similar
                   outfit on the other side. In this mode, if a link 
                   fails, the transmitted bandwidth is not affected "
      ::= { prtDimCnfgEntry 3}

prtDimPolarity OBJECT-TYPE
      SYNTAX  INTEGER
       {
       normalClk (2),
       inverted  (3)
       }
      MAX-ACCESS  read-write
      STATUS  current
      DESCRIPTION
      "Polarity."
      ::= { prtDimCnfgEntry 4}

prtDimClkMode OBJECT-TYPE
      SYNTAX  INTEGER
       {
       extDce   (2),
       dce      (3),
	   smooth   (4),
	   extSmooth(5)
       }
      MAX-ACCESS  read-write
      STATUS  current
      DESCRIPTION
      "Clock Mode.
       smooth - a clock that is not 'pulsed'(has no 'gaps'). In this mode
	            the DXC does NOT receive back the clock signal.
       extSmooth - same as 'smooth' but in this mode, the DXC receives back
                the clock signal."
      ::= { prtDimCnfgEntry 5}

prtDimMaxDelay OBJECT-TYPE
      SYNTAX  INTEGER
       {
       t16msec (2),
       t64msec (3)
       }
      MAX-ACCESS  read-write
      STATUS  current
      DESCRIPTION
      "Max Delay permitted between the links, in msec."
      ::= { prtDimCnfgEntry 6}

prtDimMng OBJECT-TYPE
      SYNTAX  INTEGER
       {
       disabled   (2), --none
       ts1        (3), --dedicated
	   dedicatedFr(4) 
       }
      MAX-ACCESS  read-write
      STATUS  current
      DESCRIPTION
      "Use of DIM port for management.
       disabled - no management on DIM
       ts1      - 1 bit of TS1 is used for management."
      ::= { prtDimCnfgEntry 7}

prtDimMngRoutProt  OBJECT-TYPE
      SYNTAX  INTEGER
       {
       notApplicable (1),
       none          (2),  
       proprietary   (3)
       }
      MAX-ACCESS  read-write
      STATUS  current
      DESCRIPTION
      "Mng Routing Protocol of the port.
       none - when prtDimMng is 'disabled'."             
      ::= { prtDimCnfgEntry 8}


prtDimDestTable OBJECT-TYPE
      SYNTAX SEQUENCE OF PrtDimDestEntry
      MAX-ACCESS not-accessible
      STATUS current
	DESCRIPTION  "A table."
	::=  {prtDim 2}

prtDimDestEntry OBJECT-TYPE
      SYNTAX PrtDimDestEntry
      MAX-ACCESS not-accessible
      STATUS current
      DESCRIPTION
      "The write operation is valid only for the TmpCnfg entry 
       (prtDimDestCnfgIdx=255)."
      INDEX {prtDestCnfgIdx, prtDestDimIdx, prtDestIdx }
      ::= { prtDimDestTable 1}

PrtDimDestEntry ::=
      SEQUENCE {
   prtDestCnfgIdx Integer32,
   prtDestDimIdx  Integer32,
   prtDestIdx     Integer32,
   prtDest        Integer32,
   prtDestConnect INTEGER
   }      
       

prtDestCnfgIdx OBJECT-TYPE
      SYNTAX  Integer32 (1..255)
      MAX-ACCESS  read-only
      STATUS  current
      DESCRIPTION
      "This attribute indicates the Idx of the Cnfg(1..255) being 
       accessed.
       Idx of 255 relates to the TmpCnfg."
      ::= { prtDimDestEntry 1}

prtDestDimIdx OBJECT-TYPE
      SYNTAX  Integer32
      MAX-ACCESS  read-only
      STATUS  current
      DESCRIPTION
      "This attribute indicates a unique  port number of the
       DIM card. 
       The convention used for DXC:
       (IO slot number+10) & 1
       Example: port1 of IO slot 11 will be: 211 ."
      ::= { prtDimDestEntry 2}

prtDestIdx OBJECT-TYPE
      SYNTAX  Integer32 (1..8)
      MAX-ACCESS  read-only
      STATUS  current
      DESCRIPTION
      "This attribute indicates a destination number of the
       DIM card. "
      ::= { prtDimDestEntry 3}


prtDest OBJECT-TYPE
      SYNTAX  Integer32
      MAX-ACCESS  read-write
      STATUS  current
      DESCRIPTION
      "Destination port,(of a T1/E1 port), that is connected to the 
    DIM card, for the specified Destination number.
    0 = No destination port.
    Else:
	For external ports:
    (IO Slot+10) & 1    for port 1 
    (IO Slot+10) & 3    for port 2 
       Example: port2 of IO slot 12 will be: 223 .
    For internal ports :
    (IO Slot+10) & 2    for port 1
    (IO Slot+10) & 4    for port 2
    (IO Slot+10) & 6    for port 3
    (IO Slot+10) & 8    for port 4, etc..."
      ::= { prtDimDestEntry 4}

prtDestConnect OBJECT-TYPE
      SYNTAX  INTEGER
       {
       no (2),
       yes(3)
       }
      MAX-ACCESS  read-only
      STATUS  current
      DESCRIPTION
      "Connection Status of the specified destination number.
    For a specified destination port, it depends both on the 
    status of the port and on the status of the far-end port.
    Since this is a RO object, same value will be received for
    all configurations."
      ::= { prtDimDestEntry 5}


--prtI - ISDN specific parameters table

prtICnfgTable  OBJECT-TYPE
      SYNTAX SEQUENCE OF PrtICnfgEntry
      MAX-ACCESS not-accessible
      STATUS current
	DESCRIPTION  "A table."
	::=  { prtI 1 }

prtICnfgEntry OBJECT-TYPE
      SYNTAX PrtICnfgEntry
      MAX-ACCESS not-accessible
      STATUS current
	DESCRIPTION  "An entry in table."
	INDEX { prtICnfgIdx, prtIIdx }
      ::= { prtICnfgTable 1}

PrtICnfgEntry ::=
      SEQUENCE {
      prtICnfgIdx  Integer32,
      prtIIdx      Integer32,
      prtIRate     INTEGER,
      prtIConnect  INTEGER
      }    

   
prtICnfgIdx OBJECT-TYPE
      SYNTAX  Integer32 (1..255)
      MAX-ACCESS  read-only
      STATUS  current
      DESCRIPTION
      "This attribute indicates the Idx of the Config being accessed.
       Idx of 255 relates to the Temporary (Scratch) Config. "
      ::= {prtICnfgEntry 1}

prtIIdx OBJECT-TYPE
      SYNTAX  Integer32
      MAX-ACCESS  read-only
      STATUS  current
      DESCRIPTION
      "This attribute indicates a unique number to identify a port. 
       The valid port number depends on the IO slot no.,  the 
       installed card type and the port type: outside, inside, 
       SP.
    * The ISDN B1, B2, D channels will be inside ports. 
      For port index, see product specification."
      ::= {prtICnfgEntry 2}

prtIRate     OBJECT-TYPE
      SYNTAX  INTEGER {
        notApplicable (1),
        nc            (2),
        r2bit         (3),
        r4bit         (4),
        r8bit         (5)
        }
      MAX-ACCESS  read-write
      STATUS  current
      DESCRIPTION
      "This object indicates the port rate in bits.
       Each TS contains 8 bits. Thus, 1 bit is equivalent to 8Kbps
       rate."
      ::= {prtICnfgEntry 3}

prtIConnect     OBJECT-TYPE
      SYNTAX  INTEGER {
        notApplicable (1),
        no            (2),
        yes           (3)
        }
      MAX-ACCESS  read-write
      STATUS  current
      DESCRIPTION
      "D channel connection.
       no  - disconnected
       yes - connected. "
      ::= {prtICnfgEntry 4}


--prtHdsl - HDSL specific parameters table

prtHdslTable  OBJECT-TYPE
      SYNTAX SEQUENCE OF PrtHdslEntry
      MAX-ACCESS not-accessible
      STATUS current
	  DESCRIPTION  "HDSL port table."
	::=  { prtHdsl 1 }

prtHdslEntry OBJECT-TYPE
      SYNTAX PrtHdslEntry
      MAX-ACCESS not-accessible
      STATUS current
	  DESCRIPTION  "An entry in table."
	  INDEX { prtHdslIdx }
      ::= { prtHdslTable 1}

PrtHdslEntry ::=
      SEQUENCE {
      prtHdslIdx       Integer32,
      prtHdslMode      INTEGER,
      prtHdslRptrType  INTEGER,
	  prtHdslMaxRate   INTEGER,
	  prtHdslLinkType  INTEGER,
	  prtHdslCompSwVer DisplayString,
	  prtHdslCompHwVer DisplayString
      }    
   
prtHdslIdx OBJECT-TYPE
      SYNTAX  Integer32
      MAX-ACCESS  read-only
      STATUS  current
      DESCRIPTION
      "This attribute indicates a unique number to identify a port. 
       The valid port number depends on the IO slot no.,  the 
       installed card type and the port type: outside, inside.
    * The HDSL ports will be external. 
      For port index, see product specification."
      ::= {prtHdslEntry 1}

prtHdslMode   OBJECT-TYPE
      SYNTAX  INTEGER {
        notApplicable (1),
        central       (2),
        remote        (3)
        }
      MAX-ACCESS  read-write
      STATUS  current
      DESCRIPTION
      "This object indicates the HDSL mode."
      ::= {prtHdslEntry 2}

prtHdslRptrType     OBJECT-TYPE
      SYNTAX  INTEGER {
      notApplicable (1),
      none    (2), 
      hrpt    (3)
        }
      MAX-ACCESS  read-only
      STATUS  current
      DESCRIPTION
      "The Repeater between Near and Far modem.
       none - no repeater exists between the modems
       hrpt - HRPT repeater exists between the modems."
      ::= {prtHdslEntry 3}

prtHdslMaxRate     OBJECT-TYPE
      SYNTAX  INTEGER {
      notApplicable (1),
      r192          (2), 
      r256          (3),
	  r320          (4),
	  r384          (5),
      r448          (6), 
      r512          (7),
	  r576          (8),
	  r640          (9),
      r768          (10), 
      r896          (11),
	  r1024         (12),
	  r1152         (13),
      r1280         (14), 
      r1536         (15),
	  r1920         (16),
	  r2048         (17)
        }
      MAX-ACCESS  read-write
      STATUS  current
      DESCRIPTION
      "Maximum Rate of the xDSL Line, in Kbps units.
       This object can be Set only for a Central unit."
      ::= {prtHdslEntry 4}

prtHdslLinkType     OBJECT-TYPE
      SYNTAX  INTEGER {
      notApplicable (1),
      msdsl2w       (2), 
      hdsl2w        (3),
	  hdsl4w        (4),
	  gDsl          (5)
        }
      MAX-ACCESS  read-only
      STATUS  current
      DESCRIPTION
      "The Link Type.
       msdsl2w - MSDSL 2 Wire
       hdsl2w  - HDSL  2 Wire
       hdsl4w  - HDSL  4 Wire
       gDsl    - G.DSL "
      ::= {prtHdslEntry 5}

prtHdslCompSwVer OBJECT-TYPE
      SYNTAX  DisplayString (SIZE (0..255))
      MAX-ACCESS  read-only
      STATUS  current
      DESCRIPTION
      "This object indicates the Software Version of the 
       component (Piggyback card) supporting this interface."
      ::= {prtHdslEntry 6}

prtHdslCompHwVer OBJECT-TYPE
      SYNTAX  DisplayString (SIZE (0..255))
      MAX-ACCESS  read-only
      STATUS  current
      DESCRIPTION
      "This object indicates the Hardware Version of the 
       component (Piggyback card) supporting this interface."
      ::= {prtHdslEntry 7}


--DACS T3/E3 port configuration parameters. Applicable also for Optimux-T3 Links.
--
--These objects were entered in this private MIB, because they do not 
--appear in RFC1407 (except prtT3E3LineLength which appears in meters) and in
--RFC-1407 MIB there is no reference to configuration number.


prtT3E3CnfgTable OBJECT-TYPE
  SYNTAX  SEQUENCE OF PrtT3E3CnfgEntry
  MAX-ACCESS  not-accessible
  STATUS  current
  DESCRIPTION
  "T3/E3 port configuration table."
  ::= { prtT3E3 1}

prtT3E3CnfgEntry   OBJECT-TYPE
  SYNTAX  PrtT3E3CnfgEntry
  MAX-ACCESS  not-accessible
  STATUS  current
  DESCRIPTION
  " An entry in the T3/E3 port configuration table."
  INDEX { prtT3E3CnfgIdx, prtT3E3PrtIdx }
  ::= { prtT3E3CnfgTable 1}

PrtT3E3CnfgEntry ::=
     SEQUENCE {
  prtT3E3CnfgIdx
  Integer32,
  prtT3E3PrtIdx
  Integer32,
  prtT3E3Slt
  INTEGER,
  prtT3E3LineLength
  INTEGER,
  prtT3E3InbandMng
  INTEGER,
  prtT3E3AisFrame
  INTEGER,
  prtT3E3TxClockSource
  INTEGER,
  prtT3E3RoutProt
  INTEGER,
  prtT3E3AisTransmit
  INTEGER
  }
 
prtT3E3CnfgIdx OBJECT-TYPE
      SYNTAX  Integer32 (1..255)
      MAX-ACCESS  read-only
      STATUS  current
      DESCRIPTION
      "This attribute indicates the Idx of the Config being accessed.
       Idx of 255 relates to the Temporary (Scratch) Config.
       For DXC, write operations can be performed only on the Temp Config.
       For products that do not support configurations, always 1 will be used."
      ::= { prtT3E3CnfgEntry 1}

prtT3E3PrtIdx OBJECT-TYPE
      SYNTAX  Integer32
      MAX-ACCESS  read-only
      STATUS  current
      DESCRIPTION
      "This attribute indicates a unique  port number.
	   For DXC:
          The same numbering as for prtGenPrtIdx.
          The valid port number depends on the IO slot no.,  the 
          installed card type and the port type: outside, inside. 
          * The external ports convention used will be (for DXC):
           - first two digits will be: (IO slot number+10)
           - last one/two digits will be the port number within the 
               card, in odd numbers:
               port1 = 1
               port2 = 3
               port3 = 5 
               etc...
               Example: port2 of IO slot 11 will be: 213 .
       For Optimux-T3:
          Link-A: 51 
          Link-B: 61 . "
      ::= { prtT3E3CnfgEntry 2}

prtT3E3Slt     OBJECT-TYPE
      SYNTAX  INTEGER
       {
       clA   (3),
       clB   (4),
       io1   (5),
       io2   (6),
       io3   (7),
       io4   (8),
       io5   (9),
       io6  (10),
       io7  (11),
       io8  (12),
       io9  (13),
       io10 (14),
       io11 (15),
       io12 (16),
       io13 (17),
       io14 (18),
       io15 (19),
       standAlone (255)
       }
      MAX-ACCESS  read-only
      STATUS  current
      DESCRIPTION
      "This attribute indicates a unique number to identify the slot where
       the card is inserted in.
       When the unit is stand-alone, this object is not applicable
       and 255 will be used."
      ::= { prtT3E3CnfgEntry 3}

prtT3E3LineLength  OBJECT-TYPE
      SYNTAX  INTEGER
       {
        notApplicable(1),
        len0p450ft   (2),
        len451p900ft (3)
       }
      MAX-ACCESS  read-write
      STATUS  current
      DESCRIPTION
      "This object is the length of the ds3 line in feet.  
       It provides information for line build out circuitry if it exists 
       and can use this object to adjust the line build out. 
       len0p450ft   = 0   - 450 feet
       len451p900ft = 451 - 900 feet."
   ::= { prtT3E3CnfgEntry 4}

prtT3E3InbandMng  OBJECT-TYPE
      SYNTAX  INTEGER
       {
          notApplicable(1),
          off          (2),
          cBit         (3), --Cbit-Tx-Rx
          cBitTxRxMng  (4),
          cBitTx       (5),
          cBitTxMng    (6),
          m13          (7),
          cdpv		   (8),
          nationalBit  (9) 
       }
      MAX-ACCESS  read-write
      STATUS  current
      DESCRIPTION
      "A unique number to identify the Frame Type over the link.
       For Optimux-T3: only values (4), (7) are supported."
      ::= {prtT3E3CnfgEntry 5}

prtT3E3AisFrame  OBJECT-TYPE
      SYNTAX  INTEGER
       {
        notApplicable(1),
        unframed     (2),
        framed       (3)
       }
      MAX-ACCESS  read-write
      STATUS  current
      DESCRIPTION
      "This object is applicable only for Optimux-T3.  
       It allows user to select whether the AIS sent will be framed or unframed."
   ::= { prtT3E3CnfgEntry 6}

prtT3E3TxClockSource  OBJECT-TYPE
      SYNTAX  INTEGER
       {
        external(1),  -- loopTiming
        internal(2),  -- localTiming
        notApplicable(255)
       }
      MAX-ACCESS  read-write
      STATUS  current
      DESCRIPTION
      "Tx Clock Source."
   ::= { prtT3E3CnfgEntry 7}

prtT3E3RoutProt  OBJECT-TYPE
      SYNTAX  INTEGER
       {
        notApplicable (1),
        none          (2),  
        proprietary   (3),
        rip2          (4)
       }
      MAX-ACCESS  read-write
      STATUS  current
      DESCRIPTION
      "Routing Protocol of the port.
       This object is applicable only for T3 ports."             
      ::= { prtT3E3CnfgEntry 8}

  prtT3E3AisTransmit  OBJECT-TYPE
      SYNTAX  INTEGER
       {
        notApplicable (1),
        disable       (2),  
        enable        (3)        
       }
      MAX-ACCESS  read-write
      STATUS  current
      DESCRIPTION
      "Indicates if AIS signal will be transmitted over the tributary E3/DS3
       upon failure."             
      ::= { prtT3E3CnfgEntry 9}


--DACS General data, unrelated to a specific level or unit type

--Compressed data table - applicable for all the MIB leafs,
--Used only by NMS station

cmprTable  OBJECT-TYPE
      SYNTAX SEQUENCE OF CmprEntry
      MAX-ACCESS not-accessible
      STATUS current
	DESCRIPTION  "A table."
	::=  { genDacsMux 1 }

cmprEntry OBJECT-TYPE
      SYNTAX CmprEntry
      MAX-ACCESS not-accessible
      STATUS current
	DESCRIPTION  "An entry in table."
	INDEX {cmprTypeIdx, cmprCnfgIdx,cmprVersion,cmprSltIdx,cmprPrtIdx}
      ::= {cmprTable  1}

CmprEntry ::=
      SEQUENCE {
  cmprTypeIdx      Integer32,
  cmprCnfgIdx      Integer32,
  cmprVersion      Integer32,
  cmprSltIdx       INTEGER,
  cmprPrtIdx       Integer32,
  cmprObj          OCTET STRING
      }

cmprTypeIdx OBJECT-TYPE
      SYNTAX  Integer32
      MAX-ACCESS  read-only
      STATUS  current
      DESCRIPTION
      "This object indicates the Type of the Compressed 
       data referred (which table, which level, etc).
       The type is a code according to a convention between
       agent and NMS."
      ::= { cmprEntry 1}

cmprCnfgIdx OBJECT-TYPE
      SYNTAX  Integer32
      MAX-ACCESS  read-only
      STATUS  current
      DESCRIPTION
      "This object indicates the configuration number the
       Compressed information relates to."
      ::= { cmprEntry 2}

cmprVersion OBJECT-TYPE
      SYNTAX  Integer32
      MAX-ACCESS  read-only
      STATUS  current
      DESCRIPTION
      "This object indicates the version of the internal format of
       the Compressed data (the version of the convention used)."
      ::= { cmprEntry 3}

cmprSltIdx  OBJECT-TYPE
     SYNTAX  INTEGER
         {
         psA   (1),
         psB   (2),
         clA   (3),
         clB   (4),
         io1   (5),
         io2   (6),
         io3   (7),
         io4   (8),
         io5   (9),
         io6  (10),
         io7  (11),
         io8  (12),
         io9  (13),
         io10 (14),
         io11 (15),
         io12 (16),
         io13 (17),
         io14 (18),
         io15 (19),
         notApplicable (255)
         }
     MAX-ACCESS  read-only
     STATUS  current
     DESCRIPTION
     "This attribute indicates a unique number of  the slot  
      position where the card is inserted.
      When the unit is stand-alone or this object is not applicable,
      255 will be used."
     ::= { cmprEntry 4}


cmprPrtIdx  OBJECT-TYPE
      SYNTAX  Integer32
      MAX-ACCESS  read-only
      STATUS  current
      DESCRIPTION
      "This object indicates a unique identifier of the port,
       the compressed information relates to.
    For DXC - according to the order in the card of cmprSltIdx:
      - first two digits will be: (IO slot number+10)
      - last one/two digits will be the port number within the 
        card in odd or even numbers, as follows:
      * For the outside/external ports, in odd numbers:
        port1 = 1
        port2 = 3
        port3 = 5 
        etc...
        Example: port2 of IO slot 11 will be: 213 .
      * The inside/internal ports, in even numbers:
        port1 = 2
        port2 = 4
        port3 = 6 
        etc...
        Example: port2 of IO slot 11 will be: 214 .
    For FCD: see product's specification.
       If the port number is irrelevant to this parameter (if it is
       a system/card level alarm) the value will be 9999."
      ::= { cmprEntry 5}

cmprObj OBJECT-TYPE
      SYNTAX  OCTET STRING
      MAX-ACCESS  read-write
      STATUS  current
      DESCRIPTION
      "This object is the compressed information itself, 
       according to a predefined format, both agent and NMS agreed
       about."
      ::= { cmprEntry 6}


--mapLinkTable

mapLinkTable OBJECT-TYPE
      SYNTAX SEQUENCE OF MapLinkEntry
      MAX-ACCESS not-accessible
      STATUS current
	DESCRIPTION  "A table."
	::=  { genDacsMux 2}

mapLinkEntry OBJECT-TYPE
      SYNTAX MapLinkEntry
      MAX-ACCESS not-accessible
      STATUS current
	DESCRIPTION  "An entry in table."
	INDEX {mapLinkIdx}
      ::= {mapLinkTable 1}

MapLinkEntry ::=
      SEQUENCE {
      mapLinkIdx               Integer32,
      mapLinkSlotIdx           INTEGER,
      mapLinkPortIdx           Integer32,
      mapLinkState             INTEGER
      }

mapLinkIdx     OBJECT-TYPE
      SYNTAX  Integer32
      MAX-ACCESS  read-only
      STATUS  current
      DESCRIPTION
      "A unique identifier of the link"
::=  {mapLinkEntry 1}

mapLinkSlotIdx    OBJECT-TYPE
      SYNTAX  INTEGER
        {
         io1   (5),
         io2   (6),
         io3   (7),
         io4   (8),
         io5   (9),
         io6  (10),
         io7  (11),
         io8  (12),
         io9  (13),
         io10 (14),
         io11 (15),
         io12 (16),
         io13 (17),
         io14 (18),
         io15 (19),
         standAlone (255)
     }
      MAX-ACCESS  read-write
      STATUS  current
      DESCRIPTION
      "This attribute indicates a unique  slot  position where
       the module is inserted."       
::=  {mapLinkEntry 2}

mapLinkPortIdx  OBJECT-TYPE
      SYNTAX  Integer32
      MAX-ACCESS  read-write
      STATUS  current
      DESCRIPTION
      "This attribute indicates a unique  port number.
       The valid port number depends on the IO slot no.,  the 
       installed card type and the port type: outside, inside, 
       SP.
       In the DXC :
      - first two digits will be: (IO slot number+10)
      - last one/two digits will be the port number within the 
        card in odd or even numbers, as follows:
      * For the outside/external ports, in odd numbers:
        port1 = 1
        port2 = 3
        port3 = 5 
        etc...
        Example: port2 of IO slot 11 will be: 213 .
      * The inside/internal ports, in even numbers:
        port1 = 2
        port2 = 4
        port3 = 6 
        etc...
        Example: port2 of IO slot 11 will be: 214 ."
::=  {mapLinkEntry 3}

mapLinkState   OBJECT-TYPE
      SYNTAX  INTEGER
 {
 unknown(1),
 down(2),
 up(3)
 }
      MAX-ACCESS  read-only
      STATUS  current
      DESCRIPTION
      "This attribute indicates the status of the link between 
       the two muxes"
::=  {mapLinkEntry 4}

 
--Alarms List - 
--              
--              

alrGenTable  OBJECT-TYPE
      SYNTAX SEQUENCE OF AlrGenEntry
      MAX-ACCESS not-accessible
      STATUS current
	DESCRIPTION  "A table."
	::=  { genDacsMux 3 }

alrGenEntry OBJECT-TYPE
      SYNTAX AlrGenEntry
      MAX-ACCESS not-accessible
      STATUS current
	DESCRIPTION  "An entry in table."
	INDEX { alrGenCode }
      ::= { alrGenTable 1}

AlrGenEntry ::=
      SEQUENCE {
     alrGenCode          Integer32,
     alrGenDescription  DisplayString,
     alrGenLevel         INTEGER,
	 alrGenSlotType      INTEGER,
	 alrGenSeverity      INTEGER,
	 alrGenDebounce      Integer32,
	 alrGenDefSeverity   INTEGER
      }

alrGenCode OBJECT-TYPE
      SYNTAX  Integer32
      MAX-ACCESS  read-only
      STATUS  current
      DESCRIPTION
      "This object is a unique code number, identifying 
       a certain alarm."
    ::= { alrGenEntry 1}

alrGenDescription  OBJECT-TYPE
      SYNTAX  DisplayString (SIZE (0..255))
      MAX-ACCESS  read-only
      STATUS  current
      DESCRIPTION
      "This entry is a unique text description, of the alarm 
       corresponding to the specified code."
       ::= { alrGenEntry 2}
       
alrGenLevel   OBJECT-TYPE
      SYNTAX  INTEGER
      {
       notApplicable(1),
       system       (2),
       card         (3),
       port         (4)
      }
      MAX-ACCESS  read-only
      STATUS  current
      DESCRIPTION
      "Alarm level."
      ::=  {alrGenEntry 3}

alrGenSlotType   OBJECT-TYPE
      SYNTAX  INTEGER
      {
       notApplicable(1),
       ps           (2),
       cl           (3),
       io           (4),
	   clAndIo      (5)
      }
      MAX-ACCESS  read-only
      STATUS  current
      DESCRIPTION
      "Slot type that the alarm is relevant to.
       clAndIo - an alarm that is relevant for both CL and IO slots."
      ::=  {alrGenEntry 4}

alrGenSeverity   OBJECT-TYPE
      SYNTAX  INTEGER
      {
       notApplicable (1),
       event    (3),
       minor    (4),
       major    (5),
       warning  (6),
       critical (7)
       }
      MAX-ACCESS  read-write
      STATUS  current
      DESCRIPTION
      "This object enables the user to select a severity for each alarm.
       The severity is set per alarm code (same for all slots/ports
       using this code)."
      ::=  {alrGenEntry 5}

alrGenDebounce   OBJECT-TYPE
      SYNTAX  Integer32 (0..255)
      MAX-ACCESS  read-write
      STATUS  current
      DESCRIPTION
      "Debounce time for each alarm code, in seconds.
       The meaning is, that an alarm will be 'declared' as ON (or OFF), only 
       after it was actually ON/OFF the Debouncing time selected by user.
       0 = default debounce selection (each alarm has a default value).
	   250 = maximum value of seconds for debounce.
	   253 = mask = the alarm will Never be reported.
	   254 = default debounce selection (each alarm has a default value).
	   255 = not applicable "
      ::=  {alrGenEntry 6}

alrGenDefSeverity OBJECT-TYPE
      SYNTAX  INTEGER
       {
      notApplicable (1),
      event    (3),
      minor    (4),
      major    (5),
	  warning  (6),
	  critical (7)
       }
      MAX-ACCESS  read-only
      STATUS  current
      DESCRIPTION
      "This object reports the default severity of each alarm.
       User can change the  severity of the alarms defined by
       this default via the alrGenSeverity object."
      ::= {alrGenEntry 7}

------------------------------------------
-- Card/ Module  Common Trap Definitions
--------------------------------------------
        
        
cardEvents  OBJECT IDENTIFIER ::= {mdlGen 0}


--CARD HW FAILURE
cardHwFailure   NOTIFICATION-TYPE
	OBJECTS { alarmEventLogSourceName, alarmEventLogAlarmOrEventId, alarmEventLogDescription, 
     alarmEventLogSeverity, alarmEventLogDateAndTime, alarmEventReason, 
     entPhysicalAlias, mdlCActualCardType, mdlCHardwareFailureReason } 
      STATUS  current
      DESCRIPTION
      "This trap indicates HW failure in card indicated by mdlCActualCardType
      " 
      ::= { cardEvents   1 }

--CARD MISMATCH
cardMismatch       NOTIFICATION-TYPE
	OBJECTS { alarmEventLogSourceName, alarmEventLogAlarmOrEventId, alarmEventLogDescription, 
     alarmEventLogSeverity, alarmEventLogDateAndTime, alarmEventReason, 
     entPhysicalAlias, mdlCActualCardType, mdlCProgCardType } 
      STATUS  current
      DESCRIPTION
      "This trap indicates that Card indicated by mdlCProgCardType 
      is incompatible with active DB 
      " 
      ::= { cardEvents   2 }

--CARD PROVISION FAILURE
cardProvisionFailure       NOTIFICATION-TYPE
	OBJECTS { alarmEventLogSourceName, alarmEventLogAlarmOrEventId, alarmEventLogDescription, 
     alarmEventLogSeverity, alarmEventLogDateAndTime, alarmEventReason, 
     entPhysicalAlias, mdlCActualCardType } 
      STATUS  current
      DESCRIPTION
      "This trap indicates Provisioning failure of card indicated by 
      mdlCActualCardType due to reason indicated by alarmEventReason
      " 
      ::= { cardEvents   3 }

--CARD UNSUPPORTED SW
cardUnsupportedSw   NOTIFICATION-TYPE
	OBJECTS { alarmEventLogSourceName, alarmEventLogAlarmOrEventId, alarmEventLogDescription, 
     alarmEventLogSeverity, alarmEventLogDateAndTime, alarmEventReason, 
     entPhysicalAlias, mdlCActualCardType, entPhysicalSoftwareRev } 
      STATUS  current
      DESCRIPTION
      "This trap indicates that Module software is not supported 
      " 
      ::= { cardEvents   4 }


--CARD UNSUPPORTED HW
cardUnsupportedHw      NOTIFICATION-TYPE
	OBJECTS { alarmEventLogSourceName, alarmEventLogAlarmOrEventId, alarmEventLogDescription, 
     alarmEventLogSeverity, alarmEventLogDateAndTime, alarmEventReason, 
     entPhysicalAlias, mdlCActualCardType, entPhysicalHardwareRev } 
      STATUS  current
      DESCRIPTION
      "This trap indicates that Module hardware is not supported 
      " 
      ::= { cardEvents   5 }

--CARD IMPROPER REMOVAL
cardImproperRemoval    NOTIFICATION-TYPE
	OBJECTS { alarmEventLogSourceName, alarmEventLogAlarmOrEventId, alarmEventLogDescription, 
     alarmEventLogSeverity, alarmEventLogDateAndTime, alarmEventReason, 
     entPhysicalAlias, mdlCProgCardType } 
      STATUS  current
      DESCRIPTION
      "This trap indicates Improper card removal 
      " 
      ::= { cardEvents   6 }

--CARD NO RESPONSE

cardNoResponse     NOTIFICATION-TYPE
	OBJECTS { alarmEventLogSourceName, alarmEventLogAlarmOrEventId, alarmEventLogDescription, 
     alarmEventLogSeverity, alarmEventLogDateAndTime, alarmEventReason, 
     entPhysicalAlias, mdlCProgCardType } 
      STATUS  current
      DESCRIPTION
      "This trap indicates Loss of communication with card
      " 
      ::= { cardEvents   8 }


--CARD INIT FAILURE
cardInitFailure    NOTIFICATION-TYPE
	OBJECTS { alarmEventLogSourceName, alarmEventLogAlarmOrEventId, alarmEventLogDescription, 
     alarmEventLogSeverity, alarmEventLogDateAndTime, alarmEventReason, 
     entPhysicalAlias, mdlCActualCardType } 
      STATUS  current
      DESCRIPTION
      "This trap indicates that Software download to card indiacted by 
      mdlCActualCardType failed
      "
      ::= { cardEvents   9 }

--CARD RESET
cardReset      NOTIFICATION-TYPE
	OBJECTS { alarmEventLogSourceName, alarmEventLogAlarmOrEventId, alarmEventLogDescription, 
     alarmEventLogSeverity, alarmEventLogDateAndTime, alarmEventReason, 
     entPhysicalAlias, mdlCActualCardType } 
      STATUS  current
      DESCRIPTION
      "This trap indicates Card  (mdlCActualCardType) Reset 
      " 
      ::= { cardEvents   10 }

--CARD PLUGGED IN
cardPluggedIn      NOTIFICATION-TYPE
	OBJECTS { alarmEventLogSourceName, alarmEventLogAlarmOrEventId, alarmEventLogDescription, 
     alarmEventLogSeverity, alarmEventLogDateAndTime, alarmEventReason, 
     entPhysicalAlias, mdlCActualCardType } 
      STATUS  current
      DESCRIPTION
      "This trap indicates that  card (indicated by mdlCActualCardType) was
       inserted to slot 
      " 
      ::= { cardEvents   11 }

--CARD PLUGGED OUT

cardPluggedOut        NOTIFICATION-TYPE
	OBJECTS { alarmEventLogSourceName, alarmEventLogAlarmOrEventId, alarmEventLogDescription, 
     alarmEventLogSeverity, alarmEventLogDateAndTime, alarmEventReason, 
     entPhysicalAlias, mdlCProgCardType } 
      STATUS  current
      DESCRIPTION
      "This trap indicates that card (indicated by mdlCProgCardType ) 
      was removed from slot 
      " 
      ::= { cardEvents   12 }

--CARD CONFIGURATION MISMATCH
cardConfigurationMismatch    NOTIFICATION-TYPE
	OBJECTS { alarmEventLogSourceName, alarmEventLogAlarmOrEventId, alarmEventLogDescription, 
     alarmEventLogSeverity, alarmEventLogDateAndTime, alarmEventReason, 
     entPhysicalAlias, mdlCActualCardType, mdlCConfigMismatchReason } 
      STATUS  current
      DESCRIPTION
      "This trap indicates a mismatch in the card configuration."
      ::= { cardEvents   14 }


     dacsMuxEvents OBJECT-IDENTITY
	    STATUS  current
	    DESCRIPTION
	    "The events for DACS MUX."
	    ::= { dacsMux 0 }

     sanityCheckTrap  NOTIFICATION-TYPE
        OBJECTS { sysSSanityCheckStatus, sysDbaseDownloadCnfgIdxCmd }
        STATUS current
        DESCRIPTION     
        "This trap is sent after a data base download attempt. 
         It returns the sanity result status and the configuration
         no.checked."
        ::= { dacsMuxEvents 1 }

     dacsMuxAlarmsTrap  NOTIFICATION-TYPE
       STATUS current
       DESCRIPTION     
       "This trap is sent when an alarm occurs."
       ::= { dacsMuxEvents 2 }

     mdlConnectTrap  NOTIFICATION-TYPE
       OBJECTS       {mdlSCardType, mdlSActivity}
       STATUS current
       DESCRIPTION     
       "This trap is sent when a card is removed."
       ::= { dacsMuxEvents 3 }

     sysAlrStatusTrap  NOTIFICATION-TYPE
       OBJECTS       { sysSAlrStatusAll, sysSAlrStatus }
       STATUS current
       DESCRIPTION     
       "This trap is sent upon any change in the value of any of 
        the variables."
       ::= { dacsMuxEvents 4 }
 

     sysStatusChangedTrap  NOTIFICATION-TYPE
       OBJECTS       {agnLed}
       STATUS current
       DESCRIPTION     
       "This trap is sent when Leds status is changed."
       ::= { dacsMuxEvents 5 }


     cnfgUpdateTrap  NOTIFICATION-TYPE
       STATUS current
       DESCRIPTION     
       "This trap is sent upon change of the active Configuration DB."  
       ::= { dacsMuxEvents 6 }
 

	sysRedundancyStatusTrap NOTIFICATION-TYPE
		OBJECTS  { sysDclRedundancyStatus }
		STATUS  current
		DESCRIPTION
		"The trap is sent upon change in Redundancy Status."
		::= { dacsMuxEvents 7 }

	sysRedundancyActiveCardTrap NOTIFICATION-TYPE
		OBJECTS  { sysDclOnline }
		STATUS  current
		DESCRIPTION
		"The trap is sent upon change of Active Main/CL Card."
		::= { dacsMuxEvents 8 }

	sysRedundancyActivePortTrap NOTIFICATION-TYPE
		OBJECTS  { sysCRdnOnline }
		STATUS  current
		DESCRIPTION
		"The trap is sent upon change of Active Port of Redundancy Group."
		::= { dacsMuxEvents 9 }


powerDeliveryFailure        NOTIFICATION-TYPE
	OBJECTS { alarmEventLogSourceName, alarmEventLogAlarmOrEventId, alarmEventLogDescription, 
     alarmEventLogSeverity, alarmEventLogDateAndTime, alarmEventReason, 
     entPhysicalAlias, mdlPsTestResult } 
      STATUS  current
      DESCRIPTION
      "This Trap indicates that a power supply failure exists in the device."   
      ::= { systemsEvents 73}



END
